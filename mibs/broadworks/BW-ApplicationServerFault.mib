-- File Name : BW-ApplicationServerFault.mib
BW-ApplicationServerFault DEFINITIONS ::= BEGIN
  IMPORTS
    MODULE-IDENTITY, NOTIFICATION-TYPE
      FROM SNMPv2-SMI
    common, faultFields, identifier, timeStamp, alarmName, systemName, severity, alarmState, component, subcomponent, problemText, recommendedActionsText
      FROM BroadworksFault;

  systemFaults MODULE-IDENTITY
    LAST-UPDATED  "200201220000Z"
    ORGANIZATION  "Broadsoft, Inc"
    CONTACT-INFO  "Broadsoft, Inc.
220 Perry Parkway
Gaithersburg, MD  20877
301-977-9440"
    DESCRIPTION
        "The defines the fault "
    REVISION    "200009191431Z"
    DESCRIPTION
        ""
    ::=  {  common  1  }

-- From the WebServer MIB...

  bwApplicationServerUnreachable  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 2501  }

  bwNetworkServerUnreachable  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 2502  }
    
  bwNetworkServerRequestError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 2503  }
    
  bwCMSConnectivityDown  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 2504  }
    
  bwCMSConnectivityUp  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 2505  }

  bwCMSDatabaseMismatch  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 2506  }

-- AS Faults...

  bwPMExecutionServerLaunched  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3501  }

  bwPMExecutionServerShutDown  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3502  }

  bwPMExecutionServerRestarted  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3503  }

  bwPMExecutionServerDeath  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3504  }

  bwPMProvisioningServerLaunched  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3505  }

  bwPMProvisioningServerShutDown  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3506  }

  bwPMProvisioningServerRestarted  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3507  }

  bwPMProvisioningServerDeath  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3508  }

  bwSipMessageParsingError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3509  }

  bwSipRegistrationFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3510  }

  bwSipUnexpectedMessage  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3511  }

  bwSipMaxRetriesExceeded  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3512  }

  bwSipRequestTimeOutReceived  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3513  }

  bwSipServiceUnavailableReceived  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3514  }

  bwSipServerTimeOutReceived  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3515  }

  bwSipAuthenticationFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3516  }

  bwAclViolation  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3517  }

  bwSipUnrecognisedDomainName  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3518  }

  bwSMTPPrimaryServerEmailMessageDeliveryError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3519  }

  bwSMTPConnectivityFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3520  }

  bwIMSRetrieveMessageError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3521  }

  bwIMSRetrieveMailBoxInfoError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3522  }

  bwIMSConnectionFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3523  }

  bwIMSCloseConnectionError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3524  }

  bwIMSUpdateMailBoxError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3525  }

  bwMediaServerNotResponding  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3526  }

  bwMssNetworkServerNotResponding  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3527  }

  bwMssNoResponse  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3528  }

  bwMGCPIOControllerUnknownReqIDInNotification  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3529  }

  bwMGCPMessageParsingError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3530  }

  bwMGCPCallAgentFailedMessageProcessing  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3531  }

  bwMGCPCallAgentMessageProcessing  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3532  }

  bwMGCPReTransmissionTimeout  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3533  }

  bwMGCPUnrecognisedDomainName  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3534  }

  bwMGCPUDPTransmitter  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3535  }

  bwAuditAbnormalCallTermination  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3536  }

  bwNSSynchronizationConnectivityFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3537  }

  bwNSSynchronizationFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3538  }

  bwNSLocationConnectivityFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3539  }

  bwNSLocationFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3540  }

  bwLicenseAuthenticationFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3541  }

--  bwLicenseHWViolation  Moved to BroadworksFault.mib

  bwLicenseAccntViolation  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3544  }

  bwLicenseUserServiceAccntViolation  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3545  }

  bwAddUserEvent  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3546  }

  bwDeleteUserEvent  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3547  }

  bwAddGroupEvent  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3548  }

  bwDeleteGroupEvent  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3549  }

  bwUserAddressChangeEvent  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3550  }

  bwGroupAddressChangeEvent  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3551  }

  bwEmergencyCallRoutingFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3552  }

  bwNetworkRoutingServiceRouteExhaustion  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3553  }

  bwCallPThreadAutoRestart  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3555  }

  bwForcedExitDueToHungThread  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3556  }

  bwOCPMissingCountryCode  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3557  }

  bwSystemDomainNameReset  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3558  }

  bwAccountingFTPConnectionError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3560  }

  bwCustomerOriginatedTrace  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3561  }

  bwMaliciousCallTrace  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3562  }

  bwLDAPConnectionError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3563  }

  bwLDAPConfigurationError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3564  }

  bwCallCapacityManagementaddCallID  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3565  }

  bwSMDIsessionRejected  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3566  }

  bwOCPMissingTransferNumber  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3567  }

  bwOCPMissingAuthorizationCode  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3568  }

  bwDeviceStatusIsOnline  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3569  }

  bwDeviceStatusIsUnavailable  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3570  }

  bwCPEDeviceConfigurationFileNotTransmitted  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3571  }

  bwCPEDeviceConfigurationDeviceReset  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3572  }

  bwCPEDeviceConfigurationFTPLogin  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3573  }

  bwSMDIInterfaceError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3574  }

  bwSMDIConfigurationError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3575  }

  bwSMDIOperationFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3576  }

  bwSMDIRouteExhaustion  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3577  }

  bwICBridgeCommunicationError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3578  }

  bwICBridgeResetError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3579  }

  bwIcPublicClusterFqdnNotConfigured  NOTIFICATION-TYPE
    OBJECTS     { identifier ,timeStamp ,alarmName ,systemName ,severity ,component ,subcomponent ,problemText ,recommendedActionsText }
    STATUS      obsolete
    DESCRIPTION
        "For the actual description, refer the BroadWorks FaultManagementGuide as it may contain variable data."
    ::=  {  systemFaults 3580  }

  bwLicenseFileExpiring  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3581  }

  bwLicenseFileExpired  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3582  }

  bwExternalAuthenticationUnknownUser  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3583  }

  bwSrvcPackMigrationTerminated  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3584  }

  bwSrvcPackMigrationCompletedWithErrors  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3585  }

  bwSrvcPackMigrationStoppedDueToErrors  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3586  }

  bwSrvcPackMigrationStoppedDueToTimeLimit  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3587  }

  bwSrvcPackMigrationStoppedBySysShutdown  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3588  }

  bwSrvcPackMigrationFoundUnfinishedTask  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3589  }

  bwSrvcPackMigrationLicenseViolation  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3590  }

  bwSrvcPackMigrationSpSrvcQuantityViolation  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3591  }

  bwSrvcPackMigrationSystemError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3592  }

  bwOverloadZoneTransition  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3593 }

  bwThreadDelayDetected  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3594  }

 bwSipTcpConnectionFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3595  }

  bwAccountingRadiusServerNotResponding  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3596  }

  bwAccountingRadiusServersNotConfigured  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3597  }

  bwMaximumFailedVoicePortalLoginAttempts  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3598  }

  bwASRDatabaseOutOfSync  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3599  }

  bwCallLogSOAPServerUnreachable  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3600  }

  bwCallLogRadiusServerUnreachable  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3601  }

  bwCallLogRadiusServersNotConfigured  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3602  }

  bwCPEDeviceConfigurationInfo  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3603  }

  bwUserExceededMaxSimultaneousCalls  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3604  }

  bwUserExceededMaxCallTime  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3605  }

  bwInvalidRingbackMediaFile  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3606  }

  bwOciReportingAclViolation  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3607  }

  bwOciReportingConnectionError  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3608  }

  bwPhysicalLocationOriginationBlocked NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3609  }

  bwCallLogRadiusQueueNotProgressing  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3610  }

  bwCallLogRadiusQueueFileDeleted NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3611  }

  bwConcurrentCallsExceeded NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3612  }

  bwENServerUnreachable NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3613  }

  bwENServerNumberInvalid NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3614  }

  bwOciReportingBackLogFileDeleted NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3615  }

  bwProvisioningValidationConnectionFailure NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3616  }

  bwXSOCICommunicationError NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3617  }

  bwCallOverloadZoneTransition NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3618  }

  bwNonCallOverloadZoneTransition NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3619  }

  bwUserExceededMaxSimultaneousVideoCalls NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3620  }

  bwMediaTypeNotSupported NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3621  }

  bwENTranslationFailed NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3622  }

  bwSOAPThreadNumberTooLow NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3623  }

  bwUserExceededMaxConcurrentRedirectedCalls NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3624  }

  bwUserExceededMaxFindMeFollowMeDepth NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3625  }

  bwUserExceededMaxRedirectionDepth NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3626  }

  bwUserExceededMaxFindMeFollowMeInvocations NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3627  }

  bwTrunkGroupCapacityExceeded NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3628  }

  bwTrunkGroupUnreachableDestination NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3629  }
    
  bwForwardDestinationLoop NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3630  }

  bwSmppConnectionLost NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3631 }

  bwSmppConnectionAttemptFailure  NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3632 }

  bwSmppRoutesExhausted NOTIFICATION-TYPE
    OBJECTS     { identifier ,timeStamp ,alarmName ,systemName ,alarmState ,severity ,component ,subcomponent ,problemText ,recommendedActionsText }
    STATUS      current
    DESCRIPTION
        "For the actual description, refer the BroadWorks FaultManagementGuide as it may contain variable data."
    ::= { systemFaults 3633 }

  bwExternalCustomRingbackServerFailure NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::=  {  systemFaults 3634  }

  bwCongestionManagementNeighborOverloaded NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3635 }

  bwCongestionManagementNeighborsInhibited NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3636 }

  bwShNoAvailableHosts   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3639 }

  bwShUserUnknownInHSS   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3640 }

  bwShUserUnknownInAS   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3641 }

  bwShGeneralErrorReceived   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3642 }

  bwShSystemRefreshInitiated   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3643 }

  bwShSystemRefreshTerminated   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3644 }

  bwDnsServerUnreachable   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3645 }

  bwDnsAllServersUnreachable   NOTIFICATION-TYPE
    OBJECTS     { identifier ,timeStamp ,alarmName ,systemName ,alarmState ,severity ,component ,subcomponent ,problemText ,recommendedActionsText }
    STATUS      current
    DESCRIPTION
        "For the actual description, refer the BroadWorks FaultManagementGuide as it may contain variable data."
    ::= { systemFaults 3646 }

  bwMobilityManagerUnreachable NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3637 }

  bwMobilityManagerError   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3638 }

  bwRemoteOfficeEmergencyCallBlocked   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3647 }

  bwEmergencyCallOriginated   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3648 }

  bwShInterfaceInitializationError   NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3649 }

  -- 3650 - 3653 Reserved - R15.0

  bwCPEDeviceConfigurationNumFilesExceeded NOTIFICATION-TYPE
    OBJECTS     { identifier ,timeStamp ,alarmName ,systemName ,severity ,component ,subcomponent ,problemText ,recommendedActionsText }
    STATUS      current
    DESCRIPTION
        "For the actual description, refer the BroadWorks FaultManagementGuide as it may contain variable data."
    ::= { systemFaults 3654 }

  bwCallCenterConnectionFailure NOTIFICATION-TYPE
    OBJECTS     { identifier, timeStamp, alarmName, systemName, severity, component, subcomponent, problemText, recommendedActionsText }
    STATUS      current
    DESCRIPTION
        "Connection between the Provisioning Server and the Execution Server for Call Center cannot be established."
    ::= { systemFaults 3661 }

  bwTrunkingLicensedCapacityExceeded NOTIFICATION-TYPE
    OBJECTS     { identifier, timeStamp, alarmName, systemName, severity, component, subcomponent, problemText, recommendedActionsText }
    STATUS      current
    DESCRIPTION
        "The Application Server blocked a business trunking call because no license units were available."
    ::= { systemFaults 3662 }

END
