-- -----------------------------------------------------------------------------
-- MIB NAME : rcProtocolManagementGroup
-- FILE NAME: raisecom-protocol-mib.my			
-- DATE     : 2011/7/25							
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2011/7/25, xiaoyingjie
-- This is the first formal version for universal MIB definition.
 
RAISECOM-PROTOCOL-MANAGEMENT-MIB DEFINITIONS ::= BEGIN
     
	IMPORTS
		MODULE-IDENTITY,
		OBJECT-TYPE,
		NOTIFICATION-TYPE,
		Integer32,
		IpAddress,
		Counter32,
		Unsigned32
			FROM SNMPv2-SMI
		InetAddress, InetAddressType
            FROM INET-ADDRESS-MIB  
		raisecomPonCommon
			FROM RAISECOM-PONSERIES-BASE-MIB;
			
	rcProtocolManagementGroup MODULE-IDENTITY
		LAST-UPDATED 	"201107200000Z"
		ORGANIZATION 	"rc TECH, Ltd."
		CONTACT-INFO 	"www.rc.com"
		DESCRIPTION  	
		    "The MIB module defining objects for version management  functions"
		::= { raisecomPonCommon  1}

--rcVersionMangngerGroup
	 
	 --version online upgtade protocol table  
	 
	 rcOnlineUpgradeProtocolTable    OBJECT-TYPE
        SYNTAX          SEQUENCE OF RcOnlineUpgradeProtocolEntry
        MAX-ACCESS      not-accessible
        STATUS          current
        DESCRIPTION     "version online upgtade protocol table"
    	::= { rcProtocolManagementGroup 1 }    
    
     rcOnlineUpgradeProtocolEntry  OBJECT-TYPE
		SYNTAX          RcOnlineUpgradeProtocolEntry
		MAX-ACCESS      not-accessible
        STATUS          current
		DESCRIPTION     "An entry in the rcOnlineUpgradeProtocolTable."
		INDEX { rcOnlineUpgradeProtocolType }
		::= { rcOnlineUpgradeProtocolTable 1 }
		
	RcOnlineUpgradeProtocolEntry ::=
		SEQUENCE { 
		rcOnlineUpgradeProtocolType					INTEGER,
		rcOnlineUpgradeProtocolServerAddress		InetAddress,
		rcOnlineUpgradeProtocolServerAddressType	InetAddressType,
		rcOnlineUpgradeProtocolUserName		        OCTET STRING (SIZE (1..40)),
		rcOnlineUpgradeProtocolUserPassord          OCTET STRING (SIZE (1..40))
		}		
    
	rcOnlineUpgradeProtocolType  OBJECT-TYPE
        SYNTAX 			INTEGER
        MAX-ACCESS 		not-accessible
        STATUS 			current
        DESCRIPTION		"The index of rcOnlineUpgradeProtocolTable. Protocol type"
        ::= { rcOnlineUpgradeProtocolEntry 1 }
        
   rcOnlineUpgradeProtocolServerAddress  	OBJECT-TYPE
        SYNTAX          InetAddress        
        MAX-ACCESS      read-create
        STATUS          current
        DESCRIPTION     "The server ip address "
    	::= { rcOnlineUpgradeProtocolEntry 2}   

	rcOnlineUpgradeProtocolServerAddressType   OBJECT-TYPE
        SYNTAX          InetAddressType        
        MAX-ACCESS      read-create
        STATUS          current
        DESCRIPTION     "The address type of the server ip address"
    	::= { rcOnlineUpgradeProtocolEntry 3 }   
   
    rcOnlineUpgradeProtocolUserName     OBJECT-TYPE
        SYNTAX          OCTET STRING  (SIZE (1..40))
        MAX-ACCESS      read-create
        STATUS          current
        DESCRIPTION     "The user name.The name of tftp protocol is null"
    	::= { rcOnlineUpgradeProtocolEntry 4 } 
    	
    rcOnlineUpgradeProtocolUserPassord     OBJECT-TYPE
        SYNTAX          OCTET STRING  (SIZE (1..40))
        MAX-ACCESS      read-create
        STATUS          current
        DESCRIPTION     "The password. The password of tftp protocol is null."
    	::= { rcOnlineUpgradeProtocolEntry 5 }   
    	
	END
