-- -----------------------------------------------------------------------------
-- MIB NAME : rcRuningConfigInterfaceTransfer
-- FILE NAME: raisecom-running-config-if-transfer-mib.my			
-- DATE     : 2013/5/21							
-- VERSION  : 1.00								
-- PURPOSE  : The MIB module defining objects for running config interface transfer
--            functions			
-- -----------------------------------------------------------------------------
-- MODIFICTION HISTORY:
-- -----------------------------------------------------------------------------
-- Version, Date, Author        
-- Description:								
--  [New Object]		
--  [Modification]
-- Notes: (Requested by who and which project)
--
-- Version 1.00, 2013/5/21, mayuanchao
-- This is the first formal version for universal MIB definition.
-----------------------------------------------------------------------------
--
-- RAISECOM base management objects
--            

RAISECOM-RUNNING-CONFIG-IF-INTERFACE-MIB DEFINITIONS ::= BEGIN

    IMPORTS
		raisecomPonCommon     FROM RAISECOM-PONSERIES-BASE-MIB
        RowStatus,TruthValue  FROM SNMPv2-TC
        EnableVar	          FROM SWITCH-TC  
        InterfaceIndex        FROM IF-MIB;


	rcRunningConfigInterfaceTransferGroup    MODULE-IDENTITY
		LAST-UPDATED 	"201305210000Z"
		ORGANIZATION 	"RAISECOM TECH, Ltd."
		CONTACT-INFO 	"www.raisecom.com"
		DESCRIPTION  	
		    "The MIB module defining objects for running config interface transfer functions."
		::= { raisecomPonCommon  15}        
		
    rcRunningConfigIfTransferTable OBJECT-TYPE
        SYNTAX SEQUENCE OF rcRunningConfigIfTransferEntry 
        ACCESS not-accessible
        STATUS current
        DESCRIPTION
           	"A list of rcRunningConfigIfTransfer entries."
           	::= { rcRunningConfigInterfaceTransferGroup 1 }

    rcRunningConfigIfTransferEntry OBJECT-TYPE
        SYNTAX rcRunningConfigIfTransferEntry 
        ACCESS not-accessible
        STATUS current
        DESCRIPTION
           	"The resources running config interface tranfer group infomation entry."
        INDEX { rcRunningConfigIfTransferIndex }
           	::= { rcRunningConfigIfTransferTable 1 }
	
	rcRunningConfigIfTransferEntry ::= SEQUENCE {
		rcRunningConfigIfTransferIndex     INTEGER,
        rcRunningConfigIfTransferSrcPort   InterfaceIndex,
        rcRunningConfigIfTransferDstPort   InterfaceIndex,   
        rcRunningConfigIfTransferClearSrc  INTEGER,
        rcRunningConfigIfTransferAction    TruthValue,
        rcRunningConfigIfTransferSate      INTEGER,
        rcRunningConfigIfTransferFailCause BITS,
        rcRunningConfigIfTransferRowStatus RowStatus
                }
        
    rcRunningConfigIfTransferIndex OBJECT-TYPE
        SYNTAX INTEGER(1..16)
        ACCESS not-accessible
        STATUS current
        DESCRIPTION
          	"The index of runnning config interface transfer."
          	::= { rcRunningConfigIfTransferEntry 1 } 
              	
    rcRunningConfigIfTransferSrcPort OBJECT-TYPE
    	SYNTAX InterfaceIndex
    	ACCESS read-create
    	STATUS current
    	DESCRIPTION
    		"The source interface of runnning config interface transfer."
    		::= { rcRunningConfigIfTransferEntry 2 }

    rcRunningConfigIfTransferDstPort OBJECT-TYPE
    	SYNTAX InterfaceIndex
    	ACCESS read-create
    	STATUS current
    	DESCRIPTION
    		"The destination interface of runnning config interface transfer."
    		::= { rcRunningConfigIfTransferEntry 3 }
   

    rcRunningConfigIfTransferClearSrc OBJECT-TYPE
        SYNTAX INTEGER{
        	reserve(1),
        	clear(2)
        	}
        ACCESS read-create
        STATUS current
        DESCRIPTION
           	"clear source running config or not, default not clear."
           	::= { rcRunningConfigIfTransferEntry 4 }
          	  
    rcRunningConfigIfTransferAction OBJECT-TYPE
        SYNTAX INTEGER{
        	go(1)
        	}
        ACCESS read-create
        STATUS current
        DESCRIPTION
           	"do running config transfer action."
           	::= { rcRunningConfigIfTransferEntry 5 } 
           	
	rcRunningConfigIfTransferSate OBJECT-TYPE
        SYNTAX INTEGER{
        	ready(1),
        	clearDst(2),
        	getSrc(3),
        	clearSrc(4),
        	setDst(5),
        	done(6)
        	}
        ACCESS read-only
        STATUS current
        DESCRIPTION
           	"The working state of running config interface transfer."
           	::= { rcRunningConfigIfTransferEntry 6 }   
           	
	rcRunningConfigIfTransferFailCause OBJECT-TYPE
        SYNTAX BITS{
        	noError(0),
        	unknown(1),
        	portSame(2),
        	portNotExist(3),
        	portTypeNotSame(4),
        	portCfgError(5)
        	}
        ACCESS read-only
        STATUS current
        DESCRIPTION
           	"The fail cause of running config interface transfer."
           	::= { rcRunningConfigIfTransferEntry 7 }    
           	
	rcRunningConfigIfTransferRowStatus OBJECT-TYPE
        SYNTAX RowStatus
        ACCESS read-create
        STATUS current
        DESCRIPTION
           	""
           	::= { rcRunningConfigIfTransferEntry 8 }
          	
END
