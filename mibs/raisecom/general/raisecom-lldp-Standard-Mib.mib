LLDP-STD-MIB DEFINITIONS ::= BEGIN

IMPORTS
    MODULE-IDENTITY, OBJECT-TYPE, Integer32, Counter32, NOTIFICATION-TYPE
        FROM SNMPv2-SMI
    TEXTUAL-CONVENTION, TimeStamp, TruthValue
        FROM SNMPv2-TC
    SnmpAdminString
        FROM SNMP-FRAMEWORK-MIB
    MODULE-COMPLIANCE, OBJECT-GROUP, NOTIFICATION-GROUP
        FROM SNMPv2-CONF
    TimeFilter, ZeroBasedCounter32
        FROM RMON2-MIB
    AddressFamilyNumbers
        FROM IANA-ADDRESS-FAMILY-NUMBERS-MIB     
    OltPortIndex	                    
        FROM RAISECOM-PONSERIES-TC 
    raisecomPonCommon           
        FROM RAISECOM-PONSERIES-BASE-MIB;
        
rcLldp 			 OBJECT IDENTIFIER ::= { raisecomPonCommon 10 }
        
rcLldpStandard MODULE-IDENTITY
    LAST-UPDATED "200505060000Z" -- May 06, 2005
    ORGANIZATION "IEEE 802.1 Working Group"
    CONTACT-INFO 
            "  WG-URL: http://grouper.ieee.org/groups/802/1/index.html
             WG-EMail: stds-802-1@ieee.org

              Contact: Paul Congdon
               Postal: Hewlett-Packard Company
                       8000 Foothills Blvd. 
                       Roseville, CA 95747
                       USA
                  Tel: +1-916-785-5753
               E-mail: paul_congdon@hp.com"
    DESCRIPTION
            "Management Information Base module for LLDP configuration,
            statistics, local system data and remote systems data
            components.

            Copyright (C) IEEE (2005).  This version of this MIB module
            is published as subclause 12.1 of IEEE Std 802.1AB-2005;
            see the standard itself for full legal notices."
    REVISION        "200505060000Z" -- May 06, 2005
    DESCRIPTION
            "Published as part of IEEE Std 802.1AB-2005 initial version."
   ::= { rcLldp 1 }

rclldpNotifications            OBJECT IDENTIFIER ::= { rcLldpStandard 0 }
rclldpObjects                  OBJECT IDENTIFIER ::= { rcLldpStandard 1 }
rclldpConformance              OBJECT IDENTIFIER ::= { rcLldpStandard 2 } 

--
-- rclldp MIB Objects
--

rclldpConfiguration            OBJECT IDENTIFIER ::= { rclldpObjects 1 }
rclldpStatistics               OBJECT IDENTIFIER ::= { rclldpObjects 2 }
rclldpLocalSystemData          OBJECT IDENTIFIER ::= { rclldpObjects 3 }
rclldpRemoteSystemsData        OBJECT IDENTIFIER ::= { rclldpObjects 4 }
rclldpExtensions               OBJECT IDENTIFIER ::= { rclldpObjects 5 }

-- 
-- ***********************************************************
-- 
-- Textual Conventions
-- 
-- ***********************************************************

LldpChassisIdSubtype ::= TEXTUAL-CONVENTION
    STATUS      current
    DESCRIPTION
            "This TC describes the source of a chassis identifier.

            The enumeration 'chassisComponent(1)' represents a chassis
            identifier based on the value of entPhysicalAlias object
            (defined in IETF RFC 2737) for a chassis component (i.e.,
            an entPhysicalClass value of 'chassis(3)').

            The enumeration 'interfaceAlias(2)' represents a chassis
            identifier based on the value of ifAlias object (defined in
            IETF RFC 2863) for an interface on the containing chassis.

            The enumeration 'portComponent(3)' represents a chassis
            identifier based on the value of entPhysicalAlias object
            (defined in IETF RFC 2737) for a port or backplane
            component (i.e., entPhysicalClass value of 'port(10)' or
            'backplane(4)'), within the containing chassis.

            The enumeration 'macAddress(4)' represents a chassis
            identifier based on the value of a unicast source address
            (encoded in network byte order and IEEE 802.3 canonical bit
            order), of a port on the containing chassis as defined in
            IEEE Std 802-2001.

            The enumeration 'networkAddress(5)' represents a chassis
            identifier based on a network address, associated with
            a particular chassis.  The encoded address is actually
            composed of two fields.  The first field is a single octet,
            representing the IANA AddressFamilyNumbers value for the
            specific address type, and the second field is the network
            address value.

            The enumeration 'interfaceName(6)' represents a chassis
            identifier based on the value of ifName object (defined in
            IETF RFC 2863) for an interface on the containing chassis.

            The enumeration 'local(7)' represents a chassis identifier
            based on a locally defined value."
    SYNTAX  INTEGER {
            chassisComponent(1),
            interfaceAlias(2),
            portComponent(3),
            macAddress(4),
            networkAddress(5),
            interfaceName(6),
            local(7)
    }

LldpChassisId ::= TEXTUAL-CONVENTION
    STATUS      current
    DESCRIPTION
            "This TC describes the format of a chassis identifier string.
            Objects of this type are always used with an associated
            LldpChassisIdSubtype object, which identifies the format of
            the particular LldpChassisId object instance.

            If the associated LldpChassisIdSubtype object has a value of
            'chassisComponent(1)', then the octet string identifies
            a particular instance of the entPhysicalAlias object
            (defined in IETF RFC 2737) for a chassis component (i.e.,
            an entPhysicalClass value of 'chassis(3)').

            If the associated LldpChassisIdSubtype object has a value
            of 'interfaceAlias(2)', then the octet string identifies
            a particular instance of the ifAlias object (defined in
            IETF RFC 2863) for an interface on the containing chassis.
            If the particular ifAlias object does not contain any values,
            another chassis identifier type should be used.

            If the associated LldpChassisIdSubtype object has a value
            of 'portComponent(3)', then the octet string identifies a
            particular instance of the entPhysicalAlias object (defined
            in IETF RFC 2737) for a port or backplane component within
            the containing chassis.

            If the associated LldpChassisIdSubtype object has a value of
            'macAddress(4)', then this string identifies a particular
            unicast source address (encoded in network byte order and
            IEEE 802.3 canonical bit order), of a port on the containing
            chassis as defined in IEEE Std 802-2001.

            If the associated LldpChassisIdSubtype object has a value of
            'networkAddress(5)', then this string identifies a particular
            network address, encoded in network byte order, associated
            with one or more ports on the containing chassis.  The first
            octet contains the IANA Address Family Numbers enumeration
            value for the specific address type, and octets 2 through
            N contain the network address value in network byte order.

            If the associated LldpChassisIdSubtype object has a value
            of 'interfaceName(6)', then the octet string identifies
            a particular instance of the ifName object (defined in
            IETF RFC 2863) for an interface on the containing chassis.
            If the particular ifName object does not contain any values,
            another chassis identifier type should be used.

            If the associated LldpChassisIdSubtype object has a value of
            'local(7)', then this string identifies a locally assigned
            Chassis ID."
    SYNTAX      OCTET STRING (SIZE (1..255))

LldpPortIdSubtype ::= TEXTUAL-CONVENTION
    STATUS      current
    DESCRIPTION
            "This TC describes the source of a particular type of port
            identifier used in the rclldp MIB.

            The enumeration 'interfaceAlias(1)' represents a port
            identifier based on the ifAlias MIB object, defined in IETF
            RFC 2863.

            The enumeration 'portComponent(2)' represents a port
            identifier based on the value of entPhysicalAlias (defined in
            IETF RFC 2737) for a port component (i.e., entPhysicalClass
            value of 'port(10)'), within the containing chassis.

            The enumeration 'macAddress(3)' represents a port identifier
            based on a unicast source address (encoded in network
            byte order and IEEE 802.3 canonical bit order), which has
            been detected by the agent and associated with a particular
            port (IEEE Std 802-2001).

            The enumeration 'networkAddress(4)' represents a port
            identifier based on a network address, detected by the agent
            and associated with a particular port.

            The enumeration 'interfaceName(5)' represents a port
            identifier based on the ifName MIB object, defined in IETF
            RFC 2863.

            The enumeration 'agentCircuitId(6)' represents a port
            identifier based on the agent-local identifier of the circuit
            (defined in RFC 3046), detected by the agent and associated
            with a particular port.

            The enumeration 'local(7)' represents a port identifier
            based on a value locally assigned."

    SYNTAX  INTEGER {
            interfaceAlias(1),
            portComponent(2),
            macAddress(3),
            networkAddress(4),
            interfaceName(5),
            agentCircuitId(6),
            local(7)
    }

LldpPortId ::= TEXTUAL-CONVENTION
    STATUS      current
    DESCRIPTION
            "This TC describes the format of a port identifier string.
            Objects of this type are always used with an associated
            LldpPortIdSubtype object, which identifies the format of the
            particular LldpPortId object instance.

            If the associated LldpPortIdSubtype object has a value of
            'interfaceAlias(1)', then the octet string identifies a
            particular instance of the ifAlias object (defined in IETF
            RFC 2863).  If the particular ifAlias object does not contain
            any values, another port identifier type should be used.

            If the associated LldpPortIdSubtype object has a value of
            'portComponent(2)', then the octet string identifies a
            particular instance of the entPhysicalAlias object (defined
            in IETF RFC 2737) for a port or backplane component.

            If the associated LldpPortIdSubtype object has a value of
            'macAddress(3)', then this string identifies a particular
            unicast source address (encoded in network byte order
            and IEEE 802.3 canonical bit order) associated with the port
            (IEEE Std 802-2001).

            If the associated LldpPortIdSubtype object has a value of
            'networkAddress(4)', then this string identifies a network
            address associated with the port.  The first octet contains
            the IANA AddressFamilyNumbers enumeration value for the
            specific address type, and octets 2 through N contain the
            networkAddress address value in network byte order.

            If the associated LldpPortIdSubtype object has a value of
            'interfaceName(5)', then the octet string identifies a
            particular instance of the ifName object (defined in IETF
            RFC 2863).  If the particular ifName object does not contain
            any values, another port identifier type should be used.

            If the associated LldpPortIdSubtype object has a value of
            'agentCircuitId(6)', then this string identifies a agent-local
            identifier of the circuit (defined in RFC 3046).

            If the associated LldpPortIdSubtype object has a value of
            'local(7)', then this string identifies a locally
            assigned port ID."
    SYNTAX      OCTET STRING (SIZE (1..255))

LldpManAddrIfSubtype ::= TEXTUAL-CONVENTION
    STATUS      current
    DESCRIPTION
            "This TC describes the basis of a particular type of
            interface associated with the management address.

            The enumeration 'unknown(1)' represents the case where the
            interface is not known.

            The enumeration 'ifIndex(2)' represents interface identifier
            based on the ifIndex MIB object.

            The enumeration 'systemPortNumber(3)' represents interface
            identifier based on the system port numbering convention."
    REFERENCE 
            "IEEE 802.1AB-2005 9.5.9.5"
            
    SYNTAX  INTEGER {
            unknown(1),
            ifIndex(2),
            systemPortNumber(3)
    }

LldpManAddress ::= TEXTUAL-CONVENTION
    STATUS      current
    DESCRIPTION
            "The value of a management address associated with the rclldp
            agent that may be used to reach higher layer entities to
            assist discovery by network management.

            It should be noted that appropriate security credentials,
            such as SNMP engineId, may be required to access the rclldp
            agent using a management address.  These necessary credentials
            should be known by the network management and the objects
            associated with the credentials are not included in the
            rclldp agent."
     SYNTAX      OCTET STRING (SIZE (1..31))

LldpSystemCapabilitiesMap ::= TEXTUAL-CONVENTION
    STATUS      current
    DESCRIPTION
            "This TC describes the system capabilities.

            The bit 'other(0)' indicates that the system has capabilities
            other than those listed below.

            The bit 'repeater(1)' indicates that the system has repeater
            capability.

            The bit 'bridge(2)' indicates that the system has bridge
            capability.

            The bit 'wlanAccessPoint(3)' indicates that the system has 
            WLAN access point capability.

            The bit 'router(4)' indicates that the system has router
            capability.

            The bit 'telephone(5)' indicates that the system has telephone
            capability.

            The bit 'docsisCableDevice(6)' indicates that the system has
            DOCSIS Cable Device capability (IETF RFC 2669 & 2670).

            The bit 'stationOnly(7)' indicates that the system has only
            station capability and nothing else."
    SYNTAX  BITS {
            other(0),
            repeater(1),
            bridge(2),
            wlanAccessPoint(3),
            router(4),
            telephone(5),
            docsisCableDevice(6),
            stationOnly(7)
    }

LldpPortNumber ::= TEXTUAL-CONVENTION
    DISPLAY-HINT "d"
    STATUS     current 
    DESCRIPTION
            "Each port contained in the chassis (that is known to the
            rclldp agent) is uniquely identified by a port number.

            A port number has no mandatory relationship to an
            InterfaceIndex object (of the interfaces MIB, IETF RFC 2863).
            If the rclldp agent is a IEEE 802.1D, IEEE 802.1Q bridge, the
            LldpPortNumber will have the same value as the dot1dBasePort
            object (defined in IETF RFC 1493) associated corresponding
            bridge port.  If the system hosting rclldp agent is not an
            IEEE 802.1D or an IEEE 802.1Q bridge, the LldpPortNumber
            will have the same value as the corresponding interface's
            InterfaceIndex object.

            Port numbers should be in the range of 1 and 4096 since a
            particular port is also represented by the corresponding
            port number bit in lldpPortList."
    SYNTAX 	Integer32(1..4096)

LldpPortList ::= TEXTUAL-CONVENTION
    STATUS      current
    DESCRIPTION
            "Each octet within this value specifies a set of eight ports,
            with the first octet specifying ports 1 through 8, the second
            octet specifying ports 9 through 16, etc.  Within each octet,
            the most significant bit represents the lowest numbered port,
            and the least significant bit represents the highest numbered
            port.  Thus, each port of the system is represented by a
            single bit within the value of this object.  If that bit has
            a value of '1' then that port is included in the set of ports;
            the port is not included if its bit has a value of '0'."
    REFERENCE 
            "IETF RFC 2674 section 5"
    SYNTAX  OCTET STRING(SIZE(0..512))

-- 
-- ***********************************************************
-- 
--                  L L D P    C O N F I G 
-- 
-- *********************************************************** 
--

rclldpMessageTxInterval OBJECT-TYPE
    SYNTAX      Integer32(5..32768)
    UNITS       "seconds"
    MAX-ACCESS  read-write
    STATUS      current
    DESCRIPTION
            "The interval at which rclldp frames are transmitted on
            behalf of this rclldp agent.

            The default value for rclldpMessageTxInterval object is
            30 seconds.

            The value of this object must be restored from non-volatile
            storage after a re-initialization of the management system."
    REFERENCE 
            "IEEE 802.1AB-2005 10.5.3.3"
    DEFVAL     { 30 }
    ::= { rclldpConfiguration 1 }

rclldpMessageTxHoldMultiplier OBJECT-TYPE
    SYNTAX      Integer32(2..10)
    MAX-ACCESS  read-write
    STATUS      current
    DESCRIPTION
            "The time-to-live value expressed as a multiple of the
            rclldpMessageTxInterval object.  The actual time-to-live value
            used in rclldp frames, transmitted on behalf of this rclldp agent,
            can be expressed by the following formula: TTL = min(65535,
            (rclldpMessageTxInterval * rclldpMessageTxHoldMultiplier)) For
            example, if the value of rclldpMessageTxInterval is '30', and
            the value of rclldpMessageTxHoldMultiplier is '4', then the
            value '120' is encoded in the TTL field in the rclldp header.

            The default value for rclldpMessageTxHoldMultiplier object is 4.

            The value of this object must be restored from non-volatile
            storage after a re-initialization of the management system."
    REFERENCE 
            "IEEE 802.1AB-2005 10.5.3.3"
    DEFVAL      { 4 }    
    ::= { rclldpConfiguration 2 }

rclldpReinitDelay OBJECT-TYPE
    SYNTAX      Integer32(1..10)
    UNITS       "seconds"
    MAX-ACCESS  read-write
    STATUS      current
    DESCRIPTION
            "The rclldpReinitDelay indicates the delay (in units of
            seconds) from when rclldpPortConfigAdminStatus object of a
            particular port becomes 'disabled' until re-initialization
            will be attempted.

            The default value for rclldpReintDelay object is two seconds.

            The value of this object must be restored from non-volatile
            storage after a re-initialization of the management system."
    REFERENCE 
            "IEEE 802.1AB-2005 10.5.3.3"
    DEFVAL      { 2 }    
    ::= { rclldpConfiguration 3 }

rclldpTxDelay OBJECT-TYPE
    SYNTAX      Integer32(1..8192)
    UNITS       "seconds"
    MAX-ACCESS  read-write
    STATUS      current
    DESCRIPTION
            "The rclldpTxDelay indicates the delay (in units
            of seconds) between successive rclldp frame transmissions 
            initiated by value/status changes in the rclldp local systems
            MIB.  The recommended value for the rclldpTxDelay is set by the
            following  formula:

               1 <= rclldpTxDelay <= (0.25 * rclldpMessageTxInterval)

            The default value for rclldpTxDelay object is two seconds.

            The value of this object must be restored from non-volatile
            storage after a re-initialization of the management system."
    REFERENCE 
            "IEEE 802.1AB-2005 10.5.3.3"
    DEFVAL      { 2 }    
    ::= { rclldpConfiguration 4 }

rclldpNotificationInterval OBJECT-TYPE
    SYNTAX      Integer32(5..3600)
    UNITS       "seconds"
    MAX-ACCESS  read-write
    STATUS      current
    DESCRIPTION
            "This object controls the transmission of rclldp notifications.

            the agent must not generate more than one rclldpRemTablesChange
            notification-event in the indicated period, where a
            'notification-event' is the transmission of a single
            notification PDU type to a list of notification destinations.
            If additional changes in rclldpRemoteSystemsData object
            groups occur within the indicated throttling period,
            then these trap- events must be suppressed by the
            agent. An NMS should periodically check the value of
            rclldpStatsRemTableLastChangeTime to detect any missed
            rclldpRemTablesChange notification-events, e.g. due to
            throttling or transmission loss.

            If notification transmission is enabled for particular ports,
            the suggested default throttling period is 5 seconds.

            The value of this object must be restored from non-volatile
            storage after a re-initialization of the management system."
    DEFVAL { 5 }
    ::= { rclldpConfiguration 5 }

--
-- rclldpPortConfigTable: rclldp configuration on a per port basis
--

rclldpPortConfigTable   OBJECT-TYPE
    SYNTAX      SEQUENCE OF rclldpPortConfigEntry
    MAX-ACCESS  not-accessible
    STATUS      current
    DESCRIPTION
            "The table that controls rclldp frame transmission on individual
            ports."
    ::= { rclldpConfiguration 6 }

rclldpPortConfigEntry   OBJECT-TYPE
    SYNTAX      rclldpPortConfigEntry
    MAX-ACCESS  not-accessible
    STATUS      current
    DESCRIPTION
            "rclldp configuration information for a particular port.
            This configuration parameter controls the transmission and
            the reception of rclldp frames on those ports whose rows are
            created in this table."
     INDEX  { rclldpPortConfigPortNum }
    ::= { rclldpPortConfigTable 1 }

rclldpPortConfigEntry ::= SEQUENCE {
      rclldpPortConfigPortNum            LldpPortNumber,
      rclldpPortConfigAdminStatus        INTEGER,
      rclldpPortConfigNotificationEnable TruthValue,
      rclldpPortConfigTLVsTxEnable       BITS }

rclldpPortConfigPortNum   OBJECT-TYPE
    SYNTAX      LldpPortNumber 
    MAX-ACCESS  not-accessible
    STATUS      current
    DESCRIPTION
            "The index value used to identify the port component
            (contained in the local chassis with the rclldp agent)
            associated with this entry.

            The value of this object is used as a port index to the
            rclldpPortConfigTable."
    ::= { rclldpPortConfigEntry 1 }

rclldpPortConfigAdminStatus  OBJECT-TYPE 
    SYNTAX INTEGER { 
       txOnly(1), 
       rxOnly(2),
       txAndRx(3),
       disabled(4)
    }
    MAX-ACCESS read-only 
    STATUS     current 
    DESCRIPTION 
            "The administratively desired status of the local rclldp agent.

            If the associated rclldpPortConfigAdminStatus object has a
            value of 'txOnly(1)', then rclldp agent will transmit rclldp
            frames on this port and it will not store any information
            about the remote systems connected.
         
            If the associated rclldpPortConfigAdminStatus object has a
            value of 'rxOnly(2)', then the rclldp agent will receive,
            but it will not transmit rclldp frames on this port.

            If the associated rclldpPortConfigAdminStatus object has a
            value of 'txAndRx(3)', then the rclldp agent will transmit
            and receive rclldp frames on this port.

            If the associated rclldpPortConfigAdminStatus object has a
            value of 'disabled(4)', then rclldp agent will not transmit or
            receive rclldp frames on this port.  If there is remote systems
            information which is received on this port and stored in
            other tables, before the port's rclldpPortConfigAdminStatus
            becomes disabled, then the information will naturally age out."
    REFERENCE 
            "IEEE 802.1AB-2005 10.5.1"
    DEFVAL  { txAndRx }    
   ::= { rclldpPortConfigEntry 2 } 

rclldpPortConfigNotificationEnable OBJECT-TYPE 
    SYNTAX     TruthValue
    MAX-ACCESS read-only 
    STATUS     current 
    DESCRIPTION 
            "The rclldpPortConfigNotificationEnable controls, on a per
            port basis,  whether or not notifications from the agent
            are enabled. The value true(1) means that notifications are
            enabled; the value false(2) means that they are not."
    DEFVAL  { false }    
   ::= { rclldpPortConfigEntry 3 } 

rclldpPortConfigTLVsTxEnable OBJECT-TYPE
    SYNTAX      BITS {
            portDesc(0),
            sysName(1),
            sysDesc(2),
            sysCap(3)
    }
    MAX-ACCESS  read-only
    STATUS      current
    DESCRIPTION
            "The rclldpPortConfigTLVsTxEnable, defined as a bitmap,
            includes the basic set of rclldp TLVs whose transmission is
            allowed on the local rclldp agent by the network management.
            Each bit in the bitmap corresponds to a TLV type associated
            with a specific optional TLV.

            It should be noted that the organizationally-specific TLVs
            are excluded from the rclldpTLVsTxEnable bitmap.
            
            rclldp Organization Specific Information Extension MIBs should
            have similar configuration object to control transmission
            of their organizationally defined TLVs.

            The bit 'portDesc(0)' indicates that rclldp agent should
            transmit 'Port Description TLV'.

            The bit 'sysName(1)' indicates that rclldp agent should transmit
            'System Name TLV'.

            The bit 'sysDesc(2)' indicates that rclldp agent should transmit
            'System Description TLV'.

            The bit 'sysCap(3)' indicates that rclldp agent should transmit
            'System Capabilities TLV'.

            There is no bit reserved for the management address TLV type
            since transmission of management address TLVs are controlled
            by another object, rclldpConfigManAddrTable.

            The default value for rclldpPortConfigTLVsTxEnable object is
            empty set, which means no enumerated values are set.

            The value of this object must be restored from non-volatile
            storage after a re-initialization of the management system."
    REFERENCE 
            "IEEE 802.1AB-2005 10.2.1.1"
    DEFVAL  { { } }
    ::= { rclldpPortConfigEntry 4 } 


--
-- rclldpManAddrConfigTxPortsTable : selection of management addresses
--                                 to be transmitted on a specified set
--                                 of ports.
-- 

rclldpConfigManAddrTable OBJECT-TYPE
    SYNTAX      SEQUENCE OF rclldpConfigManAddrEntry
    MAX-ACCESS  not-accessible
    STATUS      current
    DESCRIPTION
            "The table that controls selection of rclldp management address
            TLV instances to be transmitted on individual ports."
    ::= { rclldpConfiguration 7 }

rclldpConfigManAddrEntry  OBJECT-TYPE
    SYNTAX      rclldpConfigManAddrEntry
    MAX-ACCESS  not-accessible
    STATUS      current
    DESCRIPTION
            "rclldp configuration information that specifies the set
            of ports (represented as a PortList) on which the local
            system management address instance will be transmitted.

            This configuration object augments the rclldpLocManAddrEntry,
            therefore it is only present along with the management
            address instance contained in the associated
            rclldpLocManAddrEntry entry.

            Each active rclldpConfigManAddrEntry must be restored from
            non-volatile and re-created (along with the corresponding
            rclldpLocManAddrEntry) after a re-initialization of the
            management system."
    AUGMENTS { rclldpLocManAddrEntry }
    ::= { rclldpConfigManAddrTable 1 }

rclldpConfigManAddrEntry  ::= SEQUENCE {
    rclldpConfigManAddrPortsTxEnable LldpPortList
}

rclldpConfigManAddrPortsTxEnable  OBJECT-TYPE
    SYNTAX        LldpPortList
    MAX-ACCESS    read-only
    STATUS        current
    DESCRIPTION
            "A set of ports that are identified by a PortList, in which
            each port is represented as a bit.  The corresponding local
            system management address instance will be transmitted on the
            member ports of the rclldpManAddrPortsTxEnable.  

            The default value for rclldpConfigManAddrPortsTxEnable object
            is empty binary string, which means no ports are specified
            for advertising indicated management address instance."
    REFERENCE 
            "IEEE 802.1AB-2005 10.2.1.1"
    DEFVAL  { ''H }     -- empty binary string
    ::= { rclldpConfigManAddrEntry 1 }


--
--  *********************************************************** 
--
--                   L L D P    S T A T S 
--
--  *********************************************************** 
--
-- rclldp Stats Group

rclldpStatsRemTablesLastChangeTime OBJECT-TYPE
    SYNTAX      TimeStamp
    MAX-ACCESS  read-only
    STATUS      current
    DESCRIPTION
            "The value of sysUpTime object (defined in IETF RFC 3418)
            at the time an entry is created, modified, or deleted in the
            in tables associated with the rclldpRemoteSystemsData objects
            and all rclldp extension objects associated with remote systems.

            An NMS can use this object to reduce polling of the
            rclldpRemoteSystemsData objects."
    ::= { rclldpStatistics 1 }

rclldpStatsRemTablesInserts OBJECT-TYPE
    SYNTAX      ZeroBasedCounter32
    UNITS       "table entries"
    MAX-ACCESS  read-only
    STATUS      current
    DESCRIPTION
            "The number of times the complete set of information
            advertised by a particular MSAP has been inserted into tables
            contained in rclldpRemoteSystemsData and rclldpExtensions objects.

            The complete set of information received from a particular
            MSAP should be inserted into related tables.  If partial
            information cannot be inserted for a reason such as lack
            of resources, all of the complete set of information should
            be removed.

            This counter should be incremented only once after the
            complete set of information is successfully recorded
            in all related tables.  Any failures during inserting
            information set which result in deletion of previously
            inserted information should not trigger any changes in
            rclldpStatsRemTablesInserts since the insert is not completed
            yet or or in rclldpStatsRemTablesDeletes, since the deletion
            would only be a partial deletion. If the failure was the
            result of lack of resources, the rclldpStatsRemTablesDrops
            counter should be incremented once."
    ::= { rclldpStatistics 2 }

rclldpStatsRemTablesDeletes   OBJECT-TYPE
    SYNTAX      ZeroBasedCounter32
    UNITS       "table entries"
    MAX-ACCESS  read-only
    STATUS      current

    DESCRIPTION
            "The number of times the complete set of information
            advertised by a particular MSAP has been deleted from
            tables contained in rclldpRemoteSystemsData and rclldpExtensions
            objects.

            This counter should be incremented only once when the
            complete set of information is completely deleted from all
            related tables.  Partial deletions, such as deletion of
            rows associated with a particular MSAP from some tables,
            but not from all tables are not allowed, thus should not
            change the value of this counter."
    ::= { rclldpStatistics 3 }

rclldpStatsRemTablesDrops  OBJECT-TYPE
    SYNTAX      ZeroBasedCounter32
    UNITS       "table entries"
    MAX-ACCESS  read-only

    STATUS      current
    DESCRIPTION
            "The number of times the complete set of information
            advertised by a particular MSAP could not be entered into
            tables contained in rclldpRemoteSystemsData and rclldpExtensions
            objects because of insufficient resources."
    ::= { rclldpStatistics 4 }

rclldpStatsRemTablesAgeouts   OBJECT-TYPE
    SYNTAX      ZeroBasedCounter32
    MAX-ACCESS  read-only
    STATUS      current
    DESCRIPTION
            "The number of times the complete set of information
            advertised by a particular MSAP has been deleted from tables
            contained in rclldpRemoteSystemsData and rclldpExtensions objects
            because the information timeliness interval has expired.

            This counter should be incremented only once when the complete
            set of information is completely invalidated (aged out)
            from all related tables.  Partial aging, similar to deletion
            case, is not allowed, and thus, should not change the value
            of this counter."
    ::= { rclldpStatistics 5 }

--
-- TX statistics
--

rclldpStatsTxPortTable  OBJECT-TYPE
    SYNTAX      SEQUENCE OF rclldpStatsTxPortEntry
    MAX-ACCESS  not-accessible
    STATUS      current
    DESCRIPTION 
            "A table containing rclldp transmission statistics for
            individual ports.  Entries are not required to exist in
            this table while the rclldpPortConfigEntry object is equal to
            'disabled(4)'."
    ::= { rclldpStatistics 6 } 

rclldpStatsTxPortEntry   OBJECT-TYPE
     SYNTAX      rclldpStatsTxPortEntry
     MAX-ACCESS  not-accessible
     STATUS      current
     DESCRIPTION
             "rclldp frame transmission statistics for a particular port.  
             The port must be contained in the same chassis as the
             rclldp agent.
            
             All counter values in a particular entry shall be
             maintained on a continuing basis and shall not be deleted
             upon expiration of rxInfoTTL timing counters in the rclldp
             remote systems MIB of the receipt of a shutdown frame from
             a remote rclldp agent.

             All statistical counters associated with a particular
             port on the local rclldp agent become frozen whenever the
             adminStatus is disabled for the same port."
     INDEX  { rclldpStatsTxPortNum }
     ::= { rclldpStatsTxPortTable 1 } 

rclldpStatsTxPortEntry ::= SEQUENCE {      
      rclldpStatsTxPortNum                 LldpPortNumber,
      rclldpStatsTxPortFramesTotal         Counter32
}

rclldpStatsTxPortNum   OBJECT-TYPE
    SYNTAX      LldpPortNumber 
    MAX-ACCESS  not-accessible
    STATUS      current
    DESCRIPTION
            "The index value used to identify the port component
            (contained in the local chassis with the rclldp agent)
            associated with this entry.

            The value of this object is used as a port index to the
            rclldpStatsTable."
    ::= { rclldpStatsTxPortEntry 1 } 

rclldpStatsTxPortFramesTotal  OBJECT-TYPE
    SYNTAX        Counter32
    MAX-ACCESS    read-only
    STATUS        current
    DESCRIPTION
            "The number of rclldp frames transmitted by this rclldp agent
            on the indicated port."
    REFERENCE 
            "IEEE 802.1AB-2005 10.5.2.1"
    ::= { rclldpStatsTxPortEntry 2 }

--
-- RX statistics
--

rclldpStatsRxPortTable  OBJECT-TYPE
    SYNTAX      SEQUENCE OF rclldpRxStatsPortEntry
    MAX-ACCESS  not-accessible
    STATUS      current
    DESCRIPTION 
            "A table containing rclldp reception statistics for individual
            ports.  Entries are not required to exist in this table while
            the rclldpPortConfigEntry object is equal to 'disabled(4)'."
    ::= { rclldpStatistics 7 } 

rclldpStatsRxPortEntry   OBJECT-TYPE
     SYNTAX      rclldpRxStatsPortEntry
     MAX-ACCESS  not-accessible
     STATUS      current
     DESCRIPTION
             "rclldp frame reception statistics for a particular port.
             The port must be contained in the same chassis as the
             rclldp agent.
            
             All counter values in a particular entry shall be
             maintained on a continuing basis and shall not be deleted
             upon expiration of rxInfoTTL timing counters in the rclldp
             remote systems MIB of the receipt of a shutdown frame from
             a remote rclldp agent.

             All statistical counters associated with a particular
             port on the local rclldp agent become frozen whenever the
             adminStatus is disabled for the same port."
     INDEX  { rclldpStatsRxPortNum }
     ::= { rclldpStatsRxPortTable 1 } 

rclldpRxStatsPortEntry ::= SEQUENCE {      
      rclldpStatsRxPortNum                   LldpPortNumber,
      rclldpStatsRxPortFramesDiscardedTotal  Counter32,
      rclldpStatsRxPortFramesErrors          Counter32,
      rclldpStatsRxPortFramesTotal           Counter32,
      rclldpStatsRxPortTLVsDiscardedTotal    Counter32,
      rclldpStatsRxPortTLVsUnrecognizedTotal Counter32,
      rclldpStatsRxPortAgeoutsTotal          ZeroBasedCounter32
}

rclldpStatsRxPortNum   OBJECT-TYPE
    SYNTAX      LldpPortNumber 
    MAX-ACCESS  not-accessible
    STATUS      current
    DESCRIPTION
            "The index value used to identify the port component
            (contained in the local chassis with the rclldp agent)
            associated with this entry.

            The value of this object is used as a port index to the
            rclldpStatsTable."
    ::= { rclldpStatsRxPortEntry 1 } 

rclldpStatsRxPortFramesDiscardedTotal OBJECT-TYPE 
    SYNTAX        Counter32
    MAX-ACCESS read-only
    STATUS     current 
    DESCRIPTION 
            "The number of rclldp frames received by this rclldp agent on
            the indicated port, and then discarded for any reason.
            This counter can provide an indication that rclldp header
            formating problems may exist with the local rclldp agent in
            the sending system or that rclldpDU validation problems may
            exist with the local rclldp agent in the receiving system."
   REFERENCE 
            "IEEE 802.1AB-2005 10.5.2.2"
   ::= { rclldpStatsRxPortEntry 2 } 

rclldpStatsRxPortFramesErrors  OBJECT-TYPE
    SYNTAX        Counter32
    MAX-ACCESS    read-only
    STATUS        current
    DESCRIPTION
            "The number of invalid rclldp frames received by this rclldp
            agent on the indicated port, while this rclldp agent is enabled."
    REFERENCE 
            "IEEE 802.1AB-2005 10.5.2.2"
    ::= { rclldpStatsRxPortEntry 3 }

rclldpStatsRxPortFramesTotal OBJECT-TYPE
    SYNTAX        Counter32
    MAX-ACCESS    read-only
    STATUS        current
    DESCRIPTION
            "The number of valid rclldp frames received by this rclldp agent
            on the indicated port, while this rclldp agent is enabled."
    REFERENCE 
            "IEEE 802.1AB-2005 10.5.2.2"
    ::= { rclldpStatsRxPortEntry 4 }

rclldpStatsRxPortTLVsDiscardedTotal OBJECT-TYPE
    SYNTAX        Counter32
    MAX-ACCESS    read-only
    STATUS        current
    DESCRIPTION
            "The number of rclldp TLVs discarded for any reason by this rclldp
            agent on the indicated port."
    REFERENCE 
            "IEEE 802.1AB-2005 10.5.2.2"
    ::= { rclldpStatsRxPortEntry 5 }

rclldpStatsRxPortTLVsUnrecognizedTotal  OBJECT-TYPE
    SYNTAX        Counter32
    MAX-ACCESS    read-only
    STATUS        current
    DESCRIPTION
            "The number of rclldp TLVs received on the given port that
            are not recognized by this rclldp agent on the indicated port.
            
            An unrecognized TLV is referred to as the TLV whose type value
            is in the range of reserved TLV types (000 1001 - 111 1110)
            in Table 9.1 of IEEE Std 802.1AB-2005.  An unrecognized
            TLV may be a basic management TLV from a later rclldp version."
    REFERENCE 
            "IEEE 802.1AB-2005 10.5.2.2"
    ::= { rclldpStatsRxPortEntry 6 }

rclldpStatsRxPortAgeoutsTotal   OBJECT-TYPE
    SYNTAX      ZeroBasedCounter32
    MAX-ACCESS  read-only
    STATUS      current
    DESCRIPTION
            "The counter that represents the number of age-outs that
            occurred on a given port.  An age-out is the number of
            times the complete set of information advertised by a
            particular MSAP has been deleted from tables contained in
            rclldpRemoteSystemsData and rclldpExtensions objects because
            the information timeliness interval has expired.

            This counter is similar to rclldpStatsRemTablesAgeouts, except
            that the counter is on a per port basis.  This enables NMS to
            poll tables associated with the rclldpRemoteSystemsData objects
            and all rclldp extension objects associated with remote systems
            on the indicated port only.

            This counter should be set to zero during agent initialization
            and its value should not be saved in non-volatile storage.
            When a port's admin status changes from 'disabled' to
            'rxOnly', 'txOnly' or 'txAndRx', the counter associated with
            the same port should reset to 0.  The agent should also flush
            all remote system information associated with the same port.

            This counter should be incremented only once when the
            complete set of information is invalidated (aged out) from
            all related tables on a particular port.  Partial aging
            is not allowed, and thus, should not change the value of
            this counter."
    REFERENCE 
            "IEEE 802.1AB-2005 10.5.2.2"
    ::= { rclldpStatsRxPortEntry 7 }

--  ***********************************************************
--
--          L O C A L    S Y S T E M    D A T A
--
--  ***********************************************************

rclldpLocChassisIdSubtype  OBJECT-TYPE
    SYNTAX      LldpChassisIdSubtype
    MAX-ACCESS  read-only
    STATUS      current
    DESCRIPTION
            "The type of encoding used to identify the chassis
            associated with the local system."
    REFERENCE 
            "IEEE 802.1AB-2005 9.5.2.2"
    ::= { rclldpLocalSystemData 1 }

rclldpLocChassisId  OBJECT-TYPE
    SYNTAX      LldpChassisId
    MAX-ACCESS  read-only
    STATUS      current
    DESCRIPTION
            "The string value used to identify the chassis component
            associated with the local system."
    REFERENCE 
            "IEEE 802.1AB-2005 9.5.2.3"
    ::= { rclldpLocalSystemData 2 }

rclldpLocSysName  OBJECT-TYPE
    SYNTAX      SnmpAdminString (SIZE(0..255))
    MAX-ACCESS  read-only
    STATUS      current
    DESCRIPTION
            "The string value used to identify the system name of the
            local system.  If the local agent supports IETF RFC 3418,
            rclldpLocSysName object should have the same value of sysName
            object."
    REFERENCE 
            "IEEE 802.1AB-2005 9.5.6.2"
    ::= { rclldpLocalSystemData 3 }

rclldpLocSysDesc  OBJECT-TYPE
    SYNTAX      SnmpAdminString (SIZE(0..255))
    MAX-ACCESS  read-only
    STATUS      current
    DESCRIPTION
            "The string value used to identify the system description
            of the local system.  If the local agent supports IETF RFC 3418,
            rclldpLocSysDesc object should have the same value of sysDesc
            object."
    REFERENCE 
            "IEEE 802.1AB-2005 9.5.7.2"
    ::= { rclldpLocalSystemData 4 }

rclldpLocSysCapSupported OBJECT-TYPE
    SYNTAX      LldpSystemCapabilitiesMap
    MAX-ACCESS  read-only
    STATUS      current
    DESCRIPTION
            "The bitmap value used to identify which system capabilities
            are supported on the local system."
    REFERENCE 
            "IEEE 802.1AB-2005 9.5.8.1"
    ::= { rclldpLocalSystemData 5 }

rclldpLocSysCapEnabled  OBJECT-TYPE
    SYNTAX      LldpSystemCapabilitiesMap
    MAX-ACCESS  read-only
    STATUS      current
    DESCRIPTION
            "The bitmap value used to identify which system capabilities
            are enabled on the local system."
    REFERENCE 
            "IEEE 802.1AB-2005 9.5.8.2"
    ::= { rclldpLocalSystemData 6 }


--
-- rclldpLocPortTable : Port specific Local system data
--

rclldpLocPortTable OBJECT-TYPE
    SYNTAX      SEQUENCE OF rclldpLocPortEntry
    MAX-ACCESS  not-accessible
    STATUS      current
    DESCRIPTION
            "This table contains one or more rows per port information
            associated with the local system known to this agent."
    ::= { rclldpLocalSystemData 7 }

rclldpLocPortEntry OBJECT-TYPE
    SYNTAX      rclldpLocPortEntry 
    MAX-ACCESS  not-accessible
    STATUS      current
    DESCRIPTION
            "Information about a particular port component.

            Entries may be created and deleted in this table by the
            agent."
    INDEX   { rclldpLocPortNum }
    ::= { rclldpLocPortTable 1 }

rclldpLocPortEntry ::= SEQUENCE {
      rclldpLocPortNum                LldpPortNumber,
      rclldpLocPortIdSubtype          LldpPortIdSubtype,
      rclldpLocPortId                 LldpPortId,
      rclldpLocPortDesc               SnmpAdminString
}

rclldpLocPortNum  OBJECT-TYPE
    SYNTAX      LldpPortNumber
    MAX-ACCESS  not-accessible
    STATUS      current
    DESCRIPTION
            "The index value used to identify the port component
            (contained in the local chassis with the rclldp agent)
            associated with this entry.
            
            The value of this object is used as a port index to the
            rclldpLocPortTable."
    ::= { rclldpLocPortEntry 1 }

rclldpLocPortIdSubtype  OBJECT-TYPE
    SYNTAX      LldpPortIdSubtype
    MAX-ACCESS  read-only
    STATUS      current
    DESCRIPTION
            "The type of port identifier encoding used in the associated
            'rclldpLocPortId' object."
    REFERENCE 
            "IEEE 802.1AB-2005 9.5.3.2"
    ::= { rclldpLocPortEntry 2 }

rclldpLocPortId  OBJECT-TYPE
    SYNTAX      LldpPortId
    MAX-ACCESS  read-only
    STATUS      current
    DESCRIPTION
            "The string value used to identify the port component
            associated with a given port in the local system."
    REFERENCE 
            "IEEE 802.1AB-2005 9.5.3.3"
    ::= { rclldpLocPortEntry 3 }

rclldpLocPortDesc  OBJECT-TYPE
    SYNTAX      SnmpAdminString (SIZE(0..255))
    MAX-ACCESS  read-only
    STATUS      current
    DESCRIPTION
            "The string value used to identify the 802 LAN station's port
            description associated with the local system.  If the local
            agent supports IETF RFC 2863, rclldpLocPortDesc object should
            have the same value of ifDescr object."
    REFERENCE 
            "IEEE 802.1AB-2005 9.5.5.2"
    ::= { rclldpLocPortEntry 4 }

--
-- rclldpLocManAddrTable : Management addresses of the local system
--

rclldpLocManAddrTable OBJECT-TYPE
    SYNTAX      SEQUENCE OF rclldpLocManAddrEntry
    MAX-ACCESS  not-accessible
    STATUS      current
    DESCRIPTION
            "This table contains management address information on the
            local system known to this agent."
    ::= { rclldpLocalSystemData 8 }

rclldpLocManAddrEntry OBJECT-TYPE
    SYNTAX      rclldpLocManAddrEntry
    MAX-ACCESS  not-accessible
    STATUS      current
    DESCRIPTION
            "Management address information about a particular chassis
            component.  There may be multiple management addresses
            configured on the system identified by a particular
            rclldpLocChassisId.  Each management address should have
            distinct 'management address type' (rclldpLocManAddrSubtype) and
            'management address' (rclldpLocManAddr.)

            Entries may be created and deleted in this table by the
            agent."
    INDEX   { rclldpLocManAddrPortIndex}
    ::= { rclldpLocManAddrTable 1 }

rclldpLocManAddrEntry ::= SEQUENCE {
      rclldpLocManAddrPortIndex  OltPortIndex ,
      rclldpLocManAddrSubtype    AddressFamilyNumbers,
      rclldpLocManAddr           LldpManAddress,
      rclldpLocManAddrLen        Integer32,
      rclldpLocManAddrIfSubtype  LldpManAddrIfSubtype,
      rclldpLocManAddrIfId       Integer32,
      rclldpLocManAddrOID        OBJECT IDENTIFIER
}

rclldpLocManAddrPortIndex  OBJECT-TYPE
    SYNTAX      OltPortIndex
    MAX-ACCESS  not-accessible
    STATUS      current
    DESCRIPTION
            "The type of management address identifier encoding used in
            the associated 'rclldpLocManagmentAddr' object."
    REFERENCE 
            "IEEE 802.1AB-2005 9.5.9.3"
    ::= { rclldpLocManAddrEntry 1 }
    
rclldpLocManAddrSubtype  OBJECT-TYPE
    SYNTAX      AddressFamilyNumbers
    MAX-ACCESS  read-only
    STATUS      current
    DESCRIPTION
            "The type of management address identifier encoding used in
            the associated 'rclldpLocManagmentAddr' object."
    REFERENCE 
            "IEEE 802.1AB-2005 9.5.9.3"
    ::= { rclldpLocManAddrEntry 2 }

rclldpLocManAddr  OBJECT-TYPE
    SYNTAX      LldpManAddress
    MAX-ACCESS  read-only
    STATUS      current
    DESCRIPTION
            "The string value used to identify the management address
            component associated with the local system.  The purpose of
            this address is to contact the management entity."
    REFERENCE 
            "IEEE 802.1AB-2005 9.5.9.4"
    ::= { rclldpLocManAddrEntry 3 }

rclldpLocManAddrLen  OBJECT-TYPE
    SYNTAX      Integer32
    MAX-ACCESS  read-only
    STATUS      current
    DESCRIPTION
            "The total length of the management address subtype and the
            management address fields in rclldpDUs transmitted by the
            local rclldp agent.

            The management address length field is needed so that the
            receiving systems that do not implement SNMP will not be
            required to implement an iana family numbers/address length
            equivalency table in order to decode the management adress."
    REFERENCE 
            "IEEE 802.1AB-2005 9.5.9.2"
    ::= { rclldpLocManAddrEntry 4 }


rclldpLocManAddrIfSubtype  OBJECT-TYPE
    SYNTAX      LldpManAddrIfSubtype
    MAX-ACCESS  read-only
    STATUS      current
    DESCRIPTION
            "The enumeration value that identifies the interface numbering
            method used for defining the interface number, associated
            with the local system."
    REFERENCE 
            "IEEE 802.1AB-2005 9.5.9.5"
    ::= { rclldpLocManAddrEntry 5 }

rclldpLocManAddrIfId  OBJECT-TYPE
    SYNTAX      Integer32
    MAX-ACCESS  read-only
    STATUS      current
    DESCRIPTION
            "The integer value used to identify the interface number
            regarding the management address component associated with
            the local system."
    REFERENCE 
            "IEEE 802.1AB-2005 9.5.9.6"
    ::= { rclldpLocManAddrEntry 6 }

rclldpLocManAddrOID  OBJECT-TYPE
    SYNTAX      OBJECT IDENTIFIER
    MAX-ACCESS  read-only
    STATUS      current
    DESCRIPTION
            "The OID value used to identify the type of hardware component
            or protocol entity associated with the management address
            advertised by the local system agent."
    REFERENCE 
            "IEEE 802.1AB-2005 9.5.9.8"
    ::= { rclldpLocManAddrEntry 7 }


--  ***********************************************************
--
--          R E M O T E    S Y S T E M S    D A T A
--
--  ***********************************************************

rclldpRemTable OBJECT-TYPE
    SYNTAX      SEQUENCE OF rclldpRemEntry
    MAX-ACCESS  not-accessible
    STATUS      current
    DESCRIPTION
            "This table contains one or more rows per physical network
            connection known to this agent.  The agent may wish to ensure
            that only one rclldpRemEntry is present for each local port,
            or it may choose to maintain multiple rclldpRemEntries for
            the same local port.

            The following procedure may be used to retrieve remote
            systems information updates from an rclldp agent:

               1. NMS polls all tables associated with remote systems
                  and keeps a local copy of the information retrieved.
                  NMS polls periodically the values of the following
                  objects:
                     a. rclldpStatsRemTablesInserts
                     b. rclldpStatsRemTablesDeletes
                     c. rclldpStatsRemTablesDrops
                     d. rclldpStatsRemTablesAgeouts
                     e. rclldpStatsRxPortAgeoutsTotal for all ports.

               2. rclldp agent updates remote systems MIB objects, and
                  sends out notifications to a list of notification
                  destinations.

               3. NMS receives the notifications and compares the new
                  values of objects listed in step 1.  

                  Periodically, NMS should poll the object
                  rclldpStatsRemTablesLastChangeTime to find out if anything
                  has changed since the last poll.  if something has
                  changed, NMS will poll the objects listed in step 1 to
                  figure out what kind of changes occurred in the tables.

                  if value of rclldpStatsRemTablesInserts has changed,
                  then NMS will walk all tables by employing TimeFilter
                  with the last-polled time value.  This request will
                  return new objects or objects whose values are updated
                  since the last poll.

                  if value of rclldpStatsRemTablesAgeouts has changed,
                  then NMS will walk the rclldpStatsRxPortAgeoutsTotal and
                  compare the new values with previously recorded ones.
                  For ports whose rclldpStatsRxPortAgeoutsTotal value is
                  greater than the recorded value, NMS will have to
                  retrieve objects associated with those ports from
                  table(s) without employing a TimeFilter (which is
                  performed by specifying 0 for the TimeFilter.)

                  rclldpStatsRemTablesDeletes and rclldpStatsRemTablesDrops
                  objects are provided for informational purposes."
    ::= { rclldpRemoteSystemsData 1 }

rclldpRemEntry OBJECT-TYPE
    SYNTAX      rclldpRemEntry
    MAX-ACCESS  not-accessible
    STATUS      current
    DESCRIPTION
            "Information about a particular physical network connection.
            Entries may be created and deleted in this table by the agent,
            if a physical topology discovery process is active."
    INDEX   {
           rclldpRemTimeMark,
           rclldpRemLocalPortNum,
           rclldpRemIndex
    }
    ::= { rclldpRemTable 1 }

rclldpRemEntry ::= SEQUENCE {
      rclldpRemTimeMark           TimeFilter,
      rclldpRemLocalPortNum       LldpPortNumber,
      rclldpRemIndex              Integer32,
      rclldpRemChassisIdSubtype   LldpChassisIdSubtype,
      rclldpRemChassisId          LldpChassisId,
      rclldpRemPortIdSubtype      LldpPortIdSubtype,
      rclldpRemPortId             LldpPortId,
      rclldpRemPortDesc           SnmpAdminString,
      rclldpRemSysName            SnmpAdminString,
      rclldpRemSysDesc            SnmpAdminString,
      rclldpRemSysCapSupported    LldpSystemCapabilitiesMap,
      rclldpRemSysCapEnabled      LldpSystemCapabilitiesMap
}

rclldpRemTimeMark  OBJECT-TYPE
    SYNTAX      TimeFilter
    MAX-ACCESS  not-accessible
    STATUS      current
    DESCRIPTION
            "A TimeFilter for this entry.  See the TimeFilter textual
            convention in IETF RFC 2021 and 
            http://www.ietf.org/IESG/Implementations/RFC2021-Implementation.txt
            to see how TimeFilter works."
    REFERENCE 
            "IETF RFC 2021 section 6"
    ::= { rclldpRemEntry 1 }

rclldpRemLocalPortNum  OBJECT-TYPE
    SYNTAX      LldpPortNumber
    MAX-ACCESS  not-accessible
    STATUS      current
    DESCRIPTION
            "The index value used to identify the port component
            (contained in the local chassis with the rclldp agent)
            associated with this entry.  The rclldpRemLocalPortNum
            identifies the port on which the remote system information
            is received.

            The value of this object is used as a port index to the
            rclldpRemTable."
    ::= { rclldpRemEntry 2 }

rclldpRemIndex  OBJECT-TYPE
    SYNTAX      Integer32(1..2147483647)
    MAX-ACCESS  not-accessible
    STATUS      current
    DESCRIPTION
            "This object represents an arbitrary local integer value used
            by this agent to identify a particular connection instance,
            unique only for the indicated remote system.

            An agent is encouraged to assign monotonically increasing
            index values to new entries, starting with one, after each
            reboot.  It is considered unlikely that the rclldpRemIndex
            will wrap between reboots."
    ::= { rclldpRemEntry 3 }

rclldpRemChassisIdSubtype  OBJECT-TYPE
    SYNTAX      LldpChassisIdSubtype
    MAX-ACCESS  read-only
    STATUS      current
    DESCRIPTION
            "The type of encoding used to identify the chassis associated
            with the remote system."
    REFERENCE 
            "IEEE 802.1AB-2005 9.5.2.2"
    ::= { rclldpRemEntry 4 }

rclldpRemChassisId  OBJECT-TYPE
    SYNTAX      LldpChassisId
    MAX-ACCESS  read-only
    STATUS      current
    DESCRIPTION
            "The string value used to identify the chassis component
            associated with the remote system."
    REFERENCE 
            "IEEE 802.1AB-2005 9.5.2.3"
    ::= { rclldpRemEntry 5 }

rclldpRemPortIdSubtype  OBJECT-TYPE
    SYNTAX      LldpPortIdSubtype
    MAX-ACCESS  read-only
    STATUS      current
    DESCRIPTION
            "The type of port identifier encoding used in the associated
            'rclldpRemPortId' object."
    REFERENCE 
            "IEEE 802.1AB-2005 9.5.3.2"
    ::= { rclldpRemEntry 6 }

rclldpRemPortId  OBJECT-TYPE
    SYNTAX      LldpPortId
    MAX-ACCESS  read-only
    STATUS      current
    DESCRIPTION
            "The string value used to identify the port component
            associated with the remote system."
    REFERENCE 
            "IEEE 802.1AB-2005 9.5.3.3"
    ::= { rclldpRemEntry 7 }

rclldpRemPortDesc  OBJECT-TYPE
    SYNTAX      SnmpAdminString (SIZE(0..255))
    MAX-ACCESS  read-only
    STATUS      current
    DESCRIPTION
            "The string value used to identify the description of
            the given port associated with the remote system."
    REFERENCE 
            "IEEE 802.1AB-2005 9.5.5.2"
    ::= { rclldpRemEntry 8 }

rclldpRemSysName  OBJECT-TYPE
    SYNTAX      SnmpAdminString (SIZE(0..255))
    MAX-ACCESS  read-only
    STATUS      current
    DESCRIPTION
            "The string value used to identify the system name of the
            remote system."
    REFERENCE 
            "IEEE 802.1AB-2005 9.5.6.2"
    ::= { rclldpRemEntry 9 }

rclldpRemSysDesc  OBJECT-TYPE
    SYNTAX      SnmpAdminString (SIZE(0..255))
    MAX-ACCESS  read-only
    STATUS      current
    DESCRIPTION
            "The string value used to identify the system description
            of the remote system."
    REFERENCE 
            "IEEE 802.1AB-2005 9.5.7.2"
    ::= { rclldpRemEntry 10 }

rclldpRemSysCapSupported OBJECT-TYPE
    SYNTAX      LldpSystemCapabilitiesMap
    MAX-ACCESS  read-only
    STATUS      current
    DESCRIPTION
            "The bitmap value used to identify which system capabilities
            are supported on the remote system."
    REFERENCE 
            "IEEE 802.1AB-2005 9.5.8.1"
    ::= { rclldpRemEntry 11 }

rclldpRemSysCapEnabled  OBJECT-TYPE
    SYNTAX      LldpSystemCapabilitiesMap
    MAX-ACCESS  read-only
    STATUS      current
    DESCRIPTION
            "The bitmap value used to identify which system capabilities
            are enabled on the remote system."
    REFERENCE 
            "IEEE 802.1AB-2005 9.5.8.2"
    ::= { rclldpRemEntry 12 }

--
-- rclldpRemManAddrTable : Management addresses of the remote system
--

rclldpRemManAddrTable OBJECT-TYPE
    SYNTAX      SEQUENCE OF rclldpRemManAddrEntry
    MAX-ACCESS  not-accessible
    STATUS      current
    DESCRIPTION
            "This table contains one or more rows per management address
            information on the remote system learned on a particular port
            contained in the local chassis known to this agent."
    ::= { rclldpRemoteSystemsData 2 }

rclldpRemManAddrEntry OBJECT-TYPE
    SYNTAX      rclldpRemManAddrEntry
    MAX-ACCESS  not-accessible
    STATUS      current
    DESCRIPTION
            "Management address information about a particular chassis
            component.  There may be multiple management addresses
            configured on the remote system identified by a particular
            rclldpRemIndex whose information is received on
            rclldpRemLocalPortNum of the local system.  Each management
            address should have distinct 'management address
            type' (rclldpRemManAddrSubtype) and 'management address'
            (rclldpRemManAddr.)

            Entries may be created and deleted in this table by the
            agent."
    INDEX   { rclldpRemTimeMark,
              rclldpRemLocalPortNum,
              rclldpRemIndex,
              rclldpRemManAddrSubtype,
              rclldpRemManAddr
 }
    ::= { rclldpRemManAddrTable 1 }

rclldpRemManAddrEntry ::= SEQUENCE {
      rclldpRemManAddrSubtype     AddressFamilyNumbers,
      rclldpRemManAddr            LldpManAddress,
      rclldpRemManAddrIfSubtype   LldpManAddrIfSubtype,
      rclldpRemManAddrIfId        Integer32,
      rclldpRemManAddrOID         OBJECT IDENTIFIER
}

rclldpRemManAddrSubtype  OBJECT-TYPE
    SYNTAX      AddressFamilyNumbers
    MAX-ACCESS  read-only
    STATUS      current
    DESCRIPTION
            "The type of management address identifier encoding used in
            the associated 'rclldpRemManagmentAddr' object."
    REFERENCE 
            "IEEE 802.1AB-2005 9.5.9.3"
    ::= { rclldpRemManAddrEntry 1 }

rclldpRemManAddr  OBJECT-TYPE
    SYNTAX      LldpManAddress
    MAX-ACCESS  read-only
    STATUS      current
    DESCRIPTION
            "The string value used to identify the management address
            component associated with the remote system.  The purpose
            of this address is to contact the management entity."
    REFERENCE 
            "IEEE 802.1AB-2005 9.5.9.4"
    ::= { rclldpRemManAddrEntry 2 }

rclldpRemManAddrIfSubtype  OBJECT-TYPE
    SYNTAX      LldpManAddrIfSubtype
    MAX-ACCESS  read-only
    STATUS      current
    DESCRIPTION
            "The enumeration value that identifies the interface numbering
            method used for defining the interface number, associated
            with the remote system."
    REFERENCE 
            "IEEE 802.1AB-2005 9.5.9.5"
    ::= { rclldpRemManAddrEntry 3 }

rclldpRemManAddrIfId  OBJECT-TYPE
    SYNTAX      Integer32
    MAX-ACCESS  read-only
    STATUS      current
    DESCRIPTION
            "The integer value used to identify the interface number
            regarding the management address component associated with
            the remote system."
    REFERENCE 
            "IEEE 802.1AB-2005 9.5.9.6"
    ::= { rclldpRemManAddrEntry 4 }

rclldpRemManAddrOID  OBJECT-TYPE
    SYNTAX      OBJECT IDENTIFIER
    MAX-ACCESS  read-only
    STATUS      current
    DESCRIPTION
            "The OID value used to identify the type of hardware component
            or protocol entity associated with the management address
            advertised by the remote system agent."
    REFERENCE 
            "IEEE 802.1AB-2005 9.5.9.8"
    ::= { rclldpRemManAddrEntry 5 }

--
-- rclldpRemUnknownTLVTable : Unrecognized TLV information 
--
rclldpRemUnknownTLVTable  OBJECT-TYPE
    SYNTAX      SEQUENCE OF rclldpRemUnknownTLVEntry
    MAX-ACCESS  not-accessible
    STATUS      current
    DESCRIPTION
            "This table contains information about an incoming TLV which
            is not recognized by the receiving rclldp agent.  The TLV may
            be from a later version of the basic management set.

            This table should only contain TLVs that are found in
            a single rclldp frame.  Entries in this table, associated
            with an MAC service access point (MSAP, the access point
            for MAC services provided to the LCC sublayer, defined
            in IEEE 100, which is also identified with a particular
            rclldpRemLocalPortNum, rclldpRemIndex pair) are overwritten with
            most recently received unrecognized TLV from the same MSAP,
            or they will naturally age out when the rxInfoTTL timer
            (associated with the MSAP) expires."
    REFERENCE 
            "IEEE 802.1AB-2005 10.3.2"
    ::= { rclldpRemoteSystemsData 3 }

rclldpRemUnknownTLVEntry OBJECT-TYPE
    SYNTAX      rclldpRemUnknownTLVEntry
    MAX-ACCESS  not-accessible
    STATUS      current
    DESCRIPTION
            "Information about an unrecognized TLV received from a
            physical network connection.  Entries may be created and
            deleted in this table by the agent, if a physical topology
            discovery process is active."
    INDEX   {
           rclldpRemTimeMark,
           rclldpRemLocalPortNum,
           rclldpRemIndex,
           rclldpRemUnknownTLVType 
    }
    ::= { rclldpRemUnknownTLVTable 1 }

rclldpRemUnknownTLVEntry ::= SEQUENCE {
      rclldpRemUnknownTLVType     Integer32,
      rclldpRemUnknownTLVInfo     OCTET STRING
}

rclldpRemUnknownTLVType OBJECT-TYPE
    SYNTAX      Integer32(9..126)
    MAX-ACCESS  not-accessible
    STATUS      current
    DESCRIPTION
            "This object represents the value extracted from the type
            field of the TLV."
    REFERENCE 
            "IEEE 802.1AB-2005 10.3.5"
    ::= { rclldpRemUnknownTLVEntry 1 }

rclldpRemUnknownTLVInfo OBJECT-TYPE
    SYNTAX      OCTET STRING (SIZE(0..511))
    MAX-ACCESS  read-only
    STATUS      current
    DESCRIPTION
            "This object represents the value extracted from the value
            field of the TLV."
    REFERENCE 
            "IEEE 802.1AB-2005 10.3.5"
    ::= { rclldpRemUnknownTLVEntry 2 }

------------------------------------------------------------------------------
-- Remote Systems Extension Table - Organizationally-Defined Information 
------------------------------------------------------------------------------
rclldpRemOrgDefInfoTable OBJECT-TYPE
    SYNTAX      SEQUENCE OF rclldpRemOrgDefInfoEntry
    MAX-ACCESS  not-accessible
    STATUS      current
    DESCRIPTION
            "This table contains one or more rows per physical network
            connection which advertises the organizationally defined
            information.

            Note that this table contains one or more rows of
            organizationally defined information that is not recognized
            by the local agent.

            If the local system is capable of recognizing any
            organizationally defined information, appropriate extension
            MIBs from the organization should be used for information
            retrieval."
    ::= { rclldpRemoteSystemsData 4 }

rclldpRemOrgDefInfoEntry OBJECT-TYPE
    SYNTAX      rclldpRemOrgDefInfoEntry
    MAX-ACCESS  not-accessible
    STATUS      current
    DESCRIPTION
            "Information about the unrecognized organizationally
            defined information advertised by the remote system.
            The rclldpRemTimeMark, rclldpRemLocalPortNum, rclldpRemIndex,
            rclldpRemOrgDefInfoOUI, rclldpRemOrgDefInfoSubtype, and
            rclldpRemOrgDefInfoIndex are indexes to this table.  If there is
            an rclldpRemOrgDefInfoEntry associated with a particular remote
            system identified by the rclldpRemLocalPortNum and rclldpRemIndex,
            there must be an rclldpRemEntry associated with the same
            instance (i.e, using same indexes.)  When the rclldpRemEntry
            for the same index is removed from the rclldpRemTable, the
            associated rclldpRemOrgDefInfoEntry should be removed from
            the rclldpRemOrgDefInfoTable.

            Entries may be created and deleted in this table by the
            agent."
    INDEX   { rclldpRemTimeMark,
              rclldpRemLocalPortNum,
              rclldpRemIndex,
              rclldpRemOrgDefInfoOUI,
              rclldpRemOrgDefInfoSubtype,
              rclldpRemOrgDefInfoIndex }
    ::= { rclldpRemOrgDefInfoTable 1 }

rclldpRemOrgDefInfoEntry ::= SEQUENCE {
      rclldpRemOrgDefInfoOUI         OCTET STRING,
      rclldpRemOrgDefInfoSubtype     Integer32,
      rclldpRemOrgDefInfoIndex       Integer32,
      rclldpRemOrgDefInfo            OCTET STRING
}

rclldpRemOrgDefInfoOUI  OBJECT-TYPE
    SYNTAX      OCTET STRING (SIZE(3))  
    MAX-ACCESS  not-accessible
    STATUS      current
    DESCRIPTION
            "The Organizationally Unique Identifier (OUI), as defined
            in IEEE std 802-2001, is a 24 bit (three octets) globally
            unique assigned number referenced by various standards,
            of the information received from the remote system."
    REFERENCE 
            "IEEE 802.1AB-2005 9.5.1.3"
    ::= { rclldpRemOrgDefInfoEntry 1 }

rclldpRemOrgDefInfoSubtype  OBJECT-TYPE
    SYNTAX      Integer32(1..255)
    MAX-ACCESS  not-accessible
    STATUS      current
    DESCRIPTION
            "The integer value used to identify the subtype of the
            organizationally defined information received from the
            remote system.

            The subtype value is required to identify different instances
            of organizationally defined information that could not be
            retrieved without a unique identifier that indicates the
            particular type of information contained in the information
            string."
    REFERENCE 
            "IEEE 802.1AB-2005 9.5.1.4"
    ::= { rclldpRemOrgDefInfoEntry 2 }

rclldpRemOrgDefInfoIndex  OBJECT-TYPE
    SYNTAX      Integer32(1..2147483647)
    MAX-ACCESS  not-accessible
    STATUS      current
    DESCRIPTION
            "This object represents an arbitrary local integer value
            used by this agent to identify a particular unrecognized
            organizationally defined information instance, unique only
            for the rclldpRemOrgDefInfoOUI and rclldpRemOrgDefInfoSubtype
            from the same remote system.

            An agent is encouraged to assign monotonically increasing
            index values to new entries, starting with one, after each
            reboot.  It is considered unlikely that the
            rclldpRemOrgDefInfoIndex will wrap between reboots."
    ::= { rclldpRemOrgDefInfoEntry 3 }

rclldpRemOrgDefInfo  OBJECT-TYPE
    SYNTAX      OCTET STRING(SIZE(0..507))
    MAX-ACCESS  read-only
    STATUS      current
    DESCRIPTION
            "The string value used to identify the organizationally
            defined information of the remote system.  The encoding for
            this object should be as defined for SnmpAdminString TC."
    REFERENCE 
            "IEEE 802.1AB-2005 9.5.1.5"
    ::= { rclldpRemOrgDefInfoEntry 4 }


--
-- ***********************************************************
-- 
--        L L D P   M I B   N O T I F I C A T I O N S
-- 
-- *********************************************************** 
--

rclldpNotificationPrefix OBJECT IDENTIFIER ::= { rclldpNotifications 0 }

rclldpRemTablesChange NOTIFICATION-TYPE
    OBJECTS {
        rclldpStatsRemTablesInserts,
        rclldpStatsRemTablesDeletes,
        rclldpStatsRemTablesDrops,
        rclldpStatsRemTablesAgeouts
    }
    STATUS        current
    DESCRIPTION
            "A rclldpRemTablesChange notification is sent when the value
            of rclldpStatsRemTableLastChangeTime changes.  It can be
            utilized by an NMS to trigger rclldp remote systems table
            maintenance polls.

            Note that transmission of rclldpRemTablesChange
            notifications are throttled by the agent, as specified by the
            'rclldpNotificationInterval' object."
   ::= { rclldpNotificationPrefix 1 }


--
-- ***********************************************************
-- 
--           L L D P   M I B   C O N F O R M A N C E 
-- 
-- *********************************************************** 
--

rclldpCompliances OBJECT IDENTIFIER ::= { rclldpConformance 1 }
rclldpGroups      OBJECT IDENTIFIER ::= { rclldpConformance 2 }

-- compliance statements

rclldpCompliance MODULE-COMPLIANCE
    STATUS  current
    DESCRIPTION
            "The compliance statement for SNMP entities which implement
            the rclldp MIB."
    MODULE  -- this module
        MANDATORY-GROUPS { rclldpConfigGroup, 
                           rclldpConfigRxGroup, 
                           rclldpConfigTxGroup, 
                           rclldpStatsRxGroup, 
                           rclldpStatsTxGroup, 
                           rclldpLocSysGroup,
                           rclldpRemSysGroup,
                           rclldpNotificationsGroup
        }
    ::= { rclldpCompliances 1 }

-- MIB groupings

rclldpConfigGroup    OBJECT-GROUP
    OBJECTS {
        rclldpPortConfigAdminStatus
    }
    STATUS  current
    DESCRIPTION
            "The collection of objects which are used to configure the
            rclldp implementation behavior.

            This group is mandatory for agents which implement the rclldp."
    ::= { rclldpGroups 1 }

rclldpConfigRxGroup    OBJECT-GROUP
    OBJECTS {
        rclldpNotificationInterval,
        rclldpPortConfigNotificationEnable
    }
    STATUS  current
    DESCRIPTION
            "The collection of objects which are used to configure the
            rclldp implementation behavior.

            This group is mandatory for agents which implement the rclldp
            and have the capability of receiving rclldp frames."
    ::= { rclldpGroups 2 }

rclldpConfigTxGroup    OBJECT-GROUP
    OBJECTS {
        rclldpMessageTxInterval,
        rclldpMessageTxHoldMultiplier,
        rclldpReinitDelay,
        rclldpTxDelay,
        rclldpPortConfigTLVsTxEnable,
        rclldpConfigManAddrPortsTxEnable
    }
    STATUS  current
    DESCRIPTION
            "The collection of objects which are used to configure the
            rclldp implementation behavior.

            This group is mandatory for agents which implement the rclldp
            and have the capability of transmitting rclldp frames."
    ::= { rclldpGroups 3 }

rclldpStatsRxGroup    OBJECT-GROUP
    OBJECTS {
        rclldpStatsRemTablesLastChangeTime,
        rclldpStatsRemTablesInserts,
        rclldpStatsRemTablesDeletes,
        rclldpStatsRemTablesDrops,
        rclldpStatsRemTablesAgeouts,
        rclldpStatsRxPortFramesDiscardedTotal,
        rclldpStatsRxPortFramesErrors,
        rclldpStatsRxPortFramesTotal,
        rclldpStatsRxPortTLVsDiscardedTotal,
        rclldpStatsRxPortTLVsUnrecognizedTotal,
        rclldpStatsRxPortAgeoutsTotal
    }
    STATUS  current
    DESCRIPTION
            "The collection of objects which are used to represent rclldp
            reception statistics.

            This group is mandatory for agents which implement the rclldp
            and have the capability of receiving rclldp frames."
    ::= { rclldpGroups 4 }

rclldpStatsTxGroup    OBJECT-GROUP
    OBJECTS {
        rclldpStatsTxPortFramesTotal
    }
    STATUS  current
    DESCRIPTION
            "The collection of objects which are used to represent rclldp
            transmission statistics.

            This group is mandatory for agents which implement the rclldp
            and have the capability of transmitting rclldp frames."
    ::= { rclldpGroups 5 }

rclldpLocSysGroup  OBJECT-GROUP
    OBJECTS {
        rclldpLocChassisIdSubtype,
        rclldpLocChassisId,
        rclldpLocPortIdSubtype,
        rclldpLocPortId,
        rclldpLocPortDesc,
        rclldpLocSysDesc,
        rclldpLocSysName,
        rclldpLocSysCapSupported,
        rclldpLocSysCapEnabled,
        rclldpLocManAddrLen,
        rclldpLocManAddrIfSubtype,
        rclldpLocManAddrIfId,
        rclldpLocManAddrOID
    }
    STATUS  current
    DESCRIPTION
            "The collection of objects which are used to represent rclldp
            Local System Information.  
            
            This group is mandatory for agents which implement the rclldp
            and have the capability of transmitting rclldp frames."
    ::= { rclldpGroups 6 }

rclldpRemSysGroup  OBJECT-GROUP
    OBJECTS {
        rclldpRemChassisIdSubtype,
        rclldpRemChassisId,
        rclldpRemPortIdSubtype,
        rclldpRemPortId,
        rclldpRemPortDesc,
        rclldpRemSysName,
        rclldpRemSysDesc,
        rclldpRemSysCapSupported,
        rclldpRemSysCapEnabled,
        rclldpRemManAddrIfSubtype,
        rclldpRemManAddrIfId,
        rclldpRemManAddrOID,
        rclldpRemUnknownTLVInfo,
        rclldpRemOrgDefInfo 
    }
    STATUS  current
    DESCRIPTION
            "The collection of objects which are used to represent
            rclldp Remote Systems Information.  The objects represent the
            information associated with the basic TLV set.  Please note
            that even the agent doesn't implement some of the optional
            TLVs, it shall recognize all the optional TLV information
            that the remote system may advertise.
            
            This group is mandatory for agents which implement the rclldp
            and have the capability of receiving rclldp frames."
    ::= { rclldpGroups 7 }

rclldpNotificationsGroup  NOTIFICATION-GROUP
    NOTIFICATIONS {
        rclldpRemTablesChange 
    }
    STATUS  current
    DESCRIPTION
            "The collection of notifications used to indicate rclldp MIB
            data consistency and general status information.

            This group is mandatory for agents which implement the rclldp
            and have the capability of receiving rclldp frames."
    ::= { rclldpGroups 8 }

END
