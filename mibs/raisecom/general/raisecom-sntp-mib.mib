--MibName=rcSntp
------------------------------------------------------------------------------
------------------------------------------------------------------------------
--
--  File         : sntp.mib
--  Description  : rose software system command  mib defination 
--  Version      : 0.1   
--  Date         : Dec 20, 2004     
--
--  Copyright (c) 2003-2004 Beijing Raisecom Science & Technology Co., ltd  All Rights Reserved.
--
------------------------------------------------------------------------------
------------------------------------------------------------------------------

    SWITCH-SNTP-MIB DEFINITIONS ::= BEGIN

    IMPORTS
        MODULE-IDENTITY, OBJECT-TYPE,
        InetAddress, InetAddressType
            					   FROM INET-ADDRESS-MIB 
        EnableVar				   FROM SWITCH-TC                               
        raisecomPonCommon		   FROM RAISECOM-PONSERIES-BASE-MIB;  

    rcSntp MODULE-IDENTITY
    
        LAST-UPDATED    "0412200000Z"  -- Dec 20, 2004
        ORGANIZATION    "Raisecom Science & Technology Co., ltd"
        CONTACT-INFO    "Raisecom Science & Technology Co., ltd.
                         E-mail: support@raisecom.com"

        DESCRIPTION     "ROSE SYSinfo Enterprise MIB definition."

        REVISION        "0412200000Z"  -- Dec 20, 2004
        DESCRIPTION     "Initial MIB creation."

                ::= { raisecomPonCommon 9 }      
                
----groups---------------------------------                
rcSntpClient       	OBJECT IDENTIFIER ::= { rcSntp 1 }
--------------------------------------------------   

--------------------------------------------------------------------------------------
--sysSntpClient  tempory defination for snmp trap server
--------------------------------------------------------------------------------------
--rcSntpClient
	-- rcSntpClientModeAdmin
	-- rcSntpClientServerIpAddrType
	-- rcSntpClientServerIpAddr    
	-- rcSntpClientSynchronizeTime

rcSntpClientModeAdmin OBJECT-TYPE
        SYNTAX EnableVar
        MAX-ACCESS read-write
        STATUS current
        DESCRIPTION
            "enable or disable sntp client function, and the client only supports unicast mode currently ."  
        DEFVAL { disable }
        ::= { rcSntpClient 1 }

rcSntpClientServerIpAddrType OBJECT-TYPE
        SYNTAX InetAddressType        
        MAX-ACCESS read-write
        STATUS current
        DESCRIPTION
            "The type of sntp server IP address ."
        DEFVAL { ipv4 }
        ::= { rcSntpClient 2 }     
        
rcSntpClientServerIpAddr OBJECT-TYPE
        SYNTAX InetAddress        
        MAX-ACCESS read-write
        STATUS current
        DESCRIPTION
            "The IPv4 of IPv6 address of sntp server ." 
     --   DEFVAL { 224.0.1.1 }
        ::= { rcSntpClient 3 }

        
rcSntpClientSynchronizeTime   OBJECT-TYPE
        SYNTAX INTEGER
        		{
        			NULL(0),
        			Synchronize(1)
        		}
        MAX-ACCESS read-write
        STATUS current
        DESCRIPTION
            " Synchronize system time with SNTP immediately  "
        DEFVAL { NULL }
        ::= { rcSntpClient 4 }      

--
-- END of SWITCH-SNTP-MIB                
--

END
