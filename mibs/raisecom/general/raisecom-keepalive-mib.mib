-- -----------------------------------------------------------------------------
-- MIB NAME : rcKeepaliveToSNMPManagerGroup
-- FILE NAME: RC-KEEPALIVE-MIB			
-- DATE     : 2011/1/20							
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2011/1/20, xiaoyingjie
-- This is the first formal version for universal MIB definition.
          

RC-KEEPALIVE-MIB DEFINITIONS ::= BEGIN

    IMPORTS
		MODULE-IDENTITY,
		OBJECT-TYPE,
		NOTIFICATION-TYPE ,
		Integer32,
		IpAddress,
		Counter32,
		Unsigned32
			FROM SNMPv2-SMI  
		raisecomPonCommon
			FROM RAISECOM-PONSERIES-BASE-MIB 		
    	sysName,sysObjectID           	
         	FROM RFC1213-MIB;  		        

	rcKeepaliveToSNMPManagerGroup    MODULE-IDENTITY
		LAST-UPDATED 	"200707090000Z"
		ORGANIZATION 	"rc TECH, Ltd."
		CONTACT-INFO 	"www.rc.com"
		DESCRIPTION  	
		    "The MIB module defining objects for SNMP keepalive functions"
		::= { raisecomPonCommon  3}  
              	
--rcKeepaliveToSNMPManagerGroup   
    
 	rcKeepaliveMibObjects OBJECT IDENTIFIER ::= { rcKeepaliveToSNMPManagerGroup 1 }
	rcKeepaliveTraps   OBJECT IDENTIFIER ::= { rcKeepaliveToSNMPManagerGroup 2 }

	rcKeepaliveTrapEnable  OBJECT-TYPE
  	SYNTAX          INTEGER{
        			enable(1),
        			disable(2),
        			pause(3)
        			}
        MAX-ACCESS read-write
        STATUS current
        DESCRIPTION
            "Indicates whether keepalive traps should be generated periodically.Disable 
            and pause indicate keepalive traps should not be generated.If the value of 
            this object is disable,it allow to be config loaded.If user makes this object 
            disable and saves config,keepalive trap will not be generated after load 
            config.If this object is pause,it don't allow to be config loaded."    
        DEFVAL	{ enable }
    	::= { rcKeepaliveMibObjects 1 }


	rcKeepaliveTrapInterval  OBJECT-TYPE
        SYNTAX        INTEGER (120 .. 28800) 
        UNITS         "seconds"
        MAX-ACCESS    read-write
        STATUS        current
        DESCRIPTION   "The value of this object indicates number of 
                       seconds between the transmission of keepalive  
                       trap."                       
        DEFVAL { 300 }
        ::= { rcKeepaliveMibObjects 2 }
        
  rcKeepaliveTrapCounter  OBJECT-TYPE
        SYNTAX        Counter32 
        MAX-ACCESS    read-only
        STATUS        current
        DESCRIPTION   "The value of this object indicates number of 
                       keepalive trap have sent."                       
        ::= { rcKeepaliveMibObjects 3}
	
   rcKeepalive NOTIFICATION-TYPE
           OBJECTS {sysName,sysObjectID,sysName,sysObjectID,sysName}
           STATUS  current
           DESCRIPTION
               "notify snmp manager that rcL3IpSubnetIp and other information periodically.
               the vars is temp,after will add macaddress,softversion,haedwareVersion."
       ::= { rcKeepaliveTraps 1 }
       
END
