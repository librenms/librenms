-- =======================================================================
-- Version info 
--
-- Version 1.0 Created 2007.6.24 by wangnan
-- This version of MIB is created just for management of base and user. 
-- modified node description by ljguang, Jul 19, 2007
-- add raisecomCpuIdV2 node by ljguang, Jul 24, 2007 
-- add node  by xyjie,Jul,11,2011
-- Copyright(c) 2007-2010 by RAISECOM TECH, Ltd. 
-- =======================================================================

-- ===========================================================================

--
-- RAISECOM base management objects
--            

RAISECOM-COMMON-MANAGEMENTV2-MIB DEFINITIONS ::= BEGIN

    IMPORTS
		MODULE-IDENTITY,
		OBJECT-TYPE,
		NOTIFICATION-TYPE ,
		Integer32,
		IpAddress,
		Unsigned32
			FROM SNMPv2-SMI
		DisplayString,
		TimeStamp,
		RowStatus,
		TruthValue
			FROM SNMPv2-TC
        EnableVar				FROM SWITCH-TC
	    PONDeviceCardType
	        FROM RAISECOM-PONSERIES-TC      
		raisecomDeviceIdV2,
		raisecomCpuIdV2
		  FROM RAISECOM-SYSTEMV2-MIB				    
		raisecomAgent		
			FROM RAISECOM-BASE-MIB
		InetAddress, InetAddressType
            FROM INET-ADDRESS-MIB;
	
	raisecomCommonManagementV2    MODULE-IDENTITY
		LAST-UPDATED 	"200706270000Z"
		ORGANIZATION 	"RAISECOM TECH, Ltd."
		CONTACT-INFO 	"www.raisecom.com"
		DESCRIPTION  	
		    "The MIB module defining objects for common management"
		::= { raisecomAgent  26}  
                
	--groups                 	  	
	raisecomOnlineUpgradeV2Group	OBJECT IDENTIFIER ::= {raisecomCommonManagementV2 1}		     
	raisecomKeepaliveToSNMPManagerV2Group	OBJECT IDENTIFIER ::= {raisecomCommonManagementV2 2} 
	raisecomSWFileGroup    OBJECT IDENTIFIER ::= {raisecomCommonManagementV2 3}
	raisecomAutoWriteGroup    OBJECT IDENTIFIER ::= {raisecomCommonManagementV2 4}
    		
   	raisecomOnlineUpgradeV2MibObjects OBJECT IDENTIFIER ::= { raisecomOnlineUpgradeV2Group 1 }
	raisecomOnlineUpgradeV2Mib      OBJECT IDENTIFIER ::= { raisecomOnlineUpgradeV2MibObjects 1 }
	raisecomOnlineUpgradeV2MibTraps   OBJECT IDENTIFIER ::= { raisecomOnlineUpgradeV2Group 2 }
		    
	raisecomOnlineUpgradeV2Table OBJECT-TYPE
		    SYNTAX SEQUENCE OF RaisecomOnlineUpgradeV2Entry
		    MAX-ACCESS not-accessible
		    STATUS current
		    DESCRIPTION
		        "A table of Upgrade requests."
		    ::= { raisecomOnlineUpgradeV2Mib 1 }

	raisecomOnlineUpgradeV2Entry OBJECT-TYPE
		    SYNTAX RaisecomOnlineUpgradeV2Entry
		    MAX-ACCESS not-accessible
		    STATUS current
		    DESCRIPTION
		        "A software upgrade request.
       
		        The index input is associated with slotId, portId and onuId. The calculation of
		        index value is
		        	index = slotId * 10 000 000 + portId * 100 000 + onuId.
		        When the OLT device's image file need to be upgraded, the slotId and portId must 
		        be zero, onuId must be none zero value.
		        
		        When the PON devices need to be upgraed, an index must be calculated as above. The
		        following items also should be definded: 
		        	raisecomOnlineUpgradeV2Protocol; 
		        	raisecomOnlineUpgradeV2OprType;   
		        	raisecomOnlineUpgradeV2FileType;
		        	raisecomOnlineUpgradeV2ServerAddress; 
		        	raisecomOnlineUpgradeV2FileName;  
		        	raisecomOnlineUpgradeV2NotificationOnCompletion; 
		        	raisecomOnlineUpgradeV2EntryRowStatus; 
		        The default protocol is tftp. If the protocol is ftp, the raisecomOnlineUpgradeV2UserName 
		        and  raisecomOnlineUpgradeV2UserPassword should be defined too.
  
		        It should also modify the default values for the other configuration objects 
		        if the defaults are not appropriate.
		        
		       	Once the appropriate instance of all the configuration objects have been created, 
		       	either by an explicit SNMP set request or by default, the row status should be set
		        to active to initiate the request. Note that this entire procedure may be initiated 
		        via a single set request which specifies a row status of createAndGo as well as 
		        specifies valid values for the non-defaulted configuration objects.
		       
		        Once the Upgrade request has been created (i.e. the
		        raisecomOnlineUpgradeV2EntryRowStatus has been made active), the entry cannot be 
		        modified - the only operation allowed is to delete the row.
		       
		        Once the request completes, the management station should retrieve the values of 
		        the status objects of interest, and should then delete the entry.  In order to prevent 
		        old entries from clogging the table, entries will be aged out, but an entry will never 
		        be deleted within 5 minutes of completing."
		    INDEX { raisecomDeviceIdV2, raisecomCpuIdV2 }
		    ::= { raisecomOnlineUpgradeV2Table 1 }

	RaisecomOnlineUpgradeV2Entry ::= SEQUENCE {
		    raisecomDeviceIdV2 						Unsigned32,
		    raisecomCpuIdV2							Unsigned32,
		    raisecomOnlineUpgradeV2Protocol 		INTEGER,
		    raisecomOnlineUpgradeV2OprType			INTEGER,
		    raisecomOnlineUpgradeV2FileType 		INTEGER,
		    raisecomOnlineUpgradeV2ServerAddress 	IpAddress,
		    raisecomOnlineUpgradeV2FileName 		DisplayString,
		    raisecomOnlineUpgradeV2UserName 		OCTET STRING,
		    raisecomOnlineUpgradeV2UserPassword 	OCTET STRING,
		    raisecomOnlineUpgradeV2NotificationOnCompletion 	TruthValue,
		    raisecomOnlineUpgradeV2State 			INTEGER,    
		    raisecomOnlineUpgradeV2Sizetoprocess	INTEGER,
		    raisecomOnlineUpgradeV2CompletedSize  	INTEGER,		
		    raisecomOnlineUpgradeV2FailCause 		INTEGER,
		    raisecomOnlineUpgradeV2EntryRowStatus RowStatus,
		    raisecomOnlineUpgradeV2DeviceCpuList    OCTET STRING,
		    raisecomOnlineUpgradeV2ServerAddressType InetAddressType,
		    raisecomOnlineUpgradeV2ServerIpv6Addr   InetAddress    
		    }

	raisecomDeviceIdV2 OBJECT-TYPE
		    SYNTAX Unsigned32
		    MAX-ACCESS read-only
		    STATUS current
		    DESCRIPTION
		        "Index."
		    ::= { raisecomOnlineUpgradeV2Entry 1 }  
	
	raisecomCpuIdV2 OBJECT-TYPE
			SYNTAX Unsigned32(0..7)
			MAX-ACCESS read-only
			STATUS current
			DESCRIPTION
				"CPU Id."
			::= { raisecomOnlineUpgradeV2Entry 2 }

	raisecomOnlineUpgradeV2Protocol OBJECT-TYPE
		    SYNTAX INTEGER {tftp(1),ftp(2),dev(3)}
		    MAX-ACCESS read-create
		    STATUS current
		    DESCRIPTION
		        "The protocol to be used for any Upgrade process. Default protocol 
		        will be tftp if not specified.
		       
		        If the Upgrade operation occurs locally on the SNMP agent,
		        this object may be ignored by the implementation."
		    DEFVAL { tftp }
		    ::= { raisecomOnlineUpgradeV2Entry 3 }

	raisecomOnlineUpgradeV2OprType OBJECT-TYPE
		    SYNTAX INTEGER {
	        		 upload (1),
	        		 download (2)
	        		 }
		    MAX-ACCESS read-create
		    STATUS current
		    DESCRIPTION
		        "Specifies the type of file to upgrade from. Now ONLY download operation
		        is supported."		        		       
		    ::= { raisecomOnlineUpgradeV2Entry 4 }

	raisecomOnlineUpgradeV2FileType OBJECT-TYPE
		    SYNTAX INTEGER {
	        		   masterImage (1),
                       slaveImage (2),
                       startupconfig (3),
                       runningconfig (4),
                       bootstrap (5),
                       firmware (6),
                       fpga (7),
                       cpld (8),
                       onutemplate(9),
                       flashdatabase(10),
                       extendBoot1(11),
					   extendBoot2(12),
					   softpackage(13),
					   historycmd(14),
					   onuxmlconfig(15),
					   commonfile(16)
	        		   }
		    MAX-ACCESS read-create
		    STATUS current
		    DESCRIPTION
		        "Specifies the type of file to be upgraded. Now ONLY masterImage type is
		        supported.s"
		    ::= { raisecomOnlineUpgradeV2Entry 5 }

	 raisecomOnlineUpgradeV2ServerAddress OBJECT-TYPE
		    SYNTAX IpAddress
		    MAX-ACCESS read-create
		    STATUS current
		    DESCRIPTION
		        "The ip address of the tftp or ftp server from (or to) which to copy
		        the file. The ip address should be a valide one."
		    ::= { raisecomOnlineUpgradeV2Entry 6 }

	 raisecomOnlineUpgradeV2FileName OBJECT-TYPE
		    SYNTAX DisplayString
		    MAX-ACCESS read-create
		    STATUS current
		    DESCRIPTION
		        "The name of the file to be transmitted."
		    ::= {  raisecomOnlineUpgradeV2Entry 7 }

	raisecomOnlineUpgradeV2UserName OBJECT-TYPE
		    SYNTAX OCTET STRING (SIZE(1..40))
		    MAX-ACCESS read-create
		    STATUS current
		    DESCRIPTION
		        "Remote user name for ftp file server. This must be defined when the 
		        raisecomOnlineUpgradeV2Protocol is ftp."
		    ::= {  raisecomOnlineUpgradeV2Entry 8 }

	 raisecomOnlineUpgradeV2UserPassword OBJECT-TYPE
		    SYNTAX OCTET STRING (SIZE(1..40))
		    MAX-ACCESS read-create
		    STATUS current
		    DESCRIPTION
		        "Password used by ftp for copying a file to/from an ftp server. This object 
		        must be created when the raisecomOnlineUpgradeV2Protocol is ftp . Reading it
		        returns a zero-length  string for security reasons."
		    ::= {  raisecomOnlineUpgradeV2Entry 9 }

	 raisecomOnlineUpgradeV2NotificationOnCompletion OBJECT-TYPE
		    SYNTAX TruthValue
		    MAX-ACCESS read-create
		    STATUS current
		    DESCRIPTION
		        "Specifies whether or not a notification should be issued on completion of the 
		        upgrade operation. If such a notification is desired, it is the responsibility 
		        of the management entity to ensure that the SNMP administrative model is configured 
		        in such a way as to allow the notification to be delivered."
		    DEFVAL { false }
		    ::= {  raisecomOnlineUpgradeV2Entry 10 }

	 raisecomOnlineUpgradeV2State OBJECT-TYPE
		    SYNTAX  INTEGER {
				        waiting(1),
				        getsource(2),
				        writedest(3), 
				        completed(4),
				        getsourcesize(5)
				     }
		    MAX-ACCESS read-only
		    STATUS current
		    DESCRIPTION
		        "Specifies the state of this Upgrade request. This value of this object is 
		        instantiated only after the row has been instantiated, i.e. after the  
		        raisecomOnlineUpgradeV2EntryRowStatus has been made active."
		    ::= {  raisecomOnlineUpgradeV2Entry 11 }

	 raisecomOnlineUpgradeV2Sizetoprocess OBJECT-TYPE
		    SYNTAX INTEGER
		    MAX-ACCESS read-only
		    STATUS current
		    DESCRIPTION
		        "Specifies the Size of the specific source file ."
		    ::= {  raisecomOnlineUpgradeV2Entry 12 }

	 raisecomOnlineUpgradeV2CompletedSize OBJECT-TYPE
		    SYNTAX INTEGER
		    MAX-ACCESS read-only
		    STATUS current
		    DESCRIPTION
		        "Specifies the Size of the specific source file that has been processed."
		    ::= {  raisecomOnlineUpgradeV2Entry 13 }

	 raisecomOnlineUpgradeV2FailCause OBJECT-TYPE
		    SYNTAX  INTEGER {
		    			noError(1),
				        badMethod(2),
				        badSourceAddress(3),
				        badDestAddress(4),
				        badPort(5),
				        badUserName(6),
				        badPassword(7),
				        badFileName(8),
				        fileOpenFail(9),
				        fileWriteFail(10),
				        timeout(11),
				        noMem(12),
				        noConfig(13),
				        fileTooLarge(14),
				        unknown(15),
				        badSourceFileType(16),
				        badDestFileType(17),
				        connectServerFail(18),
				        fileCheckFail(19),
				        packetLost(20),
				        sameVersion(21),
				        objectNotSupport(22), 
				        onuNoMem(23),
				        fileSizeError(24)				        				        
				    }
		    MAX-ACCESS read-only
		    STATUS current
		    DESCRIPTION
		        "The reason why the Upgrade operation failed. This object is instantiated 
		        only when the raisecomOnlineUpgradev2State for this  entry is in the failed 
		        state."
		    ::= {  raisecomOnlineUpgradeV2Entry 14 }

	 raisecomOnlineUpgradeV2EntryRowStatus OBJECT-TYPE
		    SYNTAX RowStatus
		    MAX-ACCESS read-create
		    STATUS current
		    DESCRIPTION
		        "The status of this table entry. Once the entry status is set to active, the 
		        associated entry cannot be modified until the request completes 
		        ( raisecomOnlineUpgradeV2State transitions to successful or failed state )."
		    ::= {  raisecomOnlineUpgradeV2Entry 15 }   
		    
	raisecomOnlineUpgradeV2DeviceCpuList OBJECT-TYPE
		    SYNTAX OCTET STRING
		    MAX-ACCESS read-create
		    STATUS current
		    DESCRIPTION
		        ""
		    ::= {  raisecomOnlineUpgradeV2Entry 16 }   
	
	raisecomOnlineUpgradeV2ServerAddressType  OBJECT-TYPE
			SYNTAX InetAddressType
        	ACCESS read-write
        	STATUS current
        	DESCRIPTION
           		"The IP address type of a specified server."
           DEFVAL { ipv4 }
           ::= {  raisecomOnlineUpgradeV2Entry 17 }
           
     raisecomOnlineUpgradeV2ServerIpv6Addr OBJECT-TYPE
		    SYNTAX InetAddress
		    ACCESS read-create
		    STATUS current
		    DESCRIPTION
		        "The IPv6 address of server"
		    ::= { raisecomOnlineUpgradeV2Entry 18 }
		    
 	 raisecomAutoUpgradeAdminState OBJECT-TYPE
		    SYNTAX EnableVar
		    MAX-ACCESS read-write
		    STATUS current
		    DESCRIPTION
		        "The administrative state of auto-upgrade."
		    ::= {  raisecomOnlineUpgradeV2Mib 2 }   

 	 raisecomAutoUpgradeExecutionTime OBJECT-TYPE
		    SYNTAX INTEGER(2..5)
		    MAX-ACCESS read-write
		    STATUS current
		    DESCRIPTION
		        "The everyday execution time of auto-upgrade."
		    ::= {  raisecomOnlineUpgradeV2Mib 3 }   

 	raisecomAutoUpgradeTable OBJECT-TYPE
		    SYNTAX SEQUENCE OF RaisecomAutoUpgradeEntry
		    MAX-ACCESS not-accessible
		    STATUS current
		    DESCRIPTION
		        "A table of auto-upgrade requests."
		    ::= { raisecomOnlineUpgradeV2Mib 4 }

	raisecomAutoUpgradeEntry OBJECT-TYPE
		    SYNTAX RaisecomAutoUpgradeEntry
		    MAX-ACCESS not-accessible
		    STATUS current
		    DESCRIPTION
		        "An auto-upgrade request."
		    INDEX { raisecomAutoUpgradeDeviceType }
		    ::= { raisecomAutoUpgradeTable 1 }

	RaisecomAutoUpgradeEntry ::= SEQUENCE {
		    raisecomAutoUpgradeDeviceType 		  PONDeviceCardType,
		    raisecomAutoUpgradeProtocol 		  INTEGER,
		    raisecomAutoUpgradeServerAddress 	  IpAddress,
		    raisecomAutoUpgradeFileName 		  DisplayString,
		    raisecomAutoUpgradeUserName 		  DisplayString,
		    raisecomAutoUpgradeUserPassword   	  DisplayString,
		    raisecomAutoUpgradeExecuteNow 		  INTEGER,
		    raisecomAutoUpgradeRowStatus 		  RowStatus,
		    raisecomAutoUpgradeServerAddressType  InetAddressType,
		    raisecomAutoUpgradeServerIpv6Addr     InetAddress
		    }

     raisecomAutoUpgradeDeviceType    OBJECT-TYPE
        SYNTAX          PONDeviceCardType       
        MAX-ACCESS      read-only
        STATUS          current
        DESCRIPTION     "ONU type."
        ::= { raisecomAutoUpgradeEntry 1 } 
     
     raisecomAutoUpgradeProtocol    OBJECT-TYPE
        SYNTAX          INTEGER {tftp(1),ftp(2)}       
        MAX-ACCESS      read-create
        STATUS          current
        DESCRIPTION     "Type of file transfer protocol."
        ::= { raisecomAutoUpgradeEntry 2 } 
     
     raisecomAutoUpgradeServerAddress    OBJECT-TYPE
        SYNTAX          IpAddress       
        MAX-ACCESS      read-create
        STATUS          current
        DESCRIPTION     "IP address of file server."
        ::= { raisecomAutoUpgradeEntry 3 } 
     
     raisecomAutoUpgradeFileName    OBJECT-TYPE
        SYNTAX          DisplayString(SIZE(1..80))      
        MAX-ACCESS      read-create
        STATUS          current
        DESCRIPTION     "Image file name."
        ::= { raisecomAutoUpgradeEntry 4 } 
     
     raisecomAutoUpgradeUserName    OBJECT-TYPE
        SYNTAX          DisplayString(SIZE(1..40))       
        MAX-ACCESS      read-create
        STATUS          current
        DESCRIPTION     "FTP user name to login file server."
        ::= { raisecomAutoUpgradeEntry 5 } 
     
     raisecomAutoUpgradeUserPassword    OBJECT-TYPE
        SYNTAX          DisplayString(SIZE(1..40))       
        MAX-ACCESS      read-create
        STATUS          current
        DESCRIPTION     "FTP user password to login file server."
        ::= { raisecomAutoUpgradeEntry 6 } 
     
     raisecomAutoUpgradeExecuteNow    OBJECT-TYPE
        SYNTAX          INTEGER {idle(0), execute(1)}
        MAX-ACCESS      read-write
        STATUS          current
        DESCRIPTION     "Force to execute this auto-upgrade request right now."
        ::= { raisecomAutoUpgradeEntry 7 } 
     
     raisecomAutoUpgradeRowStatus    OBJECT-TYPE
        SYNTAX          RowStatus       
        MAX-ACCESS      read-create
        STATUS          current
        DESCRIPTION     "Row status of this auto-upgrade request."
        ::= { raisecomAutoUpgradeEntry 8 }   
        
   	 raisecomAutoUpgradeServerAddressType  OBJECT-TYPE
		SYNTAX         InetAddressType
       	ACCESS         read-write
       	STATUS         current
       	DESCRIPTION	   "The IP address type of a specified server."
        DEFVAL { ipv4 }
        ::= {  raisecomAutoUpgradeEntry 9 }
           
     raisecomAutoUpgradeServerIpv6Addr OBJECT-TYPE
	    SYNTAX         InetAddress
	    ACCESS         read-create
	    STATUS         current
	    DESCRIPTION   "The IPv6 address of server."
	    ::= {  raisecomAutoUpgradeEntry 10 }
     
	raisecomOnlineUpgradeV2Completion NOTIFICATION-TYPE
		    OBJECTS { raisecomDeviceIdV2, raisecomCpuIdV2,
		        raisecomOnlineUpgradeV2ServerAddress, raisecomOnlineUpgradeV2FileName, raisecomOnlineUpgradeV2State,
		        raisecomOnlineUpgradeV2Sizetoprocess, raisecomOnlineUpgradeV2CompletedSize, raisecomOnlineUpgradeV2FailCause }
			STATUS current
		    DESCRIPTION
		        "A raisecomOnlineUpgradeV2Completion trap is sent at the completion of a Upgrade 
		        request. The raisecomOnlineUpgradeFailCause is not instantiated, and hence not 
		        included in a trap, when the raisecomOnlineUpgradeV2State is success."
		    ::= {raisecomOnlineUpgradeV2MibTraps 1}      

	raisecomCtcOnuSwUpgradeCompletion NOTIFICATION-TYPE
		    OBJECTS { raisecomCtcOnuSwUpgradeOnuId,
				    raisecomCtcOnuSwUpgradeServerAddress, 
				    raisecomCtcOnuSwUpgradeFileName, 
				    raisecomCtcOnuSwUpgradeState,
				    raisecomCtcOnuSwUpgradeSizetoProcess, 
				    raisecomCtcOnuSwUpgradeCompleteSize, 
				    raisecomCtcOnuSwUpgradeFailCause }
			STATUS current
		    DESCRIPTION
		        "."
		    ::= {raisecomOnlineUpgradeV2MibTraps 2}   		    

--raisecomKeepaliveToSNMPManagerV2Group   
    
   	raisecomKeepaliveMibV2Objects OBJECT IDENTIFIER ::= { raisecomKeepaliveToSNMPManagerV2Group 1 }
	raisecomKeepaliveTrapsV2   OBJECT IDENTIFIER ::= { raisecomKeepaliveToSNMPManagerV2Group 2 }

	raisecomKeepaliveTrapEnableV2  OBJECT-TYPE
  	SYNTAX          INTEGER{
        			enable(1),
        			disable(2),
        			pause(3)
        			}
        MAX-ACCESS read-write
        STATUS current
        DESCRIPTION
            "Indicates whether keepalive traps should be generated periodically.Disable 
            and pause indicate keepalive traps should not be generated.If the value of 
            this object is disable,it allow to be config loaded.If user makes this object 
            disable and saves config,keepalive trap will not be generated after load 
            config.If this object is pause,it don't allow to be config loaded."    
        DEFVAL	{ enable }
    	::= { raisecomKeepaliveMibV2Objects 1 }


	raisecomKeepaliveTrapIntervalV2  OBJECT-TYPE
        SYNTAX        INTEGER (120..28800) 
        UNITS         "seconds"
        MAX-ACCESS    read-write
        STATUS        current
        DESCRIPTION   "The value of this object indicates number of 
                       seconds between the transmission of keepalive  
                       trap."                       
        DEFVAL { 300 }
        ::= { raisecomKeepaliveMibV2Objects 2 }
	
  raisecomKeepaliveTrapCounterV2  OBJECT-TYPE
        SYNTAX        Counter32 
        MAX-ACCESS    read-only
        STATUS        current
        DESCRIPTION   "The value of this object indicates number of 
                       keepalive trap have sent."                       
        ::= { raisecomKeepaliveMibV2Objects 3}
	
   raisecomKeepaliveV2 NOTIFICATION-TYPE
           OBJECTS {sysName,sysObjectID,raisecomOutbandMgmtIpAddress, raisecomOutbandMgtPortIpSubnetMask}
           STATUS  current
           DESCRIPTION
               "notify snmp manager that the switch is in network now by send this trap."
       ::= { raisecomKeepaliveTrapsV2 1 }
       
 --raisecomSWFileGroup
    raisecomSWFileTable    OBJECT-TYPE
        SYNTAX          SEQUENCE OF  RaisecomSWFileEntry
        MAX-ACCESS      not-accessible
        STATUS          current
        DESCRIPTION     "Software image management table."
    ::= { raisecomSWFileGroup 1 }

    raisecomSWFileEntry    OBJECT-TYPE
	SYNTAX          RaisecomSWFileEntry
	MAX-ACCESS      not-accessible
    STATUS          current
	DESCRIPTION     "Software image management table entry."
	INDEX { raisecomDeviceIdV2, raisecomCpuIdV2, raisecomSWFileType }
    ::= { raisecomSWFileTable 1 }

    RaisecomSWFileEntry ::=
        SEQUENCE {        
        raisecomSWFileType             			 INTEGER, 
        raisecomSWFileVersion                    OCTET STRING (SIZE (0..64)),
        raisecomSWFileCommit                     TruthValue,
        raisecomSWFileActivate                   TruthValue,
        raisecomSWFileSize                       INTEGER, 
        raisecomSWFileUpdateTime                 TimeStamp,
		raisecomSWFileValid                      TruthValue
        }         
                    
     raisecomSWFileType     OBJECT-TYPE
        SYNTAX          INTEGER {
                                 	image1(1), 
									image2(2),
									bootrom(3),
									firmware1(4),
									firmware2(5),
									fpga1(6),
									fpga2(7),
									cpld (8),
									extboot1(9),
									extboot2(10)
								}
        MAX-ACCESS      not-accessible
        STATUS          current
        DESCRIPTION     "Image type."
        ::= { raisecomSWFileEntry 1 } 
        
    raisecomSWFileVersion   OBJECT-TYPE
        SYNTAX          OCTET STRING (SIZE(0..64))      
        MAX-ACCESS      read-only
        STATUS          current
        DESCRIPTION     "Image version."
        ::= { raisecomSWFileEntry 2 }    
  
    raisecomSWFileCommit   OBJECT-TYPE
        SYNTAX          TruthValue     
        MAX-ACCESS      read-write
        STATUS          current
        DESCRIPTION     
        "Image committed or not. If there are duplicate copy of the same image, 
        the committed image will be used to bootup the system. For single copy 
        images, the value for this attribute are fixed to be TRUE."
        ::= { raisecomSWFileEntry 3 } 
        
    raisecomSWFileActivate   OBJECT-TYPE
        SYNTAX          TruthValue     
        MAX-ACCESS      read-write
        STATUS          current
        DESCRIPTION     
        "Image activated or not. After this attribute is set TRUE, system is rebooted
         and this image will be loaded after system rebooted. The attribute value will 
         be reset to FALSE after the image are loaded." 
        ::= { raisecomSWFileEntry 4 }   
             
   raisecomSWFileSize     OBJECT-TYPE
        SYNTAX          INTEGER 
        MAX-ACCESS      read-only
        STATUS          current
        DESCRIPTION     "Image size."
        ::= { raisecomSWFileEntry 5 } 

   raisecomSWFileUpdateTime     OBJECT-TYPE
        SYNTAX          TimeStamp
        MAX-ACCESS      read-only
        STATUS          current
        DESCRIPTION     "Image update time."
        ::= { raisecomSWFileEntry 6 }  

	raisecomSWFileValid   OBJECT-TYPE
        SYNTAX          TruthValue     
        MAX-ACCESS      read-write
        STATUS          current
        DESCRIPTION     
        "Image valid or not. ."
        ::= { raisecomSWFileEntry 7 } 
        
--raisecomAutoWriteGroup   
 
 		raisecomAutoWriteAdmin  OBJECT-TYPE
  	SYNTAX          EnableVar{
        			enable(1),
        			disable(2)
        			}
        MAX-ACCESS read-write
        STATUS current
        DESCRIPTION
            "Indicates whether auto write should be set."    
        DEFVAL	{ disable }
    	::= { raisecomAutoWriteGroup 1 }
    	
    raisecomAutoWriteHour  OBJECT-TYPE
  			SYNTAX  INTEGER(0..23)
        MAX-ACCESS read-write
        STATUS current
        DESCRIPTION
            "Indicates the time when auto-write to commit"    
        DEFVAL	{ 4 }
    	::= { raisecomAutoWriteGroup 2 }   
    	
    raisecomAutoWriteLastResult  OBJECT-TYPE
  			SYNTAX  INTEGER{ Succeed(1),Failed(2)}
        MAX-ACCESS read-only
        STATUS current
        DESCRIPTION
            "Indicates the Last auto-write commit result"    
        DEFVAL	{ Succeed }
    	::= { raisecomAutoWriteGroup 3 }  
   	
	 raisecomAutoWriteTraps   OBJECT IDENTIFIER ::= { raisecomAutoWriteGroup 4 }
	
   raisecomAutoWriteCompletion NOTIFICATION-TYPE
           OBJECTS {raisecomAutoWriteState,raisecomAutoWriteHour,raisecomAutoWriteLastResult}
           STATUS  current
           DESCRIPTION
               "notify snmp manager that auto-writing have been commit and saving successfully by send this trap."
       ::= { raisecomAutoWriteTraps 1 }
       
   raisecomAutoWriteConfigUnsync NOTIFICATION-TYPE
           OBJECTS {raisecomAutoWriteState,raisecomAutoWriteHour,raisecomAutoWriteLastResult}
           STATUS  current
           DESCRIPTION
               "notify snmp manager that auto-writing doesn`t commit and some unsaved config maybe lost by send this trap."
       ::= { raisecomAutoWriteTraps 2 }
                                      


END
