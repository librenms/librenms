--MibName=rcAAAMib
-- *****************************************************************
-- RAISECOM-PON-USER-AAA-MIB.mib:  AAA MIB
--
-- Nov 2011, zhangronghua
--
-- Copyright (c) 1996-2011 by Raisecom Technology Co., Ltd. 
-- All rights reserved.
-- 
-- *****************************************************************
--
   
RAISECOM-PON-USER-AAA-MIB DEFINITIONS ::= BEGIN

    IMPORTS
		MODULE-IDENTITY,
		OBJECT-TYPE,
		Unsigned32
			FROM SNMPv2-SMI
		TruthValue
			FROM SNMPv2-TC    
		InetAddress, InetAddressType
            FROM INET-ADDRESS-MIB
		raisecomPonCommon
			FROM RAISECOM-PONSERIES-BASE-MIB;

	raisecomPonUserAAA    MODULE-IDENTITY
		LAST-UPDATED 	"201112130000Z"
		ORGANIZATION 	"RAISECOM TECH, Ltd."
		CONTACT-INFO 	"www.raisecom.com"
		DESCRIPTION  	
		    "The MIB module defining objects for user AAA functions."
		::= { raisecomPonCommon  14}  
   
    raisecomPonUserRadiusAuthServer  OBJECT IDENTIFIER ::= { raisecomPonUserAAA 1 } 
    
    raisecomPonUserRadiusAuthServerAddress OBJECT-TYPE
		SYNTAX InetAddress
		MAX-ACCESS read-write
		STATUS current
		DESCRIPTION
			"The IP Address of Radius server to store user information."
	::= { raisecomPonUserRadiusAuthServer 1 }   
	 
	raisecomPonUserRadiusAuthServerAddressType         OBJECT-TYPE
        SYNTAX          InetAddressType        
        MAX-ACCESS      read-write
        STATUS          current
        DESCRIPTION     
            "The address type of the radius server ip address"
    ::= { raisecomPonUserRadiusAuthServer 2 }		   
    
	raisecomPonUserRadiusAuthServerPort OBJECT-TYPE
	    SYNTAX Unsigned32
        MAX-ACCESS read-write
	    STATUS current
		DESCRIPTION
			"The Port of Radius server to store user information."
    ::= { raisecomPonUserRadiusAuthServer 3 }
		
	raisecomPonUserRadiusAuthServerBackupAddress OBJECT-TYPE
		SYNTAX InetAddress
		MAX-ACCESS read-write
		STATUS current
		DESCRIPTION
			"Backup IP Address of Radius server to store user information."
	::= { raisecomPonUserRadiusAuthServer 4 }  
	
    raisecomPonUserRadiusAuthServerBackupAddressType         OBJECT-TYPE
        SYNTAX          InetAddressType        
        MAX-ACCESS      read-write
        STATUS          current
        DESCRIPTION     
            "The address type of the radius backup server ip address"
    ::= { raisecomPonUserRadiusAuthServer 5 } 
          
	raisecomPonUserRadiusAuthServerBackupPort OBJECT-TYPE  
	    SYNTAX Unsigned32
	    MAX-ACCESS read-write
		STATUS current
		DESCRIPTION
			"Backup Port of Radius server to store user information."
    ::= { raisecomPonUserRadiusAuthServer 6 }
		
	raisecomPonUserRadiusAuthKey OBJECT-TYPE
	     SYNTAX OCTET STRING 	(SIZE (0..200))
	     MAX-ACCESS read-write
	     STATUS current
	     DESCRIPTION
	         "The shared secret text string used between the authenticator and a RADIUS server."
    ::= { raisecomPonUserRadiusAuthServer 7 } 
    
	raisecomPonUserTacacsPlusAuthServer   OBJECT IDENTIFIER ::= { raisecomPonUserAAA 2 } 
	
	 raisecomPonUserTacacsPlusAuthServerAddress OBJECT-TYPE
		SYNTAX InetAddress
		MAX-ACCESS read-write
		STATUS current
		DESCRIPTION
			"The IP Address of Radius server to store user information."
	::= { raisecomPonUserTacacsPlusAuthServer 1 }   
	 
	raisecomPonUserTacacsPlusAuthServerAddressType         OBJECT-TYPE
        SYNTAX          InetAddressType        
        MAX-ACCESS      read-write
        STATUS          current
        DESCRIPTION     
            "The address type of the radius server ip address"
    ::= { raisecomPonUserTacacsPlusAuthServer 2 }		   
    		
	raisecomPonUserTacacsPlusAuthServerBackupAddress OBJECT-TYPE
		SYNTAX InetAddress
		MAX-ACCESS read-write
		STATUS current
		DESCRIPTION
			"Backup IP Address of Radius server to store user information."
	::= { raisecomPonUserTacacsPlusAuthServer 3 }  
	
    raisecomPonUserTacacsPlusAuthServerBackupAddressType         OBJECT-TYPE
        SYNTAX          InetAddressType        
        MAX-ACCESS      read-write
        STATUS          current
        DESCRIPTION     
            "The address type of the radius backup server ip address"
    ::= { raisecomPonUserTacacsPlusAuthServer 4 } 
    
    raisecomPonUserTacacsPlusAuthKey   OBJECT-TYPE
    SYNTAX OCTET STRING 	(SIZE (0..200))
	     MAX-ACCESS read-write
	     STATUS current
	     DESCRIPTION
	     "The shared secret text string used between the authenticator and a RADIUS server."
        ::= { raisecomPonUserTacacsPlusAuthServer 5 } 
        
    raisecomPonUserTacacsPlusResultSendPkts   OBJECT-TYPE
        SYNTAX    Unsigned32						    
	    MAX-ACCESS read-only
	    STATUS current
	    DESCRIPTION
	        "This object indicates the number of packets which Tacacs+ client sent to Tacacs+ server."
    ::= { raisecomPonUserTacacsPlusAuthServer 6 }    
             
    raisecomPonUserTacacsPlusResultReceivePkts OBJECT-TYPE
        SYNTAX    Unsigned32						    
	    MAX-ACCESS read-only
	    STATUS current
	    DESCRIPTION
	        "This object indicates the number of packets which Tacacs+ client received from Tacacs+ server."
    ::= { raisecomPonUserTacacsPlusAuthServer 7 }   
     
    raisecomPonUserTacacsPlusResultErrorPkts OBJECT-TYPE
        SYNTAX    Unsigned32						    
	    MAX-ACCESS read-only
	    STATUS current
	    DESCRIPTION
	       "This object indicates the number of error packets which Tacacs+ client received from Tacacs+ server."
    ::= { raisecomPonUserTacacsPlusAuthServer 8 }   
    
    raisecomPonUserTacacsPlusClearStatistics OBJECT-TYPE
        SYNTAX    TruthValue						    
	    MAX-ACCESS read-write
	    STATUS current
	    DESCRIPTION
	        "The purpose of this object is to clear all the packet statistics. 
	    Set the value to true(1) means clear current packet statistics and begin the next recalculation."
    ::= { raisecomPonUserTacacsPlusAuthServer 9 }   
    
END
