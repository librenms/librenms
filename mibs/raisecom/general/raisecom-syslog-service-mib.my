-- MibName = raisecomSyslogService
-- =======================================================================
-- Syslog Service info 
--
-- Version 0.1 Created 2011.1.17 by YANZHIJIE
-- This version of MIB is created just for the use of Network Management Systems
-- display and config the syslog service.
-- log:
--
-- Copyright(c) 2003-2005 by RAISECOM TECH, Ltd.
-- =======================================================================

-- raisecom-syslog-service
-- 2011/1/17
-- This MIB provides a means to gather syslog messages generated

-- Terminology:
-- Various textual messages are generated by the RaisecomOS.  The
-- RaisecomOS can be configured such that these messages are sent
-- to a "syslog" server. These messages are hereupon referred to 
-- as "syslog messages" in this document.          
-- 
-- Note: Messages generated as a result of entering CLI debug
--       commands are not made available via the SNMP at this time.
-- 
-- All syslog messages have the following attributes:
--	timestamp (optional), facility name (where the message came
--	from), severity, message name, message text
--
-- The following example is often seen:
--	%SYS-5-CONFIG_I: Configured from console ...
-- where facility=SYS, severity=5, message name=CONFIG_I
-- ===========================================================================
--
-- RAISECOM syslog service objects
--

RAISECOM-SYSLOG-SERVICE-MIB    DEFINITIONS ::= BEGIN

	IMPORTS
		MODULE-IDENTITY,
		OBJECT-TYPE,
		IpAddress
			FROM SNMPv2-SMI
		RowStatus
			FROM SNMPv2-TC   
		EnableVar
			FROM SWITCH-TC
		InetAddress, InetAddressType
            FROM INET-ADDRESS-MIB
		raisecomPonCommon
			FROM RAISECOM-PONSERIES-BASE-MIB;
	
			
-------------------------------------------------------------------------------			
--
--  Syslog Service MIB
--
	rcSyslogService	MODULE-IDENTITY
        LAST-UPDATED 	"201101170000Z"
        ORGANIZATION 	"RAISECOM TECH, Ltd."
        CONTACT-INFO 	"www.raisecom.com"
        DESCRIPTION  	
            "The MIB module defining objects for Syslog Service"
    ::= { raisecomPonCommon 11 }


--------------------------------------------------------------------------------
--
-- Textual Conventions
--
	SyslogSeverity ::= TEXTUAL-CONVENTION
		STATUS	current
		DESCRIPTION
	   	    	"The severity of a syslog message.  The enumeration
				values are equal to the values that syslog uses + 1.
				For example, with syslog, emergency=0."
		SYNTAX	INTEGER {
			emergency(1),
			alert(2),
			critical(3),
			error(4),
			warning(5),
			notice(6),
			info(7),
			debug(8)
		}


--------------------------------------------------------------------------------
		
rcSyslogMibGroup OBJECT IDENTIFIER ::= { rcSyslogService 1 }

--------------------------------------------------------------------------------
--
-- Subgroups 供以后扩展使用
--

rcSyslogGlobalConfig OBJECT IDENTIFIER ::= { rcSyslogMibGroup 1 }
rcSyslogServerConfig OBJECT IDENTIFIER ::= { rcSyslogMibGroup 2 }
rcSyslogDebugConfig  OBJECT IDENTIFIER ::= { rcSyslogMibGroup 3 }
rcSyslogStatistics   OBJECT IDENTIFIER ::= { rcSyslogMibGroup 4 }


--------------------------------------------------------------------------------
--
-- rcSyslogGlobalConfig 
--
	rcSyslogAdmin OBJECT-TYPE
		SYNTAX EnableVar
		ACCESS read-write
		STATUS current
		DESCRIPTION
				"The administration status of the syslog function."
			::= { rcSyslogGlobalConfig 1 }
 
	rcSyslogRateLimit OBJECT-TYPE	 	
		SYNTAX INTEGER (0..10000)
		ACCESS read-write
		STATUS current
		DESCRIPTION
			"The Rate Limit for syslog."
			::= { rcSyslogGlobalConfig 2 }
		
	rcSyslogTimeStamp OBJECT-TYPE	 	
		SYNTAX INTEGER {
					no-timestamp(1),
					standard-timestamp(2),
					relative-timestamp(3)
					}
		ACCESS read-write
		STATUS current  
		DESCRIPTION
			"no-timestamp : no time stamp
			 standard-timestamp : APR-26-2004 17:27:45 
			 relative-timestamp : 17:27:45 time from start up
			"      
		DEFVAL { standard-timestamp }
			::= { rcSyslogGlobalConfig 3 }	
				
				
--------------------------------------------------------------------------------
--
-- rcSyslogServerConfig 
--	 	             
	rcSyslogServerMaxNum OBJECT-TYPE
    	SYNTAX INTEGER 
        ACCESS read-only
        STATUS current
        DESCRIPTION
           	"The maximum number of syslog server "
          	::= { rcSyslogServerConfig 1 }
           	
    rcSyslogServerConfigTable OBJECT-TYPE
        SYNTAX SEQUENCE OF RcSyslogServerConfigEntry 
        ACCESS not-accessible
        STATUS current
        DESCRIPTION
           	"A list of raisecomSyslogServiceServer entries."
           	::= { rcSyslogServerConfig 2 }

    rcSyslogServerConfigEntry OBJECT-TYPE
        SYNTAX RcSyslogServerConfigEntry 
        ACCESS not-accessible
        STATUS current
        DESCRIPTION
           	"The syslog service server list group infomation entry."
        INDEX { rcSyslogServerIndex }
           	::= { rcSyslogServerConfigTable 1 }
	
	RcSyslogServerConfigEntry ::= SEQUENCE {
		rcSyslogServerIndex INTEGER,
        rcSyslogServerIPAddr InetAddress,
        rcSyslogServerIPAddrType InetAddressType,
        rcSyslogServerPort INTEGER,
        rcSyslogServerFacility INTEGER,
		rcSyslogServerMaxServerity INTEGER, 
		rcSyslogContentOfHeader INTEGER,
		rcSyslogServerRowStatus	RowStatus
        }
 
	rcSyslogServerIndex OBJECT-TYPE
        SYNTAX INTEGER
        ACCESS read-create
        STATUS current
        DESCRIPTION
          	"The index of configed syslog server."
          	::= { rcSyslogServerConfigEntry 1 } 
              	
    rcSyslogServerIPAddr OBJECT-TYPE
    	SYNTAX InetAddress
    	ACCESS read-create
    	STATUS current
    	DESCRIPTION
    		"The IPv4 or IPv6 address of a specified server."
    		::= { rcSyslogServerConfigEntry 2 }

	rcSyslogServerIPAddrType OBJECT-TYPE
        SYNTAX InetAddressType
        ACCESS read-create
        STATUS current
        DESCRIPTION
           	"The IP address type of a specified server."
           	::= { rcSyslogServerConfigEntry 3 }
              	
    rcSyslogServerPort OBJECT-TYPE
    	SYNTAX INTEGER
    	ACCESS read-create
    	STATUS current
    	DESCRIPTION
    		"The UDP port used by the syslog server."
    		::= { rcSyslogServerConfigEntry 4 }

	rcSyslogServerFacility OBJECT-TYPE
        SYNTAX INTEGER{
            		local0(1),
              		local1(2),
              		local2(3),
              		local3(4),
              		local4(5),
              		local5(6),
              		local6(7),
              		local7(8)
               	}
        ACCESS read-create
        STATUS current
        DESCRIPTION
           	"The facility is one of the following keywords: local0 through local7.
           	The facility specifies the subsystem that produced the message, i.e. 
           	all mail programs log with the mail facility (LOG_MAIL) if they log 
           	using syslog.The default value is local0(0)."
           	::= { rcSyslogServerConfigEntry 5 }

	rcSyslogServerMaxServerity OBJECT-TYPE
       	SYNTAX INTEGER{
       				emergency(1),
       				alert(2),
       				critical(3),
       				error(4),
       				warning(5),
       				notice(6),
       				informational(7)
       			}
		ACCESS read-create
		STATUS current
		DESCRIPTION
           	"The max severity of messages which will be sent to syslog host."
           	::= { rcSyslogServerConfigEntry 6 } 
           	
    rcSyslogContentOfHeader OBJECT-TYPE
    	SYNTAX INTEGER{
    				hostname(1),
    				ipaddress(2)
    			}
    	ACCESS read-create
    	STATUS current
		DESCRIPTION
           	"The content to fill PRI of Syslog."
           	::= { rcSyslogServerConfigEntry 7 } 

	rcSyslogServerRowStatus	OBJECT-TYPE
	  	SYNTAX RowStatus 	
		ACCESS read-create
		STATUS current
		DESCRIPTION
			"This object indicates the status of this entry."
			::= { rcSyslogServerConfigEntry 8 }
			
			
--------------------------------------------------------------------------------
--
-- rcSyslogDebugConfigTable
---	
	rcSyslogDebugConfigTable OBJECT-TYPE
              	SYNTAX SEQUENCE OF RcSyslogDebugConfigEntry 
              	ACCESS not-accessible
              	STATUS current
              	DESCRIPTION
                  	"A list of raisecom Debug  entries."
              	::= { rcSyslogDebugConfig 1 }

	rcSyslogDebugConfigEntry OBJECT-TYPE
        SYNTAX RcSyslogDebugConfigEntry 
        ACCESS not-accessible
        STATUS current
        DESCRIPTION
           	"The debug  infomation entry."
        INDEX { rcSyslogDebugIndex }
        	::= { rcSyslogDebugConfigTable 1 }

	RcSyslogDebugConfigEntry ::= SEQUENCE {
            rcSyslogDebugIndex INTEGER,
            rcSyslogDebugModuleName	OCTET STRING,
            rcSyslogDebugModuleAdmin EnableVar
          	}

	rcSyslogDebugIndex OBJECT-TYPE
	  	SYNTAX INTEGER 	
		ACCESS not-accessible
		STATUS current
		DESCRIPTION
			"This object index of system debug entry."
			::= { rcSyslogDebugConfigEntry 1 }
		
	rcSyslogDebugModuleName OBJECT-TYPE
	  	SYNTAX OCTET STRING (SIZE (0..32))
		ACCESS read-write
		STATUS current
		DESCRIPTION
			"This name of debugging module."
			::= { rcSyslogDebugConfigEntry 2 }

	rcSyslogDebugModuleAdmin OBJECT-TYPE
	  	SYNTAX EnableVar
		ACCESS read-write
		STATUS current
		DESCRIPTION
			"This switch of specific module."
			::= { rcSyslogDebugConfigEntry 3 }

		
--------------------------------------------------------------------------------
--
-- rcSyslogStatistics
--
	rcSyslogDroppedMsgs OBJECT-TYPE
		SYNTAX Counter32
		ACCESS read-only
		STATUS current
		DESCRIPTION
				"The number of messages that syslog droped."
			::= { rcSyslogStatistics 1 } 
			
	rcSyslogConsloleLogedMsgs OBJECT-TYPE
		SYNTAX Counter32
		ACCESS read-only
		STATUS current
		DESCRIPTION
				"The number of messages that syslog loged to console."
			::= { rcSyslogStatistics 2 }
			
	rcSyslogMonitorLogedMsgs OBJECT-TYPE
		SYNTAX Counter32
		ACCESS read-only
		STATUS current
		DESCRIPTION
				"The number of messages that syslog loged to monitor."
			::= { rcSyslogStatistics 3 }

END
