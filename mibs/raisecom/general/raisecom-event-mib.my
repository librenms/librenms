-- -----------------------------------------------------------------------------
-- MIB NAME : raisecomEventMib
-- FILE NAME: raisecom-event-mib.my			
-- DATE     : 2011/4/1							
-- VERSION  : 1.00								
-- PURPOSE  : The MIB module defining objects for notification manager
--            functions			
-- -----------------------------------------------------------------------------
-- MODIFICTION HISTORY:
-- -----------------------------------------------------------------------------
-- Version, Date, Author
-- Description:								
--  [New Object]		
--  [Modification]
-- Notes: (Requested by who and which project)
--
-- Version 1.00, 2011/4/1, xiaoyingjie
-- This is the first formal version for universal MIB definition.
-----------------------------------------------------------------------------
--
-- RAISECOM base management objects
--  

RAISECOM-EVENT-MIB DEFINITIONS ::= BEGIN

    IMPORTS
		MODULE-IDENTITY,
		OBJECT-TYPE,
		NOTIFICATION-TYPE
            FROM SNMPv2-SMI
        RowStatus,StorageType
			FROM SNMPv2-TC
        EnableVar
        	FROM SWITCH-TC
  		SnmpAdminString
      		FROM SNMP-FRAMEWORK-MIB
      	ResourceId, alarmListName, alarmModelIndex,
      	alarmActiveDateAndTime, alarmActiveIndex
      		FROM ALARM-MIB
      	ItuPerceivedSeverity,
      	ItuTrendIndication
      		FROM ITU-ALARM-TC-MIB
      	IANAItuProbableCauseOrZero
      	    FROM ARC-MIB
      	IANAItuProbableCause,
      	IANAItuEventType
      		FROM IANA-ITU-ALARM-TC-MIB
      	ZeroBasedCounter32
      		FROM RMON2-MIB
        rcNotificationManagerGroup
        	FROM RAISECOM-NOTIFICATION-MIB;
        	
	rcEventManagerObjects    MODULE-IDENTITY
		LAST-UPDATED 	"201104010000Z"
		ORGANIZATION 	"RAISECOM TECH, Ltd."
		CONTACT-INFO 	"www.raisecom.com"
		DESCRIPTION  	
		    "The MIB module defining objects for notification manager functions."
		::= { rcNotificationManagerGroup  2}     
   		
-- event --

 	rcEventTrapEnable OBJECT-TYPE
    SYNTAX   EnableVar
    MAX-ACCESS read-write
    STATUS     current
    DESCRIPTION " The status of the event trap send function is enable or disable"
    	::= { rcEventManagerObjects 1 }  
    
    rcEventTableSize  OBJECT-TYPE
    SYNTAX   INTEGER
    MAX-ACCESS read-only
    STATUS     current
    DESCRIPTION " The size of the event table."
    	::= { rcEventManagerObjects 2 }
    	
 	rcEventTableSizeCurrent  OBJECT-TYPE
    SYNTAX   INTEGER
    MAX-ACCESS read-only
    STATUS     current
    DESCRIPTION " The size of the event table."
    	::= { rcEventManagerObjects 3 }
    	   	
    rcEventHistoryOverflow  OBJECT-TYPE
    SYNTAX   Counter32
    UNITS       "history events"
    MAX-ACCESS read-only
    STATUS     current
    DESCRIPTION 
    	"The number of events that have not been put into
         the eventHistoryTable since system restart as a result
         of extreme resource constraints."
    	::= { rcEventManagerObjects 4 }
    	   
-- Alarm filter Table --
			
   	rcEventModelTable    OBJECT-TYPE
	SYNTAX SEQUENCE OF RcEventModelEntry
   	ACCESS not-accessible
   	STATUS current
   	DESCRIPTION " A list of event model entries."
   		::= { rcEventManagerObjects 5} 
   		
   	rcEventModelEntry OBJECT-TYPE
   	SYNTAX  RcEventModelEntry
   	ACCESS not-accessible
	STATUS current
	DESCRIPTION " The event model entry"
	INDEX { alarmListName, rcEventModelIndex }
   		::= {rcEventModelTable 1}  
   		
   	RcEventModelEntry ::= SEQUENCE {
   		rcEventModelIndex  				Unsigned32,
   		rcEventModelPerceivedSeverity 	ItuPerceivedSeverity,
   		rcEventModelNotificationId 		OBJECT IDENTIFIER,  
   		rcEventModelDescription 		SnmpAdminString, 
   		rcEventModelVarbindSubtree		OBJECT IDENTIFIER, 	 
   		rcEventModelResourcePrefix		OBJECT IDENTIFIER,  
   		rcEventModelEventType			IANAItuEventType,			     
   		rcEventModelProbableCause		IANAItuProbableCause
   		}
   	rcEventModelIndex OBJECT-TYPE
   	SYNTAX     Unsigned32 (1..4294967295)
	MAX-ACCESS read-only
   	STATUS     current
   	DESCRIPTION
       "An integer that acts as an event Id
       to uniquely identify each event
       within the named alarm list. "
   		::= { rcEventModelEntry 1 }	
 
    rcEventModelPerceivedSeverity OBJECT-TYPE
    SYNTAX  ItuPerceivedSeverity
    MAX-ACCESS   read-only
    STATUS       current
    DESCRIPTION
               "ITU perceived severity values."
    REFERENCE
           "ITU Recommendation M.3100, 'Generic Network Information
               Model', 1995
            ITU Recommendation X.733, 'Information Technology - Open
               Systems Interconnection - System Management: Alarm
               Reporting Function', 1992"
       ::= { rcEventModelEntry 2 }
 
 
 	rcEventModelNotificationId OBJECT-TYPE
   	SYNTAX      OBJECT IDENTIFIER
   	MAX-ACCESS  read-only
   	STATUS      current
   	DESCRIPTION
       "The NOTIFICATION-TYPE object identifier of this event
        transition.  If there is no notification associated
       with this event, the value of this object MUST be
       '0.0'"
   	DEFVAL { zeroDotZero }
   		::= { rcEventModelEntry 3 }  
   		
	rcEventModelDescription OBJECT-TYPE
    SYNTAX SnmpAdminString
    MAX-ACCESS read-only
    STATUS current
    DESCRIPTION
      "A brief description of this event 
      to display to operators."
    DEFVAL { "" }
   		::= { rcEventModelEntry 4 } 
   		
	rcEventModelVarbindSubtree  OBJECT-TYPE
	SYNTAX  OBJECT IDENTIFIER
	MAX-ACCESS   read-only
	STATUS       current
	DESCRIPTION
       "The name portion of each VarBind in the notification,
        in order, is compared to the value of this object.
        If the name is equal to or a subtree of the value
        of this object, for purposes of computing the value
        of AlarmActiveResourceID the 'prefix' will be the
        matching portion, and the 'indexes' will be any
        remainder.  The examination of varbinds ends with
        the first match.  If the value of this object is 0.0,
        then the first varbind, or in the case of v2, the
        first varbind after the timestamp and the trap
        OID, will always be matched.
       "
	DEFVAL { zeroDotZero }
		::= { rcEventModelEntry 5 }

	rcEventModelResourcePrefix  OBJECT-TYPE
    SYNTAX  OBJECT IDENTIFIER
    MAX-ACCESS   read-only
    STATUS       current
    DESCRIPTION
       "The value of AlarmActiveResourceId is computed
        by appending any indexes extracted in accordance
        with the description of alarmModelVarbindSubtree
        onto the value of this object.  If this object's
        value is 0.0, then the 'prefix' extracted is used
        instead.
       "
    DEFVAL { zeroDotZero }
     	::= { rcEventModelEntry 6 }
     
	rcEventModelEventType OBJECT-TYPE
    SYNTAX      IANAItuEventType
    MAX-ACCESS  read-only
    STATUS       current
    DESCRIPTION
               "ITU probable cause values."
    REFERENCE
           "ITU Recommendation M.3100, 'Generic Network Information
               Model', 1995
            ITU Recommendation X.733, 'Information Technology - Open
               Systems Interconnection - System Management: Alarm
               Reporting Function', 1992
            ITU Recommendation X.736, 'Information Technology - Open
               Systems Interconnection - System Management: Security
               Alarm Reporting Function', 1992"
		::= { rcEventModelEntry 7 }

	rcEventModelProbableCause OBJECT-TYPE
    SYNTAX      IANAItuProbableCause
    MAX-ACCESS  read-only
    STATUS       current
    DESCRIPTION
               "ITU probable cause values."
    REFERENCE
           "ITU Recommendation M.3100, 'Generic Network Information
               Model', 1995
            ITU Recommendation X.733, 'Information Technology - Open
               Systems Interconnection - System Management: Alarm
               Reporting Function', 1992
            ITU Recommendation X.736, 'Information Technology - Open
               Systems Interconnection - System Management: Security
               Alarm Reporting Function', 1992"
		::= { rcEventModelEntry 8 }				
-- event inhibit Table --
   
    rcEventInhibitTable  OBJECT-TYPE
    SYNTAX SEQUENCE OF RcEventInhibitEntry 
    ACCESS not-accessible
    STATUS current
    DESCRIPTION "A list of event inhibit entries."
		::= { rcEventManagerObjects 6 }
    
	rcEventInhibitEntry   OBJECT-TYPE
	SYNTAX RcEventInhibitEntry
	ACCESS not-accessible
	STATUS current
	DESCRIPTION " The alarm filter entry"
	INDEX { rcEventInhibitResourceId, rcEventInhibitModelIndex }
   		::= {rcEventInhibitTable 1}
    
	RcEventInhibitEntry ::= SEQUENCE {
   		rcEventInhibitResourceId ResourceId,
   		rcEventInhibitModelIndex Unsigned32,
   		rcEventInhibitRowStatus RowStatus
   		}	

	rcEventInhibitResourceId OBJECT-TYPE
	SYNTAX ResourceId		
	MAX-ACCESS  not-accessible
	STATUS  current
	DESCRIPTION
		"This object uniquely identifies a resource.
		
		For example, if the resource is an interface, this object will
		point to an instance of interface, e.g., ifIndex.1."
		::= { rcEventInhibitEntry 1 }
		
	rcEventInhibitModelIndex OBJECT-TYPE
	SYNTAX  Unsigned32
	MAX-ACCESS  not-accessible
	STATUS  current
	DESCRIPTION
		"This object identifies the type of notification to be filter.
     	The notification type identified should be the one normally used
     	by the resource for reporting its alarms.  When the value of 0.0 is
     	specified for this object, it implies all applicable notification
     	types."
  		::= { rcEventInhibitEntry 2 }
  		
  	rcEventInhibitRowStatus OBJECT-TYPE
	SYNTAX  RowStatus
	MAX-ACCESS  read-create
	STATUS  current
	DESCRIPTION
    	"This columnar object is used for creating and deleting a conceptual
     	row of the rcEventInhibitTable.  It is used to create and delete an alarm
     	filter	setting.

     	Setting RowStatus to createAndGo or createAndWait implies creating
     	a new alarm filter setting for the specified resource and alarm type.
     	Setting RowStatus to destroy implies removing the alarm filter setting and
     	thus has the effect of resuming normal reporting behaviour of the
     	resource for the alarm type."
  		::= { rcEventInhibitEntry 3 }

-- event history Table --
	rcEventHistoryTable OBJECT-TYPE
   	SYNTAX      SEQUENCE OF RcEventHistoryEntry
   	MAX-ACCESS  not-accessible
   	STATUS      current
   	DESCRIPTION
       	"A table of history events entries."
   		::= { rcEventManagerObjects 7 }

	rcEventHistoryEntry OBJECT-TYPE
   	SYNTAX      RcEventHistoryEntry
   	MAX-ACCESS  not-accessible
   	STATUS      current
   	DESCRIPTION
       "Entries appear in this table when events are raised.  
        If under extreme resource constraint the system is unable to
        add any more entries into this table, then the
        rcEventHistoryOverflow statistic will be increased by one."
   	INDEX       { alarmListName, rcEventHistoryDateAndTime,
                 rcEventHistoryIndex }
   		::= { rcEventHistoryTable 1 }

	RcEventHistoryEntry ::= SEQUENCE {
   		rcEventHistoryDateAndTime           DateAndTime,
   		rcEventHistoryIndex                 Unsigned32,
   		rcEventHistoryVariables             Unsigned32,
		rcEventHistoryNotificationID        OBJECT IDENTIFIER,
		rcEventHistoryResourceId            ResourceId,
   		rcEventHistoryDescription           SnmpAdminString,
   		rcEventHistoryEvnetType  			INTEGER,
   		rcEventHistoryEvnetId				Unsigned32   		 
		}

	rcEventHistoryDateAndTime OBJECT-TYPE
   	SYNTAX      DateAndTime
   	MAX-ACCESS  not-accessible
   	STATUS      current
   	DESCRIPTION
       "The local date and time when the event occurred.

       This object facilitates retrieving all instances of

       alarms that have been raised or have changed state
       since a given point in time.

       Implementations MUST include the offset from UTC,
       if available.  Implementation in environments in which
       the UTC offset is not available is NOT RECOMMENDED."
   		::= { rcEventHistoryEntry 2 }

	rcEventHistoryIndex OBJECT-TYPE
   	SYNTAX     Unsigned32 (1..4294967295)
   	MAX-ACCESS not-accessible
   	STATUS     current
   	DESCRIPTION
       "A strictly monotonically increasing integer which
       acts as the index of entries within the named alarm
       list.  It wraps back to 1 after it reaches its
       maximum value."
   		::= { rcEventHistoryEntry 3 }

	rcEventHistoryVariables OBJECT-TYPE
   	SYNTAX      Unsigned32
   	MAX-ACCESS  read-only
   	STATUS      current
   	DESCRIPTION
       "The number of variables in rcEventHistoryVariableTable for this
       event."
   		::= { rcEventHistoryEntry 4 }

	rcEventHistoryNotificationID OBJECT-TYPE
   	SYNTAX      OBJECT IDENTIFIER
   	MAX-ACCESS  read-only
   	STATUS      current
   	DESCRIPTION
       "The NOTIFICATION-TYPE object identifier of the event
        transition that is occurring."
   		::= { rcEventHistoryEntry 5 }

	rcEventHistoryResourceId    OBJECT-TYPE
   	SYNTAX      ResourceId
   	MAX-ACCESS  read-only
   	STATUS      current
   	DESCRIPTION
      "This object identifies the resource under event.

      If there is no corresponding resource, then
      the value of this object MUST be 0.0."
   		::= { rcEventHistoryEntry 6 }

	rcEventHistoryDescription    OBJECT-TYPE
   	SYNTAX      SnmpAdminString
   	MAX-ACCESS  read-only
   	STATUS      current
   	DESCRIPTION
      "This object provides a textual description of the
      event.  This text is generated dynamically by the
      notification generator to provide useful information
      to the human operator.  This information SHOULD
      provide information allowing the operator to locate
      the resource for which this alarm is being generated.
      This information is not intended for consumption by
      automated tools."
   		::= { rcEventHistoryEntry 7 } 
   	
   	rcEventHistoryEvnetType OBJECT-TYPE
	SYNTAX INTEGER{ 
			normal(1),
			eventDisable(2)			}		
	MAX-ACCESS  read-only
	STATUS  current
	DESCRIPTION
		" The reason of the alarm to active table. the alarmfilter identifies 
		the alarm is filtered, not sended to the EMS. The alarmEnable identifies
		the rcAlarmTrapEnable is disable, the alarm is not sended to the EMS."
		::= { rcEventHistoryEntry 8 }
		
   	rcEventHistoryEvnetId OBJECT-TYPE
	SYNTAX Unsigned32		
	MAX-ACCESS  read-only
	STATUS  current
	DESCRIPTION
		""
		::= { rcEventHistoryEntry 9 } 

-- Clear Alarm Variable Table --

	rcEventHistoryVariableTable OBJECT-TYPE
   	SYNTAX      SEQUENCE OF RcEventHistoryVariableEntry
   	MAX-ACCESS  not-accessible
   	STATUS      current
   	DESCRIPTION
       "A table of variables to go with clear alarm entries."
   	::= { rcEventManagerObjects 8 }

	rcEventHistoryVariableEntry OBJECT-TYPE
   	SYNTAX      RcEventHistoryVariableEntry
   	MAX-ACCESS  not-accessible
   	STATUS      current
   	DESCRIPTION
       "Entries appear in this table when there are variables in
       the varbind list of a corresponding alarm in
       alarmActiveTable.

       Entries appear in this table as though
       the trap/notification had been transported using a
       alarmActiveVariableIndex 1 will always be sysUpTime
       and alarmActiveVariableIndex 2 will always be
       snmpTrapOID.

       If the incoming notification is instead an SNMPv1 Trap-PDU and
       the value of alarmModelVarbindIndex is 1 or 2, an appropriate
       value for sysUpTime.0 or snmpTrapOID.0 shall be determined
       by using the rules in section 3.1 of [RFC3584]."
   	INDEX   {  alarmListName, rcEventHistoryIndex,
              rcEventHistoryVariableIndex  }
   		::= { rcEventHistoryVariableTable 1 }

	RcEventHistoryVariableEntry ::= SEQUENCE {
	   rcEventHistoryVariableIndex                 Unsigned32,
	   rcEventHistoryVariableID                    OBJECT IDENTIFIER,
	   rcEventHistoryVariableValueType             INTEGER,
	   rcEventHistoryVariableCounter32Val          Counter32,
	   rcEventHistoryVariableUnsigned32Val         Unsigned32,
	   rcEventHistoryVariableTimeTicksVal          TimeTicks,
	   rcEventHistoryVariableInteger32Val          Integer32,
	   rcEventHistoryVariableOctetStringVal        OCTET STRING,
	   rcEventHistoryVariableIpAddressVal          IpAddress,
	   rcEventHistoryVariableOidVal                OBJECT IDENTIFIER,
	   rcEventHistoryVariableCounter64Val          Counter64,
	   rcEventHistoryVariableOpaqueVal             Opaque }

	rcEventHistoryVariableIndex OBJECT-TYPE
   	SYNTAX     Unsigned32 (1..4294967295)
   	MAX-ACCESS not-accessible
   	STATUS     current
   	DESCRIPTION
       "A strictly monotonically increasing integer, starting at
       1 for a given alarmActiveIndex, for indexing variables
       within the active alarm variable list. "
   		::= { rcEventHistoryVariableEntry 1 }

	rcEventHistoryVariableID OBJECT-TYPE
   	SYNTAX     OBJECT IDENTIFIER
   	MAX-ACCESS read-only
   	STATUS     current
   	DESCRIPTION
       "The alarm variable's object identifier."
   		::= { rcEventHistoryVariableEntry 2 }

	rcEventHistoryVariableValueType OBJECT-TYPE
   	SYNTAX      INTEGER {
         counter32(1),
         unsigned32(2),
         timeTicks(3),
         integer32(4),
         ipAddress(5),
         octetString(6),
         objectId(7),
         counter64(8),
         opaque(9)
         }
   	MAX-ACCESS  read-only
   	STATUS      current
   	DESCRIPTION
       "The type of the value.  One and only one of the value
       objects that follow is used for a given row in this table,
       based on this type."
   		::= { rcEventHistoryVariableEntry 3 }

	rcEventHistoryVariableCounter32Val OBJECT-TYPE
   	SYNTAX      Counter32
   	MAX-ACCESS  read-only
   	STATUS      current
   	DESCRIPTION
       "The value when alarmActiveVariableType is 'counter32'."
   		::= { rcEventHistoryVariableEntry 4 }

	rcEventHistoryVariableUnsigned32Val OBJECT-TYPE
   	SYNTAX      Unsigned32
   	MAX-ACCESS  read-only
   	STATUS      current
   	DESCRIPTION
       "The value when alarmActiveVariableType is 'unsigned32'."
   		::= { rcEventHistoryVariableEntry 5 }

	rcEventHistoryVariableTimeTicksVal OBJECT-TYPE
   	SYNTAX      TimeTicks
   	MAX-ACCESS  read-only
   	STATUS      current
   	DESCRIPTION
       "The value when alarmActiveVariableType is 'timeTicks'."
   		::= { rcEventHistoryVariableEntry 6 }

	rcEventHistoryVariableInteger32Val OBJECT-TYPE
   	SYNTAX      Integer32
   	MAX-ACCESS  read-only
   	STATUS      current
   	DESCRIPTION
       "The value when alarmActiveVariableType is 'integer32'."
   		::= { rcEventHistoryVariableEntry 7 }

	rcEventHistoryVariableOctetStringVal OBJECT-TYPE
   	SYNTAX      OCTET STRING (SIZE(0..65535))
   	MAX-ACCESS  read-only
   	STATUS      current
   	DESCRIPTION
       "The value when alarmActiveVariableType is 'octetString'."
   		::= { rcEventHistoryVariableEntry 8 }

	rcEventHistoryVariableIpAddressVal OBJECT-TYPE
   	SYNTAX      IpAddress
   	MAX-ACCESS  read-only
   	STATUS      current
   	DESCRIPTION
       "The value when alarmActiveVariableType is 'ipAddress'."
   		::= { rcEventHistoryVariableEntry 9 }

	rcEventHistoryVariableOidVal OBJECT-TYPE
   	SYNTAX      OBJECT IDENTIFIER
   	MAX-ACCESS  read-only
   	STATUS      current
   	DESCRIPTION
       "The value when alarmActiveVariableType is 'objectId'."
   		::= { rcEventHistoryVariableEntry 10 }

	rcEventHistoryVariableCounter64Val OBJECT-TYPE
   	SYNTAX      Counter64
   	MAX-ACCESS  read-only
   	STATUS      current
   	DESCRIPTION
       "The value when alarmActiveVariableType is 'counter64'."
   		::= { rcEventHistoryVariableEntry 11 }

	rcEventHistoryVariableOpaqueVal OBJECT-TYPE
   	SYNTAX      Opaque (SIZE(0..65535))
   	MAX-ACCESS  read-only
   	STATUS      current
   	DESCRIPTION
       "The value when alarmActiveVariableType is 'opaque'.

       of Opaque in 'standard' MIB modules, this particular
       usage is driven by the need to be able to accurately
       represent any well-formed notification, and justified
       by the need for backward compatibility."
   		::= { rcEventHistoryVariableEntry 12 }  
   		
-- Statistics --

	rcEventHistoryStatsTable   OBJECT-TYPE
    SYNTAX  SEQUENCE OF RcEventHistoryStatsEntry
    MAX-ACCESS  not-accessible
    STATUS  current
    DESCRIPTION
         "This table represents the event statistics
         information."
  		::= { rcEventManagerObjects 9 }

	rcEventHistoryStatsEntry OBJECT-TYPE
	SYNTAX  RcEventHistoryStatsEntry
	MAX-ACCESS  not-accessible
	STATUS  current
	DESCRIPTION
         "Statistics on the current events."
	INDEX   { alarmListName }
		::= {  rcEventHistoryStatsTable 1 }

	RcEventHistoryStatsEntry ::=
      SEQUENCE {
           rcEventHistoryStatsCurrent  Gauge32,
           rcEventHistoryStats        ZeroBasedCounter32
           }

	rcEventHistoryStatsCurrent OBJECT-TYPE
	SYNTAX Gauge32
	MAX-ACCESS read-only
	STATUS  current
	DESCRIPTION
         "The total number of currently active alarms on the system."
		::= { rcEventHistoryStatsEntry 1 }

	rcEventHistoryStats OBJECT-TYPE
	SYNTAX ZeroBasedCounter32
	MAX-ACCESS read-only
	STATUS  current
	DESCRIPTION
         "The total number of active alarms since system restarted."
		::= { rcEventHistoryStatsEntry 2 }
END
