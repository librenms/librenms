-- -----------------------------------------------------------------------------
-- MIB NAME : rcIsolateGroup
-- FILE NAME: raisecom-isolate-mib.mi2			
-- DATE     : 2011/10/25						
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2011/10/25, xiaoyingjie
-- This is the first formal version for universal MIB definition.
 
SWITCH-ISOLATE-MIB DEFINITIONS ::= BEGIN
     
	IMPORTS
		MODULE-IDENTITY,
		OBJECT-TYPE,
		NOTIFICATION-TYPE,
		Integer32,
		IpAddress,
		Counter32,
		Unsigned32
			FROM SNMPv2-SMI    
		RowStatus
			FROM SNMPv2-TC
		raisecomSwitchMgt
			FROM RAISECOM-PONSERIES-BASE-MIB;
			
	rcIsolateGroup MODULE-IDENTITY
		LAST-UPDATED 	"201107200000Z"
		ORGANIZATION 	"rc TECH, Ltd."
		CONTACT-INFO 	"www.rc.com"
		DESCRIPTION  	
		    "The MIB module defining objects for port and vlan isolate functions"
		::= { raisecomSwitchMgt  10}

--rcIsolateGroup
	
	rcPortIsolateConfig OBJECT IDENTIFIER ::= { rcIsolateGroup 1 }
	rcVlanIsolateConfig OBJECT IDENTIFIER ::= { rcIsolateGroup 2 }
	
	rcPortIsolateGroupNextId OBJECT-TYPE
		SYNTAX INTEGER
		MAX-ACCESS read-only
		STATUS current
		DESCRIPTION  "The  next available groupId."
        	::= { rcPortIsolateConfig 1 } 
         	
    -- port isolate table
	rcPortIsolateTable    OBJECT-TYPE
		SYNTAX          SEQUENCE OF  RcPortIsolateEntry
        MAX-ACCESS      not-accessible
        STATUS          current
        DESCRIPTION     "port isolate table"
    		::= { rcPortIsolateConfig 2 }    
    
     rcPortIsolateEntry  OBJECT-TYPE
		SYNTAX          RcPortIsolateEntry
		MAX-ACCESS      not-accessible
        STATUS          current
		DESCRIPTION     "An entry in the rcPortIsolateTable."
			INDEX { rcPortIsolateGroupId }
			::= { rcPortIsolateTable 1 }
		
	RcPortIsolateEntry ::=
		SEQUENCE { 
		rcPortIsolateGroupId				INTEGER,
		rcPortIsolateGroupPortList 			OCTET STRING (SIZE (1..512)),
		rcPortIsolateGroupRowStatus			RowStatus
		}		
    
	rcPortIsolateGroupId  OBJECT-TYPE
        SYNTAX 			INTEGER
        MAX-ACCESS 		read-only
        STATUS 			current
        DESCRIPTION		"The index of rcPortIsolateTable."
        ::= { rcPortIsolateEntry 1 }        
         
    rcPortIsolateGroupPortList  OBJECT-TYPE
        SYNTAX 			OCTET STRING (SIZE (1..512))
        MAX-ACCESS 		read-write
        STATUS 			current
        DESCRIPTION		"The port list."
        ::= { rcPortIsolateEntry 2 }    
        
    rcPortIsolateGroupRowStatus  OBJECT-TYPE
        SYNTAX 			RowStatus
        MAX-ACCESS 		read-create
        STATUS 			current
        DESCRIPTION		"The row status of this table entry."
        ::= { rcPortIsolateEntry 3 }   
 
    -- vlan isolate table
	rcVlanIsolateTable    OBJECT-TYPE
		SYNTAX          SEQUENCE OF  RcVlanIsolateEntry
        MAX-ACCESS      not-accessible
        STATUS          current
        DESCRIPTION     "vlan isolate table"
    		::= { rcVlanIsolateConfig 1 }    
    
     rcVlanIsolateEntry  OBJECT-TYPE
		SYNTAX          RcVlanIsolateEntry
		MAX-ACCESS      not-accessible
        STATUS          current
		DESCRIPTION     "An entry in the rcVlanIsolateTable."
			INDEX { rcVlanIsolateValnIndex,rcVlanIsolateGroupId }
			::= { rcVlanIsolateTable 1 }
		
	RcVlanIsolateEntry ::=
		SEQUENCE { 
		rcVlanIsolateValnIndex				INTEGER,
		rcVlanIsolateGroupId				INTEGER,
		rcVlanIsolateGroupPortList 			OCTET STRING (SIZE (1..512)),
		rcVlanIsolateRowStatus			    RowStatus
		}   

	rcVlanIsolateValnIndex  OBJECT-TYPE
        SYNTAX 			INTEGER
        MAX-ACCESS 		read-only
        STATUS 			current
        DESCRIPTION		"The index of rcVlanIsolateTable."
        ::= { rcVlanIsolateEntry 1 }        

	rcVlanIsolateGroupId  OBJECT-TYPE
        SYNTAX 			INTEGER
        MAX-ACCESS 		read-only
        STATUS 			current
        DESCRIPTION		"The index of rcVlanIsolateTable."
        ::= { rcVlanIsolateEntry 2 }
                 
    rcVlanIsolateGroupPortList  OBJECT-TYPE
        SYNTAX 			OCTET STRING (SIZE (1..512))
        MAX-ACCESS 		read-write
        STATUS 			current
        DESCRIPTION		"The port list."
        ::= { rcVlanIsolateEntry 3 }    
        
    rcVlanIsolateRowStatus  OBJECT-TYPE
        SYNTAX 			RowStatus
        MAX-ACCESS 		read-create
        STATUS 			current
        DESCRIPTION		"The row status of this table entry."
        ::= { rcVlanIsolateEntry 4 } 
END
