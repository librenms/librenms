--MibName=switch-l2muticast-mib
SWITCH-L2MUTICAST-MIB DEFINITIONS ::= BEGIN

IMPORTS
    MODULE-IDENTITY, OBJECT-TYPE,
    RowStatus,TruthValue,MacAddress		FROM SNMPv2-TC 
    Vlanset,PortList,EnableVar	FROM SWITCH-TC   
	InetAddressType,InetAddress,InetAddressIPv6,InetAddressIPv4 FROM INET-ADDRESS-MIB
	InterfaceIndex				FROM IF-MIB
	VlanIndex,VlanId            FROM Q-BRIDGE-MIB	   
    raisecomSwitchMgt           FROM RAISECOM-PONSERIES-BASE-MIB;
                
roapL2Muticast MODULE-IDENTITY
    LAST-UPDATED "1203200000Z"
    ORGANIZATION "roap Group"
    CONTACT-INFO
            ""
    DESCRIPTION
            "The MIB module for l2 muticast."
    REVISION     "1203200000Z"
    DESCRIPTION
            ""
    ::= { raisecomSwitchMgt 19}   


roapL2MuticastBase		OBJECT IDENTIFIER ::= {	roapL2Muticast 1 } 
roapL2MuticastIgmp		OBJECT IDENTIFIER ::= {	roapL2Muticast 2 } 
roapL2MuticastMld		OBJECT IDENTIFIER ::= {	roapL2Muticast 3 }
roapL2MuticastMvr		OBJECT IDENTIFIER ::= {	roapL2Muticast 4 }
roapMuticastCtrl		OBJECT IDENTIFIER ::= {	roapL2Muticast 5 }

-----------------------------------------------------------------------------
roapL2MuticastBaseScalar		OBJECT IDENTIFIER ::= {	roapL2MuticastBase 1 }
roapL2MuticastIgmpScalar		OBJECT IDENTIFIER ::= {	roapL2MuticastIgmp 1 }
roapL2MuticastMldScalar			OBJECT IDENTIFIER ::= {	roapL2MuticastMld 1 }
roapL2MuticastMvrScalar			OBJECT IDENTIFIER ::= {	roapL2MuticastMvr 1 }

roapL2MuticastUnknownFilterVlanlist OBJECT-TYPE           
        SYNTAX        	Vlanset 
		MAX-ACCESS  	read-write
        STATUS      	current
        DESCRIPTION
               " "
         ::= { roapL2MuticastBaseScalar 1 } 

roapL2MuticastVlanAnyGroupVlanId   OBJECT-TYPE           
        SYNTAX        	VlanId 
		MAX-ACCESS  	read-write
        STATUS      	current
        DESCRIPTION
               " "
         ::= { roapL2MuticastBaseScalar 2 } 
           
--roapL2MuticastAddressTable
	roapL2MuticastAddressTable OBJECT-TYPE
        SYNTAX SEQUENCE OF RoapL2MuticastAddressEntry
        MAX-ACCESS      not-accessible
        STATUS current
        DESCRIPTION
            " "
        ::= { roapL2MuticastBase 2 }
        
	roapL2MuticastAddressEntry OBJECT-TYPE
	    SYNTAX     RoapL2MuticastAddressEntry
        MAX-ACCESS not-accessible
        STATUS     current
        DESCRIPTION
                ""
        INDEX      { roapL2MuticastAddress, roapL2MuticastAddressVlanIndex}
        ::= { roapL2MuticastAddressTable 1 }
        
	RoapL2MuticastAddressEntry ::= SEQUENCE {    
		roapL2MuticastAddressVlanIndex		  		VlanId,        
        roapL2MuticastAddress        				MacAddress,
        roapL2MuticastAddressEgressPorts    		PortList,
        roapL2MuticastAddressStaticEgressPorts   	PortList,
        roapL2MuticastAddressType					INTEGER,
        roapL2MuticastAddressRowStatus				RowStatus
        }

	roapL2MuticastAddressVlanIndex OBJECT-TYPE
	        SYNTAX        VlanId  
	        MAX-ACCESS    read-create 
	        STATUS        current
		DESCRIPTION  
			" "
	        ::= { roapL2MuticastAddressEntry 1 }
	        
    
	roapL2MuticastAddress OBJECT-TYPE
	        SYNTAX        MacAddress  
	        MAX-ACCESS    read-create 
	        STATUS        current
		DESCRIPTION  
			" "
	        ::= { roapL2MuticastAddressEntry 2 }
	        	        	        
	roapL2MuticastAddressEgressPorts OBJECT-TYPE
	        SYNTAX        PortList  
	        MAX-ACCESS    read-only 
	        STATUS        current
		DESCRIPTION  
			" "
	        ::= { roapL2MuticastAddressEntry 3 }
	              
	roapL2MuticastAddressStaticEgressPorts OBJECT-TYPE
	        SYNTAX        PortList  
	        MAX-ACCESS    read-write 
	        STATUS        current
		DESCRIPTION  
			" "
	        ::= { roapL2MuticastAddressEntry 4 }
	        
	roapL2MuticastAddressType OBJECT-TYPE
	        SYNTAX        INTEGER{
				dynamic(1),
				static(2)                
				}
	        MAX-ACCESS    read-only 
	        STATUS        current
		DESCRIPTION  
			" "
	        ::= { roapL2MuticastAddressEntry 5 }   
	        
	roapL2MuticastAddressRowStatus OBJECT-TYPE
	        SYNTAX        RowStatus  
	        MAX-ACCESS    read-create 
	        STATUS        current
		DESCRIPTION  
			" "
	        ::= { roapL2MuticastAddressEntry 6 }   
	        
--roapL2MuticastVlanTable	        
	roapL2MuticastVlanTable OBJECT-TYPE
        SYNTAX SEQUENCE OF RoapL2MuticastVlanEntry
        MAX-ACCESS      not-accessible
        STATUS current
        DESCRIPTION
            " "
        ::= { roapL2MuticastBase 3 }
        
	roapL2MuticastVlanEntry OBJECT-TYPE
	    SYNTAX     RoapL2MuticastVlanEntry
        MAX-ACCESS not-accessible
        STATUS     current
        DESCRIPTION
                ""
        INDEX      {roapL2MuticastVlanIndex}
        ::= { roapL2MuticastVlanTable 1 }
        
	RoapL2MuticastVlanEntry ::= SEQUENCE {    
        roapL2MuticastVlanIndex        		VlanId,
		roapL2MuticastVlanMode		  		INTEGER,
        roapL2MuticastVlanCVlanForward    	INTEGER,
        roapL2MuticastVlanUpPriority   		INTEGER,
        roapL2MuticastVlanDownPriority		INTEGER,
        roapL2MuticastVlanRowStaus         	RowStatus
        }
    
	roapL2MuticastVlanIndex OBJECT-TYPE
	        SYNTAX        VlanId 
	        MAX-ACCESS    read-create 
	        STATUS        current
		DESCRIPTION  
			" "
	        ::= { roapL2MuticastVlanEntry 1 }
	        
	roapL2MuticastVlanMode OBJECT-TYPE
	        SYNTAX        INTEGER{
		        snooping(1),
		        proxy(2)
		        }  
	        MAX-ACCESS    read-write 
	        STATUS        current
			DESCRIPTION  
			" "
	        ::= { roapL2MuticastVlanEntry 2 }
	        
	        	        
	roapL2MuticastVlanCVlanForward OBJECT-TYPE
	        SYNTAX        EnableVar  
	        MAX-ACCESS    read-write 
	        STATUS        current
			DESCRIPTION  
			" "
			DEFVAL 		{ 2 }			
	        ::= { roapL2MuticastVlanEntry 3 }
	              
	roapL2MuticastVlanUpPriority OBJECT-TYPE
	        SYNTAX        INTEGER{
	        cos0(0),
	        cos1(1),
	        cos2(2),
	        cos3(3),
	        cos4(4),
	        cos5(5),
	        cos6(6),
	        cos7(7),
	        keep(8)
	        }
	        MAX-ACCESS    read-create 
	        STATUS        current
			DESCRIPTION  
			" "
			DEFVAL 		{ 9 }
	        ::= { roapL2MuticastVlanEntry 4 }
	        
	roapL2MuticastVlanDownPriority OBJECT-TYPE
	        SYNTAX        INTEGER{
	        cos0(0),
	        cos1(1),
	        cos2(2),
	        cos3(3),
	        cos4(4),
	        cos5(5),
	        cos6(6),
	        cos7(7),
	        keep(8)
	        }  
	        MAX-ACCESS    read-write 
	        STATUS        current
			DESCRIPTION  
			" " 
			DEFVAL 		{ 9 }
	        ::= { roapL2MuticastVlanEntry 5 }   
	        	        
	roapL2MuticastVlanRowStaus OBJECT-TYPE
	        SYNTAX        RowStatus  
	        MAX-ACCESS    read-create 
	        STATUS        current
			DESCRIPTION  
			" "
	        ::= { roapL2MuticastVlanEntry 6 } 
	        
--roapL2MuticastVlanGroupTable		        
	roapL2MuticastVlanGroupTable OBJECT-TYPE
	        SYNTAX SEQUENCE OF RoapL2MuticastVlanGroupEntry
	        MAX-ACCESS      not-accessible
	        STATUS current
	        DESCRIPTION
	            " "
	        ::= { roapL2MuticastBase 4 }
        
	roapL2MuticastVlanGroupEntry OBJECT-TYPE
		    SYNTAX     RoapL2MuticastVlanGroupEntry
	        MAX-ACCESS not-accessible
	        STATUS     current
	        DESCRIPTION
	                ""
	        INDEX      { roapL2MuticastVlanGroupIpType, roapL2MuticastVlanGroupIp}
	        ::= { roapL2MuticastVlanGroupTable 1 }
        
	RoapL2MuticastVlanGroupEntry ::= SEQUENCE {    
	        roapL2MuticastVlanGroupIpType		InetAddressType,
	        roapL2MuticastVlanGroupIp			InetAddress,
			roapL2MuticastVlanGroupVlanIndex	VlanId,	        
	        roapL2MuticastVlanGroupRowStatus	RowStatus
	        }
	        	         	        	        
	roapL2MuticastVlanGroupIpType OBJECT-TYPE
	        SYNTAX        InetAddressType  
	        MAX-ACCESS    read-create 
	        STATUS        current
			DESCRIPTION  
			" "
	        ::= { roapL2MuticastVlanGroupEntry 1 } 
	        
	roapL2MuticastVlanGroupIp OBJECT-TYPE
	        SYNTAX        InetAddress(SIZE(0..20)) 
	        MAX-ACCESS    read-create 
	        STATUS        current
			DESCRIPTION  
			" "
	        ::= { roapL2MuticastVlanGroupEntry 2 } 

	roapL2MuticastVlanGroupVlanIndex OBJECT-TYPE
	        SYNTAX        VlanId  
	        MAX-ACCESS    read-create 
	        STATUS        current
			DESCRIPTION  
			" "
	        ::= { roapL2MuticastVlanGroupEntry 3 }
	        
	roapL2MuticastVlanGroupRowStatus OBJECT-TYPE
	        SYNTAX        RowStatus  
	        MAX-ACCESS    read-create 
	        STATUS        current
			DESCRIPTION  
			" "
	        ::= { roapL2MuticastVlanGroupEntry 4 }

--roapL2MuticastVlanIfTable
	roapL2MuticastVlanRouterTable OBJECT-TYPE
	        SYNTAX SEQUENCE OF RoapL2MuticastVlanRouterEntry
	        MAX-ACCESS      not-accessible
	        STATUS current
	        DESCRIPTION
	            " "
	        ::= { roapL2MuticastBase 5 }
	        
	roapL2MuticastVlanRouterEntry OBJECT-TYPE
		    SYNTAX     RoapL2MuticastVlanRouterEntry
	        MAX-ACCESS not-accessible
	        STATUS     current
	        DESCRIPTION
	                ""
	        INDEX      { roapL2MuticastVlanRouterVlanIndex,roapL2MuticastVlanRouterIfindex}
	        ::= { roapL2MuticastVlanRouterTable 1 }
        
	RoapL2MuticastVlanRouterEntry ::= SEQUENCE {    
	        roapL2MuticastVlanRouterVlanIndex	VlanId,
			roapL2MuticastVlanRouterIfindex		InterfaceIndex,
	        roapL2MuticastVlanRouterRowStatus   RowStatus,
	        roapL2MuticastVlanRouterStatic      INTEGER
	        }
	         
	roapL2MuticastVlanRouterVlanIndex OBJECT-TYPE
	        SYNTAX        VlanId  
	        MAX-ACCESS    read-create 
	        STATUS        current
			DESCRIPTION  
			" "
	        ::= { roapL2MuticastVlanRouterEntry 1 }
	        
	roapL2MuticastVlanRouterIfindex OBJECT-TYPE
	        SYNTAX        InterfaceIndex  
	        MAX-ACCESS    read-create 
	        STATUS        current
			DESCRIPTION  
			" "
	        ::= { roapL2MuticastVlanRouterEntry 2 }
	        
	roapL2MuticastVlanRouterRowStatus OBJECT-TYPE
	        SYNTAX        RowStatus  
	        MAX-ACCESS    read-create 
	        STATUS        current
			DESCRIPTION  
			" "
	        ::= { roapL2MuticastVlanRouterEntry 3 }   
	        
	roapL2MuticastVlanRouterStatic OBJECT-TYPE
	        SYNTAX        INTEGER{static(1),dynamic(2),other(3)}  
	        MAX-ACCESS    read-only 
	        STATUS        current
			DESCRIPTION  
			" "
	        ::= { roapL2MuticastVlanRouterEntry 4 } 
       

--roapL2MuticastVlanIfTable
	roapL2MuticastVlanMemberTable OBJECT-TYPE
	        SYNTAX SEQUENCE OF RoapL2MuticastVlanMemberEntry
	        MAX-ACCESS      not-accessible
	        STATUS current
	        DESCRIPTION
	            " "
	        ::= { roapL2MuticastBase 6 }
	        
	roapL2MuticastVlanMemberEntry OBJECT-TYPE
		    SYNTAX     RoapL2MuticastVlanMemberEntry
	        MAX-ACCESS not-accessible
	        STATUS     current
	        DESCRIPTION
	                ""
	        INDEX      { roapL2MuticastVlanMemberVlanIndex,roapL2MuticastVlanMemberIfindex}
	        ::= { roapL2MuticastVlanMemberTable 1 }
        
	RoapL2MuticastVlanMemberEntry ::= SEQUENCE {    
	        roapL2MuticastVlanMemberVlanIndex		VlanId,
			roapL2MuticastVlanMemberIfindex			InterfaceIndex,
			roapL2MuticastVlanMemberImmLeaveEnable	EnableVar,
	        roapL2MuticastVlanMemberRowStatus   	RowStatus,
	        roapL2MuticastVlanMemberStatic          INTEGER
	        }
	         
	roapL2MuticastVlanMemberVlanIndex OBJECT-TYPE
	        SYNTAX        VlanId  
	        MAX-ACCESS    read-create 
	        STATUS        current
			DESCRIPTION  
			" "
	        ::= { roapL2MuticastVlanMemberEntry 1 }
	        
	roapL2MuticastVlanMemberIfindex OBJECT-TYPE
	        SYNTAX        InterfaceIndex  
	        MAX-ACCESS    read-create 
	        STATUS        current
			DESCRIPTION  
			" "
	        ::= { roapL2MuticastVlanMemberEntry 2 }

	roapL2MuticastVlanMemberImmLeaveEnable OBJECT-TYPE
	        SYNTAX        EnableVar  
	        MAX-ACCESS    read-write 
	        STATUS        current
			DESCRIPTION  
			" "
	        ::= { roapL2MuticastVlanMemberEntry 3 }
	        
	roapL2MuticastVlanMemberRowStatus OBJECT-TYPE
	        SYNTAX        RowStatus  
	        MAX-ACCESS    read-create 
	        STATUS        current
			DESCRIPTION  
			" "
	        ::= { roapL2MuticastVlanMemberEntry 4 }    
	        
	roapL2MuticastVlanMemberStatic OBJECT-TYPE
	        SYNTAX        INTEGER{static(1),dynamic(2),other(3)}  
	        MAX-ACCESS    read-only 
	        STATUS        current
			DESCRIPTION  
			" "
	        ::= { roapL2MuticastVlanMemberEntry 5 } 
	            
--roapL2MuticastIgmpScalar	        
roapL2MuticastIgmpEnable OBJECT-TYPE           
        SYNTAX      EnableVar  
		MAX-ACCESS  read-write
        STATUS      current
        DESCRIPTION
               " "
        DEFVAL { 2 }
        ::= { roapL2MuticastIgmpScalar 1 }  
        
        
roapL2MuticastIgmpSnoopingTimeout OBJECT-TYPE           
        SYNTAX      INTEGER(0|30..3600)  
		MAX-ACCESS  read-write
        STATUS      current
        DESCRIPTION
               " "
        DEFVAL { 300 }
        ::= { roapL2MuticastIgmpScalar 2 }
        
        
roapL2MuticastIgmpProxyVersion OBJECT-TYPE           
        SYNTAX        INTEGER{
			v1(1),	
			v2(2),
			v3(3)        
        } 
		MAX-ACCESS  read-write
        STATUS      current
        DESCRIPTION
               " "
        DEFVAL { 3 }
        ::= { roapL2MuticastIgmpScalar 3 }
        
        
roapL2MuticastIgmpProxyQueryInterval OBJECT-TYPE           
        SYNTAX        	INTEGER(10..65535) 
		MAX-ACCESS  	read-write
        STATUS      	current
        DESCRIPTION
               " "
        DEFVAL { 125 }
        ::= { roapL2MuticastIgmpScalar 4 }
        
roapL2MuticastIgmpProxyQueryMaxResponse OBJECT-TYPE           
        SYNTAX        	INTEGER(1..25)  
		MAX-ACCESS  	read-write
        STATUS      	current
        DESCRIPTION
               " "
        DEFVAL { 5 }
        ::= { roapL2MuticastIgmpScalar 5 }
        
roapL2MuticastIgmpProxyLastQueryInterval OBJECT-TYPE           
        SYNTAX        	INTEGER(1..25)  
		MAX-ACCESS  	read-write
        STATUS      	current
        DESCRIPTION
               " "
        DEFVAL { 10 }
        ::= { roapL2MuticastIgmpScalar 6 } 
        
roapL2MuticastIgmpProxyLastQueryCount OBJECT-TYPE           
        SYNTAX        	INTEGER(2..5)  
		MAX-ACCESS  	read-write
        STATUS      	current
        DESCRIPTION
               " "
        DEFVAL { 2 }
        ::= { roapL2MuticastIgmpScalar 7 }  
        
roapL2MuticastIgmpProxySourceIp OBJECT-TYPE           
        SYNTAX  	InetAddressIPv4       
		MAX-ACCESS  read-write
        STATUS      current
        DESCRIPTION
               " "
        ::= { roapL2MuticastIgmpScalar 8 }                                          	        

roapL2MuticastIgmpProxyRobustnesss OBJECT-TYPE           
        SYNTAX  	INTEGER(1..5)       
		MAX-ACCESS  read-write
        STATUS      current
        DESCRIPTION
               " "
        ::= { roapL2MuticastIgmpScalar 9 }    
        	        
--roapL2MuticastMldScalar     
roapL2MuticastMldEnable OBJECT-TYPE           
        SYNTAX      EnableVar  
		MAX-ACCESS  read-write
        STATUS      current
        DESCRIPTION
               " "
        DEFVAL { 2 }
        ::= { roapL2MuticastMldScalar 1 }        
        
roapL2MuticastMldSnoopingTimeout OBJECT-TYPE           
        SYNTAX      INTEGER(0..3600)  
		MAX-ACCESS  read-write
        STATUS      current
        DESCRIPTION
               " "
        DEFVAL { 300 }
        ::= { roapL2MuticastMldScalar 2 }
        
        
roapL2MuticastMldProxyVersion OBJECT-TYPE           
        SYNTAX        INTEGER{
			v1(1),
			v2(2)        
        } 
		MAX-ACCESS  read-write
        STATUS      current
        DESCRIPTION
               " "
        DEFVAL { 2 }
        ::= { roapL2MuticastMldScalar 3 }
        
        
roapL2MuticastMldProxyQueryInterval OBJECT-TYPE           
        SYNTAX        	INTEGER(10..65535) 
		MAX-ACCESS  	read-write
        STATUS      	current
        DESCRIPTION
               " "
        DEFVAL { 125 }
        ::= { roapL2MuticastMldScalar 4 }
        
roapL2MuticastMldProxyQueryMaxResponse OBJECT-TYPE           
        SYNTAX        	INTEGER(1..25)  
		MAX-ACCESS  	read-write
        STATUS      	current
        DESCRIPTION
               " "
        DEFVAL { 5 }
        ::= { roapL2MuticastMldScalar 5 }
        
roapL2MuticastMldProxyLastQueryInterval OBJECT-TYPE           
        SYNTAX        	INTEGER(1..25)  
		MAX-ACCESS  	read-write
        STATUS      	current
        DESCRIPTION
               " "
        DEFVAL { 2 }
        ::= { roapL2MuticastMldScalar 6 } 
        
roapL2MuticastMldProxyLastQueryCount OBJECT-TYPE           
        SYNTAX        	INTEGER(2..5)  
		MAX-ACCESS  	read-write
        STATUS      	current
        DESCRIPTION
               " "
        DEFVAL { 2 }
        ::= { roapL2MuticastMldScalar 7 }  
        
roapL2MuticastMldProxySourceIp OBJECT-TYPE           
        SYNTAX  	InetAddressIPv6       
		MAX-ACCESS  read-write
        STATUS      current
        DESCRIPTION
               " "
        ::= { roapL2MuticastMldScalar 8 }     	        
	        
roapL2MuticastMldProxyRobustnesss OBJECT-TYPE           
        SYNTAX  	INTEGER(1..5)       
		MAX-ACCESS  read-write
        STATUS      current
        DESCRIPTION
               " "
        ::= { roapL2MuticastMldScalar 9 }  
        	        
--roapL2MuticastMvrScalar
roapL2MuticastMvrEnable OBJECT-TYPE           
        SYNTAX        	EnableVar  
		MAX-ACCESS  	read-write
        STATUS      	current
        DESCRIPTION
               " "
        DEFVAL { 2 }
        ::= { roapL2MuticastMvrScalar 1 } 
        


---roapMuticastCtrl--------------------------------------------------------------------------

roapMuticastCtrlScalar		OBJECT IDENTIFIER ::= {	roapMuticastCtrl 1 }  

roapMuticastCtrlEnable OBJECT-TYPE           
        SYNTAX      EnableVar  
		MAX-ACCESS  read-write
        STATUS      current
        DESCRIPTION
               " "
        DEFVAL { 2 }
        ::= { roapMuticastCtrlScalar 1 }

roapMuticastCtrlMaxNoReportDuration OBJECT-TYPE           
        SYNTAX      INTEGER  
		MAX-ACCESS  read-write
        STATUS      current
        DESCRIPTION
               "unit min"
        DEFVAL { 5 }
        ::= { roapMuticastCtrlScalar 2 }

----------PreviewScalar-----------
roapMuticastCtrlPreviewScalar	OBJECT IDENTIFIER ::= {	roapMuticastCtrlScalar 3 }  

roapMuticastCtrlPreviewEnable OBJECT-TYPE           
        SYNTAX      EnableVar  
		MAX-ACCESS  read-write
        STATUS      current
        DESCRIPTION
               " "
        DEFVAL { 1 }
        ::= { roapMuticastCtrlPreviewScalar 1 }
        
roapMuticastCtrlPreviewReset OBJECT-TYPE           
        SYNTAX        INTEGER{
			notdoing(0),
			reset(1)   
        } 
		MAX-ACCESS  read-write
        STATUS      current
        DESCRIPTION
               " "
        ::= { roapMuticastCtrlPreviewScalar 2 }
        
roapMuticastCtrlPreviewAutoResetPeriod OBJECT-TYPE           
        SYNTAX        INTEGER{
			daily(1),
			week(2),
			month(3)        
        } 
		MAX-ACCESS  read-write
        STATUS      current
        DESCRIPTION
               " "
        DEFVAL { 2 }
        ::= { roapMuticastCtrlPreviewScalar 3 }
        
roapMuticastCtrlPreviewAutoResetTime OBJECT-TYPE           
        SYNTAX      INTEGER  
		MAX-ACCESS  read-write
        STATUS      current
        DESCRIPTION
               " "
        ::= { roapMuticastCtrlPreviewScalar 4 }
        
roapMuticastCtrlPreviewAwareTime OBJECT-TYPE           
        SYNTAX      INTEGER(1..60)  
		MAX-ACCESS  read-write
        STATUS      current
        DESCRIPTION
               "unit:s"
        DEFVAL { 4 }
        ::= { roapMuticastCtrlPreviewScalar 5 }
        
----------CdrScalar-----------
roapMuticastCtrlCdrScalar	OBJECT IDENTIFIER ::= {	roapMuticastCtrlScalar 4 }  

roapMuticastCtrlCdrEnable OBJECT-TYPE           
        SYNTAX      EnableVar  
		MAX-ACCESS  read-write
        STATUS      current
        DESCRIPTION
               " "
        DEFVAL { 1 }
        ::= { roapMuticastCtrlCdrScalar 1 }

roapMuticastCtrlCdrSeverAddrType OBJECT-TYPE           
        SYNTAX      InetAddressType  
		MAX-ACCESS  read-write
        STATUS      current
        DESCRIPTION
               " "
        ::= { roapMuticastCtrlCdrScalar 2 }

roapMuticastCtrlCdrSeverAddr OBJECT-TYPE           
        SYNTAX      InetAddress  
		MAX-ACCESS  read-write
        STATUS      current
        DESCRIPTION
               " "
        ::= { roapMuticastCtrlCdrScalar 3 }

roapMuticastCtrlCdrMaxRecords OBJECT-TYPE           
        SYNTAX      INTEGER(500..65535)  
		MAX-ACCESS  read-write
        STATUS      current
        DESCRIPTION
               " "  
        DEFVAL {65535}
        ::= { roapMuticastCtrlCdrScalar 4 }

roapMuticastCtrlCdrReport OBJECT-TYPE           
        SYNTAX      INTEGER{
			notdoing(0),
			report(1)   
        }  
		MAX-ACCESS  read-write
        STATUS      current
        DESCRIPTION
               " "  
        ::= { roapMuticastCtrlCdrScalar 5 }

roapMuticastCtrlCdrReportInterval OBJECT-TYPE           
        SYNTAX      INTEGER(1..30)  
		MAX-ACCESS  read-write
        STATUS      current
        DESCRIPTION
               "unit:min"
        DEFVAL {5}  
        ::= { roapMuticastCtrlCdrScalar 6 }

roapMuticastCtrlCdrReportThreshold OBJECT-TYPE           
        SYNTAX      INTEGER(300..65535)  
		MAX-ACCESS  read-write
        STATUS      current
        DESCRIPTION
               " "
        DEFVAL {300}  
        ::= { roapMuticastCtrlCdrScalar 7 }

roapMuticastCtrlCdrAwareTime OBJECT-TYPE           
        SYNTAX      INTEGER(1..60)  
		MAX-ACCESS  read-write
        STATUS      current
        DESCRIPTION
               "unit:s"
        DEFVAL {4}  
        ::= { roapMuticastCtrlCdrScalar 8 }

roapMuticastCtrlCdrClear OBJECT-TYPE           
        SYNTAX      INTEGER{
			notdoing(0),
			clear(1)   
        }  
		MAX-ACCESS  read-write
        STATUS      current
        DESCRIPTION
               " "  
        ::= { roapMuticastCtrlCdrScalar 9 }

----------------------------------------------
roapMuticastCtrlPreviewProfileIDNext  OBJECT-TYPE      
        SYNTAX      INTEGER(1..64)  
		MAX-ACCESS  read-write
        STATUS      current
        DESCRIPTION
               " "
        ::= { roapMuticastCtrl 2 }

-----roapMuticastCtrlPreviewProfileTable
roapMuticastCtrlPreviewProfileTable OBJECT-TYPE
        SYNTAX SEQUENCE OF RoapMuticastCtrlPreviewProfileEntry
        MAX-ACCESS      not-accessible
        STATUS current
        DESCRIPTION
            " "
        ::= { roapMuticastCtrl 3 }

roapMuticastCtrlPreviewProfileEntry OBJECT-TYPE
	    SYNTAX     RoapMuticastCtrlPreviewProfileEntry
        MAX-ACCESS not-accessible
        STATUS     current
        DESCRIPTION
                " "
        INDEX      { roapMuticastCtrlPreviewProfileID }
        ::= { roapMuticastCtrlPreviewProfileTable 1 }

RoapMuticastCtrlPreviewProfileEntry ::= SEQUENCE {    
        roapMuticastCtrlPreviewProfileID		    INTEGER,
		roapMuticastCtrlPreviewProfileName			OCTET STRING,
		roapMuticastCtrlPreviewProfileTotalTime	    INTEGER,
		roapMuticastCtrlPreviewProfileCount		    INTEGER,
		roapMuticastCtrlPreviewProfileDuration		INTEGER,
		roapMuticastCtrlPreviewProfileInterval	    INTEGER,
        roapMuticastCtrlPreviewProfileRowStatus   	RowStatus
        }

roapMuticastCtrlPreviewProfileID OBJECT-TYPE
        SYNTAX        INTEGER(1..64)  
        MAX-ACCESS    read-create 
        STATUS        current
		DESCRIPTION  
		" "
        ::= { roapMuticastCtrlPreviewProfileEntry 1 }
        
roapMuticastCtrlPreviewProfileName OBJECT-TYPE
        SYNTAX        OCTET STRING(SIZE(16))  
        MAX-ACCESS    read-create 
        STATUS        current
		DESCRIPTION  
		" "
        ::= { roapMuticastCtrlPreviewProfileEntry 2 }

roapMuticastCtrlPreviewProfileTotalTime OBJECT-TYPE
        SYNTAX        INTEGER(1..12000)  
        MAX-ACCESS    read-create 
        STATUS        current
		DESCRIPTION  
		"unit:s"
		DEFVAL {3600}
        ::= { roapMuticastCtrlPreviewProfileEntry 3 }

roapMuticastCtrlPreviewProfileCount OBJECT-TYPE
        SYNTAX        INTEGER(1..100)  
        MAX-ACCESS    read-create 
        STATUS        current
		DESCRIPTION  
		" "
		DEFVAL {3}
        ::= { roapMuticastCtrlPreviewProfileEntry 4 }
	        
roapMuticastCtrlPreviewProfileDuration OBJECT-TYPE
        SYNTAX        INTEGER(1..6000)  
        MAX-ACCESS    read-create 
        STATUS        current
		DESCRIPTION  
		"unit:s"
		DEFVAL {300}
        ::= { roapMuticastCtrlPreviewProfileEntry 5 }

roapMuticastCtrlPreviewProfileInterval OBJECT-TYPE
        SYNTAX        INTEGER(1..7200)  
        MAX-ACCESS    read-create 
        STATUS        current
		DESCRIPTION  
		"unit:s"
		DEFVAL {60}
        ::= { roapMuticastCtrlPreviewProfileEntry 6 }

roapMuticastCtrlPreviewProfileRowStatus OBJECT-TYPE
        SYNTAX        RowStatus  
        MAX-ACCESS    read-create 
        STATUS        current
		DESCRIPTION  
		" "
        ::= { roapMuticastCtrlPreviewProfileEntry 7 }

	        
----------------------------------------------
roapMuticastCtrlPackageIDNext  OBJECT-TYPE      
        SYNTAX      INTEGER(1..128)  
		MAX-ACCESS  read-write
        STATUS      current
        DESCRIPTION
               " "
        ::= { roapMuticastCtrl 4 }

-----roapMuticastCtrlPackageTable
roapMuticastCtrlPackageTable OBJECT-TYPE
        SYNTAX SEQUENCE OF RoapMuticastCtrlPackageEntry
        MAX-ACCESS      not-accessible
        STATUS current
        DESCRIPTION
            " "
        ::= { roapMuticastCtrl 5 }

roapMuticastCtrlPackageEntry OBJECT-TYPE
	    SYNTAX     RoapMuticastCtrlPackageEntry
        MAX-ACCESS not-accessible
        STATUS     current
        DESCRIPTION
                " "
        INDEX      { roapMuticastCtrlPackageID }
        ::= { roapMuticastCtrlPackageTable 1 }

RoapMuticastCtrlPackageEntry ::= SEQUENCE {    
        roapMuticastCtrlPackageID		    INTEGER,
		roapMuticastCtrlPackageName			OCTET STRING,
		roapMuticastCtrlPackageUsers	    INTEGER,
        roapMuticastCtrlPackageRowStatus   	RowStatus
        }

roapMuticastCtrlPackageID OBJECT-TYPE
        SYNTAX        INTEGER(1..128)  
        MAX-ACCESS    read-create 
        STATUS        current
		DESCRIPTION  
		" "
        ::= { roapMuticastCtrlPackageEntry 1 }
        
roapMuticastCtrlPackageName OBJECT-TYPE
        SYNTAX        OCTET STRING(SIZE(16))  
        MAX-ACCESS    read-create 
        STATUS        current
		DESCRIPTION  
		" "
        ::= { roapMuticastCtrlPackageEntry 2 }

roapMuticastCtrlPackageUsers OBJECT-TYPE
        SYNTAX        INTEGER  
        MAX-ACCESS    read-only 
        STATUS        current
		DESCRIPTION  
		" " 
       ::= { roapMuticastCtrlPackageEntry 3 }

roapMuticastCtrlPackageRowStatus OBJECT-TYPE
        SYNTAX        RowStatus  
        MAX-ACCESS    read-create 
        STATUS        current
		DESCRIPTION  
		" "
        ::= { roapMuticastCtrlPackageEntry 4 }

-----roapMuticastCtrlChannelTable
roapMuticastCtrlChannelTable OBJECT-TYPE
        SYNTAX SEQUENCE OF RoapMuticastCtrlChannelEntry
        MAX-ACCESS      not-accessible
        STATUS current
        DESCRIPTION
            " "
        ::= { roapMuticastCtrl 6 }

roapMuticastCtrlChannelEntry OBJECT-TYPE
	    SYNTAX     RoapMuticastCtrlChannelEntry
        MAX-ACCESS not-accessible
        STATUS     current
        DESCRIPTION
                " "
        INDEX      { roapMuticastCtrlChannelID }
        ::= { roapMuticastCtrlChannelTable 1 }

RoapMuticastCtrlChannelEntry ::= SEQUENCE {    
        roapMuticastCtrlChannelID		    INTEGER,
        roapMuticastCtrlChannelIpType       InetAddressType,
        roapMuticastCtrlChannelIp           InetAddress,
		roapMuticastCtrlChannelName			OCTET STRING,
		roapMuticastCtrlChannelCdrEnable	EnableVar,
		roapMuticastCtrlChannelRowStatus    RowStatus,
		roapMuticastCtrlChannelEndIp        InetAddress
        }

roapMuticastCtrlChannelID OBJECT-TYPE
        SYNTAX        INTEGER(1..1024)  
        MAX-ACCESS    read-create 
        STATUS        current
		DESCRIPTION  
		" "
        ::= { roapMuticastCtrlChannelEntry 1 }

roapMuticastCtrlChannelIpType OBJECT-TYPE           
        SYNTAX      InetAddressType  
		MAX-ACCESS  read-create
        STATUS      current
        DESCRIPTION
               " "
        ::= { roapMuticastCtrlChannelEntry 2 }

roapMuticastCtrlChannelIp OBJECT-TYPE           
        SYNTAX      InetAddress  
		MAX-ACCESS  read-create
        STATUS      current
        DESCRIPTION
               " "
        ::= { roapMuticastCtrlChannelEntry 3 }
        
roapMuticastCtrlChannelName OBJECT-TYPE
        SYNTAX        OCTET STRING(SIZE(16))  
        MAX-ACCESS    read-create 
        STATUS        current
		DESCRIPTION  
		" "
        ::= { roapMuticastCtrlChannelEntry 4 }

roapMuticastCtrlChannelCdrEnable OBJECT-TYPE
        SYNTAX        EnableVar  
        MAX-ACCESS    read-write 
        STATUS        current
		DESCRIPTION  
		" "
        ::= { roapMuticastCtrlChannelEntry 5 }

roapMuticastCtrlChannelRowStatus OBJECT-TYPE
        SYNTAX        RowStatus  
        MAX-ACCESS    read-create 
        STATUS        current
		DESCRIPTION  
		" "
        ::= { roapMuticastCtrlChannelEntry 6 }

roapMuticastCtrlChannelEndIp OBJECT-TYPE           
        SYNTAX      InetAddress  
		MAX-ACCESS  read-create
        STATUS      current
        DESCRIPTION
               " "
        ::= { roapMuticastCtrlChannelEntry 7 }
        
-----roapMuticastCtrlPackageChannelTable
roapMuticastCtrlPackageChannelTable OBJECT-TYPE
        SYNTAX SEQUENCE OF RoapMuticastCtrlPackageChannelEntry
        MAX-ACCESS      not-accessible
        STATUS current
        DESCRIPTION
            " "
        ::= { roapMuticastCtrl 7 }

roapMuticastCtrlPackageChannelEntry OBJECT-TYPE
	    SYNTAX     RoapMuticastCtrlPackageChannelEntry
        MAX-ACCESS not-accessible
        STATUS     current
        DESCRIPTION
                " "
        INDEX      { roapMuticastCtrlPackageChannelPackageID, roapMuticastCtrlPackageChannelChannelID }
        ::= { roapMuticastCtrlPackageChannelTable 1 }

RoapMuticastCtrlPackageChannelEntry ::= SEQUENCE {    
        roapMuticastCtrlPackageChannelPackageID		            INTEGER,
        roapMuticastCtrlPackageChannelChannelID		            INTEGER,
		roapMuticastCtrlPackageChannelRight			INTEGER,
		roapMuticastCtrlPackageChannelPreviewProfileID	    INTEGER,
        roapMuticastCtrlPackageChannelRowStatus   	RowStatus
        }

roapMuticastCtrlPackageChannelPackageID OBJECT-TYPE
        SYNTAX        INTEGER(1..128)  
        MAX-ACCESS    read-create 
        STATUS        current
		DESCRIPTION  
		" "
        ::= { roapMuticastCtrlPackageChannelEntry 1 }

roapMuticastCtrlPackageChannelChannelID OBJECT-TYPE
        SYNTAX        INTEGER(1..1024)  
        MAX-ACCESS    read-create 
        STATUS        current
		DESCRIPTION  
		" "
        ::= { roapMuticastCtrlPackageChannelEntry 2 }
        
roapMuticastCtrlPackageChannelRight OBJECT-TYPE
        SYNTAX        INTEGER{
			permit(1),
			deny(2),
			preview(3)        
        }  
        MAX-ACCESS    read-create 
        STATUS        current
		DESCRIPTION  
		" "
        ::= { roapMuticastCtrlPackageChannelEntry 3 }

roapMuticastCtrlPackageChannelPreviewProfileID OBJECT-TYPE
        SYNTAX        INTEGER(1..64)  
        MAX-ACCESS    read-write 
        STATUS        current
		DESCRIPTION  
		" "
        ::= { roapMuticastCtrlPackageChannelEntry 4 }

roapMuticastCtrlPackageChannelRowStatus OBJECT-TYPE
        SYNTAX        RowStatus  
        MAX-ACCESS    read-create 
        STATUS        current
		DESCRIPTION  
		" "
        ::= { roapMuticastCtrlPackageChannelEntry 5 }

-----roapMuticastCtrlUserTable
roapMuticastCtrlUserTable OBJECT-TYPE
        SYNTAX SEQUENCE OF RoapMuticastCtrlUserEntry
        MAX-ACCESS      not-accessible
        STATUS current
        DESCRIPTION
            " "
        ::= { roapMuticastCtrl 8 }

roapMuticastCtrlUserEntry OBJECT-TYPE
	    SYNTAX     RoapMuticastCtrlUserEntry
        MAX-ACCESS not-accessible
        STATUS     current
        DESCRIPTION
                " "
        INDEX      { roapMuticastCtrlUserIfindex, roapMuticastCtrlUserVlan }
        ::= { roapMuticastCtrlUserTable 1 }

RoapMuticastCtrlUserEntry ::= SEQUENCE {    
        roapMuticastCtrlUserIfindex		    INTEGER,
        roapMuticastCtrlUserVlan		    INTEGER,
		roapMuticastCtrlUserName			OCTET STRING,
		roapMuticastCtrlUserPackageID       INTEGER,
        roapMuticastCtrlUserRowStatus   	RowStatus
        }

roapMuticastCtrlUserIfindex OBJECT-TYPE
        SYNTAX        INTEGER  
        MAX-ACCESS    read-create 
        STATUS        current
		DESCRIPTION  
		" "
        ::= { roapMuticastCtrlUserEntry 1 }

roapMuticastCtrlUserVlan OBJECT-TYPE
        SYNTAX        INTEGER(1..4094)  
        MAX-ACCESS    read-create 
        STATUS        current
		DESCRIPTION  
		" "
        ::= { roapMuticastCtrlUserEntry 2 }
        
roapMuticastCtrlUserName OBJECT-TYPE
        SYNTAX        OCTET STRING(SIZE(16))  
        MAX-ACCESS    read-create 
        STATUS        current
		DESCRIPTION  
		" "
        ::= { roapMuticastCtrlUserEntry 3 }

roapMuticastCtrlUserPackageID OBJECT-TYPE
        SYNTAX        INTEGER(1..128)  
        MAX-ACCESS    read-write 
        STATUS        current
		DESCRIPTION  
		" "
        ::= { roapMuticastCtrlUserEntry 4 }

roapMuticastCtrlUserRowStatus OBJECT-TYPE
        SYNTAX        RowStatus  
        MAX-ACCESS    read-create 
        STATUS        current
		DESCRIPTION  
		" "
        ::= { roapMuticastCtrlUserEntry 5 }

-----roapMuticastCtrlCurOnlineTable
roapMuticastCtrlCurOnlineTable OBJECT-TYPE
        SYNTAX SEQUENCE OF RoapMuticastCtrlCurOnlineEntry
        MAX-ACCESS      not-accessible
        STATUS current
        DESCRIPTION
            " "
        ::= { roapMuticastCtrl 9 }

roapMuticastCtrlCurOnlineEntry OBJECT-TYPE
	    SYNTAX     RoapMuticastCtrlCurOnlineEntry
        MAX-ACCESS not-accessible
        STATUS     current
        DESCRIPTION
                ""
        INDEX      { roapMuticastCtrlCurOnlineUserIfindex, roapMuticastCtrlCurOnlineUserVlan, roapMuticastCtrlCurOnlineChannelID }
        ::= { roapMuticastCtrlCurOnlineTable 1 }

RoapMuticastCtrlCurOnlineEntry ::= SEQUENCE {    
        roapMuticastCtrlCurOnlineUserIfindex		    INTEGER,
        roapMuticastCtrlCurOnlineUserVlan		    INTEGER,
		roapMuticastCtrlCurOnlineChannelID	INTEGER,
		roapMuticastCtrlCurOnlineDuartion   INTEGER
        }

roapMuticastCtrlCurOnlineUserIfindex OBJECT-TYPE
        SYNTAX        INTEGER  
        MAX-ACCESS    read-create 
        STATUS        current
		DESCRIPTION  
		" "
        ::= { roapMuticastCtrlCurOnlineEntry 1 }

roapMuticastCtrlCurOnlineUserVlan OBJECT-TYPE
        SYNTAX        INTEGER(1..4094)  
        MAX-ACCESS    read-create 
        STATUS        current
		DESCRIPTION  
		" "
        ::= { roapMuticastCtrlCurOnlineEntry 2 }
        
roapMuticastCtrlCurOnlineChannelID OBJECT-TYPE
        SYNTAX        INTEGER(1..1024)  
        MAX-ACCESS    read-only 
        STATUS        current
		DESCRIPTION  
		" "
        ::= { roapMuticastCtrlCurOnlineEntry 3 }

roapMuticastCtrlCurOnlineDuartion OBJECT-TYPE
        SYNTAX        INTEGER  
        MAX-ACCESS    read-only 
        STATUS        current
		DESCRIPTION  
		"unit:s"
        ::= { roapMuticastCtrlCurOnlineEntry 4 }
	        
----------------------------------------------
roapMuticastCtrlChannelIDNext  OBJECT-TYPE      
        SYNTAX      INTEGER(1..1024)  
		MAX-ACCESS  read-write
        STATUS      current
        DESCRIPTION
               " "
        ::= { roapMuticastCtrl 10 }	        
END
