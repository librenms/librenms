--MibName=roapPPPoEAgent
-- *****************************************************************
-- RAISECOM-VLAN-MIB.MIB:  Raisecom PPPoEAgent MIB file
-- April 2012,pangxijia
--
-- Copyright (c) 2008 by Raisecom, Inc.
-- All rights reserved.
--
-- *****************************************************************
RAISECOM-PPPOEAGENT-MIB  DEFINITIONS ::= BEGIN

IMPORTS
        EnableVar      FROM SWITCH-TC
        ifIndex        FROM IF-MIB  
        OltPortIndex	                    FROM RAISECOM-PONSERIES-TC 
	    raisecomSwitchMgt                   FROM RAISECOM-PONSERIES-BASE-MIB;

        
	roapPPPoEAgent MODULE-IDENTITY
        LAST-UPDATED    "201204090000Z"
        ORGANIZATION    "Raisecom, Inc."
        CONTACT-INFO
                "       Raise Systems

                Postal: Beijing, China

                   Tel: 86-010-82884499

                E-mail: pangxijia@raisecom.com"
        DESCRIPTION
                "description of PPPoEAgent object."
                ::= { raisecomSwitchMgt   18}

-- -------------------------------------------------------------
-- groups in the MIB
-- -------------------------------------------------------------
-- pppoeAgent global switch--   
roapPPPoEAgentGlobalSwitch  OBJECT-TYPE 
        SYNTAX   EnableVar
        ACCESS	 read-write
        STATUS   current
        DESCRIPTION
                 "This table provides objects to pppoe+ port config list"
        ::= { roapPPPoEAgent 1 }    

-- config table--    
roapPPPoEAgentConfigTable  OBJECT-TYPE 
        SYNTAX   SEQUENCE OF RoapPPPoEAgentConfigEntry
        ACCESS	 not-accessible
        STATUS   current
        DESCRIPTION
                 "This table provides objects to pppoe+ port config list"
        ::= { roapPPPoEAgent 2 }       

roapPPPoEAgentConfigEntry  OBJECT-TYPE
        SYNTAX   RoapPPPoEAgentConfigEntry
        ACCESS   not-accessible
        STATUS   current
        DESCRIPTION
                 "An entry in rcPPPoEAgentConfigTable"   
        INDEX { roapPppoePortIndex }
        ::= { roapPPPoEAgentConfigTable 1 } 
      
RoapPPPoEAgentConfigEntry ::= SEQUENCE {   
        roapPppoePortIndex                        OltPortIndex,
		roapPPPoEAgentConfigPortEnable       EnableVar,     
		roapPPPoEAgentConfigPortTrust            INTEGER,
		roapPPPoEAgentConfigPktProcessPolicy     INTEGER,     
		roapPPPoEAgentConfigPktOverwritePosition INTEGER,    
		roapPPPoEAgentConfigPktOverwriteLength   INTEGER,
		roapPPPoEAgentConfigCircuitIDInfo	   OCTET STRING
		}
 
roapPppoePortIndex  OBJECT-TYPE
		SYNTAX	OltPortIndex
		ACCESS	read-write
		STATUS	current
		DESCRIPTION
		    	"Enable PPPoE intermediate agent"
		::= { roapPPPoEAgentConfigEntry 1 }

roapPPPoEAgentConfigPortEnable  OBJECT-TYPE
		SYNTAX	EnableVar
		ACCESS	read-write
		STATUS	current
		DESCRIPTION
		    	"Enable PPPoE intermediate agent"
		::= { roapPPPoEAgentConfigEntry 2 }
		 
		
roapPPPoEAgentConfigPortTrust  OBJECT-TYPE
		SYNTAX	INTEGER{true(1), false(2)}
		ACCESS	read-write
		STATUS	current
		DESCRIPTION
		    	"Trust port of PPPoE intermediate agent" 
		DEFVAL {True}
		::= { roapPPPoEAgentConfigEntry 3 }   
		
roapPPPoEAgentConfigPktProcessPolicy  OBJECT-TYPE
		SYNTAX	INTEGER
		ACCESS	read-write
		STATUS	current
		DESCRIPTION
		    	"packet process policy"
		::= { roapPPPoEAgentConfigEntry 4 }
roapPPPoEAgentConfigPktOverwritePosition   OBJECT-TYPE
  		SYNTAX	INTEGER
		ACCESS	read-write
		STATUS	current
		DESCRIPTION
		    	"overwrite position"
		::= { roapPPPoEAgentConfigEntry 5 }   
		
roapPPPoEAgentConfigPktOverwriteLength   OBJECT-TYPE
  		SYNTAX	INTEGER
		ACCESS	read-write
		STATUS	current
		DESCRIPTION
		    	"overwrite length"
		::= { roapPPPoEAgentConfigEntry 6 }

		
roapPPPoEAgentConfigCircuitIDInfo  OBJECT-TYPE
		SYNTAX	OCTET STRING(SIZE(0..127))
		ACCESS	read-write
		STATUS	current
		DESCRIPTION
		    	"Circuit-ID infomation of PPPoE intermediate agent"
		::= { roapPPPoEAgentConfigEntry 7}
				
		
		
--statistic table---
 
roapPPPoEAgentStatisticsTable  OBJECT-TYPE 
        SYNTAX   SEQUENCE OF RoapPPPoEAgentStatisticsEntry
        ACCESS	 not-accessible
        STATUS   current
        DESCRIPTION
                 "This table provides objects to pppoe+ port statistics list"
        ::= { roapPPPoEAgent 3 }
        
roapPPPoEAgentStatisticsEntry  OBJECT-TYPE
        SYNTAX   RoapPPPoEAgentStatisticsEntry
        ACCESS   not-accessible
        STATUS   current
        DESCRIPTION
                 "An entry in rcPPPoEAgentStatisticsTable" 
        INDEX { ifIndex }
        ::= { roapPPPoEAgentStatisticsTable 1 } 
      
RoapPPPoEAgentStatisticsEntry ::= SEQUENCE {
    roapPPPoEAgentStatisticsPortIndex      OltPortIndex,
		roapPPPoEAgentStatisticsReset			     INTEGER,
		roapPPPoEAgentStatisticsPADIReceived	 INTEGER,
		roapPPPoEAgentStatisticsPADISend	     INTEGER,
		roapPPPoEAgentStatisticsPADRReceived	 INTEGER,
		roapPPPoEAgentStatisticsPADRSend	     INTEGER
}
roapPPPoEAgentStatisticsPortIndex   OBJECT-TYPE
		SYNTAX	OltPortIndex
		ACCESS	read-write
		STATUS	current
		DESCRIPTION
		    	"port index"
		::= { roapPPPoEAgentStatisticsEntry  1 }
		
roapPPPoEAgentStatisticsReset  OBJECT-TYPE
		SYNTAX	INTEGER {reset(1)}
		ACCESS	read-write
		STATUS	current
		DESCRIPTION
		    	"To reset PPPoE packet counter"
		::= { roapPPPoEAgentStatisticsEntry 2 }

roapPPPoEAgentStatisticsPADIReceived  OBJECT-TYPE
		SYNTAX	INTEGER
		ACCESS	read-only
		STATUS	current
		DESCRIPTION
		    	"Indicate how many PADI packet the CPU of switch had received"
		::= { roapPPPoEAgentStatisticsEntry 3 }
		
roapPPPoEAgentStatisticsPADISend  OBJECT-TYPE
		SYNTAX	INTEGER
		ACCESS	read-only
		STATUS	current
		DESCRIPTION
		    	"Indicate how many PADI packet the CPU of switch had send"
		::= { roapPPPoEAgentStatisticsEntry 4 }
		
roapPPPoEAgentStatisticsPADRReceived  OBJECT-TYPE
		SYNTAX	INTEGER
		ACCESS	read-only
		STATUS	current
		DESCRIPTION
		    	"Indicate how many PADR packet the CPU of switch had received"
		::= { roapPPPoEAgentStatisticsEntry 5 }
		
roapPPPoEAgentStatisticsPADRSend  OBJECT-TYPE
		SYNTAX	INTEGER
		ACCESS	read-only
		STATUS	current
		DESCRIPTION
		    	"Indicate how many PADR packet the CPU of switch had send"
		::= { roapPPPoEAgentStatisticsEntry 6 } 

		
END
