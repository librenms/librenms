--MibName=roapLbDetect
-- *****************************************************************
-- switch-portbackup-mib.MIB:	 switch port backup MIB file
--
-- Feb 2012, gxd
--
-- Copyright (c) 1994-2012,	2012 by	Raisecom, Inc.
-- All rights reserved.
-- Modify
-- *****************************************************************

SWITCH-LBDETECT-MIB DEFINITIONS ::= BEGIN

IMPORTS
        raisecomSwitchMgt                FROM RAISECOM-PONSERIES-BASE-MIB  
        RowStatus,TruthValue             FROM SNMPv2-TC
        Vlanset,EnableVar	             FROM SWITCH-TC  
        InterfaceIndex                   FROM IF-MIB;
                 
     roapLbDetect MODULE-IDENTITY
        LAST-UPDATED    "201307040000Z"
        ORGANIZATION    "Raisecom, Inc."
        CONTACT-INFO
                "Raisecom Systems
                        
                Postal: Beijing,
                        China

                Tel: 86-010-82884499

                E-mail: mayuanchao@raisecom.com"
        DESCRIPTION
                "description of loopback detection manage object."
                ::= { raisecomSwitchMgt 26} 
                    
         roapLbDetectPktConfig 			OBJECT IDENTIFIER ::= { roapLbDetect 1 }    
         roapLbDetectTrap               OBJECT IDENTIFIER ::= { roapLbDetect 4 }

-- -------------------------------------------------------------
-- scalar in the MIB
-- -------------------------------------------------------------

roapLbDetectDestAddr  OBJECT-TYPE 
        SYNTAX   OCTET STRING(SIZE(6))
        ACCESS	 read-write
        STATUS   current
        DESCRIPTION
                 "Destinate mac address of loopbackdetect packet"
        ::= { roapLbDetectPktConfig 1}    
         
roapLbDetectVlan  OBJECT-TYPE 
        SYNTAX   INTEGER(1..4094)
        ACCESS	 read-write
        STATUS   current
        DESCRIPTION
                 "vlan id of loopbackdetect packet"
        ::= { roapLbDetectPktConfig 2}      

roapLbDetectInterval OBJECT-TYPE 
        SYNTAX   INTEGER(1..65535)
        ACCESS	 read-write
        STATUS   current
        DESCRIPTION
                 "Period of loopback detection"
        ::= { roapLbDetectPktConfig 3}

roapLbDetectRestoreTime  OBJECT-TYPE
        SYNTAX   INTEGER(0..65535)
        ACCESS   read-write
        STATUS   current
        DESCRIPTION
                 "Restore time for blocking port"
        ::= { roapLbDetectPktConfig 4 }   

roapLbDetectGlobalEnable  OBJECT-TYPE
        SYNTAX   INTEGER{enable(1), disable(2)}
        ACCESS   read-write
        STATUS   current
        DESCRIPTION
                 "Enable loopback detect function"
        ::= { roapLbDetectPktConfig 5 }         
------------------------------------------------------------------
--table in the mib
------------------------------------------------------------------
                         
-- roapLbDetectPortTable

roapLbDetectPortTable  OBJECT-TYPE 
        SYNTAX   SEQUENCE OF roapLbDetectPortEntry
        ACCESS	 not-accessible
        STATUS   current
        DESCRIPTION
                 "Port infomation of loopbackdetection"
        ::= { roapLbDetect 2 }
        
roapLbDetectPortEntry  OBJECT-TYPE
        SYNTAX   roapLbDetectPortEntry
        ACCESS   not-accessible
        STATUS   current
        DESCRIPTION
                 "An entry in rcLbDetectPortTable"
        INDEX { roapLbDetectPortIndex }
        ::= { roapLbDetectPortTable 1 } 
      
roapLbDetectPortEntry ::= SEQUENCE {
		roapLbDetectPortIndex              InterfaceIndex,
		roapLbDetectPortSubIndex           INTEGER,
		roapLbDetectPortEnable	           INTEGER,
		roapLbDetectPortLoopAction         INTEGER,
		roapLbDetectPortExloopAction       INTEGER,
		roapLbDetectPortManualRestore	   INTEGER,
		roapLbDetectPortStatus             INTEGER,
		roapLbDetectPortBlockCount	       INTEGER,
		roapLbDetectPortLastOccur	       INTEGER,
		roapLbDetectPortLastDuration	   INTEGER,  
		roapLbDetectPortLastSrcMac	       OCTET STRING,
		roapLbDetectPortLastSrcPort	   	   INTEGER,
		roapLbDetectPortLastSrcSubIndex    INTEGER,
		roapLbDetectPortLastVlan  	       INTEGER
		}            
		
roapLbDetectPortIndex OBJECT-TYPE
        SYNTAX   InterfaceIndex
        ACCESS   not-accessible
        STATUS   current
        DESCRIPTION
                 "Table index,it means the index of port."
        ::= { roapLbDetectPortEntry 1 }

roapLbDetectPortSubIndex OBJECT-TYPE
        SYNTAX   INTEGER
        ACCESS   read-only
        STATUS   current
        DESCRIPTION
                 "The detected loopback ONU ID, if there is no detected ONU, sub id set 0."
        ::= { roapLbDetectPortEntry 2 }
        
roapLbDetectPortEnable  OBJECT-TYPE
        SYNTAX   INTEGER{enable(1), disable(2)}
        ACCESS   read-write
        STATUS   current
        DESCRIPTION
                 "Enable or disable loopbackdetection for special port"
        ::= { roapLbDetectPortEntry 3 }

roapLbDetectPortLoopAction  OBJECT-TYPE
        SYNTAX   INTEGER{discarding(1), trap-only(2)}
        ACCESS   read-write
        STATUS   current
        DESCRIPTION
                 "Action when detect loopback. 
                 discarding means port will be blocked except send a trap, 
                 trap-only means only send a trap."
        ::= { roapLbDetectPortEntry 4 }

roapLbDetectPortExloopAction  OBJECT-TYPE
        SYNTAX   INTEGER{discarding(1), trap-only(2)}
        ACCESS   read-write
        STATUS   current
        DESCRIPTION
                 "Action when received a packet form other bridge"
        ::= { roapLbDetectPortEntry 5 }

roapLbDetectPortManualRestore  OBJECT-TYPE
        SYNTAX   INTEGER{restore(1)}
        ACCESS   read-write
        STATUS   current
        DESCRIPTION
                 "Set the port non-block manualy"
        ::= { roapLbDetectPortEntry 6 }

roapLbDetectPortStatus  OBJECT-TYPE
        SYNTAX   INTEGER{loopyes(1), loopno(2)}
        ACCESS   read-only
        STATUS   current
        DESCRIPTION
                 "The status of this port"
        ::= { roapLbDetectPortEntry 7 }

roapLbDetectPortBlockCount  OBJECT-TYPE
        SYNTAX   INTEGER
        ACCESS   read-only
        STATUS   current
        DESCRIPTION
                 "How many times this port was blocked"
        ::= { roapLbDetectPortEntry 8 }

roapLbDetectPortLastOccur  OBJECT-TYPE
        SYNTAX   INTEGER
        ACCESS   read-only
        STATUS   current
        DESCRIPTION
                 "The moment of last loop happen"
        ::= { roapLbDetectPortEntry 9 }

roapLbDetectPortLastDuration  OBJECT-TYPE
        SYNTAX   INTEGER
        ACCESS   read-only
        STATUS   current
        DESCRIPTION
                 "The duration of last loop"
        ::= { roapLbDetectPortEntry 10 }

roapLbDetectPortLastSrcMac  OBJECT-TYPE
        SYNTAX   OCTET STRING(SIZE(6))
        ACCESS   read-only
        STATUS   current
        DESCRIPTION
                 "The source mac address of last loop"
        ::= { roapLbDetectPortEntry 11 }

roapLbDetectPortLastSrcPort  OBJECT-TYPE
        SYNTAX   INTEGER
        ACCESS   read-only
        STATUS   current
        DESCRIPTION
                 "The source port of last loop"
        ::= { roapLbDetectPortEntry 12 } 

roapLbDetectPortLastSrcSubIndex  OBJECT-TYPE
        SYNTAX   INTEGER
        ACCESS   read-only
        STATUS   current
        DESCRIPTION
                 "The source ONU index of last loop"
        ::= { roapLbDetectPortEntry 13 } 

roapLbDetectPortLastVlan  OBJECT-TYPE
        SYNTAX   INTEGER
        ACCESS   read-only
        STATUS   current
        DESCRIPTION
                 "The vlan of last loop"
        ::= { roapLbDetectPortEntry 14 }
     
     
--roapLbDetectErrorTable        

roapLbDetectErrorDeviceTable  OBJECT-TYPE 
        SYNTAX   SEQUENCE OF roapLbDetectErrorDeviceEntry
        ACCESS	 not-accessible
        STATUS   current
        DESCRIPTION
                 "Error infomation of loopbackdetection"
        ::= { roapLbDetect 3 }
        
roapLbDetectErrorDeviceEntry  OBJECT-TYPE
        SYNTAX   roapLbDetectErrorDeviceEntry
        ACCESS   not-accessible
        STATUS   current
        DESCRIPTION
                 "An entry in roapLbDetectErrorDeviceTable"
        INDEX { roapLbDetectErrorDeviceIndex, roapLbDetectErrorDeviceErrorIndex }
        ::= { roapLbDetectErrorDeviceTable 1 } 
      
roapLbDetectErrorDeviceEntry ::= SEQUENCE {
		roapLbDetectErrorDeviceIndex	    InterfaceIndex,
		roapLbDetectErrorDeviceErrorIndex   INTEGER,
		roapLbDetectErrorDeviceMac          OCTET STRING,
		roapLbDetectErrorDevicePeerPort     INTEGER,
		roapLbDetectErrorDeviceCounts	    INTEGER,
		roapLbDetectErrorDeviceLastOccur    INTEGER
		}
 
roapLbDetectErrorDeviceIndex  OBJECT-TYPE
        SYNTAX   InterfaceIndex
        ACCESS   not-accessible
        STATUS   current
        DESCRIPTION
                 "Table index, it means the index of port."
        ::= { roapLbDetectErrorDeviceEntry 1 }

roapLbDetectErrorDeviceErrorIndex  OBJECT-TYPE
        SYNTAX   INTEGER(1..5)
        ACCESS   not-accessible
        STATUS   current
        DESCRIPTION
                 "Error number 
                 every port can record most five error information, 
                 this means the error number."
        ::= { roapLbDetectErrorDeviceEntry 2 }

roapLbDetectErrorDeviceMac  OBJECT-TYPE
        SYNTAX   OCTET STRING(SIZE(0..6))
        ACCESS   read-only
        STATUS   current
        DESCRIPTION
                 "Mac address of received packet"
        ::= { roapLbDetectErrorDeviceEntry 3 }

roapLbDetectErrorDevicePeerPort  OBJECT-TYPE
        SYNTAX   INTEGER
        ACCESS   read-only
        STATUS   current
        DESCRIPTION
                 "Peer port of received packet"
        ::= { roapLbDetectErrorDeviceEntry 4 }

roapLbDetectErrorDeviceCounts  OBJECT-TYPE
        SYNTAX   INTEGER
        ACCESS   read-only
        STATUS   current
        DESCRIPTION
                 "How many times this port have receive a loopbackdetect packet from same mac and same port"
        ::= { roapLbDetectErrorDeviceEntry 5 }

roapLbDetectErrorDeviceLastOccur  OBJECT-TYPE
        SYNTAX   INTEGER
        ACCESS   read-only
        STATUS   current
        DESCRIPTION
                 "The moment of last error happen"
        ::= { roapLbDetectErrorDeviceEntry 6 } 

--traps
roapLbDetectLoopTrap NOTIFICATION-GROUP
        NOTIFICATIONS{  
        	roapLbDetectPortIndex,
        	roapLbDetectPortSubIndex, 
            roapLbDetectPortStatus,    
            roapLbDetectPortLastSrcMac,
            roapLbDetectPortLastSrcPort,
            roapLbDetectPortLastSrcSubIndex,
            roapLbDetectPortLastVlan
            }
        STATUS      current
        DESCRIPTION 
        "Port's state change"
        ::= { roapLbDetectTrap 1 }

roapLbDetectErrorDeviceTrap NOTIFICATION-GROUP
        NOTIFICATIONS{
        	roapLbDetectErrorDeviceIndex,   
            roapLbDetectErrorDeviceMac,    
            roapLbDetectErrorDevicePeerPort,
            roapLbDetectErrorDeviceCounts
            }
        STATUS      current
        DESCRIPTION 
        "Receive a loopback detection packet"
        ::= { roapLbDetectTrap 2 }
        			
END
