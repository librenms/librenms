--MibName=roapUplinkProtect
-- *****************************************************************
-- switch-uplinkprotect-mib.MIB:	 switch uplink protect MIB file
--
-- Feb 2012, gxd
--
-- Copyright (c) 1994-2012,	2012 by	Raisecom, Inc.
-- All rights reserved.
-- Modify
-- *****************************************************************

SWITCH-UPLINKPROTECT-MIB DEFINITIONS ::= BEGIN

IMPORTS
        raisecomSwitchMgt                FROM RAISECOM-PONSERIES-BASE-MIB  
        RowStatus,TruthValue             FROM SNMPv2-TC
        Vlanset,EnableVar	             FROM SWITCH-TC  
        InterfaceIndex                   FROM IF-MIB;
                 
     roapUplinkProtect MODULE-IDENTITY
        LAST-UPDATED    "201301180000Z"
        ORGANIZATION    "Raisecom, Inc."
        CONTACT-INFO
                "Raisecom Systems
                        
                Postal: Beijing,
                        China

                Tel: 86-010-82884499

                E-mail: mayuanchao@raisecom.com"
        DESCRIPTION
                "description of uplink protect group manage object."
                ::= { raisecomSwitchMgt 24}  
                
         roapUplinkProtectObjects	      OBJECT IDENTIFIER ::= { roapUplinkProtect 1 }
         roapUplinkProtectNotifications   OBJECT IDENTIFIER ::= { roapUplinkProtect 2 }  
                         
-- roapUplinkProtectTable

	roapUplinkProtectTable OBJECT-TYPE
    SYNTAX      SEQUENCE OF roapUplinkProtectEntry
    MAX-ACCESS  not-accessible
    STATUS      current
    DESCRIPTION
        "A table of uplink protect group"
    ::={ roapUplinkProtectObjects 1 }
    

	roapUplinkProtectEntry OBJECT-TYPE
    SYNTAX      roapUplinkProtectEntry
    MAX-ACCESS  not-accessible
    STATUS      current
    DESCRIPTION
        "An entry in the roapUplinkProtectTable provides objects ."
    INDEX        { roapUplinkProtectGroupIndex }
    ::={ roapUplinkProtectTable 1 }
    
	roapUplinkProtectEntry ::= SEQUENCE {
		roapUplinkProtectGroupIndex	              INTEGER,     
		roapUplinkProtectPrimaryPort	          InterfaceIndex,
		roapUplinkProtectBackupPort               InterfaceIndex,
		roapUplinkProtectEnable                   EnableVar,  
		roapUplinkProtectWorkingState             INTEGER,      		
		roapUplinkProtectPrimaryPortLinkState	  INTEGER,
		roapUplinkProtectBackupPortLinkState      INTEGER,  
		roapUplinkProtectSwitchCount              INTEGER,   
	    roapUplinkProtectForceSwitch              TruthValue,
	    roapUplinkProtectRestoreMode              EnableVar,
	    roapUplinkProtectRestoreDelay             INTEGER,
	    roapUplinkProtectRowStatus                RowStatus
	}
 
 	roapUplinkProtectGroupIndex OBJECT-TYPE
		SYNTAX	INTEGER(1..2)
		ACCESS	not-accessible
		STATUS	current
		DESCRIPTION
			"An index that uniquely identifies an entry in
             the port backup group table."
		::=	{ roapUplinkProtectEntry 1 }
	
	roapUplinkProtectPrimaryPort OBJECT-TYPE
		SYNTAX	InterfaceIndex
		ACCESS	read-create
		STATUS	current
		DESCRIPTION
			"This object is the first index of an roapUplinkProtectTable. 
			It is the primary port of a backup group."
		::=	{ roapUplinkProtectEntry 2 }
		
	roapUplinkProtectBackupPort OBJECT-TYPE
		SYNTAX	InterfaceIndex
		ACCESS	read-create
		STATUS	current
		DESCRIPTION
			"This object is the second index of an roapUplinkProtectTable. 
			It is the standby port of a backup group."
		::=	{ roapUplinkProtectEntry 3 }

	roapUplinkProtectEnable OBJECT-TYPE
		SYNTAX	EnableVar
		ACCESS	read-create
		STATUS	current
		DESCRIPTION
			"The purpose of this object is to set backup function enable or disable."
		::=	{ roapUplinkProtectEntry 4 }
				
	roapUplinkProtectWorkingState OBJECT-TYPE
        SYNTAX INTEGER	{
                normal(1),
            	protect(2),
    			pending(3),
    			stop(4)
        			}
		ACCESS	read-only
		STATUS	current
		DESCRIPTION
			"the uplink protect group working state,if primary port is working,
			the working state is normal,if backup port is working,the working 
			state is protect.the working state is pending, which mean the port of
			uplink protect group are both down.if the group is disable, the state is
			stop. "
		::=	{ roapUplinkProtectEntry 5 }
				
	roapUplinkProtectPrimaryPortLinkState OBJECT-TYPE
        SYNTAX INTEGER	{
                unknown(1),
            	up(2),
    			down(3)
        			}
		ACCESS	read-only
		STATUS	current
		DESCRIPTION
			"Primary port link status，including three states: unknown,
			up and down. If the primary port is not set, the primary port 
			link state is unknown. "
		::=	{ roapUplinkProtectEntry 6 }

	roapUplinkProtectBackupPortLinkState OBJECT-TYPE
        SYNTAX INTEGER	{
                unknown(1),
            	up(2),
    			down(3)
        			}
		ACCESS	read-only
		STATUS	current
		DESCRIPTION
			"Backup port link status，including three states: unknown,
			up and down. If the backup port is not set, the backup port 
			link state is unknown. "
		::=	{ roapUplinkProtectEntry 7 }   
		
	roapUplinkProtectSwitchCount OBJECT-TYPE
		SYNTAX	INTEGER
		ACCESS	read-only     
		STATUS	current
		DESCRIPTION
			"The count of switch between primary port and standby port."
		::=	{ roapUplinkProtectEntry 8 } 
			
	roapUplinkProtectForceSwitch OBJECT-TYPE   
        SYNTAX TruthValue
        MAX-ACCESS read-write
        STATUS current
        DESCRIPTION
            "The purpose of this object is to force transition between main and backup port."
        DEFVAL { False }
        ::= { roapUplinkProtectEntry 9 }  
		               
	roapUplinkProtectRestoreMode OBJECT-TYPE 
		SYNTAX EnableVar
        ACCESS read-write
        STATUS current
        DESCRIPTION
            "The mode of port restoration."
        ::= { roapUplinkProtectEntry 10 } 
        
    roapUplinkProtectRestoreDelay OBJECT-TYPE 
		SYNTAX INTEGER (0..180)
        ACCESS read-write
        STATUS current
        DESCRIPTION
            "The restoration delay when bridge received the restoration incident."
        ::= { roapUplinkProtectEntry 11 }  
        
 	roapUplinkProtectRowStatus OBJECT-TYPE
		SYNTAX	RowStatus
		ACCESS	read-create
		STATUS	current
		DESCRIPTION
			"This object allows entries to be created and deleted
			 in the roapUplinkProtectTable. Deletion of an entry in
			 this table results in a deletion of all corresponding (same
			 roapUplinkProtectPrimaryPortIndex and roapUplinkProtectStandbyPort index values) roapUplinkProtectTable."
		::=	{ roapUplinkProtectEntry 12 }      
		  
    roapUplinkProtectBackupPortOperate NOTIFICATION-TYPE
        OBJECTS { roapUplinkProtectGroupIndex,
                  roapUplinkProtectPrimaryPort,
				  roapUplinkProtectBackupPort
            	}
        STATUS  current
        DESCRIPTION
          "Backup PORT Switch TRAP"
       ::= { roapUplinkProtectNotifications 1 } 
       
    roapUplinkProtectPrimaryPortOperate NOTIFICATION-TYPE
        OBJECTS { roapUplinkProtectGroupIndex,
                  roapUplinkProtectPrimaryPort,
				  roapUplinkProtectBackupPort
            	}
        STATUS  current
        DESCRIPTION
          "Backup PORT Restore TRAP"
       ::= { roapUplinkProtectNotifications 2 }        

			
END
