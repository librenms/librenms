-- -----------------------------------------------------------------------------
-- MIB NAME : rcAclCfg
-- FILE NAME: switch-acl-mib.mi2			
-- DATE     : 2011/1/4						
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2012/1/4, yanzhijie
-- This is the first formal version for universal MIB definition.
 
SWITCH-ACL-MIB DEFINITIONS ::= BEGIN
     
	IMPORTS
		MODULE-IDENTITY, OBJECT-TYPE, NOTIFICATION-TYPE,
		Integer32, IpAddress, Counter32, Unsigned32
			FROM SNMPv2-SMI

		MacAddress, RowStatus
			FROM SNMPv2-TC
	    
	    Ipv6Address
	    	FROM IPV6-TC
		
		InetAddressPrefixLength, InetPortNumber
			FROM INET-ADDRESS-MIB
		
		EnableVar
			FROM SWITCH-TC
		
		raisecomSwitchMgt
			FROM RAISECOM-PONSERIES-BASE-MIB;
			
	rcAclCfg MODULE-IDENTITY
		LAST-UPDATED 	"201107200000Z"
		ORGANIZATION 	"rc TECH, Ltd."
		CONTACT-INFO 	"www.rc.com"
		DESCRIPTION  	
		    "The MIB module defining objects for version management  functions"
		::= { raisecomSwitchMgt  4}
		
--Textual Conventions
------------------------------------------------------------------------------
--	textual conventions in swtich-acl-mib
------------------------------------------------------------------------------
	AclAccessType ::= TEXTUAL-CONVENTION
        STATUS       current
        DESCRIPTION                
        		"Access type of ACL"
        SYNTAX       INTEGER { deny(1), permit(2) }
        
    AclMatchField ::= TEXTUAL-CONVENTION
        STATUS       current
        DESCRIPTION                
        		"Match filed of acl table"
        SYNTAX       OCTET STRING ( SIZE(8) )
        
    AclVlanId ::= TEXTUAL-CONVENTION
        STATUS       current
        DESCRIPTION                
        		"VLAN ID"
        SYNTAX       INTEGER( 1..4094 )
        
    AclVlanCos ::= TEXTUAL-CONVENTION
        STATUS       current
        DESCRIPTION                
        		"VLAN COS"
        SYNTAX       INTEGER( 0..7 )
------------------------------------------------------------------------------


--rcAclCfg 

------------------------------------------------------------------------------
--	define groups in swtich-acl-mib
------------------------------------------------------------------------------
	rcL2AccessList	    	OBJECT IDENTIFIER ::= {	rcAclCfg 1 }
	rcIpv4AccessList		OBJECT IDENTIFIER ::= {	rcAclCfg 2 }
	rcIpv6AccessList	    OBJECT IDENTIFIER ::= {	rcAclCfg 3 }
	rcHybridAccessList      OBJECT IDENTIFIER ::= {	rcAclCfg 4 } 	
	rcUserAccessList        OBJECT IDENTIFIER ::= {	rcAclCfg 5 }
	rcAclAttribute          OBJECT IDENTIFIER ::= {	rcAclCfg 6 }  
	rcIPv6HybridAccessList  OBJECT IDENTIFIER ::= {	rcAclCfg 7 }
------------------------------------------------------------------------------
	  	
-- L2 Access List Control Table
	-- The l2 access control list contains some rules that are 
    -- associated with layer 2 and will be bound to the ports
    -- or vlans on device.

     rcL2AclTable    OBJECT-TYPE
        SYNTAX          SEQUENCE OF  RcL2AclEntry
        MAX-ACCESS      not-accessible
        STATUS          current
        DESCRIPTION     "Layer 2 access list control table"
    	::= { rcL2AccessList 1 }    
    
     rcL2AclEntry  OBJECT-TYPE
		SYNTAX          RcL2AclEntry
		MAX-ACCESS      not-accessible
        STATUS          current
		DESCRIPTION     "An entry in the rcL2AclTable."
		INDEX { rcAclId, rcAclRuleId }
		::= { rcL2AclTable 1 }
		
	RcL2AclEntry ::=	SEQUENCE { 
		rcAclId                     Integer32,
		rcAclRuleId                 Integer32,
		rcL2AclAccessType           AclAccessType,
		rcL2AclMatchFieldFlag       AclMatchField,
		rcL2AclSVlanId              AclVlanId,
		rcL2AclSVlanCos             AclVlanCos,
		rcL2AclCVlanId              AclVlanId,
		rcL2AclCVlanCos             AclVlanCos,
		rcL2AclSrcMacAddress        MacAddress,
		rcL2AclSrcMacMask           MacAddress,
		rcL2AclDstMacAddress        MacAddress,
		rcL2AclDstMacMask           MacAddress,
		rcL2AclEthernetType         INTEGER,
		rcL2AclEthernetTypeMask     INTEGER,
		rcL2AclRowStatus            RowStatus
		}		
    
		rcAclId  OBJECT-TYPE
	        SYNTAX 			Integer32(1..9000)
	        MAX-ACCESS 		read-only
	        STATUS 			current
	        DESCRIPTION		"Index of rcL2AclTable."
	        ::= { rcL2AclEntry 1 }        
         
    	rcAclRuleId  OBJECT-TYPE
	        SYNTAX 			Integer32(1..256)
	        MAX-ACCESS 		read-only
	        STATUS 			current
	        DESCRIPTION		"Index of L2 access control list rule."
	        ::= { rcL2AclEntry 2 }    
        
    	rcL2AclAccessType  OBJECT-TYPE
	        SYNTAX 			AclAccessType
	        MAX-ACCESS 		read-create
	        STATUS 			current
	        DESCRIPTION		"Access type of L2 acl rule."
	        ::= { rcL2AclEntry 3 }   
    
	    rcL2AclMatchFieldFlag  OBJECT-TYPE
	        SYNTAX 			AclMatchField
	        MAX-ACCESS 		read-create
	        STATUS 			current
	        DESCRIPTION		"Set the match filed of the table."
	        ::= { rcL2AclEntry 4 }  
	         
	    rcL2AclSVlanId  OBJECT-TYPE
	        SYNTAX 			AclVlanId
	        MAX-ACCESS 		read-create
	        STATUS 			current
	        DESCRIPTION		"SVLAN ID."
	        ::= { rcL2AclEntry 5 }
	        
	    rcL2AclSVlanCos  OBJECT-TYPE
	        SYNTAX 			AclVlanCos    
	        MAX-ACCESS 		read-create
	        STATUS 			current
	        DESCRIPTION		"SVLAN COS."
	        ::= { rcL2AclEntry 6 }
	        
	    rcL2AclCVlanId  OBJECT-TYPE
	        SYNTAX 			AclVlanId
	        MAX-ACCESS 		read-create
	        STATUS 			current
	        DESCRIPTION		"CVLAN ID."
	        ::= { rcL2AclEntry 7 }
	        
	    rcL2AclCVlanCos  OBJECT-TYPE
	        SYNTAX 			AclVlanCos
	        MAX-ACCESS 		read-create
	        STATUS 			current
	        DESCRIPTION		"CVLAN COS."
	        ::= { rcL2AclEntry 8 }
	        
	    rcL2AclSrcMacAddress  OBJECT-TYPE
	        SYNTAX 			MacAddress    
	        MAX-ACCESS 		read-create
	        STATUS 			current
	        DESCRIPTION		"Source MAC address."
	        ::= { rcL2AclEntry 9 }
	        
	    rcL2AclSrcMacMask  OBJECT-TYPE
	        SYNTAX 			MacAddress
	        MAX-ACCESS 		read-create
	        STATUS 			current
	        DESCRIPTION		"Sourcd MAC address mask."
	        ::= { rcL2AclEntry 10 }
	        
	    rcL2AclDstMacAddress  OBJECT-TYPE
	        SYNTAX 			MacAddress    
	        MAX-ACCESS 		read-create
	        STATUS 			current
	        DESCRIPTION		"Destination MAC address."
	        ::= { rcL2AclEntry 11 }
	        
	    rcL2AclDstMacMask  OBJECT-TYPE
	        SYNTAX 			MacAddress
	        MAX-ACCESS 		read-create
	        STATUS 			current
	        DESCRIPTION		"Destination MAC address mask."
	        ::= { rcL2AclEntry 12 }
	        
	    rcL2AclEthernetType  OBJECT-TYPE
	        SYNTAX 			INTEGER(1536..65535)
	        MAX-ACCESS 		read-create
	        STATUS 			current
	        DESCRIPTION		"Ethernet type in layer 2 framer header."
	        ::= { rcL2AclEntry 13 }
	        
	    rcL2AclEthernetTypeMask  OBJECT-TYPE
	        SYNTAX 			INTEGER(0..65535)    
	        MAX-ACCESS 		read-create
	        STATUS 			current
	        DESCRIPTION		"Ethernet type mask."
	        ::= { rcL2AclEntry 14 }
	        
	    rcL2AclRowStatus  OBJECT-TYPE
	        SYNTAX 			RowStatus
	        MAX-ACCESS 		read-create
	        STATUS 			current
	        DESCRIPTION		"Row status of the table."
	        ::= { rcL2AclEntry 15 }


-- Ipv4 Access List Control Table
	-- The Ipv4 access control list contains some rules that are 
    -- associated with Ipv4 header and will be bound to the ports
    -- or vlans on device.

     rcIpv4AclTable    OBJECT-TYPE
        SYNTAX          SEQUENCE OF  RcIpv4AclEntry
        MAX-ACCESS      not-accessible
        STATUS          current
        DESCRIPTION     "IP version 4 access list control table"
    	::= { rcIpv4AccessList 1 }    
    
     rcIpv4AclEntry  OBJECT-TYPE
		SYNTAX          RcIpv4AclEntry
		MAX-ACCESS      not-accessible
        STATUS          current
		DESCRIPTION     "An entry in the rcIpv4AclTable."
		INDEX { rcAclId, rcAclRuleId }
		::= { rcIpv4AclTable 1 }
		
	RcIpv4AclEntry ::=	SEQUENCE { 
		rcIpv4AclAccessType         AclAccessType,
		rcIpv4AclMatchFieldFlag     AclMatchField,
		rcIpv4AclSrcIpv4Address     IpAddress,
		rcIpv4AclSrcIpv4Mask        IpAddress,
		rcIpv4AclDestIpv4Address    IpAddress,
		rcIpv4AclDestIpv4Mask       IpAddress,
		rcIpv4AclIpv4Precedence     INTEGER,
		rcIpv4AclIpv4Tos            INTEGER,
		rcIpv4AclIpv4Dscp           INTEGER,
		rcIpv4AclIpv4MfFlag         INTEGER,
		rcIpv4AclUpperProtocol      INTEGER,
		rcIpv4AclSrcProtocolPort    InetPortNumber,
		rcIpv4AclDestProtocolPort   InetPortNumber,
		rcIpv4AclTcpFlags           INTEGER,
		rcIpv4AclRowStatus          RowStatus,
		rcIpv4AclSrcProtocolPortBoundHigh    InetPortNumber,
		rcIpv4AclDestProtocolPortBoundHigh   InetPortNumber
		}		

    	rcIpv4AclAccessType  OBJECT-TYPE
	        SYNTAX 			AclAccessType
	        MAX-ACCESS 		read-create
	        STATUS 			current
	        DESCRIPTION		"Access type of L2 acl rule."
	        ::= { rcIpv4AclEntry 1 }   
    
	    rcIpv4AclMatchFieldFlag  OBJECT-TYPE
	        SYNTAX 			AclMatchField
	        MAX-ACCESS 		read-create
	        STATUS 			current
	        DESCRIPTION		"Set the match filed of the table."
	        ::= { rcIpv4AclEntry 2 }  
	         
	    rcIpv4AclSrcIpv4Address  OBJECT-TYPE
	        SYNTAX 			IpAddress
	        MAX-ACCESS 		read-create
	        STATUS 			current
	        DESCRIPTION		"Source IP address."
	        ::= { rcIpv4AclEntry 3 }
	        
	    rcIpv4AclSrcIpv4Mask  OBJECT-TYPE
	        SYNTAX 			IpAddress    
	        MAX-ACCESS 		read-create
	        STATUS 			current
	        DESCRIPTION		"SVLAN COS."
	        ::= { rcIpv4AclEntry 4 }
	        
	    rcIpv4AclDestIpv4Address  OBJECT-TYPE
	        SYNTAX 			IpAddress
	        MAX-ACCESS 		read-create
	        STATUS 			current
	        DESCRIPTION		"Source IP address mask."
	        ::= { rcIpv4AclEntry 5 }
	        
	    rcIpv4AclDestIpv4Mask  OBJECT-TYPE
	        SYNTAX 			IpAddress
	        MAX-ACCESS 		read-create
	        STATUS 			current
	        DESCRIPTION		"Destination IP address."
	        ::= { rcIpv4AclEntry 6 }
	        
	    rcIpv4AclIpv4Precedence  OBJECT-TYPE
	        SYNTAX 			INTEGER {
	        					routine(0),
			                    priority(1),
			                    immediate(2),
			                    flash(3),
			                    flash-override(4),
			                    critical(5),
			                    internet(6),
			                    network(7)
			                }
	        MAX-ACCESS 		read-create
	        STATUS 			current
	        DESCRIPTION		"The value of the IP precedence in the IP protocol. 
							It conflicts with the Tos and Dscp when setting."
	        ::= { rcIpv4AclEntry 7 }
	        
	    rcIpv4AclIpv4Tos  OBJECT-TYPE
	        SYNTAX 			INTEGER (0..15)
	        MAX-ACCESS 		read-create
	        STATUS 			current
	        DESCRIPTION		"The value of the TOS in the IP protocol. 
							It conflicts with the Precedence and Dscp when setting."
	        ::= { rcIpv4AclEntry 8 }
	        
	    rcIpv4AclIpv4Dscp  OBJECT-TYPE
	        SYNTAX 			INTEGER (0..63)    
	        MAX-ACCESS 		read-create
	        STATUS 			current
	        DESCRIPTION		"The value of the DSCP in the IP protocol. 
							It conflicts with the Precedence and Tos when setting."
	        ::= { rcIpv4AclEntry 9 }
	        
	    rcIpv4AclIpv4MfFlag  OBJECT-TYPE
	        SYNTAX 			INTEGER {
	        					nofragments(1),
	        					fragments(2)
	        				}
	        MAX-ACCESS 		read-create
	        STATUS 			current
	        DESCRIPTION		"The flag that marks whether there are another IP fragments."
	        ::= { rcIpv4AclEntry 10 }
	        
	    rcIpv4AclUpperProtocol  OBJECT-TYPE
	        SYNTAX 			INTEGER(0..255)
	        MAX-ACCESS 		read-create
	        STATUS 			current
	        DESCRIPTION		"The protocol type in the IP protocol.To match any Internet protocol, use the ip(0)."
	        ::= { rcIpv4AclEntry 11 }
	        
	    rcIpv4AclSrcProtocolPort  OBJECT-TYPE
	        SYNTAX 			InetPortNumber    
	        MAX-ACCESS 		read-create
	        STATUS 			current
	        DESCRIPTION		"The source protocol port in the TCP or UDP protocol."
	        ::= { rcIpv4AclEntry 12 }
	        
	    rcIpv4AclDestProtocolPort  OBJECT-TYPE
	        SYNTAX 			InetPortNumber
	        MAX-ACCESS 		read-create
	        STATUS 			current
	        DESCRIPTION		"The destination protocol port in the TCP or UDP protocol."
	        ::= { rcIpv4AclEntry 13 }
	        
	    rcIpv4AclTcpFlags  OBJECT-TYPE
	        SYNTAX 			INTEGER(0..63)    
	        MAX-ACCESS 		read-create
	        STATUS 			current
	        DESCRIPTION		"The flags in the TCP protocol."
	        ::= { rcIpv4AclEntry 14 }
	        
	    rcIpv4AclRowStatus  OBJECT-TYPE
	        SYNTAX 			RowStatus
	        MAX-ACCESS 		read-create
	        STATUS 			current
	        DESCRIPTION		"Row status of the table."
	        ::= { rcIpv4AclEntry 15 } 
	        
	    rcIpv4AclSrcProtocolPortBoundHigh  OBJECT-TYPE
	        SYNTAX 			InetPortNumber    
	        MAX-ACCESS 		read-create
	        STATUS 			current
	        DESCRIPTION		"The source protocol end port in the TCP or UDP protocol."
	        ::= { rcIpv4AclEntry 16 }
	        
	    rcIpv4AclDestProtocolPortBoundHigh  OBJECT-TYPE
	        SYNTAX 			InetPortNumber
	        MAX-ACCESS 		read-create
	        STATUS 			current
	        DESCRIPTION		"The destination protocol end port in the TCP or UDP protocol."
	        ::= { rcIpv4AclEntry 17 }

-- Ipv6 Access List Control Table
	-- The Ipv6 access control list contains some rules that are 
    -- associated with Ipv6 header and will be bound to the ports
    -- or vlans on device.

     rcIpv6AclTable    OBJECT-TYPE
        SYNTAX          SEQUENCE OF  RcIpv6AclEntry
        MAX-ACCESS      not-accessible
        STATUS          current
        DESCRIPTION     "IP version 6 access list control table"
    	::= { rcIpv6AccessList 1 }    
    
     rcIpv6AclEntry  OBJECT-TYPE
		SYNTAX          RcIpv6AclEntry
		MAX-ACCESS      not-accessible
        STATUS          current
		DESCRIPTION     "An entry in the rcIpv6AclTable."
		INDEX { rcAclId, rcAclRuleId }
		::= { rcIpv6AclTable 1 }
		
	RcIpv6AclEntry ::=	SEQUENCE { 
		rcIpv6AclAccessType              AclAccessType,
		rcIpv6AclMatchFieldFlag          AclMatchField,
		rcIpv6AclSrcIpv6Address          Ipv6Address,
		rcIpv6AclSrcIpv6PrefixLen        InetAddressPrefixLength,
		rcIpv6AclDestIpv6Address         Ipv6Address,
		rcIpv6AclDestIpv6PrefixLen       InetAddressPrefixLength,
		rcIpv6AclTrafficClass            INTEGER,
		rcIpv6AclFlowLabel               INTEGER,
		rcIpv6AclNextHeader              INTEGER,
		rcIpv6AclSrcProtocolPort         InetPortNumber,
		rcIpv6AclDestProtocolPort        InetPortNumber,
		rcIpv6AclTcpFlags                INTEGER,
		rcIpv6AclRowStatus               RowStatus,
		rcIpv6AclSrcProtocolPortBoundHigh         InetPortNumber,
		rcIpv6AclDestProtocolPortBoundHigh        InetPortNumber
		}		

    	rcIpv6AclAccessType  OBJECT-TYPE
	        SYNTAX 			AclAccessType
	        MAX-ACCESS 		read-create
	        STATUS 			current
	        DESCRIPTION		"Access type of L2 acl rule."
	        ::= { rcIpv6AclEntry 1 }   
    
	    rcIpv6AclMatchFieldFlag  OBJECT-TYPE
	        SYNTAX 			AclMatchField
	        MAX-ACCESS 		read-create
	        STATUS 			current
	        DESCRIPTION		"Set the match filed of the table."
	        ::= { rcIpv6AclEntry 2 }  
	         
	    rcIpv6AclSrcIpv6Address  OBJECT-TYPE
	        SYNTAX 			Ipv6Address
	        MAX-ACCESS 		read-create
	        STATUS 			current
	        DESCRIPTION		"Source IP version 6 address."
	        ::= { rcIpv6AclEntry 3 }
	        
	    rcIpv6AclSrcIpv6PrefixLen  OBJECT-TYPE
	        SYNTAX 			InetAddressPrefixLength    
	        MAX-ACCESS 		read-create
	        STATUS 			current
	        DESCRIPTION		"Source IP version 6 address prefix length."
	        ::= { rcIpv6AclEntry 4 }
	        
	    rcIpv6AclDestIpv6Address  OBJECT-TYPE
	        SYNTAX 			Ipv6Address
	        MAX-ACCESS 		read-create
	        STATUS 			current
	        DESCRIPTION		"Destination IP version 6 address."
	        ::= { rcIpv6AclEntry 5 }
	        
	    rcIpv6AclDestIpv6PrefixLen  OBJECT-TYPE
	        SYNTAX 			InetAddressPrefixLength
	        MAX-ACCESS 		read-create
	        STATUS 			current
	        DESCRIPTION		"Destination IP version 6 address prefix length."
	        ::= { rcIpv6AclEntry 6 }
	        
	    rcIpv6AclTrafficClass  OBJECT-TYPE
	        SYNTAX 			INTEGER (0..255)
	        MAX-ACCESS 		read-create
	        STATUS 			current
	        DESCRIPTION		"The value of the IP precedence in the IP protocol. 
							It conflicts with the Tos and Dscp when setting."
	        ::= { rcIpv6AclEntry 7 }
	        
	    rcIpv6AclFlowLabel  OBJECT-TYPE
	        SYNTAX 			INTEGER (0..1048575)
	        MAX-ACCESS 		read-create
	        STATUS 			current
	        DESCRIPTION		"The value of the TOS in the IP protocol. 
							It conflicts with the Precedence and Dscp when setting."
	        ::= { rcIpv6AclEntry 8 }
	        
	    rcIpv6AclNextHeader  OBJECT-TYPE
	        SYNTAX 			INTEGER (0..255)    
	        MAX-ACCESS 		read-create
	        STATUS 			current
	        DESCRIPTION		"The value of the DSCP in the IP protocol. 
							It conflicts with the Precedence and Tos when setting."
	        ::= { rcIpv6AclEntry 9 }

	    rcIpv6AclSrcProtocolPort  OBJECT-TYPE
	        SYNTAX 			InetPortNumber    
	        MAX-ACCESS 		read-create
	        STATUS 			current
	        DESCRIPTION		"The source protocol port in the TCP or UDP protocol."
	        ::= { rcIpv6AclEntry 10 }
	        
	    rcIpv6AclDestProtocolPort  OBJECT-TYPE
	        SYNTAX 			InetPortNumber
	        MAX-ACCESS 		read-create
	        STATUS 			current
	        DESCRIPTION		"The destination protocol port in the TCP or UDP protocol."
	        ::= { rcIpv6AclEntry 11 }
	        
	    rcIpv6AclTcpFlags  OBJECT-TYPE
	        SYNTAX 			INTEGER(0..63)    
	        MAX-ACCESS 		read-create
	        STATUS 			current
	        DESCRIPTION		"The flags in the TCP protocol."
	        ::= { rcIpv6AclEntry 12 }
	        
	    rcIpv6AclRowStatus  OBJECT-TYPE
	        SYNTAX 			RowStatus
	        MAX-ACCESS 		read-create
	        STATUS 			current
	        DESCRIPTION		"Row status of the table."
	        ::= { rcIpv6AclEntry 13 } 
	    
	    rcIpv6AclSrcProtocolPortBoundHigh  OBJECT-TYPE
	        SYNTAX 			InetPortNumber    
	        MAX-ACCESS 		read-create
	        STATUS 			current
	        DESCRIPTION		"The source protocol end port in the TCP or UDP protocol."
	        ::= { rcIpv6AclEntry 14 }
	        
	    rcIpv6AclDestProtocolPortBoundHigh  OBJECT-TYPE
	        SYNTAX 			InetPortNumber
	        MAX-ACCESS 		read-create
	        STATUS 			current
	        DESCRIPTION		"The destination protocol end port in the TCP or UDP protocol."
	        ::= { rcIpv6AclEntry 15 }


-- Hybrid Access List Control Table
	-- The hybrid access control list contains some rules that are 
    -- associated with layer 2 and Ipv4 header, and will be bound to the ports
    -- or vlans on device.

     rcHybridAclTable    OBJECT-TYPE
        SYNTAX          SEQUENCE OF  RcHybridAclEntry
        MAX-ACCESS      not-accessible
        STATUS          current
        DESCRIPTION     "Hybrid access list control table"
    	::= { rcHybridAccessList 1 }    
    
     rcHybridAclEntry  OBJECT-TYPE
		SYNTAX          RcHybridAclEntry
		MAX-ACCESS      not-accessible
        STATUS          current
		DESCRIPTION     "An entry in the rcHybridAclTable."
		INDEX { rcAclId, rcAclRuleId }
		::= { rcHybridAclTable 1 }
		
	RcHybridAclEntry ::=	SEQUENCE { 
		rcHybridAclAccessType           AclAccessType,
		rcHybridAclMatchFieldFlag       AclMatchField,
		rcHybridAclSVlanId              AclVlanId,
		rcHybridAclSVlanCos             AclVlanCos,
		rcHybridAclCVlanId              AclVlanId,
		rcHybridAclCVlanCos             AclVlanCos,
		rcHybridAclSrcMacAddress        MacAddress,
		rcHybridAclSrcMacMask           MacAddress,
		rcHybridAclDstMacAddress        MacAddress,
		rcHybridAclDstMacMask           MacAddress,
		rcHybridAclEthernetType         INTEGER,
		rcHybridAclEthernetTypeMask     INTEGER,
		rcHybridAclSrcIpv4Address     	IpAddress,
		rcHybridAclSrcIpv4Mask        	IpAddress,
		rcHybridAclDestIpv4Address    	IpAddress,
		rcHybridAclDestIpv4Mask       	IpAddress,
		rcHybridAclIpv4Precedence     	INTEGER,
		rcHybridAclIpv4Tos            	INTEGER,
		rcHybridAclIpv4Dscp          	INTEGER,
		rcHybridAclIpv4MfFlag        	INTEGER,
		rcHybridAclUpperProtocol    	INTEGER,
		rcHybridAclSrcProtocolPort      InetPortNumber,
		rcHybridAclDestProtocolPort     InetPortNumber,
		rcHybridAclTcpFlags             INTEGER,
		rcHybridAclRowStatus            RowStatus,
		rcHybridAclSrcProtocolPortBoundHigh      InetPortNumber,
		rcHybridAclDestProtocolPortBoundHigh     InetPortNumber
		}		
        
    	rcHybridAclAccessType  OBJECT-TYPE
	        SYNTAX 			AclAccessType
	        MAX-ACCESS 		read-create
	        STATUS 			current
	        DESCRIPTION		"Access type of L2 acl rule."
	        ::= { rcHybridAclEntry 1 }   
    
	    rcHybridAclMatchFieldFlag  OBJECT-TYPE
	        SYNTAX 			AclMatchField
	        MAX-ACCESS 		read-create
	        STATUS 			current
	        DESCRIPTION		"Set the match filed of the table."
	        ::= { rcHybridAclEntry 2 }  
	         
	    rcHybridAclSVlanId  OBJECT-TYPE
	        SYNTAX 			AclVlanId
	        MAX-ACCESS 		read-create
	        STATUS 			current
	        DESCRIPTION		"SVLAN ID."
	        ::= { rcHybridAclEntry 3 }
	        
	    rcHybridAclSVlanCos  OBJECT-TYPE
	        SYNTAX 			AclVlanCos    
	        MAX-ACCESS 		read-create
	        STATUS 			current
	        DESCRIPTION		"SVLAN COS."
	        ::= { rcHybridAclEntry 4 }
	        
	    rcHybridAclCVlanId  OBJECT-TYPE
	        SYNTAX 			AclVlanId
	        MAX-ACCESS 		read-create
	        STATUS 			current
	        DESCRIPTION		"CVLAN ID."
	        ::= { rcHybridAclEntry 5 }
	        
	    rcHybridAclCVlanCos  OBJECT-TYPE
	        SYNTAX 			AclVlanCos
	        MAX-ACCESS 		read-create
	        STATUS 			current
	        DESCRIPTION		"CVLAN COS."
	        ::= { rcHybridAclEntry 6 }
	        
	    rcHybridAclSrcMacAddress  OBJECT-TYPE
	        SYNTAX 			MacAddress    
	        MAX-ACCESS 		read-create
	        STATUS 			current
	        DESCRIPTION		"Source MAC address."
	        ::= { rcHybridAclEntry 7 }
	        
	    rcHybridAclSrcMacMask  OBJECT-TYPE
	        SYNTAX 			MacAddress
	        MAX-ACCESS 		read-create
	        STATUS 			current
	        DESCRIPTION		"MAc address mask."
	        ::= { rcHybridAclEntry 8 }
	        
	    rcHybridAclDstMacAddress  OBJECT-TYPE
	        SYNTAX 			MacAddress    
	        MAX-ACCESS 		read-create
	        STATUS 			current
	        DESCRIPTION		"Destination MAC address."
	        ::= { rcHybridAclEntry 9 }
	        
	    rcHybridAclDstMacMask  OBJECT-TYPE
	        SYNTAX 			MacAddress
	        MAX-ACCESS 		read-create
	        STATUS 			current
	        DESCRIPTION		"Destination MAC address mask."
	        ::= { rcHybridAclEntry 10 }
	        
	    rcHybridAclEthernetType  OBJECT-TYPE
	        SYNTAX 			INTEGER(1536..65535)
	        MAX-ACCESS 		read-create
	        STATUS 			current
	        DESCRIPTION		"Ethernet type in layer 2 framer header."
	        ::= { rcHybridAclEntry 11 }
	        
	    rcHybridAclEthernetTypeMask  OBJECT-TYPE
	        SYNTAX 			INTEGER(0..65535)    
	        MAX-ACCESS 		read-create
	        STATUS 			current
	        DESCRIPTION		"Ethernet type mask."
	        ::= { rcHybridAclEntry 12 }
	        
	    rcHybridAclSrcIpv4Address  OBJECT-TYPE
	        SYNTAX 			IpAddress
	        MAX-ACCESS 		read-create
	        STATUS 			current
	        DESCRIPTION		"Source IP address."
	        ::= { rcHybridAclEntry 13 }
	        
	    rcHybridAclSrcIpv4Mask  OBJECT-TYPE
	        SYNTAX 			IpAddress    
	        MAX-ACCESS 		read-create
	        STATUS 			current
	        DESCRIPTION		"SVLAN COS."
	        ::= { rcHybridAclEntry 14 }
	        
	    rcHybridAclDestIpv4Address  OBJECT-TYPE
	        SYNTAX 			IpAddress
	        MAX-ACCESS 		read-create
	        STATUS 			current
	        DESCRIPTION		"Source IP address mask."
	        ::= { rcHybridAclEntry 15 }
	        
	    rcHybridAclDestIpv4Mask  OBJECT-TYPE
	        SYNTAX 			IpAddress
	        MAX-ACCESS 		read-create
	        STATUS 			current
	        DESCRIPTION		"Destination IP address."
	        ::= { rcHybridAclEntry 16 }
	        
	    rcHybridAclIpv4Precedence  OBJECT-TYPE
	        SYNTAX 			INTEGER {
	        					routine(0),
			                    priority(1),
			                    immediate(2),
			                    flash(3),
			                    flash-override(4),
			                    critical(5),
			                    internet(6),
			                    network(7)
			                }
	        MAX-ACCESS 		read-create
	        STATUS 			current
	        DESCRIPTION		"The value of the IP precedence in the IP protocol. 
							It conflicts with the Tos and Dscp when setting."
	        ::= { rcHybridAclEntry 17 }
	        
	    rcHybridAclIpv4Tos  OBJECT-TYPE
	        SYNTAX 			INTEGER (0..15)
	        MAX-ACCESS 		read-create
	        STATUS 			current
	        DESCRIPTION		"The value of the TOS in the IP protocol. 
							It conflicts with the Precedence and Dscp when setting."
	        ::= { rcHybridAclEntry 18 }
	        
	    rcHybridAclIpv4Dscp  OBJECT-TYPE
	        SYNTAX 			INTEGER (0..63)    
	        MAX-ACCESS 		read-create
	        STATUS 			current
	        DESCRIPTION		"The value of the DSCP in the IP protocol. 
							It conflicts with the Precedence and Tos when setting."
	        ::= { rcHybridAclEntry 19 }
	        
	    rcHybridAclIpv4MfFlag  OBJECT-TYPE
	        SYNTAX 			INTEGER {
	        					nofragments(1),
	        					fragments(2)
	        				}
	        MAX-ACCESS 		read-create
	        STATUS 			current
	        DESCRIPTION		"The flag that marks whether there are another IP fragments."
	        ::= { rcHybridAclEntry 20 }
	        
	    rcHybridAclUpperProtocol  OBJECT-TYPE
	        SYNTAX 			INTEGER(0..255)
	        MAX-ACCESS 		read-create
	        STATUS 			current
	        DESCRIPTION		"The protocol type in the IP protocol.To match any Internet protocol, use the ip(0)."
	        ::= { rcHybridAclEntry 21 }
	        
	    rcHybridAclSrcProtocolPort  OBJECT-TYPE
	        SYNTAX 			InetPortNumber    
	        MAX-ACCESS 		read-create
	        STATUS 			current
	        DESCRIPTION		"The source protocol port in the TCP or UDP protocol."
	        ::= { rcHybridAclEntry 22 }
	        
	    rcHybridAclDestProtocolPort  OBJECT-TYPE
	        SYNTAX 			InetPortNumber
	        MAX-ACCESS 		read-create
	        STATUS 			current
	        DESCRIPTION		"The destination protocol port in the TCP or UDP protocol."
	        ::= { rcHybridAclEntry 23 }
	        
	    rcHybridAclTcpFlags  OBJECT-TYPE
	        SYNTAX 			INTEGER(0..63)    
	        MAX-ACCESS 		read-create
	        STATUS 			current
	        DESCRIPTION		"The flags in the TCP protocol."
	        ::= { rcHybridAclEntry 24 }
	        
	    rcHybridAclRowStatus  OBJECT-TYPE
	        SYNTAX 			RowStatus
	        MAX-ACCESS 		read-create
	        STATUS 			current
	        DESCRIPTION		"Row status of the table."
	        ::= { rcHybridAclEntry 25 }
	        
	    rcHybridAclSrcProtocolPortBoundHigh  OBJECT-TYPE
	        SYNTAX 			InetPortNumber    
	        MAX-ACCESS 		read-create
	        STATUS 			current
	        DESCRIPTION		"The source protocol end port in the TCP or UDP protocol."
	        ::= { rcHybridAclEntry 26 }
	        
	    rcHybridAclDestProtocolPortBoundHigh  OBJECT-TYPE
	        SYNTAX 			InetPortNumber
	        MAX-ACCESS 		read-create
	        STATUS 			current
	        DESCRIPTION		"The destination protocol end port in the TCP or UDP protocol."
	        ::= { rcHybridAclEntry 27 }  
	        
-- User Access List Control Table
	-- The user access control list profile
	rcUserAclProfileTable OBJECT-TYPE
		SYNTAX          SEQUENCE OF  RcUserAclProfileEntry
        MAX-ACCESS      not-accessible
        STATUS          current
        DESCRIPTION     "User access list profile table"
    	::= { rcUserAccessList 1 }    
    
     rcUserAclProfileEntry  OBJECT-TYPE
		SYNTAX          RcUserAclProfileEntry
		MAX-ACCESS      not-accessible
        STATUS          current
		DESCRIPTION     "An entry in the rcUserAclTable."
		INDEX { rcUserAclFieldId }
		::= { rcUserAclProfileTable 1 }
		
	RcUserAclProfileEntry ::=	SEQUENCE { 
		rcUserAclFieldId           Integer32,
		rcUserAclFieldStart        INTEGER,
		rcUserAclFieldOffset       INTEGER,
		rcUserAclFieldLength       INTEGER,
		rcUserAclFieldReferTimes   Integer32,
		rcUserAclFieldRowStatus    RowStatus
		}
		  
	rcUserAclFieldId  OBJECT-TYPE
	        SYNTAX 			Integer32(1..8)
	        MAX-ACCESS 		read-create
	        STATUS 			current
	        DESCRIPTION		"Match field ID."
	        ::= { rcUserAclProfileEntry 1 }
	        
	rcUserAclFieldStart  OBJECT-TYPE
	        SYNTAX 			INTEGER {
	        					l2(1),
	        					l3(2),
	        					l4(3)
	        					}
	        MAX-ACCESS 		read-create
	        STATUS 			current
	        DESCRIPTION		"Match field start position."
	        ::= { rcUserAclProfileEntry 2 }
	        
	rcUserAclFieldOffset  OBJECT-TYPE
	        SYNTAX 			INTEGER (0..123)
	        MAX-ACCESS 		read-create
	        STATUS 			current
	        DESCRIPTION		"Offset of match field relative the start position."
	        ::= { rcUserAclProfileEntry 3 } 
	        
	rcUserAclFieldLength  OBJECT-TYPE
	        SYNTAX 			INTEGER
	        MAX-ACCESS 		read-only
	        STATUS 			current
	        DESCRIPTION		"Length of match field."
	        ::= { rcUserAclProfileEntry 4 }
	        
	rcUserAclFieldReferTimes  OBJECT-TYPE
	        SYNTAX 			Integer32
	        MAX-ACCESS 		read-only
	        STATUS 			current
	        DESCRIPTION		"Whether the match field is used."
	        ::= { rcUserAclProfileEntry 5 }
	        
	rcUserAclFieldRowStatus  OBJECT-TYPE
	        SYNTAX 			RowStatus
	        MAX-ACCESS 		read-create
	        STATUS 			current
	        DESCRIPTION		"Row status."
	        ::= { rcUserAclProfileEntry 6 }

	-- The user access control list contains some rules that are 
    -- associated with layer 2, Ipv4 header, Ipv6 header and others,
    -- and will be bound to the ports or vlans on device.

     rcUserAclTable    OBJECT-TYPE
        SYNTAX          SEQUENCE OF  RcUserAclEntry
        MAX-ACCESS      not-accessible
        STATUS          current
        DESCRIPTION     "User access list control table"
    	::= { rcUserAccessList 2 }    
    
     rcUserAclEntry  OBJECT-TYPE
		SYNTAX          RcUserAclEntry
		MAX-ACCESS      not-accessible
        STATUS          current
		DESCRIPTION     "An entry in the rcUserAclTable."
		INDEX { rcAclId, rcAclRuleId }
		::= { rcUserAclTable 1 }
		
	RcUserAclEntry ::=	SEQUENCE { 
		rcUserAclAccessType           AclAccessType,
		rcUserAclFieldIdList          AclMatchField,
		rcUserAclMatchString          OCTET STRING,
		rcUserAclMatchMask            OCTET STRING,
		rcUserAclMatchTagType         INTEGER,
		rcUserAclRowStatus            RowStatus
		}		
        
    	rcUserAclAccessType  OBJECT-TYPE
	        SYNTAX 			AclAccessType
	        MAX-ACCESS 		read-create
	        STATUS 			current
	        DESCRIPTION		"Access type of L2 acl rule."
	        ::= { rcUserAclEntry 1 }   
    
	    rcUserAclFieldIdList  OBJECT-TYPE
	        SYNTAX 			AclMatchField
	        MAX-ACCESS 		read-create
	        STATUS 			current
	        DESCRIPTION		"Set the match filed id list of the table."
	        ::= { rcUserAclEntry 2 }  
	         
	    rcUserAclMatchString  OBJECT-TYPE
	        SYNTAX 			OCTET STRING (SIZE (0..32))
	        MAX-ACCESS 		read-create
	        STATUS 			current
	        DESCRIPTION		"Match string."
	        ::= { rcUserAclEntry 3 }
	        
	    rcUserAclMatchMask  OBJECT-TYPE
	        SYNTAX 			OCTET STRING (SIZE (0..32))
	        MAX-ACCESS 		read-create
	        STATUS 			current
	        DESCRIPTION		"Match field mask."
	        ::= { rcUserAclEntry 4 }
	        
	    rcUserAclMatchTagType  OBJECT-TYPE
	        SYNTAX 			INTEGER{
	        					any(1),
	        					untagged(2),
	        					single-tagged(3),
	        					double-tagged(4)
	        					}
	        MAX-ACCESS 		read-create
	        STATUS 			current
	        DESCRIPTION		"Match packet type."
	        ::= { rcUserAclEntry 5 }
	        
	    rcUserAclRowStatus  OBJECT-TYPE
	        SYNTAX 			RowStatus
	        MAX-ACCESS 		read-create
	        STATUS 			current
	        DESCRIPTION		"Row status."
	        ::= { rcUserAclEntry 6 }
	        
-- ACL attribute Table
	-- Manage acl attribute

     rcAclAttributeTable    OBJECT-TYPE
        SYNTAX          SEQUENCE OF  RcAclAttributeEntry
        MAX-ACCESS      not-accessible
        STATUS          current
        DESCRIPTION     "Acl attribute management table"
    	::= { rcAclAttribute 1 }    
    
     rcAclAttributeEntry  OBJECT-TYPE
		SYNTAX          RcAclAttributeEntry
		MAX-ACCESS      not-accessible
        STATUS          current
		DESCRIPTION     "An entry in the rcAclAttributeTable."
		INDEX { rcAclId }
		::= { rcAclAttributeTable 1 }
		
	RcAclAttributeEntry ::=	SEQUENCE { 
		rcAclDescString      OCTET STRING,
		rcAclReferedTimes    Gauge32,
		rcAclRowStatus       RowStatus
		}
    
    rcAclDescString  OBJECT-TYPE
	        SYNTAX 			OCTET STRING (SIZE(1..16))
	        MAX-ACCESS 		read-create
	        STATUS 			current
	        DESCRIPTION		"Acl description string."
	        ::= { rcAclAttributeEntry 1 }
	        
	rcAclReferedTimes  OBJECT-TYPE
	        SYNTAX 			Gauge32
	        MAX-ACCESS 		read-only
	        STATUS 			current
	        DESCRIPTION		"Acl referened times."
	        ::= { rcAclAttributeEntry 2 }
	        
	rcAclRowStatus  OBJECT-TYPE
	        SYNTAX 			RowStatus
	        MAX-ACCESS 		read-create
	        STATUS 			current
	        DESCRIPTION		"Acl attribute table row status."
	        ::= { rcAclAttributeEntry 3 }  

-- IPV6 Hybrid Access List Control Table
	-- The hybrid access control list contains some rules that are 
    -- associated with layer 2 and Ipv6 header, and will be bound to the ports
    -- or vlans on device.

     rcIPv6HybridAclTable    OBJECT-TYPE
        SYNTAX          SEQUENCE OF  RcIPv6HybridAclEntry
        MAX-ACCESS      not-accessible
        STATUS          current
        DESCRIPTION     "Ipv6 Hybrid access list control table"
    	::= { rcIPv6HybridAccessList 1 }    
    
     rcIPv6HybridAclEntry  OBJECT-TYPE
		SYNTAX          RcIPv6HybridAclEntry
		MAX-ACCESS      not-accessible
        STATUS          current
		DESCRIPTION     "An entry in the rcIPv6HybridAclTable."
		INDEX { rcAclId, rcAclRuleId }
		::= { rcIPv6HybridAclTable 1 }
		
	RcIPv6HybridAclEntry ::=	SEQUENCE { 
		rcIPv6HybridAclAccessType           AclAccessType,
		rcIPv6HybridAclMatchFieldFlag       AclMatchField,
		rcIPv6HybridAclSVlanId              AclVlanId,
		rcIPv6HybridAclSVlanCos             AclVlanCos,
		rcIPv6HybridAclCVlanId              AclVlanId,
		rcIPv6HybridAclCVlanCos             AclVlanCos,
		rcIPv6HybridAclSrcMacAddress        MacAddress,
		rcIPv6HybridAclSrcMacMask           MacAddress,
		rcIPv6HybridAclDstMacAddress        MacAddress,
		rcIPv6HybridAclDstMacMask           MacAddress,
		rcIPv6HybridAclEthernetType         INTEGER,
		rcIPv6HybridAclEthernetTypeMask     INTEGER,
		rcIPv6HybridAclSrcIpv6Address     	Ipv6Address,
		rcIPv6HybridAclSrcIpPrefixLen     	InetAddressPrefixLength,
		rcIPv6HybridAclTrafficClass         INTEGER,
		rcIPv6HybridAclNextHeader          	INTEGER,
		rcIPv6HybridAclSrcProtocolPort               InetPortNumber,
		rcIPv6HybridAclSrcProtocolPortBoundHigh      InetPortNumber,  
		rcIPv6HybridAclDestProtocolPort              InetPortNumber,
		rcIPv6HybridAclDestProtocolPortBoundHigh     InetPortNumber,
		rcIPv6HybridAclRowStatus            RowStatus
		}		
        
    	rcIPv6HybridAclAccessType  OBJECT-TYPE
	        SYNTAX 			AclAccessType
	        MAX-ACCESS 		read-create
	        STATUS 			current
	        DESCRIPTION		"Access type of IPv6 hybrid acl rule."
	        ::= { rcIPv6HybridAclEntry 1 }   
    
	    rcIPv6HybridAclMatchFieldFlag  OBJECT-TYPE
	        SYNTAX 			AclMatchField
	        MAX-ACCESS 		read-create
	        STATUS 			current
	        DESCRIPTION		"Set the match filed of the table."
	        ::= { rcIPv6HybridAclEntry 2 }  
	         
	    rcIPv6HybridAclSVlanId  OBJECT-TYPE
	        SYNTAX 			AclVlanId
	        MAX-ACCESS 		read-create
	        STATUS 			current
	        DESCRIPTION		"SVLAN ID."
	        ::= { rcIPv6HybridAclEntry 3 }
	        
	    rcIPv6HybridAclSVlanCos  OBJECT-TYPE
	        SYNTAX 			AclVlanCos    
	        MAX-ACCESS 		read-create
	        STATUS 			current
	        DESCRIPTION		"SVLAN COS."
	        ::= { rcIPv6HybridAclEntry 4 }
	        
	    rcIPv6HybridAclCVlanId  OBJECT-TYPE
	        SYNTAX 			AclVlanId
	        MAX-ACCESS 		read-create
	        STATUS 			current
	        DESCRIPTION		"CVLAN ID."
	        ::= { rcIPv6HybridAclEntry 5 }
	        
	    rcIPv6HybridAclCVlanCos  OBJECT-TYPE
	        SYNTAX 			AclVlanCos
	        MAX-ACCESS 		read-create
	        STATUS 			current
	        DESCRIPTION		"CVLAN COS."
	        ::= { rcIPv6HybridAclEntry 6 }
	        
	    rcIPv6HybridAclSrcMacAddress  OBJECT-TYPE
	        SYNTAX 			MacAddress    
	        MAX-ACCESS 		read-create
	        STATUS 			current
	        DESCRIPTION		"Source MAC address."
	        ::= { rcIPv6HybridAclEntry 7 }
	        
	    rcIPv6HybridAclSrcMacMask  OBJECT-TYPE
	        SYNTAX 			MacAddress
	        MAX-ACCESS 		read-create
	        STATUS 			current
	        DESCRIPTION		"MAc address mask."
	        ::= { rcIPv6HybridAclEntry 8 }
	        
	    rcIPv6HybridAclDstMacAddress  OBJECT-TYPE
	        SYNTAX 			MacAddress    
	        MAX-ACCESS 		read-create
	        STATUS 			current
	        DESCRIPTION		"Destination MAC address."
	        ::= { rcIPv6HybridAclEntry 9 }
	        
	    rcIPv6HybridAclDstMacMask  OBJECT-TYPE
	        SYNTAX 			MacAddress
	        MAX-ACCESS 		read-create
	        STATUS 			current
	        DESCRIPTION		"Destination MAC address mask."
	        ::= { rcIPv6HybridAclEntry 10 }
	        
	    rcIPv6HybridAclEthernetType  OBJECT-TYPE
	        SYNTAX 			INTEGER(1536..65535)
	        MAX-ACCESS 		read-create
	        STATUS 			current
	        DESCRIPTION		"Ethernet type in layer 2 framer header."
	        ::= { rcIPv6HybridAclEntry 11 }
	        
	    rcIPv6HybridAclEthernetTypeMask  OBJECT-TYPE
	        SYNTAX 			INTEGER(0..65535)    
	        MAX-ACCESS 		read-create
	        STATUS 			current
	        DESCRIPTION		"Ethernet type mask."
	        ::= { rcIPv6HybridAclEntry 12 }
	        
	    rcIPv6HybridAclSrcIpv6Address  OBJECT-TYPE
	        SYNTAX 			Ipv6Address
	        MAX-ACCESS 		read-create
	        STATUS 			current
	        DESCRIPTION		"Source IPv6 address."
	        ::= { rcIPv6HybridAclEntry 13 }
	        
	    rcIPv6HybridAclSrcIpPrefixLen  OBJECT-TYPE
	        SYNTAX 			InetAddressPrefixLength    
	        MAX-ACCESS 		read-create
	        STATUS 			current
	        DESCRIPTION		"Source IPv6 address prefix length."
	        ::= { rcIPv6HybridAclEntry 14 }
	        
	    rcIPv6HybridAclTrafficClass  OBJECT-TYPE
	        SYNTAX 			INTEGER(0..255)
	        MAX-ACCESS 		read-create
	        STATUS 			current
	        DESCRIPTION		"Traffic Class of ipv6 packet."
	        ::= { rcIPv6HybridAclEntry 15 }
	        
	    rcIPv6HybridAclNextHeader  OBJECT-TYPE
	        SYNTAX 			INTEGER(0..255)
	        MAX-ACCESS 		read-create
	        STATUS 			current
	        DESCRIPTION		"Next Header of ipv6 packet."
	        ::= { rcIPv6HybridAclEntry 16 }
	        
	    rcIPv6HybridAclSrcProtocolPort  OBJECT-TYPE
	        SYNTAX 			InetPortNumber
	        MAX-ACCESS 		read-create
	        STATUS 			current
	        DESCRIPTION		"source protocol start port of tcp or udp."
	        ::= { rcIPv6HybridAclEntry 17 }
	        
	    rcIPv6HybridAclSrcProtocolPortBoundHigh  OBJECT-TYPE
	        SYNTAX 			InetPortNumber
	        MAX-ACCESS 		read-create
	        STATUS 			current
	        DESCRIPTION		"source protocol terminal port of tcp or udp."
	        ::= { rcIPv6HybridAclEntry 18 }
	    
	    rcIPv6HybridAclDestProtocolPort  OBJECT-TYPE
	        SYNTAX 			InetPortNumber
	        MAX-ACCESS 		read-create
	        STATUS 			current
	        DESCRIPTION		"destination protocol start port of tcp or udp."
	        ::= { rcIPv6HybridAclEntry 19 }
	        
	    rcIPv6HybridAclDestProtocolPortBoundHigh  OBJECT-TYPE
	        SYNTAX 			InetPortNumber
	        MAX-ACCESS 		read-create
	        STATUS 			current
	        DESCRIPTION		"destination protocol terminal port of tcp or udp."
	        ::= { rcIPv6HybridAclEntry 20 }
  
	    rcIPv6HybridAclRowStatus  OBJECT-TYPE
	        SYNTAX 			RowStatus
	        MAX-ACCESS 		read-create
	        STATUS 			current
	        DESCRIPTION		"Row status of the table."
	        ::= { rcIPv6HybridAclEntry 21 }
	 
END
