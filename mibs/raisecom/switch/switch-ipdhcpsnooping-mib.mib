-- -----------------------------------------------------------------------------
-- MIB NAME : roapIpDhcpSnoopingMib
-- FILE NAME: switch-ipdhcpsnooping-mib.mib			
-- DATE     : 2012/03/09						
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2012/03/09, xiaoyingjie
-- This is the first formal version for universal MIB definition.  

IP-DHCP-SNOOPING-MIB  DEFINITIONS ::= BEGIN

IMPORTS
    MODULE-IDENTITY,
    NOTIFICATION-TYPE,
    OBJECT-TYPE                         FROM SNMPv2-SMI

    MODULE-COMPLIANCE,
    NOTIFICATION-GROUP,
    OBJECT-GROUP                        FROM SNMPv2-CONF
    MacAddress                          FROM SNMPv2-TC

    EnableVar                           FROM SWITCH-TC

    raisecomSwitchMgt					FROM RAISECOM-PONSERIES-BASE-MIB
        
    InetAddressIPv4,
    InetAddressIPv6                     FROM INET-ADDRESS-MIB;


    roapIpDhcpSnooping MODULE-IDENTITY
        LAST-UPDATED    "201203090000Z"
        ORGANIZATION    "Raisecom Technology Co., Ltd."
        CONTACT-INFO
              "raisecom
               E-mail: raisecom@raisecom.com"

        DESCRIPTION "dhcp snooping module management."
        ::= { raisecomSwitchMgt 14 }

------------------------------------------------------------------------------
-- define groups in roapIpDhcpSnooping
------------------------------------------------------------------------------
    roapIpDhcpSnoopingMibObjects
        OBJECT IDENTIFIER ::= { roapIpDhcpSnooping 1 }

    roapIpDhcpSnoopingGroup
        OBJECT IDENTIFIER ::= { roapIpDhcpSnoopingMibObjects 1 }
                 
    roapIpDhcp6SnoopingGroup
        OBJECT IDENTIFIER ::= { roapIpDhcpSnoopingMibObjects 2 }
  
------------------------------------------------------------------------------
-- begin--roapIpDhcpSnoopingGroup-----
-- roapIpDhcpSnoopingGroup scale MIB--
----------------------------------
roapIpDhcpSnoopingEnable OBJECT-TYPE
        SYNTAX EnableVar
        MAX-ACCESS read-write
        STATUS current
        DESCRIPTION
            "The state of global dhcp snooping. It has two values,
            one is enable(1),which indicates that the system start dhcp snooping;
            the other is disable(2) that means dhcp snooping is invalid in this system."
        DEFVAL { disable }
        ::= { roapIpDhcpSnoopingGroup 1 }

------------------------------------------------
-- roapIpDhcpSnoopingGroup roapIpDhcpSnoopingPortTable--
------------------------------------------------
roapIpDhcpSnoopingPortTable OBJECT-TYPE
        SYNTAX SEQUENCE OF RoapIpDhcpSnoopingPortEntry
        MAX-ACCESS not-accessible
        STATUS current
        DESCRIPTION
            "A table provides the mechanism to control DHCP Snooping per port."
        ::= { roapIpDhcpSnoopingGroup 2 }

roapIpDhcpSnoopingPortEntry OBJECT-TYPE
        SYNTAX RoapIpDhcpSnoopingPortEntry
        MAX-ACCESS not-accessible
        STATUS current
        DESCRIPTION
            "Table entry for switch dhcp snooping config based on port."
        INDEX { roapIpDhcpSnoopingPortIndex }
        ::= { roapIpDhcpSnoopingPortTable 1 }

RoapIpDhcpSnoopingPortEntry ::= SEQUENCE
    {
        roapIpDhcpSnoopingPortIndex     INTEGER,
        roapIpDhcpSnoopingPortEnable    EnableVar,
        roapIpDhcpSnoopingPortTrust     INTEGER
    }

roapIpDhcpSnoopingPortIndex OBJECT-TYPE
        SYNTAX INTEGER
        MAX-ACCESS not-accessible
        STATUS current
        DESCRIPTION
            "An index that uniquely identifies a configuration about dhcp snooping."
        ::= { roapIpDhcpSnoopingPortEntry 1}

roapIpDhcpSnoopingPortEnable OBJECT-TYPE
        SYNTAX EnableVar
        MAX-ACCESS read-write
        STATUS current
        DESCRIPTION
            "The state of dhcp snooping about specified port.
            It also has two values,one is enabled(1),which indicates that the port
            start dhcp snooping; the other is disable(2) that means dhcp snooping
            is invalid on the port.The default value is enable(1)."
        ::= { roapIpDhcpSnoopingPortEntry 2 }

roapIpDhcpSnoopingPortTrust OBJECT-TYPE
        SYNTAX      INTEGER{trusted(1), untrusted(2)}
        MAX-ACCESS  read-write
        STATUS      current
        DESCRIPTION
            "Trust state of port.It has two values,one is trusted(1),the other is untrusted(2).
            The default value is untrusted(2)."
        ::= { roapIpDhcpSnoopingPortEntry 3}

roapIpDhcpSnoopingBindCurrentRows OBJECT-TYPE
        SYNTAX INTEGER
        MAX-ACCESS read-only
        STATUS current
        DESCRIPTION
            "Current rows of binding table."
        DEFVAL { 0 }
        ::= { roapIpDhcpSnoopingGroup 3 }

roapIpDhcpSnoopingBindHistoryMaxRows OBJECT-TYPE
        SYNTAX INTEGER
        MAX-ACCESS read-only
        STATUS current
        DESCRIPTION
            "History max rows of binding table."
        DEFVAL { 0 }
        ::= { roapIpDhcpSnoopingGroup 4 }   
        

------------------------------------------------
-- roapIpDhcpSnoopingGroup roapIpDhcpSnoopingBindTable--
------------------------------------------------
roapIpDhcpSnoopingBindTable OBJECT-TYPE
        SYNTAX SEQUENCE OF RoapIpDhcpSnoopingBindEntry
        MAX-ACCESS not-accessible
        STATUS current
        DESCRIPTION
            "A table records dhcp snooping bindings."
        ::= { roapIpDhcpSnoopingGroup 5 }

roapIpDhcpSnoopingBindEntry OBJECT-TYPE
        SYNTAX RoapIpDhcpSnoopingBindEntry
        MAX-ACCESS not-accessible
        STATUS current
        DESCRIPTION
            "Table entry for dhcp snooping binding."
        INDEX { roapIpDhcpSnoopingBindIp }
        ::= { roapIpDhcpSnoopingBindTable 1 }

RoapIpDhcpSnoopingBindEntry ::= SEQUENCE
    {
        roapIpDhcpSnoopingBindIp    InetAddressIPv4,
        roapIpDhcpSnoopingBindMac   MacAddress,
        roapIpDhcpSnoopingBindLease Unsigned32,
        roapIpDhcpSnoopingBindVlan  INTEGER(1..4094),
        roapIpDhcpSnoopingBindPort  INTEGER
    }

roapIpDhcpSnoopingBindIp OBJECT-TYPE
        SYNTAX InetAddressIPv4
        MAX-ACCESS not-accessible
        STATUS current
        DESCRIPTION
            "Binding IP address, the index of this table"
        ::= { roapIpDhcpSnoopingBindEntry 1}

roapIpDhcpSnoopingBindMac OBJECT-TYPE
        SYNTAX MacAddress
        MAX-ACCESS read-only
        STATUS current
        DESCRIPTION
            "Binding MAC address."
        ::= { roapIpDhcpSnoopingBindEntry 2 }

roapIpDhcpSnoopingBindLease OBJECT-TYPE
        SYNTAX      Unsigned32
        MAX-ACCESS  read-only
        STATUS      current
        DESCRIPTION
            "Binding lease remaining time(sec)."
        ::= { roapIpDhcpSnoopingBindEntry 3}

roapIpDhcpSnoopingBindVlan OBJECT-TYPE
        SYNTAX      INTEGER (1..4094)
        MAX-ACCESS  read-only
        STATUS      current
        DESCRIPTION
            "Binding vlan."
        ::= { roapIpDhcpSnoopingBindEntry 4}

roapIpDhcpSnoopingBindPort OBJECT-TYPE
        SYNTAX      INTEGER
        MAX-ACCESS  read-only
        STATUS      current
        DESCRIPTION
            "Binding port."
        ::= { roapIpDhcpSnoopingBindEntry 5}

-- end--roapIpDhcpSnoopingGroup------------------------      


------------------------------------------------------------------------------
-- begin--roapIpDhcp6SnoopingGroup-----
-- roapIpDhcp6SnoopingGroup scale MIB--
----------------------------------
roapIpDhcp6SnoopingEnable OBJECT-TYPE
        SYNTAX EnableVar
        MAX-ACCESS read-write
        STATUS current
        DESCRIPTION
            "The state of global dhcp snooping. It has two values,
            one is enable(1),which indicates that the system start dhcp snooping;
            the other is disable(2) that means dhcp snooping is invalid in this system."
        DEFVAL { disable }
        ::= { roapIpDhcp6SnoopingGroup 1 }

------------------------------------------------
-- roapIpDhcp6SnoopingGroup roapIpDhcp6SnoopingPortTable--
------------------------------------------------
roapIpDhcp6SnoopingPortTable OBJECT-TYPE
        SYNTAX SEQUENCE OF RoapIpDhcp6SnoopingPortEntry
        MAX-ACCESS not-accessible
        STATUS current
        DESCRIPTION
            "A table provides the mechanism to control DHCP Snooping per port."
        ::= { roapIpDhcp6SnoopingGroup 2 }

roapIpDhcp6SnoopingPortEntry OBJECT-TYPE
        SYNTAX RoapIpDhcp6SnoopingPortEntry
        MAX-ACCESS not-accessible
        STATUS current
        DESCRIPTION
            "Table entry for switch dhcp snooping config based on port."
        INDEX { roapIpDhcp6SnoopingPortIndex }
        ::= { roapIpDhcp6SnoopingPortTable 1 }

RoapIpDhcp6SnoopingPortEntry ::= SEQUENCE
    {
        roapIpDhcp6SnoopingPortIndex     INTEGER,
        roapIpDhcp6SnoopingPortEnable    EnableVar,
        roapIpDhcp6SnoopingPortTrust     INTEGER
    }

roapIpDhcp6SnoopingPortIndex OBJECT-TYPE
        SYNTAX INTEGER
        MAX-ACCESS not-accessible
        STATUS current
        DESCRIPTION
            "An index that uniquely identifies a configuration about dhcp snooping."
        ::= { roapIpDhcp6SnoopingPortEntry 1}

roapIpDhcp6SnoopingPortEnable OBJECT-TYPE
        SYNTAX EnableVar
        MAX-ACCESS read-write
        STATUS current
        DESCRIPTION
            "The state of dhcp snooping about specified port.
            It also has two values,one is enabled(1),which indicates that the port
            start dhcp snooping; the other is disable(2) that means dhcp snooping
            is invalid on the port.The default value is enable(1)."
        ::= { roapIpDhcp6SnoopingPortEntry 2 }

roapIpDhcp6SnoopingPortTrust OBJECT-TYPE
        SYNTAX      INTEGER{trusted(1), untrusted(2)}
        MAX-ACCESS  read-write
        STATUS      current
        DESCRIPTION
            "Trust state of port.It has two values,one is trusted(1),the other is untrusted(2).
            The default value is untrusted(2)."
        ::= { roapIpDhcp6SnoopingPortEntry 3}
   
   
------------------------------------------------
-- roapIpDhcp6SnoopingGroup scale MIB--
------------------------------------------------
   
roapIpDhcp6SnoopingBindCurrentRows OBJECT-TYPE
        SYNTAX INTEGER
        MAX-ACCESS read-only
        STATUS current
        DESCRIPTION
            "Current rows of binding table."
        DEFVAL { 0 }
        ::= { roapIpDhcp6SnoopingGroup 3 }

roapIpDhcp6SnoopingBindHistoryMaxRows OBJECT-TYPE
        SYNTAX INTEGER
        MAX-ACCESS read-only
        STATUS current
        DESCRIPTION
            "History max rows of binding table."
        DEFVAL { 0 }
        ::= { roapIpDhcp6SnoopingGroup 4 }

------------------------------------------------
-- roapIpDhcp6SnoopingGroup roapIpDhcp6SnoopingBindTable--
------------------------------------------------
roapIpDhcp6SnoopingBindTable OBJECT-TYPE
        SYNTAX SEQUENCE OF RoapIpDhcp6SnoopingBindEntry
        MAX-ACCESS not-accessible
        STATUS current
        DESCRIPTION
            "A table records dhcp snooping bindings."
        ::= { roapIpDhcp6SnoopingGroup 5 }

roapIpDhcp6SnoopingBindEntry OBJECT-TYPE
        SYNTAX RoapIpDhcp6SnoopingBindEntry
        MAX-ACCESS not-accessible
        STATUS current
        DESCRIPTION
            "Table entry for dhcp snooping binding."
        INDEX { roapIpDhcp6SnoopingBindIp }
        ::= { roapIpDhcp6SnoopingBindTable 1 }

RoapIpDhcp6SnoopingBindEntry ::= SEQUENCE
    {
        roapIpDhcp6SnoopingBindIp    InetAddressIPv6,
        roapIpDhcp6SnoopingBindMac   MacAddress,
        roapIpDhcp6SnoopingBindLease Unsigned32,
        roapIpDhcp6SnoopingBindVlan  INTEGER,
        roapIpDhcp6SnoopingBindPort  INTEGER
    }

roapIpDhcp6SnoopingBindIp OBJECT-TYPE
        SYNTAX InetAddressIPv6
        MAX-ACCESS not-accessible
        STATUS current
        DESCRIPTION
            "Binding IP address, the index of this table"
        ::= { roapIpDhcp6SnoopingBindEntry 1}

roapIpDhcp6SnoopingBindMac OBJECT-TYPE
        SYNTAX MacAddress
        MAX-ACCESS read-only
        STATUS current
        DESCRIPTION
            "Binding MAC address."
        ::= { roapIpDhcp6SnoopingBindEntry 2 }

roapIpDhcp6SnoopingBindLease OBJECT-TYPE
        SYNTAX      Unsigned32
        MAX-ACCESS  read-only
        STATUS      current
        DESCRIPTION
            "Binding lease remaining time(sec)."
        ::= { roapIpDhcp6SnoopingBindEntry 3}

roapIpDhcp6SnoopingBindVlan OBJECT-TYPE
        SYNTAX      INTEGER
        MAX-ACCESS  read-only
        STATUS      current
        DESCRIPTION
            "Binding vlan."
        ::= { roapIpDhcp6SnoopingBindEntry 4}

roapIpDhcp6SnoopingBindPort OBJECT-TYPE
        SYNTAX      INTEGER
        MAX-ACCESS  read-only
        STATUS      current
        DESCRIPTION
            "Binding port."
        ::= { roapIpDhcp6SnoopingBindEntry 5}

-- end--roapIpDhcp6SnoopingGroup------------------------
  
END
