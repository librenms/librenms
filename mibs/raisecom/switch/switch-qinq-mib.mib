-- -----------------------------------------------------------------------------
-- MIB NAME : rcQinQCfg
-- FILE NAME: switch-qinq-mib.mib			
-- DATE     : 2012/3/19						
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2012/3/19, yanzhijie
-- This is the first formal version for universal MIB definition.
 
SWITCH-QINQ-MIB DEFINITIONS ::= BEGIN
     
	IMPORTS
		MODULE-IDENTITY, OBJECT-TYPE, NOTIFICATION-TYPE,
		Integer32, IpAddress, Counter32, Unsigned32
			FROM SNMPv2-SMI

		TruthValue, MacAddress, RowStatus
			FROM SNMPv2-TC
	    
	    Ipv6Address
   			FROM IPV6-TC
		
		InetAddressPrefixLength, InetPortNumber
			FROM INET-ADDRESS-MIB
			
		ifIndex
        	FROM IF-MIB
        	
        OltPortIndex
			FROM RAISECOM-PONSERIES-TC

		EnableVar
			FROM SWITCH-TC 


		raisecomSwitchMgt
			FROM RAISECOM-PONSERIES-BASE-MIB;
			
	rcQinQCfg MODULE-IDENTITY
		LAST-UPDATED 	"201107200000Z"
		ORGANIZATION 	"rc TECH, Ltd."
		CONTACT-INFO 	"www.rc.com"
		DESCRIPTION  	
		    "The MIB module defining objects for version management  functions"
		::= { raisecomSwitchMgt  7}
		
--Textual Conventions
------------------------------------------------------------------------------
--	textual conventions in swtich-qinq-mib
------------------------------------------------------------------------------

------------------------------------------------------------------------------


--rcQinQCfg 

------------------------------------------------------------------------------
--	define groups in swtich-qinq-mib
------------------------------------------------------------------------------
	rcQinQAcl	    OBJECT IDENTIFIER ::= {	rcQinQCfg 1 }
	rcQinQPort		OBJECT IDENTIFIER ::= {	rcQinQCfg 2 }
------------------------------------------------------------------------------
	  	
-- QinQ Access List Control Management
	-- QinQ access control list attribute table

    rcQinQAclAttributeTable    OBJECT-TYPE
        SYNTAX          SEQUENCE OF  RcQinQAclAttributeEntry
        MAX-ACCESS      not-accessible
        STATUS          current
        DESCRIPTION     "QinQ ACL attribute table"
    	::= { rcQinQAcl 1 }    
    
    rcQinQAclAttributeEntry  OBJECT-TYPE
		SYNTAX          RcQinQAclAttributeEntry
		MAX-ACCESS      not-accessible
        STATUS          current
		DESCRIPTION     "An entry in the rcQinQAclTable."
		INDEX { rcQinQAclId }
		::= { rcQinQAclAttributeTable 1 }
		
	RcQinQAclAttributeEntry ::=	SEQUENCE { 
		rcQinQAclId                       Integer32,
		rcQinQAclDesc                     OCTET STRING,
		rcQinQAclReferTimes               Gauge32,
		rcQinQAclAttributeRowStatus       RowStatus
		}		
    
		rcQinQAclId  OBJECT-TYPE
	        SYNTAX 			Integer32(1..2000)
	        MAX-ACCESS 		not-accessible
	        STATUS 			current
	        DESCRIPTION		"Index of rcQinQAclTable."
	        ::= { rcQinQAclAttributeEntry 1 }        
         
    	rcQinQAclDesc  OBJECT-TYPE
	        SYNTAX 			OCTET STRING (SIZE(1..16))
	        MAX-ACCESS 		read-create
	        STATUS 			current
	        DESCRIPTION		"Description of ACL."
	        ::= { rcQinQAclAttributeEntry 2 }    
        
    	rcQinQAclReferTimes  OBJECT-TYPE
	        SYNTAX 			Gauge32
	        MAX-ACCESS 		read-only
	        STATUS 			current
	        DESCRIPTION		"Reference times of acl rule."
	        ::= { rcQinQAclAttributeEntry 3 }   
    
	    rcQinQAclAttributeRowStatus  OBJECT-TYPE
	        SYNTAX 			RowStatus
	        MAX-ACCESS 		read-create
	        STATUS 			current
	        DESCRIPTION		"Set RowStatus of the table."
	        ::= { rcQinQAclAttributeEntry 4 }

-- QinQ Access List Control Table
	-- The QinQ access control list contains some rules that are 
    -- associated with Layer 2 and Ipv4 header and will be bound to the ports
    -- or vlans on device.

    rcQinQAclRuleTable    OBJECT-TYPE
        SYNTAX          SEQUENCE OF  RcQinQAclRuleEntry
        MAX-ACCESS      not-accessible
        STATUS          current
        DESCRIPTION     "QinQ access list control table"
    	::= { rcQinQAcl 2 }    
    
    rcQinQAclRuleEntry  OBJECT-TYPE
		SYNTAX          RcQinQAclRuleEntry
		MAX-ACCESS      not-accessible
        STATUS          current
		DESCRIPTION     "An entry in the rcQinQAclTable."
		INDEX { rcQinQAclId, rcQinQAclRuleId }
		::= { rcQinQAclRuleTable 1 }
		
	RcQinQAclRuleEntry ::=	SEQUENCE { 
		rcQinQAclRuleId            Integer32 (1..256),
		rcQinQAclAccessType        INTEGER,
		rcQinQAclMatchField        BITS,
		rcQinQAclSrcMac            MacAddress,
		rcQinQAclSrcMacMask        MacAddress,
		rcQinQAclSVlanId           INTEGER (1..4094),
		rcQinQAclSVlanCos          INTEGER (0..7),
		rcQinQAclCVlanId           INTEGER (1..4094),
		rcQinQAclCVlanCos          INTEGER (0..7),
		rcQinQAclEtherType         INTEGER,
		rcQinQAclEtherTypeMask     INTEGER,
		rcQinQAclSrcIp             IpAddress,
		rcQinQAclSrcIpMask         IpAddress,
		rcQinQAclDstIp             IpAddress,
		rcQinQAclDstIpMask         IpAddress,
		rcQinQAclIpProtocol        INTEGER,
		rcQinQAclSrcL4Port         InetPortNumber,
		rcQinQAclDstL4Port         InetPortNumber,
		rcQinQAclRowStatus         RowStatus,
		rcQinQAclSrcIpv6Addr       Ipv6Address,
		rcQinQAclSrcIpv6PrefixLen  InetAddressPrefixLength,
		rcQinQAclDstIpv6Addr       Ipv6Address,
		rcQinQAclDstIpv6PrefixLen  InetAddressPrefixLength,
		rcQinQAclIpv6TrafficClass  INTEGER,
		rcQinQAclIpv6NextHeader    INTEGER
		}		

    	rcQinQAclRuleId  OBJECT-TYPE
	        SYNTAX 			Integer32 (1..256)
	        MAX-ACCESS 		not-accessible
	        STATUS 			current
	        DESCRIPTION		"QinQ acl rule ID."
	        ::= { rcQinQAclRuleEntry 1 }
	        
	    rcQinQAclAccessType  OBJECT-TYPE
	        SYNTAX 			INTEGER {
	        					deny(1),
	        					permit(2)
	        					}
	        MAX-ACCESS 		read-create
	        STATUS 			current
	        DESCRIPTION		"QinQ acl access type."
	        ::= { rcQinQAclRuleEntry 2 }     
    
	    rcQinQAclMatchField  OBJECT-TYPE
	        SYNTAX 			BITS{
	        					src_mac(0),
	        					svlan_id(1),
	        					svlan_cos(2),
	        					cvlan_id(3),
	        					cvlan_cos(4),
	        					ether_type(5),
	        					src_ip(6),
	        					dst_ip(7),
	        					ip_protocol(8),
	        					src_port(9),
	        					dst_port(10),
	        					src_ipv6(11),
	        					src_prelen(12),
	        					dst_ipv6(13),
	        					dst_prelen(14),
	        					ipv6_trafclass(15),
	        					ipv6_nextheader(16)
	        					}
	        MAX-ACCESS 		read-create
	        STATUS 			current
	        DESCRIPTION		"Set the match filed of the table."
	        ::= { rcQinQAclRuleEntry 3 }  
	         
	    rcQinQAclSrcMac  OBJECT-TYPE
	        SYNTAX 			MacAddress
	        MAX-ACCESS 		read-create
	        STATUS 			current
	        DESCRIPTION		"Source MAC address."
	        ::= { rcQinQAclRuleEntry 4 }
	        
	    rcQinQAclSrcMacMask  OBJECT-TYPE
	        SYNTAX 			MacAddress    
	        MAX-ACCESS 		read-create
	        STATUS 			current
	        DESCRIPTION		"Source MAC address MASK."
	        ::= { rcQinQAclRuleEntry 5 }
	        
	    rcQinQAclSVlanId  OBJECT-TYPE
	        SYNTAX 			INTEGER (1..4094)
	        MAX-ACCESS 		read-create
	        STATUS 			current
	        DESCRIPTION		"SVLAN ID."
	        ::= { rcQinQAclRuleEntry 6 }
	        
	    rcQinQAclSVlanCos  OBJECT-TYPE
	        SYNTAX 			INTEGER (0..7)
	        MAX-ACCESS 		read-create
	        STATUS 			current
	        DESCRIPTION		"SVLAN COS."
	        ::= { rcQinQAclRuleEntry 7 }
	        
	    rcQinQAclCVlanId  OBJECT-TYPE
	        SYNTAX 			INTEGER (1..4094)
	        MAX-ACCESS 		read-create
	        STATUS 			current
	        DESCRIPTION		"CVLAN ID."
	        ::= { rcQinQAclRuleEntry 8 }
	        
	    rcQinQAclCVlanCos  OBJECT-TYPE
	        SYNTAX 			INTEGER (0..7)
	        MAX-ACCESS 		read-create
	        STATUS 			current
	        DESCRIPTION		"CVLAN COS."
	        ::= { rcQinQAclRuleEntry 9 }
	        
	    rcQinQAclEtherType  OBJECT-TYPE
	        SYNTAX 			INTEGER
	        MAX-ACCESS 		read-create
	        STATUS 			current
	        DESCRIPTION		"Ether type."
	        ::= { rcQinQAclRuleEntry 10 }
	        
	    rcQinQAclEtherTypeMask  OBJECT-TYPE
	        SYNTAX 			INTEGER
	        MAX-ACCESS 		read-create
	        STATUS 			current
	        DESCRIPTION		"Ether type mask."
	        ::= { rcQinQAclRuleEntry 11 }
	        
	    rcQinQAclSrcIp  OBJECT-TYPE
	        SYNTAX 			IpAddress    
	        MAX-ACCESS 		read-create
	        STATUS 			current
	        DESCRIPTION		"Source IP address."
	        ::= { rcQinQAclRuleEntry 12 }
	        
	    rcQinQAclSrcIpMask  OBJECT-TYPE
	        SYNTAX 			IpAddress
	        MAX-ACCESS 		read-create
	        STATUS 			current
	        DESCRIPTION		"Source IP address mask."
	        ::= { rcQinQAclRuleEntry 13 }
	        
	    rcQinQAclDstIp  OBJECT-TYPE
	        SYNTAX 			IpAddress
	        MAX-ACCESS 		read-create
	        STATUS 			current
	        DESCRIPTION		"Destination IP address."
	        ::= { rcQinQAclRuleEntry 14 }
	        
	    rcQinQAclDstIpMask  OBJECT-TYPE
	        SYNTAX 			IpAddress
	        MAX-ACCESS 		read-create
	        STATUS 			current
	        DESCRIPTION		"Destination IP address mask."
	        ::= { rcQinQAclRuleEntry 15 }
	        
	    rcQinQAclIpProtocol  OBJECT-TYPE
	        SYNTAX 			INTEGER
	        MAX-ACCESS 		read-create
	        STATUS 			current
	        DESCRIPTION		"Ip protocol contained in IP header."
	        ::= { rcQinQAclRuleEntry 16 } 
	        
	    rcQinQAclSrcL4Port  OBJECT-TYPE
	        SYNTAX 			InetPortNumber
	        MAX-ACCESS 		read-create
	        STATUS 			current
	        DESCRIPTION		"Source port of layer 4 header(TCP/UDP)."
	        ::= { rcQinQAclRuleEntry 17 }
	        
	    rcQinQAclDstL4Port  OBJECT-TYPE
	        SYNTAX 			InetPortNumber
	        MAX-ACCESS 		read-create
	        STATUS 			current
	        DESCRIPTION		"Destination port of layer 4 header(TCP/UDP)."
	        ::= { rcQinQAclRuleEntry 18 } 
	        
	    rcQinQAclRowStatus  OBJECT-TYPE
	        SYNTAX 			RowStatus
	        MAX-ACCESS 		read-create
	        STATUS 			current
	        DESCRIPTION		"Row status of table."
	        ::= { rcQinQAclRuleEntry 19 }  
	        
	    rcQinQAclSrcIpv6Addr  OBJECT-TYPE
	        SYNTAX 			Ipv6Address
	        MAX-ACCESS 		read-create
	        STATUS 			current
	        DESCRIPTION		"Source IP version 6 address."
	        ::= { rcQinQAclRuleEntry 20 }
	        
	    rcQinQAclSrcIpv6PrefixLen  OBJECT-TYPE
	        SYNTAX 			InetAddressPrefixLength    
	        MAX-ACCESS 		read-create
	        STATUS 			current
	        DESCRIPTION		"Source IP version 6 address prefix length."
	        ::= { rcQinQAclRuleEntry 21 }
	        
	    rcQinQAclDstIpv6Addr  OBJECT-TYPE
	        SYNTAX 			Ipv6Address
	        MAX-ACCESS 		read-create
	        STATUS 			current
	        DESCRIPTION		"Destination IP version 6 address."
	        ::= { rcQinQAclRuleEntry 22 }
	        
	    rcQinQAclDstIpv6PrefixLen  OBJECT-TYPE
	        SYNTAX 			InetAddressPrefixLength
	        MAX-ACCESS 		read-create
	        STATUS 			current
	        DESCRIPTION		"Destination IP version 6 address prefix length."
	        ::= { rcQinQAclRuleEntry 23 }
	        
	    rcQinQAclIpv6TrafficClass  OBJECT-TYPE
	        SYNTAX 			INTEGER (0..255)
	        MAX-ACCESS 		read-create
	        STATUS 			current
	        DESCRIPTION		"The value of the IP precedence in the IP protocol. 
							It conflicts with the Tos and Dscp when setting."
	        ::= { rcQinQAclRuleEntry 24 }
	        
	     rcQinQAclIpv6NextHeader  OBJECT-TYPE
	        SYNTAX 			INTEGER (0..255)    
	        MAX-ACCESS 		read-create
	        STATUS 			current
	        DESCRIPTION		"The value of the DSCP in the IP protocol. 
							It conflicts with the Precedence and Tos when setting."
	        ::= { rcQinQAclRuleEntry 25 }



-- QinQ IPv6 Access List Control Table
	-- The QinQ IPv6 access control list contains some rules that are 
    -- associated with ipv6 header, and will be bound to the ports
    -- or vlans on device.
    
    -- currently unsupport

    rcQinQIpv6AclRuleTable    OBJECT-TYPE
        SYNTAX          SEQUENCE OF  RcQinQIpv6AclRuleEntry
        MAX-ACCESS      not-accessible
        STATUS          current
        DESCRIPTION     "QinQ IPv6 access list control table"
    	::= { rcQinQAcl 3 }    
    
    rcQinQIpv6AclRuleEntry  OBJECT-TYPE
		SYNTAX          RcQinQIpv6AclRuleEntry
		MAX-ACCESS      not-accessible
        STATUS          current
		DESCRIPTION     "An entry in the rcHybridAclTable."
		INDEX { rcQinQAclId, rcQinQAclRuleId }
		::= { rcQinQIpv6AclRuleTable 1 }
		
	RcQinQIpv6AclRuleEntry ::=	SEQUENCE { 
		rcQinQIpv6AclAccessType        INTEGER,
		rcQinQIpv6AclMatchField        BITS,
		rcQinQIpv6AclIpv6AddrType      INTEGER,
		rcQinQAclIpv6Addr              Ipv6Address,
		rcQinQAclIpv6PrefixLen         InetAddressPrefixLength,
		rcQinQIpv6AclRowStatus         RowStatus
		}		
        
    	rcQinQIpv6AclAccessType  OBJECT-TYPE
	        SYNTAX 			INTEGER {
	        					deny(1),
	        					permit(2)
	        					}
	        MAX-ACCESS 		read-create
	        STATUS 			current
	        DESCRIPTION		"QinQ Ipv6 acl access type."
	        ::= { rcQinQIpv6AclRuleEntry 1 }
    	
    	rcQinQIpv6AclMatchField  OBJECT-TYPE
	        SYNTAX 			BITS
	        MAX-ACCESS 		read-create
	        STATUS 			current
	        DESCRIPTION		"Match field of QinQ Ipv6 acl rule."
	        ::= { rcQinQIpv6AclRuleEntry 2 }   
    
	    rcQinQIpv6AclIpv6AddrType  OBJECT-TYPE
	        SYNTAX 			INTEGER{
	        					src(1),
	        					dst(2)
	        					}
	        MAX-ACCESS 		read-create
	        STATUS 			current
	        DESCRIPTION		"Set Ipv6 address type. Source or Destination."
	        ::= { rcQinQIpv6AclRuleEntry 3 }  
	         
	    rcQinQAclIpv6Addr  OBJECT-TYPE
	        SYNTAX 			Ipv6Address
	        MAX-ACCESS 		read-create
	        STATUS 			current
	        DESCRIPTION		"IPv6 address."
	        ::= { rcQinQIpv6AclRuleEntry 4 }
	        
	    rcQinQAclIpv6PrefixLen  OBJECT-TYPE
	        SYNTAX 			InetAddressPrefixLength    
	        MAX-ACCESS 		read-create
	        STATUS 			current
	        DESCRIPTION		"IPv6 prefix length."
	        ::= { rcQinQIpv6AclRuleEntry 5 }
	        
	    rcQinQIpv6AclRowStatus  OBJECT-TYPE
	        SYNTAX 			RowStatus
	        MAX-ACCESS 		read-create
	        STATUS 			current
	        DESCRIPTION		"Row Status of the table."
	        ::= { rcQinQIpv6AclRuleEntry 6 }        

-- QinQ Access List Control Action Table
	-- The QinQ access control list action table 

    rcQinQAclActionTable    OBJECT-TYPE
        SYNTAX          SEQUENCE OF  RcQinQAclActionEntry
        MAX-ACCESS      not-accessible
        STATUS          current
        DESCRIPTION     "QinQ access list control action table"
    	::= { rcQinQAcl 4 }    
    
    rcQinQAclActionEntry  OBJECT-TYPE
		SYNTAX          RcQinQAclActionEntry
		MAX-ACCESS      not-accessible
        STATUS          current
		DESCRIPTION     "An entry in the rcQinQAclActionTable."
		INDEX { rcQinQAclId, rcQinQAclRuleId }
		::= { rcQinQAclActionTable 1 }
		
	RcQinQAclActionEntry ::=	SEQUENCE { 
		rcQinQAclActionType        BITS,
		rcQinQAclActionOuterVid    INTEGER (1..4094),
		rcQinQAclActionOuterCos    INTEGER (0..7),
		rcQinQAclActionInnerVid    INTEGER (1..4094),
		rcQinQAclActionInnerCos    INTEGER (0..7)
		}		
        
    	rcQinQAclActionType  OBJECT-TYPE
	        SYNTAX 			BITS {
	        					unchange(0),
	        					add_ovid(1),
	        					mod_ovid(2),
	        					mod_ovlancos(3),
	        					add_ivid(4),
	        					mod_ivid(5),
	        					mod_ivlancos(6),
	        					del_ivid(7)
	        					}
	        MAX-ACCESS 		read-create
	        STATUS 			current
	        DESCRIPTION		"Action type list."
	        ::= { rcQinQAclActionEntry 1 }
	        
	    rcQinQAclActionOuterVid  OBJECT-TYPE
	        SYNTAX 			INTEGER (1..4094)
	        MAX-ACCESS 		read-create
	        STATUS 			current
	        DESCRIPTION		"Action value of outer vlan id."
	        ::= { rcQinQAclActionEntry 2 }
	    
	    rcQinQAclActionOuterCos  OBJECT-TYPE
	        SYNTAX 			INTEGER (0..7)
	        MAX-ACCESS 		read-create
	        STATUS 			current
	        DESCRIPTION		"Action value of outer vlan cos."
	        ::= { rcQinQAclActionEntry 3 }
	        
	    rcQinQAclActionInnerVid  OBJECT-TYPE
	        SYNTAX 			INTEGER (1..4094)
	        MAX-ACCESS 		read-create
	        STATUS 			current
	        DESCRIPTION		"Action value of inner vlan id."
	        ::= { rcQinQAclActionEntry 4 }
	        
	    rcQinQAclActionInnerCos  OBJECT-TYPE
	        SYNTAX 			INTEGER (0..7)
	        MAX-ACCESS 		read-create
	        STATUS 			current
	        DESCRIPTION		"Action value of inner vlan cos."
	        ::= { rcQinQAclActionEntry 5 }    

-- QinQ Access List Control Application Table
	-- Apply QinQ ACL on ingress direction of port 

    rcQinQAclAppTable    OBJECT-TYPE
        SYNTAX          SEQUENCE OF  RcQinQAclAppEntry
        MAX-ACCESS      not-accessible
        STATUS          current
        DESCRIPTION     "QinQ access list control application table"
    	::= { rcQinQAcl 5 }    
    
    rcQinQAclAppEntry  OBJECT-TYPE
		SYNTAX          RcQinQAclAppEntry
		MAX-ACCESS      not-accessible
        STATUS          current
		DESCRIPTION     "An entry in the rcQinQAclActionTable."
		INDEX { rcQinQAclAppPortIndex }
		::= { rcQinQAclAppTable 1 }
		
	RcQinQAclAppEntry ::=	SEQUENCE {
		rcQinQAclAppPortIndex        OltPortIndex,
		rcQinQAclAppAclId            Integer32, 
		rcQinQAclAppRowStatus        RowStatus
		}		
        
    	rcQinQAclAppPortIndex  OBJECT-TYPE
	        SYNTAX 			OltPortIndex
	        MAX-ACCESS 		not-accessible
	        STATUS 			current
	        DESCRIPTION		"Port index that the acl will be applied on."
	        ::= { rcQinQAclAppEntry 1 } 
	        
	    rcQinQAclAppAclId  OBJECT-TYPE
	        SYNTAX 			Integer32 (1..2000)
	        MAX-ACCESS 		read-create
	        STATUS 			current
	        DESCRIPTION		"QinQ ACL ID."
	        ::= { rcQinQAclAppEntry 2 }
	        
	    rcQinQAclAppRowStatus  OBJECT-TYPE
	        SYNTAX 			RowStatus
	        MAX-ACCESS 		read-create
	        STATUS 			current
	        DESCRIPTION		"Row Status of the table."
	        ::= { rcQinQAclAppEntry 3 }

-- QinQ Access List Control Application Table
	-- Apply QinQ ACL on ingress direction of port - Extension

    rcQinQAclAppExtTable    OBJECT-TYPE
        SYNTAX          SEQUENCE OF  RcQinQAclAppExtEntry
        MAX-ACCESS      not-accessible
        STATUS          current
        DESCRIPTION     "QinQ access list control application table - extension"
    	::= { rcQinQAcl 6 }    
    
    rcQinQAclAppExtEntry  OBJECT-TYPE
		SYNTAX          RcQinQAclAppExtEntry
		MAX-ACCESS      not-accessible
        STATUS          current
		DESCRIPTION     "An extended entry in the rcQinQAclAppExtTable."
		INDEX { rcQinQAclAppExtPortIndex, rcQinQAclAppExtAclId, rcQinQAclAppExtAclRuleId }
		::= { rcQinQAclAppExtTable 1 }
		
	RcQinQAclAppExtEntry ::=	SEQUENCE {
		rcQinQAclAppExtPortIndex        OltPortIndex,
		rcQinQAclAppExtAclId            Integer32, 
		rcQinQAclAppExtAclRuleId        Integer32,
		rcQinQAclAppExtActionType       BITS,
		rcQinQAclAppExtActionOuterVid   INTEGER (1..4094),
		rcQinQAclAppExtActionOuterCos   INTEGER (0..7),
		rcQinQAclAppExtActionInnerVid   INTEGER (1..4094),
		rcQinQAclAppExtActionInnerCos   INTEGER (0..7),
		rcQinQAclAppExtRowStatus        RowStatus
		}
        
    	rcQinQAclAppExtPortIndex  OBJECT-TYPE
	        SYNTAX 			OltPortIndex
	        MAX-ACCESS 		not-accessible
	        STATUS 			current
	        DESCRIPTION		"Port index that the acl will be applied on."
	        ::= { rcQinQAclAppExtEntry 1 } 
	        
	    rcQinQAclAppExtAclId  OBJECT-TYPE
	        SYNTAX 			Integer32 (1..2000)
	        MAX-ACCESS 		not-accessible
	        STATUS 			current
	        DESCRIPTION		"QinQ ACL ID."
	        ::= { rcQinQAclAppExtEntry 2 }
			
		rcQinQAclAppExtAclRuleId  OBJECT-TYPE
	        SYNTAX 			Integer32 (0..2000)
	        MAX-ACCESS 		not-accessible
	        STATUS 			current
	        DESCRIPTION		"QinQ ACL RULE ID."
	        ::= { rcQinQAclAppExtEntry 3 }
			
		rcQinQAclAppExtActionType  OBJECT-TYPE
	        SYNTAX 			BITS {
	        					unchange(0),
	        					add_ovid(1),
	        					mod_ovid(2),
	        					mod_ovlancos(3),
	        					add_ivid(4),
	        					mod_ivid(5),
	        					mod_ivlancos(6),
	        					del_ivid(7)
	        					}
	        MAX-ACCESS 		read-create
	        STATUS 			current
	        DESCRIPTION		"Action type list."
	        ::= { rcQinQAclAppExtEntry 4 }
	        
	    rcQinQAclAppExtActionOuterVid  OBJECT-TYPE
	        SYNTAX 			INTEGER (1..4094)
	        MAX-ACCESS 		read-create
	        STATUS 			current
	        DESCRIPTION		"Action value of outer vlan id."
	        ::= { rcQinQAclAppExtEntry 5 }
	    
	    rcQinQAclAppExtActionOuterCos  OBJECT-TYPE
	        SYNTAX 			INTEGER (0..7)
	        MAX-ACCESS 		read-create
	        STATUS 			current
	        DESCRIPTION		"Action value of outer vlan cos."
	        ::= { rcQinQAclAppExtEntry 6 }
	        
	    rcQinQAclAppExtActionInnerVid  OBJECT-TYPE
	        SYNTAX 			INTEGER (1..4094)
	        MAX-ACCESS 		read-create
	        STATUS 			current
	        DESCRIPTION		"Action value of inner vlan id."
	        ::= { rcQinQAclAppExtEntry 7 }
	        
	    rcQinQAclAppExtActionInnerCos  OBJECT-TYPE
	        SYNTAX 			INTEGER (0..7)
	        MAX-ACCESS 		read-create
	        STATUS 			current
	        DESCRIPTION		"Action value of inner vlan cos."
	        ::= { rcQinQAclAppExtEntry 8 }
	        
	    rcQinQAclAppExtRowStatus  OBJECT-TYPE
	        SYNTAX 			RowStatus
	        MAX-ACCESS 		read-create
	        STATUS 			current
	        DESCRIPTION		"Row Status of the table."
	        ::= { rcQinQAclAppExtEntry 9 }

-- QinQ port config part
	
-- QinQ Port config Table
	-- mainly admin the switch of port on QinQ function 

    rcQinQPortAdminTable    OBJECT-TYPE
        SYNTAX          SEQUENCE OF  RcQinQPortAdminEntry
        MAX-ACCESS      not-accessible
        STATUS          current
        DESCRIPTION     "QinQ port config table"
    	::= { rcQinQPort 1 }    
    
    rcQinQPortAdminEntry  OBJECT-TYPE
		SYNTAX          RcQinQPortAdminEntry
		MAX-ACCESS      not-accessible
        STATUS          current
		DESCRIPTION     "An entry in the rcQinQAclActionTable."
		INDEX { ifIndex }
		::= { rcQinQPortAdminTable 1 }
		
	RcQinQPortAdminEntry ::=	SEQUENCE { 
		rcQinQVTAdmin            	   EnableVar,
		rcQinQVTMode             	   INTEGER,
		rcQinQVTAwareCos         	   TruthValue,
		rcQinQVTDropUnmatched    	   TruthValue,
		rcQinQPortBasedQinQAdmin 	   EnableVar,
		rcQinQOuterVlanTpid      	   INTEGER,
		rcQinQVTEgressDropUnmatched    TruthValue
		}		
        
    	rcQinQVTAdmin  OBJECT-TYPE
	        SYNTAX 			EnableVar
	        MAX-ACCESS 		read-write
	        STATUS 			current
	        DESCRIPTION		"Administrate Vlan Translation on port."
	        DEFVAL          { disable }
	        ::= { rcQinQPortAdminEntry 1 } 
	        
	   rcQinQVTMode  OBJECT-TYPE
	        SYNTAX 			INTEGER {
	        					one_to_one(1),
	        					n_to_one(2)
	        					}
	        MAX-ACCESS 		read-write
	        STATUS 			current
	        DESCRIPTION		"Set Vlan Translation mode."
	        DEFVAL { one_to_one }
	        ::= { rcQinQPortAdminEntry 2 }
	        
		rcQinQVTAwareCos  OBJECT-TYPE
		    SYNTAX 			TruthValue
		    MAX-ACCESS 		read-write
		    STATUS 			current
		    DESCRIPTION		"Whether cos aware for Vlan Translation or not."
		    DEFVAL          { false }
		    ::= { rcQinQPortAdminEntry 3 } 
		    
		rcQinQVTDropUnmatched  OBJECT-TYPE
		    SYNTAX 			TruthValue
		    MAX-ACCESS 		read-write
		    STATUS 			current
		    DESCRIPTION		"Whether to drop packets unmatched VT rule or not in ingress."
		    DEFVAL          { false }
		    ::= { rcQinQPortAdminEntry 4 }
		    
		rcQinQPortBasedQinQAdmin  OBJECT-TYPE
		    SYNTAX 			EnableVar
		    MAX-ACCESS 		read-write
		    STATUS 			current
		    DESCRIPTION		"Enable QinQ on port." 
		    DEFVAL           { disable }
		    ::= { rcQinQPortAdminEntry 5 }
		    
		rcQinQOuterVlanTpid  OBJECT-TYPE
		    SYNTAX 			INTEGER
		    MAX-ACCESS 		read-write
		    STATUS 			current
		    DESCRIPTION		"Vlan Tpid of outer Vlan."
		    ::= { rcQinQPortAdminEntry 6 }
		    
		rcQinQVTEgressDropUnmatched  OBJECT-TYPE
		    SYNTAX 			TruthValue
		    MAX-ACCESS 		read-write
		    STATUS 			current
		    DESCRIPTION		"Whether to drop packets unmatched VT rule or not in egress."
		    DEFVAL          { false }
		    ::= { rcQinQPortAdminEntry 7 }
		    
-- QinQ Port ingress vlan translation rule config Table
	-- create vlan translation rule on port ingress direction 

    rcQinQIngressVTTable    OBJECT-TYPE
        SYNTAX          SEQUENCE OF  RcQinQIngressVTEntry
        MAX-ACCESS      not-accessible
        STATUS          current
        DESCRIPTION     "Vlan one to one translation rule on port"
    	::= { rcQinQPort 2 }    
    
    rcQinQIngressVTEntry  OBJECT-TYPE
		SYNTAX          RcQinQIngressVTEntry
		MAX-ACCESS      not-accessible
        STATUS          current
		DESCRIPTION     "An entry in the rcQinQAclActionTable."
		INDEX { ifIndex, rcQinQIngressVTOldOVID, rcQinQIngressVTOldIVID }
		::= { rcQinQIngressVTTable 1 }
		
	RcQinQIngressVTEntry ::=	SEQUENCE { 
		rcQinQIngressVTOldOVID            INTEGER,
		rcQinQIngressVTOldIVID            INTEGER,
		rcQinQIngressVTIVlanTransAction   INTEGER,
		rcQinQIngressVTNewOVID            INTEGER,
		rcQinQIngressVTNewOVlanCos        INTEGER,
		rcQinQIngressVTNewIVID            INTEGER,
		rcQinQIngressVTNewIVlanCos        INTEGER,
		rcQinQIngressVTRowStatus          RowStatus,
		rcQinQIngressVTOldOVIDHighBound   INTEGER
		}		
        
    	rcQinQIngressVTOldOVID  OBJECT-TYPE
	        SYNTAX 			INTEGER (1..4094)
	        MAX-ACCESS 		not-accessible
	        STATUS 			current
	        DESCRIPTION		"Outer vlan id before translation."
	        ::= { rcQinQIngressVTEntry 1 }
	        
	    rcQinQIngressVTOldIVID  OBJECT-TYPE
	        SYNTAX 			INTEGER (0..4094)
	        MAX-ACCESS 		not-accessible
	        STATUS 			current
	        DESCRIPTION		"Inner vlan id before translation."
	        ::= { rcQinQIngressVTEntry 2 }
	        
	    rcQinQIngressVTIVlanTransAction  OBJECT-TYPE
	        SYNTAX 			INTEGER {
	        					unchange(1),
	        					add(2),
	        					remove(3),
	        					change(4),
	        					copyfromouter(5)
	        					}
	        MAX-ACCESS 		read-create
	        STATUS 			current
	        DESCRIPTION		"Inner vlan translation action."
	        ::= { rcQinQIngressVTEntry 3 }
	        
	    rcQinQIngressVTNewOVID  OBJECT-TYPE
	        SYNTAX 			INTEGER (1..4094)
	        MAX-ACCESS 		read-create
	        STATUS 			current
	        DESCRIPTION		"Outer vlan id after translation."
	        ::= { rcQinQIngressVTEntry 4 }
	        
	    rcQinQIngressVTNewOVlanCos  OBJECT-TYPE
	        SYNTAX 			INTEGER (0..7)
	        MAX-ACCESS 		read-create
	        STATUS 			current
	        DESCRIPTION		"Outer vlan cos after translation. cuurently unsupport"
	        ::= { rcQinQIngressVTEntry 5 }
	        
	    rcQinQIngressVTNewIVID  OBJECT-TYPE
	        SYNTAX 			INTEGER (0..4094)
	        MAX-ACCESS 		read-create
	        STATUS 			current
	        DESCRIPTION		"Inner vlan id after translation."
	        ::= { rcQinQIngressVTEntry 6 }
	        
	    rcQinQIngressVTNewIVlanCos  OBJECT-TYPE
	        SYNTAX 			INTEGER (0..7)
	        MAX-ACCESS 		read-create
	        STATUS 			current
	        DESCRIPTION		"Inner vlan cos after translation. cuurently unsupport"
	        ::= { rcQinQIngressVTEntry 7 }
	        
	    rcQinQIngressVTRowStatus  OBJECT-TYPE
	        SYNTAX 			RowStatus
	        MAX-ACCESS 		read-create
	        STATUS 			current
	        DESCRIPTION		"Row Status of the table."
	        ::= { rcQinQIngressVTEntry 8 }
	    
	    rcQinQIngressVTOldOVIDHighBound  OBJECT-TYPE
	        SYNTAX 			INTEGER (1..4094)
	        MAX-ACCESS 		read-create
	        STATUS 			current
	        DESCRIPTION		"Outer end vlan id before translation."
	        ::= { rcQinQIngressVTEntry 9 }

-- QinQ Port Egress vlan translation rule config Table
	-- create vlan translation rule on port Egress direction 

    rcQinQEgressVTTable    OBJECT-TYPE
        SYNTAX          SEQUENCE OF  RcQinQEgressVTEntry
        MAX-ACCESS      not-accessible
        STATUS          current
        DESCRIPTION     "Vlan one to one translation rule on port"
    	::= { rcQinQPort 3 }    
    
    rcQinQEgressVTEntry  OBJECT-TYPE
		SYNTAX          RcQinQEgressVTEntry
		MAX-ACCESS      not-accessible
        STATUS          current
		DESCRIPTION     "An entry in the rcQinQAclActionTable."
		INDEX { ifIndex, rcQinQEgressVTOldOVID, rcQinQEgressVTOldIVID }
		::= { rcQinQEgressVTTable 1 }
		
	RcQinQEgressVTEntry ::=	SEQUENCE { 
		rcQinQEgressVTOldOVID            INTEGER,
		rcQinQEgressVTOldIVID            INTEGER,
		rcQinQEgressVTIVlanTransAction   INTEGER,
		rcQinQEgressVTNewOVID            INTEGER,
		rcQinQEgressVTNewOVlanCos        INTEGER,
		rcQinQEgressVTNewIVID            INTEGER,
		rcQinQEgressVTNewIVlanCos        INTEGER,
		rcQinQEgressVTRowStatus          RowStatus
		}		
        
    	rcQinQEgressVTOldOVID  OBJECT-TYPE
	        SYNTAX 			INTEGER (1..4094)
	        MAX-ACCESS 		not-accessible
	        STATUS 			current
	        DESCRIPTION		"Outer vlan id before translation."
	        ::= { rcQinQEgressVTEntry 1 }
	        
	    rcQinQEgressVTOldIVID  OBJECT-TYPE
	        SYNTAX 			INTEGER (0..4094)
	        MAX-ACCESS 		not-accessible
	        STATUS 			current
	        DESCRIPTION		"Inner vlan id before translation."
	        ::= { rcQinQEgressVTEntry 2 }
	        
	    rcQinQEgressVTIVlanTransAction  OBJECT-TYPE
	        SYNTAX 			INTEGER {
	        					unchange(1),
	        					add(2),
	        					remove(3),
	        					change(4)
	        					}
	        MAX-ACCESS 		read-create
	        STATUS 			current
	        DESCRIPTION		"Inner vlan translation action."
	        ::= { rcQinQEgressVTEntry 3 }
	        
	    rcQinQEgressVTNewOVID  OBJECT-TYPE
	        SYNTAX 			INTEGER (1..4094)
	        MAX-ACCESS 		read-create
	        STATUS 			current
	        DESCRIPTION		"Outer vlan id after translation."
	        ::= { rcQinQEgressVTEntry 4 }
	        
	    rcQinQEgressVTNewOVlanCos  OBJECT-TYPE
	        SYNTAX 			INTEGER (0..7)
	        MAX-ACCESS 		read-create
	        STATUS 			current
	        DESCRIPTION		"Outer vlan cos after translation.cuurently unsupport"
	        ::= { rcQinQEgressVTEntry 5 }
	        
	    rcQinQEgressVTNewIVID  OBJECT-TYPE
	        SYNTAX 			INTEGER (0..4094)
	        MAX-ACCESS 		read-create
	        STATUS 			current
	        DESCRIPTION		"Inner vlan id after translation."
	        ::= { rcQinQEgressVTEntry 6 }
	        
	    rcQinQEgressVTNewIVlanCos  OBJECT-TYPE
	        SYNTAX 			INTEGER (0..7)
	        MAX-ACCESS 		read-create
	        STATUS 			current
	        DESCRIPTION		"Inner vlan cos after translation.cuurently unsupport"
	        ::= { rcQinQEgressVTEntry 7 }
	        
	    rcQinQEgressVTRowStatus  OBJECT-TYPE
	        SYNTAX 			RowStatus
	        MAX-ACCESS 		read-create
	        STATUS 			current
	        DESCRIPTION		"Row Status of the table."
	        ::= { rcQinQEgressVTEntry 8 }

-- QinQ Port vlan aggregation rule config Table
	-- create vlan aggregation rule on port  direction 

    rcQinQVATable    OBJECT-TYPE
        SYNTAX          SEQUENCE OF  RcQinQVAEntry
        MAX-ACCESS      not-accessible
        STATUS          current
        DESCRIPTION     "Vlan n to one translation rule on port"
    	::= { rcQinQPort 4 }    
    
    rcQinQVAEntry  OBJECT-TYPE
		SYNTAX          RcQinQVAEntry
		MAX-ACCESS      not-accessible
        STATUS          current
		DESCRIPTION     "An entry in the prcQinQVATable."
		INDEX { ifIndex, rcQinQVAOldOVID, rcQinQVAOldIVID }
		::= { rcQinQVATable 1 }
		
	RcQinQVAEntry ::=	SEQUENCE { 
		rcQinQVAOldOVID            INTEGER,
		rcQinQVAOldIVID            INTEGER,
		rcQinQVAIVlanTransAction   INTEGER,
		rcQinQVANewOVID            INTEGER,
		rcQinQVANewOVlanCos        INTEGER,
		rcQinQVANewIVID            INTEGER,
		rcQinQVANewIVlanCos        INTEGER,
		rcQinQVARowStatus          RowStatus,
		}		
        
    	rcQinQVAOldOVID  OBJECT-TYPE
	        SYNTAX 			INTEGER (1..4094)
	        MAX-ACCESS 		not-accessible
	        STATUS 			current
	        DESCRIPTION		"Outer vlan id before translation."
	        ::= { rcQinQVAEntry 1 }
	        
	    rcQinQVAOldIVID  OBJECT-TYPE
	        SYNTAX 			INTEGER (0..4094)
	        MAX-ACCESS 		not-accessible
	        STATUS 			current
	        DESCRIPTION		"Inner vlan id before translation."
	        ::= { rcQinQVAEntry 2 }
	        
	    rcQinQVAIVlanTransAction  OBJECT-TYPE
	        SYNTAX 			INTEGER {
	        					unchange(1),
	        					add(2),
	        					remove(3),
	        					change(4)
	        					}
	        MAX-ACCESS 		read-create
	        STATUS 			current
	        DESCRIPTION		"Inner vlan translation action."
	        ::= { rcQinQVAEntry 3 }
	        
	    rcQinQVANewOVID  OBJECT-TYPE
	        SYNTAX 			INTEGER (1..4094)
	        MAX-ACCESS 		read-create
	        STATUS 			current
	        DESCRIPTION		"Outer vlan id after translation."
	        ::= { rcQinQVAEntry 4 }
	        
	    rcQinQVANewOVlanCos  OBJECT-TYPE
	        SYNTAX 			INTEGER (0..7)
	        MAX-ACCESS 		read-create
	        STATUS 			current
	        DESCRIPTION		"Outer vlan cos after translation."
	        ::= { rcQinQVAEntry 5 }
	        
	    rcQinQVANewIVID  OBJECT-TYPE
	        SYNTAX 			INTEGER (0..4094)
	        MAX-ACCESS 		read-create
	        STATUS 			current
	        DESCRIPTION		"Inner vlan id after translation."
	        ::= { rcQinQVAEntry 6 }
	        
	    rcQinQVANewIVlanCos  OBJECT-TYPE
	        SYNTAX 			INTEGER (0..7)
	        MAX-ACCESS 		read-create
	        STATUS 			current
	        DESCRIPTION		"Inner vlan cos after translation."
	        ::= { rcQinQVAEntry 7 }
	        
	    rcQinQVARowStatus  OBJECT-TYPE
	        SYNTAX 			RowStatus
	        MAX-ACCESS 		read-create
	        STATUS 			current
	        DESCRIPTION		"Row Status of the table."
	        ::= { rcQinQVAEntry 8 }  

-- QinQ Port vlan translation aware cos rule config Table
	-- create vlan translation rule on port ingress direction 

    rcQinQVlanCosAwareVTTable    OBJECT-TYPE
        SYNTAX          SEQUENCE OF  RcQinQVlanCosAwareVTEntry
        MAX-ACCESS      not-accessible
        STATUS          current
        DESCRIPTION     "Vlan one to one translation rule on port"
    	::= { rcQinQPort 5 }    
    
    rcQinQVlanCosAwareVTEntry  OBJECT-TYPE
		SYNTAX          RcQinQVlanCosAwareVTEntry
		MAX-ACCESS      not-accessible
        STATUS          current
		DESCRIPTION     "An entry in the rcQinQVlanCosAwareVTTable."
		INDEX { ifIndex, rcQinQCosAwareVTOldOVID, rcQinQCosAwareVTOldOVlanCos }
		::= { rcQinQVlanCosAwareVTTable 1 }
		
	RcQinQVlanCosAwareVTEntry ::=	SEQUENCE { 
		rcQinQCosAwareVTOldOVID       INTEGER,
		rcQinQCosAwareVTOldOVlanCos   INTEGER,
		rcQinQCosAwareVTIVlanAction   INTEGER,
		rcQinQCosAwareVTNewOVID       INTEGER,
		rcQinQCosAwareVTNewOVlanCos   INTEGER,
		rcQinQCosAwareVTNewIVID       INTEGER,
		rcQinQCosAwareVTNewIVlanCos   INTEGER,
		rcQinQCosAwareVTRowStatus     RowStatus
		}		
        
    	rcQinQCosAwareVTOldOVID  OBJECT-TYPE
	        SYNTAX 			INTEGER (1..4094)
	        MAX-ACCESS 		not-accessible
	        STATUS 			current
	        DESCRIPTION		"Outer vlan id before translation."
	        ::= { rcQinQVlanCosAwareVTEntry 1 }
	        
	    rcQinQCosAwareVTOldOVlanCos  OBJECT-TYPE
	        SYNTAX 			INTEGER (0..7)
	        MAX-ACCESS 		not-accessible
	        STATUS 			current
	        DESCRIPTION		"Inner vlan cos before translation."
	        ::= { rcQinQVlanCosAwareVTEntry 2 }
	        
	    rcQinQCosAwareVTIVlanAction  OBJECT-TYPE
	        SYNTAX 			INTEGER {
	        					unchange(1),
	        					add(2),
	        					remove(3),
	        					change(4)
	        					}
	        MAX-ACCESS 		read-create
	        STATUS 			current
	        DESCRIPTION		"Inner vlan translation action."
	        ::= { rcQinQVlanCosAwareVTEntry 3 }
	        
	    rcQinQCosAwareVTNewOVID  OBJECT-TYPE
	        SYNTAX 			INTEGER (1..4094)
	        MAX-ACCESS 		read-create
	        STATUS 			current
	        DESCRIPTION		"Outer vlan id after translation."
	        ::= { rcQinQVlanCosAwareVTEntry 4 }
	        
	    rcQinQCosAwareVTNewOVlanCos  OBJECT-TYPE
	        SYNTAX 			INTEGER (0..7)
	        MAX-ACCESS 		read-create
	        STATUS 			current
	        DESCRIPTION		"Outer vlan cos after translation."
	        ::= { rcQinQVlanCosAwareVTEntry 5 }
	        
	    rcQinQCosAwareVTNewIVID  OBJECT-TYPE
	        SYNTAX 			INTEGER (1..4094)
	        MAX-ACCESS 		read-create
	        STATUS 			current
	        DESCRIPTION		"Inner vlan id after translation."
	        ::= { rcQinQVlanCosAwareVTEntry 6 }
	        
	    rcQinQCosAwareVTNewIVlanCos  OBJECT-TYPE
	        SYNTAX 			INTEGER (0..7)
	        MAX-ACCESS 		read-create
	        STATUS 			current
	        DESCRIPTION		"Inner vlan cos after translation."
	        ::= { rcQinQVlanCosAwareVTEntry 7 }

	        
	    rcQinQCosAwareVTRowStatus  OBJECT-TYPE
	        SYNTAX 			RowStatus
	        MAX-ACCESS 		read-create
	        STATUS 			current
	        DESCRIPTION		"Row Status of the table."
	        ::= { rcQinQVlanCosAwareVTEntry 8 }

-- QinQ Port vlan aggregate aware cos rule config Table
	-- create vlan aggregate rule on port ingress direction 

    rcQinQVlanCosAwareVATable    OBJECT-TYPE
        SYNTAX          SEQUENCE OF  RcQinQVlanCosAwareVAEntry
        MAX-ACCESS      not-accessible
        STATUS          current
        DESCRIPTION     "Vlan n to one aggregate rule on port"
    	::= { rcQinQPort 6 }    
    
    rcQinQVlanCosAwareVAEntry  OBJECT-TYPE
		SYNTAX          RcQinQVlanCosAwareVAEntry
		MAX-ACCESS      not-accessible
        STATUS          current
		DESCRIPTION     "An entry in the rcQinQVlanCosAwareVTTable."
		INDEX { ifIndex, rcQinQCosAwareVAOldOVID, rcQinQCosAwareVAOldOVlanCos }
		::= { rcQinQVlanCosAwareVATable 1 }
		
	RcQinQVlanCosAwareVAEntry ::=	SEQUENCE { 
		rcQinQCosAwareVAOldOVID       INTEGER,
		rcQinQCosAwareVAOldOVlanCos   INTEGER,
		rcQinQCosAwareVAIVlanAction   INTEGER,
		rcQinQCosAwareVANewOVID       INTEGER,
		rcQinQCosAwareVANewOVlanCos   INTEGER,
		rcQinQCosAwareVANewIVID       INTEGER,
		rcQinQCosAwareVANewIVlanCos   INTEGER,
		rcQinQCosAwareVARowStatus     RowStatus
		}		
        
    	rcQinQCosAwareVAOldOVID  OBJECT-TYPE
	        SYNTAX 			INTEGER (1..4094)
	        MAX-ACCESS 		not-accessible
	        STATUS 			current
	        DESCRIPTION		"Outer vlan id before translation."
	        ::= { rcQinQVlanCosAwareVAEntry 1 }
	        
	    rcQinQCosAwareVAOldOVlanCos  OBJECT-TYPE
	        SYNTAX 			INTEGER (0..7)
	        MAX-ACCESS 		not-accessible
	        STATUS 			current
	        DESCRIPTION		"Inner vlan cos before translation."
	        ::= { rcQinQVlanCosAwareVAEntry 2 }
	        
	    rcQinQCosAwareVAIVlanAction  OBJECT-TYPE
	        SYNTAX 			INTEGER {
	        					unchange(1),
	        					add(2),
	        					remove(3),
	        					change(4)
	        					}
	        MAX-ACCESS 		read-create
	        STATUS 			current
	        DESCRIPTION		"Inner vlan translation action."
	        ::= { rcQinQVlanCosAwareVAEntry 3 }
	        
	    rcQinQCosAwareVANewOVID  OBJECT-TYPE
	        SYNTAX 			INTEGER (1..4094)
	        MAX-ACCESS 		read-create
	        STATUS 			current
	        DESCRIPTION		"Outer vlan id after translation."
	        ::= { rcQinQVlanCosAwareVAEntry 4 }
	        
	    rcQinQCosAwareVANewOVlanCos  OBJECT-TYPE
	        SYNTAX 			INTEGER (0..7)
	        MAX-ACCESS 		read-create
	        STATUS 			current
	        DESCRIPTION		"Outer vlan cos after translation."
	        ::= { rcQinQVlanCosAwareVAEntry 5 }
	        
	    rcQinQCosAwareVANewIVID  OBJECT-TYPE
	        SYNTAX 			INTEGER (1..4094)
	        MAX-ACCESS 		read-create
	        STATUS 			current
	        DESCRIPTION		"Inner vlan id after translation."
	        ::= { rcQinQVlanCosAwareVAEntry 6 }
	        
	    rcQinQCosAwareVANewIVlanCos  OBJECT-TYPE
	        SYNTAX 			INTEGER (0..7)
	        MAX-ACCESS 		read-create
	        STATUS 			current
	        DESCRIPTION		"Inner vlan cos after translation."
	        ::= { rcQinQVlanCosAwareVAEntry 7 }
	        
	    rcQinQCosAwareVARowStatus  OBJECT-TYPE
	        SYNTAX 			RowStatus
	        MAX-ACCESS 		read-create
	        STATUS 			current
	        DESCRIPTION		"Row Status of the table."
	        ::= { rcQinQVlanCosAwareVAEntry 8 }
END
