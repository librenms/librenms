-- -----------------------------------------------------------------------------
-- MIB NAME : rcFilterCfg
-- FILE NAME: switch-filter-mib.mi2			
-- DATE     : 2011/1/4						
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2012/1/4, yanzhijie
-- This is the first formal version for universal MIB definition.
 
SWITCH-FILTER-MIB DEFINITIONS ::= BEGIN
     
	IMPORTS
		MODULE-IDENTITY, OBJECT-TYPE, NOTIFICATION-TYPE,
		Integer32, IpAddress, Counter32, Unsigned32
			FROM SNMPv2-SMI

		RowStatus, TruthValue
			FROM SNMPv2-TC
		
		PortList, EnableVar
			FROM SWITCH-TC
			
		rcAclId, rcAclRuleId
			FROM SWITCH-ACL-MIB
			
		OltPortIndex
			FROM RAISECOM-PONSERIES-TC
		
		raisecomSwitchMgt
			FROM RAISECOM-PONSERIES-BASE-MIB;
			
	rcFilterCfg MODULE-IDENTITY
		LAST-UPDATED 	"201107200000Z"
		ORGANIZATION 	"rc TECH, Ltd."
		CONTACT-INFO 	"www.rc.com"
		DESCRIPTION  	
		    "The MIB module defining objects for version management  functions"
		::= { raisecomSwitchMgt  6}
		
--rcFilterCfg 

------------------------------------------------------------------------------
--	define groups in swtich-filter-mib
------------------------------------------------------------------------------
	rcFilterScalar	        	OBJECT IDENTIFIER ::= {	rcFilterCfg 1 }
	--rcFilterTable		        OBJECT IDENTIFIER ::= {	rcFilterCfg 2 }
	--rcFilterStatTable	        OBJECT IDENTIFIER ::= {	rcFilterCfg 3 }
------------------------------------------------------------------------------
	  	
-- Filter scalar table

     rcFilterNextIndex    OBJECT-TYPE
        SYNTAX          INTEGER
        MAX-ACCESS      read-only
        STATUS          current
        DESCRIPTION     "the next filter Index."
    	::= { rcFilterScalar 1 }    

-- Filter management table
	 rcFilterTable OBJECT-TYPE
	 	SYNTAX      SEQUENCE OF RcFilterEntry
	 	MAX-ACCESS      not-accessible
        STATUS          current
	 	DESCRIPTION     "A table of	filter."
	 	::=	{ rcFilterCfg 2 }
	 	       
     rcFilterEntry  OBJECT-TYPE
		SYNTAX          RcFilterEntry
		MAX-ACCESS      not-accessible
        STATUS          current
		DESCRIPTION     "An entry in the rcL2AclTable."
		INDEX { rcFilterId }
		::= { rcFilterTable 1 }
		
	RcFilterEntry ::=	SEQUENCE {
		rcFilterId                  INTEGER,
		rcFilterAclId               INTEGER,
		rcFilterTarget              INTEGER,
		rcFilterTargetPara          OCTET STRING,
		rcFilterTargetParaExtra     OCTET STRING,
		rcFilterHwStatus            TruthValue,
		rcFilterStatAdmin           EnableVar,
		rcFilterStatUnit            INTEGER,
		rcFilterRowStatus           RowStatus
		}		
        
        rcFilterId  OBJECT-TYPE
	        SYNTAX 			INTEGER (1..1024)
	        MAX-ACCESS 		not-accessible
	        STATUS 			current
	        DESCRIPTION		"Index of rcFilterTable."
	        ::= { rcFilterEntry 1 }
        
		rcFilterAclId  OBJECT-TYPE
	        SYNTAX 			INTEGER (1..5000)
	        MAX-ACCESS 		read-write
	        STATUS 			current
	        DESCRIPTION		"Index of acl."
	        ::= { rcFilterEntry 2 }        
         
    	rcFilterTarget  OBJECT-TYPE
	        SYNTAX 			INTEGER {
	        					null(0),
	        					ingress(1),
	        					egress(2),
	        					global(3),
	        					svlan(4),
	        					cvlan(5)
	        				}
	        MAX-ACCESS 		read-create
	        STATUS 			current
	        DESCRIPTION		"Target that filter will be applied on. As ingress, filter is applied on ingress ports,
	        				and about egress, filter is applied on gress port, meanwhile, ingress ports can also be 
	        				appointed. If ingress ports are appointed, the target is the flow from ingress ports to
	        				egress port. As for svlan and cvlan, filter is applied on SVLAN and CVLAN"
	        ::= { rcFilterEntry 3 }    
        
    	rcFilterTargetPara  OBJECT-TYPE
	        SYNTAX 			OCTET STRING (SIZE(512))
	        MAX-ACCESS 		read-create
	        STATUS 			current
	        DESCRIPTION		"Target parameters of filter. If the target is ingress, the node represents the ingress
	        				port list, and if the target is egress, the node represents the egress port. if the target
	        				is svlan or cvlan, the node reprents vlan id list."
	        ::= { rcFilterEntry 4 }
	        
	    rcFilterTargetParaExtra  OBJECT-TYPE
	        SYNTAX 			OCTET STRING (SIZE(512))
	        MAX-ACCESS 		read-create
	        STATUS 			current
	        DESCRIPTION		"When filter target is set to be egress port, ingress port can also be appointed, and the
	        				 node represents the egress port list. As for other target, the node represents nothing."
	        ::= { rcFilterEntry 5 }   
    
	    rcFilterHwStatus  OBJECT-TYPE
	        SYNTAX 			TruthValue
	        MAX-ACCESS 		read-only
	        STATUS 			current
	        DESCRIPTION		"Indicats whether the filter is applied in hardware or not."
	        ::= { rcFilterEntry 6 }
	        
	    rcFilterStatAdmin  OBJECT-TYPE
	        SYNTAX 			EnableVar
	        MAX-ACCESS 		read-write
	        STATUS 			current
	        DESCRIPTION		"Enable of disable statistics function."
	        ::= { rcFilterEntry 7 }
	        
	    rcFilterStatUnit  OBJECT-TYPE
	        SYNTAX 			INTEGER {
	        					packet(1),
	        					byte(2)
	        				}
	        MAX-ACCESS 		read-only
	        STATUS 			current
	        DESCRIPTION		"Statistics unit."
	        ::= { rcFilterEntry 8 }

	    rcFilterRowStatus  OBJECT-TYPE
	        SYNTAX 			RowStatus
	        MAX-ACCESS 		read-create
	        STATUS 			current
	        DESCRIPTION		"Row status of the table."
	        ::= { rcFilterEntry 9 }


-- Filter statistics result tabel
	rcFilterStatResultTable OBJECT-TYPE
	 	SYNTAX      SEQUENCE OF RcFilterStatResultEntry
	 	MAX-ACCESS      not-accessible
        STATUS          current
	 	DESCRIPTION     "A table of	filter statistics."
	 	::=	{ rcFilterCfg 4 }

     rcFilterStatResultEntry  OBJECT-TYPE
		SYNTAX          RcFilterStatResultEntry
		MAX-ACCESS      not-accessible
        STATUS          current
		DESCRIPTION     "An entry in the rcL2AclTable."
		INDEX { rcFilterId, rcAclRuleId }
		::= { rcFilterStatResultTable 1 }
		
	RcFilterStatResultEntry ::=	SEQUENCE {
		rcFilterStatPkt64           Counter64,
		rcFilterStatByte64          Counter64,
		rcFilterStatReset           INTEGER
		}		
        
	    rcFilterStatPkt64  OBJECT-TYPE
	        SYNTAX 			Counter64
	        MAX-ACCESS 		read-only
	        STATUS 			current
	        DESCRIPTION		"packets of filter statistics."
	        ::= { rcFilterStatResultEntry 1 }
	        
	    rcFilterStatByte64  OBJECT-TYPE
	        SYNTAX 			Counter64
	        MAX-ACCESS 		read-only
	        STATUS 			current
	        DESCRIPTION		"bytes of filter statistics."
	        ::= { rcFilterStatResultEntry 2 }
	        
	    rcFilterStatReset  OBJECT-TYPE
	        SYNTAX 			INTEGER {
	        					ready(0),
	        					reset(1)
	        				}
	        MAX-ACCESS 		read-write
	        STATUS 			current
	        DESCRIPTION		"clear the filter counter."
	        ::= { rcFilterStatResultEntry 3 }

-- Layer 3 Filter tabel
	rcL3FilterTable OBJECT-TYPE
	 	SYNTAX      SEQUENCE OF RcL3FilterEntry
	 	MAX-ACCESS      not-accessible
        STATUS          current
	 	DESCRIPTION     "A table of	layer 3 filter."
	 	::=	{ rcFilterCfg 5 }

     rcL3FilterEntry  OBJECT-TYPE
		SYNTAX          RcL3FilterEntry
		MAX-ACCESS      not-accessible
        STATUS          current
		DESCRIPTION     "An entry in the rcL3FilterTable."
		INDEX { rcL3FilterIfIndex }
		::= { rcL3FilterTable 1 }
		
	RcL3FilterEntry ::=	SEQUENCE {
		rcL3FilterIfIndex           OltPortIndex,
		rcL3FilterAclId             Integer32,
		rcL3FilterPortList          PortList,
		rcL3FilterRowStatus         RowStatus
		}		
        
	    rcL3FilterIfIndex  OBJECT-TYPE
	        SYNTAX 			OltPortIndex
	        MAX-ACCESS 		not-accessible
	        STATUS 			current
	        DESCRIPTION		"the L3IpSubnet IfIndex from which the packets are received."
	        ::= { rcL3FilterEntry 1 }
	        
	    rcL3FilterAclId  OBJECT-TYPE
	        SYNTAX 			Integer32(1001..3000)
	        MAX-ACCESS 		read-create
	        STATUS 			current
	        DESCRIPTION		"ACL ID binded with the filter."
	        ::= { rcL3FilterEntry 2 }
        
        rcL3FilterPortList  OBJECT-TYPE
	        SYNTAX 			PortList
	        MAX-ACCESS 		read-create
	        STATUS 			current
	        DESCRIPTION		"The physical ports where the ip access list is applied."
	        ::= { rcL3FilterEntry 3 }
	        
	    rcL3FilterRowStatus  OBJECT-TYPE
	        SYNTAX 			RowStatus
	        MAX-ACCESS 		read-create
	        STATUS 			current
	        DESCRIPTION		"L3 filter row status."
	        ::= { rcL3FilterEntry 4 }
END
