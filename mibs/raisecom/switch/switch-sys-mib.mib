-- =======================================================================
-- Version info 
--
-- Version 0.1 Created 2008.7.31 by yuhui
-- Copyright(c) 2003-2011 by RAISECOM TECH, Ltd. 
-- =======================================================================

-- ===========================================================================

--
-- RAISECOM switch sub-system config management objects
--
SWITCH-SYS-MIB DEFINITIONS ::= BEGIN

IMPORTS
    MODULE-IDENTITY, OBJECT-TYPE     	FROM SNMPv2-SMI
    raisecomSwitchMgt           		FROM RAISECOM-PONSERIES-BASE-MIB;

	rcSwitchSystem MODULE-IDENTITY
    	LAST-UPDATED "201111240000Z"
    	ORGANIZATION "RAISECOM Group"
    	CONTACT-INFO
            	" 
             	Phone:  01082884499
             	Email:  support@raisecom.com"
    	DESCRIPTION
            	"The MIB module for switch sub-system  management."
    	REVISION      "9103310000Z"
    	DESCRIPTION
            ""
    	::= { raisecomSwitchMgt 1}
    	
	rcSwitchConfig     OBJECT IDENTIFIER ::= { rcSwitchSystem 1 }
	rcSwitchPortGroup     OBJECT IDENTIFIER ::= { rcSwitchSystem 2 }

------------------------------------------------------------------------------	        
	rcSwitchConfigMtu OBJECT-TYPE
	        SYNTAX INTEGER (1500..9000)
	        MAX-ACCESS read-write
	        STATUS current
	        DESCRIPTION
	            "the system mtu config"
	        ::= { rcSwitchConfig 1 }   
	        
	 -- port config table
     rcSwitchPortTable    OBJECT-TYPE
        SYNTAX          SEQUENCE OF  RcSwitchPortEntry
        MAX-ACCESS      not-accessible
        STATUS          current
        DESCRIPTION     "port config table"
    	::= { rcSwitchPortGroup 1 }    
    
     rcSwitchPortEntry  OBJECT-TYPE
		SYNTAX          RcSwitchPortEntry
		MAX-ACCESS      not-accessible
        STATUS          current
		DESCRIPTION     "An entry in the rcSwitchPortTable."
		INDEX { rcSwitchPortIndex }
		::= { rcSwitchPortTable 1 }
		
	RcSwitchPortEntry ::=
		SEQUENCE { 
		rcSwitchPortIndex					INTEGER,
		rcSwitchPortDownHoldTime   			INTEGER
		}		
    
	rcSwitchPortIndex  OBJECT-TYPE
        SYNTAX 			INTEGER
        MAX-ACCESS 		read-only
        STATUS 			current
        DESCRIPTION		"The index of rcSwitchPortTable."
        ::= { RcSwitchPortEntry 1 }        
         
    rcSwitchPortDownHoldTime  OBJECT-TYPE
        SYNTAX 			EnableVar
        MAX-ACCESS 		read-create
        STATUS 			current
        DESCRIPTION		"Set the down hold time on the interface."
        ::= { RcSwitchPortEntry 2 }           
END
