-- -----------------------------------------------------------------------------
-- MIB NAME : roapIpDhcpServerMib
-- FILE NAME: switch-ipdhcpserver-mib.mib			
-- DATE     : 2012/03/09						
-- VERSION  : 1.00								
-- PURPOSE  : 			
-- -----------------------------------------------------------------------------
-- MODIFICTION HISTORY:
-- -----------------------------------------------------------------------------
-- Version, Date, Author
-- Description:								
--  [New Object]		
--  [Modification]
-- Notes: (Requested by who and which project)
--
-- Version 1.00, 2012/03/09, xiaoyingjie
-- This is the first formal version for universal MIB definition.   

IP-DHCP-SERVER-MIB DEFINITIONS ::= BEGIN

    IMPORTS
        MODULE-IDENTITY, TimeTicks, OBJECT-TYPE
             FROM SNMPv2-SMI       
        RowStatus,MacAddress FROM SNMPv2-TC 
        EnableVar,Vlanset	 FROM SWITCH-TC       
        raisecomSwitchMgt
			FROM RAISECOM-PONSERIES-BASE-MIB;

    roapIpDhcpServer MODULE-IDENTITY
          LAST-UPDATED "201203090000Z"
          ORGANIZATION "raisecom."
          CONTACT-INFO
              "raisecom
               E-mail: raisecom@raisecom.com"

          DESCRIPTION "dhcp server module management."
          ::= { raisecomSwitchMgt 12 }

-----------------roapIpDhcpServer-------------------
          
    roapIpDhcpServerConfig      OBJECT IDENTIFIER ::= { roapIpDhcpServer 1 }
    roapIpDhcpServerStatistics  OBJECT IDENTIFIER ::= { roapIpDhcpServer 2 }        
    roapIpDhcpIpLease           OBJECT IDENTIFIER ::= { roapIpDhcpServer 3 }

                   
-----------------roapIpDhcpServerConfig-------------------
    
          roapIpDhcpPropEnable OBJECT-TYPE
              SYNTAX  EnableVar
              MAX-ACCESS  read-write
              STATUS  current
              DESCRIPTION
                      "The enabled/disabled status of the dhcp server."
              DEFVAL { disable }
              ::= { roapIpDhcpServerConfig 1 }
              
          roapIpDhcpIpNextIndex OBJECT-TYPE
              SYNTAX  INTEGER 
              MAX-ACCESS  read-only
              STATUS  current
              DESCRIPTION
                      "The next index of the dhcp server ip pool.
                       It's range is 1..((MAX_SW_NUM-1)*4).
                       MAX_SW_NUM is the max interface ip number of device"
              REFERENCE
                      "DHCP SERVER SOUCE-CODE"
              ::= { roapIpDhcpServerConfig 2 }
              
          roapIpDhcpMaxLease OBJECT-TYPE
              SYNTAX  INTEGER (30..10080) -- is caculated with minute.It is must be greater than 30.
              MAX-ACCESS  read-write
              STATUS  current
              DESCRIPTION
                      "The max Lease of Ip address(minute)."             
              REFERENCE
                      "DHCP SERVER SOUCE-CODE"    
              DEFVAL { 10080 }
              ::= { roapIpDhcpServerConfig 3 }

          roapIpDhcpMinLease OBJECT-TYPE
              SYNTAX  INTEGER  (30..10080)-- is caculated with minute.It is must be greater than 30.
              MAX-ACCESS  read-write
              STATUS  current
              DESCRIPTION
                      "The min Lease of Ip address(minute)."             
              REFERENCE
                      "DHCP SERVER SOUCE-CODE"   
              DEFVAL { 30 }
              ::= { roapIpDhcpServerConfig 4 }

          roapIpDhcpDefLease OBJECT-TYPE
              SYNTAX  INTEGER  (30..10080)-- is caculated with minute. It is must be greater than 30.
              MAX-ACCESS  read-write
              STATUS  current
              DESCRIPTION
                      "The default Lease of Ip address(minute)."              
              REFERENCE
                      "DHCP SERVER SOUCE-CODE"      
              DEFVAL { 30 }
              ::= { roapIpDhcpServerConfig 5 }           

          roapIpDhcpServerStartTime OBJECT-TYPE
              SYNTAX  TimeTicks 
              MAX-ACCESS  read-only
              STATUS  current
              DESCRIPTION
                      "This read-only object displays the DHCP server startup time."
              REFERENCE
                      "DHCP SERVER SOUCE-CODE"
              ::= { roapIpDhcpServerConfig 6 }

---------------IP Interface Table--------------------------                      
          roapIpDhcpIpIfTable OBJECT-TYPE
              SYNTAX  SEQUENCE OF RoapIpDhcpIpIfEntry
              MAX-ACCESS  not-accessible
              STATUS  current
              DESCRIPTION
                      "A table that contains DHCP Server State information for ip interfaces."
              ::= { roapIpDhcpServerConfig 7 }
              
          roapIpDhcpIpIfEntry OBJECT-TYPE
              SYNTAX  RoapIpDhcpIpIfEntry
              MAX-ACCESS  not-accessible
              STATUS  current
              DESCRIPTION
                      "An entry that contains DHCP Server State information for ip interface."
              INDEX   { roapIpDhcpIpIfIndex }
              ::= { roapIpDhcpIpIfTable 1 }
            
          RoapIpDhcpIpIfEntry ::=
              SEQUENCE {
                  roapIpDhcpIpIfIndex INTEGER,
                  roapIpDhcpIpIfDhcpsEnable EnableVar
                  }
                  
          roapIpDhcpIpIfIndex OBJECT-TYPE
              SYNTAX  INTEGER
              MAX-ACCESS  not-accessible
              STATUS  current
              DESCRIPTION
                      "The index of IP Interface Table. The format is 
                      IP Interface's range is 0..((MAX_SW_NUM-1)).
                       MAX_SW_NUM is the max interface ip number of device"
              REFERENCE
                      "SOUCE-CODE OF DHCP SERVER"
              ::= { roapIpDhcpIpIfEntry 1 }                  
              
          roapIpDhcpIpIfDhcpsEnable OBJECT-TYPE
              SYNTAX  EnableVar
              MAX-ACCESS  read-write
              STATUS  current
              DESCRIPTION
                      "The state of dhcp server on ip interface. 
 	                   It also has two values,one is enable(1),which indicates that this ip interface 
 	                   start dhcp server; the other is disable(2) that means dhcp server is invalid on 
 	                   this ip interface. 
 	                   The default value is disable(2)."
              REFERENCE
                      "SOUCE-CODE OF DHCP SERVER"
              ::= { roapIpDhcpIpIfEntry 2 } 
              
---------------IP Pool Table--------------------------            
          roapIpDhcpIpTable OBJECT-TYPE
              SYNTAX  SEQUENCE OF RoapIpDhcpIpEntry
              MAX-ACCESS  not-accessible
              STATUS  current
              DESCRIPTION
                      "A table that contains ip-pool information
                      for the DHCP Server."
              ::= { roapIpDhcpServerConfig 8 }
              
          roapIpDhcpIpEntry OBJECT-TYPE
              SYNTAX  RoapIpDhcpIpEntry
              MAX-ACCESS  not-accessible
              STATUS  current
              DESCRIPTION
                      "A entry that contains ip-pool information
                      for the DHCP Server."
              INDEX   { roapIpDhcpIpIndex }
              ::= { roapIpDhcpIpTable 1 }
            
          RoapIpDhcpIpEntry ::=
              SEQUENCE {
                  roapIpDhcpIpIndex		INTEGER, 
                  roapIpDhcpIpPoolName  OCTET STRING,
                  roapIpDhcpIpInterface INTEGER,
                  roapIpDhcpIpStartIp 	IpAddress,
                  roapIpDhcpIpEndIp   	IpAddress,
                  roapIpDhcpIpNetmask   IpAddress,
                  roapIpDhcpIpGateway   IpAddress,
                  roapIpDhcpIpDnsServer IpAddress,
                  roapIpDhcpIpSecondaryDnsServer IpAddress,
                  roapIpDhcpIpTftpSvrAddress IpAddress,
                  roapIpDhcpIpBootfileName OCTET STRING, 
                  roapIpDhcpIpMaxLease  INTEGER,
				  roapIpDhcpIpMinLease  INTEGER,
				  roapIpDhcpIpDefLease  INTEGER,
                  roapIpDhcpIpRowStatus RowStatus
                  }
               
          roapIpDhcpIpIndex OBJECT-TYPE
              SYNTAX  INTEGER 
              MAX-ACCESS  not-accessible
              STATUS  current
              DESCRIPTION
                      "index of Ip-pool row.
                       It's range is 1..((MAX_SW_NUM-1)*4).
                       MAX_SW_NUM is the max interface ip number of device"
              REFERENCE
                      "SOUCE-CODE OF DHCP SERVER"
              ::= { roapIpDhcpIpEntry 1 }
              
          roapIpDhcpIpPoolName OBJECT-TYPE
              SYNTAX  OCTET STRING (SIZE(1..16))
              MAX-ACCESS  read-create
              STATUS  current
              DESCRIPTION
                      "Name of Ip-pool row."
              REFERENCE
                      "SOUCE-CODE OF DHCP SERVER"
              ::= { roapIpDhcpIpEntry 2 }
              
          roapIpDhcpIpInterface OBJECT-TYPE
              SYNTAX  INTEGER
              MAX-ACCESS  read-create
              STATUS  current
              DESCRIPTION
                      "DURABLE:
                       Ip interface.
                       It's range is 0..((MAX_SW_NUM-2)).
                       MAX_SW_NUM is the max interface ip number of device"
              REFERENCE
                      "SOUCE-CODE OF DHCP SERVER."
              ::= { roapIpDhcpIpEntry 3 }
              
          roapIpDhcpIpStartIp OBJECT-TYPE
              SYNTAX  IpAddress
              MAX-ACCESS  read-create
              STATUS  current
              DESCRIPTION
                      "DURABLE:
                      start ip address."
              REFERENCE
                      "SOUCE-CODE OF DHCP SERVER."
              ::= { roapIpDhcpIpEntry 4 }
              
          roapIpDhcpIpEndIp OBJECT-TYPE
              SYNTAX  IpAddress
              MAX-ACCESS  read-create
              STATUS  current
              DESCRIPTION
                      "DURABLE:
                      end ip address."
              REFERENCE
                      "SOUCE-CODE OF DHCP SERVER."
              ::= { roapIpDhcpIpEntry 5 }              
              
          roapIpDhcpIpNetmask OBJECT-TYPE
              SYNTAX  IpAddress
              MAX-ACCESS  read-create
              STATUS  current
              DESCRIPTION
                      "DURABLE:
                      netmask of ip address."
              REFERENCE
                      "SOUCE-CODE OF DHCP SERVER."
              ::= { roapIpDhcpIpEntry 6 }   
              
          roapIpDhcpIpGateway OBJECT-TYPE
              SYNTAX  IpAddress
              MAX-ACCESS  read-create
              STATUS  current
              DESCRIPTION
                      "DURABLE:
                      gateway of ip address."
              REFERENCE
                      "SOUCE-CODE OF DHCP SERVER."
              ::= { roapIpDhcpIpEntry 7 }  
              
          roapIpDhcpIpDnsServer OBJECT-TYPE
              SYNTAX  IpAddress
              MAX-ACCESS  read-create
              STATUS  current
              DESCRIPTION
                      "DURABLE:
                      dns of ip address."
              REFERENCE
                      "SOUCE-CODE OF DHCP SERVER."
              ::= { roapIpDhcpIpEntry 8 }   
                 
          roapIpDhcpIpSecondaryDnsServer OBJECT-TYPE
              SYNTAX  IpAddress
              MAX-ACCESS  read-create
              STATUS  current
              DESCRIPTION
                      "DURABLE:
                      dns of ip address."
              REFERENCE
                      "SOUCE-CODE OF DHCP SERVER."
              ::= { roapIpDhcpIpEntry 9 }  
             
          roapIpDhcpIpTftpSvrAddress OBJECT-TYPE
              SYNTAX  IpAddress
              MAX-ACCESS  read-create
              STATUS  current
              DESCRIPTION
                      "The IP Address of TFTP Server configured by DHCP Server for Client. 
                      DHCP Client downloads configuration files from the TFTP Server during 
                      auto-configuration procedure. 
                      No default TFTP Server was configured under DHCP Server IP pool."
              REFERENCE
                      "SOUCE-CODE OF DHCP SERVER."
              ::= { roapIpDhcpIpEntry 10 }   
          
          roapIpDhcpIpBootfileName OBJECT-TYPE
              SYNTAX  OCTET STRING (SIZE(1..63))
              MAX-ACCESS  read-create
              STATUS  current
              DESCRIPTION
                      "The boot-file name configured by DHCP Server for Client. 
                      DHCP Client downloads this designated file from specified server 
                      to complete auto-configuration. 
                      No default boot file was configured under DHCP IP pool."
              REFERENCE
                      "SOUCE-CODE OF DHCP SERVER"
              ::= { roapIpDhcpIpEntry 11 } 

          roapIpDhcpIpRowStatus OBJECT-TYPE
              SYNTAX  RowStatus               
              MAX-ACCESS  read-create
              STATUS  current
              DESCRIPTION
                      "DURABLE:
                      rowstatus of ip address."
              REFERENCE
                      "SOUCE-CODE OF DHCP SERVER."
              ::= { roapIpDhcpIpEntry 12 }
  			  
---------------dhcp relay table--------------------------  
          roapIpDhcpRelayNextIndex OBJECT-TYPE
              SYNTAX  INTEGER (1..8)
              MAX-ACCESS  read-only
              STATUS  current
              DESCRIPTION
                      "The next index of Relay server."
              REFERENCE
                      "DHCP SERVER SOUCE-CODE"
              ::= { roapIpDhcpServerConfig 9 }  
                      
          roapIpDhcpRelayTable OBJECT-TYPE
              SYNTAX  SEQUENCE OF RoapIpDhcpRelayEntry
              MAX-ACCESS  not-accessible
              STATUS  current
              DESCRIPTION
                      "A table that contains relay server information
                      for the DHCP Server."
              ::= { roapIpDhcpServerConfig 10 }
              
          roapIpDhcpRelayEntry OBJECT-TYPE
              SYNTAX  RoapIpDhcpRelayEntry
              MAX-ACCESS  not-accessible
              STATUS  current
              DESCRIPTION
                      "A entry that contains relay server information
                      for the DHCP Server."
              INDEX   { roapIpDhcpRelayIndex }
              ::= { roapIpDhcpRelayTable 1 }
            
          RoapIpDhcpRelayEntry ::=
              SEQUENCE {
                  roapIpDhcpRelayIndex INTEGER,
                  roapIpDhcpRelayAddress IpAddress,
                  roapIpDhcpRelayMask IpAddress,
                  roapIpDhcpRelayRowStatus RowStatus                 
                  }
                  
          roapIpDhcpRelayIndex OBJECT-TYPE
              SYNTAX  INTEGER
              MAX-ACCESS  not-accessible
              STATUS  current
              DESCRIPTION
                      "index of relay server."
              REFERENCE
                      "SOUCE-CODE OF DHCP SERVER"
              ::= { roapIpDhcpRelayEntry 1 }                  
              
          roapIpDhcpRelayAddress OBJECT-TYPE
              SYNTAX  IpAddress
              MAX-ACCESS  read-create
              STATUS  current
              DESCRIPTION
                      "ip address of relay server."
              REFERENCE
                      "SOUCE-CODE OF DHCP SERVER"
              ::= { roapIpDhcpRelayEntry 2 } 
              
          roapIpDhcpRelayMask OBJECT-TYPE
              SYNTAX  IpAddress
              MAX-ACCESS  read-create
              STATUS  current
              DESCRIPTION
                      "ip mask of relay server."
              REFERENCE
                      "SOUCE-CODE OF DHCP SERVER"
              ::= { roapIpDhcpRelayEntry 3 }
              
          roapIpDhcpRelayRowStatus OBJECT-TYPE
              SYNTAX    RowStatus            
              MAX-ACCESS  read-create
              STATUS  current
              DESCRIPTION
                      "DURABLE:
                      rowstatus of relay server address."
              REFERENCE
                      "SOUCE-CODE OF DHCP SERVER."
              ::= { roapIpDhcpRelayEntry 4 }    
 
 
 ---------------dhcp server vendor-specific option table--------------------------          
          roapIpDhcpIpVendorOptTable OBJECT-TYPE
              SYNTAX  SEQUENCE OF RoapIpDhcpIpVendorOptEntry
              MAX-ACCESS  not-accessible
              STATUS  current
              DESCRIPTION
                      "A table that contains vendor-specific DHCP option which were
                       configured on DHCP server by network administrator."
              ::= { roapIpDhcpServerConfig 11 } 
                   
          roapIpDhcpIpVendorOptEntry OBJECT-TYPE
              SYNTAX  RoapIpDhcpIpVendorOptEntry
              MAX-ACCESS  not-accessible
              STATUS  current
              DESCRIPTION
                      "A entry that contains vendor-specific DHCP option defined on DHCP Server."
              INDEX   { roapIpDhcpIpIndex, roapIpDhcpIpOptionCode }  
              ::= { roapIpDhcpIpVendorOptTable 1 } 
              
          RoapIpDhcpIpVendorOptEntry ::=
              SEQUENCE {
                  roapIpDhcpIpOptionCode INTEGER,
                  roapIpDhcpIpOptionType INTEGER,
                  roapIpDhcpIpOptionContents OCTET STRING,   
                  roapIpDhcpIpOptionLength INTEGER,
                  roapIpDhcpIpOptionRowStatus RowStatus                 
                  } 
              
          roapIpDhcpIpOptionCode OBJECT-TYPE
              SYNTAX  INTEGER(0..15)
              MAX-ACCESS  not-accessible
              STATUS  current
              DESCRIPTION
                      "The code of vendor-specified option."
              REFERENCE
                      "SOUCE-CODE OF DHCP SERVER."
              ::= { roapIpDhcpIpVendorOptEntry 1 }

          roapIpDhcpIpOptionType OBJECT-TYPE
              SYNTAX  INTEGER(0..31)
              MAX-ACCESS  read-create
              STATUS  current
              DESCRIPTION
                      "The type of vendor-specified option contents. 
                      AsciiString(1) stands for ASCII String, 
                      HexString(2) for HEX String, IpAddress(3) for IP Address. 
                      The default value is NULL."
              REFERENCE
                      "SOUCE-CODE OF DHCP SERVER."
              ::= { roapIpDhcpIpVendorOptEntry 2 }  
              
          roapIpDhcpIpOptionContents OBJECT-TYPE
              SYNTAX  OCTET STRING(SIZE(1..192))
              MAX-ACCESS  read-create
              STATUS  current
              DESCRIPTION
                      "The contents of vendor-specified option, which may consist of an ASCII string, 
                      a HEX string or an IP address. The default value is ASCII string. 
                      Network administrator can change this variable's value through SET operation. 
                      When implement SET, a specified criteria which was depicted as follows should be
                      conformed.
                      Vendor-specified option contents consisted of a hex string should have a pre-0x 
                      with it. For instance, administrator can set contents as fafb by inputting '0xfafb',
                      and no space amid the string permitted.
                      For ASCII string, administrator can input the string directly. E.g, user can set 
                      the option contents as test by input 'test' in the column, then perform SET.
                      As regards ip address, it's required to input '0# 0x14 0x20 0x20 0x30' in order to
                      set contents as '20.32.32.48'."
              REFERENCE
                      "SOUCE-CODE OF DHCP SERVER."
              ::= { roapIpDhcpIpVendorOptEntry 3 }  
          
          roapIpDhcpIpOptionLength OBJECT-TYPE
              SYNTAX  INTEGER(0..192)
              MAX-ACCESS  read-only
              STATUS  current
              DESCRIPTION
                      "The length of vendor-specified option contents. Default length is 0. 
                      When vendor-specified option contents are consisted of ASCII and hex strings, 
                      this variable indicates the byte number of option contents(omit 0x). 
                      Or else, it indicates the length of an IP address (i.e. 4 bytes)."
              REFERENCE
                      "SOUCE-CODE OF DHCP SERVER."
              ::= { roapIpDhcpIpVendorOptEntry 4 } 
         
          roapIpDhcpIpOptionRowStatus OBJECT-TYPE
              SYNTAX    RowStatus            
              MAX-ACCESS  read-create
              STATUS  current
              DESCRIPTION
                      "The row status of vendor-specified option table. This variable has three values 
                      which are listed as follows: Active (1); createAndGo (4); Destroy(6). 
                      The network administrator can delete a row in the vendor-specified option table 
                      by setting this variable's value as destroy (6). Before create a new row, 
                      administrator should set the row status as createAndGo (4). Once the row was created successfully,
                      the row status will change to Active(1)"
              REFERENCE
                      "SOUCE-CODE OF DHCP SERVER."
              ::= { roapIpDhcpIpVendorOptEntry 5 } 
              
          roapIpDhcpIpOptionRowNumCurrent OBJECT-TYPE
              SYNTAX  INTEGER(1..15) 
              MAX-ACCESS  read-only
              STATUS  current
              DESCRIPTION
                      "Current row number of the vendor-specified option table. Administrator can define at most 10 options under a specified IP address pool. 
                      The maximum row number are (10 * 4* IP interface number supported)."
              REFERENCE
                      "DHCP SERVER SOUCE-CODE"
              ::= { roapIpDhcpServerConfig 12 }  
              
          roapIpDhcpIpOptionRowNumHistoryMax OBJECT-TYPE
              SYNTAX  INTEGER(1..15) 
              MAX-ACCESS  read-only
              STATUS  current
              DESCRIPTION
                      "The maximum row number of the vendor-specific table ever since it was created. 
                      The default value is also 0. The maximum row number are (10 * 4* IP interface number supported), 
                      the IP interface number are determined by the device characteristic."
              REFERENCE
                      "DHCP SERVER SOUCE-CODE"
              ::= { roapIpDhcpServerConfig 13 }              

---------------dhcp band ip table--------------------------   
                      
          roapIpDhcpIpBandTable OBJECT-TYPE
              SYNTAX  SEQUENCE OF RoapIpDhcpIpBandEntry
              MAX-ACCESS  not-accessible
              STATUS  current
              DESCRIPTION
                      "A table that contains relay server information
                      for the DHCP Server."
              ::= { roapIpDhcpServerConfig 14 }
              
          roapIpDhcpIpBandEntry OBJECT-TYPE
              SYNTAX  RoapIpDhcpIpBandEntry
              MAX-ACCESS  not-accessible
              STATUS  current
              DESCRIPTION
                      "A entry that contains relay server information
                      for the DHCP Server."
              INDEX   { roapIpDhcpIpBandIpAddress }
              ::= { roapIpDhcpIpBandTable 1 }
            
          RoapIpDhcpIpBandEntry ::=
              SEQUENCE {
                  roapIpDhcpIpBandIpAddress 	IpAddress,
                  roapIpDhcpIpBandMacAddress 	MacAddress, 
                  roapIpDhcpIpBandPoolIndex 	INTEGER,
                  roapIpDhcpIpBandRowState 		RowStatus                 
                  }                
              
          roapIpDhcpIpBandIpAddress OBJECT-TYPE
              SYNTAX  IpAddress
              MAX-ACCESS  not-accessible
              STATUS  current
              DESCRIPTION
                      "ip address."
              REFERENCE
                      "SOUCE-CODE OF DHCP SERVER"
              ::= { roapIpDhcpIpBandEntry 1 } 

          roapIpDhcpIpBandMacAddress OBJECT-TYPE
              SYNTAX  MacAddress
              MAX-ACCESS  read-create
              STATUS  current
              DESCRIPTION
                      "mac address."
              REFERENCE
                      "SOUCE-CODE OF DHCP SERVER"
              ::= { roapIpDhcpIpBandEntry 2 }
                           
          roapIpDhcpIpBandPoolIndex OBJECT-TYPE
              SYNTAX  INTEGER
              MAX-ACCESS  read-create
              STATUS  current
              DESCRIPTION
                      "pool index."
              REFERENCE
                      "SOUCE-CODE OF DHCP SERVER"
              ::= { roapIpDhcpIpBandEntry 3 }
              
          roapIpDhcpIpBandRowState OBJECT-TYPE
              SYNTAX    RowStatus            
              MAX-ACCESS  read-create
              STATUS  current
              DESCRIPTION
                      "DURABLE:
                      rowstatus of  dhcpe ip band."
              REFERENCE
                      "SOUCE-CODE OF DHCP SERVER."
              ::= { roapIpDhcpIpBandEntry 4 }  
                                                                                            
-------------dhcp server statistics---------------
    roapIpDhcpServerStatsBootps  OBJECT-TYPE
        SYNTAX Counter
        MAX-ACCESS read-only
        STATUS mandatory
        DESCRIPTION
            "This read-only object displays the DHCP Server receive the Bootps num."
        ::= {roapIpDhcpServerStatistics 1 }  
        
    roapIpDhcpServerStatsDiscovers  OBJECT-TYPE
        SYNTAX Counter
        MAX-ACCESS read-only
        STATUS mandatory
        DESCRIPTION
            "This read-only object displays the DHCP Server receive the Discovers num."
        ::= { roapIpDhcpServerStatistics 2 }        
        
    roapIpDhcpServerStatsRequests  OBJECT-TYPE
        SYNTAX Counter
        MAX-ACCESS read-only
        STATUS mandatory
        DESCRIPTION
            "This read-only object displays the DHCP Server receive the Requests num."
        ::= { roapIpDhcpServerStatistics 3 }        

    roapIpDhcpServerStatsReleases  OBJECT-TYPE
        SYNTAX Counter
        MAX-ACCESS read-only
        STATUS mandatory
        DESCRIPTION
            "This read-only object displays the DHCP Server receive the Releases num."
        ::= { roapIpDhcpServerStatistics 4 }                

    roapIpDhcpServerStatsOffers  OBJECT-TYPE
        SYNTAX Counter
        MAX-ACCESS read-only
        STATUS mandatory
        DESCRIPTION
            "This read-only object displays the DHCP Server receive the Offers num."
        ::= { roapIpDhcpServerStatistics 5 }        

    roapIpDhcpServerStatsAcks  OBJECT-TYPE
        SYNTAX Counter
        MAX-ACCESS read-only
        STATUS mandatory
        DESCRIPTION
            "This read-only object displays the DHCP Server receive the Acks num."
        ::= { roapIpDhcpServerStatistics 6 }        

    roapIpDhcpServerStatsNacks  OBJECT-TYPE
        SYNTAX Counter
        MAX-ACCESS read-only
        STATUS mandatory
        DESCRIPTION
            "This read-only object displays the DHCP Server receive the Nacks num."
        ::= { roapIpDhcpServerStatistics 7 }     
           
    roapIpDhcpServerStatsDeclines  OBJECT-TYPE
        SYNTAX Counter
        MAX-ACCESS read-only
        STATUS mandatory
        DESCRIPTION
            "This read-only object displays the DHCP Server receive the Declines num."
        ::= {roapIpDhcpServerStatistics 8 }  

    roapIpDhcpServerStatsInformations  OBJECT-TYPE
        SYNTAX Counter
        MAX-ACCESS read-only
        STATUS mandatory
        DESCRIPTION
            "This read-only object displays the DHCP Server receive the Informations num."
        ::= {roapIpDhcpServerStatistics 9 }  
                
    roapIpDhcpServerStatsUnknows  OBJECT-TYPE
        SYNTAX Counter
        MAX-ACCESS read-only
        STATUS mandatory
        DESCRIPTION
            "This read-only object displays the DHCP Server receive the unknowed packets num."
        ::= {roapIpDhcpServerStatistics 10 }  
                
    roapIpDhcpServerStatsPackets  OBJECT-TYPE
        SYNTAX Counter
        MAX-ACCESS read-only
        STATUS mandatory
        DESCRIPTION
            "This read-only object displays the DHCP Server receive the total packets num."
        ::= {roapIpDhcpServerStatistics 11 }  
                                                                                                                  
---------------Lease IP Table--------------------------                      
          roapIpDhcpIpLeaseTable OBJECT-TYPE
              SYNTAX  SEQUENCE OF RoapIpDhcpIpLeaseEntry
              MAX-ACCESS  not-accessible
              STATUS  current
              DESCRIPTION
                      "A table that contains Lease IP information
                      for the DHCP Server."
              ::= { roapIpDhcpIpLease 1 }
              
          roapIpDhcpIpLeaseEntry OBJECT-TYPE
              SYNTAX  RoapIpDhcpIpLeaseEntry
              MAX-ACCESS  not-accessible
              STATUS  current
              DESCRIPTION
                      "A entry that contains relay server information
                      for the DHCP Server."
              INDEX   { roapIpDhcpIpLeaseIndex }
              ::= { roapIpDhcpIpLeaseTable 1 }
            
          RoapIpDhcpIpLeaseEntry ::=
              SEQUENCE {
                  roapIpDhcpIpLeaseIndex INTEGER,
                  roapIpDhcpIpLeaseIpAddres IpAddress,
                  roapIpDhcpIpLeaseClientMacAddress MacAddress,
                  roapIpDhcpIpLeaseExpiration INTEGER,
                  roapIpDhcpIpLeaseIpInterface INTEGER,
                  roapIpDhcpIpLeaseType INTEGER  
                  }
                  
          roapIpDhcpIpLeaseIndex OBJECT-TYPE
              SYNTAX  INTEGER
              MAX-ACCESS  not-accessible
              STATUS  current
              DESCRIPTION
                      "The index of bindlist."
              REFERENCE
                      "SOUCE-CODE OF DHCP SERVER"
              ::= { roapIpDhcpIpLeaseEntry 1 }                  
              
          roapIpDhcpIpLeaseIpAddres OBJECT-TYPE
              SYNTAX  IpAddress
              MAX-ACCESS  read-only
              STATUS  current
              DESCRIPTION
                      "The IP address of client."
              REFERENCE
                      "SOUCE-CODE OF DHCP SERVER"
              ::= { roapIpDhcpIpLeaseEntry 2 } 
              
          roapIpDhcpIpLeaseClientMacAddress OBJECT-TYPE
              SYNTAX  MacAddress
              MAX-ACCESS  read-only
              STATUS  current
              DESCRIPTION
                      "Client Mac Address."
              REFERENCE
                      "SOUCE-CODE OF DHCP SERVER"
              ::= { roapIpDhcpIpLeaseEntry 3 }
              
          roapIpDhcpIpLeaseExpiration OBJECT-TYPE
              SYNTAX    INTEGER           
              MAX-ACCESS  read-write
              STATUS  current
              DESCRIPTION
                      "Ip Lease Expiration（NPT UTC time,the seconds from 1/1/1970）. will be 0 if lease expiration is infinate"
              REFERENCE
                      "SOUCE-CODE OF DHCP SERVER."
              ::= { roapIpDhcpIpLeaseEntry 4 }  
              
          roapIpDhcpIpLeaseIpInterface OBJECT-TYPE
              SYNTAX    INTEGER            
              MAX-ACCESS  read-only
              STATUS  current
              DESCRIPTION
                      "Ip Interface.   
                      It's range is 0..((MAX_SW_NUM-2)).
                       MAX_SW_NUM is the max interface ip number of device"
              REFERENCE
                      "SOUCE-CODE OF DHCP SERVER."
              ::= { roapIpDhcpIpLeaseEntry 5 }    
              
		  roapIpDhcpIpLeaseType OBJECT-TYPE
              SYNTAX    INTEGER            
              MAX-ACCESS  read-only
              STATUS  current
              DESCRIPTION
                      "The leaseType"
              REFERENCE
                      "SOUCE-CODE OF DHCP SERVER."
              ::= { roapIpDhcpIpLeaseEntry 6 } 

END
