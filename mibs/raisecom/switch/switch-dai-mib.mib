--MibName=roapDai
-- *****************************************************************
-- switch-dai-mib.mib:  Raisecom DAI MIB file
--
-- April 2012, pangxijia
--
-- Copyright (c) 2012-2019, 2012 by Raisecom, Inc.
-- All rights reserved.
-- 
-- *****************************************************************

SWITCH-DAI-MIB DEFINITIONS ::= BEGIN

IMPORTS
    MODULE-IDENTITY, OBJECT-TYPE,
    Integer32     	 			    FROM SNMPv2-SMI
    MacAddress,RowStatus		    FROM SNMPv2-TC 
    PortList, Vlanset, EnableVar	FROM SWITCH-TC 
    InetAddressType, InetAddressIPv6    FROM INET-ADDRESS-MIB
    OltPortIndex	                    FROM RAISECOM-PONSERIES-TC 
	raisecomSwitchMgt                   FROM RAISECOM-PONSERIES-BASE-MIB;
         
roapDai MODULE-IDENTITY
    LAST-UPDATED "0806130000Z"
    ORGANIZATION "raisecom Group"
    CONTACT-INFO
                "       Raise Systems
                        
                Postal: Beijing,
                        China

                   Tel: 86-010-82884499

                E-mail: pangxijia@raisecom.com"
    DESCRIPTION
            "The MIB module for dynamic arp inspection."
    ::= { raisecomSwitchMgt  16}   
    
------------------------------------------------------------------------------
--
--  roapDai - Dynamic ARP Inspection
--
--  This group is used to instrument the dynamic ARP inspection support.
--
------------------------------------------------------------------------------    
------------------------------------------------------------------------------
roapDaiConfig			OBJECT IDENTIFIER ::= {	roapDai 1 }

------------------------------------------------------------------------------
--
-- DAI Config
--

roapDaiStaticEnable OBJECT-TYPE
	    SYNTAX      EnableVar
        MAX-ACCESS  read-write
        STATUS      current
        DESCRIPTION
               "This object controls whether the static DAI 
               bind is enabled on the device. A disable(2) value 
               will prevent the static DAI bind rule to write 
               to hardware on the device."
        DEFVAL { 2 }
        ::= { roapDaiConfig 1 }   
        
roapDaiDhcpSnoopEnable OBJECT-TYPE
	    SYNTAX      EnableVar
        MAX-ACCESS  read-write
        STATUS      current
        DESCRIPTION
               "This object controls whether the dhcp snooping DAI 
               bind is   enabled on the device. A disable(2) value 
               will prevent the dhcp snooping DAI bind on the device."
        DEFVAL { 2 }
        ::= { roapDaiConfig 2 }

roapDaiBindCurrentRules OBJECT-TYPE
        SYNTAX     INTEGER
        MAX-ACCESS read-only
        STATUS     current
        DESCRIPTION
            "This object indicates the current DAI rule number on the device."
        ::= { roapDaiConfig 3 }

--
-- DAI Port Config
--

roapDaiPortTrustTable	OBJECT-TYPE
        SYNTAX SEQUENCE OF RoapDaiPortTrustEntry
        MAX-ACCESS      not-accessible
        STATUS current
        DESCRIPTION
            "This table contains entries that identify the configured DAI trust
            for each port."
        ::= { roapDaiConfig 5 }

roapDaiPortTrustEntry OBJECT-TYPE
	    SYNTAX     RoapDaiPortTrustEntry
        MAX-ACCESS not-accessible
        STATUS     current
        DESCRIPTION
                "An entry (conceptual row) in the roapDaiPortStateTable.
                The entry identify the configured DAI trust for the port."
       INDEX      { roapDaiPortIndex}
       ::= { roapDaiPortTrustTable 1 }

RoapDaiPortTrustEntry ::= 
SEQUENCE {
                	
                roapDaiPortIndex			OltPortIndex,
                roapDaiTrust			INTEGER
         }

roapDaiPortIndex OBJECT-TYPE
        SYNTAX OltPortIndex 
        MAX-ACCESS read-write 
        STATUS current
        DESCRIPTION     
                "."       
        ::= { roapDaiPortTrustEntry 1 }

roapDaiTrust OBJECT-TYPE
        SYNTAX INTEGER { trust(1), untrust(2) }  
        MAX-ACCESS read-write 
        STATUS current
        DESCRIPTION     
                "This object indicates the whether trust arp packet on this port."   
        DEFVAL { 2 }        
        ::= { roapDaiPortTrustEntry 2 }

--
--  The DAI bind table
--

roapDaiBindTable OBJECT-TYPE
        SYNTAX SEQUENCE OF RoapDaiBindEntry
        MAX-ACCESS not-accessible
        STATUS current
        DESCRIPTION                   
                "This table contains the list of DAI bind table."
        ::= { roapDaiConfig 6 } 

roapDaiBindEntry OBJECT-TYPE
	    SYNTAX     RoapDaiBindEntry
        MAX-ACCESS not-accessible
        STATUS     current
        DESCRIPTION
                "Each entry contains the list of DAI bind table."
        INDEX      { roapDaiBindIp}
        ::= { roapDaiBindTable 1 }

RoapDaiBindEntry ::= SEQUENCE {
                roapDaiBindIp		    IpAddress,
                roapDaiBindPortId		INTEGER,
                roapDaiBindMac		MacAddress,
                roapDaiBindVlan       INTEGER,
                roapDaiBindMode       INTEGER,  
                roapDaiBindInHw       INTEGER,
                roapDaiBindRowStatus  RowStatus
        }

roapDaiBindIp OBJECT-TYPE
        SYNTAX        IpAddress
        MAX-ACCESS    not-accessible 
        STATUS        current
        DESCRIPTION
		 "Index identifying this entry.The ip address of this bind rule."
        ::= { roapDaiBindEntry 1 }
        
roapDaiBindPortId OBJECT-TYPE
        SYNTAX        INTEGER
        MAX-ACCESS    read-create 
        STATUS        current
        DESCRIPTION
		 "This object specifies the port id of this rule."
        ::= { roapDaiBindEntry 2 }
        
roapDaiBindMac OBJECT-TYPE
        SYNTAX        MacAddress
        MAX-ACCESS    read-create 
        STATUS        current
        DESCRIPTION
		 "This object specifies the mac address of this rule."
        ::= { roapDaiBindEntry 3 }

roapDaiBindVlan OBJECT-TYPE
        SYNTAX        INTEGER (1..4094)
        MAX-ACCESS    read-create 
        STATUS        current
        DESCRIPTION
                "This object specifies the vlan of this rule."
        ::= { roapDaiBindEntry 4 }

roapDaiBindMode OBJECT-TYPE
        SYNTAX        INTEGER { static(1), dhcp-snooping(2) }
        MAX-ACCESS    read-only 
        STATUS        current
        DESCRIPTION
		 "This object specifies the mode of this rule.static(1) specifies 
		 this rule is staticly configured.dhcp snooping(2) specifies this 
		 rule is learned from dhcp snooping."
        ::= { roapDaiBindEntry 5 }

roapDaiBindInHw  OBJECT-TYPE
        SYNTAX        INTEGER { inHw(1), notinHw(2) }
        MAX-ACCESS    read-only 
        STATUS        current
        DESCRIPTION
		 "This object specifies the state of this rule.InHw(1) specifies 
		 this rule is in hardware.notInHw(1) specifies this rule is not in hardware."
        ::= { roapDaiBindEntry 6 }     
        
roapDaiBindRowStatus OBJECT-TYPE
        SYNTAX        RowStatus
        MAX-ACCESS    read-create 
        STATUS        current
        DESCRIPTION
		 "The row status of this entry."
        ::= { roapDaiBindEntry 7 }
--
END
