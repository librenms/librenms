--MibName=roapVlanCfg
-- *****************************************************************
-- RAISECOM-VLAN-MIB.MIB:  Raisecom VLAN MIB file
-- 20090320, longyang
--
-- Copyright (c) 1994-2004 by Raisecom, Inc.
-- All rights reserved.
--
-- *****************************************************************
SWITCH-VLANCFG-MIB  DEFINITIONS ::= BEGIN

IMPORTS
        MODULE-IDENTITY, OBJECT-TYPE,
        Integer32
        	FROM SNMPv2-SMI

        TruthValue, RowStatus
            FROM SNMPv2-TC
        
        Vlanset, EnableVar                
            FROM SWITCH-TC
        
        OltPortIndex
			FROM RAISECOM-PONSERIES-TC
		
		raisecomSwitchMgt
			FROM RAISECOM-PONSERIES-BASE-MIB;


	roapVlanCfg MODULE-IDENTITY
        LAST-UPDATED    "200901200000Z"
        ORGANIZATION    "Raisecom, Inc."
        CONTACT-INFO
                "       Raise Systems

                Postal: Beijing,
                        China

                   Tel: 86-010-82884499

                E-mail: support@raisecom.com"
        DESCRIPTION
                "Configuration of vlan object."
                ::= { raisecomSwitchMgt 20 }

-- -------------------------------------------------------------
-- groups in the SWITCH-VLANCFG MIB
-- -------------------------------------------------------------

roapVlanCfgMib       OBJECT IDENTIFIER ::= { roapVlanCfg 1 }  

roapVlanCfgPort      OBJECT IDENTIFIER ::= { roapVlanCfgMib 1 }
          
-- -------------------------------------------------------------
-- roapVlanCfgPort
-- -------------------------------------------------------------
    roapVlanCfgPortTable OBJECT-TYPE
        SYNTAX SEQUENCE OF RoapVlanCfgPortEntry
        MAX-ACCESS not-accessible
        STATUS current
        DESCRIPTION
            "Vlan port configuration table."
        ::= { roapVlanCfgPort 1 }

    roapVlanCfgPortEntry OBJECT-TYPE
        SYNTAX RoapVlanCfgPortEntry
        MAX-ACCESS not-accessible
        STATUS current
        DESCRIPTION
            "Vlan port configuration table entry."
        INDEX { roapPortIndex }
        ::= { roapVlanCfgPortTable 1 }

    RoapVlanCfgPortEntry ::= SEQUENCE {
        roapPortIndex                           OltPortIndex,
        roapPortMode                            INTEGER,
        roapPortAccessVlanId                    INTEGER,
        roapPortTrunkVlanNative                 INTEGER,
        roapPortTrunkAllowVlanList              Vlanset,
        roapPortTrunkUntagVlanList              Vlanset,
        roapPortDropUntagged                    TruthValue
     }

    roapPortIndex OBJECT-TYPE
        SYNTAX   OltPortIndex
        MAX-ACCESS not-accessible
        STATUS current
        DESCRIPTION
            "Vlan port index."
        ::= { roapVlanCfgPortEntry 1 }
    
    roapPortMode OBJECT-TYPE
        SYNTAX  INTEGER  {
                 access(1),
                 trunk(2)                
                 }
        MAX-ACCESS read-write
        STATUS current
        DESCRIPTION
            "Vlan port mode."
        ::= { roapVlanCfgPortEntry 2 }

    roapPortAccessVlanId OBJECT-TYPE
        SYNTAX  INTEGER  (1..4094)
        MAX-ACCESS read-write
        STATUS current
        DESCRIPTION
            "Access vlan ID, when port is in access mode."
        ::= { roapVlanCfgPortEntry 3 }

    roapPortTrunkVlanNative OBJECT-TYPE
        SYNTAX  INTEGER (1..4094)
        MAX-ACCESS read-write
        STATUS current
        DESCRIPTION
            "Native vlan when port is in trunk mode."
        ::= { roapVlanCfgPortEntry 4 }

    roapPortTrunkAllowVlanList OBJECT-TYPE
        SYNTAX  Vlanset
        MAX-ACCESS read-write
        STATUS current
        DESCRIPTION
            "Allowed vlan list when port is in trunk mode."
        ::= { roapVlanCfgPortEntry 5 }

    roapPortTrunkUntagVlanList OBJECT-TYPE
        SYNTAX  Vlanset
        MAX-ACCESS read-write
        STATUS current
        DESCRIPTION
            "Untagged vlan list when port is in trunk mode."
        ::= { roapVlanCfgPortEntry 6 }
        
    roapPortDropUntagged OBJECT-TYPE
        SYNTAX  TruthValue
        MAX-ACCESS read-write
        STATUS current
        DESCRIPTION
            "Drop untagged packet or not."
        ::= { roapVlanCfgPortEntry 7 }
END
