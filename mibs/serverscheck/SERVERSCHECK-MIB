--SensorGateway control MIB.
--
--Author                   Date        Comment
--==================================================================
--SiebenSense		    Mar 29, 2012  Rev. D

SERVERSCHECK-MIB DEFINITIONS ::= BEGIN
    IMPORTS
    enterprises, IpAddress
        FROM RFC1155-SMI
    DisplayString
        FROM RFC1213-MIB
    OBJECT-TYPE
        FROM RFC-1212
    TRAP-TYPE
        FROM RFC-1215;


    serverscheck OBJECT IDENTIFIER ::= { enterprises 17095 }

    product OBJECT IDENTIFIER ::= { serverscheck 1 }

    productname OBJECT-TYPE
        SYNTAX              DisplayString
        ACCESS              read-only
        STATUS              mandatory
        DESCRIPTION         "Name of product. e.g. SensorGateway etc."
        ::= { product 1 }

    productversion OBJECT-TYPE
        SYNTAX              DisplayString
        ACCESS              read-only
        STATUS              mandatory
        DESCRIPTION         "Version of product. e.g. 1.0 etc"
        ::= { product 2 }

    productdate OBJECT-TYPE
        SYNTAX              DisplayString
        ACCESS              read-only
        STATUS              mandatory
        DESCRIPTION         "Build date of product. e.g. Apr 2010 etc"
        ::= { product 3 }

    productusername OBJECT-TYPE
        SYNTAX              DisplayString
        ACCESS              read-only
        STATUS              mandatory
        DESCRIPTION         "User give name of product. e.g. ABCD etc"
        ::= { product 4 }

    productuserloc OBJECT-TYPE
        SYNTAX              DisplayString
        ACCESS              read-only
        STATUS              mandatory
        DESCRIPTION         "Usage loaction of product. e.g. Data center etc"
        ::= { product 5 }

    productnetip OBJECT-TYPE
        SYNTAX              IpAddress
        ACCESS              read-only
        STATUS              mandatory
        DESCRIPTION         "IP Address of product"
        ::= { product 6 }

    productnetgateway OBJECT-TYPE
        SYNTAX              IpAddress
        ACCESS              read-only
        STATUS              mandatory
        DESCRIPTION         "Gateway of product"
        ::= { product 7 }

    productnetpridns OBJECT-TYPE
        SYNTAX              IpAddress
        ACCESS              read-only
        STATUS              mandatory
        DESCRIPTION         "Primary DNS of product"
        ::= { product 8 }

    productnetsecdns OBJECT-TYPE
        SYNTAX              IpAddress
        ACCESS              read-only
        STATUS              mandatory
        DESCRIPTION         "Secondary DNS of product"
        ::= { product 9 }

    setup OBJECT IDENTIFIER ::= { serverscheck 2 }

    traps OBJECT-TYPE
        SYNTAX              SEQUENCE OF TrapEntry
        ACCESS              not-accessible
        STATUS              mandatory
        DESCRIPTION         "Trap table"
        ::= { setup 1 }

    trapEntry OBJECT-TYPE
        SYNTAX              TrapEntry
        ACCESS              not-accessible
        STATUS              mandatory
        DESCRIPTION         "Single trap entry containing trap receiver info."
        INDEX               {
                                trapReceiverNumber
                            }
        ::= { traps 1 }

    TrapEntry ::= SEQUENCE {
        trapReceiverNumber
            INTEGER,
        trapEnabled
            INTEGER,
        trapReceiverIPAddress
            IpAddress,
        trapCommunity
            DisplayString
    }

    trapReceiverNumber OBJECT-TYPE
        SYNTAX              INTEGER (0..3)
        ACCESS              not-accessible
        STATUS              mandatory
        DESCRIPTION         "Index of trap receiver"
        ::= { trapEntry 1 }

    trapEnabled OBJECT-TYPE
        SYNTAX              INTEGER {
                                no( 1 ),
                                yes( 2 )
                            }
        ACCESS              read-write
        STATUS              mandatory
        DESCRIPTION         "Indicates if this trap entry is enabled or not."
        ::= { trapEntry 2 }

    trapReceiverIPAddress OBJECT-TYPE
        SYNTAX              IpAddress
        ACCESS              read-write
        STATUS              mandatory
        DESCRIPTION         "Trap receiver IP address"
        ::= { trapEntry 3 }

    trapCommunity OBJECT-TYPE
        SYNTAX              DisplayString
        ACCESS              read-write
        STATUS              mandatory
        DESCRIPTION         "Trap community to be used by agent to send trap"
        ::= { trapEntry 4 }

    control OBJECT IDENTIFIER ::= { serverscheck 3 }

    sensor1name OBJECT-TYPE
        SYNTAX              DisplayString
        ACCESS              read-only
        STATUS              mandatory
        DESCRIPTION         "Type of Sensor"
        ::= { control 1 }

    sensor1Value OBJECT-TYPE
        SYNTAX              DisplayString
        ACCESS              read-only
        STATUS              mandatory
        DESCRIPTION         "Value of Sensor"
        ::= { control 2 }

    sensor1LastErrMsg OBJECT-TYPE
        SYNTAX              DisplayString
        ACCESS              read-only
        STATUS              mandatory
        DESCRIPTION         "Last error message of Sensor"
        ::= { control 3 }

    sensor1LastErrTime OBJECT-TYPE
        SYNTAX              DisplayString
        ACCESS              read-only
        STATUS              mandatory
        DESCRIPTION         "Last error time of Sensor"
        ::= { control 4 }

    sensor2name OBJECT-TYPE
        SYNTAX              DisplayString
        ACCESS              read-only
        STATUS              mandatory
        DESCRIPTION         "Type of Sensor"
        ::= { control 5 }

    sensor2Value OBJECT-TYPE
        SYNTAX              DisplayString
        ACCESS              read-only
        STATUS              mandatory
        DESCRIPTION         "Value of Sensor"
        ::= { control 6 }

    sensor2LastErrMsg OBJECT-TYPE
        SYNTAX              DisplayString
        ACCESS              read-only
        STATUS              mandatory
        DESCRIPTION         "Last error message of Sensor"
        ::= { control 7 }

    sensor2LastErrTime OBJECT-TYPE
        SYNTAX              DisplayString
        ACCESS              read-only
        STATUS              mandatory
        DESCRIPTION         "Last error time of Sensor"
        ::= { control 8 }

    sensor3name OBJECT-TYPE
        SYNTAX              DisplayString
        ACCESS              read-only
        STATUS              mandatory
        DESCRIPTION         "Type of Sensor"
        ::= { control 9 }

    sensor3Value OBJECT-TYPE
        SYNTAX              DisplayString
        ACCESS              read-only
        STATUS              mandatory
        DESCRIPTION         "Value of Sensor"
        ::= { control 10 }

    sensor3LastErrMsg OBJECT-TYPE
        SYNTAX              DisplayString
        ACCESS              read-only
        STATUS              mandatory
        DESCRIPTION         "Last error message of Sensor"
        ::= { control 11 }

    sensor3LastErrTime OBJECT-TYPE
        SYNTAX              DisplayString
        ACCESS              read-only
        STATUS              mandatory
        DESCRIPTION         "Last error time of Sensor"
        ::= { control 12 }

    sensor4name OBJECT-TYPE
        SYNTAX              DisplayString
        ACCESS              read-only
        STATUS              mandatory
        DESCRIPTION         "Type of Sensor"
        ::= { control 13 }

    sensor4Value OBJECT-TYPE
        SYNTAX              DisplayString
        ACCESS              read-only
        STATUS              mandatory
        DESCRIPTION         "Value of Sensor"
        ::= { control 14 }

    sensor4LastErrMsg OBJECT-TYPE
        SYNTAX              DisplayString
        ACCESS              read-only
        STATUS              mandatory
        DESCRIPTION         "Last error message of Sensor"
        ::= { control 15 }

    sensor4LastErrTime OBJECT-TYPE
        SYNTAX              DisplayString
        ACCESS              read-only
        STATUS              mandatory
        DESCRIPTION         "Last error time of Sensor"
        ::= { control 16 }

    sensor5name OBJECT-TYPE
        SYNTAX              DisplayString
        ACCESS              read-only
        STATUS              mandatory
        DESCRIPTION         "Type of Sensor"
        ::= { control 17 }

    sensor5Value OBJECT-TYPE
        SYNTAX              DisplayString
        ACCESS              read-only
        STATUS              mandatory
        DESCRIPTION         "Value of Sensor"
        ::= { control 18 }

    sensor5LastErrMsg OBJECT-TYPE
        SYNTAX              DisplayString
        ACCESS              read-only
        STATUS              mandatory
        DESCRIPTION         "Last error message of Sensor"
        ::= { control 19 }

    sensor5LastErrTime OBJECT-TYPE
        SYNTAX              DisplayString
        ACCESS              read-only
        STATUS              mandatory
        DESCRIPTION         "Last error time of Sensor"
        ::= { control 20 }

    trapalerts OBJECT IDENTIFIER ::= { serverscheck 4 }

    sensor1TrapErrMsg OBJECT-TYPE
        SYNTAX              OCTET STRING
        ACCESS              read-only
        STATUS              mandatory
        DESCRIPTION         "Latest complete error message of the first sensor
                            reading"
        ::= { trapalerts 1 }

    sensor2TrapErrMsg OBJECT-TYPE
        SYNTAX              OCTET STRING
        ACCESS              read-only
        STATUS              mandatory
        DESCRIPTION         "Latest complete error message of the second sensor
                            reading"
        ::= { trapalerts 2 }

    sensor3TrapErrMsg OBJECT-TYPE
        SYNTAX              OCTET STRING
        ACCESS              read-only
        STATUS              mandatory
        DESCRIPTION         "Latest complete error message of the third sensor
                            reading"
        ::= { trapalerts 3 }

    sensor4TrapErrMsg OBJECT-TYPE
        SYNTAX              OCTET STRING
        ACCESS              read-only
        STATUS              mandatory
        DESCRIPTION         "Latest complete error message of the fourth sensor
                            reading"
        ::= { trapalerts 4 }


    sensor5TrapErrMsg OBJECT-TYPE
        SYNTAX              OCTET STRING
        ACCESS              read-only
        STATUS              mandatory
        DESCRIPTION         "Latest complete error message of the fifth sensor
                            reading"
        ::= { trapalerts 5 }

    sensor6TrapErrMsg OBJECT-TYPE
        SYNTAX              OCTET STRING
        ACCESS              read-only
        STATUS              mandatory
        DESCRIPTION         "Latest complete error message of the sixth sensor
                            reading"
        ::= { trapalerts 6 }

    sensorAlert TRAP-TYPE
        ENTERPRISE          serverscheck
        VARIABLES           {
                                sensor1TrapErrMsg,
                                sensor2TrapErrMsg,
                                sensor3TrapErrMsg,
				sensor4TrapErrMsg,
				sensor5TrapErrMsg,
				sensor6TrapErrMsg
                            }
        DESCRIPTION         "An alert has been triggered by the SensorGateway on
                             one of the connected sensors.  See the detailed error
                             message for information."
        ::= 1



    iotrapalerts OBJECT IDENTIFIER ::= { serverscheck 5 }

    iosensorINPUT1trapErrMsg OBJECT-TYPE
        SYNTAX              OCTET STRING
        ACCESS              read-only
        STATUS              mandatory
        DESCRIPTION         "Latest complete error message of dry contact input 1"
        ::= { iotrapalerts 1 }

    iosensorINPUT2trapErrMsg OBJECT-TYPE
        SYNTAX              OCTET STRING
        ACCESS              read-only
        STATUS              mandatory
        DESCRIPTION         "Latest complete error message of dry contact input 2"
        ::= { iotrapalerts 2 }

    iosensorINPUT3trapErrMsg OBJECT-TYPE
        SYNTAX              OCTET STRING
        ACCESS              read-only
        STATUS              mandatory
        DESCRIPTION         "Latest complete error message of dry contact input 3"
        ::= { iotrapalerts 3 }

    iosensorINPUT4trapErrMsg OBJECT-TYPE
        SYNTAX              OCTET STRING
        ACCESS              read-only
        STATUS              mandatory
        DESCRIPTION         "Latest complete error message of dry contact input 4"
        ::= { iotrapalerts 4 }

    iosensorINPUT5trapErrMsg OBJECT-TYPE
        SYNTAX              OCTET STRING
        ACCESS              read-only
        STATUS              mandatory
        DESCRIPTION         "Latest complete error message of dry contact input 5"
        ::= { iotrapalerts 5 }

    iosensorINPUT6trapErrMsg OBJECT-TYPE
        SYNTAX              OCTET STRING
        ACCESS              read-only
        STATUS              mandatory
        DESCRIPTION         "Latest complete error message of dry contact input 6"
        ::= { iotrapalerts 6 }

    iosensorINPUT7trapErrMsg OBJECT-TYPE
        SYNTAX              OCTET STRING
        ACCESS              read-only
        STATUS              mandatory
        DESCRIPTION         "Latest complete error message of dry contact input 7"
        ::= { iotrapalerts 7 }

    iosensorINPUT8trapErrMsg OBJECT-TYPE
        SYNTAX              OCTET STRING
        ACCESS              read-only
        STATUS              mandatory
        DESCRIPTION         "Latest complete error message of dry contact input 8"
        ::= { iotrapalerts 8 }

    iosensorINPUT9trapErrMsg OBJECT-TYPE
        SYNTAX              OCTET STRING
        ACCESS              read-only
        STATUS              mandatory
        DESCRIPTION         "Latest complete error message of dry contact input 9"
        ::= { iotrapalerts 9 }

    iosensorINPUT10trapErrMsg OBJECT-TYPE
        SYNTAX              OCTET STRING
        ACCESS              read-only
        STATUS              mandatory
        DESCRIPTION         "Latest complete error message of dry contact input 10"
        ::= { iotrapalerts 10 }

    iosensorINPUT11trapErrMsg OBJECT-TYPE
        SYNTAX              OCTET STRING
        ACCESS              read-only
        STATUS              mandatory
        DESCRIPTION         "Latest complete error message of dry contact input 11"
        ::= { iotrapalerts 11 }

    iosensorINPUT12trapErrMsg OBJECT-TYPE
        SYNTAX              OCTET STRING
        ACCESS              read-only
        STATUS              mandatory
        DESCRIPTION         "Latest complete error message of dry contact input 12"
        ::= { iotrapalerts 12 }

    iosensorINPUT13trapErrMsg OBJECT-TYPE
        SYNTAX              OCTET STRING
        ACCESS              read-only
        STATUS              mandatory
        DESCRIPTION         "Latest complete error message of dry contact input 13"
        ::= { iotrapalerts 13 }

    iosensorINPUT14trapErrMsg OBJECT-TYPE
        SYNTAX              OCTET STRING
        ACCESS              read-only
        STATUS              mandatory
        DESCRIPTION         "Latest complete error message of dry contact input 14"
        ::= { iotrapalerts 14 }

    iosensorINPUT15trapErrMsg OBJECT-TYPE
        SYNTAX              OCTET STRING
        ACCESS              read-only
        STATUS              mandatory
        DESCRIPTION         "Latest complete error message of dry contact input 15"
        ::= { iotrapalerts 15 }

    iosensorINPUT16trapErrMsg OBJECT-TYPE
        SYNTAX              OCTET STRING
        ACCESS              read-only
        STATUS              mandatory
        DESCRIPTION         "Latest complete error message of dry contact input 16"
        ::= { iotrapalerts 16 }


    iosensorAlert TRAP-TYPE
        ENTERPRISE          serverscheck
        VARIABLES           {
                                iosensorINPUT1trapErrMsg,
                                iosensorINPUT2trapErrMsg,
                                iosensorINPUT3trapErrMsg,
				iosensorINPUT4trapErrMsg,
				iosensorINPUT5trapErrMsg,
				iosensorINPUT6trapErrMsg,
                                iosensorINPUT7trapErrMsg,
                                iosensorINPUT8trapErrMsg,
				iosensorINPUT9trapErrMsg,
				iosensorINPUT10trapErrMsg,
				iosensorINPUT11trapErrMsg,
                                iosensorINPUT12trapErrMsg,
                                iosensorINPUT13trapErrMsg,
				iosensorINPUT14trapErrMsg,
				iosensorINPUT15trapErrMsg,
				iosensorINPUT16trapErrMsg
                            }
        DESCRIPTION         "An alert has been triggered by the SensorGateway on
                             one of the connected sensors.  See the detailed error
                             message for information."
        ::= 2



    input OBJECT IDENTIFIER ::= { serverscheck 6 }

    input1name OBJECT-TYPE
        SYNTAX              DisplayString
        ACCESS              read-only
        STATUS              mandatory
        DESCRIPTION         "Name"
        ::= { input 1 }

    input1Value OBJECT-TYPE
        SYNTAX              DisplayString
        ACCESS              read-only
        STATUS              mandatory
        DESCRIPTION         "State - O for Open and 1 for Close"
        ::= { input 2 }

    input1LastErrMsg OBJECT-TYPE
        SYNTAX              DisplayString
        ACCESS              read-only
        STATUS              mandatory
        DESCRIPTION         "Last error message of input"
        ::= { input 3 }

    input2name OBJECT-TYPE
        SYNTAX              DisplayString
        ACCESS              read-only
        STATUS              mandatory
        DESCRIPTION         "Name"
        ::= { input 4 }

    input2Value OBJECT-TYPE
        SYNTAX              DisplayString
        ACCESS              read-only
        STATUS              mandatory
        DESCRIPTION         "State - O for Open and 1 for Close"
        ::= { input 5 }

    input2LastErrMsg OBJECT-TYPE
        SYNTAX              DisplayString
        ACCESS              read-only
        STATUS              mandatory
        DESCRIPTION         "Last error message of input"
        ::= { input 6 }

    input3name OBJECT-TYPE
        SYNTAX              DisplayString
        ACCESS              read-only
        STATUS              mandatory
        DESCRIPTION         "Name"
        ::= { input 7 }

    input3Value OBJECT-TYPE
        SYNTAX              DisplayString
        ACCESS              read-only
        STATUS              mandatory
        DESCRIPTION         "State - O for Open and 1 for Close"
        ::= { input 8 }

    input3LastErrMsg OBJECT-TYPE
        SYNTAX              DisplayString
        ACCESS              read-only
        STATUS              mandatory
        DESCRIPTION         "Last error message of input"
        ::= { input 9 }

    input4name OBJECT-TYPE
        SYNTAX              DisplayString
        ACCESS              read-only
        STATUS              mandatory
        DESCRIPTION         "Name"
        ::= { input 10 }

    input4Value OBJECT-TYPE
        SYNTAX              DisplayString
        ACCESS              read-only
        STATUS              mandatory
        DESCRIPTION         "State - O for Open and 1 for Close"
        ::= { input 11 }

    input4LastErrMsg OBJECT-TYPE
        SYNTAX              DisplayString
        ACCESS              read-only
        STATUS              mandatory
        DESCRIPTION         "Last error message of input"
        ::= { input 12 }

    input5name OBJECT-TYPE
        SYNTAX              DisplayString
        ACCESS              read-only
        STATUS              mandatory
        DESCRIPTION         "Name"
        ::= { input 13 }

    input5Value OBJECT-TYPE
        SYNTAX              DisplayString
        ACCESS              read-only
        STATUS              mandatory
        DESCRIPTION         "State - O for Open and 1 for Close"
        ::= { input 14 }

    input5LastErrMsg OBJECT-TYPE
        SYNTAX              DisplayString
        ACCESS              read-only
        STATUS              mandatory
        DESCRIPTION         "Last error message of input"
        ::= { input 15 }

    input6name OBJECT-TYPE
        SYNTAX              DisplayString
        ACCESS              read-only
        STATUS              mandatory
        DESCRIPTION         "Name"
        ::= { input 16 }

    input6Value OBJECT-TYPE
        SYNTAX              DisplayString
        ACCESS              read-only
        STATUS              mandatory
        DESCRIPTION         "State - O for Open and 1 for Close"
        ::= { input 17 }

    input6LastErrMsg OBJECT-TYPE
        SYNTAX              DisplayString
        ACCESS              read-only
        STATUS              mandatory
        DESCRIPTION         "Last error message of input"
        ::= { input 18 }

    input7name OBJECT-TYPE
        SYNTAX              DisplayString
        ACCESS              read-only
        STATUS              mandatory
        DESCRIPTION         "Name"
        ::= { input 19 }

    input7Value OBJECT-TYPE
        SYNTAX              DisplayString
        ACCESS              read-only
        STATUS              mandatory
        DESCRIPTION         "State - O for Open and 1 for Close"
        ::= { input 20 }

    input7LastErrMsg OBJECT-TYPE
        SYNTAX              DisplayString
        ACCESS              read-only
        STATUS              mandatory
        DESCRIPTION         "Last error message of input"
	::= { input 21 }

    input8name OBJECT-TYPE
        SYNTAX              DisplayString
        ACCESS              read-only
        STATUS              mandatory
        DESCRIPTION         "Name"
        ::= { input 22 }

    input8Value OBJECT-TYPE
        SYNTAX              DisplayString
        ACCESS              read-only
        STATUS              mandatory
        DESCRIPTION         "State - O for Open and 1 for Close"
        ::= { input 23 }

    input8LastErrMsg OBJECT-TYPE
        SYNTAX              DisplayString
        ACCESS              read-only
        STATUS              mandatory
        DESCRIPTION         "Last error message of input"
        ::= { input 24 }

    input9name OBJECT-TYPE
        SYNTAX              DisplayString
        ACCESS              read-only
        STATUS              mandatory
        DESCRIPTION         "Name"
        ::= { input 25 }

    input9Value OBJECT-TYPE
        SYNTAX              DisplayString
        ACCESS              read-only
        STATUS              mandatory
        DESCRIPTION         "State - O for Open and 1 for Close"
        ::= { input 26 }

    input9LastErrMsg OBJECT-TYPE
        SYNTAX              DisplayString
        ACCESS              read-only
        STATUS              mandatory
        DESCRIPTION         "Last error message of input"
        ::= { input 27 }

    input10name OBJECT-TYPE
        SYNTAX              DisplayString
        ACCESS              read-only
        STATUS              mandatory
        DESCRIPTION         "Name"
        ::= { input 28 }

    input10Value OBJECT-TYPE
        SYNTAX              DisplayString
        ACCESS              read-only
        STATUS              mandatory
        DESCRIPTION         "State - O for Open and 1 for Close"
        ::= { input 29 }

    input10LastErrMsg OBJECT-TYPE
        SYNTAX              DisplayString
        ACCESS              read-only
        STATUS              mandatory
        DESCRIPTION         "Last error message of input"
        ::= { input 30 }

    input11name OBJECT-TYPE
        SYNTAX              DisplayString
        ACCESS              read-only
        STATUS              mandatory
        DESCRIPTION         "Name"
        ::= { input 31 }

    input11Value OBJECT-TYPE
        SYNTAX              DisplayString
        ACCESS              read-only
        STATUS              mandatory
        DESCRIPTION         "State - O for Open and 1 for Close"
        ::= { input 32 }

    input11LastErrMsg OBJECT-TYPE
        SYNTAX              DisplayString
        ACCESS              read-only
        STATUS              mandatory
        DESCRIPTION         "Last error message of input"
        ::= { input 33 }

    input12name OBJECT-TYPE
        SYNTAX              DisplayString
        ACCESS              read-only
        STATUS              mandatory
        DESCRIPTION         "Name"
        ::= { input 34 }

    input12Value OBJECT-TYPE
        SYNTAX              DisplayString
        ACCESS              read-only
        STATUS              mandatory
        DESCRIPTION         "State - O for Open and 1 for Close"
        ::= { input 35 }

    input12LastErrMsg OBJECT-TYPE
        SYNTAX              DisplayString
        ACCESS              read-only
        STATUS              mandatory
        DESCRIPTION         "Last error message of input"
        ::= { input 36 }


    input13name OBJECT-TYPE
        SYNTAX              DisplayString
        ACCESS              read-only
        STATUS              mandatory
        DESCRIPTION         "Name"
        ::= { input 37 }

    input13Value OBJECT-TYPE
        SYNTAX              DisplayString
        ACCESS              read-only
        STATUS              mandatory
        DESCRIPTION         "State - O for Open and 1 for Close"
        ::= { input 38 }

    input13LastErrMsg OBJECT-TYPE
        SYNTAX              DisplayString
        ACCESS              read-only
        STATUS              mandatory
        DESCRIPTION         "Last error message of input"
        ::= { input 39 }


    input14name OBJECT-TYPE
        SYNTAX              DisplayString
        ACCESS              read-only
        STATUS              mandatory
        DESCRIPTION         "Name"
        ::= { input 40 }

    input14Value OBJECT-TYPE
        SYNTAX              DisplayString
        ACCESS              read-only
        STATUS              mandatory
        DESCRIPTION         "State - O for Open and 1 for Close"
        ::= { input 41 }

    input14LastErrMsg OBJECT-TYPE
        SYNTAX              DisplayString
        ACCESS              read-only
        STATUS              mandatory
        DESCRIPTION         "Last error message of input"
        ::= { input 42 }

    input15name OBJECT-TYPE
        SYNTAX              DisplayString
        ACCESS              read-only
        STATUS              mandatory
        DESCRIPTION         "Name"
        ::= { input 43 }

    input15Value OBJECT-TYPE
        SYNTAX              DisplayString
        ACCESS              read-only
        STATUS              mandatory
        DESCRIPTION         "State - O for Open and 1 for Close"
        ::= { input 44 }

    input15LastErrMsg OBJECT-TYPE
        SYNTAX              DisplayString
        ACCESS              read-only
        STATUS              mandatory
        DESCRIPTION         "Last error message of input"
        ::= { input 45 }

    input16name OBJECT-TYPE
        SYNTAX              DisplayString
        ACCESS              read-only
        STATUS              mandatory
        DESCRIPTION         "Name"
        ::= { input 46 }

    input16Value OBJECT-TYPE
        SYNTAX              DisplayString
        ACCESS              read-only
        STATUS              mandatory
        DESCRIPTION         "State - O for Open and 1 for Close"
        ::= { input 47 }

    input16LastErrMsg OBJECT-TYPE
        SYNTAX              DisplayString
        ACCESS              read-only
        STATUS              mandatory
        DESCRIPTION         "Last error message of input"
        ::= { input 48 }

    output OBJECT IDENTIFIER ::= { serverscheck 7 }

    output1State OBJECT-TYPE
        SYNTAX              DisplayString
        ACCESS              read-only
        STATUS              mandatory
        DESCRIPTION         "State - O for Open and 1 for Close"
        ::= { output 1 }

    output2State OBJECT-TYPE
        SYNTAX              DisplayString
        ACCESS              read-only
        STATUS              mandatory
        DESCRIPTION         "State - O for Open and 1 for Close"
        ::= { output  2 }

    output3State OBJECT-TYPE
        SYNTAX              DisplayString
        ACCESS              read-only
        STATUS              mandatory
        DESCRIPTION         "State - O for Open and 1 for Close"
        ::= { output  3 }

    output4State OBJECT-TYPE
        SYNTAX              DisplayString
        ACCESS              read-only
        STATUS              mandatory
        DESCRIPTION         "State - O for Open and 1 for Close"
        ::= { output  4 }

sensorTable  OBJECT IDENTIFIER ::={serverscheck 11}
sensor1 OBJECT IDENTIFIER ::= {sensorTable 1}
sensor2 OBJECT IDENTIFIER ::= {sensorTable 2}
sensor3 OBJECT IDENTIFIER ::= {sensorTable 3}
sensor4 OBJECT IDENTIFIER ::= {sensorTable 4}
sensor5 OBJECT IDENTIFIER ::= {sensorTable 5}
sensor6 OBJECT IDENTIFIER ::= {sensorTable 6}
sensor7 OBJECT IDENTIFIER ::= {sensorTable 7}
sensor8 OBJECT IDENTIFIER ::= {sensorTable 8}
sensor9 OBJECT IDENTIFIER ::= {sensorTable 9}
sensor10 OBJECT IDENTIFIER ::= {sensorTable 10}
sensor11 OBJECT IDENTIFIER ::= {sensorTable 11}
sensor12 OBJECT IDENTIFIER ::= {sensorTable 12}
sensor13 OBJECT IDENTIFIER ::= {sensorTable 13}
sensor14 OBJECT IDENTIFIER ::= {sensorTable 14}
sensor15 OBJECT IDENTIFIER ::= {sensorTable 15}
sensor16 OBJECT IDENTIFIER ::= {sensorTable 16}
sensor17 OBJECT IDENTIFIER ::= {sensorTable 17}
sensor18 OBJECT IDENTIFIER ::= {sensorTable 18}
sensor19 OBJECT IDENTIFIER ::= {sensorTable 19}
sensor20 OBJECT IDENTIFIER ::= {sensorTable 20}
sensor21 OBJECT IDENTIFIER ::= {sensorTable 21}
sensor22 OBJECT IDENTIFIER ::= {sensorTable 22}
sensor23 OBJECT IDENTIFIER ::= {sensorTable 23}
sensor24 OBJECT IDENTIFIER ::= {sensorTable 24}
sensor25 OBJECT IDENTIFIER ::= {sensorTable 25}
sensor26 OBJECT IDENTIFIER ::= {sensorTable 26}
sensor27 OBJECT IDENTIFIER ::= {sensorTable 27}
sensor28 OBJECT IDENTIFIER ::= {sensorTable 28}
sensor29 OBJECT IDENTIFIER ::= {sensorTable 29}
sensor30 OBJECT IDENTIFIER ::= {sensorTable 30}
sensor31 OBJECT IDENTIFIER ::= {sensorTable 31}
sensor32 OBJECT IDENTIFIER ::= {sensorTable 32}


sensor1Name OBJECT-TYPE 
SYNTAX DisplayString  ACCESS  read-only  STATUS mandatory  
  ::= {sensor1 1}

sensor2Name OBJECT-TYPE 
SYNTAX DisplayString  ACCESS  read-only  STATUS mandatory  
  ::= {sensor2 1}

sensor3Name OBJECT-TYPE 
SYNTAX DisplayString  ACCESS  read-only  STATUS mandatory  
  ::= {sensor3 1}

sensor4Name OBJECT-TYPE 
SYNTAX DisplayString  ACCESS  read-only  STATUS mandatory  
  ::= {sensor4 1}

sensor5Name OBJECT-TYPE 
SYNTAX DisplayString  ACCESS  read-only  STATUS mandatory  
  ::= {sensor5 1}

sensor6Name OBJECT-TYPE 
SYNTAX DisplayString  ACCESS  read-only  STATUS mandatory  
  ::= {sensor6 1}

sensor7Name OBJECT-TYPE 
SYNTAX DisplayString  ACCESS  read-only  STATUS mandatory  
  ::= {sensor7 1}

sensor8Name OBJECT-TYPE 
SYNTAX DisplayString  ACCESS  read-only  STATUS mandatory  
  ::= {sensor8 1}

sensor9Name OBJECT-TYPE 
SYNTAX DisplayString  ACCESS  read-only  STATUS mandatory  
  ::= {sensor9 1}

sensor10Name OBJECT-TYPE 
SYNTAX DisplayString  ACCESS  read-only  STATUS mandatory  
  ::= {sensor10 1}

sensor11Name OBJECT-TYPE 
SYNTAX DisplayString  ACCESS  read-only  STATUS mandatory  
  ::= {sensor11 1}

sensor12Name OBJECT-TYPE 
SYNTAX DisplayString  ACCESS  read-only  STATUS mandatory  
  ::= {sensor12 1}

sensor13Name OBJECT-TYPE 
SYNTAX DisplayString  ACCESS  read-only  STATUS mandatory  
  ::= {sensor13 1}

sensor14Name OBJECT-TYPE 
SYNTAX DisplayString  ACCESS  read-only  STATUS mandatory  
  ::= {sensor14 1}

sensor15Name OBJECT-TYPE 
SYNTAX DisplayString  ACCESS  read-only  STATUS mandatory  
  ::= {sensor15 1}

sensor16Name OBJECT-TYPE 
SYNTAX DisplayString  ACCESS  read-only  STATUS mandatory  
  ::= {sensor16 1}

sensor17Name OBJECT-TYPE 
SYNTAX DisplayString  ACCESS  read-only  STATUS mandatory  
  ::= {sensor17 1}

sensor18Name OBJECT-TYPE 
SYNTAX DisplayString  ACCESS  read-only  STATUS mandatory  
  ::= {sensor18 1}

sensor19Name OBJECT-TYPE 
SYNTAX DisplayString  ACCESS  read-only  STATUS mandatory  
  ::= {sensor19 1}

sensor20Name OBJECT-TYPE 
SYNTAX DisplayString  ACCESS  read-only  STATUS mandatory  
  ::= {sensor20 1}

sensor21Name OBJECT-TYPE 
SYNTAX DisplayString  ACCESS  read-only  STATUS mandatory  
  ::= {sensor21 1}

sensor22Name OBJECT-TYPE 
SYNTAX DisplayString  ACCESS  read-only  STATUS mandatory  
  ::= {sensor22 1}

sensor23Name OBJECT-TYPE 
SYNTAX DisplayString  ACCESS  read-only  STATUS mandatory  
  ::= {sensor23 1}

sensor24Name OBJECT-TYPE 
SYNTAX DisplayString  ACCESS  read-only  STATUS mandatory  
  ::= {sensor24 1}

sensor25Name OBJECT-TYPE 
SYNTAX DisplayString  ACCESS  read-only  STATUS mandatory  
  ::= {sensor25 1}

sensor26Name OBJECT-TYPE 
SYNTAX DisplayString  ACCESS  read-only  STATUS mandatory  
  ::= {sensor26 1}

sensor27Name OBJECT-TYPE 
SYNTAX DisplayString  ACCESS  read-only  STATUS mandatory  
  ::= {sensor27 1}

sensor28Name OBJECT-TYPE 
SYNTAX DisplayString  ACCESS  read-only  STATUS mandatory  
  ::= {sensor28 1}

sensor29Name OBJECT-TYPE 
SYNTAX DisplayString  ACCESS  read-only  STATUS mandatory  
  ::= {sensor29 1}

sensor30Name OBJECT-TYPE 
SYNTAX DisplayString  ACCESS  read-only  STATUS mandatory  
  ::= {sensor30 1}

sensor31Name OBJECT-TYPE 
SYNTAX DisplayString  ACCESS  read-only  STATUS mandatory  
  ::= {sensor31 1}

sensor32Name OBJECT-TYPE 
SYNTAX DisplayString  ACCESS  read-only  STATUS mandatory  
  ::= {sensor32 1}

sensor1value OBJECT-TYPE 
SYNTAX DisplayString  ACCESS  read-only  STATUS mandatory  
  ::= {sensor1 2}

sensor2value OBJECT-TYPE 
SYNTAX DisplayString  ACCESS  read-only  STATUS mandatory  
  ::= {sensor2 2}

sensor3value OBJECT-TYPE 
SYNTAX DisplayString  ACCESS  read-only  STATUS mandatory  
  ::= {sensor3 2}

sensor4value OBJECT-TYPE 
SYNTAX DisplayString  ACCESS  read-only  STATUS mandatory  
  ::= {sensor4 2}

sensor5value OBJECT-TYPE 
SYNTAX DisplayString  ACCESS  read-only  STATUS mandatory  
  ::= {sensor5 2}

sensor6value OBJECT-TYPE 
SYNTAX DisplayString  ACCESS  read-only  STATUS mandatory  
  ::= {sensor6 2}

sensor7value OBJECT-TYPE 
SYNTAX DisplayString  ACCESS  read-only  STATUS mandatory  
  ::= {sensor7 2}

sensor8value OBJECT-TYPE 
SYNTAX DisplayString  ACCESS  read-only  STATUS mandatory  
  ::= {sensor8 2}

sensor9value OBJECT-TYPE 
SYNTAX DisplayString  ACCESS  read-only  STATUS mandatory  
  ::= {sensor9 2}

sensor10value OBJECT-TYPE 
SYNTAX DisplayString  ACCESS  read-only  STATUS mandatory  
  ::= {sensor10 2}

sensor11value OBJECT-TYPE 
SYNTAX DisplayString  ACCESS  read-only  STATUS mandatory  
  ::= {sensor11 2}

sensor12value OBJECT-TYPE 
SYNTAX DisplayString  ACCESS  read-only  STATUS mandatory  
  ::= {sensor12 2}

sensor13value OBJECT-TYPE 
SYNTAX DisplayString  ACCESS  read-only  STATUS mandatory  
  ::= {sensor13 2}

sensor14value OBJECT-TYPE 
SYNTAX DisplayString  ACCESS  read-only  STATUS mandatory  
  ::= {sensor14 2}

sensor15value OBJECT-TYPE 
SYNTAX DisplayString  ACCESS  read-only  STATUS mandatory  
  ::= {sensor15 2}

sensor16value OBJECT-TYPE 
SYNTAX DisplayString  ACCESS  read-only  STATUS mandatory  
  ::= {sensor16 2}

sensor17value OBJECT-TYPE 
SYNTAX DisplayString  ACCESS  read-only  STATUS mandatory  
  ::= {sensor17 2}

sensor18value OBJECT-TYPE 
SYNTAX DisplayString  ACCESS  read-only  STATUS mandatory  
  ::= {sensor18 2}

sensor19value OBJECT-TYPE 
SYNTAX DisplayString  ACCESS  read-only  STATUS mandatory  
  ::= {sensor19 2}

sensor20value OBJECT-TYPE 
SYNTAX DisplayString  ACCESS  read-only  STATUS mandatory  
  ::= {sensor20 2}

sensor21value OBJECT-TYPE 
SYNTAX DisplayString  ACCESS  read-only  STATUS mandatory  
  ::= {sensor21 2}

sensor22value OBJECT-TYPE 
SYNTAX DisplayString  ACCESS  read-only  STATUS mandatory  
  ::= {sensor22 2}

sensor23value OBJECT-TYPE 
SYNTAX DisplayString  ACCESS  read-only  STATUS mandatory  
  ::= {sensor23 2}

sensor24value OBJECT-TYPE 
SYNTAX DisplayString  ACCESS  read-only  STATUS mandatory  
  ::= {sensor24 2}

sensor25value OBJECT-TYPE 
SYNTAX DisplayString  ACCESS  read-only  STATUS mandatory  
  ::= {sensor25 2}

sensor26value OBJECT-TYPE 
SYNTAX DisplayString  ACCESS  read-only  STATUS mandatory  
  ::= {sensor26 2}

sensor27value OBJECT-TYPE 
SYNTAX DisplayString  ACCESS  read-only  STATUS mandatory  
  ::= {sensor27 2}

sensor28value OBJECT-TYPE 
SYNTAX DisplayString  ACCESS  read-only  STATUS mandatory  
  ::= {sensor28 2}

sensor29value OBJECT-TYPE 
SYNTAX DisplayString  ACCESS  read-only  STATUS mandatory  
  ::= {sensor29 2}

sensor30value OBJECT-TYPE 
SYNTAX DisplayString  ACCESS  read-only  STATUS mandatory  
  ::= {sensor30 2}

sensor31value OBJECT-TYPE 
SYNTAX DisplayString  ACCESS  read-only  STATUS mandatory  
  ::= {sensor31 2}

sensor32value OBJECT-TYPE 
SYNTAX DisplayString  ACCESS  read-only  STATUS mandatory  
  ::= {sensor32 2}
sensor1ErrState OBJECT-TYPE 
SYNTAX DisplayString  ACCESS  read-only  STATUS mandatory  
  ::= {sensor1 3}

sensor2ErrState OBJECT-TYPE 
SYNTAX DisplayString  ACCESS  read-only  STATUS mandatory  
  ::= {sensor2 3}

sensor3ErrState OBJECT-TYPE 
SYNTAX DisplayString  ACCESS  read-only  STATUS mandatory  
  ::= {sensor3 3}

sensor4ErrState OBJECT-TYPE 
SYNTAX DisplayString  ACCESS  read-only  STATUS mandatory  
  ::= {sensor4 3}

sensor5ErrState OBJECT-TYPE 
SYNTAX DisplayString  ACCESS  read-only  STATUS mandatory  
  ::= {sensor5 3}

sensor6ErrState OBJECT-TYPE 
SYNTAX DisplayString  ACCESS  read-only  STATUS mandatory  
  ::= {sensor6 3}

sensor7ErrState OBJECT-TYPE 
SYNTAX DisplayString  ACCESS  read-only  STATUS mandatory  
  ::= {sensor7 3}

sensor8ErrState OBJECT-TYPE 
SYNTAX DisplayString  ACCESS  read-only  STATUS mandatory  
  ::= {sensor8 3}

sensor9ErrState OBJECT-TYPE 
SYNTAX DisplayString  ACCESS  read-only  STATUS mandatory  
  ::= {sensor9 3}

sensor10ErrState OBJECT-TYPE 
SYNTAX DisplayString  ACCESS  read-only  STATUS mandatory  
  ::= {sensor10 3}

sensor11ErrState OBJECT-TYPE 
SYNTAX DisplayString  ACCESS  read-only  STATUS mandatory  
  ::= {sensor11 3}

sensor12ErrState OBJECT-TYPE 
SYNTAX DisplayString  ACCESS  read-only  STATUS mandatory  
  ::= {sensor12 3}

sensor13ErrState OBJECT-TYPE 
SYNTAX DisplayString  ACCESS  read-only  STATUS mandatory  
  ::= {sensor13 3}

sensor14ErrState OBJECT-TYPE 
SYNTAX DisplayString  ACCESS  read-only  STATUS mandatory  
  ::= {sensor14 3}

sensor15ErrState OBJECT-TYPE 
SYNTAX DisplayString  ACCESS  read-only  STATUS mandatory  
  ::= {sensor15 3}

sensor16ErrState OBJECT-TYPE 
SYNTAX DisplayString  ACCESS  read-only  STATUS mandatory  
  ::= {sensor16 3}

sensor17ErrState OBJECT-TYPE 
SYNTAX DisplayString  ACCESS  read-only  STATUS mandatory  
  ::= {sensor17 3}

sensor18ErrState OBJECT-TYPE 
SYNTAX DisplayString  ACCESS  read-only  STATUS mandatory  
  ::= {sensor18 3}

sensor19ErrState OBJECT-TYPE 
SYNTAX DisplayString  ACCESS  read-only  STATUS mandatory  
  ::= {sensor19 3}

sensor20ErrState OBJECT-TYPE 
SYNTAX DisplayString  ACCESS  read-only  STATUS mandatory  
  ::= {sensor20 3}

sensor21ErrState OBJECT-TYPE 
SYNTAX DisplayString  ACCESS  read-only  STATUS mandatory  
  ::= {sensor21 3}

sensor22ErrState OBJECT-TYPE 
SYNTAX DisplayString  ACCESS  read-only  STATUS mandatory  
  ::= {sensor22 3}

sensor23ErrState OBJECT-TYPE 
SYNTAX DisplayString  ACCESS  read-only  STATUS mandatory  
  ::= {sensor23 3}

sensor24ErrState OBJECT-TYPE 
SYNTAX DisplayString  ACCESS  read-only  STATUS mandatory  
  ::= {sensor24 3}

sensor25ErrState OBJECT-TYPE 
SYNTAX DisplayString  ACCESS  read-only  STATUS mandatory  
  ::= {sensor25 3}

sensor26ErrState OBJECT-TYPE 
SYNTAX DisplayString  ACCESS  read-only  STATUS mandatory  
  ::= {sensor26 3}

sensor27ErrState OBJECT-TYPE 
SYNTAX DisplayString  ACCESS  read-only  STATUS mandatory  
  ::= {sensor27 3}

sensor28ErrState OBJECT-TYPE 
SYNTAX DisplayString  ACCESS  read-only  STATUS mandatory  
  ::= {sensor28 3}

sensor29ErrState OBJECT-TYPE 
SYNTAX DisplayString  ACCESS  read-only  STATUS mandatory  
  ::= {sensor29 3}

sensor30ErrState OBJECT-TYPE 
SYNTAX DisplayString  ACCESS  read-only  STATUS mandatory  
  ::= {sensor30 3}

sensor31ErrState OBJECT-TYPE 
SYNTAX DisplayString  ACCESS  read-only  STATUS mandatory  
  ::= {sensor31 3}

sensor32ErrState OBJECT-TYPE 
SYNTAX DisplayString  ACCESS  read-only  STATUS mandatory  
  ::= {sensor32 3}


sensor1lastErrTime OBJECT-TYPE 
SYNTAX DisplayString  ACCESS  read-only  STATUS mandatory  
  ::= {sensor1 4}

sensor2lastErrTime OBJECT-TYPE 
SYNTAX DisplayString  ACCESS  read-only  STATUS mandatory  
  ::= {sensor2 4}

sensor3lastErrTime OBJECT-TYPE 
SYNTAX DisplayString  ACCESS  read-only  STATUS mandatory  
  ::= {sensor3 4}

sensor4lastErrTime OBJECT-TYPE 
SYNTAX DisplayString  ACCESS  read-only  STATUS mandatory  
  ::= {sensor4 4}

sensor5lastErrTime OBJECT-TYPE 
SYNTAX DisplayString  ACCESS  read-only  STATUS mandatory  
  ::= {sensor5 4}

sensor6lastErrTime OBJECT-TYPE 
SYNTAX DisplayString  ACCESS  read-only  STATUS mandatory  
  ::= {sensor6 4}

sensor7lastErrTime OBJECT-TYPE 
SYNTAX DisplayString  ACCESS  read-only  STATUS mandatory  
  ::= {sensor7 4}

sensor8lastErrTime OBJECT-TYPE 
SYNTAX DisplayString  ACCESS  read-only  STATUS mandatory  
  ::= {sensor8 4}

sensor9lastErrTime OBJECT-TYPE 
SYNTAX DisplayString  ACCESS  read-only  STATUS mandatory  
  ::= {sensor9 4}

sensor10lastErrTime OBJECT-TYPE 
SYNTAX DisplayString  ACCESS  read-only  STATUS mandatory  
  ::= {sensor10 4}

sensor11lastErrTime OBJECT-TYPE 
SYNTAX DisplayString  ACCESS  read-only  STATUS mandatory  
  ::= {sensor11 4}

sensor12lastErrTime OBJECT-TYPE 
SYNTAX DisplayString  ACCESS  read-only  STATUS mandatory  
  ::= {sensor12 4}

sensor13lastErrTime OBJECT-TYPE 
SYNTAX DisplayString  ACCESS  read-only  STATUS mandatory  
  ::= {sensor13 4}

sensor14lastErrTime OBJECT-TYPE 
SYNTAX DisplayString  ACCESS  read-only  STATUS mandatory  
  ::= {sensor14 4}

sensor15lastErrTime OBJECT-TYPE 
SYNTAX DisplayString  ACCESS  read-only  STATUS mandatory  
  ::= {sensor15 4}

sensor16lastErrTime OBJECT-TYPE 
SYNTAX DisplayString  ACCESS  read-only  STATUS mandatory  
  ::= {sensor16 4}

sensor17lastErrTime OBJECT-TYPE 
SYNTAX DisplayString  ACCESS  read-only  STATUS mandatory  
  ::= {sensor17 4}

sensor18lastErrTime OBJECT-TYPE 
SYNTAX DisplayString  ACCESS  read-only  STATUS mandatory  
  ::= {sensor18 4}

sensor19lastErrTime OBJECT-TYPE 
SYNTAX DisplayString  ACCESS  read-only  STATUS mandatory  
  ::= {sensor19 4}

sensor20lastErrTime OBJECT-TYPE 
SYNTAX DisplayString  ACCESS  read-only  STATUS mandatory  
  ::= {sensor20 4}

sensor21lastErrTime OBJECT-TYPE 
SYNTAX DisplayString  ACCESS  read-only  STATUS mandatory  
  ::= {sensor21 4}

sensor22lastErrTime OBJECT-TYPE 
SYNTAX DisplayString  ACCESS  read-only  STATUS mandatory  
  ::= {sensor22 4}

sensor23lastErrTime OBJECT-TYPE 
SYNTAX DisplayString  ACCESS  read-only  STATUS mandatory  
  ::= {sensor23 4}

sensor24lastErrTime OBJECT-TYPE 
SYNTAX DisplayString  ACCESS  read-only  STATUS mandatory  
  ::= {sensor24 4}

sensor25lastErrTime OBJECT-TYPE 
SYNTAX DisplayString  ACCESS  read-only  STATUS mandatory  
  ::= {sensor25 4}

sensor26lastErrTime OBJECT-TYPE 
SYNTAX DisplayString  ACCESS  read-only  STATUS mandatory  
  ::= {sensor26 4}

sensor27lastErrTime OBJECT-TYPE 
SYNTAX DisplayString  ACCESS  read-only  STATUS mandatory  
  ::= {sensor27 4}

sensor28lastErrTime OBJECT-TYPE 
SYNTAX DisplayString  ACCESS  read-only  STATUS mandatory  
  ::= {sensor28 4}

sensor29lastErrTime OBJECT-TYPE 
SYNTAX DisplayString  ACCESS  read-only  STATUS mandatory  
  ::= {sensor29 4}

sensor30lastErrTime OBJECT-TYPE 
SYNTAX DisplayString  ACCESS  read-only  STATUS mandatory  
  ::= {sensor30 4}

sensor31lastErrTime OBJECT-TYPE 
SYNTAX DisplayString  ACCESS  read-only  STATUS mandatory  
  ::= {sensor31 4}

sensor32lastErrTime OBJECT-TYPE 
SYNTAX DisplayString  ACCESS  read-only  STATUS mandatory  
  ::= {sensor32 4}

sensor1lastErrMsg OBJECT-TYPE 
SYNTAX DisplayString  ACCESS  read-only  STATUS mandatory  
  ::= {sensor1 5}

sensor2lastErrMsg OBJECT-TYPE 
SYNTAX DisplayString  ACCESS  read-only  STATUS mandatory  
  ::= {sensor2 5}

sensor3lastErrMsg OBJECT-TYPE 
SYNTAX DisplayString  ACCESS  read-only  STATUS mandatory  
  ::= {sensor3 5}

sensor4lastErrMsg OBJECT-TYPE 
SYNTAX DisplayString  ACCESS  read-only  STATUS mandatory  
  ::= {sensor4 5}

sensor5lastErrMsg OBJECT-TYPE 
SYNTAX DisplayString  ACCESS  read-only  STATUS mandatory  
  ::= {sensor5 5}

sensor6lastErrMsg OBJECT-TYPE 
SYNTAX DisplayString  ACCESS  read-only  STATUS mandatory  
  ::= {sensor6 5}

sensor7lastErrMsg OBJECT-TYPE 
SYNTAX DisplayString  ACCESS  read-only  STATUS mandatory  
  ::= {sensor7 5}

sensor8lastErrMsg OBJECT-TYPE 
SYNTAX DisplayString  ACCESS  read-only  STATUS mandatory  
  ::= {sensor8 5}

sensor9lastErrMsg OBJECT-TYPE 
SYNTAX DisplayString  ACCESS  read-only  STATUS mandatory  
  ::= {sensor9 5}

sensor10lastErrMsg OBJECT-TYPE 
SYNTAX DisplayString  ACCESS  read-only  STATUS mandatory  
  ::= {sensor10 5}

sensor11lastErrMsg OBJECT-TYPE 
SYNTAX DisplayString  ACCESS  read-only  STATUS mandatory  
  ::= {sensor11 5}

sensor12lastErrMsg OBJECT-TYPE 
SYNTAX DisplayString  ACCESS  read-only  STATUS mandatory  
  ::= {sensor12 5}

sensor13lastErrMsg OBJECT-TYPE 
SYNTAX DisplayString  ACCESS  read-only  STATUS mandatory  
  ::= {sensor13 5}

sensor14lastErrMsg OBJECT-TYPE 
SYNTAX DisplayString  ACCESS  read-only  STATUS mandatory  
  ::= {sensor14 5}

sensor15lastErrMsg OBJECT-TYPE 
SYNTAX DisplayString  ACCESS  read-only  STATUS mandatory  
  ::= {sensor15 5}

sensor16lastErrMsg OBJECT-TYPE 
SYNTAX DisplayString  ACCESS  read-only  STATUS mandatory  
  ::= {sensor16 5}

sensor17lastErrMsg OBJECT-TYPE 
SYNTAX DisplayString  ACCESS  read-only  STATUS mandatory  
  ::= {sensor17 5}

sensor18lastErrMsg OBJECT-TYPE 
SYNTAX DisplayString  ACCESS  read-only  STATUS mandatory  
  ::= {sensor18 5}

sensor19lastErrMsg OBJECT-TYPE 
SYNTAX DisplayString  ACCESS  read-only  STATUS mandatory  
  ::= {sensor19 5}

sensor20lastErrMsg OBJECT-TYPE 
SYNTAX DisplayString  ACCESS  read-only  STATUS mandatory  
  ::= {sensor20 5}

sensor21lastErrMsg OBJECT-TYPE 
SYNTAX DisplayString  ACCESS  read-only  STATUS mandatory  
  ::= {sensor21 5}

sensor22lastErrMsg OBJECT-TYPE 
SYNTAX DisplayString  ACCESS  read-only  STATUS mandatory  
  ::= {sensor22 5}

sensor23lastErrMsg OBJECT-TYPE 
SYNTAX DisplayString  ACCESS  read-only  STATUS mandatory  
  ::= {sensor23 5}

sensor24lastErrMsg OBJECT-TYPE 
SYNTAX DisplayString  ACCESS  read-only  STATUS mandatory  
  ::= {sensor24 5}

sensor25lastErrMsg OBJECT-TYPE 
SYNTAX DisplayString  ACCESS  read-only  STATUS mandatory  
  ::= {sensor25 5}

sensor26lastErrMsg OBJECT-TYPE 
SYNTAX DisplayString  ACCESS  read-only  STATUS mandatory  
  ::= {sensor26 5}

sensor27lastErrMsg OBJECT-TYPE 
SYNTAX DisplayString  ACCESS  read-only  STATUS mandatory  
  ::= {sensor27 5}

sensor28lastErrMsg OBJECT-TYPE 
SYNTAX DisplayString  ACCESS  read-only  STATUS mandatory  
  ::= {sensor28 5}

sensor29lastErrMsg OBJECT-TYPE 
SYNTAX DisplayString  ACCESS  read-only  STATUS mandatory  
  ::= {sensor29 5}

sensor30lastErrMsg OBJECT-TYPE 
SYNTAX DisplayString  ACCESS  read-only  STATUS mandatory  
  ::= {sensor30 5}

sensor31lastErrMsg OBJECT-TYPE 
SYNTAX DisplayString  ACCESS  read-only  STATUS mandatory  
  ::= {sensor31 5}

sensor32lastErrMsg OBJECT-TYPE 
SYNTAX DisplayString  ACCESS  read-only  STATUS mandatory  
  ::= {sensor32 5}


   
        

END
