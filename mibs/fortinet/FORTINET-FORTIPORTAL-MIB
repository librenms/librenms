FORTINET-FORTIPORTAL-MIB DEFINITIONS ::= BEGIN

IMPORTS
    fnSysSerial, fortinet
        FROM FORTINET-CORE-MIB
    ifMIBObjects
        FROM IF-MIB
    sysDescr, sysUpTime, sysName
        FROM SNMPv2-MIB;

fnFortiPortalMib MODULE-IDENTITY
    LAST-UPDATED "202309080000Z"
    ORGANIZATION
        "Fortinet Technologies, Inc."
    CONTACT-INFO
        "
         Technical Support
         email: support@fortinet.com
         http://www.fortinet.com"
    DESCRIPTION
        "Initial version of FORTINET-FORTIPORTAL-MIB."
    ::= { fortinet 123 }

--
-- fortinet.fnFortiPortalMib.fpSystem
--

fpSystem OBJECT IDENTIFIER
    ::= { fnFortiPortalMib 1 }

--
-- fortinet.fnFortiPortalMib.fpSystem.fpSystemInfo
--

fpSystemInfo OBJECT IDENTIFIER
    ::= { fpSystem 1 }

fpSysCpuUsage OBJECT-TYPE
    SYNTAX      Integer32 (0..100)
    MAX-ACCESS  read-only
    STATUS      current
    DESCRIPTION
        "Current CPU usage (percentage)"
    ::= { fpSystemInfo 1 }

fpSysMemUsed OBJECT-TYPE
    SYNTAX      Gauge32
    MAX-ACCESS  read-only
    STATUS      current
    DESCRIPTION
        "Current memory used (KB)"
    ::= { fpSystemInfo 2 }

fpSysMemCapacity OBJECT-TYPE
    SYNTAX      Gauge32
    MAX-ACCESS  read-only
    STATUS      current
    DESCRIPTION
        "Total physical and swap memory installed (KB)"
    ::= { fpSystemInfo 3 }

fpSysDiskUsage OBJECT-TYPE
    SYNTAX      Gauge32
    MAX-ACCESS  read-only
    STATUS      current
    DESCRIPTION
        "Current hard disk usage (MB)"
    ::= { fpSystemInfo 4 }

fpSysDiskCapacity OBJECT-TYPE
    SYNTAX      Gauge32
    MAX-ACCESS  read-only
    STATUS      current
    DESCRIPTION
        "Total hard disk capacity (MB)"
    ::= { fpSystemInfo 5 }

fpSysCpuUsageExcludedNice OBJECT-TYPE
    SYNTAX      Gauge32 (0..100)
    MAX-ACCESS  read-only
    STATUS      current
    DESCRIPTION
        "Current CPU usage excluded nice processes usage (percentage)"
    ::= { fpSystemInfo 6 }

fpSysMemUsage OBJECT-TYPE
    SYNTAX      Integer32 (0..100)
    MAX-ACCESS  read-only
    STATUS      current
    DESCRIPTION
        "Current Memory usage (percentage)"
    ::= { fpSystemInfo 7 }

fpSysPrimaryDiskUsage OBJECT-TYPE
    SYNTAX      Integer32 (0..100)
    MAX-ACCESS  read-only
    STATUS      current
    DESCRIPTION
        "Current Primary Disk usage (percentage)"
    ::= { fpSystemInfo 8 }

END
