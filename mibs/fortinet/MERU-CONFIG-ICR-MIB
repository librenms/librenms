-- *****************************************************************
-- Meru Networks Enterprise Specific MIB
--
-- Copyright (c) 2005 by Meru Networks
-- All rights reserved
--
-- *****************************************************************

MERU-CONFIG-ICR-MIB  DEFINITIONS ::= BEGIN

IMPORTS
    NOTIFICATION-TYPE, 
    OBJECT-TYPE, 
    MODULE-IDENTITY, 
    OBJECT-IDENTITY,
    enterprises, 
    Counter32, 
    Counter64, 
    Gauge32, 
    TimeTicks, 
    IpAddress, 
    Integer32
        FROM SNMPv2-SMI
    Ipv6Address
        FROM IPV6-TC
    TEXTUAL-CONVENTION, 
    TimeInterval, 
    TimeStamp,
    DateAndTime, 
    TruthValue, 
    DisplayString, 
    MacAddress, 
    RowStatus
        FROM SNMPv2-TC
    mwConfiguration
        FROM MERU-SMI
    ;

  mwConfigIcr  MODULE-IDENTITY
    LAST-UPDATED "200506050000Z"
    ORGANIZATION "Meru Networks"
    CONTACT-INFO "support@merunetworks.com"
    DESCRIPTION
        "This MIB defines all the managed objects used to manage the Meru WLAN 
         RAC Configuration infrastructure"
    ::= { mwConfiguration 18 } 
  
    
  
  mwIcrTable  OBJECT-TYPE
    SYNTAX SEQUENCE OF MwIcrEntry
    MAX-ACCESS not-accessible
    STATUS     current
    DESCRIPTION
         "This object describes Roaming Across Controllers "
    ::= { mwConfigIcr 1 }

  mwIcrEntry  OBJECT-TYPE
    SYNTAX MwIcrEntry
    MAX-ACCESS not-accessible
    STATUS     current
    DESCRIPTION
         "This object describes Roaming Across Controllers "
    INDEX {  mwIcrTableIndex  }
    ::= { mwIcrTable 1 }

  MwIcrEntry  ::=  SEQUENCE { 
       mwIcrTableIndex                                             Integer32, 
       mwIcrEssId                                                  DisplayString(SIZE (0..31)),
       mwIcrHomeDhcpIp                                             IpAddress,
       mwIcrControllerIp                                           IpAddress,
       mwIcrRowStatus                                              RowStatus 
  }
   
   
  mwIcrTableIndex  OBJECT-TYPE
    SYNTAX Integer32 
    MAX-ACCESS not-accessible 
    STATUS     current
    DESCRIPTION
         "The index value of the  table "
    ::= { mwIcrEntry 1 }

  mwIcrEssId  OBJECT-TYPE
    SYNTAX DisplayString(SIZE (0..31))
    MAX-ACCESS read-create
    STATUS     current
    DESCRIPTION
         "This object describes ESSID"
    ::= { mwIcrEntry    2 }

  mwIcrControllerIp  OBJECT-TYPE
    SYNTAX IpAddress
    MAX-ACCESS read-create
    STATUS     current
    DESCRIPTION
         "This object describes Controller IP"
    ::= { mwIcrEntry    3 }

  mwIcrHomeDhcpIp  OBJECT-TYPE
    SYNTAX IpAddress
    MAX-ACCESS read-create
    STATUS     current
    DESCRIPTION
         "This object describes Home DHCP Controller IP"
    ::= { mwIcrEntry    4 }

  mwIcrRowStatus  OBJECT-TYPE
    SYNTAX RowStatus
    MAX-ACCESS read-create
    STATUS     current
    DESCRIPTION
         "This object is used to create and delete rows in the table"
    ::= { mwIcrEntry 5 }

  
END
