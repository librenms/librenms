--
-- MODULE-IDENTITY
--  OrgName
--    Fortinet, Inc.
--  ContactInfo
--     Technical Support
--     e-mail: support@fortinet.com
--     http://www.fortinet.com
--

FORTINET-FORTIEXTENDER-MIB DEFINITIONS ::= BEGIN
	IMPORTS
		MODULE-COMPLIANCE, NOTIFICATION-GROUP, OBJECT-GROUP
			FROM SNMPv2-CONF
		DisplayString, TEXTUAL-CONVENTION
			FROM SNMPv2-TC
		MODULE-IDENTITY, OBJECT-TYPE, NOTIFICATION-TYPE, Integer32, Gauge32, 
		IpAddress, OBJECT-IDENTITY, Counter64
			FROM SNMPv2-SMI
		ifIndex, ifEntry, ifName
			FROM IF-MIB
		FnBoolState, FnIndex, fortinet
			FROM FORTINET-CORE-MIB;

fnFortiExtenderMib MODULE-IDENTITY
	LAST-UPDATED "202004060000Z"
	ORGANIZATION
		"Fortinet Technologies, Inc."
	CONTACT-INFO
		"Technical Support
		email: support@fortinet.com
		http://www.fortinet.com
		"
	DESCRIPTION
		"Initial version of FORTINET-EXTENDER-MIB."
	::= {fortinet 121}

	--
	-- Text conventions --
	--

	--FextOptionEnableDisable ::= TEXTUAL-CONVENTION
	--	STATUS      current
	--	DESCRIPTION	"Enable/Disable Option."
	--	SYNTAX		INTEGER {
	--		enable	(1),
	--		disable	(2)
	--	}
		
	--FextOptionUpDown ::= TEXTUAL-CONVENTION
	--	STATUS      current
	--	DESCRIPTION	"Up/Down Option."
	--	SYNTAX		INTEGER {
	--		up	 (1),
	--		down (2)
	--	}

	--FextOptionInterfaceType ::= TEXTUAL-CONVENTION
	--	STATUS      current
	--	DESCRIPTION	"Interface Type Option."
	--	SYNTAX		INTEGER {
	--		physical	(1),
	--		tunnel		(2),
	--		loopback 	(3),
	--		lte 		(4),
	--		virtual-wan	(5),
	--		lan-switch 	(6)
	--	}

	--FextOptionInterfaceMode ::= TEXTUAL-CONVENTION
	--	STATUS      current
	--	DESCRIPTION	"Interface Addressing Mode."
	--	SYNTAX		INTEGER {
	--		static (1),
	--		dhcp   (2)
	--	}

	--FextOptionInterfaceAllowAccess ::= TEXTUAL-CONVENTION
	--	STATUS      current
	--	DESCRIPTION	"Permitted types of management access."
	--	SYNTAX		INTEGER {
	--		ping   (1),
	--		http   (2),
	--		telnet (3),
	--		ssh    (4),
	--		https  (5)
	--	}

	--FextOptionInterfaceAlgorithm ::= TEXTUAL-CONVENTION
	--	STATUS      current
	--	DESCRIPTION	"Interface Addressing Mode."
	--	SYNTAX		INTEGER {
	--		redundant (1),
	--		WRR       (2)
	--	}

	--FextOptionInterfaceFEC ::= TEXTUAL-CONVENTION
	--	STATUS      current
	--	DESCRIPTION	"Interface forward equivalence class."
	--	SYNTAX 		INTEGER {
	--		source_ip           (1),
	--		dest_ip             (2),
	--		source_dest_ip_pair (3),
	--		connection          (4)
	--	}

	--FextOptionDiscoveryType ::= TEXTUAL-CONVENTION
	--	STATUS      current
	--	DESCRIPTION	"Interface forward equivalence class."
	--	SYNTAX		INTEGER {
	--		auto      (1),
	--		fortigate (2),
	--		cloud     (3),
	--		local     (4)
	--	}

	--FextOptionFGTDiscoveryType ::= TEXTUAL-CONVENTION
	--	STATUS      current
	--	DESCRIPTION	"Fortigate Discovery type."
	--	SYNTAX		INTEGER {
	--		static    (1),
	--		broadcast (2)
	--	}

	--FextOptionNetworkMode ::= TEXTUAL-CONVENTION
	--	STATUS      current
	--	DESCRIPTION	"System networking mode."
	--	SYNTAX		INTEGER {
	--		ip-passthrough (1),
	--		nat            (2)
	--	}

	--FextOptionDHCPServerDNS ::= TEXTUAL-CONVENTION
	--	STATUS      current
	--	DESCRIPTION	"DHCP clients' DNS server option."
	--	SYNTAX		INTEGER {
	--		default	(1),
	--		specify	(2),
	--		wan-dns (3)
	--	}

	--FextOptionDHCPServerNTP ::= TEXTUAL-CONVENTION
	--	STATUS      current
	--	DESCRIPTION	"DHCP clients' NTP server option."
	--	SYNTAX		INTEGER {
	--		specify	(1)
	--	}

	--FextOptionHchkProbeProtocol ::= TEXTUAL-CONVENTION
	--	STATUS      current
	--	DESCRIPTION	"The protocol to use for VWAN status checking."
	--	SYNTAX		INTEGER {
	--		ping (1),
	--		http (2),
	--		dns  (3)
	--	}

	--FextOptionSMSAlert ::= TEXTUAL-CONVENTION
	--	STATUS      current
	--	DESCRIPTION	"SMS notification alert types."
	--	SYNTAX		INTEGER {
	--		system-reboot	       (1),
	--		data-exhausted		   (2),
	--		session-disconnect 	   (3),
	--		low-signal-strength    (4),
	--		os-image-fallback-wan  (5),
	--		mode-switch 	       (6),
	--		fgt-backup-mode-switch (7)
	--	}

	--FextOptionSMSCommand ::= TEXTUAL-CONVENTION
	--	STATUS      current
	--	DESCRIPTION	"SMS remote diagnose command types."
	--	SYNTAX		INTEGER {
	--		reboot	            (1),
	--		factory-reset		(2),
	--		set-apn 	        (3),
	--		modem-reset         (4),
	--		get-modem-status    (5),
	--		get-extender-status (6),
	--		get-system-version  (7),
	--		get-system-status   (8)
	--	}

    --FextOptionInfoManagementType ::= TEXTUAL-CONVENTION
    --    STATUS      current
    --    DESCRIPTION "Control Management type."
    --    SYNTAX      INTEGER {
    --        CLOUD  (1),
    --        CAPWAP (2),
    --        LOCAL  (3)
    --    }

    --FextOptionInfoNetworkMode ::= TEXTUAL-CONVENTION
    --   STATUS      current
    --    DESCRIPTION "System networking mode."
    --    SYNTAX      INTEGER {
    --        ip-passthrough        (1),
    --        ip-passthrough-capwap (2),
    --        ip-passthrough-vlan   (3),
    --        nat                   (4)
    --    }

	--
	-- fnCoreMib.fnFortiExtenderMib
	--
	-- fextHeader	::= {fnFortiExtenderMib 1}
	-- fextSystem	::= {fnFortiExtenderMib 2}
	-- fextLTE		::= {fnFortiExtenderMib 3}
	-- fextNetwork	::= {fnFortiExtenderMib 4}
	-- fextFirewall ::= {fnFortiExtenderMib 5}
	-- fextRouter	::= {fnFortiExtenderMib 6}
	-- fextVPN		::= {fnFortiExtenderMib 7}
	-- fextHMon	    ::= {fnFortiExtenderMib 8}
	-- fextSNMP	    ::= {fnFortiExtenderMib 9}
    -- fextInfo     ::= {fnFortiExtenderMib 21}
    -- fextTraps    ::= {fnFortiExtenderMib 100}
    -- fextModel    ::= {fnFortiExtenderMib 200}
	
	--

	fextHeader	 OBJECT IDENTIFIER ::= {fnFortiExtenderMib 1}
	fextSystem	 OBJECT IDENTIFIER ::= {fnFortiExtenderMib 2}
	fextLTE		 OBJECT IDENTIFIER ::= {fnFortiExtenderMib 3}
	fextNetwork	 OBJECT IDENTIFIER ::= {fnFortiExtenderMib 4}
	fextFirewall OBJECT IDENTIFIER ::= {fnFortiExtenderMib 5}
	fextRouter	 OBJECT IDENTIFIER ::= {fnFortiExtenderMib 6}
	fextVPN		 OBJECT IDENTIFIER ::= {fnFortiExtenderMib 7}
	fextHMon	 OBJECT IDENTIFIER ::= {fnFortiExtenderMib 8}
	fextSNMP	 OBJECT IDENTIFIER ::= {fnFortiExtenderMib 9}
    fextInfo     OBJECT IDENTIFIER ::= {fnFortiExtenderMib 21}
	fextTraps	 OBJECT IDENTIFIER ::= {fnFortiExtenderMib 100}
	fextModel	 OBJECT IDENTIFIER ::= {fnFortiExtenderMib 200}

	--
	-- fnFortiExtenderMib.fextHeader
	--
	-- fextVersion ::= {fextHeader 1}
	--

	fextVersion OBJECT IDENTIFIER ::= {fextHeader 1}

	--
	-- fextHeader.fextVersion
	--
	-- fextVersionConfig  ::= {fextVersion 1}
	-- fextVersionCarrier ::= {fextVersion 2}
	-- fextVersionSimmap  ::= {fextVersion 3}
	--

	fextVersionConfig OBJECT-TYPE
		SYNTAX      DisplayString (SIZE (0 .. 32)) 
		MAX-ACCESS  read-only
		STATUS      current
		DESCRIPTION	"System configuration version."
		::= {fextVersion 1}

	fextVersionCarrier OBJECT-TYPE
		SYNTAX      DisplayString (SIZE (0 .. 48)) 
		MAX-ACCESS  read-only
		STATUS      current
		DESCRIPTION	"LTE Carrier configuration version."
		::= {fextVersion 2}

	fextVersionSimmap OBJECT-TYPE
		SYNTAX      DisplayString (SIZE (0 .. 32)) 
		MAX-ACCESS  read-only
		STATUS      current
		DESCRIPTION	"LTE SIMMAP configuration version."
		::= {fextVersion 3}

	--
	-- fnFortiExtenderMib.fextSystem
	--
	-- fextGlobal          ::= {fextSystem 1}
	-- fextManagement      ::= {fextSystem 2}
	-- fextInterface       ::= {fextSystem 3}
	-- fextDHCPServer      ::= {fextSystem 4}
	-- fextDNS             ::= {fextSystem 5}
	-- fextVWANMember      ::= {fextSystem 6}
	-- fextVWANHchk        ::= {fextSystem 7}
	-- fextSMSNotification ::= {fextSystem 8}
	-- fextSMSRemoteDiag   ::= {fextSystem 9}
	-- fextSysLog          ::= {fextSystem 10}
	-- fextLANSwitch       ::= {fextSystem 11}
	-- fextVirtualWirePair ::= {fextSystem 12}
	--

	fextGlobal OBJECT-IDENTITY
		STATUS      current
		DESCRIPTION
			"Extender global settings."
		::=	{fextSystem 1}

	fextManagement OBJECT-IDENTITY
		STATUS      current
		DESCRIPTION
			"Extender management settings."
		::=	{fextSystem 2}

	fextInterface OBJECT-TYPE
		SYNTAX      SEQUENCE OF FextInterfaceEntry
		MAX-ACCESS  not-accessible
		STATUS      current
		DESCRIPTION	"A table of inerfaces. This table is intended to be extended
				     with platform specific information."
		::= {fextSystem 3}

	fextDHCPServer OBJECT-TYPE
		SYNTAX      SEQUENCE OF FextDHCPServerEntry
		MAX-ACCESS  not-accessible
		STATUS      current
		DESCRIPTION	"A table of DHCP Servers. This table is intended to be
					 extended with platform specific information."
		::= {fextSystem 4}

	fextDNS OBJECT-IDENTITY
		STATUS      current
		DESCRIPTION
			"DNS settings to resolve domain names to IP addresses."
		::=	{fextSystem 5}

	fextVWANMember OBJECT-TYPE
		SYNTAX      SEQUENCE OF FextVWANMemberEntry
		MAX-ACCESS  not-accessible
		STATUS      current
		DESCRIPTION	"A table of virtual VWAN Interface members. This table is
					 intended to be extended with platform specific information."
		::=	{fextSystem 6}

	fextVWANHchk OBJECT-TYPE
		SYNTAX      SEQUENCE OF FextVWANHchkEntry
		MAX-ACCESS  not-accessible
		STATUS      obsolete
		DESCRIPTION	"A table of virtual VWAN Interface member's status or health
					 check configuration. This table is intended to be extended
					 with platform specific information."
		::=	{fextSystem 7}

	fextSMSNotification OBJECT-IDENTITY
		STATUS      current
		DESCRIPTION "System SMS notification setting."
		::=	{fextSystem 8}

	fextSMSRemoteDiag OBJECT-IDENTITY
		STATUS      current
		DESCRIPTION "System SMS remote diagnose setting."
		::=	{fextSystem 9}

	fextSysLog OBJECT-IDENTITY
		STATUS      current
		DESCRIPTION "Syslog server setting."
		::=	{fextSystem 10}

	fextLANSwitch OBJECT-IDENTITY
		STATUS      current
		DESCRIPTION "System LAN Switch setting."
		::=	{fextSystem 11}

	fextVirtualWirePair OBJECT-IDENTITY
		STATUS      current
		DESCRIPTION "System LAN-to-LTE interface mapping."
		::=	{fextSystem 12}

	--
	-- fextSystem.fextGlobal
	--
	-- fextHostname         ::= {fextGlobal 1}
	-- fextTimezone         ::= {fextGlobal 2}
	-- fextAutoInstallImage ::= {fextGlobal 3}
	-- fextDefaultImageFile ::= {fextGlobal 4}
	-- fextMDMFWServer      ::= {fextGlobal 5}
	-- fextOSFWServer       ::= {fextGlobal 6}
	--

	fextHostname OBJECT-TYPE
		SYNTAX      DisplayString (SIZE (0 .. 32))
		MAX-ACCESS  read-only
		STATUS      current
		DESCRIPTION	"System hostname."
		::= {fextGlobal 1}

	fextTimezone OBJECT-TYPE
		SYNTAX      Integer32 (0 .. 82)
		MAX-ACCESS  read-only
		STATUS      current
		DESCRIPTION "System timezone."
		::= {fextGlobal 2}

	fextAutoInstallImage OBJECT-TYPE
	 --	SYNTAX      FextOptionEnableDisable
		SYNTAX      DisplayString
		MAX-ACCESS	read-only
		STATUS      current
		DESCRIPTION	"Automatically install image from USB."
		::= {fextGlobal 3}

	fextDefaultImageFile OBJECT-TYPE
		SYNTAX      DisplayString (SIZE (0 .. 64))
		MAX-ACCESS  read-only
		STATUS      current
		DESCRIPTION "Image file name from USB."
		::= {fextGlobal 4}

	fextMDMFWServer OBJECT-TYPE
		SYNTAX      DisplayString (SIZE (0 .. 64))
		MAX-ACCESS  read-only
		STATUS      current
		DESCRIPTION "Cloud Modem image upgrade URL."
		::= {fextGlobal 5}

	fextOSFWServer OBJECT-TYPE
		SYNTAX      DisplayString (SIZE (0 .. 64))
		MAX-ACCESS  read-only
		STATUS      current
		DESCRIPTION "Cloud OS image upgrade URL."
		::= {fextGlobal 6}

	--
	-- fextSystem.fextManagement
	--
	-- fextMgmtDiscoveryType ::= {fextManagement 1}
	-- fextMgmtFortigate     ::= {fextManagement 2}
	-- fextMgmtCloud         ::= {fextManagement 3}
	-- fextMgmtLocal         ::= {fextManagement 4}
	-- fextMgmtLocalAccess   ::= {fextManagement 5}
	-- fextMgmtFGTBackup     ::= {fextManagement 6}
	--

	fextMgmtDiscoveryType OBJECT-TYPE
	 --	SYNTAX      FextOptionDiscoveryType
		SYNTAX      DisplayString 
		MAX-ACCESS  read-only
		STATUS      current
		DESCRIPTION "Control Management discovery type."
		::= {fextManagement 1}

	fextMgmtFortigate OBJECT-IDENTITY
		STATUS      current
		DESCRIPTION "Fortigate Management setting."
		::= {fextManagement 2}

	fextMgmtCloud OBJECT-IDENTITY
		STATUS      current
		DESCRIPTION "Cloud Management setting."
		::= {fextManagement 3}

	fextMgmtLocal OBJECT-IDENTITY
		STATUS      current
		DESCRIPTION "Local Management setting."
		::= {fextManagement 4}

	fextMgmtLocalAccess OBJECT-IDENTITY
		STATUS      current
		DESCRIPTION "Administrative access setting."
		::= {fextManagement 5}

	fextMgmtFGTBackup OBJECT-IDENTITY
		STATUS      current
		DESCRIPTION "Fortigate Backup feature."
		::= {fextManagement 6}

	--
	-- fextManagement.fextMgmtFortigate
	--
	-- fextFGTDiscoveryType ::= {fextMgmtFortigate 1}
	-- fextFGTStaticIP      ::= {fextMgmtFortigate 2}
	-- fextFGTControlPort   ::= {fextMgmtFortigate 3}
	-- fextFGTDataPort      ::= {fextMgmtFortigate 4}
	-- fextFGTDiscoveryIntf ::= {fextMgmtFortigate 5}
	-- fextFGTIngressIntf   ::= {fextMgmtFortigate 6}
	--

	fextFGTDiscoveryType OBJECT-TYPE
	 --	SYNTAX      FextOptionFGTDiscoveryType 
		SYNTAX      DisplayString 
		MAX-ACCESS  read-only
		STATUS      current
		DESCRIPTION	"Fortigate Discovery type."
		::= {fextMgmtFortigate 1}

	fextFGTStaticIP OBJECT-TYPE
	    SYNTAX      DisplayString
	    MAX-ACCESS  read-only
	    STATUS      current
	    DESCRIPTION "Fortigate static IP address."
	    ::= {fextMgmtFortigate 2}

	fextFGTControlPort OBJECT-TYPE
		SYNTAX      Integer32 (1024..49150)
		MAX-ACCESS  read-only
		STATUS      current
		DESCRIPTION	"Fortigate CAPWAP control port."
		::= {fextMgmtFortigate 3}

	fextFGTDataPort OBJECT-TYPE
		SYNTAX      Integer32 (1024..49150)
		MAX-ACCESS  read-only
		STATUS      current
		DESCRIPTION	"Fortigate CAPWAP data port."
		::= {fextMgmtFortigate 4}

	fextFGTDiscoveryIntf OBJECT-TYPE
		SYNTAX      DisplayString
		MAX-ACCESS  read-only
		STATUS      current
		DESCRIPTION	"Interfaces for discovery fortigate."
		::= {fextMgmtFortigate 5}

	fextFGTIngressIntf OBJECT-TYPE
		SYNTAX      DisplayString
		MAX-ACCESS  read-only
		STATUS      current
		DESCRIPTION	"CAPWAP virtual interface's original interface."
		::= {fextMgmtFortigate 6}

	--
	-- fextManagement.fextMgmtCloud
	--
	-- fextCloudDispatcher     ::= {fextMgmtCloud 1}
	-- fextCloudDispatcherPort ::= {fextMgmtCloud 2}
	-- fextCloudMode           ::= {fextMgmtCloud 3}
	-- fextCloudProxy          ::= {fextMgmtCloud 4}
	-- fextCloudProxyServer    ::= {fextMgmtCloud 5}
	-- fextCloudProxyPort      ::= {fextMgmtCloud 6}
	--

	fextCloudDispatcher OBJECT-TYPE
		SYNTAX      DisplayString 
		MAX-ACCESS  read-only
		STATUS      current
		DESCRIPTION	"Cloud dispatcher URL."
		::= {fextMgmtCloud 1}

	fextCloudDispatcherPort OBJECT-TYPE
	    SYNTAX      Integer32
	    MAX-ACCESS  read-only
	    STATUS      current
	    DESCRIPTION "Cloud dispatcher port."
	    ::= {fextMgmtCloud 2}

	fextCloudMode OBJECT-TYPE
	 --	SYNTAX      FextOptionNetworkMode 
		SYNTAX      DisplayString 
		MAX-ACCESS  read-only
		STATUS      current
		DESCRIPTION	"System networking mode."
		::= {fextMgmtCloud 3}

	fextCloudProxy OBJECT-TYPE
	 -- SYNTAX      FextOptionEnableDisable
		SYNTAX      DisplayString 
	    MAX-ACCESS  read-only
	    STATUS      current
	    DESCRIPTION "Enable/disable proxy connection."
	    ::= {fextMgmtCloud 4}

	fextCloudProxyServer OBJECT-TYPE
		SYNTAX      DisplayString 
		MAX-ACCESS  read-only
		STATUS      current
		DESCRIPTION	"Cloud proxy server IP address."
		::= {fextMgmtCloud 5}

	fextCloudProxyPort OBJECT-TYPE
	    SYNTAX      Integer32
	    MAX-ACCESS  read-only
	    STATUS      current
	    DESCRIPTION "Cloud proxy socks5 port."
	    ::= {fextMgmtCloud 6}

	--
	-- fextManagement.fextMgmtLocal
	--
	-- fextLocalMode ::= {fextMgmtLocal 1}
	--

	fextLocalMode OBJECT-TYPE
	 --	SYNTAX      FextOptionNetworkMode 
		SYNTAX      DisplayString 
		MAX-ACCESS  read-only
		STATUS      current
		DESCRIPTION	"System networking mode."
		::= {fextMgmtLocal 1}

	--
	-- fextManagement.fextMgmtLocalAccess
	--
	-- fextAccessHTTP    ::= {fextMgmtLocalAccess 1}
	-- fextAccessHTTPS   ::= {fextMgmtLocalAccess 2}
	-- fextAccessSSH     ::= {fextMgmtLocalAccess 3}
	-- fextAccessTelnet  ::= {fextMgmtLocalAccess 4}
	-- fextAccessTimeout ::= {fextMgmtLocalAccess 5}
	--

	fextAccessHTTP OBJECT-TYPE
	    SYNTAX      Integer32 (1..65535)
	    MAX-ACCESS  read-only
	    STATUS      current
	    DESCRIPTION "System local access HTTP port."
	    ::= {fextMgmtLocalAccess 1}

	fextAccessHTTPS OBJECT-TYPE
	    SYNTAX      Integer32 (1..65535)
	    MAX-ACCESS  read-only
	    STATUS      current
	    DESCRIPTION "System local access HTTPS port."
	    ::= {fextMgmtLocalAccess 2}

	fextAccessSSH OBJECT-TYPE
	    SYNTAX      Integer32 (1..65535)
	    MAX-ACCESS  read-only
	    STATUS      current
	    DESCRIPTION "System local access SSH port."
	    ::= {fextMgmtLocalAccess 3}

	fextAccessTelnet OBJECT-TYPE
	    SYNTAX      Integer32 (1..65535)
	    MAX-ACCESS  read-only
	    STATUS      current
	    DESCRIPTION "System local access Telnet port."
	    ::= {fextMgmtLocalAccess 4}

	fextAccessTimeout OBJECT-TYPE
	    SYNTAX      Integer32 (1..480)
	    MAX-ACCESS  read-only
	    STATUS      current
	    DESCRIPTION "System local access timeout in minutes."
	    ::= {fextMgmtLocalAccess 5}

	--
	-- fextManagement.fextMgmtFGTBackup
	--
	-- fextBackupVRRPInterface ::= {fextMgmtFGTBackup 1}
	-- fextBackupStatus        ::= {fextMgmtFGTBackup 2}
	--

	fextBackupVRRPInterface OBJECT-TYPE
		SYNTAX      DisplayString 
		MAX-ACCESS  read-only
		STATUS      current
		DESCRIPTION	"The interface for Fortigate backup purpose."
		::= {fextMgmtFGTBackup 1}

	fextBackupStatus OBJECT-TYPE
	 -- SYNTAX      FextOptionEnableDisable
		SYNTAX      DisplayString 
	    MAX-ACCESS  read-only
	    STATUS      current
	    DESCRIPTION "Enable/disable backup feature."
	    ::= {fextMgmtFGTBackup 2}

	--
	-- fextSystem.fextInterface
	--

	fextInterfaceEntry OBJECT-TYPE
		SYNTAX      FextInterfaceEntry
		MAX-ACCESS  not-accessible
		STATUS      current
		DESCRIPTION "An entry containing interface configuration."
		INDEX       {fextInterfaceIndex}
		::= {fextInterface 1}

	FextInterfaceEntry ::= SEQUENCE {
		fextInterfaceIndex			FnIndex,
		fextInterfaceName			DisplayString,
	 --	fextInterfaceType			FextOptionInterfaceType,
		fextInterfaceType			DisplayString,
	 --	fextInterfaceStatus			FextOptionUpDown,
		fextInterfaceStatus			DisplayString,
	 --	fextInterfaceMode			FextOptionInterfaceMode,
		fextInterfaceMode			DisplayString,
		fextInterfaceIP				DisplayString,
		fextInterfaceIPMask			Integer32,
		fextInterfaceGateway		DisplayString,
	 --	fextInterfaceMTUOverride	FextOptionEnableDisable,
		fextInterfaceMTUOverride	DisplayString,
		fextInterfaceMTU			Integer32,
		fextInterfaceRID			Integer32,
		fextInterfaceVID			Integer32,
		fextInterfaceIngressIntf	DisplayString,
	 --	fextInterfaceVRRPVirtualMAC	FextOptionEnableDisable,
		fextInterfaceVRRPVirtualMAC	DisplayString,
	 --	fextInterfaceVRRP			OBJECT IDENTIFIER,
	 --	fextInterfaceAllowAccess	FextOptionInterfaceAllowAccess,
		fextInterfaceAllowAccess	DisplayString,
	 --	fextInterfaceAlgorithm		FextOptionInterfaceAlgorithm,
		fextInterfaceAlgorithm		DisplayString,
	 --	fextInterfaceFEC			FextOptionInterfaceFEC,
		fextInterfaceFEC			DisplayString,
		fextInterfaceSessionTimeout	Integer32,
		fextInterfaceGracePeriod	Integer32,
		fextInterfaceMembers		DisplayString
	}

	fextInterfaceIndex OBJECT-TYPE
		SYNTAX      FnIndex
		MAX-ACCESS  not-accessible
		STATUS      current
		DESCRIPTION	"An index uniquely defining an interface within the
					 fextInterface."
		::= {fextInterfaceEntry 1}

	fextInterfaceName OBJECT-TYPE
	    SYNTAX      DisplayString
	    MAX-ACCESS  read-only
	    STATUS      current
	    DESCRIPTION "The name of interface."
	    ::= {fextInterfaceEntry 2}

	fextInterfaceType OBJECT-TYPE
	 -- SYNTAX      FextOptionInterfaceType
		SYNTAX      DisplayString
	    MAX-ACCESS  read-only
	    STATUS      current
	    DESCRIPTION "The Interface Type."
	    ::= {fextInterfaceEntry 3}

	fextInterfaceStatus OBJECT-TYPE
	 -- SYNTAX      FextOptionUpDown
		SYNTAX      DisplayString
	    MAX-ACCESS  read-only
	    STATUS      current
	    DESCRIPTION "Bring up or shut down the interface."
	    ::= {fextInterfaceEntry 4}

	fextInterfaceMode OBJECT-TYPE
	 -- SYNTAX      FextOptionInterfaceMode
		SYNTAX      DisplayString
	    MAX-ACCESS  read-only
	    STATUS      current
	    DESCRIPTION "The interface addressing mode."
	    ::= {fextInterfaceEntry 5}

	fextInterfaceIP OBJECT-TYPE
	    SYNTAX      DisplayString
	    MAX-ACCESS  read-only
	    STATUS      current
	    DESCRIPTION "Interface IPv4 address and subnet mask."
	    ::= {fextInterfaceEntry 6}

	fextInterfaceIPMask OBJECT-TYPE
	    SYNTAX      Integer32 (8..32)
	    MAX-ACCESS  read-only
	    STATUS      current
	    DESCRIPTION "IP mask length of LTE interface."
	    ::= {fextInterfaceEntry 7}

	fextInterfaceGateway OBJECT-TYPE
	    SYNTAX      DisplayString
	    MAX-ACCESS  read-only
	    STATUS      current
	    DESCRIPTION "Interface's connected Gateway."
	    ::= {fextInterfaceEntry 8}

	fextInterfaceMTUOverride OBJECT-TYPE
	 -- SYNTAX      FextOptionEnableDisable
		SYNTAX      DisplayString
	    MAX-ACCESS  read-only
	    STATUS      current
	    DESCRIPTION "enable/disable the mtu override."
	    ::= {fextInterfaceEntry 9}

	fextInterfaceMTU OBJECT-TYPE
	    SYNTAX      Integer32 (512..1500)
	    MAX-ACCESS  read-only
	    STATUS      current
	    DESCRIPTION "The MTU value of interface."
	    ::= {fextInterfaceEntry 10}

	fextInterfaceRID OBJECT-TYPE
	    SYNTAX      Integer32 (512..1500)
	    MAX-ACCESS  read-only
	    STATUS      current
	    DESCRIPTION "CAPWAP virtual interface's ID."
	    ::= {fextInterfaceEntry 11}

	fextInterfaceVID OBJECT-TYPE
	    SYNTAX      Integer32 (512..1500)
	    MAX-ACCESS  read-only
	    STATUS      current
	    DESCRIPTION "VLAN ID."
	    ::= {fextInterfaceEntry 12}

	fextInterfaceIngressIntf OBJECT-TYPE
	    SYNTAX      DisplayString
	    MAX-ACCESS  read-only
	    STATUS      current
	    DESCRIPTION "CAPWAP or VLAN interfaces' parent interface."
	    ::= {fextInterfaceEntry 13}

	fextInterfaceVRRPVirtualMAC OBJECT-TYPE
	 -- SYNTAX      FextOptionEnableDisable
		SYNTAX      DisplayString
	    MAX-ACCESS  read-only
	    STATUS      current
	    DESCRIPTION "Enable/disable usage of virtual MAC for VRRP."
	    ::= {fextInterfaceEntry 14}

	--fextInterfaceVRRP OBJECT-IDENTITY
	--	STATUS      current
	--	DESCRIPTION "The VRRP configuration of interface."
	--    ::= {fextInterfaceEntry 15}

	fextInterfaceAllowAccess OBJECT-TYPE
	 -- SYNTAX      FextOptionInterfaceAllowAccess
		SYNTAX      DisplayString
	    MAX-ACCESS  read-only
	    STATUS      current
	    DESCRIPTION "Permitted types of management access to this interface."
	    ::= {fextInterfaceEntry 15}

	fextInterfaceAlgorithm OBJECT-TYPE
	 -- SYNTAX      FextOptionInterfaceAlgorithm
		SYNTAX      DisplayString
	    MAX-ACCESS  read-only
	    STATUS      current
	    DESCRIPTION "LLB algorithm."
	    ::= {fextInterfaceEntry 16}

	fextInterfaceFEC OBJECT-TYPE
	 -- SYNTAX      FextOptionInterfaceFEC
		SYNTAX      DisplayString
	    MAX-ACCESS  read-only
	    STATUS      current
	    DESCRIPTION "Forward equivalence class."
	    ::= {fextInterfaceEntry 17}

	fextInterfaceSessionTimeout OBJECT-TYPE
	    SYNTAX      Integer32 (0..86400)
	    MAX-ACCESS  read-only
	    STATUS      current
	    DESCRIPTION "FEC Session timeout in seconds."
	    ::= {fextInterfaceEntry 18}

	fextInterfaceGracePeriod OBJECT-TYPE
	    SYNTAX      Integer32 (0..10000000)
	    MAX-ACCESS  read-only
	    STATUS      current
	    DESCRIPTION "Grace period measured in seconds before failback."
	    ::= {fextInterfaceEntry 19}

	fextInterfaceMembers OBJECT-TYPE
	    SYNTAX      DisplayString
	    MAX-ACCESS  read-only
	    STATUS      current
	    DESCRIPTION "The link members of virtual-wan interface."
	    ::= {fextInterfaceEntry 20}

	--
	-- fextInterfaceEntry.fextInterfaceVRRP
	--

	--fextVRRPStatus OBJECT-TYPE
	 --	SYNTAX      FextOptionEnableDisable
	--	SYNTAX      DisplayString
	--	MAX-ACCESS  read-only
	--	STATUS      current
	--	DESCRIPTION	"Enable/disable this VRRP configuration."
	--	::= {fextInterfaceVRRP 1}

	--fextVRRPVersion OBJECT-TYPE
	--	SYNTAX      DisplayString
	--	MAX-ACCESS  read-only
	--	STATUS      current
	--	DESCRIPTION "VRRP version."
	--	::= {fextInterfaceVRRP 2}

	--fextVRRPIP OBJECT-TYPE
	--	SYNTAX      DisplayString
	--	MAX-ACCESS  read-only
	--	STATUS      current
	--	DESCRIPTION	"IP address of the virtual router."
	--	::= {fextInterfaceVRRP 3}

	--fextVRRPId OBJECT-TYPE
	--	SYNTAX      Integer32 (1..255)
	--	MAX-ACCESS  read-only
	--	STATUS      current
	--	DESCRIPTION	"ID of the virtual router."
	--	::= {fextInterfaceVRRP 4}

	--fextVRRPPriority OBJECT-TYPE
	--	SYNTAX      Integer32 (1..255)
	--	MAX-ACCESS  read-only
	--	STATUS      current
	--	DESCRIPTION	"Priority of the virtual router."
	--	::= {fextInterfaceVRRP 5}

	--fextVRRPADVInterval OBJECT-TYPE
	--	SYNTAX      Integer32 (1..255)
	--	MAX-ACCESS  read-only
	--	STATUS      current
	--	DESCRIPTION	"Advertisement interval."
	--	::= {fextInterfaceVRRP 6}

	--fextVRRPStartTime OBJECT-TYPE
	--	SYNTAX      Integer32 (1..255)
	--	MAX-ACCESS  read-only
	--	STATUS      current
	--	DESCRIPTION	"Startup time."
	--	::= {fextInterfaceVRRP 7}

	--fextVRRPPreempt OBJECT-TYPE
	 --	SYNTAX      FextOptionEnableDisable
	--	SYNTAX      DisplayString
	--	MAX-ACCESS  read-only
	--	STATUS      current
	--	DESCRIPTION	"Enable/disable preempt mode."
	--	::= {fextInterfaceVRRP 8}

	--
	-- fextSystem.fextDHCPServer
	--

	fextDHCPServerEntry OBJECT-TYPE
		SYNTAX      FextDHCPServerEntry
		MAX-ACCESS  not-accessible
		STATUS      current
		DESCRIPTION "An entry containing DHCP Server configuration."
		INDEX       {fextDHCPServerIndex}
		::= {fextDHCPServer 1}

	FextDHCPServerEntry ::= SEQUENCE {
		fextDHCPServerIndex		FnIndex,
		fextDHCPServerName		DisplayString,
	 --	fextDHCPServerStatus	FextOptionEnableDisable,
		fextDHCPServerStatus	DisplayString,
		fextDHCPServerLeaseTime	Integer32,
	 --	fextDHCPServerDNS		FextOptionDHCPServerDNS,
		fextDHCPServerDNS		DisplayString,
	 --	fextDHCPServerNTP		FextOptionDHCPServerNTP,
		fextDHCPServerNTP		DisplayString,
		fextDHCPServerNTP1		DisplayString,
		fextDHCPServerNTP2		DisplayString,
		fextDHCPServerNTP3		DisplayString,
		fextDHCPServerGatewayIP	DisplayString,
		fextDHCPServerNetmask	DisplayString,
		fextDHCPServerInterface	DisplayString,
		fextDHCPServerStartIP	DisplayString,
		fextDHCPServerEndIP		DisplayString,
		fextDHCPServerMTU		Integer32
	}

	fextDHCPServerIndex OBJECT-TYPE
		SYNTAX      FnIndex
		MAX-ACCESS  not-accessible
		STATUS      current
		DESCRIPTION	"An index uniquely defining a DHCP Server within the
					 fextDHCPServer."
		::= {fextDHCPServerEntry 1}

	fextDHCPServerName OBJECT-TYPE
	    SYNTAX      DisplayString
	    MAX-ACCESS  read-only
	    STATUS      current
	    DESCRIPTION "The name of DHCP Server."
	    ::= {fextDHCPServerEntry 2}

	fextDHCPServerStatus OBJECT-TYPE
	 -- SYNTAX      FextOptionEnableDisable
		SYNTAX      DisplayString
	    MAX-ACCESS  read-only
	    STATUS      current
	    DESCRIPTION "Enable/disable this DHCP configuration."
	    ::= {fextDHCPServerEntry 3}

	fextDHCPServerLeaseTime OBJECT-TYPE
	    SYNTAX      Integer32 (300..8640000)
	    MAX-ACCESS  read-only
	    STATUS      current
	    DESCRIPTION "Lease time in seconds."
	    ::= {fextDHCPServerEntry 4}

	fextDHCPServerDNS OBJECT-TYPE
	 -- SYNTAX      FextOptionDHCPServerDNS
		SYNTAX      DisplayString
	    MAX-ACCESS  read-only
	    STATUS      current
	    DESCRIPTION "Options for assigning DNS servers to DHCP clients."
	    ::= {fextDHCPServerEntry 5}

	fextDHCPServerNTP OBJECT-TYPE
	 -- SYNTAX      FextOptionDHCPServerNTP
		SYNTAX      DisplayString
	    MAX-ACCESS  read-only
	    STATUS      current
	    DESCRIPTION "Options for assigning NTP servers to DHCP clients."
	    ::= {fextDHCPServerEntry 6}

	fextDHCPServerNTP1 OBJECT-TYPE
	    SYNTAX      DisplayString
	    MAX-ACCESS  read-only
	    STATUS      current
	    DESCRIPTION "NTP server 1."
	    ::= {fextDHCPServerEntry 7}

	fextDHCPServerNTP2 OBJECT-TYPE
	    SYNTAX      DisplayString
	    MAX-ACCESS  read-only
	    STATUS      current
	    DESCRIPTION "NTP server 2."
	    ::= {fextDHCPServerEntry 8}

	fextDHCPServerNTP3 OBJECT-TYPE
	    SYNTAX      DisplayString
	    MAX-ACCESS  read-only
	    STATUS      current
	    DESCRIPTION "NTP server 3."
	    ::= {fextDHCPServerEntry 9}

	fextDHCPServerGatewayIP OBJECT-TYPE
	    SYNTAX      DisplayString
	    MAX-ACCESS  read-only
	    STATUS      current
	    DESCRIPTION "Default gateway IP address assigned by the DHCP server."
	    ::= {fextDHCPServerEntry 10}

	fextDHCPServerNetmask OBJECT-TYPE
	    SYNTAX      DisplayString
	    MAX-ACCESS  read-only
	    STATUS      current
	    DESCRIPTION "Netmask assigned by the DHCP server."
	    ::= {fextDHCPServerEntry 11}

	fextDHCPServerInterface OBJECT-TYPE
	    SYNTAX      DisplayString
	    MAX-ACCESS  read-only
	    STATUS      current
	    DESCRIPTION "DHCP server can assign IP configurations to clients
					 connected to this interface."
	    ::= {fextDHCPServerEntry 12}

	fextDHCPServerStartIP OBJECT-TYPE
	    SYNTAX      DisplayString
	    MAX-ACCESS  read-only
	    STATUS      current
	    DESCRIPTION "Start of IP range."
	    ::= {fextDHCPServerEntry 13}

	fextDHCPServerEndIP OBJECT-TYPE
	    SYNTAX      DisplayString
	    MAX-ACCESS  read-only
	    STATUS      current
	    DESCRIPTION "End of IP range."
	    ::= {fextDHCPServerEntry 14}

	fextDHCPServerMTU OBJECT-TYPE
	    SYNTAX      Integer32 (512..9000)
	    MAX-ACCESS  read-only
	    STATUS      current
	    DESCRIPTION "Client's MTU."
	    ::= {fextDHCPServerEntry 15}

	--
	-- fextSystem.fextDNS
	--
	-- fextDNSPrimary   ::= {fextDNS 1}
	-- fextDNSSecondary ::= {fextDNS 2}
	-- fextDNSOrder     ::= {fextDSN 3}
	--

	fextDNSPrimary OBJECT-TYPE
	    SYNTAX      DisplayString
	    MAX-ACCESS  read-only
	    STATUS      current
		DESCRIPTION "Primary DNS server IP address."
		::= {fextDNS 1}

	fextDNSSecondary OBJECT-TYPE
	    SYNTAX      DisplayString
	    MAX-ACCESS  read-only
	    STATUS      current
		DESCRIPTION "Secondary DNS server IP address."
		::= {fextDNS 2}

	fextDNSOrder OBJECT-TYPE
	    SYNTAX      DisplayString
	    MAX-ACCESS  read-only
	    STATUS      current
		DESCRIPTION "DNS Search order."
		::= {fextDNS 3}

	--
	-- fextSystem.fextVWANMember
	--

	fextVWANMemberEntry OBJECT-TYPE
		SYNTAX      FextVWANMemberEntry
		MAX-ACCESS  not-accessible
		STATUS      current
		DESCRIPTION "An entry containing virtual VWAN Interface member
					 configuration."
		INDEX       {fextVWANMemberIndex}
		::= {fextVWANMember 1}

	FextVWANMemberEntry ::= SEQUENCE {
		fextVWANMemberIndex                 FnIndex,
		fextVWANMemberName                  DisplayString,
		fextVWANMemberTarget                DisplayString,
		fextVWANMemberPriority              Integer32,
		fextVWANMemberWeight                Integer32,
		fextVWANMemberInThreshold           Integer32,
		fextVWANMemberOutThreshold          Integer32,
		fextVWANMemberAllThreshold          Integer32,
		fextVWANMemberHchk                  DisplayString,
		fextVWANMemberHchkFailThreshold     Integer32,
		fextVWANMemberHchkSuccessThreshold  Integer32
	}

	fextVWANMemberIndex OBJECT-TYPE
		SYNTAX      FnIndex
		MAX-ACCESS  not-accessible
		STATUS      current
		DESCRIPTION	"An index uniquely defining a virtual VWAN Interface member
					 within the fextVWANMember."
		::= {fextVWANMemberEntry 1}

	fextVWANMemberName OBJECT-TYPE
	    SYNTAX      DisplayString
	    MAX-ACCESS  read-only
	    STATUS      current
	    DESCRIPTION "The name of virtual VWAN Interface member."
	    ::= {fextVWANMemberEntry 2}

	fextVWANMemberTarget OBJECT-TYPE
	    SYNTAX      DisplayString
	    MAX-ACCESS  read-only
	    STATUS      current
	    DESCRIPTION "The target forwarding to."
	    ::= {fextVWANMemberEntry 3}

	fextVWANMemberPriority OBJECT-TYPE
	    SYNTAX      Integer32 (1..7)
	    MAX-ACCESS  read-only
	    STATUS      current
	    DESCRIPTION "Priority of this member."
	    ::= {fextVWANMemberEntry 4}

	fextVWANMemberWeight OBJECT-TYPE
	    SYNTAX      Integer32 (1..256)
	    MAX-ACCESS  read-only
	    STATUS      current
	    DESCRIPTION "Weight for this member."
	    ::= {fextVWANMemberEntry 5}

	fextVWANMemberInThreshold OBJECT-TYPE
	    SYNTAX      Integer32 (0..2147483647)
	    MAX-ACCESS  read-only
	    STATUS      current
	    DESCRIPTION "Bandwidth threshold for input traffic in MB."
	    ::= {fextVWANMemberEntry 6}

	fextVWANMemberOutThreshold OBJECT-TYPE
	    SYNTAX      Integer32 (0..2147483647)
	    MAX-ACCESS  read-only
	    STATUS      current
	    DESCRIPTION "Bandwidth threshold for output traffic in MB."
	    ::= {fextVWANMemberEntry 7}

	fextVWANMemberAllThreshold OBJECT-TYPE
	    SYNTAX      Integer32 (0..2147483647)
	    MAX-ACCESS  read-only
	    STATUS      current
	    DESCRIPTION "Bandwidth threshold for total traffic in MB."
	    ::= {fextVWANMemberEntry 8}

	fextVWANMemberHchk OBJECT-TYPE
	    SYNTAX      DisplayString
	    MAX-ACCESS  read-only
	    STATUS      current
	    DESCRIPTION "The link health check of virtual-wan."
	    ::= {fextVWANMemberEntry 9}

	fextVWANMemberHchkFailThreshold OBJECT-TYPE
	    SYNTAX      Integer32 (1..10)
	    MAX-ACCESS  read-only
	    STATUS      current
	    DESCRIPTION "The number of consecutive failed probes before member is considered dead(1 - 10, default = 5)."
	    ::= {fextVWANMemberEntry 10}

	fextVWANMemberHchkSuccessThreshold OBJECT-TYPE
	    SYNTAX      Integer32 (1..10)
	    MAX-ACCESS  read-only
	    STATUS      current
	    DESCRIPTION "The number of consecutive successful probes before member is considered alive(1 - 10, default = 5)."
	    ::= {fextVWANMemberEntry 11}

	--
	-- fextSystem.fextVWANHchk
	--

	fextVWANHchkEntry OBJECT-TYPE
		SYNTAX      FextVWANHchkEntry
		MAX-ACCESS  not-accessible
		STATUS      current
		DESCRIPTION "An entry containing virtual VWAN Interface member
					 configuration."
		INDEX       {fextVWANHchkIndex}
		::= {fextVWANHchk 1}

	FextVWANHchkEntry ::= SEQUENCE {
		fextVWANHchkIndex		    FnIndex,
		fextVWANHchkName		    DisplayString,
		fextVWANHchkProtocol	    DisplayString,
		fextVWANHchkInterval	    Integer32,
		fextVWANHchkProbeCount	    Integer32,
		fextVWANHchkProbeTimeout    Integer32,
		fextVWANHchkProbeTarget     DisplayString,
		fextVWANHchkPort	        Integer32,
		fextVWANHchkHTTPGet         DisplayString,
		fextVWANHchkSourceInterface DisplayString,
		fextVWANHchkFailCount	    Integer32,
		fextVWANHchkRecoveryCount	Integer32
	}

	fextVWANHchkIndex OBJECT-TYPE
		SYNTAX      FnIndex
		MAX-ACCESS  not-accessible
		STATUS      current
		DESCRIPTION	"An index uniquely defining a virtual VWAN Interface member
					 within the fextVWANMember."
		::= {fextVWANHchkEntry 1}

	fextVWANHchkName OBJECT-TYPE
	    SYNTAX      DisplayString
	    MAX-ACCESS  read-only
	    STATUS      current
	    DESCRIPTION "The name of virtual VWAN Interface member."
	    ::= {fextVWANHchkEntry 2}

	fextVWANHchkProtocol OBJECT-TYPE
	 -- SYNTAX      FextOptionHchkProbeProtocol
		SYNTAX      DisplayString
	    MAX-ACCESS  read-only
	    STATUS      current
	    DESCRIPTION "The protocol to use for status check."
	    ::= {fextVWANHchkEntry 3}

	fextVWANHchkInterval OBJECT-TYPE
	    SYNTAX      Integer32 (1..3600)
	    MAX-ACCESS  read-only
	    STATUS      current
	    DESCRIPTION "Monitoring Interval in seconds."
	    ::= {fextVWANHchkEntry 4}

	fextVWANHchkProbeCount OBJECT-TYPE
	    SYNTAX      Integer32 (1..10)
	    MAX-ACCESS  read-only
	    STATUS      current
	    DESCRIPTION "Number of probes sent within an interval."
	    ::= {fextVWANHchkEntry 5}

	fextVWANHchkProbeTimeout OBJECT-TYPE
	    SYNTAX      Integer32 (1..10)
	    MAX-ACCESS  read-only
	    STATUS      current
	    DESCRIPTION "Timeout for a probe in seconds."
	    ::= {fextVWANHchkEntry 6}

	fextVWANHchkProbeTarget OBJECT-TYPE
	    SYNTAX      DisplayString
	    MAX-ACCESS  read-only
	    STATUS      current
	    DESCRIPTION "IPv4 address or FQDN name of the target to which a probe is
					 sent."
	    ::= {fextVWANHchkEntry 7}

	fextVWANHchkPort OBJECT-TYPE
	    SYNTAX      Integer32 (1..10)
	    MAX-ACCESS  read-only
	    STATUS      current
	    DESCRIPTION "Port number used to communicate with the HTTP server."
	    ::= {fextVWANHchkEntry 8}

	fextVWANHchkHTTPGet OBJECT-TYPE
	    SYNTAX      DisplayString
	    MAX-ACCESS  read-only
	    STATUS      current
	    DESCRIPTION "URL used to communicate with the HTTP server."
	    ::= {fextVWANHchkEntry 9}

	fextVWANHchkSourceInterface OBJECT-TYPE
	    SYNTAX      DisplayString
	    MAX-ACCESS  read-only
	    STATUS      current
	    DESCRIPTION "The source address derived from specified interface."
	    ::= {fextVWANHchkEntry 10}

	fextVWANHchkFailCount OBJECT-TYPE
	    SYNTAX      Integer32 (1..10)
	    MAX-ACCESS  read-only
	    STATUS      current
	    DESCRIPTION "Number of failures before probe_target is considered lost."
	    ::= {fextVWANHchkEntry 11}

	fextVWANHchkRecoveryCount OBJECT-TYPE
	    SYNTAX      Integer32 (1..10)
	    MAX-ACCESS  read-only
	    STATUS      current
	    DESCRIPTION "Number of successful responses received before probe_target
					 is considered recovered."
	    ::= {fextVWANHchkEntry 12}

	--
	-- fextSystem.fextSMSNotification
	--
	-- fextSMSNotify   ::= {fextSMSNotification 1}
	-- fextSMSReceiver ::= {fextSMSNotification 2}
	-- fextSMSAlert    ::= {fextSMSNotification 3}
	--

	fextSMSNotify OBJECT-TYPE
	 --	SYNTAX      FextOptionEnableDisable
		SYNTAX      DisplayString
		MAX-ACCESS  read-only
		STATUS      current
		DESCRIPTION "Enable/disable SMS notification."
		::= {fextSMSNotification 1}

	fextSMSReceiver OBJECT-TYPE
		SYNTAX      SEQUENCE OF FextSMSReceiverEntry
		MAX-ACCESS  not-accessible
		STATUS      current
		DESCRIPTION
			"A table of SMS notification receivers' configuration. This table is
			 intended to be extended with platform specific information."
		::= {fextSMSNotification 2}

	fextSMSAlert OBJECT-IDENTITY
		STATUS      current
		DESCRIPTION "Cloud Management setting."
		::= {fextSMSNotification 3}

	--
	-- fextSMSNotification.fextSMSReceiver
	--

	fextSMSReceiverEntry OBJECT-TYPE
		SYNTAX      FextSMSReceiverEntry
		MAX-ACCESS  not-accessible
		STATUS      current
		DESCRIPTION "An entry containing SMS notification receiver's configuration."
		INDEX       {fextSMSReceiverIndex}
		::= {fextSMSReceiver 1}

	FextSMSReceiverEntry ::= SEQUENCE {
		fextSMSReceiverIndex  FnIndex,
		fextSMSReceiverName	  DisplayString,
	 -- fextSMSReceiverRcvr	  FextOptionEnableDisable,
		fextSMSReceiverRcvr	  DisplayString,
		fextSMSReceiverNumber DisplayString,
	 -- fextSMSReceiverAlert  FextOptionSMSAlert
		fextSMSReceiverAlert  DisplayString
	}

	fextSMSReceiverIndex OBJECT-TYPE
		SYNTAX      FnIndex
		MAX-ACCESS  not-accessible
		STATUS      current
		DESCRIPTION	"An index uniquely defining a SMS notification receiver."
		::= {fextSMSReceiverEntry 1}

	fextSMSReceiverName OBJECT-TYPE
	    SYNTAX      DisplayString
	    MAX-ACCESS  read-only
	    STATUS      current
	    DESCRIPTION "The name of SMS notification receiver."
	    ::= {fextSMSReceiverEntry 2}

	fextSMSReceiverRcvr OBJECT-TYPE
	 -- SYNTAX      FextOptionEnableDisable
	    SYNTAX      DisplayString
	    MAX-ACCESS  read-only
	    STATUS      current
	    DESCRIPTION "To enable/disable this receiver."
	    ::= {fextSMSReceiverEntry 3}

	fextSMSReceiverNumber OBJECT-TYPE
	    SYNTAX      DisplayString
	    MAX-ACCESS  read-only
	    STATUS      current
	    DESCRIPTION "The phone number of SMS notification receiver,
					 format: +(country code)(phone number)."
	    ::= {fextSMSReceiverEntry 4}

	fextSMSReceiverAlert OBJECT-TYPE
	 -- SYNTAX      FextOptionSMSAlert
	    SYNTAX      DisplayString
	    MAX-ACCESS  read-only
	    STATUS      current
	    DESCRIPTION "The name of SMS notification receiver."
	    ::= {fextSMSReceiverEntry 5}

	--
	-- fextSMSNotification.fextSMSAlert
	--
	-- fextSMSAlertSystemReboot   ::= {fextSMSAlert 1}
	-- fextSMSAlertLTEDataExhaust ::= {fextSMSAlert 2}
	-- fextSMSAlertLTEDisconnect  ::= {fextSMSAlert 3}
	-- fextSMSAlertLTEWeakSignal  ::= {fextSMSAlert 4}
	-- fextSMSAlertOSFallback     ::= {fextSMSAlert 5}
	-- fextSMSAlertNetworkMode    ::= {fextSMSAlert 6}
	-- fextSMSAlertBackupMode     ::= {fextSMSAlert 7}
	--

	fextSMSAlertSystemReboot OBJECT-TYPE
	    SYNTAX      DisplayString
	    MAX-ACCESS  read-only
	    STATUS      current
	    DESCRIPTION "The system is rebooting."
	    ::= {fextSMSAlert 1}

	fextSMSAlertLTEDataExhaust OBJECT-TYPE
	    SYNTAX      DisplayString
	    MAX-ACCESS  read-only
	    STATUS      current
	    DESCRIPTION "The LTE data plan is exhausted."
	    ::= {fextSMSAlert 2}

	fextSMSAlertLTEDisconnect OBJECT-TYPE
	    SYNTAX      DisplayString
	    MAX-ACCESS  read-only
	    STATUS      current
	    DESCRIPTION "The LTE data session is disconnected."
	    ::= {fextSMSAlert 3}

	fextSMSAlertLTEWeakSignal OBJECT-TYPE
	    SYNTAX      DisplayString
	    MAX-ACCESS  read-only
	    STATUS      current
	    DESCRIPTION "The LTE signal strength is too low."
	    ::= {fextSMSAlert 4}

	fextSMSAlertOSFallback OBJECT-TYPE
	    SYNTAX      DisplayString
	    MAX-ACCESS  read-only
	    STATUS      current
	    DESCRIPTION "The system start to fallback OS image."
	    ::= {fextSMSAlert 5}

	fextSMSAlertNetworkMode OBJECT-TYPE
	    SYNTAX      DisplayString
	    MAX-ACCESS  read-only
	    STATUS      current
	    DESCRIPTION "The system networking mode changed."
	    ::= {fextSMSAlert 6}

	fextSMSAlertBackupMode OBJECT-TYPE
	    SYNTAX      DisplayString
	    MAX-ACCESS  read-only
	    STATUS      current
	    DESCRIPTION "The FortiGate backup mode changed."
	    ::= {fextSMSAlert 7}

	--
	-- fextSystem.fextSMSRemoteDiag
	--
	-- fextSMSDiag ::= {fextSMSRemoteDiag 1}
	-- fextSMSUser ::= {fextSMSRemoteDiag 2}
	--

	fextSMSDiag OBJECT-TYPE
	 -- SYNTAX      FextOptionEnableDisable
	    SYNTAX      DisplayString
		MAX-ACCESS  read-only
		STATUS      current
		DESCRIPTION "Enable/disable SMS remote diagnose."
		::= {fextSMSRemoteDiag 1}

	fextSMSUser OBJECT-TYPE
		SYNTAX      SEQUENCE OF FextSMSUserEntry
		MAX-ACCESS  not-accessible
		STATUS      current
		DESCRIPTION	"A table of allowed users to SMS remote diagnose. This table
					 is intended to be extended with platform specific information."
		::= {fextSMSRemoteDiag 2}

	--
	-- fextSMSRemoteDiag.fextSMSUser
	--

	fextSMSUserEntry OBJECT-TYPE
		SYNTAX      FextSMSUserEntry
		MAX-ACCESS  not-accessible
		STATUS      current
		DESCRIPTION "An entry containing SMS remote diagnose user."
		INDEX       {fextSMSUserIndex}
		::= {fextSMSUser 1}

	FextSMSUserEntry ::= SEQUENCE {
		fextSMSUserIndex   FnIndex,
		fextSMSUserName	   DisplayString,
	 -- fextSMSUserSender  FextOptionEnableDisable,
		fextSMSUserSender  DisplayString,
		fextSMSUserNumber  DisplayString,
	 -- fextSMSUserCommand FextOptionSMSCommand
		fextSMSUserCommand DisplayString
	}

	fextSMSUserIndex OBJECT-TYPE
		SYNTAX      FnIndex
		MAX-ACCESS  not-accessible
		STATUS      current
		DESCRIPTION	"An index uniquely defining a SMS remote diagnose user."
		::= {fextSMSUserEntry 1}

	fextSMSUserName OBJECT-TYPE
	    SYNTAX      DisplayString
	    MAX-ACCESS  read-only
	    STATUS      current
	    DESCRIPTION "The name of SMS remote diagnose user."
	    ::= {fextSMSUserEntry 2}

	fextSMSUserSender OBJECT-TYPE
	 -- SYNTAX      FextOptionEnableDisable
	    SYNTAX      DisplayString
	    MAX-ACCESS  read-only
	    STATUS      current
	    DESCRIPTION "To enable/disable this user."
	    ::= {fextSMSUserEntry 3}

	fextSMSUserNumber OBJECT-TYPE
	    SYNTAX      DisplayString
	    MAX-ACCESS  read-only
	    STATUS      current
	    DESCRIPTION "The phone number of SMS remote diagnose user,
					 format: +(country code)(phone number)."
	    ::= {fextSMSUserEntry 4}

	fextSMSUserCommand OBJECT-TYPE
	 -- SYNTAX      FextOptionSMSCommand
	    SYNTAX      DisplayString
	    MAX-ACCESS  read-only
	    STATUS      current
	    DESCRIPTION "The name of SMS remote diagnose user."
	    ::= {fextSMSUserEntry 5}

	--
	-- fextSystem.fextSysLog
	--
	-- fextSysLogRemoteIP   ::= {fextSysLog 1}
	-- fextSysLogRemotePort ::= {fextSysLog 2}
	--

	fextSysLogRemoteIP OBJECT-TYPE
	    SYNTAX      DisplayString
	    MAX-ACCESS  read-only
	    STATUS      current
	    DESCRIPTION "Remote Syslog server IP address."
	    ::= {fextSysLog 1}

	fextSysLogRemotePort OBJECT-TYPE
		SYNTAX      Integer32 (1..65535)
		MAX-ACCESS  read-only
		STATUS      current
		DESCRIPTION	"Remote Syslog server port."
		::= {fextSysLog 2}

	fextSysLogStatReport  OBJECT-IDENTITY
		STATUS      current
		DESCRIPTION	"Syslog statistic report setting."
		::= {fextSysLog 3}

	--
	-- fextSysLog.fextSysLogStatReport
	--

	fextSysLogStatRptStatus OBJECT-TYPE
	    SYNTAX      DisplayString
	    MAX-ACCESS  read-only
	    STATUS      current
	    DESCRIPTION "Syslog system status report function switch option."
	    ::= {fextSysLogStatReport 1}

	fextSysLogStatRptItv OBJECT-TYPE
		SYNTAX      Integer32 (1..3600)
		MAX-ACCESS  read-only
		STATUS      current
		DESCRIPTION	"The time interval for system status report(1-3600 sec)."
		::= {fextSysLogStatReport 2}

	fextSysLogStatRptCPUUsage OBJECT-IDENTITY
		STATUS      current
		DESCRIPTION	"cpu usage rate statistic report configurations."
		::= {fextSysLogStatReport 3}

	fextSysLogStatRptMemUsage OBJECT-IDENTITY
		STATUS      current
		DESCRIPTION	"memory usage rate statistic report configurations."
		::= {fextSysLogStatReport 4}

	fextSysLogStatRptCPUTemp OBJECT-IDENTITY
		STATUS      current
		DESCRIPTION	"cpu temperature statistic report configurations."
		::= {fextSysLogStatReport 5}

	--
	-- fextSysLogStatReport.fextSysLogStatRptCPUUsage
	--

	fextSysLogStatRptCPUUsageThrsd OBJECT-TYPE
	    SYNTAX      Integer32 (0..100)
	    MAX-ACCESS  read-only
	    STATUS      current
	    DESCRIPTION "The percentage rate of CPU usage threshold for system abnormal event report, 0 means disabled."
	    ::= {fextSysLogStatRptCPUUsage 1}

	fextSysLogStatRptCPUUsageVariance OBJECT-TYPE
		SYNTAX      Integer32 (0..100)
		MAX-ACCESS  read-only
		STATUS      current
		DESCRIPTION	"The variance for the report of CPU usage when exceed the threshold, 0 means report all the time."
		::= {fextSysLogStatRptCPUUsage 2}

	--
	-- fextSysLogStatReport.fextSysLogStatRptMemUsage
	--

	fextSysLogStatRptMemUsageThrsd OBJECT-TYPE
	    SYNTAX      Integer32 (0..100)
	    MAX-ACCESS  read-only
	    STATUS      current
	    DESCRIPTION "The percentage rate of memory usage threshold for system abnormal event report, 0 means disabled."
	    ::= {fextSysLogStatRptMemUsage 1}

	fextSysLogStatRptMemUsageVariance OBJECT-TYPE
		SYNTAX      Integer32 (0..100)
		MAX-ACCESS  read-only
		STATUS      current
		DESCRIPTION	"The variance for the report of memory usage when exceed the threshold, 0 means report all the time."
		::= {fextSysLogStatRptMemUsage 2}

	--
	-- fextSysLogStatReport.fextSysLogStatRptCPUTemp
	--

	fextSysLogStatRptCPUTempThrsd OBJECT-TYPE
	    SYNTAX      Integer32 (0..120)
	    MAX-ACCESS  read-only
	    STATUS      current
	    DESCRIPTION "The cpu temperature threshold for system abnormal event report, 0 means disabled."
	    ::= {fextSysLogStatRptCPUTemp 1}

	fextSysLogStatRptCPUTempVariance OBJECT-TYPE
		SYNTAX      Integer32 (0..120)
		MAX-ACCESS  read-only
		STATUS      current
		DESCRIPTION	"The variance for the report of cpu temperature when exceed the threshold, 0 means report all the time."
		::= {fextSysLogStatRptCPUTemp 2}

	--
	-- fextSystem.fextLANSwitch
	--
	-- fextLANSwitchPort ::= {fextLANSwitch 1}
	--

	fextLANSwitchPort OBJECT-TYPE
		SYNTAX      SEQUENCE OF FextLANSwitchPortEntry
		MAX-ACCESS  not-accessible
		STATUS      current
		DESCRIPTION	"A table of LAN Switch ports. This table is intended to be
					 extended with platform specific information."
		::= {fextLANSwitch 1}

	--
	-- fextLANSwitch.fextLANSwitchPort
	--

	fextLANSwitchPortEntry OBJECT-TYPE
		SYNTAX      FextLANSwitchPortEntry
		MAX-ACCESS  not-accessible
		STATUS      current
		DESCRIPTION "An entry containing LAN Switch port."
		INDEX       {fextLANSwitchPortIndex}
		::= {fextLANSwitchPort 1}

	FextLANSwitchPortEntry ::= SEQUENCE {
		fextLANSwitchPortIndex FnIndex,
		fextLANSwitchPortName  DisplayString
	}

	fextLANSwitchPortIndex OBJECT-TYPE
		SYNTAX      FnIndex
		MAX-ACCESS  not-accessible
		STATUS      current
		DESCRIPTION	"An index uniquely defining a LAN Switch port."
		::= {fextLANSwitchPortEntry 1}

	fextLANSwitchPortName OBJECT-TYPE
	    SYNTAX      DisplayString
	    MAX-ACCESS  read-only
	    STATUS      current
	    DESCRIPTION "The name of LAN Switch port."
	    ::= {fextLANSwitchPortEntry 2}

	--
	-- fextSystem.fextVirtualWirePair
	--
	-- fextLTE1Mapping ::= {fextVirtualWirePair 1}
	-- fextLTE2Mapping ::= {fextVirtualWirePair 2}
	--

	fextLTE1Mapping OBJECT-TYPE
	    SYNTAX      DisplayString
	    MAX-ACCESS  read-only
	    STATUS      current
		DESCRIPTION "LTE1 interface's LAN interface mapping."
		::= {fextVirtualWirePair 1}

	fextLTE2Mapping OBJECT-TYPE
	    SYNTAX      DisplayString
	    MAX-ACCESS  read-only
	    STATUS      current
		DESCRIPTION "LTE2 interface's LAN interface mapping."
		::= {fextVirtualWirePair 2}

	--
	-- fnFortiExtenderMib.fextLTE
	--
	-- fextLTESetting ::= {fextLTE 1}
	-- fextLTECarrier ::= {fextLTE 2}
	-- fextLTESIMMap  ::= {fextLTE 3}
	-- fextLTEPlan    ::= {fextLTE 4}
	--

	fextLTESetting OBJECT-IDENTITY
		STATUS      current
		DESCRIPTION	"LTE modem setup."
		::= {fextLTE 1}

	fextLTECarrier OBJECT-TYPE
		SYNTAX      SEQUENCE OF FextLTECarrierEntry
		MAX-ACCESS  read-only
		STATUS      current
		DESCRIPTION "LTE Carrier configuration."
		::= {fextLTE 2}

	fextLTESIMMap OBJECT-TYPE
		SYNTAX      SEQUENCE OF FextLTESIMMapEntry
		MAX-ACCESS  not-accessible
		STATUS      current
		DESCRIPTION	"LTE SIM card mapping information."
		::= {fextLTE 3}

	fextLTEPlan OBJECT-TYPE
		SYNTAX      SEQUENCE OF FextLTEPlanEntry
		MAX-ACCESS  not-accessible
		STATUS      current
		DESCRIPTION	"LTE SIM card configuration."
		::= {fextLTE 4}

	--
	-- fextLTE.fextLTESetting
	--
	-- fextLTEReport ::= {fextLTESetting 1}
	-- fextLTEModem1 ::= {fextLTESetting 2}
	-- fextLTEModem2 ::= {fextLTESetting 3}
	--

	fextLTEReport OBJECT-IDENTITY
		STATUS      current
		DESCRIPTION	"The reporting setting to controller."
		::= {fextLTESetting 1}

	fextLTEModem1 OBJECT-IDENTITY
		STATUS      current
		DESCRIPTION	"The LTE Modem 1 operational setting."
		::= {fextLTESetting 2}

	fextLTEModem2 OBJECT-IDENTITY
		STATUS      current
		DESCRIPTION	"The LTE Modem 2 operational setting."
		::= {fextLTESetting 3}

	--
	-- fextLTESetting.fextLTEReport
	--
	-- fextLTEReportStatus          ::= {fextLTEReport 1}
	-- fextLTEReportInterval        ::= {fextLTEReport 2}
	-- fextLTEReportSignalThreshold ::= {fextLTEReport 3}
	--

	fextLTEReportStatus OBJECT-TYPE
	    SYNTAX      DisplayString
	    MAX-ACCESS  read-only
	    STATUS      current
		DESCRIPTION "Enable/disable the periodical report to controller."
		::= {fextLTEReport 1}

	fextLTEReportInterval OBJECT-TYPE
	    SYNTAX      DisplayString
	    MAX-ACCESS  read-only
	    STATUS      current
		DESCRIPTION "The reporting interval (30 - 86400 seconds)."
		::= {fextLTEReport 2}

	fextLTEReportSignalThreshold OBJECT-TYPE
	    SYNTAX      DisplayString
	    MAX-ACCESS  read-only
	    STATUS      current
		DESCRIPTION "The RSSI signal level threshold to notify controller."
		::= {fextLTEReport 3}

	--
	-- fextLTESetting.fextLTEModem1
	--
	-- fextModem1CertMode         ::= {fextLTEModem1 1}
	-- fextModem1DefaultSIM       ::= {fextLTEModem1 2}
	-- fextModem1PreferredCarrier ::= {fextLTEModem1 3}
	-- fextModem1GPS              ::= {fextLTEModem1 4}
	-- fextModem1SIM1Pin          ::= {fextLTEModem1 5}
	-- fextModem1SIM1PinCode      ::= {fextLTEModem1 6}
	-- fextModem1SIM2Pin          ::= {fextLTEModem1 7}
	-- fextModem1SIM2PinCode      ::= {fextLTEModem1 8}
	-- fextModem1AutoSwitch       ::= {fextLTEModem1 9}
	--

	fextModem1CertMode OBJECT-TYPE
	    SYNTAX      DisplayString
	    MAX-ACCESS  read-only
	    STATUS      current
		DESCRIPTION "Enable/disable the certification."
		::= {fextLTEModem1 1}

	fextModem1DefaultSIM OBJECT-TYPE
	    SYNTAX      DisplayString
	    MAX-ACCESS  read-only
	    STATUS      current
		DESCRIPTION "Preferred SIM slot setting."
		::= {fextLTEModem1 2}

	fextModem1PreferredCarrier OBJECT-TYPE
	    SYNTAX      DisplayString
	    MAX-ACCESS  read-only
	    STATUS      current
		DESCRIPTION "Preferred Carrier setting."
		::= {fextLTEModem1 3}

	fextModem1GPS OBJECT-TYPE
	    SYNTAX      DisplayString
	    MAX-ACCESS  read-only
	    STATUS      current
		DESCRIPTION "Enable/disable GPS support."
		::= {fextLTEModem1 4}

	fextModem1SIM1Pin OBJECT-TYPE
	    SYNTAX      DisplayString
	    MAX-ACCESS  read-only
	    STATUS      current
		DESCRIPTION "Enable/disable SIM1 pin code support."
		::= {fextLTEModem1 5}

	fextModem1SIM1PinCode OBJECT-TYPE
	    SYNTAX      DisplayString
	    MAX-ACCESS  read-only
	    STATUS      current
		DESCRIPTION "SIM1 pin code."
		::= {fextLTEModem1 6}

	fextModem1SIM2Pin OBJECT-TYPE
	    SYNTAX      DisplayString
	    MAX-ACCESS  read-only
	    STATUS      current
		DESCRIPTION "Enable/disable SIM2 pin code support."
		::= {fextLTEModem1 7}

	fextModem1SIM2PinCode OBJECT-TYPE
	    SYNTAX      DisplayString
	    MAX-ACCESS  read-only
	    STATUS      current
		DESCRIPTION "SIM2 pin code."
		::= {fextLTEModem1 8}

	fextModem1AutoSwitch OBJECT-IDENTITY
	    STATUS      current
		DESCRIPTION "The configuration to switching SIM card."
		::= {fextLTEModem1 9}

	--
	-- fextLTEModem1.fextModem1AutoSwitch
	--
	-- fextModem1SwitchByDisconnect        ::= {fextModem1AutoSwitch 1}
	-- fextModem1SwitchBySignal            ::= {fextModem1AutoSwitch 2}
	-- fextModem1SwitchByPlan              ::= {fextModem1AutoSwitch 3}
	-- fextModem1SwitchDisconnectThreshold ::= {fextModem1AutoSwitch 4}
	-- fextModem1SwitchDisconnectPeriod    ::= {fextModem1AutoSwitch 5}
	-- fextModem1SwitchBack                ::= {fextModem1AutoSwitch 6}
	-- fextModem1SwitchBackTime            ::= {fextModem1AutoSwitch 7}
	-- fextModem1SwitchBackTimer           ::= {fextModem1AutoSwitch 8}
	--

	fextModem1SwitchByDisconnect OBJECT-TYPE
	    SYNTAX      DisplayString
	    MAX-ACCESS  read-only
	    STATUS      current
		DESCRIPTION "Switching SIM card due to disconnection."
		::= {fextModem1AutoSwitch 1}

	fextModem1SwitchBySignal OBJECT-TYPE
	    SYNTAX      DisplayString
	    MAX-ACCESS  read-only
	    STATUS      current
		DESCRIPTION "Switching SIM card due to bad signal."
		::= {fextModem1AutoSwitch 2}

	fextModem1SwitchByPlan OBJECT-TYPE
	    SYNTAX      DisplayString
	    MAX-ACCESS  read-only
	    STATUS      current
		DESCRIPTION "Switching SIM card due to data plan."
		::= {fextModem1AutoSwitch 3}

	fextModem1SwitchDisconnectThreshold OBJECT-TYPE
	    SYNTAX      DisplayString
	    MAX-ACCESS  read-only
	    STATUS      current
		DESCRIPTION "Number of disconnects for SIM switch."
		::= {fextModem1AutoSwitch 4}

	fextModem1SwitchDisconnectPeriod OBJECT-TYPE
	    SYNTAX      DisplayString
	    MAX-ACCESS  read-only
	    STATUS      current
		DESCRIPTION "Evaluation period in seconds for SIM switch."
		::= {fextModem1AutoSwitch 5}

	fextModem1SwitchBack OBJECT-TYPE
	    SYNTAX      DisplayString
	    MAX-ACCESS  read-only
	    STATUS      current
		DESCRIPTION "Enable/disable switching back to preferred SIM card."
		::= {fextModem1AutoSwitch 6}

	fextModem1SwitchBackTime OBJECT-TYPE
	    SYNTAX      DisplayString
	    MAX-ACCESS  read-only
	    STATUS      current
		DESCRIPTION "Switching back to preferred SIM card at a specific time."
		::= {fextModem1AutoSwitch 7}

	fextModem1SwitchBackTimer OBJECT-TYPE
	    SYNTAX      DisplayString
	    MAX-ACCESS  read-only
	    STATUS      current
		DESCRIPTION "Switching back to preferred SIM card after the given time."
		::= {fextModem1AutoSwitch 8}

	--
	-- fextLTESetting.fextLTEModem2
	--
	-- fextModem2CertMode         ::= {fextLTEModem2 1}
	-- fextModem2DefaultSIM       ::= {fextLTEModem2 2}
	-- fextModem2PreferredCarrier ::= {fextLTEModem2 3}
	-- fextModem2GPS              ::= {fextLTEModem2 4}
	-- fextModem2SIM1Pin          ::= {fextLTEModem2 5}
	-- fextModem2SIM1PinCode      ::= {fextLTEModem2 6}
	-- fextModem2SIM2Pin          ::= {fextLTEModem2 7}
	-- fextModem2SIM2PinCode      ::= {fextLTEModem2 8}
	-- fextModem2AutoSwitch       ::= {fextLTEModem2 9}
	--

	fextModem2CertMode OBJECT-TYPE
	    SYNTAX      DisplayString
	    MAX-ACCESS  read-only
	    STATUS      current
		DESCRIPTION "Enable/disable the certification."
		::= {fextLTEModem2 1}

	fextModem2DefaultSIM OBJECT-TYPE
	    SYNTAX      DisplayString
	    MAX-ACCESS  read-only
	    STATUS      current
		DESCRIPTION "Preferred SIM slot setting."
		::= {fextLTEModem2 2}

	fextModem2PreferredCarrier OBJECT-TYPE
	    SYNTAX      DisplayString
	    MAX-ACCESS  read-only
	    STATUS      current
		DESCRIPTION "Preferred Carrier setting."
		::= {fextLTEModem2 3}

	fextModem2GPS OBJECT-TYPE
	    SYNTAX      DisplayString
	    MAX-ACCESS  read-only
	    STATUS      current
		DESCRIPTION "Enable/disable GPS support."
		::= {fextLTEModem2 4}

	fextModem2SIM1Pin OBJECT-TYPE
	    SYNTAX      DisplayString
	    MAX-ACCESS  read-only
	    STATUS      current
		DESCRIPTION "Enable/disable SIM1 pin code support."
		::= {fextLTEModem2 5}

	fextModem2SIM1PinCode OBJECT-TYPE
	    SYNTAX      DisplayString
	    MAX-ACCESS  read-only
	    STATUS      current
		DESCRIPTION "SIM1 pin code."
		::= {fextLTEModem2 6}

	fextModem2SIM2Pin OBJECT-TYPE
	    SYNTAX      DisplayString
	    MAX-ACCESS  read-only
	    STATUS      current
		DESCRIPTION "Enable/disable SIM2 pin code support."
		::= {fextLTEModem2 7}

	fextModem2SIM2PinCode OBJECT-TYPE
	    SYNTAX      DisplayString
	    MAX-ACCESS  read-only
	    STATUS      current
		DESCRIPTION "SIM2 pin code."
		::= {fextLTEModem2 8}

	fextModem2AutoSwitch OBJECT-IDENTITY
	    STATUS      current
		DESCRIPTION "The configuration to switching SIM card."
		::= {fextLTEModem2 9}

	--
	-- fextLTEModem2.fextModem2AutoSwitch
	--
	-- fextModem2SwitchByDisconnect        ::= {fextModem2AutoSwitch 1}
	-- fextModem2SwitchBySignal            ::= {fextModem2AutoSwitch 2}
	-- fextModem2SwitchByPlan              ::= {fextModem2AutoSwitch 3}
	-- fextModem2SwitchDisconnectThreshold ::= {fextModem2AutoSwitch 4}
	-- fextModem2SwitchDisconnectPeriod    ::= {fextModem2AutoSwitch 5}
	-- fextModem2SwitchBack                ::= {fextModem2AutoSwitch 6}
	-- fextModem2SwitchBackByTime          ::= {fextModem2AutoSwitch 7}
	-- fextModem2SwitchBackByTimer         ::= {fextModem2AutoSwitch 8}
	--

	fextModem2SwitchByDisconnect OBJECT-TYPE
	    SYNTAX      DisplayString
	    MAX-ACCESS  read-only
	    STATUS      current
		DESCRIPTION "Switching SIM card due to disconnection."
		::= {fextModem2AutoSwitch 1}

	fextModem2SwitchBySignal OBJECT-TYPE
	    SYNTAX      DisplayString
	    MAX-ACCESS  read-only
	    STATUS      current
		DESCRIPTION "Switching SIM card due to bad signal."
		::= {fextModem2AutoSwitch 2}

	fextModem2SwitchByPlan OBJECT-TYPE
	    SYNTAX      DisplayString
	    MAX-ACCESS  read-only
	    STATUS      current
		DESCRIPTION "Switching SIM card due to data plan."
		::= {fextModem2AutoSwitch 3}

	fextModem2SwitchDisconnectThreshold OBJECT-TYPE
	    SYNTAX      DisplayString
	    MAX-ACCESS  read-only
	    STATUS      current
		DESCRIPTION "Number of disconnects for SIM switch."
		::= {fextModem2AutoSwitch 4}

	fextModem2SwitchDisconnectPeriod OBJECT-TYPE
	    SYNTAX      DisplayString
	    MAX-ACCESS  read-only
	    STATUS      current
		DESCRIPTION "Evaluation period in seconds for SIM switch."
		::= {fextModem2AutoSwitch 5}

	fextModem2SwitchBack OBJECT-TYPE
	    SYNTAX      DisplayString
	    MAX-ACCESS  read-only
	    STATUS      current
		DESCRIPTION "Enable/disable switching back to preferred SIM card."
		::= {fextModem2AutoSwitch 6}

	fextModem2SwitchBackByTime OBJECT-TYPE
	    SYNTAX      DisplayString
	    MAX-ACCESS  read-only
	    STATUS      current
		DESCRIPTION "Switching back to preferred SIM card at a specific time."
		::= {fextModem2AutoSwitch 7}

	fextModem2SwitchBackByTimer OBJECT-TYPE
	    SYNTAX      DisplayString
	    MAX-ACCESS  read-only
	    STATUS      current
		DESCRIPTION "Switching back to preferred SIM card after the given time."
		::= {fextModem2AutoSwitch 8}

	--
	-- fextLTE.fextLTECarrier
	--

	fextLTECarrierEntry OBJECT-TYPE
		SYNTAX      FextLTECarrierEntry
		MAX-ACCESS  not-accessible
		STATUS      current
		DESCRIPTION "An entry containing LTE Carrier information."
		INDEX       {fextLTECarrierIndex}
		::= {fextLTECarrier 1}

	FextLTECarrierEntry ::= SEQUENCE {
		fextLTECarrierIndex    FnIndex,
		fextLTECarrierName     DisplayString,
		fextLTECarrierFirmware DisplayString,
		fextLTECarrierPRI      DisplayString
	}

	fextLTECarrierIndex OBJECT-TYPE
		SYNTAX      FnIndex
		MAX-ACCESS  not-accessible
		STATUS      current
		DESCRIPTION	"An index uniquely defining a LTE Carrier."
		::= {fextLTECarrierEntry 1}

	fextLTECarrierName OBJECT-TYPE
	    SYNTAX      DisplayString
	    MAX-ACCESS  read-only
	    STATUS      current
	    DESCRIPTION "Name of the LTE Carrier."
	    ::= {fextLTECarrierEntry 2}

	fextLTECarrierFirmware OBJECT-TYPE
	    SYNTAX      DisplayString
	    MAX-ACCESS  read-only
	    STATUS      current
	    DESCRIPTION "Modem Firmware to run with this LTE Carrier."
	    ::= {fextLTECarrierEntry 3}

	fextLTECarrierPRI OBJECT-TYPE
	    SYNTAX      DisplayString
	    MAX-ACCESS  read-only
	    STATUS      current
	    DESCRIPTION "Modem PRI to run with this LTE Carrier."
	    ::= {fextLTECarrierEntry 4}

	--
	-- fextLTE.fextLTESIMMap
	--

	fextLTESIMMapEntry OBJECT-TYPE
		SYNTAX      FextLTESIMMapEntry
		MAX-ACCESS  not-accessible
		STATUS      current
		DESCRIPTION "An entry containing LTE SIM mapping information."
		INDEX       {fextLTESIMMapIndex}
		::= {fextLTESIMMap 1}

	FextLTESIMMapEntry ::= SEQUENCE {
		fextLTESIMMapIndex   FnIndex,
		fextLTESIMMapName    DisplayString,
		fextLTESIMMapMCC     DisplayString,
		fextLTESIMMapMNC     DisplayString,
		fextLTESIMMapCarrier DisplayString
	}

	fextLTESIMMapIndex OBJECT-TYPE
		SYNTAX      FnIndex
		MAX-ACCESS  not-accessible
		STATUS      current
		DESCRIPTION	"An index uniquely defining a LTE SIM mapping."
		::= {fextLTESIMMapEntry 1}

	fextLTESIMMapName OBJECT-TYPE
	    SYNTAX      DisplayString
	    MAX-ACCESS  read-only
	    STATUS      current
	    DESCRIPTION "Name of the LTE SIM mapping."
	    ::= {fextLTESIMMapEntry 2}

	fextLTESIMMapMCC OBJECT-TYPE
	    SYNTAX      DisplayString
	    MAX-ACCESS  read-only
	    STATUS      current
	    DESCRIPTION "MCC of the LTE SIM mapping."
	    ::= {fextLTESIMMapEntry 3}

	fextLTESIMMapMNC OBJECT-TYPE
	    SYNTAX      DisplayString
	    MAX-ACCESS  read-only
	    STATUS      current
	    DESCRIPTION "MNC of the LTE SIM mapping."
	    ::= {fextLTESIMMapEntry 4}

	fextLTESIMMapCarrier OBJECT-TYPE
	    SYNTAX      DisplayString
	    MAX-ACCESS  read-only
	    STATUS      current
	    DESCRIPTION "Carrier of the LTE SIM mapping."
	    ::= {fextLTESIMMapEntry 5}

	--
	-- fextLTE.fextLTEPlan
	--

	fextLTEPlanEntry OBJECT-TYPE
		SYNTAX      FextLTEPlanEntry
		MAX-ACCESS  not-accessible
		STATUS      current
		DESCRIPTION "An entry containing LTE Plan information."
		INDEX       {fextLTEPlanIndex}
		::= {fextLTEPlan 1}

	FextLTEPlanEntry ::= SEQUENCE {
		fextLTEPlanIndex           FnIndex,
		fextLTEPlanName            DisplayString,
		fextLTEPlanModem           DisplayString,
		fextLTEPlanType            DisplayString,
		fextLTEPlanICCID           DisplayString,
		fextLTEPlanCarrier         DisplayString,
		fextLTEPlanSlot            DisplayString,
		fextLTEPlanAPN             DisplayString,
		fextLTEPlanAuth            DisplayString,
		fextLTEPlanUser            DisplayString,
		fextLTEPlanPWD             DisplayString,
		fextLTEPlanPDN             DisplayString,
		fextLTEPlanSignalThreshold DisplayString,
		fextLTEPlanSignalPeriod    DisplayString,
		fextLTEPlanCapacity        DisplayString,
		fextLTEPlanMonthlyFee      DisplayString,
		fextLTEPlanBillingDate     DisplayString,
		fextLTEPlanOverage         DisplayString,
		fextLTEPlanPreferredSubnet DisplayString,
		fextLTEPlanPrivateSubnet   DisplayString
	}

	fextLTEPlanIndex OBJECT-TYPE
		SYNTAX      FnIndex
		MAX-ACCESS  not-accessible
		STATUS      current
		DESCRIPTION	"An index uniquely defining a LTE Plan."
		::= {fextLTEPlanEntry 1}

	fextLTEPlanName OBJECT-TYPE
	    SYNTAX      DisplayString
	    MAX-ACCESS  read-only
	    STATUS      current
	    DESCRIPTION "Name of the LTE Plan."
	    ::= {fextLTEPlanEntry 2}

	fextLTEPlanModem OBJECT-TYPE
	    SYNTAX      DisplayString
	    MAX-ACCESS  read-only
	    STATUS      current
	    DESCRIPTION "LTE Modem to be used."
	    ::= {fextLTEPlanEntry 3}

	fextLTEPlanType OBJECT-TYPE
	    SYNTAX      DisplayString
	    MAX-ACCESS  read-only
	    STATUS      current
	    DESCRIPTION "Method to activate this LTE Plan."
	    ::= {fextLTEPlanEntry 4}

	fextLTEPlanICCID OBJECT-TYPE
	    SYNTAX      DisplayString
	    MAX-ACCESS  read-only
	    STATUS      current
	    DESCRIPTION "SIM card ICCID."
	    ::= {fextLTEPlanEntry 5}

	fextLTEPlanCarrier OBJECT-TYPE
	    SYNTAX      DisplayString
	    MAX-ACCESS  read-only
	    STATUS      current
	    DESCRIPTION "LTE Carrier."
	    ::= {fextLTEPlanEntry 6}

	fextLTEPlanSlot OBJECT-TYPE
	    SYNTAX      DisplayString
	    MAX-ACCESS  read-only
	    STATUS      current
	    DESCRIPTION "Modem Slot."
	    ::= {fextLTEPlanEntry 7}

	fextLTEPlanAPN OBJECT-TYPE
	    SYNTAX      DisplayString
	    MAX-ACCESS  read-only
	    STATUS      current
	    DESCRIPTION "LTE Carrier APN."
	    ::= {fextLTEPlanEntry 8}

	fextLTEPlanAuth OBJECT-TYPE
	    SYNTAX      DisplayString
	    MAX-ACCESS  read-only
	    STATUS      current
	    DESCRIPTION "Authorization mode."
	    ::= {fextLTEPlanEntry 9}

	fextLTEPlanUser OBJECT-TYPE
	    SYNTAX      DisplayString
	    MAX-ACCESS  read-only
	    STATUS      current
	    DESCRIPTION "User name."
	    ::= {fextLTEPlanEntry 10}

	fextLTEPlanPWD OBJECT-TYPE
	    SYNTAX      DisplayString
	    MAX-ACCESS  read-only
	    STATUS      current
	    DESCRIPTION "Password."
	    ::= {fextLTEPlanEntry 11}

	fextLTEPlanPDN OBJECT-TYPE
	    SYNTAX      DisplayString
	    MAX-ACCESS  read-only
	    STATUS      current
	    DESCRIPTION "Packet Data Network (PDN) IP address family."
	    ::= {fextLTEPlanEntry 12}

	fextLTEPlanSignalThreshold OBJECT-TYPE
	    SYNTAX      DisplayString
	    MAX-ACCESS  read-only
	    STATUS      current
	    DESCRIPTION "Signal level threshold (-100 ~ -50) to switch SIM card."
	    ::= {fextLTEPlanEntry 13}

	fextLTEPlanSignalPeriod OBJECT-TYPE
	    SYNTAX      DisplayString
	    MAX-ACCESS  read-only
	    STATUS      current
	    DESCRIPTION "Signal period (600 - 18000 sec) to switch SIM card."
	    ::= {fextLTEPlanEntry 14}

	fextLTEPlanCapacity OBJECT-TYPE
	    SYNTAX      DisplayString
	    MAX-ACCESS  read-only
	    STATUS      current
	    DESCRIPTION "Data per month (0-102400000 MB)."
	    ::= {fextLTEPlanEntry 15}

	fextLTEPlanMonthlyFee OBJECT-TYPE
	    SYNTAX      DisplayString
	    MAX-ACCESS  read-only
	    STATUS      current
	    DESCRIPTION "Monthly fee (0-1000000)."
	    ::= {fextLTEPlanEntry 16}

	fextLTEPlanBillingDate OBJECT-TYPE
	    SYNTAX      DisplayString
	    MAX-ACCESS  read-only
	    STATUS      current
	    DESCRIPTION "Billing date of the month."
	    ::= {fextLTEPlanEntry 17}

	fextLTEPlanOverage OBJECT-TYPE
	    SYNTAX      DisplayString
	    MAX-ACCESS  read-only
	    STATUS      current
	    DESCRIPTION "Enable/disable for data overage."
	    ::= {fextLTEPlanEntry 18}

	fextLTEPlanPreferredSubnet OBJECT-TYPE
	    SYNTAX      DisplayString
	    MAX-ACCESS  read-only
	    STATUS      current
	    DESCRIPTION "DHCP subnet."
	    ::= {fextLTEPlanEntry 19}

	fextLTEPlanPrivateSubnet OBJECT-TYPE
	    SYNTAX      DisplayString
	    MAX-ACCESS  read-only
	    STATUS      current
	    DESCRIPTION "Enable/Disable blocking all non-NAT'ed traffic."
	    ::= {fextLTEPlanEntry 20}

	--
	-- fnFortiExtenderMib.fextNetwork
	--
	-- fextNetworkAddress ::= {fextNetwork 1}
	-- fextNetworkService ::= {fextNetwork 2}
	--

	fextNetworkAddress OBJECT-TYPE
		SYNTAX      SEQUENCE OF FextNetworkAddressEntry
		MAX-ACCESS  read-only
		STATUS      current
		DESCRIPTION "Configure IPv4 addresses."
		::= {fextNetwork 1}

	fextNetworkService OBJECT-IDENTITY
		STATUS      current
		DESCRIPTION	"Configure Firewall Service."
		::= {fextNetwork 2}

	--
	-- fextNetwork.fextNetworkAddress
	--

	fextNetworkAddressEntry OBJECT-TYPE
		SYNTAX      FextNetworkAddressEntry
		MAX-ACCESS  not-accessible
		STATUS      current
		DESCRIPTION "An entry containing IPv4 address setting."
		INDEX       {fextNetworkAddressIndex}
		::= {fextNetworkAddress 1}

	FextNetworkAddressEntry ::= SEQUENCE {
		fextNetworkAddressIndex   FnIndex,
		fextNetworkAddressName    DisplayString,
		fextNetworkAddressType    DisplayString,
		fextNetworkAddressSubnet  DisplayString,
		fextNetworkAddressStartIP DisplayString,
		fextNetworkAddressEndIP   DisplayString
	}

	fextNetworkAddressIndex OBJECT-TYPE
		SYNTAX      FnIndex
		MAX-ACCESS  not-accessible
		STATUS      current
		DESCRIPTION	"An index uniquely defining an IPv4 address setting."
		::= {fextNetworkAddressEntry 1}

	fextNetworkAddressName OBJECT-TYPE
	    SYNTAX      DisplayString
	    MAX-ACCESS  read-only
	    STATUS      current
	    DESCRIPTION "Name of the IPv4 address setting."
	    ::= {fextNetworkAddressEntry 2}

	fextNetworkAddressType OBJECT-TYPE
	    SYNTAX      DisplayString
	    MAX-ACCESS  read-only
	    STATUS      current
	    DESCRIPTION "Type of IPv4 address."
	    ::= {fextNetworkAddressEntry 3}

	fextNetworkAddressSubnet OBJECT-TYPE
	    SYNTAX      DisplayString
	    MAX-ACCESS  read-only
	    STATUS      current
	    DESCRIPTION "IP address and subnet mask of address."
	    ::= {fextNetworkAddressEntry 4}

	fextNetworkAddressStartIP OBJECT-TYPE
	    SYNTAX      DisplayString
	    MAX-ACCESS  read-only
	    STATUS      current
	    DESCRIPTION "First IP address (inclusive) in the range for the address."
	    ::= {fextNetworkAddressEntry 5}

	fextNetworkAddressEndIP OBJECT-TYPE
	    SYNTAX      DisplayString
	    MAX-ACCESS  read-only
	    STATUS      current
	    DESCRIPTION "Last IP address (inclusive) in the range for the address."
	    ::= {fextNetworkAddressEntry 6}

	--
	-- fextNetwork.fextNetworkService
	--
	-- fextServiceCustom ::= {fextNetworkService 1}
	--

	fextServiceCustom OBJECT-TYPE
		SYNTAX      SEQUENCE OF FextServiceCustomEntry
		MAX-ACCESS  read-only
		STATUS      current
		DESCRIPTION "Configure custom services."
		::= {fextNetworkService 1}

	--
	-- fextNetworkService.fextServiceCustom
	--

	fextServiceCustomEntry OBJECT-TYPE
		SYNTAX      FextServiceCustomEntry
		MAX-ACCESS  not-accessible
		STATUS      current
		DESCRIPTION "An entry containing custom service setting."
		INDEX       {fextServiceCustomIndex}
		::= {fextServiceCustom 1}

	FextServiceCustomEntry ::= SEQUENCE {
		fextServiceCustomIndex          FnIndex,
		fextServiceCustomName           DisplayString,
		fextServiceCustomProtocol       DisplayString,
		fextServiceCustomProtocolNumber DisplayString,
		fextServiceCustomTCPPortRange   DisplayString,
		fextServiceCustomUDPPortRange   DisplayString
	}

	fextServiceCustomIndex OBJECT-TYPE
		SYNTAX      FnIndex
		MAX-ACCESS  not-accessible
		STATUS      current
		DESCRIPTION	"An index uniquely defining custom service setting."
		::= {fextServiceCustomEntry 1}

	fextServiceCustomName OBJECT-TYPE
	    SYNTAX      DisplayString
	    MAX-ACCESS  read-only
	    STATUS      current
	    DESCRIPTION "Name of the custom service setting."
	    ::= {fextServiceCustomEntry 2}

	fextServiceCustomProtocol OBJECT-TYPE
	    SYNTAX      DisplayString
	    MAX-ACCESS  read-only
	    STATUS      current
	    DESCRIPTION "Protocol type based on IANA numbers."
	    ::= {fextServiceCustomEntry 3}

	fextServiceCustomProtocolNumber OBJECT-TYPE
	    SYNTAX      DisplayString
	    MAX-ACCESS  read-only
	    STATUS      current
	    DESCRIPTION "IP protocol number."
	    ::= {fextServiceCustomEntry 4}

	fextServiceCustomTCPPortRange OBJECT-TYPE
	    SYNTAX      DisplayString
	    MAX-ACCESS  read-only
	    STATUS      current
	    DESCRIPTION "Multiple TCP port ranges."
	    ::= {fextServiceCustomEntry 5}

	fextServiceCustomUDPPortRange OBJECT-TYPE
	    SYNTAX      DisplayString
	    MAX-ACCESS  read-only
	    STATUS      current
	    DESCRIPTION "Multiple UDP port ranges."
	    ::= {fextServiceCustomEntry 6}

	--
	-- fnFortiExtenderMib.fextFirewall
	--
	-- fextFirewallPolicy ::= {fextFirewall 1}
	--

	fextFirewallPolicy OBJECT-TYPE
		SYNTAX      SEQUENCE OF FextFirewallPolicyEntry
		MAX-ACCESS  read-only
		STATUS      current
		DESCRIPTION "Configure IPv4 policies."
		::= {fextFirewall 1}

	--
	-- fextFirewall.fextFirewallPolicy
	--

	fextFirewallPolicyEntry OBJECT-TYPE
		SYNTAX      FextFirewallPolicyEntry
		MAX-ACCESS  not-accessible
		STATUS      current
		DESCRIPTION "An entry containing IPv4 policies setting."
		INDEX       {fextFirewallPolicyIndex}
		::= {fextFirewallPolicy 1}

	FextFirewallPolicyEntry ::= SEQUENCE {
		fextFirewallPolicyIndex   FnIndex,
		fextFirewallPolicyName    DisplayString,
		fextFirewallPolicySrcIntf DisplayString,
		fextFirewallPolicyDstIntf DisplayString,
		fextFirewallPolicySrcAddr DisplayString,
		fextFirewallPolicyDstAddr DisplayString,
		fextFirewallPolicyAction  DisplayString,
		fextFirewallPolicyStatus  DisplayString,
		fextFirewallPolicyService DisplayString,
		fextFirewallPolicyNAT     DisplayString
	}

	fextFirewallPolicyIndex OBJECT-TYPE
		SYNTAX      FnIndex
		MAX-ACCESS  not-accessible
		STATUS      current
		DESCRIPTION	"An index uniquely defining an IPv4 policies setting."
		::= {fextFirewallPolicyEntry 1}

	fextFirewallPolicyName OBJECT-TYPE
	    SYNTAX      DisplayString
	    MAX-ACCESS  read-only
	    STATUS      current
	    DESCRIPTION "Name of the IPv4 policies setting."
	    ::= {fextFirewallPolicyEntry 2}

	fextFirewallPolicySrcIntf OBJECT-TYPE
	    SYNTAX      DisplayString
	    MAX-ACCESS  read-only
	    STATUS      current
	    DESCRIPTION "Ingress interface."
	    ::= {fextFirewallPolicyEntry 3}

	fextFirewallPolicyDstIntf OBJECT-TYPE
	    SYNTAX      DisplayString
	    MAX-ACCESS  read-only
	    STATUS      current
	    DESCRIPTION "Egress interface."
	    ::= {fextFirewallPolicyEntry 4}

	fextFirewallPolicySrcAddr OBJECT-TYPE
	    SYNTAX      DisplayString
	    MAX-ACCESS  read-only
	    STATUS      current
	    DESCRIPTION "Source address."
	    ::= {fextFirewallPolicyEntry 5}

	fextFirewallPolicyDstAddr OBJECT-TYPE
	    SYNTAX      DisplayString
	    MAX-ACCESS  read-only
	    STATUS      current
	    DESCRIPTION "Destination address."
	    ::= {fextFirewallPolicyEntry 6}

	fextFirewallPolicyAction OBJECT-TYPE
	    SYNTAX      DisplayString
	    MAX-ACCESS  read-only
	    STATUS      current
	    DESCRIPTION "Policy action."
	    ::= {fextFirewallPolicyEntry 7}

	fextFirewallPolicyStatus OBJECT-TYPE
	    SYNTAX      DisplayString
	    MAX-ACCESS  read-only
	    STATUS      current
	    DESCRIPTION "Enable/disable this policy."
	    ::= {fextFirewallPolicyEntry 8}

	fextFirewallPolicyService OBJECT-TYPE
	    SYNTAX      DisplayString
	    MAX-ACCESS  read-only
	    STATUS      current
	    DESCRIPTION "Service and service group names."
	    ::= {fextFirewallPolicyEntry 9}

	fextFirewallPolicyNAT OBJECT-TYPE
	    SYNTAX      DisplayString
	    MAX-ACCESS  read-only
	    STATUS      current
	    DESCRIPTION "Enable/disable source NAT."
	    ::= {fextFirewallPolicyEntry 10}

	--
	-- fnFortiExtenderMib.fextRouter
	--
	-- fextRouterPolicy    ::= {fextRouter 1}
	-- fextRouterStatic    ::= {fextRouter 2}
	-- fextRouterTarget    ::= {fextRouter 3}
	-- fextRouterMulticast ::= {fextRouter 4}
	--

	fextRouterPolicy OBJECT-TYPE
		SYNTAX      SEQUENCE OF FextRouterPolicyEntry
		MAX-ACCESS  read-only
		STATUS      current
		DESCRIPTION "Configure IPv4 policy based routing table rule."
		::= {fextRouter 1}

	fextRouterStatic OBJECT-TYPE
		SYNTAX      SEQUENCE OF FextRouterStaticEntry
		MAX-ACCESS  read-only
		STATUS      current
		DESCRIPTION "Configure IPv4 static routing tables."
		::= {fextRouter 2}

	fextRouterTarget OBJECT-TYPE
		SYNTAX      SEQUENCE OF FextRouterTargetEntry
		MAX-ACCESS  read-only
		STATUS      current
		DESCRIPTION "Configure IPv4 routing target."
		::= {fextRouter 3}

	fextRouterMulticast OBJECT-IDENTITY
		STATUS      current
		DESCRIPTION	"Configure multicast."
		::= {fextRouter 4}

	--
	-- fextRouter.fextRouterPolicy
	--

	fextRouterPolicyEntry OBJECT-TYPE
		SYNTAX      FextRouterPolicyEntry
		MAX-ACCESS  not-accessible
		STATUS      current
		DESCRIPTION "An entry containing IPv4 policy based routing table rule."
		INDEX       {fextRouterPolicyIndex}
		::= {fextRouterPolicy 1}

	FextRouterPolicyEntry ::= SEQUENCE {
		fextRouterPolicyIndex       FnIndex,
		fextRouterPolicyName        DisplayString,
		fextRouterPolicyInputDevice DisplayString,
		fextRouterPolicySrcAddr     DisplayString,
		fextRouterPolicySrc         DisplayString,
		fextRouterPolicyDstAddr     DisplayString,
		fextRouterPolicyDst         DisplayString,
		fextRouterPolicyService     DisplayString,
		fextRouterPolicyTarget      DisplayString,
		fextRouterPolicyStatus      DisplayString,
		fextRouterPolicyComment     DisplayString
	}

	fextRouterPolicyIndex OBJECT-TYPE
		SYNTAX      FnIndex
		MAX-ACCESS  not-accessible
		STATUS      current
		DESCRIPTION	"An index uniquely defining an IPv4 policy based routing
					 table rule."
		::= {fextRouterPolicyEntry 1}

	fextRouterPolicyName OBJECT-TYPE
	    SYNTAX      DisplayString
	    MAX-ACCESS  read-only
	    STATUS      current
	    DESCRIPTION "Name of the IPv4 policy based routing table rule."
	    ::= {fextRouterPolicyEntry 2}

	fextRouterPolicyInputDevice OBJECT-TYPE
	    SYNTAX      DisplayString
	    MAX-ACCESS  read-only
	    STATUS      current
	    DESCRIPTION "Incoming interface name."
	    ::= {fextRouterPolicyEntry 3}

	fextRouterPolicySrcAddr OBJECT-TYPE
	    SYNTAX      DisplayString
	    MAX-ACCESS  read-only
	    STATUS      current
	    DESCRIPTION "Source address."
	    ::= {fextRouterPolicyEntry 4}

	fextRouterPolicySrc OBJECT-TYPE
	    SYNTAX      DisplayString
	    MAX-ACCESS  read-only
	    STATUS      current
	    DESCRIPTION "Source IP and mask for this policy based route rule."
	    ::= {fextRouterPolicyEntry 5}

	fextRouterPolicyDstAddr OBJECT-TYPE
	    SYNTAX      DisplayString
	    MAX-ACCESS  read-only
	    STATUS      current
	    DESCRIPTION "Destination address."
	    ::= {fextRouterPolicyEntry 6}

	fextRouterPolicyDst OBJECT-TYPE
	    SYNTAX      DisplayString
	    MAX-ACCESS  read-only
	    STATUS      current
	    DESCRIPTION "Destination IP and mask for this policy based route rule."
	    ::= {fextRouterPolicyEntry 7}

	fextRouterPolicyService OBJECT-TYPE
	    SYNTAX      DisplayString
	    MAX-ACCESS  read-only
	    STATUS      current
	    DESCRIPTION "Service and service group names."
	    ::= {fextRouterPolicyEntry 8}

	fextRouterPolicyTarget OBJECT-TYPE
	    SYNTAX      DisplayString
	    MAX-ACCESS  read-only
	    STATUS      current
	    DESCRIPTION "Out-going interface and next-hop."
	    ::= {fextRouterPolicyEntry 9}

	fextRouterPolicyStatus OBJECT-TYPE
	    SYNTAX      DisplayString
	    MAX-ACCESS  read-only
	    STATUS      current
	    DESCRIPTION "Enable/disable this policy based route rule."
	    ::= {fextRouterPolicyEntry 10}

	fextRouterPolicyComment OBJECT-TYPE
	    SYNTAX      DisplayString
	    MAX-ACCESS  read-only
	    STATUS      current
	    DESCRIPTION "Optional comments."
	    ::= {fextRouterPolicyEntry 11}

	--
	-- fextRouter.fextRouterStatic
	--

	fextRouterStaticEntry OBJECT-TYPE
		SYNTAX      FextRouterStaticEntry
		MAX-ACCESS  not-accessible
		STATUS      current
		DESCRIPTION "An entry containing IPv4 static routing tables."
		INDEX       {fextRouterStaticIndex}
		::= {fextRouterStatic 1}

	FextRouterStaticEntry ::= SEQUENCE {
		fextRouterStaticIndex    FnIndex,
		fextRouterStaticName     DisplayString,
		fextRouterStaticStatus   DisplayString,
		fextRouterStaticDst      DisplayString,
		fextRouterStaticGateway  DisplayString,
		fextRouterStaticDistance DisplayString,
		fextRouterStaticDevice   DisplayString,
		fextRouterStaticComment  DisplayString
	}

	fextRouterStaticIndex OBJECT-TYPE
		SYNTAX      FnIndex
		MAX-ACCESS  not-accessible
		STATUS      current
		DESCRIPTION	"An index uniquely defining an IPv4 static routing tables."
		::= {fextRouterStaticEntry 1}

	fextRouterStaticName OBJECT-TYPE
	    SYNTAX      DisplayString
	    MAX-ACCESS  read-only
	    STATUS      current
	    DESCRIPTION "Name of the IPv4 static routing tables."
	    ::= {fextRouterStaticEntry 2}

	fextRouterStaticStatus OBJECT-TYPE
	    SYNTAX      DisplayString
	    MAX-ACCESS  read-only
	    STATUS      current
	    DESCRIPTION "Enable/disable this static route."
	    ::= {fextRouterStaticEntry 3}

	fextRouterStaticDst OBJECT-TYPE
	    SYNTAX      DisplayString
	    MAX-ACCESS  read-only
	    STATUS      current
	    DESCRIPTION "Source address."
	    ::= {fextRouterStaticEntry 4}

	fextRouterStaticGateway OBJECT-TYPE
	    SYNTAX      DisplayString
	    MAX-ACCESS  read-only
	    STATUS      current
	    DESCRIPTION "Gateway IP for this route."
	    ::= {fextRouterStaticEntry 5}

	fextRouterStaticDistance OBJECT-TYPE
	    SYNTAX      DisplayString
	    MAX-ACCESS  read-only
	    STATUS      current
	    DESCRIPTION "Administrative distance."
	    ::= {fextRouterStaticEntry 6}

	fextRouterStaticDevice OBJECT-TYPE
	    SYNTAX      DisplayString
	    MAX-ACCESS  read-only
	    STATUS      current
	    DESCRIPTION "Gateway out interface or tunnel."
	    ::= {fextRouterStaticEntry 7}

	fextRouterStaticComment OBJECT-TYPE
	    SYNTAX      DisplayString
	    MAX-ACCESS  read-only
	    STATUS      current
	    DESCRIPTION "Optional comments."
	    ::= {fextRouterStaticEntry 8}

	--
	-- fextRouter.fextRouterTarget
	--

	fextRouterTargetEntry OBJECT-TYPE
		SYNTAX      FextRouterTargetEntry
		MAX-ACCESS  not-accessible
		STATUS      current
		DESCRIPTION "An entry containing IPv4 routing target."
		INDEX       {fextRouterTargetIndex}
		::= {fextRouterTarget 1}

	FextRouterTargetEntry ::= SEQUENCE {
		fextRouterTargetIndex     FnIndex,
		fextRouterTargetName      DisplayString,
		fextRouterTargetInterface DisplayString,
		fextRouterTargetNextHop   DisplayString,
		fextRouterTargetIntfNH    DisplayString
	}

	fextRouterTargetIndex OBJECT-TYPE
		SYNTAX      FnIndex
		MAX-ACCESS  not-accessible
		STATUS      current
		DESCRIPTION	"An index uniquely defining an IPv4 routing target."
		::= {fextRouterTargetEntry 1}

	fextRouterTargetName OBJECT-TYPE
	    SYNTAX      DisplayString
	    MAX-ACCESS  read-only
	    STATUS      current
	    DESCRIPTION "Name of the IPv4 routing target."
	    ::= {fextRouterTargetEntry 2}

	fextRouterTargetInterface OBJECT-TYPE
	    SYNTAX      DisplayString
	    MAX-ACCESS  read-only
	    STATUS      current
	    DESCRIPTION "Target interface."
	    ::= {fextRouterTargetEntry 3}

	fextRouterTargetNextHop OBJECT-TYPE
	    SYNTAX      DisplayString
	    MAX-ACCESS  read-only
	    STATUS      current
	    DESCRIPTION "Next-hop IPv4 address."
	    ::= {fextRouterTargetEntry 4}

	fextRouterTargetIntfNH OBJECT-TYPE
	    SYNTAX      DisplayString
	    MAX-ACCESS  read-only
	    STATUS      current
	    DESCRIPTION "Next-hop is from interface gateway."
	    ::= {fextRouterTargetEntry 5}

	--
	-- fextRouter.fextRouterMulticast
	--
	-- fextMcastPIMSMGlobal ::= {fextRouterMulticast 1}
	-- fextMcastInterface   ::= {fextRouterMulticast 2}
	--

	fextMcastPIMSMGlobal OBJECT-IDENTITY
		STATUS      current
		DESCRIPTION	"PIM sparse-mode global settings."
		::= {fextRouterMulticast 1}

	fextMcastInterface OBJECT-TYPE
		SYNTAX      SEQUENCE OF FextMcastInterfaceEntry
		MAX-ACCESS  read-only
		STATUS      current
		DESCRIPTION "PIM interfaces."
		::= {fextRouterMulticast 2}

	--
	-- fextRouterMulticast.fextMcastPIMSMGlobal
	--
	-- fextPIMSMGlobalJoinPruneInterval ::= {fextMcastPIMSMGlobal 1}
	-- fextPIMSMGlobalHelloInterval     ::= {fextMcastPIMSMGlobal 2}
	-- fextPIMSMGlobalRPAddress         ::= {fextMcastPIMSMGlobal 3}
	--

	fextPIMSMGlobalJoinPruneInterval OBJECT-TYPE
		SYNTAX      DisplayString
		MAX-ACCESS  read-only
		STATUS      current
		DESCRIPTION	"Interval between sending PIM Join/prune messages."
		::= {fextMcastPIMSMGlobal 1}

	fextPIMSMGlobalHelloInterval OBJECT-TYPE
	    SYNTAX      DisplayString
	    MAX-ACCESS  read-only
	    STATUS      current
	    DESCRIPTION "Interval between sending PIM hello messages."
	    ::= {fextMcastPIMSMGlobal 2}

	fextPIMSMGlobalRPAddress OBJECT-TYPE
		SYNTAX      SEQUENCE OF FextPIMSMGlobalRPAddressEntry
		MAX-ACCESS  read-only
		STATUS      current
		DESCRIPTION "Statically configure RP addresses."
		::= {fextMcastPIMSMGlobal 3}

	--
	-- fextMcastPIMSMGlobal.fextPIMSMGlobalRPAddress
	--

	fextPIMSMGlobalRPAddressEntry OBJECT-TYPE
		SYNTAX      FextPIMSMGlobalRPAddressEntry
		MAX-ACCESS  not-accessible
		STATUS      current
		DESCRIPTION "An entry containing statically configure RP address."
		INDEX       {fextPIMRPAddressIndex}
		::= {fextPIMSMGlobalRPAddress 1}

	FextPIMSMGlobalRPAddressEntry ::= SEQUENCE {
		fextPIMRPAddressIndex   FnIndex,
		fextPIMRPAddressName    DisplayString,
		fextPIMRPAddressAddress DisplayString,
		fextPIMRPAddressGroup   DisplayString
	}

	fextPIMRPAddressIndex OBJECT-TYPE
		SYNTAX      FnIndex
		MAX-ACCESS  not-accessible
		STATUS      current
		DESCRIPTION	"An index uniquely defining a statically configure RP
					 address."
		::= {fextPIMSMGlobalRPAddressEntry 1}

	fextPIMRPAddressName OBJECT-TYPE
	    SYNTAX      DisplayString
	    MAX-ACCESS  read-only
	    STATUS      current
	    DESCRIPTION "Name of the statically configure RP address."
	    ::= {fextPIMSMGlobalRPAddressEntry 2}

	fextPIMRPAddressAddress OBJECT-TYPE
	    SYNTAX      DisplayString
	    MAX-ACCESS  read-only
	    STATUS      current
	    DESCRIPTION "RP router address."
	    ::= {fextPIMSMGlobalRPAddressEntry 3}

	fextPIMRPAddressGroup OBJECT-TYPE
	    SYNTAX      DisplayString
	    MAX-ACCESS  read-only
	    STATUS      current
	    DESCRIPTION "Groups to use this RP."
	    ::= {fextPIMSMGlobalRPAddressEntry 4}

	--
	-- fextRouterMulticast.fextMcastInterface
	--

	fextMcastInterfaceEntry OBJECT-TYPE
		SYNTAX      FextMcastInterfaceEntry
		MAX-ACCESS  not-accessible
		STATUS      current
		DESCRIPTION "An entry containing PIM interface."
		INDEX       {fextMcastInterfaceIndex}
		::= {fextMcastInterface 1}

	FextMcastInterfaceEntry ::= SEQUENCE {
		fextMcastInterfaceIndex FnIndex,
		fextMcastInterfaceName  DisplayString
	}

	fextMcastInterfaceIndex OBJECT-TYPE
		SYNTAX      FnIndex
		MAX-ACCESS  not-accessible
		STATUS      current
		DESCRIPTION	"An index uniquely defining PIM interface."
		::= {fextMcastInterfaceEntry 1}

	fextMcastInterfaceName OBJECT-TYPE
	    SYNTAX      DisplayString
	    MAX-ACCESS  read-only
	    STATUS      current
	    DESCRIPTION "Name of the PIM interface."
	    ::= {fextMcastInterfaceEntry 2}

	--
	-- fnFortiExtenderMib.fextVPN
	--
	-- fextVPNIPsec       ::= {fextVPN 1}
	-- fextVPNCertificate ::= {fextVPN 2}
	--

	fextVPNIPsec OBJECT-IDENTITY
		STATUS      current
		DESCRIPTION "Configure IPsec."
		::= {fextVPN 1}

	fextVPNCertificate OBJECT-IDENTITY
		STATUS      current
		DESCRIPTION	"Configure VPN certificates."
		::= {fextVPN 2}

	--
	-- fextVPN.fextVPNIPsec
	--
	-- fextVPNIPsecPhase1 ::= {fextVPNIPsec 1}
	-- fextVPNIPsecPhase2 ::= {fextVPNIPsec 2}
	--

	fextVPNIPsecPhase1 OBJECT-TYPE
		SYNTAX      SEQUENCE OF FextVPNIPsecPhase1Entry
		MAX-ACCESS  read-only
		STATUS      current
		DESCRIPTION "Configure VPN remote gateway."
		::= {fextVPNIPsec 1}

	fextVPNIPsecPhase2 OBJECT-TYPE
		SYNTAX      SEQUENCE OF FextVPNIPsecPhase2Entry
		MAX-ACCESS  read-only
		STATUS      current
		DESCRIPTION "Configure VPN autokey tunnel."
		::= {fextVPNIPsec 2}

	--
	-- fextVPNIPsec.fextVPNIPsecPhase1
	--

	fextVPNIPsecPhase1Entry OBJECT-TYPE
		SYNTAX      FextVPNIPsecPhase1Entry
		MAX-ACCESS  not-accessible
		STATUS      current
		DESCRIPTION "An entry containing VPN remote gateway."
		INDEX       {fextIPsecPhase1Index}
		::= {fextVPNIPsecPhase1 1}

	FextVPNIPsecPhase1Entry ::= SEQUENCE {
		fextIPsecPhase1Index        FnIndex,
		fextIPsecPhase1Name         DisplayString,
		fextIPsecPhase1IKEVersion   DisplayString,
		fextIPsecPhase1KeyLife      DisplayString,
		fextIPsecPhase1Mode         DisplayString,
		fextIPsecPhase1Proposal     DisplayString,
		fextIPsecPhase1DHGroup      DisplayString,
		fextIPsecPhase1Interface    DisplayString,
		fextIPsecPhase1Type         DisplayString,
		fextIPsecPhase1RemoteGW     DisplayString,
		fextIPsecPhase1RemoteGWDDNS DisplayString,
		fextIPsecPhase1AuthMethod   DisplayString,
		fextIPsecPhase1PSKSecret    DisplayString,
		fextIPsecPhase1Certificate  DisplayString,
		fextIPsecPhase1Peer         DisplayString,
		fextIPsecPhase1LocalID      DisplayString,
		fextIPsecPhase1PeerID       DisplayString
	}

	fextIPsecPhase1Index OBJECT-TYPE
		SYNTAX      FnIndex
		MAX-ACCESS  not-accessible
		STATUS      current
		DESCRIPTION	"An index uniquely defining a VPN remote gateway."
		::= {fextVPNIPsecPhase1Entry 1}

	fextIPsecPhase1Name OBJECT-TYPE
	    SYNTAX      DisplayString
	    MAX-ACCESS  read-only
	    STATUS      current
	    DESCRIPTION "Name of the VPN remote gateway."
	    ::= {fextVPNIPsecPhase1Entry 2}

	fextIPsecPhase1IKEVersion OBJECT-TYPE
	    SYNTAX      DisplayString
	    MAX-ACCESS  read-only
	    STATUS      current
	    DESCRIPTION "IKE protocol version."
	    ::= {fextVPNIPsecPhase1Entry 3}

	fextIPsecPhase1KeyLife OBJECT-TYPE
	    SYNTAX      DisplayString
	    MAX-ACCESS  read-only
	    STATUS      current
	    DESCRIPTION "Time to wait in seconds before phase 1 encryption key expires."
	    ::= {fextVPNIPsecPhase1Entry 4}

	fextIPsecPhase1Mode OBJECT-TYPE
	    SYNTAX      DisplayString
	    MAX-ACCESS  read-only
	    STATUS      current
	    DESCRIPTION "The ID protection mode used to establish a secure channel."
	    ::= {fextVPNIPsecPhase1Entry 5}

	fextIPsecPhase1Proposal OBJECT-TYPE
	    SYNTAX      DisplayString
	    MAX-ACCESS  read-only
	    STATUS      current
	    DESCRIPTION "Phase1 proposal."
	    ::= {fextVPNIPsecPhase1Entry 6}

	fextIPsecPhase1DHGroup OBJECT-TYPE
	    SYNTAX      DisplayString
	    MAX-ACCESS  read-only
	    STATUS      current
	    DESCRIPTION "DH group."
	    ::= {fextVPNIPsecPhase1Entry 7}

	fextIPsecPhase1Interface OBJECT-TYPE
	    SYNTAX      DisplayString
	    MAX-ACCESS  read-only
	    STATUS      current
	    DESCRIPTION "Local physical or lte outgoing interface."
	    ::= {fextVPNIPsecPhase1Entry 8}

	fextIPsecPhase1Type OBJECT-TYPE
	    SYNTAX      DisplayString
	    MAX-ACCESS  read-only
	    STATUS      current
	    DESCRIPTION "Remote gateway type."
	    ::= {fextVPNIPsecPhase1Entry 9}

	fextIPsecPhase1RemoteGW OBJECT-TYPE
	    SYNTAX      DisplayString
	    MAX-ACCESS  read-only
	    STATUS      current
	    DESCRIPTION "IPv4 address of the remote gateway's external interface."
	    ::= {fextVPNIPsecPhase1Entry 10}

	fextIPsecPhase1RemoteGWDDNS OBJECT-TYPE
	    SYNTAX      DisplayString
	    MAX-ACCESS  read-only
	    STATUS      current
	    DESCRIPTION "Domain name of remote gateway."
	    ::= {fextVPNIPsecPhase1Entry 11}

	fextIPsecPhase1AuthMethod OBJECT-TYPE
	    SYNTAX      DisplayString
	    MAX-ACCESS  read-only
	    STATUS      current
	    DESCRIPTION "Authentication method."
	    ::= {fextVPNIPsecPhase1Entry 12}

	fextIPsecPhase1PSKSecret OBJECT-TYPE
	    SYNTAX      DisplayString
	    MAX-ACCESS  read-only
	    STATUS      current
	    DESCRIPTION "Pre-shared secret for PSK authentication."
	    ::= {fextVPNIPsecPhase1Entry 13}

	fextIPsecPhase1Certificate OBJECT-TYPE
	    SYNTAX      DisplayString
	    MAX-ACCESS  read-only
	    STATUS      current
	    DESCRIPTION "The names of up to 4 signed personal certificates."
	    ::= {fextVPNIPsecPhase1Entry 14}

	fextIPsecPhase1Peer OBJECT-TYPE
	    SYNTAX      DisplayString
	    MAX-ACCESS  read-only
	    STATUS      current
	    DESCRIPTION "The CA certificate used to authenticate peer certificate."
	    ::= {fextVPNIPsecPhase1Entry 15}

	fextIPsecPhase1LocalID OBJECT-TYPE
	    SYNTAX      DisplayString
	    MAX-ACCESS  read-only
	    STATUS      current
	    DESCRIPTION "Local ID."
	    ::= {fextVPNIPsecPhase1Entry 16}

	fextIPsecPhase1PeerID OBJECT-TYPE
	    SYNTAX      DisplayString
	    MAX-ACCESS  read-only
	    STATUS      current
	    DESCRIPTION "Accept this peer identity."
	    ::= {fextVPNIPsecPhase1Entry 17}

	--
	-- fextVPNIPsec.fextVPNIPsecPhase2
	--

	fextVPNIPsecPhase2Entry OBJECT-TYPE
		SYNTAX      FextVPNIPsecPhase2Entry
		MAX-ACCESS  not-accessible
		STATUS      current
		DESCRIPTION "An entry containing VPN autokey tunnel."
		INDEX       {fextIPsecPhase2Index}
		::= {fextVPNIPsecPhase2 1}

	FextVPNIPsecPhase2Entry ::= SEQUENCE {
		fextIPsecPhase2Index          FnIndex,
		fextIPsecPhase2Name           DisplayString,
		fextIPsecPhase2Phase1Name     DisplayString,
		fextIPsecPhase2Proposal       DisplayString,
		fextIPsecPhase2PFS            DisplayString,
		fextIPsecPhase2DHGroup        DisplayString,
		fextIPsecPhase2KeyLifeType    DisplayString,
		fextIPsecPhase2KeyLifeSeconds DisplayString,
		fextIPsecPhase2KeyLifeKBs     DisplayString,
		fextIPsecPhase2Encapsulation  DisplayString,
		fextIPsecPhase2Protocol       DisplayString,
		fextIPsecPhase2SrcAddrType	  DisplayString,
		fextIPsecPhase2SrcSubnet      DisplayString,
		fextIPsecPhase2SrcStartIp     DisplayString,
		fextIPsecPhase2SrcEndIp       DisplayString,
		fextIPsecPhase2SrcName        DisplayString,
		fextIPsecPhase2SrcPort        DisplayString,
		fextIPsecPhase2DstAddrType	  DisplayString,
		fextIPsecPhase2DstSubnet      DisplayString,
		fextIPsecPhase2DstStartIp     DisplayString,
		fextIPsecPhase2DstEndIp       DisplayString,
		fextIPsecPhase2DstName        DisplayString,
		fextIPsecPhase2DstPort        DisplayString
	}

	fextIPsecPhase2Index OBJECT-TYPE
		SYNTAX      FnIndex
		MAX-ACCESS  not-accessible
		STATUS      current
		DESCRIPTION	"An index uniquely defining a VPN autokey tunnel."
		::= {fextVPNIPsecPhase2Entry 1}

	fextIPsecPhase2Name OBJECT-TYPE
	    SYNTAX      DisplayString
	    MAX-ACCESS  read-only
	    STATUS      current
	    DESCRIPTION "Name of the VPN autokey tunnel."
	    ::= {fextVPNIPsecPhase2Entry 2}

	fextIPsecPhase2Phase1Name OBJECT-TYPE
	    SYNTAX      DisplayString
	    MAX-ACCESS  read-only
	    STATUS      current
	    DESCRIPTION "Phase 1 determines the options required for phase 2."
	    ::= {fextVPNIPsecPhase2Entry 3}

	fextIPsecPhase2Proposal OBJECT-TYPE
	    SYNTAX      DisplayString
	    MAX-ACCESS  read-only
	    STATUS      current
	    DESCRIPTION "Phase2 proposal."
	    ::= {fextVPNIPsecPhase2Entry 4}

	fextIPsecPhase2PFS OBJECT-TYPE
	    SYNTAX      DisplayString
	    MAX-ACCESS  read-only
	    STATUS      current
	    DESCRIPTION "Enable/disable PFS feature."
	    ::= {fextVPNIPsecPhase2Entry 5}

	fextIPsecPhase2DHGroup OBJECT-TYPE
	    SYNTAX      DisplayString
	    MAX-ACCESS  read-only
	    STATUS      current
	    DESCRIPTION "Phase2 DH group."
	    ::= {fextVPNIPsecPhase2Entry 6}

	fextIPsecPhase2KeyLifeType OBJECT-TYPE
	    SYNTAX      DisplayString
	    MAX-ACCESS  read-only
	    STATUS      current
	    DESCRIPTION "Keylife type."
	    ::= {fextVPNIPsecPhase2Entry 7}

	fextIPsecPhase2KeyLifeSeconds OBJECT-TYPE
	    SYNTAX      DisplayString
	    MAX-ACCESS  read-only
	    STATUS      current
	    DESCRIPTION "Phase2 key life in time in seconds."
	    ::= {fextVPNIPsecPhase2Entry 8}

	fextIPsecPhase2KeyLifeKBs OBJECT-TYPE
	    SYNTAX      DisplayString
	    MAX-ACCESS  read-only
	    STATUS      current
	    DESCRIPTION "Phase2 key life in number of bytes of traffic."
	    ::= {fextVPNIPsecPhase2Entry 9}

	fextIPsecPhase2Encapsulation OBJECT-TYPE
	    SYNTAX      DisplayString
	    MAX-ACCESS  read-only
	    STATUS      current
	    DESCRIPTION "ESP encapsulation mode."
	    ::= {fextVPNIPsecPhase2Entry 10}

	fextIPsecPhase2Protocol OBJECT-TYPE
	    SYNTAX      DisplayString
	    MAX-ACCESS  read-only
	    STATUS      current
	    DESCRIPTION "Quick mode protocol selector."
	    ::= {fextVPNIPsecPhase2Entry 11}

	fextIPsecPhase2SrcAddrType OBJECT-TYPE
		SYNTAX      DisplayString
		MAX-ACCESS  read-only
		STATUS      current
		DESCRIPTION "Local proxy ID type."
		::= {fextVPNIPsecPhase2Entry 12}

	fextIPsecPhase2SrcSubnet OBJECT-TYPE
	    SYNTAX      DisplayString
	    MAX-ACCESS  read-only
	    STATUS      current
	    DESCRIPTION "Local proxy ID subnet."
	    ::= {fextVPNIPsecPhase2Entry 13}

	fextIPsecPhase2SrcStartIp OBJECT-TYPE
	    SYNTAX      DisplayString
	    MAX-ACCESS  read-only
	    STATUS      current
	    DESCRIPTION "Local proxy ID start."
	    ::= {fextVPNIPsecPhase2Entry 14}

	fextIPsecPhase2SrcEndIp OBJECT-TYPE
	    SYNTAX      DisplayString
	    MAX-ACCESS  read-only
	    STATUS      current
	    DESCRIPTION "Local proxy ID end."
	    ::= {fextVPNIPsecPhase2Entry 15}

	fextIPsecPhase2SrcName OBJECT-TYPE
	    SYNTAX      DisplayString
	    MAX-ACCESS  read-only
	    STATUS      current
	    DESCRIPTION "Local proxy ID name."
	    ::= {fextVPNIPsecPhase2Entry 16}

	fextIPsecPhase2SrcPort OBJECT-TYPE
	    SYNTAX      DisplayString
	    MAX-ACCESS  read-only
	    STATUS      current
	    DESCRIPTION "Quick mode source port."
	    ::= {fextVPNIPsecPhase2Entry 17}

	fextIPsecPhase2DstAddrType OBJECT-TYPE
		SYNTAX      DisplayString
		MAX-ACCESS  read-only
		STATUS      current
		DESCRIPTION "Remote proxy ID type."
		::= {fextVPNIPsecPhase2Entry 18}

	fextIPsecPhase2DstSubnet OBJECT-TYPE
	    SYNTAX      DisplayString
	    MAX-ACCESS  read-only
	    STATUS      current
	    DESCRIPTION "Remote proxy ID subnet."
	    ::= {fextVPNIPsecPhase2Entry 19}

	fextIPsecPhase2DstStartIp OBJECT-TYPE
	    SYNTAX      DisplayString
	    MAX-ACCESS  read-only
	    STATUS      current
	    DESCRIPTION "Remote proxy ID start."
	    ::= {fextVPNIPsecPhase2Entry 20}

	fextIPsecPhase2DstEndIp OBJECT-TYPE
	    SYNTAX      DisplayString
	    MAX-ACCESS  read-only
	    STATUS      current
	    DESCRIPTION "Remote proxy ID end."
	    ::= {fextVPNIPsecPhase2Entry 21}

	fextIPsecPhase2DstName OBJECT-TYPE
	    SYNTAX      DisplayString
	    MAX-ACCESS  read-only
	    STATUS      current
	    DESCRIPTION "Remote proxy ID name."
	    ::= {fextVPNIPsecPhase2Entry 22}

	fextIPsecPhase2DstPort OBJECT-TYPE
	    SYNTAX      DisplayString
	    MAX-ACCESS  read-only
	    STATUS      current
	    DESCRIPTION "Quick mode destination port."
	    ::= {fextVPNIPsecPhase2Entry 23}

	--
	-- fextVPN.fextVPNCertificate
	--
	-- fextVPNCertificateCA    ::= {fextVPNCertificate 1}
	-- fextVPNCertificateLocal ::= {fextVPNCertificate 2}
	--

	fextVPNCertificateCA OBJECT-TYPE
		SYNTAX      SEQUENCE OF FextVPNCertificateCAEntry
		MAX-ACCESS  read-only
		STATUS      current
		DESCRIPTION "CA certificates."
		::= {fextVPNCertificate 1}

	fextVPNCertificateLocal OBJECT-TYPE
		SYNTAX      SEQUENCE OF FextVPNCertificateLocalEntry
		MAX-ACCESS  read-only
		STATUS      current
		DESCRIPTION "Local keys and certificates."
		::= {fextVPNCertificate 2}

	--
	-- fextVPNCertificate.fextVPNCertificateCA
	--

	fextVPNCertificateCAEntry OBJECT-TYPE
		SYNTAX      FextVPNCertificateCAEntry
		MAX-ACCESS  not-accessible
		STATUS      current
		DESCRIPTION "An entry containing CA certificate."
		INDEX       {fextCertificateCAIndex}
		::= {fextVPNCertificateCA 1}

	FextVPNCertificateCAEntry ::= SEQUENCE {
		fextCertificateCAIndex   FnIndex,
		fextCertificateCAName    DisplayString,
		fextCertificateCAComment DisplayString,
		fextCertificateCASource  DisplayString
	}

	fextCertificateCAIndex OBJECT-TYPE
		SYNTAX      FnIndex
		MAX-ACCESS  not-accessible
		STATUS      current
		DESCRIPTION	"An index uniquely defining a CA certificate."
		::= {fextVPNCertificateCAEntry 1}

	fextCertificateCAName OBJECT-TYPE
	    SYNTAX      DisplayString
	    MAX-ACCESS  read-only
	    STATUS      current
	    DESCRIPTION "Name of the CA certificate."
	    ::= {fextVPNCertificateCAEntry 2}

	fextCertificateCAComment OBJECT-TYPE
	    SYNTAX      DisplayString
	    MAX-ACCESS  read-only
	    STATUS      current
	    DESCRIPTION "Comment."
	    ::= {fextVPNCertificateCAEntry 3}

	fextCertificateCASource OBJECT-TYPE
	    SYNTAX      DisplayString
	    MAX-ACCESS  read-only
	    STATUS      current
	    DESCRIPTION "CA certificate source type."
	    ::= {fextVPNCertificateCAEntry 4}

	--
	-- fextVPNCertificate.fextVPNCertificateLocal
	--

	fextVPNCertificateLocalEntry OBJECT-TYPE
		SYNTAX      FextVPNCertificateLocalEntry
		MAX-ACCESS  not-accessible
		STATUS      current
		DESCRIPTION "An entry containing local key and certificate."
		INDEX       {fextCertificateLocalIndex}
		::= {fextVPNCertificateLocal 1}

	FextVPNCertificateLocalEntry ::= SEQUENCE {
		fextCertificateLocalIndex   FnIndex,
		fextCertificateLocalName    DisplayString,
		fextCertificateLocalComment DisplayString,
		fextCertificateLocalSource  DisplayString
	}

	fextCertificateLocalIndex OBJECT-TYPE
		SYNTAX      FnIndex
		MAX-ACCESS  not-accessible
		STATUS      current
		DESCRIPTION	"An index uniquely defining a local key and certificate."
		::= {fextVPNCertificateLocalEntry 1}

	fextCertificateLocalName OBJECT-TYPE
	    SYNTAX      DisplayString
	    MAX-ACCESS  read-only
	    STATUS      current
	    DESCRIPTION "Name of the local key and certificate."
	    ::= {fextVPNCertificateLocalEntry 2}

	fextCertificateLocalComment OBJECT-TYPE
	    SYNTAX      DisplayString
	    MAX-ACCESS  read-only
	    STATUS      current
	    DESCRIPTION "Comment."
	    ::= {fextVPNCertificateLocalEntry 3}

	fextCertificateLocalSource OBJECT-TYPE
	    SYNTAX      DisplayString
	    MAX-ACCESS  read-only
	    STATUS      current
	    DESCRIPTION "Certificate source type."
	    ::= {fextVPNCertificateLocalEntry 4}

	--
	-- fnFortiExtenderMib.fextHMon
	--
	-- fextHMonIntf ::= {fextHMon 1}
	-- fextHMonHchk ::= {fextHMon 2}
	--

	fextHMonIntf OBJECT-TYPE
		SYNTAX      SEQUENCE OF FextHMonIntfEntry
		MAX-ACCESS  read-only
		STATUS      current
		DESCRIPTION "Configure monitoring interfaces."
		::= {fextHMon 1}

	fextHMonHchk OBJECT-TYPE
		SYNTAX      SEQUENCE OF FextHMonHchkEntry
		MAX-ACCESS  read-only
		STATUS      current
		DESCRIPTION "Configure measuring latency/loss/jitter."
		::= {fextHMon 2}

	--
	-- fextHMon.fextHMonIntf
	--

	fextHMonIntfEntry OBJECT-TYPE
		SYNTAX      FextHMonIntfEntry
		MAX-ACCESS  not-accessible
		STATUS      current
		DESCRIPTION "An entry containing monitoring interface."
		INDEX       {fextHMonIntfIndex}
		::= {fextHMonIntf 1}

	FextHMonIntfEntry ::= SEQUENCE {
		fextHMonIntfIndex     FnIndex,
		fextHMonIntfName      DisplayString,
		fextHMonIntfInterval  DisplayString,
		fextHMonIntfInterface DisplayString,
		fextHMonIntfFilter    DisplayString
	}

	fextHMonIntfIndex OBJECT-TYPE
		SYNTAX      FnIndex
		MAX-ACCESS  not-accessible
		STATUS      current
		DESCRIPTION	"An index uniquely defining a monitoring interface."
		::= {fextHMonIntfEntry 1}

	fextHMonIntfName OBJECT-TYPE
	    SYNTAX      DisplayString
	    MAX-ACCESS  read-only
	    STATUS      current
	    DESCRIPTION "Name of the monitoring interface."
	    ::= {fextHMonIntfEntry 2}

	fextHMonIntfInterval OBJECT-TYPE
	    SYNTAX      DisplayString
	    MAX-ACCESS  read-only
	    STATUS      current
	    DESCRIPTION "Monitoring Interval in second."
	    ::= {fextHMonIntfEntry 3}

	fextHMonIntfInterface OBJECT-TYPE
	    SYNTAX      DisplayString
	    MAX-ACCESS  read-only
	    STATUS      current
	    DESCRIPTION "Interested interfaces."
	    ::= {fextHMonIntfEntry 4}

	fextHMonIntfFilter OBJECT-TYPE
	    SYNTAX      DisplayString
	    MAX-ACCESS  read-only
	    STATUS      current
	    DESCRIPTION "Interested fields."
	    ::= {fextHMonIntfEntry 5}

	--
	-- fextHMon.fextHMonHchk
	--

	fextHMonHchkEntry OBJECT-TYPE
		SYNTAX      FextHMonHchkEntry
		MAX-ACCESS  not-accessible
		STATUS      current
		DESCRIPTION "An entry containing measuring latency/loss/jitter."
		INDEX       {fextHMonHchkIndex}
		::= {fextHMonHchk 1}

	FextHMonHchkEntry ::= SEQUENCE {
		fextHMonHchkIndex        FnIndex,
		fextHMonHchkName         DisplayString,
		fextHMonHchkProtocol     DisplayString,
		fextHMonHchkInterval     DisplayString,
		fextHMonHchkProbeCnt     DisplayString,
		fextHMonHchkProbeTM      DisplayString,
		fextHMonHchkProbeTarget  DisplayString,
		fextHMonHchkPort         DisplayString,
		fextHMonHchkHTTPGet      DisplayString,
		fextHMonHchkInterface    DisplayString,
		fextHMonHchkSrcType      DisplayString,
		fextHMonHchkSrcInterface DisplayString,
		fextHMonHchkSrcIP        DisplayString,
		fextHMonHchkFilter       DisplayString
	}

	fextHMonHchkIndex OBJECT-TYPE
		SYNTAX      FnIndex
		MAX-ACCESS  not-accessible
		STATUS      current
		DESCRIPTION	"An index uniquely defining a measuring latency/loss/jitter."
		::= {fextHMonHchkEntry 1}

	fextHMonHchkName OBJECT-TYPE
	    SYNTAX      DisplayString
	    MAX-ACCESS  read-only
	    STATUS      current
	    DESCRIPTION "Name of the measuring latency/loss/jitter."
	    ::= {fextHMonHchkEntry 2}

	fextHMonHchkProtocol OBJECT-TYPE
	    SYNTAX      DisplayString
	    MAX-ACCESS  read-only
	    STATUS      current
	    DESCRIPTION "The protocol to use for status checks."
	    ::= {fextHMonHchkEntry 3}

	fextHMonHchkInterval OBJECT-TYPE
	    SYNTAX      DisplayString
	    MAX-ACCESS  read-only
	    STATUS      current
	    DESCRIPTION "Monitoring Interval in second."
	    ::= {fextHMonHchkEntry 4}

	fextHMonHchkProbeCnt OBJECT-TYPE
	    SYNTAX      DisplayString
	    MAX-ACCESS  read-only
	    STATUS      current
	    DESCRIPTION "Number of probes sent within an interval."
	    ::= {fextHMonHchkEntry 5}

	fextHMonHchkProbeTM OBJECT-TYPE
	    SYNTAX      DisplayString
	    MAX-ACCESS  read-only
	    STATUS      current
	    DESCRIPTION "Timeout for a probe in second."
	    ::= {fextHMonHchkEntry 6}

	fextHMonHchkProbeTarget OBJECT-TYPE
	    SYNTAX      DisplayString
	    MAX-ACCESS  read-only
	    STATUS      current
	    DESCRIPTION "IPv4 address or FQDN name of the target to which a probe
					 is sent."
	    ::= {fextHMonHchkEntry 7}

	fextHMonHchkPort OBJECT-TYPE
	    SYNTAX      DisplayString
	    MAX-ACCESS  read-only
	    STATUS      current
	    DESCRIPTION "Port number used to communicate with the server."
	    ::= {fextHMonHchkEntry 8}

	fextHMonHchkHTTPGet OBJECT-TYPE
	    SYNTAX      DisplayString
	    MAX-ACCESS  read-only
	    STATUS      current
	    DESCRIPTION "URL used to communicate with the server."
	    ::= {fextHMonHchkEntry 9}

	fextHMonHchkInterface OBJECT-TYPE
	    SYNTAX      DisplayString
	    MAX-ACCESS  read-only
	    STATUS      current
	    DESCRIPTION "Interested interfaces."
	    ::= {fextHMonHchkEntry 10}

	fextHMonHchkSrcType OBJECT-TYPE
	    SYNTAX      DisplayString
	    MAX-ACCESS  read-only
	    STATUS      current
	    DESCRIPTION "The way to set the source address for probes."
	    ::= {fextHMonHchkEntry 11}

	fextHMonHchkSrcInterface OBJECT-TYPE
	    SYNTAX      DisplayString
	    MAX-ACCESS  read-only
	    STATUS      current
	    DESCRIPTION "Source address derived from specified interfaces."
	    ::= {fextHMonHchkEntry 12}

	fextHMonHchkSrcIP OBJECT-TYPE
	    SYNTAX      DisplayString
	    MAX-ACCESS  read-only
	    STATUS      current
	    DESCRIPTION "Source IP address."
	    ::= {fextHMonHchkEntry 13}

	fextHMonHchkFilter OBJECT-TYPE
	    SYNTAX      DisplayString
	    MAX-ACCESS  read-only
	    STATUS      current
	    DESCRIPTION "Interested fields."
	    ::= {fextHMonHchkEntry 14}

	--
	-- fnFortiExtenderMib.fextSNMP
	--
	-- fextSNMPSysInfo   ::= {fextSNMP 1}
	-- fextSNMPCommunity ::= {fextSNMP 2}
	-- fextSNMPUser      ::= {fextSNMP 3}
	-- fextSNMPHost      ::= {fextSNMP 4}
	--

	fextSNMPSysInfo OBJECT-IDENTITY
		STATUS      current
		DESCRIPTION	"SNMP system info setting."
		::= {fextSNMP 1}

	fextSNMPCommunity OBJECT-TYPE
		SYNTAX      SEQUENCE OF FextSNMPCommunityEntry
		MAX-ACCESS  read-only
		STATUS      current
		DESCRIPTION "SNMP v1/v2c community setting."
		::= {fextSNMP 2}

	fextSNMPUser OBJECT-TYPE
		SYNTAX      SEQUENCE OF FextSNMPUserEntry
		MAX-ACCESS  not-accessible
		STATUS      current
		DESCRIPTION	"SNMP v3 user setting."
		::= {fextSNMP 3}

	fextSNMPHost OBJECT-TYPE
		SYNTAX      SEQUENCE OF FextSNMPHostEntry
		MAX-ACCESS  not-accessible
		STATUS      current
		DESCRIPTION	"SNMP hosts setting."
		::= {fextSNMP 4}

	--
	-- fextSNMP.fextSNMPSysInfo
	--
	-- fextSNMPSysInfoStatus      ::= {fextSNMPSysInfo 1}
	-- fextSNMPSysInfoDescription ::= {fextSNMPSysInfo 2}
	-- fextSNMPSysInfoContactInfo ::= {fextSNMPSysInfo 3}
	-- fextSNMPSysInfoLocation    ::= {fextSNMPSysInfo 4}
	--

	fextSNMPSysInfoStatus OBJECT-TYPE
	    SYNTAX      DisplayString
	    MAX-ACCESS  read-only
	    STATUS      current
		DESCRIPTION "Enable/disable SNMP service."
		::= {fextSNMPSysInfo 1}

	fextSNMPSysInfoDescription OBJECT-TYPE
	    SYNTAX      DisplayString
	    MAX-ACCESS  read-only
	    STATUS      current
		DESCRIPTION "System description."
		::= {fextSNMPSysInfo 2}

	fextSNMPSysInfoContactInfo OBJECT-TYPE
	    SYNTAX      DisplayString
	    MAX-ACCESS  read-only
	    STATUS      current
		DESCRIPTION "Contact information."
		::= {fextSNMPSysInfo 3}

	fextSNMPSysInfoLocation OBJECT-TYPE
	    SYNTAX      DisplayString
	    MAX-ACCESS  read-only
	    STATUS      current
		DESCRIPTION "System location."
		::= {fextSNMPSysInfo 4}

	--
	-- fextSNMP.fextSNMPCommunity
	--

	fextSNMPCommunityEntry OBJECT-TYPE
		SYNTAX      FextSNMPCommunityEntry
		MAX-ACCESS  not-accessible
		STATUS      current
		DESCRIPTION "An entry containing SNMP v1/v2c community setting."
		INDEX       {fextSNMPCommunityIndex}
		::= {fextSNMPCommunity 1}

	FextSNMPCommunityEntry ::= SEQUENCE {
		fextSNMPCommunityIndex          FnIndex,
		fextSNMPCommunityID             DisplayString,
		fextSNMPCommunityName           DisplayString,
		fextSNMPCommunityStatus         DisplayString,
		fextSNMPCommunityHosts          DisplayString,
		fextSNMPCommunityQueryV1Status  DisplayString,
		fextSNMPCommunityQueryV1Port    DisplayString,
		fextSNMPCommunityQueryV2CStatus DisplayString,
		fextSNMPCommunityQueryV2CPort   DisplayString,
		fextSNMPCommunityTrapV1Status   DisplayString,
		fextSNMPCommunityTrapV1LPort    DisplayString,
		fextSNMPCommunityTrapV1RPort    DisplayString,
		fextSNMPCommunityTrapV2CStatus  DisplayString,
		fextSNMPCommunityTrapV2CLPort   DisplayString,
		fextSNMPCommunityTrapV2CRPort   DisplayString,
		fextSNMPCommunityEvents         DisplayString
	}

	fextSNMPCommunityIndex OBJECT-TYPE
		SYNTAX      FnIndex
		MAX-ACCESS  not-accessible
		STATUS      current
		DESCRIPTION	"An index uniquely defining a SNMP community."
		::= {fextSNMPCommunityEntry 1}

	fextSNMPCommunityID OBJECT-TYPE
	    SYNTAX      DisplayString
	    MAX-ACCESS  read-only
	    STATUS      current
	    DESCRIPTION "The ID of the SNMP community."
	    ::= {fextSNMPCommunityEntry 2}

	fextSNMPCommunityName OBJECT-TYPE
	    SYNTAX      DisplayString
	    MAX-ACCESS  read-only
	    STATUS      current
	    DESCRIPTION "Name of the SNMP community."
	    ::= {fextSNMPCommunityEntry 3}

	fextSNMPCommunityStatus OBJECT-TYPE
	    SYNTAX      DisplayString
	    MAX-ACCESS  read-only
	    STATUS      current
	    DESCRIPTION "Enable/disable this SNMP community."
	    ::= {fextSNMPCommunityEntry 4}

	fextSNMPCommunityHosts OBJECT-TYPE
	    SYNTAX      DisplayString
	    MAX-ACCESS  read-only
	    STATUS      current
	    DESCRIPTION "Configure IPv4 SNMP managers."
	    ::= {fextSNMPCommunityEntry 5}

	fextSNMPCommunityQueryV1Status OBJECT-TYPE
	    SYNTAX      DisplayString
	    MAX-ACCESS  read-only
	    STATUS      current
	    DESCRIPTION "Enable/disable SNMP v1 queries."
	    ::= {fextSNMPCommunityEntry 6}

	fextSNMPCommunityQueryV1Port OBJECT-TYPE
	    SYNTAX      DisplayString
	    MAX-ACCESS  read-only
	    STATUS      current
	    DESCRIPTION "SNMP v1 query port."
	    ::= {fextSNMPCommunityEntry 7}

	fextSNMPCommunityQueryV2CStatus OBJECT-TYPE
	    SYNTAX      DisplayString
	    MAX-ACCESS  read-only
	    STATUS      current
	    DESCRIPTION "Enable/disable SNMP v2c queries."
	    ::= {fextSNMPCommunityEntry 8}

	fextSNMPCommunityQueryV2CPort OBJECT-TYPE
	    SYNTAX      DisplayString
	    MAX-ACCESS  read-only
	    STATUS      current
	    DESCRIPTION "SNMP v2c query port."
	    ::= {fextSNMPCommunityEntry 9}

	fextSNMPCommunityTrapV1Status OBJECT-TYPE
	    SYNTAX      DisplayString
	    MAX-ACCESS  read-only
	    STATUS      current
	    DESCRIPTION "Enable/disable SNMP v1 traps."
	    ::= {fextSNMPCommunityEntry 10}

	fextSNMPCommunityTrapV1LPort OBJECT-TYPE
	    SYNTAX      DisplayString
	    MAX-ACCESS  read-only
	    STATUS      current
	    DESCRIPTION "SNMP v1 trap local port."
	    ::= {fextSNMPCommunityEntry 11}

	fextSNMPCommunityTrapV1RPort OBJECT-TYPE
	    SYNTAX      DisplayString
	    MAX-ACCESS  read-only
	    STATUS      current
	    DESCRIPTION "SNMP v1 trap remote port."
	    ::= {fextSNMPCommunityEntry 12}

	fextSNMPCommunityTrapV2CStatus OBJECT-TYPE
	    SYNTAX      DisplayString
	    MAX-ACCESS  read-only
	    STATUS      current
	    DESCRIPTION "Enable/disable SNMP v2c traps."
	    ::= {fextSNMPCommunityEntry 13}

	fextSNMPCommunityTrapV2CLPort OBJECT-TYPE
	    SYNTAX      DisplayString
	    MAX-ACCESS  read-only
	    STATUS      current
	    DESCRIPTION "SNMP v2c trap local port."
	    ::= {fextSNMPCommunityEntry 14}

	fextSNMPCommunityTrapV2CRPort OBJECT-TYPE
	    SYNTAX      DisplayString
	    MAX-ACCESS  read-only
	    STATUS      current
	    DESCRIPTION "SNMP v2c trap remote port."
	    ::= {fextSNMPCommunityEntry 15}

	fextSNMPCommunityEvents OBJECT-TYPE
	    SYNTAX      DisplayString
	    MAX-ACCESS  read-only
	    STATUS      current
	    DESCRIPTION "SNMP trap events."
	    ::= {fextSNMPCommunityEntry 16}

	--
	-- fextSNMP.fextSNMPUser
	--

	fextSNMPUserEntry OBJECT-TYPE
		SYNTAX      FextSNMPUserEntry
		MAX-ACCESS  not-accessible
		STATUS      current
		DESCRIPTION "An entry containing SNMP v3 user setting."
		INDEX       {fextSNMPUserIndex}
		::= {fextSNMPUser 1}

	FextSNMPUserEntry ::= SEQUENCE {
		fextSNMPUserIndex         FnIndex,
		fextSNMPUserID            DisplayString,
		fextSNMPUserName          DisplayString,
		fextSNMPUserStatus        DisplayString,
		fextSNMPUserNotifyHosts   DisplayString,
		fextSNMPUserTrapStatus    DisplayString,
		fextSNMPUserTrapLPort     DisplayString,
		fextSNMPUserTrapRPort     DisplayString,
		fextSNMPUserQueryStatus   DisplayString,
		fextSNMPUserQueryPort     DisplayString,
		fextSNMPUserEvents        DisplayString,
		fextSNMPUserSecurityLevel DisplayString,
		fextSNMPUserAuthProtocol  DisplayString,
		fextSNMPUserAuthPWD       DisplayString,
		fextSNMPUserPrivProtocol  DisplayString,
		fextSNMPUserPrivPWD       DisplayString
	}

	fextSNMPUserIndex OBJECT-TYPE
		SYNTAX      FnIndex
		MAX-ACCESS  not-accessible
		STATUS      current
		DESCRIPTION	"An index uniquely defining a SNMP user."
		::= {fextSNMPUserEntry 1}

	fextSNMPUserID OBJECT-TYPE
	    SYNTAX      DisplayString
	    MAX-ACCESS  read-only
	    STATUS      current
	    DESCRIPTION "The ID of the SNMP user."
	    ::= {fextSNMPUserEntry 2}

	fextSNMPUserName OBJECT-TYPE
	    SYNTAX      DisplayString
	    MAX-ACCESS  read-only
	    STATUS      current
	    DESCRIPTION "Name of the SNMP user."
	    ::= {fextSNMPUserEntry 3}

	fextSNMPUserStatus OBJECT-TYPE
	    SYNTAX      DisplayString
	    MAX-ACCESS  read-only
	    STATUS      current
	    DESCRIPTION "Enable/disable this SNMP user."
	    ::= {fextSNMPUserEntry 4}

	fextSNMPUserNotifyHosts OBJECT-TYPE
	    SYNTAX      DisplayString
	    MAX-ACCESS  read-only
	    STATUS      current
	    DESCRIPTION "SNMP managers to send notifications (traps) to."
	    ::= {fextSNMPUserEntry 5}

	fextSNMPUserTrapStatus OBJECT-TYPE
	    SYNTAX      DisplayString
	    MAX-ACCESS  read-only
	    STATUS      current
	    DESCRIPTION "Enable/disable traps for this SNMP user."
	    ::= {fextSNMPUserEntry 6}

	fextSNMPUserTrapLPort OBJECT-TYPE
	    SYNTAX      DisplayString
	    MAX-ACCESS  read-only
	    STATUS      current
	    DESCRIPTION "SNMPv3 local trap port."
	    ::= {fextSNMPUserEntry 7}

	fextSNMPUserTrapRPort OBJECT-TYPE
	    SYNTAX      DisplayString
	    MAX-ACCESS  read-only
	    STATUS      current
	    DESCRIPTION "SNMPv3 trap remote port."
	    ::= {fextSNMPUserEntry 8}

	fextSNMPUserQueryStatus OBJECT-TYPE
	    SYNTAX      DisplayString
	    MAX-ACCESS  read-only
	    STATUS      current
	    DESCRIPTION "Enable/disable SNMP queries for this user."
	    ::= {fextSNMPUserEntry 9}

	fextSNMPUserQueryPort OBJECT-TYPE
	    SYNTAX      DisplayString
	    MAX-ACCESS  read-only
	    STATUS      current
	    DESCRIPTION "SNMPv3 query port."
	    ::= {fextSNMPUserEntry 10}

	fextSNMPUserEvents OBJECT-TYPE
	    SYNTAX      DisplayString
	    MAX-ACCESS  read-only
	    STATUS      current
	    DESCRIPTION "SNMP trap events."
	    ::= {fextSNMPUserEntry 11}

	fextSNMPUserSecurityLevel OBJECT-TYPE
	    SYNTAX      DisplayString
	    MAX-ACCESS  read-only
	    STATUS      current
	    DESCRIPTION "Security level for message authentication and encryption."
	    ::= {fextSNMPUserEntry 12}

	fextSNMPUserAuthProtocol OBJECT-TYPE
	    SYNTAX      DisplayString
	    MAX-ACCESS  read-only
	    STATUS      current
	    DESCRIPTION "Authentication protocol."
	    ::= {fextSNMPUserEntry 13}

	fextSNMPUserAuthPWD OBJECT-TYPE
	    SYNTAX      DisplayString
	    MAX-ACCESS  read-only
	    STATUS      current
	    DESCRIPTION "Password for authentication protocol."
	    ::= {fextSNMPUserEntry 14}

	fextSNMPUserPrivProtocol OBJECT-TYPE
	    SYNTAX      DisplayString
	    MAX-ACCESS  read-only
	    STATUS      current
	    DESCRIPTION "Privacy (encryption) protocol."
	    ::= {fextSNMPUserEntry 15}

	fextSNMPUserPrivPWD OBJECT-TYPE
	    SYNTAX      DisplayString
	    MAX-ACCESS  read-only
	    STATUS      current
	    DESCRIPTION "Password for privacy (encryption) protocol."
	    ::= {fextSNMPUserEntry 16}

	--
	-- fextSNMP.fextSNMPHost
	--

	fextSNMPHostEntry OBJECT-TYPE
		SYNTAX      FextSNMPHostEntry
		MAX-ACCESS  not-accessible
		STATUS      current
		DESCRIPTION "An entry containing SNMP host setting."
		INDEX       {fextSNMPHostIndex}
		::= {fextSNMPHost 1}

	FextSNMPHostEntry ::= SEQUENCE {
		fextSNMPHostIndex FnIndex,
		fextSNMPHostName  DisplayString,
		fextSNMPHostIP    DisplayString,
		fextSNMPHostType  DisplayString
	}

	fextSNMPHostIndex OBJECT-TYPE
		SYNTAX      FnIndex
		MAX-ACCESS  not-accessible
		STATUS      current
		DESCRIPTION	"An index uniquely defining a SNMP host."
		::= {fextSNMPHostEntry 1}

	fextSNMPHostName OBJECT-TYPE
	    SYNTAX      DisplayString
	    MAX-ACCESS  read-only
	    STATUS      current
	    DESCRIPTION "Name of the SNMP host."
	    ::= {fextSNMPHostEntry 2}

	fextSNMPHostIP OBJECT-TYPE
	    SYNTAX      DisplayString
	    MAX-ACCESS  read-only
	    STATUS      current
	    DESCRIPTION "IPv4 address of the SNMP manager."
	    ::= {fextSNMPHostEntry 3}

	fextSNMPHostType OBJECT-TYPE
	    SYNTAX      DisplayString
	    MAX-ACCESS  read-only
	    STATUS      current
	    DESCRIPTION "Control whether the SNMP manager sends SNMP queries,
					 receives SNMP traps, or both."
	    ::= {fextSNMPHostEntry 4}

	--
	-- fnFortiExtenderMib.fextInfo
	--
	-- fextInfoSystem   ::= {fextInfo 1}
	-- fextInfoExtender ::= {fextInfo 2}
	-- fextInfoModem	::= {fextInfo 3}
	-- fextInfoRouter	::= {fextInfo 4}
	-- fextInfoVWAN     ::= {fextInfo 5}
	-- fextInfoVPN		::= {fextInfo 6}
	-- fextInfoHMon	    ::= {fextInfo 7}
	-- fextInfoCPM      ::= {fextInfo 8}
	--

	fextInfoSystem	 OBJECT IDENTIFIER ::= {fextInfo 1}
	fextInfoExtender OBJECT IDENTIFIER ::= {fextInfo 2}
	fextInfoModem	 OBJECT IDENTIFIER ::= {fextInfo 3}
	fextInfoRouter	 OBJECT IDENTIFIER ::= {fextInfo 4}
	fextInfoVWAN     OBJECT IDENTIFIER ::= {fextInfo 5}
	fextInfoVPN	     OBJECT IDENTIFIER ::= {fextInfo 6}
	fextInfoHMon	 OBJECT IDENTIFIER ::= {fextInfo 7}
	fextInfoCPM	     OBJECT IDENTIFIER ::= {fextInfo 8}

	--
	-- fextInfo.fextInfoSystem
	--
	-- fextInfoVersion    ::= {fextInfoSystem 1}
	-- fextInfoStatus     ::= {fextInfoSystem 2}
	-- fextInfoInterface  ::= {fextInfoSystem 3}
	-- fextInfoDHCPServer ::= {fextInfoSystem 4}
	-- fextInfoDHCPClient ::= {fextInfoSystem 5}
	-- fextInfoDNS        ::= {fextInfoSystem 6}
	--

	fextInfoVersion OBJECT-IDENTITY
		STATUS      current
		DESCRIPTION	"System version information."
		::=	{fextInfoSystem 1}

	fextInfoStatus OBJECT-IDENTITY
		STATUS      current
		DESCRIPTION	"System status information."
		::=	{fextInfoSystem 2}

	fextInfoInterface OBJECT-TYPE
		SYNTAX      SEQUENCE OF FextInfoInterfaceEntry
		MAX-ACCESS  not-accessible
		STATUS      current
		DESCRIPTION	"FortiExtender specific extension to MIB-2 ifTable."
		::=	{fextInfoSystem 3}

	fextInfoDHCPServer OBJECT-IDENTITY
		STATUS      current
		DESCRIPTION	"System DHCP servers information."
		::=	{fextInfoSystem 4}

	fextInfoDHCPClient OBJECT-TYPE
		SYNTAX      SEQUENCE OF FextInfoDHCPClientEntry
		MAX-ACCESS  not-accessible
		STATUS      current
		DESCRIPTION	"System DHCP clients information."
		::=	{fextInfoSystem 5}

	fextInfoDNS OBJECT-TYPE
		SYNTAX      SEQUENCE OF FextInfoDNSEntry
		MAX-ACCESS  not-accessible
		STATUS      current
		DESCRIPTION	"DNS servers information."
		::=	{fextInfoSystem 6}

	--
	-- fextInfoSystem.fextInfoVersion
	--
	-- fextInfoImage             ::= {fextInfoVersion 1}
	-- fextInfoImageType         ::= {fextInfoVersion 2}
	-- fextInfoModel             ::= {fextInfoVersion 3}
	-- fextInfoMAC               ::= {fextInfoVersion 4}
	-- fextInfoSN                ::= {fextInfoVersion 5}
	-- fextInfoLicense           ::= {fextInfoVersion 6}
	-- fextInfoOEMSN             ::= {fextInfoVersion 7}
	-- fextInfoREV               ::= {fextInfoVersion 8}
	-- fextInfoVERSION           ::= {fextInfoVersion 9}
	-- fextInfoROMREV            ::= {fextInfoVersion 10}
	-- fextInfoFallbackImage     ::= {fextInfoVersion 11}
	-- fextInfoFallbackImageType ::= {fextInfoVersion 12}
	--

	fextInfoImage OBJECT-TYPE
	    SYNTAX      DisplayString
	    MAX-ACCESS  read-only
	    STATUS      current
		DESCRIPTION "System image version."
		::= {fextInfoVersion 1}

	fextInfoImageType OBJECT-TYPE
	    SYNTAX      DisplayString
	    MAX-ACCESS  read-only
	    STATUS      current
		DESCRIPTION "System image type."
		::= {fextInfoVersion 2}

	fextInfoModel OBJECT-TYPE
	    SYNTAX      DisplayString
	    MAX-ACCESS  read-only
	    STATUS      current
		DESCRIPTION "System model."
		::= {fextInfoVersion 3}

	fextInfoMAC OBJECT-TYPE
	    SYNTAX      DisplayString
	    MAX-ACCESS  read-only
	    STATUS      current
		DESCRIPTION "System MAC address."
		::= {fextInfoVersion 4}

	fextInfoSN OBJECT-TYPE
	    SYNTAX      DisplayString
	    MAX-ACCESS  read-only
	    STATUS      current
		DESCRIPTION "System SN."
		::= {fextInfoVersion 5}

	fextInfoLicense OBJECT-TYPE
	    SYNTAX      DisplayString
	    MAX-ACCESS  read-only
	    STATUS      current
		DESCRIPTION "System license information."
		::= {fextInfoVersion 6}

	fextInfoOEMSN OBJECT-TYPE
	    SYNTAX      DisplayString
	    MAX-ACCESS  read-only
	    STATUS      current
		DESCRIPTION "System OEM SN."
		::= {fextInfoVersion 7}

	fextInfoREV OBJECT-TYPE
	    SYNTAX      DisplayString
	    MAX-ACCESS  read-only
	    STATUS      current
		DESCRIPTION "System REV information."
		::= {fextInfoVersion 8}

	fextInfoVERSION OBJECT-TYPE
	    SYNTAX      DisplayString
	    MAX-ACCESS  read-only
	    STATUS      current
		DESCRIPTION "System VERSION information."
		::= {fextInfoVersion 9}

	fextInfoROMREV OBJECT-TYPE
	    SYNTAX      DisplayString
	    MAX-ACCESS  read-only
	    STATUS      current
		DESCRIPTION "System ROM REV information."
		::= {fextInfoVersion 10}

	fextInfoFallbackImage OBJECT-TYPE
	    SYNTAX      DisplayString
	    MAX-ACCESS  read-only
	    STATUS      current
		DESCRIPTION "System fallback image version."
		::= {fextInfoVersion 11}

	fextInfoFallbackImageType OBJECT-TYPE
	    SYNTAX      DisplayString
	    MAX-ACCESS  read-only
	    STATUS      current
		DESCRIPTION "System fallback image type."
		::= {fextInfoVersion 12}

	--
	-- fextInfoSystem.fextInfoStatus
	--
	-- fextInfoCPUUsage ::= {fextInfoStatus 1}
	-- fextInfoMemUsage ::= {fextInfoStatus 2}
	-- fextInfoUptime   ::= {fextInfoStatus 3}
	--

	fextInfoCPUUsage OBJECT-TYPE
	    SYNTAX      Integer32
	    MAX-ACCESS  read-only
	    STATUS      current
		DESCRIPTION "CPU usage information."
		::= {fextInfoStatus 1}

	fextInfoMemUsage OBJECT-TYPE
	    SYNTAX      Integer32
	    MAX-ACCESS  read-only
	    STATUS      current
		DESCRIPTION "Memory usage information."
		::= {fextInfoStatus 2}

	fextInfoUptime OBJECT-TYPE
	    SYNTAX      DisplayString
	    MAX-ACCESS  read-only
	    STATUS      current
		DESCRIPTION "System uptime information."
		::= {fextInfoStatus 3}

	--
	-- fextInfoSystem.fextInfoInterface
	--

	fextInfoInterfaceEntry OBJECT-TYPE
		SYNTAX      FextInfoInterfaceEntry
		MAX-ACCESS  not-accessible
		STATUS      current
		DESCRIPTION "FortiExtender specific information about an ifEntry. This
					 table augments the standard ifTable, so the same indexing
					 is used."
		AUGMENTS    {ifEntry}
		::= {fextInfoInterface 1}

	FextInfoInterfaceEntry ::= SEQUENCE {
		fextInfoInterfaceName	 DisplayString,
	 --	fextInfoInterfaceStatus	 FextOptionUpDown,
		fextInfoInterfaceStatus	 DisplayString,
	 --	fextInfoInterfaceType	 FextOptionInterfaceType,
		fextInfoInterfaceType	 DisplayString,
		-- fextInfoInterfaceMAC	 (ifPhysAddress, 1.3.6.1.2.1.2.2.1.6)
	 --	fextInfoInterfaceMode	 FextOptionInterfaceMode,
		fextInfoInterfaceMode	 DisplayString,
		fextInfoInterfaceIP		 DisplayString,
		-- fextInfoInterfaceMTU	 (ifMtu 1.3.6.1.2.1.2.2.1.4)
		fextInfoInterfaceGateway DisplayString
	}

	fextInfoInterfaceName OBJECT-TYPE
	    SYNTAX      DisplayString
	    MAX-ACCESS  read-only
	    STATUS      current
	    DESCRIPTION "The name of interface."
	    ::= {fextInfoInterfaceEntry 1}

	fextInfoInterfaceStatus OBJECT-TYPE
	 -- SYNTAX      FextOptionUpDown
	    SYNTAX      DisplayString
	    MAX-ACCESS  read-only
	    STATUS      current
	    DESCRIPTION "The status and link status of interface."
	    ::= {fextInfoInterfaceEntry 2}

	fextInfoInterfaceType OBJECT-TYPE
	 -- SYNTAX      FextOptionInterfaceType
	    SYNTAX      DisplayString
	    MAX-ACCESS  read-only
	    STATUS      current
	    DESCRIPTION "The Interface Type."
	    ::= {fextInfoInterfaceEntry 3}

	-- fextInfoInterfaceMAC OBJECT-TYPE
	--     SYNTAX      DisplayString
	--     MAX-ACCESS  read-only
	--     STATUS      current
	--     DESCRIPTION "The interface MAC address."
	--     (ifPhysAddress, 1.3.6.1.2.1.2.2.1.6)

	fextInfoInterfaceMode OBJECT-TYPE
	 -- SYNTAX      FextOptionInterfaceMode
	    SYNTAX      DisplayString
	    MAX-ACCESS  read-only
	    STATUS      current
	    DESCRIPTION "The interface addressing mode."
	    ::= {fextInfoInterfaceEntry 4}

	fextInfoInterfaceIP OBJECT-TYPE
	    SYNTAX      DisplayString
	    MAX-ACCESS  read-only
	    STATUS      current
	    DESCRIPTION "Interface IPv4 address and subnet mask."
	    ::= {fextInfoInterfaceEntry 5}

	-- fextInfoInterfaceMTU OBJECT-TYPE
	--     SYNTAX      Integer32 (512..1500)
	--     MAX-ACCESS  read-only
	--     STATUS      current
	--     DESCRIPTION "The MTU value of interface."
	--     (ifMtu 1.3.6.1.2.1.2.2.1.4)

	fextInfoInterfaceGateway OBJECT-TYPE
	    SYNTAX      DisplayString
	    MAX-ACCESS  read-only
	    STATUS      current
	    DESCRIPTION "Interface's connected Gateway."
	    ::= {fextInfoInterfaceEntry 6}

	--
	-- fextInfoSystem.fextInfoDHCPServer
	--
	-- fextInfoDHCPServerConfig ::= {fextInfoDHCPServer 1}
	-- fextInfoDHCPServerClient ::= {fextInfoDHCPServer 2}
	--

	fextInfoDHCPServerConfig OBJECT-TYPE
	    SYNTAX      SEQUENCE OF FextInfoDHCPServerEntry
	    MAX-ACCESS  not-accessible
	    STATUS      current
		DESCRIPTION "System DHCP servers' configuration information."
		::= {fextInfoDHCPServer 1}

	fextInfoDHCPServerClient OBJECT-TYPE
	    SYNTAX      SEQUENCE OF FextInfoDHCPServerClientEntry
	    MAX-ACCESS  not-accessible
	    STATUS      current
		DESCRIPTION "System DHCP servers' clients list."
		::= {fextInfoDHCPServer 2}

	--
	-- fextInfoDHCPServer.fextInfoDHCPServerConfig
	--

	fextInfoDHCPServerEntry OBJECT-TYPE
		SYNTAX      FextInfoDHCPServerEntry
		MAX-ACCESS  not-accessible
		STATUS      current
		DESCRIPTION "An entry containing DHCP Server configuration information."
		INDEX       {fextInfoDHCPServerIndex}
		::= {fextInfoDHCPServerConfig 1}

	FextInfoDHCPServerEntry ::= SEQUENCE {
		fextInfoDHCPServerIndex	    FnIndex,
		fextInfoDHCPServerName	    DisplayString,
	 --	fextInfoDHCPServerStatus	FextOptionEnableDisable,
		fextInfoDHCPServerStatus	DisplayString,
		fextInfoDHCPServerLeaseTime	Integer32,
		fextInfoDHCPServerInterface	DisplayString,
	 --	fextInfoDHCPServerDNS		FextOptionDHCPServerDNS,
		fextInfoDHCPServerDNS		DisplayString,
		fextInfoDHCPServerDNSServer	DisplayString,
	 --	fextInfoDHCPServerNTP		FextOptionDHCPServerNTP,
		fextInfoDHCPServerNTP		DisplayString,
		fextInfoDHCPServerNTPServer	DisplayString,
		fextInfoDHCPServerGatewayIP	DisplayString,
		fextInfoDHCPServerIPRange	DisplayString,
		fextInfoDHCPServerNetmask	DisplayString
	}

	fextInfoDHCPServerIndex OBJECT-TYPE
		SYNTAX      FnIndex
		MAX-ACCESS  not-accessible
		STATUS      current
		DESCRIPTION	"An index uniquely defining a DHCP Server."
		::= {fextInfoDHCPServerEntry 1}

	fextInfoDHCPServerName OBJECT-TYPE
	    SYNTAX      DisplayString
	    MAX-ACCESS  read-only
	    STATUS      current
	    DESCRIPTION "The name of DHCP Server."
	    ::= {fextInfoDHCPServerEntry 2}

	fextInfoDHCPServerStatus OBJECT-TYPE
	 -- SYNTAX      FextOptionEnableDisable
		SYNTAX      DisplayString
	    MAX-ACCESS  read-only
	    STATUS      current
	    DESCRIPTION "DHCP Server enable/disable status."
	    ::= {fextInfoDHCPServerEntry 3}

	fextInfoDHCPServerLeaseTime OBJECT-TYPE
	    SYNTAX      Integer32 (300..8640000)
	    MAX-ACCESS  read-only
	    STATUS      current
	    DESCRIPTION "Lease time in seconds."
	    ::= {fextInfoDHCPServerEntry 4}

	fextInfoDHCPServerInterface OBJECT-TYPE
	    SYNTAX      DisplayString
	    MAX-ACCESS  read-only
	    STATUS      current
	    DESCRIPTION "The interface the clients connected to which DHCP server
					 can assign IP to."
	    ::= {fextInfoDHCPServerEntry 5}

	fextInfoDHCPServerDNS OBJECT-TYPE
	 -- SYNTAX      FextOptionDHCPServerDNS
		SYNTAX      DisplayString
	    MAX-ACCESS  read-only
	    STATUS      current
	    DESCRIPTION "DNS servers option."
	    ::= {fextInfoDHCPServerEntry 6}

	fextInfoDHCPServerDNSServer OBJECT-TYPE
	    SYNTAX      DisplayString
	    MAX-ACCESS  read-only
	    STATUS      current
	    DESCRIPTION "DNS server."
	    ::= {fextInfoDHCPServerEntry 7}

	fextInfoDHCPServerNTP OBJECT-TYPE
	 -- SYNTAX      FextOptionDHCPServerNTP
		SYNTAX      DisplayString
	    MAX-ACCESS  read-only
	    STATUS      current
	    DESCRIPTION "NTP servers option."
	    ::= {fextInfoDHCPServerEntry 8}

	fextInfoDHCPServerNTPServer OBJECT-TYPE
	    SYNTAX      DisplayString
	    MAX-ACCESS  read-only
	    STATUS      current
	    DESCRIPTION "NTP server."
	    ::= {fextInfoDHCPServerEntry 9}

	fextInfoDHCPServerGatewayIP OBJECT-TYPE
	    SYNTAX      DisplayString
	    MAX-ACCESS  read-only
	    STATUS      current
	    DESCRIPTION "Gateway IP address."
	    ::= {fextInfoDHCPServerEntry 10}

	fextInfoDHCPServerIPRange OBJECT-TYPE
	    SYNTAX      DisplayString
	    MAX-ACCESS  read-only
	    STATUS      current
	    DESCRIPTION "IP range the DHCP can assign to clients."
	    ::= {fextInfoDHCPServerEntry 11}

	fextInfoDHCPServerNetmask OBJECT-TYPE
	    SYNTAX      DisplayString
	    MAX-ACCESS  read-only
	    STATUS      current
	    DESCRIPTION "Netmask assigned by the DHCP server."
	    ::= {fextInfoDHCPServerEntry 12}

	--
	-- fextInfoDHCPServer.fextInfoDHCPServerClient
	--

	fextInfoDHCPServerClientEntry OBJECT-TYPE
		SYNTAX      FextInfoDHCPServerClientEntry
		MAX-ACCESS  not-accessible
		STATUS      current
		DESCRIPTION "An entry containing DHCP Server's client information."
		INDEX       {fextInfoDHCPServerClientIndex}
		::= {fextInfoDHCPServerClient 1}

	FextInfoDHCPServerClientEntry ::= SEQUENCE {
		fextInfoDHCPServerClientIndex	  FnIndex,
		fextInfoDHCPServerClientMAC       DisplayString,
		fextInfoDHCPServerClientIP		  DisplayString,
		fextInfoDHCPServerClientHost	  DisplayString,
		fextInfoDHCPServerClientLeaseTime DisplayString
	}

	fextInfoDHCPServerClientIndex OBJECT-TYPE
		SYNTAX      FnIndex
		MAX-ACCESS  not-accessible
		STATUS      current
		DESCRIPTION	"An index uniquely defining a DHCP Server's client."
		::= {fextInfoDHCPServerClientEntry 1}

	fextInfoDHCPServerClientMAC OBJECT-TYPE
	    SYNTAX      DisplayString
	    MAX-ACCESS  read-only
	    STATUS      current
	    DESCRIPTION "Client MAC address."
	    ::= {fextInfoDHCPServerClientEntry 2}

	fextInfoDHCPServerClientIP OBJECT-TYPE
	    SYNTAX      DisplayString
	    MAX-ACCESS  read-only
	    STATUS      current
	    DESCRIPTION "Client IP address."
	    ::= {fextInfoDHCPServerClientEntry 3}

	fextInfoDHCPServerClientHost OBJECT-TYPE
	    SYNTAX      DisplayString
	    MAX-ACCESS  read-only
	    STATUS      current
	    DESCRIPTION "Client Hostname."
	    ::= {fextInfoDHCPServerClientEntry 4}

	fextInfoDHCPServerClientLeaseTime OBJECT-TYPE
	    SYNTAX      DisplayString
	    MAX-ACCESS  read-only
	    STATUS      current
	    DESCRIPTION "Remaining Lease time."
	    ::= {fextInfoDHCPServerClientEntry 5}

	--
	-- fextInfoSystem.fextInfoDHCPClient
	--

	fextInfoDHCPClientEntry OBJECT-TYPE
		SYNTAX      FextInfoDHCPClientEntry
		MAX-ACCESS  not-accessible
		STATUS      current
		DESCRIPTION "An entry containing DHCP Client Leasing information."
		INDEX       {fextInfoDHCPClientIndex}
		::= {fextInfoDHCPClient 1}

	FextInfoDHCPClientEntry ::= SEQUENCE {
		fextInfoDHCPClientIndex	    FnIndex,
		fextInfoDHCPClientInterface DisplayString,
		fextInfoDHCPClientIP		DisplayString,
		fextInfoDHCPClientNetmask	DisplayString,
		fextInfoDHCPClientGatewayIP DisplayString,
		fextInfoDHCPClientDNSServer DisplayString,
		fextInfoDHCPClientLeaseTime Integer32,
		fextInfoDHCPClientLeftTime  Integer32
	}

	fextInfoDHCPClientIndex OBJECT-TYPE
		SYNTAX      FnIndex
		MAX-ACCESS  not-accessible
		STATUS      current
		DESCRIPTION	"An index uniquely defining a DHCP client."
		::= {fextInfoDHCPClientEntry 1}

	fextInfoDHCPClientInterface OBJECT-TYPE
	    SYNTAX      DisplayString
	    MAX-ACCESS  read-only
	    STATUS      current
	    DESCRIPTION "The interface the client connected to."
	    ::= {fextInfoDHCPClientEntry 2}

	fextInfoDHCPClientIP OBJECT-TYPE
	    SYNTAX      DisplayString
	    MAX-ACCESS  read-only
	    STATUS      current
	    DESCRIPTION "Client IP address."
	    ::= {fextInfoDHCPClientEntry 3}

	fextInfoDHCPClientNetmask OBJECT-TYPE
	    SYNTAX      DisplayString
	    MAX-ACCESS  read-only
	    STATUS      current
	    DESCRIPTION "Netmask assigned by the DHCP server."
	    ::= {fextInfoDHCPClientEntry 4}

	fextInfoDHCPClientGatewayIP OBJECT-TYPE
	    SYNTAX      DisplayString
	    MAX-ACCESS  read-only
	    STATUS      current
	    DESCRIPTION "Gateway IP address."
	    ::= {fextInfoDHCPClientEntry 5}

	fextInfoDHCPClientDNSServer OBJECT-TYPE
	    SYNTAX      DisplayString
	    MAX-ACCESS  read-only
	    STATUS      current
	    DESCRIPTION "DNS server."
	    ::= {fextInfoDHCPClientEntry 6}

	fextInfoDHCPClientLeaseTime OBJECT-TYPE
	    SYNTAX      Integer32 (300..8640000)
	    MAX-ACCESS  read-only
	    STATUS      current
	    DESCRIPTION "Lease time in seconds."
	    ::= {fextInfoDHCPClientEntry 7}

	fextInfoDHCPClientLeftTime OBJECT-TYPE
	    SYNTAX      Integer32 (300..8640000)
	    MAX-ACCESS  read-only
	    STATUS      current
	    DESCRIPTION "Lease expired time in seconds."
	    ::= {fextInfoDHCPClientEntry 8}

	--
	-- fextInfoSystem.fextInfoDNS
	--

	fextInfoDNSEntry OBJECT-TYPE
		SYNTAX      FextInfoDNSEntry
		MAX-ACCESS  not-accessible
		STATUS      current
		DESCRIPTION "An entry containing DNS server information."
		INDEX       {fextInfoDNSIndex}
		::= {fextInfoDNS 1}

	FextInfoDNSEntry ::= SEQUENCE {
		fextInfoDNSIndex FnIndex,
		fextInfoDNSType  DisplayString,
		fextInfoDNSIP	 DisplayString,
        fextInfoDNSInterface    DisplayString
	}

	fextInfoDNSIndex OBJECT-TYPE
		SYNTAX      FnIndex
		MAX-ACCESS  not-accessible
		STATUS      current
		DESCRIPTION	"An index uniquely defining a DNS server."
		::= {fextInfoDNSEntry 1}

	fextInfoDNSType OBJECT-TYPE
	    SYNTAX      DisplayString
	    MAX-ACCESS  read-only
	    STATUS      current
	    DESCRIPTION "The type of DNS server."
	    ::= {fextInfoDNSEntry 2}

	fextInfoDNSIP OBJECT-TYPE
	    SYNTAX      DisplayString
	    MAX-ACCESS  read-only
	    STATUS      current
	    DESCRIPTION "DNS server IP address."
	    ::= {fextInfoDNSEntry 3}

    fextInfoDNSInterface OBJECT-TYPE
        SYNTAX      DisplayString
        MAX-ACCESS  read-only
        STATUS      current
        DESCRIPTION "The interface through which the DNS server IP is acquired."
        ::= {fextInfoDNSEntry 4}

	--
	-- fextInfo.fextInfoExtender
	--
	-- fextInfoEXTDStatus ::= {fextInfoExtender 1}
	--

	fextInfoEXTDStatus OBJECT-IDENTITY
		STATUS      current
		DESCRIPTION	"Extenderd opeartion status."
		::=	{fextInfoExtender 1}

	--
	-- fextInfoExtender.fextInfoEXTDStatus
	--
	-- fextInfoEXTDHostname          ::= {fextInfoEXTDStatus 1}
	-- fextInfoEXTDMode              ::= {fextInfoEXTDStatus 2}
	-- fextInfoEXTDADDR              ::= {fextInfoEXTDStatus 3}
	-- fextInfoEXTDWANADDR           ::= {fextInfoEXTDStatus 4}
	-- fextInfoEXTDController        ::= {fextInfoEXTDStatus 5}
	-- fextInfoEXTDControllerName    ::= {fextInfoEXTDStatus 6}
	-- fextInfoEXTDDeployed          ::= {fextInfoEXTDStatus 7}
	-- fextInfoEXTDAccount           ::= {fextInfoEXTDStatus 8}
	-- fextInfoEXTDUptime            ::= {fextInfoEXTDStatus 9}
	-- fextInfoEXTDMGMTState         ::= {fextInfoEXTDStatus 10}
	-- fextInfoEXTDMAC               ::= {fextInfoEXTDStatus 11}
	-- fextInfoEXTDNetworkMode       ::= {fextInfoEXTDStatus 12}
	-- fextInfoEXTDFGTBackupMode     ::= {fextInfoEXTDStatus 13}
	-- fextInfoEXTDDiscoveryType     ::= {fextInfoEXTDStatus 14}
	-- fextInfoEXTDDiscoveryInterval ::= {fextInfoEXTDStatus 15}
	-- fextInfoEXTDEchoInterval      ::= {fextInfoEXTDStatus 16}
	-- fextInfoEXTDReportInterval    ::= {fextInfoEXTDStatus 17}
	-- fextInfoEXTDStatsInterval     ::= {fextInfoEXTDStatus 18}
	-- fextInfoEXTDMDMFWServer       ::= {fextInfoEXTDStatus 19}
	-- fextInfoEXTDOSFWServer        ::= {fextInfoEXTDStatus 20}
	--

	fextInfoEXTDHostName OBJECT-TYPE
	    SYNTAX      DisplayString
	    MAX-ACCESS  read-only
	    STATUS      current
		DESCRIPTION "System Hostname."
		::= {fextInfoEXTDStatus 1}

	fextInfoEXTDMode OBJECT-TYPE
	 --	SYNTAX      FextOptionInfoManagementType
		SYNTAX      DisplayString
		MAX-ACCESS  read-only
		STATUS      current
		DESCRIPTION "System control management mode."
		::= {fextInfoEXTDStatus 2}

	fextInfoEXTDADDR OBJECT-TYPE
	    SYNTAX      DisplayString
	    MAX-ACCESS  read-only
	    STATUS      current
	    DESCRIPTION "System control management IP address."
	    ::= {fextInfoEXTDStatus 3}

	fextInfoEXTDWANADDR OBJECT-TYPE
	    SYNTAX      DisplayString
	    MAX-ACCESS  read-only
	    STATUS      current
	    DESCRIPTION "Management controller IP address."
	    ::= {fextInfoEXTDStatus 4}

	fextInfoEXTDController OBJECT-TYPE
		SYNTAX      DisplayString
		MAX-ACCESS  read-only
		STATUS      current
		DESCRIPTION "Management controller URL."
		::= {fextInfoEXTDStatus 5}

	fextInfoEXTDControllerName OBJECT-TYPE
		SYNTAX      DisplayString
		MAX-ACCESS  read-only
		STATUS      current
		DESCRIPTION "Management controller name."
		::= {fextInfoEXTDStatus 6}

	fextInfoEXTDDeployed OBJECT-TYPE
		SYNTAX      DisplayString
		MAX-ACCESS  read-only
		STATUS      current
		DESCRIPTION "Cloud Management deployment status."
		::= {fextInfoEXTDStatus 7}

	fextInfoEXTDAccount OBJECT-TYPE
		SYNTAX      Integer32
		MAX-ACCESS  read-only
		STATUS      current
		DESCRIPTION "Cloud Management account information."
		::= {fextInfoEXTDStatus 8}

	fextInfoEXTDUptime OBJECT-TYPE
		SYNTAX      Integer32
		MAX-ACCESS  read-only
		STATUS      current
		DESCRIPTION "System up time under management."
		::= {fextInfoEXTDStatus 9}

	fextInfoEXTDMGMTState OBJECT-TYPE
		SYNTAX      DisplayString
		MAX-ACCESS  read-only
		STATUS      current
		DESCRIPTION "Management controller URL."
		::= {fextInfoEXTDStatus 10}

	fextInfoEXTDMAC OBJECT-TYPE
		SYNTAX      DisplayString
		MAX-ACCESS  read-only
		STATUS      current
		DESCRIPTION "Systme MAC address."
		::= {fextInfoEXTDStatus 11}

	fextInfoEXTDNetworkMode OBJECT-TYPE
	 --	SYNTAX      FextOptionInfoNetworkMode
		SYNTAX      DisplayString
		MAX-ACCESS  read-only
		STATUS      current
		DESCRIPTION "System network operation mode."
		::= {fextInfoEXTDStatus 12}

	fextInfoEXTDFGTBackupMode OBJECT-TYPE
		SYNTAX      DisplayString
		MAX-ACCESS  read-only
		STATUS      current
		DESCRIPTION "Systme Backup support status to FortiGate."
		::= {fextInfoEXTDStatus 13}

	fextInfoEXTDDiscoveryType OBJECT-TYPE
		SYNTAX      DisplayString
		MAX-ACCESS  read-only
		STATUS      current
		DESCRIPTION "Control Management discovery type."
		::= {fextInfoEXTDStatus 14}

	fextInfoEXTDDiscoveryInterval OBJECT-TYPE
		SYNTAX      Integer32
		MAX-ACCESS  read-only
		STATUS      current
		DESCRIPTION "Control Management attempting interval."
		::= {fextInfoEXTDStatus 15}

	fextInfoEXTDEchoInterval OBJECT-TYPE
		SYNTAX      Integer32
		MAX-ACCESS  read-only
		STATUS      current
		DESCRIPTION "System Management echo interval."
		::= {fextInfoEXTDStatus 16}

	fextInfoEXTDReportInterval OBJECT-TYPE
		SYNTAX      Integer32
		MAX-ACCESS  read-only
		STATUS      current
		DESCRIPTION "System Management status report interval."
		::= {fextInfoEXTDStatus 17}

	fextInfoEXTDStatsInterval OBJECT-TYPE
		SYNTAX      Integer32
		MAX-ACCESS  read-only
		STATUS      current
		DESCRIPTION "System Management statistics report interval."
		::= {fextInfoEXTDStatus 18}

	fextInfoEXTDMDMFWServer OBJECT-TYPE
		SYNTAX      DisplayString
		MAX-ACCESS  read-only
		STATUS      current
		DESCRIPTION "System Modem firmware downloading server URL."
		::= {fextInfoEXTDStatus 19}

	fextInfoEXTDOSFWServer OBJECT-TYPE
		SYNTAX      DisplayString
		MAX-ACCESS  read-only
		STATUS      current
		DESCRIPTION "System OS firmware downloading server URL."
		::= {fextInfoEXTDStatus 20}

    --
    -- fextInfo.fextInfoModem
    --
    -- fextInfoModemStatus    ::= {fextInfoModem 1}
    -- fextInfoModemFWVersion ::= {fextInfoModem 2}
    -- fextInfoModemDataUsage ::= {fextInfoModem 3}
    --

    fextInfoModemStatus OBJECT-TYPE
        SYNTAX      SEQUENCE OF FextInfoModemStatusEntry
        MAX-ACCESS  not-accessible
        STATUS      current
        DESCRIPTION "Modem status."
        ::= {fextInfoModem 1}

    fextInfoModemFWVersion OBJECT-IDENTITY
        STATUS      current
        DESCRIPTION "Modem firmware version."
        ::= {fextInfoModem 2}

    fextInfoModemDataUsage OBJECT-TYPE
        SYNTAX      SEQUENCE OF FextInfoModemDataUsageEntry
        MAX-ACCESS  not-accessible
        STATUS      current
        DESCRIPTION "Modem data usage."
        ::= {fextInfoModem 3}

    --
    -- fextInfoModem.fextInfoModemStatus
    --

    fextInfoModemStatusEntry OBJECT-TYPE
        SYNTAX      FextInfoModemStatusEntry
        MAX-ACCESS  not-accessible
        STATUS      current
        DESCRIPTION "FortiExtender Modem status."
        INDEX       {fextInfoModemStatusIndex}
        ::= {fextInfoModemStatus 1}

    FextInfoModemStatusEntry ::= SEQUENCE {
        fextInfoModemStatusIndex          FnIndex,
        fextInfoModemStatusModem          DisplayString,
        fextInfoModemStatusUSBPath        DisplayString,
        fextInfoModemStatusVender         DisplayString,
        fextInfoModemStatusProduct        DisplayString,
        fextInfoModemStatusModel          DisplayString,
        fextInfoModemStatusSIMSlot        DisplayString,
        fextInfoModemStatusRevision       DisplayString,
        fextInfoModemStatusIMEI           DisplayString,
        fextInfoModemStatusICCID          DisplayString,
        fextInfoModemStatusIMSI           DisplayString,
        fextInfoModemStatusPinStatus      DisplayString,
        fextInfoModemStatusPinCode        DisplayString,
        fextInfoModemStatusCarrier        DisplayString,
        fextInfoModemStatusAPN            DisplayString,
        fextInfoModemStatusService        DisplayString,
        fextInfoModemStatusPhoneNumber    DisplayString,
        fextInfoModemStatusSIM1Pin        DisplayString,
        fextInfoModemStatusSIM1Puk        DisplayString,
        fextInfoModemStatusSIM2Pin        DisplayString,
        fextInfoModemStatusSIM2Puk        DisplayString,
        fextInfoModemStatusRSSI           DisplayString,
        fextInfoModemStatusSignalStrength DisplayString,
        fextInfoModemStatusCAState        DisplayString,
        fextInfoModemStatusCellID         DisplayString,
        fextInfoModemStatusBand           DisplayString,
        fextInfoModemStatusBandwidth      DisplayString,
        fextInfoModemStatusSINR           DisplayString,
        fextInfoModemStatusRSRP           DisplayString,
        fextInfoModemStatusRSRQ           DisplayString,
        fextInfoModemStatusPlanName       DisplayString,
        fextInfoModemStatusConnectStatus  DisplayString,
        fextInfoModemStatusReconnectCount Integer32,
        fextInfoModemStatusSmartSIMSwitch DisplayString,
        fextInfoModemStatusUptime         DisplayString,
        fextInfoModemStatusClock          DisplayString,
        fextInfoModemStatusTemperature    DisplayString,
        fextInfoModemStatusActivateStatus DisplayString,
        fextInfoModemStatusRoamingStatus  DisplayString,
        fextInfoModemStatusLatitude       DisplayString,
        fextInfoModemStatusLongitude      DisplayString
    }

    fextInfoModemStatusIndex OBJECT-TYPE
        SYNTAX      FnIndex
        MAX-ACCESS  not-accessible
        STATUS      current
        DESCRIPTION "An index uniquely defining a Modem status."
        ::= {fextInfoModemStatusEntry 1}

    fextInfoModemStatusModem OBJECT-TYPE
        SYNTAX      DisplayString
        MAX-ACCESS  read-only
        STATUS      current
        DESCRIPTION "The Modem of this status report for."
        ::= {fextInfoModemStatusEntry 2}

    fextInfoModemStatusUSBPath OBJECT-TYPE
        SYNTAX      DisplayString
        MAX-ACCESS  read-only
        STATUS      current
        DESCRIPTION "The USB path accessing this Modem."
        ::= {fextInfoModemStatusEntry 3}

    fextInfoModemStatusVender OBJECT-TYPE
        SYNTAX      DisplayString
        MAX-ACCESS  read-only
        STATUS      current
        DESCRIPTION "The vender of this Modem."
        ::= {fextInfoModemStatusEntry 4}

    fextInfoModemStatusProduct OBJECT-TYPE
        SYNTAX      DisplayString
        MAX-ACCESS  read-only
        STATUS      current
        DESCRIPTION "The product of this Modem."
        ::= {fextInfoModemStatusEntry 5}

    fextInfoModemStatusModel OBJECT-TYPE
        SYNTAX      DisplayString
        MAX-ACCESS  read-only
        STATUS      current
        DESCRIPTION "The model of this Modem."
        ::= {fextInfoModemStatusEntry 6}

    fextInfoModemStatusSIMSlot OBJECT-TYPE
        SYNTAX      DisplayString
        MAX-ACCESS  read-only
        STATUS      current
        DESCRIPTION "The SIM slot used for this Modem."
        ::= {fextInfoModemStatusEntry 7}

    fextInfoModemStatusRevision OBJECT-TYPE
        SYNTAX      DisplayString
        MAX-ACCESS  read-only
        STATUS      current
        DESCRIPTION "The firmware version used for this Modem."
        ::= {fextInfoModemStatusEntry 8}

    fextInfoModemStatusIMEI OBJECT-TYPE
        SYNTAX      DisplayString
        MAX-ACCESS  read-only
        STATUS      current
        DESCRIPTION "The IMEI of this Modem."
        ::= {fextInfoModemStatusEntry 9}

    fextInfoModemStatusICCID OBJECT-TYPE
        SYNTAX      DisplayString
        MAX-ACCESS  read-only
        STATUS      current
        DESCRIPTION "The SIM ICCID used in this Modem."
        ::= {fextInfoModemStatusEntry 10}

    fextInfoModemStatusIMSI OBJECT-TYPE
        SYNTAX      DisplayString
        MAX-ACCESS  read-only
        STATUS      current
        DESCRIPTION "The SIM IMSI used in this Modem."
        ::= {fextInfoModemStatusEntry 11}

    fextInfoModemStatusPinStatus OBJECT-TYPE
        SYNTAX      DisplayString
        MAX-ACCESS  read-only
        STATUS      current
        DESCRIPTION "The SIM Pin status of this Modem."
        ::= {fextInfoModemStatusEntry 12}

    fextInfoModemStatusPinCode OBJECT-TYPE
        SYNTAX      DisplayString
        MAX-ACCESS  read-only
        STATUS      current
        DESCRIPTION "The SIM Pin code of this Modem."
        ::= {fextInfoModemStatusEntry 13}

    fextInfoModemStatusCarrier OBJECT-TYPE
        SYNTAX      DisplayString
        MAX-ACCESS  read-only
        STATUS      current
        DESCRIPTION "The SIM Carrier used in this Modem."
        ::= {fextInfoModemStatusEntry 14}

    fextInfoModemStatusAPN OBJECT-TYPE
        SYNTAX      DisplayString
        MAX-ACCESS  read-only
        STATUS      current
        DESCRIPTION "The SIM APN used in this Modem."
        ::= {fextInfoModemStatusEntry 15}

    fextInfoModemStatusService OBJECT-TYPE
        SYNTAX      DisplayString
        MAX-ACCESS  read-only
        STATUS      current
        DESCRIPTION "The SIM Carrier service used in this Modem."
        ::= {fextInfoModemStatusEntry 16}

    fextInfoModemStatusPhoneNumber OBJECT-TYPE
        SYNTAX      DisplayString
        MAX-ACCESS  read-only
        STATUS      current
        DESCRIPTION "The SIM Phone number used in this Modem."
        ::= {fextInfoModemStatusEntry 17}

    fextInfoModemStatusSIM1Pin OBJECT-TYPE
        SYNTAX      DisplayString
        MAX-ACCESS  read-only
        STATUS      current
        DESCRIPTION "The SIM Pin in slot 1 of this Modem."
        ::= {fextInfoModemStatusEntry 18}

    fextInfoModemStatusSIM1Puk OBJECT-TYPE
        SYNTAX      DisplayString
        MAX-ACCESS  read-only
        STATUS      current
        DESCRIPTION "The SIM Puk in slot 1 of this Modem."
        ::= {fextInfoModemStatusEntry 19}

    fextInfoModemStatusSIM2Pin OBJECT-TYPE
        SYNTAX      DisplayString
        MAX-ACCESS  read-only
        STATUS      current
        DESCRIPTION "The SIM Pin in slot 2 of this Modem."
        ::= {fextInfoModemStatusEntry 20}

    fextInfoModemStatusSIM2Puk OBJECT-TYPE
        SYNTAX      DisplayString
        MAX-ACCESS  read-only
        STATUS      current
        DESCRIPTION "The SIM Puk in slot 2 of this Modem."
        ::= {fextInfoModemStatusEntry 21}

    fextInfoModemStatusRSSI OBJECT-TYPE
        SYNTAX      DisplayString
        MAX-ACCESS  read-only
        STATUS      current
        DESCRIPTION "The RSSI value of this Modem."
        ::= {fextInfoModemStatusEntry 22}

    fextInfoModemStatusSignalStrength OBJECT-TYPE
        SYNTAX      DisplayString
        MAX-ACCESS  read-only
        STATUS      current
        DESCRIPTION "The Carrier signal strength of this Modem."
        ::= {fextInfoModemStatusEntry 23}

    fextInfoModemStatusCAState OBJECT-TYPE
        SYNTAX      DisplayString
        MAX-ACCESS  read-only
        STATUS      current
        DESCRIPTION "The CA state of this Modem."
        ::= {fextInfoModemStatusEntry 24}

    fextInfoModemStatusCellID OBJECT-TYPE
        SYNTAX      DisplayString
        MAX-ACCESS  read-only
        STATUS      current
        DESCRIPTION "The Carrier Cell ID of this Modem."
        ::= {fextInfoModemStatusEntry 25}

    fextInfoModemStatusBand OBJECT-TYPE
        SYNTAX      DisplayString
        MAX-ACCESS  read-only
        STATUS      current
        DESCRIPTION "The band select of this Modem."
        ::= {fextInfoModemStatusEntry 26}

    fextInfoModemStatusBandwidth OBJECT-TYPE
        SYNTAX      DisplayString
        MAX-ACCESS  read-only
        STATUS      current
        DESCRIPTION "The bandwidth of this Modem."
        ::= {fextInfoModemStatusEntry 27}

    fextInfoModemStatusSINR OBJECT-TYPE
        SYNTAX      DisplayString
        MAX-ACCESS  read-only
        STATUS      current
        DESCRIPTION "The SINR value of this Modem."
        ::= {fextInfoModemStatusEntry 28}

    fextInfoModemStatusRSRP OBJECT-TYPE
        SYNTAX      DisplayString
        MAX-ACCESS  read-only
        STATUS      current
        DESCRIPTION "The RSRP value of this Modem."
        ::= {fextInfoModemStatusEntry 29}

    fextInfoModemStatusRSRQ OBJECT-TYPE
        SYNTAX      DisplayString
        MAX-ACCESS  read-only
        STATUS      current
        DESCRIPTION "The RSRQ value of this Modem."
        ::= {fextInfoModemStatusEntry 30}

    fextInfoModemStatusPlanName OBJECT-TYPE
        SYNTAX      DisplayString
        MAX-ACCESS  read-only
        STATUS      current
        DESCRIPTION "The plan used in this Modem."
        ::= {fextInfoModemStatusEntry 31}

    fextInfoModemStatusConnectStatus OBJECT-TYPE
        SYNTAX      DisplayString
        MAX-ACCESS  read-only
        STATUS      current
        DESCRIPTION "The connection status of this Modem."
        ::= {fextInfoModemStatusEntry 32}

    fextInfoModemStatusReconnectCount OBJECT-TYPE
        SYNTAX      Integer32
        MAX-ACCESS  read-only
        STATUS      current
        DESCRIPTION "The reconnection count of this Modem."
        ::= {fextInfoModemStatusEntry 33}

    fextInfoModemStatusSmartSIMSwitch OBJECT-TYPE
        SYNTAX      DisplayString
        MAX-ACCESS  read-only
        STATUS      current
        DESCRIPTION "The Smart SIM Switch status of this Modem."
        ::= {fextInfoModemStatusEntry 34}

    fextInfoModemStatusUptime OBJECT-TYPE
        SYNTAX      DisplayString
        MAX-ACCESS  read-only
        STATUS      current
        DESCRIPTION "The connection uptime of this Modem."
        ::= {fextInfoModemStatusEntry 35}

    fextInfoModemStatusClock OBJECT-TYPE
        SYNTAX      DisplayString
        MAX-ACCESS  read-only
        STATUS      current
        DESCRIPTION "The current time of this Modem."
        ::= {fextInfoModemStatusEntry 36}

    fextInfoModemStatusTemperature OBJECT-TYPE
        SYNTAX      DisplayString
        MAX-ACCESS  read-only
        STATUS      current
        DESCRIPTION "The current temperatute of this Modem."
        ::= {fextInfoModemStatusEntry 37}

    fextInfoModemStatusActivateStatus OBJECT-TYPE
        SYNTAX      DisplayString
        MAX-ACCESS  read-only
        STATUS      current
        DESCRIPTION "The activation status of this Modem."
        ::= {fextInfoModemStatusEntry 38}

    fextInfoModemStatusRoamingStatus OBJECT-TYPE
        SYNTAX      DisplayString
        MAX-ACCESS  read-only
        STATUS      current
        DESCRIPTION "The roaming status of this Modem."
        ::= {fextInfoModemStatusEntry 39}

    fextInfoModemStatusLatitude OBJECT-TYPE
        SYNTAX      DisplayString
        MAX-ACCESS  read-only
        STATUS      current
        DESCRIPTION "The latitude of this Modem."
        ::= {fextInfoModemStatusEntry 40}

    fextInfoModemStatusLongitude OBJECT-TYPE
        SYNTAX      DisplayString
        MAX-ACCESS  read-only
        STATUS      current
        DESCRIPTION "The longitude of this Modem."
        ::= {fextInfoModemStatusEntry 41}

    --
    -- fextInfoModem.fextInfoModemFWVersion
    -- fextInfoModemFWVersionVersion    ::= {fextInfoModemFWVersion 1}
    --

    fextInfoModemFWVersionVersion OBJECT-TYPE
        SYNTAX      DisplayString
        MAX-ACCESS  read-only
        STATUS      current
        DESCRIPTION "Modem firmware version."
        ::= {fextInfoModemFWVersion 1}

    --
    -- fextInfoModem.fextInfoModemDataUsage
    --

    fextInfoModemDataUsageEntry OBJECT-TYPE
        SYNTAX      FextInfoModemDataUsageEntry
        MAX-ACCESS  not-accessible
        STATUS      current
        DESCRIPTION "FortiExtender Modem data usage."
        INDEX       {fextInfoModemDataUsageIndex}
        ::= {fextInfoModemDataUsage 1}

    FextInfoModemDataUsageEntry ::= SEQUENCE {
        fextInfoModemDataUsageIndex        FnIndex,
        fextInfoModemDataUsageModem        DisplayString,
        fextInfoModemDataUsageSlot         Integer32,
        fextInfoModemDataUsageCarrier      DisplayString,
        fextInfoModemDataUsageIMSI         DisplayString,
        fextInfoModemDataUsageMB           Integer32,
        fextInfoModemDataUsagePercentage   DisplayString,
        fextInfoModemDataUsageDataPlan     Integer32,
        fextInfoModemDataUsageOverage      DisplayString,
        fextInfoModemDataUsageNextBillDate DisplayString
    }

    fextInfoModemDataUsageIndex OBJECT-TYPE
        SYNTAX      FnIndex
        MAX-ACCESS  not-accessible
        STATUS      current
        DESCRIPTION "An index uniquely reporting a Modem data usage."
        ::= {fextInfoModemDataUsageEntry 1}

    fextInfoModemDataUsageModem OBJECT-TYPE
        SYNTAX      DisplayString
        MAX-ACCESS  read-only
        STATUS      current
        DESCRIPTION "The Modem of this data usage report for."
        ::= {fextInfoModemDataUsageEntry 2}

    fextInfoModemDataUsageSlot OBJECT-TYPE
        SYNTAX      Integer32
        MAX-ACCESS  read-only
        STATUS      current
        DESCRIPTION "The slot number used."
        ::= {fextInfoModemDataUsageEntry 3}

    fextInfoModemDataUsageCarrier OBJECT-TYPE
        SYNTAX      DisplayString
        MAX-ACCESS  read-only
        STATUS      current
        DESCRIPTION "The carrier used."
        ::= {fextInfoModemDataUsageEntry 4}

    fextInfoModemDataUsageIMSI OBJECT-TYPE
        SYNTAX      DisplayString
        MAX-ACCESS  read-only
        STATUS      current
        DESCRIPTION "The SIM IMSI used."
        ::= {fextInfoModemDataUsageEntry 5}

    fextInfoModemDataUsageMB OBJECT-TYPE
        SYNTAX      Integer32
        MAX-ACCESS  read-only
        STATUS      current
        DESCRIPTION "The usage in MB."
        ::= {fextInfoModemDataUsageEntry 6}

    fextInfoModemDataUsagePercentage OBJECT-TYPE
        SYNTAX      DisplayString
        MAX-ACCESS  read-only
        STATUS      current
        DESCRIPTION "The usage in percentage."
        ::= {fextInfoModemDataUsageEntry 7}

    fextInfoModemDataUsageDataPlan OBJECT-TYPE
        SYNTAX      Integer32
        MAX-ACCESS  read-only
        STATUS      current
        DESCRIPTION "The data plan used."
        ::= {fextInfoModemDataUsageEntry 8}

    fextInfoModemDataUsageOverage OBJECT-TYPE
        SYNTAX      DisplayString
        MAX-ACCESS  read-only
        STATUS      current
        DESCRIPTION "The overage setting."
        ::= {fextInfoModemDataUsageEntry 9}

    fextInfoModemDataUsageNextBillDate OBJECT-TYPE
        SYNTAX      DisplayString
        MAX-ACCESS  read-only
        STATUS      current
        DESCRIPTION "The coming billing date."
        ::= {fextInfoModemDataUsageEntry 10}

    --
    -- fextInfo.fextInfoRouter
    --
    -- fextInfoRouterRoute        ::= {fextInfoRouter 1}
    -- fextInfoRouterPolicy       ::= {fextInfoRouter 2}
    -- fextInfoRouterTarget       ::= {fextInfoRouter 3}
    -- fextInfoRouterMulticast    ::= {fextInfoRouter 4}
    -- fextInfoRouterVRRP         ::= {fextInfoRouter 5}
    --

    fextInfoRouterRoute OBJECT-TYPE
        SYNTAX      SEQUENCE OF FextInfoRouterRouteEntry
        MAX-ACCESS  not-accessible
        STATUS      current
        DESCRIPTION "Routing table information."
        ::= {fextInfoRouter 1}

    fextInfoRouterPolicy OBJECT-TYPE
        SYNTAX      SEQUENCE OF FextInfoRouterPolicyEntry
        MAX-ACCESS  not-accessible
        STATUS      current
        DESCRIPTION "Policy based routing rule."
        ::= {fextInfoRouter 2}

    fextInfoRouterTarget OBJECT-TYPE
        SYNTAX      SEQUENCE OF FextInfoRouterTargetEntry
        MAX-ACCESS  not-accessible
        STATUS      current
        DESCRIPTION "Route target entries."
        ::= {fextInfoRouter 3}

    fextInfoRouterMulticast OBJECT-IDENTITY
        STATUS      current
        DESCRIPTION "Multicast information."
        ::= {fextInfoRouter 4}

    fextInfoRouterVRRP OBJECT-TYPE
        SYNTAX      SEQUENCE OF FextInfoRouterVRRPEntry
        MAX-ACCESS  not-accessible
        STATUS      current
        DESCRIPTION "VRRP infomation."
        ::= {fextInfoRouter 5}

    --
    -- fextInfoRouter.fextInfoRouterRoute
    --

    fextInfoRouterRouteEntry OBJECT-TYPE
        SYNTAX      FextInfoRouterRouteEntry
        MAX-ACCESS  not-accessible
        STATUS      current
        DESCRIPTION "Routing table information."
        INDEX       {fextInfoRouterRouteIndex}
        ::= {fextInfoRouterRoute 1}

    FextInfoRouterRouteEntry ::= SEQUENCE {
        fextInfoRouterRouteIndex FnIndex,
        fextInfoRouterRouteType  DisplayString,
        fextInfoRouterRouteDst   DisplayString,
        fextInfoRouterRouteGW    DisplayString,
        fextInfoRouterRouteHelp  DisplayString,
        fextInfoRouterRouteDev   DisplayString
    }

    fextInfoRouterRouteIndex OBJECT-TYPE
        SYNTAX      FnIndex
        MAX-ACCESS  not-accessible
        STATUS      current
        DESCRIPTION "An index uniquely defining a routing table entry."
        ::= {fextInfoRouterRouteEntry 1}

    fextInfoRouterRouteType OBJECT-TYPE
        SYNTAX      DisplayString
        MAX-ACCESS  read-only
        STATUS      current
        DESCRIPTION "The code of routine table entry."
        ::= {fextInfoRouterRouteEntry 2}

    fextInfoRouterRouteDst OBJECT-TYPE
        SYNTAX      DisplayString
        MAX-ACCESS  read-only
        STATUS      current
        DESCRIPTION "The destination of routine table entry."
        ::= {fextInfoRouterRouteEntry 3}

    fextInfoRouterRouteGW OBJECT-TYPE
        SYNTAX      DisplayString
        MAX-ACCESS  read-only
        STATUS      current
        DESCRIPTION "The gateway of routine table entry."
        ::= {fextInfoRouterRouteEntry 4}

    fextInfoRouterRouteHelp OBJECT-TYPE
        SYNTAX      DisplayString
        MAX-ACCESS  read-only
        STATUS      current
        DESCRIPTION "The description of routine table entry."
        ::= {fextInfoRouterRouteEntry 5}

    fextInfoRouterRouteDev OBJECT-TYPE
        SYNTAX      DisplayString
        MAX-ACCESS  read-only
        STATUS      current
        DESCRIPTION "The device of routine table entry."
        ::= {fextInfoRouterRouteEntry 6}

    --
    -- fextInfoRouter.fextInfoRouterPolicy
    --

    fextInfoRouterPolicyEntry OBJECT-TYPE
        SYNTAX      FextInfoRouterPolicyEntry
        MAX-ACCESS  not-accessible
        STATUS      current
        DESCRIPTION "Policy based routing rule."
        INDEX       {fextInfoRouterPolicyIndex}
        ::= {fextInfoRouterPolicy 1}

    FextInfoRouterPolicyEntry ::= SEQUENCE {
        fextInfoRouterPolicyIndex        FnIndex,
        fextInfoRouterPolicySeq          Integer32,
        fextInfoRouterPolicyStatus       DisplayString,
        fextInfoRouterPolicyInputIntf    DisplayString,
        fextInfoRouterPolicySrc          DisplayString,
        fextInfoRouterPolicySrcAddr      DisplayString,
        fextInfoRouterPolicyDst          DisplayString,
        fextInfoRouterPolicyDstAddr      DisplayString,
        fextInfoRouterPolicyService      DisplayString,
        fextInfoRouterPolicyTarget       DisplayString,
        fextInfoRouterPolicyRoutingTable DisplayString,
        fextInfoRouterPolicyComment      DisplayString
    }

    fextInfoRouterPolicyIndex OBJECT-TYPE
        SYNTAX      FnIndex
        MAX-ACCESS  not-accessible
        STATUS      current
        DESCRIPTION "An index uniquely defining a policy based routing rule."
        ::= {fextInfoRouterPolicyEntry 1}

    fextInfoRouterPolicySeq OBJECT-TYPE
        SYNTAX      Integer32
        MAX-ACCESS  read-only
        STATUS      current
        DESCRIPTION "The sequence of policy based routing rule."
        ::= {fextInfoRouterPolicyEntry 2}

    fextInfoRouterPolicyStatus OBJECT-TYPE
        SYNTAX      DisplayString
        MAX-ACCESS  read-only
        STATUS      current
        DESCRIPTION "The status of policy based routing rule."
        ::= {fextInfoRouterPolicyEntry 3}

    fextInfoRouterPolicyInputIntf OBJECT-TYPE
        SYNTAX      DisplayString
        MAX-ACCESS  read-only
        STATUS      current
        DESCRIPTION "The input interface of policy based routing rule."
        ::= {fextInfoRouterPolicyEntry 4}

    fextInfoRouterPolicySrc OBJECT-TYPE
        SYNTAX      DisplayString
        MAX-ACCESS  read-only
        STATUS      current
        DESCRIPTION "The source of policy based routing rule."
        ::= {fextInfoRouterPolicyEntry 5}

    fextInfoRouterPolicySrcAddr OBJECT-TYPE
        SYNTAX      DisplayString
        MAX-ACCESS  read-only
        STATUS      current
        DESCRIPTION "The source address of policy based routing rule."
        ::= {fextInfoRouterPolicyEntry 6}

    fextInfoRouterPolicyDst OBJECT-TYPE
        SYNTAX      DisplayString
        MAX-ACCESS  read-only
        STATUS      current
        DESCRIPTION "The destination of policy based routing rule."
        ::= {fextInfoRouterPolicyEntry 7}

    fextInfoRouterPolicyDstAddr OBJECT-TYPE
        SYNTAX      DisplayString
        MAX-ACCESS  read-only
        STATUS      current
        DESCRIPTION "The destination address of policy based routing rule."
        ::= {fextInfoRouterPolicyEntry 8}

    fextInfoRouterPolicyService OBJECT-TYPE
        SYNTAX      DisplayString
        MAX-ACCESS  read-only
        STATUS      current
        DESCRIPTION "The service of policy based routing rule."
        ::= {fextInfoRouterPolicyEntry 9}

    fextInfoRouterPolicyTarget OBJECT-TYPE
        SYNTAX      DisplayString
        MAX-ACCESS  read-only
        STATUS      current
        DESCRIPTION "The target of policy based routing rule."
        ::= {fextInfoRouterPolicyEntry 10}

    fextInfoRouterPolicyRoutingTable OBJECT-TYPE
        SYNTAX      DisplayString
        MAX-ACCESS  read-only
        STATUS      current
        DESCRIPTION "The routing table of policy based routing rule."
        ::= {fextInfoRouterPolicyEntry 11}

    fextInfoRouterPolicyComment OBJECT-TYPE
        SYNTAX      DisplayString
        MAX-ACCESS  read-only
        STATUS      current
        DESCRIPTION "The comment of policy based routing rule."
        ::= {fextInfoRouterPolicyEntry 12}

    --
    -- fextInfoRouter.fextInfoRouterTarget
    --

    fextInfoRouterTargetEntry OBJECT-TYPE
        SYNTAX      FextInfoRouterTargetEntry
        MAX-ACCESS  not-accessible
        STATUS      current
        DESCRIPTION "Route target."
        INDEX       {fextInfoRouterTargetIndex}
        ::= {fextInfoRouterTarget 1}

    FextInfoRouterTargetEntry ::= SEQUENCE {
        fextInfoRouterTargetIndex        FnIndex,
        fextInfoRouterTargetStatus       DisplayString,
        fextInfoRouterTargetDevice       DisplayString,
        fextInfoRouterTargetDevStatus    DisplayString,
        fextInfoRouterTargetNextHop      DisplayString,
        fextInfoRouterTargetNHStatus     DisplayString,
        fextInfoRouterTargetRouteType    DisplayString,
        fextInfoRouterTargetRoutingTable DisplayString,
        fextInfoRouterTargetRefCounter   Integer32
    }

    fextInfoRouterTargetIndex OBJECT-TYPE
        SYNTAX      FnIndex
        MAX-ACCESS  not-accessible
        STATUS      current
        DESCRIPTION "An index uniquely defining a route target."
        ::= {fextInfoRouterTargetEntry 1}

    fextInfoRouterTargetStatus OBJECT-TYPE
        SYNTAX      DisplayString
        MAX-ACCESS  read-only
        STATUS      current
        DESCRIPTION "The status of route target."
        ::= {fextInfoRouterTargetEntry 2}

    fextInfoRouterTargetDevice OBJECT-TYPE
        SYNTAX      DisplayString
        MAX-ACCESS  read-only
        STATUS      current
        DESCRIPTION "The device of route target."
        ::= {fextInfoRouterTargetEntry 3}

    fextInfoRouterTargetDevStatus OBJECT-TYPE
        SYNTAX      DisplayString
        MAX-ACCESS  read-only
        STATUS      current
        DESCRIPTION "The status of device of route target."
        ::= {fextInfoRouterTargetEntry 4}

    fextInfoRouterTargetNextHop OBJECT-TYPE
        SYNTAX      DisplayString
        MAX-ACCESS  read-only
        STATUS      current
        DESCRIPTION "The next hop of route target."
        ::= {fextInfoRouterTargetEntry 5}

    fextInfoRouterTargetNHStatus OBJECT-TYPE
        SYNTAX      DisplayString
        MAX-ACCESS  read-only
        STATUS      current
        DESCRIPTION "The status of next hop of route target."
        ::= {fextInfoRouterTargetEntry 6}

    fextInfoRouterTargetRouteType OBJECT-TYPE
        SYNTAX      DisplayString
        MAX-ACCESS  read-only
        STATUS      current
        DESCRIPTION "The route type of route target."
        ::= {fextInfoRouterTargetEntry 7}

    fextInfoRouterTargetRoutingTable OBJECT-TYPE
        SYNTAX      DisplayString
        MAX-ACCESS  read-only
        STATUS      current
        DESCRIPTION "The routing table of route target."
        ::= {fextInfoRouterTargetEntry 8}

    fextInfoRouterTargetRefCounter OBJECT-TYPE
        SYNTAX      Integer32
        MAX-ACCESS  read-only
        STATUS      current
        DESCRIPTION "The reference counter of route target."
        ::= {fextInfoRouterTargetEntry 9}

    --
    -- fextInfoRouter.fextInfoRouterMulticast
    --
    -- fextInfoMcastPIMSM ::= {fextInfoRouterMulticast 1}
    --

    fextInfoMcastPIMSM OBJECT-IDENTITY
        STATUS      current
        DESCRIPTION "Multicast information."
        ::= {fextInfoRouterMulticast 1}

    --
    -- fextInfoRouterMulticast.fextInfoMcastPIMSM
    --
    -- fextInfoPIMSMVIF         ::= {fextInfoMcastPIMSM 1}
    -- fextInfoPIMSMVIFNeighbor ::= {fextInfoMcastPIMSM 2}
    -- fextInfoPIMSMRoute       ::= {fextInfoMcastPIMSM 3}
    -- fextInfoPIMSMRP          ::= {fextInfoMcastPIMSM 4}
    -- fextInfoPIMSMRPGroup     ::= {fextInfoMcastPIMSM 5}
    --

    fextInfoPIMSMVIF OBJECT-TYPE
        SYNTAX      SEQUENCE OF FextInfoPIMSMVIFEntry
        MAX-ACCESS  not-accessible
        STATUS      current
        DESCRIPTION "VIF information."
        ::= {fextInfoMcastPIMSM 1}

    fextInfoPIMSMVIFNeighbor OBJECT-TYPE
        SYNTAX      SEQUENCE OF FextInfoPIMSMVIFNeighborEntry
        MAX-ACCESS  not-accessible
        STATUS      current
        DESCRIPTION "VIF neighbor information."
        ::= {fextInfoMcastPIMSM 2}

    fextInfoPIMSMRoute OBJECT-TYPE
        SYNTAX      SEQUENCE OF FextInfoPIMSMRouteEntry
        MAX-ACCESS  not-accessible
        STATUS      current
        DESCRIPTION "Route table information."
        ::= {fextInfoMcastPIMSM 3}

    fextInfoPIMSMRP OBJECT-TYPE
        SYNTAX      SEQUENCE OF FextInfoPIMSMRPEntry
        MAX-ACCESS  not-accessible
        STATUS      current
        DESCRIPTION "RP list."
        ::= {fextInfoMcastPIMSM 4}

    fextInfoPIMSMRPGroup OBJECT-TYPE
        SYNTAX      SEQUENCE OF FextInfoPIMSMRPGroupEntry
        MAX-ACCESS  not-accessible
        STATUS      current
        DESCRIPTION "RP neighbor information."
        ::= {fextInfoMcastPIMSM 5}

    --
    -- fextInfoMcastPIMSM.fextInfoPIMSMVIF
    --

    fextInfoPIMSMVIFEntry OBJECT-TYPE
        SYNTAX      FextInfoPIMSMVIFEntry
        MAX-ACCESS  not-accessible
        STATUS      current
        DESCRIPTION "VIF information."
        INDEX       {fextInfoPIMSMVIFIndex}
        ::= {fextInfoPIMSMVIF 1}

    FextInfoPIMSMVIFEntry ::= SEQUENCE {
        fextInfoPIMSMVIFIndex      FnIndex,
        fextInfoPIMSMVIFName       DisplayString,
        fextInfoPIMSMVIFAddress    DisplayString,
        fextInfoPIMSMVIFFlag       DisplayString,
        fextInfoPIMSMVIFHelloTimer Integer32,
        fextInfoPIMSMVIFDRPriority Integer32
    }

    fextInfoPIMSMVIFIndex OBJECT-TYPE
        SYNTAX      FnIndex
        MAX-ACCESS  not-accessible
        STATUS      current
        DESCRIPTION "An index uniquely defining a VIF information."
        ::= {fextInfoPIMSMVIFEntry 1}

    fextInfoPIMSMVIFName OBJECT-TYPE
        SYNTAX      DisplayString
        MAX-ACCESS  read-only
        STATUS      current
        DESCRIPTION "The name of VIF information."
        ::= {fextInfoPIMSMVIFEntry 2}

    fextInfoPIMSMVIFAddress OBJECT-TYPE
        SYNTAX      DisplayString
        MAX-ACCESS  read-only
        STATUS      current
        DESCRIPTION "The address of VIF information."
        ::= {fextInfoPIMSMVIFEntry 3}

    fextInfoPIMSMVIFFlag OBJECT-TYPE
        SYNTAX      DisplayString
        MAX-ACCESS  read-only
        STATUS      current
        DESCRIPTION "The flag of VIF information."
        ::= {fextInfoPIMSMVIFEntry 4}

    fextInfoPIMSMVIFHelloTimer OBJECT-TYPE
        SYNTAX      Integer32
        MAX-ACCESS  read-only
        STATUS      current
        DESCRIPTION "The hello timer of VIF information."
        ::= {fextInfoPIMSMVIFEntry 5}

    fextInfoPIMSMVIFDRPriority OBJECT-TYPE
        SYNTAX      Integer32
        MAX-ACCESS  read-only
        STATUS      current
        DESCRIPTION "The DR priority of VIF information."
        ::= {fextInfoPIMSMVIFEntry 6}

    --
    -- fextInfoMcastPIMSM.fextInfoPIMSMVIFNeighbor
    --

    fextInfoPIMSMVIFNeighborEntry OBJECT-TYPE
        SYNTAX      FextInfoPIMSMVIFNeighborEntry
        MAX-ACCESS  not-accessible
        STATUS      current
        DESCRIPTION "The neighbor of VIF information."
        INDEX       {fextInfoPIMSMVIFIndex, fextInfoPIMSMVIFNeighborIndex}
        ::= {fextInfoPIMSMVIFNeighbor 1}

    FextInfoPIMSMVIFNeighborEntry ::= SEQUENCE {
        fextInfoPIMSMVIFNeighborIndex  FnIndex,
        fextInfoPIMSMVIFNeighborIP     DisplayString,
        fextInfoPIMSMVIFNeighborExpire Integer32
    }

    fextInfoPIMSMVIFNeighborIndex OBJECT-TYPE
        SYNTAX      FnIndex
        MAX-ACCESS  not-accessible
        STATUS      current
        DESCRIPTION "An index uniquely defining a VIF neighbor information."
        ::= {fextInfoPIMSMVIFNeighborEntry 1}

    fextInfoPIMSMVIFNeighborIP OBJECT-TYPE
        SYNTAX      DisplayString
        MAX-ACCESS  read-only
        STATUS      current
        DESCRIPTION "The IP of VIF neighbor."
        ::= {fextInfoPIMSMVIFNeighborEntry 2}

    fextInfoPIMSMVIFNeighborExpire OBJECT-TYPE
        SYNTAX      Integer32
        MAX-ACCESS  read-only
        STATUS      current
        DESCRIPTION "The expiration of VIF neighbor in seconds."
        ::= {fextInfoPIMSMVIFNeighborEntry 3}

    --
    -- fextInfoMcastPIMSM.fextInfoPIMSMRoute
    --

    fextInfoPIMSMRouteEntry OBJECT-TYPE
        SYNTAX      FextInfoPIMSMRouteEntry
        MAX-ACCESS  not-accessible
        STATUS      current
        DESCRIPTION "Route table information."
        INDEX       {fextInfoPIMSMRouteIndex}
        ::= {fextInfoPIMSMRoute 1}

    FextInfoPIMSMRouteEntry ::= SEQUENCE {
        fextInfoPIMSMRouteIndex          FnIndex,
        fextInfoPIMSMRouteSRC            DisplayString,
        fextInfoPIMSMRouteGRP            DisplayString,
        fextInfoPIMSMRouteRP             DisplayString,
        fextInfoPIMSMRouteFlag           DisplayString,
        fextInfoPIMSMRouteJoinedOIFs     DisplayString,
        fextInfoPIMSMRoutePrunedOIFs     DisplayString,
        fextInfoPIMSMRouteLeavesOIFs     DisplayString,
        fextInfoPIMSMRouteAssertedOIFs   DisplayString,
        fextInfoPIMSMRouteOutgoingOIFs   DisplayString,
        fextInfoPIMSMRouteIncomingIFs    DisplayString,
        fextInfoPIMSMRouteJoinPruneTimer Integer32
    }

    fextInfoPIMSMRouteIndex OBJECT-TYPE
        SYNTAX      FnIndex
        MAX-ACCESS  not-accessible
        STATUS      current
        DESCRIPTION "An index uniquely defining a route table information."
        ::= {fextInfoPIMSMRouteEntry 1}

    fextInfoPIMSMRouteSRC OBJECT-TYPE
        SYNTAX      DisplayString
        MAX-ACCESS  read-only
        STATUS      current
        DESCRIPTION "The source of route table information."
        ::= {fextInfoPIMSMRouteEntry 2}

    fextInfoPIMSMRouteGRP OBJECT-TYPE
        SYNTAX      DisplayString
        MAX-ACCESS  read-only
        STATUS      current
        DESCRIPTION "The group of route table information."
        ::= {fextInfoPIMSMRouteEntry 3}

    fextInfoPIMSMRouteRP OBJECT-TYPE
        SYNTAX      DisplayString
        MAX-ACCESS  read-only
        STATUS      current
        DESCRIPTION "The RP of route table information."
        ::= {fextInfoPIMSMRouteEntry 4}

    fextInfoPIMSMRouteFlag OBJECT-TYPE
        SYNTAX      DisplayString
        MAX-ACCESS  read-only
        STATUS      current
        DESCRIPTION "The flag of route table information."
        ::= {fextInfoPIMSMRouteEntry 5}

    fextInfoPIMSMRouteJoinedOIFs OBJECT-TYPE
        SYNTAX      DisplayString
        MAX-ACCESS  read-only
        STATUS      current
        DESCRIPTION "The joined OIFs of route table information."
        ::= {fextInfoPIMSMRouteEntry 6}

    fextInfoPIMSMRoutePrunedOIFs OBJECT-TYPE
        SYNTAX      DisplayString
        MAX-ACCESS  read-only
        STATUS      current
        DESCRIPTION "The pruned OIFs of route table information."
        ::= {fextInfoPIMSMRouteEntry 7}

    fextInfoPIMSMRouteLeavesOIFs OBJECT-TYPE
        SYNTAX      DisplayString
        MAX-ACCESS  read-only
        STATUS      current
        DESCRIPTION "The leaves OIFs of route table information."
        ::= {fextInfoPIMSMRouteEntry 8}

    fextInfoPIMSMRouteAssertedOIFs OBJECT-TYPE
        SYNTAX      DisplayString
        MAX-ACCESS  read-only
        STATUS      current
        DESCRIPTION "The asserted OIFs of route table information."
        ::= {fextInfoPIMSMRouteEntry 9}

    fextInfoPIMSMRouteOutgoingOIFs OBJECT-TYPE
        SYNTAX      DisplayString
        MAX-ACCESS  read-only
        STATUS      current
        DESCRIPTION "The outgoing OIFs of route table information."
        ::= {fextInfoPIMSMRouteEntry 10}

    fextInfoPIMSMRouteIncomingIFs OBJECT-TYPE
        SYNTAX      DisplayString
        MAX-ACCESS  read-only
        STATUS      current
        DESCRIPTION "The incoming IFs of route table information."
        ::= {fextInfoPIMSMRouteEntry 11}

    fextInfoPIMSMRouteJoinPruneTimer OBJECT-TYPE
        SYNTAX      Integer32
        MAX-ACCESS  read-only
        STATUS      current
        DESCRIPTION "The Join/Prune timer of route table information."
        ::= {fextInfoPIMSMRouteEntry 12}

    --
    -- fextInfoMcastPIMSM.fextInfoPIMSMRP
    --

    fextInfoPIMSMRPEntry OBJECT-TYPE
        SYNTAX      FextInfoPIMSMRPEntry
        MAX-ACCESS  not-accessible
        STATUS      current
        DESCRIPTION "RP list information."
        INDEX       {fextInfoPIMSMRPIndex}
        ::= {fextInfoPIMSMRP 1}

    FextInfoPIMSMRPEntry ::= SEQUENCE {
        fextInfoPIMSMRPIndex   FnIndex,
        fextInfoPIMSMRPAddress DisplayString
    }

    fextInfoPIMSMRPIndex OBJECT-TYPE
        SYNTAX      FnIndex
        MAX-ACCESS  not-accessible
        STATUS      current
        DESCRIPTION "An index uniquely defining a RP information entry."
        ::= {fextInfoPIMSMRPEntry 1}

    fextInfoPIMSMRPAddress OBJECT-TYPE
        SYNTAX      DisplayString
        MAX-ACCESS  read-only
        STATUS      current
        DESCRIPTION "The address of RP."
        ::= {fextInfoPIMSMRPEntry 2}

    --
    -- fextInfoMcastPIMSM.fextInfoPIMSMRPGroup
    --

    fextInfoPIMSMRPGroupEntry OBJECT-TYPE
        SYNTAX      FextInfoPIMSMRPGroupEntry
        MAX-ACCESS  not-accessible
        STATUS      current
        DESCRIPTION "The group of RP information."
        INDEX       {fextInfoPIMSMRPIndex, fextInfoPIMSMRPGroupIndex}
        ::= {fextInfoPIMSMRPGroup 1}

    FextInfoPIMSMRPGroupEntry ::= SEQUENCE {
        fextInfoPIMSMRPGroupIndex    FnIndex,
        fextInfoPIMSMRPGroupAddress  DisplayString,
        fextInfoPIMSMRPGroupPriority Integer32
    }

    fextInfoPIMSMRPGroupIndex OBJECT-TYPE
        SYNTAX      FnIndex
        MAX-ACCESS  not-accessible
        STATUS      current
        DESCRIPTION "An index uniquely defining a RP group information."
        ::= {fextInfoPIMSMRPGroupEntry 1}

    fextInfoPIMSMRPGroupAddress OBJECT-TYPE
        SYNTAX      DisplayString
        MAX-ACCESS  read-only
        STATUS      current
        DESCRIPTION "The address of RP group."
        ::= {fextInfoPIMSMRPGroupEntry 2}

    fextInfoPIMSMRPGroupPriority OBJECT-TYPE
        SYNTAX      Integer32
        MAX-ACCESS  read-only
        STATUS      current
        DESCRIPTION "The priority of RP group."
        ::= {fextInfoPIMSMRPGroupEntry 3}

    --
    -- fextInfoRouter.fextInfoRouterVRRP
    --

    fextInfoRouterVRRPEntry OBJECT-TYPE
        SYNTAX      FextInfoRouterVRRPEntry
        MAX-ACCESS  not-accessible
        STATUS      current
        DESCRIPTION "VRRP infomation."
        INDEX       {fextInfoRouterVRRPIndex}
        ::= {fextInfoRouterVRRP 1}

    FextInfoRouterVRRPEntry ::= SEQUENCE {
        fextInfoRouterVRRPIndex     FnIndex,
        fextInfoRouterVRRPIfName    DisplayString,
        fextInfoRouterVRRPState     DisplayString
    }

    fextInfoRouterVRRPIndex OBJECT-TYPE
        SYNTAX      FnIndex
        MAX-ACCESS  not-accessible
        STATUS      current
        DESCRIPTION "An index uniquely defining a VRRP infomation entry."
        ::= {fextInfoRouterVRRPEntry 1}

    fextInfoRouterVRRPIfName OBJECT-TYPE
        SYNTAX      DisplayString
        MAX-ACCESS  read-only
        STATUS      current
        DESCRIPTION "The interface of VRRP infomation entry."
        ::= {fextInfoRouterVRRPEntry 2}

    fextInfoRouterVRRPState OBJECT-TYPE
        SYNTAX      DisplayString
        MAX-ACCESS  read-only
        STATUS      current
        DESCRIPTION "The state of VRRP infomation entry."
        ::= {fextInfoRouterVRRPEntry 3}

    --
    -- fextInfo.fextInfoVWAN
    --
    -- fextInfoVWANStatus       ::= {fextInfoVWAN 1}
    -- fextInfoVWANStatusMember ::= {fextInfoVWAN 2}
    -- fextInfoVWANMember       ::= {fextInfoVWAN 3}
    --

    fextInfoVWANStatus OBJECT-TYPE
        SYNTAX      SEQUENCE OF FextInfoVWANStatusEntry
        MAX-ACCESS  not-accessible
        STATUS      current
        DESCRIPTION "Virtual WAN status."
        ::= {fextInfoVWAN 1}

    fextInfoVWANStatusMember OBJECT-TYPE
        SYNTAX      SEQUENCE OF FextInfoVWANStatusMemberEntry
        MAX-ACCESS  not-accessible
        STATUS      current
        DESCRIPTION "Member infromation of a Virtual WAN."
        ::= {fextInfoVWAN 2}

    fextInfoVWANMember OBJECT-TYPE
        SYNTAX      SEQUENCE OF FextInfoVWANMemberEntry
        MAX-ACCESS  not-accessible
        STATUS      current
        DESCRIPTION "Virtual WAN member information."
        ::= {fextInfoVWAN 3}

    --
    -- fextInfoVWAN.fextInfoVWANStatus
    --

    fextInfoVWANStatusEntry OBJECT-TYPE
        SYNTAX      FextInfoVWANStatusEntry
        MAX-ACCESS  not-accessible
        STATUS      current
        DESCRIPTION "Virtual WAN status."
        INDEX       {fextInfoVWANStatusIndex}
        ::= {fextInfoVWANStatus 1}

    FextInfoVWANStatusEntry ::= SEQUENCE {
        fextInfoVWANStatusIndex          FnIndex,
        fextInfoVWANStatusName           DisplayString,
        fextInfoVWANStatusAlgorithm      DisplayString,
        fextInfoVWANStatusRedundantBy    DisplayString,
        fextInfoVWANStatusFECName        DisplayString,
        fextInfoVWANStatusTargetCount    Integer32,
        fextInfoVWANStatusSessionCount   Integer32,
        fextInfoVWANStatusSessionTimeout Integer32,
        fextInfoVWANStatusVersion        Integer32
    }

    fextInfoVWANStatusIndex OBJECT-TYPE
        SYNTAX      FnIndex
        MAX-ACCESS  not-accessible
        STATUS      current
        DESCRIPTION "An index uniquely defining a VWAN status."
        ::= {fextInfoVWANStatusEntry 1}

    fextInfoVWANStatusName OBJECT-TYPE
        SYNTAX      DisplayString
        MAX-ACCESS  read-only
        STATUS      current
        DESCRIPTION "The name of VWAN."
        ::= {fextInfoVWANStatusEntry 2}

    fextInfoVWANStatusAlgorithm OBJECT-TYPE
        SYNTAX      DisplayString
        MAX-ACCESS  read-only
        STATUS      current
        DESCRIPTION "The algorithm of VWAN."
        ::= {fextInfoVWANStatusEntry 3}

    fextInfoVWANStatusRedundantBy OBJECT-TYPE
        SYNTAX      DisplayString
        MAX-ACCESS  read-only
        STATUS      current
        DESCRIPTION "The redundant by information of VWAN."
        ::= {fextInfoVWANStatusEntry 4}

    fextInfoVWANStatusFECName OBJECT-TYPE
        SYNTAX      DisplayString
        MAX-ACCESS  read-only
        STATUS      current
        DESCRIPTION "The FEC name of VWAN."
        ::= {fextInfoVWANStatusEntry 5}

    fextInfoVWANStatusTargetCount OBJECT-TYPE
        SYNTAX      Integer32
        MAX-ACCESS  read-only
        STATUS      current
        DESCRIPTION "The target count of VWAN."
        ::= {fextInfoVWANStatusEntry 6}

    fextInfoVWANStatusSessionCount OBJECT-TYPE
        SYNTAX      Integer32
        MAX-ACCESS  read-only
        STATUS      current
        DESCRIPTION "The session count of VWAN."
        ::= {fextInfoVWANStatusEntry 7}

    fextInfoVWANStatusSessionTimeout OBJECT-TYPE
        SYNTAX      Integer32
        MAX-ACCESS  read-only
        STATUS      current
        DESCRIPTION "The session timeout of VWAN."
        ::= {fextInfoVWANStatusEntry 8}

    fextInfoVWANStatusVersion OBJECT-TYPE
        SYNTAX      Integer32
        MAX-ACCESS  read-only
        STATUS      current
        DESCRIPTION "The version of VWAN."
        ::= {fextInfoVWANStatusEntry 9}

    --
    -- fextInfoVWAN.fextInfoVWANStatusMember
    --

    fextInfoVWANStatusMemberEntry OBJECT-TYPE
        SYNTAX      FextInfoVWANStatusMemberEntry
        MAX-ACCESS  not-accessible
        STATUS      current
        DESCRIPTION "Member infromation of a Virtual WAN."
        INDEX       {fextInfoVWANStatusIndex, fextInfoVWANStatusMemberIndex}
        ::= {fextInfoVWANStatusMember 1}

    FextInfoVWANStatusMemberEntry ::= SEQUENCE {
        fextInfoVWANStatusMemberIndex          FnIndex,
        fextInfoVWANStatusMemberName           DisplayString,
        fextInfoVWANStatusMemberStatus         DisplayString,
        fextInfoVWANStatusMemberPriority       Integer32,
        fextInfoVWANStatusMemberWeight         Integer32,
        fextInfoVWANStatusMemberCapacity       Integer32,
        fextInfoVWANStatusMemberMonthlyFee     Integer32,
        fextInfoVWANStatusMemberSessionCount   Integer32,
        fextInfoVWANStatusMemberReference      Integer32,
        fextInfoVWANStatusMemberInterface      DisplayString,
        fextInfoVWANStatusMemberNextHop        DisplayString,
        fextInfoVWANStatusMemberInBandwidth    Integer32,
        fextInfoVWANStatusMemberOutBandwidth   Integer32,
        fextInfoVWANStatusMemberTotalBandwidth Integer32,
        fextInfoVWANStatusMemberDataIn         Counter64,
        fextInfoVWANStatusMemberDataOut        Counter64,
        fextInfoVWANStatusMemberTPIn           Counter64,
        fextInfoVWANStatusMemberTPOut          Counter64
    }

    fextInfoVWANStatusMemberIndex OBJECT-TYPE
        SYNTAX      FnIndex
        MAX-ACCESS  not-accessible
        STATUS      current
        DESCRIPTION "An index uniquely defining a member information of VWAN."
        ::= {fextInfoVWANStatusMemberEntry 1}

    fextInfoVWANStatusMemberName OBJECT-TYPE
        SYNTAX      DisplayString
        MAX-ACCESS  read-only
        STATUS      current
        DESCRIPTION "The name of VWAN member."
        ::= {fextInfoVWANStatusMemberEntry 2}

    fextInfoVWANStatusMemberStatus OBJECT-TYPE
        SYNTAX      DisplayString
        MAX-ACCESS  read-only
        STATUS      current
        DESCRIPTION "The status of VWAN member (dead,busy or overage)."
        ::= {fextInfoVWANStatusMemberEntry 3}

    fextInfoVWANStatusMemberPriority OBJECT-TYPE
        SYNTAX      Integer32
        MAX-ACCESS  read-only
        STATUS      current
        DESCRIPTION "The priority of VWAN member."
        ::= {fextInfoVWANStatusMemberEntry 4}

    fextInfoVWANStatusMemberWeight OBJECT-TYPE
        SYNTAX      Integer32
        MAX-ACCESS  read-only
        STATUS      current
        DESCRIPTION "The weight of VWAN member."
        ::= {fextInfoVWANStatusMemberEntry 5}

    fextInfoVWANStatusMemberCapacity OBJECT-TYPE
        SYNTAX      Integer32
        MAX-ACCESS  read-only
        STATUS      current
        DESCRIPTION "The capacity of VWAN member."
        ::= {fextInfoVWANStatusMemberEntry 6}

    fextInfoVWANStatusMemberMonthlyFee OBJECT-TYPE
        SYNTAX      Integer32
        MAX-ACCESS  read-only
        STATUS      current
        DESCRIPTION "The monthly fee of VWAN member."
        ::= {fextInfoVWANStatusMemberEntry 7}

    fextInfoVWANStatusMemberSessionCount OBJECT-TYPE
        SYNTAX      Integer32
        MAX-ACCESS  read-only
        STATUS      current
        DESCRIPTION "The session count of VWAN member."
        ::= {fextInfoVWANStatusMemberEntry 8}

    fextInfoVWANStatusMemberReference OBJECT-TYPE
        SYNTAX      Integer32
        MAX-ACCESS  read-only
        STATUS      current
        DESCRIPTION "The reference of VWAN member."
        ::= {fextInfoVWANStatusMemberEntry 9}

    fextInfoVWANStatusMemberInterface OBJECT-TYPE
        SYNTAX      DisplayString
        MAX-ACCESS  read-only
        STATUS      current
        DESCRIPTION "The interface of VWAN member."
        ::= {fextInfoVWANStatusMemberEntry 10}

    fextInfoVWANStatusMemberNextHop OBJECT-TYPE
        SYNTAX      DisplayString
        MAX-ACCESS  read-only
        STATUS      current
        DESCRIPTION "The next hop of VWAN member."
        ::= {fextInfoVWANStatusMemberEntry 11}

    fextInfoVWANStatusMemberInBandwidth OBJECT-TYPE
        SYNTAX      Integer32
        MAX-ACCESS  read-only
        STATUS      current
        DESCRIPTION "The inbound bandwidth of VWAN member."
        ::= {fextInfoVWANStatusMemberEntry 12}

    fextInfoVWANStatusMemberOutBandwidth OBJECT-TYPE
        SYNTAX      Integer32
        MAX-ACCESS  read-only
        STATUS      current
        DESCRIPTION "The outbound bandwidth of VWAN member."
        ::= {fextInfoVWANStatusMemberEntry 13}

    fextInfoVWANStatusMemberTotalBandwidth OBJECT-TYPE
        SYNTAX      Integer32
        MAX-ACCESS  read-only
        STATUS      current
        DESCRIPTION "The total bandwidth of VWAN member."
        ::= {fextInfoVWANStatusMemberEntry 14}

    fextInfoVWANStatusMemberDataIn OBJECT-TYPE
        SYNTAX      Counter64
        MAX-ACCESS  read-only
        STATUS      current
        DESCRIPTION "The in data of VWAN member."
        ::= {fextInfoVWANStatusMemberEntry 15}

    fextInfoVWANStatusMemberDataOut OBJECT-TYPE
        SYNTAX      Counter64
        MAX-ACCESS  read-only
        STATUS      current
        DESCRIPTION "The out data of VWAN member."
        ::= {fextInfoVWANStatusMemberEntry 16}

    fextInfoVWANStatusMemberTPIn OBJECT-TYPE
        SYNTAX      Counter64
        MAX-ACCESS  read-only
        STATUS      current
        DESCRIPTION "The in packets of VWAN member."
        ::= {fextInfoVWANStatusMemberEntry 17}

    fextInfoVWANStatusMemberTPOut OBJECT-TYPE
        SYNTAX      Counter64
        MAX-ACCESS  read-only
        STATUS      current
        DESCRIPTION "The out packets of VWAN member."
        ::= {fextInfoVWANStatusMemberEntry 18}

    --
    -- fextInfoVWAN.fextInfoVWANMember
    --

    fextInfoVWANMemberEntry OBJECT-TYPE
        SYNTAX      FextInfoVWANMemberEntry
        MAX-ACCESS  not-accessible
        STATUS      current
        DESCRIPTION "Virtual WAN Member infromation."
        INDEX       {fextInfoVWANMemberIndex}
        ::= {fextInfoVWANMember 1}

    FextInfoVWANMemberEntry ::= SEQUENCE {
        fextInfoVWANMemberIndex            FnIndex,
        fextInfoVWANMemberName             DisplayString,
        fextInfoVWANMemberTarget           DisplayString,
        fextInfoVWANMemberPriority         Integer32,
        fextInfoVWANMemberCapacity         Integer32,
        fextInfoVWANMemberMonthlyFee       Integer32,
        fextInfoVWANMemberWeight           Integer32,
        fextInfoVWANMemberInBwThreshold    Integer32,
        fextInfoVWANMemberOutBwThreshold   Integer32,
        fextInfoVWANMemberTotalBwThreshold Integer32,
        fextInfoVWANMemberReference        Integer32
    }

    fextInfoVWANMemberIndex OBJECT-TYPE
        SYNTAX      FnIndex
        MAX-ACCESS  not-accessible
        STATUS      current
        DESCRIPTION "An index uniquely defining a VWAN member information."
        ::= {fextInfoVWANMemberEntry 1}

    fextInfoVWANMemberName OBJECT-TYPE
        SYNTAX      DisplayString
        MAX-ACCESS  read-only
        STATUS      current
        DESCRIPTION "The name of VWAN member."
        ::= {fextInfoVWANMemberEntry 2}

    fextInfoVWANMemberTarget OBJECT-TYPE
        SYNTAX      DisplayString
        MAX-ACCESS  read-only
        STATUS      current
        DESCRIPTION "The target of VWAN member."
        ::= {fextInfoVWANMemberEntry 3}

    fextInfoVWANMemberPriority OBJECT-TYPE
        SYNTAX      Integer32
        MAX-ACCESS  read-only
        STATUS      current
        DESCRIPTION "The priority of VWAN member."
        ::= {fextInfoVWANMemberEntry 4}

    fextInfoVWANMemberCapacity OBJECT-TYPE
        SYNTAX      Integer32
        MAX-ACCESS  read-only
        STATUS      current
        DESCRIPTION "The capacity of VWAN member."
        ::= {fextInfoVWANMemberEntry 5}

    fextInfoVWANMemberMonthlyFee OBJECT-TYPE
        SYNTAX      Integer32
        MAX-ACCESS  read-only
        STATUS      current
        DESCRIPTION "The monthly fee of VWAN member."
        ::= {fextInfoVWANMemberEntry 6}

    fextInfoVWANMemberWeight OBJECT-TYPE
        SYNTAX      Integer32
        MAX-ACCESS  read-only
        STATUS      current
        DESCRIPTION "The monthly fee of VWAN member."
        ::= {fextInfoVWANMemberEntry 7}

    fextInfoVWANMemberInBwThreshold OBJECT-TYPE
        SYNTAX      Integer32
        MAX-ACCESS  read-only
        STATUS      current
        DESCRIPTION "The inbound bandwidth threshold of VWAN member."
        ::= {fextInfoVWANMemberEntry 8}

    fextInfoVWANMemberOutBwThreshold OBJECT-TYPE
        SYNTAX      Integer32
        MAX-ACCESS  read-only
        STATUS      current
        DESCRIPTION "The outbound bandwidth threshold of VWAN member."
        ::= {fextInfoVWANMemberEntry 9}

    fextInfoVWANMemberTotalBwThreshold OBJECT-TYPE
        SYNTAX      Integer32
        MAX-ACCESS  read-only
        STATUS      current
        DESCRIPTION "The total bandwidth threshold of VWAN member."
        ::= {fextInfoVWANMemberEntry 10}

    fextInfoVWANMemberReference OBJECT-TYPE
        SYNTAX      Integer32
        MAX-ACCESS  read-only
        STATUS      current
        DESCRIPTION "The reference of VWAN member information."
        ::= {fextInfoVWANMemberEntry 11}

    --
    -- fextInfo.fextInfoVPN
    --
    -- fextInfoVPNIPsec ::= {fextInfoVPN 1}
    -- fextInfoVPNCert  ::= {fextInfoVPN 2}
    --

    fextInfoVPNIPsec    OBJECT IDENTIFIER ::= {fextInfoVPN 1}
    fextInfoVPNCert     OBJECT IDENTIFIER ::= {fextInfoVPN 2}

    --
    -- fextInfoVPN.fextInfoVPNIPsec
    --
    -- fextInfoIPsecTunnel      ::= {fextInfoVPNIPsec 1}
    -- fextInfoIPsecTunSelector ::= {fextInfoVPNIPsec 2}
    --

    fextInfoIPsecTunnel OBJECT-TYPE
        SYNTAX      SEQUENCE OF FextInfoIPsecTunnelEntry
        MAX-ACCESS  not-accessible
        STATUS      current
        DESCRIPTION "A table of IPsec VPN tunnels."
        ::= {fextInfoVPNIPsec 1}

    fextInfoIPsecTunSelector OBJECT-TYPE
        SYNTAX      SEQUENCE OF FextInfoIPsecTunSelectorEntry
        MAX-ACCESS  not-accessible
        STATUS      current
        DESCRIPTION "A table of IPsec VPN tunnel selectors."
        ::= {fextInfoVPNIPsec 2}

    --
    -- fextInfoVPNIPsec.fextInfoIPsecTunnel
    --

    fextInfoIPsecTunnelEntry OBJECT-TYPE
        SYNTAX      FextInfoIPsecTunnelEntry
        MAX-ACCESS  not-accessible
        STATUS      current
        DESCRIPTION "An entry containing IPsec VPN tunnel info."
        INDEX       {fextInfoIPsecTunIndex}
        ::= {fextInfoIPsecTunnel 1}

    FextInfoIPsecTunnelEntry ::= SEQUENCE {
        fextInfoIPsecTunIndex            FnIndex,
        fextInfoIPsecTunPhase1Name       DisplayString,
        fextInfoIPsecTunStatus           DisplayString,
        fextInfoIPsecTunLocGwIp          DisplayString,
        fextInfoIPsecTunRemGwIp          DisplayString,
        fextInfoIPsecTunInBytes          Counter64,
        fextInfoIPsecTunOutBytes         Counter64,
        fextInfoIPsecTunUpSeconds        Integer32
    }

    fextInfoIPsecTunIndex OBJECT-TYPE
        SYNTAX      FnIndex
        MAX-ACCESS  not-accessible
        STATUS      current
        DESCRIPTION "An index uniquely defining a IPsec tunnel."
        ::= {fextInfoIPsecTunnelEntry 1}

    fextInfoIPsecTunPhase1Name OBJECT-TYPE
        SYNTAX      DisplayString
        MAX-ACCESS  read-only
        STATUS      current
        DESCRIPTION  "Descriptive name of phase1 configuration for the tunnel."
        ::= {fextInfoIPsecTunnelEntry 2}

    fextInfoIPsecTunStatus OBJECT-TYPE
        SYNTAX      DisplayString
        MAX-ACCESS  read-only
        STATUS      current
        DESCRIPTION "Current status of tunnel (up or down)."
        ::= {fextInfoIPsecTunnelEntry 3}

    fextInfoIPsecTunLocGwIp OBJECT-TYPE
        SYNTAX      DisplayString
        MAX-ACCESS  read-only
        STATUS      current
        DESCRIPTION "IP of local gateway used by the tunnel."
        ::= {fextInfoIPsecTunnelEntry 4}

    fextInfoIPsecTunRemGwIp OBJECT-TYPE
        SYNTAX      DisplayString
        MAX-ACCESS  read-only
        STATUS      current
        DESCRIPTION "IP of remote gateway used by the tunnel."
        ::= {fextInfoIPsecTunnelEntry 5}

    fextInfoIPsecTunInBytes OBJECT-TYPE
        SYNTAX      Counter64
        MAX-ACCESS  read-only
        STATUS      current
        DESCRIPTION "The number of bytes received on the tunnel after the tunnel was up."
        ::= {fextInfoIPsecTunnelEntry 6}

    fextInfoIPsecTunOutBytes OBJECT-TYPE
        SYNTAX      Counter64
        MAX-ACCESS  read-only
        STATUS      current
        DESCRIPTION "The number of bytes sent out on the tunnel after the tunnel was up."
        ::= {fextInfoIPsecTunnelEntry 7}

    fextInfoIPsecTunUpSeconds OBJECT-TYPE
        SYNTAX      Integer32
        MAX-ACCESS  read-only
        STATUS      current
        DESCRIPTION "Tunnel up time in seconds."
        ::= {fextInfoIPsecTunnelEntry 8}

    --
    -- fextInfoVPNIPsec.fextInfoIPsecTunSelector
    --

    fextInfoIPsecTunSelectorEntry OBJECT-TYPE
        SYNTAX      FextInfoIPsecTunSelectorEntry
        MAX-ACCESS  not-accessible
        STATUS      current
        DESCRIPTION "An entry containing IPsec VPN tunnel selector info."
        INDEX       {fextInfoIPsecTunIndex, fextInfoIPsecTunSelectorIndex}
        ::= {fextInfoIPsecTunSelector 1}

    FextInfoIPsecTunSelectorEntry ::= SEQUENCE {
        fextInfoIPsecTunSelectorIndex    FnIndex,
        fextInfoIPsecTunSelectorP2Name   DisplayString,
        fextInfoIPsecTunSelectorStatus   DisplayString,
        fextInfoIPsecTunSelectorExpire   Integer32,
        fextInfoIPsecTunSelectorSrcNet   DisplayString,
        fextInfoIPsecTunSelectorDstNet   DisplayString,
        fextInfoIPsecTunSelectorSrcPort  Integer32,
        fextInfoIPsecTunSelectorDstPort  Integer32,
        fextInfoIPsecTunSelectorProto    Integer32,
        fextInfoIPsecTunSelectorInBytes  Counter64,
        fextInfoIPsecTunSelectorOutBytes Counter64
    }

    fextInfoIPsecTunSelectorIndex OBJECT-TYPE
        SYNTAX      FnIndex
        MAX-ACCESS  not-accessible
        STATUS      current
        DESCRIPTION "An index uniquely defining a IPsec tunnel selector."
        ::= {fextInfoIPsecTunSelectorEntry 1}

    fextInfoIPsecTunSelectorP2Name OBJECT-TYPE
        SYNTAX      DisplayString
        MAX-ACCESS  read-only
        STATUS      current
        DESCRIPTION  "The phase2 name of a IPsec tunnel selector."
        ::= {fextInfoIPsecTunSelectorEntry 2}

    fextInfoIPsecTunSelectorStatus OBJECT-TYPE
        SYNTAX      DisplayString
        MAX-ACCESS  read-only
        STATUS      current
        DESCRIPTION "Current status of IPsec tunnel selector (up or down)."
        ::= {fextInfoIPsecTunSelectorEntry 3}

    fextInfoIPsecTunSelectorExpire OBJECT-TYPE
        SYNTAX      Integer32
        MAX-ACCESS  read-only
        STATUS      current
        DESCRIPTION "The expire time of IPsec tunnel selector in seconds."
        ::= {fextInfoIPsecTunSelectorEntry 4}

    fextInfoIPsecTunSelectorSrcNet OBJECT-TYPE
        SYNTAX      DisplayString
        MAX-ACCESS  read-only
        STATUS      current
        DESCRIPTION "Subnet of source selector."
        ::= {fextInfoIPsecTunSelectorEntry 5}

    fextInfoIPsecTunSelectorDstNet OBJECT-TYPE
        SYNTAX      DisplayString
        MAX-ACCESS  read-only
        STATUS      current
        DESCRIPTION "Subnet of destination selector."
        ::= {fextInfoIPsecTunSelectorEntry 6}

    fextInfoIPsecTunSelectorSrcPort OBJECT-TYPE
        SYNTAX      Integer32
        MAX-ACCESS  read-only
        STATUS      current
        DESCRIPTION "Port of source selector."
        ::= {fextInfoIPsecTunSelectorEntry 7}

    fextInfoIPsecTunSelectorDstPort OBJECT-TYPE
        SYNTAX      Integer32
        MAX-ACCESS  read-only
        STATUS      current
        DESCRIPTION "Port of destination selector."
        ::= {fextInfoIPsecTunSelectorEntry 8}

    fextInfoIPsecTunSelectorProto OBJECT-TYPE
        SYNTAX      Integer32
        MAX-ACCESS  read-only
        STATUS      current
        DESCRIPTION  "Protocol number for selector."
        ::= {fextInfoIPsecTunSelectorEntry 9}

    fextInfoIPsecTunSelectorInBytes OBJECT-TYPE
        SYNTAX      Counter64
        MAX-ACCESS  read-only
        STATUS      current
        DESCRIPTION "The number of bytes received on the selector after the selector was up."
        ::= {fextInfoIPsecTunSelectorEntry 10}

    fextInfoIPsecTunSelectorOutBytes OBJECT-TYPE
        SYNTAX      Counter64
        MAX-ACCESS  read-only
        STATUS      current
        DESCRIPTION "The number of bytes sent out on the selector after the selector was up."
        ::= {fextInfoIPsecTunSelectorEntry 11}

    --
    -- fextInfoVPN.fextInfoVPNCert
    --
    -- fextInfoVPNCertCA    ::= {fextInfoVPNCert 1}
    -- fextInfoVPNCertLocal ::= {fextInfoVPNCert 2}
    --

    fextInfoVPNCertCA OBJECT-TYPE
        SYNTAX      SEQUENCE OF FextInfoVPNCertCAEntry
        MAX-ACCESS  not-accessible
        STATUS      current
        DESCRIPTION "A table of VPN CA certificates."
        ::= {fextInfoVPNCert 1}

    fextInfoVPNCertLocal OBJECT-TYPE
        SYNTAX      SEQUENCE OF FextInfoVPNCertLocalEntry
        MAX-ACCESS  not-accessible
        STATUS      current
        DESCRIPTION "A table of VPN local certificates."
        ::= {fextInfoVPNCert 2}

    --
    -- fextInfoVPNCert.fextInfoVPNCertCA
    --

    fextInfoVPNCertCAEntry OBJECT-TYPE
        SYNTAX      FextInfoVPNCertCAEntry
        MAX-ACCESS  not-accessible
        STATUS      current
        DESCRIPTION "An entry containing VPN CA certificate info."
        INDEX       {fextInfoVPNCertCAIndex}
        ::= {fextInfoVPNCertCA 1}

    FextInfoVPNCertCAEntry ::= SEQUENCE {
        fextInfoVPNCertCAIndex          FnIndex,
        fextInfoVPNCertCAName           DisplayString,
        fextInfoVPNCertCAStatus         DisplayString,
        fextInfoVPNCertCASubject        DisplayString,
        fextInfoVPNCertCAIssuer         DisplayString,
        fextInfoVPNCertCAValidFrom      DisplayString,
        fextInfoVPNCertCAValidTo        DisplayString,
        fextInfoVPNCertCAFingerprint    DisplayString,
        fextInfoVPNCertCASerialNum      DisplayString
    }

    fextInfoVPNCertCAIndex OBJECT-TYPE
        SYNTAX      FnIndex
        MAX-ACCESS  not-accessible
        STATUS      current
        DESCRIPTION "An index uniquely defining a CA certificate."
        ::= {fextInfoVPNCertCAEntry 1}

    fextInfoVPNCertCAName OBJECT-TYPE
        SYNTAX      DisplayString
        MAX-ACCESS  read-only
        STATUS      current
        DESCRIPTION "The name of CA certificate."
        ::= {fextInfoVPNCertCAEntry 2}

    fextInfoVPNCertCAStatus OBJECT-TYPE
        SYNTAX      DisplayString
        MAX-ACCESS  read-only
        STATUS      current
        DESCRIPTION "Current status of certificate (valid or invalid)."
        ::= {fextInfoVPNCertCAEntry 3}

    fextInfoVPNCertCASubject OBJECT-TYPE
        SYNTAX      DisplayString
        MAX-ACCESS  read-only
        STATUS      current
        DESCRIPTION "Subject of the certificate."
        ::= {fextInfoVPNCertCAEntry 4}

    fextInfoVPNCertCAIssuer OBJECT-TYPE
        SYNTAX      DisplayString
        MAX-ACCESS  read-only
        STATUS      current
        DESCRIPTION "Issuer of the certificate."
        ::= {fextInfoVPNCertCAEntry 5}

    fextInfoVPNCertCAValidFrom OBJECT-TYPE
        SYNTAX      DisplayString
        MAX-ACCESS  read-only
        STATUS      current
        DESCRIPTION "The start time of the certificate validity period."
        ::= {fextInfoVPNCertCAEntry 6}

    fextInfoVPNCertCAValidTo OBJECT-TYPE
        SYNTAX      DisplayString
        MAX-ACCESS  read-only
        STATUS      current
        DESCRIPTION "The end time of the certificate validity period."
        ::= {fextInfoVPNCertCAEntry 7}

    fextInfoVPNCertCAFingerprint OBJECT-TYPE
        SYNTAX      DisplayString
        MAX-ACCESS  read-only
        STATUS      current
        DESCRIPTION "The MD5 fingerprint of the certificate."
        ::= {fextInfoVPNCertCAEntry 8}

    fextInfoVPNCertCASerialNum OBJECT-TYPE
        SYNTAX      DisplayString
        MAX-ACCESS  read-only
        STATUS      current
        DESCRIPTION "The serial number of the certificate."
        ::= {fextInfoVPNCertCAEntry 9}

	--
	-- fextInfoVPNCert.fextInfoVPNCertLocal
	--

	fextInfoVPNCertLocalEntry OBJECT-TYPE
		SYNTAX      FextInfoVPNCertLocalEntry
		MAX-ACCESS  not-accessible
		STATUS      current
		DESCRIPTION "An entry containing VPN local certificate info."
		INDEX       {fextInfoVPNCertLocIndex}
		::= {fextInfoVPNCertLocal 1}

	FextInfoVPNCertLocalEntry ::= SEQUENCE {
		fextInfoVPNCertLocIndex          FnIndex,
		fextInfoVPNCertLocName           DisplayString,
		fextInfoVPNCertLocStatus         DisplayString,
		fextInfoVPNCertLocSubject        DisplayString,
		fextInfoVPNCertLocIssuer         DisplayString,
		fextInfoVPNCertLocValidFrom      DisplayString,
		fextInfoVPNCertLocValidTo        DisplayString,
		fextInfoVPNCertLocFingerprint    DisplayString,
		fextInfoVPNCertLocSerialNum      DisplayString
	}

	fextInfoVPNCertLocIndex OBJECT-TYPE
		SYNTAX      FnIndex
		MAX-ACCESS  not-accessible
		STATUS      current
		DESCRIPTION	"An index uniquely defining a local certificate."
		::= {fextInfoVPNCertLocalEntry 1}

	fextInfoVPNCertLocName OBJECT-TYPE
	    SYNTAX      DisplayString
	    MAX-ACCESS  read-only
	    STATUS      current
	    DESCRIPTION "The name of local certificate."
	    ::= {fextInfoVPNCertLocalEntry 2}

	fextInfoVPNCertLocStatus OBJECT-TYPE
	    SYNTAX      DisplayString
	    MAX-ACCESS  read-only
	    STATUS      current
	    DESCRIPTION "Current status of certificate (valid or invalid)."
	    ::= {fextInfoVPNCertLocalEntry 3}

	fextInfoVPNCertLocSubject OBJECT-TYPE
	    SYNTAX      DisplayString
	    MAX-ACCESS  read-only
	    STATUS      current
	    DESCRIPTION "Subject of the certificate."
	    ::= {fextInfoVPNCertLocalEntry 4}

	fextInfoVPNCertLocIssuer OBJECT-TYPE
	    SYNTAX      DisplayString
	    MAX-ACCESS  read-only
	    STATUS      current
	    DESCRIPTION "Issuer of the certificate."
	    ::= {fextInfoVPNCertLocalEntry 5}

	fextInfoVPNCertLocValidFrom OBJECT-TYPE
	    SYNTAX      DisplayString
	    MAX-ACCESS  read-only
	    STATUS      current
	    DESCRIPTION "The start time of the certificate validity period."
	    ::= {fextInfoVPNCertLocalEntry 6}

	fextInfoVPNCertLocValidTo OBJECT-TYPE
	    SYNTAX      DisplayString
	    MAX-ACCESS  read-only
	    STATUS      current
	    DESCRIPTION "The end time of the certificate validity period."
	    ::= {fextInfoVPNCertLocalEntry 7}

	fextInfoVPNCertLocFingerprint OBJECT-TYPE
	    SYNTAX      DisplayString
	    MAX-ACCESS  read-only
	    STATUS      current
	    DESCRIPTION "The MD5 fingerprint of the certificate."
	    ::= {fextInfoVPNCertLocalEntry 8}

	fextInfoVPNCertLocSerialNum OBJECT-TYPE
	    SYNTAX      DisplayString
	    MAX-ACCESS  read-only
	    STATUS      current
	    DESCRIPTION "The serial number of the certificate."
	    ::= {fextInfoVPNCertLocalEntry 9}

    --
    -- fextInfo.fextInfoHMon
    --
    -- fextInfoHMonIfStat   ::= {fextInfoHMon 1}
    -- fextInfoHMonHChkStat ::= {fextInfoHMon 2}
    --

    fextInfoHMonIfStat OBJECT-TYPE
        SYNTAX      SEQUENCE OF FextInfoHMonIfStatEntry
        MAX-ACCESS  not-accessible
        STATUS      current
        DESCRIPTION "A table of interface send and receive statistics."
        ::= {fextInfoHMon 1}

    fextInfoHMonHChkStat OBJECT-TYPE
        SYNTAX      SEQUENCE OF FextInfoHMonHChkStatEntry
        MAX-ACCESS  not-accessible
        STATUS      current
        DESCRIPTION "A table of interface health check statistics."
        ::= {fextInfoHMon 2}

	--
	-- fextInfoHMon.fextInfoHMonIfStat
	--

	fextInfoHMonIfStatEntry OBJECT-TYPE
		SYNTAX      FextInfoHMonIfStatEntry
		MAX-ACCESS  not-accessible
		STATUS      current
		DESCRIPTION "An entry containing interface send and receive statistics."
		INDEX       {fextInfoHMonIfStatIndex}
		::= {fextInfoHMonIfStat 1}

	FextInfoHMonIfStatEntry ::= SEQUENCE {
        fextInfoHMonIfStatIndex     FnIndex,
        fextInfoHMonIfStatMonitor   DisplayString,
        fextInfoHMonIfStatIfName    DisplayString,
        fextInfoHMonIfStatRxBytes   Counter64,
        fextInfoHMonIfStatTxBytes   Counter64,
        fextInfoHMonIfStatRxPkts    Counter64,
        fextInfoHMonIfStatTxPkts    Counter64,
        fextInfoHMonIfStatRxDropped Counter64,
        fextInfoHMonIfStatTxDropped Counter64,
        fextInfoHMonIfStatRxBps     Counter64,
        fextInfoHMonIfStatTxBps     Counter64,
        fextInfoHMonIfStatRxPps     Counter64,
        fextInfoHMonIfStatTxPps     Counter64
	}

	fextInfoHMonIfStatIndex OBJECT-TYPE
		SYNTAX      FnIndex
		MAX-ACCESS  not-accessible
		STATUS      current
		DESCRIPTION	"An index uniquely defining a interface statistic."
		::= {fextInfoHMonIfStatEntry 1}

	fextInfoHMonIfStatMonitor OBJECT-TYPE
	    SYNTAX      DisplayString
	    MAX-ACCESS  read-only
	    STATUS      current
	    DESCRIPTION "The name of the monitor that collected the interface statistic."
	    ::= {fextInfoHMonIfStatEntry 2}

	fextInfoHMonIfStatIfName OBJECT-TYPE
	    SYNTAX      DisplayString
	    MAX-ACCESS  read-only
	    STATUS      current
	    DESCRIPTION "The name of interface."
	    ::= {fextInfoHMonIfStatEntry 3}

	fextInfoHMonIfStatRxBytes OBJECT-TYPE
	    SYNTAX      Counter64
	    MAX-ACCESS  read-only
	    STATUS      current
	    DESCRIPTION "The total number of bytes received on the interface."
	    ::= {fextInfoHMonIfStatEntry 4}

	fextInfoHMonIfStatTxBytes OBJECT-TYPE
	    SYNTAX      Counter64
	    MAX-ACCESS  read-only
	    STATUS      current
	    DESCRIPTION "The total number of bytes transmitted out of the interface."
	    ::= {fextInfoHMonIfStatEntry 5}

	fextInfoHMonIfStatRxPkts OBJECT-TYPE
	    SYNTAX      Counter64
	    MAX-ACCESS  read-only
	    STATUS      current
	    DESCRIPTION "The total number of packets received on the interface."
	    ::= {fextInfoHMonIfStatEntry 6}

	fextInfoHMonIfStatTxPkts OBJECT-TYPE
	    SYNTAX      Counter64
	    MAX-ACCESS  read-only
	    STATUS      current
	    DESCRIPTION "The total number of packets transmitted out of the interface."
	    ::= {fextInfoHMonIfStatEntry 7}

	fextInfoHMonIfStatRxDropped OBJECT-TYPE
	    SYNTAX      Counter64
	    MAX-ACCESS  read-only
	    STATUS      current
	    DESCRIPTION "The number of inbound packets which were discarded on the interface."
	    ::= {fextInfoHMonIfStatEntry 8}

	fextInfoHMonIfStatTxDropped OBJECT-TYPE
	    SYNTAX      Counter64
	    MAX-ACCESS  read-only
	    STATUS      current
	    DESCRIPTION "The number of outbound packets which were discarded on the interface."
	    ::= {fextInfoHMonIfStatEntry 9}

	fextInfoHMonIfStatRxBps OBJECT-TYPE
	    SYNTAX      Counter64
	    MAX-ACCESS  read-only
	    STATUS      current
	    DESCRIPTION "The inbound throughput of the interface in bits per second."
	    ::= {fextInfoHMonIfStatEntry 10}

	fextInfoHMonIfStatTxBps OBJECT-TYPE
	    SYNTAX      Counter64
	    MAX-ACCESS  read-only
	    STATUS      current
	    DESCRIPTION "The outbound throughput of the interface in bits per second."
	    ::= {fextInfoHMonIfStatEntry 11}

	fextInfoHMonIfStatRxPps OBJECT-TYPE
	    SYNTAX      Counter64
	    MAX-ACCESS  read-only
	    STATUS      current
	    DESCRIPTION "The inbound throughput of the interface in data packets per second."
	    ::= {fextInfoHMonIfStatEntry 12}

	fextInfoHMonIfStatTxPps OBJECT-TYPE
	    SYNTAX      Counter64
	    MAX-ACCESS  read-only
	    STATUS      current
	    DESCRIPTION "The outbound throughput of the interface in data packets per second."
	    ::= {fextInfoHMonIfStatEntry 13}

	--
	-- fextInfoHMon.fextInfoHMonHChkStat
	--

	fextInfoHMonHChkStatEntry OBJECT-TYPE
		SYNTAX      FextInfoHMonHChkStatEntry
		MAX-ACCESS  not-accessible
		STATUS      current
		DESCRIPTION "An entry containing interface health check statistics."
		INDEX       {fextInfoHMonHChkStatIndex}
		::= {fextInfoHMonHChkStat 1}

	FextInfoHMonHChkStatEntry ::= SEQUENCE {
        fextInfoHMonHChkStatIndex       FnIndex,
        fextInfoHMonHChkStatMonitor     DisplayString,
        fextInfoHMonHChkStatIfName      DisplayString,
        fextInfoHMonHChkStatRttAvg      DisplayString,
        fextInfoHMonHChkStatRttMax      DisplayString,
        fextInfoHMonHChkStatRttMin      DisplayString,
        fextInfoHMonHChkStatRttNow      DisplayString,
        fextInfoHMonHChkStatRttSd       DisplayString,
        fextInfoHMonHChkStatRttAmsd     DisplayString,
        fextInfoHMonHChkStatLossAvg     DisplayString,
        fextInfoHMonHChkStatLossMax     DisplayString,
        fextInfoHMonHChkStatLossMin     DisplayString,
        fextInfoHMonHChkStatLossNow     DisplayString
	}

	fextInfoHMonHChkStatIndex OBJECT-TYPE
		SYNTAX      FnIndex
		MAX-ACCESS  not-accessible
		STATUS      current
		DESCRIPTION	"An index uniquely defining a interface health check statistics."
		::= {fextInfoHMonHChkStatEntry 1}

	fextInfoHMonHChkStatMonitor OBJECT-TYPE
	    SYNTAX      DisplayString
	    MAX-ACCESS  read-only
	    STATUS      current
	    DESCRIPTION "The name of the monitor that measure interface health check statistics."
	    ::= {fextInfoHMonHChkStatEntry 2}

	fextInfoHMonHChkStatIfName OBJECT-TYPE
	    SYNTAX      DisplayString
	    MAX-ACCESS  read-only
	    STATUS      current
	    DESCRIPTION "The name of interface."
	    ::= {fextInfoHMonHChkStatEntry 3}

	fextInfoHMonHChkStatRttAvg OBJECT-TYPE
	    SYNTAX      DisplayString
	    MAX-ACCESS  read-only
	    STATUS      current
	    DESCRIPTION "The average latency of the interface in milliseconds during the last 10 measurements."
	    ::= {fextInfoHMonHChkStatEntry 4}

	fextInfoHMonHChkStatRttMax OBJECT-TYPE
	    SYNTAX      DisplayString
	    MAX-ACCESS  read-only
	    STATUS      current
	    DESCRIPTION "The max latency of the interface in milliseconds during the last 10 measurements."
	    ::= {fextInfoHMonHChkStatEntry 5}

	fextInfoHMonHChkStatRttMin OBJECT-TYPE
	    SYNTAX      DisplayString
	    MAX-ACCESS  read-only
	    STATUS      current
	    DESCRIPTION "The min latency of the interface in milliseconds during the last 10 measurements."
	    ::= {fextInfoHMonHChkStatEntry 6}

	fextInfoHMonHChkStatRttNow OBJECT-TYPE
	    SYNTAX      DisplayString
	    MAX-ACCESS  read-only
	    STATUS      current
	    DESCRIPTION "The latency of the interface in milliseconds in the latest measurement."
	    ::= {fextInfoHMonHChkStatEntry 7}

	fextInfoHMonHChkStatRttSd OBJECT-TYPE
	    SYNTAX      DisplayString
	    MAX-ACCESS  read-only
	    STATUS      current
	    DESCRIPTION "The latency variation (jitter) of the interface in milliseconds during the last 10 measurements."
	    ::= {fextInfoHMonHChkStatEntry 8}

	fextInfoHMonHChkStatRttAmsd OBJECT-TYPE
	    SYNTAX      DisplayString
	    MAX-ACCESS  read-only
	    STATUS      current
	    DESCRIPTION "The ratio of average latency vs standard deviation."
	    ::= {fextInfoHMonHChkStatEntry 9}

	fextInfoHMonHChkStatLossAvg OBJECT-TYPE
	    SYNTAX      DisplayString
	    MAX-ACCESS  read-only
	    STATUS      current
	    DESCRIPTION "The average packet loss rate of the interface during the last 10 measurements."
	    ::= {fextInfoHMonHChkStatEntry 10}

	fextInfoHMonHChkStatLossMax OBJECT-TYPE
	    SYNTAX      DisplayString
	    MAX-ACCESS  read-only
	    STATUS      current
	    DESCRIPTION "The max packet loss rate of the interface during the last 10 measurements."
	    ::= {fextInfoHMonHChkStatEntry 11}

	fextInfoHMonHChkStatLossMin OBJECT-TYPE
	    SYNTAX      DisplayString
	    MAX-ACCESS  read-only
	    STATUS      current
	    DESCRIPTION "The min packet loss rate of the interface during the last 10 measurements."
	    ::= {fextInfoHMonHChkStatEntry 12}

	fextInfoHMonHChkStatLossNow OBJECT-TYPE
	    SYNTAX      DisplayString
	    MAX-ACCESS  read-only
	    STATUS      current
	    DESCRIPTION "The packet loss ratio of interface in the latest measurement."
	    ::= {fextInfoHMonHChkStatEntry 13}

    --
    -- fextInfo.fextInfoCPM
    --
    -- fextInfoCPMStatus ::= {fextInfoCPM 1}
    --

    fextInfoCPMStatus OBJECT-IDENTITY
        STATUS      current
        DESCRIPTION "CPM status."
        ::= {fextInfoCPM 1}

    --
    -- fextInfoCPM.fextInfoCPMStatus
    --
    -- fextInfoCPMProcessID      ::= {fextInfoCPMStatus 1}
    -- fextInfoCPMConnectStatus  ::= {fextInfoCPMStatus 2}
    -- fextInfoCPMCloudSSLHost   ::= {fextInfoCPMStatus 3}
    -- fextInfoCPMCloudSSLPort   ::= {fextInfoCPMStatus 4}
    -- fextInfoCPMReconnectCount ::= {fextInfoCPMStatus 5}
    --

    fextInfoCPMProcessID OBJECT-TYPE
        SYNTAX      DisplayString
        MAX-ACCESS  read-only
        STATUS      current
        DESCRIPTION "CPM process ID."
        ::= {fextInfoCPMStatus 1}

    fextInfoCPMConnectStatus OBJECT-TYPE
        SYNTAX      DisplayString
        MAX-ACCESS  read-only
        STATUS      current
        DESCRIPTION "CPM connection status."
        ::= {fextInfoCPMStatus 2}

    fextInfoCPMCloudSSLHost OBJECT-TYPE
        SYNTAX      DisplayString
        MAX-ACCESS  read-only
        STATUS      current
        DESCRIPTION "CPM cloud SSL host."
        ::= {fextInfoCPMStatus 3}

    fextInfoCPMCloudSSLPort OBJECT-TYPE
        SYNTAX      DisplayString
        MAX-ACCESS  read-only
        STATUS      current
        DESCRIPTION "CPM cloud SSL port."
        ::= {fextInfoCPMStatus 4}

    fextInfoCPMReconnectCount OBJECT-TYPE
        SYNTAX      DisplayString
        MAX-ACCESS  read-only
        STATUS      current
        DESCRIPTION "CPM reconnection count."
        ::= {fextInfoCPMStatus 5}

    --
    -- fnFortiExtenderMib.fextTraps
    --

    fextTrapSystemReboot  NOTIFICATION-TYPE
        OBJECTS       { fextInfoEXTDHostName }
        STATUS        current
        DESCRIPTION   "system will reboot."
        ::=  {fextTraps 101}

    fextTrapOSImageFallback NOTIFICATION-TYPE
        OBJECTS       { fextInfoEXTDHostName }
        STATUS        current
        DESCRIPTION   "system start to fallback OS image."
        ::=  {fextTraps 102}

    fextTrapModeSwitch  NOTIFICATION-TYPE
        OBJECTS       { fextInfoEXTDHostName }
        STATUS        current
        DESCRIPTION   "system networking mode switched."
        ::=  {fextTraps 103}

    fextTrapFGTBackupModeSwitch  NOTIFICATION-TYPE
        OBJECTS       { fextInfoEXTDHostName }
        STATUS        current
        DESCRIPTION   "FortiGate backup work mode switched."
        ::=  {fextTraps 104}

    fextTrapDataExhausted  NOTIFICATION-TYPE
        OBJECTS       { fextInfoEXTDHostName }
        STATUS        current
        DESCRIPTION   "data plan is exhausted."
        ::=  {fextTraps 201}

    fextTrapSessionDisconnect  NOTIFICATION-TYPE
        OBJECTS       { fextInfoEXTDHostName }
        STATUS        current
        DESCRIPTION   "LTE data session is disconnected."
        ::=  {fextTraps 202}

    fextTrapLowSignalStrength  NOTIFICATION-TYPE
        OBJECTS       { fextInfoEXTDHostName }
        STATUS        current
        DESCRIPTION   "LTE signal strength is too low."
        ::=  {fextTraps 203}

	--
	-- fortinet.fnFortiExtenderMib.fextModel
	--
	
	-- fextModel start
	fextUnknown			OBJECT IDENTIFIER ::=	{fextModel 1}
	fextVM				OBJECT IDENTIFIER ::=	{fextModel 10}
	fext20D				OBJECT IDENTIFIER ::=	{fextModel 21}
	fext40D				OBJECT IDENTIFIER ::=	{fextModel 41}
	fext40DA			OBJECT IDENTIFIER ::=	{fextModel 42}
	fext200F			OBJECT IDENTIFIER ::=	{fextModel 200}
	fext201E			OBJECT IDENTIFIER ::=	{fextModel 201}
	fext202E			OBJECT IDENTIFIER ::=	{fextModel 202}
	fext211E			OBJECT IDENTIFIER ::=	{fextModel 211}
	fext212E			OBJECT IDENTIFIER ::=	{fextModel 212}
	fext311F			OBJECT IDENTIFIER ::=	{fextModel 311}
	fext312F			OBJECT IDENTIFIER ::=	{fextModel 312}
	fext511F			OBJECT IDENTIFIER ::=	{fextModel 511}
	fextF11A			OBJECT IDENTIFIER ::=	{fextModel 1011}
	fextF11E			OBJECT IDENTIFIER ::=	{fextModel 1012}
	fext212F			OBJECT IDENTIFIER ::=	{fextModel 2121}
	fextF21A			OBJECT IDENTIFIER ::=	{fextModel 2011}
	fextF21E			OBJECT IDENTIFIER ::=	{fextModel 2012}
	fev211FA			OBJECT IDENTIFIER ::=	{fextModel 2111}
	fev211F				OBJECT IDENTIFIER ::=	{fextModel 2112}
	fev212FA			OBJECT IDENTIFIER ::=	{fextModel 2121}
	fev212F				OBJECT IDENTIFIER ::=	{fextModel 2122}
	fextF22A			OBJECT IDENTIFIER ::=	{fextModel 2021}
	fextF22E			OBJECT IDENTIFIER ::=	{fextModel 2022}
	fer511G				OBJECT IDENTIFIER ::=	{fextModel 1511}
	fext30GWifi			OBJECT IDENTIFIER ::=	{fextModel 301}
	-- fextModel end

END
