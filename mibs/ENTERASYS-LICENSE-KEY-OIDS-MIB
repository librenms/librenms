ENTERASYS-LICENSE-KEY-OIDS-MIB DEFINITIONS ::= BEGIN

--  enterasys-license-key-oids-mib.txt
--
--  Part Number:
--
--

--  This module provides authoritative definitions for Enterasys
--  Networks' licensable feature OIDs.
--
--  This module will be extended, as needed.

--  Enterasys Networks reserves the right to make changes in
--  specification and other information contained in this document
--  without prior notice.  The reader should consult Enterasys
--  Networks to determine whether any such changes have been made.
--
--  In no event shall Enterasys Networks be liable for any incidental,
--  indirect, special, or consequential damages whatsoever (including
--  but not limited to lost profits) arising out of or related to this
--  document or the information contained in it, even if Enterasys
--  Networks has been advised of, known, or should have known, the
--  possibility of such damages.
--
--  Enterasys Networks grants vendors, end-users, and other interested
--  parties a non-exclusive license to use this Specification in connection
--  with the management of Enterasys products.

--  Copyright June, (2004-2007) Enterasys Networks, Inc.

IMPORTS
    MODULE-IDENTITY, OBJECT-IDENTITY
        FROM SNMPv2-SMI
    etsysOidOtherLicenseKeyId
        FROM ENTERASYS-OIDS-MIB
    etsysModules
        FROM ENTERASYS-MIB-NAMES;


etsysLicenseKeyOidsMIB MODULE-IDENTITY
    LAST-UPDATED "200706111424Z"  -- Mon Jun 11 14:24 UTC 2007
    ORGANIZATION "Enterasys Networks"
    CONTACT-INFO
        "Postal:  Enterasys Networks
                  50 Minuteman Rd.
                  Andover, MA 01810-1008
                  USA
         Phone:   +1 978 684 1000
         E-mail:  support@enterasys.com
         WWW:     http://www.enterasys.com"

    DESCRIPTION
        "This MIB module defines a portion of the SNMP enterprise
         MIBs under Enterasys Networks' enterprise OID pertaining to
         OIDs for licensable features on Enterasys Networks' 
         devices.  The OIDs contained in this module are intended to
         be returned by the etsysLicenseKeyIdentifier of the
         ENTERASYS-LICENSE-KEY-MIB."

    REVISION    "200706111424Z"  -- Mon Jun 11 14:24 UTC 2007
    DESCRIPTION "Added an OID for the hardware based N-EOS-L3-DIAMOND 
                 license key."

    REVISION    "200611131529Z"  -- Mon Nov 13 15:29 UTC 2006
    DESCRIPTION "Added an OID for the N-EOS-GPOLICY license key."

    REVISION    "200609051737Z"  -- Tue Sep  5 17:37 UTC 2006
    DESCRIPTION "Added an OID for the C Series IPV6 Routing feature."

    REVISION    "200608151956Z"  -- Tue Aug 15 19:56 UTC 2006
    DESCRIPTION "Added OIDs for the B Series Routing feature and
                 the C Series Advanced Routing feature."
    
    REVISION    "200512132112Z"  -- Tue Dec 13 21:12 GMT 2005
    DESCRIPTION "Added an OID for the B Series Policy feature."

    REVISION    "200411031701Z"  -- Wed Nov  3 17:01 GMT 2004
    DESCRIPTION "Added an OID for the N-EOS-PPC license key."

    REVISION    "200408241329Z"  -- Tue Aug 24 13:29 GMT 2004
    DESCRIPTION "The initial version of this MIB module."
    ::= { etsysModules 56 }

--  This part of the OID tree is used for licensable feature OID 
--  assignments for the various N-Series platforms.

etsysLicKeyIdNSeries OBJECT IDENTIFIER ::= { etsysOidOtherLicenseKeyId 1 }

etsysLicKeyIdNL3AdvancedFeature OBJECT-IDENTITY
    STATUS      current
--  Date        "200408241329Z"  - Tue Aug 24 13:29 GMT 2004
    DESCRIPTION
        "N-Series Layer 3 Advanced Features license.  This is the
         N-EOS-L3 license key."
    ::= { etsysLicKeyIdNSeries 1 }

etsysLicKeyIdNGoldRedundancy OBJECT-IDENTITY
    STATUS      current
--  Date        "200408241329Z"  - Tue Aug 24 13:29 GMT 2004
    DESCRIPTION
        "N-Series DFE-Gold Master Redundancy license.  This is the
         N-EOS-RED license key."
    ::= { etsysLicKeyIdNSeries 2 }

etsysLicKeyIdNPlatinumHighCapacity OBJECT-IDENTITY
    STATUS      current
--  Date        "200408241329Z"  - Tue Aug 24 13:29 GMT 2004
    DESCRIPTION
        "N-Series DFE-Platinum User Capacity license.  This is 
         the N-EOS-PUC license key."
    ::= { etsysLicKeyIdNSeries 3 }

etsysLicKeyIdNPlatinumPortCapacity OBJECT-IDENTITY
    STATUS      current
--  Date        "200411031701Z"  - Wed Nov  3 17:01 GMT 2004
    DESCRIPTION
        "N-Series DFE-Platinum Port Capacity license.  This is 
         the N-EOS-PPC license key."
    ::= { etsysLicKeyIdNSeries 4 }

etsysLicKeyIdNGoldPolicy OBJECT-IDENTITY
    STATUS      current
--  Date        "200611131529Z"  - Mon Nov 13 15:29 UTC 2006
    DESCRIPTION
        "N-Series DFE-Gold Policy license.  This is the N-EOS-GPOLICY 
         license key."
    ::= { etsysLicKeyIdNSeries 5 }

etsysLicKeyIdNL3DiamondFeature OBJECT-IDENTITY
    STATUS      current
--  Date        "200706111424Z"  - Mon Jun 11 14:24 UTC 2007
    DESCRIPTION
        "N-Series Layer 3 Diamond hardware based Advanced Features 
         license.  This is the N-EOS-L3-DIAMOND license key."
    ::= { etsysLicKeyIdNSeries 6 }

--  This part of the OID tree is used for licensable feature OID 
--  assignments for the various C-Series platforms.
etsysLicKeyIdCSeries OBJECT IDENTIFIER ::= { etsysOidOtherLicenseKeyId 2 }

etsysLicKeyIdCAdvancedRouting OBJECT-IDENTITY
    STATUS      current
--  Date        "200608151956Z"  - Tue Aug 15 19:56 UTC 2006
    DESCRIPTION
        "C-Series Advanced Routing License."
    ::= { etsysLicKeyIdCSeries 1 }

etsysLicKeyIdC3IpV6Routing OBJECT-IDENTITY
    STATUS      current
--  Date        "200609051737Z"  - Tue Sep  5 17:37 UTC 2006
    DESCRIPTION
        "C3 IP Version 6 Routing License."
    ::= { etsysLicKeyIdCSeries 2 }

--  This part of the OID tree is used for licensable feature OID 
--  assignments for the various B-Series platforms.
etsysLicKeyIdBSeries OBJECT IDENTIFIER ::= { etsysOidOtherLicenseKeyId 3 }

etsysLicKeyIdBPolicy OBJECT-IDENTITY
    STATUS      current
--  Date        "200512132113Z"  - Tue Dec 13 21:13 UTC 2005
    DESCRIPTION
        "B-Series Policy License."
    ::= { etsysLicKeyIdBSeries 1 }

etsysLicKeyIdBRouting OBJECT-IDENTITY
    STATUS      current
--  Date        "200608151956Z"  - Tue Aug 15 19:56 UTC 2006
    DESCRIPTION
        "B-Series Routing License."
    ::= { etsysLicKeyIdBSeries 2 }

END
