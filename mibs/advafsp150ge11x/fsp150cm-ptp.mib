F3-PTP-MIB DEFINITIONS ::= BEGIN

IMPORTS
    MODULE-COMPLIANCE, OBJECT-GROUP, NOTIFICATION-GROUP
             FROM SNMPv2-CONF
    MODULE-IDENTITY, OBJECT-TYPE, NOTIFICATION-TYPE,
    IpAddress, Integer32, Unsigned32, Counter64
             FROM SNMPv2-SMI
    DisplayString, TruthValue, RowStatus, StorageType, VariablePointer,
    MacAddress, DateAndTime, TEXTUAL-CONVENTION
             FROM SNMPv2-TC
    neIndex, shelfIndex, slotIndex
             FROM  CM-ENTITY-MIB
    cmEthernetAccPortIndex, cmEthernetNetPortIndex,
    cmEthernetAccPortEntry, cmEthernetNetPortEntry
             FROM  CM-FACILITY-MIB
    IpVersion, CmPmIntervalType, CmPmBinAction
             FROM  CM-COMMON-MIB
    fsp150cm
             FROM  ADVA-MIB
    AdminState, OperationalState, SecondaryState, 
          PerfCounter64, IpPriorityMapMode
             FROM  CM-COMMON-MIB
    SSMQualityLevel, HoldoverAccuracy, TimeSource
             FROM F3-SYNC-MIB;

f3PtpMIB MODULE-IDENTITY
    LAST-UPDATED    "201309240000Z"
    ORGANIZATION    "ADVA Optical Networking"
    CONTACT-INFO
            "        Raghav Trivedi
                     ADVA Optical Networking, Inc.
                Tel: +1 972 759-1239
             E-mail: rtrivedi@advaoptical.com
             Postal: 2301 N. Greenville Ave. #300
                     Richardson, TX USA 75082"
    DESCRIPTION
            "This module defines the 1588 PTP MIB definitions used by 
             the F3 (FSP150CM/CC) product lines.  
             Copyright (C) ADVA Optical Networking."
    REVISION        "201206130000Z"
    DESCRIPTION
         "
          Notes from release 201309240000Z,
           (1) Added the following object
                f3PtpDynamicRemoteSlaveRowStatus
                    
          Notes from release 201304240000Z,
           (1) New tables: f3PtpMasterClockTable
                    
          Notes from release 201301170000Z,
           (1) New tables: f3PtpBCTable, f3PtpMCITable, f3PtpMasterVirtualPortTable,
                           f3PtpRemoteSlaveTable,
                           f3PtpMCIStatsTable, f3PtpMCIHistoryTable, 
                           f3PtpMCIThresholdTable,
                           f3PtpRemoteSlaveStatsTable, f3PtpRemoteSlaveHistoryTable
                           f3PtpRemoteSlaveThresholdTable
           (2) New notifications: f3PtpMCICrossingAlert, f3PtpRemoteSlaveCrossingAlert  

          Notes from release 201207190000Z,
           (1) New tables: f3PtpEthernetAccPortExtTable, f3PtpEthernetNetPortExtTable  

          Notes from release 201206130000Z
            (i)Added the following objects
                f3PtpTSClockSyncEEnabled, f3PtpTSClockQLModeEnabled,
                f3PtpTSClockExpectedQL, f3PtpTSClockAssumedQL,
                f3PtpTSClockReceivedQL, 

          Notes from release 201205180000Z
            (i)INDEX objects are made not-accessible

          Notes from release 201105060000Z
            (i)f3PtpAccPortFlowPointService and f3PtpNetPortFlowPointService are
                    read-create instead of read-only
           (ii)Threshold Crossing Notifications are now defined
                f3PtpAccPortFlowPointThresholdCrossingAlert,
                f3PtpNetPortFlowPointThresholdCrossingAlert,
                f3PtpSOOCCrossingAlert 

          Notes from release 201104040000Z
          Initial version of the MIB, now with Performance Objects." 
    ::= {fsp150cm 18}    

-- 
-- OID definitions
-- 
f3PtpConfigObjects             OBJECT IDENTIFIER ::= {f3PtpMIB 1}
f3PtpPerformanceObjects        OBJECT IDENTIFIER ::= {f3PtpMIB 2}
f3PtpPerformanceNotifications  OBJECT IDENTIFIER ::= {f3PtpMIB 3}
f3PtpConformance               OBJECT IDENTIFIER ::= {f3PtpMIB 4}
f3PtpStatusChangeNotifications OBJECT IDENTIFIER ::= {f3PtpMIB 5}

-- 
-- Textual Conventions 
-- 
PtpFlowPointType ::= TEXTUAL-CONVENTION
    STATUS       current
    DESCRIPTION
        "Enumerations for PTP Flow Point Type.
             transparent - represents the 1588 Transparent clock type,
             oc-slave - represents a 1588 Ordinary Clock Slave clock type,
             monitoring - represents monitoring Flow Point,
             oc-master - represents a 1588 Ordinary Clock master clock type."
    SYNTAX       INTEGER {
                   transparent (1),
                   oc-slave (2),
                   monitoring(3),
                   oc-master(4),
                   eth-multicast(5)
                 }

PtpPortState ::= TEXTUAL-CONVENTION
    STATUS       current
    DESCRIPTION
          "Enumerations for PTP Port State."
    SYNTAX   INTEGER {
               initializing(1),
               faulty(2),
               disabled(3),
               listening(4),
               uncalibrated(5),
               slave(6),
               premaster(7),
               master(8),  
               passive(9) 
             }

MasterClockType ::= TEXTUAL-CONVENTION
    STATUS       current
    DESCRIPTION
          "Enumerations for Master CloCk Type."
    SYNTAX   INTEGER {
               unknown(1),
               one-step(2),
               two-step(3)
             }

DelayMechanism ::= TEXTUAL-CONVENTION
    STATUS       current
    DESCRIPTION
          "Enumerations for Delay Mechanism."
    SYNTAX   INTEGER {
               end-to-end(1)
             }

ClockIdentity ::= TEXTUAL-CONVENTION
    STATUS       current
    DESCRIPTION
          "1588 Clock Identity."
    SYNTAX       OCTET STRING (SIZE(8))

PortIdentity ::= TEXTUAL-CONVENTION
    STATUS       current
    DESCRIPTION
          "1588 Port Identity."
    SYNTAX       OCTET STRING (SIZE(10))


ClockRecoveryMode ::= TEXTUAL-CONVENTION
    STATUS       current
    DESCRIPTION
          "Enumerations for 1588 Clock Recovery Mode."
    SYNTAX   INTEGER {
               one-way(1),
               two-way(2)
             }

ClockRecoveryState ::= TEXTUAL-CONVENTION
    STATUS       current
    DESCRIPTION
          "Enumerations for 1588 Clock Recovery State."
    SYNTAX   INTEGER {
               start(1),
               normal(2),
               freerun(3),
               holdover(4),
               acquisition(5),
               transient(6),
	       none(7)
             }

AnnounceMsgRate ::= TEXTUAL-CONVENTION
    STATUS       current
    DESCRIPTION
          "Enumerations for 1588 Announce Message Rate."
    SYNTAX   INTEGER {
               not-applicable(0),
               pkt1per16secs(1),
               pkt1per8secs(2),
               pkt1per4secs(3),
               pkt1per2secs(4),
               pkt1per1sec(5),
               pkts2per1sec(6),
               pkts4per1sec(7),
               pkts8per1sec(8),
               none(9)
            }

SyncMsgRate ::= TEXTUAL-CONVENTION
    STATUS       current
    DESCRIPTION
          "Enumerations for 1588 Sync Message Rate."
    SYNTAX   INTEGER {
               not-applicable(0),
               pkt1persec(1),
               pkts2persec(2),
               pkts4persec(3),
               pkts8persec(4),
               pkts16persec(5),
               pkts32persec(6),
               pkts64persec(7),
               pkts128persec(8),
               none(9)
             }

DelayRespMsgRate ::= TEXTUAL-CONVENTION
    STATUS       current
    DESCRIPTION
          "Enumerations for 1588 Delay Response Message Rate."
    SYNTAX   INTEGER {
               not-applicable(0),
               pkt1persec(1),
               pkts2persec(2),
               pkts4persec(3),
               pkts8persec(4),
               pkts16persec(5),
               pkts32persec(6),
               pkts64persec(7),
               pkts128persec(8),
               none(9)
             }

DelayReqMsgRate ::= TEXTUAL-CONVENTION
    STATUS       current
    DESCRIPTION
          "Enumerations for 1588 Delay Request Message Rate."
    SYNTAX   INTEGER {
               not-applicable(0),
               pkt1persec(1),
               pkts2persec(2),
               pkts4persec(3),
               pkts8persec(4),
               pkts16persec(5),
               pkts32persec(6),
               pkts64persec(7),
               pkts128persec(8)
             }

FreqRecoveryTarget ::= TEXTUAL-CONVENTION
    STATUS       current
    DESCRIPTION
          "Enumerations for Frequency Recovery Target."
    SYNTAX   INTEGER {
               not-applicable(0),
               traffic-mask(1),
               sync-mask(2),
               traffic-sync-mask(3)
             }

ScaledNanoseconds ::= TEXTUAL-CONVENTION
    STATUS       current
    DESCRIPTION
          "Definition of scaled nanoseconds as specified by 1588v2.
           The most significant 48 bits represent nanoseconds and 
           the least signifcant 16-bits represent sub-nanoseconds.
           The currently supported granularity is nanoseconds and
           the least significant 16 bits will always be 0.
           The 48-bits representing nanoseconds supports the range
           of [-2^47..2^47-1].
           Negative values of nanonseconds are interpreted
           as two's complement."
    SYNTAX   Counter64

RemoteSlaveType ::= TEXTUAL-CONVENTION
    STATUS       current
    DESCRIPTION
          "Enumerations for Remote Slave Type."
    SYNTAX   INTEGER {
               dynamic(1),
               static(2)
             }

TimeScale ::= TEXTUAL-CONVENTION
    STATUS       current
    DESCRIPTION
          ""
    SYNTAX   INTEGER {
               ptp(1),
               arb(2)
             }

PhaseRecoveryState ::= TEXTUAL-CONVENTION
    STATUS       current
    DESCRIPTION
          "Enumerations for Phase Recovery State."
    SYNTAX   INTEGER {
               not-applicable(0),
               freerun(1),
               holdover(2),
               normal(3),
               start(4),
               acquisition(5),
               transient(6),
               none(7)
             }

PTPProtectionState ::= TEXTUAL-CONVENTION
    STATUS       current
    DESCRIPTION
          "Enumerations for PTP Protection State."
    SYNTAX   INTEGER {
               active(1),
               standby(2)
             }

CompensationMode ::= TEXTUAL-CONVENTION
    STATUS       current
    DESCRIPTION
          "Enumerations for Compensation Mode."
    SYNTAX   INTEGER {
               disabled(1),
               automatic(2),
               manual(3)
             }

CompensationStatus ::= TEXTUAL-CONVENTION
    STATUS       current
    DESCRIPTION
          "Enumerations for Compensation Status."
    SYNTAX   INTEGER {
               operational(1),
               failed(2),
               not-available(3),
               manual(4),
               initializing(5)
             }

PTPClockProfile ::= TEXTUAL-CONVENTION
    STATUS       current
    DESCRIPTION
          "Enumerations for PTP Clock Profile."
    SYNTAX   INTEGER {
               g8275-1(1)
             }

PTPClockType ::= TEXTUAL-CONVENTION
    STATUS       current
    DESCRIPTION
          "Enumerations for PTP Clock Type."
    SYNTAX   INTEGER {
               master-only(1),
               slave-only(2),
               dynamic(3)
             }

PTPClockOperMode ::= TEXTUAL-CONVENTION
    STATUS       current
    DESCRIPTION
          "Enumerations for PTP Clock Oper Mode."
    SYNTAX   INTEGER {
               t-gm(1),
               t-tsc(2),
               idle(3),
               t-bc(4)
             }

DestMacAddrType ::= TEXTUAL-CONVENTION
    STATUS       current
    DESCRIPTION
          "Enumerations for Dest Mac Addr Type."
    SYNTAX   INTEGER {
               forwardable(1),
               non-forwardable(2)
             }


AnnounceMessageRate ::= TEXTUAL-CONVENTION
    STATUS       current
    DESCRIPTION
          "Enumerations for g8275.1 Announce Message Rate."
    SYNTAX   INTEGER {
               not-applicable(0),
               pkt1per16secs(1),
               pkt1per8secs(2),
               pkt1per4secs(3),
               pkt1per2secs(4),
               pkt1per1sec(5),
               pkts2per1sec(6),
               pkts4per1sec(7),
               pkts8per1sec(8),
               none(9)        
            }

DelayReqMessageRate ::= TEXTUAL-CONVENTION
    STATUS       current
    DESCRIPTION
          "Enumerations for g8275.1 Delay Req Message Rate."
    SYNTAX   INTEGER {
               not-applicable(0),
               pkt1persec(1),
               pkts2persec(2),
               pkts4persec(3),
               pkts8persec(4),
               pkts16persec(5),
               pkts32persec(6),
               pkts64persec(7),
               pkts128persec(8),
               none(9)
            }

SyncMessageRate ::= TEXTUAL-CONVENTION
    STATUS       current
    DESCRIPTION
          "Enumerations for g8275.1 Sync Message Rate."
    SYNTAX   INTEGER {
               not-applicable(0),
               pkt1persec(1),
               pkts2persec(2),
               pkts4persec(3),
               pkts8persec(4),
               pkts16persec(5),
               pkts32persec(6),
               pkts64persec(7),
               pkts128persec(8),
               none(9)
            }

BMCARole ::= TEXTUAL-CONVENTION
    STATUS       current
    DESCRIPTION
          "Enumerations for g8275.1 BMCA Role."
    SYNTAX   INTEGER {
               m1(1),  
               m2(2),   
               m3(3),   
               s1(4),   
               p1(5),    
               p2(6),   
               na(7)   
            }


ClockClassProfile ::= TEXTUAL-CONVENTION
    STATUS       current
    DESCRIPTION
          "Enumerations for Master Clock Interface the Clock Class Profile."
    SYNTAX   INTEGER {
               g82651(1),  
               ieee-1588-2008(2)  
            }




--
-- CONFIGURATION 
--
-- Transparent Clock Table 
--
f3PtpTCTable OBJECT-TYPE
    SYNTAX     SEQUENCE OF F3PtpTCEntry 
    MAX-ACCESS not-accessible
    STATUS     current
    DESCRIPTION
       "A list of entries corresponding to the PTP Transparent Clock entities."
    ::= { f3PtpConfigObjects 1 }

f3PtpTCEntry OBJECT-TYPE
    SYNTAX     F3PtpTCEntry
    MAX-ACCESS not-accessible
    STATUS     current
    DESCRIPTION
          "An entry containing information applicable to a particular
           Transparent Clock Entity."
    INDEX { neIndex, f3PtpTCIndex}
    ::= { f3PtpTCTable 1 }


F3PtpTCEntry ::= SEQUENCE {
    f3PtpTCIndex              Integer32,

    f3PtpTCAlias              DisplayString,

    f3PtpTCAdminState         AdminState,
    f3PtpTCOperationalState   OperationalState,
    f3PtpTCSecondaryState     SecondaryState,

    f3PtpTCServiceFlow        VariablePointer,
    f3PtpTCDelayMechanism     DelayMechanism,
    f3PtpTCSync               VariablePointer,
    f3PtpTCClockIdentity      ClockIdentity,

    f3PtpTCStorageType        StorageType,
    f3PtpTCRowStatus          RowStatus
}

f3PtpTCIndex OBJECT-TYPE
    SYNTAX     Integer32
    MAX-ACCESS not-accessible 
    STATUS     current
    DESCRIPTION
         "Unique index value associated with the Transparent Clock Entity."
     ::= { f3PtpTCEntry 1 }

f3PtpTCAlias    OBJECT-TYPE
    SYNTAX      DisplayString (SIZE(0..256))
    MAX-ACCESS  read-create
    STATUS      current
    DESCRIPTION
         "This object allows SNMP management entities to provide an 
          alias to the Transparent Clock entity."
     ::= { f3PtpTCEntry 2 }

f3PtpTCAdminState OBJECT-TYPE
    SYNTAX      AdminState 
    MAX-ACCESS  read-write
    STATUS      current
    DESCRIPTION
          "This object represents the Administrative State of the Transparent Clock."
    ::= { f3PtpTCEntry 3 }

f3PtpTCOperationalState   OBJECT-TYPE
    SYNTAX      OperationalState 
    MAX-ACCESS  read-only
    STATUS      current
    DESCRIPTION
          "This object represents the Operational State of the Transparent Clock." 
    ::= { f3PtpTCEntry 4 }

f3PtpTCSecondaryState     OBJECT-TYPE
    SYNTAX      SecondaryState 
    MAX-ACCESS  read-only
    STATUS      current
    DESCRIPTION
           "This object represents the Secondary State of the Transparent Clock."
    ::= { f3PtpTCEntry 5 }

f3PtpTCServiceFlow OBJECT-TYPE
    SYNTAX      VariablePointer 
    MAX-ACCESS  read-create
    STATUS      current
    DESCRIPTION
            "This object represents the Service(Traffic) Flow associated
             with the Transparent Clock."
    ::= { f3PtpTCEntry 6 }

f3PtpTCDelayMechanism OBJECT-TYPE
    SYNTAX      DelayMechanism 
    MAX-ACCESS  read-create
    STATUS      current
    DESCRIPTION
            "This object  represents the Delay Mechanism of the Transparent 
             Clock."
    ::= { f3PtpTCEntry 7 }

f3PtpTCSync OBJECT-TYPE
    SYNTAX     VariablePointer 
    MAX-ACCESS read-create
    STATUS     current
    DESCRIPTION
         "This object provides the entry from the f3SyncTable, which is
          used as frequency clock for this Transparent Clock."
     ::= { f3PtpTCEntry 8 }

f3PtpTCClockIdentity OBJECT-TYPE
    SYNTAX     ClockIdentity 
    MAX-ACCESS read-create
    STATUS     current
    DESCRIPTION
         "This object specifies the Clock Identity of the PTP Transparent Clock." 
     ::= { f3PtpTCEntry 9 }

f3PtpTCStorageType OBJECT-TYPE
    SYNTAX     StorageType
    MAX-ACCESS read-create
    STATUS     current
    DESCRIPTION
            "The type of storage configured for this entry."
    ::= { f3PtpTCEntry 10 }

f3PtpTCRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTCRowStatus supported are
            createAndGo(4) and destroy(6).  All mandatory attributes
            must be specified in a single SNMP SET request with
            f3PtpTCRowStatus value as createAndGo(4).
            Upon successful row creation, this object has a
            value of active(1).

            The f3PtpTCRowStatus object may be modified if
            the associated instance of this object is equal to active(1)."
    ::= { f3PtpTCEntry 11 }


--
-- PTP Transparent Clock Virtual Port Table 
--
f3PtpTCVirtualPortTable OBJECT-TYPE
    SYNTAX     SEQUENCE OF F3PtpTCVirtualPortEntry 
    MAX-ACCESS not-accessible
    STATUS     current
    DESCRIPTION
         "A list of entries corresponding to the PTP Transparent 
          Clock Virtual Ports."
    ::= { f3PtpConfigObjects 2 }

f3PtpTCVirtualPortEntry OBJECT-TYPE
    SYNTAX     F3PtpTCVirtualPortEntry
    MAX-ACCESS not-accessible
    STATUS     current
    DESCRIPTION
          "An entry containing information applicable to a particular
           PTP TC Virtual Port Entity."
    INDEX { neIndex, f3PtpTCIndex,  f3PtpTCVirtualPortIndex }
    ::= { f3PtpTCVirtualPortTable 1 }

F3PtpTCVirtualPortEntry ::= SEQUENCE {
    f3PtpTCVirtualPortIndex              Integer32,

    f3PtpTCVirtualPortAlias              DisplayString,

    f3PtpTCVirtualPortAdminState         AdminState,
    f3PtpTCVirtualPortOperationalState   OperationalState,
    f3PtpTCVirtualPortSecondaryState     SecondaryState,

    f3PtpTCVirtualPortIdentity           PortIdentity,
    f3PtpTCVirtualPortFlowPoint          VariablePointer,
    f3PtpTCVirtualPortStorageType        StorageType,
    f3PtpTCVirtualPortRowStatus          RowStatus
}

f3PtpTCVirtualPortIndex OBJECT-TYPE
    SYNTAX     Integer32
    MAX-ACCESS not-accessible
    STATUS     current
    DESCRIPTION
         "Unique index value associated with the PTP Transparent Clock
          Virtual Port index."
     ::= { f3PtpTCVirtualPortEntry 1 }

f3PtpTCVirtualPortAlias    OBJECT-TYPE
    SYNTAX      DisplayString (SIZE(0..256))
    MAX-ACCESS  read-create
    STATUS      current
    DESCRIPTION
         "This object allows SNMP management entities to provide an 
          alias to the PTP TC Virtual Port entity."
     ::= { f3PtpTCVirtualPortEntry 2 }

f3PtpTCVirtualPortAdminState OBJECT-TYPE
    SYNTAX      AdminState 
    MAX-ACCESS  read-write
    STATUS      current
    DESCRIPTION
            "This object represents the Administrative State of the TC Virtual 
             Port."
    ::= { f3PtpTCVirtualPortEntry 3 }

f3PtpTCVirtualPortOperationalState   OBJECT-TYPE
    SYNTAX      OperationalState 
    MAX-ACCESS  read-only
    STATUS      current
    DESCRIPTION
            "This object represents the Operational State of the TC Virtual 
             Port."
    ::= { f3PtpTCVirtualPortEntry 4 }

f3PtpTCVirtualPortSecondaryState     OBJECT-TYPE
    SYNTAX      SecondaryState 
    MAX-ACCESS  read-only
    STATUS      current
    DESCRIPTION
           "This object represents the Secondary State of the TC Virtual Port." 
    ::= { f3PtpTCVirtualPortEntry 5 }

f3PtpTCVirtualPortIdentity OBJECT-TYPE
    SYNTAX     PortIdentity 
    MAX-ACCESS read-write
    STATUS     current
    DESCRIPTION
         "This object represents the PTP Port Identity of the TC Virtual Port." 
     ::= { f3PtpTCVirtualPortEntry 6 }

f3PtpTCVirtualPortFlowPoint OBJECT-TYPE
    SYNTAX     VariablePointer 
    MAX-ACCESS read-create
    STATUS     current
    DESCRIPTION
         "This object associates the PTP Flow Point with the 
          Transparent Clock."
     ::= { f3PtpTCVirtualPortEntry 7 }

f3PtpTCVirtualPortStorageType OBJECT-TYPE
    SYNTAX     StorageType
    MAX-ACCESS read-create
    STATUS     current
    DESCRIPTION
            "The type of storage configured for this entry."
    ::= { f3PtpTCVirtualPortEntry 8 }

f3PtpTCVirtualPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTCVirtualPortRowStatus supported are
            createAndGo(4) and destroy(6).  All mandatory attributes
            must be specified in a single SNMP SET request with
            f3PtpTCVirtualPortRowStatus value as createAndGo(4).
            Upon successful row creation, this object has a
            value of active(1).

            The f3PtpTCVirtualPortRowStatus object may be modified if
            the associated instance of this object is equal to active(1)."
    ::= { f3PtpTCVirtualPortEntry 9 }


--
-- Telecom Slave Table 
--
f3PtpTSTable OBJECT-TYPE
    SYNTAX     SEQUENCE OF F3PtpTSEntry 
    MAX-ACCESS not-accessible
    STATUS     current
    DESCRIPTION
       "A list of entries corresponding to the PTP Telecom Slave entities."
    ::= { f3PtpConfigObjects 3 }

f3PtpTSEntry OBJECT-TYPE
    SYNTAX     F3PtpTSEntry
    MAX-ACCESS not-accessible
    STATUS     current
    DESCRIPTION
          "An entry containing information applicable to a particular
           Telecom Slave Entity."
    INDEX { neIndex, f3PtpTSIndex}
    ::= { f3PtpTSTable 1 }


F3PtpTSEntry ::= SEQUENCE {
    f3PtpTSIndex                             Integer32,

    f3PtpTSAlias                             DisplayString,

    f3PtpTSAdminState                        AdminState,
    f3PtpTSOperationalState                  OperationalState,
    f3PtpTSSecondaryState                    SecondaryState,

    f3PtpTSClockIdentity                     ClockIdentity,
    f3PtpTSDomainNumber                      Integer32,
    f3PtpTSSync                              VariablePointer,
    f3PtpTSCurrentTOD                        DateAndTime,
    f3PtpTSSelectedPacketClock               VariablePointer,

    f3PtpTSClockRecoveryMode                 ClockRecoveryMode,
    f3PtpTSClockRecoveryState                ClockRecoveryState,

    f3PtpTSClockSyncEEnabled                 TruthValue,
    f3PtpTSClockQLModeEnabled                TruthValue,
    f3PtpTSClockExpectedQL                   SSMQualityLevel,
    f3PtpTSClockAssumedQL                    SSMQualityLevel,
    f3PtpTSClockReceivedQL                   SSMQualityLevel,

    f3PtpTSStorageType                       StorageType,
    f3PtpTSRowStatus                         RowStatus,

    f3PtpTSTimeTraceabilityStatus            TruthValue,
    f3PtpTSTimeSinceTimeTraceabilityChanged  Unsigned32,
    f3PtpTSFreqTraceabilityStatus            TruthValue,
    f3PtpTSTimeSinceFreqTraceabilityChanged  Unsigned32,
    f3PtpTSFreqRecoveryTarget                FreqRecoveryTarget,
    f3PtpTSCurrentCRScore                    Unsigned32,
    f3PtpTSTimeLastCRScore                   DateAndTime,
    f3PtpTSTargetPhaseRecoveryAccuracy       Unsigned32,
    f3PtpTSCurrentPRScore                    Unsigned32,
    f3PtpTSTimeLastPRScore                   DateAndTime,
    f3PtpTSClockClass                        Unsigned32,
    f3PtpTSClockAccuracy                     Unsigned32,
    f3PtpTSTimeSource                        TimeSource,
    f3PtpTSPhaseRecoveryState                PhaseRecoveryState, 
    f3PtpTSTimeHoldoverAccuracy              HoldoverAccuracy,
    f3PtpTSWtrTime                           Integer32
}

f3PtpTSIndex OBJECT-TYPE
    SYNTAX     Integer32
    MAX-ACCESS not-accessible 
    STATUS     current
    DESCRIPTION
         "Unique index value associated with the Telecom Slave Entity."
     ::= { f3PtpTSEntry 1 }

f3PtpTSAlias    OBJECT-TYPE
    SYNTAX      DisplayString (SIZE(0..256))
    MAX-ACCESS  read-create
    STATUS      current
    DESCRIPTION
         "This object allows SNMP management entities to provide an 
          alias to the Telecom Slave entity."
     ::= { f3PtpTSEntry 2 }

f3PtpTSAdminState OBJECT-TYPE
    SYNTAX      AdminState 
    MAX-ACCESS  read-write
    STATUS      current
    DESCRIPTION
          "This object represents the Administrative State of the Telecom Slave."
    ::= { f3PtpTSEntry 3 }

f3PtpTSOperationalState   OBJECT-TYPE
    SYNTAX      OperationalState 
    MAX-ACCESS  read-only
    STATUS      current
    DESCRIPTION
          "This object represents the Operational State of the Telecom Slave." 
    ::= { f3PtpTSEntry 4 }

f3PtpTSSecondaryState     OBJECT-TYPE
    SYNTAX      SecondaryState 
    MAX-ACCESS  read-only
    STATUS      current
    DESCRIPTION
           "This object represents the Secondary State of the Telecom Slave."
    ::= { f3PtpTSEntry 5 }

f3PtpTSClockIdentity OBJECT-TYPE
    SYNTAX     ClockIdentity 
    MAX-ACCESS read-create
    STATUS     current
    DESCRIPTION
         "This object specifies the Clock Identity of the PTP Telecom Slave." 
     ::= { f3PtpTSEntry 6 }

f3PtpTSDomainNumber OBJECT-TYPE
    SYNTAX     Integer32 
    MAX-ACCESS read-write
    STATUS     current
    DESCRIPTION
         "This object allows specification of the PTP domain number of the
          Telecom Slave." 
     ::= { f3PtpTSEntry 7 }

f3PtpTSSync OBJECT-TYPE
    SYNTAX     VariablePointer 
    MAX-ACCESS read-create
    STATUS     current
    DESCRIPTION
         "This object provides the entry from the f3SyncTable, which is
          used as frequency for this Telecom Slave."
     ::= { f3PtpTSEntry 8 }

f3PtpTSCurrentTOD OBJECT-TYPE
    SYNTAX     DateAndTime 
    MAX-ACCESS read-only
    STATUS     current
    DESCRIPTION
         "This object allows specification of the Telecom Slave Current
          Time of Day." 
     ::= { f3PtpTSEntry 9 }

f3PtpTSSelectedPacketClock OBJECT-TYPE
    SYNTAX     VariablePointer 
    MAX-ACCESS read-only
    STATUS     current
    DESCRIPTION
         "This object provides the Slave Only Ordinary Clock selected
          as the best source of Time Of Day."
     ::= { f3PtpTSEntry 10 }

f3PtpTSClockRecoveryMode    OBJECT-TYPE 
    SYNTAX     ClockRecoveryMode 
    MAX-ACCESS read-create
    STATUS     current
    DESCRIPTION
         "This object allows specification of whether the Clock Recovery Mode
          is one-way or two-way.  In one-way mode, only Sync messages are
          used for frequency recovery.  In two-way mode, both Sync and 
          Delay Request-Response messages are used for measuring the mean path delay." 
     ::= { f3PtpTSEntry 11 }

f3PtpTSClockRecoveryState    OBJECT-TYPE 
    SYNTAX     ClockRecoveryState 
    MAX-ACCESS read-only
    STATUS     current
    DESCRIPTION
         "This object provides the Telecom Slave's clock recovery state." 
     ::= { f3PtpTSEntry 12 }

--Synchronous Port params
f3PtpTSClockSyncEEnabled OBJECT-TYPE 
    SYNTAX     TruthValue
    MAX-ACCESS read-write
    STATUS     current
    DESCRIPTION
         "This object allows to specify whether the Telecom Slave 
          can be enabled/disabled for Synchronous Ethernet. 
          When enabled, on receive side 
            -telecom slave can extract the frequency 
             and pass the recovered clock to the system clock
            -QL is extracted (when QL is enabled) from the selected SOOC's clock class
            -telecom slave is eligible to be selected as a system clock reference
          When disabled, on receive side,
            -telecom slave does not pass the recovered clock to the system clock 
            -telecom slave does not process the QL from selected SOOC's clock class 
            -telecom slave is not eligible to be selected as a 
                     system clock reference."
     ::= { f3PtpTSEntry 13 }

f3PtpTSClockQLModeEnabled OBJECT-TYPE 
    SYNTAX     TruthValue
    MAX-ACCESS read-write
    STATUS     current
    DESCRIPTION
         "This object allows to specify whether the Telecom Slave 
          can be enabled/disabled for QL Mode.  
          When enabled, on receive side 
            -telecom slave can extract the QL from selected SOOC's clock class 
          When disabled, on receive side,
            -telecom slave does not process the QL from selected SOOC's clock class."
     ::= { f3PtpTSEntry 14 }

f3PtpTSClockExpectedQL OBJECT-TYPE 
    SYNTAX     SSMQualityLevel
    MAX-ACCESS read-write
    STATUS     current
    DESCRIPTION
         "This object allows to specify the expected QL when the 
          Telecom Slave is enabled for QL Mode.  This is applicable 
          when f3PtpTSClockQLModeEnabled is set to true.
          This object allows the user to set a minimum
          expected received Quality Level on the Telecom Slave. 
          The valid values depend upon the SYNC entity's Network Clock Type. 
          A value of None represents that a minimum Quality Level is not expected. 
          The default value shall be None."
     ::= { f3PtpTSEntry 15 }

f3PtpTSClockAssumedQL OBJECT-TYPE 
    SYNTAX     SSMQualityLevel
    MAX-ACCESS read-write
    STATUS     current
    DESCRIPTION
         "This object allows to specify the assumed QL on the 
          Telecom Slave.  The Assumed QL is only meaningful if the Network Clock Type
          (see fsp150cm-sync.mib) is option1 and the 
          telecom slave's QL Mode is disabled and the telecom slave is being used as 
          an input reference source. Under these conditions,
          the specified QL value is assumed to be the Quality Level of the
          non-failed reference."
     ::= { f3PtpTSEntry 16 }

f3PtpTSClockReceivedQL OBJECT-TYPE 
    SYNTAX     SSMQualityLevel
    MAX-ACCESS read-only
    STATUS     current
    DESCRIPTION
         "This object provides the Received QL value for the Telecom Slave. 
          If the Telecom Slave's QL Mode is disabled, then the received 
          QL value is not applicable."
     ::= { f3PtpTSEntry 17 }

f3PtpTSStorageType OBJECT-TYPE
    SYNTAX     StorageType
    MAX-ACCESS read-create
    STATUS     current
    DESCRIPTION
            "The type of storage configured for this entry."
    ::= { f3PtpTSEntry 18 }

f3PtpTSRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTSRowStatus supported are
            createAndGo(4) and destroy(6).  All mandatory attributes
            must be specified in a single SNMP SET request with
            f3PtpTSRowStatus value as createAndGo(4).
            Upon successful row creation, this object has a
            value of active(1).

            The f3PtpTSRowStatus object may be modified if
            the associated instance of this object is equal to active(1)."
    ::= { f3PtpTSEntry 19 }

f3PtpTSTimeTraceabilityStatus OBJECT-TYPE
    SYNTAX      TruthValue
    MAX-ACCESS  read-only
    STATUS      current
    DESCRIPTION
           "This object provides the Time traceability status of the
            Telecom Slave."
    ::= { f3PtpTSEntry 20 }

f3PtpTSTimeSinceTimeTraceabilityChanged OBJECT-TYPE
    SYNTAX      Unsigned32
    MAX-ACCESS  read-only
    STATUS      current
    DESCRIPTION
           "This object provides the time in seconds since the Time traceability 
            changed on the Telecom Slave."
    ::= { f3PtpTSEntry 21 }

f3PtpTSFreqTraceabilityStatus OBJECT-TYPE
    SYNTAX      TruthValue
    MAX-ACCESS  read-only
    STATUS      current
    DESCRIPTION
           "This object provides the Frequency traceability status of the
            Telecom Slave."
    ::= { f3PtpTSEntry 22 }

f3PtpTSTimeSinceFreqTraceabilityChanged OBJECT-TYPE
    SYNTAX      Unsigned32
    MAX-ACCESS  read-only
    STATUS      current
    DESCRIPTION
           "This object provides the time in seconds since the Frequency traceability 
            changed on the Telecom Slave."
    ::= { f3PtpTSEntry 23 }

f3PtpTSFreqRecoveryTarget OBJECT-TYPE
    SYNTAX      FreqRecoveryTarget
    MAX-ACCESS  read-write
    STATUS      current
    DESCRIPTION
           "This object provides the frequency recovery target." 
    ::= { f3PtpTSEntry 24 }

f3PtpTSCurrentCRScore OBJECT-TYPE
    SYNTAX      Unsigned32
    MAX-ACCESS  read-only
    STATUS      current
    DESCRIPTION
           "This object provides the current Clock Recovery Score."
    ::= { f3PtpTSEntry 25 }

f3PtpTSTimeLastCRScore OBJECT-TYPE
    SYNTAX      DateAndTime
    MAX-ACCESS  read-only
    STATUS      current
    DESCRIPTION
           "This object provides the time of the last Clock Recovery Score."
    ::= { f3PtpTSEntry 26 }

f3PtpTSTargetPhaseRecoveryAccuracy OBJECT-TYPE
    SYNTAX      Unsigned32
    MAX-ACCESS  read-write
    STATUS      current
    DESCRIPTION
           "This object allows specification of the expected Time of Day accuracy
            in nanoseconds."
    ::= { f3PtpTSEntry 27 }

f3PtpTSCurrentPRScore OBJECT-TYPE
    SYNTAX      Unsigned32
    MAX-ACCESS  read-only
    STATUS      current
    DESCRIPTION
           "This object provides the current Phase Recovery Score."
    ::= { f3PtpTSEntry 28 }

f3PtpTSTimeLastPRScore OBJECT-TYPE
    SYNTAX      DateAndTime
    MAX-ACCESS  read-only
    STATUS      current
    DESCRIPTION
           "This object provides the time of the last Phase Recovery Score."
    ::= { f3PtpTSEntry 29 }

f3PtpTSClockClass OBJECT-TYPE
    SYNTAX      Unsigned32
    MAX-ACCESS  read-only
    STATUS      current
    DESCRIPTION
           "This object specify Telecome Slave clock class."
    ::= { f3PtpTSEntry 30 }

f3PtpTSClockAccuracy OBJECT-TYPE
    SYNTAX      Unsigned32
    MAX-ACCESS  read-only
    STATUS      current
    DESCRIPTION
           "This object specify Telecome Slave clock accuracy."
    ::= { f3PtpTSEntry 31 }

f3PtpTSTimeSource OBJECT-TYPE
    SYNTAX      TimeSource
    MAX-ACCESS  read-only
    STATUS      current
    DESCRIPTION
           "This object specify Telecome Slave time source."
    ::= { f3PtpTSEntry 32 }

f3PtpTSPhaseRecoveryState OBJECT-TYPE
    SYNTAX      PhaseRecoveryState
    MAX-ACCESS  read-only
    STATUS      current
    DESCRIPTION
           "This object specify the phase recovery state."
    ::= { f3PtpTSEntry 33 }

f3PtpTSTimeHoldoverAccuracy OBJECT-TYPE
    SYNTAX      HoldoverAccuracy
    MAX-ACCESS  read-write
    STATUS      current
    DESCRIPTION
           "This object specify the time hold over accuracy."
    ::= { f3PtpTSEntry 34 }

f3PtpTSWtrTime OBJECT-TYPE
    SYNTAX     Integer32 (0..12)
    MAX-ACCESS  read-write
    STATUS      current
    DESCRIPTION
           "This object should allow configuration of Wait To Restore timeout in minutes.
           The range of this object should be 0-12."
    ::= { f3PtpTSEntry 35 }

--
-- PTP Slave Only Ordinary Clock Table 
--
f3PtpSOOCTable OBJECT-TYPE
    SYNTAX     SEQUENCE OF F3PtpSOOCEntry 
    MAX-ACCESS not-accessible
    STATUS     current
    DESCRIPTION
         "A list of entries corresponding to the Slave Only Ordinary Clocks."
    ::= { f3PtpConfigObjects 4 }

f3PtpSOOCEntry OBJECT-TYPE
    SYNTAX     F3PtpSOOCEntry 
    MAX-ACCESS not-accessible
    STATUS     current
    DESCRIPTION
          "An entry containing information applicable to a particular
           Slave Only Ordinary Clock Entity."
    INDEX { neIndex, f3PtpTSIndex,  f3PtpSOOCIndex }
    ::= { f3PtpSOOCTable 1 }

F3PtpSOOCEntry ::= SEQUENCE {
    f3PtpSOOCIndex                               Integer32,

    f3PtpSOOCName                                DisplayString,
    f3PtpSOOCAlias                               DisplayString,

    f3PtpSOOCAdminState                          AdminState,
    f3PtpSOOCOperationalState                    OperationalState,
    f3PtpSOOCSecondaryState                      SecondaryState,

    f3PtpSOOCServiceFlow                         VariablePointer,
    f3PtpSOOCMasterClockType                     MasterClockType,
    f3PtpSOOCUnicastMessageNegEnabled            TruthValue,
    f3PtpSOOCMasterDelayMechanism                DelayMechanism,
    f3PtpSOOCMasterPriority                      Integer32,

    f3PtpSOOCMasterIpProtocol                    IpVersion,
    f3PtpSOOCSlaveIpV4Address                    IpAddress,
    f3PtpSOOCSlaveIpV4SubnetMask                 IpAddress,
    f3PtpSOOCMasterIpV4Address                   IpAddress,
    f3PtpSOOCIpPriorityMapMode                   IpPriorityMapMode,
    f3PtpSOOCIpPriority                          Integer32,

    f3PtpSOOCMasterLeaseDuration                 Integer32,

    f3PtpSOOCMasterAnnounceMsgRate               AnnounceMsgRate,
    f3PtpSOOCMasterAnnounceMsgReceiptTimeout     Integer32,

    f3PtpSOOCMasterSyncMsgRate                   SyncMsgRate,
    f3PtpSOOCMasterSyncReceiptTimeout            Integer32,

    f3PtpSOOCMasterDelayRspMsgRate               DelayRespMsgRate,
    f3PtpSOOCMasterDelayRspReceiptTimeout        Integer32,

    f3PtpSOOCMasterRequestUnicastTimeout         Integer32,
    f3PtpSOOCMasterRequestUnicastRestartTimer    Integer32,

    f3PtpSOOCCurrentOffsetFromMaster             ScaledNanoseconds,
    f3PtpSOOCAnnounceMsgClockClass               Integer32,
    f3PtpSOOCLastReceivedAnnounceMsg             OCTET STRING,
    f3PtpSOOCLastReceivedSyncMsg                 OCTET STRING,
    f3PtpSOOCLastReceivedDelayRspMsg             OCTET STRING,

    f3PtpSOOCRecentMeanPathDelay                 ScaledNanoseconds,
    f3PtpSOOCRecentSyncPDV                       ScaledNanoseconds,

    f3PtpSOOCStorageType                         StorageType,
    f3PtpSOOCRowStatus                           RowStatus,

    f3PtpSOOCRecentSyncPathDelay                 ScaledNanoseconds,

    f3PtpSOOCSoocProtectionState                 PTPProtectionState,
    f3PtpSOOCSoocWtr                             TruthValue,
    f3PtpSOOCSoocClockClass                      Unsigned32,
    f3PtpSOOCSoocClockRecoveryState              ClockRecoveryState,
    f3PtpSOOCSoocPhaseRecoveryState              PhaseRecoveryState,
    f3PtpSOOCE2eDelayAsymmetryComp               CompensationMode,
    f3PtpSOOCE2eAutoAsymmetryCompStatus          CompensationStatus,
    f3PtpSOOCE2eDelayAsymmetry                   Integer32,
    f3PtpSOOCSoocLockOutControl                  TruthValue

}

f3PtpSOOCIndex OBJECT-TYPE
    SYNTAX     Integer32
    MAX-ACCESS not-accessible 
    STATUS     current
    DESCRIPTION
         "Unique index value associated with the Slave Only Ordinary Clock."
     ::= { f3PtpSOOCEntry 1 }

f3PtpSOOCName    OBJECT-TYPE
    SYNTAX       DisplayString (SIZE(1..15))
    MAX-ACCESS   read-create
    STATUS       current
    DESCRIPTION
         "This object allows SNMP management entities to provide a
          name to the Slave Only Ordinary Clock.  This is used
          for creation of the underlying IP Interface associated 
          with the SOOC."
     ::= { f3PtpSOOCEntry 2 }

f3PtpSOOCAlias    OBJECT-TYPE
    SYNTAX      DisplayString (SIZE(0..256))
    MAX-ACCESS  read-create
    STATUS      current
    DESCRIPTION
         "This object allows SNMP management entities to provide an 
          alias to the Slave Only Ordinary Clock."
     ::= { f3PtpSOOCEntry 3 }

f3PtpSOOCAdminState OBJECT-TYPE
    SYNTAX      AdminState 
    MAX-ACCESS  read-write
    STATUS      current
    DESCRIPTION
            "This object represents the Administrative State of the Slave Only 
             Ordinary Clock."
     ::= { f3PtpSOOCEntry 4 }

f3PtpSOOCOperationalState   OBJECT-TYPE
    SYNTAX      OperationalState 
    MAX-ACCESS  read-only
    STATUS      current
    DESCRIPTION
            "This object represents the Operational State of the Slave Only 
             Ordinary Clock."
     ::= { f3PtpSOOCEntry 5 }

f3PtpSOOCSecondaryState     OBJECT-TYPE
    SYNTAX      SecondaryState 
    MAX-ACCESS  read-only
    STATUS      current
    DESCRIPTION
           "This object represents the Secondary State of the Slave Only
            Ordinary Clock."
     ::= { f3PtpSOOCEntry 6 }

f3PtpSOOCServiceFlow OBJECT-TYPE
    SYNTAX     VariablePointer
    MAX-ACCESS read-create 
    STATUS     current
    DESCRIPTION
         "Traffic Flow or SHG associated with the Slave Only Ordinary Clock."
     ::= { f3PtpSOOCEntry 7 }

f3PtpSOOCMasterClockType OBJECT-TYPE
    SYNTAX     MasterClockType
    MAX-ACCESS read-only 
    STATUS     current
    DESCRIPTION
         "This object must be used to specify the type of the Master Clock."
     ::= { f3PtpSOOCEntry 8 }

f3PtpSOOCUnicastMessageNegEnabled OBJECT-TYPE
    SYNTAX     TruthValue
    MAX-ACCESS read-create 
    STATUS     current
    DESCRIPTION
         "This object must be used to specify whether Unicast Message
          Negotiation is enabled for the Master Clock."
     ::= { f3PtpSOOCEntry 9 }

f3PtpSOOCMasterDelayMechanism OBJECT-TYPE
    SYNTAX     DelayMechanism
    MAX-ACCESS read-write 
    STATUS     current
    DESCRIPTION
         "This object allows specification of the delay mechanism." 
     ::= { f3PtpSOOCEntry 10 }

f3PtpSOOCMasterPriority OBJECT-TYPE
    SYNTAX     Integer32
    MAX-ACCESS read-create 
    STATUS     current
    DESCRIPTION
         "This object allows specification of the OC Master Priority."
     ::= { f3PtpSOOCEntry 11 }

f3PtpSOOCMasterIpProtocol OBJECT-TYPE
    SYNTAX     IpVersion
    MAX-ACCESS read-create 
    STATUS     current
    DESCRIPTION
         "This object allows specification of the IP Protocol to
          communicate with the OC Master.  Only ipv4 is supported."
     ::= { f3PtpSOOCEntry 12 }

f3PtpSOOCSlaveIpV4Address OBJECT-TYPE
    SYNTAX     IpAddress
    MAX-ACCESS read-create 
    STATUS     current
    DESCRIPTION
         "This object allows specification of the IPv4 Address of
          the Slave Only Ordinary Clock."
     ::= { f3PtpSOOCEntry 13 }

f3PtpSOOCSlaveIpV4SubnetMask OBJECT-TYPE
    SYNTAX     IpAddress
    MAX-ACCESS read-create 
    STATUS     current
    DESCRIPTION
         "This object allows specification of the IPv4 Subnet Mask of
          the Slave Only Ordinary Clock."
     ::= { f3PtpSOOCEntry 14 }

f3PtpSOOCMasterIpV4Address OBJECT-TYPE
    SYNTAX     IpAddress
    MAX-ACCESS read-create 
    STATUS     current
    DESCRIPTION
         "This object allows specification of the IPv4 Address of
          the OC Master."
     ::= { f3PtpSOOCEntry 15 }

f3PtpSOOCIpPriorityMapMode  OBJECT-TYPE
    SYNTAX     IpPriorityMapMode 
    MAX-ACCESS read-write
    STATUS     current
    DESCRIPTION
         "This object enables specification of Priority Mapping Mode for
          the Slave Only Ordinary Clock."
     ::= { f3PtpSOOCEntry 16 }

f3PtpSOOCIpPriority  OBJECT-TYPE
    SYNTAX     Integer32 (0..63)
    MAX-ACCESS read-write
    STATUS     current
    DESCRIPTION
         "This object enables specification of Priority Value for
          f3PtpSOOCIpPriorityMapMode as priomap-tos,priomap-dscp."
     ::= { f3PtpSOOCEntry 17 }

f3PtpSOOCMasterLeaseDuration OBJECT-TYPE
    SYNTAX     Integer32
    MAX-ACCESS read-create
    STATUS     current
    DESCRIPTION
        "This object allows specification of the lease Duration for Announce and Sync
         messages." 
     ::= { f3PtpSOOCEntry 18 }

f3PtpSOOCMasterAnnounceMsgRate OBJECT-TYPE
    SYNTAX     AnnounceMsgRate
    MAX-ACCESS read-create
    STATUS     current
    DESCRIPTION
         "This object allows specification of the PTP Announce Message Rate."
     ::= { f3PtpSOOCEntry 19 }

f3PtpSOOCMasterAnnounceMsgReceiptTimeout OBJECT-TYPE
    SYNTAX     Integer32
    MAX-ACCESS read-create
    STATUS     current
    DESCRIPTION
        "This object allows specification of the PTP Announce Message 
         Receipt Timeout."
     ::= { f3PtpSOOCEntry 20 }

f3PtpSOOCMasterSyncMsgRate OBJECT-TYPE
    SYNTAX     SyncMsgRate
    MAX-ACCESS read-create
    STATUS     current
    DESCRIPTION
        "This object allows specification of the PTP Sync 
         Message Rate." 
     ::= { f3PtpSOOCEntry 21 }

f3PtpSOOCMasterSyncReceiptTimeout OBJECT-TYPE
    SYNTAX     Integer32
    MAX-ACCESS read-create
    STATUS     current
    DESCRIPTION
        "This object allows specification of the PTP Sync Message 
         Receipt Timeout."
     ::= { f3PtpSOOCEntry 22 }

f3PtpSOOCMasterDelayRspMsgRate OBJECT-TYPE
    SYNTAX     DelayRespMsgRate
    MAX-ACCESS read-create
    STATUS     current
    DESCRIPTION
        "This object allows specification of the PTP Delay Response 
         Message Rate." 
     ::= { f3PtpSOOCEntry 23 }

f3PtpSOOCMasterDelayRspReceiptTimeout OBJECT-TYPE
    SYNTAX     Integer32
    MAX-ACCESS read-create
    STATUS     current
    DESCRIPTION
        "This object allows specification of the PTP Delay Response 
         Message Receipt Timeout."
     ::= { f3PtpSOOCEntry 24 }

f3PtpSOOCMasterRequestUnicastTimeout  OBJECT-TYPE 
    SYNTAX     Integer32
    MAX-ACCESS read-write
    STATUS     current
    DESCRIPTION
        "This object allows specification of the Request Unicast 
         Timeout in seconds.  Unicast transmission is termed as
         failed when this timeout occurs."
     ::= { f3PtpSOOCEntry 25 }

f3PtpSOOCMasterRequestUnicastRestartTimer  OBJECT-TYPE 
    SYNTAX     Integer32
    MAX-ACCESS read-write
    STATUS     current
    DESCRIPTION
        "This object allows specification of the time (in seconds) to wait
         to restart the Request Unicast signalling." 
     ::= { f3PtpSOOCEntry 26 }

f3PtpSOOCCurrentOffsetFromMaster OBJECT-TYPE
    SYNTAX     ScaledNanoseconds 
    MAX-ACCESS read-only
    STATUS     current
    DESCRIPTION
        "This object provides the current Offset From Master.
         The value provided is in nanoseconds." 
     ::= { f3PtpSOOCEntry 27 }

f3PtpSOOCAnnounceMsgClockClass OBJECT-TYPE
    SYNTAX     Integer32
    MAX-ACCESS read-only
    STATUS     deprecated
    DESCRIPTION
        "This object provides the Clock Class obtained in the
         Announce Message." 
     ::= { f3PtpSOOCEntry 28 }

f3PtpSOOCLastReceivedAnnounceMsg OBJECT-TYPE
    SYNTAX     OCTET STRING (SIZE(0..128))
    MAX-ACCESS read-only
    STATUS     current
    DESCRIPTION
        "This object provides the Last Received  
         Announce Message." 
     ::= { f3PtpSOOCEntry 29 }

f3PtpSOOCLastReceivedSyncMsg OBJECT-TYPE
    SYNTAX     OCTET STRING (SIZE(0..128))
    MAX-ACCESS read-only
    STATUS     current
    DESCRIPTION
        "This object provides the Last Received  
         Sync Message." 
     ::= { f3PtpSOOCEntry 30 }

f3PtpSOOCLastReceivedDelayRspMsg OBJECT-TYPE
    SYNTAX     OCTET STRING (SIZE(0..128))
    MAX-ACCESS read-only
    STATUS     current
    DESCRIPTION
        "This object provides the Last Received  
         Delay Response Message." 
     ::= { f3PtpSOOCEntry 31 }

f3PtpSOOCRecentMeanPathDelay OBJECT-TYPE
    SYNTAX     ScaledNanoseconds  
    MAX-ACCESS read-only
    STATUS     current
    DESCRIPTION
        "This object provides the most recent 
         mean path delay." 
     ::= { f3PtpSOOCEntry 32 }

f3PtpSOOCRecentSyncPDV OBJECT-TYPE
    SYNTAX     ScaledNanoseconds 
    MAX-ACCESS read-only
    STATUS     current
    DESCRIPTION
        "This object provides the Sync messages 
         packet delay variation."
     ::= { f3PtpSOOCEntry 33 }

f3PtpSOOCStorageType OBJECT-TYPE
    SYNTAX     StorageType
    MAX-ACCESS read-create
    STATUS     current
    DESCRIPTION
            "The type of storage configured for this entry."
    ::= { f3PtpSOOCEntry 34 }

f3PtpSOOCRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpSOOCRowStatus supported are
            createAndGo(4) and destroy(6).  All mandatory attributes
            must be specified in a single SNMP SET request with
            f3PtpSOOCRowStatus value as createAndGo(4).
            Upon successful row creation, this object has a
            value of active(1).

            The f3PtpSOOCRowStatus object may be modified if
            the associated instance of this object is equal to active(1)."
    ::= { f3PtpSOOCEntry 35 }

f3PtpSOOCRecentSyncPathDelay OBJECT-TYPE
    SYNTAX     ScaledNanoseconds  
    MAX-ACCESS read-only
    STATUS     current
    DESCRIPTION
        "This object provides the Sync messages 
         packet delay."
     ::= { f3PtpSOOCEntry 36 }

f3PtpSOOCSoocProtectionState  OBJECT-TYPE 
    SYNTAX     PTPProtectionState
    MAX-ACCESS read-only
    STATUS     current
    DESCRIPTION
        "This object indicates whether the Sooc is used by 
        the Telecom Slave for the clock recovery."
     ::= { f3PtpSOOCEntry 37 }

f3PtpSOOCSoocWtr OBJECT-TYPE
    SYNTAX     TruthValue 
    MAX-ACCESS read-only
    STATUS     current
    DESCRIPTION
        "This object provides WTR protection state of the Sooc."
     ::= { f3PtpSOOCEntry 38 }

f3PtpSOOCSoocClockClass OBJECT-TYPE
    SYNTAX     Unsigned32
    MAX-ACCESS read-only
    STATUS     current
    DESCRIPTION
        "This object provides the Clock Class of the Sooc."
     ::= { f3PtpSOOCEntry 39 }

f3PtpSOOCSoocClockRecoveryState OBJECT-TYPE
    SYNTAX     ClockRecoveryState
    MAX-ACCESS read-only
    STATUS     current
    DESCRIPTION
        "This object provides the frequency recovery state
        of the Sooc."   
     ::= { f3PtpSOOCEntry 40 }

f3PtpSOOCSoocPhaseRecoveryState OBJECT-TYPE
    SYNTAX     PhaseRecoveryState
    MAX-ACCESS read-only
    STATUS     current
    DESCRIPTION
        "This object provides the Phase recovery state
        of the Sooc."   
     ::= { f3PtpSOOCEntry 41 }



f3PtpSOOCE2eDelayAsymmetryComp OBJECT-TYPE
    SYNTAX     CompensationMode
    MAX-ACCESS read-write
    STATUS     current
    DESCRIPTION
        "This object allows configuration of end to end asymmetry 
        delay compensation mode."   
     ::= { f3PtpSOOCEntry 42 }

f3PtpSOOCE2eAutoAsymmetryCompStatus OBJECT-TYPE
    SYNTAX     CompensationStatus  
    MAX-ACCESS read-only
    STATUS     current
    DESCRIPTION
        "This object provides the automatic end to end delay asymmetry 
        status." 
     ::= { f3PtpSOOCEntry 43 }

f3PtpSOOCE2eDelayAsymmetry OBJECT-TYPE
    SYNTAX     Integer32 
    MAX-ACCESS read-write
    STATUS     current
    DESCRIPTION
        "This object is used for manual configuration of end to end 
        delay asymmetry in ns if end to end delay asymmetry compensation is Manual.
        Or for indication of the measured delay asymmetry if
        end to end delay asymmetry compensation is automatic."
     ::= { f3PtpSOOCEntry 44 }

f3PtpSOOCSoocLockOutControl OBJECT-TYPE
    SYNTAX     TruthValue 
    MAX-ACCESS read-write
    STATUS     current
    DESCRIPTION
        "This object is used to specify whether Sooc
          Lockout operation is enabled for the Sooc."
     ::= { f3PtpSOOCEntry 45 }

--
-- PTP Ordinary Clock Slave Virtual Port Table 
--
f3PtpOCSlaveVirtualPortTable OBJECT-TYPE
    SYNTAX     SEQUENCE OF F3PtpOCSlaveVirtualPortEntry 
    MAX-ACCESS not-accessible
    STATUS     current
    DESCRIPTION
         "A list of entries corresponding to the PTP Transparent 
          Clock Virtual Ports."
    ::= { f3PtpConfigObjects 5 }

f3PtpOCSlaveVirtualPortEntry OBJECT-TYPE
    SYNTAX     F3PtpOCSlaveVirtualPortEntry
    MAX-ACCESS not-accessible
    STATUS     current
    DESCRIPTION
          "An entry containing information applicable to a particular
           PTP OCSlave Virtual Port Entity."
    INDEX { neIndex, f3PtpTSIndex,  
                     f3PtpSOOCIndex, f3PtpOCSlaveVirtualPortIndex }
    ::= { f3PtpOCSlaveVirtualPortTable 1 }

F3PtpOCSlaveVirtualPortEntry ::= SEQUENCE {
    f3PtpOCSlaveVirtualPortIndex              Integer32,

    f3PtpOCSlaveVirtualPortAlias              DisplayString,

    f3PtpOCSlaveVirtualPortAdminState         AdminState,
    f3PtpOCSlaveVirtualPortOperationalState   OperationalState,
    f3PtpOCSlaveVirtualPortSecondaryState     SecondaryState,

    f3PtpOCSlaveVirtualPortIdentity           PortIdentity,
    f3PtpOCSlaveVirtualPortFlowPoint          VariablePointer,
    f3PtpOCSlaveVirtualPortState              PtpPortState,
    f3PtpOCSlaveVirtualPortStorageType        StorageType,
    f3PtpOCSlaveVirtualPortRowStatus          RowStatus
}

f3PtpOCSlaveVirtualPortIndex OBJECT-TYPE
    SYNTAX     Integer32
    MAX-ACCESS not-accessible 
    STATUS     current
    DESCRIPTION
         "Unique index value associated with the PTP OC Slave 
          Virtual Port index."
     ::= { f3PtpOCSlaveVirtualPortEntry 1 }

f3PtpOCSlaveVirtualPortAlias OBJECT-TYPE
    SYNTAX      DisplayString (SIZE(0..256))
    MAX-ACCESS  read-create
    STATUS      current
    DESCRIPTION
         "This object allows SNMP management entities to provide an 
          alias to the OC Slave Virtual Port entity."
     ::= { f3PtpOCSlaveVirtualPortEntry 2 }

f3PtpOCSlaveVirtualPortAdminState OBJECT-TYPE
    SYNTAX      AdminState 
    MAX-ACCESS  read-write
    STATUS      current
    DESCRIPTION
            "This object represents the Administrative State of the 
             OC Slave Virtual Port."
    ::= { f3PtpOCSlaveVirtualPortEntry 3 }

f3PtpOCSlaveVirtualPortOperationalState   OBJECT-TYPE
    SYNTAX      OperationalState 
    MAX-ACCESS  read-only
    STATUS      current
    DESCRIPTION
            "This object represents the Operational State of the OC Slave 
             Virtual Port."
    ::= { f3PtpOCSlaveVirtualPortEntry 4 }

f3PtpOCSlaveVirtualPortSecondaryState     OBJECT-TYPE
    SYNTAX      SecondaryState 
    MAX-ACCESS  read-only
    STATUS      current
    DESCRIPTION
           "This object represents the Secondary State of the OC Slave
            Virtual Port." 
    ::= { f3PtpOCSlaveVirtualPortEntry 5 }

f3PtpOCSlaveVirtualPortIdentity OBJECT-TYPE
    SYNTAX     PortIdentity 
    MAX-ACCESS read-write
    STATUS     current
    DESCRIPTION
         "This object represents the PTP Port Identity of the 
                       OC Slave Virtual Port." 
     ::= { f3PtpOCSlaveVirtualPortEntry 6 }

f3PtpOCSlaveVirtualPortFlowPoint OBJECT-TYPE
    SYNTAX     VariablePointer 
    MAX-ACCESS read-create
    STATUS     current
    DESCRIPTION
         "This object associates the PTP Flow Point with the 
          Slave Only Ordinary Clock."
     ::= { f3PtpOCSlaveVirtualPortEntry 7 }

f3PtpOCSlaveVirtualPortState OBJECT-TYPE
    SYNTAX     PtpPortState 
    MAX-ACCESS read-only
    STATUS     current
    DESCRIPTION
         "This object provides the PTP state of the OC Slave Virtual Port." 
     ::= { f3PtpOCSlaveVirtualPortEntry 8 }

f3PtpOCSlaveVirtualPortStorageType OBJECT-TYPE
    SYNTAX     StorageType
    MAX-ACCESS read-create
    STATUS     current
    DESCRIPTION
            "The type of storage configured for this entry."
    ::= { f3PtpOCSlaveVirtualPortEntry 9 }

f3PtpOCSlaveVirtualPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpOCSlaveVirtualPortRowStatus supported are
            createAndGo(4) and destroy(6).  All mandatory attributes
            must be specified in a single SNMP SET request with
            f3PtpOCSlaveVirtualPortRowStatus value as createAndGo(4).
            Upon successful row creation, this object has a
            value of active(1).

            The f3PtpOCSlaveVirtualPortRowStatus object may be modified if
            the associated instance of this object is equal to active(1)."
    ::= { f3PtpOCSlaveVirtualPortEntry 10 }

--
-- Ethernet Access Port - PTP Flow Point Table 
--
f3PtpAccPortFlowPointTable OBJECT-TYPE
    SYNTAX     SEQUENCE OF F3PtpAccPortFlowPointEntry 
    MAX-ACCESS not-accessible
    STATUS     current
    DESCRIPTION
       "A list of entries corresponding to the PTP Access Port Flow Point
        entities."
    ::= { f3PtpConfigObjects 6 }

f3PtpAccPortFlowPointEntry OBJECT-TYPE
    SYNTAX     F3PtpAccPortFlowPointEntry
    MAX-ACCESS not-accessible
    STATUS     current
    DESCRIPTION
          "An entry containing information applicable to a particular
           Access Port Flow Point Entity."
    INDEX { neIndex, shelfIndex, slotIndex, cmEthernetAccPortIndex, 
            f3PtpAccPortFlowPointIndex }
    ::= { f3PtpAccPortFlowPointTable 1 }


F3PtpAccPortFlowPointEntry ::= SEQUENCE {
    f3PtpAccPortFlowPointIndex                 Integer32,

    f3PtpAccPortFlowPointAlias                 DisplayString,

    f3PtpAccPortFlowPointAdminState            AdminState,
    f3PtpAccPortFlowPointOperationalState      OperationalState,
    f3PtpAccPortFlowPointSecondaryState        SecondaryState,

    f3PtpAccPortFlowPointType                  PtpFlowPointType,
    f3PtpAccPortFlowPointClock                 VariablePointer,
    f3PtpAccPortFlowPointService               VariablePointer,
    f3PtpAccPortFlowPointOuterVlanEtherType    Integer32,
    f3PtpAccPortFlowPointOuterVlanMemberList   DisplayString,
    f3PtpAccPortFlowPointOuterUntaggedEnabled  TruthValue,
    f3PtpAccPortFlowPointInner1VlanEtherType   Integer32,
    f3PtpAccPortFlowPointInner1VlanMemberList  DisplayString,
    f3PtpAccPortFlowPointInner1UntaggedEnabled TruthValue,
    f3PtpAccPortFlowPointInner2VlanEtherType   Integer32,
    f3PtpAccPortFlowPointInner2VlanMemberList  DisplayString,
    f3PtpAccPortFlowPointInner2UntaggedEnabled TruthValue,

    f3PtpAccPortFlowPointStorageType           StorageType,
    f3PtpAccPortFlowPointRowStatus             RowStatus,
    f3PtpAccPortFlowPointCOS                   Integer32,
    f3PtpAccPortFlowPointCIRLo                 Unsigned32,
    f3PtpAccPortFlowPointCIRHi                 Unsigned32,
    f3PtpAccPortFlowPointEIRLo                 Unsigned32,
    f3PtpAccPortFlowPointEIRHi                 Unsigned32,
    f3PtpAccPortFlowPointBufferSize            Unsigned32
}

f3PtpAccPortFlowPointIndex OBJECT-TYPE
    SYNTAX     Integer32
    MAX-ACCESS not-accessible 
    STATUS     current
    DESCRIPTION
         "Unique index value associated with the Access Port PTP Flow Point."
     ::= { f3PtpAccPortFlowPointEntry 1 }

f3PtpAccPortFlowPointAlias OBJECT-TYPE
    SYNTAX      DisplayString (SIZE(0..256))
    MAX-ACCESS  read-create
    STATUS      current
    DESCRIPTION
         "This object allows SNMP management entities to provide an 
          alias to the Access Port PTP Flow Point."
     ::= { f3PtpAccPortFlowPointEntry 2 }

f3PtpAccPortFlowPointAdminState OBJECT-TYPE
    SYNTAX      AdminState 
    MAX-ACCESS  read-write
    STATUS      current
    DESCRIPTION
            "This object represents the Administrative State of the 
             PTP Flow Point." 
     ::= { f3PtpAccPortFlowPointEntry 3 }

f3PtpAccPortFlowPointOperationalState   OBJECT-TYPE
    SYNTAX      OperationalState 
    MAX-ACCESS  read-only
    STATUS      current
    DESCRIPTION
            "This object represents the Operational State of the PTP Flow 
             Point."
     ::= { f3PtpAccPortFlowPointEntry 4 }

f3PtpAccPortFlowPointSecondaryState     OBJECT-TYPE
    SYNTAX      SecondaryState 
    MAX-ACCESS  read-only
    STATUS      current
    DESCRIPTION
           "This object represents the Secondary State of the PTP Flow Point."
     ::= { f3PtpAccPortFlowPointEntry 5 }

f3PtpAccPortFlowPointType OBJECT-TYPE
    SYNTAX      PtpFlowPointType 
    MAX-ACCESS  read-create
    STATUS      current
    DESCRIPTION
            "This object represents the PTP Flow Point Type, i.e. whether
             it is an Transparent Clock or an OC Slave."
    ::= { f3PtpAccPortFlowPointEntry 6 }

f3PtpAccPortFlowPointClock OBJECT-TYPE
    SYNTAX      VariablePointer 
    MAX-ACCESS  read-only
    STATUS      current
    DESCRIPTION
            "This object points to the Transparent Clock or Slave Only
             Ordinary Clock instance which is associated with this
             PTP Flow Point." 
    ::= { f3PtpAccPortFlowPointEntry 7 }

f3PtpAccPortFlowPointService OBJECT-TYPE
    SYNTAX      VariablePointer 
    MAX-ACCESS  read-create
    STATUS      current
    DESCRIPTION
            "This object points to the associated Traffic Service Flow."
    ::= { f3PtpAccPortFlowPointEntry 8 }

f3PtpAccPortFlowPointOuterVlanEtherType OBJECT-TYPE
    SYNTAX      Integer32 
    MAX-ACCESS  read-create
    STATUS      current
    DESCRIPTION
            "This object allows specification of the Outer VLAN Ether Type
             of the PTP Flow."
    ::= { f3PtpAccPortFlowPointEntry 9 }

f3PtpAccPortFlowPointOuterVlanMemberList OBJECT-TYPE
    SYNTAX      DisplayString 
    MAX-ACCESS  read-create
    STATUS      current
    DESCRIPTION
            "This object allows specification of the Outer VLAN(s) 
             of the PTP Flow."
    ::= { f3PtpAccPortFlowPointEntry 10 }

f3PtpAccPortFlowPointOuterUntaggedEnabled OBJECT-TYPE
    SYNTAX      TruthValue 
    MAX-ACCESS  read-create
    STATUS      current
    DESCRIPTION
            "This object allows specification of whether the Outer VLAN
             exists or not." 
    ::= { f3PtpAccPortFlowPointEntry 11 }

f3PtpAccPortFlowPointInner1VlanEtherType OBJECT-TYPE
    SYNTAX      Integer32 
    MAX-ACCESS  read-create
    STATUS      current
    DESCRIPTION
            "This object allows specification of the Inner1 VLAN Ether Type
             of the PTP Flow."
    ::= { f3PtpAccPortFlowPointEntry 12 }

f3PtpAccPortFlowPointInner1VlanMemberList OBJECT-TYPE
    SYNTAX      DisplayString 
    MAX-ACCESS  read-create
    STATUS      current
    DESCRIPTION
            "This object allows specification of the Inner1 VLAN(s) 
             of the PTP Flow."
    ::= { f3PtpAccPortFlowPointEntry 13 }

f3PtpAccPortFlowPointInner1UntaggedEnabled OBJECT-TYPE
    SYNTAX      TruthValue 
    MAX-ACCESS  read-create
    STATUS      current
    DESCRIPTION
            "This object allows specification of whether the Inner1 VLAN
             exists or not." 
    ::= { f3PtpAccPortFlowPointEntry 14 }

f3PtpAccPortFlowPointInner2VlanEtherType OBJECT-TYPE
    SYNTAX      Integer32 
    MAX-ACCESS  read-create
    STATUS      current
    DESCRIPTION
            "This object allows specification of the Inner2 VLAN Ether Type
             of the PTP Flow."
    ::= { f3PtpAccPortFlowPointEntry 15 }

f3PtpAccPortFlowPointInner2VlanMemberList OBJECT-TYPE
    SYNTAX      DisplayString 
    MAX-ACCESS  read-create
    STATUS      current
    DESCRIPTION
            "This object allows specification of the Inner2 VLAN(s) 
             of the PTP Flow."
    ::= { f3PtpAccPortFlowPointEntry 16 }

f3PtpAccPortFlowPointInner2UntaggedEnabled OBJECT-TYPE
    SYNTAX      TruthValue 
    MAX-ACCESS  read-create
    STATUS      current
    DESCRIPTION
            "This object allows specification of whether the Inner1 VLAN
             exists or not." 
    ::= { f3PtpAccPortFlowPointEntry 17 }

f3PtpAccPortFlowPointStorageType OBJECT-TYPE
    SYNTAX     StorageType
    MAX-ACCESS read-create
    STATUS     current
    DESCRIPTION
            "The type of storage configured for this entry."
    ::= { f3PtpAccPortFlowPointEntry 18 }

f3PtpAccPortFlowPointRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpAccPortFlowPointRowStatus supported are
            createAndGo(4) and destroy(6).  All mandatory attributes
            must be specified in a single SNMP SET request with
            f3PtpAccPortFlowPointRowStatus value as createAndGo(4).
            Upon successful row creation, this object has a
            value of active(1).

            The f3PtpAccPortFlowPointRowStatus object may be modified if
            the associated instance of this object is equal to active(1)."
    ::= { f3PtpAccPortFlowPointEntry 19 }


f3PtpAccPortFlowPointCOS OBJECT-TYPE
    SYNTAX      Integer32 (0..7)
    MAX-ACCESS  read-create
    STATUS      current
    DESCRIPTION
            "This object allows specification of Class of Service of the PTP traffic
             associated with this Flow Point."
    ::= { f3PtpAccPortFlowPointEntry 20 }

f3PtpAccPortFlowPointCIRLo OBJECT-TYPE
    SYNTAX      Unsigned32
    MAX-ACCESS  read-create
    STATUS      current
    DESCRIPTION
            "This object allows specification of Committed Information Rate of the 
             PTP traffic associated with this Flow Point.
             The CIR value is in bits-per-second units. The value of this object
             represents the lower 32 bits of the total CIR value."
    ::= { f3PtpAccPortFlowPointEntry 21 }

f3PtpAccPortFlowPointCIRHi OBJECT-TYPE
    SYNTAX      Unsigned32
    MAX-ACCESS  read-create
    STATUS      current
    DESCRIPTION
            "This object allows specification of Committed Information Rate of the 
             PTP traffic associated with this Flow Point.
             The CIR value is in bits-per-second units. The value of this object
             represents the higher 32 bits of the total CIR value."
    ::= { f3PtpAccPortFlowPointEntry 22 }

f3PtpAccPortFlowPointEIRLo OBJECT-TYPE
    SYNTAX      Unsigned32
    MAX-ACCESS  read-create
    STATUS      current
    DESCRIPTION
            "This object allows specification of Excess Information Rate of the 
             PTP traffic associated with this Flow Point.
             The EIR value is in bits-per-second units. The value of this object
             represents the lower 32 bits of the total EIR value."
    ::= { f3PtpAccPortFlowPointEntry 23 }

f3PtpAccPortFlowPointEIRHi OBJECT-TYPE
    SYNTAX      Unsigned32
    MAX-ACCESS  read-create
    STATUS      current
    DESCRIPTION
            "This object allows specification of Excess Information Rate of the 
             PTP traffic associated with this Flow Point.
             The EIR value is in bits-per-second units. The value of this object
             represents the higher 32 bits of the total EIR value."
    ::= { f3PtpAccPortFlowPointEntry 24 }

f3PtpAccPortFlowPointBufferSize OBJECT-TYPE
    SYNTAX      Unsigned32
    MAX-ACCESS  read-create
    STATUS      current
    DESCRIPTION
            "This object allows specification the Buffer Size of the queue associated
             with this Flow Point."
    ::= { f3PtpAccPortFlowPointEntry 25 }

--
-- Ethernet Network Port - PTP Flow Point Table 
--
f3PtpNetPortFlowPointTable OBJECT-TYPE
    SYNTAX     SEQUENCE OF F3PtpNetPortFlowPointEntry 
    MAX-ACCESS not-accessible
    STATUS     current
    DESCRIPTION
       "A list of entries corresponding to the PTP Network Port Flow Point
        entities."
    ::= { f3PtpConfigObjects 7 }

f3PtpNetPortFlowPointEntry OBJECT-TYPE
    SYNTAX     F3PtpNetPortFlowPointEntry
    MAX-ACCESS not-accessible
    STATUS     current
    DESCRIPTION
          "An entry containing information applicable to a particular
           Network Port Flow Point Entity."
    INDEX { neIndex, shelfIndex, slotIndex, cmEthernetNetPortIndex, 
            f3PtpNetPortFlowPointIndex }
    ::= { f3PtpNetPortFlowPointTable 1 }


F3PtpNetPortFlowPointEntry ::= SEQUENCE {
    f3PtpNetPortFlowPointIndex                 Integer32,

    f3PtpNetPortFlowPointAlias                 DisplayString,

    f3PtpNetPortFlowPointAdminState            AdminState,
    f3PtpNetPortFlowPointOperationalState      OperationalState,
    f3PtpNetPortFlowPointSecondaryState        SecondaryState,

    f3PtpNetPortFlowPointType                  PtpFlowPointType,
    f3PtpNetPortFlowPointClock                 VariablePointer,
    f3PtpNetPortFlowPointService               VariablePointer,
    f3PtpNetPortFlowPointOuterVlanEtherType    Integer32,
    f3PtpNetPortFlowPointOuterVlanMemberList   DisplayString,
    f3PtpNetPortFlowPointOuterUntaggedEnabled  TruthValue,
    f3PtpNetPortFlowPointInner1VlanEtherType   Integer32,
    f3PtpNetPortFlowPointInner1VlanMemberList  DisplayString,
    f3PtpNetPortFlowPointInner1UntaggedEnabled TruthValue,
    f3PtpNetPortFlowPointInner2VlanEtherType   Integer32,
    f3PtpNetPortFlowPointInner2VlanMemberList  DisplayString,
    f3PtpNetPortFlowPointInner2UntaggedEnabled TruthValue,

    f3PtpNetPortFlowPointStorageType           StorageType,
    f3PtpNetPortFlowPointRowStatus             RowStatus,
    f3PtpNetPortFlowPointCOS                   Integer32,
    f3PtpNetPortFlowPointCIRLo                 Unsigned32,
    f3PtpNetPortFlowPointCIRHi                 Unsigned32,
    f3PtpNetPortFlowPointEIRLo                 Unsigned32,
    f3PtpNetPortFlowPointEIRHi                 Unsigned32,
    f3PtpNetPortFlowPointBufferSize            Unsigned32
}

f3PtpNetPortFlowPointIndex OBJECT-TYPE
    SYNTAX     Integer32
    MAX-ACCESS not-accessible 
    STATUS     current
    DESCRIPTION
         "Unique index value associated with the Network Port PTP Flow Point."
     ::= { f3PtpNetPortFlowPointEntry 1 }

f3PtpNetPortFlowPointAlias    OBJECT-TYPE
    SYNTAX      DisplayString (SIZE(0..256))
    MAX-ACCESS  read-create
    STATUS      current
    DESCRIPTION
         "This object allows SNMP management entities to provide an 
          alias to the Network Port Flow Point entity."
     ::= { f3PtpNetPortFlowPointEntry 2 }

f3PtpNetPortFlowPointAdminState OBJECT-TYPE
    SYNTAX      AdminState 
    MAX-ACCESS  read-write
    STATUS      current
    DESCRIPTION
            "This object represents the Administrative State of the 
             PTP Flow Point." 
     ::= { f3PtpNetPortFlowPointEntry 3 }

f3PtpNetPortFlowPointOperationalState   OBJECT-TYPE
    SYNTAX      OperationalState 
    MAX-ACCESS  read-only
    STATUS      current
    DESCRIPTION
            "This object represents the Operational State of the PTP Flow 
             Point."
     ::= { f3PtpNetPortFlowPointEntry 4 }

f3PtpNetPortFlowPointSecondaryState     OBJECT-TYPE
    SYNTAX      SecondaryState 
    MAX-ACCESS  read-only
    STATUS      current
    DESCRIPTION
           "This object represents the Secondary State of the PTP Flow Point."
     ::= { f3PtpNetPortFlowPointEntry 5 }

f3PtpNetPortFlowPointType OBJECT-TYPE
    SYNTAX      PtpFlowPointType 
    MAX-ACCESS  read-create
    STATUS      current
    DESCRIPTION
            "This object represents the PTP Flow Point Type, i.e. whether
             it is an Transparent Clock or an OC Slave."
    ::= { f3PtpNetPortFlowPointEntry 6 }

f3PtpNetPortFlowPointClock OBJECT-TYPE
    SYNTAX      VariablePointer 
    MAX-ACCESS  read-only
    STATUS      current
    DESCRIPTION
            "This object points to the Transparent Clock or Slave Only
             Ordinary Clock instance which is associated with this
             PTP Flow Point." 
    ::= { f3PtpNetPortFlowPointEntry 7 }

f3PtpNetPortFlowPointService OBJECT-TYPE
    SYNTAX      VariablePointer 
    MAX-ACCESS  read-create
    STATUS      current
    DESCRIPTION
            "This object points to the associated Traffic Service Flow."
    ::= { f3PtpNetPortFlowPointEntry 8 }

f3PtpNetPortFlowPointOuterVlanEtherType OBJECT-TYPE
    SYNTAX      Integer32 
    MAX-ACCESS  read-create
    STATUS      current
    DESCRIPTION
            "This object allows specification of the Outer VLAN Ether Type
             of the PTP Flow."
    ::= { f3PtpNetPortFlowPointEntry 9 }

f3PtpNetPortFlowPointOuterVlanMemberList OBJECT-TYPE
    SYNTAX      DisplayString 
    MAX-ACCESS  read-create
    STATUS      current
    DESCRIPTION
            "This object allows specification of the Outer VLAN(s) 
             of the PTP Flow."
    ::= { f3PtpNetPortFlowPointEntry 10 }

f3PtpNetPortFlowPointOuterUntaggedEnabled OBJECT-TYPE
    SYNTAX      TruthValue 
    MAX-ACCESS  read-create
    STATUS      current
    DESCRIPTION
            "This object allows specification of whether the Outer VLAN
             exists or not." 
    ::= { f3PtpNetPortFlowPointEntry 11 }

f3PtpNetPortFlowPointInner1VlanEtherType OBJECT-TYPE
    SYNTAX      Integer32 
    MAX-ACCESS  read-create
    STATUS      current
    DESCRIPTION
            "This object allows specification of the Inner1 VLAN Ether Type
             of the PTP Flow."
    ::= { f3PtpNetPortFlowPointEntry 12 }

f3PtpNetPortFlowPointInner1VlanMemberList OBJECT-TYPE
    SYNTAX      DisplayString 
    MAX-ACCESS  read-create
    STATUS      current
    DESCRIPTION
            "This object allows specification of the Inner1 VLAN(s) 
             of the PTP Flow."
    ::= { f3PtpNetPortFlowPointEntry 13 }

f3PtpNetPortFlowPointInner1UntaggedEnabled OBJECT-TYPE
    SYNTAX      TruthValue 
    MAX-ACCESS  read-create
    STATUS      current
    DESCRIPTION
            "This object allows specification of whether the Inner1 VLAN
             exists or not." 
    ::= { f3PtpNetPortFlowPointEntry 14 }

f3PtpNetPortFlowPointInner2VlanEtherType OBJECT-TYPE
    SYNTAX      Integer32 
    MAX-ACCESS  read-create
    STATUS      current
    DESCRIPTION
            "This object allows specification of the Inner2 VLAN Ether Type
             of the PTP Flow."
    ::= { f3PtpNetPortFlowPointEntry 15 }

f3PtpNetPortFlowPointInner2VlanMemberList OBJECT-TYPE
    SYNTAX      DisplayString 
    MAX-ACCESS  read-create
    STATUS      current
    DESCRIPTION
            "This object allows specification of the Inner2 VLAN(s) 
             of the PTP Flow."
    ::= { f3PtpNetPortFlowPointEntry 16 }

f3PtpNetPortFlowPointInner2UntaggedEnabled OBJECT-TYPE
    SYNTAX      TruthValue 
    MAX-ACCESS  read-create
    STATUS      current
    DESCRIPTION
            "This object allows specification of whether the Inner1 VLAN
             exists or not." 
    ::= { f3PtpNetPortFlowPointEntry 17 }

f3PtpNetPortFlowPointStorageType OBJECT-TYPE
    SYNTAX     StorageType
    MAX-ACCESS read-create
    STATUS     current
    DESCRIPTION
            "The type of storage configured for this entry."
    ::= { f3PtpNetPortFlowPointEntry 18 }

f3PtpNetPortFlowPointRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpNetPortFlowPointRowStatus supported are
            createAndGo(4) and destroy(6).  All mandatory attributes
            must be specified in a single SNMP SET request with
            f3PtpNetPortFlowPointRowStatus value as createAndGo(4).
            Upon successful row creation, this object has a
            value of active(1).

            The f3PtpNetPortFlowPointRowStatus object may be modified if
            the associated instance of this object is equal to active(1)."
    ::= { f3PtpNetPortFlowPointEntry 19 }

f3PtpNetPortFlowPointCOS OBJECT-TYPE
    SYNTAX      Integer32 (0..7)
    MAX-ACCESS  read-create
    STATUS      current
    DESCRIPTION
            "This object allows specification of Class of Service of the PTP traffic
             associated with this Flow Point."
    ::= { f3PtpNetPortFlowPointEntry 20 }

f3PtpNetPortFlowPointCIRLo OBJECT-TYPE
    SYNTAX      Unsigned32
    MAX-ACCESS  read-create
    STATUS      current
    DESCRIPTION
            "This object allows specification of Committed Information Rate of the 
             PTP traffic associated with this Flow Point.
             The CIR value is in bits-per-second units. The value of this object
             represents the lower 32 bits of the total CIR value."
    ::= { f3PtpNetPortFlowPointEntry 21 }

f3PtpNetPortFlowPointCIRHi OBJECT-TYPE
    SYNTAX      Unsigned32
    MAX-ACCESS  read-create
    STATUS      current
    DESCRIPTION
            "This object allows specification of Committed Information Rate of the 
             PTP traffic associated with this Flow Point.
             The CIR value is in bits-per-second units. The value of this object
             represents the higher 32 bits of the total CIR value."
    ::= { f3PtpNetPortFlowPointEntry 22 }

f3PtpNetPortFlowPointEIRLo OBJECT-TYPE
    SYNTAX      Unsigned32
    MAX-ACCESS  read-create
    STATUS      current
    DESCRIPTION
            "This object allows specification of Excess Information Rate of the 
             PTP traffic associated with this Flow Point.
             The EIR value is in bits-per-second units. The value of this object
             represents the lower 32 bits of the total EIR value."
    ::= { f3PtpNetPortFlowPointEntry 23 }

f3PtpNetPortFlowPointEIRHi OBJECT-TYPE
    SYNTAX      Unsigned32
    MAX-ACCESS  read-create
    STATUS      current
    DESCRIPTION
            "This object allows specification of Excess Information Rate of the 
             PTP traffic associated with this Flow Point.
             The EIR value is in bits-per-second units. The value of this object
             represents the higher 32 bits of the total EIR value."
    ::= { f3PtpNetPortFlowPointEntry 24 }

f3PtpNetPortFlowPointBufferSize OBJECT-TYPE
    SYNTAX      Unsigned32
    MAX-ACCESS  read-create
    STATUS      current
    DESCRIPTION
            "This object allows specification the Buffer Size of the queue associated
             with this Flow Point."
    ::= { f3PtpNetPortFlowPointEntry 25 }



f3PtpEthernetAccPortExtTable  OBJECT-TYPE
    SYNTAX      SEQUENCE OF F3PtpEthernetAccPortExtEntry
    MAX-ACCESS  not-accessible
    STATUS      current
    DESCRIPTION
            "This table extends cmEthernetAccPortTable by adding PTP related parameters."
    ::= { f3PtpConfigObjects 8 }

f3PtpEthernetAccPortExtEntry OBJECT-TYPE
    SYNTAX      F3PtpEthernetAccPortExtEntry
    MAX-ACCESS  not-accessible
    STATUS      current
    DESCRIPTION
            "A conceptual row in the f3PtpEthernetAccPortExtTable."
    AUGMENTS { cmEthernetAccPortEntry }
    ::= { f3PtpEthernetAccPortExtTable 1 }

F3PtpEthernetAccPortExtEntry ::= SEQUENCE {
    f3PtpEthernetAccPortDelayAsymmetry Integer32
}

f3PtpEthernetAccPortDelayAsymmetry OBJECT-TYPE
     SYNTAX     Integer32
     MAX-ACCESS read-write
     STATUS     current
     DESCRIPTION
         "This object allows configuring Delay Asymmetry in nanoseconds on 
          the Ethernet Access Port. The default value is 0."
     ::= { f3PtpEthernetAccPortExtEntry 1 }

f3PtpEthernetNetPortExtTable  OBJECT-TYPE
    SYNTAX      SEQUENCE OF F3PtpEthernetNetPortExtEntry
    MAX-ACCESS  not-accessible
    STATUS      current
    DESCRIPTION
            "This table extends cmEthernetNetPortTable by adding PTP related parameters."
    ::= { f3PtpConfigObjects 9 }

f3PtpEthernetNetPortExtEntry OBJECT-TYPE
    SYNTAX      F3PtpEthernetNetPortExtEntry
    MAX-ACCESS  not-accessible
    STATUS      current
    DESCRIPTION
            "A conceptual row in the f3PtpEthernetNetPortExtTable."
    AUGMENTS { cmEthernetNetPortEntry }
    ::= { f3PtpEthernetNetPortExtTable 1 }

F3PtpEthernetNetPortExtEntry ::= SEQUENCE {
    f3PtpEthernetNetPortDelayAsymmetry Integer32
}

f3PtpEthernetNetPortDelayAsymmetry OBJECT-TYPE
     SYNTAX     Integer32
     MAX-ACCESS read-write
     STATUS     current
     DESCRIPTION
         "This object allows configuring Delay Asymmetry in nanoseconds on 
          the Ethernet Network Port. The default value is 0."
     ::= { f3PtpEthernetNetPortExtEntry 1 }

-- 
-- Scalars
--
f3PtpConfigScalars             OBJECT IDENTIFIER ::= {f3PtpConfigObjects 10}

f3PtpSysTimeOfDayClock  OBJECT-TYPE
    SYNTAX      VariablePointer
    MAX-ACCESS  read-write
    STATUS      current
    DESCRIPTION
            "This objects allows configuing PTP Telecom Slave object to be used as 
             clock source for System Time of Day. 
             This object is applicable when sysTimeOfDayType object is set to 'ptp' and 
             points to f3PtpTSAlias.
             When sysTimeOfDayType is set to value other than 'ptp' this object should
             return zeroDotZero."
    ::= { f3PtpConfigScalars 1 }


f3PtpBCTable OBJECT-TYPE
    SYNTAX     SEQUENCE OF F3PtpBCEntry
    MAX-ACCESS not-accessible
    STATUS     current
    DESCRIPTION
       "A list of entries corresponding to the PTP Boundary Clock entities."
    ::= { f3PtpConfigObjects 11 }

f3PtpBCEntry OBJECT-TYPE
    SYNTAX     F3PtpBCEntry
    MAX-ACCESS not-accessible
    STATUS     current
    DESCRIPTION
          "An entry containing information applicable to a particular
           Boundary Clock Entity."
    INDEX { neIndex, f3PtpBCIndex}
            
    ::= { f3PtpBCTable 1 }

F3PtpBCEntry ::= SEQUENCE {
    f3PtpBCIndex              Integer32,
    f3PtpBCAlias              DisplayString,
    f3PtpBCAdminState         AdminState,
    f3PtpBCOperationalState   OperationalState,
    f3PtpBCSecondaryState     SecondaryState,
    f3PtpBCClockIdentity      ClockIdentity,
    f3PtpBCTimingSource       VariablePointer,
    f3PtpBCClockClass         Unsigned32,
    f3PtpBCDomainNumber       Integer32,
    f3PtpBCStorageType        StorageType,
    f3PtpBCRowStatus          RowStatus
}

f3PtpBCIndex OBJECT-TYPE
    SYNTAX     Integer32
    MAX-ACCESS not-accessible 
    STATUS     current
    DESCRIPTION
         "Unique index value associated with the Boundary Clock Entity."
     ::= { f3PtpBCEntry 1 }

f3PtpBCAlias    OBJECT-TYPE
    SYNTAX      DisplayString (SIZE(0..256))
    MAX-ACCESS  read-create
    STATUS      current
    DESCRIPTION
         "This object allows SNMP management entities to provide an 
          alias to the Boundary Clock entity."
     ::= { f3PtpBCEntry 2 }

f3PtpBCAdminState OBJECT-TYPE
    SYNTAX      AdminState 
    MAX-ACCESS  read-create
    STATUS      current
    DESCRIPTION
          "This object represents the Administrative State of the Boundary Clock."
    ::= { f3PtpBCEntry 3 }

f3PtpBCOperationalState   OBJECT-TYPE
    SYNTAX      OperationalState 
    MAX-ACCESS  read-only
    STATUS      current
    DESCRIPTION
          "This object represents the Operational State of the Boundary Clock." 
    ::= { f3PtpBCEntry 4 }

f3PtpBCSecondaryState     OBJECT-TYPE
    SYNTAX      SecondaryState 
    MAX-ACCESS  read-only
    STATUS      current
    DESCRIPTION
           "This object represents the Secondary State of the Boundary Clock."
    ::= { f3PtpBCEntry 5 }

f3PtpBCClockIdentity OBJECT-TYPE
    SYNTAX     ClockIdentity 
    MAX-ACCESS read-create
    STATUS     current
    DESCRIPTION
         "This object specifies the Clock Identity of the PTP Boundary Clock." 
     ::= { f3PtpBCEntry 6 }

f3PtpBCTimingSource OBJECT-TYPE
    SYNTAX     VariablePointer 
    MAX-ACCESS read-create
    STATUS     current
    DESCRIPTION
         "This object provides the entry from the f3PtpTSTable, which is
          used as frequency and time of day source this Boundary Clock."
     ::= { f3PtpBCEntry 7 }

f3PtpBCClockClass OBJECT-TYPE
    SYNTAX     Unsigned32 
    MAX-ACCESS read-only
    STATUS     current
    DESCRIPTION
         "This object provides the entry from the f3PtpTSTable, which is
          used as frequency and time of day source this Boundary Clock."
     ::= { f3PtpBCEntry 8 }

f3PtpBCDomainNumber OBJECT-TYPE
    SYNTAX     Integer32 
    MAX-ACCESS read-create
    STATUS     current
    DESCRIPTION
         "This object provides the entry from the f3PtpTSTable, which is
          used as frequency and time of day source this Boundary Clock."
     ::= { f3PtpBCEntry 9 }

f3PtpBCStorageType OBJECT-TYPE
    SYNTAX     StorageType
    MAX-ACCESS read-create
    STATUS     current
    DESCRIPTION
            "The type of storage configured for this entry."
    ::= { f3PtpBCEntry 10 }

f3PtpBCRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpBCRowStatus supported are
            createAndGo(4) and destroy(6).  All mandatory attributes
            must be specified in a single SNMP SET request with
            f3PtpBCRowStatus value as createAndGo(4).
            Upon successful row creation, this object has a
            value of active(1).

            The f3PtpBCRowStatus object may be modified if
            the associated instance of this object is equal to active(1)."
    ::= { f3PtpBCEntry 11 }
                               
      
  
--
-- Master Clock Table 
-- 

f3PtpMasterClockTable OBJECT-TYPE
    SYNTAX     SEQUENCE OF F3PtpMasterClockEntry
    MAX-ACCESS not-accessible
    STATUS     current
    DESCRIPTION
       "A list of entries corresponding to the PTP Master Clock entities."
    ::= { f3PtpConfigObjects 12 }

f3PtpMasterClockEntry OBJECT-TYPE
    SYNTAX     F3PtpMasterClockEntry
    MAX-ACCESS not-accessible
    STATUS     current
    DESCRIPTION
          "An entry containing information applicable to a particular
           Master Clock Entity."
    INDEX { neIndex, f3PtpMasterClockIndex}
            
    ::= { f3PtpMasterClockTable 1 }

F3PtpMasterClockEntry ::= SEQUENCE {
    f3PtpMasterClockIndex              Integer32,
    f3PtpMasterClockAlias              DisplayString,
    f3PtpMasterClockAdminState         AdminState,
    f3PtpMasterClockOperationalState   OperationalState,
    f3PtpMasterClockSecondaryState     SecondaryState,
    f3PtpMasterClockClockIdentity      ClockIdentity,
    f3PtpMasterClockTimeClock          VariablePointer,
    f3PtpMasterClockDomainNumber       Integer32,
    f3PtpMasterClockPriority1          Unsigned32,
    f3PtpMasterClockPriority2          Unsigned32,
    f3PtpMasterClockClockClass         Unsigned32,
    f3PtpMasterClockClockAccuracy      Unsigned32,
    f3PtpMasterClockTimeScale          TimeScale,
    f3PtpMasterClockUtcOffset          Integer32,
    f3PtpMasterClockStorageType        StorageType,
    f3PtpMasterClockRowStatus          RowStatus,
    f3PtpMasterClockActiveTimeRef      VariablePointer
}

f3PtpMasterClockIndex OBJECT-TYPE
    SYNTAX     Integer32
    MAX-ACCESS not-accessible 
    STATUS     current
    DESCRIPTION
         "Unique index value associated with the Boundary Clock Entity."
     ::= { f3PtpMasterClockEntry 1 }

f3PtpMasterClockAlias    OBJECT-TYPE
    SYNTAX      DisplayString (SIZE(0..256))
    MAX-ACCESS  read-create
    STATUS      current
    DESCRIPTION
         "This object allows SNMP management entities to provide an 
          alias to the Master Clock entity."
     ::= { f3PtpMasterClockEntry 2 }

f3PtpMasterClockAdminState OBJECT-TYPE
    SYNTAX      AdminState 
    MAX-ACCESS  read-create
    STATUS      current
    DESCRIPTION
          "This object represents the Administrative State of the Master Clock."
    ::= { f3PtpMasterClockEntry 3 }

f3PtpMasterClockOperationalState   OBJECT-TYPE
    SYNTAX      OperationalState 
    MAX-ACCESS  read-only
    STATUS      current
    DESCRIPTION
          "This object represents the Operational State of the Master Clock." 
    ::= { f3PtpMasterClockEntry 4 }

f3PtpMasterClockSecondaryState     OBJECT-TYPE
    SYNTAX      SecondaryState 
    MAX-ACCESS  read-only
    STATUS      current
    DESCRIPTION
           "This object represents the Secondary State of the Master Clock."
    ::= { f3PtpMasterClockEntry 5 }

f3PtpMasterClockClockIdentity OBJECT-TYPE
    SYNTAX     ClockIdentity 
    MAX-ACCESS read-create
    STATUS     current
    DESCRIPTION
         "This object specifies the Clock Identity of the PTP Boundary Clock." 
     ::= { f3PtpMasterClockEntry 6 }

f3PtpMasterClockTimeClock OBJECT-TYPE
    SYNTAX     VariablePointer 
    MAX-ACCESS read-create
    STATUS     current
    DESCRIPTION
         "This object provides the entry from the f3TimeClockTable, which is
          used as frequency and time of day source this Master Clock."
     ::= { f3PtpMasterClockEntry 7 }

f3PtpMasterClockDomainNumber OBJECT-TYPE
    SYNTAX     Integer32 
    MAX-ACCESS read-create
    STATUS     current
    DESCRIPTION
          "This object allows specification of the PTP domain number of the
           Master Clock ."
     ::= { f3PtpMasterClockEntry 8 }
     
f3PtpMasterClockPriority1 OBJECT-TYPE
    SYNTAX     Unsigned32 (0..255) 
    MAX-ACCESS read-create
    STATUS     current
    DESCRIPTION
         ""
     ::= { f3PtpMasterClockEntry 9 }
     
f3PtpMasterClockPriority2 OBJECT-TYPE
    SYNTAX     Unsigned32 (0..255) 
    MAX-ACCESS read-create
    STATUS     current
    DESCRIPTION
         ""
     ::= { f3PtpMasterClockEntry 10 }

f3PtpMasterClockClockClass OBJECT-TYPE
    SYNTAX     Unsigned32 
    MAX-ACCESS read-only
    STATUS     current
    DESCRIPTION
         "This object provides the Time Clock Clock Class"
     ::= { f3PtpMasterClockEntry 11 }
     
f3PtpMasterClockClockAccuracy OBJECT-TYPE
    SYNTAX     Unsigned32 
    MAX-ACCESS read-only
    STATUS     obsolete
    DESCRIPTION
         "This object indicates Clock accuracy of the clock"
     ::= { f3PtpMasterClockEntry 12 }

f3PtpMasterClockTimeScale   OBJECT-TYPE
    SYNTAX      TimeScale 
    MAX-ACCESS  read-only
    STATUS      current
    DESCRIPTION
          "" 
    ::= { f3PtpMasterClockEntry 13 }

f3PtpMasterClockUtcOffset OBJECT-TYPE
    SYNTAX     Integer32 
    MAX-ACCESS read-only
    STATUS     current
    DESCRIPTION
          "Seconds offset between TAI and UTC"
     ::= { f3PtpMasterClockEntry 14 }
     
     
f3PtpMasterClockStorageType OBJECT-TYPE
    SYNTAX     StorageType
    MAX-ACCESS read-create
    STATUS     current
    DESCRIPTION
            "The type of storage configured for this entry."
    ::= { f3PtpMasterClockEntry 15 }

f3PtpMasterClockRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpMasterClockRowStatus supported are
            createAndGo(4) and destroy(6).  All mandatory attributes
            must be specified in a single SNMP SET request with
            f3PtpMasterClockRowStatus value as createAndGo(4).
            Upon successful row creation, this object has a
            value of active(1).

            The f3PtpMasterClockRowStatus object may be modified if
            the associated instance of this object is equal to active(1)."
    ::= { f3PtpMasterClockEntry 16 }

f3PtpMasterClockActiveTimeRef OBJECT-TYPE
    SYNTAX     VariablePointer 
    MAX-ACCESS read-only
    STATUS     current
    DESCRIPTION
         "This object specifies timig reference of the Master Clock."
     ::= { f3PtpMasterClockEntry 17 }

--
-- Master Clock Interface Table 
--

f3PtpMCITable OBJECT-TYPE
    SYNTAX     SEQUENCE OF F3PtpMCIEntry
    MAX-ACCESS not-accessible
    STATUS     current
    DESCRIPTION
       "A list of entries corresponding to the PTP Master Clock Interface entities."
    ::= { f3PtpConfigObjects 13 }


f3PtpMCIEntry OBJECT-TYPE
    SYNTAX     F3PtpMCIEntry
    MAX-ACCESS not-accessible
    STATUS     current
    DESCRIPTION
          "An entry containing information applicable to a particular
           Master Clock Interface Entity."
    INDEX { neIndex, f3PtpBCIndex, f3PtpMCIIndex }
            
    ::= { f3PtpMCITable 1 }

F3PtpMCIEntry ::= SEQUENCE {
    f3PtpMCIIndex                    Integer32,
    f3PtpMCIAlias                    DisplayString,
    f3PtpMCIAdminState               AdminState,
    f3PtpMCIOperationalState         OperationalState,
    f3PtpMCISecondaryState           SecondaryState,
    f3PtpMCIPortIdentity             PortIdentity,
    f3PtpMCIDomainNumber             Integer32,
    f3PtpMCIClockType                MasterClockType,
    f3PtpMCIDelayMechanism           DelayMechanism,
    f3PtpMCIIfName                   DisplayString,
    f3PtpMCIIpProtocol               IpVersion,
    f3PtpMCIMasterIpV4Address        IpAddress,
    f3PtpMCIMasterIpV4SubnetMask     IpAddress,
    f3PtpMCIIpPriorityMapMode        IpPriorityMapMode,
    f3PtpMCIIpPriority               Integer32,
    f3PtpMCIMaxLeaseDuration         Integer32,
    f3PtpMCIMaxSlavesSupported       Integer32,
    f3PtpMCIMaxStaticSlavesSupported Integer32,
    f3PtpMCIMaxSyncMsgRate           SyncMsgRate,
    f3PtpMCIMaxDelayRespMsgRate      DelayRespMsgRate,
    f3PtpMCIMaxAnnounceMsgRate       AnnounceMsgRate,
    f3PtpMCIStorageType              StorageType,
    f3PtpMCIRowStatus                RowStatus,
    f3PtpMCIServiceFlow              VariablePointer,
    f3PtpMCIClockClassProfile        ClockClassProfile,
    f3PtpMCIClockClass               Unsigned32 
}

f3PtpMCIIndex OBJECT-TYPE
    SYNTAX     Integer32
    MAX-ACCESS not-accessible 
    STATUS     current
    DESCRIPTION
         "Unique index value associated with the Master Clock Interface."
     ::= { f3PtpMCIEntry 1 }

f3PtpMCIAlias    OBJECT-TYPE
    SYNTAX      DisplayString (SIZE(0..256))
    MAX-ACCESS  read-create
    STATUS      current
    DESCRIPTION
         "This object allows SNMP management entities to provide an 
          alias to the Master Clock Interface entity."
     ::= { f3PtpMCIEntry 2 }

f3PtpMCIAdminState OBJECT-TYPE
    SYNTAX      AdminState 
    MAX-ACCESS  read-create
    STATUS      current
    DESCRIPTION
          "This object represents the Administrative State of the Master Clock Interface."
    ::= { f3PtpMCIEntry 3 }

f3PtpMCIOperationalState   OBJECT-TYPE
    SYNTAX      OperationalState 
    MAX-ACCESS  read-only
    STATUS      current
    DESCRIPTION
          "This object represents the Operational State of the Master Clock Interface." 
    ::= { f3PtpMCIEntry 4 }

f3PtpMCISecondaryState     OBJECT-TYPE
    SYNTAX      SecondaryState 
    MAX-ACCESS  read-only
    STATUS      current
    DESCRIPTION
           "This object represents the Secondary State of the Master Clock Interface."
    ::= { f3PtpMCIEntry 5 }

f3PtpMCIPortIdentity OBJECT-TYPE
    SYNTAX     PortIdentity 
    MAX-ACCESS read-only
    STATUS     current
    DESCRIPTION
         "This object represents the PTP Port Identity of the Master Clock Interface." 
     ::= { f3PtpMCIEntry 6 }

f3PtpMCIDomainNumber OBJECT-TYPE
    SYNTAX     Integer32 
    MAX-ACCESS read-only
    STATUS     current
    DESCRIPTION
         "This object allows specification of the PTP domain number of the
           Master Clock Interface." 
     ::= { f3PtpMCIEntry 7 }

f3PtpMCIClockType OBJECT-TYPE
    SYNTAX     MasterClockType
    MAX-ACCESS read-create 
    STATUS     current
    DESCRIPTION
         "This object must be used to specify the type of the Master Clock Interface."
     ::= { f3PtpMCIEntry 8 }

f3PtpMCIDelayMechanism OBJECT-TYPE
    SYNTAX      DelayMechanism 
    MAX-ACCESS  read-create
    STATUS      current
    DESCRIPTION
            "This object  represents the Delay Mechanism of the  Master Clock Interface."
    ::= { f3PtpMCIEntry 9 }

f3PtpMCIIfName     OBJECT-TYPE
    SYNTAX         DisplayString (SIZE(1..15))
    MAX-ACCESS     read-create
    STATUS         current
    DESCRIPTION
         "This object allows SNMP management entities to provide a
          name to the Slave Only Ordinary Clock.  This is used
          for creation of the underlying IP Interface associated 
          with the Master Clock Interface."
     ::= { f3PtpMCIEntry 10 }

f3PtpMCIIpProtocol OBJECT-TYPE
    SYNTAX     IpVersion
    MAX-ACCESS read-create 
    STATUS     current
    DESCRIPTION
         "This object allows specification of the IP Protocol to
          communicate with Remote Slaves. Only ipv4 is supported."
     ::= { f3PtpMCIEntry 11 }

f3PtpMCIMasterIpV4Address OBJECT-TYPE
    SYNTAX     IpAddress
    MAX-ACCESS read-create 
    STATUS     current
    DESCRIPTION
         "This object allows specification of the IPv4 Address of
          the PTP Master."
     ::= { f3PtpMCIEntry 12 }

f3PtpMCIMasterIpV4SubnetMask OBJECT-TYPE
    SYNTAX     IpAddress
    MAX-ACCESS read-create 
    STATUS     current
    DESCRIPTION
         "This object allows specification of the IPv4 Subnet Mask of
          the PTP Master."
     ::= { f3PtpMCIEntry 13 }

f3PtpMCIIpPriorityMapMode  OBJECT-TYPE
    SYNTAX     IpPriorityMapMode 
    MAX-ACCESS read-create
    STATUS     current
    DESCRIPTION
         "This object enables specification of Priority Mapping Mode for
          the  Master Clock Interface."
     ::= { f3PtpMCIEntry 14 }

f3PtpMCIIpPriority  OBJECT-TYPE
    SYNTAX     Integer32 (0..63)
    MAX-ACCESS read-create
    STATUS     current
    DESCRIPTION
         "This object enables specification of Priority Value for
          f3PtpMCIIpPriorityMapMode as priomap-tos,priomap-dscp."
     ::= { f3PtpMCIEntry 15 }

f3PtpMCIMaxLeaseDuration  OBJECT-TYPE
    SYNTAX     Integer32
    MAX-ACCESS read-create
    STATUS     current
    DESCRIPTION
         "This enables specification of maximum lease duration for granted announce, 
          Sync and Delay Response service in seconds."
     ::= { f3PtpMCIEntry 16 }

f3PtpMCIMaxSlavesSupported OBJECT-TYPE
    SYNTAX     Integer32
    MAX-ACCESS read-write
    STATUS     current
    DESCRIPTION
         "This attribute specifies maximum total number of Static and Dynamic
          Remote Slaves supported by the Master Clock Interface."
     ::= { f3PtpMCIEntry 17 }

f3PtpMCIMaxStaticSlavesSupported OBJECT-TYPE
    SYNTAX     Integer32
    MAX-ACCESS read-write
    STATUS     current
    DESCRIPTION
         "This attribute specifies maximum  total number of Static
          Remote Slaves supported by the Master Clock Interface."
     ::= { f3PtpMCIEntry 18 }

f3PtpMCIMaxSyncMsgRate OBJECT-TYPE
    SYNTAX     SyncMsgRate
    MAX-ACCESS read-create
    STATUS     current
    DESCRIPTION
         "This attribute specifies maximum allowed negotiated Sync Messages rate per 
          remote Slave Clock with UMN enabled of default Sync Messages rate per 
          remote Slave Clock with UMN disabled."
     ::= { f3PtpMCIEntry 19 }

f3PtpMCIMaxDelayRespMsgRate OBJECT-TYPE
    SYNTAX     DelayRespMsgRate
    MAX-ACCESS read-create
    STATUS     current
    DESCRIPTION
         "This attribute specifies maximum allowed negotiated Delay_Resp Messages rate 
          per remote Slave Clock with UMN enabled of default Delay_Resp Messages rate 
          per remote Slave Clock with UMN disabled."
     ::= { f3PtpMCIEntry 20 }

f3PtpMCIMaxAnnounceMsgRate OBJECT-TYPE
    SYNTAX     AnnounceMsgRate
    MAX-ACCESS read-create
    STATUS     current
    DESCRIPTION
         "This attribute specifies maximum allowed negotiated Delay_Req Messages rate 
          per remote Slave Clock with UMN enabled of default Delay_Req Messages rate 
          per remote Slave Clock with UMN disabled."
     ::= { f3PtpMCIEntry 21 }

f3PtpMCIStorageType OBJECT-TYPE
    SYNTAX     StorageType
    MAX-ACCESS read-create
    STATUS     current
    DESCRIPTION
            "The type of storage configured for this entry."
    ::= { f3PtpMCIEntry 22 }

f3PtpMCIRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpMCIRowStatus supported are
            createAndGo(4) and destroy(6).  All mandatory attributes
            must be specified in a single SNMP SET request with
            f3PtpMCIRowStatus value as createAndGo(4).
            Upon successful row creation, this object has a
            value of active(1).

            The f3PtpMCIRowStatus object may be modified if
            the associated instance of this object is equal to active(1)."
    ::= { f3PtpMCIEntry 23 }

f3PtpMCIServiceFlow OBJECT-TYPE
    SYNTAX     VariablePointer
    MAX-ACCESS read-write
    STATUS     current
    DESCRIPTION
            "This object describe the associated service flow."
    ::= { f3PtpMCIEntry 24 }


f3PtpMCIClockClassProfile OBJECT-TYPE
    SYNTAX     ClockClassProfile
    MAX-ACCESS read-create
    STATUS     current
    DESCRIPTION
            "This object describe the Clock Class Profile."
    ::= { f3PtpMCIEntry 25 }

f3PtpMCIClockClass OBJECT-TYPE
    SYNTAX     Unsigned32 
    MAX-ACCESS read-only
    STATUS     current
    DESCRIPTION
         "This object provides the MCI Clock Class"
     ::= { f3PtpMCIEntry 26 }


f3PtpMasterVirtualPortTable OBJECT-TYPE
    SYNTAX     SEQUENCE OF F3PtpMasterVirtualPortEntry
    MAX-ACCESS not-accessible
    STATUS     current
    DESCRIPTION
       "A list of entries corresponding to the PTP Master Clock Interface 
        Virtual Port entities."
    ::= { f3PtpConfigObjects 14 }


f3PtpMasterVirtualPortEntry OBJECT-TYPE
    SYNTAX     F3PtpMasterVirtualPortEntry
    MAX-ACCESS not-accessible
    STATUS     current
    DESCRIPTION
          "An entry containing information applicable to a particular
           Master Clock Interface Virtual Port entity."
    INDEX { neIndex, f3PtpBCIndex, f3PtpMCIIndex, f3PtpMasterVirtualPortIndex}
            
    ::= { f3PtpMasterVirtualPortTable 1 }

F3PtpMasterVirtualPortEntry ::= SEQUENCE {
    f3PtpMasterVirtualPortIndex                    Integer32,
    f3PtpMasterVirtualPortAlias                    DisplayString,
    f3PtpMasterVirtualPortAdminState               AdminState,
    f3PtpMasterVirtualPortOperationalState         OperationalState,
    f3PtpMasterVirtualPortSecondaryState           SecondaryState,
    f3PtpMasterVirtualPortFlowPoint                VariablePointer,
    f3PtpMasterVirtualPortStorageType              StorageType,
    f3PtpMasterVirtualPortRowStatus                RowStatus
}

f3PtpMasterVirtualPortIndex OBJECT-TYPE
    SYNTAX     Integer32
    MAX-ACCESS not-accessible 
    STATUS     current
    DESCRIPTION
         "Unique index value associated with the Master Virtual Port entity."
     ::= { f3PtpMasterVirtualPortEntry 1 }

f3PtpMasterVirtualPortAlias    OBJECT-TYPE
    SYNTAX      DisplayString (SIZE(0..256))
    MAX-ACCESS  read-create
    STATUS      current
    DESCRIPTION
         "This object allows SNMP management entities to provide an 
          alias to the Master Virtual Port entity."
     ::= { f3PtpMasterVirtualPortEntry 2 }

f3PtpMasterVirtualPortAdminState OBJECT-TYPE
    SYNTAX      AdminState 
    MAX-ACCESS  read-create
    STATUS      current
    DESCRIPTION
          "This object represents the Administrative State of the Master Virtual Port."
    ::= { f3PtpMasterVirtualPortEntry 3 }

f3PtpMasterVirtualPortOperationalState   OBJECT-TYPE
    SYNTAX      OperationalState 
    MAX-ACCESS  read-only
    STATUS      current
    DESCRIPTION
          "This object represents the Operational State of the Master Virtual Port."
    ::= { f3PtpMasterVirtualPortEntry 4 }

f3PtpMasterVirtualPortSecondaryState     OBJECT-TYPE
    SYNTAX      SecondaryState 
    MAX-ACCESS  read-only
    STATUS      current
    DESCRIPTION
           "This object represents the Secondary State of the Master Virtual Port."
    ::= { f3PtpMasterVirtualPortEntry 5 }

f3PtpMasterVirtualPortFlowPoint     OBJECT-TYPE
    SYNTAX      VariablePointer 
    MAX-ACCESS  read-create
    STATUS      current
    DESCRIPTION
         "This object associates the PTP Flow Point with the Master Virtual Port."
    ::= { f3PtpMasterVirtualPortEntry 6 }

f3PtpMasterVirtualPortStorageType OBJECT-TYPE
    SYNTAX     StorageType
    MAX-ACCESS read-create
    STATUS     current
    DESCRIPTION
            "The type of storage configured for this entry."
    ::= { f3PtpMasterVirtualPortEntry 7 }

f3PtpMasterVirtualPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpMasterVirtualPortRowStatus supported are
            createAndGo(4) and destroy(6).  All mandatory attributes
            must be specified in a single SNMP SET request with
            f3PtpMasterVirtualPortRowStatus value as createAndGo(4).
            Upon successful row creation, this object has a
            value of active(1).

            The f3PtpMasterVirtualPortRowStatus object may be modified if
            the associated instance of this object is equal to active(1)."
    ::= { f3PtpMasterVirtualPortEntry 8 }

f3PtpStaticRemoteSlaveTable OBJECT-TYPE
    SYNTAX     SEQUENCE OF F3PtpStaticRemoteSlaveEntry
    MAX-ACCESS not-accessible
    STATUS     current
    DESCRIPTION
       "A list of entries corresponding to the PTP Remote Slave entities."
    ::= { f3PtpConfigObjects 15 }


f3PtpStaticRemoteSlaveEntry OBJECT-TYPE
    SYNTAX     F3PtpStaticRemoteSlaveEntry
    MAX-ACCESS not-accessible
    STATUS     current
    DESCRIPTION
          "An entry containing information applicable to a particular
           Static Remote Slave entity."
    INDEX { neIndex, f3PtpBCIndex, f3PtpMCIIndex, f3PtpStaticRemoteSlaveIndex}
            
    ::= { f3PtpStaticRemoteSlaveTable 1 }

F3PtpStaticRemoteSlaveEntry ::= SEQUENCE {
    f3PtpStaticRemoteSlaveIndex                    Integer32,
    f3PtpStaticRemoteSlaveAlias                    DisplayString,
    f3PtpStaticRemoteSlaveAdminState               AdminState,
    f3PtpStaticRemoteSlaveOperationalState         OperationalState,
    f3PtpStaticRemoteSlaveSecondaryState           SecondaryState,
    f3PtpStaticRemoteSlaveClockIdentity            ClockIdentity,
    f3PtpStaticRemoteSlaveIpV4Address              IpAddress,
    f3PtpStaticRemoteSlaveTimeCreated              DateAndTime,
    f3PtpStaticRemoteSlaveSyncMsgRate              SyncMsgRate,
    f3PtpStaticRemoteSlaveDelayRspMsgRate          DelayRespMsgRate,
    f3PtpStaticRemoteSlaveAnnounceMsgRate          AnnounceMsgRate,
    f3PtpStaticRemoteSlaveNegSyncLeaseDur          Integer32,
    f3PtpStaticRemoteSlaveNegDelayRspLeaseDur      Integer32,
    f3PtpStaticRemoteSlaveNegAnnounceLeaseDur      Integer32,
    f3PtpStaticRemoteSlaveSyncDurRemTime           Unsigned32,
    f3PtpStaticRemoteSlaveDelayRspDurRemTime       Unsigned32,
    f3PtpStaticRemoteSlaveAnnounceDurRemTime       Unsigned32,
    f3PtpStaticRemoteSlaveUmnControl               TruthValue,
    f3PtpStaticRemoteSlaveStorageType              StorageType,
    f3PtpStaticRemoteSlaveRowStatus                RowStatus
}

f3PtpStaticRemoteSlaveIndex OBJECT-TYPE
    SYNTAX     Integer32
    MAX-ACCESS not-accessible 
    STATUS     current
    DESCRIPTION
         "Unique index value associated with the Remote Slave."
     ::= { f3PtpStaticRemoteSlaveEntry 1 }

f3PtpStaticRemoteSlaveAlias    OBJECT-TYPE
    SYNTAX      DisplayString (SIZE(0..256))
    MAX-ACCESS  read-create
    STATUS      current
    DESCRIPTION
         "This object allows SNMP management entities to provide an 
          alias to the Remote Slave."
     ::= { f3PtpStaticRemoteSlaveEntry 2 }

f3PtpStaticRemoteSlaveAdminState OBJECT-TYPE
    SYNTAX      AdminState 
    MAX-ACCESS  read-create
    STATUS      current
    DESCRIPTION
          "This object represents the Administrative State of the Remote Slave."
    ::= { f3PtpStaticRemoteSlaveEntry 3 }

f3PtpStaticRemoteSlaveOperationalState   OBJECT-TYPE
    SYNTAX      OperationalState 
    MAX-ACCESS  read-only
    STATUS      current
    DESCRIPTION
          "This object represents the Operational State of the Remote Slave."
    ::= { f3PtpStaticRemoteSlaveEntry 4 }

f3PtpStaticRemoteSlaveSecondaryState     OBJECT-TYPE
    SYNTAX      SecondaryState 
    MAX-ACCESS  read-only
    STATUS      current
    DESCRIPTION
           "This object represents the Secondary State of the Remote Slave."
    ::= { f3PtpStaticRemoteSlaveEntry 5 }

f3PtpStaticRemoteSlaveClockIdentity OBJECT-TYPE
    SYNTAX     ClockIdentity 
    MAX-ACCESS read-only
    STATUS     current
    DESCRIPTION
         "This object represents the Clock Identity of the Remote Slave."
     ::= { f3PtpStaticRemoteSlaveEntry 6 }

f3PtpStaticRemoteSlaveIpV4Address OBJECT-TYPE
    SYNTAX     IpAddress
    MAX-ACCESS read-create 
    STATUS     current
    DESCRIPTION
         "This object allows specification of the IPv4 Address of
          the Remote Slave."
     ::= { f3PtpStaticRemoteSlaveEntry 7 }

f3PtpStaticRemoteSlaveTimeCreated OBJECT-TYPE
    SYNTAX     DateAndTime
    MAX-ACCESS read-only 
    STATUS     current
    DESCRIPTION
         "This object presents time when this Remote Slave entity was created."
     ::= { f3PtpStaticRemoteSlaveEntry 8 }

f3PtpStaticRemoteSlaveSyncMsgRate OBJECT-TYPE
    SYNTAX     SyncMsgRate
    MAX-ACCESS read-create
    STATUS     current
    DESCRIPTION
         "This attribute specifies Sync Message Rate of the Remote Slave."
     ::= { f3PtpStaticRemoteSlaveEntry 9 }

f3PtpStaticRemoteSlaveDelayRspMsgRate OBJECT-TYPE
    SYNTAX     DelayRespMsgRate
    MAX-ACCESS read-create
    STATUS     current
    DESCRIPTION
         "This attribute specifies Delay Respone Message Rate of the Remote Slave."
     ::= { f3PtpStaticRemoteSlaveEntry 10 }

f3PtpStaticRemoteSlaveAnnounceMsgRate OBJECT-TYPE
    SYNTAX     AnnounceMsgRate
    MAX-ACCESS read-create
    STATUS     current
    DESCRIPTION
         "This attribute specifies Announce Message Rate of the Remote Slave."
     ::= { f3PtpStaticRemoteSlaveEntry 11 }

f3PtpStaticRemoteSlaveNegSyncLeaseDur OBJECT-TYPE
    SYNTAX     Integer32
    MAX-ACCESS read-only
    STATUS     current
    DESCRIPTION
         "This attribute indicates Sync messages negotiated Lease Duration in seconds."
     ::= { f3PtpStaticRemoteSlaveEntry 12 }

f3PtpStaticRemoteSlaveNegDelayRspLeaseDur OBJECT-TYPE
    SYNTAX     Integer32
    MAX-ACCESS read-only
    STATUS     current
    DESCRIPTION
         "This attribute indicates Delay Response messages negotiated Lease 
          Duration in seconds."
     ::= { f3PtpStaticRemoteSlaveEntry 13 }

f3PtpStaticRemoteSlaveNegAnnounceLeaseDur OBJECT-TYPE
    SYNTAX     Integer32
    MAX-ACCESS read-only
    STATUS     current
    DESCRIPTION
         "This attribute indicates Announce messages negotiated Lease 
          Duration in seconds."
     ::= { f3PtpStaticRemoteSlaveEntry 14 }

f3PtpStaticRemoteSlaveSyncDurRemTime OBJECT-TYPE
    SYNTAX     Unsigned32
    MAX-ACCESS read-only
    STATUS     current
    DESCRIPTION
         "This attribute indicates Remaining seconds of Lease Duration of Sync service."
     ::= { f3PtpStaticRemoteSlaveEntry 15 }

f3PtpStaticRemoteSlaveDelayRspDurRemTime OBJECT-TYPE
    SYNTAX     Unsigned32
    MAX-ACCESS read-only
    STATUS     current
    DESCRIPTION
         "This attribute indicates Remaining seconds of Lease Duration of Delay Response 
          service."
     ::= { f3PtpStaticRemoteSlaveEntry 16 }

f3PtpStaticRemoteSlaveAnnounceDurRemTime OBJECT-TYPE
    SYNTAX     Unsigned32
    MAX-ACCESS read-only
    STATUS     current
    DESCRIPTION
         "This attribute indicates Remaining seconds of Lease Duration of Announce 
          service."
     ::= { f3PtpStaticRemoteSlaveEntry 17 }

f3PtpStaticRemoteSlaveUmnControl OBJECT-TYPE
    SYNTAX     TruthValue
    MAX-ACCESS read-create
    STATUS     current
    DESCRIPTION
         "This attribute controls UMN for the static remote slave."
     ::= { f3PtpStaticRemoteSlaveEntry 18 }

f3PtpStaticRemoteSlaveStorageType OBJECT-TYPE
    SYNTAX     StorageType
    MAX-ACCESS read-create
    STATUS     current
    DESCRIPTION
            "The type of storage configured for this entry."
    ::= { f3PtpStaticRemoteSlaveEntry 19 }

f3PtpStaticRemoteSlaveRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpStaticRemoteSlaveRowStatus supported are
            createAndGo(4) and destroy(6).  All mandatory attributes
            must be specified in a single SNMP SET request with
            f3PtpStaticRemoteSlaveRowStatus value as createAndGo(4).
            Upon successful row creation, this object has a
            value of active(1).

            The f3PtpStaticRemoteSlaveRowStatus object may be modified if
            the associated instance of this object is equal to active(1)."
    ::= { f3PtpStaticRemoteSlaveEntry 20 }


f3PtpDynamicRemoteSlaveTable OBJECT-TYPE
    SYNTAX     SEQUENCE OF F3PtpDynamicRemoteSlaveEntry
    MAX-ACCESS not-accessible
    STATUS     current
    DESCRIPTION
       "A list of entries corresponding to the PTP Remote Slave entities."
    ::= { f3PtpConfigObjects 16 }


f3PtpDynamicRemoteSlaveEntry OBJECT-TYPE
    SYNTAX     F3PtpDynamicRemoteSlaveEntry
    MAX-ACCESS not-accessible
    STATUS     current
    DESCRIPTION
          "An entry containing information applicable to a particular
           Dynamic Remote Slave entity."
    INDEX { neIndex, f3PtpBCIndex, f3PtpMCIIndex, f3PtpDynamicRemoteSlaveIndex}
            
    ::= { f3PtpDynamicRemoteSlaveTable 1 }

F3PtpDynamicRemoteSlaveEntry ::= SEQUENCE {
    f3PtpDynamicRemoteSlaveIndex                    Integer32,
    f3PtpDynamicRemoteSlaveAlias                    DisplayString,
    f3PtpDynamicRemoteSlaveAdminState               AdminState,
    f3PtpDynamicRemoteSlaveOperationalState         OperationalState,
    f3PtpDynamicRemoteSlaveSecondaryState           SecondaryState,
    f3PtpDynamicRemoteSlaveClockIdentity            ClockIdentity,
    f3PtpDynamicRemoteSlaveIpV4Address              IpAddress,
    f3PtpDynamicRemoteSlaveTimeCreated              DateAndTime,
    f3PtpDynamicRemoteSlaveSyncMsgRate              SyncMsgRate,
    f3PtpDynamicRemoteSlaveDelayRspMsgRate          DelayRespMsgRate,
    f3PtpDynamicRemoteSlaveAnnounceMsgRate          AnnounceMsgRate,
    f3PtpDynamicRemoteSlaveNegSyncLeaseDur          Integer32,
    f3PtpDynamicRemoteSlaveNegDelayRspLeaseDur      Integer32,
    f3PtpDynamicRemoteSlaveNegAnnounceLeaseDur      Integer32,
    f3PtpDynamicRemoteSlaveSyncDurRemTime           Unsigned32,
    f3PtpDynamicRemoteSlaveDelayRspDurRemTime       Unsigned32,
    f3PtpDynamicRemoteSlaveAnnounceDurRemTime       Unsigned32,
    f3PtpDynamicRemoteSlaveRowStatus                RowStatus,
    f3PtpDynamicRemoteSlaveStorageType              StorageType
}

f3PtpDynamicRemoteSlaveIndex OBJECT-TYPE
    SYNTAX     Integer32
    MAX-ACCESS not-accessible 
    STATUS     current
    DESCRIPTION
         "Unique index value associated with the Remote Slave."
     ::= { f3PtpDynamicRemoteSlaveEntry 1 }

f3PtpDynamicRemoteSlaveAlias    OBJECT-TYPE
    SYNTAX      DisplayString (SIZE(0..256))
    MAX-ACCESS  read-write
    STATUS      current
    DESCRIPTION
         "This object allows SNMP management entities to provide an 
          alias to the Remote Slave."
     ::= { f3PtpDynamicRemoteSlaveEntry 2 }

f3PtpDynamicRemoteSlaveAdminState OBJECT-TYPE
    SYNTAX      AdminState 
    MAX-ACCESS  read-write
    STATUS      current
    DESCRIPTION
          "This object represents the Administrative State of the Remote Slave."
    ::= { f3PtpDynamicRemoteSlaveEntry 3 }

f3PtpDynamicRemoteSlaveOperationalState   OBJECT-TYPE
    SYNTAX      OperationalState 
    MAX-ACCESS  read-only
    STATUS      current
    DESCRIPTION
          "This object represents the Operational State of the Remote Slave."
    ::= { f3PtpDynamicRemoteSlaveEntry 4 }

f3PtpDynamicRemoteSlaveSecondaryState     OBJECT-TYPE
    SYNTAX      SecondaryState 
    MAX-ACCESS  read-only
    STATUS      current
    DESCRIPTION
           "This object represents the Secondary State of the Remote Slave."
    ::= { f3PtpDynamicRemoteSlaveEntry 5 }

f3PtpDynamicRemoteSlaveClockIdentity OBJECT-TYPE
    SYNTAX     ClockIdentity 
    MAX-ACCESS read-only
    STATUS     current
    DESCRIPTION
         "This object represents the Clock Identity of the Remote Slave."
     ::= { f3PtpDynamicRemoteSlaveEntry 6 }

f3PtpDynamicRemoteSlaveIpV4Address OBJECT-TYPE
    SYNTAX     IpAddress
    MAX-ACCESS read-only 
    STATUS     current
    DESCRIPTION
         "This object allows specification of the IPv4 Address of
          the Remote Slave."
     ::= { f3PtpDynamicRemoteSlaveEntry 7 }

f3PtpDynamicRemoteSlaveTimeCreated OBJECT-TYPE
    SYNTAX     DateAndTime
    MAX-ACCESS read-only 
    STATUS     current
    DESCRIPTION
         "This object presents time when this Remote Slave entity was created."
     ::= { f3PtpDynamicRemoteSlaveEntry 8 }

f3PtpDynamicRemoteSlaveSyncMsgRate OBJECT-TYPE
    SYNTAX     SyncMsgRate
    MAX-ACCESS read-only
    STATUS     current
    DESCRIPTION
         "This attribute specifies Sync Message Rate of the Remote Slave."
     ::= { f3PtpDynamicRemoteSlaveEntry 9 }

f3PtpDynamicRemoteSlaveDelayRspMsgRate OBJECT-TYPE
    SYNTAX     DelayRespMsgRate
    MAX-ACCESS read-only
    STATUS     current
    DESCRIPTION
         "This attribute specifies Delay Respone Message Rate of the Remote Slave."
     ::= { f3PtpDynamicRemoteSlaveEntry 10 }

f3PtpDynamicRemoteSlaveAnnounceMsgRate OBJECT-TYPE
    SYNTAX     AnnounceMsgRate
    MAX-ACCESS read-only
    STATUS     current
    DESCRIPTION
         "This attribute specifies Announce Message Rate of the Remote Slave."
     ::= { f3PtpDynamicRemoteSlaveEntry 11 }

f3PtpDynamicRemoteSlaveNegSyncLeaseDur OBJECT-TYPE
    SYNTAX     Integer32
    MAX-ACCESS read-only
    STATUS     current
    DESCRIPTION
         "This attribute indicates Sync messages negotiated Lease Duration in seconds."
     ::= { f3PtpDynamicRemoteSlaveEntry 12 }

f3PtpDynamicRemoteSlaveNegDelayRspLeaseDur OBJECT-TYPE
    SYNTAX     Integer32
    MAX-ACCESS read-only
    STATUS     current
    DESCRIPTION
         "This attribute indicates Delay Response messages negotiated Lease 
          Duration in seconds."
     ::= { f3PtpDynamicRemoteSlaveEntry 13 }

f3PtpDynamicRemoteSlaveNegAnnounceLeaseDur OBJECT-TYPE
    SYNTAX     Integer32
    MAX-ACCESS read-only
    STATUS     current
    DESCRIPTION
         "This attribute indicates Announce messages negotiated Lease 
          Duration in seconds."
     ::= { f3PtpDynamicRemoteSlaveEntry 14 }

f3PtpDynamicRemoteSlaveSyncDurRemTime OBJECT-TYPE
    SYNTAX     Unsigned32
    MAX-ACCESS read-only
    STATUS     current
    DESCRIPTION
         "This attribute indicates Remaining seconds of Lease Duration of Sync service."
     ::= { f3PtpDynamicRemoteSlaveEntry 15 }

f3PtpDynamicRemoteSlaveDelayRspDurRemTime OBJECT-TYPE
    SYNTAX     Unsigned32
    MAX-ACCESS read-only
    STATUS     current
    DESCRIPTION
         "This attribute indicates Remaining seconds of Lease Duration of Delay Response 
          service."
     ::= { f3PtpDynamicRemoteSlaveEntry 16 }

f3PtpDynamicRemoteSlaveAnnounceDurRemTime OBJECT-TYPE
    SYNTAX     Unsigned32
    MAX-ACCESS read-only
    STATUS     current
    DESCRIPTION
         "This attribute indicates Remaining seconds of Lease Duration of Announce 
          service."
     ::= { f3PtpDynamicRemoteSlaveEntry 17 }


f3PtpDynamicRemoteSlaveRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpDynamicRemoteSlaveRowStatus supported is
            destroy(6).  

            The f3PtpDynamicRemoteSlaveRowStatus object may be modified if
            the associated instance of this object is equal to active(1)."
    ::= { f3PtpDynamicRemoteSlaveEntry 18 }


f3PtpDynamicRemoteSlaveStorageType OBJECT-TYPE
    SYNTAX     StorageType
    MAX-ACCESS read-create
    STATUS     current
    DESCRIPTION
            "The type of storage configured for this entry."
    ::= { f3PtpDynamicRemoteSlaveEntry 19 }

--
-- Ethernet Traffic Port - PTP Flow Point Table 
--
f3PtpTrafficPortFlowPointTable OBJECT-TYPE
    SYNTAX     SEQUENCE OF F3PtpTrafficPortFlowPointEntry 
    MAX-ACCESS not-accessible
    STATUS     current
    DESCRIPTION
       "A list of entries corresponding to the PTP Access Port Flow Point
        entities."
    ::= { f3PtpConfigObjects 17}

f3PtpTrafficPortFlowPointEntry OBJECT-TYPE
    SYNTAX     F3PtpTrafficPortFlowPointEntry
    MAX-ACCESS not-accessible
    STATUS     current
    DESCRIPTION
          "An entry containing information applicable to a particular
           Traffic Port Flow Point Entity."
    INDEX { neIndex, shelfIndex, slotIndex, cmEthernetTrafficPortIndex, 
            f3PtpTrafficPortFlowPointIndex }
    ::= { f3PtpTrafficPortFlowPointTable 1 }

F3PtpTrafficPortFlowPointEntry ::= SEQUENCE {
    f3PtpTrafficPortFlowPointIndex                 Integer32,
    f3PtpTrafficPortFlowPointAlias                 DisplayString,

    f3PtpTrafficPortFlowPointAdminState            AdminState,
    f3PtpTrafficPortFlowPointOperationalState      OperationalState,
    f3PtpTrafficPortFlowPointSecondaryState        SecondaryState,

    f3PtpTrafficPortFlowPointType                  PtpFlowPointType,
    f3PtpTrafficPortFlowPointClock                 VariablePointer,
    f3PtpTrafficPortFlowPointService               VariablePointer,
    f3PtpTrafficPortFlowPointOuterVlanEtherType    Integer32,
    f3PtpTrafficPortFlowPointOuterVlanMemberList   DisplayString,
    f3PtpTrafficPortFlowPointOuterUntaggedEnabled  TruthValue,
    f3PtpTrafficPortFlowPointInner1VlanEtherType   Integer32,
    f3PtpTrafficPortFlowPointInner1VlanMemberList  DisplayString,
    f3PtpTrafficPortFlowPointInner1UntaggedEnabled TruthValue,
    f3PtpTrafficPortFlowPointInner2VlanEtherType   Integer32,
    f3PtpTrafficPortFlowPointInner2VlanMemberList  DisplayString,
    f3PtpTrafficPortFlowPointInner2UntaggedEnabled TruthValue,

    f3PtpTrafficPortFlowPointStorageType           StorageType,
    f3PtpTrafficPortFlowPointRowStatus             RowStatus,
    f3PtpTrafficPortFlowPointCOS                   Integer32,
    f3PtpTrafficPortFlowPointCIRLo                 Unsigned32,
    f3PtpTrafficPortFlowPointCIRHi                 Unsigned32,
    f3PtpTrafficPortFlowPointEIRLo                 Unsigned32,
    f3PtpTrafficPortFlowPointEIRHi                 Unsigned32,
    f3PtpTrafficPortFlowPointAssociatedQueueProfile  VariablePointer,
    f3PtpTrafficPortFlowPointLoopAvoidance           VariablePointer
}

f3PtpTrafficPortFlowPointIndex OBJECT-TYPE
    SYNTAX     Integer32
    MAX-ACCESS not-accessible 
    STATUS     current
    DESCRIPTION
         "Unique index value associated with the Traffic Port PTP Flow Point."
     ::= { f3PtpTrafficPortFlowPointEntry 1 }

f3PtpTrafficPortFlowPointAlias OBJECT-TYPE
    SYNTAX      DisplayString (SIZE(0..256))
    MAX-ACCESS  read-create
    STATUS      current
    DESCRIPTION
         "This object allows SNMP management entities to provide an 
          alias to the Traffic Port PTP Flow Point."
     ::= { f3PtpTrafficPortFlowPointEntry 2 }

f3PtpTrafficPortFlowPointAdminState OBJECT-TYPE
    SYNTAX      AdminState 
    MAX-ACCESS  read-write
    STATUS      current
    DESCRIPTION
            "This object represents the Administrative State of the 
             PTP Flow Point." 
     ::= { f3PtpTrafficPortFlowPointEntry 3 }

f3PtpTrafficPortFlowPointOperationalState   OBJECT-TYPE
    SYNTAX      OperationalState 
    MAX-ACCESS  read-only
    STATUS      current
    DESCRIPTION
            "This object represents the Operational State of the PTP Flow 
             Point."
     ::= { f3PtpTrafficPortFlowPointEntry 4 }

f3PtpTrafficPortFlowPointSecondaryState     OBJECT-TYPE
    SYNTAX      SecondaryState 
    MAX-ACCESS  read-only
    STATUS      current
    DESCRIPTION
           "This object represents the Secondary State of the PTP Flow Point."
     ::= { f3PtpTrafficPortFlowPointEntry 5 }

f3PtpTrafficPortFlowPointType OBJECT-TYPE
    SYNTAX      PtpFlowPointType 
    MAX-ACCESS  read-create
    STATUS      current
    DESCRIPTION
            "This object represents the PTP Flow Point Type, i.e. whether
             it is an Transparent Clock or an OC Slave."
    ::= { f3PtpTrafficPortFlowPointEntry 6 }

f3PtpTrafficPortFlowPointClock OBJECT-TYPE
    SYNTAX      VariablePointer 
    MAX-ACCESS  read-only
    STATUS      current
    DESCRIPTION
            "This object points to the Transparent Clock or Slave Only
             Ordinary Clock instance which is associated with this
             PTP Flow Point." 
    ::= { f3PtpTrafficPortFlowPointEntry 7 }

f3PtpTrafficPortFlowPointService OBJECT-TYPE
    SYNTAX      VariablePointer 
    MAX-ACCESS  read-create
    STATUS      current
    DESCRIPTION
            "This object points to the associated Traffic Service Flow."
    ::= { f3PtpTrafficPortFlowPointEntry 8 }

f3PtpTrafficPortFlowPointOuterVlanEtherType OBJECT-TYPE
    SYNTAX      Integer32 
    MAX-ACCESS  read-create
    STATUS      current
    DESCRIPTION
            "This object allows specification of the Outer VLAN Ether Type
             of the PTP Flow."
    ::= { f3PtpTrafficPortFlowPointEntry 9 }

f3PtpTrafficPortFlowPointOuterVlanMemberList OBJECT-TYPE
    SYNTAX      DisplayString 
    MAX-ACCESS  read-create
    STATUS      current
    DESCRIPTION
            "This object allows specification of the Outer VLAN(s) 
             of the PTP Flow."
    ::= { f3PtpTrafficPortFlowPointEntry 10 }

f3PtpTrafficPortFlowPointOuterUntaggedEnabled OBJECT-TYPE
    SYNTAX      TruthValue 
    MAX-ACCESS  read-create
    STATUS      current
    DESCRIPTION
            "This object allows specification of whether the Outer VLAN
             exists or not." 
    ::= { f3PtpTrafficPortFlowPointEntry 11 }

f3PtpTrafficPortFlowPointInner1VlanEtherType OBJECT-TYPE
    SYNTAX      Integer32 
    MAX-ACCESS  read-create
    STATUS      current
    DESCRIPTION
            "This object allows specification of the Inner1 VLAN Ether Type
             of the PTP Flow."
    ::= { f3PtpTrafficPortFlowPointEntry 12 }

f3PtpTrafficPortFlowPointInner1VlanMemberList OBJECT-TYPE
    SYNTAX      DisplayString 
    MAX-ACCESS  read-create
    STATUS      current
    DESCRIPTION
            "This object allows specification of the Inner1 VLAN(s) 
             of the PTP Flow."
    ::= { f3PtpTrafficPortFlowPointEntry 13 }

f3PtpTrafficPortFlowPointInner1UntaggedEnabled OBJECT-TYPE
    SYNTAX      TruthValue 
    MAX-ACCESS  read-create
    STATUS      current
    DESCRIPTION
            "This object allows specification of whether the Inner1 VLAN
             exists or not." 
    ::= { f3PtpTrafficPortFlowPointEntry 14 }

f3PtpTrafficPortFlowPointInner2VlanEtherType OBJECT-TYPE
    SYNTAX      Integer32 
    MAX-ACCESS  read-create
    STATUS      current
    DESCRIPTION
            "This object allows specification of the Inner2 VLAN Ether Type
             of the PTP Flow."
    ::= { f3PtpTrafficPortFlowPointEntry 15 }

f3PtpTrafficPortFlowPointInner2VlanMemberList OBJECT-TYPE
    SYNTAX      DisplayString 
    MAX-ACCESS  read-create
    STATUS      current
    DESCRIPTION
            "This object allows specification of the Inner2 VLAN(s) 
             of the PTP Flow."
    ::= { f3PtpTrafficPortFlowPointEntry 16 }

f3PtpTrafficPortFlowPointInner2UntaggedEnabled OBJECT-TYPE
    SYNTAX      TruthValue 
    MAX-ACCESS  read-create
    STATUS      current
    DESCRIPTION
            "This object allows specification of whether the Inner1 VLAN
             exists or not." 
    ::= { f3PtpTrafficPortFlowPointEntry 17 }

f3PtpTrafficPortFlowPointStorageType OBJECT-TYPE
    SYNTAX     StorageType
    MAX-ACCESS read-create
    STATUS     current
    DESCRIPTION
            "The type of storage configured for this entry."
    ::= { f3PtpTrafficPortFlowPointEntry 18 }

f3PtpTrafficPortFlowPointRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpTrafficPortFlowPointRowStatus supported are
            createAndGo(4) and destroy(6).  All mandatory attributes
            must be specified in a single SNMP SET request with
            f3PtpTrafficPortFlowPointRowStatus value as createAndGo(4).
            Upon successful row creation, this object has a
            value of active(1).

            The f3PtpTrafficPortFlowPointRowStatus object may be modified if
            the associated instance of this object is equal to active(1)."
    ::= { f3PtpTrafficPortFlowPointEntry 19 }


f3PtpTrafficPortFlowPointCOS OBJECT-TYPE
    SYNTAX      Integer32 (0..7)
    MAX-ACCESS  read-create
    STATUS      current
    DESCRIPTION
            "This object allows specification of Class of Service of the PTP traffic
             associated with this Flow Point."
    ::= { f3PtpTrafficPortFlowPointEntry 20 }

f3PtpTrafficPortFlowPointCIRLo OBJECT-TYPE
    SYNTAX      Unsigned32
    MAX-ACCESS  read-create
    STATUS      current
    DESCRIPTION
            "This object allows specification of Committed Information Rate of the 
             PTP traffic associated with this Flow Point.
             The CIR value is in bits-per-second units. The value of this object
             represents the lower 32 bits of the total CIR value."
    ::= { f3PtpTrafficPortFlowPointEntry 21 }

f3PtpTrafficPortFlowPointCIRHi OBJECT-TYPE
    SYNTAX      Unsigned32
    MAX-ACCESS  read-create
    STATUS      current
    DESCRIPTION
            "This object allows specification of Committed Information Rate of the 
             PTP traffic associated with this Flow Point.
             The CIR value is in bits-per-second units. The value of this object
             represents the higher 32 bits of the total CIR value."
    ::= { f3PtpTrafficPortFlowPointEntry 22 }

f3PtpTrafficPortFlowPointEIRLo OBJECT-TYPE
    SYNTAX      Unsigned32
    MAX-ACCESS  read-create
    STATUS      current
    DESCRIPTION
            "This object allows specification of Excess Information Rate of the 
             PTP traffic associated with this Flow Point.
             The EIR value is in bits-per-second units. The value of this object
             represents the lower 32 bits of the total EIR value."
    ::= { f3PtpTrafficPortFlowPointEntry 23 }

f3PtpTrafficPortFlowPointEIRHi OBJECT-TYPE
    SYNTAX      Unsigned32
    MAX-ACCESS  read-create
    STATUS      current
    DESCRIPTION
            "This object allows specification of Excess Information Rate of the 
             PTP traffic associated with this Flow Point.
             The EIR value is in bits-per-second units. The value of this object
             represents the higher 32 bits of the total EIR value."
    ::= { f3PtpTrafficPortFlowPointEntry 24 }

f3PtpTrafficPortFlowPointAssociatedQueueProfile OBJECT-TYPE
    SYNTAX      VariablePointer
    MAX-ACCESS  read-create
    STATUS      current
    DESCRIPTION
            "This object allows specification of the related queue profile."
    ::= { f3PtpTrafficPortFlowPointEntry 25 }

f3PtpTrafficPortFlowPointLoopAvoidance OBJECT-TYPE
    SYNTAX      VariablePointer
    MAX-ACCESS  read-create
    STATUS      current
    DESCRIPTION
            "This object allows specify OID of this associated Loop Avoidance protocol entity."
    ::= { f3PtpTrafficPortFlowPointEntry 26 }

--
-- traffic port ext talbe 
--
f3PtpEthernetTrafficPortExtTable  OBJECT-TYPE
    SYNTAX      SEQUENCE OF F3PtpEthernetTrafficPortExtEntry
    MAX-ACCESS  not-accessible
    STATUS      current
    DESCRIPTION
            "This table extends cmEthernetTrafficPortTable by adding PTP related parameters."
    ::= { f3PtpConfigObjects 18 }

f3PtpEthernetTrafficPortExtEntry OBJECT-TYPE
    SYNTAX      F3PtpEthernetTrafficPortExtEntry
    MAX-ACCESS  not-accessible
    STATUS      current
    DESCRIPTION
            "A conceptual row in the f3PtpEthernetTrafficPortExtTable."
    AUGMENTS { cmEthernetTrafficPortEntry }
    ::= { f3PtpEthernetTrafficPortExtTable 1 }

F3PtpEthernetTrafficPortExtEntry ::= SEQUENCE {
    f3PtpEthernetTrafficPortDelayAsymmetry Integer32
}

f3PtpEthernetTrafficPortDelayAsymmetry OBJECT-TYPE
     SYNTAX     Integer32
     MAX-ACCESS read-write
     STATUS     current
     DESCRIPTION
         "This object allows configuring Delay Asymmetry in nanoseconds on 
          the Ethernet Traffic Port. The default value is 0."
     ::= { f3PtpEthernetTrafficPortExtEntry 1 }

--
-- PTP Clock Table 
-- 

f3PtpPTPClockTable OBJECT-TYPE
    SYNTAX     SEQUENCE OF F3PtpPTPClockEntry
    MAX-ACCESS not-accessible
    STATUS     current
    DESCRIPTION
       "A list of entries corresponding to the PTP PTP Clock entities."
    ::= { f3PtpConfigObjects 19 }

f3PtpPTPClockEntry OBJECT-TYPE
    SYNTAX     F3PtpPTPClockEntry
    MAX-ACCESS not-accessible
    STATUS     current
    DESCRIPTION
          "An entry containing information applicable to a particular
           PTP Clock Entity."
    INDEX { neIndex, f3PtpPTPClockIndex}
            
    ::= { f3PtpPTPClockTable 1 }


F3PtpPTPClockEntry ::= SEQUENCE {
    f3PtpPTPClockIndex                              Integer32,
    f3PtpPTPClockAdminState                         AdminState,           
    f3PtpPTPClockAlias                              DisplayString,
    f3PtpPTPClockOperationalState                   OperationalState,  
    f3PtpPTPClockSecondaryState                     SecondaryState,
    f3PtpPTPClockProfile                            PTPClockProfile,  
    f3PtpPTPClockClockType                          PTPClockType,    
    f3PtpPTPClockOperationalMode                    PTPClockOperMode,  
    f3PtpPTPClockClockIdentity                      ClockIdentity,  
    f3PtpPTPClockDomainNumber                       Integer32, 
    f3PtpPTPClockTimeSource                         VariablePointer,  
    f3PtpPTPClockPriority1                          Unsigned32,                         
    f3PtpPTPClockPriority2                          Unsigned32,  
    f3PtpPTPClockLocalPriority                      Unsigned32,     
    f3PtpPTPClockClockAccuracy                      Unsigned32, 
    f3PtpPTPClockScaledLogVariance                  Integer32, 
    f3PtpPTPClockSyncEid                            VariablePointer,  
    f3PtpPTPClockCurrentTimeOfDay                   DateAndTime,  
    f3PtpPTPClockActiveSlavePort                    VariablePointer, 
    f3PtpPTPClockClockRecoveryState                 ClockRecoveryState, 
    f3PtpPTPClockPhaseRecoveryState                 PhaseRecoveryState, 
    f3PtpPTPClockTimeTraceabilityStatus             TruthValue,   
    f3PtpPTPClockTimeSinceTimeTraceabilityChanged   Unsigned32, 
    f3PtpPTPClockFreqTraceabilityStatus             TruthValue,                           
    f3PtpPTPClockTimeSinceFreqTraceabilityChanged   Unsigned32, 

    f3PtpPTPClockClockSyncEEnabled                  TruthValue,
    f3PtpPTPClockClockQLModeEnabled                 TruthValue,
    f3PtpPTPClockClockExpectedQL                    SSMQualityLevel,
    f3PtpPTPClockClockAssumedQL                     SSMQualityLevel,
    f3PtpPTPClockClockReceivedQL                    SSMQualityLevel,



    f3PtpPTPClockStorageType                        StorageType,
    f3PtpPTPClockRowStatus                          RowStatus

}                  


f3PtpPTPClockIndex OBJECT-TYPE
    SYNTAX     Integer32
    MAX-ACCESS not-accessible 
    STATUS     current
    DESCRIPTION
         "Unique index value associated with the PTP Clock Entity."
     ::= { f3PtpPTPClockEntry 1 }


f3PtpPTPClockAdminState OBJECT-TYPE
    SYNTAX      AdminState 
    MAX-ACCESS  read-write
    STATUS      current
    DESCRIPTION
          "This object represents the Administrative State of the PTP Clock."
    ::= { f3PtpPTPClockEntry 2 }

f3PtpPTPClockAlias    OBJECT-TYPE
    SYNTAX      DisplayString (SIZE(0..256))
    MAX-ACCESS  read-write
    STATUS      current
    DESCRIPTION
         "This object allows SNMP management entities to provide an 
          alias to the PTP Clock entity."
     ::= { f3PtpPTPClockEntry 3 }


f3PtpPTPClockOperationalState   OBJECT-TYPE
    SYNTAX      OperationalState 
    MAX-ACCESS  read-only
    STATUS      current
    DESCRIPTION
          "This object represents the Operational State of the PTP Clock." 
    ::= { f3PtpPTPClockEntry 4 }

f3PtpPTPClockSecondaryState     OBJECT-TYPE
    SYNTAX      SecondaryState 
    MAX-ACCESS  read-only
    STATUS      current
    DESCRIPTION
           "This object represents the Secondary State of the PTP Clock."
    ::= { f3PtpPTPClockEntry 5 }

f3PtpPTPClockProfile     OBJECT-TYPE
    SYNTAX      PTPClockProfile 
    MAX-ACCESS  read-create
    STATUS      current
    DESCRIPTION
           "This object represents the Secondary State of the PTP Clock."
    ::= { f3PtpPTPClockEntry 6 }


f3PtpPTPClockClockType OBJECT-TYPE
    SYNTAX     PTPClockType 
    MAX-ACCESS read-create
    STATUS     current
    DESCRIPTION
         "This object provides the entry from the f3TimeClockTable, which is
          used as frequency and time of day source this Master Clock."
     ::= { f3PtpPTPClockEntry 7 }

f3PtpPTPClockOperationalMode OBJECT-TYPE
    SYNTAX     PTPClockOperMode 
    MAX-ACCESS read-only
    STATUS     current
    DESCRIPTION
         "This object provides the entry from the f3TimeClockTable, which is
          used as frequency and time of day source this Master Clock."
     ::= { f3PtpPTPClockEntry 8 }

f3PtpPTPClockClockIdentity OBJECT-TYPE
    SYNTAX     ClockIdentity 
    MAX-ACCESS read-create
    STATUS     current
    DESCRIPTION
         "This object specifies the Clock Identity of the PTP Clock." 
     ::= { f3PtpPTPClockEntry 9 }

f3PtpPTPClockDomainNumber OBJECT-TYPE
    SYNTAX     Integer32 
    MAX-ACCESS read-create
    STATUS     current
    DESCRIPTION
          "This object allows specification of the PTP domain number of the
           Master Clock ."
     ::= { f3PtpPTPClockEntry 10 }

f3PtpPTPClockTimeSource OBJECT-TYPE
    SYNTAX      VariablePointer
    MAX-ACCESS  read-only
    STATUS      current
    DESCRIPTION
           "This object specify PTP Clock time source."
    ::= { f3PtpPTPClockEntry 11 }
 
f3PtpPTPClockPriority1 OBJECT-TYPE
    SYNTAX     Unsigned32 (0..255) 
    MAX-ACCESS read-write
    STATUS     current
    DESCRIPTION
         ""
     ::= { f3PtpPTPClockEntry 12 }
     
f3PtpPTPClockPriority2 OBJECT-TYPE
    SYNTAX     Unsigned32 (0..255) 
    MAX-ACCESS read-write
    STATUS     current
    DESCRIPTION
         ""
     ::= { f3PtpPTPClockEntry 13 }

f3PtpPTPClockLocalPriority OBJECT-TYPE
    SYNTAX     Unsigned32 (1..255) 
    MAX-ACCESS read-write
    STATUS     current
    DESCRIPTION
        "This object allows configuration of  local priority used by the PTP Clock." 
     ::= { f3PtpPTPClockEntry 14 }

     
f3PtpPTPClockClockAccuracy OBJECT-TYPE
    SYNTAX     Unsigned32 
    MAX-ACCESS read-only
    STATUS     obsolete
    DESCRIPTION
         "This object indicates Clock accuracy of the clock"
     ::= { f3PtpPTPClockEntry 15 }

f3PtpPTPClockScaledLogVariance   OBJECT-TYPE
    SYNTAX      Integer32 
    MAX-ACCESS  read-only
    STATUS      current
    DESCRIPTION
          "" 
    ::= { f3PtpPTPClockEntry 16 }

f3PtpPTPClockSyncEid OBJECT-TYPE
    SYNTAX     VariablePointer 
    MAX-ACCESS read-write
    STATUS     current
    DESCRIPTION
         "This object provides the entry from the f3SyncTable, which is
          used as frequency for this PTP Clock."
     ::= { f3PtpPTPClockEntry 17 }

f3PtpPTPClockCurrentTimeOfDay OBJECT-TYPE
    SYNTAX     DateAndTime 
    MAX-ACCESS read-only
    STATUS     current
    DESCRIPTION
         "This object allows specification of the PTP Clock Current
          Time of Day." 
     ::= { f3PtpPTPClockEntry 18 }

f3PtpPTPClockActiveSlavePort OBJECT-TYPE
    SYNTAX     VariablePointer 
    MAX-ACCESS read-only
    STATUS     current
    DESCRIPTION
         "This object specifies Active Slave Port of the PTP Clock."
     ::= { f3PtpPTPClockEntry 19 }

f3PtpPTPClockClockRecoveryState    OBJECT-TYPE 
    SYNTAX     ClockRecoveryState 
    MAX-ACCESS read-only
    STATUS     current
    DESCRIPTION
         "This object provides the TPTP Clock's clock recovery state." 
     ::= { f3PtpPTPClockEntry 20 }

f3PtpPTPClockPhaseRecoveryState OBJECT-TYPE
    SYNTAX      PhaseRecoveryState
    MAX-ACCESS  read-only
    STATUS      current
    DESCRIPTION
           "This object specify the phase recovery state."
    ::= { f3PtpPTPClockEntry 21 }
    
f3PtpPTPClockTimeTraceabilityStatus OBJECT-TYPE
    SYNTAX      TruthValue
    MAX-ACCESS  read-only
    STATUS      current
    DESCRIPTION
           "This object provides the Time traceability status of the
            PTP Clock."
    ::= { f3PtpPTPClockEntry 22 }


f3PtpPTPClockTimeSinceTimeTraceabilityChanged OBJECT-TYPE
    SYNTAX      Unsigned32
    MAX-ACCESS  read-only
    STATUS      current
    DESCRIPTION
           "This object provides the time in seconds since the Time traceability 
            changed on the PTP Clock."
    ::= { f3PtpPTPClockEntry 23 }

f3PtpPTPClockFreqTraceabilityStatus OBJECT-TYPE
    SYNTAX      TruthValue
    MAX-ACCESS  read-only
    STATUS      current
    DESCRIPTION
           "This object provides the Frequency traceability status of the
            PTP Clock."
    ::= { f3PtpPTPClockEntry 24 }

f3PtpPTPClockTimeSinceFreqTraceabilityChanged OBJECT-TYPE
    SYNTAX      Unsigned32
    MAX-ACCESS  read-only
    STATUS      current
    DESCRIPTION
           "This object provides the time in seconds since the Frequency traceability 
            changed on the PTP Clock."
    ::= { f3PtpPTPClockEntry 25 }
    
--Synchronous Port params
f3PtpPTPClockClockSyncEEnabled OBJECT-TYPE 
    SYNTAX     TruthValue
    MAX-ACCESS read-write
    STATUS     current
    DESCRIPTION
         "This object allows to specify whether the Telecom Slave 
          can be enabled/disabled for Synchronous Ethernet. 
          When enabled, on receive side 
            -telecom slave can extract the frequency 
             and pass the recovered clock to the system clock
            -QL is extracted (when QL is enabled) from the selected SOOC's clock class
            -telecom slave is eligible to be selected as a system clock reference
          When disabled, on receive side,
            -telecom slave does not pass the recovered clock to the system clock 
            -telecom slave does not process the QL from selected SOOC's clock class 
            -telecom slave is not eligible to be selected as a 
                     system clock reference."
     ::= { f3PtpPTPClockEntry 26 }

f3PtpPTPClockClockQLModeEnabled OBJECT-TYPE 
    SYNTAX     TruthValue
    MAX-ACCESS read-write
    STATUS     current
    DESCRIPTION
         "This object allows to specify whether the Telecom Slave 
          can be enabled/disabled for QL Mode.  
          When enabled, on receive side 
            -telecom slave can extract the QL from selected SOOC's clock class 
          When disabled, on receive side,
            -telecom slave does not process the QL from selected SOOC's clock class."
     ::= { f3PtpPTPClockEntry 27 }

f3PtpPTPClockClockExpectedQL OBJECT-TYPE 
    SYNTAX     SSMQualityLevel
    MAX-ACCESS read-write
    STATUS     current
    DESCRIPTION
         "This object allows to specify the expected QL when the 
          Telecom Slave is enabled for QL Mode.  This is applicable 
          when f3PtpPTPClockClockQLModeEnabled is set to true.
          This object allows the user to set a minimum
          expected received Quality Level on the Telecom Slave. 
          The valid values depend upon the SYNC entity's Network Clock Type. 
          A value of None represents that a minimum Quality Level is not expected. 
          The default value shall be None."
     ::= { f3PtpPTPClockEntry 28 }

f3PtpPTPClockClockAssumedQL OBJECT-TYPE 
    SYNTAX     SSMQualityLevel
    MAX-ACCESS read-write
    STATUS     current
    DESCRIPTION
         "This object allows to specify the assumed QL on the 
          Telecom Slave.  The Assumed QL is only meaningful if the Network Clock Type
          (see fsp150cm-sync.mib) is option1 and the 
          telecom slave's QL Mode is disabled and the telecom slave is being used as 
          an input reference source. Under these conditions,
          the specified QL value is assumed to be the Quality Level of the
          non-failed reference."
     ::= { f3PtpPTPClockEntry 29 }

f3PtpPTPClockClockReceivedQL OBJECT-TYPE 
    SYNTAX     SSMQualityLevel
    MAX-ACCESS read-only
    STATUS     current
    DESCRIPTION
         "This object provides the Received QL value for the Telecom Slave. 
          If the Telecom Slave's QL Mode is disabled, then the received 
          QL value is not applicable."
     ::= { f3PtpPTPClockEntry 30 }


f3PtpPTPClockStorageType OBJECT-TYPE
    SYNTAX     StorageType
    MAX-ACCESS read-create
    STATUS     current
    DESCRIPTION
            "The type of storage configured for this entry."
    ::= { f3PtpPTPClockEntry 31 }

f3PtpPTPClockRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpPTPClockRowStatus supported are
            createAndGo(4) and destroy(6).  All mandatory attributes
            must be specified in a single SNMP SET request with
            f3PtpPTPClockRowStatus value as createAndGo(4).
            Upon successful row creation, this object has a
            value of active(1).

            The f3PtpPTPClockRowStatus object may be modified if
            the associated instance of this object is equal to active(1)."
    ::= { f3PtpPTPClockEntry 32 }
     
     
--
-- PTP Port Table 
-- 

f3PtpPTPPortTable OBJECT-TYPE
    SYNTAX     SEQUENCE OF F3PtpPTPPortEntry
    MAX-ACCESS not-accessible
    STATUS     current
    DESCRIPTION
       "A list of entries corresponding to the PTP PTP Port entities."
    ::= { f3PtpConfigObjects 20 }

f3PtpPTPPortEntry OBJECT-TYPE
    SYNTAX     F3PtpPTPPortEntry
    MAX-ACCESS not-accessible
    STATUS     current
    DESCRIPTION
          "An entry containing information applicable to a particular
           PTP Port Entity."
    INDEX { neIndex, f3PtpPTPClockIndex,f3PtpPTPPortIndex}
            
    ::= { f3PtpPTPPortTable 1 }


F3PtpPTPPortEntry ::= SEQUENCE {
    f3PtpPTPPortIndex                              Integer32,
    f3PtpPTPPortAdminState                         AdminState,
    f3PtpPTPPortAlias                              DisplayString,          
    f3PtpPTPPortOperationalState                   OperationalState,  
    f3PtpPTPPortSecondaryState                     SecondaryState,
    f3PtpPTPPortPeerPortIdentity                   PortIdentity,
    f3PtpPTPPortLocalPriority                      Unsigned32,     
    f3PtpPTPPortPtpFlowPointEid                    VariablePointer,   
    f3PtpPTPPortNotSlave                           TruthValue,   
    f3PtpPTPPortTxDestMacAddress                   DestMacAddrType,   
    f3PtpPTPPortSyncMessageRate                    SyncMessageRate,   
    f3PtpPTPPortmDelayReqRespMsgRate               DelayReqMessageRate,
    f3PtpPTPPortmAnnounceMsgRate                   AnnounceMessageRate,
    f3PtpPTPPortAnnounceReceiptTimeout             Integer32,                            
    f3PtpPTPPortSyncReceiptTimeout                 Integer32,                            
    f3PtpPTPPortDelayRespTimeout                   Integer32,  
    f3PtpPTPPortPortState                          PtpPortState,
    f3PtpPTPPortBmcaDecisionCode                   BMCARole, 
    f3PtpPTPPortClockClass                         Unsigned32, 
    f3PtpPTPPortPeerPortMacAddress                 MacAddress,
    f3PtpPTPPortRowStatus                          RowStatus,
    f3PtpPTPPortPortIdentity                       PortIdentity

      
       

}                  


f3PtpPTPPortIndex OBJECT-TYPE
    SYNTAX     Integer32
    MAX-ACCESS not-accessible 
    STATUS     current
    DESCRIPTION
         "Unique index value associated with the PTP Port Entity."
     ::= { f3PtpPTPPortEntry 1 }



f3PtpPTPPortAdminState OBJECT-TYPE
    SYNTAX      AdminState 
    MAX-ACCESS  read-write
    STATUS      current
    DESCRIPTION
          "This object represents the Administrative State of the PTP Port."
    ::= { f3PtpPTPPortEntry 2 }

f3PtpPTPPortAlias    OBJECT-TYPE
    SYNTAX      DisplayString (SIZE(0..256))
    MAX-ACCESS  read-write
    STATUS      current
    DESCRIPTION
         "This object allows SNMP management entities to provide an 
          alias to the PTP Port entity."
     ::= { f3PtpPTPPortEntry 3 }


f3PtpPTPPortOperationalState   OBJECT-TYPE
    SYNTAX      OperationalState 
    MAX-ACCESS  read-only
    STATUS      current
    DESCRIPTION
          "This object represents the Operational State of the PTP Port." 
    ::= { f3PtpPTPPortEntry 4 }

f3PtpPTPPortSecondaryState     OBJECT-TYPE
    SYNTAX      SecondaryState 
    MAX-ACCESS  read-only
    STATUS      current
    DESCRIPTION
           "This object represents the Secondary State of the PTP Port."
    ::= { f3PtpPTPPortEntry 5 }
                                 
f3PtpPTPPortPeerPortIdentity OBJECT-TYPE
    SYNTAX     PortIdentity 
    MAX-ACCESS read-only
    STATUS     current
    DESCRIPTION
         "This object specifies the Peer Port Identity of the PTP Port." 
     ::= { f3PtpPTPPortEntry 6 }
                                 
f3PtpPTPPortLocalPriority OBJECT-TYPE
    SYNTAX     Unsigned32 (1..255) 
    MAX-ACCESS read-write
    STATUS     current
    DESCRIPTION
        "This object allows configuration of  local priority used by the PTP Port." 
     ::= { f3PtpPTPPortEntry 7 }

f3PtpPTPPortPtpFlowPointEid OBJECT-TYPE
    SYNTAX     VariablePointer 
    MAX-ACCESS read-create
    STATUS     current
    DESCRIPTION
         "This object associates the PTP Flow Point Eid."
     ::= { f3PtpPTPPortEntry 8 }
                                 
f3PtpPTPPortNotSlave OBJECT-TYPE
    SYNTAX      TruthValue
    MAX-ACCESS  read-only
    STATUS      current
    DESCRIPTION
           "This object indicate if PTP Port is slave."
    ::= { f3PtpPTPPortEntry 9 }

f3PtpPTPPortTxDestMacAddress OBJECT-TYPE
    SYNTAX     DestMacAddrType 
    MAX-ACCESS read-create
    STATUS     current
    DESCRIPTION
         "This object specifies the Mac address of the PTP Port." 
     ::= { f3PtpPTPPortEntry 10 }
                                 
f3PtpPTPPortSyncMessageRate OBJECT-TYPE
    SYNTAX     SyncMessageRate
    MAX-ACCESS read-create
    STATUS     current
    DESCRIPTION
        "This object allows specification of the PTP Port Sync 
         Message Rate." 
     ::= { f3PtpPTPPortEntry 11 }
                                 
f3PtpPTPPortmDelayReqRespMsgRate OBJECT-TYPE
    SYNTAX     DelayReqMessageRate
    MAX-ACCESS read-create
    STATUS     current
    DESCRIPTION
        "This object allows specification of the PTP Port Delay Response 
         Message Rate." 
     ::= { f3PtpPTPPortEntry 12 }
                                 
f3PtpPTPPortmAnnounceMsgRate OBJECT-TYPE
    SYNTAX     AnnounceMessageRate
    MAX-ACCESS read-create
    STATUS     current
    DESCRIPTION
         "This object allows specification of the PTP Port Announce Message Rate."
     ::= { f3PtpPTPPortEntry 13 }
                   
f3PtpPTPPortAnnounceReceiptTimeout OBJECT-TYPE
    SYNTAX     Integer32
    MAX-ACCESS read-write
    STATUS     current
    DESCRIPTION
        "This object allows specification of the PTP Port Announce Message 
         Receipt Timeout."
     ::= { f3PtpPTPPortEntry 14 }

f3PtpPTPPortSyncReceiptTimeout OBJECT-TYPE
    SYNTAX     Integer32
    MAX-ACCESS read-write
    STATUS     current
    DESCRIPTION
        "This object allows specification of the PTP Port Sync Message 
         Receipt Timeout."
     ::= { f3PtpPTPPortEntry 15 }

f3PtpPTPPortDelayRespTimeout OBJECT-TYPE
    SYNTAX     Integer32
    MAX-ACCESS read-write
    STATUS     current
    DESCRIPTION
        "This object allows specification of the PTP Port Delay Response 
         Message Receipt Timeout."
     ::= { f3PtpPTPPortEntry 16 }

f3PtpPTPPortPortState OBJECT-TYPE
    SYNTAX     PtpPortState 
    MAX-ACCESS read-only
    STATUS     current
    DESCRIPTION
         "This object provides the PTP Port state." 
     ::= { f3PtpPTPPortEntry 17 }
                          
f3PtpPTPPortBmcaDecisionCode OBJECT-TYPE
    SYNTAX     BMCARole 
    MAX-ACCESS read-only
    STATUS     current
    DESCRIPTION
         "This object provides the PTP Port BMCA Role" 
     ::= { f3PtpPTPPortEntry 18 }
                          
f3PtpPTPPortClockClass OBJECT-TYPE
    SYNTAX      Unsigned32
    MAX-ACCESS  read-only
    STATUS      current
    DESCRIPTION
           "This object specify PTP Port class."
     ::= { f3PtpPTPPortEntry 19 }
                          
f3PtpPTPPortPeerPortMacAddress OBJECT-TYPE
    SYNTAX      MacAddress 
    MAX-ACCESS  read-only
    STATUS      current
    DESCRIPTION
        "This attribute description PTP Port Mac Address."
    ::= { f3PtpPTPPortEntry 20 }

f3PtpPTPPortRowStatus OBJECT-TYPE
    SYNTAX      RowStatus
    MAX-ACCESS  read-create
    STATUS      current
    DESCRIPTION
           "The status of this row.  An entry MUST NOT exist in the 
            active state unless all objects in the entry have an 
            appropriate value, as described
            in the description clause for each writable object.

            The values of f3PtpPTPPortRowStatus supported are
            createAndGo(4) and destroy(6).  All mandatory attributes
            must be specified in a single SNMP SET request with
            f3PtpPTPPortRowStatus value as createAndGo(4).
            Upon successful row creation, this object has a
            value of active(1).

            The f3PtpPTPPortRowStatus object may be modified if
            the associated instance of this object is equal to active(1)."
    ::= { f3PtpPTPPortEntry 21 }
 
f3PtpPTPPortPortIdentity OBJECT-TYPE
   SYNTAX     PortIdentity 
   MAX-ACCESS read-only
   STATUS     current
   DESCRIPTION
        "This object specifies the Port Identity of the PTP Port." 
    ::= { f3PtpPTPPortEntry 22 }



--
-- PERFORMANCE 
--

--
-- Access Port PTP Flow Point Current Statistics Table
--
f3PtpAccPortFlowPointStatsTable OBJECT-TYPE
    SYNTAX      SEQUENCE OF F3PtpAccPortFlowPointStatsEntry
    MAX-ACCESS  not-accessible
    STATUS      current
    DESCRIPTION
            "A collection of Access Port PTP Flow Point statistics.  
             These reflect the current data."
    ::= { f3PtpPerformanceObjects 1 }

f3PtpAccPortFlowPointStatsEntry OBJECT-TYPE
    SYNTAX      F3PtpAccPortFlowPointStatsEntry 
    MAX-ACCESS  not-accessible
    STATUS      current
    DESCRIPTION
            "A conceptual row in the f3PtpAccPortFlowPointStatsTable.
             Entries exist in this table for each Access Port Flow Point."
    INDEX { neIndex, shelfIndex, slotIndex, cmEthernetAccPortIndex, 
            f3PtpAccPortFlowPointIndex, f3PtpAccPortFlowPointStatsIndex }
    ::= { f3PtpAccPortFlowPointStatsTable 1 }

F3PtpAccPortFlowPointStatsEntry ::= SEQUENCE {
    f3PtpAccPortFlowPointStatsIndex                  Integer32,
    f3PtpAccPortFlowPointStatsIntervalType           CmPmIntervalType,
    f3PtpAccPortFlowPointStatsValid                  TruthValue,
    f3PtpAccPortFlowPointStatsAction                 CmPmBinAction,
    f3PtpAccPortFlowPointStatsAnnouncesRx            PerfCounter64,
    f3PtpAccPortFlowPointStatsAnnouncesTx            PerfCounter64,
    f3PtpAccPortFlowPointStatsSyncsRx                PerfCounter64,
    f3PtpAccPortFlowPointStatsSyncsTx                PerfCounter64,
    f3PtpAccPortFlowPointStatsFollowupsRx            PerfCounter64,
    f3PtpAccPortFlowPointStatsFollowupsTx            PerfCounter64,
    f3PtpAccPortFlowPointStatsDelayReqsRx            PerfCounter64,
    f3PtpAccPortFlowPointStatsDelayReqsTx            PerfCounter64,
    f3PtpAccPortFlowPointStatsDelayRspsRx            PerfCounter64,
    f3PtpAccPortFlowPointStatsDelayRspsTx            PerfCounter64,
    f3PtpAccPortFlowPointStatsPDelayReqsRx           PerfCounter64,
    f3PtpAccPortFlowPointStatsPDelayReqsTx           PerfCounter64,
    f3PtpAccPortFlowPointStatsPDelayRspsRx           PerfCounter64,
    f3PtpAccPortFlowPointStatsPDelayRspsTx           PerfCounter64,
    f3PtpAccPortFlowPointStatsPDelayRspFollowupsRx   PerfCounter64,
    f3PtpAccPortFlowPointStatsPDelayRspFollowupsTx   PerfCounter64,
    f3PtpAccPortFlowPointStatsSignalingRx            PerfCounter64,
    f3PtpAccPortFlowPointStatsSignalingTx            PerfCounter64,
    f3PtpAccPortFlowPointStatsMgmtFramesRx           PerfCounter64,
    f3PtpAccPortFlowPointStatsMgmtFramesTx           PerfCounter64,
    f3PtpAccPortFlowPointStatsPtpUnknownsRx          PerfCounter64,
    f3PtpAccPortFlowPointStatsPtpUnknownsTx          PerfCounter64,
    f3PtpAccPortFlowPointStatsMinSyncResTime         Unsigned32,
    f3PtpAccPortFlowPointStatsMaxSyncResTime         Unsigned32,
    f3PtpAccPortFlowPointStatsAvgSyncResTime         Unsigned32,
    f3PtpAccPortFlowPointStatsMinDelayReqResTime     Unsigned32,
    f3PtpAccPortFlowPointStatsMaxDelayReqResTime     Unsigned32,
    f3PtpAccPortFlowPointStatsAvgDelayReqResTime     Unsigned32,
    f3PtpAccPortFlowPointStatsMinPDelayReqResTime    Unsigned32,
    f3PtpAccPortFlowPointStatsMaxPDelayReqResTime    Unsigned32,
    f3PtpAccPortFlowPointStatsAvgPDelayReqResTime    Unsigned32,
    f3PtpAccPortFlowPointStatsMinPDelayRspResTime    Unsigned32,
    f3PtpAccPortFlowPointStatsMaxPDelayRspResTime    Unsigned32,
    f3PtpAccPortFlowPointStatsAvgPDelayRspResTime    Unsigned32,
    f3PtpAccPortFlowPointStatsDestMciNoMatchDiscards PerfCounter64
}

f3PtpAccPortFlowPointStatsIndex OBJECT-TYPE
    SYNTAX      Integer32 (1..4)
    MAX-ACCESS  not-accessible 
    STATUS      current
    DESCRIPTION
            "An arbitrary integer index value used to uniquely identify
            this Access Port PTP Flow Point statistics entry. 
            1 - 15min
            2 - 1day
            3 - rollover
            4 - 5min"
    ::= { f3PtpAccPortFlowPointStatsEntry 1 }

f3PtpAccPortFlowPointStatsIntervalType OBJECT-TYPE
    SYNTAX      CmPmIntervalType
    MAX-ACCESS  read-only
    STATUS      current
    DESCRIPTION
            "Indicates the type of collection, i.e. whether it is
             15 Min, 1 Day or rollover."
    ::= { f3PtpAccPortFlowPointStatsEntry 2 }

f3PtpAccPortFlowPointStatsValid OBJECT-TYPE
    SYNTAX      TruthValue
    MAX-ACCESS  read-only
    STATUS      current
    DESCRIPTION
            "Indicates the validity of the bin."
    ::= { f3PtpAccPortFlowPointStatsEntry 3 }

f3PtpAccPortFlowPointStatsAction OBJECT-TYPE
    SYNTAX      CmPmBinAction
    MAX-ACCESS  read-write
    STATUS      current
    DESCRIPTION
            "Allows the Manager to clear the bin."
    ::= { f3PtpAccPortFlowPointStatsEntry 4 }

f3PtpAccPortFlowPointStatsAnnouncesRx OBJECT-TYPE
     SYNTAX     PerfCounter64
     MAX-ACCESS read-only
     STATUS     current
     DESCRIPTION
         "Number of PTP Announce messages received on the PTP Flow Point."
     ::= { f3PtpAccPortFlowPointStatsEntry 5 }

f3PtpAccPortFlowPointStatsAnnouncesTx OBJECT-TYPE
     SYNTAX     PerfCounter64
     MAX-ACCESS read-only
     STATUS     current
     DESCRIPTION
         "Number of Announce Messages transmitted on the PTP Flow Point.
          This object is applicable for transparent clocks."
     ::= { f3PtpAccPortFlowPointStatsEntry 6 }

f3PtpAccPortFlowPointStatsSyncsRx OBJECT-TYPE
     SYNTAX     PerfCounter64
     MAX-ACCESS read-only
     STATUS     current
     DESCRIPTION
         "Number of Sync Messages received on the PTP Flow Point."
     ::= { f3PtpAccPortFlowPointStatsEntry 7 }

f3PtpAccPortFlowPointStatsSyncsTx OBJECT-TYPE
     SYNTAX     PerfCounter64
     MAX-ACCESS read-only
     STATUS     current
     DESCRIPTION
         "Number of Sync Messages transmitted on the PTP Flow Point.
          This object is applicable for transparent clocks."
     ::= { f3PtpAccPortFlowPointStatsEntry 8 }

f3PtpAccPortFlowPointStatsFollowupsRx OBJECT-TYPE
     SYNTAX     PerfCounter64
     MAX-ACCESS read-only
     STATUS     current
     DESCRIPTION
         "Number of Follow up Messages received on the PTP Flow Point."
     ::= { f3PtpAccPortFlowPointStatsEntry 9 }

f3PtpAccPortFlowPointStatsFollowupsTx OBJECT-TYPE
     SYNTAX     PerfCounter64
     MAX-ACCESS read-only
     STATUS     current
     DESCRIPTION
         "Number of Follow up Messages transmitted on the PTP Flow Point."
     ::= { f3PtpAccPortFlowPointStatsEntry 10 }

f3PtpAccPortFlowPointStatsDelayReqsRx OBJECT-TYPE
     SYNTAX     PerfCounter64
     MAX-ACCESS read-only
     STATUS     current
     DESCRIPTION
         "Number of Delay Request Messages received on the PTP Flow Point."
     ::= { f3PtpAccPortFlowPointStatsEntry 11 }

f3PtpAccPortFlowPointStatsDelayReqsTx OBJECT-TYPE
     SYNTAX     PerfCounter64
     MAX-ACCESS read-only
     STATUS     current
     DESCRIPTION
         "Number of Delay Request Messages transmitted on the PTP Flow Point."
     ::= { f3PtpAccPortFlowPointStatsEntry 12 }

f3PtpAccPortFlowPointStatsDelayRspsRx OBJECT-TYPE
     SYNTAX     PerfCounter64
     MAX-ACCESS read-only
     STATUS     current
     DESCRIPTION
         "Number of Delay Response Messages received on the PTP Flow Point."
     ::= { f3PtpAccPortFlowPointStatsEntry 13 }

f3PtpAccPortFlowPointStatsDelayRspsTx OBJECT-TYPE
     SYNTAX     PerfCounter64
     MAX-ACCESS read-only
     STATUS     current
     DESCRIPTION
         "Number of Delay Response Messages transmitted on the PTP Flow Point."
     ::= { f3PtpAccPortFlowPointStatsEntry 14 }

f3PtpAccPortFlowPointStatsPDelayReqsRx OBJECT-TYPE
     SYNTAX     PerfCounter64
     MAX-ACCESS read-only
     STATUS     current
     DESCRIPTION
         "Number of Peer Delay Request Messages received on the PTP Flow Point."
     ::= { f3PtpAccPortFlowPointStatsEntry 15 }

f3PtpAccPortFlowPointStatsPDelayReqsTx OBJECT-TYPE
     SYNTAX     PerfCounter64
     MAX-ACCESS read-only
     STATUS     current
     DESCRIPTION
         "Number of Peer Delay Request Messages transmitted on the PTP Flow Point."
     ::= { f3PtpAccPortFlowPointStatsEntry 16 }

f3PtpAccPortFlowPointStatsPDelayRspsRx OBJECT-TYPE
     SYNTAX     PerfCounter64
     MAX-ACCESS read-only
     STATUS     current
     DESCRIPTION
         "Number of Peer Delay Response Messages received on the PTP Flow Point."
     ::= { f3PtpAccPortFlowPointStatsEntry 17 }

f3PtpAccPortFlowPointStatsPDelayRspsTx OBJECT-TYPE
     SYNTAX     PerfCounter64
     MAX-ACCESS read-only
     STATUS     current
     DESCRIPTION
         "Number of Peer Delay Response Messages transmitted on the PTP Flow Point."
     ::= { f3PtpAccPortFlowPointStatsEntry 18 }

f3PtpAccPortFlowPointStatsPDelayRspFollowupsRx OBJECT-TYPE
     SYNTAX     PerfCounter64
     MAX-ACCESS read-only
     STATUS     current
     DESCRIPTION
         "Number of Peer Delay Response Followup Messages received on the PTP Flow Point."
     ::= { f3PtpAccPortFlowPointStatsEntry 19 }

f3PtpAccPortFlowPointStatsPDelayRspFollowupsTx OBJECT-TYPE
     SYNTAX     PerfCounter64
     MAX-ACCESS read-only
     STATUS     current
     DESCRIPTION
         "Number of Peer Delay Response Followup Messages transmitted on the PTP Flow Point."
     ::= { f3PtpAccPortFlowPointStatsEntry 20 }

f3PtpAccPortFlowPointStatsSignalingRx OBJECT-TYPE
     SYNTAX     PerfCounter64
     MAX-ACCESS read-only
     STATUS     current
     DESCRIPTION
         "Number of PTP Signaling Messages received on the PTP Flow Point."
     ::= { f3PtpAccPortFlowPointStatsEntry 21 }

f3PtpAccPortFlowPointStatsSignalingTx OBJECT-TYPE
     SYNTAX     PerfCounter64
     MAX-ACCESS read-only
     STATUS     current
     DESCRIPTION
         "Number of PTP Signaling Messages Messages transmitted on the PTP Flow Point."
     ::= { f3PtpAccPortFlowPointStatsEntry 22 }

f3PtpAccPortFlowPointStatsMgmtFramesRx OBJECT-TYPE
     SYNTAX     PerfCounter64
     MAX-ACCESS read-only
     STATUS     current
     DESCRIPTION
         "Number of PTP Management Frames received on the PTP Flow Point."
     ::= { f3PtpAccPortFlowPointStatsEntry 23 }

f3PtpAccPortFlowPointStatsMgmtFramesTx OBJECT-TYPE
     SYNTAX     PerfCounter64
     MAX-ACCESS read-only
     STATUS     current
     DESCRIPTION
         "Number of PTP Management Frames Messages transmitted on the PTP Flow Point."
     ::= { f3PtpAccPortFlowPointStatsEntry 24 }

f3PtpAccPortFlowPointStatsPtpUnknownsRx OBJECT-TYPE
     SYNTAX     PerfCounter64
     MAX-ACCESS read-only
     STATUS     current
     DESCRIPTION
         "Number of Unknown PTP Messages received on the PTP Flow Point."
     ::= { f3PtpAccPortFlowPointStatsEntry 25 }

f3PtpAccPortFlowPointStatsPtpUnknownsTx OBJECT-TYPE
     SYNTAX     PerfCounter64
     MAX-ACCESS read-only
     STATUS     current
     DESCRIPTION
         "Number of Unknown PTP Messages transmitted on the PTP Flow Point."
     ::= { f3PtpAccPortFlowPointStatsEntry 26 }

f3PtpAccPortFlowPointStatsMinSyncResTime OBJECT-TYPE
     SYNTAX     Unsigned32
     MAX-ACCESS read-only
     STATUS     current
     DESCRIPTION
         "The minimum residence time for PTP Sync messages."
     ::= { f3PtpAccPortFlowPointStatsEntry 27 }

f3PtpAccPortFlowPointStatsMaxSyncResTime OBJECT-TYPE
     SYNTAX     Unsigned32
     MAX-ACCESS read-only
     STATUS     current
     DESCRIPTION
         "The maximum residence time for PTP Sync messages."
     ::= { f3PtpAccPortFlowPointStatsEntry 28 }

f3PtpAccPortFlowPointStatsAvgSyncResTime OBJECT-TYPE
     SYNTAX     Unsigned32
     MAX-ACCESS read-only
     STATUS     current
     DESCRIPTION
         "The average residence time for PTP Sync messages."
     ::= { f3PtpAccPortFlowPointStatsEntry 29 }

f3PtpAccPortFlowPointStatsMinDelayReqResTime OBJECT-TYPE
     SYNTAX     Unsigned32
     MAX-ACCESS read-only
     STATUS     current
     DESCRIPTION
         "The minimum residence time for PTP Delay Request messages."
     ::= { f3PtpAccPortFlowPointStatsEntry 30 }

f3PtpAccPortFlowPointStatsMaxDelayReqResTime OBJECT-TYPE
     SYNTAX     Unsigned32
     MAX-ACCESS read-only
     STATUS     current
     DESCRIPTION
         "The maximum residence time for PTP Delay Request messages."
     ::= { f3PtpAccPortFlowPointStatsEntry 31 }

f3PtpAccPortFlowPointStatsAvgDelayReqResTime OBJECT-TYPE
     SYNTAX     Unsigned32
     MAX-ACCESS read-only
     STATUS     current
     DESCRIPTION
         "The average residence time for PTP Delay Request messages."
     ::= { f3PtpAccPortFlowPointStatsEntry 32 }

f3PtpAccPortFlowPointStatsMinPDelayReqResTime OBJECT-TYPE
     SYNTAX     Unsigned32
     MAX-ACCESS read-only
     STATUS     current
     DESCRIPTION
         "The minimum residence time for PTP Peer Delay Request messages."
     ::= { f3PtpAccPortFlowPointStatsEntry 33 }

f3PtpAccPortFlowPointStatsMaxPDelayReqResTime OBJECT-TYPE
     SYNTAX     Unsigned32
     MAX-ACCESS read-only
     STATUS     current
     DESCRIPTION
         "The maximum residence time for PTP Peer Delay Request messages."
     ::= { f3PtpAccPortFlowPointStatsEntry 34 }

f3PtpAccPortFlowPointStatsAvgPDelayReqResTime OBJECT-TYPE
     SYNTAX     Unsigned32
     MAX-ACCESS read-only
     STATUS     current
     DESCRIPTION
         "The average residence time for PTP Peer Delay Request messages."
     ::= { f3PtpAccPortFlowPointStatsEntry 35 }

f3PtpAccPortFlowPointStatsMinPDelayRspResTime OBJECT-TYPE
     SYNTAX     Unsigned32
     MAX-ACCESS read-only
     STATUS     current
     DESCRIPTION
         "The minimum residence time for PTP Peer Delay Response messages."
     ::= { f3PtpAccPortFlowPointStatsEntry 36 }

f3PtpAccPortFlowPointStatsMaxPDelayRspResTime OBJECT-TYPE
     SYNTAX     Unsigned32
     MAX-ACCESS read-only
     STATUS     current
     DESCRIPTION
         "The maximum residence time for PTP Peer Delay Response messages."
     ::= { f3PtpAccPortFlowPointStatsEntry 37 }

f3PtpAccPortFlowPointStatsAvgPDelayRspResTime OBJECT-TYPE
     SYNTAX     Unsigned32
     MAX-ACCESS read-only
     STATUS     current
     DESCRIPTION
         "The average residence time for PTP Peer Delay Response messages."
     ::= { f3PtpAccPortFlowPointStatsEntry 38 }

f3PtpAccPortFlowPointStatsDestMciNoMatchDiscards OBJECT-TYPE
     SYNTAX     PerfCounter64
     MAX-ACCESS read-write
     STATUS     current
     DESCRIPTION
         "The dest MCI no match discards messages."
     ::= { f3PtpAccPortFlowPointStatsEntry 39 }

--
-- Access Port PTP Flow Point History Table
--
f3PtpAccPortFlowPointHistoryTable OBJECT-TYPE
    SYNTAX      SEQUENCE OF F3PtpAccPortFlowPointHistoryEntry
    MAX-ACCESS  not-accessible
    STATUS      current
    DESCRIPTION
            "A collection of Access Port PTP Flow Point history statistics.  
             These reflect the history data."
    ::= { f3PtpPerformanceObjects 2 }

f3PtpAccPortFlowPointHistoryEntry OBJECT-TYPE
    SYNTAX      F3PtpAccPortFlowPointHistoryEntry 
    MAX-ACCESS  not-accessible
    STATUS      current
    DESCRIPTION
            "A conceptual row in the f3PtpAccPortFlowPointHistoryTable.
             Entries exist in this table for each Access Port Flow Point."
    INDEX { neIndex, shelfIndex, slotIndex, cmEthernetAccPortIndex, 
            f3PtpAccPortFlowPointIndex, f3PtpAccPortFlowPointStatsIndex, 
            f3PtpAccPortFlowPointHistoryIndex }
    ::= { f3PtpAccPortFlowPointHistoryTable 1 }

F3PtpAccPortFlowPointHistoryEntry ::= SEQUENCE {
    f3PtpAccPortFlowPointHistoryIndex                  Integer32,
    f3PtpAccPortFlowPointHistoryTime                   DateAndTime,
    f3PtpAccPortFlowPointHistoryValid                  TruthValue,
    f3PtpAccPortFlowPointHistoryAction                 CmPmBinAction,
    f3PtpAccPortFlowPointHistoryAnnouncesRx            PerfCounter64,
    f3PtpAccPortFlowPointHistoryAnnouncesTx            PerfCounter64,
    f3PtpAccPortFlowPointHistorySyncsRx                PerfCounter64,
    f3PtpAccPortFlowPointHistorySyncsTx                PerfCounter64,
    f3PtpAccPortFlowPointHistoryFollowupsRx            PerfCounter64,
    f3PtpAccPortFlowPointHistoryFollowupsTx            PerfCounter64,
    f3PtpAccPortFlowPointHistoryDelayReqsRx            PerfCounter64,
    f3PtpAccPortFlowPointHistoryDelayReqsTx            PerfCounter64,
    f3PtpAccPortFlowPointHistoryDelayRspsRx            PerfCounter64,
    f3PtpAccPortFlowPointHistoryDelayRspsTx            PerfCounter64,
    f3PtpAccPortFlowPointHistoryPDelayReqsRx           PerfCounter64,
    f3PtpAccPortFlowPointHistoryPDelayReqsTx           PerfCounter64,
    f3PtpAccPortFlowPointHistoryPDelayRspsRx           PerfCounter64,
    f3PtpAccPortFlowPointHistoryPDelayRspsTx           PerfCounter64,
    f3PtpAccPortFlowPointHistoryPDelayRspFollowupsRx   PerfCounter64,
    f3PtpAccPortFlowPointHistoryPDelayRspFollowupsTx   PerfCounter64,
    f3PtpAccPortFlowPointHistorySignalingRx            PerfCounter64,
    f3PtpAccPortFlowPointHistorySignalingTx            PerfCounter64,
    f3PtpAccPortFlowPointHistoryMgmtFramesRx           PerfCounter64,
    f3PtpAccPortFlowPointHistoryMgmtFramesTx           PerfCounter64,
    f3PtpAccPortFlowPointHistoryPtpUnknownsRx          PerfCounter64,
    f3PtpAccPortFlowPointHistoryPtpUnknownsTx          PerfCounter64,
    f3PtpAccPortFlowPointHistoryMinSyncResTime         Unsigned32,
    f3PtpAccPortFlowPointHistoryMaxSyncResTime         Unsigned32,
    f3PtpAccPortFlowPointHistoryAvgSyncResTime         Unsigned32,
    f3PtpAccPortFlowPointHistoryMinDelayReqResTime     Unsigned32,
    f3PtpAccPortFlowPointHistoryMaxDelayReqResTime     Unsigned32,
    f3PtpAccPortFlowPointHistoryAvgDelayReqResTime     Unsigned32,
    f3PtpAccPortFlowPointHistoryMinPDelayReqResTime    Unsigned32,
    f3PtpAccPortFlowPointHistoryMaxPDelayReqResTime    Unsigned32,
    f3PtpAccPortFlowPointHistoryAvgPDelayReqResTime    Unsigned32,
    f3PtpAccPortFlowPointHistoryMinPDelayRspResTime    Unsigned32,
    f3PtpAccPortFlowPointHistoryMaxPDelayRspResTime    Unsigned32,
    f3PtpAccPortFlowPointHistoryAvgPDelayRspResTime    Unsigned32,
    f3PtpAccPortFlowPointHistoryDestMciNoMatchDiscards PerfCounter64
}

f3PtpAccPortFlowPointHistoryIndex OBJECT-TYPE
    SYNTAX      Integer32 (1..32)
    MAX-ACCESS  not-accessible 
    STATUS      current
    DESCRIPTION
            "An arbitrary integer index value used to uniquely identify
            this Ethernet Access Port PTP Flow point PM history entry."
    ::= { f3PtpAccPortFlowPointHistoryEntry 1 }

f3PtpAccPortFlowPointHistoryTime OBJECT-TYPE
    SYNTAX      DateAndTime
    MAX-ACCESS  read-only
    STATUS      current
    DESCRIPTION
            "Indicates the time of history bin creation." 
    ::= { f3PtpAccPortFlowPointHistoryEntry 2 }

f3PtpAccPortFlowPointHistoryValid OBJECT-TYPE
    SYNTAX      TruthValue
    MAX-ACCESS  read-only
    STATUS      current
    DESCRIPTION
            "Indicates the validity of the bin."
    ::= { f3PtpAccPortFlowPointHistoryEntry 3 }

f3PtpAccPortFlowPointHistoryAction OBJECT-TYPE
    SYNTAX      CmPmBinAction
    MAX-ACCESS  read-write
    STATUS      current
    DESCRIPTION
            "Allows the Manager to clear the bin."
    ::= { f3PtpAccPortFlowPointHistoryEntry 4 }

f3PtpAccPortFlowPointHistoryAnnouncesRx OBJECT-TYPE
     SYNTAX     PerfCounter64
     MAX-ACCESS read-only
     STATUS     current
     DESCRIPTION
         "Number of PTP Announce messages received on the PTP Flow Point."
     ::= { f3PtpAccPortFlowPointHistoryEntry 5 }

f3PtpAccPortFlowPointHistoryAnnouncesTx OBJECT-TYPE
     SYNTAX     PerfCounter64
     MAX-ACCESS read-only
     STATUS     current
     DESCRIPTION
         "Number of Announce Messages transmitted on the PTP Flow Point.
          This object is applicable for transparent clocks."
     ::= { f3PtpAccPortFlowPointHistoryEntry 6 }

f3PtpAccPortFlowPointHistorySyncsRx OBJECT-TYPE
     SYNTAX     PerfCounter64
     MAX-ACCESS read-only
     STATUS     current
     DESCRIPTION
         "Number of Sync Messages received on the PTP Flow Point."
     ::= { f3PtpAccPortFlowPointHistoryEntry 7 }

f3PtpAccPortFlowPointHistorySyncsTx OBJECT-TYPE
     SYNTAX     PerfCounter64
     MAX-ACCESS read-only
     STATUS     current
     DESCRIPTION
         "Number of Sync Messages transmitted on the PTP Flow Point.
          This object is applicable for transparent clocks."
     ::= { f3PtpAccPortFlowPointHistoryEntry 8 }

f3PtpAccPortFlowPointHistoryFollowupsRx OBJECT-TYPE
     SYNTAX     PerfCounter64
     MAX-ACCESS read-only
     STATUS     current
     DESCRIPTION
         "Number of Follow up Messages received on the PTP Flow Point."
     ::= { f3PtpAccPortFlowPointHistoryEntry 9 }

f3PtpAccPortFlowPointHistoryFollowupsTx OBJECT-TYPE
     SYNTAX     PerfCounter64
     MAX-ACCESS read-only
     STATUS     current
     DESCRIPTION
         "Number of Follow up Messages transmitted on the PTP Flow Point."
     ::= { f3PtpAccPortFlowPointHistoryEntry 10 }

f3PtpAccPortFlowPointHistoryDelayReqsRx OBJECT-TYPE
     SYNTAX     PerfCounter64
     MAX-ACCESS read-only
     STATUS     current
     DESCRIPTION
         "Number of Delay Request Messages received on the PTP Flow Point."
     ::= { f3PtpAccPortFlowPointHistoryEntry 11 }

f3PtpAccPortFlowPointHistoryDelayReqsTx OBJECT-TYPE
     SYNTAX     PerfCounter64
     MAX-ACCESS read-only
     STATUS     current
     DESCRIPTION
         "Number of Delay Request Messages transmitted on the PTP Flow Point."
     ::= { f3PtpAccPortFlowPointHistoryEntry 12 }

f3PtpAccPortFlowPointHistoryDelayRspsRx OBJECT-TYPE
     SYNTAX     PerfCounter64
     MAX-ACCESS read-only
     STATUS     current
     DESCRIPTION
         "Number of Delay Response Messages received on the PTP Flow Point."
     ::= { f3PtpAccPortFlowPointHistoryEntry 13 }

f3PtpAccPortFlowPointHistoryDelayRspsTx OBJECT-TYPE
     SYNTAX     PerfCounter64
     MAX-ACCESS read-only
     STATUS     current
     DESCRIPTION
         "Number of Delay Response Messages transmitted on the PTP Flow Point."
     ::= { f3PtpAccPortFlowPointHistoryEntry 14 }

f3PtpAccPortFlowPointHistoryPDelayReqsRx OBJECT-TYPE
     SYNTAX     PerfCounter64
     MAX-ACCESS read-only
     STATUS     current
     DESCRIPTION
         "Number of Peer Delay Request Messages received on the PTP Flow Point."
     ::= { f3PtpAccPortFlowPointHistoryEntry 15 }

f3PtpAccPortFlowPointHistoryPDelayReqsTx OBJECT-TYPE
     SYNTAX     PerfCounter64
     MAX-ACCESS read-only
     STATUS     current
     DESCRIPTION
         "Number of Peer Delay Request Messages transmitted on the PTP Flow Point."
     ::= { f3PtpAccPortFlowPointHistoryEntry 16 }

f3PtpAccPortFlowPointHistoryPDelayRspsRx OBJECT-TYPE
     SYNTAX     PerfCounter64
     MAX-ACCESS read-only
     STATUS     current
     DESCRIPTION
         "Number of Peer Delay Response Messages received on the PTP Flow Point."
     ::= { f3PtpAccPortFlowPointHistoryEntry 17 }

f3PtpAccPortFlowPointHistoryPDelayRspsTx OBJECT-TYPE
     SYNTAX     PerfCounter64
     MAX-ACCESS read-only
     STATUS     current
     DESCRIPTION
         "Number of Peer Delay Response Messages transmitted on the PTP Flow Point."
     ::= { f3PtpAccPortFlowPointHistoryEntry 18 }

f3PtpAccPortFlowPointHistoryPDelayRspFollowupsRx OBJECT-TYPE
     SYNTAX     PerfCounter64
     MAX-ACCESS read-only
     STATUS     current
     DESCRIPTION
         "Number of Peer Delay Response Followup Messages received on the PTP Flow Point."
     ::= { f3PtpAccPortFlowPointHistoryEntry 19 }

f3PtpAccPortFlowPointHistoryPDelayRspFollowupsTx OBJECT-TYPE
     SYNTAX     PerfCounter64
     MAX-ACCESS read-only
     STATUS     current
     DESCRIPTION
         "Number of Peer Delay Response Followup Messages transmitted on the PTP Flow Point."
     ::= { f3PtpAccPortFlowPointHistoryEntry 20 }

f3PtpAccPortFlowPointHistorySignalingRx OBJECT-TYPE
     SYNTAX     PerfCounter64
     MAX-ACCESS read-only
     STATUS     current
     DESCRIPTION
         "Number of PTP Signaling Messages received on the PTP Flow Point."
     ::= { f3PtpAccPortFlowPointHistoryEntry 21 }

f3PtpAccPortFlowPointHistorySignalingTx OBJECT-TYPE
     SYNTAX     PerfCounter64
     MAX-ACCESS read-only
     STATUS     current
     DESCRIPTION
         "Number of PTP Signaling Messages Messages transmitted on the PTP Flow Point."
     ::= { f3PtpAccPortFlowPointHistoryEntry 22 }

f3PtpAccPortFlowPointHistoryMgmtFramesRx OBJECT-TYPE
     SYNTAX     PerfCounter64
     MAX-ACCESS read-only
     STATUS     current
     DESCRIPTION
         "Number of PTP Management Frames received on the PTP Flow Point."
     ::= { f3PtpAccPortFlowPointHistoryEntry 23 }

f3PtpAccPortFlowPointHistoryMgmtFramesTx OBJECT-TYPE
     SYNTAX     PerfCounter64
     MAX-ACCESS read-only
     STATUS     current
     DESCRIPTION
         "Number of PTP Management Frames Messages transmitted on the PTP Flow Point."
     ::= { f3PtpAccPortFlowPointHistoryEntry 24 }

f3PtpAccPortFlowPointHistoryPtpUnknownsRx OBJECT-TYPE
     SYNTAX     PerfCounter64
     MAX-ACCESS read-only
     STATUS     current
     DESCRIPTION
         "Number of Unknown PTP Messages received on the PTP Flow Point."
     ::= { f3PtpAccPortFlowPointHistoryEntry 25 }

f3PtpAccPortFlowPointHistoryPtpUnknownsTx OBJECT-TYPE
     SYNTAX     PerfCounter64
     MAX-ACCESS read-only
     STATUS     current
     DESCRIPTION
         "Number of Unknown PTP Messages transmitted on the PTP Flow Point."
     ::= { f3PtpAccPortFlowPointHistoryEntry 26 }

f3PtpAccPortFlowPointHistoryMinSyncResTime OBJECT-TYPE
     SYNTAX     Unsigned32
     MAX-ACCESS read-only
     STATUS     current
     DESCRIPTION
         "The minimum residence time for PTP Sync messages."
     ::= { f3PtpAccPortFlowPointHistoryEntry 27 }

f3PtpAccPortFlowPointHistoryMaxSyncResTime OBJECT-TYPE
     SYNTAX     Unsigned32
     MAX-ACCESS read-only
     STATUS     current
     DESCRIPTION
         "The maximum residence time for PTP Sync messages."
     ::= { f3PtpAccPortFlowPointHistoryEntry 28 }

f3PtpAccPortFlowPointHistoryAvgSyncResTime OBJECT-TYPE
     SYNTAX     Unsigned32
     MAX-ACCESS read-only
     STATUS     current
     DESCRIPTION
         "The average residence time for PTP Sync messages."
     ::= { f3PtpAccPortFlowPointHistoryEntry 29 }

f3PtpAccPortFlowPointHistoryMinDelayReqResTime OBJECT-TYPE
     SYNTAX     Unsigned32
     MAX-ACCESS read-only
     STATUS     current
     DESCRIPTION
         "The minimum residence time for PTP Delay Request messages."
     ::= { f3PtpAccPortFlowPointHistoryEntry 30 }

f3PtpAccPortFlowPointHistoryMaxDelayReqResTime OBJECT-TYPE
     SYNTAX     Unsigned32
     MAX-ACCESS read-only
     STATUS     current
     DESCRIPTION
         "The maximum residence time for PTP Delay Request messages."
     ::= { f3PtpAccPortFlowPointHistoryEntry 31 }

f3PtpAccPortFlowPointHistoryAvgDelayReqResTime OBJECT-TYPE
     SYNTAX     Unsigned32
     MAX-ACCESS read-only
     STATUS     current
     DESCRIPTION
         "The average residence time for PTP Delay Request messages."
     ::= { f3PtpAccPortFlowPointHistoryEntry 32 }

f3PtpAccPortFlowPointHistoryMinPDelayReqResTime OBJECT-TYPE
     SYNTAX     Unsigned32
     MAX-ACCESS read-only
     STATUS     current
     DESCRIPTION
         "The minimum residence time for PTP Peer Delay Request messages."
     ::= { f3PtpAccPortFlowPointHistoryEntry 33 }

f3PtpAccPortFlowPointHistoryMaxPDelayReqResTime OBJECT-TYPE
     SYNTAX     Unsigned32
     MAX-ACCESS read-only
     STATUS     current
     DESCRIPTION
         "The maximum residence time for PTP Peer Delay Request messages."
     ::= { f3PtpAccPortFlowPointHistoryEntry 34 }

f3PtpAccPortFlowPointHistoryAvgPDelayReqResTime OBJECT-TYPE
     SYNTAX     Unsigned32
     MAX-ACCESS read-only
     STATUS     current
     DESCRIPTION
         "The average residence time for PTP Peer Delay Request messages."
     ::= { f3PtpAccPortFlowPointHistoryEntry 35 }

f3PtpAccPortFlowPointHistoryMinPDelayRspResTime OBJECT-TYPE
     SYNTAX     Unsigned32
     MAX-ACCESS read-only
     STATUS     current
     DESCRIPTION
         "The minimum residence time for PTP Peer Delay Response messages."
     ::= { f3PtpAccPortFlowPointHistoryEntry 36 }

f3PtpAccPortFlowPointHistoryMaxPDelayRspResTime OBJECT-TYPE
     SYNTAX     Unsigned32
     MAX-ACCESS read-only
     STATUS     current
     DESCRIPTION
         "The maximum residence time for PTP Peer Delay Response messages."
     ::= { f3PtpAccPortFlowPointHistoryEntry 37 }

f3PtpAccPortFlowPointHistoryAvgPDelayRspResTime OBJECT-TYPE
     SYNTAX     Unsigned32
     MAX-ACCESS read-only
     STATUS     current
     DESCRIPTION
         "The average residence time for PTP Peer Delay Response messages."
     ::= { f3PtpAccPortFlowPointHistoryEntry 38 }

f3PtpAccPortFlowPointHistoryDestMciNoMatchDiscards OBJECT-TYPE
     SYNTAX     PerfCounter64
     MAX-ACCESS read-write
     STATUS     current
     DESCRIPTION
         "The dest MCI no match discards messages."
     ::= { f3PtpAccPortFlowPointHistoryEntry 39 }

--
-- Access Port PTP Flow Point Threshold Table
--
f3PtpAccPortFlowPointThresholdTable OBJECT-TYPE
    SYNTAX      SEQUENCE OF F3PtpAccPortFlowPointThresholdEntry
    MAX-ACCESS  not-accessible
    STATUS      current
    DESCRIPTION
            "A table of entries that allow manageability of Access Port PTP Flow Point
             Thresholds."
    ::= { f3PtpPerformanceObjects 3 }

f3PtpAccPortFlowPointThresholdEntry OBJECT-TYPE
    SYNTAX      F3PtpAccPortFlowPointThresholdEntry
    MAX-ACCESS  not-accessible
    STATUS      current
    DESCRIPTION
            "A conceptual row in the f3PtpAccPortFlowPointThresholdTable."
    INDEX { neIndex, shelfIndex, slotIndex, cmEthernetAccPortIndex, 
            f3PtpAccPortFlowPointIndex, f3PtpAccPortFlowPointStatsIndex, 
            f3PtpAccPortFlowPointThresholdIndex }
    ::= { f3PtpAccPortFlowPointThresholdTable 1 }

F3PtpAccPortFlowPointThresholdEntry ::= SEQUENCE {
    f3PtpAccPortFlowPointThresholdIndex       Integer32,
    f3PtpAccPortFlowPointThresholdInterval    CmPmIntervalType,
    f3PtpAccPortFlowPointThresholdVariable    VariablePointer,
    f3PtpAccPortFlowPointThresholdValueLo     Unsigned32,
    f3PtpAccPortFlowPointThresholdValueHi     Unsigned32,
    f3PtpAccPortFlowPointThresholdMonValue    PerfCounter64
}

f3PtpAccPortFlowPointThresholdIndex OBJECT-TYPE
    SYNTAX     Integer32 (1..65535)
    MAX-ACCESS not-accessible 
    STATUS     current
    DESCRIPTION
        "An index that uniquely identifies an entry in the
        f3PtpAccPortFlowPointThresholdTable."
    ::= { f3PtpAccPortFlowPointThresholdEntry 1 }

f3PtpAccPortFlowPointThresholdInterval OBJECT-TYPE
    SYNTAX     CmPmIntervalType
    MAX-ACCESS read-only
    STATUS     current
    DESCRIPTION
        "The interval over which monitored value is
        sampled and compared with the specified threshold."
    ::= { f3PtpAccPortFlowPointThresholdEntry 2 }

f3PtpAccPortFlowPointThresholdVariable OBJECT-TYPE
    SYNTAX     VariablePointer
    MAX-ACCESS read-only
    STATUS     current
    DESCRIPTION
        "The object identifier of the particular variable to be
        sampled."
    ::= { f3PtpAccPortFlowPointThresholdEntry 3 }

f3PtpAccPortFlowPointThresholdValueLo OBJECT-TYPE
    SYNTAX     Unsigned32
    MAX-ACCESS read-write
    STATUS     current
    DESCRIPTION
        "Lower 32 bits of the threshold value."
    ::= { f3PtpAccPortFlowPointThresholdEntry 4 }

f3PtpAccPortFlowPointThresholdValueHi OBJECT-TYPE
    SYNTAX     Unsigned32
    MAX-ACCESS read-write
    STATUS     current
    DESCRIPTION
        "Higher 32 bits of the threshold value."
    ::= { f3PtpAccPortFlowPointThresholdEntry 5 }

f3PtpAccPortFlowPointThresholdMonValue OBJECT-TYPE
    SYNTAX     PerfCounter64
    MAX-ACCESS read-only
    STATUS     current
    DESCRIPTION
        "Monitored value corresponding to f3PtpAccPortFlowPointThresholdVariable."
    ::= { f3PtpAccPortFlowPointThresholdEntry 6 }

--
-- Network Port PTP Flow Point Current Statistics Table
--
f3PtpNetPortFlowPointStatsTable OBJECT-TYPE
    SYNTAX      SEQUENCE OF F3PtpNetPortFlowPointStatsEntry
    MAX-ACCESS  not-accessible
    STATUS      current
    DESCRIPTION
            "A collection of Network Port PTP Flow Point statistics.  
             These reflect the current data."
    ::= { f3PtpPerformanceObjects 4 }

f3PtpNetPortFlowPointStatsEntry OBJECT-TYPE
    SYNTAX      F3PtpNetPortFlowPointStatsEntry 
    MAX-ACCESS  not-accessible
    STATUS      current
    DESCRIPTION
            "A conceptual row in the f3PtpNetPortFlowPointStatsTable.
             Entries exist in this table for each Network Port Flow Point."
    INDEX { neIndex, shelfIndex, slotIndex, cmEthernetNetPortIndex, 
            f3PtpNetPortFlowPointIndex, f3PtpNetPortFlowPointStatsIndex }
    ::= { f3PtpNetPortFlowPointStatsTable 1 }

F3PtpNetPortFlowPointStatsEntry ::= SEQUENCE {
    f3PtpNetPortFlowPointStatsIndex                  Integer32,
    f3PtpNetPortFlowPointStatsIntervalType           CmPmIntervalType,
    f3PtpNetPortFlowPointStatsValid                  TruthValue,
    f3PtpNetPortFlowPointStatsAction                 CmPmBinAction,
    f3PtpNetPortFlowPointStatsAnnouncesRx            PerfCounter64,
    f3PtpNetPortFlowPointStatsAnnouncesTx            PerfCounter64,
    f3PtpNetPortFlowPointStatsSyncsRx                PerfCounter64,
    f3PtpNetPortFlowPointStatsSyncsTx                PerfCounter64,
    f3PtpNetPortFlowPointStatsFollowupsRx            PerfCounter64,
    f3PtpNetPortFlowPointStatsFollowupsTx            PerfCounter64,
    f3PtpNetPortFlowPointStatsDelayReqsRx            PerfCounter64,
    f3PtpNetPortFlowPointStatsDelayReqsTx            PerfCounter64,
    f3PtpNetPortFlowPointStatsDelayRspsRx            PerfCounter64,
    f3PtpNetPortFlowPointStatsDelayRspsTx            PerfCounter64,
    f3PtpNetPortFlowPointStatsPDelayReqsRx           PerfCounter64,
    f3PtpNetPortFlowPointStatsPDelayReqsTx           PerfCounter64,
    f3PtpNetPortFlowPointStatsPDelayRspsRx           PerfCounter64,
    f3PtpNetPortFlowPointStatsPDelayRspsTx           PerfCounter64,
    f3PtpNetPortFlowPointStatsPDelayRspFollowupsRx   PerfCounter64,
    f3PtpNetPortFlowPointStatsPDelayRspFollowupsTx   PerfCounter64,
    f3PtpNetPortFlowPointStatsSignalingRx            PerfCounter64,
    f3PtpNetPortFlowPointStatsSignalingTx            PerfCounter64,
    f3PtpNetPortFlowPointStatsMgmtFramesRx           PerfCounter64,
    f3PtpNetPortFlowPointStatsMgmtFramesTx           PerfCounter64,
    f3PtpNetPortFlowPointStatsPtpUnknownsRx          PerfCounter64,
    f3PtpNetPortFlowPointStatsPtpUnknownsTx          PerfCounter64,
    f3PtpNetPortFlowPointStatsAvgSyncResTime         Unsigned32,
    f3PtpNetPortFlowPointStatsMinSyncResTime         Unsigned32,
    f3PtpNetPortFlowPointStatsMaxSyncResTime         Unsigned32,
    f3PtpNetPortFlowPointStatsAvgDelayReqResTime     Unsigned32,
    f3PtpNetPortFlowPointStatsMinDelayReqResTime     Unsigned32,
    f3PtpNetPortFlowPointStatsMaxDelayReqResTime     Unsigned32,
    f3PtpNetPortFlowPointStatsMinPDelayReqResTime    Unsigned32,
    f3PtpNetPortFlowPointStatsMaxPDelayReqResTime    Unsigned32,
    f3PtpNetPortFlowPointStatsAvgPDelayReqResTime    Unsigned32,
    f3PtpNetPortFlowPointStatsMinPDelayRspResTime    Unsigned32,
    f3PtpNetPortFlowPointStatsMaxPDelayRspResTime    Unsigned32,
    f3PtpNetPortFlowPointStatsAvgPDelayRspResTime    Unsigned32,
    f3PtpNetPortFlowPointStatsDestMciNoMatchDiscards PerfCounter64
}

f3PtpNetPortFlowPointStatsIndex OBJECT-TYPE
    SYNTAX      Integer32 (1..4)
    MAX-ACCESS  not-accessible
    STATUS      current
    DESCRIPTION
            "An arbitrary integer index value used to uniquely identify
            this Network Port PTP Flow Point statistics entry. 
            1 - 15min
            2 - 1day
            3 - rollover
            4 - 5min"
    ::= { f3PtpNetPortFlowPointStatsEntry 1 }

f3PtpNetPortFlowPointStatsIntervalType OBJECT-TYPE
    SYNTAX      CmPmIntervalType
    MAX-ACCESS  read-only
    STATUS      current
    DESCRIPTION
            "Indicates the type of collection, i.e. whether it is
             15 Min, 1 Day or rollover."
    ::= { f3PtpNetPortFlowPointStatsEntry 2 }

f3PtpNetPortFlowPointStatsValid OBJECT-TYPE
    SYNTAX      TruthValue
    MAX-ACCESS  read-only
    STATUS      current
    DESCRIPTION
            "Indicates the validity of the bin."
    ::= { f3PtpNetPortFlowPointStatsEntry 3 }

f3PtpNetPortFlowPointStatsAction OBJECT-TYPE
    SYNTAX      CmPmBinAction
    MAX-ACCESS  read-write
    STATUS      current
    DESCRIPTION
            "Allows the Manager to clear the bin."
    ::= { f3PtpNetPortFlowPointStatsEntry 4 }

f3PtpNetPortFlowPointStatsAnnouncesRx OBJECT-TYPE
     SYNTAX     PerfCounter64
     MAX-ACCESS read-only
     STATUS     current
     DESCRIPTION
         "Number of PTP Announce messages received on the PTP Flow Point."
     ::= { f3PtpNetPortFlowPointStatsEntry 5 }

f3PtpNetPortFlowPointStatsAnnouncesTx OBJECT-TYPE
     SYNTAX     PerfCounter64
     MAX-ACCESS read-only
     STATUS     current
     DESCRIPTION
         "Number of Announce Messages transmitted on the PTP Flow Point.
          This object is applicable for transparent clocks."
     ::= { f3PtpNetPortFlowPointStatsEntry 6 }

f3PtpNetPortFlowPointStatsSyncsRx OBJECT-TYPE
     SYNTAX     PerfCounter64
     MAX-ACCESS read-only
     STATUS     current
     DESCRIPTION
         "Number of Sync Messages received on the PTP Flow Point."
     ::= { f3PtpNetPortFlowPointStatsEntry 7 }

f3PtpNetPortFlowPointStatsSyncsTx OBJECT-TYPE
     SYNTAX     PerfCounter64
     MAX-ACCESS read-only
     STATUS     current
     DESCRIPTION
         "Number of Sync Messages transmitted on the PTP Flow Point.
          This object is applicable for transparent clocks."
     ::= { f3PtpNetPortFlowPointStatsEntry 8 }

f3PtpNetPortFlowPointStatsFollowupsRx OBJECT-TYPE
     SYNTAX     PerfCounter64
     MAX-ACCESS read-only
     STATUS     current
     DESCRIPTION
         "Number of Follow up Messages received on the PTP Flow Point."
     ::= { f3PtpNetPortFlowPointStatsEntry 9 }

f3PtpNetPortFlowPointStatsFollowupsTx OBJECT-TYPE
     SYNTAX     PerfCounter64
     MAX-ACCESS read-only
     STATUS     current
     DESCRIPTION
         "Number of Follow up Messages transmitted on the PTP Flow Point."
     ::= { f3PtpNetPortFlowPointStatsEntry 10 }

f3PtpNetPortFlowPointStatsDelayReqsRx OBJECT-TYPE
     SYNTAX     PerfCounter64
     MAX-ACCESS read-only
     STATUS     current
     DESCRIPTION
         "Number of Delay Request Messages received on the PTP Flow Point."
     ::= { f3PtpNetPortFlowPointStatsEntry 11 }

f3PtpNetPortFlowPointStatsDelayReqsTx OBJECT-TYPE
     SYNTAX     PerfCounter64
     MAX-ACCESS read-only
     STATUS     current
     DESCRIPTION
         "Number of Delay Request Messages transmitted on the PTP Flow Point."
     ::= { f3PtpNetPortFlowPointStatsEntry 12 }

f3PtpNetPortFlowPointStatsDelayRspsRx OBJECT-TYPE
     SYNTAX     PerfCounter64
     MAX-ACCESS read-only
     STATUS     current
     DESCRIPTION
         "Number of Delay Response Messages received on the PTP Flow Point."
     ::= { f3PtpNetPortFlowPointStatsEntry 13 }

f3PtpNetPortFlowPointStatsDelayRspsTx OBJECT-TYPE
     SYNTAX     PerfCounter64
     MAX-ACCESS read-only
     STATUS     current
     DESCRIPTION
         "Number of Delay Response Messages transmitted on the PTP Flow Point."
     ::= { f3PtpNetPortFlowPointStatsEntry 14 }

f3PtpNetPortFlowPointStatsPDelayReqsRx OBJECT-TYPE
     SYNTAX     PerfCounter64
     MAX-ACCESS read-only
     STATUS     current
     DESCRIPTION
         "Number of Peer Delay Request Messages received on the PTP Flow Point."
     ::= { f3PtpNetPortFlowPointStatsEntry 15 }

f3PtpNetPortFlowPointStatsPDelayReqsTx OBJECT-TYPE
     SYNTAX     PerfCounter64
     MAX-ACCESS read-only
     STATUS     current
     DESCRIPTION
         "Number of Peer Delay Request Messages transmitted on the PTP Flow Point."
     ::= { f3PtpNetPortFlowPointStatsEntry 16 }

f3PtpNetPortFlowPointStatsPDelayRspsRx OBJECT-TYPE
     SYNTAX     PerfCounter64
     MAX-ACCESS read-only
     STATUS     current
     DESCRIPTION
         "Number of Peer Delay Response Messages received on the PTP Flow Point."
     ::= { f3PtpNetPortFlowPointStatsEntry 17 }

f3PtpNetPortFlowPointStatsPDelayRspsTx OBJECT-TYPE
     SYNTAX     PerfCounter64
     MAX-ACCESS read-only
     STATUS     current
     DESCRIPTION
         "Number of Peer Delay Response Messages transmitted on the PTP Flow Point."
     ::= { f3PtpNetPortFlowPointStatsEntry 18 }

f3PtpNetPortFlowPointStatsPDelayRspFollowupsRx OBJECT-TYPE
     SYNTAX     PerfCounter64
     MAX-ACCESS read-only
     STATUS     current
     DESCRIPTION
         "Number of Peer Delay Response Followup Messages received on the PTP Flow Point."
     ::= { f3PtpNetPortFlowPointStatsEntry 19 }

f3PtpNetPortFlowPointStatsPDelayRspFollowupsTx OBJECT-TYPE
     SYNTAX     PerfCounter64
     MAX-ACCESS read-only
     STATUS     current
     DESCRIPTION
         "Number of Peer Delay Response Followup Messages transmitted on the PTP Flow Point."
     ::= { f3PtpNetPortFlowPointStatsEntry 20 }

f3PtpNetPortFlowPointStatsSignalingRx OBJECT-TYPE
     SYNTAX     PerfCounter64
     MAX-ACCESS read-only
     STATUS     current
     DESCRIPTION
         "Number of PTP Signaling Messages received on the PTP Flow Point."
     ::= { f3PtpNetPortFlowPointStatsEntry 21 }

f3PtpNetPortFlowPointStatsSignalingTx OBJECT-TYPE
     SYNTAX     PerfCounter64
     MAX-ACCESS read-only
     STATUS     current
     DESCRIPTION
         "Number of PTP Signaling Messages Messages transmitted on the PTP Flow Point."
     ::= { f3PtpNetPortFlowPointStatsEntry 22 }

f3PtpNetPortFlowPointStatsMgmtFramesRx OBJECT-TYPE
     SYNTAX     PerfCounter64
     MAX-ACCESS read-only
     STATUS     current
     DESCRIPTION
         "Number of PTP Management Frames received on the PTP Flow Point."
     ::= { f3PtpNetPortFlowPointStatsEntry 23 }

f3PtpNetPortFlowPointStatsMgmtFramesTx OBJECT-TYPE
     SYNTAX     PerfCounter64
     MAX-ACCESS read-only
     STATUS     current
     DESCRIPTION
         "Number of PTP Management Frames Messages transmitted on the PTP Flow Point."
     ::= { f3PtpNetPortFlowPointStatsEntry 24 }

f3PtpNetPortFlowPointStatsPtpUnknownsRx OBJECT-TYPE
     SYNTAX     PerfCounter64
     MAX-ACCESS read-only
     STATUS     current
     DESCRIPTION
         "Number of Unknown PTP Messages received on the PTP Flow Point."
     ::= { f3PtpNetPortFlowPointStatsEntry 25 }

f3PtpNetPortFlowPointStatsPtpUnknownsTx OBJECT-TYPE
     SYNTAX     PerfCounter64
     MAX-ACCESS read-only
     STATUS     current
     DESCRIPTION
         "Number of Unknown PTP Messages transmitted on the PTP Flow Point."
     ::= { f3PtpNetPortFlowPointStatsEntry 26 }

f3PtpNetPortFlowPointStatsAvgSyncResTime OBJECT-TYPE
     SYNTAX     Unsigned32
     MAX-ACCESS read-only
     STATUS     current
     DESCRIPTION
         "The average residence time for PTP Sync messages."
     ::= { f3PtpNetPortFlowPointStatsEntry 27 }

f3PtpNetPortFlowPointStatsMinSyncResTime OBJECT-TYPE
     SYNTAX     Unsigned32
     MAX-ACCESS read-only
     STATUS     current
     DESCRIPTION
         "The minimum residence time for PTP Sync messages."
     ::= { f3PtpNetPortFlowPointStatsEntry 28 }

f3PtpNetPortFlowPointStatsMaxSyncResTime OBJECT-TYPE
     SYNTAX     Unsigned32
     MAX-ACCESS read-only
     STATUS     current
     DESCRIPTION
         "The maximum residence time for PTP Sync messages."
     ::= { f3PtpNetPortFlowPointStatsEntry 29 }

f3PtpNetPortFlowPointStatsAvgDelayReqResTime OBJECT-TYPE
     SYNTAX     Unsigned32
     MAX-ACCESS read-only
     STATUS     current
     DESCRIPTION
         "The average residence time for PTP Delay Request messages."
     ::= { f3PtpNetPortFlowPointStatsEntry 30 }

f3PtpNetPortFlowPointStatsMinDelayReqResTime OBJECT-TYPE
     SYNTAX     Unsigned32
     MAX-ACCESS read-only
     STATUS     current
     DESCRIPTION
         "The minimum residence time for PTP Delay Request messages."
     ::= { f3PtpNetPortFlowPointStatsEntry 31 }

f3PtpNetPortFlowPointStatsMaxDelayReqResTime OBJECT-TYPE
     SYNTAX     Unsigned32
     MAX-ACCESS read-only
     STATUS     current
     DESCRIPTION
         "The maximum residence time for PTP Delay Request messages."
     ::= { f3PtpNetPortFlowPointStatsEntry 32 }

f3PtpNetPortFlowPointStatsMinPDelayReqResTime OBJECT-TYPE
     SYNTAX     Unsigned32
     MAX-ACCESS read-only
     STATUS     current
     DESCRIPTION
         "The minimum residence time for PTP Peer Delay Request messages."
     ::= { f3PtpNetPortFlowPointStatsEntry 33 }

f3PtpNetPortFlowPointStatsMaxPDelayReqResTime OBJECT-TYPE
     SYNTAX     Unsigned32
     MAX-ACCESS read-only
     STATUS     current
     DESCRIPTION
         "The maximum residence time for PTP Peer Delay Request messages."
     ::= { f3PtpNetPortFlowPointStatsEntry 34 }

f3PtpNetPortFlowPointStatsAvgPDelayReqResTime OBJECT-TYPE
     SYNTAX     Unsigned32
     MAX-ACCESS read-only
     STATUS     current
     DESCRIPTION
         "The average residence time for PTP Peer Delay Request messages."
     ::= { f3PtpNetPortFlowPointStatsEntry 35 }

f3PtpNetPortFlowPointStatsMinPDelayRspResTime OBJECT-TYPE
     SYNTAX     Unsigned32
     MAX-ACCESS read-only
     STATUS     current
     DESCRIPTION
         "The minimum residence time for PTP Peer Delay Response messages."
     ::= { f3PtpNetPortFlowPointStatsEntry 36 }

f3PtpNetPortFlowPointStatsMaxPDelayRspResTime OBJECT-TYPE
     SYNTAX     Unsigned32
     MAX-ACCESS read-only
     STATUS     current
     DESCRIPTION
         "The maximum residence time for PTP Peer Delay Response messages."
     ::= { f3PtpNetPortFlowPointStatsEntry 37 }

f3PtpNetPortFlowPointStatsAvgPDelayRspResTime OBJECT-TYPE
     SYNTAX     Unsigned32
     MAX-ACCESS read-only
     STATUS     current
     DESCRIPTION
         "The average residence time for PTP Peer Delay Response messages."
     ::= { f3PtpNetPortFlowPointStatsEntry 38 }

f3PtpNetPortFlowPointStatsDestMciNoMatchDiscards OBJECT-TYPE
     SYNTAX     PerfCounter64
     MAX-ACCESS read-write
     STATUS     current
     DESCRIPTION
         "The dest MCI no match discards messages."
     ::= { f3PtpNetPortFlowPointStatsEntry 39 }

--
-- Network Port PTP Flow Point History Table
--
f3PtpNetPortFlowPointHistoryTable OBJECT-TYPE
    SYNTAX      SEQUENCE OF F3PtpNetPortFlowPointHistoryEntry
    MAX-ACCESS  not-accessible
    STATUS      current
    DESCRIPTION
            "A collection of Network Port PTP Flow Point history statistics.  
             These reflect the history data."
    ::= { f3PtpPerformanceObjects 5 }

f3PtpNetPortFlowPointHistoryEntry OBJECT-TYPE
    SYNTAX      F3PtpNetPortFlowPointHistoryEntry 
    MAX-ACCESS  not-accessible
    STATUS      current
    DESCRIPTION
            "A conceptual row in the f3PtpNetPortFlowPointHistoryTable.
             Entries exist in this table for each Network Port Flow Point."
    INDEX { neIndex, shelfIndex, slotIndex, cmEthernetNetPortIndex, 
            f3PtpNetPortFlowPointIndex, f3PtpNetPortFlowPointStatsIndex, f3PtpNetPortFlowPointHistoryIndex }
    ::= { f3PtpNetPortFlowPointHistoryTable 1 }

F3PtpNetPortFlowPointHistoryEntry ::= SEQUENCE {
    f3PtpNetPortFlowPointHistoryIndex                  Integer32,
    f3PtpNetPortFlowPointHistoryTime                   DateAndTime,
    f3PtpNetPortFlowPointHistoryValid                  TruthValue,
    f3PtpNetPortFlowPointHistoryAction                 CmPmBinAction,
    f3PtpNetPortFlowPointHistoryAnnouncesRx            PerfCounter64,
    f3PtpNetPortFlowPointHistoryAnnouncesTx            PerfCounter64,
    f3PtpNetPortFlowPointHistorySyncsRx                PerfCounter64,
    f3PtpNetPortFlowPointHistorySyncsTx                PerfCounter64,
    f3PtpNetPortFlowPointHistoryFollowupsRx            PerfCounter64,
    f3PtpNetPortFlowPointHistoryFollowupsTx            PerfCounter64,
    f3PtpNetPortFlowPointHistoryDelayReqsRx            PerfCounter64,
    f3PtpNetPortFlowPointHistoryDelayReqsTx            PerfCounter64,
    f3PtpNetPortFlowPointHistoryDelayRspsRx            PerfCounter64,
    f3PtpNetPortFlowPointHistoryDelayRspsTx            PerfCounter64,
    f3PtpNetPortFlowPointHistoryPDelayReqsRx           PerfCounter64,
    f3PtpNetPortFlowPointHistoryPDelayReqsTx           PerfCounter64,
    f3PtpNetPortFlowPointHistoryPDelayRspsRx           PerfCounter64,
    f3PtpNetPortFlowPointHistoryPDelayRspsTx           PerfCounter64,
    f3PtpNetPortFlowPointHistoryPDelayRspFollowupsRx   PerfCounter64,
    f3PtpNetPortFlowPointHistoryPDelayRspFollowupsTx   PerfCounter64,
    f3PtpNetPortFlowPointHistorySignalingRx            PerfCounter64,
    f3PtpNetPortFlowPointHistorySignalingTx            PerfCounter64,
    f3PtpNetPortFlowPointHistoryMgmtFramesRx           PerfCounter64,
    f3PtpNetPortFlowPointHistoryMgmtFramesTx           PerfCounter64,
    f3PtpNetPortFlowPointHistoryPtpUnknownsRx          PerfCounter64,
    f3PtpNetPortFlowPointHistoryPtpUnknownsTx          PerfCounter64,
    f3PtpNetPortFlowPointHistoryAvgSyncResTime         Unsigned32,
    f3PtpNetPortFlowPointHistoryMinSyncResTime         Unsigned32,
    f3PtpNetPortFlowPointHistoryMaxSyncResTime         Unsigned32,
    f3PtpNetPortFlowPointHistoryAvgDelayReqResTime     Unsigned32,
    f3PtpNetPortFlowPointHistoryMinDelayReqResTime     Unsigned32,
    f3PtpNetPortFlowPointHistoryMaxDelayReqResTime     Unsigned32,
    f3PtpNetPortFlowPointHistoryMinPDelayReqResTime    Unsigned32,
    f3PtpNetPortFlowPointHistoryMaxPDelayReqResTime    Unsigned32,
    f3PtpNetPortFlowPointHistoryAvgPDelayReqResTime    Unsigned32,
    f3PtpNetPortFlowPointHistoryMinPDelayRspResTime    Unsigned32,
    f3PtpNetPortFlowPointHistoryMaxPDelayRspResTime    Unsigned32,
    f3PtpNetPortFlowPointHistoryAvgPDelayRspResTime    Unsigned32,
    f3PtpNetPortFlowPointHistoryDestMciNoMatchDiscards PerfCounter64
}

f3PtpNetPortFlowPointHistoryIndex OBJECT-TYPE
    SYNTAX      Integer32 (1..32)
    MAX-ACCESS  not-accessible
    STATUS      current
    DESCRIPTION
            "An arbitrary integer index value used to uniquely identify
            this Ethernet Network Port PTP Flow point PM history entry."
    ::= { f3PtpNetPortFlowPointHistoryEntry 1 }

f3PtpNetPortFlowPointHistoryTime OBJECT-TYPE
    SYNTAX      DateAndTime
    MAX-ACCESS  read-only
    STATUS      current
    DESCRIPTION
            "Indicates the time of history bin creation." 
    ::= { f3PtpNetPortFlowPointHistoryEntry 2 }

f3PtpNetPortFlowPointHistoryValid OBJECT-TYPE
    SYNTAX      TruthValue
    MAX-ACCESS  read-only
    STATUS      current
    DESCRIPTION
            "Indicates the validity of the bin."
    ::= { f3PtpNetPortFlowPointHistoryEntry 3 }

f3PtpNetPortFlowPointHistoryAction OBJECT-TYPE
    SYNTAX      CmPmBinAction
    MAX-ACCESS  read-write
    STATUS      current
    DESCRIPTION
            "Allows the Manager to clear the bin."
    ::= { f3PtpNetPortFlowPointHistoryEntry 4 }

f3PtpNetPortFlowPointHistoryAnnouncesRx OBJECT-TYPE
     SYNTAX     PerfCounter64
     MAX-ACCESS read-only
     STATUS     current
     DESCRIPTION
         "Number of PTP Announce messages received on the PTP Flow Point."
     ::= { f3PtpNetPortFlowPointHistoryEntry 5 }

f3PtpNetPortFlowPointHistoryAnnouncesTx OBJECT-TYPE
     SYNTAX     PerfCounter64
     MAX-ACCESS read-only
     STATUS     current
     DESCRIPTION
         "Number of Announce Messages transmitted on the PTP Flow Point.
          This object is applicable for transparent clocks."
     ::= { f3PtpNetPortFlowPointHistoryEntry 6 }

f3PtpNetPortFlowPointHistorySyncsRx OBJECT-TYPE
     SYNTAX     PerfCounter64
     MAX-ACCESS read-only
     STATUS     current
     DESCRIPTION
         "Number of Sync Messages received on the PTP Flow Point."
     ::= { f3PtpNetPortFlowPointHistoryEntry 7 }

f3PtpNetPortFlowPointHistorySyncsTx OBJECT-TYPE
     SYNTAX     PerfCounter64
     MAX-ACCESS read-only
     STATUS     current
     DESCRIPTION
         "Number of Sync Messages transmitted on the PTP Flow Point.
          This object is applicable for transparent clocks."
     ::= { f3PtpNetPortFlowPointHistoryEntry 8 }

f3PtpNetPortFlowPointHistoryFollowupsRx OBJECT-TYPE
     SYNTAX     PerfCounter64
     MAX-ACCESS read-only
     STATUS     current
     DESCRIPTION
         "Number of Follow up Messages received on the PTP Flow Point."
     ::= { f3PtpNetPortFlowPointHistoryEntry 9 }

f3PtpNetPortFlowPointHistoryFollowupsTx OBJECT-TYPE
     SYNTAX     PerfCounter64
     MAX-ACCESS read-only
     STATUS     current
     DESCRIPTION
         "Number of Follow up Messages transmitted on the PTP Flow Point."
     ::= { f3PtpNetPortFlowPointHistoryEntry 10 }

f3PtpNetPortFlowPointHistoryDelayReqsRx OBJECT-TYPE
     SYNTAX     PerfCounter64
     MAX-ACCESS read-only
     STATUS     current
     DESCRIPTION
         "Number of Delay Request Messages received on the PTP Flow Point."
     ::= { f3PtpNetPortFlowPointHistoryEntry 11 }

f3PtpNetPortFlowPointHistoryDelayReqsTx OBJECT-TYPE
     SYNTAX     PerfCounter64
     MAX-ACCESS read-only
     STATUS     current
     DESCRIPTION
         "Number of Delay Request Messages transmitted on the PTP Flow Point."
     ::= { f3PtpNetPortFlowPointHistoryEntry 12 }

f3PtpNetPortFlowPointHistoryDelayRspsRx OBJECT-TYPE
     SYNTAX     PerfCounter64
     MAX-ACCESS read-only
     STATUS     current
     DESCRIPTION
         "Number of Delay Response Messages received on the PTP Flow Point."
     ::= { f3PtpNetPortFlowPointHistoryEntry 13 }

f3PtpNetPortFlowPointHistoryDelayRspsTx OBJECT-TYPE
     SYNTAX     PerfCounter64
     MAX-ACCESS read-only
     STATUS     current
     DESCRIPTION
         "Number of Delay Response Messages transmitted on the PTP Flow Point."
     ::= { f3PtpNetPortFlowPointHistoryEntry 14 }

f3PtpNetPortFlowPointHistoryPDelayReqsRx OBJECT-TYPE
     SYNTAX     PerfCounter64
     MAX-ACCESS read-only
     STATUS     current
     DESCRIPTION
         "Number of Peer Delay Request Messages received on the PTP Flow Point."
     ::= { f3PtpNetPortFlowPointHistoryEntry 15 }

f3PtpNetPortFlowPointHistoryPDelayReqsTx OBJECT-TYPE
     SYNTAX     PerfCounter64
     MAX-ACCESS read-only
     STATUS     current
     DESCRIPTION
         "Number of Peer Delay Request Messages transmitted on the PTP Flow Point."
     ::= { f3PtpNetPortFlowPointHistoryEntry 16 }

f3PtpNetPortFlowPointHistoryPDelayRspsRx OBJECT-TYPE
     SYNTAX     PerfCounter64
     MAX-ACCESS read-only
     STATUS     current
     DESCRIPTION
         "Number of Peer Delay Response Messages received on the PTP Flow Point."
     ::= { f3PtpNetPortFlowPointHistoryEntry 17 }

f3PtpNetPortFlowPointHistoryPDelayRspsTx OBJECT-TYPE
     SYNTAX     PerfCounter64
     MAX-ACCESS read-only
     STATUS     current
     DESCRIPTION
         "Number of Peer Delay Response Messages transmitted on the PTP Flow Point."
     ::= { f3PtpNetPortFlowPointHistoryEntry 18 }

f3PtpNetPortFlowPointHistoryPDelayRspFollowupsRx OBJECT-TYPE
     SYNTAX     PerfCounter64
     MAX-ACCESS read-only
     STATUS     current
     DESCRIPTION
         "Number of Peer Delay Response Followup Messages received on the PTP Flow Point."
     ::= { f3PtpNetPortFlowPointHistoryEntry 19 }

f3PtpNetPortFlowPointHistoryPDelayRspFollowupsTx OBJECT-TYPE
     SYNTAX     PerfCounter64
     MAX-ACCESS read-only
     STATUS     current
     DESCRIPTION
         "Number of Peer Delay Response Followup Messages transmitted on the PTP Flow Point."
     ::= { f3PtpNetPortFlowPointHistoryEntry 20 }

f3PtpNetPortFlowPointHistorySignalingRx OBJECT-TYPE
     SYNTAX     PerfCounter64
     MAX-ACCESS read-only
     STATUS     current
     DESCRIPTION
         "Number of PTP Signaling Messages received on the PTP Flow Point."
     ::= { f3PtpNetPortFlowPointHistoryEntry 21 }

f3PtpNetPortFlowPointHistorySignalingTx OBJECT-TYPE
     SYNTAX     PerfCounter64
     MAX-ACCESS read-only
     STATUS     current
     DESCRIPTION
         "Number of PTP Signaling Messages Messages transmitted on the PTP Flow Point."
     ::= { f3PtpNetPortFlowPointHistoryEntry 22 }

f3PtpNetPortFlowPointHistoryMgmtFramesRx OBJECT-TYPE
     SYNTAX     PerfCounter64
     MAX-ACCESS read-only
     STATUS     current
     DESCRIPTION
         "Number of PTP Management Frames received on the PTP Flow Point."
     ::= { f3PtpNetPortFlowPointHistoryEntry 23 }

f3PtpNetPortFlowPointHistoryMgmtFramesTx OBJECT-TYPE
     SYNTAX     PerfCounter64
     MAX-ACCESS read-only
     STATUS     current
     DESCRIPTION
         "Number of PTP Management Frames Messages transmitted on the PTP Flow Point."
     ::= { f3PtpNetPortFlowPointHistoryEntry 24 }

f3PtpNetPortFlowPointHistoryPtpUnknownsRx OBJECT-TYPE
     SYNTAX     PerfCounter64
     MAX-ACCESS read-only
     STATUS     current
     DESCRIPTION
         "Number of Unknown PTP Messages received on the PTP Flow Point."
     ::= { f3PtpNetPortFlowPointHistoryEntry 25 }

f3PtpNetPortFlowPointHistoryPtpUnknownsTx OBJECT-TYPE
     SYNTAX     PerfCounter64
     MAX-ACCESS read-only
     STATUS     current
     DESCRIPTION
         "Number of Unknown PTP Messages transmitted on the PTP Flow Point."
     ::= { f3PtpNetPortFlowPointHistoryEntry 26 }

f3PtpNetPortFlowPointHistoryAvgSyncResTime OBJECT-TYPE
     SYNTAX     Unsigned32
     MAX-ACCESS read-only
     STATUS     current
     DESCRIPTION
         "The average residence time for PTP Sync messages."
     ::= { f3PtpNetPortFlowPointHistoryEntry 27 }

f3PtpNetPortFlowPointHistoryMinSyncResTime OBJECT-TYPE
     SYNTAX     Unsigned32
     MAX-ACCESS read-only
     STATUS     current
     DESCRIPTION
         "The minimum residence time for PTP Sync messages."
     ::= { f3PtpNetPortFlowPointHistoryEntry 28 }

f3PtpNetPortFlowPointHistoryMaxSyncResTime OBJECT-TYPE
     SYNTAX     Unsigned32
     MAX-ACCESS read-only
     STATUS     current
     DESCRIPTION
         "The maximum residence time for PTP Sync messages."
     ::= { f3PtpNetPortFlowPointHistoryEntry 29 }

f3PtpNetPortFlowPointHistoryAvgDelayReqResTime OBJECT-TYPE
     SYNTAX     Unsigned32
     MAX-ACCESS read-only
     STATUS     current
     DESCRIPTION
         "The average residence time for PTP Delay Request messages."
     ::= { f3PtpNetPortFlowPointHistoryEntry 30 }

f3PtpNetPortFlowPointHistoryMinDelayReqResTime OBJECT-TYPE
     SYNTAX     Unsigned32
     MAX-ACCESS read-only
     STATUS     current
     DESCRIPTION
         "The minimum residence time for PTP Delay Request messages."
     ::= { f3PtpNetPortFlowPointHistoryEntry 31 }

f3PtpNetPortFlowPointHistoryMaxDelayReqResTime OBJECT-TYPE
     SYNTAX     Unsigned32
     MAX-ACCESS read-only
     STATUS     current
     DESCRIPTION
         "The maximum residence time for PTP Delay Request messages."
     ::= { f3PtpNetPortFlowPointHistoryEntry 32 }

f3PtpNetPortFlowPointHistoryMinPDelayReqResTime OBJECT-TYPE
     SYNTAX     Unsigned32
     MAX-ACCESS read-only
     STATUS     current
     DESCRIPTION
         "The minimum residence time for PTP Peer Delay Request messages."
     ::= { f3PtpNetPortFlowPointHistoryEntry 33 }

f3PtpNetPortFlowPointHistoryMaxPDelayReqResTime OBJECT-TYPE
     SYNTAX     Unsigned32
     MAX-ACCESS read-only
     STATUS     current
     DESCRIPTION
         "The maximum residence time for PTP Peer Delay Request messages."
     ::= { f3PtpNetPortFlowPointHistoryEntry 34 }

f3PtpNetPortFlowPointHistoryAvgPDelayReqResTime OBJECT-TYPE
     SYNTAX     Unsigned32
     MAX-ACCESS read-only
     STATUS     current
     DESCRIPTION
         "The average residence time for PTP Peer Delay Request messages."
     ::= { f3PtpNetPortFlowPointHistoryEntry 35 }

f3PtpNetPortFlowPointHistoryMinPDelayRspResTime OBJECT-TYPE
     SYNTAX     Unsigned32
     MAX-ACCESS read-only
     STATUS     current
     DESCRIPTION
         "The minimum residence time for PTP Peer Delay Response messages."
     ::= { f3PtpNetPortFlowPointHistoryEntry 36 }

f3PtpNetPortFlowPointHistoryMaxPDelayRspResTime OBJECT-TYPE
     SYNTAX     Unsigned32
     MAX-ACCESS read-only
     STATUS     current
     DESCRIPTION
         "The maximum residence time for PTP Peer Delay Response messages."
     ::= { f3PtpNetPortFlowPointHistoryEntry 37 }

f3PtpNetPortFlowPointHistoryAvgPDelayRspResTime OBJECT-TYPE
     SYNTAX     Unsigned32
     MAX-ACCESS read-only
     STATUS     current
     DESCRIPTION
         "The average residence time for PTP Peer Delay Response messages."
     ::= { f3PtpNetPortFlowPointHistoryEntry 38 }

f3PtpNetPortFlowPointHistoryDestMciNoMatchDiscards OBJECT-TYPE
     SYNTAX     PerfCounter64
     MAX-ACCESS read-write
     STATUS     current
     DESCRIPTION
         "The dest MCI no match discards messages."
     ::= { f3PtpNetPortFlowPointHistoryEntry 39 }

--
-- Network Port PTP Flow Point Threshold Table
--
f3PtpNetPortFlowPointThresholdTable OBJECT-TYPE
    SYNTAX      SEQUENCE OF F3PtpNetPortFlowPointThresholdEntry
    MAX-ACCESS  not-accessible
    STATUS      current
    DESCRIPTION
            "A table of entries that allow manageability of Access Port PTP Flow Point
             Thresholds."
    ::= { f3PtpPerformanceObjects 6 }

f3PtpNetPortFlowPointThresholdEntry OBJECT-TYPE
    SYNTAX      F3PtpNetPortFlowPointThresholdEntry
    MAX-ACCESS  not-accessible
    STATUS      current
    DESCRIPTION
            "A conceptual row in the f3PtpNetPortFlowPointThresholdTable."
    INDEX { neIndex, shelfIndex, slotIndex, cmEthernetNetPortIndex, 
            f3PtpNetPortFlowPointIndex, f3PtpNetPortFlowPointStatsIndex, 
            f3PtpNetPortFlowPointThresholdIndex }
    ::= { f3PtpNetPortFlowPointThresholdTable 1 }

F3PtpNetPortFlowPointThresholdEntry ::= SEQUENCE {
    f3PtpNetPortFlowPointThresholdIndex       Integer32,
    f3PtpNetPortFlowPointThresholdInterval    CmPmIntervalType,
    f3PtpNetPortFlowPointThresholdVariable    VariablePointer,
    f3PtpNetPortFlowPointThresholdValueLo     Unsigned32,
    f3PtpNetPortFlowPointThresholdValueHi     Unsigned32,
    f3PtpNetPortFlowPointThresholdMonValue    PerfCounter64
}

f3PtpNetPortFlowPointThresholdIndex OBJECT-TYPE
    SYNTAX     Integer32 (1..65535)
    MAX-ACCESS not-accessible
    STATUS     current
    DESCRIPTION
        "An index that uniquely identifies an entry in the
        f3PtpNetPortFlowPointThresholdTable."
    ::= { f3PtpNetPortFlowPointThresholdEntry 1 }

f3PtpNetPortFlowPointThresholdInterval OBJECT-TYPE
    SYNTAX     CmPmIntervalType
    MAX-ACCESS read-only
    STATUS     current
    DESCRIPTION
        "The interval over which monitored value is
        sampled and compared with the specified threshold."
    ::= { f3PtpNetPortFlowPointThresholdEntry 2 }

f3PtpNetPortFlowPointThresholdVariable OBJECT-TYPE
    SYNTAX     VariablePointer
    MAX-ACCESS read-only
    STATUS     current
    DESCRIPTION
        "The object identifier of the particular variable to be
        sampled."
    ::= { f3PtpNetPortFlowPointThresholdEntry 3 }

f3PtpNetPortFlowPointThresholdValueLo OBJECT-TYPE
    SYNTAX     Unsigned32
    MAX-ACCESS read-write
    STATUS     current
    DESCRIPTION
        "Lower 32 bits of the threshold value."
    ::= { f3PtpNetPortFlowPointThresholdEntry 4 }

f3PtpNetPortFlowPointThresholdValueHi OBJECT-TYPE
    SYNTAX     Unsigned32
    MAX-ACCESS read-write
    STATUS     current
    DESCRIPTION
        "Higher 32 bits of the threshold value."
    ::= { f3PtpNetPortFlowPointThresholdEntry 5 }

f3PtpNetPortFlowPointThresholdMonValue OBJECT-TYPE
    SYNTAX     PerfCounter64
    MAX-ACCESS read-only
    STATUS     current
    DESCRIPTION
        "Monitored value corresponding to f3PtpNetPortFlowPointThresholdVariable."
    ::= { f3PtpNetPortFlowPointThresholdEntry 6 }

--
-- Slave Only Ordinary Clock Current Statistics Table
--
f3PtpSOOCStatsTable OBJECT-TYPE
    SYNTAX      SEQUENCE OF F3PtpSOOCStatsEntry
    MAX-ACCESS  not-accessible
    STATUS      current
    DESCRIPTION
            "A collection of Slave Only Ordinary Clock related statistics.  
             These reflect the current data."
    ::= { f3PtpPerformanceObjects 7 }

f3PtpSOOCStatsEntry OBJECT-TYPE
    SYNTAX      F3PtpSOOCStatsEntry 
    MAX-ACCESS  not-accessible
    STATUS      current
    DESCRIPTION
            "A conceptual row in the f3PtpSOOCStatsTable.
             Entries exist in this table for each Slave Only Ordinary Clock."
    INDEX { neIndex, f3PtpTSIndex,  
                     f3PtpSOOCIndex, f3PtpSOOCStatsIndex }
    ::= { f3PtpSOOCStatsTable 1 }

F3PtpSOOCStatsEntry ::= SEQUENCE {
    f3PtpSOOCStatsIndex                       Integer32,
    f3PtpSOOCStatsIntervalType                CmPmIntervalType,
    f3PtpSOOCStatsValid                       TruthValue,
    f3PtpSOOCStatsAction                      CmPmBinAction,
    f3PtpSOOCStatsMinOffsetFromMaster         ScaledNanoseconds,
    f3PtpSOOCStatsMaxOffsetFromMaster         ScaledNanoseconds,
    f3PtpSOOCStatsAvgOffsetFromMaster         ScaledNanoseconds,
    f3PtpSOOCStatsMinMeanPathDelay            ScaledNanoseconds,
    f3PtpSOOCStatsMaxMeanPathDelay            ScaledNanoseconds,
    f3PtpSOOCStatsAvgMeanPathDelay            ScaledNanoseconds,
    f3PtpSOOCStatsMinSyncPathDelay            ScaledNanoseconds,
    f3PtpSOOCStatsMaxSyncPathDelay            ScaledNanoseconds,
    f3PtpSOOCStatsAvgSyncPathDelay            ScaledNanoseconds,
    f3PtpSOOCStatsMinSyncPDV                  ScaledNanoseconds,
    f3PtpSOOCStatsMaxSyncPDV                  ScaledNanoseconds,
    f3PtpSOOCStatsAvgSyncPDV                  ScaledNanoseconds,
    f3PtpSOOCStatsMgmtMsgsDiscarded           PerfCounter64,
    f3PtpSOOCStatsInvalidMsgLenDiscards       PerfCounter64,
    f3PtpSOOCStatsUnknownMasterDiscards       PerfCounter64,
    f3PtpSOOCStatsUnknownDomainDiscards       PerfCounter64,
    f3PtpSOOCStatsMulticastAnnounceDiscards   PerfCounter64,
    f3PtpSOOCStatsOutOfSeqAnnounceMsgs        PerfCounter64,
    f3PtpSOOCStatsMulticastSyncDiscards       PerfCounter64,
    f3PtpSOOCStatsTwoStepSyncDiscards         PerfCounter64,
    f3PtpSOOCStatsFollowupDiscards            PerfCounter64,
    f3PtpSOOCStatsDelayReqDiscards            PerfCounter64,
    f3PtpSOOCStatsPDelayReqDiscards           PerfCounter64,
    f3PtpSOOCStatsPDelayRspDiscards           PerfCounter64,
    f3PtpSOOCStatsPDelayFollowupDiscards      PerfCounter64,
    f3PtpSOOCStatsInvalidTLVLenDiscards       PerfCounter64,
    f3PtpSOOCStatsInvalidTLVTypeDiscards      PerfCounter64,
    f3PtpSOOCStatsMaxFwdFlowWeight            Integer32,
    f3PtpSOOCStatsAvgFwdFlowWeight            Integer32,
    f3PtpSOOCStatsMinRevFlowWeight            Integer32,
    f3PtpSOOCStatsMaxRevFlowWeight            Integer32,
    f3PtpSOOCStatsAvgRevFlowWeight            Integer32,
    f3PtpSOOCStatsNumClockRecTransients       Unsigned32
}

f3PtpSOOCStatsIndex OBJECT-TYPE
    SYNTAX      Integer32 (1..4)
    MAX-ACCESS  not-accessible
    STATUS      current
    DESCRIPTION
            "An arbitrary integer index value used to uniquely identify
            this Slave Only Ordinary Clock statistics entry. 
            1 - 15min
            2 - 1day
            3 - rollover
            4 - 5min"
    ::= { f3PtpSOOCStatsEntry 1 }

f3PtpSOOCStatsIntervalType OBJECT-TYPE
    SYNTAX      CmPmIntervalType
    MAX-ACCESS  read-only
    STATUS      current
    DESCRIPTION
            "Indicates the type of collection, i.e. whether it is
             15 Min, 1 Day or rollover."
    ::= { f3PtpSOOCStatsEntry 2 }

f3PtpSOOCStatsValid OBJECT-TYPE
    SYNTAX      TruthValue
    MAX-ACCESS  read-only
    STATUS      current
    DESCRIPTION
            "Indicates the validity of the bin."
    ::= { f3PtpSOOCStatsEntry 3 }

f3PtpSOOCStatsAction OBJECT-TYPE
    SYNTAX      CmPmBinAction
    MAX-ACCESS  read-write
    STATUS      current
    DESCRIPTION
            "Allows the Manager to clear the bin."
    ::= { f3PtpSOOCStatsEntry 4 }

f3PtpSOOCStatsMinOffsetFromMaster OBJECT-TYPE
     SYNTAX     ScaledNanoseconds  
     MAX-ACCESS read-only
     STATUS     current
     DESCRIPTION
         "Minimum Offset from Master"
     ::= { f3PtpSOOCStatsEntry 5 }

f3PtpSOOCStatsMaxOffsetFromMaster OBJECT-TYPE
     SYNTAX     ScaledNanoseconds  
     MAX-ACCESS read-only
     STATUS     current
     DESCRIPTION
         "Maximum Offset from Master"
     ::= { f3PtpSOOCStatsEntry 6 }

f3PtpSOOCStatsAvgOffsetFromMaster OBJECT-TYPE
     SYNTAX     ScaledNanoseconds  
     MAX-ACCESS read-only
     STATUS     current
     DESCRIPTION
         "Average Offset from Master"
     ::= { f3PtpSOOCStatsEntry 7 }

f3PtpSOOCStatsMinMeanPathDelay OBJECT-TYPE
     SYNTAX     ScaledNanoseconds 
     MAX-ACCESS read-only
     STATUS     current
     DESCRIPTION
         "The minimum mean path delay at the SOOC."
     ::= { f3PtpSOOCStatsEntry 8 }

f3PtpSOOCStatsMaxMeanPathDelay OBJECT-TYPE
     SYNTAX     ScaledNanoseconds 
     MAX-ACCESS read-only
     STATUS     current
     DESCRIPTION
         "The maximum mean path delay at the SOOC."
     ::= { f3PtpSOOCStatsEntry 9 }

f3PtpSOOCStatsAvgMeanPathDelay OBJECT-TYPE
     SYNTAX     ScaledNanoseconds 
     MAX-ACCESS read-only
     STATUS     current
     DESCRIPTION
         "The average mean path delay at the SOOC."
     ::= { f3PtpSOOCStatsEntry 10 }

f3PtpSOOCStatsMinSyncPathDelay OBJECT-TYPE
     SYNTAX     ScaledNanoseconds 
     MAX-ACCESS read-only
     STATUS     current
     DESCRIPTION
         "The minimum mean path delay of Sync messages at the SOOC."
     ::= { f3PtpSOOCStatsEntry 11 }

f3PtpSOOCStatsMaxSyncPathDelay OBJECT-TYPE
     SYNTAX     ScaledNanoseconds 
     MAX-ACCESS read-only
     STATUS     current
     DESCRIPTION
         "The maximum mean path delay of Sync messages at the SOOC."
     ::= { f3PtpSOOCStatsEntry 12 }

f3PtpSOOCStatsAvgSyncPathDelay OBJECT-TYPE
     SYNTAX     ScaledNanoseconds
     MAX-ACCESS read-only
     STATUS     current
     DESCRIPTION
         "The average mean path delay of Sync messages at the SOOC."
     ::= { f3PtpSOOCStatsEntry 13 }

f3PtpSOOCStatsMinSyncPDV OBJECT-TYPE
     SYNTAX     ScaledNanoseconds
     MAX-ACCESS read-only
     STATUS     current
     DESCRIPTION
         "The minimum Sync message path delay variation at the SOOC."
     ::= { f3PtpSOOCStatsEntry 14 }

f3PtpSOOCStatsMaxSyncPDV OBJECT-TYPE
     SYNTAX     ScaledNanoseconds
     MAX-ACCESS read-only
     STATUS     current
     DESCRIPTION
         "The maximum Sync message path delay variation at the SOOC."
     ::= { f3PtpSOOCStatsEntry 15 }

f3PtpSOOCStatsAvgSyncPDV OBJECT-TYPE
     SYNTAX     ScaledNanoseconds
     MAX-ACCESS read-only
     STATUS     current
     DESCRIPTION
         "The average Sync message packet delay variation at the SOOC."
     ::= { f3PtpSOOCStatsEntry 16 }

f3PtpSOOCStatsMgmtMsgsDiscarded OBJECT-TYPE
     SYNTAX     PerfCounter64
     MAX-ACCESS read-only
     STATUS     current
     DESCRIPTION
         "The number of PTP management messages discarded at the SOOC."
     ::= { f3PtpSOOCStatsEntry 17 }

f3PtpSOOCStatsInvalidMsgLenDiscards OBJECT-TYPE
     SYNTAX     PerfCounter64
     MAX-ACCESS read-only
     STATUS     current
     DESCRIPTION
         "The number of messages discarded due to invalid message length at the SOOC."
     ::= { f3PtpSOOCStatsEntry 18 }

f3PtpSOOCStatsUnknownMasterDiscards OBJECT-TYPE
     SYNTAX     PerfCounter64
     MAX-ACCESS read-only
     STATUS     current
     DESCRIPTION
         "The number of messages discard due to unknown Master at the SOOC."
     ::= { f3PtpSOOCStatsEntry 19 }

f3PtpSOOCStatsUnknownDomainDiscards OBJECT-TYPE
     SYNTAX     PerfCounter64
     MAX-ACCESS read-only
     STATUS     current
     DESCRIPTION
         "The number of messages discard due to unknown domain at the SOOC."
     ::= { f3PtpSOOCStatsEntry 20 }

f3PtpSOOCStatsMulticastAnnounceDiscards OBJECT-TYPE
     SYNTAX     PerfCounter64
     MAX-ACCESS read-only
     STATUS     current
     DESCRIPTION
         "The number of multicast Announce message discards at the SOOC."
     ::= { f3PtpSOOCStatsEntry 21 }

f3PtpSOOCStatsOutOfSeqAnnounceMsgs OBJECT-TYPE
     SYNTAX     PerfCounter64
     MAX-ACCESS read-only
     STATUS     current
     DESCRIPTION
         "The number of out-of-sequence Announce message discards at the SOOC."
     ::= { f3PtpSOOCStatsEntry 22 }

f3PtpSOOCStatsMulticastSyncDiscards OBJECT-TYPE
     SYNTAX     PerfCounter64
     MAX-ACCESS read-only
     STATUS     current
     DESCRIPTION
         "The number of Multicast Sync discards at the SOOC."
     ::= { f3PtpSOOCStatsEntry 23 }

f3PtpSOOCStatsTwoStepSyncDiscards OBJECT-TYPE
     SYNTAX     PerfCounter64
     MAX-ACCESS read-only
     STATUS     current
     DESCRIPTION
         "The number of Two Step Sync discards at the SOOC."
     ::= { f3PtpSOOCStatsEntry 24 }

f3PtpSOOCStatsFollowupDiscards OBJECT-TYPE
     SYNTAX     PerfCounter64
     MAX-ACCESS read-only
     STATUS     current
     DESCRIPTION
         "The number of Follow up discards at the SOOC."
     ::= { f3PtpSOOCStatsEntry 25 }

f3PtpSOOCStatsDelayReqDiscards OBJECT-TYPE
     SYNTAX     PerfCounter64
     MAX-ACCESS read-only
     STATUS     current
     DESCRIPTION
         "The number of Delay Request discards at the SOOC."
     ::= { f3PtpSOOCStatsEntry 26 }

f3PtpSOOCStatsPDelayReqDiscards OBJECT-TYPE
     SYNTAX     PerfCounter64
     MAX-ACCESS read-only
     STATUS     current
     DESCRIPTION
         "The number of P-Delay Request discards at the SOOC."
     ::= { f3PtpSOOCStatsEntry 27 }

f3PtpSOOCStatsPDelayRspDiscards OBJECT-TYPE
     SYNTAX     PerfCounter64
     MAX-ACCESS read-only
     STATUS     current
     DESCRIPTION
         "The number of P-Delay Response discards at the SOOC."
     ::= { f3PtpSOOCStatsEntry 28 }

f3PtpSOOCStatsPDelayFollowupDiscards OBJECT-TYPE
     SYNTAX     PerfCounter64
     MAX-ACCESS read-only
     STATUS     current
     DESCRIPTION
         "The number of P-Delay Followup discards at the SOOC."
     ::= { f3PtpSOOCStatsEntry 29 }

f3PtpSOOCStatsInvalidTLVLenDiscards OBJECT-TYPE
     SYNTAX     PerfCounter64
     MAX-ACCESS read-only
     STATUS     current
     DESCRIPTION
         "The number of discards due to invalid TLV Length at the SOOC."
     ::= { f3PtpSOOCStatsEntry 30 }

f3PtpSOOCStatsInvalidTLVTypeDiscards OBJECT-TYPE
     SYNTAX     PerfCounter64
     MAX-ACCESS read-only
     STATUS     current
     DESCRIPTION
         "The number of discards due to invalid TLV type at the SOOC."
     ::= { f3PtpSOOCStatsEntry 31 }

f3PtpSOOCStatsMaxFwdFlowWeight OBJECT-TYPE
     SYNTAX     Integer32
     MAX-ACCESS read-write
     STATUS     current
     DESCRIPTION
         "The max forward flow weight for this entry."
     ::= { f3PtpSOOCStatsEntry 32 }

f3PtpSOOCStatsAvgFwdFlowWeight OBJECT-TYPE
     SYNTAX     Integer32
     MAX-ACCESS read-write
     STATUS     current
     DESCRIPTION
         "The average forward flow weight for this entry."
     ::= { f3PtpSOOCStatsEntry 33 }

f3PtpSOOCStatsMinRevFlowWeight OBJECT-TYPE
     SYNTAX     Integer32
     MAX-ACCESS read-write
     STATUS     current
     DESCRIPTION
         "The min reverted flow weight for this entry."
     ::= { f3PtpSOOCStatsEntry 34 }

f3PtpSOOCStatsMaxRevFlowWeight OBJECT-TYPE
     SYNTAX     Integer32
     MAX-ACCESS read-write
     STATUS     current
     DESCRIPTION
         "The max reverted flow weight for this entry."
     ::= { f3PtpSOOCStatsEntry 35 }

f3PtpSOOCStatsAvgRevFlowWeight OBJECT-TYPE
     SYNTAX     Integer32
     MAX-ACCESS read-write
     STATUS     current
     DESCRIPTION
         "The average reverted flow weight for this entry."
     ::= { f3PtpSOOCStatsEntry 36 }

f3PtpSOOCStatsNumClockRecTransients OBJECT-TYPE
     SYNTAX     Unsigned32
     MAX-ACCESS read-write
     STATUS     current
     DESCRIPTION
         "The number of clock recovery transients for this entry."
     ::= { f3PtpSOOCStatsEntry 37 }


-- Slave Only Ordinary Clock History Table
--
f3PtpSOOCHistoryTable OBJECT-TYPE
    SYNTAX      SEQUENCE OF F3PtpSOOCHistoryEntry
    MAX-ACCESS  not-accessible
    STATUS      current
    DESCRIPTION
            "A collection of Slave Only Ordinary Clock related statistics.  
             These reflect the current data."
    ::= { f3PtpPerformanceObjects 8 }

f3PtpSOOCHistoryEntry OBJECT-TYPE
    SYNTAX      F3PtpSOOCHistoryEntry 
    MAX-ACCESS  not-accessible
    STATUS      current
    DESCRIPTION
            "A conceptual row in the f3PtpSOOCHistoryTable.
             Entries exist in this table for each Slave Only Ordinary Clock."
    INDEX { neIndex, f3PtpTSIndex,  
            f3PtpSOOCIndex, f3PtpSOOCStatsIndex, f3PtpSOOCHistoryIndex }
    ::= { f3PtpSOOCHistoryTable 1 }

F3PtpSOOCHistoryEntry ::= SEQUENCE {
    f3PtpSOOCHistoryIndex                     Integer32,
    f3PtpSOOCHistoryTime                      DateAndTime,
    f3PtpSOOCHistoryValid                     TruthValue,
    f3PtpSOOCHistoryAction                    CmPmBinAction,
    f3PtpSOOCHistoryMinOffsetFromMaster       ScaledNanoseconds,
    f3PtpSOOCHistoryMaxOffsetFromMaster       ScaledNanoseconds,
    f3PtpSOOCHistoryAvgOffsetFromMaster       ScaledNanoseconds,
    f3PtpSOOCHistoryMinMeanPathDelay          ScaledNanoseconds,
    f3PtpSOOCHistoryMaxMeanPathDelay          ScaledNanoseconds,
    f3PtpSOOCHistoryAvgMeanPathDelay          ScaledNanoseconds,
    f3PtpSOOCHistoryMinSyncPathDelay          ScaledNanoseconds,
    f3PtpSOOCHistoryMaxSyncPathDelay          ScaledNanoseconds,
    f3PtpSOOCHistoryAvgSyncPathDelay          ScaledNanoseconds,
    f3PtpSOOCHistoryMinSyncPDV                ScaledNanoseconds,
    f3PtpSOOCHistoryMaxSyncPDV                ScaledNanoseconds,
    f3PtpSOOCHistoryAvgSyncPDV                ScaledNanoseconds,
    f3PtpSOOCHistoryMgmtMsgsDiscarded         PerfCounter64,
    f3PtpSOOCHistoryInvalidMsgLenDiscards     PerfCounter64,
    f3PtpSOOCHistoryUnknownMasterDiscards     PerfCounter64,
    f3PtpSOOCHistoryUnknownDomainDiscards     PerfCounter64,
    f3PtpSOOCHistoryMulticastAnnounceDiscards PerfCounter64,
    f3PtpSOOCHistoryOutOfSeqAnnounceMsgs      PerfCounter64,
    f3PtpSOOCHistoryMulticastSyncDiscards     PerfCounter64,
    f3PtpSOOCHistoryTwoStepSyncDiscards       PerfCounter64,
    f3PtpSOOCHistoryFollowupDiscards          PerfCounter64,
    f3PtpSOOCHistoryDelayReqDiscards          PerfCounter64,
    f3PtpSOOCHistoryPDelayReqDiscards         PerfCounter64,
    f3PtpSOOCHistoryPDelayRspDiscards         PerfCounter64,
    f3PtpSOOCHistoryPDelayFollowupDiscards    PerfCounter64,
    f3PtpSOOCHistoryInvalidTLVLenDiscards     PerfCounter64,
    f3PtpSOOCHistoryInvalidTLVTypeDiscards    PerfCounter64,
    f3PtpSOOCHistoryMaxFwdFlowWeight          Integer32,
    f3PtpSOOCHistoryAvgFwdFlowWeight          Integer32,
    f3PtpSOOCHistoryMinRevFlowWeight          Integer32,
    f3PtpSOOCHistoryMaxRevFlowWeight          Integer32,
    f3PtpSOOCHistoryAvgRevFlowWeight          Integer32,
    f3PtpSOOCHistoryNumClockRecTransients     Unsigned32
}

f3PtpSOOCHistoryIndex OBJECT-TYPE
    SYNTAX      Integer32 (1..32)
    MAX-ACCESS  not-accessible
    STATUS      current
    DESCRIPTION
            "An arbitrary integer index value used to uniquely identify
            this Slave Only Ordinary Clock statistics entry. 
            Index 1 corresponds to 15minute, index 2 to 1 day and index
            3 corresponds to rollover."
    ::= { f3PtpSOOCHistoryEntry 1 }

f3PtpSOOCHistoryTime OBJECT-TYPE
    SYNTAX      DateAndTime
    MAX-ACCESS  read-only
    STATUS      current
    DESCRIPTION
            "Indicates the time of history bin creation." 
    ::= { f3PtpSOOCHistoryEntry 2 }

f3PtpSOOCHistoryValid OBJECT-TYPE
    SYNTAX      TruthValue
    MAX-ACCESS  read-only
    STATUS      current
    DESCRIPTION
            "Indicates the validity of the bin."
    ::= { f3PtpSOOCHistoryEntry 3 }

f3PtpSOOCHistoryAction OBJECT-TYPE
    SYNTAX      CmPmBinAction
    MAX-ACCESS  read-write
    STATUS      current
    DESCRIPTION
            "Allows the Manager to clear the bin."
    ::= { f3PtpSOOCHistoryEntry 4 }

f3PtpSOOCHistoryMinOffsetFromMaster OBJECT-TYPE
     SYNTAX    ScaledNanoseconds 
     MAX-ACCESS read-only
     STATUS     current
     DESCRIPTION
         "Minimum Offset from Master"
     ::= { f3PtpSOOCHistoryEntry 5 }

f3PtpSOOCHistoryMaxOffsetFromMaster OBJECT-TYPE
     SYNTAX    ScaledNanoseconds 
     MAX-ACCESS read-only
     STATUS     current
     DESCRIPTION
         "Maximum Offset from Master"
     ::= { f3PtpSOOCHistoryEntry 6 }

f3PtpSOOCHistoryAvgOffsetFromMaster OBJECT-TYPE
     SYNTAX    ScaledNanoseconds 
     MAX-ACCESS read-only
     STATUS     current
     DESCRIPTION
         "Average Offset from Master"
     ::= { f3PtpSOOCHistoryEntry 7 }

f3PtpSOOCHistoryMinMeanPathDelay OBJECT-TYPE
     SYNTAX    ScaledNanoseconds 
     MAX-ACCESS read-only
     STATUS     current
     DESCRIPTION
         "The minimum mean path delay at the SOOC."
     ::= { f3PtpSOOCHistoryEntry 8 }

f3PtpSOOCHistoryMaxMeanPathDelay OBJECT-TYPE
     SYNTAX    ScaledNanoseconds 
     MAX-ACCESS read-only
     STATUS     current
     DESCRIPTION
         "The maximum mean path delay at the SOOC."
     ::= { f3PtpSOOCHistoryEntry 9 }

f3PtpSOOCHistoryAvgMeanPathDelay OBJECT-TYPE
     SYNTAX    ScaledNanoseconds 
     MAX-ACCESS read-only
     STATUS     current
     DESCRIPTION
         "The average mean path delay at the SOOC."
     ::= { f3PtpSOOCHistoryEntry 10 }

f3PtpSOOCHistoryMinSyncPathDelay OBJECT-TYPE
     SYNTAX    ScaledNanoseconds 
     MAX-ACCESS read-only
     STATUS     current
     DESCRIPTION
         "The minimum mean path delay of Sync messages at the SOOC."
     ::= { f3PtpSOOCHistoryEntry 11 }

f3PtpSOOCHistoryMaxSyncPathDelay OBJECT-TYPE
     SYNTAX    ScaledNanoseconds 
     MAX-ACCESS read-only
     STATUS     current
     DESCRIPTION
         "The maximum mean path delay of Sync messages at the SOOC."
     ::= { f3PtpSOOCHistoryEntry 12 }

f3PtpSOOCHistoryAvgSyncPathDelay OBJECT-TYPE
     SYNTAX    ScaledNanoseconds 
     MAX-ACCESS read-only
     STATUS     current
     DESCRIPTION
         "The average mean path delay of Sync messages at the SOOC."
     ::= { f3PtpSOOCHistoryEntry 13 }

f3PtpSOOCHistoryMinSyncPDV OBJECT-TYPE
     SYNTAX    ScaledNanoseconds 
     MAX-ACCESS read-only
     STATUS     current
     DESCRIPTION
         "The minimum Sync message path delay variation at the SOOC."
     ::= { f3PtpSOOCHistoryEntry 14 }

f3PtpSOOCHistoryMaxSyncPDV OBJECT-TYPE
     SYNTAX    ScaledNanoseconds 
     MAX-ACCESS read-only
     STATUS     current
     DESCRIPTION
         "The maximum Sync message path delay variation at the SOOC."
     ::= { f3PtpSOOCHistoryEntry 15 }

f3PtpSOOCHistoryAvgSyncPDV OBJECT-TYPE
     SYNTAX    ScaledNanoseconds 
     MAX-ACCESS read-only
     STATUS     current
     DESCRIPTION
         "The average Sync message packet delay variation at the SOOC."
     ::= { f3PtpSOOCHistoryEntry 16 }

f3PtpSOOCHistoryMgmtMsgsDiscarded OBJECT-TYPE
     SYNTAX     PerfCounter64
     MAX-ACCESS read-only
     STATUS     current
     DESCRIPTION
         "The number of PTP management messages discarded at the SOOC."
     ::= { f3PtpSOOCHistoryEntry 17 }

f3PtpSOOCHistoryInvalidMsgLenDiscards OBJECT-TYPE
     SYNTAX     PerfCounter64
     MAX-ACCESS read-only
     STATUS     current
     DESCRIPTION
         "The number of messages discarded due to invalid message length at the SOOC."
     ::= { f3PtpSOOCHistoryEntry 18 }

f3PtpSOOCHistoryUnknownMasterDiscards OBJECT-TYPE
     SYNTAX     PerfCounter64
     MAX-ACCESS read-only
     STATUS     current
     DESCRIPTION
         "The number of messages discard due to unknown Master at the SOOC."
     ::= { f3PtpSOOCHistoryEntry 19 }

f3PtpSOOCHistoryUnknownDomainDiscards OBJECT-TYPE
     SYNTAX     PerfCounter64
     MAX-ACCESS read-only
     STATUS     current
     DESCRIPTION
         "The number of messages discard due to unknown domain at the SOOC."
     ::= { f3PtpSOOCHistoryEntry 20 }

f3PtpSOOCHistoryMulticastAnnounceDiscards OBJECT-TYPE
     SYNTAX     PerfCounter64
     MAX-ACCESS read-only
     STATUS     current
     DESCRIPTION
         "The number of multicast Announce message discards at the SOOC."
     ::= { f3PtpSOOCHistoryEntry 21 }

f3PtpSOOCHistoryOutOfSeqAnnounceMsgs OBJECT-TYPE
     SYNTAX     PerfCounter64
     MAX-ACCESS read-only
     STATUS     current
     DESCRIPTION
         "The number of out-of-sequence Announce message discards at the SOOC."
     ::= { f3PtpSOOCHistoryEntry 22 }

f3PtpSOOCHistoryMulticastSyncDiscards OBJECT-TYPE
     SYNTAX     PerfCounter64
     MAX-ACCESS read-only
     STATUS     current
     DESCRIPTION
         "The number of Multicast Sync discards at the SOOC."
     ::= { f3PtpSOOCHistoryEntry 23 }

f3PtpSOOCHistoryTwoStepSyncDiscards OBJECT-TYPE
     SYNTAX     PerfCounter64
     MAX-ACCESS read-only
     STATUS     current
     DESCRIPTION
         "The number of Two Step Sync discards at the SOOC."
     ::= { f3PtpSOOCHistoryEntry 24 }

f3PtpSOOCHistoryFollowupDiscards OBJECT-TYPE
     SYNTAX     PerfCounter64
     MAX-ACCESS read-only
     STATUS     current
     DESCRIPTION
         "The number of Follow up discards at the SOOC."
     ::= { f3PtpSOOCHistoryEntry 25 }

f3PtpSOOCHistoryDelayReqDiscards OBJECT-TYPE
     SYNTAX     PerfCounter64
     MAX-ACCESS read-only
     STATUS     current
     DESCRIPTION
         "The number of Delay Request discards at the SOOC."
     ::= { f3PtpSOOCHistoryEntry 26 }

f3PtpSOOCHistoryPDelayReqDiscards OBJECT-TYPE
     SYNTAX     PerfCounter64
     MAX-ACCESS read-only
     STATUS     current
     DESCRIPTION
         "The number of P-Delay Request discards at the SOOC."
     ::= { f3PtpSOOCHistoryEntry 27 }

f3PtpSOOCHistoryPDelayRspDiscards OBJECT-TYPE
     SYNTAX     PerfCounter64
     MAX-ACCESS read-only
     STATUS     current
     DESCRIPTION
         "The number of P-Delay Response discards at the SOOC."
     ::= { f3PtpSOOCHistoryEntry 28 }

f3PtpSOOCHistoryPDelayFollowupDiscards OBJECT-TYPE
     SYNTAX     PerfCounter64
     MAX-ACCESS read-only
     STATUS     current
     DESCRIPTION
         "The number of P-Delay Followup discards at the SOOC."
     ::= { f3PtpSOOCHistoryEntry 29 }

f3PtpSOOCHistoryInvalidTLVLenDiscards OBJECT-TYPE
     SYNTAX     PerfCounter64
     MAX-ACCESS read-only
     STATUS     current
     DESCRIPTION
         "The number of discards due to invalid TLV Length at the SOOC."
     ::= { f3PtpSOOCHistoryEntry 30 }

f3PtpSOOCHistoryInvalidTLVTypeDiscards OBJECT-TYPE
     SYNTAX     PerfCounter64
     MAX-ACCESS read-only
     STATUS     current
     DESCRIPTION
         "The number of discards due to invalid TLV type at the SOOC."
     ::= { f3PtpSOOCHistoryEntry 31 }

f3PtpSOOCHistoryMaxFwdFlowWeight OBJECT-TYPE
     SYNTAX     Integer32
     MAX-ACCESS read-write
     STATUS     current
     DESCRIPTION
         "The max forward flow weight for this entry."
     ::= { f3PtpSOOCHistoryEntry 32 }

f3PtpSOOCHistoryAvgFwdFlowWeight OBJECT-TYPE
     SYNTAX     Integer32
     MAX-ACCESS read-write
     STATUS     current
     DESCRIPTION
         "The average forward flow weight for this entry."
     ::= { f3PtpSOOCHistoryEntry 33 }

f3PtpSOOCHistoryMinRevFlowWeight OBJECT-TYPE
     SYNTAX     Integer32
     MAX-ACCESS read-write
     STATUS     current
     DESCRIPTION
         "The min reverted flow weight for this entry."
     ::= { f3PtpSOOCHistoryEntry 34 }

f3PtpSOOCHistoryMaxRevFlowWeight OBJECT-TYPE
     SYNTAX     Integer32
     MAX-ACCESS read-write
     STATUS     current
     DESCRIPTION
         "The max reverted flow weight for this entry."
     ::= { f3PtpSOOCHistoryEntry 35 }

f3PtpSOOCHistoryAvgRevFlowWeight OBJECT-TYPE
     SYNTAX     Integer32
     MAX-ACCESS read-write
     STATUS     current
     DESCRIPTION
         "The average reverted flow weight for this entry."
     ::= { f3PtpSOOCHistoryEntry 36 }

f3PtpSOOCHistoryNumClockRecTransients OBJECT-TYPE
     SYNTAX     Unsigned32
     MAX-ACCESS read-write
     STATUS     current
     DESCRIPTION
         "The number of clock recovery transients for this entry."
     ::= { f3PtpSOOCHistoryEntry 37 }

--
-- Slave Only Ordinary Clock Threshold Table
--
f3PtpSOOCThresholdTable OBJECT-TYPE
    SYNTAX      SEQUENCE OF F3PtpSOOCThresholdEntry
    MAX-ACCESS  not-accessible
    STATUS      current
    DESCRIPTION
            "A table of entries that allow manageability 
             of Slave Only Ordinary Clock Thresholds. 
             Below MonTypes should be treated as nanoseconds 
             despite being ScaledNanoseconds in Stats and History:
             - f3PtpSOOCStatsMinOffsetFromMaster,
             - f3PtpSOOCStatsMaxOffsetFromMaster,
             - f3PtpSOOCStatsAvgOffsetFromMaster,
             - f3PtpSOOCStatsMinMeanPathDelay,
             - f3PtpSOOCStatsMaxMeanPathDelay,
             - f3PtpSOOCStatsAvgMeanPathDelay,
             - f3PtpSOOCStatsMinSyncPathDelay,
             - f3PtpSOOCStatsMaxSyncPathDelay,
             - f3PtpSOOCStatsAvgSyncPathDelay,
             - f3PtpSOOCStatsMinSyncPDV,
             - f3PtpSOOCStatsMaxSyncPDV,
             - f3PtpSOOCStatsAvgSyncPDV"
    ::= { f3PtpPerformanceObjects 9 }

f3PtpSOOCThresholdEntry OBJECT-TYPE
    SYNTAX      F3PtpSOOCThresholdEntry
    MAX-ACCESS  not-accessible
    STATUS      current
    DESCRIPTION
            "A conceptual row in the f3PtpSOOCThresholdTable."
    INDEX { neIndex, f3PtpTSIndex,  
            f3PtpSOOCIndex, f3PtpSOOCStatsIndex, f3PtpSOOCThresholdIndex }
    ::= { f3PtpSOOCThresholdTable 1 }

F3PtpSOOCThresholdEntry ::= SEQUENCE {
    f3PtpSOOCThresholdIndex       Integer32,
    f3PtpSOOCThresholdInterval    CmPmIntervalType,
    f3PtpSOOCThresholdVariable    VariablePointer,
    f3PtpSOOCThresholdValueLo     Unsigned32,
    f3PtpSOOCThresholdValueHi     Unsigned32,
    f3PtpSOOCThresholdMonValue    PerfCounter64
}

f3PtpSOOCThresholdIndex OBJECT-TYPE
    SYNTAX     Integer32 (1..65535)
    MAX-ACCESS not-accessible
    STATUS     current
    DESCRIPTION
        "An index that uniquely identifies an entry in the
        f3PtpSOOCThresholdTable."
    ::= { f3PtpSOOCThresholdEntry 1 }

f3PtpSOOCThresholdInterval OBJECT-TYPE
    SYNTAX     CmPmIntervalType
    MAX-ACCESS read-only
    STATUS     current
    DESCRIPTION
        "The interval over which monitored value is
        sampled and compared with the specified threshold."
    ::= { f3PtpSOOCThresholdEntry 2 }

f3PtpSOOCThresholdVariable OBJECT-TYPE
    SYNTAX     VariablePointer
    MAX-ACCESS read-only
    STATUS     current
    DESCRIPTION
        "The object identifier of the particular variable to be
        sampled."
    ::= { f3PtpSOOCThresholdEntry 3 }

f3PtpSOOCThresholdValueLo OBJECT-TYPE
    SYNTAX     Unsigned32
    MAX-ACCESS read-write
    STATUS     current
    DESCRIPTION
        "Lower 32 bits of the threshold value."
    ::= { f3PtpSOOCThresholdEntry 4 }

f3PtpSOOCThresholdValueHi OBJECT-TYPE
    SYNTAX     Unsigned32
    MAX-ACCESS read-write
    STATUS     current
    DESCRIPTION
        "Higher 32 bits of the threshold value."
    ::= { f3PtpSOOCThresholdEntry 5 }

f3PtpSOOCThresholdMonValue OBJECT-TYPE
    SYNTAX     PerfCounter64
    MAX-ACCESS read-only
    STATUS     current
    DESCRIPTION
        "Monitored value corresponding to f3PtpSOOCThresholdVariable."
    ::= { f3PtpSOOCThresholdEntry 6 }


--
-- Telecom Slave Current Statistics Table
--
f3PtpTSStatsTable OBJECT-TYPE
    SYNTAX      SEQUENCE OF F3PtpTSStatsEntry
    MAX-ACCESS  not-accessible
    STATUS      current
    DESCRIPTION
            "A collection of Telecom Slave related statistics.  
             These reflect the current data."
    ::= { f3PtpPerformanceObjects 10 }

f3PtpTSStatsEntry OBJECT-TYPE
    SYNTAX      F3PtpTSStatsEntry 
    MAX-ACCESS  not-accessible
    STATUS      current
    DESCRIPTION
            "A conceptual row in the f3PtpTSStatsTable.
             Entries exist in this table for each Telecom Slave."
    INDEX { neIndex, f3PtpTSIndex,  f3PtpTSStatsIndex }
    ::= { f3PtpTSStatsTable 1 }

F3PtpTSStatsEntry ::= SEQUENCE {
    f3PtpTSStatsIndex                Integer32,
    f3PtpTSStatsIntervalType         CmPmIntervalType,
    f3PtpTSStatsValid                TruthValue,
    f3PtpTSStatsAction               CmPmBinAction,
    f3PtpTSStatsTotalTimeCR5         Unsigned32,
    f3PtpTSStatsTotalTimeCR4         Unsigned32,
    f3PtpTSStatsTotalTimeCR3         Unsigned32,
    f3PtpTSStatsTotalTimePR5         Unsigned32,
    f3PtpTSStatsTotalTimePR4         Unsigned32,
    f3PtpTSStatsTotalTimePR3         Unsigned32
}

f3PtpTSStatsIndex OBJECT-TYPE
    SYNTAX      Integer32 (1..4)
    MAX-ACCESS  not-accessible
    STATUS      current
    DESCRIPTION
            "An arbitrary integer index value used to uniquely identify
            this Telecom Slave statistics entry. 
            1 - 15min
            2 - 1day
            3 - rollover
            4 - 5min"
    ::= { f3PtpTSStatsEntry 1 }

f3PtpTSStatsIntervalType OBJECT-TYPE
    SYNTAX      CmPmIntervalType
    MAX-ACCESS  read-only
    STATUS      current
    DESCRIPTION
            "Indicates the type of collection, i.e. whether it is
             15 Min, 1 Day or rollover."
    ::= { f3PtpTSStatsEntry 2 }

f3PtpTSStatsValid OBJECT-TYPE
    SYNTAX      TruthValue
    MAX-ACCESS  read-only
    STATUS      current
    DESCRIPTION
            "Indicates the validity of the bin."
    ::= { f3PtpTSStatsEntry 3 }

f3PtpTSStatsAction OBJECT-TYPE
    SYNTAX      CmPmBinAction
    MAX-ACCESS  read-write
    STATUS      current
    DESCRIPTION
            "Allows the Manager to clear the bin."
    ::= { f3PtpTSStatsEntry 4 }

f3PtpTSStatsTotalTimeCR5 OBJECT-TYPE
     SYNTAX     Unsigned32
     MAX-ACCESS read-only
     STATUS     current
     DESCRIPTION
         "Total Time in seconds Clock Recovery Score is 5."
     ::= { f3PtpTSStatsEntry 5 }

f3PtpTSStatsTotalTimeCR4 OBJECT-TYPE
     SYNTAX     Unsigned32
     MAX-ACCESS read-only
     STATUS     current
     DESCRIPTION
         "Total Time in seconds Clock Recovery Score is 4."
     ::= { f3PtpTSStatsEntry 6 }

f3PtpTSStatsTotalTimeCR3 OBJECT-TYPE
     SYNTAX     Unsigned32
     MAX-ACCESS read-only
     STATUS     current
     DESCRIPTION
         "Total Time in seconds Clock Recovery Score is 3."
     ::= { f3PtpTSStatsEntry 7 }

f3PtpTSStatsTotalTimePR5 OBJECT-TYPE
     SYNTAX     Unsigned32
     MAX-ACCESS read-only
     STATUS     current
     DESCRIPTION
         "Total Time in seconds Phase Recovery Score is 5."
     ::= { f3PtpTSStatsEntry 8 }

f3PtpTSStatsTotalTimePR4 OBJECT-TYPE
     SYNTAX     Unsigned32
     MAX-ACCESS read-only
     STATUS     current
     DESCRIPTION
         "Total Time in seconds Phase Recovery Score is 4."
     ::= { f3PtpTSStatsEntry 9 }

f3PtpTSStatsTotalTimePR3 OBJECT-TYPE
     SYNTAX     Unsigned32
     MAX-ACCESS read-only
     STATUS     current
     DESCRIPTION
         "Total Time in seconds Phase Recovery Score is 3."
     ::= { f3PtpTSStatsEntry 10 }

--
-- Telecom Slave History Table
--
f3PtpTSHistoryTable OBJECT-TYPE
    SYNTAX      SEQUENCE OF F3PtpTSHistoryEntry
    MAX-ACCESS  not-accessible
    STATUS      current
    DESCRIPTION
            "A collection of Telecom Slave related statistics.  
             These reflect the historical data."
    ::= { f3PtpPerformanceObjects 11 }

f3PtpTSHistoryEntry OBJECT-TYPE
    SYNTAX      F3PtpTSHistoryEntry 
    MAX-ACCESS  not-accessible
    STATUS      current
    DESCRIPTION
            "A conceptual row in the f3PtpTSHistoryTable.
             Entries exist in this table for each Telecom Slave."
    INDEX { neIndex, f3PtpTSIndex,  f3PtpTSStatsIndex, f3PtpTSHistoryIndex }
    ::= { f3PtpTSHistoryTable 1 }

F3PtpTSHistoryEntry ::= SEQUENCE {
    f3PtpTSHistoryIndex                  Integer32,
    f3PtpTSHistoryTime                   DateAndTime,
    f3PtpTSHistoryValid                  TruthValue,
    f3PtpTSHistoryAction                 CmPmBinAction,
    f3PtpTSHistoryTotalTimeCR5           Unsigned32,
    f3PtpTSHistoryTotalTimeCR4           Unsigned32,
    f3PtpTSHistoryTotalTimeCR3           Unsigned32,
    f3PtpTSHistoryTotalTimePR5           Unsigned32,
    f3PtpTSHistoryTotalTimePR4           Unsigned32,
    f3PtpTSHistoryTotalTimePR3           Unsigned32
}

f3PtpTSHistoryIndex OBJECT-TYPE
    SYNTAX      Integer32 (1..32)
    MAX-ACCESS  not-accessible
    STATUS      current
    DESCRIPTION
            "An arbitrary integer index value used to uniquely identify
            this Telecom Slave statistics entry. 
            Index 1 corresponds to 15minute, index 2 to 1 day and index
            3 corresponds to rollover."
    ::= { f3PtpTSHistoryEntry 1 }

f3PtpTSHistoryTime OBJECT-TYPE
    SYNTAX      DateAndTime 
    MAX-ACCESS  read-only
    STATUS      current
    DESCRIPTION
            "Indicates the time of history bin creation." 
    ::= { f3PtpTSHistoryEntry 2 }

f3PtpTSHistoryValid OBJECT-TYPE
    SYNTAX      TruthValue
    MAX-ACCESS  read-only
    STATUS      current
    DESCRIPTION
            "Indicates the validity of the bin."
    ::= { f3PtpTSHistoryEntry 3 }

f3PtpTSHistoryAction OBJECT-TYPE
    SYNTAX      CmPmBinAction
    MAX-ACCESS  read-write
    STATUS      current
    DESCRIPTION
            "Allows the Manager to clear the bin."
    ::= { f3PtpTSHistoryEntry 4 }

f3PtpTSHistoryTotalTimeCR5 OBJECT-TYPE
     SYNTAX     Unsigned32
     MAX-ACCESS read-only
     STATUS     current
     DESCRIPTION
         "Total Time in seconds Clock Recovery Score is 5."
     ::= { f3PtpTSHistoryEntry 5 }

f3PtpTSHistoryTotalTimeCR4 OBJECT-TYPE
     SYNTAX     Unsigned32
     MAX-ACCESS read-only
     STATUS     current
     DESCRIPTION
         "Total Time in seconds Clock Recovery Score is 4."
     ::= { f3PtpTSHistoryEntry 6 }

f3PtpTSHistoryTotalTimeCR3 OBJECT-TYPE
     SYNTAX     Unsigned32
     MAX-ACCESS read-only
     STATUS     current
     DESCRIPTION
         "Total Time in seconds Clock Recovery Score is 3."
     ::= { f3PtpTSHistoryEntry 7 }

f3PtpTSHistoryTotalTimePR5 OBJECT-TYPE
     SYNTAX     Unsigned32
     MAX-ACCESS read-only
     STATUS     current
     DESCRIPTION
         "Total Time in seconds Phase Recovery Score is 5."
     ::= { f3PtpTSHistoryEntry 8 }

f3PtpTSHistoryTotalTimePR4 OBJECT-TYPE
     SYNTAX     Unsigned32
     MAX-ACCESS read-only
     STATUS     current
     DESCRIPTION
         "Total Time in seconds Phase Recovery Score is 4."
     ::= { f3PtpTSHistoryEntry 9 }

f3PtpTSHistoryTotalTimePR3 OBJECT-TYPE
     SYNTAX     Unsigned32
     MAX-ACCESS read-only
     STATUS     current
     DESCRIPTION
         "Total Time in seconds Phase Recovery Score is 3."
     ::= { f3PtpTSHistoryEntry 10 }


--
-- Telecom Slave Threshold Table
--
f3PtpTSThresholdTable OBJECT-TYPE
    SYNTAX      SEQUENCE OF F3PtpTSThresholdEntry
    MAX-ACCESS  not-accessible
    STATUS      current
    DESCRIPTION
            "A table of entries that allow manageability of 
             Telecom Slave Thresholds."
    ::= { f3PtpPerformanceObjects 12 }

f3PtpTSThresholdEntry OBJECT-TYPE
    SYNTAX      F3PtpTSThresholdEntry
    MAX-ACCESS  not-accessible
    STATUS      current
    DESCRIPTION
            "A conceptual row in the f3PtpTSThresholdTable."
    INDEX { neIndex, f3PtpTSIndex,  
            f3PtpTSStatsIndex, f3PtpTSThresholdIndex }
    ::= { f3PtpTSThresholdTable 1 }

F3PtpTSThresholdEntry ::= SEQUENCE {
    f3PtpTSThresholdIndex       Integer32,
    f3PtpTSThresholdInterval    CmPmIntervalType,
    f3PtpTSThresholdVariable    VariablePointer,
    f3PtpTSThresholdValueLo     Unsigned32,
    f3PtpTSThresholdValueHi     Unsigned32,
    f3PtpTSThresholdMonValue    PerfCounter64
}

f3PtpTSThresholdIndex OBJECT-TYPE
    SYNTAX     Integer32 (1..65535)
    MAX-ACCESS not-accessible
    STATUS     current
    DESCRIPTION
        "An index that uniquely identifies an entry in the
        f3PtpTSThresholdTable."
    ::= { f3PtpTSThresholdEntry 1 }

f3PtpTSThresholdInterval OBJECT-TYPE
    SYNTAX     CmPmIntervalType
    MAX-ACCESS read-only
    STATUS     current
    DESCRIPTION
        "The interval over which monitored value is
        sampled and compared with the specified threshold."
    ::= { f3PtpTSThresholdEntry 2 }

f3PtpTSThresholdVariable OBJECT-TYPE
    SYNTAX     VariablePointer
    MAX-ACCESS read-only
    STATUS     current
    DESCRIPTION
        "The object identifier of the particular variable to be
        sampled."
    ::= { f3PtpTSThresholdEntry 3 }

f3PtpTSThresholdValueLo OBJECT-TYPE
    SYNTAX     Unsigned32
    MAX-ACCESS read-write
    STATUS     current
    DESCRIPTION
        "Lower 32 bits of the threshold value."
    ::= { f3PtpTSThresholdEntry 4 }

f3PtpTSThresholdValueHi OBJECT-TYPE
    SYNTAX     Unsigned32
    MAX-ACCESS read-write
    STATUS     current
    DESCRIPTION
        "Higher 32 bits of the threshold value."
    ::= { f3PtpTSThresholdEntry 5 }

f3PtpTSThresholdMonValue OBJECT-TYPE
    SYNTAX     PerfCounter64
    MAX-ACCESS read-only
    STATUS     current
    DESCRIPTION
        "Monitored value corresponding to f3PtpTSThresholdVariable."
    ::= { f3PtpTSThresholdEntry 6 }

--
-- Master Clock Interface current data
--
f3PtpMCIStatsTable OBJECT-TYPE
    SYNTAX      SEQUENCE OF F3PtpMCIStatsEntry
    MAX-ACCESS  not-accessible
    STATUS      current
    DESCRIPTION
            "A collection of Master Clock Interface related statistics.  
             These reflect the current data."
    ::= { f3PtpPerformanceObjects 13 }

f3PtpMCIStatsEntry OBJECT-TYPE
    SYNTAX      F3PtpMCIStatsEntry 
    MAX-ACCESS  not-accessible
    STATUS      current
    DESCRIPTION
            "A conceptual row in the f3PtpMCIStatsTable.
             Entries exist in this table for each Telecom Slave."
    INDEX { neIndex, f3PtpBCIndex, f3PtpMCIIndex, f3PtpMCIStatsIndex }
    ::= { f3PtpMCIStatsTable 1 }

F3PtpMCIStatsEntry ::= SEQUENCE {
    f3PtpMCIStatsIndex                    Integer32,
    f3PtpMCIStatsIntervalType             CmPmIntervalType,
    f3PtpMCIStatsValid                    TruthValue,
    f3PtpMCIStatsAction                   CmPmBinAction,
    f3PtpMCIStatsPtpDiscards              PerfCounter64,
    f3PtpMCIStatsSyncDeniedEvents         PerfCounter64,
    f3PtpMCIStatsDelayRspDeniedEvents     PerfCounter64,
    f3PtpMCIStatsAnnounceDeniedEvents     PerfCounter64,
    f3PtpMCIStatsSyncCancelledEvents      PerfCounter64,
    f3PtpMCIStatsDelayRspCancelledEvents  PerfCounter64,
    f3PtpMCIStatsAnnounceCancelledEvents  PerfCounter64,
    f3PtpMCIStatsDynamicSlavesLearnt      PerfCounter64,
    f3PtpMCIStatsDynamicSlavesDropped     PerfCounter64
}

f3PtpMCIStatsIndex OBJECT-TYPE
    SYNTAX      Integer32 (1..4)
    MAX-ACCESS  not-accessible
    STATUS      current
    DESCRIPTION
            "An arbitrary integer index value used to uniquely identify
            this Master Clock Interface statistics entry. 
            1 - 15min
            2 - 1day
            3 - rollover
            4 - 5min"
    ::= { f3PtpMCIStatsEntry 1 }

f3PtpMCIStatsIntervalType OBJECT-TYPE
    SYNTAX      CmPmIntervalType
    MAX-ACCESS  read-only
    STATUS      current
    DESCRIPTION
            "Indicates the type of collection, i.e. whether it is
             15 Min, 1 Day or rollover."
    ::= { f3PtpMCIStatsEntry 2 }

f3PtpMCIStatsValid OBJECT-TYPE
    SYNTAX      TruthValue
    MAX-ACCESS  read-only
    STATUS      current
    DESCRIPTION
            "Indicates the validity of the bin."
    ::= { f3PtpMCIStatsEntry 3 }

f3PtpMCIStatsAction OBJECT-TYPE
    SYNTAX      CmPmBinAction
    MAX-ACCESS  read-write
    STATUS      current
    DESCRIPTION
            "Allows the Manager to clear the bin."
    ::= { f3PtpMCIStatsEntry 4 }

f3PtpMCIStatsPtpDiscards OBJECT-TYPE
    SYNTAX      PerfCounter64
    MAX-ACCESS  read-only
    STATUS      current
    DESCRIPTION
            "Count of PTP messages that have been discarded by the MCI since either 
             Source IP, PTP Domain number, Port Identity did not match any 
             Remote Slave clock."
    ::= { f3PtpMCIStatsEntry 5 }

f3PtpMCIStatsSyncDeniedEvents OBJECT-TYPE
    SYNTAX      PerfCounter64
    MAX-ACCESS  read-only
    STATUS      current
    DESCRIPTION
            "Count of Sync service denied events."
    ::= { f3PtpMCIStatsEntry 6 }

f3PtpMCIStatsDelayRspDeniedEvents OBJECT-TYPE
    SYNTAX      PerfCounter64
    MAX-ACCESS  read-only
    STATUS      current
    DESCRIPTION
            "Count of Delay Response service denied events."
    ::= { f3PtpMCIStatsEntry 7 }

f3PtpMCIStatsAnnounceDeniedEvents OBJECT-TYPE
    SYNTAX      PerfCounter64
    MAX-ACCESS  read-only
    STATUS      current
    DESCRIPTION
            "Count of Announce service denied events."
    ::= { f3PtpMCIStatsEntry 8 }

f3PtpMCIStatsSyncCancelledEvents OBJECT-TYPE
    SYNTAX      PerfCounter64
    MAX-ACCESS  read-only
    STATUS      current
    DESCRIPTION
            "Count of Sync service canceled events initiated by the Remote Slave Clocks."
    ::= { f3PtpMCIStatsEntry 9 }

f3PtpMCIStatsDelayRspCancelledEvents OBJECT-TYPE
    SYNTAX      PerfCounter64
    MAX-ACCESS  read-only
    STATUS      current
    DESCRIPTION
            "Count of Delay Response service canceled events initiated by the 
             Remote Slave Clocks."
    ::= { f3PtpMCIStatsEntry 10 }

f3PtpMCIStatsAnnounceCancelledEvents OBJECT-TYPE
    SYNTAX      PerfCounter64
    MAX-ACCESS  read-only
    STATUS      current
    DESCRIPTION
            "Count of Announce service canceled events initiated by the 
             Remote Slave Clocks."
    ::= { f3PtpMCIStatsEntry 11 }

f3PtpMCIStatsDynamicSlavesLearnt OBJECT-TYPE
    SYNTAX      PerfCounter64
    MAX-ACCESS  read-only
    STATUS      current
    DESCRIPTION
            "Count of Successfully learned Dynamic Slaves."
    ::= { f3PtpMCIStatsEntry 12 }

f3PtpMCIStatsDynamicSlavesDropped OBJECT-TYPE
    SYNTAX      PerfCounter64
    MAX-ACCESS  read-only
    STATUS      current
    DESCRIPTION
            "Count of Dynamic Slaves removed from the Remote Slaves table due to 
             lease expired."
    ::= { f3PtpMCIStatsEntry 13 }

--
-- Master Clock Interface history data
--
f3PtpMCIHistoryTable OBJECT-TYPE
    SYNTAX      SEQUENCE OF F3PtpMCIHistoryEntry
    MAX-ACCESS  not-accessible
    STATUS      current
    DESCRIPTION
            "A collection of Master Clock Interface related history data.  
             These reflect the current data."
    ::= { f3PtpPerformanceObjects 14 }

f3PtpMCIHistoryEntry OBJECT-TYPE
    SYNTAX      F3PtpMCIHistoryEntry 
    MAX-ACCESS  not-accessible
    STATUS      current
    DESCRIPTION
            "A conceptual row in the f3PtpMCIHistoryTable.
             Entries exist in this table for each Master Clock Interface."
    INDEX { neIndex, f3PtpBCIndex, f3PtpMCIIndex, f3PtpMCIStatsIndex,
            f3PtpMCIHistoryIndex }
    ::= { f3PtpMCIHistoryTable 1 }

F3PtpMCIHistoryEntry ::= SEQUENCE {
    f3PtpMCIHistoryIndex                    Integer32,
    f3PtpMCIHistoryTime                     DateAndTime,
    f3PtpMCIHistoryValid                    TruthValue,
    f3PtpMCIHistoryAction                   CmPmBinAction,
    f3PtpMCIHistoryPtpDiscards              PerfCounter64,
    f3PtpMCIHistorySyncDeniedEvents         PerfCounter64,
    f3PtpMCIHistoryDelayRspDeniedEvents     PerfCounter64,
    f3PtpMCIHistoryAnnounceDeniedEvents     PerfCounter64,
    f3PtpMCIHistorySyncCancelledEvents      PerfCounter64,
    f3PtpMCIHistoryDelayRspCancelledEvents  PerfCounter64,
    f3PtpMCIHistoryAnnounceCancelledEvents  PerfCounter64,
    f3PtpMCIHistoryDynamicSlavesLearnt      PerfCounter64,
    f3PtpMCIHistoryDynamicSlavesDropped     PerfCounter64
}

f3PtpMCIHistoryIndex OBJECT-TYPE
    SYNTAX      Integer32 (1..32)
    MAX-ACCESS  not-accessible
    STATUS      current
    DESCRIPTION
            "An arbitrary integer index value used to uniquely identify
            this Master Clock Interface PM history entry."
    ::= { f3PtpMCIHistoryEntry 1 }

f3PtpMCIHistoryTime OBJECT-TYPE
    SYNTAX      DateAndTime 
    MAX-ACCESS  read-only
    STATUS      current
    DESCRIPTION
            "Indicates the time of history bin creation." 
    ::= { f3PtpMCIHistoryEntry 2 }

f3PtpMCIHistoryValid OBJECT-TYPE
    SYNTAX      TruthValue
    MAX-ACCESS  read-only
    STATUS      current
    DESCRIPTION
            "Indicates the validity of the bin."
    ::= { f3PtpMCIHistoryEntry 3 }

f3PtpMCIHistoryAction OBJECT-TYPE
    SYNTAX      CmPmBinAction
    MAX-ACCESS  read-write
    STATUS      current
    DESCRIPTION
            "Allows the Manager to clear the bin."
    ::= { f3PtpMCIHistoryEntry 4 }

f3PtpMCIHistoryPtpDiscards OBJECT-TYPE
    SYNTAX      PerfCounter64
    MAX-ACCESS  read-only
    STATUS      current
    DESCRIPTION
            "Count of PTP messages that have been discarded by the MCI since either 
             Source IP, PTP Domain number, Port Identity did not match any 
             Remote Slave clock."
    ::= { f3PtpMCIHistoryEntry 5 }

f3PtpMCIHistorySyncDeniedEvents OBJECT-TYPE
    SYNTAX      PerfCounter64
    MAX-ACCESS  read-only
    STATUS      current
    DESCRIPTION
            "Count of Sync service denied events."
    ::= { f3PtpMCIHistoryEntry 6 }

f3PtpMCIHistoryDelayRspDeniedEvents OBJECT-TYPE
    SYNTAX      PerfCounter64
    MAX-ACCESS  read-only
    STATUS      current
    DESCRIPTION
            "Count of Delay Response service denied events."
    ::= { f3PtpMCIHistoryEntry 7 }

f3PtpMCIHistoryAnnounceDeniedEvents OBJECT-TYPE
    SYNTAX      PerfCounter64
    MAX-ACCESS  read-only
    STATUS      current
    DESCRIPTION
            "Count of Announce service denied events."
    ::= { f3PtpMCIHistoryEntry 8 }

f3PtpMCIHistorySyncCancelledEvents OBJECT-TYPE
    SYNTAX      PerfCounter64
    MAX-ACCESS  read-only
    STATUS      current
    DESCRIPTION
            "Count of Sync service canceled events initiated by the Remote Slave Clocks."
    ::= { f3PtpMCIHistoryEntry 9 }

f3PtpMCIHistoryDelayRspCancelledEvents OBJECT-TYPE
    SYNTAX      PerfCounter64
    MAX-ACCESS  read-only
    STATUS      current
    DESCRIPTION
            "Count of Delay Response service canceled events initiated by the 
             Remote Slave Clocks."
    ::= { f3PtpMCIHistoryEntry 10 }

f3PtpMCIHistoryAnnounceCancelledEvents OBJECT-TYPE
    SYNTAX      PerfCounter64
    MAX-ACCESS  read-only
    STATUS      current
    DESCRIPTION
            "Count of Announce service canceled events initiated by the 
             Remote Slave Clocks."
    ::= { f3PtpMCIHistoryEntry 11 }

f3PtpMCIHistoryDynamicSlavesLearnt OBJECT-TYPE
    SYNTAX      PerfCounter64
    MAX-ACCESS  read-only
    STATUS      current
    DESCRIPTION
            "Count of Successfully learned Dynamic Slaves."
    ::= { f3PtpMCIHistoryEntry 12 }

f3PtpMCIHistoryDynamicSlavesDropped OBJECT-TYPE
    SYNTAX      PerfCounter64
    MAX-ACCESS  read-only
    STATUS      current
    DESCRIPTION
            "Count of Dynamic Slaves removed from the Remote Slaves table due to 
             lease expired."
    ::= { f3PtpMCIHistoryEntry 13 }

--
-- Master Clock Interface Threshold Table
--
f3PtpMCIThresholdTable OBJECT-TYPE
    SYNTAX      SEQUENCE OF F3PtpMCIThresholdEntry
    MAX-ACCESS  not-accessible
    STATUS      current
    DESCRIPTION
            "A table of entries that allow manageability of 
             Master Clock Interface Thresholds."
    ::= { f3PtpPerformanceObjects 15 }

f3PtpMCIThresholdEntry OBJECT-TYPE
    SYNTAX      F3PtpMCIThresholdEntry
    MAX-ACCESS  not-accessible
    STATUS      current
    DESCRIPTION
            "A conceptual row in the f3PtpMCIThresholdTable."
    INDEX { neIndex, f3PtpBCIndex, f3PtpMCIIndex, f3PtpMCIStatsIndex, 
            f3PtpMCIThresholdIndex }
    ::= { f3PtpMCIThresholdTable 1 }

F3PtpMCIThresholdEntry ::= SEQUENCE {
    f3PtpMCIThresholdIndex       Integer32,
    f3PtpMCIThresholdInterval    CmPmIntervalType,
    f3PtpMCIThresholdVariable    VariablePointer,
    f3PtpMCIThresholdValueLo     Unsigned32,
    f3PtpMCIThresholdValueHi     Unsigned32,
    f3PtpMCIThresholdMonValue    PerfCounter64
}

f3PtpMCIThresholdIndex OBJECT-TYPE
    SYNTAX     Integer32 (1..65535)
    MAX-ACCESS not-accessible
    STATUS     current
    DESCRIPTION
        "An index that uniquely identifies an entry in the
        f3PtpMCIThresholdTable."
    ::= { f3PtpMCIThresholdEntry 1 }

f3PtpMCIThresholdInterval OBJECT-TYPE
    SYNTAX     CmPmIntervalType
    MAX-ACCESS read-only
    STATUS     current
    DESCRIPTION
        "The interval over which monitored value is
        sampled and compared with the specified threshold."
    ::= { f3PtpMCIThresholdEntry 2 }

f3PtpMCIThresholdVariable OBJECT-TYPE
    SYNTAX     VariablePointer
    MAX-ACCESS read-only
    STATUS     current
    DESCRIPTION
        "The object identifier of the particular variable to be
        sampled."
    ::= { f3PtpMCIThresholdEntry 3 }

f3PtpMCIThresholdValueLo OBJECT-TYPE
    SYNTAX     Unsigned32
    MAX-ACCESS read-write
    STATUS     current
    DESCRIPTION
        "Lower 32 bits of the threshold value."
    ::= { f3PtpMCIThresholdEntry 4 }

f3PtpMCIThresholdValueHi OBJECT-TYPE
    SYNTAX     Unsigned32
    MAX-ACCESS read-write
    STATUS     current
    DESCRIPTION
        "Higher 32 bits of the threshold value."
    ::= { f3PtpMCIThresholdEntry 5 }

f3PtpMCIThresholdMonValue OBJECT-TYPE
    SYNTAX     PerfCounter64
    MAX-ACCESS read-only
    STATUS     current
    DESCRIPTION
        "Monitored value corresponding to f3PtpMCIThresholdVariable."
    ::= { f3PtpMCIThresholdEntry 6 }

--
-- Remote Slave current data
--
f3PtpRemoteSlaveStatsTable OBJECT-TYPE
    SYNTAX      SEQUENCE OF F3PtpRemoteSlaveStatsEntry
    MAX-ACCESS  not-accessible
    STATUS      current
    DESCRIPTION
            "A collection of Remote Slave related statistics.  
             These reflect the current data."
    ::= { f3PtpPerformanceObjects 16 }

f3PtpRemoteSlaveStatsEntry OBJECT-TYPE
    SYNTAX      F3PtpRemoteSlaveStatsEntry 
    MAX-ACCESS  not-accessible
    STATUS      current
    DESCRIPTION
            "A conceptual row in the f3PtpRemoteSlaveStatsTable.
             Entries exist in this table for each Remote Slave."
    INDEX { neIndex, f3PtpBCIndex, f3PtpMCIIndex, f3PtpRemoteSlaveStatsSlaveType, f3PtpRemoteSlaveStatsSlaveIndex,
            f3PtpRemoteSlaveStatsIndex }
    ::= { f3PtpRemoteSlaveStatsTable 1 }

F3PtpRemoteSlaveStatsEntry ::= SEQUENCE {
    f3PtpRemoteSlaveStatsSlaveType                RemoteSlaveType,
    f3PtpRemoteSlaveStatsSlaveIndex               Integer32,
    f3PtpRemoteSlaveStatsIndex                    Integer32,
    f3PtpRemoteSlaveStatsIntervalType             CmPmIntervalType,
    f3PtpRemoteSlaveStatsValid                    TruthValue,
    f3PtpRemoteSlaveStatsAction                   CmPmBinAction,
    f3PtpRemoteSlaveStatsSyncMsgsGen              PerfCounter64,
    f3PtpRemoteSlaveStatsDelayRspMsgsGen          PerfCounter64,
    f3PtpRemoteSlaveStatsAnnounceMsgsGen          PerfCounter64,
    f3PtpRemoteSlaveStatsSignallingMsgsGen        PerfCounter64,
    f3PtpRemoteSlaveStatsDelayReqMsgsRx           PerfCounter64,
    f3PtpRemoteSlaveStatsSignallingMsgsRx         PerfCounter64,
    f3PtpRemoteSlaveStatsDelayReqMsgsDropped      PerfCounter64,
    f3PtpRemoteSlaveStatsInvalidTLVLenDiscards    PerfCounter64,
    f3PtpRemoteSlaveStatsInvalidTLVTypeDiscards   PerfCounter64,
    f3PtpRemoteSlaveStatsTimesSyncLeaseExp        PerfCounter64,
    f3PtpRemoteSlaveStatsTimesDelayRspLeaseExp    PerfCounter64,
    f3PtpRemoteSlaveStatsTimesAnnounceLeaseExp    PerfCounter64
}

f3PtpRemoteSlaveStatsSlaveType OBJECT-TYPE
    SYNTAX      RemoteSlaveType
    MAX-ACCESS  not-accessible
    STATUS      current
    DESCRIPTION
            "This object indicates if this row referts to Static or Dynamic Remote Slave."
    ::= { f3PtpRemoteSlaveStatsEntry 1 }

f3PtpRemoteSlaveStatsSlaveIndex OBJECT-TYPE
    SYNTAX      Integer32
    MAX-ACCESS  not-accessible
    STATUS      current
    DESCRIPTION
            "Index of a Static or Dynamic Remote Slave.
             When f3PtpRemoteSlaveStatsSlaveType is 'static' then this object referts to f3PtpStaticRemoteSlaveIndex.
             When f3PtpRemoteSlaveStatsSlaveType is 'dynamic' then this object referts to f3PtpDynamicRemoteSlaveIndex."
    ::= { f3PtpRemoteSlaveStatsEntry 2 }

f3PtpRemoteSlaveStatsIndex OBJECT-TYPE
    SYNTAX      Integer32 (1..4)
    MAX-ACCESS  not-accessible
    STATUS      current
    DESCRIPTION
            "An arbitrary integer index value used to uniquely identify
            this Remote Slave statistics entry. 
            1 - 15min
            2 - 1day
            3 - rollover
            4 - 5min"
    ::= { f3PtpRemoteSlaveStatsEntry 3 }

f3PtpRemoteSlaveStatsIntervalType OBJECT-TYPE
    SYNTAX      CmPmIntervalType
    MAX-ACCESS  read-only
    STATUS      current
    DESCRIPTION
            "Indicates the type of collection, i.e. whether it is
             15 Min, 1 Day or rollover."
    ::= { f3PtpRemoteSlaveStatsEntry 4 }

f3PtpRemoteSlaveStatsValid OBJECT-TYPE
    SYNTAX      TruthValue
    MAX-ACCESS  read-only
    STATUS      current
    DESCRIPTION
            "Indicates the validity of the bin."
    ::= { f3PtpRemoteSlaveStatsEntry 5 }

f3PtpRemoteSlaveStatsAction OBJECT-TYPE
    SYNTAX      CmPmBinAction
    MAX-ACCESS  read-write
    STATUS      current
    DESCRIPTION
            "Allows the Manager to clear the bin."
    ::= { f3PtpRemoteSlaveStatsEntry 6 }

f3PtpRemoteSlaveStatsSyncMsgsGen OBJECT-TYPE
    SYNTAX      PerfCounter64
    MAX-ACCESS  read-only
    STATUS      current
    DESCRIPTION
            "Total Sync messages generated."
    ::= { f3PtpRemoteSlaveStatsEntry 7 }

f3PtpRemoteSlaveStatsDelayRspMsgsGen OBJECT-TYPE
    SYNTAX      PerfCounter64
    MAX-ACCESS  read-only
    STATUS      current
    DESCRIPTION
            "Total Delay Response messages generated."
    ::= { f3PtpRemoteSlaveStatsEntry 8 }

f3PtpRemoteSlaveStatsAnnounceMsgsGen OBJECT-TYPE
    SYNTAX      PerfCounter64
    MAX-ACCESS  read-only
    STATUS      current
    DESCRIPTION
            "Total Announce messages generated."
    ::= { f3PtpRemoteSlaveStatsEntry 9 }

f3PtpRemoteSlaveStatsSignallingMsgsGen OBJECT-TYPE
    SYNTAX      PerfCounter64
    MAX-ACCESS  read-only
    STATUS      current
    DESCRIPTION
            "Total Signalling messages generated."
    ::= { f3PtpRemoteSlaveStatsEntry 10 }

f3PtpRemoteSlaveStatsDelayReqMsgsRx OBJECT-TYPE
    SYNTAX      PerfCounter64
    MAX-ACCESS  read-only
    STATUS      current
    DESCRIPTION
            "Total Delay Request messages received."
    ::= { f3PtpRemoteSlaveStatsEntry 11 }

f3PtpRemoteSlaveStatsSignallingMsgsRx OBJECT-TYPE
    SYNTAX      PerfCounter64
    MAX-ACCESS  read-only
    STATUS      current
    DESCRIPTION
            "Total Signalling messages received."
    ::= { f3PtpRemoteSlaveStatsEntry 12 }

f3PtpRemoteSlaveStatsDelayReqMsgsDropped OBJECT-TYPE
    SYNTAX      PerfCounter64
    MAX-ACCESS  read-only
    STATUS      current
    DESCRIPTION
            "Total Delay Request messages dropped."
    ::= { f3PtpRemoteSlaveStatsEntry 13 }

f3PtpRemoteSlaveStatsInvalidTLVLenDiscards OBJECT-TYPE
    SYNTAX      PerfCounter64
    MAX-ACCESS  read-only
    STATUS      current
    DESCRIPTION
            "Total number of PTP messages discarded due to invalid PTP TLV length."
    ::= { f3PtpRemoteSlaveStatsEntry 14 }

f3PtpRemoteSlaveStatsInvalidTLVTypeDiscards OBJECT-TYPE
    SYNTAX      PerfCounter64
    MAX-ACCESS  read-only
    STATUS      current
    DESCRIPTION
            "Total number of PTP messages discarded due to invalid PTP TLV type."
    ::= { f3PtpRemoteSlaveStatsEntry 15 }

f3PtpRemoteSlaveStatsTimesSyncLeaseExp OBJECT-TYPE
    SYNTAX      PerfCounter64
    MAX-ACCESS  read-only
    STATUS      current
    DESCRIPTION
            "Count of Sync service lease duration expired events."
    ::= { f3PtpRemoteSlaveStatsEntry 16 }

f3PtpRemoteSlaveStatsTimesDelayRspLeaseExp OBJECT-TYPE
    SYNTAX      PerfCounter64
    MAX-ACCESS  read-only
    STATUS      current
    DESCRIPTION
            "Count of Delay Response service lease duration expired events."
    ::= { f3PtpRemoteSlaveStatsEntry 17 }

f3PtpRemoteSlaveStatsTimesAnnounceLeaseExp OBJECT-TYPE
    SYNTAX      PerfCounter64
    MAX-ACCESS  read-only
    STATUS      current
    DESCRIPTION
            "Count of Announce service lease duration expired events."
    ::= { f3PtpRemoteSlaveStatsEntry 18 }

--
-- Remote Slave history data
--
f3PtpRemoteSlaveHistoryTable OBJECT-TYPE
    SYNTAX      SEQUENCE OF F3PtpRemoteSlaveHistoryEntry
    MAX-ACCESS  not-accessible
    STATUS      current
    DESCRIPTION
            "A collection of Remote Slave related history.  
             These reflect the current data."
    ::= { f3PtpPerformanceObjects 17 }

f3PtpRemoteSlaveHistoryEntry OBJECT-TYPE
    SYNTAX      F3PtpRemoteSlaveHistoryEntry 
    MAX-ACCESS  not-accessible
    STATUS      current
    DESCRIPTION
            "A conceptual row in the f3PtpRemoteSlaveHistoryTable.
             Entries exist in this table for each Remote Slave."
    INDEX { neIndex, f3PtpBCIndex, f3PtpMCIIndex, f3PtpRemoteSlaveStatsSlaveType, f3PtpRemoteSlaveStatsSlaveIndex,
            f3PtpRemoteSlaveStatsIndex, f3PtpRemoteSlaveHistoryIndex }
    ::= { f3PtpRemoteSlaveHistoryTable 1 }

F3PtpRemoteSlaveHistoryEntry ::= SEQUENCE {
    f3PtpRemoteSlaveHistoryIndex                    Integer32,
    f3PtpRemoteSlaveHistoryTime                     DateAndTime,
    f3PtpRemoteSlaveHistoryValid                    TruthValue,
    f3PtpRemoteSlaveHistoryAction                   CmPmBinAction,
    f3PtpRemoteSlaveHistorySyncMsgsGen              PerfCounter64,
    f3PtpRemoteSlaveHistoryDelayRspMsgsGen          PerfCounter64,
    f3PtpRemoteSlaveHistoryAnnounceMsgsGen          PerfCounter64,
    f3PtpRemoteSlaveHistorySignallingMsgsGen        PerfCounter64,
    f3PtpRemoteSlaveHistoryDelayReqMsgsRx           PerfCounter64,
    f3PtpRemoteSlaveHistorySignallingMsgsRx         PerfCounter64,
    f3PtpRemoteSlaveHistoryDelayReqMsgsDropped      PerfCounter64,
    f3PtpRemoteSlaveHistoryInvalidTLVLenDiscards    PerfCounter64,
    f3PtpRemoteSlaveHistoryInvalidTLVTypeDiscards   PerfCounter64,
    f3PtpRemoteSlaveHistoryTimesSyncLeaseExp        PerfCounter64,
    f3PtpRemoteSlaveHistoryTimesDelayRspLeaseExp    PerfCounter64,
    f3PtpRemoteSlaveHistoryTimesAnnounceLeaseExp    PerfCounter64
}


f3PtpRemoteSlaveHistoryIndex OBJECT-TYPE
    SYNTAX      Integer32 (1..32)
    MAX-ACCESS  not-accessible
    STATUS      current
    DESCRIPTION
            "An arbitrary integer index value used to uniquely identify
             this Remote Slave PM history entry."
    ::= { f3PtpRemoteSlaveHistoryEntry 1 }

f3PtpRemoteSlaveHistoryTime OBJECT-TYPE
    SYNTAX      DateAndTime 
    MAX-ACCESS  read-only
    STATUS      current
    DESCRIPTION
            "Indicates the time of history bin creation." 
    ::= { f3PtpRemoteSlaveHistoryEntry 2 }

f3PtpRemoteSlaveHistoryValid OBJECT-TYPE
    SYNTAX      TruthValue
    MAX-ACCESS  read-only
    STATUS      current
    DESCRIPTION
            "Indicates the validity of the bin."
    ::= { f3PtpRemoteSlaveHistoryEntry 3 }

f3PtpRemoteSlaveHistoryAction OBJECT-TYPE
    SYNTAX      CmPmBinAction
    MAX-ACCESS  read-write
    STATUS      current
    DESCRIPTION
            "Allows the Manager to clear the bin."
    ::= { f3PtpRemoteSlaveHistoryEntry 4 }

f3PtpRemoteSlaveHistorySyncMsgsGen OBJECT-TYPE
    SYNTAX      PerfCounter64
    MAX-ACCESS  read-only
    STATUS      current
    DESCRIPTION
            "Total Sync messages generated."
    ::= { f3PtpRemoteSlaveHistoryEntry 5 }

f3PtpRemoteSlaveHistoryDelayRspMsgsGen OBJECT-TYPE
    SYNTAX      PerfCounter64
    MAX-ACCESS  read-only
    STATUS      current
    DESCRIPTION
            "Total Delay Response messages generated."
    ::= { f3PtpRemoteSlaveHistoryEntry 6 }

f3PtpRemoteSlaveHistoryAnnounceMsgsGen OBJECT-TYPE
    SYNTAX      PerfCounter64
    MAX-ACCESS  read-only
    STATUS      current
    DESCRIPTION
            "Total Announce messages generated."
    ::= { f3PtpRemoteSlaveHistoryEntry 7 }

f3PtpRemoteSlaveHistorySignallingMsgsGen OBJECT-TYPE
    SYNTAX      PerfCounter64
    MAX-ACCESS  read-only
    STATUS      current
    DESCRIPTION
            "Total Signalling messages generated."
    ::= { f3PtpRemoteSlaveHistoryEntry 8 }

f3PtpRemoteSlaveHistoryDelayReqMsgsRx OBJECT-TYPE
    SYNTAX      PerfCounter64
    MAX-ACCESS  read-only
    STATUS      current
    DESCRIPTION
            "Total Delay Request messages received."
    ::= { f3PtpRemoteSlaveHistoryEntry 9 }

f3PtpRemoteSlaveHistorySignallingMsgsRx OBJECT-TYPE
    SYNTAX      PerfCounter64
    MAX-ACCESS  read-only
    STATUS      current
    DESCRIPTION
            "Total Signalling messages received."
    ::= { f3PtpRemoteSlaveHistoryEntry 10 }

f3PtpRemoteSlaveHistoryDelayReqMsgsDropped OBJECT-TYPE
    SYNTAX      PerfCounter64
    MAX-ACCESS  read-only
    STATUS      current
    DESCRIPTION
            "Total Delay Request messages dropped."
    ::= { f3PtpRemoteSlaveHistoryEntry 11 }

f3PtpRemoteSlaveHistoryInvalidTLVLenDiscards OBJECT-TYPE
    SYNTAX      PerfCounter64
    MAX-ACCESS  read-only
    STATUS      current
    DESCRIPTION
            "Total number of PTP messages discarded due to invalid PTP TLV length."
    ::= { f3PtpRemoteSlaveHistoryEntry 12 }

f3PtpRemoteSlaveHistoryInvalidTLVTypeDiscards OBJECT-TYPE
    SYNTAX      PerfCounter64
    MAX-ACCESS  read-only
    STATUS      current
    DESCRIPTION
            "Total number of PTP messages discarded due to invalid PTP TLV type."
    ::= { f3PtpRemoteSlaveHistoryEntry 13 }

f3PtpRemoteSlaveHistoryTimesSyncLeaseExp OBJECT-TYPE
    SYNTAX      PerfCounter64
    MAX-ACCESS  read-only
    STATUS      current
    DESCRIPTION
            "Count of Sync service lease duration expired events."
    ::= { f3PtpRemoteSlaveHistoryEntry 14 }

f3PtpRemoteSlaveHistoryTimesDelayRspLeaseExp OBJECT-TYPE
    SYNTAX      PerfCounter64
    MAX-ACCESS  read-only
    STATUS      current
    DESCRIPTION
            "Count of Delay Response service lease duration expired events."
    ::= { f3PtpRemoteSlaveHistoryEntry 15 }

f3PtpRemoteSlaveHistoryTimesAnnounceLeaseExp OBJECT-TYPE
    SYNTAX      PerfCounter64
    MAX-ACCESS  read-only
    STATUS      current
    DESCRIPTION
            "Count of Announce service lease duration expired events."
    ::= { f3PtpRemoteSlaveHistoryEntry 16 }

--
-- Remote Slave Threshold Table
--
f3PtpRemoteSlaveThresholdTable OBJECT-TYPE
    SYNTAX      SEQUENCE OF F3PtpRemoteSlaveThresholdEntry
    MAX-ACCESS  not-accessible
    STATUS      current
    DESCRIPTION
            "A table of entries that allow manageability of 
             Master Clock Interface Thresholds."
    ::= { f3PtpPerformanceObjects 18 }

f3PtpRemoteSlaveThresholdEntry OBJECT-TYPE
    SYNTAX      F3PtpRemoteSlaveThresholdEntry
    MAX-ACCESS  not-accessible
    STATUS      current
    DESCRIPTION
            "A conceptual row in the f3PtpRemoteSlaveThresholdTable."
    INDEX { neIndex, f3PtpBCIndex, f3PtpMCIIndex, f3PtpRemoteSlaveStatsSlaveType, f3PtpRemoteSlaveStatsSlaveIndex, 
            f3PtpRemoteSlaveStatsIndex, f3PtpRemoteSlaveThresholdIndex }
    ::= { f3PtpRemoteSlaveThresholdTable 1 }

F3PtpRemoteSlaveThresholdEntry ::= SEQUENCE {
    f3PtpRemoteSlaveThresholdIndex       Integer32,
    f3PtpRemoteSlaveThresholdInterval    CmPmIntervalType,
    f3PtpRemoteSlaveThresholdVariable    VariablePointer,
    f3PtpRemoteSlaveThresholdValueLo     Unsigned32,
    f3PtpRemoteSlaveThresholdValueHi     Unsigned32,
    f3PtpRemoteSlaveThresholdMonValue    PerfCounter64
}

f3PtpRemoteSlaveThresholdIndex OBJECT-TYPE
    SYNTAX     Integer32 (1..65535)
    MAX-ACCESS not-accessible
    STATUS     current
    DESCRIPTION
        "An index that uniquely identifies an entry in the
        f3PtpRemoteSlaveThresholdTable."
    ::= { f3PtpRemoteSlaveThresholdEntry 1 }

f3PtpRemoteSlaveThresholdInterval OBJECT-TYPE
    SYNTAX     CmPmIntervalType
    MAX-ACCESS read-only
    STATUS     current
    DESCRIPTION
        "The interval over which monitored value is
        sampled and compared with the specified threshold."
    ::= { f3PtpRemoteSlaveThresholdEntry 2 }

f3PtpRemoteSlaveThresholdVariable OBJECT-TYPE
    SYNTAX     VariablePointer
    MAX-ACCESS read-only
    STATUS     current
    DESCRIPTION
        "The object identifier of the particular variable to be
        sampled."
    ::= { f3PtpRemoteSlaveThresholdEntry 3 }

f3PtpRemoteSlaveThresholdValueLo OBJECT-TYPE
    SYNTAX     Unsigned32
    MAX-ACCESS read-write
    STATUS     current
    DESCRIPTION
        "Lower 32 bits of the threshold value."
    ::= { f3PtpRemoteSlaveThresholdEntry 4 }

f3PtpRemoteSlaveThresholdValueHi OBJECT-TYPE
    SYNTAX     Unsigned32
    MAX-ACCESS read-write
    STATUS     current
    DESCRIPTION
        "Higher 32 bits of the threshold value."
    ::= { f3PtpRemoteSlaveThresholdEntry 5 }

f3PtpRemoteSlaveThresholdMonValue OBJECT-TYPE
    SYNTAX     PerfCounter64
    MAX-ACCESS read-only
    STATUS     current
    DESCRIPTION
        "Monitored value corresponding to f3PtpRemoteSlaveThresholdVariable."
    ::= { f3PtpRemoteSlaveThresholdEntry 6 }

--
-- Traffic Port PTP Flow Point Current Statistics Table
--
f3PtpTrafficPortFlowPointStatsTable OBJECT-TYPE
    SYNTAX      SEQUENCE OF F3PtpTrafficPortFlowPointStatsEntry
   MAX-ACCESS  not-accessible
    STATUS      current
    DESCRIPTION
            "A collection of Traffic Port PTP Flow Point statistics.  
             These reflect the current data."
    ::= { f3PtpPerformanceObjects 19 }

f3PtpTrafficPortFlowPointStatsEntry OBJECT-TYPE
    SYNTAX      F3PtpTrafficPortFlowPointStatsEntry 
   MAX-ACCESS  not-accessible
    STATUS      current
    DESCRIPTION
            "A conceptual row in the f3PtpTrafficPortFlowPointStatsTable.
             Entries exist in this table for each Traffic Port Flow Point."
    INDEX { neIndex, shelfIndex, slotIndex, cmEthernetTrafficPortIndex, 
            f3PtpTrafficPortFlowPointIndex, f3PtpTrafficPortFlowPointStatsIndex }
    ::= { f3PtpTrafficPortFlowPointStatsTable 1 }

F3PtpTrafficPortFlowPointStatsEntry ::= SEQUENCE {
    f3PtpTrafficPortFlowPointStatsIndex                  Integer32,
    f3PtpTrafficPortFlowPointStatsIntervalType           CmPmIntervalType,
    f3PtpTrafficPortFlowPointStatsValid                  TruthValue,
    f3PtpTrafficPortFlowPointStatsAction                 CmPmBinAction,
    f3PtpTrafficPortFlowPointStatsAnnouncesRx            PerfCounter64,
    f3PtpTrafficPortFlowPointStatsAnnouncesTx            PerfCounter64,
    f3PtpTrafficPortFlowPointStatsSyncsRx                PerfCounter64,
    f3PtpTrafficPortFlowPointStatsSyncsTx                PerfCounter64,
    f3PtpTrafficPortFlowPointStatsFollowupsRx            PerfCounter64,
    f3PtpTrafficPortFlowPointStatsFollowupsTx            PerfCounter64,
    f3PtpTrafficPortFlowPointStatsDelayReqsRx            PerfCounter64,
    f3PtpTrafficPortFlowPointStatsDelayReqsTx            PerfCounter64,
    f3PtpTrafficPortFlowPointStatsDelayRspsRx            PerfCounter64,
    f3PtpTrafficPortFlowPointStatsDelayRspsTx            PerfCounter64,
    f3PtpTrafficPortFlowPointStatsPDelayReqsRx           PerfCounter64,
    f3PtpTrafficPortFlowPointStatsPDelayReqsTx           PerfCounter64,
    f3PtpTrafficPortFlowPointStatsPDelayRspsRx           PerfCounter64,
    f3PtpTrafficPortFlowPointStatsPDelayRspsTx           PerfCounter64,
    f3PtpTrafficPortFlowPointStatsPDelayRspFollowupsRx   PerfCounter64,
    f3PtpTrafficPortFlowPointStatsPDelayRspFollowupsTx   PerfCounter64,
    f3PtpTrafficPortFlowPointStatsSignalingRx            PerfCounter64,
    f3PtpTrafficPortFlowPointStatsSignalingTx            PerfCounter64,
    f3PtpTrafficPortFlowPointStatsMgmtFramesRx           PerfCounter64,
    f3PtpTrafficPortFlowPointStatsMgmtFramesTx           PerfCounter64,
    f3PtpTrafficPortFlowPointStatsPtpUnknownsRx          PerfCounter64,
    f3PtpTrafficPortFlowPointStatsPtpUnknownsTx          PerfCounter64,
    f3PtpTrafficPortFlowPointStatsMinSyncResTime         Unsigned32,
    f3PtpTrafficPortFlowPointStatsMaxSyncResTime         Unsigned32,
    f3PtpTrafficPortFlowPointStatsAvgSyncResTime         Unsigned32,
    f3PtpTrafficPortFlowPointStatsMinDelayReqResTime     Unsigned32,
    f3PtpTrafficPortFlowPointStatsMaxDelayReqResTime     Unsigned32,
    f3PtpTrafficPortFlowPointStatsAvgDelayReqResTime     Unsigned32,
    f3PtpTrafficPortFlowPointStatsMinPDelayReqResTime    Unsigned32,
    f3PtpTrafficPortFlowPointStatsMaxPDelayReqResTime    Unsigned32,
    f3PtpTrafficPortFlowPointStatsAvgPDelayReqResTime    Unsigned32,
    f3PtpTrafficPortFlowPointStatsMinPDelayRspResTime    Unsigned32,
    f3PtpTrafficPortFlowPointStatsMaxPDelayRspResTime    Unsigned32,
    f3PtpTrafficPortFlowPointStatsAvgPDelayRspResTime    Unsigned32,
    f3PtpTrafficPortFlowPointStatsDestMciNoMatchDiscards PerfCounter64
}

f3PtpTrafficPortFlowPointStatsIndex OBJECT-TYPE
    SYNTAX      Integer32 (1..4)
   MAX-ACCESS  not-accessible 
    STATUS      current
    DESCRIPTION
            "An arbitrary integer index value used to uniquely identify
            this Traffic Port PTP Flow Point statistics entry. 
            1 - 15min
            2 - 1day
            3 - rollover
            4 - 5min"
    ::= { f3PtpTrafficPortFlowPointStatsEntry 1 }

f3PtpTrafficPortFlowPointStatsIntervalType OBJECT-TYPE
    SYNTAX      CmPmIntervalType
   MAX-ACCESS  read-only
    STATUS      current
    DESCRIPTION
            "Indicates the type of collection, i.e. whether it is
             15 Min, 1 Day or rollover."
    ::= { f3PtpTrafficPortFlowPointStatsEntry 2 }

f3PtpTrafficPortFlowPointStatsValid OBJECT-TYPE
    SYNTAX      TruthValue
   MAX-ACCESS  read-only
    STATUS      current
    DESCRIPTION
            "Indicates the validity of the bin."
    ::= { f3PtpTrafficPortFlowPointStatsEntry 3 }

f3PtpTrafficPortFlowPointStatsAction OBJECT-TYPE
    SYNTAX      CmPmBinAction
   MAX-ACCESS  read-write
    STATUS      current
    DESCRIPTION
            "Allows the Manager to clear the bin."
    ::= { f3PtpTrafficPortFlowPointStatsEntry 4 }

f3PtpTrafficPortFlowPointStatsAnnouncesRx OBJECT-TYPE
     SYNTAX     PerfCounter64
    MAX-ACCESS read-only
     STATUS     current
     DESCRIPTION
         "Number of PTP Announce messages received on the PTP Flow Point."
     ::= { f3PtpTrafficPortFlowPointStatsEntry 5 }

f3PtpTrafficPortFlowPointStatsAnnouncesTx OBJECT-TYPE
     SYNTAX     PerfCounter64
    MAX-ACCESS read-only
     STATUS     current
     DESCRIPTION
         "Number of Announce Messages transmitted on the PTP Flow Point.
          This object is applicable for transparent clocks."
     ::= { f3PtpTrafficPortFlowPointStatsEntry 6 }

f3PtpTrafficPortFlowPointStatsSyncsRx OBJECT-TYPE
     SYNTAX     PerfCounter64
    MAX-ACCESS read-only
     STATUS     current
     DESCRIPTION
         "Number of Sync Messages received on the PTP Flow Point."
     ::= { f3PtpTrafficPortFlowPointStatsEntry 7 }

f3PtpTrafficPortFlowPointStatsSyncsTx OBJECT-TYPE
     SYNTAX     PerfCounter64
    MAX-ACCESS read-only
     STATUS     current
     DESCRIPTION
         "Number of Sync Messages transmitted on the PTP Flow Point.
          This object is applicable for transparent clocks."
     ::= { f3PtpTrafficPortFlowPointStatsEntry 8 }

f3PtpTrafficPortFlowPointStatsFollowupsRx OBJECT-TYPE
     SYNTAX     PerfCounter64
    MAX-ACCESS read-only
     STATUS     current
     DESCRIPTION
         "Number of Follow up Messages received on the PTP Flow Point."
     ::= { f3PtpTrafficPortFlowPointStatsEntry 9 }

f3PtpTrafficPortFlowPointStatsFollowupsTx OBJECT-TYPE
     SYNTAX     PerfCounter64
    MAX-ACCESS read-only
     STATUS     current
     DESCRIPTION
         "Number of Follow up Messages transmitted on the PTP Flow Point."
     ::= { f3PtpTrafficPortFlowPointStatsEntry 10 }

f3PtpTrafficPortFlowPointStatsDelayReqsRx OBJECT-TYPE
     SYNTAX     PerfCounter64
    MAX-ACCESS read-only
     STATUS     current
     DESCRIPTION
         "Number of Delay Request Messages received on the PTP Flow Point."
     ::= { f3PtpTrafficPortFlowPointStatsEntry 11 }

f3PtpTrafficPortFlowPointStatsDelayReqsTx OBJECT-TYPE
     SYNTAX     PerfCounter64
    MAX-ACCESS read-only
     STATUS     current
     DESCRIPTION
         "Number of Delay Request Messages transmitted on the PTP Flow Point."
     ::= { f3PtpTrafficPortFlowPointStatsEntry 12 }

f3PtpTrafficPortFlowPointStatsDelayRspsRx OBJECT-TYPE
     SYNTAX     PerfCounter64
    MAX-ACCESS read-only
     STATUS     current
     DESCRIPTION
         "Number of Delay Response Messages received on the PTP Flow Point."
     ::= { f3PtpTrafficPortFlowPointStatsEntry 13 }

f3PtpTrafficPortFlowPointStatsDelayRspsTx OBJECT-TYPE
     SYNTAX     PerfCounter64
    MAX-ACCESS read-only
     STATUS     current
     DESCRIPTION
         "Number of Delay Response Messages transmitted on the PTP Flow Point."
     ::= { f3PtpTrafficPortFlowPointStatsEntry 14 }

f3PtpTrafficPortFlowPointStatsPDelayReqsRx OBJECT-TYPE
     SYNTAX     PerfCounter64
    MAX-ACCESS read-only
     STATUS     current
     DESCRIPTION
         "Number of Peer Delay Request Messages received on the PTP Flow Point."
     ::= { f3PtpTrafficPortFlowPointStatsEntry 15 }

f3PtpTrafficPortFlowPointStatsPDelayReqsTx OBJECT-TYPE
     SYNTAX     PerfCounter64
    MAX-ACCESS read-only
     STATUS     current
     DESCRIPTION
         "Number of Peer Delay Request Messages transmitted on the PTP Flow Point."
     ::= { f3PtpTrafficPortFlowPointStatsEntry 16 }

f3PtpTrafficPortFlowPointStatsPDelayRspsRx OBJECT-TYPE
     SYNTAX     PerfCounter64
    MAX-ACCESS read-only
     STATUS     current
     DESCRIPTION
         "Number of Peer Delay Response Messages received on the PTP Flow Point."
     ::= { f3PtpTrafficPortFlowPointStatsEntry 17 }

f3PtpTrafficPortFlowPointStatsPDelayRspsTx OBJECT-TYPE
     SYNTAX     PerfCounter64
    MAX-ACCESS read-only
     STATUS     current
     DESCRIPTION
         "Number of Peer Delay Response Messages transmitted on the PTP Flow Point."
     ::= { f3PtpTrafficPortFlowPointStatsEntry 18 }

f3PtpTrafficPortFlowPointStatsPDelayRspFollowupsRx OBJECT-TYPE
     SYNTAX     PerfCounter64
    MAX-ACCESS read-only
     STATUS     current
     DESCRIPTION
         "Number of Peer Delay Response Followup Messages received on the PTP Flow Point."
     ::= { f3PtpTrafficPortFlowPointStatsEntry 19 }

f3PtpTrafficPortFlowPointStatsPDelayRspFollowupsTx OBJECT-TYPE
     SYNTAX     PerfCounter64
    MAX-ACCESS read-only
     STATUS     current
     DESCRIPTION
         "Number of Peer Delay Response Followup Messages transmitted on the PTP Flow Point."
     ::= { f3PtpTrafficPortFlowPointStatsEntry 20 }

f3PtpTrafficPortFlowPointStatsSignalingRx OBJECT-TYPE
     SYNTAX     PerfCounter64
    MAX-ACCESS read-only
     STATUS     current
     DESCRIPTION
         "Number of PTP Signaling Messages received on the PTP Flow Point."
     ::= { f3PtpTrafficPortFlowPointStatsEntry 21 }

f3PtpTrafficPortFlowPointStatsSignalingTx OBJECT-TYPE
     SYNTAX     PerfCounter64
    MAX-ACCESS read-only
     STATUS     current
     DESCRIPTION
         "Number of PTP Signaling Messages Messages transmitted on the PTP Flow Point."
     ::= { f3PtpTrafficPortFlowPointStatsEntry 22 }

f3PtpTrafficPortFlowPointStatsMgmtFramesRx OBJECT-TYPE
     SYNTAX     PerfCounter64
    MAX-ACCESS read-only
     STATUS     current
     DESCRIPTION
         "Number of PTP Management Frames received on the PTP Flow Point."
     ::= { f3PtpTrafficPortFlowPointStatsEntry 23 }

f3PtpTrafficPortFlowPointStatsMgmtFramesTx OBJECT-TYPE
     SYNTAX     PerfCounter64
    MAX-ACCESS read-only
     STATUS     current
     DESCRIPTION
         "Number of PTP Management Frames Messages transmitted on the PTP Flow Point."
     ::= { f3PtpTrafficPortFlowPointStatsEntry 24 }

f3PtpTrafficPortFlowPointStatsPtpUnknownsRx OBJECT-TYPE
     SYNTAX     PerfCounter64
    MAX-ACCESS read-only
     STATUS     current
     DESCRIPTION
         "Number of Unknown PTP Messages received on the PTP Flow Point."
     ::= { f3PtpTrafficPortFlowPointStatsEntry 25 }

f3PtpTrafficPortFlowPointStatsPtpUnknownsTx OBJECT-TYPE
     SYNTAX     PerfCounter64
    MAX-ACCESS read-only
     STATUS     current
     DESCRIPTION
         "Number of Unknown PTP Messages transmitted on the PTP Flow Point."
     ::= { f3PtpTrafficPortFlowPointStatsEntry 26 }

f3PtpTrafficPortFlowPointStatsMinSyncResTime OBJECT-TYPE
     SYNTAX     Unsigned32
    MAX-ACCESS read-only
     STATUS     current
     DESCRIPTION
         "The minimum residence time for PTP Sync messages."
     ::= { f3PtpTrafficPortFlowPointStatsEntry 27 }

f3PtpTrafficPortFlowPointStatsMaxSyncResTime OBJECT-TYPE
     SYNTAX     Unsigned32
    MAX-ACCESS read-only
     STATUS     current
     DESCRIPTION
         "The maximum residence time for PTP Sync messages."
     ::= { f3PtpTrafficPortFlowPointStatsEntry 28 }

f3PtpTrafficPortFlowPointStatsAvgSyncResTime OBJECT-TYPE
     SYNTAX     Unsigned32
    MAX-ACCESS read-only
     STATUS     current
     DESCRIPTION
         "The average residence time for PTP Sync messages."
     ::= { f3PtpTrafficPortFlowPointStatsEntry 29 }

f3PtpTrafficPortFlowPointStatsMinDelayReqResTime OBJECT-TYPE
     SYNTAX     Unsigned32
    MAX-ACCESS read-only
     STATUS     current
     DESCRIPTION
         "The minimum residence time for PTP Delay Request messages."
     ::= { f3PtpTrafficPortFlowPointStatsEntry 30 }

f3PtpTrafficPortFlowPointStatsMaxDelayReqResTime OBJECT-TYPE
     SYNTAX     Unsigned32
    MAX-ACCESS read-only
     STATUS     current
     DESCRIPTION
         "The maximum residence time for PTP Delay Request messages."
     ::= { f3PtpTrafficPortFlowPointStatsEntry 31 }

f3PtpTrafficPortFlowPointStatsAvgDelayReqResTime OBJECT-TYPE
     SYNTAX     Unsigned32
    MAX-ACCESS read-only
     STATUS     current
     DESCRIPTION
         "The average residence time for PTP Delay Request messages."
     ::= { f3PtpTrafficPortFlowPointStatsEntry 32 }

f3PtpTrafficPortFlowPointStatsMinPDelayReqResTime OBJECT-TYPE
     SYNTAX     Unsigned32
    MAX-ACCESS read-only
     STATUS     current
     DESCRIPTION
         "The minimum residence time for PTP Peer Delay Request messages."
     ::= { f3PtpTrafficPortFlowPointStatsEntry 33 }

f3PtpTrafficPortFlowPointStatsMaxPDelayReqResTime OBJECT-TYPE
     SYNTAX     Unsigned32
    MAX-ACCESS read-only
     STATUS     current
     DESCRIPTION
         "The maximum residence time for PTP Peer Delay Request messages."
     ::= { f3PtpTrafficPortFlowPointStatsEntry 34 }

f3PtpTrafficPortFlowPointStatsAvgPDelayReqResTime OBJECT-TYPE
     SYNTAX     Unsigned32
    MAX-ACCESS read-only
     STATUS     current
     DESCRIPTION
         "The average residence time for PTP Peer Delay Request messages."
     ::= { f3PtpTrafficPortFlowPointStatsEntry 35 }

f3PtpTrafficPortFlowPointStatsMinPDelayRspResTime OBJECT-TYPE
     SYNTAX     Unsigned32
    MAX-ACCESS read-only
     STATUS     current
     DESCRIPTION
         "The minimum residence time for PTP Peer Delay Response messages."
     ::= { f3PtpTrafficPortFlowPointStatsEntry 36 }

f3PtpTrafficPortFlowPointStatsMaxPDelayRspResTime OBJECT-TYPE
     SYNTAX     Unsigned32
    MAX-ACCESS read-only
     STATUS     current
     DESCRIPTION
         "The maximum residence time for PTP Peer Delay Response messages."
     ::= { f3PtpTrafficPortFlowPointStatsEntry 37 }

f3PtpTrafficPortFlowPointStatsAvgPDelayRspResTime OBJECT-TYPE
     SYNTAX     Unsigned32
    MAX-ACCESS read-only
     STATUS     current
     DESCRIPTION
         "The average residence time for PTP Peer Delay Response messages."
     ::= { f3PtpTrafficPortFlowPointStatsEntry 38 }

f3PtpTrafficPortFlowPointStatsDestMciNoMatchDiscards OBJECT-TYPE
     SYNTAX     PerfCounter64
    MAX-ACCESS read-only
     STATUS     current
     DESCRIPTION
         "The dest MCI no match discards messages."
     ::= { f3PtpTrafficPortFlowPointStatsEntry 39 }

--
-- Traffic Port PTP Flow Point History Table
--
f3PtpTrafficPortFlowPointHistoryTable OBJECT-TYPE
    SYNTAX      SEQUENCE OF F3PtpTrafficPortFlowPointHistoryEntry
   MAX-ACCESS  not-accessible
    STATUS      current
    DESCRIPTION
            "A collection of Traffic Port PTP Flow Point history statistics.  
             These reflect the history data."
    ::= { f3PtpPerformanceObjects 20 }

f3PtpTrafficPortFlowPointHistoryEntry OBJECT-TYPE
    SYNTAX      F3PtpTrafficPortFlowPointHistoryEntry 
   MAX-ACCESS  not-accessible
    STATUS      current
    DESCRIPTION
            "A conceptual row in the f3PtpTrafficPortFlowPointHistoryTable.
             Entries exist in this table for each Traffic Port Flow Point."
    INDEX { neIndex, shelfIndex, slotIndex, cmEthernetTrafficPortIndex, 
            f3PtpTrafficPortFlowPointIndex, f3PtpTrafficPortFlowPointStatsIndex, 
            f3PtpTrafficPortFlowPointHistoryIndex }
    ::= { f3PtpTrafficPortFlowPointHistoryTable 1 }

F3PtpTrafficPortFlowPointHistoryEntry ::= SEQUENCE {
    f3PtpTrafficPortFlowPointHistoryIndex                  Integer32,
    f3PtpTrafficPortFlowPointHistoryTime                   DateAndTime,
    f3PtpTrafficPortFlowPointHistoryValid                  TruthValue,
    f3PtpTrafficPortFlowPointHistoryAction                 CmPmBinAction,
    f3PtpTrafficPortFlowPointHistoryAnnouncesRx            PerfCounter64,
    f3PtpTrafficPortFlowPointHistoryAnnouncesTx            PerfCounter64,
    f3PtpTrafficPortFlowPointHistorySyncsRx                PerfCounter64,
    f3PtpTrafficPortFlowPointHistorySyncsTx                PerfCounter64,
    f3PtpTrafficPortFlowPointHistoryFollowupsRx            PerfCounter64,
    f3PtpTrafficPortFlowPointHistoryFollowupsTx            PerfCounter64,
    f3PtpTrafficPortFlowPointHistoryDelayReqsRx            PerfCounter64,
    f3PtpTrafficPortFlowPointHistoryDelayReqsTx            PerfCounter64,
    f3PtpTrafficPortFlowPointHistoryDelayRspsRx            PerfCounter64,
    f3PtpTrafficPortFlowPointHistoryDelayRspsTx            PerfCounter64,
    f3PtpTrafficPortFlowPointHistoryPDelayReqsRx           PerfCounter64,
    f3PtpTrafficPortFlowPointHistoryPDelayReqsTx           PerfCounter64,
    f3PtpTrafficPortFlowPointHistoryPDelayRspsRx           PerfCounter64,
    f3PtpTrafficPortFlowPointHistoryPDelayRspsTx           PerfCounter64,
    f3PtpTrafficPortFlowPointHistoryPDelayRspFollowupsRx   PerfCounter64,
    f3PtpTrafficPortFlowPointHistoryPDelayRspFollowupsTx   PerfCounter64,
    f3PtpTrafficPortFlowPointHistorySignalingRx            PerfCounter64,
    f3PtpTrafficPortFlowPointHistorySignalingTx            PerfCounter64,
    f3PtpTrafficPortFlowPointHistoryMgmtFramesRx           PerfCounter64,
    f3PtpTrafficPortFlowPointHistoryMgmtFramesTx           PerfCounter64,
    f3PtpTrafficPortFlowPointHistoryPtpUnknownsRx          PerfCounter64,
    f3PtpTrafficPortFlowPointHistoryPtpUnknownsTx          PerfCounter64,
    f3PtpTrafficPortFlowPointHistoryMinSyncResTime         Unsigned32,
    f3PtpTrafficPortFlowPointHistoryMaxSyncResTime         Unsigned32,
    f3PtpTrafficPortFlowPointHistoryAvgSyncResTime         Unsigned32,
    f3PtpTrafficPortFlowPointHistoryMinDelayReqResTime     Unsigned32,
    f3PtpTrafficPortFlowPointHistoryMaxDelayReqResTime     Unsigned32,
    f3PtpTrafficPortFlowPointHistoryAvgDelayReqResTime     Unsigned32,
    f3PtpTrafficPortFlowPointHistoryMinPDelayReqResTime    Unsigned32,
    f3PtpTrafficPortFlowPointHistoryMaxPDelayReqResTime    Unsigned32,
    f3PtpTrafficPortFlowPointHistoryAvgPDelayReqResTime    Unsigned32,
    f3PtpTrafficPortFlowPointHistoryMinPDelayRspResTime    Unsigned32,
    f3PtpTrafficPortFlowPointHistoryMaxPDelayRspResTime    Unsigned32,
    f3PtpTrafficPortFlowPointHistoryAvgPDelayRspResTime    Unsigned32,
    f3PtpTrafficPortFlowPointHistoryDestMciNoMatchDiscards PerfCounter64
}

f3PtpTrafficPortFlowPointHistoryIndex OBJECT-TYPE
    SYNTAX      Integer32 (1..32)
   MAX-ACCESS  not-accessible 
    STATUS      current
    DESCRIPTION
            "An arbitrary integer index value used to uniquely identify
            this Ethernet Traffic Port PTP Flow point PM history entry."
    ::= { f3PtpTrafficPortFlowPointHistoryEntry 1 }

f3PtpTrafficPortFlowPointHistoryTime OBJECT-TYPE
    SYNTAX      DateAndTime
   MAX-ACCESS  read-only
    STATUS      current
    DESCRIPTION
            "Indicates the time of history bin creation." 
    ::= { f3PtpTrafficPortFlowPointHistoryEntry 2 }

f3PtpTrafficPortFlowPointHistoryValid OBJECT-TYPE
    SYNTAX      TruthValue
   MAX-ACCESS  read-only
    STATUS      current
    DESCRIPTION
            "Indicates the validity of the bin."
    ::= { f3PtpTrafficPortFlowPointHistoryEntry 3 }

f3PtpTrafficPortFlowPointHistoryAction OBJECT-TYPE
    SYNTAX      CmPmBinAction
   MAX-ACCESS  read-write
    STATUS      current
    DESCRIPTION
            "Allows the Manager to clear the bin."
    ::= { f3PtpTrafficPortFlowPointHistoryEntry 4 }

f3PtpTrafficPortFlowPointHistoryAnnouncesRx OBJECT-TYPE
     SYNTAX     PerfCounter64
    MAX-ACCESS read-only
     STATUS     current
     DESCRIPTION
         "Number of PTP Announce messages received on the PTP Flow Point."
     ::= { f3PtpTrafficPortFlowPointHistoryEntry 5 }

f3PtpTrafficPortFlowPointHistoryAnnouncesTx OBJECT-TYPE
     SYNTAX     PerfCounter64
    MAX-ACCESS read-only
     STATUS     current
     DESCRIPTION
         "Number of Announce Messages transmitted on the PTP Flow Point.
          This object is applicable for transparent clocks."
     ::= { f3PtpTrafficPortFlowPointHistoryEntry 6 }

f3PtpTrafficPortFlowPointHistorySyncsRx OBJECT-TYPE
     SYNTAX     PerfCounter64
    MAX-ACCESS read-only
     STATUS     current
     DESCRIPTION
         "Number of Sync Messages received on the PTP Flow Point."
     ::= { f3PtpTrafficPortFlowPointHistoryEntry 7 }

f3PtpTrafficPortFlowPointHistorySyncsTx OBJECT-TYPE
     SYNTAX     PerfCounter64
    MAX-ACCESS read-only
     STATUS     current
     DESCRIPTION
         "Number of Sync Messages transmitted on the PTP Flow Point.
          This object is applicable for transparent clocks."
     ::= { f3PtpTrafficPortFlowPointHistoryEntry 8 }

f3PtpTrafficPortFlowPointHistoryFollowupsRx OBJECT-TYPE
     SYNTAX     PerfCounter64
    MAX-ACCESS read-only
     STATUS     current
     DESCRIPTION
         "Number of Follow up Messages received on the PTP Flow Point."
     ::= { f3PtpTrafficPortFlowPointHistoryEntry 9 }

f3PtpTrafficPortFlowPointHistoryFollowupsTx OBJECT-TYPE
     SYNTAX     PerfCounter64
    MAX-ACCESS read-only
     STATUS     current
     DESCRIPTION
         "Number of Follow up Messages transmitted on the PTP Flow Point."
     ::= { f3PtpTrafficPortFlowPointHistoryEntry 10 }

f3PtpTrafficPortFlowPointHistoryDelayReqsRx OBJECT-TYPE
     SYNTAX     PerfCounter64
    MAX-ACCESS read-only
     STATUS     current
     DESCRIPTION
         "Number of Delay Request Messages received on the PTP Flow Point."
     ::= { f3PtpTrafficPortFlowPointHistoryEntry 11 }

f3PtpTrafficPortFlowPointHistoryDelayReqsTx OBJECT-TYPE
     SYNTAX     PerfCounter64
    MAX-ACCESS read-only
     STATUS     current
     DESCRIPTION
         "Number of Delay Request Messages transmitted on the PTP Flow Point."
     ::= { f3PtpTrafficPortFlowPointHistoryEntry 12 }

f3PtpTrafficPortFlowPointHistoryDelayRspsRx OBJECT-TYPE
     SYNTAX     PerfCounter64
    MAX-ACCESS read-only
     STATUS     current
     DESCRIPTION
         "Number of Delay Response Messages received on the PTP Flow Point."
     ::= { f3PtpTrafficPortFlowPointHistoryEntry 13 }

f3PtpTrafficPortFlowPointHistoryDelayRspsTx OBJECT-TYPE
     SYNTAX     PerfCounter64
    MAX-ACCESS read-only
     STATUS     current
     DESCRIPTION
         "Number of Delay Response Messages transmitted on the PTP Flow Point."
     ::= { f3PtpTrafficPortFlowPointHistoryEntry 14 }

f3PtpTrafficPortFlowPointHistoryPDelayReqsRx OBJECT-TYPE
     SYNTAX     PerfCounter64
    MAX-ACCESS read-only
     STATUS     current
     DESCRIPTION
         "Number of Peer Delay Request Messages received on the PTP Flow Point."
     ::= { f3PtpTrafficPortFlowPointHistoryEntry 15 }

f3PtpTrafficPortFlowPointHistoryPDelayReqsTx OBJECT-TYPE
     SYNTAX     PerfCounter64
    MAX-ACCESS read-only
     STATUS     current
     DESCRIPTION
         "Number of Peer Delay Request Messages transmitted on the PTP Flow Point."
     ::= { f3PtpTrafficPortFlowPointHistoryEntry 16 }

f3PtpTrafficPortFlowPointHistoryPDelayRspsRx OBJECT-TYPE
     SYNTAX     PerfCounter64
    MAX-ACCESS read-only
     STATUS     current
     DESCRIPTION
         "Number of Peer Delay Response Messages received on the PTP Flow Point."
     ::= { f3PtpTrafficPortFlowPointHistoryEntry 17 }

f3PtpTrafficPortFlowPointHistoryPDelayRspsTx OBJECT-TYPE
     SYNTAX     PerfCounter64
    MAX-ACCESS read-only
     STATUS     current
     DESCRIPTION
         "Number of Peer Delay Response Messages transmitted on the PTP Flow Point."
     ::= { f3PtpTrafficPortFlowPointHistoryEntry 18 }

f3PtpTrafficPortFlowPointHistoryPDelayRspFollowupsRx OBJECT-TYPE
     SYNTAX     PerfCounter64
    MAX-ACCESS read-only
     STATUS     current
     DESCRIPTION
         "Number of Peer Delay Response Followup Messages received on the PTP Flow Point."
     ::= { f3PtpTrafficPortFlowPointHistoryEntry 19 }

f3PtpTrafficPortFlowPointHistoryPDelayRspFollowupsTx OBJECT-TYPE
     SYNTAX     PerfCounter64
    MAX-ACCESS read-only
     STATUS     current
     DESCRIPTION
         "Number of Peer Delay Response Followup Messages transmitted on the PTP Flow Point."
     ::= { f3PtpTrafficPortFlowPointHistoryEntry 20 }

f3PtpTrafficPortFlowPointHistorySignalingRx OBJECT-TYPE
     SYNTAX     PerfCounter64
    MAX-ACCESS read-only
     STATUS     current
     DESCRIPTION
         "Number of PTP Signaling Messages received on the PTP Flow Point."
     ::= { f3PtpTrafficPortFlowPointHistoryEntry 21 }

f3PtpTrafficPortFlowPointHistorySignalingTx OBJECT-TYPE
     SYNTAX     PerfCounter64
    MAX-ACCESS read-only
     STATUS     current
     DESCRIPTION
         "Number of PTP Signaling Messages Messages transmitted on the PTP Flow Point."
     ::= { f3PtpTrafficPortFlowPointHistoryEntry 22 }

f3PtpTrafficPortFlowPointHistoryMgmtFramesRx OBJECT-TYPE
     SYNTAX     PerfCounter64
    MAX-ACCESS read-only
     STATUS     current
     DESCRIPTION
         "Number of PTP Management Frames received on the PTP Flow Point."
     ::= { f3PtpTrafficPortFlowPointHistoryEntry 23 }

f3PtpTrafficPortFlowPointHistoryMgmtFramesTx OBJECT-TYPE
     SYNTAX     PerfCounter64
    MAX-ACCESS read-only
     STATUS     current
     DESCRIPTION
         "Number of PTP Management Frames Messages transmitted on the PTP Flow Point."
     ::= { f3PtpTrafficPortFlowPointHistoryEntry 24 }

f3PtpTrafficPortFlowPointHistoryPtpUnknownsRx OBJECT-TYPE
     SYNTAX     PerfCounter64
    MAX-ACCESS read-only
     STATUS     current
     DESCRIPTION
         "Number of Unknown PTP Messages received on the PTP Flow Point."
     ::= { f3PtpTrafficPortFlowPointHistoryEntry 25 }

f3PtpTrafficPortFlowPointHistoryPtpUnknownsTx OBJECT-TYPE
     SYNTAX     PerfCounter64
    MAX-ACCESS read-only
     STATUS     current
     DESCRIPTION
         "Number of Unknown PTP Messages transmitted on the PTP Flow Point."
     ::= { f3PtpTrafficPortFlowPointHistoryEntry 26 }

f3PtpTrafficPortFlowPointHistoryMinSyncResTime OBJECT-TYPE
     SYNTAX     Unsigned32
    MAX-ACCESS read-only
     STATUS     current
     DESCRIPTION
         "The minimum residence time for PTP Sync messages."
     ::= { f3PtpTrafficPortFlowPointHistoryEntry 27 }

f3PtpTrafficPortFlowPointHistoryMaxSyncResTime OBJECT-TYPE
     SYNTAX     Unsigned32
    MAX-ACCESS read-only
     STATUS     current
     DESCRIPTION
         "The maximum residence time for PTP Sync messages."
     ::= { f3PtpTrafficPortFlowPointHistoryEntry 28 }

f3PtpTrafficPortFlowPointHistoryAvgSyncResTime OBJECT-TYPE
     SYNTAX     Unsigned32
    MAX-ACCESS read-only
     STATUS     current
     DESCRIPTION
         "The average residence time for PTP Sync messages."
     ::= { f3PtpTrafficPortFlowPointHistoryEntry 29 }

f3PtpTrafficPortFlowPointHistoryMinDelayReqResTime OBJECT-TYPE
     SYNTAX     Unsigned32
    MAX-ACCESS read-only
     STATUS     current
     DESCRIPTION
         "The minimum residence time for PTP Delay Request messages."
     ::= { f3PtpTrafficPortFlowPointHistoryEntry 30 }

f3PtpTrafficPortFlowPointHistoryMaxDelayReqResTime OBJECT-TYPE
     SYNTAX     Unsigned32
    MAX-ACCESS read-only
     STATUS     current
     DESCRIPTION
         "The maximum residence time for PTP Delay Request messages."
     ::= { f3PtpTrafficPortFlowPointHistoryEntry 31 }

f3PtpTrafficPortFlowPointHistoryAvgDelayReqResTime OBJECT-TYPE
     SYNTAX     Unsigned32
    MAX-ACCESS read-only
     STATUS     current
     DESCRIPTION
         "The average residence time for PTP Delay Request messages."
     ::= { f3PtpTrafficPortFlowPointHistoryEntry 32 }

f3PtpTrafficPortFlowPointHistoryMinPDelayReqResTime OBJECT-TYPE
     SYNTAX     Unsigned32
    MAX-ACCESS read-only
     STATUS     current
     DESCRIPTION
         "The minimum residence time for PTP Peer Delay Request messages."
     ::= { f3PtpTrafficPortFlowPointHistoryEntry 33 }

f3PtpTrafficPortFlowPointHistoryMaxPDelayReqResTime OBJECT-TYPE
     SYNTAX     Unsigned32
    MAX-ACCESS read-only
     STATUS     current
     DESCRIPTION
         "The maximum residence time for PTP Peer Delay Request messages."
     ::= { f3PtpTrafficPortFlowPointHistoryEntry 34 }

f3PtpTrafficPortFlowPointHistoryAvgPDelayReqResTime OBJECT-TYPE
     SYNTAX     Unsigned32
    MAX-ACCESS read-only
     STATUS     current
     DESCRIPTION
         "The average residence time for PTP Peer Delay Request messages."
     ::= { f3PtpTrafficPortFlowPointHistoryEntry 35 }

f3PtpTrafficPortFlowPointHistoryMinPDelayRspResTime OBJECT-TYPE
     SYNTAX     Unsigned32
    MAX-ACCESS read-only
     STATUS     current
     DESCRIPTION
         "The minimum residence time for PTP Peer Delay Response messages."
     ::= { f3PtpTrafficPortFlowPointHistoryEntry 36 }

f3PtpTrafficPortFlowPointHistoryMaxPDelayRspResTime OBJECT-TYPE
     SYNTAX     Unsigned32
    MAX-ACCESS read-only
     STATUS     current
     DESCRIPTION
         "The maximum residence time for PTP Peer Delay Response messages."
     ::= { f3PtpTrafficPortFlowPointHistoryEntry 37 }

f3PtpTrafficPortFlowPointHistoryAvgPDelayRspResTime OBJECT-TYPE
     SYNTAX     Unsigned32
    MAX-ACCESS read-only
     STATUS     current
     DESCRIPTION
         "The average residence time for PTP Peer Delay Response messages."
     ::= { f3PtpTrafficPortFlowPointHistoryEntry 38 }

f3PtpTrafficPortFlowPointHistoryDestMciNoMatchDiscards OBJECT-TYPE
     SYNTAX     PerfCounter64
    MAX-ACCESS read-only
     STATUS     current
     DESCRIPTION
         "The dest MCI no match discards messages."
     ::= { f3PtpTrafficPortFlowPointHistoryEntry 39 }

--
-- Traffic Port PTP Flow Point Threshold Table
--
f3PtpTrafficPortFlowPointThresholdTable OBJECT-TYPE
    SYNTAX      SEQUENCE OF F3PtpTrafficPortFlowPointThresholdEntry
   MAX-ACCESS  not-accessible
    STATUS      current
    DESCRIPTION
            "A table of entries that allow manageability of Traffic Port PTP Flow Point
             Thresholds."
    ::= { f3PtpPerformanceObjects 21 }

f3PtpTrafficPortFlowPointThresholdEntry OBJECT-TYPE
    SYNTAX      F3PtpTrafficPortFlowPointThresholdEntry
   MAX-ACCESS  not-accessible
    STATUS      current
    DESCRIPTION
            "A conceptual row in the f3PtpTrafficPortFlowPointThresholdTable."
    INDEX { neIndex, shelfIndex, slotIndex, cmEthernetTrafficPortIndex, 
            f3PtpTrafficPortFlowPointIndex, f3PtpTrafficPortFlowPointStatsIndex, 
            f3PtpTrafficPortFlowPointThresholdIndex }
    ::= { f3PtpTrafficPortFlowPointThresholdTable 1 }

F3PtpTrafficPortFlowPointThresholdEntry ::= SEQUENCE {
    f3PtpTrafficPortFlowPointThresholdIndex       Integer32,
    f3PtpTrafficPortFlowPointThresholdInterval    CmPmIntervalType,
    f3PtpTrafficPortFlowPointThresholdVariable    VariablePointer,
    f3PtpTrafficPortFlowPointThresholdValueLo     Unsigned32,
    f3PtpTrafficPortFlowPointThresholdValueHi     Unsigned32,
    f3PtpTrafficPortFlowPointThresholdMonValue    PerfCounter64
}

f3PtpTrafficPortFlowPointThresholdIndex OBJECT-TYPE
    SYNTAX     Integer32 (1..65535)
   MAX-ACCESS not-accessible 
    STATUS     current
    DESCRIPTION
        "An index that uniquely identifies an entry in the
        f3PtpTrafficPortFlowPointThresholdTable."
    ::= { f3PtpTrafficPortFlowPointThresholdEntry 1 }

f3PtpTrafficPortFlowPointThresholdInterval OBJECT-TYPE
    SYNTAX     CmPmIntervalType
   MAX-ACCESS read-only
    STATUS     current
    DESCRIPTION
        "The interval over which monitored value is
        sampled and compared with the specified threshold."
    ::= { f3PtpTrafficPortFlowPointThresholdEntry 2 }

f3PtpTrafficPortFlowPointThresholdVariable OBJECT-TYPE
    SYNTAX     VariablePointer
   MAX-ACCESS read-only
    STATUS     current
    DESCRIPTION
        "The object identifier of the particular variable to be
        sampled."
    ::= { f3PtpTrafficPortFlowPointThresholdEntry 3 }

f3PtpTrafficPortFlowPointThresholdValueLo OBJECT-TYPE
    SYNTAX     Unsigned32
   MAX-ACCESS read-write
    STATUS     current
    DESCRIPTION
        "Lower 32 bits of the threshold value."
    ::= { f3PtpTrafficPortFlowPointThresholdEntry 4 }

f3PtpTrafficPortFlowPointThresholdValueHi OBJECT-TYPE
    SYNTAX     Unsigned32
   MAX-ACCESS read-write
    STATUS     current
    DESCRIPTION
        "Higher 32 bits of the threshold value."
    ::= { f3PtpTrafficPortFlowPointThresholdEntry 5 }

f3PtpTrafficPortFlowPointThresholdMonValue OBJECT-TYPE
    SYNTAX     PerfCounter64
   MAX-ACCESS read-only
    STATUS     current
    DESCRIPTION
        "Monitored value corresponding to f3PtpTrafficPortFlowPointThresholdVariable."
    ::= { f3PtpTrafficPortFlowPointThresholdEntry 6 }


--
-- PTP Clock Current Statistics Table
--
--f3PtpPTPClockStatsTable OBJECT-TYPE
--    SYNTAX      SEQUENCE OF F3PtpPTPClockStatsEntry
--    MAX-ACCESS  not-accessible
--    STATUS      current
--    DESCRIPTION
--            "A collection of PTP Clock related statistics.  
--             These reflect the current data."
--    ::= { f3PtpPerformanceObjects 22 }
--
--f3PtpPTPClockStatsEntry OBJECT-TYPE
--    SYNTAX      F3PtpPTPClockStatsEntry 
--    MAX-ACCESS  not-accessible
--    STATUS      current
--    DESCRIPTION
--            "A conceptual row in the f3PtpPTPClockStatsTable.
--             Entries exist in this table for each PTP Clock."
--    INDEX { neIndex, f3PtpPTPClockIndex,  f3PtpPTPClockStatsIndex }
--    ::= { f3PtpPTPClockStatsTable 1 }
--
--F3PtpPTPClockStatsEntry ::= SEQUENCE {
--    f3PtpPTPClockStatsIndex                Integer32,
--    f3PtpPTPClockStatsIntervalType         CmPmIntervalType,
--    f3PtpPTPClockStatsValid                TruthValue,
--    f3PtpPTPClockStatsAction               CmPmBinAction,
--    f3PtpPTPClockStatsTotalTimeCR5         Unsigned32,
--    f3PtpPTPClockStatsTotalTimeCR4         Unsigned32,
--    f3PtpPTPClockStatsTotalTimeCR3         Unsigned32,
--    f3PtpPTPClockStatsTotalTimePR5         Unsigned32,
--    f3PtpPTPClockStatsTotalTimePR4         Unsigned32,
--    f3PtpPTPClockStatsTotalTimePR3         Unsigned32
--}
--
--f3PtpPTPClockStatsIndex OBJECT-TYPE
--    SYNTAX      Integer32 (1..4)
--    MAX-ACCESS  not-accessible
--    STATUS      current
--    DESCRIPTION
--            "An arbitrary integer index value used to uniquely identify
--            this PTP Clock statistics entry. 
--            1 - 15min
--            2 - 1day
--            3 - rollover
--            4 - 5min"
--    ::= { f3PtpPTPClockStatsEntry 1 }
--
--f3PtpPTPClockStatsIntervalType OBJECT-TYPE
--    SYNTAX      CmPmIntervalType
--    MAX-ACCESS  read-only
--    STATUS      current
--    DESCRIPTION
--            "Indicates the type of collection, i.e. whether it is
--             15 Min, 1 Day or rollover."
--    ::= { f3PtpPTPClockStatsEntry 2 }
--
--f3PtpPTPClockStatsValid OBJECT-TYPE
--    SYNTAX      TruthValue
--    MAX-ACCESS  read-only
--    STATUS      current
--    DESCRIPTION
--            "Indicates the validity of the bin."
--    ::= { f3PtpPTPClockStatsEntry 3 }
--
--f3PtpPTPClockStatsAction OBJECT-TYPE
--    SYNTAX      CmPmBinAction
--    MAX-ACCESS  read-write
--    STATUS      current
--    DESCRIPTION
--            "Allows the Manager to clear the bin."
--    ::= { f3PtpPTPClockStatsEntry 4 }
--
--f3PtpPTPClockStatsTotalTimeCR5 OBJECT-TYPE
--     SYNTAX     Unsigned32
--     MAX-ACCESS read-only
--     STATUS     current
--     DESCRIPTION
--         "Total Time in seconds Clock Recovery Score is 5."
--     ::= { f3PtpPTPClockStatsEntry 5 }
--
--f3PtpPTPClockStatsTotalTimeCR4 OBJECT-TYPE
--     SYNTAX     Unsigned32
--     MAX-ACCESS read-only
--     STATUS     current
--     DESCRIPTION
--         "Total Time in seconds Clock Recovery Score is 4."
--     ::= { f3PtpPTPClockStatsEntry 6 }
--
--f3PtpPTPClockStatsTotalTimeCR3 OBJECT-TYPE
--     SYNTAX     Unsigned32
--     MAX-ACCESS read-only
--     STATUS     current
--     DESCRIPTION
--         "Total Time in seconds Clock Recovery Score is 3."
--     ::= { f3PtpPTPClockStatsEntry 7 }
--
--f3PtpPTPClockStatsTotalTimePR5 OBJECT-TYPE
--     SYNTAX     Unsigned32
--     MAX-ACCESS read-only
--     STATUS     current
--     DESCRIPTION
--         "Total Time in seconds Phase Recovery Score is 5."
--     ::= { f3PtpPTPClockStatsEntry 8 }
--
--f3PtpPTPClockStatsTotalTimePR4 OBJECT-TYPE
--     SYNTAX     Unsigned32
--     MAX-ACCESS read-only
--     STATUS     current
--     DESCRIPTION
--         "Total Time in seconds Phase Recovery Score is 4."
--     ::= { f3PtpPTPClockStatsEntry 9 }
--
--f3PtpPTPClockStatsTotalTimePR3 OBJECT-TYPE
--     SYNTAX     Unsigned32
--     MAX-ACCESS read-only
--     STATUS     current
--     DESCRIPTION
--         "Total Time in seconds Phase Recovery Score is 3."
--     ::= { f3PtpPTPClockStatsEntry 10 }
--
--
-- PTP Clock History Table
--
--f3PtpPTPClockHistoryTable OBJECT-TYPE
--    SYNTAX      SEQUENCE OF F3PtpPTPClockHistoryEntry
--    MAX-ACCESS  not-accessible
--    STATUS      current
--    DESCRIPTION
--            "A collection of PTP Clock related statistics.  
--             These reflect the historical data."
--    ::= { f3PtpPerformanceObjects 23 }
--
--f3PtpPTPClockHistoryEntry OBJECT-TYPE
--    SYNTAX      F3PtpPTPClockHistoryEntry 
--    MAX-ACCESS  not-accessible
--    STATUS      current
--    DESCRIPTION
--            "A conceptual row in the f3PtpPTPClockHistoryTable.
--             Entries exist in this table for each PTP Clock."
--    INDEX { neIndex, f3PtpPTPClockIndex,  f3PtpPTPClockStatsIndex, f3PtpPTPClockHistoryIndex }
--    ::= { f3PtpPTPClockHistoryTable 1 }
--
--F3PtpPTPClockHistoryEntry ::= SEQUENCE {
--    f3PtpPTPClockHistoryIndex                  Integer32,
--    f3PtpPTPClockHistoryTime                   DateAndTime,
--    f3PtpPTPClockHistoryValid                  TruthValue,
--    f3PtpPTPClockHistoryAction                 CmPmBinAction,
--    f3PtpPTPClockHistoryTotalTimeCR5           Unsigned32,
--    f3PtpPTPClockHistoryTotalTimeCR4           Unsigned32,
--    f3PtpPTPClockHistoryTotalTimeCR3           Unsigned32,
--    f3PtpPTPClockHistoryTotalTimePR5           Unsigned32,
--    f3PtpPTPClockHistoryTotalTimePR4           Unsigned32,
--    f3PtpPTPClockHistoryTotalTimePR3           Unsigned32
--}
--
--f3PtpPTPClockHistoryIndex OBJECT-TYPE
--    SYNTAX      Integer32 (1..32)
--    MAX-ACCESS  not-accessible
--    STATUS      current
--    DESCRIPTION
--            "An arbitrary integer index value used to uniquely identify
--            this PTP Clock statistics entry. 
--            Index 1 corresponds to 15minute, index 2 to 1 day and index
--            3 corresponds to rollover."
--    ::= { f3PtpPTPClockHistoryEntry 1 }
--
--f3PtpPTPClockHistoryTime OBJECT-TYPE
--    SYNTAX      DateAndTime 
--    MAX-ACCESS  read-only
--    STATUS      current
--    DESCRIPTION
--            "Indicates the time of history bin creation." 
--    ::= { f3PtpPTPClockHistoryEntry 2 }
--
--f3PtpPTPClockHistoryValid OBJECT-TYPE
--    SYNTAX      TruthValue
--    MAX-ACCESS  read-only
--    STATUS      current
--    DESCRIPTION
--            "Indicates the validity of the bin."
--    ::= { f3PtpPTPClockHistoryEntry 3 }
--
--f3PtpPTPClockHistoryAction OBJECT-TYPE
--    SYNTAX      CmPmBinAction
--    MAX-ACCESS  read-write
--    STATUS      current
--    DESCRIPTION
--            "Allows the Manager to clear the bin."
--    ::= { f3PtpPTPClockHistoryEntry 4 }
--
--f3PtpPTPClockHistoryTotalTimeCR5 OBJECT-TYPE
--     SYNTAX     Unsigned32
--     MAX-ACCESS read-only
--     STATUS     current
--     DESCRIPTION
--         "Total Time in seconds Clock Recovery Score is 5."
--     ::= { f3PtpPTPClockHistoryEntry 5 }
--
--f3PtpPTPClockHistoryTotalTimeCR4 OBJECT-TYPE
--     SYNTAX     Unsigned32
--     MAX-ACCESS read-only
--     STATUS     current
--     DESCRIPTION
--         "Total Time in seconds Clock Recovery Score is 4."
--     ::= { f3PtpPTPClockHistoryEntry 6 }
--
--f3PtpPTPClockHistoryTotalTimeCR3 OBJECT-TYPE
--     SYNTAX     Unsigned32
--     MAX-ACCESS read-only
--     STATUS     current
--     DESCRIPTION
--         "Total Time in seconds Clock Recovery Score is 3."
--     ::= { f3PtpPTPClockHistoryEntry 7 }
--
--f3PtpPTPClockHistoryTotalTimePR5 OBJECT-TYPE
--     SYNTAX     Unsigned32
--     MAX-ACCESS read-only
--     STATUS     current
--     DESCRIPTION
--         "Total Time in seconds Phase Recovery Score is 5."
--     ::= { f3PtpPTPClockHistoryEntry 8 }
--
--f3PtpPTPClockHistoryTotalTimePR4 OBJECT-TYPE
--     SYNTAX     Unsigned32
--     MAX-ACCESS read-only
--     STATUS     current
--     DESCRIPTION
--         "Total Time in seconds Phase Recovery Score is 4."
--     ::= { f3PtpPTPClockHistoryEntry 9 }
--
--f3PtpPTPClockHistoryTotalTimePR3 OBJECT-TYPE
--     SYNTAX     Unsigned32
--     MAX-ACCESS read-only
--     STATUS     current
--     DESCRIPTION
--         "Total Time in seconds Phase Recovery Score is 3."
--     ::= { f3PtpPTPClockHistoryEntry 10 }
--
--
--
-- PTP Clock Threshold Table
--
--f3PtpPTPClockThresholdTable OBJECT-TYPE
--    SYNTAX      SEQUENCE OF F3PtpPTPClockThresholdEntry
--    MAX-ACCESS  not-accessible
--    STATUS      current
--    DESCRIPTION
--            "A table of entries that allow manageability of 
--             PTP Clock Thresholds."
--    ::= { f3PtpPerformanceObjects 24 }
--
--f3PtpPTPClockThresholdEntry OBJECT-TYPE
--    SYNTAX      F3PtpPTPClockThresholdEntry
--    MAX-ACCESS  not-accessible
--    STATUS      current
--    DESCRIPTION
--            "A conceptual row in the f3PtpPTPClockThresholdTable."
--    INDEX { neIndex, f3PtpPTPClockIndex,  
--            f3PtpPTPClockStatsIndex, f3PtpPTPClockThresholdIndex }
--    ::= { f3PtpPTPClockThresholdTable 1 }
--
--F3PtpPTPClockThresholdEntry ::= SEQUENCE {
--    f3PtpPTPClockThresholdIndex       Integer32,
--    f3PtpPTPClockThresholdInterval    CmPmIntervalType,
--    f3PtpPTPClockThresholdVariable    VariablePointer,
--    f3PtpPTPClockThresholdValueLo     Unsigned32,
--    f3PtpPTPClockThresholdValueHi     Unsigned32,
--    f3PtpPTPClockThresholdMonValue    PerfCounter64
--}
--
--f3PtpPTPClockThresholdIndex OBJECT-TYPE
--    SYNTAX     Integer32 (1..65535)
--    MAX-ACCESS not-accessible
--    STATUS     current
--    DESCRIPTION
--        "An index that uniquely identifies an entry in the
--        f3PtpPTPClockThresholdTable."
--    ::= { f3PtpPTPClockThresholdEntry 1 }
--
--f3PtpPTPClockThresholdInterval OBJECT-TYPE
--    SYNTAX     CmPmIntervalType
--    MAX-ACCESS read-only
--    STATUS     current
--    DESCRIPTION
--        "The interval over which monitored value is
--        sampled and compared with the specified threshold."
--    ::= { f3PtpPTPClockThresholdEntry 2 }
--
--f3PtpPTPClockThresholdVariable OBJECT-TYPE
--    SYNTAX     VariablePointer
--    MAX-ACCESS read-only
--    STATUS     current
--    DESCRIPTION
--        "The object identifier of the particular variable to be
--        sampled."
--    ::= { f3PtpPTPClockThresholdEntry 3 }
--
--f3PtpPTPClockThresholdValueLo OBJECT-TYPE
--    SYNTAX     Unsigned32
--    MAX-ACCESS read-write
--    STATUS     current
--    DESCRIPTION
--        "Lower 32 bits of the threshold value."
--    ::= { f3PtpPTPClockThresholdEntry 4 }
--
--f3PtpPTPClockThresholdValueHi OBJECT-TYPE
--    SYNTAX     Unsigned32
--    MAX-ACCESS read-write
--    STATUS     current
--    DESCRIPTION
--        "Higher 32 bits of the threshold value."
--    ::= { f3PtpPTPClockThresholdEntry 5 }
--
--f3PtpPTPClockThresholdMonValue OBJECT-TYPE
--    SYNTAX     PerfCounter64
--    MAX-ACCESS read-only
--    STATUS     current
--    DESCRIPTION
--        "Monitored value corresponding to f3PtpPTPClockThresholdVariable."
--    ::= { f3PtpPTPClockThresholdEntry 6 }




--
-- PTP Port Current Statistics Table
--
f3PtpPTPPortStatsTable OBJECT-TYPE
    SYNTAX      SEQUENCE OF F3PtpPTPPortStatsEntry
    MAX-ACCESS  not-accessible
    STATUS      current
    DESCRIPTION
            "A collection of PTP Port related statistics.  
             These reflect the current data."
    ::= { f3PtpPerformanceObjects 22 }

f3PtpPTPPortStatsEntry OBJECT-TYPE
    SYNTAX      F3PtpPTPPortStatsEntry 
    MAX-ACCESS  not-accessible
    STATUS      current
    DESCRIPTION
            "A conceptual row in the f3PtpPTPPortStatsTable.
             Entries exist in this table for each PTP Port."
    INDEX { neIndex, f3PtpPTPClockIndex, f3PtpPTPPortIndex,  f3PtpPTPPortStatsIndex }
 
    ::= { f3PtpPTPPortStatsTable 1 }

F3PtpPTPPortStatsEntry ::= SEQUENCE {
    f3PtpPTPPortStatsIndex                        Integer32,
    f3PtpPTPPortStatsIntervalType                 CmPmIntervalType,
    f3PtpPTPPortStatsValid                        TruthValue,
    f3PtpPTPPortStatsAction                       CmPmBinAction,
    f3PtpPTPPortStatsAvgAnnounceRate              Unsigned32,
    f3PtpPTPPortStatsAvgSyncRate                  Unsigned32,
    f3PtpPTPPortStatsAvgDelayReqRate              Unsigned32,
    f3PtpPTPPortStatsAvgDelayRespRate             Unsigned32,
    f3PtpPTPPortStatsMismatchDomainDiscards       PerfCounter64,
    f3PtpPTPPortStatsMessageWrongTypeDiscards     PerfCounter64,
    f3PtpPTPPortStatsMessagesWrongLengthDiscards  PerfCounter64,
    f3PtpPTPPortStatsUnknownMasterDiscards        PerfCounter64,
    f3PtpPTPPortStatsMinOffsetFromMaster          PerfCounter64,
    f3PtpPTPPortStatsMaxOffsetFromMaster          PerfCounter64,
    f3PtpPTPPortStatsAvgOffsetFromMaster          PerfCounter64,
    f3PtpPTPPortStatsMinSyncPathDelay             PerfCounter64,
    f3PtpPTPPortStatsMaxSyncPathDelay             PerfCounter64,
    f3PtpPTPPortStatsAvgSyncPathDelay             PerfCounter64,
    f3PtpPTPPortStatsMinMeanPathDelay             PerfCounter64,
    f3PtpPTPPortStatsMaxMeanPathDelay             PerfCounter64,
    f3PtpPTPPortStatsAvgMeanPathDelay             PerfCounter64
}

f3PtpPTPPortStatsIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpPTPPortStatsEntry 1 }

f3PtpPTPPortStatsIntervalType OBJECT-TYPE
    SYNTAX      CmPmIntervalType
    MAX-ACCESS  read-only
    STATUS      current
    DESCRIPTION
            "Indicates the type of collection, i.e. whether it is
             15 Min, 1 Day or rollover."
    ::= { f3PtpPTPPortStatsEntry 2 }

f3PtpPTPPortStatsValid OBJECT-TYPE
    SYNTAX      TruthValue
    MAX-ACCESS  read-only
    STATUS      current
    DESCRIPTION
            "Indicates the validity of the bin."
    ::= { f3PtpPTPPortStatsEntry 3 }

f3PtpPTPPortStatsAction OBJECT-TYPE
    SYNTAX      CmPmBinAction
    MAX-ACCESS  read-write
    STATUS      current
    DESCRIPTION
            "Allows the Manager to clear the bin."
    ::= { f3PtpPTPPortStatsEntry 4 }

f3PtpPTPPortStatsAvgAnnounceRate OBJECT-TYPE
     SYNTAX     Unsigned32
     MAX-ACCESS read-only
     STATUS     current
     DESCRIPTION
         "Avg Announce Rate."
     ::= { f3PtpPTPPortStatsEntry 5 }

f3PtpPTPPortStatsAvgSyncRate OBJECT-TYPE
     SYNTAX     Unsigned32
     MAX-ACCESS read-only
     STATUS     current
     DESCRIPTION
         "Avg Sync Rate."
     ::= { f3PtpPTPPortStatsEntry 6 }

f3PtpPTPPortStatsAvgDelayReqRate OBJECT-TYPE
     SYNTAX     Unsigned32
     MAX-ACCESS read-only
     STATUS     current
     DESCRIPTION
         "Avg Delay Req Rate."
     ::= { f3PtpPTPPortStatsEntry 7 }

f3PtpPTPPortStatsAvgDelayRespRate OBJECT-TYPE
     SYNTAX     Unsigned32
     MAX-ACCESS read-only
     STATUS     current
     DESCRIPTION
         "Avg Delay Resp Rate."
     ::= { f3PtpPTPPortStatsEntry 8 }

f3PtpPTPPortStatsMismatchDomainDiscards OBJECT-TYPE
     SYNTAX     PerfCounter64
     MAX-ACCESS read-only
     STATUS     current
     DESCRIPTION
         "Mismatch Domain Discards."
     ::= { f3PtpPTPPortStatsEntry 9 }

f3PtpPTPPortStatsMessageWrongTypeDiscards OBJECT-TYPE
     SYNTAX     PerfCounter64
     MAX-ACCESS read-only
     STATUS     current
     DESCRIPTION
         "Message Wrong Type Discards."
     ::= { f3PtpPTPPortStatsEntry 10 }

f3PtpPTPPortStatsMessagesWrongLengthDiscards OBJECT-TYPE
     SYNTAX     PerfCounter64
     MAX-ACCESS read-only
     STATUS     current
     DESCRIPTION
         "Messages Wrong Length Discards."
     ::= { f3PtpPTPPortStatsEntry 11 }

f3PtpPTPPortStatsUnknownMasterDiscards OBJECT-TYPE
     SYNTAX     PerfCounter64
     MAX-ACCESS read-only
     STATUS     current
     DESCRIPTION
         "Unknown Master Discards."
     ::= { f3PtpPTPPortStatsEntry 12 }

f3PtpPTPPortStatsMinOffsetFromMaster OBJECT-TYPE
     SYNTAX     PerfCounter64
     MAX-ACCESS read-only
     STATUS     current
     DESCRIPTION
         "Min Offset From Master."
     ::= { f3PtpPTPPortStatsEntry 13 }

f3PtpPTPPortStatsMaxOffsetFromMaster OBJECT-TYPE
     SYNTAX     PerfCounter64
     MAX-ACCESS read-only
     STATUS     current
     DESCRIPTION
         "Max Offset From Master."
     ::= { f3PtpPTPPortStatsEntry 14 }

f3PtpPTPPortStatsAvgOffsetFromMaster OBJECT-TYPE
     SYNTAX     PerfCounter64
     MAX-ACCESS read-only
     STATUS     current
     DESCRIPTION
         "Avg Offset From Master."
     ::= { f3PtpPTPPortStatsEntry 15 }

f3PtpPTPPortStatsMinSyncPathDelay OBJECT-TYPE
     SYNTAX     PerfCounter64
     MAX-ACCESS read-only
     STATUS     current
     DESCRIPTION
         "Min Sync Path Delay."
     ::= { f3PtpPTPPortStatsEntry 16 }

f3PtpPTPPortStatsMaxSyncPathDelay OBJECT-TYPE
     SYNTAX     PerfCounter64
     MAX-ACCESS read-only
     STATUS     current
     DESCRIPTION
         "Max Sync Path Delay."
     ::= { f3PtpPTPPortStatsEntry 17 }

f3PtpPTPPortStatsAvgSyncPathDelay OBJECT-TYPE
     SYNTAX     PerfCounter64
     MAX-ACCESS read-only
     STATUS     current
     DESCRIPTION
         "Avg Sync Path Delay."
     ::= { f3PtpPTPPortStatsEntry 18 }


f3PtpPTPPortStatsMinMeanPathDelay OBJECT-TYPE
     SYNTAX     PerfCounter64
     MAX-ACCESS read-only
     STATUS     current
     DESCRIPTION
         "Min Mean Path Delay."
     ::= { f3PtpPTPPortStatsEntry 19 }

f3PtpPTPPortStatsMaxMeanPathDelay OBJECT-TYPE
     SYNTAX     PerfCounter64
     MAX-ACCESS read-only
     STATUS     current
     DESCRIPTION
         "Max Mean Path Delay."
     ::= { f3PtpPTPPortStatsEntry 20 }

f3PtpPTPPortStatsAvgMeanPathDelay OBJECT-TYPE
     SYNTAX     PerfCounter64
     MAX-ACCESS read-only
     STATUS     current
     DESCRIPTION
         "Avg Mean Path Delay."
     ::= { f3PtpPTPPortStatsEntry 21 }


--
-- PTP Port Current History Table
--
f3PtpPTPPortHistoryTable OBJECT-TYPE
    SYNTAX      SEQUENCE OF F3PtpPTPPortHistoryEntry
    MAX-ACCESS  not-accessible
    STATUS      current
    DESCRIPTION
            "A collection of PTP Port related statistics.  
             These reflect the current data."
    ::= { f3PtpPerformanceObjects 23 }

f3PtpPTPPortHistoryEntry OBJECT-TYPE
    SYNTAX      F3PtpPTPPortHistoryEntry 
    MAX-ACCESS  not-accessible
    STATUS      current
    DESCRIPTION
            "A conceptual row in the f3PtpPTPPortHistoryTable.
             Entries exist in this table for each PTP Port."
    INDEX { neIndex, f3PtpPTPClockIndex, f3PtpPTPPortIndex,  f3PtpPTPPortStatsIndex, f3PtpPTPPortHistoryIndex }

    ::= { f3PtpPTPPortHistoryTable 1 }

F3PtpPTPPortHistoryEntry ::= SEQUENCE {
    f3PtpPTPPortHistoryIndex                        Integer32,
    f3PtpPTPPortHistoryTime                         DateAndTime,
    f3PtpPTPPortHistoryValid                        TruthValue,
    f3PtpPTPPortHistoryAction                       CmPmBinAction,
    f3PtpPTPPortHistoryAvgAnnounceRate              Unsigned32,
    f3PtpPTPPortHistoryAvgSyncRate                  Unsigned32,
    f3PtpPTPPortHistoryAvgDelayReqRate              Unsigned32,
    f3PtpPTPPortHistoryAvgDelayRespRate             Unsigned32,
    f3PtpPTPPortHistoryMismatchDomainDiscards       PerfCounter64,
    f3PtpPTPPortHistoryMessageWrongTypeDiscards     PerfCounter64,
    f3PtpPTPPortHistoryMessagesWrongLengthDiscards  PerfCounter64,
    f3PtpPTPPortHistoryUnknownMasterDiscards        PerfCounter64,
    f3PtpPTPPortHistoryMinOffsetFromMaster          PerfCounter64,
    f3PtpPTPPortHistoryMaxOffsetFromMaster          PerfCounter64,
    f3PtpPTPPortHistoryAvgOffsetFromMaster          PerfCounter64,
    f3PtpPTPPortHistoryMinSyncPathDelay             PerfCounter64,
    f3PtpPTPPortHistoryMaxSyncPathDelay             PerfCounter64,
    f3PtpPTPPortHistoryAvgSyncPathDelay             PerfCounter64,
    f3PtpPTPPortHistoryMinMeanPathDelay             PerfCounter64,
    f3PtpPTPPortHistoryMaxMeanPathDelay             PerfCounter64,
    f3PtpPTPPortHistoryAvgMeanPathDelay             PerfCounter64
}

f3PtpPTPPortHistoryIndex OBJECT-TYPE
    SYNTAX      Integer32 (1..4)
    MAX-ACCESS  not-accessible
    STATUS      current
    DESCRIPTION
            "An arbitrary integer index value used to uniquely identify
            this PTP Port statistics entry. 
            1 - 15min
            2 - 1day
            3 - rollover
            4 - 5min"
    ::= { f3PtpPTPPortHistoryEntry 1 }

f3PtpPTPPortHistoryTime OBJECT-TYPE
    SYNTAX      DateAndTime
    MAX-ACCESS  read-only
    STATUS      current
    DESCRIPTION
            "Indicates the time of history bin creation." 
    ::= { f3PtpPTPPortHistoryEntry 2 }

f3PtpPTPPortHistoryValid OBJECT-TYPE
    SYNTAX      TruthValue
    MAX-ACCESS  read-only
    STATUS      current
    DESCRIPTION
            "Indicates the validity of the bin."
    ::= { f3PtpPTPPortHistoryEntry 3 }

f3PtpPTPPortHistoryAction OBJECT-TYPE
    SYNTAX      CmPmBinAction
    MAX-ACCESS  read-write
    STATUS      current
    DESCRIPTION
            "Allows the Manager to clear the bin."
    ::= { f3PtpPTPPortHistoryEntry 4 }

f3PtpPTPPortHistoryAvgAnnounceRate OBJECT-TYPE
     SYNTAX     Unsigned32
     MAX-ACCESS read-only
     STATUS     current
     DESCRIPTION
         "Avg Announce Rate."
     ::= { f3PtpPTPPortHistoryEntry 5 }

f3PtpPTPPortHistoryAvgSyncRate OBJECT-TYPE
     SYNTAX     Unsigned32
     MAX-ACCESS read-only
     STATUS     current
     DESCRIPTION
         "Avg Sync Rate."
     ::= { f3PtpPTPPortHistoryEntry 6 }

f3PtpPTPPortHistoryAvgDelayReqRate OBJECT-TYPE
     SYNTAX     Unsigned32
     MAX-ACCESS read-only
     STATUS     current
     DESCRIPTION
         "Avg Delay Req Rate."
     ::= { f3PtpPTPPortHistoryEntry 7 }

f3PtpPTPPortHistoryAvgDelayRespRate OBJECT-TYPE
     SYNTAX     Unsigned32
     MAX-ACCESS read-only
     STATUS     current
     DESCRIPTION
         "Avg Delay Resp Rate."
     ::= { f3PtpPTPPortHistoryEntry 8 }

f3PtpPTPPortHistoryMismatchDomainDiscards OBJECT-TYPE
     SYNTAX     PerfCounter64
     MAX-ACCESS read-only
     STATUS     current
     DESCRIPTION
         "Mismatch Domain Discards."
     ::= { f3PtpPTPPortHistoryEntry 9 }

f3PtpPTPPortHistoryMessageWrongTypeDiscards OBJECT-TYPE
     SYNTAX     PerfCounter64
     MAX-ACCESS read-only
     STATUS     current
     DESCRIPTION
         "Message Wrong Type Discards."
     ::= { f3PtpPTPPortHistoryEntry 10 }

f3PtpPTPPortHistoryMessagesWrongLengthDiscards OBJECT-TYPE
     SYNTAX     PerfCounter64
     MAX-ACCESS read-only
     STATUS     current
     DESCRIPTION
         "Messages Wrong Length Discards."
     ::= { f3PtpPTPPortHistoryEntry 11 }

f3PtpPTPPortHistoryUnknownMasterDiscards OBJECT-TYPE
     SYNTAX     PerfCounter64
     MAX-ACCESS read-only
     STATUS     current
     DESCRIPTION
         "Unknown Master Discards."
     ::= { f3PtpPTPPortHistoryEntry 12 }

f3PtpPTPPortHistoryMinOffsetFromMaster OBJECT-TYPE
     SYNTAX     PerfCounter64
     MAX-ACCESS read-only
     STATUS     current
     DESCRIPTION
         "Min Offset From Master."
     ::= { f3PtpPTPPortHistoryEntry 13 }

f3PtpPTPPortHistoryMaxOffsetFromMaster OBJECT-TYPE
     SYNTAX     PerfCounter64
     MAX-ACCESS read-only
     STATUS     current
     DESCRIPTION
         "Max Offset From Master."
     ::= { f3PtpPTPPortHistoryEntry 14 }

f3PtpPTPPortHistoryAvgOffsetFromMaster OBJECT-TYPE
     SYNTAX     PerfCounter64
     MAX-ACCESS read-only
     STATUS     current
     DESCRIPTION
         "Avg Offset From Master."
     ::= { f3PtpPTPPortHistoryEntry 15 }

f3PtpPTPPortHistoryMinSyncPathDelay OBJECT-TYPE
     SYNTAX     PerfCounter64
     MAX-ACCESS read-only
     STATUS     current
     DESCRIPTION
         "Min Sync Path Delay."
     ::= { f3PtpPTPPortHistoryEntry 16 }

f3PtpPTPPortHistoryMaxSyncPathDelay OBJECT-TYPE
     SYNTAX     PerfCounter64
     MAX-ACCESS read-only
     STATUS     current
     DESCRIPTION
         "Max Sync Path Delay."
     ::= { f3PtpPTPPortHistoryEntry 17 }

f3PtpPTPPortHistoryAvgSyncPathDelay OBJECT-TYPE
     SYNTAX     PerfCounter64
     MAX-ACCESS read-only
     STATUS     current
     DESCRIPTION
         "Avg Sync Path Delay."
     ::= { f3PtpPTPPortHistoryEntry 18 }

f3PtpPTPPortHistoryMinMeanPathDelay OBJECT-TYPE
     SYNTAX     PerfCounter64
     MAX-ACCESS read-only
     STATUS     current
     DESCRIPTION
         "Min Mean Path Delay."
     ::= { f3PtpPTPPortHistoryEntry 19 }

f3PtpPTPPortHistoryMaxMeanPathDelay OBJECT-TYPE
     SYNTAX     PerfCounter64
     MAX-ACCESS read-only
     STATUS     current
     DESCRIPTION
         "Max Mean Path Delay."
     ::= { f3PtpPTPPortHistoryEntry 20 }

f3PtpPTPPortHistoryAvgMeanPathDelay OBJECT-TYPE
     SYNTAX     PerfCounter64
     MAX-ACCESS read-only
     STATUS     current
     DESCRIPTION
         "Avg Mean Path Delay."
     ::= { f3PtpPTPPortHistoryEntry 21 }



--
-- PTP Port Threshold Table
--
f3PtpPTPPortThresholdTable OBJECT-TYPE
    SYNTAX      SEQUENCE OF F3PtpPTPPortThresholdEntry
    MAX-ACCESS  not-accessible
    STATUS      current
    DESCRIPTION
            "A table of entries that allow manageability of 
             PTP Port Thresholds."
    ::= { f3PtpPerformanceObjects 24 }

f3PtpPTPPortThresholdEntry OBJECT-TYPE
    SYNTAX      F3PtpPTPPortThresholdEntry
    MAX-ACCESS  not-accessible
    STATUS      current
    DESCRIPTION
            "A conceptual row in the f3PtpPTPPortThresholdTable."
    INDEX { neIndex, f3PtpPTPClockIndex, f3PtpPTPPortIndex,  
            f3PtpPTPPortStatsIndex, f3PtpPTPPortThresholdIndex }
    ::= { f3PtpPTPPortThresholdTable 1 }

F3PtpPTPPortThresholdEntry ::= SEQUENCE {
    f3PtpPTPPortThresholdIndex       Integer32,
    f3PtpPTPPortThresholdInterval    CmPmIntervalType,
    f3PtpPTPPortThresholdVariable    VariablePointer,
    f3PtpPTPPortThresholdValueLo     Unsigned32,
    f3PtpPTPPortThresholdValueHi     Unsigned32,
    f3PtpPTPPortThresholdMonValue    PerfCounter64
}

f3PtpPTPPortThresholdIndex OBJECT-TYPE
    SYNTAX     Integer32 (1..65535)
    MAX-ACCESS not-accessible
    STATUS     current
    DESCRIPTION
        "An index that uniquely identifies an entry in the
        f3PtpPTPPortThresholdTable."
    ::= { f3PtpPTPPortThresholdEntry 1 }

f3PtpPTPPortThresholdInterval OBJECT-TYPE
    SYNTAX     CmPmIntervalType
    MAX-ACCESS read-only
    STATUS     current
    DESCRIPTION
        "The interval over which monitored value is
        sampled and compared with the specified threshold."
    ::= { f3PtpPTPPortThresholdEntry 2 }

f3PtpPTPPortThresholdVariable OBJECT-TYPE
    SYNTAX     VariablePointer
    MAX-ACCESS read-only
    STATUS     current
    DESCRIPTION
        "The object identifier of the particular variable to be
        sampled."
    ::= { f3PtpPTPPortThresholdEntry 3 }

f3PtpPTPPortThresholdValueLo OBJECT-TYPE
    SYNTAX     Unsigned32
    MAX-ACCESS read-write
    STATUS     current
    DESCRIPTION
        "Lower 32 bits of the threshold value."
    ::= { f3PtpPTPPortThresholdEntry 4 }

f3PtpPTPPortThresholdValueHi OBJECT-TYPE
    SYNTAX     Unsigned32
    MAX-ACCESS read-write
    STATUS     current
    DESCRIPTION
        "Higher 32 bits of the threshold value."
    ::= { f3PtpPTPPortThresholdEntry 5 }

f3PtpPTPPortThresholdMonValue OBJECT-TYPE
    SYNTAX     PerfCounter64
    MAX-ACCESS read-only
    STATUS     current
    DESCRIPTION
        "Monitored value corresponding to f3PtpPTPPortThresholdVariable."
    ::= { f3PtpPTPPortThresholdEntry 6 }


---
---Notifications
---

f3PtpAccPortFlowPointThresholdCrossingAlert NOTIFICATION-TYPE
    OBJECTS {
        f3PtpAccPortFlowPointThresholdIndex,
        f3PtpAccPortFlowPointThresholdInterval,
        f3PtpAccPortFlowPointThresholdVariable,
        f3PtpAccPortFlowPointThresholdValueLo,
        f3PtpAccPortFlowPointThresholdValueHi,
        f3PtpAccPortFlowPointThresholdMonValue
    }
    STATUS  current
    DESCRIPTION
            "This trap is sent each time a threshold on a PM condition
             on an PTP Access Port Flow Point is crossed."
  ::= { f3PtpPerformanceNotifications 1 }

f3PtpNetPortFlowPointThresholdCrossingAlert NOTIFICATION-TYPE
    OBJECTS {
        f3PtpNetPortFlowPointThresholdIndex,
        f3PtpNetPortFlowPointThresholdInterval,
        f3PtpNetPortFlowPointThresholdVariable,
        f3PtpNetPortFlowPointThresholdValueLo,
        f3PtpNetPortFlowPointThresholdValueHi,
        f3PtpNetPortFlowPointThresholdMonValue
    }
    STATUS  current
    DESCRIPTION
            "This trap is sent each time a threshold on a PM condition
             on an PTP Network Port Flow Point is crossed."
  ::= { f3PtpPerformanceNotifications 2 }


f3PtpSOOCCrossingAlert NOTIFICATION-TYPE
    OBJECTS {
        f3PtpSOOCThresholdIndex,
        f3PtpSOOCThresholdInterval,
        f3PtpSOOCThresholdVariable,
        f3PtpSOOCThresholdValueLo,
        f3PtpSOOCThresholdValueHi,
        f3PtpSOOCThresholdMonValue
    }
    STATUS  current
    DESCRIPTION
            "This trap is sent each time a threshold on a PM condition
             on an PTP Slave Only Ordinary Clock is crossed."
  ::= { f3PtpPerformanceNotifications 3 }

f3PtpTSCrossingAlert NOTIFICATION-TYPE
    OBJECTS {
        f3PtpTSThresholdIndex,
        f3PtpTSThresholdInterval,
        f3PtpTSThresholdVariable,
        f3PtpTSThresholdValueLo,
        f3PtpTSThresholdValueHi,
        f3PtpTSThresholdMonValue
    }
    STATUS  current
    DESCRIPTION
            "This trap is sent each time a threshold on a PM condition
             on an PTP Telecom Slave is crossed."
  ::= { f3PtpPerformanceNotifications 4 }


f3PtpMCICrossingAlert NOTIFICATION-TYPE
    OBJECTS {
        f3PtpMCIThresholdIndex,
        f3PtpMCIThresholdInterval,
        f3PtpMCIThresholdVariable,
        f3PtpMCIThresholdValueLo,
        f3PtpMCIThresholdValueHi,
        f3PtpMCIThresholdMonValue
    }
    STATUS  current
    DESCRIPTION
            "This trap is sent each time a threshold on a PM condition
             on an PTP Master Clock Interface is crossed."
  ::= { f3PtpPerformanceNotifications 5 }

f3PtpRemoteSlaveCrossingAlert NOTIFICATION-TYPE
    OBJECTS {
        f3PtpRemoteSlaveThresholdIndex,
        f3PtpRemoteSlaveThresholdInterval,
        f3PtpRemoteSlaveThresholdVariable,
        f3PtpRemoteSlaveThresholdValueLo,
        f3PtpRemoteSlaveThresholdValueHi,
        f3PtpRemoteSlaveThresholdMonValue
    }
    STATUS  current
    DESCRIPTION
            "This trap is sent each time a threshold on a PM condition
             on an PTP Remote Slave is crossed."
  ::= { f3PtpPerformanceNotifications 6 }

f3PtpTrafficPortFlowPointThresholdCrossingAlert NOTIFICATION-TYPE
    OBJECTS {
        f3PtpTrafficPortFlowPointThresholdIndex,
        f3PtpTrafficPortFlowPointThresholdInterval,
        f3PtpTrafficPortFlowPointThresholdVariable,
        f3PtpTrafficPortFlowPointThresholdValueLo,
        f3PtpTrafficPortFlowPointThresholdValueHi,
        f3PtpTrafficPortFlowPointThresholdMonValue
    }
    STATUS  current
    DESCRIPTION
            "This trap is sent each time a threshold on a PM condition
             on an PTP Traffic Port Flow Point is crossed."
  ::= { f3PtpPerformanceNotifications 7 }


--f3PtpPTPClockCrossingAlert NOTIFICATION-TYPE
--    OBJECTS {
--        f3PtpPTPClockThresholdIndex,
--        f3PtpPTPClockThresholdInterval,
--        f3PtpPTPClockThresholdVariable,
--        f3PtpPTPClockThresholdValueLo,
--        f3PtpPTPClockThresholdValueHi,
--        f3PtpPTPClockThresholdMonValue
--    }
--    STATUS  current
--    DESCRIPTION
--            "This trap is sent each time a threshold on a PM condition
--             on an PTP PTPClock is crossed."
--  ::= { f3PtpPerformanceNotifications 8 }

f3PtpPTPPortCrossingAlert NOTIFICATION-TYPE
    OBJECTS {
        f3PtpPTPPortThresholdIndex,
        f3PtpPTPPortThresholdInterval,
        f3PtpPTPPortThresholdVariable,
        f3PtpPTPPortThresholdValueLo,
        f3PtpPTPPortThresholdValueHi,
        f3PtpPTPPortThresholdMonValue
    }
    STATUS  current
    DESCRIPTION
            "This trap is sent each time a threshold on a PM condition
             on an PTP PTPPort is crossed."
  ::= { f3PtpPerformanceNotifications 8 }




f3PtpTSStatusChangeTrap NOTIFICATION-TYPE
    OBJECTS {
        f3PtpTSAdminState,
        f3PtpTSCurrentCRScore,
        f3PtpTSCurrentPRScore,
        f3PtpTSClockRecoveryState,
        f3PtpTSSelectedPacketClock
    }
    STATUS  current
    DESCRIPTION
            "This trap is sent there is a status change on the Telecom Slave." 
  ::= { f3PtpStatusChangeNotifications 1 }


f3PtpMasterClockStatusChangeTrap NOTIFICATION-TYPE
    OBJECTS {
        f3PtpMasterClockClockClass,
        f3PtpMasterClockUtcOffset,
        f3PtpMasterClockActiveTimeRef
    }
    STATUS  current
    DESCRIPTION
            "This trap is sent there is a status change on the Master Clock." 
  ::= { f3PtpStatusChangeNotifications 2 }

f3PtpBCStatusChangeTrap NOTIFICATION-TYPE
    OBJECTS {
        f3PtpBCClockClass
    }
    STATUS  current
    DESCRIPTION
            "This trap is sent there is a status change on the Boundary Clock." 
  ::= { f3PtpStatusChangeNotifications 3 }

f3PtpDynamicRemoteSlaveStatusChangeTrap NOTIFICATION-TYPE
    OBJECTS {
        f3PtpDynamicRemoteSlaveClockIdentity,
        f3PtpDynamicRemoteSlaveIpV4Address,
        f3PtpDynamicRemoteSlaveSyncMsgRate,
        f3PtpDynamicRemoteSlaveDelayRspMsgRate,
        f3PtpDynamicRemoteSlaveAnnounceMsgRate
    }
    STATUS  current
    DESCRIPTION
            "This trap is sent there is a status change on the Dynamic Remote Slave." 
  ::= { f3PtpStatusChangeNotifications 4 }


--
-- CONFORMANCE
--
f3PtpCompliances OBJECT IDENTIFIER ::= {f3PtpConformance 1}
f3PtpGroups      OBJECT IDENTIFIER ::= {f3PtpConformance 2}

f3PtpCompliance MODULE-COMPLIANCE
    STATUS  current
    DESCRIPTION
            "Describes the requirements for conformance to the F3 PTP
             group."
    MODULE  -- this module
        MANDATORY-GROUPS {
              f3PtpObjectGroup, f3PtpPerfObjectGroup, f3PtpPerfNotifGroup,
              f3PtpStatusChangeNotifGroup
        }
    ::= { f3PtpCompliances 1 }

f3PtpObjectGroup OBJECT-GROUP
    OBJECTS {
      f3PtpTCIndex, f3PtpTCAlias, f3PtpTCAdminState,
      f3PtpTCOperationalState, f3PtpTCSecondaryState,
      f3PtpTCServiceFlow, f3PtpTCDelayMechanism, 
      f3PtpTCSync, f3PtpTCClockIdentity, f3PtpTCStorageType, f3PtpTCRowStatus,

      f3PtpTCVirtualPortIndex, f3PtpTCVirtualPortAlias,
      f3PtpTCVirtualPortAdminState,
      f3PtpTCVirtualPortOperationalState, f3PtpTCVirtualPortSecondaryState,
      f3PtpTCVirtualPortIdentity, f3PtpTCVirtualPortFlowPoint,
      f3PtpTCVirtualPortStorageType, f3PtpTCVirtualPortRowStatus,

      f3PtpTSIndex, f3PtpTSAlias, f3PtpTSAdminState,
      f3PtpTSOperationalState, f3PtpTSSecondaryState,
      f3PtpTSClockIdentity, f3PtpTSDomainNumber, f3PtpTSSync,
      f3PtpTSCurrentTOD, f3PtpTSSelectedPacketClock, 
      f3PtpTSClockRecoveryMode, f3PtpTSClockRecoveryState,
      f3PtpTSClockSyncEEnabled, f3PtpTSClockQLModeEnabled,
      f3PtpTSClockExpectedQL, f3PtpTSClockAssumedQL,
      f3PtpTSClockReceivedQL, f3PtpTSStorageType, f3PtpTSRowStatus,

      f3PtpTSTimeTraceabilityStatus, f3PtpTSTimeSinceTimeTraceabilityChanged,
      f3PtpTSFreqTraceabilityStatus, f3PtpTSTimeSinceFreqTraceabilityChanged,
      f3PtpTSFreqRecoveryTarget, f3PtpTSCurrentCRScore,
      f3PtpTSTimeLastCRScore, f3PtpTSTargetPhaseRecoveryAccuracy,
      f3PtpTSCurrentPRScore, f3PtpTSTimeLastPRScore,
      f3PtpTSClockClass,
      f3PtpTSClockAccuracy,
      f3PtpTSTimeSource,
      f3PtpTSPhaseRecoveryState, 
      f3PtpTSTimeHoldoverAccuracy,

      f3PtpSOOCIndex, f3PtpSOOCName, f3PtpSOOCAlias,
      f3PtpSOOCAdminState, f3PtpSOOCOperationalState, 
      f3PtpSOOCSecondaryState, f3PtpSOOCServiceFlow,
      f3PtpSOOCMasterClockType, f3PtpSOOCUnicastMessageNegEnabled,
      f3PtpSOOCMasterDelayMechanism, f3PtpSOOCMasterPriority,
      f3PtpSOOCMasterIpProtocol, f3PtpSOOCSlaveIpV4Address,
      f3PtpSOOCSlaveIpV4SubnetMask, f3PtpSOOCMasterIpV4Address,
      f3PtpSOOCIpPriorityMapMode, f3PtpSOOCIpPriority,
      f3PtpSOOCMasterLeaseDuration, f3PtpSOOCMasterAnnounceMsgRate,
      f3PtpSOOCMasterAnnounceMsgReceiptTimeout, 
      f3PtpSOOCMasterSyncMsgRate, f3PtpSOOCMasterSyncReceiptTimeout,
      f3PtpSOOCMasterDelayRspMsgRate, f3PtpSOOCMasterDelayRspReceiptTimeout,
      f3PtpSOOCMasterRequestUnicastTimeout, f3PtpSOOCMasterRequestUnicastRestartTimer,
      f3PtpSOOCCurrentOffsetFromMaster, f3PtpSOOCAnnounceMsgClockClass,
      f3PtpSOOCLastReceivedAnnounceMsg, f3PtpSOOCLastReceivedSyncMsg,
      f3PtpSOOCLastReceivedDelayRspMsg, f3PtpSOOCRecentMeanPathDelay,
      f3PtpSOOCRecentSyncPDV,
      f3PtpSOOCStorageType, f3PtpSOOCRowStatus,
      f3PtpSOOCRecentSyncPathDelay, f3PtpSOOCSoocProtectionState,
      f3PtpSOOCSoocWtr, f3PtpSOOCSoocClockClass,
      f3PtpSOOCSoocClockRecoveryState,f3PtpSOOCSoocPhaseRecoveryState,
      f3PtpSOOCE2eDelayAsymmetryComp, f3PtpSOOCE2eAutoAsymmetryCompStatus,
      f3PtpSOOCE2eDelayAsymmetry, f3PtpSOOCSoocLockOutControl,

      f3PtpOCSlaveVirtualPortIndex, f3PtpOCSlaveVirtualPortAlias,
      f3PtpOCSlaveVirtualPortAdminState,
      f3PtpOCSlaveVirtualPortOperationalState, 
      f3PtpOCSlaveVirtualPortSecondaryState,
      f3PtpOCSlaveVirtualPortIdentity, f3PtpOCSlaveVirtualPortFlowPoint,
      f3PtpOCSlaveVirtualPortState, f3PtpOCSlaveVirtualPortStorageType,
      f3PtpOCSlaveVirtualPortRowStatus,

      f3PtpAccPortFlowPointIndex, f3PtpAccPortFlowPointAlias,
      f3PtpAccPortFlowPointAdminState, f3PtpAccPortFlowPointOperationalState, 
      f3PtpAccPortFlowPointSecondaryState, f3PtpAccPortFlowPointType,
      f3PtpAccPortFlowPointClock, f3PtpAccPortFlowPointService,               
      f3PtpAccPortFlowPointOuterVlanEtherType,
      f3PtpAccPortFlowPointOuterVlanMemberList,
      f3PtpAccPortFlowPointOuterUntaggedEnabled,
      f3PtpAccPortFlowPointInner1VlanEtherType,
      f3PtpAccPortFlowPointInner1VlanMemberList,
      f3PtpAccPortFlowPointInner1UntaggedEnabled,
      f3PtpAccPortFlowPointInner2VlanEtherType,
      f3PtpAccPortFlowPointInner2VlanMemberList,
      f3PtpAccPortFlowPointInner2UntaggedEnabled,
      f3PtpAccPortFlowPointStorageType,
      f3PtpAccPortFlowPointRowStatus,
      f3PtpAccPortFlowPointCOS,
      f3PtpAccPortFlowPointCIRLo,
      f3PtpAccPortFlowPointCIRHi,
      f3PtpAccPortFlowPointEIRLo,
      f3PtpAccPortFlowPointEIRHi,
      f3PtpAccPortFlowPointBufferSize,

      f3PtpNetPortFlowPointIndex, f3PtpNetPortFlowPointAlias,
      f3PtpNetPortFlowPointAdminState, f3PtpNetPortFlowPointOperationalState, 
      f3PtpNetPortFlowPointSecondaryState, f3PtpNetPortFlowPointType,
      f3PtpNetPortFlowPointClock, f3PtpNetPortFlowPointService,               
      f3PtpNetPortFlowPointOuterVlanEtherType,
      f3PtpNetPortFlowPointOuterVlanMemberList,
      f3PtpNetPortFlowPointOuterUntaggedEnabled,
      f3PtpNetPortFlowPointInner1VlanEtherType,
      f3PtpNetPortFlowPointInner1VlanMemberList,
      f3PtpNetPortFlowPointInner1UntaggedEnabled,
      f3PtpNetPortFlowPointInner2VlanEtherType,
      f3PtpNetPortFlowPointInner2VlanMemberList,
      f3PtpNetPortFlowPointInner2UntaggedEnabled,
      f3PtpNetPortFlowPointStorageType,
      f3PtpNetPortFlowPointRowStatus,
      f3PtpNetPortFlowPointCOS,
      f3PtpNetPortFlowPointCIRLo,
      f3PtpNetPortFlowPointCIRHi,
      f3PtpNetPortFlowPointEIRLo,
      f3PtpNetPortFlowPointEIRHi,
      f3PtpNetPortFlowPointBufferSize,

      f3PtpEthernetAccPortDelayAsymmetry, f3PtpEthernetNetPortDelayAsymmetry,
      f3PtpSysTimeOfDayClock,      
       
      f3PtpTrafficPortFlowPointIndex,
      f3PtpTrafficPortFlowPointAlias,      
      f3PtpTrafficPortFlowPointAdminState,
      f3PtpTrafficPortFlowPointOperationalState,
      f3PtpTrafficPortFlowPointSecondaryState,      
      f3PtpTrafficPortFlowPointType,
      f3PtpTrafficPortFlowPointClock,
      f3PtpTrafficPortFlowPointService,
      f3PtpTrafficPortFlowPointOuterVlanEtherType,
      f3PtpTrafficPortFlowPointOuterVlanMemberList,
      f3PtpTrafficPortFlowPointOuterUntaggedEnabled,
      f3PtpTrafficPortFlowPointInner1VlanEtherType,
      f3PtpTrafficPortFlowPointInner1VlanMemberList,
      f3PtpTrafficPortFlowPointInner1UntaggedEnabled,
      f3PtpTrafficPortFlowPointInner2VlanEtherType,
      f3PtpTrafficPortFlowPointInner2VlanMemberList,
      f3PtpTrafficPortFlowPointInner2UntaggedEnabled,      
      f3PtpTrafficPortFlowPointStorageType,
      f3PtpTrafficPortFlowPointRowStatus,
      f3PtpTrafficPortFlowPointCOS,
      f3PtpTrafficPortFlowPointCIRLo,
      f3PtpTrafficPortFlowPointCIRHi,
      f3PtpTrafficPortFlowPointEIRLo,
      f3PtpTrafficPortFlowPointEIRHi,
      f3PtpTrafficPortFlowPointAssociatedQueueProfile,
      f3PtpTrafficPortFlowPointLoopAvoidance,
      
      f3PtpEthernetTrafficPortDelayAsymmetry,

       f3PtpPTPClockIndex,
       f3PtpPTPClockAdminState,
       f3PtpPTPClockAlias,                      
       f3PtpPTPClockOperationalState,                
       f3PtpPTPClockSecondaryState,                 
       f3PtpPTPClockProfile,                         
       f3PtpPTPClockClockType,                       
       f3PtpPTPClockOperationalMode,                 
       f3PtpPTPClockClockIdentity,                   
       f3PtpPTPClockDomainNumber,                    
       f3PtpPTPClockTimeSource,                      
       f3PtpPTPClockPriority1,                       
       f3PtpPTPClockPriority2,                       
       f3PtpPTPClockLocalPriority,                   
       f3PtpPTPClockClockAccuracy,                   
       f3PtpPTPClockScaledLogVariance,               
       f3PtpPTPClockSyncEid,                         
       f3PtpPTPClockCurrentTimeOfDay,                
       f3PtpPTPClockActiveSlavePort,                 
       f3PtpPTPClockClockRecoveryState,              
       f3PtpPTPClockPhaseRecoveryState,              
       f3PtpPTPClockTimeTraceabilityStatus,          
       f3PtpPTPClockTimeSinceTimeTraceabilityChanged,
       f3PtpPTPClockFreqTraceabilityStatus,          
       f3PtpPTPClockTimeSinceFreqTraceabilityChanged,
       f3PtpPTPClockClockSyncEEnabled, 
       f3PtpPTPClockClockQLModeEnabled, 
       f3PtpPTPClockClockExpectedQL,
       f3PtpPTPClockClockAssumedQL,   
       f3PtpPTPClockClockReceivedQL,    

       f3PtpPTPClockStorageType,                     
       f3PtpPTPClockRowStatus,

       f3PtpPTPPortIndex,                 
       f3PtpPTPPortAdminState, 
       f3PtpPTPPortAlias,           
       f3PtpPTPPortOperationalState,      
       f3PtpPTPPortSecondaryState,        
       f3PtpPTPPortPeerPortIdentity,      
       f3PtpPTPPortLocalPriority,         
       f3PtpPTPPortPtpFlowPointEid,       
       f3PtpPTPPortNotSlave,              
       f3PtpPTPPortTxDestMacAddress,      
       f3PtpPTPPortSyncMessageRate,       
       f3PtpPTPPortmDelayReqRespMsgRate,  
       f3PtpPTPPortmAnnounceMsgRate,      
       f3PtpPTPPortAnnounceReceiptTimeout,
       f3PtpPTPPortSyncReceiptTimeout,    
       f3PtpPTPPortDelayRespTimeout,      
       f3PtpPTPPortPortState,             
       f3PtpPTPPortBmcaDecisionCode,      
       f3PtpPTPPortClockClass,        
       f3PtpPTPPortPeerPortMacAddress,
       f3PtpPTPPortRowStatus,
       f3PtpPTPPortPortIdentity
           

    }
    STATUS  current
    DESCRIPTION
        "A collection of objects used to manage the F3 PTP Configuration data."
    ::= { f3PtpGroups 1 }

f3PtpPerfObjectGroup OBJECT-GROUP
    OBJECTS {
    f3PtpAccPortFlowPointStatsIndex, f3PtpAccPortFlowPointStatsIntervalType,
    f3PtpAccPortFlowPointStatsValid, f3PtpAccPortFlowPointStatsAction,
    f3PtpAccPortFlowPointStatsAnnouncesRx, f3PtpAccPortFlowPointStatsAnnouncesTx,
    f3PtpAccPortFlowPointStatsSyncsRx, f3PtpAccPortFlowPointStatsSyncsTx,
    f3PtpAccPortFlowPointStatsFollowupsRx, f3PtpAccPortFlowPointStatsFollowupsTx,
    f3PtpAccPortFlowPointStatsDelayReqsRx, f3PtpAccPortFlowPointStatsDelayReqsTx,
    f3PtpAccPortFlowPointStatsDelayRspsRx, f3PtpAccPortFlowPointStatsDelayRspsTx,
    f3PtpAccPortFlowPointStatsPDelayReqsRx, f3PtpAccPortFlowPointStatsPDelayReqsTx,
    f3PtpAccPortFlowPointStatsPDelayRspsRx, f3PtpAccPortFlowPointStatsPDelayRspsTx,
    f3PtpAccPortFlowPointStatsPDelayRspFollowupsRx, f3PtpAccPortFlowPointStatsPDelayRspFollowupsTx,
    f3PtpAccPortFlowPointStatsSignalingRx, f3PtpAccPortFlowPointStatsSignalingTx,
    f3PtpAccPortFlowPointStatsMgmtFramesRx, f3PtpAccPortFlowPointStatsMgmtFramesTx,
    f3PtpAccPortFlowPointStatsPtpUnknownsRx, f3PtpAccPortFlowPointStatsPtpUnknownsTx,
    f3PtpAccPortFlowPointStatsAvgSyncResTime,
    f3PtpAccPortFlowPointStatsMinSyncResTime, f3PtpAccPortFlowPointStatsMaxSyncResTime,
    f3PtpAccPortFlowPointStatsAvgDelayReqResTime, f3PtpAccPortFlowPointStatsMinDelayReqResTime,
    f3PtpAccPortFlowPointStatsMaxDelayReqResTime,
    f3PtpAccPortFlowPointStatsMinPDelayReqResTime,
    f3PtpAccPortFlowPointStatsMaxPDelayReqResTime,
    f3PtpAccPortFlowPointStatsAvgPDelayReqResTime,
    f3PtpAccPortFlowPointStatsMinPDelayRspResTime,
    f3PtpAccPortFlowPointStatsMaxPDelayRspResTime,
    f3PtpAccPortFlowPointStatsAvgPDelayRspResTime,
    f3PtpAccPortFlowPointStatsDestMciNoMatchDiscards,

    f3PtpAccPortFlowPointHistoryIndex, f3PtpAccPortFlowPointHistoryTime,
    f3PtpAccPortFlowPointHistoryValid, f3PtpAccPortFlowPointHistoryAction,
    f3PtpAccPortFlowPointHistoryAnnouncesRx, f3PtpAccPortFlowPointHistoryAnnouncesTx,
    f3PtpAccPortFlowPointHistorySyncsRx, f3PtpAccPortFlowPointHistorySyncsTx,
    f3PtpAccPortFlowPointHistoryFollowupsRx, f3PtpAccPortFlowPointHistoryFollowupsTx,
    f3PtpAccPortFlowPointHistoryDelayReqsRx, f3PtpAccPortFlowPointHistoryDelayReqsTx,
    f3PtpAccPortFlowPointHistoryDelayRspsRx, f3PtpAccPortFlowPointHistoryDelayRspsTx,
    f3PtpAccPortFlowPointHistoryPDelayReqsRx, f3PtpAccPortFlowPointHistoryPDelayReqsTx,
    f3PtpAccPortFlowPointHistoryPDelayRspsRx, f3PtpAccPortFlowPointHistoryPDelayRspsTx,
    f3PtpAccPortFlowPointHistoryPDelayRspFollowupsRx, f3PtpAccPortFlowPointHistoryPDelayRspFollowupsTx,
    f3PtpAccPortFlowPointHistorySignalingRx, f3PtpAccPortFlowPointHistorySignalingTx,
    f3PtpAccPortFlowPointHistoryMgmtFramesRx, f3PtpAccPortFlowPointHistoryMgmtFramesTx,
    f3PtpAccPortFlowPointHistoryPtpUnknownsRx, f3PtpAccPortFlowPointHistoryPtpUnknownsTx,
    f3PtpAccPortFlowPointHistoryAvgSyncResTime,
    f3PtpAccPortFlowPointHistoryMinSyncResTime, f3PtpAccPortFlowPointHistoryMaxSyncResTime,
    f3PtpAccPortFlowPointHistoryAvgDelayReqResTime, f3PtpAccPortFlowPointHistoryMinDelayReqResTime,
    f3PtpAccPortFlowPointHistoryMaxDelayReqResTime,
    f3PtpAccPortFlowPointHistoryMinPDelayReqResTime,
    f3PtpAccPortFlowPointHistoryMaxPDelayReqResTime,
    f3PtpAccPortFlowPointHistoryAvgPDelayReqResTime,
    f3PtpAccPortFlowPointHistoryMinPDelayRspResTime,
    f3PtpAccPortFlowPointHistoryMaxPDelayRspResTime,
    f3PtpAccPortFlowPointHistoryAvgPDelayRspResTime,
    f3PtpAccPortFlowPointHistoryDestMciNoMatchDiscards,

    f3PtpAccPortFlowPointThresholdIndex, f3PtpAccPortFlowPointThresholdInterval,
    f3PtpAccPortFlowPointThresholdVariable, f3PtpAccPortFlowPointThresholdValueLo,
    f3PtpAccPortFlowPointThresholdValueHi, f3PtpAccPortFlowPointThresholdMonValue,

    f3PtpNetPortFlowPointStatsIndex, f3PtpNetPortFlowPointStatsIntervalType,
    f3PtpNetPortFlowPointStatsValid, f3PtpNetPortFlowPointStatsAction,
    f3PtpNetPortFlowPointStatsAnnouncesRx, f3PtpNetPortFlowPointStatsAnnouncesTx,
    f3PtpNetPortFlowPointStatsSyncsRx, f3PtpNetPortFlowPointStatsSyncsTx,
    f3PtpNetPortFlowPointStatsFollowupsRx, f3PtpNetPortFlowPointStatsFollowupsTx,
    f3PtpNetPortFlowPointStatsDelayReqsRx, f3PtpNetPortFlowPointStatsDelayReqsTx,
    f3PtpNetPortFlowPointStatsDelayRspsRx, f3PtpNetPortFlowPointStatsDelayRspsTx,
    f3PtpNetPortFlowPointStatsPDelayReqsRx, f3PtpNetPortFlowPointStatsPDelayReqsTx,
    f3PtpNetPortFlowPointStatsPDelayRspsRx, f3PtpNetPortFlowPointStatsPDelayRspsTx,
    f3PtpNetPortFlowPointStatsPDelayRspFollowupsRx, f3PtpNetPortFlowPointStatsPDelayRspFollowupsTx,
    f3PtpNetPortFlowPointStatsSignalingRx, f3PtpNetPortFlowPointStatsSignalingTx,
    f3PtpNetPortFlowPointStatsMgmtFramesRx, f3PtpNetPortFlowPointStatsMgmtFramesTx,
    f3PtpNetPortFlowPointStatsPtpUnknownsRx, f3PtpNetPortFlowPointStatsPtpUnknownsTx,
    f3PtpNetPortFlowPointStatsAvgSyncResTime,
    f3PtpNetPortFlowPointStatsMinSyncResTime, f3PtpNetPortFlowPointStatsMaxSyncResTime,
    f3PtpNetPortFlowPointStatsAvgDelayReqResTime, f3PtpNetPortFlowPointStatsMinDelayReqResTime,
    f3PtpNetPortFlowPointStatsMaxDelayReqResTime,
    f3PtpNetPortFlowPointStatsMinPDelayReqResTime,
    f3PtpNetPortFlowPointStatsMaxPDelayReqResTime,
    f3PtpNetPortFlowPointStatsAvgPDelayReqResTime,
    f3PtpNetPortFlowPointStatsMinPDelayRspResTime,
    f3PtpNetPortFlowPointStatsMaxPDelayRspResTime,
    f3PtpNetPortFlowPointStatsAvgPDelayRspResTime,
    f3PtpNetPortFlowPointStatsDestMciNoMatchDiscards,

    f3PtpNetPortFlowPointHistoryIndex, f3PtpNetPortFlowPointHistoryTime,
    f3PtpNetPortFlowPointHistoryValid, f3PtpNetPortFlowPointHistoryAction,
    f3PtpNetPortFlowPointHistoryAnnouncesRx, f3PtpNetPortFlowPointHistoryAnnouncesTx,
    f3PtpNetPortFlowPointHistorySyncsRx, f3PtpNetPortFlowPointHistorySyncsTx,
    f3PtpNetPortFlowPointHistoryFollowupsRx, f3PtpNetPortFlowPointHistoryFollowupsTx,
    f3PtpNetPortFlowPointHistoryDelayReqsRx, f3PtpNetPortFlowPointHistoryDelayReqsTx,
    f3PtpNetPortFlowPointHistoryDelayRspsRx, f3PtpNetPortFlowPointHistoryDelayRspsTx,
    f3PtpNetPortFlowPointHistoryPDelayReqsRx, f3PtpNetPortFlowPointHistoryPDelayReqsTx,
    f3PtpNetPortFlowPointHistoryPDelayRspsRx, f3PtpNetPortFlowPointHistoryPDelayRspsTx,
    f3PtpNetPortFlowPointHistoryPDelayRspFollowupsRx, f3PtpNetPortFlowPointHistoryPDelayRspFollowupsTx,
    f3PtpNetPortFlowPointHistorySignalingRx, f3PtpNetPortFlowPointHistorySignalingTx,
    f3PtpNetPortFlowPointHistoryMgmtFramesRx, f3PtpNetPortFlowPointHistoryMgmtFramesTx,
    f3PtpNetPortFlowPointHistoryPtpUnknownsRx, f3PtpNetPortFlowPointHistoryPtpUnknownsTx,
    f3PtpNetPortFlowPointHistoryAvgSyncResTime,
    f3PtpNetPortFlowPointHistoryMinSyncResTime, f3PtpNetPortFlowPointHistoryMaxSyncResTime,
    f3PtpNetPortFlowPointHistoryAvgDelayReqResTime, f3PtpNetPortFlowPointHistoryMinDelayReqResTime,
    f3PtpNetPortFlowPointHistoryMaxDelayReqResTime,
    f3PtpNetPortFlowPointHistoryMinPDelayReqResTime,
    f3PtpNetPortFlowPointHistoryMaxPDelayReqResTime,
    f3PtpNetPortFlowPointHistoryAvgPDelayReqResTime,
    f3PtpNetPortFlowPointHistoryMinPDelayRspResTime,
    f3PtpNetPortFlowPointHistoryMaxPDelayRspResTime,
    f3PtpNetPortFlowPointHistoryAvgPDelayRspResTime,
    f3PtpNetPortFlowPointHistoryDestMciNoMatchDiscards,

    f3PtpNetPortFlowPointThresholdIndex, f3PtpNetPortFlowPointThresholdInterval,
    f3PtpNetPortFlowPointThresholdVariable, f3PtpNetPortFlowPointThresholdValueLo,
    f3PtpNetPortFlowPointThresholdValueHi, f3PtpNetPortFlowPointThresholdMonValue,

    f3PtpSOOCStatsIndex, f3PtpSOOCStatsIntervalType, f3PtpSOOCStatsValid,
    f3PtpSOOCStatsAction, f3PtpSOOCStatsMinOffsetFromMaster, f3PtpSOOCStatsMaxOffsetFromMaster,
    f3PtpSOOCStatsAvgOffsetFromMaster, f3PtpSOOCStatsMinMeanPathDelay,
    f3PtpSOOCStatsMaxMeanPathDelay, f3PtpSOOCStatsAvgMeanPathDelay,
    f3PtpSOOCStatsMinSyncPathDelay, f3PtpSOOCStatsMaxSyncPathDelay,
    f3PtpSOOCStatsAvgSyncPathDelay, f3PtpSOOCStatsMinSyncPDV,
    f3PtpSOOCStatsMaxSyncPDV, f3PtpSOOCStatsAvgSyncPDV, f3PtpSOOCStatsMgmtMsgsDiscarded,
    f3PtpSOOCStatsInvalidMsgLenDiscards, f3PtpSOOCStatsUnknownMasterDiscards,
    f3PtpSOOCStatsUnknownDomainDiscards, f3PtpSOOCStatsMulticastAnnounceDiscards,
    f3PtpSOOCStatsOutOfSeqAnnounceMsgs, f3PtpSOOCStatsMulticastSyncDiscards,
    f3PtpSOOCStatsTwoStepSyncDiscards, f3PtpSOOCStatsFollowupDiscards,
    f3PtpSOOCStatsDelayReqDiscards, f3PtpSOOCStatsPDelayReqDiscards,
    f3PtpSOOCStatsPDelayRspDiscards, f3PtpSOOCStatsPDelayFollowupDiscards,
    f3PtpSOOCStatsInvalidTLVLenDiscards, f3PtpSOOCStatsInvalidTLVTypeDiscards,
    f3PtpSOOCStatsMaxFwdFlowWeight,
    f3PtpSOOCStatsAvgFwdFlowWeight,
    f3PtpSOOCStatsMinRevFlowWeight,
    f3PtpSOOCStatsMaxRevFlowWeight,
    f3PtpSOOCStatsAvgRevFlowWeight,
    f3PtpSOOCStatsNumClockRecTransients,

    f3PtpSOOCHistoryIndex, f3PtpSOOCHistoryTime, f3PtpSOOCHistoryValid,
    f3PtpSOOCHistoryAction, f3PtpSOOCHistoryMinOffsetFromMaster, f3PtpSOOCHistoryMaxOffsetFromMaster,
    f3PtpSOOCHistoryAvgOffsetFromMaster, f3PtpSOOCHistoryMinMeanPathDelay,
    f3PtpSOOCHistoryMaxMeanPathDelay, f3PtpSOOCHistoryAvgMeanPathDelay,
    f3PtpSOOCHistoryMinSyncPathDelay, f3PtpSOOCHistoryMaxSyncPathDelay,
    f3PtpSOOCHistoryAvgSyncPathDelay, f3PtpSOOCHistoryMinSyncPDV,
    f3PtpSOOCHistoryMaxSyncPDV, f3PtpSOOCHistoryAvgSyncPDV, f3PtpSOOCHistoryMgmtMsgsDiscarded,
    f3PtpSOOCHistoryInvalidMsgLenDiscards, f3PtpSOOCHistoryUnknownMasterDiscards,
    f3PtpSOOCHistoryUnknownDomainDiscards, f3PtpSOOCHistoryMulticastAnnounceDiscards,
    f3PtpSOOCHistoryOutOfSeqAnnounceMsgs, f3PtpSOOCHistoryMulticastSyncDiscards,
    f3PtpSOOCHistoryTwoStepSyncDiscards, f3PtpSOOCHistoryFollowupDiscards,
    f3PtpSOOCHistoryDelayReqDiscards, f3PtpSOOCHistoryPDelayReqDiscards,
    f3PtpSOOCHistoryPDelayRspDiscards, f3PtpSOOCHistoryPDelayFollowupDiscards,
    f3PtpSOOCHistoryInvalidTLVLenDiscards, f3PtpSOOCHistoryInvalidTLVTypeDiscards,
    f3PtpSOOCHistoryMaxFwdFlowWeight,
    f3PtpSOOCHistoryAvgFwdFlowWeight,
    f3PtpSOOCHistoryMinRevFlowWeight,
    f3PtpSOOCHistoryMaxRevFlowWeight,
    f3PtpSOOCHistoryAvgRevFlowWeight,
    f3PtpSOOCHistoryNumClockRecTransients,

    f3PtpSOOCThresholdIndex, f3PtpSOOCThresholdInterval, f3PtpSOOCThresholdVariable,
    f3PtpSOOCThresholdValueLo, f3PtpSOOCThresholdValueHi, f3PtpSOOCThresholdMonValue,

    f3PtpTSStatsIndex, f3PtpTSStatsIntervalType,
    f3PtpTSStatsValid, f3PtpTSStatsAction, f3PtpTSStatsTotalTimeCR5,
    f3PtpTSStatsTotalTimeCR4, f3PtpTSStatsTotalTimeCR3,
    f3PtpTSStatsTotalTimePR5, f3PtpTSStatsTotalTimePR4,
    f3PtpTSStatsTotalTimePR3,

    f3PtpTSHistoryIndex, f3PtpTSHistoryTime, f3PtpTSHistoryValid,
    f3PtpTSHistoryAction, f3PtpTSHistoryTotalTimeCR5,
    f3PtpTSHistoryTotalTimeCR4, f3PtpTSHistoryTotalTimeCR3,
    f3PtpTSHistoryTotalTimePR5, f3PtpTSHistoryTotalTimePR4,
    f3PtpTSHistoryTotalTimePR3,

    f3PtpTSThresholdIndex, f3PtpTSThresholdInterval,
    f3PtpTSThresholdVariable, f3PtpTSThresholdValueLo,
    f3PtpTSThresholdValueHi, f3PtpTSThresholdMonValue,
       
    f3PtpTrafficPortFlowPointStatsIndex,
    f3PtpTrafficPortFlowPointStatsIntervalType,
    f3PtpTrafficPortFlowPointStatsValid,
    f3PtpTrafficPortFlowPointStatsAction,
    f3PtpTrafficPortFlowPointStatsAnnouncesRx,
    f3PtpTrafficPortFlowPointStatsAnnouncesTx,
    f3PtpTrafficPortFlowPointStatsSyncsRx,
    f3PtpTrafficPortFlowPointStatsSyncsTx,
    f3PtpTrafficPortFlowPointStatsFollowupsRx,
    f3PtpTrafficPortFlowPointStatsFollowupsTx,
    f3PtpTrafficPortFlowPointStatsDelayReqsRx,
    f3PtpTrafficPortFlowPointStatsDelayReqsTx,
    f3PtpTrafficPortFlowPointStatsDelayRspsRx,
    f3PtpTrafficPortFlowPointStatsDelayRspsTx,
    f3PtpTrafficPortFlowPointStatsPDelayReqsRx,
    f3PtpTrafficPortFlowPointStatsPDelayReqsTx,
    f3PtpTrafficPortFlowPointStatsPDelayRspsRx,
    f3PtpTrafficPortFlowPointStatsPDelayRspsTx,
    f3PtpTrafficPortFlowPointStatsPDelayRspFollowupsRx,
    f3PtpTrafficPortFlowPointStatsPDelayRspFollowupsTx,
    f3PtpTrafficPortFlowPointStatsSignalingRx,
    f3PtpTrafficPortFlowPointStatsSignalingTx,
    f3PtpTrafficPortFlowPointStatsMgmtFramesRx,
    f3PtpTrafficPortFlowPointStatsMgmtFramesTx,
    f3PtpTrafficPortFlowPointStatsPtpUnknownsRx,
    f3PtpTrafficPortFlowPointStatsPtpUnknownsTx,
    f3PtpTrafficPortFlowPointStatsMinSyncResTime,
    f3PtpTrafficPortFlowPointStatsMaxSyncResTime,
    f3PtpTrafficPortFlowPointStatsAvgSyncResTime,
    f3PtpTrafficPortFlowPointStatsMinDelayReqResTime,
    f3PtpTrafficPortFlowPointStatsMaxDelayReqResTime,
    f3PtpTrafficPortFlowPointStatsAvgDelayReqResTime,
    f3PtpTrafficPortFlowPointStatsMinPDelayReqResTime,
    f3PtpTrafficPortFlowPointStatsMaxPDelayReqResTime,
    f3PtpTrafficPortFlowPointStatsAvgPDelayReqResTime,
    f3PtpTrafficPortFlowPointStatsMinPDelayRspResTime,
    f3PtpTrafficPortFlowPointStatsMaxPDelayRspResTime,
    f3PtpTrafficPortFlowPointStatsAvgPDelayRspResTime,
    f3PtpTrafficPortFlowPointStatsDestMciNoMatchDiscards,
    
    f3PtpTrafficPortFlowPointHistoryIndex,
    f3PtpTrafficPortFlowPointHistoryTime,
    f3PtpTrafficPortFlowPointHistoryValid,
    f3PtpTrafficPortFlowPointHistoryAction,
    f3PtpTrafficPortFlowPointHistoryAnnouncesRx,
    f3PtpTrafficPortFlowPointHistoryAnnouncesTx,
    f3PtpTrafficPortFlowPointHistorySyncsRx,
    f3PtpTrafficPortFlowPointHistorySyncsTx,
    f3PtpTrafficPortFlowPointHistoryFollowupsRx,
    f3PtpTrafficPortFlowPointHistoryFollowupsTx,
    f3PtpTrafficPortFlowPointHistoryDelayReqsRx,
    f3PtpTrafficPortFlowPointHistoryDelayReqsTx,
    f3PtpTrafficPortFlowPointHistoryDelayRspsRx,
    f3PtpTrafficPortFlowPointHistoryDelayRspsTx,
    f3PtpTrafficPortFlowPointHistoryPDelayReqsRx,
    f3PtpTrafficPortFlowPointHistoryPDelayReqsTx,
    f3PtpTrafficPortFlowPointHistoryPDelayRspsRx,
    f3PtpTrafficPortFlowPointHistoryPDelayRspsTx,
    f3PtpTrafficPortFlowPointHistoryPDelayRspFollowupsRx,
    f3PtpTrafficPortFlowPointHistoryPDelayRspFollowupsTx,
    f3PtpTrafficPortFlowPointHistorySignalingRx,
    f3PtpTrafficPortFlowPointHistorySignalingTx,
    f3PtpTrafficPortFlowPointHistoryMgmtFramesRx,
    f3PtpTrafficPortFlowPointHistoryMgmtFramesTx,
    f3PtpTrafficPortFlowPointHistoryPtpUnknownsRx,
    f3PtpTrafficPortFlowPointHistoryPtpUnknownsTx,
    f3PtpTrafficPortFlowPointHistoryMinSyncResTime,
    f3PtpTrafficPortFlowPointHistoryMaxSyncResTime,
    f3PtpTrafficPortFlowPointHistoryAvgSyncResTime,
    f3PtpTrafficPortFlowPointHistoryMinDelayReqResTime,
    f3PtpTrafficPortFlowPointHistoryMaxDelayReqResTime,
    f3PtpTrafficPortFlowPointHistoryAvgDelayReqResTime,
    f3PtpTrafficPortFlowPointHistoryMinPDelayReqResTime,
    f3PtpTrafficPortFlowPointHistoryMaxPDelayReqResTime,
    f3PtpTrafficPortFlowPointHistoryAvgPDelayReqResTime,
    f3PtpTrafficPortFlowPointHistoryMinPDelayRspResTime,
    f3PtpTrafficPortFlowPointHistoryMaxPDelayRspResTime,
    f3PtpTrafficPortFlowPointHistoryAvgPDelayRspResTime,
    f3PtpTrafficPortFlowPointHistoryDestMciNoMatchDiscards,
    
    f3PtpTrafficPortFlowPointThresholdIndex,
    f3PtpTrafficPortFlowPointThresholdInterval,
    f3PtpTrafficPortFlowPointThresholdVariable,
    f3PtpTrafficPortFlowPointThresholdValueLo,
    f3PtpTrafficPortFlowPointThresholdValueHi,
    f3PtpTrafficPortFlowPointThresholdMonValue,

--    f3PtpPTPClockStatsIndex, f3PtpPTPClockStatsIntervalType,
--    f3PtpPTPClockStatsValid, f3PtpPTPClockStatsAction, f3PtpPTPClockStatsTotalTimeCR5,
--    f3PtpPTPClockStatsTotalTimeCR4, f3PtpPTPClockStatsTotalTimeCR3,
--    f3PtpPTPClockStatsTotalTimePR5, f3PtpPTPClockStatsTotalTimePR4,
--    f3PtpPTPClockStatsTotalTimePR3,

--    f3PtpPTPClockHistoryIndex, f3PtpPTPClockHistoryTime, f3PtpPTPClockHistoryValid,
--    f3PtpPTPClockHistoryAction, f3PtpPTPClockHistoryTotalTimeCR5,
--    f3PtpPTPClockHistoryTotalTimeCR4, f3PtpPTPClockHistoryTotalTimeCR3,
--    f3PtpPTPClockHistoryTotalTimePR5, f3PtpPTPClockHistoryTotalTimePR4,
--    f3PtpPTPClockHistoryTotalTimePR3,

--    f3PtpPTPClockThresholdIndex, f3PtpPTPClockThresholdInterval,
--    f3PtpPTPClockThresholdVariable, f3PtpPTPClockThresholdValueLo,
--    f3PtpPTPClockThresholdValueHi, f3PtpPTPClockThresholdMonValue,

    f3PtpPTPPortStatsIndex,                        
    f3PtpPTPPortStatsIntervalType,
    f3PtpPTPPortStatsValid,
    f3PtpPTPPortStatsAction,
    f3PtpPTPPortStatsAvgAnnounceRate,
    f3PtpPTPPortStatsAvgSyncRate,
    f3PtpPTPPortStatsAvgDelayReqRate,
    f3PtpPTPPortStatsAvgDelayRespRate,
    f3PtpPTPPortStatsMismatchDomainDiscards,
    f3PtpPTPPortStatsMessageWrongTypeDiscards,
    f3PtpPTPPortStatsMessagesWrongLengthDiscards,
    f3PtpPTPPortStatsUnknownMasterDiscards,
    f3PtpPTPPortStatsMinOffsetFromMaster, 
    f3PtpPTPPortStatsMaxOffsetFromMaster,
    f3PtpPTPPortStatsAvgOffsetFromMaster,
    f3PtpPTPPortStatsMinSyncPathDelay,
    f3PtpPTPPortStatsMaxSyncPathDelay,
    f3PtpPTPPortStatsAvgSyncPathDelay,
    f3PtpPTPPortStatsMinMeanPathDelay,
    f3PtpPTPPortStatsMaxMeanPathDelay,
    f3PtpPTPPortStatsAvgMeanPathDelay,


    f3PtpPTPPortHistoryIndex,
    f3PtpPTPPortHistoryTime,
    f3PtpPTPPortHistoryValid,
    f3PtpPTPPortHistoryAction,
    f3PtpPTPPortHistoryAvgAnnounceRate,
    f3PtpPTPPortHistoryAvgSyncRate,
    f3PtpPTPPortHistoryAvgDelayReqRate,
    f3PtpPTPPortHistoryAvgDelayRespRate,
    f3PtpPTPPortHistoryMismatchDomainDiscards,
    f3PtpPTPPortHistoryMessageWrongTypeDiscards,
    f3PtpPTPPortHistoryMessagesWrongLengthDiscards,
    f3PtpPTPPortHistoryUnknownMasterDiscards,
    f3PtpPTPPortHistoryMinOffsetFromMaster,
    f3PtpPTPPortHistoryMaxOffsetFromMaster,
    f3PtpPTPPortHistoryAvgOffsetFromMaster,        
    f3PtpPTPPortHistoryMinSyncPathDelay,
    f3PtpPTPPortHistoryMaxSyncPathDelay,
    f3PtpPTPPortHistoryAvgSyncPathDelay,
    f3PtpPTPPortHistoryMinMeanPathDelay,
    f3PtpPTPPortHistoryMaxMeanPathDelay,
    f3PtpPTPPortHistoryAvgMeanPathDelay,

    f3PtpPTPPortThresholdIndex, f3PtpPTPPortThresholdInterval,
    f3PtpPTPPortThresholdVariable, f3PtpPTPPortThresholdValueLo,
    f3PtpPTPPortThresholdValueHi, f3PtpPTPPortThresholdMonValue

    }
    STATUS  current
    DESCRIPTION
        "A collection of objects used to manage the F3 PTP Performance data."
    ::= { f3PtpGroups 2 }

f3PtpPerfNotifGroup NOTIFICATION-GROUP
    NOTIFICATIONS {
        f3PtpAccPortFlowPointThresholdCrossingAlert,
        f3PtpNetPortFlowPointThresholdCrossingAlert,
        f3PtpSOOCCrossingAlert, f3PtpTSCrossingAlert,
--        f3PtpPTPClockCrossingAlert,
        f3PtpPTPPortCrossingAlert

    }
    STATUS  current
    DESCRIPTION
            "A collection of notifications related to F3 PTP Threshold Crossing 
             Alerts."
    ::= { f3PtpGroups 3 }

f3PtpStatusChangeNotifGroup NOTIFICATION-GROUP
    NOTIFICATIONS {
        f3PtpTSStatusChangeTrap 
    }
    STATUS  current
    DESCRIPTION
            "A collection of notifications related to F3 PTP Status Changes ." 
    ::= { f3PtpGroups 4 }

f3PtpBoundaryClockObjectGroup OBJECT-GROUP
    OBJECTS {
       f3PtpBCAlias,
       f3PtpBCAdminState,
       f3PtpBCOperationalState,
       f3PtpBCSecondaryState,
       f3PtpBCClockIdentity,
       f3PtpBCTimingSource,
       f3PtpBCClockClass,
       f3PtpBCDomainNumber,
       f3PtpBCStorageType,
       f3PtpBCRowStatus,
       
       f3PtpMasterClockIndex,
       f3PtpMasterClockAlias,
       f3PtpMasterClockAdminState,
       f3PtpMasterClockOperationalState,
       f3PtpMasterClockSecondaryState,
       f3PtpMasterClockClockIdentity,
       f3PtpMasterClockTimeClock,
       f3PtpMasterClockClockClass,
       f3PtpMasterClockDomainNumber,
       f3PtpMasterClockPriority1,
       f3PtpMasterClockPriority2,
       f3PtpMasterClockClockAccuracy,
       f3PtpMasterClockTimeScale,
       f3PtpMasterClockUtcOffset,
       f3PtpMasterClockStorageType,
       f3PtpMasterClockRowStatus,
       f3PtpMasterClockActiveTimeRef,

       f3PtpMCIAlias,
       f3PtpMCIAdminState,
       f3PtpMCIOperationalState,
       f3PtpMCISecondaryState,
       f3PtpMCIPortIdentity,
       f3PtpMCIDomainNumber,
       f3PtpMCIClockType,
       f3PtpMCIDelayMechanism,
       f3PtpMCIIfName,
       f3PtpMCIIpProtocol,
       f3PtpMCIMasterIpV4Address,
       f3PtpMCIMasterIpV4SubnetMask,
       f3PtpMCIIpPriorityMapMode,
       f3PtpMCIIpPriority,
       f3PtpMCIMaxLeaseDuration,
       f3PtpMCIMaxSlavesSupported,
       f3PtpMCIMaxStaticSlavesSupported,
       f3PtpMCIMaxSyncMsgRate,
       f3PtpMCIMaxDelayRespMsgRate,
       f3PtpMCIMaxAnnounceMsgRate,
       f3PtpMCIStorageType,
       f3PtpMCIRowStatus, 
       f3PtpMCIServiceFlow,
       f3PtpMCIClockClassProfile,
       f3PtpMCIClockClass, 


       f3PtpMasterVirtualPortAlias,
       f3PtpMasterVirtualPortAdminState,
       f3PtpMasterVirtualPortOperationalState,
       f3PtpMasterVirtualPortSecondaryState,
       f3PtpMasterVirtualPortFlowPoint,
       f3PtpMasterVirtualPortStorageType,
       f3PtpMasterVirtualPortRowStatus,

       f3PtpStaticRemoteSlaveAlias,
       f3PtpStaticRemoteSlaveAdminState,
       f3PtpStaticRemoteSlaveOperationalState,
       f3PtpStaticRemoteSlaveSecondaryState,
       f3PtpStaticRemoteSlaveClockIdentity,
       f3PtpStaticRemoteSlaveIpV4Address,
       f3PtpStaticRemoteSlaveTimeCreated,
       f3PtpStaticRemoteSlaveSyncMsgRate,
       f3PtpStaticRemoteSlaveDelayRspMsgRate,
       f3PtpStaticRemoteSlaveAnnounceMsgRate,
       f3PtpStaticRemoteSlaveNegSyncLeaseDur,
       f3PtpStaticRemoteSlaveNegDelayRspLeaseDur,
       f3PtpStaticRemoteSlaveNegAnnounceLeaseDur,
       f3PtpStaticRemoteSlaveSyncDurRemTime,
       f3PtpStaticRemoteSlaveDelayRspDurRemTime,
       f3PtpStaticRemoteSlaveAnnounceDurRemTime,
       f3PtpStaticRemoteSlaveUmnControl,
       f3PtpStaticRemoteSlaveStorageType,
       f3PtpStaticRemoteSlaveRowStatus,

       f3PtpDynamicRemoteSlaveAlias,
       f3PtpDynamicRemoteSlaveAdminState,
       f3PtpDynamicRemoteSlaveOperationalState,
       f3PtpDynamicRemoteSlaveSecondaryState,
       f3PtpDynamicRemoteSlaveClockIdentity,
       f3PtpDynamicRemoteSlaveIpV4Address,
       f3PtpDynamicRemoteSlaveTimeCreated,
       f3PtpDynamicRemoteSlaveSyncMsgRate,
       f3PtpDynamicRemoteSlaveDelayRspMsgRate,
       f3PtpDynamicRemoteSlaveAnnounceMsgRate,
       f3PtpDynamicRemoteSlaveNegSyncLeaseDur,
       f3PtpDynamicRemoteSlaveNegDelayRspLeaseDur,
       f3PtpDynamicRemoteSlaveNegAnnounceLeaseDur,
       f3PtpDynamicRemoteSlaveSyncDurRemTime,
       f3PtpDynamicRemoteSlaveDelayRspDurRemTime,
       f3PtpDynamicRemoteSlaveAnnounceDurRemTime,
       f3PtpDynamicRemoteSlaveRowStatus,
       f3PtpDynamicRemoteSlaveStorageType,

       f3PtpMCIStatsIntervalType,
       f3PtpMCIStatsValid,
       f3PtpMCIStatsAction,
       f3PtpMCIStatsPtpDiscards,
       f3PtpMCIStatsSyncDeniedEvents,
       f3PtpMCIStatsDelayRspDeniedEvents,
       f3PtpMCIStatsAnnounceDeniedEvents,
       f3PtpMCIStatsSyncCancelledEvents,
       f3PtpMCIStatsDelayRspCancelledEvents,
       f3PtpMCIStatsAnnounceCancelledEvents,
       f3PtpMCIStatsDynamicSlavesLearnt,
       f3PtpMCIStatsDynamicSlavesDropped,

       f3PtpMCIHistoryIndex,
       f3PtpTSHistoryTime,
       f3PtpMCIHistoryValid,
       f3PtpMCIHistoryAction,
       f3PtpMCIHistoryPtpDiscards,
       f3PtpMCIHistorySyncDeniedEvents,
       f3PtpMCIHistoryDelayRspDeniedEvents,
       f3PtpMCIHistoryAnnounceDeniedEvents,
       f3PtpMCIHistorySyncCancelledEvents,
       f3PtpMCIHistoryDelayRspCancelledEvents,
       f3PtpMCIHistoryAnnounceCancelledEvents,
       f3PtpMCIHistoryDynamicSlavesLearnt,
       f3PtpMCIHistoryDynamicSlavesDropped,

       f3PtpMCIThresholdInterval,
       f3PtpMCIThresholdVariable,
       f3PtpMCIThresholdValueLo,
       f3PtpMCIThresholdValueHi,
       f3PtpMCIThresholdMonValue,

       f3PtpRemoteSlaveStatsIntervalType,
       f3PtpRemoteSlaveStatsValid,
       f3PtpRemoteSlaveStatsAction,
       f3PtpRemoteSlaveStatsSyncMsgsGen,
       f3PtpRemoteSlaveStatsDelayRspMsgsGen,
       f3PtpRemoteSlaveStatsAnnounceMsgsGen,
       f3PtpRemoteSlaveStatsSignallingMsgsGen,
       f3PtpRemoteSlaveStatsDelayReqMsgsRx,
       f3PtpRemoteSlaveStatsSignallingMsgsRx,
       f3PtpRemoteSlaveStatsDelayReqMsgsDropped,
       f3PtpRemoteSlaveStatsInvalidTLVLenDiscards,
       f3PtpRemoteSlaveStatsInvalidTLVTypeDiscards,
       f3PtpRemoteSlaveStatsTimesSyncLeaseExp,
       f3PtpRemoteSlaveStatsTimesDelayRspLeaseExp,
       f3PtpRemoteSlaveStatsTimesAnnounceLeaseExp,

       f3PtpRemoteSlaveHistoryTime,
       f3PtpRemoteSlaveHistoryValid,
       f3PtpRemoteSlaveHistoryAction,
       f3PtpRemoteSlaveHistorySyncMsgsGen,
       f3PtpRemoteSlaveHistoryDelayRspMsgsGen,
       f3PtpRemoteSlaveHistoryAnnounceMsgsGen,
       f3PtpRemoteSlaveHistorySignallingMsgsGen,
       f3PtpRemoteSlaveHistoryDelayReqMsgsRx,
       f3PtpRemoteSlaveHistorySignallingMsgsRx,
       f3PtpRemoteSlaveHistoryDelayReqMsgsDropped,
       f3PtpRemoteSlaveHistoryInvalidTLVLenDiscards,
       f3PtpRemoteSlaveHistoryInvalidTLVTypeDiscards,
       f3PtpRemoteSlaveHistoryTimesSyncLeaseExp,
       f3PtpRemoteSlaveHistoryTimesDelayRspLeaseExp,
       f3PtpRemoteSlaveHistoryTimesAnnounceLeaseExp,

       f3PtpRemoteSlaveThresholdInterval,
       f3PtpRemoteSlaveThresholdVariable,
       f3PtpRemoteSlaveThresholdValueLo,
       f3PtpRemoteSlaveThresholdValueHi,
       f3PtpRemoteSlaveThresholdMonValue
    }
    STATUS  current
    DESCRIPTION
            "A collection of objects related to F3 PTP Boundary Clock feature." 
    ::= { f3PtpGroups 5 }

f3PtpBoundaryClockNotifGroup NOTIFICATION-GROUP
    NOTIFICATIONS {
       f3PtpMCICrossingAlert,
       f3PtpRemoteSlaveCrossingAlert,
       f3PtpMasterClockStatusChangeTrap,	 
       f3PtpBCStatusChangeTrap,	 
       f3PtpDynamicRemoteSlaveStatusChangeTrap 
    }
    STATUS  current
    DESCRIPTION
            "A collection of notifications related to F3 PTP Boundary Clock feature." 
    ::= { f3PtpGroups 6 }

END
