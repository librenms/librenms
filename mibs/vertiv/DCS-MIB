------------------------------------------------------------
-- Vertiv
-- ITEI MIB 
------------------------------------------------------------

DCS-MIB DEFINITIONS ::= BEGIN

IMPORTS
	MODULE-IDENTITY, OBJECT-TYPE, NOTIFICATION-TYPE,Integer32, Counter32, enterprises		FROM SNMPv2-SMI
	TEXTUAL-CONVENTION, DisplayString, DateAndTime											FROM SNMPv2-TC;
	
------------------------------------------------------------
-- Node definitions
------------------------------------------------------------
dcs MODULE-IDENTITY
	LAST-UPDATED "201808160000Z"
	ORGANIZATION "Vertiv"
	CONTACT-INFO "vertivc.service@vertivco.com"
	DESCRIPTION  "Vertiv device MIB"
	::= { enp 3 }
	


enp OBJECT IDENTIFIER ::= { enterprises 13400 }


------------------------------------------------------------
-- Textual conventions
------------------------------------------------------------

AlarmSeverity ::= TEXTUAL-CONVENTION
	STATUS current
	DESCRIPTION "
		The severity of the alarm. One of
		(1) informational
		(2) warning
		(3) critical"
	SYNTAX INTEGER {
		informational(1),
		warning(2),
		critical(3) }
		
AlarmStatusChange ::= TEXTUAL-CONVENTION
	STATUS current
	DESCRIPTION "
		Indicates 'activated' (0) or 'deactivated' (1) alarm events."
	SYNTAX INTEGER {
		activated(0),
		deactivated(1) }
		
		
------------------------------------------------------------
-- System Info{ 13400.3.1 }
------------------------------------------------------------

systemInfo OBJECT IDENTIFIER ::=  { dcs 1 }

systemLoaction OBJECT-TYPE
		SYNTAX 			DisplayString
		MAX-ACCESS 		read-only
		STATUS 			current
		DESCRIPTION 	"Where is this Uint"
		::= 			{ systemInfo 1 }

systemEquipNum OBJECT-TYPE
		SYNTAX 			Integer32
		MAX-ACCESS 		read-only
		STATUS 			current
		DESCRIPTION 	"System Equipment Number"
		::=				{ systemInfo 2 }
		
systemEquipListTable OBJECT-TYPE
		SYNTAX 			SEQUENCE OF SystemEquipListEntry
		MAX-ACCESS 		not-accessible
		STATUS 			current
		DESCRIPTION 	"System Equipment List Table"
		::= 			{ systemInfo 3 }
	
systemEquipListEntry OBJECT-TYPE
		SYNTAX 			SystemEquipListEntry
		MAX-ACCESS 		not-accessible
		STATUS 			current
		DESCRIPTION 	"System Equipment List Entry"
		INDEX 			{ systemEquipListIndex }
		::= 			{ systemEquipListTable 1 }

SystemEquipListEntry ::= SEQUENCE {
		systemEquipListIndex 		Integer32,
		systemEquipTypeName			DisplayString,
		systemEquipID				Integer32,
		systemEquipTypeID	 		Integer32}
	
systemEquipListIndex OBJECT-TYPE
		SYNTAX 			Integer32(1..64)
		MAX-ACCESS 		read-only
		STATUS 			current
		DESCRIPTION 	"System Equipment List Index"
		::=				{ systemEquipListEntry 1 }
		
systemEquipTypeName OBJECT-TYPE
		SYNTAX 			DisplayString
		MAX-ACCESS 		read-only
		STATUS 			current
		DESCRIPTION 	"System Equipment Type Name"
		::= 			{ systemEquipListEntry 2 }
		
systemEquipID OBJECT-TYPE
		SYNTAX 			Integer32
		MAX-ACCESS 		read-only
		STATUS 			current
		DESCRIPTION 	"System Equipment ID"
		::= 			{ systemEquipListEntry 3 }

systemEquipTypeID OBJECT-TYPE
		SYNTAX 			Integer32
		MAX-ACCESS 		read-only
		STATUS 			current
		DESCRIPTION 	"System Equipment Type ID"
		::= 			{ systemEquipListEntry 4 }


------------------------------------------------------------
-- System { 13400.3.1.100 }
------------------------------------------------------------
rdua-System OBJECT IDENTIFIER ::= { systemInfo 100 }
rduaSystemTable OBJECT-TYPE
		SYNTAX			SEQUENCE OF RduaSystemEntry
		MAX-ACCESS		not-accessible
		STATUS			current
		DESCRIPTION	"rduaSystemTable"
		::=			{ rdua-System 1 }
rduaSystemEntry OBJECT-TYPE
		SYNTAX			RduaSystemEntry
		MAX-ACCESS		not-accessible
		STATUS			current
		DESCRIPTION		"rduaSystemEntry"
		INDEX			{ rduaSystemIndex }
		::=				{ rduaSystemTable 1 }
RduaSystemEntry ::= SEQUENCE {
		rduaSystemIndex								Integer32,
		rduaSystemsSystemstatus						INTEGER,
		rduaSystemsUnitInternalStatus				INTEGER,
		rduaSystemsRunningConfigType				INTEGER,
		rduaSystemsAutoManState						INTEGER,
		rduaSystemsOutgoingAlarmBlocked				INTEGER,
		rduaSystemsDatastatstartclock				INTEGER,
		rduaSystemsDatastatperiod					INTEGER }
rduaSystemIndex OBJECT-TYPE
		SYNTAX Integer32(1..8)
		MAX-ACCESS read-only
		STATUS current
		DESCRIPTION
		"rduaSystem System Entry Index."
		::= { rduaSystemEntry 1 }
rduaSystemsSystemstatus OBJECT-TYPE
		SYNTAX Integer32
		
		MAX-ACCESS read-only
		STATUS current
		DESCRIPTION
		"rduaSystemsSystemstatus status."
		::= { rduaSystemEntry 2 }
rduaSystemsUnitInternalStatus OBJECT-TYPE
		SYNTAX Integer32
		
		MAX-ACCESS read-only
		STATUS current
		DESCRIPTION
		"rduaSystemsUnitInternalStatus status."
		::= { rduaSystemEntry 3 }
rduaSystemsRunningConfigType OBJECT-TYPE
		SYNTAX Integer32
		
		MAX-ACCESS read-only
		STATUS current
		DESCRIPTION
		"rduaSystemsRunningConfigType status."
		::= { rduaSystemEntry 4 }
rduaSystemsAutoManState OBJECT-TYPE
		SYNTAX Integer32
		
		MAX-ACCESS read-write
		STATUS current
		DESCRIPTION
		"rduaSystemsAuto/ManState status."
		::= { rduaSystemEntry 5 }
rduaSystemsOutgoingAlarmBlocked OBJECT-TYPE
		SYNTAX Integer32
		
		MAX-ACCESS read-write
		STATUS current
		DESCRIPTION
		"rduaSystemsOutgoingAlarmBlocked status."
		::= { rduaSystemEntry 6 }
rduaSystemsDatastatstartclock OBJECT-TYPE
		SYNTAX Integer32
		
		MAX-ACCESS read-write
		STATUS current
		DESCRIPTION
		"rduaSystemsDatastatstartclock oclock."
		::= { rduaSystemEntry 7 }
rduaSystemsDatastatperiod OBJECT-TYPE
		SYNTAX Integer32
		
		MAX-ACCESS read-write
		STATUS current
		DESCRIPTION
		"rduaSystemsDatastatperiod h."
		::= { rduaSystemEntry 8 }


------------------------------------------------------------
-- Env { 13400.3.5 }
------------------------------------------------------------
env OBJECT IDENTIFIER ::=  { dcs 5 }


------------------------------------------------------------
-- Tdicom { 13400.3.5.541 }
------------------------------------------------------------
env-Tdicom OBJECT IDENTIFIER ::= { env 541 }
envTdicomTable OBJECT-TYPE
		SYNTAX			SEQUENCE OF EnvTdicomEntry
		MAX-ACCESS		not-accessible
		STATUS			current
		DESCRIPTION	"envTdicomTable"
		::=			{ env-Tdicom 1 }
envTdicomEntry OBJECT-TYPE
		SYNTAX			EnvTdicomEntry
		MAX-ACCESS		not-accessible
		STATUS			current
		DESCRIPTION		"envTdicomEntry"
		INDEX			{ envTdicomIndex }
		::=				{ envTdicomTable 1 }
EnvTdicomEntry ::= SEQUENCE {
		envTdicomIndex					Integer32,
		envTdicom2FrontTemp					Integer32,
		envTdicom3RearTemp					Integer32,
		envTdicom4FrontDoor					INTEGER,
		envTdicom5RearDoor					INTEGER,
		envTdicom6Water					INTEGER,
		envTdicom7FrontTempAlarmStatus					INTEGER,
		envTdicom8RearTempAlarmStatus					INTEGER,
		envTdicom9FrontSensorCommStatus					INTEGER,
		envTdicom10RearSensorCommStatus					INTEGER,
		envTdicom114DICommStatus					INTEGER,
		envTdicom12FrontSensorCommStatus					INTEGER,
		envTdicom13FrontTempAlarmhystersis					Integer32,
		envTdicom14RearTempAlarmhystersis					Integer32,
		envTdicom15HighFrontTempAlarmlimit					Integer32,
		envTdicom16HighRearTempAlarmlimit					Integer32,
		envTdicom17LowFrontTempAlarmlimit					Integer32,
		envTdicom18LightningArresterStatus					INTEGER,
		envTdicom19OutsideCabinetTemp					Integer32,
		envTdicom20OutsideCabinetHum					Integer32 }
envTdicomIndex OBJECT-TYPE
		SYNTAX Integer32(1..20)
		MAX-ACCESS read-only
		STATUS current
		DESCRIPTION
		"envTdicom System Entry Index."
		::= { envTdicomEntry 1 }
envTdicom2FrontTemp OBJECT-TYPE
		SYNTAX Integer32
		MAX-ACCESS read-only
		STATUS current
		DESCRIPTION
		"envTdicom1FrontTemp stored as 0.1℃."
		::= { envTdicomEntry 2 }
envTdicom3RearTemp OBJECT-TYPE
		SYNTAX Integer32
		MAX-ACCESS read-only
		STATUS current
		DESCRIPTION
		"envTdicom2RearTemp stored as 0.1℃."
		::= { envTdicomEntry 3 }
envTdicom4FrontDoor OBJECT-TYPE
		SYNTAX INTEGER {
			close(0),
			open(1),
			uninstalled(2),
			leave(3) }
		MAX-ACCESS read-only
		STATUS current
		DESCRIPTION
		"envTdicom3FrontDoor status."
		::= { envTdicomEntry 4 }
envTdicom5RearDoor OBJECT-TYPE
		SYNTAX INTEGER {
			close(0),
			open(1),
			uninstalled(2),
			leave(3) }
		MAX-ACCESS read-only
		STATUS current
		DESCRIPTION
		"envTdicom4RearDoor status."
		::= { envTdicomEntry 5 }
envTdicom6Water OBJECT-TYPE
		SYNTAX INTEGER {
			normal(0),
			alarm(1),
			uninstalled(2),
			leave(3) }
		MAX-ACCESS read-only
		STATUS current
		DESCRIPTION
		"envTdicom5Water status."
		::= { envTdicomEntry 6 }
envTdicom7FrontTempAlarmStatus OBJECT-TYPE
		SYNTAX INTEGER {
			normal(0),
			hightemp(1),
			lowtemp(2),
			invalid(3) }
		MAX-ACCESS read-only
		STATUS current
		DESCRIPTION
		"envTdicom6FrontTempAlarmStatus status."
		::= { envTdicomEntry 7 }
envTdicom8RearTempAlarmStatus OBJECT-TYPE
		SYNTAX INTEGER {
			normal(0),
			hightemp(1),
			lowtemp(2),
			invalid(3) }
		MAX-ACCESS read-only
		STATUS current
		DESCRIPTION
		"envTdicom7RearTempAlarmStatus status."
		::= { envTdicomEntry 8 }
envTdicom9FrontSensorCommStatus OBJECT-TYPE
		SYNTAX INTEGER {
			normal(0),
			failure(1) }
		MAX-ACCESS read-only
		STATUS current
		DESCRIPTION
		"envTdicom8FrontSensorCommStatus status."
		::= { envTdicomEntry 9 }
envTdicom10RearSensorCommStatus OBJECT-TYPE
		SYNTAX INTEGER {
			normal(0),
			failure(1) }
		MAX-ACCESS read-only
		STATUS current
		DESCRIPTION
		"envTdicom9RearSensorCommStatus status."
		::= { envTdicomEntry 10 }
envTdicom114DICommStatus OBJECT-TYPE
		SYNTAX INTEGER {
			normal(0),
			failure(1) }
		MAX-ACCESS read-only
		STATUS current
		DESCRIPTION
		"envTdicom104DICommStatus status."
		::= { envTdicomEntry 11 }
envTdicom12FrontSensorCommStatus OBJECT-TYPE
		SYNTAX INTEGER {
			frontsensorcommstatus(0) }
		MAX-ACCESS read-write
		STATUS current
		DESCRIPTION
		"envTdicom11FrontSensorCommStatus status."
		::= { envTdicomEntry 12 }
envTdicom13FrontTempAlarmhystersis OBJECT-TYPE
		SYNTAX Integer32
		
		MAX-ACCESS read-write
		STATUS current
		DESCRIPTION
		"envTdicom12FrontTempAlarmhystersis stored as 1℃."
		::= { envTdicomEntry 13 }
envTdicom14RearTempAlarmhystersis OBJECT-TYPE
		SYNTAX Integer32
		
		MAX-ACCESS read-write
		STATUS current
		DESCRIPTION
		"envTdicom13RearTempAlarmhystersis stored as 1℃."
		::= { envTdicomEntry 14 }
envTdicom15HighFrontTempAlarmlimit OBJECT-TYPE
		SYNTAX Integer32
		
		MAX-ACCESS read-write
		STATUS current
		DESCRIPTION
		"envTdicom14HighFrontTempAlarmlimit stored as 1℃."
		::= { envTdicomEntry 15 }
envTdicom16HighRearTempAlarmlimit OBJECT-TYPE
		SYNTAX Integer32
		
		MAX-ACCESS read-write
		STATUS current
		DESCRIPTION
		"envTdicom15HighRearTempAlarmlimit stored as 1℃."
		::= { envTdicomEntry 16 }
envTdicom17LowFrontTempAlarmlimit OBJECT-TYPE
		SYNTAX Integer32
		
		MAX-ACCESS read-write
		STATUS current
		DESCRIPTION
		"envTdicom16LowFrontTempAlarmlimit stored as 1℃."
		::= { envTdicomEntry 17 }
envTdicom18LightningArresterStatus OBJECT-TYPE
		SYNTAX INTEGER {
			normal(0),
			alarm(1),
			uninstalled(2),
			leave(3) }
		MAX-ACCESS read-only
		STATUS current
		DESCRIPTION
		"envTdicom17LightningArresterStatus status."
		::= { envTdicomEntry 18 }
envTdicom19OutsideCabinetTemp OBJECT-TYPE
		SYNTAX Integer32
		
		MAX-ACCESS read-only
		STATUS current
		DESCRIPTION
		"envTdicom18OutsideCabinetTemp stored as 0.1℃."
		::= { envTdicomEntry 19 }
envTdicom20OutsideCabinetHum OBJECT-TYPE
		SYNTAX Integer32
		
		MAX-ACCESS read-only
		STATUS current
		DESCRIPTION
		"envTdicom19OutsideCabinetHum stored as 0.1%."
		::= { envTdicomEntry 20 }

------------------------------------------------------------
-- 4dosensor { 13400.3.5.519 }
------------------------------------------------------------
env-4dosensor OBJECT IDENTIFIER ::= { env 519 }
env4dosensorTable OBJECT-TYPE
		SYNTAX			SEQUENCE OF Env4dosensorEntry
		MAX-ACCESS		not-accessible
		STATUS			current
		DESCRIPTION	"env4dosensorTable"
		::=			{ env-4dosensor 1 }
env4dosensorEntry OBJECT-TYPE
		SYNTAX			Env4dosensorEntry
		MAX-ACCESS		not-accessible
		STATUS			current
		DESCRIPTION		"env4dosensorEntry"
		INDEX			{ env4dosensorIndex }
		::=				{ env4dosensorTable 1 }
Env4dosensorEntry ::= SEQUENCE {
		env4dosensorIndex					Integer32,
		env4dosensor2RedLightStatus					INTEGER,
		env4dosensor3BlueLightStatus					INTEGER,
		env4dosensor4FanStatus					INTEGER,
		env4dosensor54DOF0CommunicateStatus					INTEGER,
		env4dosensor6FanStatus					INTEGER,
		env4dosensor74DOF0CommOvertimeValue					INTEGER }
env4dosensorIndex OBJECT-TYPE
		SYNTAX Integer32(1..7)
		MAX-ACCESS read-only
		STATUS current
		DESCRIPTION
		"env4dosensor System Entry Index."
		::= { env4dosensorEntry 1 }
env4dosensor2RedLightStatus OBJECT-TYPE
		SYNTAX INTEGER {
			off(0),
			on(1) }
		MAX-ACCESS read-only
		STATUS current
		DESCRIPTION
		"env4dosensor1RedLightStatus status."
		::= { env4dosensorEntry 2 }
env4dosensor3BlueLightStatus OBJECT-TYPE
		SYNTAX INTEGER {
			off(0),
			on(1) }
		MAX-ACCESS read-only
		STATUS current
		DESCRIPTION
		"env4dosensor2BlueLightStatus status."
		::= { env4dosensorEntry 3 }
env4dosensor4FanStatus OBJECT-TYPE
		SYNTAX INTEGER {
			off(0),
			on(1) }
		MAX-ACCESS read-only
		STATUS current
		DESCRIPTION
		"env4dosensor3FanStatus status."
		::= { env4dosensorEntry 5 }
env4dosensor54DOF0CommunicateStatus OBJECT-TYPE
		SYNTAX INTEGER {
			normal(0),
			failure(1) }
		MAX-ACCESS read-only
		STATUS current
		DESCRIPTION
		"env4dosensor44DOF0CommunicateStatus status."
		::= { env4dosensorEntry 42 }
env4dosensor6FanStatus OBJECT-TYPE
		SYNTAX INTEGER {
			off(0),
			on(1) }
		MAX-ACCESS read-write
		STATUS current
		DESCRIPTION
		"env4dosensor5FanStatus status."
		::= { env4dosensorEntry 49 }
env4dosensor74DOF0CommOvertimeValue OBJECT-TYPE
		SYNTAX Integer32
		
		MAX-ACCESS read-write
		STATUS current
		DESCRIPTION
		"env4dosensor64DOF0CommOvertimeValue stored as 1Min."
		::= { env4dosensorEntry 62 }

------------------------------------------------------------
-- Ups { 13400.3.4 }
------------------------------------------------------------
ups OBJECT IDENTIFIER ::=  { dcs 4 }


------------------------------------------------------------
-- Ita2com { 13400.3.4.491 }
------------------------------------------------------------
ups-Ita2com OBJECT IDENTIFIER ::= { ups 491 }
upsIta2comTable OBJECT-TYPE
		SYNTAX			SEQUENCE OF UpsIta2comEntry
		MAX-ACCESS		not-accessible
		STATUS			current
		DESCRIPTION	"upsIta2comTable"
		::=			{ ups-Ita2com 1 }
upsIta2comEntry OBJECT-TYPE
		SYNTAX			UpsIta2comEntry
		MAX-ACCESS		not-accessible
		STATUS			current
		DESCRIPTION		"upsIta2comEntry"
		INDEX			{ upsIta2comIndex }
		::=				{ upsIta2comTable 1 }
UpsIta2comEntry ::= SEQUENCE {
		upsIta2comIndex					Integer32,
		upsIta2com2PhaseAInputVoltage					Integer32,
		upsIta2com3PhaseBInputVoltage					Integer32,
		upsIta2com4PhaseCInputVoltage					Integer32,
		upsIta2com5PhaseAOutputVoltage					Integer32,
		upsIta2com6PhaseBOutputVoltage					Integer32,
		upsIta2com7PhaseCOutputVoltage					Integer32,
		upsIta2com8PhaseAOutputCurrent					Integer32,
		upsIta2com9PhaseBOutputCurrent					Integer32,
		upsIta2com10PhaseCOutputCurrent					Integer32,
		upsIta2com11OutputFrequency					Integer32,
		upsIta2com12InputPhaseNumber					INTEGER,
		upsIta2com13LineAbInputVoltage					Integer32,
		upsIta2com14LineBcInputVoltage					Integer32,
		upsIta2com15LineCaInputVoltage					Integer32,
		upsIta2com16PhaseAInputCurrent					Integer32,
		upsIta2com17PhaseBInputCurrent					Integer32,
		upsIta2com18PhaseCInputCurrent					Integer32,
		upsIta2com19SystemInputFrequency					Integer32,
		upsIta2com20PhaseAInputPowerFactor					Integer32,
		upsIta2com21PhaseBInputPowerFactor					Integer32,
		upsIta2com22PhaseCInputPowerFactor					Integer32,
		upsIta2com23BypassAVoltageA					Integer32,
		upsIta2com24BypassBVoltageB					Integer32,
		upsIta2com25BypassCVoltageC					Integer32,
		upsIta2com26BypassLineAbVoltage					Integer32,
		upsIta2com27BypassLineBcVoltage					Integer32,
		upsIta2com28BypassLineCaVoltage					Integer32,
		upsIta2com29BypassFrequency					Integer32,
		upsIta2com30BusvoltageP					Integer32,
		upsIta2com31BusvoltageN					Integer32,
		upsIta2com32OutputPhaseNumber					INTEGER,
		upsIta2com33PhaseAOutputPowerFactor					Integer32,
		upsIta2com34PhaseBOutputPowerFactor					Integer32,
		upsIta2com35PhaseCOutputPowerFactor					Integer32,
		upsIta2com36LPhaseAOutputPeakRatio					Integer32,
		upsIta2com37LPhaseBOutputPeakRatio					Integer32,
		upsIta2com38LPhaseCOutputPeakRatio					Integer32,
		upsIta2com39LPhaseAOutputActivePower					Integer32,
		upsIta2com40LPhaseBOutputActivePower					Integer32,
		upsIta2com41LPhaseCOutputActivePower					Integer32,
		upsIta2com42LPhaseAOutputApparentPower					Integer32,
		upsIta2com43LPhaseBOutputApparentPower					Integer32,
		upsIta2com44LPhaseCOutputApparentPower					Integer32,
		upsIta2com45LPhaseAOutputLoadPercent					Integer32,
		upsIta2com46LPhaseBOutputLoadPercent					Integer32,
		upsIta2com47LPhaseCOutputLoadPercent					Integer32,
		upsIta2com48SPhaseAOutputPowerFactor					Integer32,
		upsIta2com49SPhaseBOutputPowerFactor					Integer32,
		upsIta2com50SPhaseCOutputPowerFactor					Integer32,
		upsIta2com51SPhaseAOutputActivePower					Integer32,
		upsIta2com52SPhaseBOutputActivePower					Integer32,
		upsIta2com53SPhaseCOutputActivePower					Integer32,
		upsIta2com54SPhaseAOutputApparentPower					Integer32,
		upsIta2com55SPhaseBOutputApparentPower					Integer32,
		upsIta2com56SPhaseCOutputApparentPower					Integer32,
		upsIta2com57ParallelMachineNumber					Integer32,
		upsIta2com58UpsRunningTime					Integer32,
		upsIta2com59BatVoltage					Integer32,
		upsIta2com60BatChargingCurrent					Integer32,
		upsIta2com61BatDischargeCurrent					Integer32,
		upsIta2com62NegativeBatVoltage					Integer32,
		upsIta2com63NegativeBatChargeCurrent					Integer32,
		upsIta2com64NegativeBatDischargeCurrent					Integer32,
		upsIta2com65BatBackupTime					Integer32,
		upsIta2com66Battemp					Integer32,
		upsIta2com67Ambienttemp					Integer32,
		upsIta2com68BatCurrentCapacity					Integer32,
		upsIta2com69BatDischargeTimes					Integer32,
		upsIta2com70BatHelth					Integer32,
		upsIta2com71InputPower					Integer32,
		upsIta2com72OutputPower					Integer32,
		upsIta2com73BatRunningTime					Integer32,
		upsIta2com74BatDischargingTime					Integer32,
		upsIta2com75PowerSupply					INTEGER,
		upsIta2com76InputPowerStatus					INTEGER,
		upsIta2com77BatStatus					INTEGER,
		upsIta2com78BatNegativeGroupStatus					INTEGER,
		upsIta2com79ChargerStatus					INTEGER,
		upsIta2com80ParallelSystemPowerState					INTEGER,
		upsIta2com81IneerNetworkconnectStatus					INTEGER,
		upsIta2com82Outlet1SwitchStatus					INTEGER,
		upsIta2com83Outlet2SwitchStatus					INTEGER,
		upsIta2com84InputAbnormal					INTEGER,
		upsIta2com85SystemOvertemp					INTEGER,
		upsIta2com86SystemBatLowPreWarning					INTEGER,
		upsIta2com87InputPhaseReversed					INTEGER,
		upsIta2com88InputNeutralLost					INTEGER,
		upsIta2com89InputGroundLost					INTEGER,
		upsIta2com90RectifierOverload					INTEGER,
		upsIta2com91BatCabinetNotConnected					INTEGER,
		upsIta2com92InverterOverload					INTEGER,
		upsIta2com93LbsAbnormal					INTEGER,
		upsIta2com94OutputPending					INTEGER,
		upsIta2com95OutputDisabled					INTEGER,
		upsIta2com96BypassAbnormal					INTEGER,
		upsIta2com97BypassAbnormalInEcoMode					INTEGER,
		upsIta2com98BypassPhaseReversed					INTEGER,
		upsIta2com99BypassOvercurrent					INTEGER,
		upsIta2com100BypassCableconnectAbnormal					INTEGER,
		upsIta2com101BatReversed					INTEGER,
		upsIta2com102BatLowPreWarning					INTEGER,
		upsIta2com103BatVoltAbnormal					INTEGER,
		upsIta2com104NoBat					INTEGER,
		upsIta2com105BatOvertemp					INTEGER,
		upsIta2com106BatAging					INTEGER,
		upsIta2com107BatTestFailure					INTEGER,
		upsIta2com108BatSeriesNotQualified					INTEGER,
		upsIta2com109FanFailure					INTEGER,
		upsIta2com110Repo					INTEGER,
		upsIta2com111ElectricLeakAlarm					INTEGER,
		upsIta2com112VersionIncompatible					INTEGER,
		upsIta2com113OutputLpeShort					INTEGER,
		upsIta2com114LossOfRedundancy					INTEGER,
		upsIta2com115SystemOverload					INTEGER,
		upsIta2com116LoadSharingAbnormal					INTEGER,
		upsIta2com117SystemParallelSetsAsync					INTEGER,
		upsIta2com118LocalParallelSetsAsync					INTEGER,
		upsIta2com119OnMaintenanceBypass					INTEGER,
		upsIta2com120BatMode					INTEGER,
		upsIta2com121BypassMode					INTEGER,
		upsIta2com122ParallelNoAbnormal					INTEGER,
		upsIta2com123BypassCableconnectAbnormal					INTEGER,
		upsIta2com124OnIntelligentSleepMode					INTEGER,
		upsIta2com125BatCabinetConnectAbnormal					INTEGER,
		upsIta2com126SystemFault					INTEGER,
		upsIta2com127EodTurnOff					INTEGER,
		upsIta2com128Bypassdisable					INTEGER,
		upsIta2com129UPShasnooutput					INTEGER,
		upsIta2com130Outputvoltageabnormal					INTEGER,
		upsIta2com131Localoutputisdisconnected					INTEGER,
		upsIta2com132Turnonfailed					INTEGER,
		upsIta2com133Inputfrequencyabnormal					INTEGER,
		upsIta2com134Fanagingtimealarm					INTEGER,
		upsIta2com135Bypassovercurrenttimeout					INTEGER,
		upsIta2com136BatDCgroundfault					INTEGER,
		upsIta2com137Systemredundantoverload					INTEGER,
		upsIta2com138BatCommfail					INTEGER,
		upsIta2com139BatummatchtheUPS					INTEGER,
		upsIta2com140BatAddrsetwrong					INTEGER,
		upsIta2com141Batmodelnotqualified					INTEGER,
		upsIta2com142BatSNabnormal					INTEGER,
		upsIta2com143Batcabinetconnectabnormal					INTEGER,
		upsIta2com144BatCANconnectabnormal					INTEGER,
		upsIta2com145BatNoexceedthelimit					INTEGER,
		upsIta2com146BatgrouplessForbiddischarge					INTEGER,
		upsIta2com147Ambienttemplowprealarm					INTEGER,
		upsIta2com148Ambienttemphighprealarm					INTEGER,
		upsIta2com149DcBusAbnormal					INTEGER,
		upsIta2com150RectifierFault					INTEGER,
		upsIta2com151DcDcFault					INTEGER,
		upsIta2com152ChargerFault					INTEGER,
		upsIta2com153InputBackfeed					INTEGER,
		upsIta2com154InverterFault					INTEGER,
		upsIta2com155InverterRelayWelded					INTEGER,
		upsIta2com156BypassBackfeed					INTEGER,
		upsIta2com157AuxiliaryPowerFault					INTEGER,
		upsIta2com158InternalCommFault					INTEGER,
		upsIta2com159OutputShortCircuit					INTEGER,
		upsIta2com160OutputOffAndVoltageIsNotZero					INTEGER,
		upsIta2com161ParallelCommBreakdown					INTEGER,
		upsIta2com162ParallelCableconnectAbnormal					INTEGER,
		upsIta2com163Systemfault					INTEGER,
		upsIta2com164Rectifiersoftstartfail					INTEGER,
		upsIta2com165DSPfault					INTEGER,
		upsIta2com166Year					INTEGER,
		upsIta2com167Month					INTEGER,
		upsIta2com168Day					INTEGER,
		upsIta2com169Hour					INTEGER,
		upsIta2com170Minute					INTEGER,
		upsIta2com171Second					INTEGER,
		upsIta2com172InputBackfeed					INTEGER,
		upsIta2com173BypassBackfeed					INTEGER,
		upsIta2com174Addr1Batmoduleonline					INTEGER,
		upsIta2com175Addr2Batmoduleonline					INTEGER,
		upsIta2com176Addr3Batmoduleonline					INTEGER,
		upsIta2com177Addr4Batmoduleonline					INTEGER,
		upsIta2com178Addr5Batmoduleonline					INTEGER,
		upsIta2com179Addr6Batmoduleonline					INTEGER,
		upsIta2com180Addr7Batmoduleonline					INTEGER,
		upsIta2com181Addr8Batmoduleonline					INTEGER,
		upsIta2com182Addr9Batmoduleonline					INTEGER,
		upsIta2com183Addr10Batmoduleonline					INTEGER,
		upsIta2com184Addr11Batmoduleonline					INTEGER,
		upsIta2com185Addr12Batmoduleonline					INTEGER,
		upsIta2com186Addr13Batmoduleonline					INTEGER,
		upsIta2com187Addr14Batmoduleonline					INTEGER,
		upsIta2com188Addr15Batmoduleonline					INTEGER,
		upsIta2com189Addr16Batmoduleonline					INTEGER,
		upsIta2com190Addr1Batstatus					INTEGER,
		upsIta2com191Addr1lithiumBatvoltage					Integer32,
		upsIta2com192Addr1lithiumBatcurrent					Integer32,
		upsIta2com193Addr1lithiumBatSOC					Integer32,
		upsIta2com194Addr1lithiumBatSOH					Integer32,
		upsIta2com195Addr1lithiumBatcellmaxvoltage					Integer32,
		upsIta2com196Addr1lithiumBatcellminvoltage					Integer32,
		upsIta2com197Addr1lithiumBatcellmaxtemp					Integer32,
		upsIta2com198Addr1lithiumBatcellmintemp					Integer32,
		upsIta2com199Addr2Batstatus					INTEGER,
		upsIta2com200Addr2lithiumBatvoltage					Integer32,
		upsIta2com201Addr2lithiumBatcurrent					Integer32,
		upsIta2com202Addr2lithiumBatSOC					Integer32,
		upsIta2com203Addr2lithiumBatSOH					Integer32,
		upsIta2com204Addr2lithiumBatcellmaxvoltage					Integer32,
		upsIta2com205Addr2lithiumBatcellminvoltage					Integer32,
		upsIta2com206Addr2lithiumBatcellmaxtemp					Integer32,
		upsIta2com207Addr2lithiumBatcellmintemp					Integer32,
		upsIta2com208Addr3Batstatus					INTEGER,
		upsIta2com209Addr3lithiumBatvoltage					Integer32,
		upsIta2com210Addr3lithiumBatcurrent					Integer32,
		upsIta2com211Addr3lithiumBatSOC					Integer32,
		upsIta2com212Addr3lithiumBatSOH					Integer32,
		upsIta2com213Addr3lithiumBatcellmaxvoltage					Integer32,
		upsIta2com214Addr3lithiumBatcellminvoltage					Integer32,
		upsIta2com215Addr3lithiumBatcellmaxtemp					Integer32,
		upsIta2com216Addr3lithiumBatcellmintemp					Integer32,
		upsIta2com217Addr4Batstatus					INTEGER,
		upsIta2com218Addr4lithiumBatvoltage					Integer32,
		upsIta2com219Addr4lithiumBatcurrent					Integer32,
		upsIta2com220Addr4lithiumBatSOC					Integer32,
		upsIta2com221Addr4lithiumBatSOH					Integer32,
		upsIta2com222Addr4lithiumBatcellmaxvoltage					Integer32,
		upsIta2com223Addr4lithiumBatcellminvoltage					Integer32,
		upsIta2com224Addr4lithiumBatcellmaxtemp					Integer32,
		upsIta2com225Addr4lithiumBatcellmintemp					Integer32,
		upsIta2com226Addr5Batstatus					INTEGER,
		upsIta2com227Addr5lithiumBatvoltage					Integer32,
		upsIta2com228Addr5LithiumBatCurrent					Integer32,
		upsIta2com229Addr5lithiumBatSOC					Integer32,
		upsIta2com230Addr5lithiumBatSOH					Integer32,
		upsIta2com231Addr5lithiumBatcellmaxvoltage					Integer32,
		upsIta2com232Addr5lithiumBatcellminvoltage					Integer32,
		upsIta2com233Addr5lithiumBatcellmaxtemp					Integer32,
		upsIta2com234Addr5lithiumBatcellmintemp					Integer32,
		upsIta2com235Addr6Batstatus					INTEGER,
		upsIta2com236Addr6lithiumBatvoltage					Integer32,
		upsIta2com237Addr6lithiumBatcurrent					Integer32,
		upsIta2com238Addr6lithiumBatSOC					Integer32,
		upsIta2com239Addr6lithiumBatSOH					Integer32,
		upsIta2com240Addr6lithiumBatcellmaxvoltage					Integer32,
		upsIta2com241Addr6lithiumBatcellminvoltage					Integer32,
		upsIta2com242Addr6lithiumBatcellmaxtemp					Integer32,
		upsIta2com243Addr6lithiumBatcellmintemp					Integer32,
		upsIta2com244Addr7Batstatus					INTEGER,
		upsIta2com245Addr7lithiumBatvoltage					Integer32,
		upsIta2com246Addr7lithiumBatcurrent					Integer32,
		upsIta2com247Addr7lithiumBatSOC					Integer32,
		upsIta2com248Addr7lithiumBatSOH					Integer32,
		upsIta2com249Addr7lithiumBatcellmaxvoltage					Integer32,
		upsIta2com250Addr7lithiumBatcellminvoltage					Integer32,
		upsIta2com251Addr7lithiumBatcellmaxtemp					Integer32,
		upsIta2com252Addr7lithiumBatcellmintemp					Integer32,
		upsIta2com253Addr8Batstatus					INTEGER,
		upsIta2com254Addr8lithiumBatvoltage					Integer32,
		upsIta2com255Addr8lithiumBatcurrent					Integer32,
		upsIta2com256Addr8lithiumBatSOC					Integer32,
		upsIta2com257Addr8lithiumBatSOH					Integer32,
		upsIta2com258Addr8lithiumBatcellmaxvoltage					Integer32,
		upsIta2com259Addr8lithiumBatcellminvoltage					Integer32,
		upsIta2com260Addr8lithiumBatcellmaxtemp					Integer32,
		upsIta2com261Addr8lithiumBatcellmintemp					Integer32,
		upsIta2com262Addr9Batstatus					INTEGER,
		upsIta2com263Addr9lithiumBatvoltage					Integer32,
		upsIta2com264Addr9lithiumBatcurrent					Integer32,
		upsIta2com265Addr9lithiumBatSOC					Integer32,
		upsIta2com266Addr9lithiumBatSOH					Integer32,
		upsIta2com267Addr9lithiumBatcellmaxvoltage					Integer32,
		upsIta2com268Addr9lithiumBatcellminvoltage					Integer32,
		upsIta2com269Addr9lithiumBatcellmaxtemp					Integer32,
		upsIta2com270Addr9lithiumBatcellmintemp					Integer32,
		upsIta2com271Addr10Batstatus					INTEGER,
		upsIta2com272Addr10lithiumBatvoltage					Integer32,
		upsIta2com273Addr10lithiumBatcurrent					Integer32,
		upsIta2com274Addr10lithiumBatSOC					Integer32,
		upsIta2com275Addr10lithiumBatSOH					Integer32,
		upsIta2com276Addr10lithiumBatcellmaxvoltage					Integer32,
		upsIta2com277Addr10lithiumBatcellminvoltage					Integer32,
		upsIta2com278Addr10lithiumBatcellmaxtemp					Integer32,
		upsIta2com279Addr10lithiumBatcellmintemp					Integer32,
		upsIta2com280Addr11Batstatus					INTEGER,
		upsIta2com281Addr11lithiumBatvoltage					Integer32,
		upsIta2com282Addr11lithiumBatcurrent					Integer32,
		upsIta2com283Addr11lithiumBatSOC					Integer32,
		upsIta2com284Addr11lithiumBatSOH					Integer32,
		upsIta2com285Addr11lithiumBatcellmaxvoltage					Integer32,
		upsIta2com286Addr11lithiumBatcellminvoltage					Integer32,
		upsIta2com287Addr11lithiumBatcellmaxtemp					Integer32,
		upsIta2com288Addr11lithiumBatcellmintemp					Integer32,
		upsIta2com289Addr12Batstatus					INTEGER,
		upsIta2com290Addr12lithiumBatvoltage					Integer32,
		upsIta2com291Addr12lithiumBatcurrent					Integer32,
		upsIta2com292Addr12lithiumBatSOC					Integer32,
		upsIta2com293Addr12lithiumBatSOH					Integer32,
		upsIta2com294Addr12lithiumBatcellmaxvoltage					Integer32,
		upsIta2com295Addr12lithiumBatcellminvoltage					Integer32,
		upsIta2com296Addr12lithiumBatcellmaxtemp					Integer32,
		upsIta2com297Addr12lithiumBatcellmintemp					Integer32,
		upsIta2com298Addr13Batstatus					INTEGER,
		upsIta2com299Addr13lithiumBatvoltage					Integer32,
		upsIta2com300Addr13lithiumBatcurrent					Integer32,
		upsIta2com301Addr13lithiumBatSOC					Integer32,
		upsIta2com302Addr13lithiumBatSOH					Integer32,
		upsIta2com303Addr13lithiumBatcellmaxvoltage					Integer32,
		upsIta2com304Addr13lithiumBatcellminvoltage					Integer32,
		upsIta2com305Addr13lithiumBatcellmaxtemp					Integer32,
		upsIta2com306Addr13lithiumBatcellmintemp					Integer32,
		upsIta2com307Addr14Batstatus					INTEGER,
		upsIta2com308Addr14lithiumBatvoltage					Integer32,
		upsIta2com309Addr14LithiumBatCurrent					Integer32,
		upsIta2com310Addr14lithiumBatSOC					Integer32,
		upsIta2com311Addr14lithiumBatSOH					Integer32,
		upsIta2com312Addr14lithiumBatcellmaxvoltage					Integer32,
		upsIta2com313Addr14lithiumBatcellminvoltage					Integer32,
		upsIta2com314Addr14lithiumBatcellmaxtemp					Integer32,
		upsIta2com315Addr14lithiumBatcellmintemp					Integer32,
		upsIta2com316Addr15Batstatus					INTEGER,
		upsIta2com317Addr15lithiumBatvoltage					Integer32,
		upsIta2com318Addr15lithiumBatcurrent					Integer32,
		upsIta2com319Addr15lithiumBatSOC					Integer32,
		upsIta2com320Addr15lithiumBatSOH					Integer32,
		upsIta2com321Addr15lithiumBatcellmaxvoltage					Integer32,
		upsIta2com322Addr15lithiumBatcellminvoltage					Integer32,
		upsIta2com323Addr15lithiumBatcellmaxtemp					Integer32,
		upsIta2com324Addr15lithiumBatcellmintemp					Integer32,
		upsIta2com325Addr16Batstatus					INTEGER,
		upsIta2com326Addr16lithiumBatvoltage					Integer32,
		upsIta2com327Addr16lithiumBatcurrent					Integer32,
		upsIta2com328Addr16lithiumBatSOC					Integer32,
		upsIta2com329Addr16lithiumBatSOH					Integer32,
		upsIta2com330Addr16lithiumBatcellmaxvoltage					Integer32,
		upsIta2com331Addr16lithiumBatcellminvoltage					Integer32,
		upsIta2com332Addr16lithiumBatcellmaxtemp					Integer32,
		upsIta2com333Addr16lithiumBatcellmintemp					Integer32,
		upsIta2com334Addr1Batalarmnumber					Integer32,
		upsIta2com335Addr1Bathighvolt					INTEGER,
		upsIta2com336Addr1Batlowvolt					INTEGER,
		upsIta2com337Addr1Bathighcellvolt					INTEGER,
		upsIta2com338Addr1Batlowcellvolt					INTEGER,
		upsIta2com339Addr1Batchargehighcelltemp					INTEGER,
		upsIta2com340Addr1Batchargelowcelltemp					INTEGER,
		upsIta2com341Addr1Batchargeovercurrent					INTEGER,
		upsIta2com342Addr1Batdischargeovercurrent					INTEGER,
		upsIta2com343Addr1BatAddrconflict					INTEGER,
		upsIta2com344Addr1Batportreverse					INTEGER,
		upsIta2com345Addr1BatBMSrelayinvalid					INTEGER,
		upsIta2com346Addr1Batsafetyundervoltage					INTEGER,
		upsIta2com347Addr1Batdischargehighcelltemp					INTEGER,
		upsIta2com348Addr1Batdischargelowcelltemp					INTEGER,
		upsIta2com349Addr1Batparallelchargehightemp					INTEGER,
		upsIta2com350Addr1BatinternalCommabnormal					INTEGER,
		upsIta2com351Addr1Batconditionfail					INTEGER,
		upsIta2com352Addr1BatLowinsulationresistance					INTEGER,
		upsIta2com353Addr1BatLargepressurediff					INTEGER,
		upsIta2com354Addr1BatBatfailure					INTEGER,
		upsIta2com355Addr1BatVoltageacquisitfailure					INTEGER,
		upsIta2com356Addr1BatCurrentcolllectfailure					INTEGER,
		upsIta2com357Addr1BatTempcolllectfailure					INTEGER,
		upsIta2com358Addr1BatAddrSeterror					INTEGER,
		upsIta2com359Addr1BatLargegrouppressurediff					INTEGER,
		upsIta2com360Addr1BatMOSFETfailure					INTEGER,
		upsIta2com361Addr1Battempabnormal					INTEGER,
		upsIta2com362Addr1Batcablefault					INTEGER,
		upsIta2com363Addr1BatShortcircuit					INTEGER,
		upsIta2com364Addr1BatOtherfailures					INTEGER,
		upsIta2com365Addr1BatCommcablefailure					INTEGER,
		upsIta2com366Addr1BatMOSFETtempishigh					INTEGER,
		upsIta2com367Addr1BatFuseblown					INTEGER,
		upsIta2com368Addr1BatWaitingforcharging					INTEGER,
		upsIta2com369Addr1BatBataging					INTEGER,
		upsIta2com370Addr1Batboxconnectabnormal					INTEGER,
		upsIta2com371Addr1batBatterySoftincompatible					INTEGER,
		upsIta2com372Addr1batEOL					INTEGER,
		upsIta2com373Addr1batSamplingfailure					INTEGER,
		upsIta2com374Addr1batHardwareprotection					INTEGER,
		upsIta2com375Addr1batBatterycapacitylow					INTEGER,
		upsIta2com376Addr2Batalarmnumber					Integer32,
		upsIta2com377Addr2Bathighvolt					INTEGER,
		upsIta2com378Addr2Batlowvolt					INTEGER,
		upsIta2com379Addr2Bathighcellvolt					INTEGER,
		upsIta2com380Addr2Batlowcellvolt					INTEGER,
		upsIta2com381Addr2Batchargehighcelltemp					INTEGER,
		upsIta2com382Addr2Batchargelowcelltemp					INTEGER,
		upsIta2com383Addr2Batchargeovercurrent					INTEGER,
		upsIta2com384Addr2Batdischargeovercurrent					INTEGER,
		upsIta2com385Addr2BatAddrconflict					INTEGER,
		upsIta2com386Addr2Batportreverse					INTEGER,
		upsIta2com387Addr2BatBMSrelayinvalid					INTEGER,
		upsIta2com388Addr2Batsafetyundervoltage					INTEGER,
		upsIta2com389Addr2Batdischargehighcelltemp					INTEGER,
		upsIta2com390Addr2Batdischargelowcelltemp					INTEGER,
		upsIta2com391Addr2Batparallelchargehightemp					INTEGER,
		upsIta2com392Addr2BatinternalCommabnormal					INTEGER,
		upsIta2com393Addr2Batconditionfail					INTEGER,
		upsIta2com394Addr2BatLowinsulationresistance					INTEGER,
		upsIta2com395Addr2BatLargepressurediff					INTEGER,
		upsIta2com396Addr2BatBatfailure					INTEGER,
		upsIta2com397Addr2BatVoltageacquisitfailure					INTEGER,
		upsIta2com398Addr2BatCurrentcolllectfailure					INTEGER,
		upsIta2com399Addr2BatTempcolllectfailure					INTEGER,
		upsIta2com400Addr2BatAddrSeterror					INTEGER,
		upsIta2com401Addr2BatLargegrouppressurediff					INTEGER,
		upsIta2com402Addr2BatMOSFETfailure					INTEGER,
		upsIta2com403Addr2Battempabnormal					INTEGER,
		upsIta2com404Addr2Batcablefault					INTEGER,
		upsIta2com405Addr2BatShortcircuit					INTEGER,
		upsIta2com406Addr2BatOtherfailures					INTEGER,
		upsIta2com407Addr2BatCommcablefailure					INTEGER,
		upsIta2com408Addr2BatMOSFETtempishigh					INTEGER,
		upsIta2com409Addr2BatFuseblown					INTEGER,
		upsIta2com410Addr2BatWaitingforcharging					INTEGER,
		upsIta2com411Addr2BatBataging					INTEGER,
		upsIta2com412Addr2Batboxconnectabnormal					INTEGER,
		upsIta2com413Addr2batBatterySoftincompatible					INTEGER,
		upsIta2com414Addr2batEOL					INTEGER,
		upsIta2com415Addr2batSamplingfailure					INTEGER,
		upsIta2com416Addr2batHardwareprotection					INTEGER,
		upsIta2com417Addr2batBatterycapacitylow					INTEGER,
		upsIta2com418Addr3Batalarmnumber					Integer32,
		upsIta2com419Addr3Bathighvolt					INTEGER,
		upsIta2com420Addr3Batlowvolt					INTEGER,
		upsIta2com421Addr3Bathighcellvolt					INTEGER,
		upsIta2com422Addr3Batlowcellvolt					INTEGER,
		upsIta2com423Addr3Batchargehighcelltemp					INTEGER,
		upsIta2com424Addr3Batchargelowcelltemp					INTEGER,
		upsIta2com425Addr3Batchargeovercurrent					INTEGER,
		upsIta2com426Addr3Batdischargeovercurrent					INTEGER,
		upsIta2com427Addr3BatAddrconflict					INTEGER,
		upsIta2com428Addr3Batportreverse					INTEGER,
		upsIta2com429Addr3BatBMSrelayinvalid					INTEGER,
		upsIta2com430Addr3Batsafetyundervoltage					INTEGER,
		upsIta2com431Addr3Batdischargehighcelltemp					INTEGER,
		upsIta2com432Addr3Batdischargelowcelltemp					INTEGER,
		upsIta2com433Addr3Batparallelchargehightemp					INTEGER,
		upsIta2com434Addr3BatinternalCommabnormal					INTEGER,
		upsIta2com435Addr3Batconditionfail					INTEGER,
		upsIta2com436Addr3BatLowinsulationresistance					INTEGER,
		upsIta2com437Addr3BatLargepressurediff					INTEGER,
		upsIta2com438Addr3BatBatfailure					INTEGER,
		upsIta2com439Addr3BatVoltageacquisitfailure					INTEGER,
		upsIta2com440Addr3BatCurrentcolllectfailure					INTEGER,
		upsIta2com441Addr3BatTempcolllectfailure					INTEGER,
		upsIta2com442Addr3BatAddrSeterror					INTEGER,
		upsIta2com443Addr3BatLargegrouppressurediff					INTEGER,
		upsIta2com444Addr3BatMOSFETfailure					INTEGER,
		upsIta2com445Addr3Battempabnormal					INTEGER,
		upsIta2com446Addr3Batcablefault					INTEGER,
		upsIta2com447Addr3BatShortcircuit					INTEGER,
		upsIta2com448Addr3BatOtherfailures					INTEGER,
		upsIta2com449Addr3BatCommcablefailure					INTEGER,
		upsIta2com450Addr3BatMOSFETtempishigh					INTEGER,
		upsIta2com451Addr3BatFuseblown					INTEGER,
		upsIta2com452Addr3BatWaitingforcharging					INTEGER,
		upsIta2com453Addr3BatBataging					INTEGER,
		upsIta2com454Addr3Batboxconnectabnormal					INTEGER,
		upsIta2com455Addr3batBatterySoftincompatible					INTEGER,
		upsIta2com456Addr3batEOL					INTEGER,
		upsIta2com457Addr3batSamplingfailure					INTEGER,
		upsIta2com458Addr3batHardwareprotection					INTEGER,
		upsIta2com459Addr3batBatterycapacitylow					INTEGER,
		upsIta2com460Addr4Batalarmnumber					Integer32,
		upsIta2com461Addr4Bathighvolt					INTEGER,
		upsIta2com462Addr4Batlowvolt					INTEGER,
		upsIta2com463Addr4Bathighcellvolt					INTEGER,
		upsIta2com464Addr4Batlowcellvolt					INTEGER,
		upsIta2com465Addr4Batchargehighcelltemp					INTEGER,
		upsIta2com466Addr4Batchargelowcelltemp					INTEGER,
		upsIta2com467Addr4Batchargeovercurrent					INTEGER,
		upsIta2com468Addr4Batdischargeovercurrent					INTEGER,
		upsIta2com469Addr4BatAddrconflict					INTEGER,
		upsIta2com470Addr4Batportreverse					INTEGER,
		upsIta2com471Addr4BatBMSrelayinvalid					INTEGER,
		upsIta2com472Addr4Batsafetyundervoltage					INTEGER,
		upsIta2com473Addr4Batdischargehighcelltemp					INTEGER,
		upsIta2com474Addr4Batdischargelowcelltemp					INTEGER,
		upsIta2com475Addr4Batparallelchargehightemp					INTEGER,
		upsIta2com476Addr4BatinternalCommabnormal					INTEGER,
		upsIta2com477Addr4Batconditionfail					INTEGER,
		upsIta2com478Addr4BatLowinsulationresistance					INTEGER,
		upsIta2com479Addr4BatLargepressurediff					INTEGER,
		upsIta2com480Addr4BatBatfailure					INTEGER,
		upsIta2com481Addr4BatVoltageacquisitfailure					INTEGER,
		upsIta2com482Addr4BatCurrentcolllectfailure					INTEGER,
		upsIta2com483Addr4BatTempcolllectfailure					INTEGER,
		upsIta2com484Addr4BatAddrSeterror					INTEGER,
		upsIta2com485Addr4BatLargegrouppressurediff					INTEGER,
		upsIta2com486Addr4BatMOSFETfailure					INTEGER,
		upsIta2com487Addr4Battempabnormal					INTEGER,
		upsIta2com488Addr4Batcablefault					INTEGER,
		upsIta2com489Addr4BatShortcircuit					INTEGER,
		upsIta2com490Addr4BatOtherfailures					INTEGER,
		upsIta2com491Addr4BatCommcablefailure					INTEGER,
		upsIta2com492Addr4BatMOSFETtempishigh					INTEGER,
		upsIta2com493Addr4BatFuseblown					INTEGER,
		upsIta2com494Addr4BatWaitingforcharging					INTEGER,
		upsIta2com495Addr4BatBataging					INTEGER,
		upsIta2com496Addr4Batboxconnectabnormal					INTEGER,
		upsIta2com497Addr4batBatterySoftincompatible					INTEGER,
		upsIta2com498Addr4batEOL					INTEGER,
		upsIta2com499Addr4batSamplingfailure					INTEGER,
		upsIta2com500Addr4batHardwareprotection					INTEGER,
		upsIta2com501Addr4batBatterycapacitylow					INTEGER,
		upsIta2com502Addr5Batalarmnumber					Integer32,
		upsIta2com503Addr5Bathighvolt					INTEGER,
		upsIta2com504Addr5Batlowvolt					INTEGER,
		upsIta2com505Addr5Bathighcellvolt					INTEGER,
		upsIta2com506Addr5Batlowcellvolt					INTEGER,
		upsIta2com507Addr5Batchargehighcelltemp					INTEGER,
		upsIta2com508Addr5Batchargelowcelltemp					INTEGER,
		upsIta2com509Addr5Batchargeovercurrent					INTEGER,
		upsIta2com510Addr5Batdischargeovercurrent					INTEGER,
		upsIta2com511Addr5BatAddrconflict					INTEGER,
		upsIta2com512Addr5Batportreverse					INTEGER,
		upsIta2com513Addr5BatBMSrelayinvalid					INTEGER,
		upsIta2com514Addr5Batsafetyundervoltage					INTEGER,
		upsIta2com515Addr5Batdischargehighcelltemp					INTEGER,
		upsIta2com516Addr5Batdischargelowcelltemp					INTEGER,
		upsIta2com517Addr5Batparallelchargehightemp					INTEGER,
		upsIta2com518Addr5BatinternalCommabnormal					INTEGER,
		upsIta2com519Addr5Batconditionfail					INTEGER,
		upsIta2com520Addr5BatLowinsulationresistance					INTEGER,
		upsIta2com521Addr5BatLargepressurediff					INTEGER,
		upsIta2com522Addr5BatBatfailure					INTEGER,
		upsIta2com523Addr5BatVoltageacquisitfailure					INTEGER,
		upsIta2com524Addr5BatCurrentcolllectfailure					INTEGER,
		upsIta2com525Addr5BatTempcolllectfailure					INTEGER,
		upsIta2com526Addr5BatAddrSeterror					INTEGER,
		upsIta2com527Addr5BatLargegrouppressurediff					INTEGER,
		upsIta2com528Addr5BatMOSFETfailure					INTEGER,
		upsIta2com529Addr5Battempabnormal					INTEGER,
		upsIta2com530Addr5Batcablefault					INTEGER,
		upsIta2com531Addr5BatShortcircuit					INTEGER,
		upsIta2com532Addr5BatOtherfailures					INTEGER,
		upsIta2com533Addr5BatCommcablefailure					INTEGER,
		upsIta2com534Addr5BatMOSFETtempishigh					INTEGER,
		upsIta2com535Addr5BatFuseblown					INTEGER,
		upsIta2com536Addr5BatWaitingforcharging					INTEGER,
		upsIta2com537Addr5BatBataging					INTEGER,
		upsIta2com538Addr5Batboxconnectabnormal					INTEGER,
		upsIta2com539Addr5batBatterySoftincompatible					INTEGER,
		upsIta2com540Addr5batEOL					INTEGER,
		upsIta2com541Addr5batSamplingfailure					INTEGER,
		upsIta2com542Addr5batHardwareprotection					INTEGER,
		upsIta2com543Addr5batBatterycapacitylow					INTEGER,
		upsIta2com544Addr6Batalarmnumber					Integer32,
		upsIta2com545Addr6Bathighvolt					INTEGER,
		upsIta2com546Addr6Batlowvolt					INTEGER,
		upsIta2com547Addr6Bathighcellvolt					INTEGER,
		upsIta2com548Addr6Batlowcellvolt					INTEGER,
		upsIta2com549Addr6Batchargehighcelltemp					INTEGER,
		upsIta2com550Addr6Batchargelowcelltemp					INTEGER,
		upsIta2com551Addr6Batchargeovercurrent					INTEGER,
		upsIta2com552Addr6Batdischargeovercurrent					INTEGER,
		upsIta2com553Addr6BatAddrconflict					INTEGER,
		upsIta2com554Addr6Batportreverse					INTEGER,
		upsIta2com555Addr6BatBMSrelayinvalid					INTEGER,
		upsIta2com556Addr6Batsafetyundervoltage					INTEGER,
		upsIta2com557Addr6Batdischargehighcelltemp					INTEGER,
		upsIta2com558Addr6Batdischargelowcelltemp					INTEGER,
		upsIta2com559Addr6Batparallelchargehightemp					INTEGER,
		upsIta2com560Addr6BatinternalCommabnormal					INTEGER,
		upsIta2com561Addr6Batconditionfail					INTEGER,
		upsIta2com562Addr6BatLowinsulationresistance					INTEGER,
		upsIta2com563Addr6BatLargepressurediff					INTEGER,
		upsIta2com564Addr6BatBatfailure					INTEGER,
		upsIta2com565Addr6BatVoltageacquisitfailure					INTEGER,
		upsIta2com566Addr6BatCurrentcolllectfailure					INTEGER,
		upsIta2com567Addr6BatTempcolllectfailure					INTEGER,
		upsIta2com568Addr6BatAddrSeterror					INTEGER,
		upsIta2com569Addr6BatLargegrouppressurediff					INTEGER,
		upsIta2com570Addr6BatMOSFETfailure					INTEGER,
		upsIta2com571Addr6Battempabnormal					INTEGER,
		upsIta2com572Addr6Batcablefault					INTEGER,
		upsIta2com573Addr6BatShortcircuit					INTEGER,
		upsIta2com574Addr6BatOtherfailures					INTEGER,
		upsIta2com575Addr6BatCommcablefailure					INTEGER,
		upsIta2com576Addr6BatMOSFETtempishigh					INTEGER,
		upsIta2com577Addr6BatFuseblown					INTEGER,
		upsIta2com578Addr6BatWaitingforcharging					INTEGER,
		upsIta2com579Addr6BatBataging					INTEGER,
		upsIta2com580Addr6Batboxconnectabnormal					INTEGER,
		upsIta2com581Addr6batBatterySoftincompatible					INTEGER,
		upsIta2com582Addr6batEOL					INTEGER,
		upsIta2com583Addr6batSamplingfailure					INTEGER,
		upsIta2com584Addr6batHardwareprotection					INTEGER,
		upsIta2com585Addr6batBatterycapacitylow					INTEGER,
		upsIta2com586Addr7Batalarmnumber					Integer32,
		upsIta2com587Addr7Bathighvolt					INTEGER,
		upsIta2com588Addr7Batlowvolt					INTEGER,
		upsIta2com589Addr7Bathighcellvolt					INTEGER,
		upsIta2com590Addr7Batlowcellvolt					INTEGER,
		upsIta2com591Addr7Batchargehighcelltemp					INTEGER,
		upsIta2com592Addr7Batchargelowcelltemp					INTEGER,
		upsIta2com593Addr7Batchargeovercurrent					INTEGER,
		upsIta2com594Addr7Batdischargeovercurrent					INTEGER,
		upsIta2com595Addr7BatAddrconflict					INTEGER,
		upsIta2com596Addr7Batportreverse					INTEGER,
		upsIta2com597Addr7BatBMSrelayinvalid					INTEGER,
		upsIta2com598Addr7Batsafetyundervoltage					INTEGER,
		upsIta2com599Addr7Batdischargehighcelltemp					INTEGER,
		upsIta2com600Addr7Batdischargelowcelltemp					INTEGER,
		upsIta2com601Addr7Batparallelchargehightemp					INTEGER,
		upsIta2com602Addr7BatinternalCommabnormal					INTEGER,
		upsIta2com603Addr7Batconditionfail					INTEGER,
		upsIta2com604Addr7BatLowinsulationresistance					INTEGER,
		upsIta2com605Addr7BatLargepressurediff					INTEGER,
		upsIta2com606Addr7BatBatfailure					INTEGER,
		upsIta2com607Addr7BatVoltageacquisitfailure					INTEGER,
		upsIta2com608Addr7BatCurrentcolllectfailure					INTEGER,
		upsIta2com609Addr7BatTempcolllectfailure					INTEGER,
		upsIta2com610Addr7BatAddrSeterror					INTEGER,
		upsIta2com611Addr7BatLargegrouppressurediff					INTEGER,
		upsIta2com612Addr7BatMOSFETfailure					INTEGER,
		upsIta2com613Addr7Battempabnormal					INTEGER,
		upsIta2com614Addr7Batcablefault					INTEGER,
		upsIta2com615Addr7BatShortcircuit					INTEGER,
		upsIta2com616Addr7BatOtherfailures					INTEGER,
		upsIta2com617Addr7BatCommcablefailure					INTEGER,
		upsIta2com618Addr7BatMOSFETtempishigh					INTEGER,
		upsIta2com619Addr7BatFuseblown					INTEGER,
		upsIta2com620Addr7BatWaitingforcharging					INTEGER,
		upsIta2com621Addr7BatBataging					INTEGER,
		upsIta2com622Addr7Batboxconnectabnormal					INTEGER,
		upsIta2com623Addr7batBatterySoftincompatible					INTEGER,
		upsIta2com624Addr7batEOL					INTEGER,
		upsIta2com625Addr7batSamplingfailure					INTEGER,
		upsIta2com626Addr7batHardwareprotection					INTEGER,
		upsIta2com627Addr7batBatterycapacitylow					INTEGER,
		upsIta2com628Addr8Batalarmnumber					Integer32,
		upsIta2com629Addr8Bathighvolt					INTEGER,
		upsIta2com630Addr8Batlowvolt					INTEGER,
		upsIta2com631Addr8Bathighcellvolt					INTEGER,
		upsIta2com632Addr8Batlowcellvolt					INTEGER,
		upsIta2com633Addr8Batchargehighcelltemp					INTEGER,
		upsIta2com634Addr8Batchargelowcelltemp					INTEGER,
		upsIta2com635Addr8Batchargeovercurrent					INTEGER,
		upsIta2com636Addr8Batdischargeovercurrent					INTEGER,
		upsIta2com637Addr8BatAddrconflict					INTEGER,
		upsIta2com638Addr8Batportreverse					INTEGER,
		upsIta2com639Addr8BatBMSrelayinvalid					INTEGER,
		upsIta2com640Addr8Batsafetyundervoltage					INTEGER,
		upsIta2com641Addr8Batdischargehighcelltemp					INTEGER,
		upsIta2com642Addr8Batdischargelowcelltemp					INTEGER,
		upsIta2com643Addr8Batparallelchargehightemp					INTEGER,
		upsIta2com644Addr8BatinternalCommabnormal					INTEGER,
		upsIta2com645Addr8Batconditionfail					INTEGER,
		upsIta2com646Addr8BatLowinsulationresistance					INTEGER,
		upsIta2com647Addr8BatLargepressurediff					INTEGER,
		upsIta2com648Addr8BatBatfailure					INTEGER,
		upsIta2com649Addr8BatVoltageacquisitfailure					INTEGER,
		upsIta2com650Addr8BatCurrentcolllectfailure					INTEGER,
		upsIta2com651Addr8BatTempcolllectfailure					INTEGER,
		upsIta2com652Addr8BatAddrSeterror					INTEGER,
		upsIta2com653Addr8BatLargegrouppressurediff					INTEGER,
		upsIta2com654Addr8BatMOSFETfailure					INTEGER,
		upsIta2com655Addr8Battempabnormal					INTEGER,
		upsIta2com656Addr8Batcablefault					INTEGER,
		upsIta2com657Addr8BatShortcircuit					INTEGER,
		upsIta2com658Addr8BatOtherfailures					INTEGER,
		upsIta2com659Addr8BatCommcablefailure					INTEGER,
		upsIta2com660Addr8BatMOSFETtempishigh					INTEGER,
		upsIta2com661Addr8BatFuseblown					INTEGER,
		upsIta2com662Addr8BatWaitingforcharging					INTEGER,
		upsIta2com663Addr8BatBataging					INTEGER,
		upsIta2com664Addr8Batboxconnectabnormal					INTEGER,
		upsIta2com665Addr8batBatterySoftincompatible					INTEGER,
		upsIta2com666Addr8batEOL					INTEGER,
		upsIta2com667Addr8batSamplingfailure					INTEGER,
		upsIta2com668Addr8batHardwareprotection					INTEGER,
		upsIta2com669Addr8batBatterycapacitylow					INTEGER,
		upsIta2com670Addr9Batalarmnumber					Integer32,
		upsIta2com671Addr9Bathighvolt					INTEGER,
		upsIta2com672Addr9Batlowvolt					INTEGER,
		upsIta2com673Addr9Bathighcellvolt					INTEGER,
		upsIta2com674Addr9Batlowcellvolt					INTEGER,
		upsIta2com675Addr9Batchargehighcelltemp					INTEGER,
		upsIta2com676Addr9Batchargelowcelltemp					INTEGER,
		upsIta2com677Addr9Batchargeovercurrent					INTEGER,
		upsIta2com678Addr9Batdischargeovercurrent					INTEGER,
		upsIta2com679Addr9BatAddrconflict					INTEGER,
		upsIta2com680Addr9Batportreverse					INTEGER,
		upsIta2com681Addr9BatBMSrelayinvalid					INTEGER,
		upsIta2com682Addr9Batsafetyundervoltage					INTEGER,
		upsIta2com683Addr9Batdischargehighcelltemp					INTEGER,
		upsIta2com684Addr9Batdischargelowcelltemp					INTEGER,
		upsIta2com685Addr9Batparallelchargehightemp					INTEGER,
		upsIta2com686Addr9BatinternalCommabnormal					INTEGER,
		upsIta2com687Addr9Batconditionfail					INTEGER,
		upsIta2com688Addr9BatLowinsulationresistance					INTEGER,
		upsIta2com689Addr9BatLargepressurediff					INTEGER,
		upsIta2com690Addr9BatBatfailure					INTEGER,
		upsIta2com691Addr9BatVoltageacquisitfailure					INTEGER,
		upsIta2com692Addr9BatCurrentcolllectfailure					INTEGER,
		upsIta2com693Addr9BatTempcolllectfailure					INTEGER,
		upsIta2com694Addr9BatAddrSeterror					INTEGER,
		upsIta2com695Addr9BatLargegrouppressurediff					INTEGER,
		upsIta2com696Addr9BatMOSFETfailure					INTEGER,
		upsIta2com697Addr9Battempabnormal					INTEGER,
		upsIta2com698Addr9Batcablefault					INTEGER,
		upsIta2com699Addr9BatShortcircuit					INTEGER,
		upsIta2com700Addr9BatOtherfailures					INTEGER,
		upsIta2com701Addr9BatCommcablefailure					INTEGER,
		upsIta2com702Addr9BatMOSFETtempishigh					INTEGER,
		upsIta2com703Addr9BatFuseblown					INTEGER,
		upsIta2com704Addr9BatWaitingforcharging					INTEGER,
		upsIta2com705Addr9BatBataging					INTEGER,
		upsIta2com706Addr9Batboxconnectabnormal					INTEGER,
		upsIta2com707Addr9batBatterySoftincompatible					INTEGER,
		upsIta2com708Addr9batEOL					INTEGER,
		upsIta2com709Addr9batSamplingfailure					INTEGER,
		upsIta2com710Addr9batHardwareprotection					INTEGER,
		upsIta2com711Addr9batBatterycapacitylow					INTEGER,
		upsIta2com712Addr10Batalarmnumber					Integer32,
		upsIta2com713Addr10Bathighvolt					INTEGER,
		upsIta2com714Addr10Batlowvolt					INTEGER,
		upsIta2com715Addr10Bathighcellvolt					INTEGER,
		upsIta2com716Addr10Batlowcellvolt					INTEGER,
		upsIta2com717Addr10Batchargehighcelltemp					INTEGER,
		upsIta2com718Addr10Batchargelowcelltemp					INTEGER,
		upsIta2com719Addr10Batchargeovercurrent					INTEGER,
		upsIta2com720Addr10Batdischargeovercurrent					INTEGER,
		upsIta2com721Addr10BatAddrconflict					INTEGER,
		upsIta2com722Addr10Batportreverse					INTEGER,
		upsIta2com723Addr10BatBMSrelayinvalid					INTEGER,
		upsIta2com724Addr10Batsafetyundervoltage					INTEGER,
		upsIta2com725Addr10Batdischargehighcelltemp					INTEGER,
		upsIta2com726Addr10Batdischargelowcelltemp					INTEGER,
		upsIta2com727Addr10Batparallelchargehightemp					INTEGER,
		upsIta2com728Addr10BatinternalCommabnormal					INTEGER,
		upsIta2com729Addr10Batconditionfail					INTEGER,
		upsIta2com730Addr10BatLowinsulationresistanc					INTEGER,
		upsIta2com731Addr10BatLargepressurediff					INTEGER,
		upsIta2com732Addr10BatBatfailure					INTEGER,
		upsIta2com733Addr10BatVoltageacquisitfailure					INTEGER,
		upsIta2com734Addr10BatCurrentcolllectfailure					INTEGER,
		upsIta2com735Addr10BatTempcolllectfailure					INTEGER,
		upsIta2com736Addr10BatAddrSeterror					INTEGER,
		upsIta2com737Addr10BatLargegrouppressurediff					INTEGER,
		upsIta2com738Addr10BatMOSFETfailure					INTEGER,
		upsIta2com739Addr10Battempabnormal					INTEGER,
		upsIta2com740Addr10Batcablefault					INTEGER,
		upsIta2com741Addr10BatShortcircuit					INTEGER,
		upsIta2com742Addr10BatOtherfailures					INTEGER,
		upsIta2com743Addr10BatCommcablefailure					INTEGER,
		upsIta2com744Addr10BatMOSFETtempishigh					INTEGER,
		upsIta2com745Addr10BatFuseblown					INTEGER,
		upsIta2com746Addr10BatWaitingforcharging					INTEGER,
		upsIta2com747Addr10BatBataging					INTEGER,
		upsIta2com748Addr10Batboxconnectabnormal					INTEGER,
		upsIta2com749Addr10batBatterySoftincompatibl					INTEGER,
		upsIta2com750Addr10batEOL					INTEGER,
		upsIta2com751Addr10batSamplingfailure					INTEGER,
		upsIta2com752Addr10batHardwareprotection					INTEGER,
		upsIta2com753Addr10batBatterycapacitylow					INTEGER,
		upsIta2com754Addr11Batalarmnumber					Integer32,
		upsIta2com755Addr11Bathighvolt					INTEGER,
		upsIta2com756Addr11Batlowvolt					INTEGER,
		upsIta2com757Addr11Bathighcellvolt					INTEGER,
		upsIta2com758Addr11Batlowcellvolt					INTEGER,
		upsIta2com759Addr11Batchargehighcelltemp					INTEGER,
		upsIta2com760Addr11Batchargelowcelltemp					INTEGER,
		upsIta2com761Addr11Batchargeovercurrent					INTEGER,
		upsIta2com762Addr11Batdischargeovercurrent					INTEGER,
		upsIta2com763Addr11BatAddrconflict					INTEGER,
		upsIta2com764Addr11Batportreverse					INTEGER,
		upsIta2com765Addr11BatBMSrelayinvalid					INTEGER,
		upsIta2com766Addr11Batsafetyundervoltage					INTEGER,
		upsIta2com767Addr11Batdischargehighcelltemp					INTEGER,
		upsIta2com768Addr11Batdischargelowcelltemp					INTEGER,
		upsIta2com769Addr11Batparallelchargehightemp					INTEGER,
		upsIta2com770Addr11BatinternalCommabnormal					INTEGER,
		upsIta2com771Addr11Batconditionfail					INTEGER,
		upsIta2com772Addr11BatLowinsulationresistanc					INTEGER,
		upsIta2com773Addr11BatLargepressurediff					INTEGER,
		upsIta2com774Addr11BatBatfailure					INTEGER,
		upsIta2com775Addr11BatVoltageacquisitfailure					INTEGER,
		upsIta2com776Addr11BatCurrentcolllectfailure					INTEGER,
		upsIta2com777Addr11BatTempcolllectfailure					INTEGER,
		upsIta2com778Addr11BatAddrSeterror					INTEGER,
		upsIta2com779Addr11BatLargegrouppressurediff					INTEGER,
		upsIta2com780Addr11BatMOSFETfailure					INTEGER,
		upsIta2com781Addr11Battempabnormal					INTEGER,
		upsIta2com782Addr11Batcablefault					INTEGER,
		upsIta2com783Addr11BatShortcircuit					INTEGER,
		upsIta2com784Addr11BatOtherfailures					INTEGER,
		upsIta2com785Addr11BatCommcablefailure					INTEGER,
		upsIta2com786Addr11BatMOSFETtempishigh					INTEGER,
		upsIta2com787Addr11BatFuseblown					INTEGER,
		upsIta2com788Addr11BatWaitingforcharging					INTEGER,
		upsIta2com789Addr11BatBataging					INTEGER,
		upsIta2com790Addr11Batboxconnectabnormal					INTEGER,
		upsIta2com791Addr11batBatterySoftincompatibl					INTEGER,
		upsIta2com792Addr11batEOL					INTEGER,
		upsIta2com793Addr11batSamplingfailure					INTEGER,
		upsIta2com794Addr11batHardwareprotection					INTEGER,
		upsIta2com795Addr11batBatterycapacitylow					INTEGER,
		upsIta2com796Addr12Batalarmnumber					Integer32,
		upsIta2com797Addr12Bathighvolt					INTEGER,
		upsIta2com798Addr12Batlowvolt					INTEGER,
		upsIta2com799Addr12Bathighcellvolt					INTEGER,
		upsIta2com800Addr12Batlowcellvolt					INTEGER,
		upsIta2com801Addr12Batchargehighcelltemp					INTEGER,
		upsIta2com802Addr12Batchargelowcelltemp					INTEGER,
		upsIta2com803Addr12Batchargeovercurrent					INTEGER,
		upsIta2com804Addr12Batdischargeovercurrent					INTEGER,
		upsIta2com805Addr12BatAddrconflict					INTEGER,
		upsIta2com806Addr12Batportreverse					INTEGER,
		upsIta2com807Addr12BatBMSrelayinvalid					INTEGER,
		upsIta2com808Addr12Batsafetyundervoltage					INTEGER,
		upsIta2com809Addr12Batdischargehighcelltemp					INTEGER,
		upsIta2com810Addr12Batdischargelowcelltemp					INTEGER,
		upsIta2com811Addr12Batparallelchargehightemp					INTEGER,
		upsIta2com812Addr12BatinternalCommabnormal					INTEGER,
		upsIta2com813Addr12Batconditionfail					INTEGER,
		upsIta2com814Addr12BatLowinsulationresistanc					INTEGER,
		upsIta2com815Addr12BatLargepressurediff					INTEGER,
		upsIta2com816Addr12BatBatfailure					INTEGER,
		upsIta2com817Addr12BatVoltageacquisitfailure					INTEGER,
		upsIta2com818Addr12BatCurrentcolllectfailure					INTEGER,
		upsIta2com819Addr12BatTempcolllectfailure					INTEGER,
		upsIta2com820Addr12BatAddrSeterror					INTEGER,
		upsIta2com821Addr12BatLargegrouppressurediff					INTEGER,
		upsIta2com822Addr12BatMOSFETfailure					INTEGER,
		upsIta2com823Addr12Battempabnormal					INTEGER,
		upsIta2com824Addr12Batcablefault					INTEGER,
		upsIta2com825Addr12BatShortcircuit					INTEGER,
		upsIta2com826Addr12BatOtherfailures					INTEGER,
		upsIta2com827Addr12BatCommcablefailure					INTEGER,
		upsIta2com828Addr12BatMOSFETtempishigh					INTEGER,
		upsIta2com829Addr12BatFuseblown					INTEGER,
		upsIta2com830Addr12BatWaitingforcharging					INTEGER,
		upsIta2com831Addr12BatBataging					INTEGER,
		upsIta2com832Addr12Batboxconnectabnormal					INTEGER,
		upsIta2com833Addr12batBatterySoftincompatibl					INTEGER,
		upsIta2com834Addr12batEOL					INTEGER,
		upsIta2com835Addr12batSamplingfailure					INTEGER,
		upsIta2com836Addr12batHardwareprotection					INTEGER,
		upsIta2com837Addr12batBatterycapacitylow					INTEGER,
		upsIta2com838Addr13Batalarmnumber					Integer32,
		upsIta2com839Addr13Bathighvolt					INTEGER,
		upsIta2com840Addr13Batlowvolt					INTEGER,
		upsIta2com841Addr13Bathighcellvolt					INTEGER,
		upsIta2com842Addr13Batlowcellvolt					INTEGER,
		upsIta2com843Addr13Batchargehighcelltemp					INTEGER,
		upsIta2com844Addr13Batchargelowcelltemp					INTEGER,
		upsIta2com845Addr13Batchargeovercurrent					INTEGER,
		upsIta2com846Addr13Batdischargeovercurrent					INTEGER,
		upsIta2com847Addr13BatAddrconflict					INTEGER,
		upsIta2com848Addr13Batportreverse					INTEGER,
		upsIta2com849Addr13BatBMSrelayinvalid					INTEGER,
		upsIta2com850Addr13Batsafetyundervoltage					INTEGER,
		upsIta2com851Addr13Batdischargehighcelltemp					INTEGER,
		upsIta2com852Addr13Batdischargelowcelltemp					INTEGER,
		upsIta2com853Addr13Batparallelchargehightemp					INTEGER,
		upsIta2com854Addr13BatinternalCommabnormal					INTEGER,
		upsIta2com855Addr13Batconditionfail					INTEGER,
		upsIta2com856Addr13BatLowinsulationresistanc					INTEGER,
		upsIta2com857Addr13BatLargepressurediff					INTEGER,
		upsIta2com858Addr13BatBatfailure					INTEGER,
		upsIta2com859Addr13BatVoltageacquisitfailure					INTEGER,
		upsIta2com860Addr13BatCurrentcolllectfailure					INTEGER,
		upsIta2com861Addr13BatTempcolllectfailure					INTEGER,
		upsIta2com862Addr13BatAddrSeterror					INTEGER,
		upsIta2com863Addr13BatLargegrouppressurediff					INTEGER,
		upsIta2com864Addr13BatMOSFETfailure					INTEGER,
		upsIta2com865Addr13Battempabnormal					INTEGER,
		upsIta2com866Addr13Batcablefault					INTEGER,
		upsIta2com867Addr13BatShortcircuit					INTEGER,
		upsIta2com868Addr13BatOtherfailures					INTEGER,
		upsIta2com869Addr13BatCommcablefailure					INTEGER,
		upsIta2com870Addr13BatMOSFETtempishigh					INTEGER,
		upsIta2com871Addr13BatFuseblown					INTEGER,
		upsIta2com872Addr13BatWaitingforcharging					INTEGER,
		upsIta2com873Addr13BatBataging					INTEGER,
		upsIta2com874Addr13Batboxconnectabnormal					INTEGER,
		upsIta2com875Addr13batBatterySoftincompatibl					INTEGER,
		upsIta2com876Addr13batEOL					INTEGER,
		upsIta2com877Addr13batSamplingfailure					INTEGER,
		upsIta2com878Addr13batHardwareprotection					INTEGER,
		upsIta2com879Addr13batBatterycapacitylow					INTEGER,
		upsIta2com880Addr14Batalarmnumber					Integer32,
		upsIta2com881Addr14Bathighvolt					INTEGER,
		upsIta2com882Addr14Batlowvolt					INTEGER,
		upsIta2com883Addr14Bathighcellvolt					INTEGER,
		upsIta2com884Addr14Batlowcellvolt					INTEGER,
		upsIta2com885Addr14Batchargehighcelltemp					INTEGER,
		upsIta2com886Addr14Batchargelowcelltemp					INTEGER,
		upsIta2com887Addr14Batchargeovercurrent					INTEGER,
		upsIta2com888Addr14Batdischargeovercurrent					INTEGER,
		upsIta2com889Addr14BatAddrconflict					INTEGER,
		upsIta2com890Addr14Batportreverse					INTEGER,
		upsIta2com891Addr14BatBMSrelayinvalid					INTEGER,
		upsIta2com892Addr14Batsafetyundervoltage					INTEGER,
		upsIta2com893Addr14Batdischargehighcelltemp					INTEGER,
		upsIta2com894Addr14Batdischargelowcelltemp					INTEGER,
		upsIta2com895Addr14Batparallelchargehightemp					INTEGER,
		upsIta2com896Addr14BatinternalCommabnormal					INTEGER,
		upsIta2com897Addr14Batconditionfail					INTEGER,
		upsIta2com898Addr14BatLowinsulationresistanc					INTEGER,
		upsIta2com899Addr14BatLargepressurediff					INTEGER,
		upsIta2com900Addr14BatBatfailure					INTEGER,
		upsIta2com901Addr14BatVoltageacquisitfailure					INTEGER,
		upsIta2com902Addr14BatCurrentcolllectfailure					INTEGER,
		upsIta2com903Addr14BatTempcolllectfailure					INTEGER,
		upsIta2com904Addr14BatAddrSeterror					INTEGER,
		upsIta2com905Addr14BatLargegrouppressurediff					INTEGER,
		upsIta2com906Addr14BatMOSFETfailure					INTEGER,
		upsIta2com907Addr14Battempabnormal					INTEGER,
		upsIta2com908Addr14Batcablefault					INTEGER,
		upsIta2com909Addr14BatShortcircuit					INTEGER,
		upsIta2com910Addr14BatOtherfailures					INTEGER,
		upsIta2com911Addr14BatCommcablefailure					INTEGER,
		upsIta2com912Addr14BatMOSFETtempishigh					INTEGER,
		upsIta2com913Addr14BatFuseblown					INTEGER,
		upsIta2com914Addr14BatWaitingforcharging					INTEGER,
		upsIta2com915Addr14BatBataging					INTEGER,
		upsIta2com916Addr14Batboxconnectabnormal					INTEGER,
		upsIta2com917Addr14batBatterySoftincompatibl					INTEGER,
		upsIta2com918Addr14batEOL					INTEGER,
		upsIta2com919Addr14batSamplingfailure					INTEGER,
		upsIta2com920Addr14batHardwareprotection					INTEGER,
		upsIta2com921Addr14batBatterycapacitylow					INTEGER,
		upsIta2com922Addr15Batalarmnumber					Integer32,
		upsIta2com923Addr15Bathighvolt					INTEGER,
		upsIta2com924Addr15Batlowvolt					INTEGER,
		upsIta2com925Addr15Bathighcellvolt					INTEGER,
		upsIta2com926Addr15Batlowcellvolt					INTEGER,
		upsIta2com927Addr15Batchargehighcelltemp					INTEGER,
		upsIta2com928Addr15Batchargelowcelltemp					INTEGER,
		upsIta2com929Addr15Batchargeovercurrent					INTEGER,
		upsIta2com930Addr15Batdischargeovercurrent					INTEGER,
		upsIta2com931Addr15BatAddrconflict					INTEGER,
		upsIta2com932Addr15Batportreverse					INTEGER,
		upsIta2com933Addr15BatBMSrelayinvalid					INTEGER,
		upsIta2com934Addr15Batsafetyundervoltage					INTEGER,
		upsIta2com935Addr15Batdischargehighcelltemp					INTEGER,
		upsIta2com936Addr15Batdischargelowcelltemp					INTEGER,
		upsIta2com937Addr15Batparallelchargehightemp					INTEGER,
		upsIta2com938Addr15BatinternalCommabnormal					INTEGER,
		upsIta2com939Addr15Batconditionfail					INTEGER,
		upsIta2com940Addr15BatLowinsulationresistanc					INTEGER,
		upsIta2com941Addr15BatLargepressurediff					INTEGER,
		upsIta2com942Addr15BatBatfailure					INTEGER,
		upsIta2com943Addr15BatVoltageacquisitfailure					INTEGER,
		upsIta2com944Addr15BatCurrentcolllectfailure					INTEGER,
		upsIta2com945Addr15BatTempcolllectfailure					INTEGER,
		upsIta2com946Addr15BatAddrSeterror					INTEGER,
		upsIta2com947Addr15BatLargegrouppressurediff					INTEGER,
		upsIta2com948Addr15BatMOSFETfailure					INTEGER,
		upsIta2com949Addr15Battempabnormal					INTEGER,
		upsIta2com950Addr15Batcablefault					INTEGER,
		upsIta2com951Addr15BatShortcircuit					INTEGER,
		upsIta2com952Addr15BatOtherfailures					INTEGER,
		upsIta2com953Addr15BatCommcablefailure					INTEGER,
		upsIta2com954Addr15BatMOSFETtempishigh					INTEGER,
		upsIta2com955Addr15BatFuseblown					INTEGER,
		upsIta2com956Addr15BatWaitingforcharging					INTEGER,
		upsIta2com957Addr15BatBataging					INTEGER,
		upsIta2com958Addr15Batboxconnectabnormal					INTEGER,
		upsIta2com959Addr15batBatterySoftincompatibl					INTEGER,
		upsIta2com960Addr15batEOL					INTEGER,
		upsIta2com961Addr15batSamplingfailure					INTEGER,
		upsIta2com962Addr15batHardwareprotection					INTEGER,
		upsIta2com963Addr15batBatterycapacitylow					INTEGER,
		upsIta2com964Addr16Batalarmnumber					Integer32,
		upsIta2com965Addr16Bathighvolt					INTEGER,
		upsIta2com966Addr16Batlowvolt					INTEGER,
		upsIta2com967Addr16Bathighcellvolt					INTEGER,
		upsIta2com968Addr16Batlowcellvolt					INTEGER,
		upsIta2com969Addr16Batchargehighcelltemp					INTEGER,
		upsIta2com970Addr16Batchargelowcelltemp					INTEGER,
		upsIta2com971Addr16Batchargeovercurrent					INTEGER,
		upsIta2com972Addr16Batdischargeovercurrent					INTEGER,
		upsIta2com973Addr16BatAddrconflict					INTEGER,
		upsIta2com974Addr16Batportreverse					INTEGER,
		upsIta2com975Addr16BatBMSrelayinvalid					INTEGER,
		upsIta2com976Addr16Batsafetyundervoltage					INTEGER,
		upsIta2com977Addr16Batdischargehighcelltemp					INTEGER,
		upsIta2com978Addr16Batdischargelowcelltemp					INTEGER,
		upsIta2com979Addr16Batparallelchargehightemp					INTEGER,
		upsIta2com980Addr16BatinternalCommabnormal					INTEGER,
		upsIta2com981Addr16Batconditionfail					INTEGER,
		upsIta2com982Addr16BatLowinsulationresistanc					INTEGER,
		upsIta2com983Addr16BatLargepressurediff					INTEGER,
		upsIta2com984Addr16BatBatfailure					INTEGER,
		upsIta2com985Addr16BatVoltageacquisitfailure					INTEGER,
		upsIta2com986Addr16BatCurrentcolllectfailure					INTEGER,
		upsIta2com987Addr16BatTempcolllectfailure					INTEGER,
		upsIta2com988Addr16BatAddrSeterror					INTEGER,
		upsIta2com989Addr16BatLargegrouppressurediff					INTEGER,
		upsIta2com990Addr16BatMOSFETfailure					INTEGER,
		upsIta2com991Addr16Battempabnormal					INTEGER,
		upsIta2com992Addr16Batcablefault					INTEGER,
		upsIta2com993Addr16BatShortcircuit					INTEGER,
		upsIta2com994Addr16BatOtherfailures					INTEGER,
		upsIta2com995Addr16BatCommcablefailure					INTEGER,
		upsIta2com996Addr16BatMOSFETtempishigh					INTEGER,
		upsIta2com997Addr16BatFuseblown					INTEGER,
		upsIta2com998Addr16BatWaitingforcharging					INTEGER,
		upsIta2com999Addr16BatBataging					INTEGER,
		upsIta2com1000Addr16Batboxconnectabnormal					INTEGER,
		upsIta2com1001Addr16batBatterySoftincompatibl					INTEGER,
		upsIta2com1002Addr16batEOL					INTEGER,
		upsIta2com1003Addr16batSamplingfailure					INTEGER,
		upsIta2com1004Addr16batHardwareprotection					INTEGER,
		upsIta2com1005Addr16batBatterycapacitylow					INTEGER,
		upsIta2com1006Addr1Batcuralarmnumber					Integer32,
		upsIta2com1007Addr2Batcuralarmnumber					Integer32,
		upsIta2com1008Addr3Batcuralarmnumber					Integer32,
		upsIta2com1009Addr4Batcuralarmnumber					Integer32,
		upsIta2com1010Addr5Batcuralarmnumber					Integer32,
		upsIta2com1011Addr6Batcuralarmnumber					Integer32,
		upsIta2com1012Addr7Batcuralarmnumber					Integer32,
		upsIta2com1013Addr8Batcuralarmnumber					Integer32,
		upsIta2com1014Addr9Batcuralarmnumber					Integer32,
		upsIta2com1015Addr10Batcuralarmnumber					Integer32,
		upsIta2com1016Addr11Batcuralarmnumber					Integer32,
		upsIta2com1017Addr12Batcuralarmnumber					Integer32,
		upsIta2com1018Addr13Batcuralarmnumber					Integer32,
		upsIta2com1019Addr14Batcuralarmnumber					Integer32,
		upsIta2com1020Addr15Batcuralarmnumber					Integer32,
		upsIta2com1021Addr16Batcuralarmnumber					Integer32,
		upsIta2com1022StanderBatteryStatus					INTEGER,
		upsIta2com1023Commtatus					INTEGER,
		upsIta2com1024RemoteBatSelftest					INTEGER,
		upsIta2com1025BatSelfTestCommand					INTEGER,
		upsIta2com1026TurnOffUpsOutput					INTEGER,
		upsIta2com1027TurnOnUpsInstantly					INTEGER,
		upsIta2com1028TurnOffUpsInstantly					INTEGER,
		upsIta2com1029SetTime					INTEGER,
		upsIta2com1030OpenInverterWithDelay					INTEGER,
		upsIta2com1031CloseOutputWithDelay					INTEGER,
		upsIta2com1032DelayedShutdownCancellation					INTEGER,
		upsIta2com1033ForcedtowakeuplithiumBat					INTEGER,
		upsIta2com1034DelayTimeOfSelfStart					Integer32,
		upsIta2com1035DelayTimeOfRemoteShutDown					Integer32,
		upsIta2com1036IntervalOfBatSelfTest					INTEGER,
		upsIta2com1037UpsWorkingMode					INTEGER,
		upsIta2com1038SelfStartSet					INTEGER,
		upsIta2com1039SetsRedundance					INTEGER,
		upsIta2com1040RemoteOpenDelayTime					Integer32,
		upsIta2com1041LogNumberSet					Integer32 }
upsIta2comIndex OBJECT-TYPE
		SYNTAX Integer32(1..1041)
		MAX-ACCESS read-only
		STATUS current
		DESCRIPTION
		"upsIta2com System Entry Index."
		::= { upsIta2comEntry 1 }
upsIta2com2PhaseAInputVoltage OBJECT-TYPE
		SYNTAX Integer32
		
		MAX-ACCESS read-only
		STATUS current
		DESCRIPTION
		"upsIta2com1PhaseAInputVoltage stored as 0.1V."
		::= { upsIta2comEntry 2 }
upsIta2com3PhaseBInputVoltage OBJECT-TYPE
		SYNTAX Integer32
		
		MAX-ACCESS read-only
		STATUS current
		DESCRIPTION
		"upsIta2com2PhaseBInputVoltage stored as 0.1V."
		::= { upsIta2comEntry 3 }
upsIta2com4PhaseCInputVoltage OBJECT-TYPE
		SYNTAX Integer32
		
		MAX-ACCESS read-only
		STATUS current
		DESCRIPTION
		"upsIta2com3PhaseCInputVoltage stored as 0.1V."
		::= { upsIta2comEntry 4 }
upsIta2com5PhaseAOutputVoltage OBJECT-TYPE
		SYNTAX Integer32
		
		MAX-ACCESS read-only
		STATUS current
		DESCRIPTION
		"upsIta2com4PhaseAOutputVoltage stored as 0.1V."
		::= { upsIta2comEntry 5 }
upsIta2com6PhaseBOutputVoltage OBJECT-TYPE
		SYNTAX Integer32
		
		MAX-ACCESS read-only
		STATUS current
		DESCRIPTION
		"upsIta2com5PhaseBOutputVoltage stored as 0.1V."
		::= { upsIta2comEntry 6 }
upsIta2com7PhaseCOutputVoltage OBJECT-TYPE
		SYNTAX Integer32
		
		MAX-ACCESS read-only
		STATUS current
		DESCRIPTION
		"upsIta2com6PhaseCOutputVoltage stored as 0.1V."
		::= { upsIta2comEntry 7 }
upsIta2com8PhaseAOutputCurrent OBJECT-TYPE
		SYNTAX Integer32
		
		MAX-ACCESS read-only
		STATUS current
		DESCRIPTION
		"upsIta2com7PhaseAOutputCurrent stored as 0.1A."
		::= { upsIta2comEntry 8 }
upsIta2com9PhaseBOutputCurrent OBJECT-TYPE
		SYNTAX Integer32
		
		MAX-ACCESS read-only
		STATUS current
		DESCRIPTION
		"upsIta2com8PhaseBOutputCurrent stored as 0.1A."
		::= { upsIta2comEntry 9 }
upsIta2com10PhaseCOutputCurrent OBJECT-TYPE
		SYNTAX Integer32
		
		MAX-ACCESS read-only
		STATUS current
		DESCRIPTION
		"upsIta2com9PhaseCOutputCurrent stored as 0.1A."
		::= { upsIta2comEntry 10 }
upsIta2com11OutputFrequency OBJECT-TYPE
		SYNTAX Integer32
		
		MAX-ACCESS read-only
		STATUS current
		DESCRIPTION
		"upsIta2com10OutputFrequency stored as 0.1Hz."
		::= { upsIta2comEntry 11 }
upsIta2com12InputPhaseNumber OBJECT-TYPE
		SYNTAX INTEGER {
			unknown(0),
			simplex(1),
			duplex(2),
			threephase(3) }
		MAX-ACCESS read-only
		STATUS current
		DESCRIPTION
		"upsIta2com11InputPhaseNumber status."
		::= { upsIta2comEntry 12 }
upsIta2com13LineAbInputVoltage OBJECT-TYPE
		SYNTAX Integer32
		
		MAX-ACCESS read-only
		STATUS current
		DESCRIPTION
		"upsIta2com12LineAbInputVoltage stored as 0.1V."
		::= { upsIta2comEntry 13 }
upsIta2com14LineBcInputVoltage OBJECT-TYPE
		SYNTAX Integer32
		
		MAX-ACCESS read-only
		STATUS current
		DESCRIPTION
		"upsIta2com13LineBcInputVoltage stored as 0.1V."
		::= { upsIta2comEntry 14 }
upsIta2com15LineCaInputVoltage OBJECT-TYPE
		SYNTAX Integer32
		
		MAX-ACCESS read-only
		STATUS current
		DESCRIPTION
		"upsIta2com14LineCaInputVoltage stored as 0.1V."
		::= { upsIta2comEntry 15 }
upsIta2com16PhaseAInputCurrent OBJECT-TYPE
		SYNTAX Integer32
		
		MAX-ACCESS read-only
		STATUS current
		DESCRIPTION
		"upsIta2com15PhaseAInputCurrent stored as 0.1A."
		::= { upsIta2comEntry 16 }
upsIta2com17PhaseBInputCurrent OBJECT-TYPE
		SYNTAX Integer32
		
		MAX-ACCESS read-only
		STATUS current
		DESCRIPTION
		"upsIta2com16PhaseBInputCurrent stored as 0.1A."
		::= { upsIta2comEntry 17 }
upsIta2com18PhaseCInputCurrent OBJECT-TYPE
		SYNTAX Integer32
		
		MAX-ACCESS read-only
		STATUS current
		DESCRIPTION
		"upsIta2com17PhaseCInputCurrent stored as 0.1A."
		::= { upsIta2comEntry 18 }
upsIta2com19SystemInputFrequency OBJECT-TYPE
		SYNTAX Integer32
		
		MAX-ACCESS read-only
		STATUS current
		DESCRIPTION
		"upsIta2com18SystemInputFrequency stored as 0.1Hz."
		::= { upsIta2comEntry 19 }
upsIta2com20PhaseAInputPowerFactor OBJECT-TYPE
		SYNTAX Integer32
		
		MAX-ACCESS read-only
		STATUS current
		DESCRIPTION
		"upsIta2com19PhaseAInputPowerFactor stored as 0.1."
		::= { upsIta2comEntry 20 }
upsIta2com21PhaseBInputPowerFactor OBJECT-TYPE
		SYNTAX Integer32
		
		MAX-ACCESS read-only
		STATUS current
		DESCRIPTION
		"upsIta2com20PhaseBInputPowerFactor stored as 0.1."
		::= { upsIta2comEntry 21 }
upsIta2com22PhaseCInputPowerFactor OBJECT-TYPE
		SYNTAX Integer32
		
		MAX-ACCESS read-only
		STATUS current
		DESCRIPTION
		"upsIta2com21PhaseCInputPowerFactor stored as 0.1."
		::= { upsIta2comEntry 22 }
upsIta2com23BypassAVoltageA OBJECT-TYPE
		SYNTAX Integer32
		
		MAX-ACCESS read-only
		STATUS current
		DESCRIPTION
		"upsIta2com22BypassAVoltageA stored as 0.1V."
		::= { upsIta2comEntry 23 }
upsIta2com24BypassBVoltageB OBJECT-TYPE
		SYNTAX Integer32
		
		MAX-ACCESS read-only
		STATUS current
		DESCRIPTION
		"upsIta2com23BypassBVoltageB stored as 0.1V."
		::= { upsIta2comEntry 24 }
upsIta2com25BypassCVoltageC OBJECT-TYPE
		SYNTAX Integer32
		
		MAX-ACCESS read-only
		STATUS current
		DESCRIPTION
		"upsIta2com24BypassCVoltageC stored as 0.1V."
		::= { upsIta2comEntry 25 }
upsIta2com26BypassLineAbVoltage OBJECT-TYPE
		SYNTAX Integer32
		
		MAX-ACCESS read-only
		STATUS current
		DESCRIPTION
		"upsIta2com25BypassLineAbVoltage stored as 0.1V."
		::= { upsIta2comEntry 26 }
upsIta2com27BypassLineBcVoltage OBJECT-TYPE
		SYNTAX Integer32
		
		MAX-ACCESS read-only
		STATUS current
		DESCRIPTION
		"upsIta2com26BypassLineBcVoltage stored as 0.1V."
		::= { upsIta2comEntry 27 }
upsIta2com28BypassLineCaVoltage OBJECT-TYPE
		SYNTAX Integer32
		
		MAX-ACCESS read-only
		STATUS current
		DESCRIPTION
		"upsIta2com27BypassLineCaVoltage stored as 0.1V."
		::= { upsIta2comEntry 28 }
upsIta2com29BypassFrequency OBJECT-TYPE
		SYNTAX Integer32
		
		MAX-ACCESS read-only
		STATUS current
		DESCRIPTION
		"upsIta2com28BypassFrequency stored as 0.1Hz."
		::= { upsIta2comEntry 29 }
upsIta2com30BusvoltageP OBJECT-TYPE
		SYNTAX Integer32
		
		MAX-ACCESS read-only
		STATUS current
		DESCRIPTION
		"upsIta2com29BusvoltageP stored as 0.1V."
		::= { upsIta2comEntry 30 }
upsIta2com31BusvoltageN OBJECT-TYPE
		SYNTAX Integer32
		
		MAX-ACCESS read-only
		STATUS current
		DESCRIPTION
		"upsIta2com30BusvoltageN stored as 0.1V."
		::= { upsIta2comEntry 31 }
upsIta2com32OutputPhaseNumber OBJECT-TYPE
		SYNTAX INTEGER {
			unknown(0),
			simplex(1),
			duplex(2),
			threephase(3) }
		MAX-ACCESS read-only
		STATUS current
		DESCRIPTION
		"upsIta2com31OutputPhaseNumber status."
		::= { upsIta2comEntry 32 }
upsIta2com33PhaseAOutputPowerFactor OBJECT-TYPE
		SYNTAX Integer32
		
		MAX-ACCESS read-only
		STATUS current
		DESCRIPTION
		"upsIta2com32PhaseAOutputPowerFactor stored as 0.1."
		::= { upsIta2comEntry 33 }
upsIta2com34PhaseBOutputPowerFactor OBJECT-TYPE
		SYNTAX Integer32
		
		MAX-ACCESS read-only
		STATUS current
		DESCRIPTION
		"upsIta2com33PhaseBOutputPowerFactor stored as 0.1."
		::= { upsIta2comEntry 34 }
upsIta2com35PhaseCOutputPowerFactor OBJECT-TYPE
		SYNTAX Integer32
		
		MAX-ACCESS read-only
		STATUS current
		DESCRIPTION
		"upsIta2com34PhaseCOutputPowerFactor stored as 0.1."
		::= { upsIta2comEntry 35 }
upsIta2com36LPhaseAOutputPeakRatio OBJECT-TYPE
		SYNTAX Integer32
		
		MAX-ACCESS read-only
		STATUS current
		DESCRIPTION
		"upsIta2com35LPhaseAOutputPeakRatio stored as 0.1."
		::= { upsIta2comEntry 36 }
upsIta2com37LPhaseBOutputPeakRatio OBJECT-TYPE
		SYNTAX Integer32
		
		MAX-ACCESS read-only
		STATUS current
		DESCRIPTION
		"upsIta2com36LPhaseBOutputPeakRatio stored as 0.1."
		::= { upsIta2comEntry 37 }
upsIta2com38LPhaseCOutputPeakRatio OBJECT-TYPE
		SYNTAX Integer32
		
		MAX-ACCESS read-only
		STATUS current
		DESCRIPTION
		"upsIta2com37LPhaseCOutputPeakRatio stored as 0.1."
		::= { upsIta2comEntry 38 }
upsIta2com39LPhaseAOutputActivePower OBJECT-TYPE
		SYNTAX Integer32
		
		MAX-ACCESS read-only
		STATUS current
		DESCRIPTION
		"upsIta2com38LPhaseAOutputActivePower stored as 0.1kW."
		::= { upsIta2comEntry 39 }
upsIta2com40LPhaseBOutputActivePower OBJECT-TYPE
		SYNTAX Integer32
		
		MAX-ACCESS read-only
		STATUS current
		DESCRIPTION
		"upsIta2com39LPhaseBOutputActivePower stored as 0.1kW."
		::= { upsIta2comEntry 40 }
upsIta2com41LPhaseCOutputActivePower OBJECT-TYPE
		SYNTAX Integer32
		
		MAX-ACCESS read-only
		STATUS current
		DESCRIPTION
		"upsIta2com40LPhaseCOutputActivePower stored as 0.1kW."
		::= { upsIta2comEntry 41 }
upsIta2com42LPhaseAOutputApparentPower OBJECT-TYPE
		SYNTAX Integer32
		
		MAX-ACCESS read-only
		STATUS current
		DESCRIPTION
		"upsIta2com41LPhaseAOutputApparentPower stored as 0.1kVA."
		::= { upsIta2comEntry 42 }
upsIta2com43LPhaseBOutputApparentPower OBJECT-TYPE
		SYNTAX Integer32
		
		MAX-ACCESS read-only
		STATUS current
		DESCRIPTION
		"upsIta2com42LPhaseBOutputApparentPower stored as 0.1kVA."
		::= { upsIta2comEntry 43 }
upsIta2com44LPhaseCOutputApparentPower OBJECT-TYPE
		SYNTAX Integer32
		
		MAX-ACCESS read-only
		STATUS current
		DESCRIPTION
		"upsIta2com43LPhaseCOutputApparentPower stored as 0.1kVA."
		::= { upsIta2comEntry 44 }
upsIta2com45LPhaseAOutputLoadPercent OBJECT-TYPE
		SYNTAX Integer32
		
		MAX-ACCESS read-only
		STATUS current
		DESCRIPTION
		"upsIta2com44LPhaseAOutputLoadPercent stored as 0.1%."
		::= { upsIta2comEntry 45 }
upsIta2com46LPhaseBOutputLoadPercent OBJECT-TYPE
		SYNTAX Integer32
		
		MAX-ACCESS read-only
		STATUS current
		DESCRIPTION
		"upsIta2com45LPhaseBOutputLoadPercent stored as 0.1%."
		::= { upsIta2comEntry 46 }
upsIta2com47LPhaseCOutputLoadPercent OBJECT-TYPE
		SYNTAX Integer32
		
		MAX-ACCESS read-only
		STATUS current
		DESCRIPTION
		"upsIta2com46LPhaseCOutputLoadPercent stored as 0.1%."
		::= { upsIta2comEntry 47 }
upsIta2com48SPhaseAOutputPowerFactor OBJECT-TYPE
		SYNTAX Integer32
		
		MAX-ACCESS read-only
		STATUS current
		DESCRIPTION
		"upsIta2com47SPhaseAOutputPowerFactor stored as 0.1."
		::= { upsIta2comEntry 48 }
upsIta2com49SPhaseBOutputPowerFactor OBJECT-TYPE
		SYNTAX Integer32
		
		MAX-ACCESS read-only
		STATUS current
		DESCRIPTION
		"upsIta2com48SPhaseBOutputPowerFactor stored as 0.1."
		::= { upsIta2comEntry 49 }
upsIta2com50SPhaseCOutputPowerFactor OBJECT-TYPE
		SYNTAX Integer32
		
		MAX-ACCESS read-only
		STATUS current
		DESCRIPTION
		"upsIta2com49SPhaseCOutputPowerFactor stored as 0.1."
		::= { upsIta2comEntry 50 }
upsIta2com51SPhaseAOutputActivePower OBJECT-TYPE
		SYNTAX Integer32
		
		MAX-ACCESS read-only
		STATUS current
		DESCRIPTION
		"upsIta2com50SPhaseAOutputActivePower stored as 0.1kW."
		::= { upsIta2comEntry 51 }
upsIta2com52SPhaseBOutputActivePower OBJECT-TYPE
		SYNTAX Integer32
		
		MAX-ACCESS read-only
		STATUS current
		DESCRIPTION
		"upsIta2com51SPhaseBOutputActivePower stored as 0.1kW."
		::= { upsIta2comEntry 52 }
upsIta2com53SPhaseCOutputActivePower OBJECT-TYPE
		SYNTAX Integer32
		
		MAX-ACCESS read-only
		STATUS current
		DESCRIPTION
		"upsIta2com52SPhaseCOutputActivePower stored as 0.1kW."
		::= { upsIta2comEntry 53 }
upsIta2com54SPhaseAOutputApparentPower OBJECT-TYPE
		SYNTAX Integer32
		
		MAX-ACCESS read-only
		STATUS current
		DESCRIPTION
		"upsIta2com53SPhaseAOutputApparentPower stored as 0.1kVA."
		::= { upsIta2comEntry 54 }
upsIta2com55SPhaseBOutputApparentPower OBJECT-TYPE
		SYNTAX Integer32
		
		MAX-ACCESS read-only
		STATUS current
		DESCRIPTION
		"upsIta2com54SPhaseBOutputApparentPower stored as 0.1kVA."
		::= { upsIta2comEntry 55 }
upsIta2com56SPhaseCOutputApparentPower OBJECT-TYPE
		SYNTAX Integer32
		
		MAX-ACCESS read-only
		STATUS current
		DESCRIPTION
		"upsIta2com55SPhaseCOutputApparentPower stored as 0.1kVA."
		::= { upsIta2comEntry 56 }
upsIta2com57ParallelMachineNumber OBJECT-TYPE
		SYNTAX Integer32
		
		MAX-ACCESS read-only
		STATUS current
		DESCRIPTION
		"upsIta2com56ParallelMachineNumber stored as 0.1."
		::= { upsIta2comEntry 57 }
upsIta2com58UpsRunningTime OBJECT-TYPE
		SYNTAX Integer32
		
		MAX-ACCESS read-only
		STATUS current
		DESCRIPTION
		"upsIta2com57UpsRunningTime stored as 0.1Day."
		::= { upsIta2comEntry 58 }
upsIta2com59BatVoltage OBJECT-TYPE
		SYNTAX Integer32
		
		MAX-ACCESS read-only
		STATUS current
		DESCRIPTION
		"upsIta2com58BatVoltage stored as 0.1V."
		::= { upsIta2comEntry 59 }
upsIta2com60BatChargingCurrent OBJECT-TYPE
		SYNTAX Integer32
		
		MAX-ACCESS read-only
		STATUS current
		DESCRIPTION
		"upsIta2com59BatChargingCurrent stored as 0.1A."
		::= { upsIta2comEntry 60 }
upsIta2com61BatDischargeCurrent OBJECT-TYPE
		SYNTAX Integer32
		
		MAX-ACCESS read-only
		STATUS current
		DESCRIPTION
		"upsIta2com60BatDischargeCurrent stored as 0.1A."
		::= { upsIta2comEntry 61 }
upsIta2com62NegativeBatVoltage OBJECT-TYPE
		SYNTAX Integer32
		
		MAX-ACCESS read-only
		STATUS current
		DESCRIPTION
		"upsIta2com61NegativeBatVoltage stored as 0.1V."
		::= { upsIta2comEntry 62 }
upsIta2com63NegativeBatChargeCurrent OBJECT-TYPE
		SYNTAX Integer32
		
		MAX-ACCESS read-only
		STATUS current
		DESCRIPTION
		"upsIta2com62NegativeBatChargeCurrent stored as 0.1A."
		::= { upsIta2comEntry 63 }
upsIta2com64NegativeBatDischargeCurrent OBJECT-TYPE
		SYNTAX Integer32
		
		MAX-ACCESS read-only
		STATUS current
		DESCRIPTION
		"upsIta2com63NegativeBatDischargeCurrent stored as 0.1A."
		::= { upsIta2comEntry 64 }
upsIta2com65BatBackupTime OBJECT-TYPE
		SYNTAX Integer32
		
		MAX-ACCESS read-only
		STATUS current
		DESCRIPTION
		"upsIta2com64BatBackupTime stored as 0.1min."
		::= { upsIta2comEntry 65 }
upsIta2com66Battemp OBJECT-TYPE
		SYNTAX Integer32
		
		MAX-ACCESS read-only
		STATUS current
		DESCRIPTION
		"upsIta2com65Battemp stored as 0.1℃."
		::= { upsIta2comEntry 66 }
upsIta2com67Ambienttemp OBJECT-TYPE
		SYNTAX Integer32
		
		MAX-ACCESS read-only
		STATUS current
		DESCRIPTION
		"upsIta2com66Ambienttemp stored as 0.1℃."
		::= { upsIta2comEntry 67 }
upsIta2com68BatCurrentCapacity OBJECT-TYPE
		SYNTAX Integer32
		
		MAX-ACCESS read-only
		STATUS current
		DESCRIPTION
		"upsIta2com67BatCurrentCapacity stored as 0.1%."
		::= { upsIta2comEntry 68 }
upsIta2com69BatDischargeTimes OBJECT-TYPE
		SYNTAX Integer32
		
		MAX-ACCESS read-only
		STATUS current
		DESCRIPTION
		"upsIta2com68BatDischargeTimes stored as 0.1."
		::= { upsIta2comEntry 69 }
upsIta2com70BatHelth OBJECT-TYPE
		SYNTAX Integer32
		
		MAX-ACCESS read-only
		STATUS current
		DESCRIPTION
		"upsIta2com69BatHelth stored as 0.1%."
		::= { upsIta2comEntry 70 }
upsIta2com71InputPower OBJECT-TYPE
		SYNTAX Integer32
		
		MAX-ACCESS read-only
		STATUS current
		DESCRIPTION
		"upsIta2com70InputPower stored as 0.1kWh."
		::= { upsIta2comEntry 71 }
upsIta2com72OutputPower OBJECT-TYPE
		SYNTAX Integer32
		
		MAX-ACCESS read-only
		STATUS current
		DESCRIPTION
		"upsIta2com71OutputPower stored as 0.1kWh."
		::= { upsIta2comEntry 72 }
upsIta2com73BatRunningTime OBJECT-TYPE
		SYNTAX Integer32
		
		MAX-ACCESS read-only
		STATUS current
		DESCRIPTION
		"upsIta2com72BatRunningTime stored as 0.01Hour."
		::= { upsIta2comEntry 73 }
upsIta2com74BatDischargingTime OBJECT-TYPE
		SYNTAX Integer32
		
		MAX-ACCESS read-only
		STATUS current
		DESCRIPTION
		"upsIta2com73BatDischargingTime stored as 0.01Hour."
		::= { upsIta2comEntry 74 }
upsIta2com75PowerSupply OBJECT-TYPE
		SYNTAX INTEGER {
			upsshutdown(0),
			utilityonline(1),
			onbat(2),
			onbypass(3),
			upsonunionmode(4) }
		MAX-ACCESS read-only
		STATUS current
		DESCRIPTION
		"upsIta2com74PowerSupply status."
		::= { upsIta2comEntry 75 }
upsIta2com76InputPowerStatus OBJECT-TYPE
		SYNTAX INTEGER {
			utilityonline(0),
			onbat(1),
			upsonunionmode(2),
			upsshutdown(3) }
		MAX-ACCESS read-only
		STATUS current
		DESCRIPTION
		"upsIta2com75InputPowerStatus status."
		::= { upsIta2comEntry 76 }
upsIta2com77BatStatus OBJECT-TYPE
		SYNTAX INTEGER {
			idle(0),
			floatcharging(1),
			equalizationcharging(2),
			discharging(3),
			selftesting(4),
			nobat(5),
			full(6),
			precharge(7),
			fastcharging(8) }
		MAX-ACCESS read-only
		STATUS current
		DESCRIPTION
		"upsIta2com76BatStatus status."
		::= { upsIta2comEntry 77 }
upsIta2com78BatNegativeGroupStatus OBJECT-TYPE
		SYNTAX INTEGER {
			idle(0),
			floatcharging(1),
			equalizationcharging(2),
			discharging(3),
			selftesting(4),
			nobat(5),
			full(6),
			precharge(7),
			fastcharging(8) }
		MAX-ACCESS read-only
		STATUS current
		DESCRIPTION
		"upsIta2com77BatNegativeGroupStatus status."
		::= { upsIta2comEntry 78 }
upsIta2com79ChargerStatus OBJECT-TYPE
		SYNTAX INTEGER {
			chargeron(0),
			chargeroff(1) }
		MAX-ACCESS read-only
		STATUS current
		DESCRIPTION
		"upsIta2com78ChargerStatus status."
		::= { upsIta2comEntry 79 }
upsIta2com80ParallelSystemPowerState OBJECT-TYPE
		SYNTAX INTEGER {
			maininverterpowersupply(0),
			onbat(1),
			onbypass(2),
			upsshutdown(3) }
		MAX-ACCESS read-only
		STATUS current
		DESCRIPTION
		"upsIta2com79ParallelSystemPowerState status."
		::= { upsIta2comEntry 80 }
upsIta2com81IneerNetworkconnectStatus OBJECT-TYPE
		SYNTAX INTEGER {
			connected(0),
			disconnected(1) }
		MAX-ACCESS read-only
		STATUS current
		DESCRIPTION
		"upsIta2com80IneerNetworkconnectStatus status."
		::= { upsIta2comEntry 81 }
upsIta2com82Outlet1SwitchStatus OBJECT-TYPE
		SYNTAX INTEGER {
			turnedon(0),
			turnedoff(1) }
		MAX-ACCESS read-only
		STATUS current
		DESCRIPTION
		"upsIta2com81Outlet1SwitchStatus status."
		::= { upsIta2comEntry 82 }
upsIta2com83Outlet2SwitchStatus OBJECT-TYPE
		SYNTAX INTEGER {
			turnedon(0),
			turnedoff(1) }
		MAX-ACCESS read-only
		STATUS current
		DESCRIPTION
		"upsIta2com82Outlet2SwitchStatus status."
		::= { upsIta2comEntry 83 }
upsIta2com84InputAbnormal OBJECT-TYPE
		SYNTAX INTEGER {
			normal(0),
			alarm(1) }
		MAX-ACCESS read-only
		STATUS current
		DESCRIPTION
		"upsIta2com83InputAbnormal status."
		::= { upsIta2comEntry 84 }
upsIta2com85SystemOvertemp OBJECT-TYPE
		SYNTAX INTEGER {
			normal(0),
			alarm(1) }
		MAX-ACCESS read-only
		STATUS current
		DESCRIPTION
		"upsIta2com84SystemOvertemp status."
		::= { upsIta2comEntry 85 }
upsIta2com86SystemBatLowPreWarning OBJECT-TYPE
		SYNTAX INTEGER {
			normal(0),
			alarm(1) }
		MAX-ACCESS read-only
		STATUS current
		DESCRIPTION
		"upsIta2com85SystemBatLowPreWarning status."
		::= { upsIta2comEntry 86 }
upsIta2com87InputPhaseReversed OBJECT-TYPE
		SYNTAX INTEGER {
			normal(0),
			alarm(1) }
		MAX-ACCESS read-only
		STATUS current
		DESCRIPTION
		"upsIta2com86InputPhaseReversed status."
		::= { upsIta2comEntry 87 }
upsIta2com88InputNeutralLost OBJECT-TYPE
		SYNTAX INTEGER {
			normal(0),
			alarm(1) }
		MAX-ACCESS read-only
		STATUS current
		DESCRIPTION
		"upsIta2com87InputNeutralLost status."
		::= { upsIta2comEntry 88 }
upsIta2com89InputGroundLost OBJECT-TYPE
		SYNTAX INTEGER {
			normal(0),
			alarm(1) }
		MAX-ACCESS read-only
		STATUS current
		DESCRIPTION
		"upsIta2com88InputGroundLost status."
		::= { upsIta2comEntry 89 }
upsIta2com90RectifierOverload OBJECT-TYPE
		SYNTAX INTEGER {
			normal(0),
			alarm(1) }
		MAX-ACCESS read-only
		STATUS current
		DESCRIPTION
		"upsIta2com89RectifierOverload status."
		::= { upsIta2comEntry 90 }
upsIta2com91BatCabinetNotConnected OBJECT-TYPE
		SYNTAX INTEGER {
			normal(0),
			alarm(1) }
		MAX-ACCESS read-only
		STATUS current
		DESCRIPTION
		"upsIta2com90BatCabinetNotConnected status."
		::= { upsIta2comEntry 91 }
upsIta2com92InverterOverload OBJECT-TYPE
		SYNTAX INTEGER {
			normal(0),
			alarm(1) }
		MAX-ACCESS read-only
		STATUS current
		DESCRIPTION
		"upsIta2com91InverterOverload status."
		::= { upsIta2comEntry 92 }
upsIta2com93LbsAbnormal OBJECT-TYPE
		SYNTAX INTEGER {
			normal(0),
			alarm(1) }
		MAX-ACCESS read-only
		STATUS current
		DESCRIPTION
		"upsIta2com92LbsAbnormal status."
		::= { upsIta2comEntry 93 }
upsIta2com94OutputPending OBJECT-TYPE
		SYNTAX INTEGER {
			normal(0),
			alarm(1) }
		MAX-ACCESS read-only
		STATUS current
		DESCRIPTION
		"upsIta2com93OutputPending status."
		::= { upsIta2comEntry 94 }
upsIta2com95OutputDisabled OBJECT-TYPE
		SYNTAX INTEGER {
			normal(0),
			alarm(1) }
		MAX-ACCESS read-only
		STATUS current
		DESCRIPTION
		"upsIta2com94OutputDisabled status."
		::= { upsIta2comEntry 95 }
upsIta2com96BypassAbnormal OBJECT-TYPE
		SYNTAX INTEGER {
			normal(0),
			alarm(1) }
		MAX-ACCESS read-only
		STATUS current
		DESCRIPTION
		"upsIta2com95BypassAbnormal status."
		::= { upsIta2comEntry 96 }
upsIta2com97BypassAbnormalInEcoMode OBJECT-TYPE
		SYNTAX INTEGER {
			normal(0),
			alarm(1) }
		MAX-ACCESS read-only
		STATUS current
		DESCRIPTION
		"upsIta2com96BypassAbnormalInEcoMode status."
		::= { upsIta2comEntry 97 }
upsIta2com98BypassPhaseReversed OBJECT-TYPE
		SYNTAX INTEGER {
			normal(0),
			alarm(1) }
		MAX-ACCESS read-only
		STATUS current
		DESCRIPTION
		"upsIta2com97BypassPhaseReversed status."
		::= { upsIta2comEntry 98 }
upsIta2com99BypassOvercurrent OBJECT-TYPE
		SYNTAX INTEGER {
			normal(0),
			alarm(1) }
		MAX-ACCESS read-only
		STATUS current
		DESCRIPTION
		"upsIta2com98BypassOvercurrent status."
		::= { upsIta2comEntry 99 }
upsIta2com100BypassCableconnectAbnormal OBJECT-TYPE
		SYNTAX INTEGER {
			normal(0),
			alarm(1) }
		MAX-ACCESS read-only
		STATUS current
		DESCRIPTION
		"upsIta2com99BypassCableconnectAbnormal status."
		::= { upsIta2comEntry 100 }
upsIta2com101BatReversed OBJECT-TYPE
		SYNTAX INTEGER {
			normal(0),
			alarm(1) }
		MAX-ACCESS read-only
		STATUS current
		DESCRIPTION
		"upsIta2com100BatReversed status."
		::= { upsIta2comEntry 101 }
upsIta2com102BatLowPreWarning OBJECT-TYPE
		SYNTAX INTEGER {
			normal(0),
			alarm(1) }
		MAX-ACCESS read-only
		STATUS current
		DESCRIPTION
		"upsIta2com101BatLowPreWarning status."
		::= { upsIta2comEntry 102 }
upsIta2com103BatVoltAbnormal OBJECT-TYPE
		SYNTAX INTEGER {
			normal(0),
			alarm(1) }
		MAX-ACCESS read-only
		STATUS current
		DESCRIPTION
		"upsIta2com102BatVoltAbnormal status."
		::= { upsIta2comEntry 103 }
upsIta2com104NoBat OBJECT-TYPE
		SYNTAX INTEGER {
			normal(0),
			alarm(1) }
		MAX-ACCESS read-only
		STATUS current
		DESCRIPTION
		"upsIta2com103NoBat status."
		::= { upsIta2comEntry 104 }
upsIta2com105BatOvertemp OBJECT-TYPE
		SYNTAX INTEGER {
			normal(0),
			alarm(1) }
		MAX-ACCESS read-only
		STATUS current
		DESCRIPTION
		"upsIta2com104BatOvertemp status."
		::= { upsIta2comEntry 105 }
upsIta2com106BatAging OBJECT-TYPE
		SYNTAX INTEGER {
			normal(0),
			alarm(1) }
		MAX-ACCESS read-only
		STATUS current
		DESCRIPTION
		"upsIta2com105BatAging status."
		::= { upsIta2comEntry 106 }
upsIta2com107BatTestFailure OBJECT-TYPE
		SYNTAX INTEGER {
			normal(0),
			alarm(1) }
		MAX-ACCESS read-only
		STATUS current
		DESCRIPTION
		"upsIta2com106BatTestFailure status."
		::= { upsIta2comEntry 107 }
upsIta2com108BatSeriesNotQualified OBJECT-TYPE
		SYNTAX INTEGER {
			normal(0),
			alarm(1) }
		MAX-ACCESS read-only
		STATUS current
		DESCRIPTION
		"upsIta2com107BatSeriesNotQualified status."
		::= { upsIta2comEntry 108 }
upsIta2com109FanFailure OBJECT-TYPE
		SYNTAX INTEGER {
			normal(0),
			alarm(1) }
		MAX-ACCESS read-only
		STATUS current
		DESCRIPTION
		"upsIta2com108FanFailure status."
		::= { upsIta2comEntry 109 }
upsIta2com110Repo OBJECT-TYPE
		SYNTAX INTEGER {
			normal(0),
			alarm(1) }
		MAX-ACCESS read-only
		STATUS current
		DESCRIPTION
		"upsIta2com109Repo status."
		::= { upsIta2comEntry 110 }
upsIta2com111ElectricLeakAlarm OBJECT-TYPE
		SYNTAX INTEGER {
			normal(0),
			alarm(1) }
		MAX-ACCESS read-only
		STATUS current
		DESCRIPTION
		"upsIta2com110ElectricLeakAlarm status."
		::= { upsIta2comEntry 111 }
upsIta2com112VersionIncompatible OBJECT-TYPE
		SYNTAX INTEGER {
			normal(0),
			alarm(1) }
		MAX-ACCESS read-only
		STATUS current
		DESCRIPTION
		"upsIta2com111VersionIncompatible status."
		::= { upsIta2comEntry 112 }
upsIta2com113OutputLpeShort OBJECT-TYPE
		SYNTAX INTEGER {
			normal(0),
			alarm(1) }
		MAX-ACCESS read-only
		STATUS current
		DESCRIPTION
		"upsIta2com112OutputLpeShort status."
		::= { upsIta2comEntry 113 }
upsIta2com114LossOfRedundancy OBJECT-TYPE
		SYNTAX INTEGER {
			normal(0),
			alarm(1) }
		MAX-ACCESS read-only
		STATUS current
		DESCRIPTION
		"upsIta2com113LossOfRedundancy status."
		::= { upsIta2comEntry 114 }
upsIta2com115SystemOverload OBJECT-TYPE
		SYNTAX INTEGER {
			normal(0),
			alarm(1) }
		MAX-ACCESS read-only
		STATUS current
		DESCRIPTION
		"upsIta2com114SystemOverload status."
		::= { upsIta2comEntry 115 }
upsIta2com116LoadSharingAbnormal OBJECT-TYPE
		SYNTAX INTEGER {
			normal(0),
			alarm(1) }
		MAX-ACCESS read-only
		STATUS current
		DESCRIPTION
		"upsIta2com115LoadSharingAbnormal status."
		::= { upsIta2comEntry 116 }
upsIta2com117SystemParallelSetsAsync OBJECT-TYPE
		SYNTAX INTEGER {
			normal(0),
			alarm(1) }
		MAX-ACCESS read-only
		STATUS current
		DESCRIPTION
		"upsIta2com116SystemParallelSetsAsync status."
		::= { upsIta2comEntry 117 }
upsIta2com118LocalParallelSetsAsync OBJECT-TYPE
		SYNTAX INTEGER {
			normal(0),
			alarm(1) }
		MAX-ACCESS read-only
		STATUS current
		DESCRIPTION
		"upsIta2com117LocalParallelSetsAsync status."
		::= { upsIta2comEntry 118 }
upsIta2com119OnMaintenanceBypass OBJECT-TYPE
		SYNTAX INTEGER {
			normal(0),
			alarm(1) }
		MAX-ACCESS read-only
		STATUS current
		DESCRIPTION
		"upsIta2com118OnMaintenanceBypass status."
		::= { upsIta2comEntry 119 }
upsIta2com120BatMode OBJECT-TYPE
		SYNTAX INTEGER {
			normal(0),
			alarm(1) }
		MAX-ACCESS read-only
		STATUS current
		DESCRIPTION
		"upsIta2com119BatMode status."
		::= { upsIta2comEntry 120 }
upsIta2com121BypassMode OBJECT-TYPE
		SYNTAX INTEGER {
			normal(0),
			alarm(1) }
		MAX-ACCESS read-only
		STATUS current
		DESCRIPTION
		"upsIta2com120BypassMode status."
		::= { upsIta2comEntry 121 }
upsIta2com122ParallelNoAbnormal OBJECT-TYPE
		SYNTAX INTEGER {
			normal(0),
			alarm(1) }
		MAX-ACCESS read-only
		STATUS current
		DESCRIPTION
		"upsIta2com121ParallelNoAbnormal status."
		::= { upsIta2comEntry 122 }
upsIta2com123BypassCableconnectAbnormal OBJECT-TYPE
		SYNTAX INTEGER {
			normal(0),
			alarm(1) }
		MAX-ACCESS read-only
		STATUS current
		DESCRIPTION
		"upsIta2com122BypassCableconnectAbnormal status."
		::= { upsIta2comEntry 123 }
upsIta2com124OnIntelligentSleepMode OBJECT-TYPE
		SYNTAX INTEGER {
			normal(0),
			alarm(1) }
		MAX-ACCESS read-only
		STATUS current
		DESCRIPTION
		"upsIta2com123OnIntelligentSleepMode status."
		::= { upsIta2comEntry 124 }
upsIta2com125BatCabinetConnectAbnormal OBJECT-TYPE
		SYNTAX INTEGER {
			normal(0),
			alarm(1) }
		MAX-ACCESS read-only
		STATUS current
		DESCRIPTION
		"upsIta2com124BatCabinetConnectAbnormal status."
		::= { upsIta2comEntry 125 }
upsIta2com126SystemFault OBJECT-TYPE
		SYNTAX INTEGER {
			normal(0),
			alarm(1) }
		MAX-ACCESS read-only
		STATUS current
		DESCRIPTION
		"upsIta2com125SystemFault status."
		::= { upsIta2comEntry 126 }
upsIta2com127EodTurnOff OBJECT-TYPE
		SYNTAX INTEGER {
			normal(0),
			abnormal(1) }
		MAX-ACCESS read-only
		STATUS current
		DESCRIPTION
		"upsIta2com126EodTurnOff status."
		::= { upsIta2comEntry 127 }
upsIta2com128Bypassdisable OBJECT-TYPE
		SYNTAX INTEGER {
			normal(0),
			alarm(1) }
		MAX-ACCESS read-only
		STATUS current
		DESCRIPTION
		"upsIta2com127Bypassdisable status."
		::= { upsIta2comEntry 128 }
upsIta2com129UPShasnooutput OBJECT-TYPE
		SYNTAX INTEGER {
			normal(0),
			alarm(1) }
		MAX-ACCESS read-only
		STATUS current
		DESCRIPTION
		"upsIta2com128UPShasnooutput status."
		::= { upsIta2comEntry 129 }
upsIta2com130Outputvoltageabnormal OBJECT-TYPE
		SYNTAX INTEGER {
			normal(0),
			alarm(1) }
		MAX-ACCESS read-only
		STATUS current
		DESCRIPTION
		"upsIta2com129Outputvoltageabnormal status."
		::= { upsIta2comEntry 130 }
upsIta2com131Localoutputisdisconnected OBJECT-TYPE
		SYNTAX INTEGER {
			normal(0),
			alarm(1) }
		MAX-ACCESS read-only
		STATUS current
		DESCRIPTION
		"upsIta2com130Localoutputisdisconnected status."
		::= { upsIta2comEntry 131 }
upsIta2com132Turnonfailed OBJECT-TYPE
		SYNTAX INTEGER {
			normal(0),
			alarm(1) }
		MAX-ACCESS read-only
		STATUS current
		DESCRIPTION
		"upsIta2com131Turnonfailed status."
		::= { upsIta2comEntry 132 }
upsIta2com133Inputfrequencyabnormal OBJECT-TYPE
		SYNTAX INTEGER {
			normal(0),
			alarm(1) }
		MAX-ACCESS read-only
		STATUS current
		DESCRIPTION
		"upsIta2com132Inputfrequencyabnormal status."
		::= { upsIta2comEntry 133 }
upsIta2com134Fanagingtimealarm OBJECT-TYPE
		SYNTAX INTEGER {
			normal(0),
			alarm(1) }
		MAX-ACCESS read-only
		STATUS current
		DESCRIPTION
		"upsIta2com133Fanagingtimealarm status."
		::= { upsIta2comEntry 134 }
upsIta2com135Bypassovercurrenttimeout OBJECT-TYPE
		SYNTAX INTEGER {
			normal(0),
			alarm(1) }
		MAX-ACCESS read-only
		STATUS current
		DESCRIPTION
		"upsIta2com134Bypassovercurrenttimeout status."
		::= { upsIta2comEntry 135 }
upsIta2com136BatDCgroundfault OBJECT-TYPE
		SYNTAX INTEGER {
			normal(0),
			alarm(1) }
		MAX-ACCESS read-only
		STATUS current
		DESCRIPTION
		"upsIta2com135BatDCgroundfault status."
		::= { upsIta2comEntry 136 }
upsIta2com137Systemredundantoverload OBJECT-TYPE
		SYNTAX INTEGER {
			normal(0),
			alarm(1) }
		MAX-ACCESS read-only
		STATUS current
		DESCRIPTION
		"upsIta2com136Systemredundantoverload status."
		::= { upsIta2comEntry 137 }
upsIta2com138BatCommfail OBJECT-TYPE
		SYNTAX INTEGER {
			normal(0),
			alarm(1) }
		MAX-ACCESS read-only
		STATUS current
		DESCRIPTION
		"upsIta2com137BatCommfail status."
		::= { upsIta2comEntry 138 }
upsIta2com139BatummatchtheUPS OBJECT-TYPE
		SYNTAX INTEGER {
			normal(0),
			alarm(1) }
		MAX-ACCESS read-only
		STATUS current
		DESCRIPTION
		"upsIta2com138BatummatchtheUPS status."
		::= { upsIta2comEntry 139 }
upsIta2com140BatAddrsetwrong OBJECT-TYPE
		SYNTAX INTEGER {
			normal(0),
			alarm(1) }
		MAX-ACCESS read-only
		STATUS current
		DESCRIPTION
		"upsIta2com139BatAddrsetwrong status."
		::= { upsIta2comEntry 140 }
upsIta2com141Batmodelnotqualified OBJECT-TYPE
		SYNTAX INTEGER {
			normal(0),
			alarm(1) }
		MAX-ACCESS read-only
		STATUS current
		DESCRIPTION
		"upsIta2com140Batmodelnotqualified status."
		::= { upsIta2comEntry 141 }
upsIta2com142BatSNabnormal OBJECT-TYPE
		SYNTAX INTEGER {
			normal(0),
			alarm(1) }
		MAX-ACCESS read-only
		STATUS current
		DESCRIPTION
		"upsIta2com141BatSNabnormal status."
		::= { upsIta2comEntry 142 }
upsIta2com143Batcabinetconnectabnormal OBJECT-TYPE
		SYNTAX INTEGER {
			normal(0),
			alarm(1) }
		MAX-ACCESS read-only
		STATUS current
		DESCRIPTION
		"upsIta2com142Batcabinetconnectabnormal status."
		::= { upsIta2comEntry 143 }
upsIta2com144BatCANconnectabnormal OBJECT-TYPE
		SYNTAX INTEGER {
			normal(0),
			alarm(1) }
		MAX-ACCESS read-only
		STATUS current
		DESCRIPTION
		"upsIta2com143BatCANconnectabnormal status."
		::= { upsIta2comEntry 144 }
upsIta2com145BatNoexceedthelimit OBJECT-TYPE
		SYNTAX INTEGER {
			normal(0),
			alarm(1) }
		MAX-ACCESS read-only
		STATUS current
		DESCRIPTION
		"upsIta2com144BatNoexceedthelimit status."
		::= { upsIta2comEntry 145 }
upsIta2com146BatgrouplessForbiddischarge OBJECT-TYPE
		SYNTAX INTEGER {
			normal(0),
			alarm(1) }
		MAX-ACCESS read-only
		STATUS current
		DESCRIPTION
		"upsIta2com145BatgrouplessForbiddischarge status."
		::= { upsIta2comEntry 146 }
upsIta2com147Ambienttemplowprealarm OBJECT-TYPE
		SYNTAX INTEGER {
			normal(0),
			alarm(1) }
		MAX-ACCESS read-only
		STATUS current
		DESCRIPTION
		"upsIta2com146Ambienttemplowprealarm status."
		::= { upsIta2comEntry 147 }
upsIta2com148Ambienttemphighprealarm OBJECT-TYPE
		SYNTAX INTEGER {
			normal(0),
			alarm(1) }
		MAX-ACCESS read-only
		STATUS current
		DESCRIPTION
		"upsIta2com147Ambienttemphighprealarm status."
		::= { upsIta2comEntry 148 }
upsIta2com149DcBusAbnormal OBJECT-TYPE
		SYNTAX INTEGER {
			normal(0),
			alarm(1) }
		MAX-ACCESS read-only
		STATUS current
		DESCRIPTION
		"upsIta2com148DcBusAbnormal status."
		::= { upsIta2comEntry 149 }
upsIta2com150RectifierFault OBJECT-TYPE
		SYNTAX INTEGER {
			normal(0),
			alarm(1) }
		MAX-ACCESS read-only
		STATUS current
		DESCRIPTION
		"upsIta2com149RectifierFault status."
		::= { upsIta2comEntry 150 }
upsIta2com151DcDcFault OBJECT-TYPE
		SYNTAX INTEGER {
			normal(0),
			alarm(1) }
		MAX-ACCESS read-only
		STATUS current
		DESCRIPTION
		"upsIta2com150DcDcFault status."
		::= { upsIta2comEntry 151 }
upsIta2com152ChargerFault OBJECT-TYPE
		SYNTAX INTEGER {
			normal(0),
			alarm(1) }
		MAX-ACCESS read-only
		STATUS current
		DESCRIPTION
		"upsIta2com151ChargerFault status."
		::= { upsIta2comEntry 152 }
upsIta2com153InputBackfeed OBJECT-TYPE
		SYNTAX INTEGER {
			normal(0),
			alarm(1) }
		MAX-ACCESS read-only
		STATUS current
		DESCRIPTION
		"upsIta2com152InputBackfeed status."
		::= { upsIta2comEntry 153 }
upsIta2com154InverterFault OBJECT-TYPE
		SYNTAX INTEGER {
			normal(0),
			alarm(1) }
		MAX-ACCESS read-only
		STATUS current
		DESCRIPTION
		"upsIta2com153InverterFault status."
		::= { upsIta2comEntry 154 }
upsIta2com155InverterRelayWelded OBJECT-TYPE
		SYNTAX INTEGER {
			normal(0),
			alarm(1) }
		MAX-ACCESS read-only
		STATUS current
		DESCRIPTION
		"upsIta2com154InverterRelayWelded status."
		::= { upsIta2comEntry 155 }
upsIta2com156BypassBackfeed OBJECT-TYPE
		SYNTAX INTEGER {
			normal(0),
			alarm(1) }
		MAX-ACCESS read-only
		STATUS current
		DESCRIPTION
		"upsIta2com155BypassBackfeed status."
		::= { upsIta2comEntry 156 }
upsIta2com157AuxiliaryPowerFault OBJECT-TYPE
		SYNTAX INTEGER {
			normal(0),
			alarm(1) }
		MAX-ACCESS read-only
		STATUS current
		DESCRIPTION
		"upsIta2com156AuxiliaryPowerFault status."
		::= { upsIta2comEntry 157 }
upsIta2com158InternalCommFault OBJECT-TYPE
		SYNTAX INTEGER {
			normal(0),
			alarm(1) }
		MAX-ACCESS read-only
		STATUS current
		DESCRIPTION
		"upsIta2com157InternalCommFault status."
		::= { upsIta2comEntry 158 }
upsIta2com159OutputShortCircuit OBJECT-TYPE
		SYNTAX INTEGER {
			normal(0),
			alarm(1) }
		MAX-ACCESS read-only
		STATUS current
		DESCRIPTION
		"upsIta2com158OutputShortCircuit status."
		::= { upsIta2comEntry 159 }
upsIta2com160OutputOffAndVoltageIsNotZero OBJECT-TYPE
		SYNTAX INTEGER {
			normal(0),
			alarm(1) }
		MAX-ACCESS read-only
		STATUS current
		DESCRIPTION
		"upsIta2com159OutputOffAndVoltageIsNotZero status."
		::= { upsIta2comEntry 160 }
upsIta2com161ParallelCommBreakdown OBJECT-TYPE
		SYNTAX INTEGER {
			normal(0),
			alarm(1) }
		MAX-ACCESS read-only
		STATUS current
		DESCRIPTION
		"upsIta2com160ParallelCommBreakdown status."
		::= { upsIta2comEntry 161 }
upsIta2com162ParallelCableconnectAbnormal OBJECT-TYPE
		SYNTAX INTEGER {
			normal(0),
			alarm(1) }
		MAX-ACCESS read-only
		STATUS current
		DESCRIPTION
		"upsIta2com161ParallelCableconnectAbnormal status."
		::= { upsIta2comEntry 162 }
upsIta2com163Systemfault OBJECT-TYPE
		SYNTAX INTEGER {
			normal(0),
			alarm(1) }
		MAX-ACCESS read-only
		STATUS current
		DESCRIPTION
		"upsIta2com162Systemfault status."
		::= { upsIta2comEntry 163 }
upsIta2com164Rectifiersoftstartfail OBJECT-TYPE
		SYNTAX INTEGER {
			normal(0),
			alarm(1) }
		MAX-ACCESS read-only
		STATUS current
		DESCRIPTION
		"upsIta2com163Rectifiersoftstartfail status."
		::= { upsIta2comEntry 164 }
upsIta2com165DSPfault OBJECT-TYPE
		SYNTAX INTEGER {
			normal(0),
			alarm(1) }
		MAX-ACCESS read-only
		STATUS current
		DESCRIPTION
		"upsIta2com164DSPfault status."
		::= { upsIta2comEntry 165 }
upsIta2com166Year OBJECT-TYPE
		SYNTAX Integer32
		
		MAX-ACCESS read-only
		STATUS current
		DESCRIPTION
		"upsIta2com165Year stored as 1."
		::= { upsIta2comEntry 166 }
upsIta2com167Month OBJECT-TYPE
		SYNTAX Integer32
		
		MAX-ACCESS read-only
		STATUS current
		DESCRIPTION
		"upsIta2com166Month stored as 1."
		::= { upsIta2comEntry 167 }
upsIta2com168Day OBJECT-TYPE
		SYNTAX Integer32
		
		MAX-ACCESS read-only
		STATUS current
		DESCRIPTION
		"upsIta2com167Day stored as 1."
		::= { upsIta2comEntry 168 }
upsIta2com169Hour OBJECT-TYPE
		SYNTAX Integer32
		
		MAX-ACCESS read-only
		STATUS current
		DESCRIPTION
		"upsIta2com168Hour stored as 1."
		::= { upsIta2comEntry 170 }
upsIta2com170Minute OBJECT-TYPE
		SYNTAX Integer32
		
		MAX-ACCESS read-only
		STATUS current
		DESCRIPTION
		"upsIta2com169Minute stored as 1."
		::= { upsIta2comEntry 171 }
upsIta2com171Second OBJECT-TYPE
		SYNTAX Integer32
		
		MAX-ACCESS read-only
		STATUS current
		DESCRIPTION
		"upsIta2com170Second stored as 1."
		::= { upsIta2comEntry 172 }
upsIta2com172InputBackfeed OBJECT-TYPE
		SYNTAX INTEGER {
			normal(0),
			alarm(1) }
		MAX-ACCESS read-only
		STATUS current
		DESCRIPTION
		"upsIta2com171InputBackfeed status."
		::= { upsIta2comEntry 173 }
upsIta2com173BypassBackfeed OBJECT-TYPE
		SYNTAX INTEGER {
			normal(0),
			alarm(1) }
		MAX-ACCESS read-only
		STATUS current
		DESCRIPTION
		"upsIta2com172BypassBackfeed status."
		::= { upsIta2comEntry 174 }
upsIta2com174Addr1Batmoduleonline OBJECT-TYPE
		SYNTAX INTEGER {
			disconnect(0),
			online(1) }
		MAX-ACCESS read-only
		STATUS current
		DESCRIPTION
		"upsIta2com173Addr1Batmoduleonline status."
		::= { upsIta2comEntry 175 }
upsIta2com175Addr2Batmoduleonline OBJECT-TYPE
		SYNTAX INTEGER {
			disconnect(0),
			online(1) }
		MAX-ACCESS read-only
		STATUS current
		DESCRIPTION
		"upsIta2com174Addr2Batmoduleonline status."
		::= { upsIta2comEntry 176 }
upsIta2com176Addr3Batmoduleonline OBJECT-TYPE
		SYNTAX INTEGER {
			disconnect(0),
			online(1) }
		MAX-ACCESS read-only
		STATUS current
		DESCRIPTION
		"upsIta2com175Addr3Batmoduleonline status."
		::= { upsIta2comEntry 177 }
upsIta2com177Addr4Batmoduleonline OBJECT-TYPE
		SYNTAX INTEGER {
			disconnect(0),
			online(1) }
		MAX-ACCESS read-only
		STATUS current
		DESCRIPTION
		"upsIta2com176Addr4Batmoduleonline status."
		::= { upsIta2comEntry 178 }
upsIta2com178Addr5Batmoduleonline OBJECT-TYPE
		SYNTAX INTEGER {
			disconnect(0),
			online(1) }
		MAX-ACCESS read-only
		STATUS current
		DESCRIPTION
		"upsIta2com177Addr5Batmoduleonline status."
		::= { upsIta2comEntry 179 }
upsIta2com179Addr6Batmoduleonline OBJECT-TYPE
		SYNTAX INTEGER {
			disconnect(0),
			online(1) }
		MAX-ACCESS read-only
		STATUS current
		DESCRIPTION
		"upsIta2com178Addr6Batmoduleonline status."
		::= { upsIta2comEntry 180 }
upsIta2com180Addr7Batmoduleonline OBJECT-TYPE
		SYNTAX INTEGER {
			disconnect(0),
			online(1) }
		MAX-ACCESS read-only
		STATUS current
		DESCRIPTION
		"upsIta2com179Addr7Batmoduleonline status."
		::= { upsIta2comEntry 181 }
upsIta2com181Addr8Batmoduleonline OBJECT-TYPE
		SYNTAX INTEGER {
			disconnect(0),
			online(1) }
		MAX-ACCESS read-only
		STATUS current
		DESCRIPTION
		"upsIta2com180Addr8Batmoduleonline status."
		::= { upsIta2comEntry 182 }
upsIta2com182Addr9Batmoduleonline OBJECT-TYPE
		SYNTAX INTEGER {
			disconnect(0),
			online(1) }
		MAX-ACCESS read-only
		STATUS current
		DESCRIPTION
		"upsIta2com181Addr9Batmoduleonline status."
		::= { upsIta2comEntry 183 }
upsIta2com183Addr10Batmoduleonline OBJECT-TYPE
		SYNTAX INTEGER {
			disconnect(0),
			online(1) }
		MAX-ACCESS read-only
		STATUS current
		DESCRIPTION
		"upsIta2com182Addr10Batmoduleonline status."
		::= { upsIta2comEntry 184 }
upsIta2com184Addr11Batmoduleonline OBJECT-TYPE
		SYNTAX INTEGER {
			disconnect(0),
			online(1) }
		MAX-ACCESS read-only
		STATUS current
		DESCRIPTION
		"upsIta2com183Addr11Batmoduleonline status."
		::= { upsIta2comEntry 185 }
upsIta2com185Addr12Batmoduleonline OBJECT-TYPE
		SYNTAX INTEGER {
			disconnect(0),
			online(1) }
		MAX-ACCESS read-only
		STATUS current
		DESCRIPTION
		"upsIta2com184Addr12Batmoduleonline status."
		::= { upsIta2comEntry 186 }
upsIta2com186Addr13Batmoduleonline OBJECT-TYPE
		SYNTAX INTEGER {
			disconnect(0),
			online(1) }
		MAX-ACCESS read-only
		STATUS current
		DESCRIPTION
		"upsIta2com185Addr13Batmoduleonline status."
		::= { upsIta2comEntry 187 }
upsIta2com187Addr14Batmoduleonline OBJECT-TYPE
		SYNTAX INTEGER {
			disconnect(0),
			online(1) }
		MAX-ACCESS read-only
		STATUS current
		DESCRIPTION
		"upsIta2com186Addr14Batmoduleonline status."
		::= { upsIta2comEntry 188 }
upsIta2com188Addr15Batmoduleonline OBJECT-TYPE
		SYNTAX INTEGER {
			disconnect(0),
			online(1) }
		MAX-ACCESS read-only
		STATUS current
		DESCRIPTION
		"upsIta2com187Addr15Batmoduleonline status."
		::= { upsIta2comEntry 189 }
upsIta2com189Addr16Batmoduleonline OBJECT-TYPE
		SYNTAX INTEGER {
			disconnect(0),
			online(1) }
		MAX-ACCESS read-only
		STATUS current
		DESCRIPTION
		"upsIta2com188Addr16Batmoduleonline status."
		::= { upsIta2comEntry 190 }
upsIta2com190Addr1Batstatus OBJECT-TYPE
		SYNTAX INTEGER {
			idle(0),
			charging(1),
			discharging(2),
			balance(3) }
		MAX-ACCESS read-only
		STATUS current
		DESCRIPTION
		"upsIta2com189Addr1Batstatus status."
		::= { upsIta2comEntry 191 }
upsIta2com191Addr1lithiumBatvoltage OBJECT-TYPE
		SYNTAX Integer32
		
		MAX-ACCESS read-only
		STATUS current
		DESCRIPTION
		"upsIta2com190Addr1lithiumBatvoltage stored as 0.01V."
		::= { upsIta2comEntry 192 }
upsIta2com192Addr1lithiumBatcurrent OBJECT-TYPE
		SYNTAX Integer32
		
		MAX-ACCESS read-only
		STATUS current
		DESCRIPTION
		"upsIta2com191Addr1lithiumBatcurrent stored as 0.01A."
		::= { upsIta2comEntry 193 }
upsIta2com193Addr1lithiumBatSOC OBJECT-TYPE
		SYNTAX Integer32
		
		MAX-ACCESS read-only
		STATUS current
		DESCRIPTION
		"upsIta2com192Addr1lithiumBatSOC stored as 0.01%."
		::= { upsIta2comEntry 194 }
upsIta2com194Addr1lithiumBatSOH OBJECT-TYPE
		SYNTAX Integer32
		
		MAX-ACCESS read-only
		STATUS current
		DESCRIPTION
		"upsIta2com193Addr1lithiumBatSOH stored as 0.01%."
		::= { upsIta2comEntry 195 }
upsIta2com195Addr1lithiumBatcellmaxvoltage OBJECT-TYPE
		SYNTAX Integer32
		
		MAX-ACCESS read-only
		STATUS current
		DESCRIPTION
		"upsIta2com194Addr1lithiumBatcellmaxvoltage stored as 0.01mV."
		::= { upsIta2comEntry 196 }
upsIta2com196Addr1lithiumBatcellminvoltage OBJECT-TYPE
		SYNTAX Integer32
		
		MAX-ACCESS read-only
		STATUS current
		DESCRIPTION
		"upsIta2com195Addr1lithiumBatcellminvoltage stored as 0.01mV."
		::= { upsIta2comEntry 197 }
upsIta2com197Addr1lithiumBatcellmaxtemp OBJECT-TYPE
		SYNTAX Integer32
		
		MAX-ACCESS read-only
		STATUS current
		DESCRIPTION
		"upsIta2com196Addr1lithiumBatcellmaxtemp stored as 0.01℃."
		::= { upsIta2comEntry 198 }
upsIta2com198Addr1lithiumBatcellmintemp OBJECT-TYPE
		SYNTAX Integer32
		
		MAX-ACCESS read-only
		STATUS current
		DESCRIPTION
		"upsIta2com197Addr1lithiumBatcellmintemp stored as 0.01℃."
		::= { upsIta2comEntry 199 }
upsIta2com199Addr2Batstatus OBJECT-TYPE
		SYNTAX INTEGER {
			idle(0),
			charging(1),
			discharging(2),
			balance(3) }
		MAX-ACCESS read-only
		STATUS current
		DESCRIPTION
		"upsIta2com198Addr2Batstatus status."
		::= { upsIta2comEntry 200 }
upsIta2com200Addr2lithiumBatvoltage OBJECT-TYPE
		SYNTAX Integer32
		
		MAX-ACCESS read-only
		STATUS current
		DESCRIPTION
		"upsIta2com199Addr2lithiumBatvoltage stored as 0.01V."
		::= { upsIta2comEntry 201 }
upsIta2com201Addr2lithiumBatcurrent OBJECT-TYPE
		SYNTAX Integer32
		
		MAX-ACCESS read-only
		STATUS current
		DESCRIPTION
		"upsIta2com200Addr2lithiumBatcurrent stored as 0.01A."
		::= { upsIta2comEntry 202 }
upsIta2com202Addr2lithiumBatSOC OBJECT-TYPE
		SYNTAX Integer32
		
		MAX-ACCESS read-only
		STATUS current
		DESCRIPTION
		"upsIta2com201Addr2lithiumBatSOC stored as 0.01%."
		::= { upsIta2comEntry 203 }
upsIta2com203Addr2lithiumBatSOH OBJECT-TYPE
		SYNTAX Integer32
		
		MAX-ACCESS read-only
		STATUS current
		DESCRIPTION
		"upsIta2com202Addr2lithiumBatSOH stored as 0.01%."
		::= { upsIta2comEntry 204 }
upsIta2com204Addr2lithiumBatcellmaxvoltage OBJECT-TYPE
		SYNTAX Integer32
		
		MAX-ACCESS read-only
		STATUS current
		DESCRIPTION
		"upsIta2com203Addr2lithiumBatcellmaxvoltage stored as 0.01mV."
		::= { upsIta2comEntry 205 }
upsIta2com205Addr2lithiumBatcellminvoltage OBJECT-TYPE
		SYNTAX Integer32
		
		MAX-ACCESS read-only
		STATUS current
		DESCRIPTION
		"upsIta2com204Addr2lithiumBatcellminvoltage stored as 0.01mV."
		::= { upsIta2comEntry 206 }
upsIta2com206Addr2lithiumBatcellmaxtemp OBJECT-TYPE
		SYNTAX Integer32
		
		MAX-ACCESS read-only
		STATUS current
		DESCRIPTION
		"upsIta2com205Addr2lithiumBatcellmaxtemp stored as 0.01℃."
		::= { upsIta2comEntry 207 }
upsIta2com207Addr2lithiumBatcellmintemp OBJECT-TYPE
		SYNTAX Integer32
		
		MAX-ACCESS read-only
		STATUS current
		DESCRIPTION
		"upsIta2com206Addr2lithiumBatcellmintemp stored as 0.01℃."
		::= { upsIta2comEntry 208 }
upsIta2com208Addr3Batstatus OBJECT-TYPE
		SYNTAX INTEGER {
			idle(0),
			charging(1),
			discharging(2),
			balance(3) }
		MAX-ACCESS read-only
		STATUS current
		DESCRIPTION
		"upsIta2com207Addr3Batstatus status."
		::= { upsIta2comEntry 209 }
upsIta2com209Addr3lithiumBatvoltage OBJECT-TYPE
		SYNTAX Integer32
		
		MAX-ACCESS read-only
		STATUS current
		DESCRIPTION
		"upsIta2com208Addr3lithiumBatvoltage stored as 0.01V."
		::= { upsIta2comEntry 210 }
upsIta2com210Addr3lithiumBatcurrent OBJECT-TYPE
		SYNTAX Integer32
		
		MAX-ACCESS read-only
		STATUS current
		DESCRIPTION
		"upsIta2com209Addr3lithiumBatcurrent stored as 0.01A."
		::= { upsIta2comEntry 211 }
upsIta2com211Addr3lithiumBatSOC OBJECT-TYPE
		SYNTAX Integer32
		
		MAX-ACCESS read-only
		STATUS current
		DESCRIPTION
		"upsIta2com210Addr3lithiumBatSOC stored as 0.01%."
		::= { upsIta2comEntry 212 }
upsIta2com212Addr3lithiumBatSOH OBJECT-TYPE
		SYNTAX Integer32
		
		MAX-ACCESS read-only
		STATUS current
		DESCRIPTION
		"upsIta2com211Addr3lithiumBatSOH stored as 0.01%."
		::= { upsIta2comEntry 213 }
upsIta2com213Addr3lithiumBatcellmaxvoltage OBJECT-TYPE
		SYNTAX Integer32
		
		MAX-ACCESS read-only
		STATUS current
		DESCRIPTION
		"upsIta2com212Addr3lithiumBatcellmaxvoltage stored as 0.01mV."
		::= { upsIta2comEntry 214 }
upsIta2com214Addr3lithiumBatcellminvoltage OBJECT-TYPE
		SYNTAX Integer32
		
		MAX-ACCESS read-only
		STATUS current
		DESCRIPTION
		"upsIta2com213Addr3lithiumBatcellminvoltage stored as 0.01mV."
		::= { upsIta2comEntry 215 }
upsIta2com215Addr3lithiumBatcellmaxtemp OBJECT-TYPE
		SYNTAX Integer32
		
		MAX-ACCESS read-only
		STATUS current
		DESCRIPTION
		"upsIta2com214Addr3lithiumBatcellmaxtemp stored as 0.01℃."
		::= { upsIta2comEntry 216 }
upsIta2com216Addr3lithiumBatcellmintemp OBJECT-TYPE
		SYNTAX Integer32
		
		MAX-ACCESS read-only
		STATUS current
		DESCRIPTION
		"upsIta2com215Addr3lithiumBatcellmintemp stored as 0.01℃."
		::= { upsIta2comEntry 217 }
upsIta2com217Addr4Batstatus OBJECT-TYPE
		SYNTAX INTEGER {
			idle(0),
			charging(1),
			discharging(2),
			balance(3) }
		MAX-ACCESS read-only
		STATUS current
		DESCRIPTION
		"upsIta2com216Addr4Batstatus status."
		::= { upsIta2comEntry 218 }
upsIta2com218Addr4lithiumBatvoltage OBJECT-TYPE
		SYNTAX Integer32
		
		MAX-ACCESS read-only
		STATUS current
		DESCRIPTION
		"upsIta2com217Addr4lithiumBatvoltage stored as 0.01V."
		::= { upsIta2comEntry 219 }
upsIta2com219Addr4lithiumBatcurrent OBJECT-TYPE
		SYNTAX Integer32
		
		MAX-ACCESS read-only
		STATUS current
		DESCRIPTION
		"upsIta2com218Addr4lithiumBatcurrent stored as 0.01A."
		::= { upsIta2comEntry 220 }
upsIta2com220Addr4lithiumBatSOC OBJECT-TYPE
		SYNTAX Integer32
		
		MAX-ACCESS read-only
		STATUS current
		DESCRIPTION
		"upsIta2com219Addr4lithiumBatSOC stored as 0.01%."
		::= { upsIta2comEntry 221 }
upsIta2com221Addr4lithiumBatSOH OBJECT-TYPE
		SYNTAX Integer32
		
		MAX-ACCESS read-only
		STATUS current
		DESCRIPTION
		"upsIta2com220Addr4lithiumBatSOH stored as 0.01%."
		::= { upsIta2comEntry 222 }
upsIta2com222Addr4lithiumBatcellmaxvoltage OBJECT-TYPE
		SYNTAX Integer32
		
		MAX-ACCESS read-only
		STATUS current
		DESCRIPTION
		"upsIta2com221Addr4lithiumBatcellmaxvoltage stored as 0.01mV."
		::= { upsIta2comEntry 223 }
upsIta2com223Addr4lithiumBatcellminvoltage OBJECT-TYPE
		SYNTAX Integer32
		
		MAX-ACCESS read-only
		STATUS current
		DESCRIPTION
		"upsIta2com222Addr4lithiumBatcellminvoltage stored as 0.01mV."
		::= { upsIta2comEntry 224 }
upsIta2com224Addr4lithiumBatcellmaxtemp OBJECT-TYPE
		SYNTAX Integer32
		
		MAX-ACCESS read-only
		STATUS current
		DESCRIPTION
		"upsIta2com223Addr4lithiumBatcellmaxtemp stored as 0.01℃."
		::= { upsIta2comEntry 225 }
upsIta2com225Addr4lithiumBatcellmintemp OBJECT-TYPE
		SYNTAX Integer32
		
		MAX-ACCESS read-only
		STATUS current
		DESCRIPTION
		"upsIta2com224Addr4lithiumBatcellmintemp stored as 0.01℃."
		::= { upsIta2comEntry 226 }
upsIta2com226Addr5Batstatus OBJECT-TYPE
		SYNTAX INTEGER {
			idle(0),
			charging(1),
			discharging(2),
			balance(3) }
		MAX-ACCESS read-only
		STATUS current
		DESCRIPTION
		"upsIta2com225Addr5Batstatus status."
		::= { upsIta2comEntry 227 }
upsIta2com227Addr5lithiumBatvoltage OBJECT-TYPE
		SYNTAX Integer32
		
		MAX-ACCESS read-only
		STATUS current
		DESCRIPTION
		"upsIta2com226Addr5lithiumBatvoltage stored as 0.01V."
		::= { upsIta2comEntry 228 }
upsIta2com228Addr5LithiumBatCurrent OBJECT-TYPE
		SYNTAX Integer32
		
		MAX-ACCESS read-only
		STATUS current
		DESCRIPTION
		"upsIta2com227Addr5LithiumBatCurrent stored as 0.01A."
		::= { upsIta2comEntry 229 }
upsIta2com229Addr5lithiumBatSOC OBJECT-TYPE
		SYNTAX Integer32
		
		MAX-ACCESS read-only
		STATUS current
		DESCRIPTION
		"upsIta2com228Addr5lithiumBatSOC stored as 0.01%."
		::= { upsIta2comEntry 230 }
upsIta2com230Addr5lithiumBatSOH OBJECT-TYPE
		SYNTAX Integer32
		
		MAX-ACCESS read-only
		STATUS current
		DESCRIPTION
		"upsIta2com229Addr5lithiumBatSOH stored as 0.01%."
		::= { upsIta2comEntry 231 }
upsIta2com231Addr5lithiumBatcellmaxvoltage OBJECT-TYPE
		SYNTAX Integer32
		
		MAX-ACCESS read-only
		STATUS current
		DESCRIPTION
		"upsIta2com230Addr5lithiumBatcellmaxvoltage stored as 0.01mV."
		::= { upsIta2comEntry 232 }
upsIta2com232Addr5lithiumBatcellminvoltage OBJECT-TYPE
		SYNTAX Integer32
		
		MAX-ACCESS read-only
		STATUS current
		DESCRIPTION
		"upsIta2com231Addr5lithiumBatcellminvoltage stored as 0.01mV."
		::= { upsIta2comEntry 233 }
upsIta2com233Addr5lithiumBatcellmaxtemp OBJECT-TYPE
		SYNTAX Integer32
		
		MAX-ACCESS read-only
		STATUS current
		DESCRIPTION
		"upsIta2com232Addr5lithiumBatcellmaxtemp stored as 0.01℃."
		::= { upsIta2comEntry 234 }
upsIta2com234Addr5lithiumBatcellmintemp OBJECT-TYPE
		SYNTAX Integer32
		
		MAX-ACCESS read-only
		STATUS current
		DESCRIPTION
		"upsIta2com233Addr5lithiumBatcellmintemp stored as 0.01℃."
		::= { upsIta2comEntry 235 }
upsIta2com235Addr6Batstatus OBJECT-TYPE
		SYNTAX INTEGER {
			idle(0),
			charging(1),
			discharging(2),
			balance(3) }
		MAX-ACCESS read-only
		STATUS current
		DESCRIPTION
		"upsIta2com234Addr6Batstatus status."
		::= { upsIta2comEntry 236 }
upsIta2com236Addr6lithiumBatvoltage OBJECT-TYPE
		SYNTAX Integer32
		
		MAX-ACCESS read-only
		STATUS current
		DESCRIPTION
		"upsIta2com235Addr6lithiumBatvoltage stored as 0.01V."
		::= { upsIta2comEntry 237 }
upsIta2com237Addr6lithiumBatcurrent OBJECT-TYPE
		SYNTAX Integer32
		
		MAX-ACCESS read-only
		STATUS current
		DESCRIPTION
		"upsIta2com236Addr6lithiumBatcurrent stored as 0.01A."
		::= { upsIta2comEntry 238 }
upsIta2com238Addr6lithiumBatSOC OBJECT-TYPE
		SYNTAX Integer32
		
		MAX-ACCESS read-only
		STATUS current
		DESCRIPTION
		"upsIta2com237Addr6lithiumBatSOC stored as 0.01%."
		::= { upsIta2comEntry 239 }
upsIta2com239Addr6lithiumBatSOH OBJECT-TYPE
		SYNTAX Integer32
		
		MAX-ACCESS read-only
		STATUS current
		DESCRIPTION
		"upsIta2com238Addr6lithiumBatSOH stored as 0.01%."
		::= { upsIta2comEntry 240 }
upsIta2com240Addr6lithiumBatcellmaxvoltage OBJECT-TYPE
		SYNTAX Integer32
		
		MAX-ACCESS read-only
		STATUS current
		DESCRIPTION
		"upsIta2com239Addr6lithiumBatcellmaxvoltage stored as 0.01mV."
		::= { upsIta2comEntry 241 }
upsIta2com241Addr6lithiumBatcellminvoltage OBJECT-TYPE
		SYNTAX Integer32
		
		MAX-ACCESS read-only
		STATUS current
		DESCRIPTION
		"upsIta2com240Addr6lithiumBatcellminvoltage stored as 0.01mV."
		::= { upsIta2comEntry 242 }
upsIta2com242Addr6lithiumBatcellmaxtemp OBJECT-TYPE
		SYNTAX Integer32
		
		MAX-ACCESS read-only
		STATUS current
		DESCRIPTION
		"upsIta2com241Addr6lithiumBatcellmaxtemp stored as 0.01℃."
		::= { upsIta2comEntry 243 }
upsIta2com243Addr6lithiumBatcellmintemp OBJECT-TYPE
		SYNTAX Integer32
		
		MAX-ACCESS read-only
		STATUS current
		DESCRIPTION
		"upsIta2com242Addr6lithiumBatcellmintemp stored as 0.01℃."
		::= { upsIta2comEntry 244 }
upsIta2com244Addr7Batstatus OBJECT-TYPE
		SYNTAX INTEGER {
			idle(0),
			charging(1),
			discharging(2),
			balance(3) }
		MAX-ACCESS read-only
		STATUS current
		DESCRIPTION
		"upsIta2com243Addr7Batstatus status."
		::= { upsIta2comEntry 245 }
upsIta2com245Addr7lithiumBatvoltage OBJECT-TYPE
		SYNTAX Integer32
		
		MAX-ACCESS read-only
		STATUS current
		DESCRIPTION
		"upsIta2com244Addr7lithiumBatvoltage stored as 0.01V."
		::= { upsIta2comEntry 246 }
upsIta2com246Addr7lithiumBatcurrent OBJECT-TYPE
		SYNTAX Integer32
		
		MAX-ACCESS read-only
		STATUS current
		DESCRIPTION
		"upsIta2com245Addr7lithiumBatcurrent stored as 0.01A."
		::= { upsIta2comEntry 247 }
upsIta2com247Addr7lithiumBatSOC OBJECT-TYPE
		SYNTAX Integer32
		
		MAX-ACCESS read-only
		STATUS current
		DESCRIPTION
		"upsIta2com246Addr7lithiumBatSOC stored as 0.01%."
		::= { upsIta2comEntry 248 }
upsIta2com248Addr7lithiumBatSOH OBJECT-TYPE
		SYNTAX Integer32
		
		MAX-ACCESS read-only
		STATUS current
		DESCRIPTION
		"upsIta2com247Addr7lithiumBatSOH stored as 0.01%."
		::= { upsIta2comEntry 249 }
upsIta2com249Addr7lithiumBatcellmaxvoltage OBJECT-TYPE
		SYNTAX Integer32
		
		MAX-ACCESS read-only
		STATUS current
		DESCRIPTION
		"upsIta2com248Addr7lithiumBatcellmaxvoltage stored as 0.01mV."
		::= { upsIta2comEntry 250 }
upsIta2com250Addr7lithiumBatcellminvoltage OBJECT-TYPE
		SYNTAX Integer32
		
		MAX-ACCESS read-only
		STATUS current
		DESCRIPTION
		"upsIta2com249Addr7lithiumBatcellminvoltage stored as 0.01mV."
		::= { upsIta2comEntry 251 }
upsIta2com251Addr7lithiumBatcellmaxtemp OBJECT-TYPE
		SYNTAX Integer32
		
		MAX-ACCESS read-only
		STATUS current
		DESCRIPTION
		"upsIta2com250Addr7lithiumBatcellmaxtemp stored as 0.01℃."
		::= { upsIta2comEntry 252 }
upsIta2com252Addr7lithiumBatcellmintemp OBJECT-TYPE
		SYNTAX Integer32
		
		MAX-ACCESS read-only
		STATUS current
		DESCRIPTION
		"upsIta2com251Addr7lithiumBatcellmintemp stored as 0.01℃."
		::= { upsIta2comEntry 253 }
upsIta2com253Addr8Batstatus OBJECT-TYPE
		SYNTAX INTEGER {
			idle(0),
			charging(1),
			discharging(2),
			balance(3) }
		MAX-ACCESS read-only
		STATUS current
		DESCRIPTION
		"upsIta2com252Addr8Batstatus status."
		::= { upsIta2comEntry 254 }
upsIta2com254Addr8lithiumBatvoltage OBJECT-TYPE
		SYNTAX Integer32
		
		MAX-ACCESS read-only
		STATUS current
		DESCRIPTION
		"upsIta2com253Addr8lithiumBatvoltage stored as 0.01V."
		::= { upsIta2comEntry 255 }
upsIta2com255Addr8lithiumBatcurrent OBJECT-TYPE
		SYNTAX Integer32
		
		MAX-ACCESS read-only
		STATUS current
		DESCRIPTION
		"upsIta2com254Addr8lithiumBatcurrent stored as 0.01A."
		::= { upsIta2comEntry 256 }
upsIta2com256Addr8lithiumBatSOC OBJECT-TYPE
		SYNTAX Integer32
		
		MAX-ACCESS read-only
		STATUS current
		DESCRIPTION
		"upsIta2com255Addr8lithiumBatSOC stored as 0.01%."
		::= { upsIta2comEntry 257 }
upsIta2com257Addr8lithiumBatSOH OBJECT-TYPE
		SYNTAX Integer32
		
		MAX-ACCESS read-only
		STATUS current
		DESCRIPTION
		"upsIta2com256Addr8lithiumBatSOH stored as 0.01%."
		::= { upsIta2comEntry 258 }
upsIta2com258Addr8lithiumBatcellmaxvoltage OBJECT-TYPE
		SYNTAX Integer32
		
		MAX-ACCESS read-only
		STATUS current
		DESCRIPTION
		"upsIta2com257Addr8lithiumBatcellmaxvoltage stored as 0.01mV."
		::= { upsIta2comEntry 259 }
upsIta2com259Addr8lithiumBatcellminvoltage OBJECT-TYPE
		SYNTAX Integer32
		
		MAX-ACCESS read-only
		STATUS current
		DESCRIPTION
		"upsIta2com258Addr8lithiumBatcellminvoltage stored as 0.01mV."
		::= { upsIta2comEntry 260 }
upsIta2com260Addr8lithiumBatcellmaxtemp OBJECT-TYPE
		SYNTAX Integer32
		
		MAX-ACCESS read-only
		STATUS current
		DESCRIPTION
		"upsIta2com259Addr8lithiumBatcellmaxtemp stored as 0.01℃."
		::= { upsIta2comEntry 261 }
upsIta2com261Addr8lithiumBatcellmintemp OBJECT-TYPE
		SYNTAX Integer32
		
		MAX-ACCESS read-only
		STATUS current
		DESCRIPTION
		"upsIta2com260Addr8lithiumBatcellmintemp stored as 0.01℃."
		::= { upsIta2comEntry 262 }
upsIta2com262Addr9Batstatus OBJECT-TYPE
		SYNTAX INTEGER {
			idle(0),
			charging(1),
			discharging(2),
			balance(3) }
		MAX-ACCESS read-only
		STATUS current
		DESCRIPTION
		"upsIta2com261Addr9Batstatus status."
		::= { upsIta2comEntry 263 }
upsIta2com263Addr9lithiumBatvoltage OBJECT-TYPE
		SYNTAX Integer32
		
		MAX-ACCESS read-only
		STATUS current
		DESCRIPTION
		"upsIta2com262Addr9lithiumBatvoltage stored as 0.01V."
		::= { upsIta2comEntry 264 }
upsIta2com264Addr9lithiumBatcurrent OBJECT-TYPE
		SYNTAX Integer32
		
		MAX-ACCESS read-only
		STATUS current
		DESCRIPTION
		"upsIta2com263Addr9lithiumBatcurrent stored as 0.01A."
		::= { upsIta2comEntry 265 }
upsIta2com265Addr9lithiumBatSOC OBJECT-TYPE
		SYNTAX Integer32
		
		MAX-ACCESS read-only
		STATUS current
		DESCRIPTION
		"upsIta2com264Addr9lithiumBatSOC stored as 0.01%."
		::= { upsIta2comEntry 266 }
upsIta2com266Addr9lithiumBatSOH OBJECT-TYPE
		SYNTAX Integer32
		
		MAX-ACCESS read-only
		STATUS current
		DESCRIPTION
		"upsIta2com265Addr9lithiumBatSOH stored as 0.01%."
		::= { upsIta2comEntry 267 }
upsIta2com267Addr9lithiumBatcellmaxvoltage OBJECT-TYPE
		SYNTAX Integer32
		
		MAX-ACCESS read-only
		STATUS current
		DESCRIPTION
		"upsIta2com266Addr9lithiumBatcellmaxvoltage stored as 0.01mV."
		::= { upsIta2comEntry 268 }
upsIta2com268Addr9lithiumBatcellminvoltage OBJECT-TYPE
		SYNTAX Integer32
		
		MAX-ACCESS read-only
		STATUS current
		DESCRIPTION
		"upsIta2com267Addr9lithiumBatcellminvoltage stored as 0.01mV."
		::= { upsIta2comEntry 269 }
upsIta2com269Addr9lithiumBatcellmaxtemp OBJECT-TYPE
		SYNTAX Integer32
		
		MAX-ACCESS read-only
		STATUS current
		DESCRIPTION
		"upsIta2com268Addr9lithiumBatcellmaxtemp stored as 0.01℃."
		::= { upsIta2comEntry 270 }
upsIta2com270Addr9lithiumBatcellmintemp OBJECT-TYPE
		SYNTAX Integer32
		
		MAX-ACCESS read-only
		STATUS current
		DESCRIPTION
		"upsIta2com269Addr9lithiumBatcellmintemp stored as 0.01℃."
		::= { upsIta2comEntry 271 }
upsIta2com271Addr10Batstatus OBJECT-TYPE
		SYNTAX INTEGER {
			idle(0),
			charging(1),
			discharging(2),
			balance(3) }
		MAX-ACCESS read-only
		STATUS current
		DESCRIPTION
		"upsIta2com270Addr10Batstatus status."
		::= { upsIta2comEntry 272 }
upsIta2com272Addr10lithiumBatvoltage OBJECT-TYPE
		SYNTAX Integer32
		
		MAX-ACCESS read-only
		STATUS current
		DESCRIPTION
		"upsIta2com271Addr10lithiumBatvoltage stored as 0.01V."
		::= { upsIta2comEntry 273 }
upsIta2com273Addr10lithiumBatcurrent OBJECT-TYPE
		SYNTAX Integer32
		
		MAX-ACCESS read-only
		STATUS current
		DESCRIPTION
		"upsIta2com272Addr10lithiumBatcurrent stored as 0.01A."
		::= { upsIta2comEntry 274 }
upsIta2com274Addr10lithiumBatSOC OBJECT-TYPE
		SYNTAX Integer32
		
		MAX-ACCESS read-only
		STATUS current
		DESCRIPTION
		"upsIta2com273Addr10lithiumBatSOC stored as 0.01%."
		::= { upsIta2comEntry 275 }
upsIta2com275Addr10lithiumBatSOH OBJECT-TYPE
		SYNTAX Integer32
		
		MAX-ACCESS read-only
		STATUS current
		DESCRIPTION
		"upsIta2com274Addr10lithiumBatSOH stored as 0.01%."
		::= { upsIta2comEntry 276 }
upsIta2com276Addr10lithiumBatcellmaxvoltage OBJECT-TYPE
		SYNTAX Integer32
		
		MAX-ACCESS read-only
		STATUS current
		DESCRIPTION
		"upsIta2com275Addr10lithiumBatcellmaxvoltage stored as 0.01mV."
		::= { upsIta2comEntry 277 }
upsIta2com277Addr10lithiumBatcellminvoltage OBJECT-TYPE
		SYNTAX Integer32
		
		MAX-ACCESS read-only
		STATUS current
		DESCRIPTION
		"upsIta2com276Addr10lithiumBatcellminvoltage stored as 0.01mV."
		::= { upsIta2comEntry 278 }
upsIta2com278Addr10lithiumBatcellmaxtemp OBJECT-TYPE
		SYNTAX Integer32
		
		MAX-ACCESS read-only
		STATUS current
		DESCRIPTION
		"upsIta2com277Addr10lithiumBatcellmaxtemp stored as 0.01℃."
		::= { upsIta2comEntry 279 }
upsIta2com279Addr10lithiumBatcellmintemp OBJECT-TYPE
		SYNTAX Integer32
		
		MAX-ACCESS read-only
		STATUS current
		DESCRIPTION
		"upsIta2com278Addr10lithiumBatcellmintemp stored as 0.01℃."
		::= { upsIta2comEntry 280 }
upsIta2com280Addr11Batstatus OBJECT-TYPE
		SYNTAX INTEGER {
			idle(0),
			charging(1),
			discharging(2),
			balance(3) }
		MAX-ACCESS read-only
		STATUS current
		DESCRIPTION
		"upsIta2com279Addr11Batstatus status."
		::= { upsIta2comEntry 281 }
upsIta2com281Addr11lithiumBatvoltage OBJECT-TYPE
		SYNTAX Integer32
		
		MAX-ACCESS read-only
		STATUS current
		DESCRIPTION
		"upsIta2com280Addr11lithiumBatvoltage stored as 0.01V."
		::= { upsIta2comEntry 282 }
upsIta2com282Addr11lithiumBatcurrent OBJECT-TYPE
		SYNTAX Integer32
		
		MAX-ACCESS read-only
		STATUS current
		DESCRIPTION
		"upsIta2com281Addr11lithiumBatcurrent stored as 0.01A."
		::= { upsIta2comEntry 283 }
upsIta2com283Addr11lithiumBatSOC OBJECT-TYPE
		SYNTAX Integer32
		
		MAX-ACCESS read-only
		STATUS current
		DESCRIPTION
		"upsIta2com282Addr11lithiumBatSOC stored as 0.01%."
		::= { upsIta2comEntry 284 }
upsIta2com284Addr11lithiumBatSOH OBJECT-TYPE
		SYNTAX Integer32
		
		MAX-ACCESS read-only
		STATUS current
		DESCRIPTION
		"upsIta2com283Addr11lithiumBatSOH stored as 0.01%."
		::= { upsIta2comEntry 285 }
upsIta2com285Addr11lithiumBatcellmaxvoltage OBJECT-TYPE
		SYNTAX Integer32
		
		MAX-ACCESS read-only
		STATUS current
		DESCRIPTION
		"upsIta2com284Addr11lithiumBatcellmaxvoltage stored as 0.01mV."
		::= { upsIta2comEntry 286 }
upsIta2com286Addr11lithiumBatcellminvoltage OBJECT-TYPE
		SYNTAX Integer32
		
		MAX-ACCESS read-only
		STATUS current
		DESCRIPTION
		"upsIta2com285Addr11lithiumBatcellminvoltage stored as 0.01mV."
		::= { upsIta2comEntry 287 }
upsIta2com287Addr11lithiumBatcellmaxtemp OBJECT-TYPE
		SYNTAX Integer32
		
		MAX-ACCESS read-only
		STATUS current
		DESCRIPTION
		"upsIta2com286Addr11lithiumBatcellmaxtemp stored as 0.01℃."
		::= { upsIta2comEntry 288 }
upsIta2com288Addr11lithiumBatcellmintemp OBJECT-TYPE
		SYNTAX Integer32
		
		MAX-ACCESS read-only
		STATUS current
		DESCRIPTION
		"upsIta2com287Addr11lithiumBatcellmintemp stored as 0.01℃."
		::= { upsIta2comEntry 289 }
upsIta2com289Addr12Batstatus OBJECT-TYPE
		SYNTAX INTEGER {
			idle(0),
			charging(1),
			discharging(2),
			balance(3) }
		MAX-ACCESS read-only
		STATUS current
		DESCRIPTION
		"upsIta2com288Addr12Batstatus status."
		::= { upsIta2comEntry 290 }
upsIta2com290Addr12lithiumBatvoltage OBJECT-TYPE
		SYNTAX Integer32
		
		MAX-ACCESS read-only
		STATUS current
		DESCRIPTION
		"upsIta2com289Addr12lithiumBatvoltage stored as 0.01V."
		::= { upsIta2comEntry 291 }
upsIta2com291Addr12lithiumBatcurrent OBJECT-TYPE
		SYNTAX Integer32
		
		MAX-ACCESS read-only
		STATUS current
		DESCRIPTION
		"upsIta2com290Addr12lithiumBatcurrent stored as 0.01A."
		::= { upsIta2comEntry 292 }
upsIta2com292Addr12lithiumBatSOC OBJECT-TYPE
		SYNTAX Integer32
		
		MAX-ACCESS read-only
		STATUS current
		DESCRIPTION
		"upsIta2com291Addr12lithiumBatSOC stored as 0.01%."
		::= { upsIta2comEntry 293 }
upsIta2com293Addr12lithiumBatSOH OBJECT-TYPE
		SYNTAX Integer32
		
		MAX-ACCESS read-only
		STATUS current
		DESCRIPTION
		"upsIta2com292Addr12lithiumBatSOH stored as 0.01%."
		::= { upsIta2comEntry 294 }
upsIta2com294Addr12lithiumBatcellmaxvoltage OBJECT-TYPE
		SYNTAX Integer32
		
		MAX-ACCESS read-only
		STATUS current
		DESCRIPTION
		"upsIta2com293Addr12lithiumBatcellmaxvoltage stored as 0.01mV."
		::= { upsIta2comEntry 295 }
upsIta2com295Addr12lithiumBatcellminvoltage OBJECT-TYPE
		SYNTAX Integer32
		
		MAX-ACCESS read-only
		STATUS current
		DESCRIPTION
		"upsIta2com294Addr12lithiumBatcellminvoltage stored as 0.01mV."
		::= { upsIta2comEntry 296 }
upsIta2com296Addr12lithiumBatcellmaxtemp OBJECT-TYPE
		SYNTAX Integer32
		
		MAX-ACCESS read-only
		STATUS current
		DESCRIPTION
		"upsIta2com295Addr12lithiumBatcellmaxtemp stored as 0.01℃."
		::= { upsIta2comEntry 297 }
upsIta2com297Addr12lithiumBatcellmintemp OBJECT-TYPE
		SYNTAX Integer32
		
		MAX-ACCESS read-only
		STATUS current
		DESCRIPTION
		"upsIta2com296Addr12lithiumBatcellmintemp stored as 0.01℃."
		::= { upsIta2comEntry 298 }
upsIta2com298Addr13Batstatus OBJECT-TYPE
		SYNTAX INTEGER {
			idle(0),
			charging(1),
			discharging(2),
			balance(3) }
		MAX-ACCESS read-only
		STATUS current
		DESCRIPTION
		"upsIta2com297Addr13Batstatus status."
		::= { upsIta2comEntry 299 }
upsIta2com299Addr13lithiumBatvoltage OBJECT-TYPE
		SYNTAX Integer32
		
		MAX-ACCESS read-only
		STATUS current
		DESCRIPTION
		"upsIta2com298Addr13lithiumBatvoltage stored as 0.01V."
		::= { upsIta2comEntry 300 }
upsIta2com300Addr13lithiumBatcurrent OBJECT-TYPE
		SYNTAX Integer32
		
		MAX-ACCESS read-only
		STATUS current
		DESCRIPTION
		"upsIta2com299Addr13lithiumBatcurrent stored as 0.01A."
		::= { upsIta2comEntry 301 }
upsIta2com301Addr13lithiumBatSOC OBJECT-TYPE
		SYNTAX Integer32
		
		MAX-ACCESS read-only
		STATUS current
		DESCRIPTION
		"upsIta2com300Addr13lithiumBatSOC stored as 0.01%."
		::= { upsIta2comEntry 302 }
upsIta2com302Addr13lithiumBatSOH OBJECT-TYPE
		SYNTAX Integer32
		
		MAX-ACCESS read-only
		STATUS current
		DESCRIPTION
		"upsIta2com301Addr13lithiumBatSOH stored as 0.01%."
		::= { upsIta2comEntry 303 }
upsIta2com303Addr13lithiumBatcellmaxvoltage OBJECT-TYPE
		SYNTAX Integer32
		
		MAX-ACCESS read-only
		STATUS current
		DESCRIPTION
		"upsIta2com302Addr13lithiumBatcellmaxvoltage stored as 0.01mV."
		::= { upsIta2comEntry 304 }
upsIta2com304Addr13lithiumBatcellminvoltage OBJECT-TYPE
		SYNTAX Integer32
		
		MAX-ACCESS read-only
		STATUS current
		DESCRIPTION
		"upsIta2com303Addr13lithiumBatcellminvoltage stored as 0.01mV."
		::= { upsIta2comEntry 305 }
upsIta2com305Addr13lithiumBatcellmaxtemp OBJECT-TYPE
		SYNTAX Integer32
		
		MAX-ACCESS read-only
		STATUS current
		DESCRIPTION
		"upsIta2com304Addr13lithiumBatcellmaxtemp stored as 0.01℃."
		::= { upsIta2comEntry 306 }
upsIta2com306Addr13lithiumBatcellmintemp OBJECT-TYPE
		SYNTAX Integer32
		
		MAX-ACCESS read-only
		STATUS current
		DESCRIPTION
		"upsIta2com305Addr13lithiumBatcellmintemp stored as 0.01℃."
		::= { upsIta2comEntry 307 }
upsIta2com307Addr14Batstatus OBJECT-TYPE
		SYNTAX INTEGER {
			idle(0),
			charging(1),
			discharging(2),
			balance(3) }
		MAX-ACCESS read-only
		STATUS current
		DESCRIPTION
		"upsIta2com306Addr14Batstatus status."
		::= { upsIta2comEntry 308 }
upsIta2com308Addr14lithiumBatvoltage OBJECT-TYPE
		SYNTAX Integer32
		
		MAX-ACCESS read-only
		STATUS current
		DESCRIPTION
		"upsIta2com307Addr14lithiumBatvoltage stored as 0.01V."
		::= { upsIta2comEntry 309 }
upsIta2com309Addr14LithiumBatCurrent OBJECT-TYPE
		SYNTAX Integer32
		
		MAX-ACCESS read-only
		STATUS current
		DESCRIPTION
		"upsIta2com308Addr14LithiumBatCurrent stored as 0.01A."
		::= { upsIta2comEntry 310 }
upsIta2com310Addr14lithiumBatSOC OBJECT-TYPE
		SYNTAX Integer32
		
		MAX-ACCESS read-only
		STATUS current
		DESCRIPTION
		"upsIta2com309Addr14lithiumBatSOC stored as 0.01%."
		::= { upsIta2comEntry 311 }
upsIta2com311Addr14lithiumBatSOH OBJECT-TYPE
		SYNTAX Integer32
		
		MAX-ACCESS read-only
		STATUS current
		DESCRIPTION
		"upsIta2com310Addr14lithiumBatSOH stored as 0.01%."
		::= { upsIta2comEntry 312 }
upsIta2com312Addr14lithiumBatcellmaxvoltage OBJECT-TYPE
		SYNTAX Integer32
		
		MAX-ACCESS read-only
		STATUS current
		DESCRIPTION
		"upsIta2com311Addr14lithiumBatcellmaxvoltage stored as 0.01mV."
		::= { upsIta2comEntry 313 }
upsIta2com313Addr14lithiumBatcellminvoltage OBJECT-TYPE
		SYNTAX Integer32
		
		MAX-ACCESS read-only
		STATUS current
		DESCRIPTION
		"upsIta2com312Addr14lithiumBatcellminvoltage stored as 0.01mV."
		::= { upsIta2comEntry 314 }
upsIta2com314Addr14lithiumBatcellmaxtemp OBJECT-TYPE
		SYNTAX Integer32
		
		MAX-ACCESS read-only
		STATUS current
		DESCRIPTION
		"upsIta2com313Addr14lithiumBatcellmaxtemp stored as 0.01℃."
		::= { upsIta2comEntry 315 }
upsIta2com315Addr14lithiumBatcellmintemp OBJECT-TYPE
		SYNTAX Integer32
		
		MAX-ACCESS read-only
		STATUS current
		DESCRIPTION
		"upsIta2com314Addr14lithiumBatcellmintemp stored as 0.01℃."
		::= { upsIta2comEntry 316 }
upsIta2com316Addr15Batstatus OBJECT-TYPE
		SYNTAX INTEGER {
			idle(0),
			charging(1),
			discharging(2),
			balance(3) }
		MAX-ACCESS read-only
		STATUS current
		DESCRIPTION
		"upsIta2com315Addr15Batstatus status."
		::= { upsIta2comEntry 317 }
upsIta2com317Addr15lithiumBatvoltage OBJECT-TYPE
		SYNTAX Integer32
		
		MAX-ACCESS read-only
		STATUS current
		DESCRIPTION
		"upsIta2com316Addr15lithiumBatvoltage stored as 0.01V."
		::= { upsIta2comEntry 318 }
upsIta2com318Addr15lithiumBatcurrent OBJECT-TYPE
		SYNTAX Integer32
		
		MAX-ACCESS read-only
		STATUS current
		DESCRIPTION
		"upsIta2com317Addr15lithiumBatcurrent stored as 0.01A."
		::= { upsIta2comEntry 319 }
upsIta2com319Addr15lithiumBatSOC OBJECT-TYPE
		SYNTAX Integer32
		
		MAX-ACCESS read-only
		STATUS current
		DESCRIPTION
		"upsIta2com318Addr15lithiumBatSOC stored as 0.01%."
		::= { upsIta2comEntry 320 }
upsIta2com320Addr15lithiumBatSOH OBJECT-TYPE
		SYNTAX Integer32
		
		MAX-ACCESS read-only
		STATUS current
		DESCRIPTION
		"upsIta2com319Addr15lithiumBatSOH stored as 0.01%."
		::= { upsIta2comEntry 321 }
upsIta2com321Addr15lithiumBatcellmaxvoltage OBJECT-TYPE
		SYNTAX Integer32
		
		MAX-ACCESS read-only
		STATUS current
		DESCRIPTION
		"upsIta2com320Addr15lithiumBatcellmaxvoltage stored as 0.01mV."
		::= { upsIta2comEntry 322 }
upsIta2com322Addr15lithiumBatcellminvoltage OBJECT-TYPE
		SYNTAX Integer32
		
		MAX-ACCESS read-only
		STATUS current
		DESCRIPTION
		"upsIta2com321Addr15lithiumBatcellminvoltage stored as 0.01mV."
		::= { upsIta2comEntry 323 }
upsIta2com323Addr15lithiumBatcellmaxtemp OBJECT-TYPE
		SYNTAX Integer32
		
		MAX-ACCESS read-only
		STATUS current
		DESCRIPTION
		"upsIta2com322Addr15lithiumBatcellmaxtemp stored as 0.01℃."
		::= { upsIta2comEntry 324 }
upsIta2com324Addr15lithiumBatcellmintemp OBJECT-TYPE
		SYNTAX Integer32
		
		MAX-ACCESS read-only
		STATUS current
		DESCRIPTION
		"upsIta2com323Addr15lithiumBatcellmintemp stored as 0.01℃."
		::= { upsIta2comEntry 325 }
upsIta2com325Addr16Batstatus OBJECT-TYPE
		SYNTAX INTEGER {
			idle(0),
			charging(1),
			discharging(2),
			balance(3) }
		MAX-ACCESS read-only
		STATUS current
		DESCRIPTION
		"upsIta2com324Addr16Batstatus status."
		::= { upsIta2comEntry 326 }
upsIta2com326Addr16lithiumBatvoltage OBJECT-TYPE
		SYNTAX Integer32
		
		MAX-ACCESS read-only
		STATUS current
		DESCRIPTION
		"upsIta2com325Addr16lithiumBatvoltage stored as 0.01V."
		::= { upsIta2comEntry 327 }
upsIta2com327Addr16lithiumBatcurrent OBJECT-TYPE
		SYNTAX Integer32
		
		MAX-ACCESS read-only
		STATUS current
		DESCRIPTION
		"upsIta2com326Addr16lithiumBatcurrent stored as 0.01A."
		::= { upsIta2comEntry 328 }
upsIta2com328Addr16lithiumBatSOC OBJECT-TYPE
		SYNTAX Integer32
		
		MAX-ACCESS read-only
		STATUS current
		DESCRIPTION
		"upsIta2com327Addr16lithiumBatSOC stored as 0.01%."
		::= { upsIta2comEntry 329 }
upsIta2com329Addr16lithiumBatSOH OBJECT-TYPE
		SYNTAX Integer32
		
		MAX-ACCESS read-only
		STATUS current
		DESCRIPTION
		"upsIta2com328Addr16lithiumBatSOH stored as 0.01%."
		::= { upsIta2comEntry 330 }
upsIta2com330Addr16lithiumBatcellmaxvoltage OBJECT-TYPE
		SYNTAX Integer32
		
		MAX-ACCESS read-only
		STATUS current
		DESCRIPTION
		"upsIta2com329Addr16lithiumBatcellmaxvoltage stored as 0.01mV."
		::= { upsIta2comEntry 331 }
upsIta2com331Addr16lithiumBatcellminvoltage OBJECT-TYPE
		SYNTAX Integer32
		
		MAX-ACCESS read-only
		STATUS current
		DESCRIPTION
		"upsIta2com330Addr16lithiumBatcellminvoltage stored as 0.01mV."
		::= { upsIta2comEntry 332 }
upsIta2com332Addr16lithiumBatcellmaxtemp OBJECT-TYPE
		SYNTAX Integer32
		
		MAX-ACCESS read-only
		STATUS current
		DESCRIPTION
		"upsIta2com331Addr16lithiumBatcellmaxtemp stored as 0.01℃."
		::= { upsIta2comEntry 333 }
upsIta2com333Addr16lithiumBatcellmintemp OBJECT-TYPE
		SYNTAX Integer32
		
		MAX-ACCESS read-only
		STATUS current
		DESCRIPTION
		"upsIta2com332Addr16lithiumBatcellmintemp stored as 0.01℃."
		::= { upsIta2comEntry 334 }
upsIta2com334Addr1Batalarmnumber OBJECT-TYPE
		SYNTAX Integer32
		
		MAX-ACCESS read-only
		STATUS current
		DESCRIPTION
		"upsIta2com333Addr1Batalarmnumber stored as 1."
		::= { upsIta2comEntry 335 }
upsIta2com335Addr1Bathighvolt OBJECT-TYPE
		SYNTAX INTEGER {
			normal(0),
			alarm(1) }
		MAX-ACCESS read-only
		STATUS current
		DESCRIPTION
		"upsIta2com334Addr1Bathighvolt status."
		::= { upsIta2comEntry 336 }
upsIta2com336Addr1Batlowvolt OBJECT-TYPE
		SYNTAX INTEGER {
			normal(0),
			alarm(1) }
		MAX-ACCESS read-only
		STATUS current
		DESCRIPTION
		"upsIta2com335Addr1Batlowvolt status."
		::= { upsIta2comEntry 337 }
upsIta2com337Addr1Bathighcellvolt OBJECT-TYPE
		SYNTAX INTEGER {
			normal(0),
			alarm(1) }
		MAX-ACCESS read-only
		STATUS current
		DESCRIPTION
		"upsIta2com336Addr1Bathighcellvolt status."
		::= { upsIta2comEntry 338 }
upsIta2com338Addr1Batlowcellvolt OBJECT-TYPE
		SYNTAX INTEGER {
			normal(0),
			alarm(1) }
		MAX-ACCESS read-only
		STATUS current
		DESCRIPTION
		"upsIta2com337Addr1Batlowcellvolt status."
		::= { upsIta2comEntry 339 }
upsIta2com339Addr1Batchargehighcelltemp OBJECT-TYPE
		SYNTAX INTEGER {
			normal(0),
			alarm(1) }
		MAX-ACCESS read-only
		STATUS current
		DESCRIPTION
		"upsIta2com338Addr1Batchargehighcelltemp status."
		::= { upsIta2comEntry 340 }
upsIta2com340Addr1Batchargelowcelltemp OBJECT-TYPE
		SYNTAX INTEGER {
			normal(0),
			alarm(1) }
		MAX-ACCESS read-only
		STATUS current
		DESCRIPTION
		"upsIta2com339Addr1Batchargelowcelltemp status."
		::= { upsIta2comEntry 341 }
upsIta2com341Addr1Batchargeovercurrent OBJECT-TYPE
		SYNTAX INTEGER {
			normal(0),
			alarm(1) }
		MAX-ACCESS read-only
		STATUS current
		DESCRIPTION
		"upsIta2com340Addr1Batchargeovercurrent status."
		::= { upsIta2comEntry 342 }
upsIta2com342Addr1Batdischargeovercurrent OBJECT-TYPE
		SYNTAX INTEGER {
			normal(0),
			alarm(1) }
		MAX-ACCESS read-only
		STATUS current
		DESCRIPTION
		"upsIta2com341Addr1Batdischargeovercurrent status."
		::= { upsIta2comEntry 343 }
upsIta2com343Addr1BatAddrconflict OBJECT-TYPE
		SYNTAX INTEGER {
			normal(0),
			alarm(1) }
		MAX-ACCESS read-only
		STATUS current
		DESCRIPTION
		"upsIta2com342Addr1BatAddrconflict status."
		::= { upsIta2comEntry 344 }
upsIta2com344Addr1Batportreverse OBJECT-TYPE
		SYNTAX INTEGER {
			normal(0),
			alarm(1) }
		MAX-ACCESS read-only
		STATUS current
		DESCRIPTION
		"upsIta2com343Addr1Batportreverse status."
		::= { upsIta2comEntry 345 }
upsIta2com345Addr1BatBMSrelayinvalid OBJECT-TYPE
		SYNTAX INTEGER {
			normal(0),
			alarm(1) }
		MAX-ACCESS read-only
		STATUS current
		DESCRIPTION
		"upsIta2com344Addr1BatBMSrelayinvalid status."
		::= { upsIta2comEntry 346 }
upsIta2com346Addr1Batsafetyundervoltage OBJECT-TYPE
		SYNTAX INTEGER {
			normal(0),
			alarm(1) }
		MAX-ACCESS read-only
		STATUS current
		DESCRIPTION
		"upsIta2com345Addr1Batsafetyundervoltage status."
		::= { upsIta2comEntry 347 }
upsIta2com347Addr1Batdischargehighcelltemp OBJECT-TYPE
		SYNTAX INTEGER {
			normal(0),
			alarm(1) }
		MAX-ACCESS read-only
		STATUS current
		DESCRIPTION
		"upsIta2com346Addr1Batdischargehighcelltemp status."
		::= { upsIta2comEntry 348 }
upsIta2com348Addr1Batdischargelowcelltemp OBJECT-TYPE
		SYNTAX INTEGER {
			normal(0),
			alarm(1) }
		MAX-ACCESS read-only
		STATUS current
		DESCRIPTION
		"upsIta2com347Addr1Batdischargelowcelltemp status."
		::= { upsIta2comEntry 349 }
upsIta2com349Addr1Batparallelchargehightemp OBJECT-TYPE
		SYNTAX INTEGER {
			normal(0),
			alarm(1) }
		MAX-ACCESS read-only
		STATUS current
		DESCRIPTION
		"upsIta2com348Addr1Batparallelchargehightemp status."
		::= { upsIta2comEntry 350 }
upsIta2com350Addr1BatinternalCommabnormal OBJECT-TYPE
		SYNTAX INTEGER {
			normal(0),
			alarm(1) }
		MAX-ACCESS read-only
		STATUS current
		DESCRIPTION
		"upsIta2com349Addr1BatinternalCommabnormal status."
		::= { upsIta2comEntry 351 }
upsIta2com351Addr1Batconditionfail OBJECT-TYPE
		SYNTAX INTEGER {
			normal(0),
			alarm(1) }
		MAX-ACCESS read-only
		STATUS current
		DESCRIPTION
		"upsIta2com350Addr1Batconditionfail status."
		::= { upsIta2comEntry 352 }
upsIta2com352Addr1BatLowinsulationresistance OBJECT-TYPE
		SYNTAX INTEGER {
			normal(0),
			alarm(1) }
		MAX-ACCESS read-only
		STATUS current
		DESCRIPTION
		"upsIta2com351Addr1BatLowinsulationresistance status."
		::= { upsIta2comEntry 353 }
upsIta2com353Addr1BatLargepressurediff OBJECT-TYPE
		SYNTAX INTEGER {
			normal(0),
			alarm(1) }
		MAX-ACCESS read-only
		STATUS current
		DESCRIPTION
		"upsIta2com352Addr1BatLargepressurediff status."
		::= { upsIta2comEntry 354 }
upsIta2com354Addr1BatBatfailure OBJECT-TYPE
		SYNTAX INTEGER {
			normal(0),
			alarm(1) }
		MAX-ACCESS read-only
		STATUS current
		DESCRIPTION
		"upsIta2com353Addr1BatBatfailure status."
		::= { upsIta2comEntry 355 }
upsIta2com355Addr1BatVoltageacquisitfailure OBJECT-TYPE
		SYNTAX INTEGER {
			normal(0),
			alarm(1) }
		MAX-ACCESS read-only
		STATUS current
		DESCRIPTION
		"upsIta2com354Addr1BatVoltageacquisitfailure status."
		::= { upsIta2comEntry 356 }
upsIta2com356Addr1BatCurrentcolllectfailure OBJECT-TYPE
		SYNTAX INTEGER {
			normal(0),
			alarm(1) }
		MAX-ACCESS read-only
		STATUS current
		DESCRIPTION
		"upsIta2com355Addr1BatCurrentcolllectfailure status."
		::= { upsIta2comEntry 357 }
upsIta2com357Addr1BatTempcolllectfailure OBJECT-TYPE
		SYNTAX INTEGER {
			normal(0),
			alarm(1) }
		MAX-ACCESS read-only
		STATUS current
		DESCRIPTION
		"upsIta2com356Addr1BatTempcolllectfailure status."
		::= { upsIta2comEntry 358 }
upsIta2com358Addr1BatAddrSeterror OBJECT-TYPE
		SYNTAX INTEGER {
			normal(0),
			alarm(1) }
		MAX-ACCESS read-only
		STATUS current
		DESCRIPTION
		"upsIta2com357Addr1BatAddrSeterror status."
		::= { upsIta2comEntry 359 }
upsIta2com359Addr1BatLargegrouppressurediff OBJECT-TYPE
		SYNTAX INTEGER {
			normal(0),
			alarm(1) }
		MAX-ACCESS read-only
		STATUS current
		DESCRIPTION
		"upsIta2com358Addr1BatLargegrouppressurediff status."
		::= { upsIta2comEntry 360 }
upsIta2com360Addr1BatMOSFETfailure OBJECT-TYPE
		SYNTAX INTEGER {
			normal(0),
			alarm(1) }
		MAX-ACCESS read-only
		STATUS current
		DESCRIPTION
		"upsIta2com359Addr1BatMOSFETfailure status."
		::= { upsIta2comEntry 361 }
upsIta2com361Addr1Battempabnormal OBJECT-TYPE
		SYNTAX INTEGER {
			normal(0),
			alarm(1) }
		MAX-ACCESS read-only
		STATUS current
		DESCRIPTION
		"upsIta2com360Addr1Battempabnormal status."
		::= { upsIta2comEntry 362 }
upsIta2com362Addr1Batcablefault OBJECT-TYPE
		SYNTAX INTEGER {
			normal(0),
			alarm(1) }
		MAX-ACCESS read-only
		STATUS current
		DESCRIPTION
		"upsIta2com361Addr1Batcablefault status."
		::= { upsIta2comEntry 363 }
upsIta2com363Addr1BatShortcircuit OBJECT-TYPE
		SYNTAX INTEGER {
			normal(0),
			alarm(1) }
		MAX-ACCESS read-only
		STATUS current
		DESCRIPTION
		"upsIta2com362Addr1BatShortcircuit status."
		::= { upsIta2comEntry 364 }
upsIta2com364Addr1BatOtherfailures OBJECT-TYPE
		SYNTAX INTEGER {
			normal(0),
			alarm(1) }
		MAX-ACCESS read-only
		STATUS current
		DESCRIPTION
		"upsIta2com363Addr1BatOtherfailures status."
		::= { upsIta2comEntry 365 }
upsIta2com365Addr1BatCommcablefailure OBJECT-TYPE
		SYNTAX INTEGER {
			normal(0),
			alarm(1) }
		MAX-ACCESS read-only
		STATUS current
		DESCRIPTION
		"upsIta2com364Addr1BatCommcablefailure status."
		::= { upsIta2comEntry 366 }
upsIta2com366Addr1BatMOSFETtempishigh OBJECT-TYPE
		SYNTAX INTEGER {
			normal(0),
			alarm(1) }
		MAX-ACCESS read-only
		STATUS current
		DESCRIPTION
		"upsIta2com365Addr1BatMOSFETtempishigh status."
		::= { upsIta2comEntry 367 }
upsIta2com367Addr1BatFuseblown OBJECT-TYPE
		SYNTAX INTEGER {
			normal(0),
			alarm(1) }
		MAX-ACCESS read-only
		STATUS current
		DESCRIPTION
		"upsIta2com366Addr1BatFuseblown status."
		::= { upsIta2comEntry 368 }
upsIta2com368Addr1BatWaitingforcharging OBJECT-TYPE
		SYNTAX INTEGER {
			normal(0),
			alarm(1) }
		MAX-ACCESS read-only
		STATUS current
		DESCRIPTION
		"upsIta2com367Addr1BatWaitingforcharging status."
		::= { upsIta2comEntry 369 }
upsIta2com369Addr1BatBataging OBJECT-TYPE
		SYNTAX INTEGER {
			normal(0),
			alarm(1) }
		MAX-ACCESS read-only
		STATUS current
		DESCRIPTION
		"upsIta2com368Addr1BatBataging status."
		::= { upsIta2comEntry 370 }
upsIta2com370Addr1Batboxconnectabnormal OBJECT-TYPE
		SYNTAX INTEGER {
			normal(0),
			alarm(1) }
		MAX-ACCESS read-only
		STATUS current
		DESCRIPTION
		"upsIta2com369Addr1Batboxconnectabnormal status."
		::= { upsIta2comEntry 371 }
upsIta2com371Addr1batBatterySoftincompatible OBJECT-TYPE
		SYNTAX INTEGER {
			normal(0),
			alarm(1) }
		MAX-ACCESS read-only
		STATUS current
		DESCRIPTION
		"upsIta2com370Addr1batBatterySoftincompatible status."
		::= { upsIta2comEntry 372 }
upsIta2com372Addr1batEOL OBJECT-TYPE
		SYNTAX INTEGER {
			normal(0),
			alarm(1) }
		MAX-ACCESS read-only
		STATUS current
		DESCRIPTION
		"upsIta2com371Addr1batEOL status."
		::= { upsIta2comEntry 373 }
upsIta2com373Addr1batSamplingfailure OBJECT-TYPE
		SYNTAX INTEGER {
			normal(0),
			alarm(1) }
		MAX-ACCESS read-only
		STATUS current
		DESCRIPTION
		"upsIta2com372Addr1batSamplingfailure status."
		::= { upsIta2comEntry 374 }
upsIta2com374Addr1batHardwareprotection OBJECT-TYPE
		SYNTAX INTEGER {
			normal(0),
			alarm(1) }
		MAX-ACCESS read-only
		STATUS current
		DESCRIPTION
		"upsIta2com373Addr1batHardwareprotection status."
		::= { upsIta2comEntry 375 }
upsIta2com375Addr1batBatterycapacitylow OBJECT-TYPE
		SYNTAX INTEGER {
			normal(0),
			alarm(1) }
		MAX-ACCESS read-only
		STATUS current
		DESCRIPTION
		"upsIta2com374Addr1batBatterycapacitylow status."
		::= { upsIta2comEntry 376 }
upsIta2com376Addr2Batalarmnumber OBJECT-TYPE
		SYNTAX Integer32
		
		MAX-ACCESS read-only
		STATUS current
		DESCRIPTION
		"upsIta2com375Addr2Batalarmnumber stored as 1."
		::= { upsIta2comEntry 377 }
upsIta2com377Addr2Bathighvolt OBJECT-TYPE
		SYNTAX INTEGER {
			normal(0),
			alarm(1) }
		MAX-ACCESS read-only
		STATUS current
		DESCRIPTION
		"upsIta2com376Addr2Bathighvolt status."
		::= { upsIta2comEntry 378 }
upsIta2com378Addr2Batlowvolt OBJECT-TYPE
		SYNTAX INTEGER {
			normal(0),
			alarm(1) }
		MAX-ACCESS read-only
		STATUS current
		DESCRIPTION
		"upsIta2com377Addr2Batlowvolt status."
		::= { upsIta2comEntry 379 }
upsIta2com379Addr2Bathighcellvolt OBJECT-TYPE
		SYNTAX INTEGER {
			normal(0),
			alarm(1) }
		MAX-ACCESS read-only
		STATUS current
		DESCRIPTION
		"upsIta2com378Addr2Bathighcellvolt status."
		::= { upsIta2comEntry 380 }
upsIta2com380Addr2Batlowcellvolt OBJECT-TYPE
		SYNTAX INTEGER {
			normal(0),
			alarm(1) }
		MAX-ACCESS read-only
		STATUS current
		DESCRIPTION
		"upsIta2com379Addr2Batlowcellvolt status."
		::= { upsIta2comEntry 381 }
upsIta2com381Addr2Batchargehighcelltemp OBJECT-TYPE
		SYNTAX INTEGER {
			normal(0),
			alarm(1) }
		MAX-ACCESS read-only
		STATUS current
		DESCRIPTION
		"upsIta2com380Addr2Batchargehighcelltemp status."
		::= { upsIta2comEntry 382 }
upsIta2com382Addr2Batchargelowcelltemp OBJECT-TYPE
		SYNTAX INTEGER {
			normal(0),
			alarm(1) }
		MAX-ACCESS read-only
		STATUS current
		DESCRIPTION
		"upsIta2com381Addr2Batchargelowcelltemp status."
		::= { upsIta2comEntry 383 }
upsIta2com383Addr2Batchargeovercurrent OBJECT-TYPE
		SYNTAX INTEGER {
			normal(0),
			alarm(1) }
		MAX-ACCESS read-only
		STATUS current
		DESCRIPTION
		"upsIta2com382Addr2Batchargeovercurrent status."
		::= { upsIta2comEntry 384 }
upsIta2com384Addr2Batdischargeovercurrent OBJECT-TYPE
		SYNTAX INTEGER {
			normal(0),
			alarm(1) }
		MAX-ACCESS read-only
		STATUS current
		DESCRIPTION
		"upsIta2com383Addr2Batdischargeovercurrent status."
		::= { upsIta2comEntry 385 }
upsIta2com385Addr2BatAddrconflict OBJECT-TYPE
		SYNTAX INTEGER {
			normal(0),
			alarm(1) }
		MAX-ACCESS read-only
		STATUS current
		DESCRIPTION
		"upsIta2com384Addr2BatAddrconflict status."
		::= { upsIta2comEntry 386 }
upsIta2com386Addr2Batportreverse OBJECT-TYPE
		SYNTAX INTEGER {
			normal(0),
			alarm(1) }
		MAX-ACCESS read-only
		STATUS current
		DESCRIPTION
		"upsIta2com385Addr2Batportreverse status."
		::= { upsIta2comEntry 387 }
upsIta2com387Addr2BatBMSrelayinvalid OBJECT-TYPE
		SYNTAX INTEGER {
			normal(0),
			alarm(1) }
		MAX-ACCESS read-only
		STATUS current
		DESCRIPTION
		"upsIta2com386Addr2BatBMSrelayinvalid status."
		::= { upsIta2comEntry 388 }
upsIta2com388Addr2Batsafetyundervoltage OBJECT-TYPE
		SYNTAX INTEGER {
			normal(0),
			alarm(1) }
		MAX-ACCESS read-only
		STATUS current
		DESCRIPTION
		"upsIta2com387Addr2Batsafetyundervoltage status."
		::= { upsIta2comEntry 389 }
upsIta2com389Addr2Batdischargehighcelltemp OBJECT-TYPE
		SYNTAX INTEGER {
			normal(0),
			alarm(1) }
		MAX-ACCESS read-only
		STATUS current
		DESCRIPTION
		"upsIta2com388Addr2Batdischargehighcelltemp status."
		::= { upsIta2comEntry 390 }
upsIta2com390Addr2Batdischargelowcelltemp OBJECT-TYPE
		SYNTAX INTEGER {
			normal(0),
			alarm(1) }
		MAX-ACCESS read-only
		STATUS current
		DESCRIPTION
		"upsIta2com389Addr2Batdischargelowcelltemp status."
		::= { upsIta2comEntry 391 }
upsIta2com391Addr2Batparallelchargehightemp OBJECT-TYPE
		SYNTAX INTEGER {
			normal(0),
			alarm(1) }
		MAX-ACCESS read-only
		STATUS current
		DESCRIPTION
		"upsIta2com390Addr2Batparallelchargehightemp status."
		::= { upsIta2comEntry 392 }
upsIta2com392Addr2BatinternalCommabnormal OBJECT-TYPE
		SYNTAX INTEGER {
			normal(0),
			alarm(1) }
		MAX-ACCESS read-only
		STATUS current
		DESCRIPTION
		"upsIta2com391Addr2BatinternalCommabnormal status."
		::= { upsIta2comEntry 393 }
upsIta2com393Addr2Batconditionfail OBJECT-TYPE
		SYNTAX INTEGER {
			normal(0),
			alarm(1) }
		MAX-ACCESS read-only
		STATUS current
		DESCRIPTION
		"upsIta2com392Addr2Batconditionfail status."
		::= { upsIta2comEntry 394 }
upsIta2com394Addr2BatLowinsulationresistance OBJECT-TYPE
		SYNTAX INTEGER {
			normal(0),
			alarm(1) }
		MAX-ACCESS read-only
		STATUS current
		DESCRIPTION
		"upsIta2com393Addr2BatLowinsulationresistance status."
		::= { upsIta2comEntry 395 }
upsIta2com395Addr2BatLargepressurediff OBJECT-TYPE
		SYNTAX INTEGER {
			normal(0),
			alarm(1) }
		MAX-ACCESS read-only
		STATUS current
		DESCRIPTION
		"upsIta2com394Addr2BatLargepressurediff status."
		::= { upsIta2comEntry 396 }
upsIta2com396Addr2BatBatfailure OBJECT-TYPE
		SYNTAX INTEGER {
			normal(0),
			alarm(1) }
		MAX-ACCESS read-only
		STATUS current
		DESCRIPTION
		"upsIta2com395Addr2BatBatfailure status."
		::= { upsIta2comEntry 397 }
upsIta2com397Addr2BatVoltageacquisitfailure OBJECT-TYPE
		SYNTAX INTEGER {
			normal(0),
			alarm(1) }
		MAX-ACCESS read-only
		STATUS current
		DESCRIPTION
		"upsIta2com396Addr2BatVoltageacquisitfailure status."
		::= { upsIta2comEntry 398 }
upsIta2com398Addr2BatCurrentcolllectfailure OBJECT-TYPE
		SYNTAX INTEGER {
			normal(0),
			alarm(1) }
		MAX-ACCESS read-only
		STATUS current
		DESCRIPTION
		"upsIta2com397Addr2BatCurrentcolllectfailure status."
		::= { upsIta2comEntry 399 }
upsIta2com399Addr2BatTempcolllectfailure OBJECT-TYPE
		SYNTAX INTEGER {
			normal(0),
			alarm(1) }
		MAX-ACCESS read-only
		STATUS current
		DESCRIPTION
		"upsIta2com398Addr2BatTempcolllectfailure status."
		::= { upsIta2comEntry 400 }
upsIta2com400Addr2BatAddrSeterror OBJECT-TYPE
		SYNTAX INTEGER {
			normal(0),
			alarm(1) }
		MAX-ACCESS read-only
		STATUS current
		DESCRIPTION
		"upsIta2com399Addr2BatAddrSeterror status."
		::= { upsIta2comEntry 401 }
upsIta2com401Addr2BatLargegrouppressurediff OBJECT-TYPE
		SYNTAX INTEGER {
			normal(0),
			alarm(1) }
		MAX-ACCESS read-only
		STATUS current
		DESCRIPTION
		"upsIta2com400Addr2BatLargegrouppressurediff status."
		::= { upsIta2comEntry 402 }
upsIta2com402Addr2BatMOSFETfailure OBJECT-TYPE
		SYNTAX INTEGER {
			normal(0),
			alarm(1) }
		MAX-ACCESS read-only
		STATUS current
		DESCRIPTION
		"upsIta2com401Addr2BatMOSFETfailure status."
		::= { upsIta2comEntry 403 }
upsIta2com403Addr2Battempabnormal OBJECT-TYPE
		SYNTAX INTEGER {
			normal(0),
			alarm(1) }
		MAX-ACCESS read-only
		STATUS current
		DESCRIPTION
		"upsIta2com402Addr2Battempabnormal status."
		::= { upsIta2comEntry 404 }
upsIta2com404Addr2Batcablefault OBJECT-TYPE
		SYNTAX INTEGER {
			normal(0),
			alarm(1) }
		MAX-ACCESS read-only
		STATUS current
		DESCRIPTION
		"upsIta2com403Addr2Batcablefault status."
		::= { upsIta2comEntry 405 }
upsIta2com405Addr2BatShortcircuit OBJECT-TYPE
		SYNTAX INTEGER {
			normal(0),
			alarm(1) }
		MAX-ACCESS read-only
		STATUS current
		DESCRIPTION
		"upsIta2com404Addr2BatShortcircuit status."
		::= { upsIta2comEntry 406 }
upsIta2com406Addr2BatOtherfailures OBJECT-TYPE
		SYNTAX INTEGER {
			normal(0),
			alarm(1) }
		MAX-ACCESS read-only
		STATUS current
		DESCRIPTION
		"upsIta2com405Addr2BatOtherfailures status."
		::= { upsIta2comEntry 407 }
upsIta2com407Addr2BatCommcablefailure OBJECT-TYPE
		SYNTAX INTEGER {
			normal(0),
			alarm(1) }
		MAX-ACCESS read-only
		STATUS current
		DESCRIPTION
		"upsIta2com406Addr2BatCommcablefailure status."
		::= { upsIta2comEntry 408 }
upsIta2com408Addr2BatMOSFETtempishigh OBJECT-TYPE
		SYNTAX INTEGER {
			normal(0),
			alarm(1) }
		MAX-ACCESS read-only
		STATUS current
		DESCRIPTION
		"upsIta2com407Addr2BatMOSFETtempishigh status."
		::= { upsIta2comEntry 409 }
upsIta2com409Addr2BatFuseblown OBJECT-TYPE
		SYNTAX INTEGER {
			normal(0),
			alarm(1) }
		MAX-ACCESS read-only
		STATUS current
		DESCRIPTION
		"upsIta2com408Addr2BatFuseblown status."
		::= { upsIta2comEntry 410 }
upsIta2com410Addr2BatWaitingforcharging OBJECT-TYPE
		SYNTAX INTEGER {
			normal(0),
			alarm(1) }
		MAX-ACCESS read-only
		STATUS current
		DESCRIPTION
		"upsIta2com409Addr2BatWaitingforcharging status."
		::= { upsIta2comEntry 411 }
upsIta2com411Addr2BatBataging OBJECT-TYPE
		SYNTAX INTEGER {
			normal(0),
			alarm(1) }
		MAX-ACCESS read-only
		STATUS current
		DESCRIPTION
		"upsIta2com410Addr2BatBataging status."
		::= { upsIta2comEntry 412 }
upsIta2com412Addr2Batboxconnectabnormal OBJECT-TYPE
		SYNTAX INTEGER {
			normal(0),
			alarm(1) }
		MAX-ACCESS read-only
		STATUS current
		DESCRIPTION
		"upsIta2com411Addr2Batboxconnectabnormal status."
		::= { upsIta2comEntry 413 }
upsIta2com413Addr2batBatterySoftincompatible OBJECT-TYPE
		SYNTAX INTEGER {
			normal(0),
			alarm(1) }
		MAX-ACCESS read-only
		STATUS current
		DESCRIPTION
		"upsIta2com412Addr2batBatterySoftincompatible status."
		::= { upsIta2comEntry 414 }
upsIta2com414Addr2batEOL OBJECT-TYPE
		SYNTAX INTEGER {
			normal(0),
			alarm(1) }
		MAX-ACCESS read-only
		STATUS current
		DESCRIPTION
		"upsIta2com413Addr2batEOL status."
		::= { upsIta2comEntry 415 }
upsIta2com415Addr2batSamplingfailure OBJECT-TYPE
		SYNTAX INTEGER {
			normal(0),
			alarm(1) }
		MAX-ACCESS read-only
		STATUS current
		DESCRIPTION
		"upsIta2com414Addr2batSamplingfailure status."
		::= { upsIta2comEntry 416 }
upsIta2com416Addr2batHardwareprotection OBJECT-TYPE
		SYNTAX INTEGER {
			normal(0),
			alarm(1) }
		MAX-ACCESS read-only
		STATUS current
		DESCRIPTION
		"upsIta2com415Addr2batHardwareprotection status."
		::= { upsIta2comEntry 417 }
upsIta2com417Addr2batBatterycapacitylow OBJECT-TYPE
		SYNTAX INTEGER {
			normal(0),
			alarm(1) }
		MAX-ACCESS read-only
		STATUS current
		DESCRIPTION
		"upsIta2com416Addr2batBatterycapacitylow status."
		::= { upsIta2comEntry 418 }
upsIta2com418Addr3Batalarmnumber OBJECT-TYPE
		SYNTAX Integer32
		
		MAX-ACCESS read-only
		STATUS current
		DESCRIPTION
		"upsIta2com417Addr3Batalarmnumber stored as 1."
		::= { upsIta2comEntry 419 }
upsIta2com419Addr3Bathighvolt OBJECT-TYPE
		SYNTAX INTEGER {
			normal(0),
			alarm(1) }
		MAX-ACCESS read-only
		STATUS current
		DESCRIPTION
		"upsIta2com418Addr3Bathighvolt status."
		::= { upsIta2comEntry 420 }
upsIta2com420Addr3Batlowvolt OBJECT-TYPE
		SYNTAX INTEGER {
			normal(0),
			alarm(1) }
		MAX-ACCESS read-only
		STATUS current
		DESCRIPTION
		"upsIta2com419Addr3Batlowvolt status."
		::= { upsIta2comEntry 421 }
upsIta2com421Addr3Bathighcellvolt OBJECT-TYPE
		SYNTAX INTEGER {
			normal(0),
			alarm(1) }
		MAX-ACCESS read-only
		STATUS current
		DESCRIPTION
		"upsIta2com420Addr3Bathighcellvolt status."
		::= { upsIta2comEntry 422 }
upsIta2com422Addr3Batlowcellvolt OBJECT-TYPE
		SYNTAX INTEGER {
			normal(0),
			alarm(1) }
		MAX-ACCESS read-only
		STATUS current
		DESCRIPTION
		"upsIta2com421Addr3Batlowcellvolt status."
		::= { upsIta2comEntry 423 }
upsIta2com423Addr3Batchargehighcelltemp OBJECT-TYPE
		SYNTAX INTEGER {
			normal(0),
			alarm(1) }
		MAX-ACCESS read-only
		STATUS current
		DESCRIPTION
		"upsIta2com422Addr3Batchargehighcelltemp status."
		::= { upsIta2comEntry 424 }
upsIta2com424Addr3Batchargelowcelltemp OBJECT-TYPE
		SYNTAX INTEGER {
			normal(0),
			alarm(1) }
		MAX-ACCESS read-only
		STATUS current
		DESCRIPTION
		"upsIta2com423Addr3Batchargelowcelltemp status."
		::= { upsIta2comEntry 425 }
upsIta2com425Addr3Batchargeovercurrent OBJECT-TYPE
		SYNTAX INTEGER {
			normal(0),
			alarm(1) }
		MAX-ACCESS read-only
		STATUS current
		DESCRIPTION
		"upsIta2com424Addr3Batchargeovercurrent status."
		::= { upsIta2comEntry 426 }
upsIta2com426Addr3Batdischargeovercurrent OBJECT-TYPE
		SYNTAX INTEGER {
			normal(0),
			alarm(1) }
		MAX-ACCESS read-only
		STATUS current
		DESCRIPTION
		"upsIta2com425Addr3Batdischargeovercurrent status."
		::= { upsIta2comEntry 427 }
upsIta2com427Addr3BatAddrconflict OBJECT-TYPE
		SYNTAX INTEGER {
			normal(0),
			alarm(1) }
		MAX-ACCESS read-only
		STATUS current
		DESCRIPTION
		"upsIta2com426Addr3BatAddrconflict status."
		::= { upsIta2comEntry 428 }
upsIta2com428Addr3Batportreverse OBJECT-TYPE
		SYNTAX INTEGER {
			normal(0),
			alarm(1) }
		MAX-ACCESS read-only
		STATUS current
		DESCRIPTION
		"upsIta2com427Addr3Batportreverse status."
		::= { upsIta2comEntry 429 }
upsIta2com429Addr3BatBMSrelayinvalid OBJECT-TYPE
		SYNTAX INTEGER {
			normal(0),
			alarm(1) }
		MAX-ACCESS read-only
		STATUS current
		DESCRIPTION
		"upsIta2com428Addr3BatBMSrelayinvalid status."
		::= { upsIta2comEntry 430 }
upsIta2com430Addr3Batsafetyundervoltage OBJECT-TYPE
		SYNTAX INTEGER {
			normal(0),
			alarm(1) }
		MAX-ACCESS read-only
		STATUS current
		DESCRIPTION
		"upsIta2com429Addr3Batsafetyundervoltage status."
		::= { upsIta2comEntry 431 }
upsIta2com431Addr3Batdischargehighcelltemp OBJECT-TYPE
		SYNTAX INTEGER {
			normal(0),
			alarm(1) }
		MAX-ACCESS read-only
		STATUS current
		DESCRIPTION
		"upsIta2com430Addr3Batdischargehighcelltemp status."
		::= { upsIta2comEntry 432 }
upsIta2com432Addr3Batdischargelowcelltemp OBJECT-TYPE
		SYNTAX INTEGER {
			normal(0),
			alarm(1) }
		MAX-ACCESS read-only
		STATUS current
		DESCRIPTION
		"upsIta2com431Addr3Batdischargelowcelltemp status."
		::= { upsIta2comEntry 433 }
upsIta2com433Addr3Batparallelchargehightemp OBJECT-TYPE
		SYNTAX INTEGER {
			normal(0),
			alarm(1) }
		MAX-ACCESS read-only
		STATUS current
		DESCRIPTION
		"upsIta2com432Addr3Batparallelchargehightemp status."
		::= { upsIta2comEntry 434 }
upsIta2com434Addr3BatinternalCommabnormal OBJECT-TYPE
		SYNTAX INTEGER {
			normal(0),
			alarm(1) }
		MAX-ACCESS read-only
		STATUS current
		DESCRIPTION
		"upsIta2com433Addr3BatinternalCommabnormal status."
		::= { upsIta2comEntry 435 }
upsIta2com435Addr3Batconditionfail OBJECT-TYPE
		SYNTAX INTEGER {
			normal(0),
			alarm(1) }
		MAX-ACCESS read-only
		STATUS current
		DESCRIPTION
		"upsIta2com434Addr3Batconditionfail status."
		::= { upsIta2comEntry 436 }
upsIta2com436Addr3BatLowinsulationresistance OBJECT-TYPE
		SYNTAX INTEGER {
			normal(0),
			alarm(1) }
		MAX-ACCESS read-only
		STATUS current
		DESCRIPTION
		"upsIta2com435Addr3BatLowinsulationresistance status."
		::= { upsIta2comEntry 437 }
upsIta2com437Addr3BatLargepressurediff OBJECT-TYPE
		SYNTAX INTEGER {
			normal(0),
			alarm(1) }
		MAX-ACCESS read-only
		STATUS current
		DESCRIPTION
		"upsIta2com436Addr3BatLargepressurediff status."
		::= { upsIta2comEntry 438 }
upsIta2com438Addr3BatBatfailure OBJECT-TYPE
		SYNTAX INTEGER {
			normal(0),
			alarm(1) }
		MAX-ACCESS read-only
		STATUS current
		DESCRIPTION
		"upsIta2com437Addr3BatBatfailure status."
		::= { upsIta2comEntry 439 }
upsIta2com439Addr3BatVoltageacquisitfailure OBJECT-TYPE
		SYNTAX INTEGER {
			normal(0),
			alarm(1) }
		MAX-ACCESS read-only
		STATUS current
		DESCRIPTION
		"upsIta2com438Addr3BatVoltageacquisitfailure status."
		::= { upsIta2comEntry 440 }
upsIta2com440Addr3BatCurrentcolllectfailure OBJECT-TYPE
		SYNTAX INTEGER {
			normal(0),
			alarm(1) }
		MAX-ACCESS read-only
		STATUS current
		DESCRIPTION
		"upsIta2com439Addr3BatCurrentcolllectfailure status."
		::= { upsIta2comEntry 441 }
upsIta2com441Addr3BatTempcolllectfailure OBJECT-TYPE
		SYNTAX INTEGER {
			normal(0),
			alarm(1) }
		MAX-ACCESS read-only
		STATUS current
		DESCRIPTION
		"upsIta2com440Addr3BatTempcolllectfailure status."
		::= { upsIta2comEntry 442 }
upsIta2com442Addr3BatAddrSeterror OBJECT-TYPE
		SYNTAX INTEGER {
			normal(0),
			alarm(1) }
		MAX-ACCESS read-only
		STATUS current
		DESCRIPTION
		"upsIta2com441Addr3BatAddrSeterror status."
		::= { upsIta2comEntry 443 }
upsIta2com443Addr3BatLargegrouppressurediff OBJECT-TYPE
		SYNTAX INTEGER {
			normal(0),
			alarm(1) }
		MAX-ACCESS read-only
		STATUS current
		DESCRIPTION
		"upsIta2com442Addr3BatLargegrouppressurediff status."
		::= { upsIta2comEntry 444 }
upsIta2com444Addr3BatMOSFETfailure OBJECT-TYPE
		SYNTAX INTEGER {
			normal(0),
			alarm(1) }
		MAX-ACCESS read-only
		STATUS current
		DESCRIPTION
		"upsIta2com443Addr3BatMOSFETfailure status."
		::= { upsIta2comEntry 445 }
upsIta2com445Addr3Battempabnormal OBJECT-TYPE
		SYNTAX INTEGER {
			normal(0),
			alarm(1) }
		MAX-ACCESS read-only
		STATUS current
		DESCRIPTION
		"upsIta2com444Addr3Battempabnormal status."
		::= { upsIta2comEntry 446 }
upsIta2com446Addr3Batcablefault OBJECT-TYPE
		SYNTAX INTEGER {
			normal(0),
			alarm(1) }
		MAX-ACCESS read-only
		STATUS current
		DESCRIPTION
		"upsIta2com445Addr3Batcablefault status."
		::= { upsIta2comEntry 447 }
upsIta2com447Addr3BatShortcircuit OBJECT-TYPE
		SYNTAX INTEGER {
			normal(0),
			alarm(1) }
		MAX-ACCESS read-only
		STATUS current
		DESCRIPTION
		"upsIta2com446Addr3BatShortcircuit status."
		::= { upsIta2comEntry 448 }
upsIta2com448Addr3BatOtherfailures OBJECT-TYPE
		SYNTAX INTEGER {
			normal(0),
			alarm(1) }
		MAX-ACCESS read-only
		STATUS current
		DESCRIPTION
		"upsIta2com447Addr3BatOtherfailures status."
		::= { upsIta2comEntry 449 }
upsIta2com449Addr3BatCommcablefailure OBJECT-TYPE
		SYNTAX INTEGER {
			normal(0),
			alarm(1) }
		MAX-ACCESS read-only
		STATUS current
		DESCRIPTION
		"upsIta2com448Addr3BatCommcablefailure status."
		::= { upsIta2comEntry 450 }
upsIta2com450Addr3BatMOSFETtempishigh OBJECT-TYPE
		SYNTAX INTEGER {
			normal(0),
			alarm(1) }
		MAX-ACCESS read-only
		STATUS current
		DESCRIPTION
		"upsIta2com449Addr3BatMOSFETtempishigh status."
		::= { upsIta2comEntry 451 }
upsIta2com451Addr3BatFuseblown OBJECT-TYPE
		SYNTAX INTEGER {
			normal(0),
			alarm(1) }
		MAX-ACCESS read-only
		STATUS current
		DESCRIPTION
		"upsIta2com450Addr3BatFuseblown status."
		::= { upsIta2comEntry 452 }
upsIta2com452Addr3BatWaitingforcharging OBJECT-TYPE
		SYNTAX INTEGER {
			normal(0),
			alarm(1) }
		MAX-ACCESS read-only
		STATUS current
		DESCRIPTION
		"upsIta2com451Addr3BatWaitingforcharging status."
		::= { upsIta2comEntry 453 }
upsIta2com453Addr3BatBataging OBJECT-TYPE
		SYNTAX INTEGER {
			normal(0),
			alarm(1) }
		MAX-ACCESS read-only
		STATUS current
		DESCRIPTION
		"upsIta2com452Addr3BatBataging status."
		::= { upsIta2comEntry 454 }
upsIta2com454Addr3Batboxconnectabnormal OBJECT-TYPE
		SYNTAX INTEGER {
			normal(0),
			alarm(1) }
		MAX-ACCESS read-only
		STATUS current
		DESCRIPTION
		"upsIta2com453Addr3Batboxconnectabnormal status."
		::= { upsIta2comEntry 455 }
upsIta2com455Addr3batBatterySoftincompatible OBJECT-TYPE
		SYNTAX INTEGER {
			normal(0),
			alarm(1) }
		MAX-ACCESS read-only
		STATUS current
		DESCRIPTION
		"upsIta2com454Addr3batBatterySoftincompatible status."
		::= { upsIta2comEntry 456 }
upsIta2com456Addr3batEOL OBJECT-TYPE
		SYNTAX INTEGER {
			normal(0),
			alarm(1) }
		MAX-ACCESS read-only
		STATUS current
		DESCRIPTION
		"upsIta2com455Addr3batEOL status."
		::= { upsIta2comEntry 457 }
upsIta2com457Addr3batSamplingfailure OBJECT-TYPE
		SYNTAX INTEGER {
			normal(0),
			alarm(1) }
		MAX-ACCESS read-only
		STATUS current
		DESCRIPTION
		"upsIta2com456Addr3batSamplingfailure status."
		::= { upsIta2comEntry 458 }
upsIta2com458Addr3batHardwareprotection OBJECT-TYPE
		SYNTAX INTEGER {
			normal(0),
			alarm(1) }
		MAX-ACCESS read-only
		STATUS current
		DESCRIPTION
		"upsIta2com457Addr3batHardwareprotection status."
		::= { upsIta2comEntry 459 }
upsIta2com459Addr3batBatterycapacitylow OBJECT-TYPE
		SYNTAX INTEGER {
			normal(0),
			alarm(1) }
		MAX-ACCESS read-only
		STATUS current
		DESCRIPTION
		"upsIta2com458Addr3batBatterycapacitylow status."
		::= { upsIta2comEntry 460 }
upsIta2com460Addr4Batalarmnumber OBJECT-TYPE
		SYNTAX Integer32
		
		MAX-ACCESS read-only
		STATUS current
		DESCRIPTION
		"upsIta2com459Addr4Batalarmnumber stored as 1."
		::= { upsIta2comEntry 461 }
upsIta2com461Addr4Bathighvolt OBJECT-TYPE
		SYNTAX INTEGER {
			normal(0),
			alarm(1) }
		MAX-ACCESS read-only
		STATUS current
		DESCRIPTION
		"upsIta2com460Addr4Bathighvolt status."
		::= { upsIta2comEntry 462 }
upsIta2com462Addr4Batlowvolt OBJECT-TYPE
		SYNTAX INTEGER {
			normal(0),
			alarm(1) }
		MAX-ACCESS read-only
		STATUS current
		DESCRIPTION
		"upsIta2com461Addr4Batlowvolt status."
		::= { upsIta2comEntry 463 }
upsIta2com463Addr4Bathighcellvolt OBJECT-TYPE
		SYNTAX INTEGER {
			normal(0),
			alarm(1) }
		MAX-ACCESS read-only
		STATUS current
		DESCRIPTION
		"upsIta2com462Addr4Bathighcellvolt status."
		::= { upsIta2comEntry 464 }
upsIta2com464Addr4Batlowcellvolt OBJECT-TYPE
		SYNTAX INTEGER {
			normal(0),
			alarm(1) }
		MAX-ACCESS read-only
		STATUS current
		DESCRIPTION
		"upsIta2com463Addr4Batlowcellvolt status."
		::= { upsIta2comEntry 465 }
upsIta2com465Addr4Batchargehighcelltemp OBJECT-TYPE
		SYNTAX INTEGER {
			normal(0),
			alarm(1) }
		MAX-ACCESS read-only
		STATUS current
		DESCRIPTION
		"upsIta2com464Addr4Batchargehighcelltemp status."
		::= { upsIta2comEntry 466 }
upsIta2com466Addr4Batchargelowcelltemp OBJECT-TYPE
		SYNTAX INTEGER {
			normal(0),
			alarm(1) }
		MAX-ACCESS read-only
		STATUS current
		DESCRIPTION
		"upsIta2com465Addr4Batchargelowcelltemp status."
		::= { upsIta2comEntry 467 }
upsIta2com467Addr4Batchargeovercurrent OBJECT-TYPE
		SYNTAX INTEGER {
			normal(0),
			alarm(1) }
		MAX-ACCESS read-only
		STATUS current
		DESCRIPTION
		"upsIta2com466Addr4Batchargeovercurrent status."
		::= { upsIta2comEntry 468 }
upsIta2com468Addr4Batdischargeovercurrent OBJECT-TYPE
		SYNTAX INTEGER {
			normal(0),
			alarm(1) }
		MAX-ACCESS read-only
		STATUS current
		DESCRIPTION
		"upsIta2com467Addr4Batdischargeovercurrent status."
		::= { upsIta2comEntry 469 }
upsIta2com469Addr4BatAddrconflict OBJECT-TYPE
		SYNTAX INTEGER {
			normal(0),
			alarm(1) }
		MAX-ACCESS read-only
		STATUS current
		DESCRIPTION
		"upsIta2com468Addr4BatAddrconflict status."
		::= { upsIta2comEntry 470 }
upsIta2com470Addr4Batportreverse OBJECT-TYPE
		SYNTAX INTEGER {
			normal(0),
			alarm(1) }
		MAX-ACCESS read-only
		STATUS current
		DESCRIPTION
		"upsIta2com469Addr4Batportreverse status."
		::= { upsIta2comEntry 471 }
upsIta2com471Addr4BatBMSrelayinvalid OBJECT-TYPE
		SYNTAX INTEGER {
			normal(0),
			alarm(1) }
		MAX-ACCESS read-only
		STATUS current
		DESCRIPTION
		"upsIta2com470Addr4BatBMSrelayinvalid status."
		::= { upsIta2comEntry 472 }
upsIta2com472Addr4Batsafetyundervoltage OBJECT-TYPE
		SYNTAX INTEGER {
			normal(0),
			alarm(1) }
		MAX-ACCESS read-only
		STATUS current
		DESCRIPTION
		"upsIta2com471Addr4Batsafetyundervoltage status."
		::= { upsIta2comEntry 473 }
upsIta2com473Addr4Batdischargehighcelltemp OBJECT-TYPE
		SYNTAX INTEGER {
			normal(0),
			alarm(1) }
		MAX-ACCESS read-only
		STATUS current
		DESCRIPTION
		"upsIta2com472Addr4Batdischargehighcelltemp status."
		::= { upsIta2comEntry 474 }
upsIta2com474Addr4Batdischargelowcelltemp OBJECT-TYPE
		SYNTAX INTEGER {
			normal(0),
			alarm(1) }
		MAX-ACCESS read-only
		STATUS current
		DESCRIPTION
		"upsIta2com473Addr4Batdischargelowcelltemp status."
		::= { upsIta2comEntry 475 }
upsIta2com475Addr4Batparallelchargehightemp OBJECT-TYPE
		SYNTAX INTEGER {
			normal(0),
			alarm(1) }
		MAX-ACCESS read-only
		STATUS current
		DESCRIPTION
		"upsIta2com474Addr4Batparallelchargehightemp status."
		::= { upsIta2comEntry 476 }
upsIta2com476Addr4BatinternalCommabnormal OBJECT-TYPE
		SYNTAX INTEGER {
			normal(0),
			alarm(1) }
		MAX-ACCESS read-only
		STATUS current
		DESCRIPTION
		"upsIta2com475Addr4BatinternalCommabnormal status."
		::= { upsIta2comEntry 477 }
upsIta2com477Addr4Batconditionfail OBJECT-TYPE
		SYNTAX INTEGER {
			normal(0),
			alarm(1) }
		MAX-ACCESS read-only
		STATUS current
		DESCRIPTION
		"upsIta2com476Addr4Batconditionfail status."
		::= { upsIta2comEntry 478 }
upsIta2com478Addr4BatLowinsulationresistance OBJECT-TYPE
		SYNTAX INTEGER {
			normal(0),
			alarm(1) }
		MAX-ACCESS read-only
		STATUS current
		DESCRIPTION
		"upsIta2com477Addr4BatLowinsulationresistance status."
		::= { upsIta2comEntry 479 }
upsIta2com479Addr4BatLargepressurediff OBJECT-TYPE
		SYNTAX INTEGER {
			normal(0),
			alarm(1) }
		MAX-ACCESS read-only
		STATUS current
		DESCRIPTION
		"upsIta2com478Addr4BatLargepressurediff status."
		::= { upsIta2comEntry 480 }
upsIta2com480Addr4BatBatfailure OBJECT-TYPE
		SYNTAX INTEGER {
			normal(0),
			alarm(1) }
		MAX-ACCESS read-only
		STATUS current
		DESCRIPTION
		"upsIta2com479Addr4BatBatfailure status."
		::= { upsIta2comEntry 481 }
upsIta2com481Addr4BatVoltageacquisitfailure OBJECT-TYPE
		SYNTAX INTEGER {
			normal(0),
			alarm(1) }
		MAX-ACCESS read-only
		STATUS current
		DESCRIPTION
		"upsIta2com480Addr4BatVoltageacquisitfailure status."
		::= { upsIta2comEntry 482 }
upsIta2com482Addr4BatCurrentcolllectfailure OBJECT-TYPE
		SYNTAX INTEGER {
			normal(0),
			alarm(1) }
		MAX-ACCESS read-only
		STATUS current
		DESCRIPTION
		"upsIta2com481Addr4BatCurrentcolllectfailure status."
		::= { upsIta2comEntry 483 }
upsIta2com483Addr4BatTempcolllectfailure OBJECT-TYPE
		SYNTAX INTEGER {
			normal(0),
			alarm(1) }
		MAX-ACCESS read-only
		STATUS current
		DESCRIPTION
		"upsIta2com482Addr4BatTempcolllectfailure status."
		::= { upsIta2comEntry 484 }
upsIta2com484Addr4BatAddrSeterror OBJECT-TYPE
		SYNTAX INTEGER {
			normal(0),
			alarm(1) }
		MAX-ACCESS read-only
		STATUS current
		DESCRIPTION
		"upsIta2com483Addr4BatAddrSeterror status."
		::= { upsIta2comEntry 485 }
upsIta2com485Addr4BatLargegrouppressurediff OBJECT-TYPE
		SYNTAX INTEGER {
			normal(0),
			alarm(1) }
		MAX-ACCESS read-only
		STATUS current
		DESCRIPTION
		"upsIta2com484Addr4BatLargegrouppressurediff status."
		::= { upsIta2comEntry 486 }
upsIta2com486Addr4BatMOSFETfailure OBJECT-TYPE
		SYNTAX INTEGER {
			normal(0),
			alarm(1) }
		MAX-ACCESS read-only
		STATUS current
		DESCRIPTION
		"upsIta2com485Addr4BatMOSFETfailure status."
		::= { upsIta2comEntry 487 }
upsIta2com487Addr4Battempabnormal OBJECT-TYPE
		SYNTAX INTEGER {
			normal(0),
			alarm(1) }
		MAX-ACCESS read-only
		STATUS current
		DESCRIPTION
		"upsIta2com486Addr4Battempabnormal status."
		::= { upsIta2comEntry 488 }
upsIta2com488Addr4Batcablefault OBJECT-TYPE
		SYNTAX INTEGER {
			normal(0),
			alarm(1) }
		MAX-ACCESS read-only
		STATUS current
		DESCRIPTION
		"upsIta2com487Addr4Batcablefault status."
		::= { upsIta2comEntry 489 }
upsIta2com489Addr4BatShortcircuit OBJECT-TYPE
		SYNTAX INTEGER {
			normal(0),
			alarm(1) }
		MAX-ACCESS read-only
		STATUS current
		DESCRIPTION
		"upsIta2com488Addr4BatShortcircuit status."
		::= { upsIta2comEntry 490 }
upsIta2com490Addr4BatOtherfailures OBJECT-TYPE
		SYNTAX INTEGER {
			normal(0),
			alarm(1) }
		MAX-ACCESS read-only
		STATUS current
		DESCRIPTION
		"upsIta2com489Addr4BatOtherfailures status."
		::= { upsIta2comEntry 491 }
upsIta2com491Addr4BatCommcablefailure OBJECT-TYPE
		SYNTAX INTEGER {
			normal(0),
			alarm(1) }
		MAX-ACCESS read-only
		STATUS current
		DESCRIPTION
		"upsIta2com490Addr4BatCommcablefailure status."
		::= { upsIta2comEntry 492 }
upsIta2com492Addr4BatMOSFETtempishigh OBJECT-TYPE
		SYNTAX INTEGER {
			normal(0),
			alarm(1) }
		MAX-ACCESS read-only
		STATUS current
		DESCRIPTION
		"upsIta2com491Addr4BatMOSFETtempishigh status."
		::= { upsIta2comEntry 493 }
upsIta2com493Addr4BatFuseblown OBJECT-TYPE
		SYNTAX INTEGER {
			normal(0),
			alarm(1) }
		MAX-ACCESS read-only
		STATUS current
		DESCRIPTION
		"upsIta2com492Addr4BatFuseblown status."
		::= { upsIta2comEntry 494 }
upsIta2com494Addr4BatWaitingforcharging OBJECT-TYPE
		SYNTAX INTEGER {
			normal(0),
			alarm(1) }
		MAX-ACCESS read-only
		STATUS current
		DESCRIPTION
		"upsIta2com493Addr4BatWaitingforcharging status."
		::= { upsIta2comEntry 495 }
upsIta2com495Addr4BatBataging OBJECT-TYPE
		SYNTAX INTEGER {
			normal(0),
			alarm(1) }
		MAX-ACCESS read-only
		STATUS current
		DESCRIPTION
		"upsIta2com494Addr4BatBataging status."
		::= { upsIta2comEntry 496 }
upsIta2com496Addr4Batboxconnectabnormal OBJECT-TYPE
		SYNTAX INTEGER {
			normal(0),
			alarm(1) }
		MAX-ACCESS read-only
		STATUS current
		DESCRIPTION
		"upsIta2com495Addr4Batboxconnectabnormal status."
		::= { upsIta2comEntry 497 }
upsIta2com497Addr4batBatterySoftincompatible OBJECT-TYPE
		SYNTAX INTEGER {
			normal(0),
			alarm(1) }
		MAX-ACCESS read-only
		STATUS current
		DESCRIPTION
		"upsIta2com496Addr4batBatterySoftincompatible status."
		::= { upsIta2comEntry 498 }
upsIta2com498Addr4batEOL OBJECT-TYPE
		SYNTAX INTEGER {
			normal(0),
			alarm(1) }
		MAX-ACCESS read-only
		STATUS current
		DESCRIPTION
		"upsIta2com497Addr4batEOL status."
		::= { upsIta2comEntry 499 }
upsIta2com499Addr4batSamplingfailure OBJECT-TYPE
		SYNTAX INTEGER {
			normal(0),
			alarm(1) }
		MAX-ACCESS read-only
		STATUS current
		DESCRIPTION
		"upsIta2com498Addr4batSamplingfailure status."
		::= { upsIta2comEntry 500 }
upsIta2com500Addr4batHardwareprotection OBJECT-TYPE
		SYNTAX INTEGER {
			normal(0),
			alarm(1) }
		MAX-ACCESS read-only
		STATUS current
		DESCRIPTION
		"upsIta2com499Addr4batHardwareprotection status."
		::= { upsIta2comEntry 501 }
upsIta2com501Addr4batBatterycapacitylow OBJECT-TYPE
		SYNTAX INTEGER {
			normal(0),
			alarm(1) }
		MAX-ACCESS read-only
		STATUS current
		DESCRIPTION
		"upsIta2com500Addr4batBatterycapacitylow status."
		::= { upsIta2comEntry 502 }
upsIta2com502Addr5Batalarmnumber OBJECT-TYPE
		SYNTAX Integer32
		
		MAX-ACCESS read-only
		STATUS current
		DESCRIPTION
		"upsIta2com501Addr5Batalarmnumber stored as 1."
		::= { upsIta2comEntry 503 }
upsIta2com503Addr5Bathighvolt OBJECT-TYPE
		SYNTAX INTEGER {
			normal(0),
			alarm(1) }
		MAX-ACCESS read-only
		STATUS current
		DESCRIPTION
		"upsIta2com502Addr5Bathighvolt status."
		::= { upsIta2comEntry 504 }
upsIta2com504Addr5Batlowvolt OBJECT-TYPE
		SYNTAX INTEGER {
			normal(0),
			alarm(1) }
		MAX-ACCESS read-only
		STATUS current
		DESCRIPTION
		"upsIta2com503Addr5Batlowvolt status."
		::= { upsIta2comEntry 505 }
upsIta2com505Addr5Bathighcellvolt OBJECT-TYPE
		SYNTAX INTEGER {
			normal(0),
			alarm(1) }
		MAX-ACCESS read-only
		STATUS current
		DESCRIPTION
		"upsIta2com504Addr5Bathighcellvolt status."
		::= { upsIta2comEntry 506 }
upsIta2com506Addr5Batlowcellvolt OBJECT-TYPE
		SYNTAX INTEGER {
			normal(0),
			alarm(1) }
		MAX-ACCESS read-only
		STATUS current
		DESCRIPTION
		"upsIta2com505Addr5Batlowcellvolt status."
		::= { upsIta2comEntry 507 }
upsIta2com507Addr5Batchargehighcelltemp OBJECT-TYPE
		SYNTAX INTEGER {
			normal(0),
			alarm(1) }
		MAX-ACCESS read-only
		STATUS current
		DESCRIPTION
		"upsIta2com506Addr5Batchargehighcelltemp status."
		::= { upsIta2comEntry 508 }
upsIta2com508Addr5Batchargelowcelltemp OBJECT-TYPE
		SYNTAX INTEGER {
			normal(0),
			alarm(1) }
		MAX-ACCESS read-only
		STATUS current
		DESCRIPTION
		"upsIta2com507Addr5Batchargelowcelltemp status."
		::= { upsIta2comEntry 509 }
upsIta2com509Addr5Batchargeovercurrent OBJECT-TYPE
		SYNTAX INTEGER {
			normal(0),
			alarm(1) }
		MAX-ACCESS read-only
		STATUS current
		DESCRIPTION
		"upsIta2com508Addr5Batchargeovercurrent status."
		::= { upsIta2comEntry 510 }
upsIta2com510Addr5Batdischargeovercurrent OBJECT-TYPE
		SYNTAX INTEGER {
			normal(0),
			alarm(1) }
		MAX-ACCESS read-only
		STATUS current
		DESCRIPTION
		"upsIta2com509Addr5Batdischargeovercurrent status."
		::= { upsIta2comEntry 511 }
upsIta2com511Addr5BatAddrconflict OBJECT-TYPE
		SYNTAX INTEGER {
			normal(0),
			alarm(1) }
		MAX-ACCESS read-only
		STATUS current
		DESCRIPTION
		"upsIta2com510Addr5BatAddrconflict status."
		::= { upsIta2comEntry 512 }
upsIta2com512Addr5Batportreverse OBJECT-TYPE
		SYNTAX INTEGER {
			normal(0),
			alarm(1) }
		MAX-ACCESS read-only
		STATUS current
		DESCRIPTION
		"upsIta2com511Addr5Batportreverse status."
		::= { upsIta2comEntry 513 }
upsIta2com513Addr5BatBMSrelayinvalid OBJECT-TYPE
		SYNTAX INTEGER {
			normal(0),
			alarm(1) }
		MAX-ACCESS read-only
		STATUS current
		DESCRIPTION
		"upsIta2com512Addr5BatBMSrelayinvalid status."
		::= { upsIta2comEntry 514 }
upsIta2com514Addr5Batsafetyundervoltage OBJECT-TYPE
		SYNTAX INTEGER {
			normal(0),
			alarm(1) }
		MAX-ACCESS read-only
		STATUS current
		DESCRIPTION
		"upsIta2com513Addr5Batsafetyundervoltage status."
		::= { upsIta2comEntry 515 }
upsIta2com515Addr5Batdischargehighcelltemp OBJECT-TYPE
		SYNTAX INTEGER {
			normal(0),
			alarm(1) }
		MAX-ACCESS read-only
		STATUS current
		DESCRIPTION
		"upsIta2com514Addr5Batdischargehighcelltemp status."
		::= { upsIta2comEntry 516 }
upsIta2com516Addr5Batdischargelowcelltemp OBJECT-TYPE
		SYNTAX INTEGER {
			normal(0),
			alarm(1) }
		MAX-ACCESS read-only
		STATUS current
		DESCRIPTION
		"upsIta2com515Addr5Batdischargelowcelltemp status."
		::= { upsIta2comEntry 517 }
upsIta2com517Addr5Batparallelchargehightemp OBJECT-TYPE
		SYNTAX INTEGER {
			normal(0),
			alarm(1) }
		MAX-ACCESS read-only
		STATUS current
		DESCRIPTION
		"upsIta2com516Addr5Batparallelchargehightemp status."
		::= { upsIta2comEntry 518 }
upsIta2com518Addr5BatinternalCommabnormal OBJECT-TYPE
		SYNTAX INTEGER {
			normal(0),
			alarm(1) }
		MAX-ACCESS read-only
		STATUS current
		DESCRIPTION
		"upsIta2com517Addr5BatinternalCommabnormal status."
		::= { upsIta2comEntry 519 }
upsIta2com519Addr5Batconditionfail OBJECT-TYPE
		SYNTAX INTEGER {
			normal(0),
			alarm(1) }
		MAX-ACCESS read-only
		STATUS current
		DESCRIPTION
		"upsIta2com518Addr5Batconditionfail status."
		::= { upsIta2comEntry 520 }
upsIta2com520Addr5BatLowinsulationresistance OBJECT-TYPE
		SYNTAX INTEGER {
			normal(0),
			alarm(1) }
		MAX-ACCESS read-only
		STATUS current
		DESCRIPTION
		"upsIta2com519Addr5BatLowinsulationresistance status."
		::= { upsIta2comEntry 521 }
upsIta2com521Addr5BatLargepressurediff OBJECT-TYPE
		SYNTAX INTEGER {
			normal(0),
			alarm(1) }
		MAX-ACCESS read-only
		STATUS current
		DESCRIPTION
		"upsIta2com520Addr5BatLargepressurediff status."
		::= { upsIta2comEntry 522 }
upsIta2com522Addr5BatBatfailure OBJECT-TYPE
		SYNTAX INTEGER {
			normal(0),
			alarm(1) }
		MAX-ACCESS read-only
		STATUS current
		DESCRIPTION
		"upsIta2com521Addr5BatBatfailure status."
		::= { upsIta2comEntry 523 }
upsIta2com523Addr5BatVoltageacquisitfailure OBJECT-TYPE
		SYNTAX INTEGER {
			normal(0),
			alarm(1) }
		MAX-ACCESS read-only
		STATUS current
		DESCRIPTION
		"upsIta2com522Addr5BatVoltageacquisitfailure status."
		::= { upsIta2comEntry 524 }
upsIta2com524Addr5BatCurrentcolllectfailure OBJECT-TYPE
		SYNTAX INTEGER {
			normal(0),
			alarm(1) }
		MAX-ACCESS read-only
		STATUS current
		DESCRIPTION
		"upsIta2com523Addr5BatCurrentcolllectfailure status."
		::= { upsIta2comEntry 525 }
upsIta2com525Addr5BatTempcolllectfailure OBJECT-TYPE
		SYNTAX INTEGER {
			normal(0),
			alarm(1) }
		MAX-ACCESS read-only
		STATUS current
		DESCRIPTION
		"upsIta2com524Addr5BatTempcolllectfailure status."
		::= { upsIta2comEntry 526 }
upsIta2com526Addr5BatAddrSeterror OBJECT-TYPE
		SYNTAX INTEGER {
			normal(0),
			alarm(1) }
		MAX-ACCESS read-only
		STATUS current
		DESCRIPTION
		"upsIta2com525Addr5BatAddrSeterror status."
		::= { upsIta2comEntry 527 }
upsIta2com527Addr5BatLargegrouppressurediff OBJECT-TYPE
		SYNTAX INTEGER {
			normal(0),
			alarm(1) }
		MAX-ACCESS read-only
		STATUS current
		DESCRIPTION
		"upsIta2com526Addr5BatLargegrouppressurediff status."
		::= { upsIta2comEntry 528 }
upsIta2com528Addr5BatMOSFETfailure OBJECT-TYPE
		SYNTAX INTEGER {
			normal(0),
			alarm(1) }
		MAX-ACCESS read-only
		STATUS current
		DESCRIPTION
		"upsIta2com527Addr5BatMOSFETfailure status."
		::= { upsIta2comEntry 529 }
upsIta2com529Addr5Battempabnormal OBJECT-TYPE
		SYNTAX INTEGER {
			normal(0),
			alarm(1) }
		MAX-ACCESS read-only
		STATUS current
		DESCRIPTION
		"upsIta2com528Addr5Battempabnormal status."
		::= { upsIta2comEntry 530 }
upsIta2com530Addr5Batcablefault OBJECT-TYPE
		SYNTAX INTEGER {
			normal(0),
			alarm(1) }
		MAX-ACCESS read-only
		STATUS current
		DESCRIPTION
		"upsIta2com529Addr5Batcablefault status."
		::= { upsIta2comEntry 531 }
upsIta2com531Addr5BatShortcircuit OBJECT-TYPE
		SYNTAX INTEGER {
			normal(0),
			alarm(1) }
		MAX-ACCESS read-only
		STATUS current
		DESCRIPTION
		"upsIta2com530Addr5BatShortcircuit status."
		::= { upsIta2comEntry 532 }
upsIta2com532Addr5BatOtherfailures OBJECT-TYPE
		SYNTAX INTEGER {
			normal(0),
			alarm(1) }
		MAX-ACCESS read-only
		STATUS current
		DESCRIPTION
		"upsIta2com531Addr5BatOtherfailures status."
		::= { upsIta2comEntry 533 }
upsIta2com533Addr5BatCommcablefailure OBJECT-TYPE
		SYNTAX INTEGER {
			normal(0),
			alarm(1) }
		MAX-ACCESS read-only
		STATUS current
		DESCRIPTION
		"upsIta2com532Addr5BatCommcablefailure status."
		::= { upsIta2comEntry 534 }
upsIta2com534Addr5BatMOSFETtempishigh OBJECT-TYPE
		SYNTAX INTEGER {
			normal(0),
			alarm(1) }
		MAX-ACCESS read-only
		STATUS current
		DESCRIPTION
		"upsIta2com533Addr5BatMOSFETtempishigh status."
		::= { upsIta2comEntry 535 }
upsIta2com535Addr5BatFuseblown OBJECT-TYPE
		SYNTAX INTEGER {
			normal(0),
			alarm(1) }
		MAX-ACCESS read-only
		STATUS current
		DESCRIPTION
		"upsIta2com534Addr5BatFuseblown status."
		::= { upsIta2comEntry 536 }
upsIta2com536Addr5BatWaitingforcharging OBJECT-TYPE
		SYNTAX INTEGER {
			normal(0),
			alarm(1) }
		MAX-ACCESS read-only
		STATUS current
		DESCRIPTION
		"upsIta2com535Addr5BatWaitingforcharging status."
		::= { upsIta2comEntry 537 }
upsIta2com537Addr5BatBataging OBJECT-TYPE
		SYNTAX INTEGER {
			normal(0),
			alarm(1) }
		MAX-ACCESS read-only
		STATUS current
		DESCRIPTION
		"upsIta2com536Addr5BatBataging status."
		::= { upsIta2comEntry 538 }
upsIta2com538Addr5Batboxconnectabnormal OBJECT-TYPE
		SYNTAX INTEGER {
			normal(0),
			alarm(1) }
		MAX-ACCESS read-only
		STATUS current
		DESCRIPTION
		"upsIta2com537Addr5Batboxconnectabnormal status."
		::= { upsIta2comEntry 539 }
upsIta2com539Addr5batBatterySoftincompatible OBJECT-TYPE
		SYNTAX INTEGER {
			normal(0),
			alarm(1) }
		MAX-ACCESS read-only
		STATUS current
		DESCRIPTION
		"upsIta2com538Addr5batBatterySoftincompatible status."
		::= { upsIta2comEntry 540 }
upsIta2com540Addr5batEOL OBJECT-TYPE
		SYNTAX INTEGER {
			normal(0),
			alarm(1) }
		MAX-ACCESS read-only
		STATUS current
		DESCRIPTION
		"upsIta2com539Addr5batEOL status."
		::= { upsIta2comEntry 541 }
upsIta2com541Addr5batSamplingfailure OBJECT-TYPE
		SYNTAX INTEGER {
			normal(0),
			alarm(1) }
		MAX-ACCESS read-only
		STATUS current
		DESCRIPTION
		"upsIta2com540Addr5batSamplingfailure status."
		::= { upsIta2comEntry 542 }
upsIta2com542Addr5batHardwareprotection OBJECT-TYPE
		SYNTAX INTEGER {
			normal(0),
			alarm(1) }
		MAX-ACCESS read-only
		STATUS current
		DESCRIPTION
		"upsIta2com541Addr5batHardwareprotection status."
		::= { upsIta2comEntry 543 }
upsIta2com543Addr5batBatterycapacitylow OBJECT-TYPE
		SYNTAX INTEGER {
			normal(0),
			alarm(1) }
		MAX-ACCESS read-only
		STATUS current
		DESCRIPTION
		"upsIta2com542Addr5batBatterycapacitylow status."
		::= { upsIta2comEntry 544 }
upsIta2com544Addr6Batalarmnumber OBJECT-TYPE
		SYNTAX Integer32
		
		MAX-ACCESS read-only
		STATUS current
		DESCRIPTION
		"upsIta2com543Addr6Batalarmnumber stored as 1."
		::= { upsIta2comEntry 545 }
upsIta2com545Addr6Bathighvolt OBJECT-TYPE
		SYNTAX INTEGER {
			normal(0),
			alarm(1) }
		MAX-ACCESS read-only
		STATUS current
		DESCRIPTION
		"upsIta2com544Addr6Bathighvolt status."
		::= { upsIta2comEntry 546 }
upsIta2com546Addr6Batlowvolt OBJECT-TYPE
		SYNTAX INTEGER {
			normal(0),
			alarm(1) }
		MAX-ACCESS read-only
		STATUS current
		DESCRIPTION
		"upsIta2com545Addr6Batlowvolt status."
		::= { upsIta2comEntry 547 }
upsIta2com547Addr6Bathighcellvolt OBJECT-TYPE
		SYNTAX INTEGER {
			normal(0),
			alarm(1) }
		MAX-ACCESS read-only
		STATUS current
		DESCRIPTION
		"upsIta2com546Addr6Bathighcellvolt status."
		::= { upsIta2comEntry 548 }
upsIta2com548Addr6Batlowcellvolt OBJECT-TYPE
		SYNTAX INTEGER {
			normal(0),
			alarm(1) }
		MAX-ACCESS read-only
		STATUS current
		DESCRIPTION
		"upsIta2com547Addr6Batlowcellvolt status."
		::= { upsIta2comEntry 549 }
upsIta2com549Addr6Batchargehighcelltemp OBJECT-TYPE
		SYNTAX INTEGER {
			normal(0),
			alarm(1) }
		MAX-ACCESS read-only
		STATUS current
		DESCRIPTION
		"upsIta2com548Addr6Batchargehighcelltemp status."
		::= { upsIta2comEntry 550 }
upsIta2com550Addr6Batchargelowcelltemp OBJECT-TYPE
		SYNTAX INTEGER {
			normal(0),
			alarm(1) }
		MAX-ACCESS read-only
		STATUS current
		DESCRIPTION
		"upsIta2com549Addr6Batchargelowcelltemp status."
		::= { upsIta2comEntry 551 }
upsIta2com551Addr6Batchargeovercurrent OBJECT-TYPE
		SYNTAX INTEGER {
			normal(0),
			alarm(1) }
		MAX-ACCESS read-only
		STATUS current
		DESCRIPTION
		"upsIta2com550Addr6Batchargeovercurrent status."
		::= { upsIta2comEntry 552 }
upsIta2com552Addr6Batdischargeovercurrent OBJECT-TYPE
		SYNTAX INTEGER {
			normal(0),
			alarm(1) }
		MAX-ACCESS read-only
		STATUS current
		DESCRIPTION
		"upsIta2com551Addr6Batdischargeovercurrent status."
		::= { upsIta2comEntry 553 }
upsIta2com553Addr6BatAddrconflict OBJECT-TYPE
		SYNTAX INTEGER {
			normal(0),
			alarm(1) }
		MAX-ACCESS read-only
		STATUS current
		DESCRIPTION
		"upsIta2com552Addr6BatAddrconflict status."
		::= { upsIta2comEntry 554 }
upsIta2com554Addr6Batportreverse OBJECT-TYPE
		SYNTAX INTEGER {
			normal(0),
			alarm(1) }
		MAX-ACCESS read-only
		STATUS current
		DESCRIPTION
		"upsIta2com553Addr6Batportreverse status."
		::= { upsIta2comEntry 555 }
upsIta2com555Addr6BatBMSrelayinvalid OBJECT-TYPE
		SYNTAX INTEGER {
			normal(0),
			alarm(1) }
		MAX-ACCESS read-only
		STATUS current
		DESCRIPTION
		"upsIta2com554Addr6BatBMSrelayinvalid status."
		::= { upsIta2comEntry 556 }
upsIta2com556Addr6Batsafetyundervoltage OBJECT-TYPE
		SYNTAX INTEGER {
			normal(0),
			alarm(1) }
		MAX-ACCESS read-only
		STATUS current
		DESCRIPTION
		"upsIta2com555Addr6Batsafetyundervoltage status."
		::= { upsIta2comEntry 557 }
upsIta2com557Addr6Batdischargehighcelltemp OBJECT-TYPE
		SYNTAX INTEGER {
			normal(0),
			alarm(1) }
		MAX-ACCESS read-only
		STATUS current
		DESCRIPTION
		"upsIta2com556Addr6Batdischargehighcelltemp status."
		::= { upsIta2comEntry 558 }
upsIta2com558Addr6Batdischargelowcelltemp OBJECT-TYPE
		SYNTAX INTEGER {
			normal(0),
			alarm(1) }
		MAX-ACCESS read-only
		STATUS current
		DESCRIPTION
		"upsIta2com557Addr6Batdischargelowcelltemp status."
		::= { upsIta2comEntry 559 }
upsIta2com559Addr6Batparallelchargehightemp OBJECT-TYPE
		SYNTAX INTEGER {
			normal(0),
			alarm(1) }
		MAX-ACCESS read-only
		STATUS current
		DESCRIPTION
		"upsIta2com558Addr6Batparallelchargehightemp status."
		::= { upsIta2comEntry 560 }
upsIta2com560Addr6BatinternalCommabnormal OBJECT-TYPE
		SYNTAX INTEGER {
			normal(0),
			alarm(1) }
		MAX-ACCESS read-only
		STATUS current
		DESCRIPTION
		"upsIta2com559Addr6BatinternalCommabnormal status."
		::= { upsIta2comEntry 561 }
upsIta2com561Addr6Batconditionfail OBJECT-TYPE
		SYNTAX INTEGER {
			normal(0),
			alarm(1) }
		MAX-ACCESS read-only
		STATUS current
		DESCRIPTION
		"upsIta2com560Addr6Batconditionfail status."
		::= { upsIta2comEntry 562 }
upsIta2com562Addr6BatLowinsulationresistance OBJECT-TYPE
		SYNTAX INTEGER {
			normal(0),
			alarm(1) }
		MAX-ACCESS read-only
		STATUS current
		DESCRIPTION
		"upsIta2com561Addr6BatLowinsulationresistance status."
		::= { upsIta2comEntry 563 }
upsIta2com563Addr6BatLargepressurediff OBJECT-TYPE
		SYNTAX INTEGER {
			normal(0),
			alarm(1) }
		MAX-ACCESS read-only
		STATUS current
		DESCRIPTION
		"upsIta2com562Addr6BatLargepressurediff status."
		::= { upsIta2comEntry 564 }
upsIta2com564Addr6BatBatfailure OBJECT-TYPE
		SYNTAX INTEGER {
			normal(0),
			alarm(1) }
		MAX-ACCESS read-only
		STATUS current
		DESCRIPTION
		"upsIta2com563Addr6BatBatfailure status."
		::= { upsIta2comEntry 565 }
upsIta2com565Addr6BatVoltageacquisitfailure OBJECT-TYPE
		SYNTAX INTEGER {
			normal(0),
			alarm(1) }
		MAX-ACCESS read-only
		STATUS current
		DESCRIPTION
		"upsIta2com564Addr6BatVoltageacquisitfailure status."
		::= { upsIta2comEntry 566 }
upsIta2com566Addr6BatCurrentcolllectfailure OBJECT-TYPE
		SYNTAX INTEGER {
			normal(0),
			alarm(1) }
		MAX-ACCESS read-only
		STATUS current
		DESCRIPTION
		"upsIta2com565Addr6BatCurrentcolllectfailure status."
		::= { upsIta2comEntry 567 }
upsIta2com567Addr6BatTempcolllectfailure OBJECT-TYPE
		SYNTAX INTEGER {
			normal(0),
			alarm(1) }
		MAX-ACCESS read-only
		STATUS current
		DESCRIPTION
		"upsIta2com566Addr6BatTempcolllectfailure status."
		::= { upsIta2comEntry 568 }
upsIta2com568Addr6BatAddrSeterror OBJECT-TYPE
		SYNTAX INTEGER {
			normal(0),
			alarm(1) }
		MAX-ACCESS read-only
		STATUS current
		DESCRIPTION
		"upsIta2com567Addr6BatAddrSeterror status."
		::= { upsIta2comEntry 569 }
upsIta2com569Addr6BatLargegrouppressurediff OBJECT-TYPE
		SYNTAX INTEGER {
			normal(0),
			alarm(1) }
		MAX-ACCESS read-only
		STATUS current
		DESCRIPTION
		"upsIta2com568Addr6BatLargegrouppressurediff status."
		::= { upsIta2comEntry 570 }
upsIta2com570Addr6BatMOSFETfailure OBJECT-TYPE
		SYNTAX INTEGER {
			normal(0),
			alarm(1) }
		MAX-ACCESS read-only
		STATUS current
		DESCRIPTION
		"upsIta2com569Addr6BatMOSFETfailure status."
		::= { upsIta2comEntry 571 }
upsIta2com571Addr6Battempabnormal OBJECT-TYPE
		SYNTAX INTEGER {
			normal(0),
			alarm(1) }
		MAX-ACCESS read-only
		STATUS current
		DESCRIPTION
		"upsIta2com570Addr6Battempabnormal status."
		::= { upsIta2comEntry 572 }
upsIta2com572Addr6Batcablefault OBJECT-TYPE
		SYNTAX INTEGER {
			normal(0),
			alarm(1) }
		MAX-ACCESS read-only
		STATUS current
		DESCRIPTION
		"upsIta2com571Addr6Batcablefault status."
		::= { upsIta2comEntry 573 }
upsIta2com573Addr6BatShortcircuit OBJECT-TYPE
		SYNTAX INTEGER {
			normal(0),
			alarm(1) }
		MAX-ACCESS read-only
		STATUS current
		DESCRIPTION
		"upsIta2com572Addr6BatShortcircuit status."
		::= { upsIta2comEntry 574 }
upsIta2com574Addr6BatOtherfailures OBJECT-TYPE
		SYNTAX INTEGER {
			normal(0),
			alarm(1) }
		MAX-ACCESS read-only
		STATUS current
		DESCRIPTION
		"upsIta2com573Addr6BatOtherfailures status."
		::= { upsIta2comEntry 575 }
upsIta2com575Addr6BatCommcablefailure OBJECT-TYPE
		SYNTAX INTEGER {
			normal(0),
			alarm(1) }
		MAX-ACCESS read-only
		STATUS current
		DESCRIPTION
		"upsIta2com574Addr6BatCommcablefailure status."
		::= { upsIta2comEntry 576 }
upsIta2com576Addr6BatMOSFETtempishigh OBJECT-TYPE
		SYNTAX INTEGER {
			normal(0),
			alarm(1) }
		MAX-ACCESS read-only
		STATUS current
		DESCRIPTION
		"upsIta2com575Addr6BatMOSFETtempishigh status."
		::= { upsIta2comEntry 577 }
upsIta2com577Addr6BatFuseblown OBJECT-TYPE
		SYNTAX INTEGER {
			normal(0),
			alarm(1) }
		MAX-ACCESS read-only
		STATUS current
		DESCRIPTION
		"upsIta2com576Addr6BatFuseblown status."
		::= { upsIta2comEntry 578 }
upsIta2com578Addr6BatWaitingforcharging OBJECT-TYPE
		SYNTAX INTEGER {
			normal(0),
			alarm(1) }
		MAX-ACCESS read-only
		STATUS current
		DESCRIPTION
		"upsIta2com577Addr6BatWaitingforcharging status."
		::= { upsIta2comEntry 579 }
upsIta2com579Addr6BatBataging OBJECT-TYPE
		SYNTAX INTEGER {
			normal(0),
			alarm(1) }
		MAX-ACCESS read-only
		STATUS current
		DESCRIPTION
		"upsIta2com578Addr6BatBataging status."
		::= { upsIta2comEntry 580 }
upsIta2com580Addr6Batboxconnectabnormal OBJECT-TYPE
		SYNTAX INTEGER {
			normal(0),
			alarm(1) }
		MAX-ACCESS read-only
		STATUS current
		DESCRIPTION
		"upsIta2com579Addr6Batboxconnectabnormal status."
		::= { upsIta2comEntry 581 }
upsIta2com581Addr6batBatterySoftincompatible OBJECT-TYPE
		SYNTAX INTEGER {
			normal(0),
			alarm(1) }
		MAX-ACCESS read-only
		STATUS current
		DESCRIPTION
		"upsIta2com580Addr6batBatterySoftincompatible status."
		::= { upsIta2comEntry 582 }
upsIta2com582Addr6batEOL OBJECT-TYPE
		SYNTAX INTEGER {
			normal(0),
			alarm(1) }
		MAX-ACCESS read-only
		STATUS current
		DESCRIPTION
		"upsIta2com581Addr6batEOL status."
		::= { upsIta2comEntry 583 }
upsIta2com583Addr6batSamplingfailure OBJECT-TYPE
		SYNTAX INTEGER {
			normal(0),
			alarm(1) }
		MAX-ACCESS read-only
		STATUS current
		DESCRIPTION
		"upsIta2com582Addr6batSamplingfailure status."
		::= { upsIta2comEntry 584 }
upsIta2com584Addr6batHardwareprotection OBJECT-TYPE
		SYNTAX INTEGER {
			normal(0),
			alarm(1) }
		MAX-ACCESS read-only
		STATUS current
		DESCRIPTION
		"upsIta2com583Addr6batHardwareprotection status."
		::= { upsIta2comEntry 585 }
upsIta2com585Addr6batBatterycapacitylow OBJECT-TYPE
		SYNTAX INTEGER {
			normal(0),
			alarm(1) }
		MAX-ACCESS read-only
		STATUS current
		DESCRIPTION
		"upsIta2com584Addr6batBatterycapacitylow status."
		::= { upsIta2comEntry 586 }
upsIta2com586Addr7Batalarmnumber OBJECT-TYPE
		SYNTAX Integer32
		
		MAX-ACCESS read-only
		STATUS current
		DESCRIPTION
		"upsIta2com585Addr7Batalarmnumber stored as 1."
		::= { upsIta2comEntry 587 }
upsIta2com587Addr7Bathighvolt OBJECT-TYPE
		SYNTAX INTEGER {
			normal(0),
			alarm(1) }
		MAX-ACCESS read-only
		STATUS current
		DESCRIPTION
		"upsIta2com586Addr7Bathighvolt status."
		::= { upsIta2comEntry 588 }
upsIta2com588Addr7Batlowvolt OBJECT-TYPE
		SYNTAX INTEGER {
			normal(0),
			alarm(1) }
		MAX-ACCESS read-only
		STATUS current
		DESCRIPTION
		"upsIta2com587Addr7Batlowvolt status."
		::= { upsIta2comEntry 589 }
upsIta2com589Addr7Bathighcellvolt OBJECT-TYPE
		SYNTAX INTEGER {
			normal(0),
			alarm(1) }
		MAX-ACCESS read-only
		STATUS current
		DESCRIPTION
		"upsIta2com588Addr7Bathighcellvolt status."
		::= { upsIta2comEntry 590 }
upsIta2com590Addr7Batlowcellvolt OBJECT-TYPE
		SYNTAX INTEGER {
			normal(0),
			alarm(1) }
		MAX-ACCESS read-only
		STATUS current
		DESCRIPTION
		"upsIta2com589Addr7Batlowcellvolt status."
		::= { upsIta2comEntry 591 }
upsIta2com591Addr7Batchargehighcelltemp OBJECT-TYPE
		SYNTAX INTEGER {
			normal(0),
			alarm(1) }
		MAX-ACCESS read-only
		STATUS current
		DESCRIPTION
		"upsIta2com590Addr7Batchargehighcelltemp status."
		::= { upsIta2comEntry 592 }
upsIta2com592Addr7Batchargelowcelltemp OBJECT-TYPE
		SYNTAX INTEGER {
			normal(0),
			alarm(1) }
		MAX-ACCESS read-only
		STATUS current
		DESCRIPTION
		"upsIta2com591Addr7Batchargelowcelltemp status."
		::= { upsIta2comEntry 593 }
upsIta2com593Addr7Batchargeovercurrent OBJECT-TYPE
		SYNTAX INTEGER {
			normal(0),
			alarm(1) }
		MAX-ACCESS read-only
		STATUS current
		DESCRIPTION
		"upsIta2com592Addr7Batchargeovercurrent status."
		::= { upsIta2comEntry 594 }
upsIta2com594Addr7Batdischargeovercurrent OBJECT-TYPE
		SYNTAX INTEGER {
			normal(0),
			alarm(1) }
		MAX-ACCESS read-only
		STATUS current
		DESCRIPTION
		"upsIta2com593Addr7Batdischargeovercurrent status."
		::= { upsIta2comEntry 595 }
upsIta2com595Addr7BatAddrconflict OBJECT-TYPE
		SYNTAX INTEGER {
			normal(0),
			alarm(1) }
		MAX-ACCESS read-only
		STATUS current
		DESCRIPTION
		"upsIta2com594Addr7BatAddrconflict status."
		::= { upsIta2comEntry 596 }
upsIta2com596Addr7Batportreverse OBJECT-TYPE
		SYNTAX INTEGER {
			normal(0),
			alarm(1) }
		MAX-ACCESS read-only
		STATUS current
		DESCRIPTION
		"upsIta2com595Addr7Batportreverse status."
		::= { upsIta2comEntry 597 }
upsIta2com597Addr7BatBMSrelayinvalid OBJECT-TYPE
		SYNTAX INTEGER {
			normal(0),
			alarm(1) }
		MAX-ACCESS read-only
		STATUS current
		DESCRIPTION
		"upsIta2com596Addr7BatBMSrelayinvalid status."
		::= { upsIta2comEntry 598 }
upsIta2com598Addr7Batsafetyundervoltage OBJECT-TYPE
		SYNTAX INTEGER {
			normal(0),
			alarm(1) }
		MAX-ACCESS read-only
		STATUS current
		DESCRIPTION
		"upsIta2com597Addr7Batsafetyundervoltage status."
		::= { upsIta2comEntry 599 }
upsIta2com599Addr7Batdischargehighcelltemp OBJECT-TYPE
		SYNTAX INTEGER {
			normal(0),
			alarm(1) }
		MAX-ACCESS read-only
		STATUS current
		DESCRIPTION
		"upsIta2com598Addr7Batdischargehighcelltemp status."
		::= { upsIta2comEntry 600 }
upsIta2com600Addr7Batdischargelowcelltemp OBJECT-TYPE
		SYNTAX INTEGER {
			normal(0),
			alarm(1) }
		MAX-ACCESS read-only
		STATUS current
		DESCRIPTION
		"upsIta2com599Addr7Batdischargelowcelltemp status."
		::= { upsIta2comEntry 601 }
upsIta2com601Addr7Batparallelchargehightemp OBJECT-TYPE
		SYNTAX INTEGER {
			normal(0),
			alarm(1) }
		MAX-ACCESS read-only
		STATUS current
		DESCRIPTION
		"upsIta2com600Addr7Batparallelchargehightemp status."
		::= { upsIta2comEntry 602 }
upsIta2com602Addr7BatinternalCommabnormal OBJECT-TYPE
		SYNTAX INTEGER {
			normal(0),
			alarm(1) }
		MAX-ACCESS read-only
		STATUS current
		DESCRIPTION
		"upsIta2com601Addr7BatinternalCommabnormal status."
		::= { upsIta2comEntry 603 }
upsIta2com603Addr7Batconditionfail OBJECT-TYPE
		SYNTAX INTEGER {
			normal(0),
			alarm(1) }
		MAX-ACCESS read-only
		STATUS current
		DESCRIPTION
		"upsIta2com602Addr7Batconditionfail status."
		::= { upsIta2comEntry 604 }
upsIta2com604Addr7BatLowinsulationresistance OBJECT-TYPE
		SYNTAX INTEGER {
			normal(0),
			alarm(1) }
		MAX-ACCESS read-only
		STATUS current
		DESCRIPTION
		"upsIta2com603Addr7BatLowinsulationresistance status."
		::= { upsIta2comEntry 605 }
upsIta2com605Addr7BatLargepressurediff OBJECT-TYPE
		SYNTAX INTEGER {
			normal(0),
			alarm(1) }
		MAX-ACCESS read-only
		STATUS current
		DESCRIPTION
		"upsIta2com604Addr7BatLargepressurediff status."
		::= { upsIta2comEntry 606 }
upsIta2com606Addr7BatBatfailure OBJECT-TYPE
		SYNTAX INTEGER {
			normal(0),
			alarm(1) }
		MAX-ACCESS read-only
		STATUS current
		DESCRIPTION
		"upsIta2com605Addr7BatBatfailure status."
		::= { upsIta2comEntry 607 }
upsIta2com607Addr7BatVoltageacquisitfailure OBJECT-TYPE
		SYNTAX INTEGER {
			normal(0),
			alarm(1) }
		MAX-ACCESS read-only
		STATUS current
		DESCRIPTION
		"upsIta2com606Addr7BatVoltageacquisitfailure status."
		::= { upsIta2comEntry 608 }
upsIta2com608Addr7BatCurrentcolllectfailure OBJECT-TYPE
		SYNTAX INTEGER {
			normal(0),
			alarm(1) }
		MAX-ACCESS read-only
		STATUS current
		DESCRIPTION
		"upsIta2com607Addr7BatCurrentcolllectfailure status."
		::= { upsIta2comEntry 609 }
upsIta2com609Addr7BatTempcolllectfailure OBJECT-TYPE
		SYNTAX INTEGER {
			normal(0),
			alarm(1) }
		MAX-ACCESS read-only
		STATUS current
		DESCRIPTION
		"upsIta2com608Addr7BatTempcolllectfailure status."
		::= { upsIta2comEntry 610 }
upsIta2com610Addr7BatAddrSeterror OBJECT-TYPE
		SYNTAX INTEGER {
			normal(0),
			alarm(1) }
		MAX-ACCESS read-only
		STATUS current
		DESCRIPTION
		"upsIta2com609Addr7BatAddrSeterror status."
		::= { upsIta2comEntry 611 }
upsIta2com611Addr7BatLargegrouppressurediff OBJECT-TYPE
		SYNTAX INTEGER {
			normal(0),
			alarm(1) }
		MAX-ACCESS read-only
		STATUS current
		DESCRIPTION
		"upsIta2com610Addr7BatLargegrouppressurediff status."
		::= { upsIta2comEntry 612 }
upsIta2com612Addr7BatMOSFETfailure OBJECT-TYPE
		SYNTAX INTEGER {
			normal(0),
			alarm(1) }
		MAX-ACCESS read-only
		STATUS current
		DESCRIPTION
		"upsIta2com611Addr7BatMOSFETfailure status."
		::= { upsIta2comEntry 613 }
upsIta2com613Addr7Battempabnormal OBJECT-TYPE
		SYNTAX INTEGER {
			normal(0),
			alarm(1) }
		MAX-ACCESS read-only
		STATUS current
		DESCRIPTION
		"upsIta2com612Addr7Battempabnormal status."
		::= { upsIta2comEntry 614 }
upsIta2com614Addr7Batcablefault OBJECT-TYPE
		SYNTAX INTEGER {
			normal(0),
			alarm(1) }
		MAX-ACCESS read-only
		STATUS current
		DESCRIPTION
		"upsIta2com613Addr7Batcablefault status."
		::= { upsIta2comEntry 615 }
upsIta2com615Addr7BatShortcircuit OBJECT-TYPE
		SYNTAX INTEGER {
			normal(0),
			alarm(1) }
		MAX-ACCESS read-only
		STATUS current
		DESCRIPTION
		"upsIta2com614Addr7BatShortcircuit status."
		::= { upsIta2comEntry 616 }
upsIta2com616Addr7BatOtherfailures OBJECT-TYPE
		SYNTAX INTEGER {
			normal(0),
			alarm(1) }
		MAX-ACCESS read-only
		STATUS current
		DESCRIPTION
		"upsIta2com615Addr7BatOtherfailures status."
		::= { upsIta2comEntry 617 }
upsIta2com617Addr7BatCommcablefailure OBJECT-TYPE
		SYNTAX INTEGER {
			normal(0),
			alarm(1) }
		MAX-ACCESS read-only
		STATUS current
		DESCRIPTION
		"upsIta2com616Addr7BatCommcablefailure status."
		::= { upsIta2comEntry 618 }
upsIta2com618Addr7BatMOSFETtempishigh OBJECT-TYPE
		SYNTAX INTEGER {
			normal(0),
			alarm(1) }
		MAX-ACCESS read-only
		STATUS current
		DESCRIPTION
		"upsIta2com617Addr7BatMOSFETtempishigh status."
		::= { upsIta2comEntry 619 }
upsIta2com619Addr7BatFuseblown OBJECT-TYPE
		SYNTAX INTEGER {
			normal(0),
			alarm(1) }
		MAX-ACCESS read-only
		STATUS current
		DESCRIPTION
		"upsIta2com618Addr7BatFuseblown status."
		::= { upsIta2comEntry 620 }
upsIta2com620Addr7BatWaitingforcharging OBJECT-TYPE
		SYNTAX INTEGER {
			normal(0),
			alarm(1) }
		MAX-ACCESS read-only
		STATUS current
		DESCRIPTION
		"upsIta2com619Addr7BatWaitingforcharging status."
		::= { upsIta2comEntry 621 }
upsIta2com621Addr7BatBataging OBJECT-TYPE
		SYNTAX INTEGER {
			normal(0),
			alarm(1) }
		MAX-ACCESS read-only
		STATUS current
		DESCRIPTION
		"upsIta2com620Addr7BatBataging status."
		::= { upsIta2comEntry 622 }
upsIta2com622Addr7Batboxconnectabnormal OBJECT-TYPE
		SYNTAX INTEGER {
			normal(0),
			alarm(1) }
		MAX-ACCESS read-only
		STATUS current
		DESCRIPTION
		"upsIta2com621Addr7Batboxconnectabnormal status."
		::= { upsIta2comEntry 623 }
upsIta2com623Addr7batBatterySoftincompatible OBJECT-TYPE
		SYNTAX INTEGER {
			normal(0),
			alarm(1) }
		MAX-ACCESS read-only
		STATUS current
		DESCRIPTION
		"upsIta2com622Addr7batBatterySoftincompatible status."
		::= { upsIta2comEntry 624 }
upsIta2com624Addr7batEOL OBJECT-TYPE
		SYNTAX INTEGER {
			normal(0),
			alarm(1) }
		MAX-ACCESS read-only
		STATUS current
		DESCRIPTION
		"upsIta2com623Addr7batEOL status."
		::= { upsIta2comEntry 625 }
upsIta2com625Addr7batSamplingfailure OBJECT-TYPE
		SYNTAX INTEGER {
			normal(0),
			alarm(1) }
		MAX-ACCESS read-only
		STATUS current
		DESCRIPTION
		"upsIta2com624Addr7batSamplingfailure status."
		::= { upsIta2comEntry 626 }
upsIta2com626Addr7batHardwareprotection OBJECT-TYPE
		SYNTAX INTEGER {
			normal(0),
			alarm(1) }
		MAX-ACCESS read-only
		STATUS current
		DESCRIPTION
		"upsIta2com625Addr7batHardwareprotection status."
		::= { upsIta2comEntry 627 }
upsIta2com627Addr7batBatterycapacitylow OBJECT-TYPE
		SYNTAX INTEGER {
			normal(0),
			alarm(1) }
		MAX-ACCESS read-only
		STATUS current
		DESCRIPTION
		"upsIta2com626Addr7batBatterycapacitylow status."
		::= { upsIta2comEntry 628 }
upsIta2com628Addr8Batalarmnumber OBJECT-TYPE
		SYNTAX Integer32
		
		MAX-ACCESS read-only
		STATUS current
		DESCRIPTION
		"upsIta2com627Addr8Batalarmnumber stored as 1."
		::= { upsIta2comEntry 629 }
upsIta2com629Addr8Bathighvolt OBJECT-TYPE
		SYNTAX INTEGER {
			normal(0),
			alarm(1) }
		MAX-ACCESS read-only
		STATUS current
		DESCRIPTION
		"upsIta2com628Addr8Bathighvolt status."
		::= { upsIta2comEntry 630 }
upsIta2com630Addr8Batlowvolt OBJECT-TYPE
		SYNTAX INTEGER {
			normal(0),
			alarm(1) }
		MAX-ACCESS read-only
		STATUS current
		DESCRIPTION
		"upsIta2com629Addr8Batlowvolt status."
		::= { upsIta2comEntry 631 }
upsIta2com631Addr8Bathighcellvolt OBJECT-TYPE
		SYNTAX INTEGER {
			normal(0),
			alarm(1) }
		MAX-ACCESS read-only
		STATUS current
		DESCRIPTION
		"upsIta2com630Addr8Bathighcellvolt status."
		::= { upsIta2comEntry 632 }
upsIta2com632Addr8Batlowcellvolt OBJECT-TYPE
		SYNTAX INTEGER {
			normal(0),
			alarm(1) }
		MAX-ACCESS read-only
		STATUS current
		DESCRIPTION
		"upsIta2com631Addr8Batlowcellvolt status."
		::= { upsIta2comEntry 633 }
upsIta2com633Addr8Batchargehighcelltemp OBJECT-TYPE
		SYNTAX INTEGER {
			normal(0),
			alarm(1) }
		MAX-ACCESS read-only
		STATUS current
		DESCRIPTION
		"upsIta2com632Addr8Batchargehighcelltemp status."
		::= { upsIta2comEntry 634 }
upsIta2com634Addr8Batchargelowcelltemp OBJECT-TYPE
		SYNTAX INTEGER {
			normal(0),
			alarm(1) }
		MAX-ACCESS read-only
		STATUS current
		DESCRIPTION
		"upsIta2com633Addr8Batchargelowcelltemp status."
		::= { upsIta2comEntry 635 }
upsIta2com635Addr8Batchargeovercurrent OBJECT-TYPE
		SYNTAX INTEGER {
			normal(0),
			alarm(1) }
		MAX-ACCESS read-only
		STATUS current
		DESCRIPTION
		"upsIta2com634Addr8Batchargeovercurrent status."
		::= { upsIta2comEntry 636 }
upsIta2com636Addr8Batdischargeovercurrent OBJECT-TYPE
		SYNTAX INTEGER {
			normal(0),
			alarm(1) }
		MAX-ACCESS read-only
		STATUS current
		DESCRIPTION
		"upsIta2com635Addr8Batdischargeovercurrent status."
		::= { upsIta2comEntry 637 }
upsIta2com637Addr8BatAddrconflict OBJECT-TYPE
		SYNTAX INTEGER {
			normal(0),
			alarm(1) }
		MAX-ACCESS read-only
		STATUS current
		DESCRIPTION
		"upsIta2com636Addr8BatAddrconflict status."
		::= { upsIta2comEntry 638 }
upsIta2com638Addr8Batportreverse OBJECT-TYPE
		SYNTAX INTEGER {
			normal(0),
			alarm(1) }
		MAX-ACCESS read-only
		STATUS current
		DESCRIPTION
		"upsIta2com637Addr8Batportreverse status."
		::= { upsIta2comEntry 639 }
upsIta2com639Addr8BatBMSrelayinvalid OBJECT-TYPE
		SYNTAX INTEGER {
			normal(0),
			alarm(1) }
		MAX-ACCESS read-only
		STATUS current
		DESCRIPTION
		"upsIta2com638Addr8BatBMSrelayinvalid status."
		::= { upsIta2comEntry 640 }
upsIta2com640Addr8Batsafetyundervoltage OBJECT-TYPE
		SYNTAX INTEGER {
			normal(0),
			alarm(1) }
		MAX-ACCESS read-only
		STATUS current
		DESCRIPTION
		"upsIta2com639Addr8Batsafetyundervoltage status."
		::= { upsIta2comEntry 641 }
upsIta2com641Addr8Batdischargehighcelltemp OBJECT-TYPE
		SYNTAX INTEGER {
			normal(0),
			alarm(1) }
		MAX-ACCESS read-only
		STATUS current
		DESCRIPTION
		"upsIta2com640Addr8Batdischargehighcelltemp status."
		::= { upsIta2comEntry 642 }
upsIta2com642Addr8Batdischargelowcelltemp OBJECT-TYPE
		SYNTAX INTEGER {
			normal(0),
			alarm(1) }
		MAX-ACCESS read-only
		STATUS current
		DESCRIPTION
		"upsIta2com641Addr8Batdischargelowcelltemp status."
		::= { upsIta2comEntry 643 }
upsIta2com643Addr8Batparallelchargehightemp OBJECT-TYPE
		SYNTAX INTEGER {
			normal(0),
			alarm(1) }
		MAX-ACCESS read-only
		STATUS current
		DESCRIPTION
		"upsIta2com642Addr8Batparallelchargehightemp status."
		::= { upsIta2comEntry 644 }
upsIta2com644Addr8BatinternalCommabnormal OBJECT-TYPE
		SYNTAX INTEGER {
			normal(0),
			alarm(1) }
		MAX-ACCESS read-only
		STATUS current
		DESCRIPTION
		"upsIta2com643Addr8BatinternalCommabnormal status."
		::= { upsIta2comEntry 645 }
upsIta2com645Addr8Batconditionfail OBJECT-TYPE
		SYNTAX INTEGER {
			normal(0),
			alarm(1) }
		MAX-ACCESS read-only
		STATUS current
		DESCRIPTION
		"upsIta2com644Addr8Batconditionfail status."
		::= { upsIta2comEntry 646 }
upsIta2com646Addr8BatLowinsulationresistance OBJECT-TYPE
		SYNTAX INTEGER {
			normal(0),
			alarm(1) }
		MAX-ACCESS read-only
		STATUS current
		DESCRIPTION
		"upsIta2com645Addr8BatLowinsulationresistance status."
		::= { upsIta2comEntry 647 }
upsIta2com647Addr8BatLargepressurediff OBJECT-TYPE
		SYNTAX INTEGER {
			normal(0),
			alarm(1) }
		MAX-ACCESS read-only
		STATUS current
		DESCRIPTION
		"upsIta2com646Addr8BatLargepressurediff status."
		::= { upsIta2comEntry 648 }
upsIta2com648Addr8BatBatfailure OBJECT-TYPE
		SYNTAX INTEGER {
			normal(0),
			alarm(1) }
		MAX-ACCESS read-only
		STATUS current
		DESCRIPTION
		"upsIta2com647Addr8BatBatfailure status."
		::= { upsIta2comEntry 649 }
upsIta2com649Addr8BatVoltageacquisitfailure OBJECT-TYPE
		SYNTAX INTEGER {
			normal(0),
			alarm(1) }
		MAX-ACCESS read-only
		STATUS current
		DESCRIPTION
		"upsIta2com648Addr8BatVoltageacquisitfailure status."
		::= { upsIta2comEntry 650 }
upsIta2com650Addr8BatCurrentcolllectfailure OBJECT-TYPE
		SYNTAX INTEGER {
			normal(0),
			alarm(1) }
		MAX-ACCESS read-only
		STATUS current
		DESCRIPTION
		"upsIta2com649Addr8BatCurrentcolllectfailure status."
		::= { upsIta2comEntry 651 }
upsIta2com651Addr8BatTempcolllectfailure OBJECT-TYPE
		SYNTAX INTEGER {
			normal(0),
			alarm(1) }
		MAX-ACCESS read-only
		STATUS current
		DESCRIPTION
		"upsIta2com650Addr8BatTempcolllectfailure status."
		::= { upsIta2comEntry 652 }
upsIta2com652Addr8BatAddrSeterror OBJECT-TYPE
		SYNTAX INTEGER {
			normal(0),
			alarm(1) }
		MAX-ACCESS read-only
		STATUS current
		DESCRIPTION
		"upsIta2com651Addr8BatAddrSeterror status."
		::= { upsIta2comEntry 653 }
upsIta2com653Addr8BatLargegrouppressurediff OBJECT-TYPE
		SYNTAX INTEGER {
			normal(0),
			alarm(1) }
		MAX-ACCESS read-only
		STATUS current
		DESCRIPTION
		"upsIta2com652Addr8BatLargegrouppressurediff status."
		::= { upsIta2comEntry 654 }
upsIta2com654Addr8BatMOSFETfailure OBJECT-TYPE
		SYNTAX INTEGER {
			normal(0),
			alarm(1) }
		MAX-ACCESS read-only
		STATUS current
		DESCRIPTION
		"upsIta2com653Addr8BatMOSFETfailure status."
		::= { upsIta2comEntry 655 }
upsIta2com655Addr8Battempabnormal OBJECT-TYPE
		SYNTAX INTEGER {
			normal(0),
			alarm(1) }
		MAX-ACCESS read-only
		STATUS current
		DESCRIPTION
		"upsIta2com654Addr8Battempabnormal status."
		::= { upsIta2comEntry 656 }
upsIta2com656Addr8Batcablefault OBJECT-TYPE
		SYNTAX INTEGER {
			normal(0),
			alarm(1) }
		MAX-ACCESS read-only
		STATUS current
		DESCRIPTION
		"upsIta2com655Addr8Batcablefault status."
		::= { upsIta2comEntry 657 }
upsIta2com657Addr8BatShortcircuit OBJECT-TYPE
		SYNTAX INTEGER {
			normal(0),
			alarm(1) }
		MAX-ACCESS read-only
		STATUS current
		DESCRIPTION
		"upsIta2com656Addr8BatShortcircuit status."
		::= { upsIta2comEntry 658 }
upsIta2com658Addr8BatOtherfailures OBJECT-TYPE
		SYNTAX INTEGER {
			normal(0),
			alarm(1) }
		MAX-ACCESS read-only
		STATUS current
		DESCRIPTION
		"upsIta2com657Addr8BatOtherfailures status."
		::= { upsIta2comEntry 659 }
upsIta2com659Addr8BatCommcablefailure OBJECT-TYPE
		SYNTAX INTEGER {
			normal(0),
			alarm(1) }
		MAX-ACCESS read-only
		STATUS current
		DESCRIPTION
		"upsIta2com658Addr8BatCommcablefailure status."
		::= { upsIta2comEntry 660 }
upsIta2com660Addr8BatMOSFETtempishigh OBJECT-TYPE
		SYNTAX INTEGER {
			normal(0),
			alarm(1) }
		MAX-ACCESS read-only
		STATUS current
		DESCRIPTION
		"upsIta2com659Addr8BatMOSFETtempishigh status."
		::= { upsIta2comEntry 661 }
upsIta2com661Addr8BatFuseblown OBJECT-TYPE
		SYNTAX INTEGER {
			normal(0),
			alarm(1) }
		MAX-ACCESS read-only
		STATUS current
		DESCRIPTION
		"upsIta2com660Addr8BatFuseblown status."
		::= { upsIta2comEntry 662 }
upsIta2com662Addr8BatWaitingforcharging OBJECT-TYPE
		SYNTAX INTEGER {
			normal(0),
			alarm(1) }
		MAX-ACCESS read-only
		STATUS current
		DESCRIPTION
		"upsIta2com661Addr8BatWaitingforcharging status."
		::= { upsIta2comEntry 663 }
upsIta2com663Addr8BatBataging OBJECT-TYPE
		SYNTAX INTEGER {
			normal(0),
			alarm(1) }
		MAX-ACCESS read-only
		STATUS current
		DESCRIPTION
		"upsIta2com662Addr8BatBataging status."
		::= { upsIta2comEntry 664 }
upsIta2com664Addr8Batboxconnectabnormal OBJECT-TYPE
		SYNTAX INTEGER {
			normal(0),
			alarm(1) }
		MAX-ACCESS read-only
		STATUS current
		DESCRIPTION
		"upsIta2com663Addr8Batboxconnectabnormal status."
		::= { upsIta2comEntry 665 }
upsIta2com665Addr8batBatterySoftincompatible OBJECT-TYPE
		SYNTAX INTEGER {
			normal(0),
			alarm(1) }
		MAX-ACCESS read-only
		STATUS current
		DESCRIPTION
		"upsIta2com664Addr8batBatterySoftincompatible status."
		::= { upsIta2comEntry 666 }
upsIta2com666Addr8batEOL OBJECT-TYPE
		SYNTAX INTEGER {
			normal(0),
			alarm(1) }
		MAX-ACCESS read-only
		STATUS current
		DESCRIPTION
		"upsIta2com665Addr8batEOL status."
		::= { upsIta2comEntry 667 }
upsIta2com667Addr8batSamplingfailure OBJECT-TYPE
		SYNTAX INTEGER {
			normal(0),
			alarm(1) }
		MAX-ACCESS read-only
		STATUS current
		DESCRIPTION
		"upsIta2com666Addr8batSamplingfailure status."
		::= { upsIta2comEntry 668 }
upsIta2com668Addr8batHardwareprotection OBJECT-TYPE
		SYNTAX INTEGER {
			normal(0),
			alarm(1) }
		MAX-ACCESS read-only
		STATUS current
		DESCRIPTION
		"upsIta2com667Addr8batHardwareprotection status."
		::= { upsIta2comEntry 669 }
upsIta2com669Addr8batBatterycapacitylow OBJECT-TYPE
		SYNTAX INTEGER {
			normal(0),
			alarm(1) }
		MAX-ACCESS read-only
		STATUS current
		DESCRIPTION
		"upsIta2com668Addr8batBatterycapacitylow status."
		::= { upsIta2comEntry 670 }
upsIta2com670Addr9Batalarmnumber OBJECT-TYPE
		SYNTAX Integer32
		
		MAX-ACCESS read-only
		STATUS current
		DESCRIPTION
		"upsIta2com669Addr9Batalarmnumber stored as 1."
		::= { upsIta2comEntry 671 }
upsIta2com671Addr9Bathighvolt OBJECT-TYPE
		SYNTAX INTEGER {
			normal(0),
			alarm(1) }
		MAX-ACCESS read-only
		STATUS current
		DESCRIPTION
		"upsIta2com670Addr9Bathighvolt status."
		::= { upsIta2comEntry 672 }
upsIta2com672Addr9Batlowvolt OBJECT-TYPE
		SYNTAX INTEGER {
			normal(0),
			alarm(1) }
		MAX-ACCESS read-only
		STATUS current
		DESCRIPTION
		"upsIta2com671Addr9Batlowvolt status."
		::= { upsIta2comEntry 673 }
upsIta2com673Addr9Bathighcellvolt OBJECT-TYPE
		SYNTAX INTEGER {
			normal(0),
			alarm(1) }
		MAX-ACCESS read-only
		STATUS current
		DESCRIPTION
		"upsIta2com672Addr9Bathighcellvolt status."
		::= { upsIta2comEntry 674 }
upsIta2com674Addr9Batlowcellvolt OBJECT-TYPE
		SYNTAX INTEGER {
			normal(0),
			alarm(1) }
		MAX-ACCESS read-only
		STATUS current
		DESCRIPTION
		"upsIta2com673Addr9Batlowcellvolt status."
		::= { upsIta2comEntry 675 }
upsIta2com675Addr9Batchargehighcelltemp OBJECT-TYPE
		SYNTAX INTEGER {
			normal(0),
			alarm(1) }
		MAX-ACCESS read-only
		STATUS current
		DESCRIPTION
		"upsIta2com674Addr9Batchargehighcelltemp status."
		::= { upsIta2comEntry 676 }
upsIta2com676Addr9Batchargelowcelltemp OBJECT-TYPE
		SYNTAX INTEGER {
			normal(0),
			alarm(1) }
		MAX-ACCESS read-only
		STATUS current
		DESCRIPTION
		"upsIta2com675Addr9Batchargelowcelltemp status."
		::= { upsIta2comEntry 677 }
upsIta2com677Addr9Batchargeovercurrent OBJECT-TYPE
		SYNTAX INTEGER {
			normal(0),
			alarm(1) }
		MAX-ACCESS read-only
		STATUS current
		DESCRIPTION
		"upsIta2com676Addr9Batchargeovercurrent status."
		::= { upsIta2comEntry 678 }
upsIta2com678Addr9Batdischargeovercurrent OBJECT-TYPE
		SYNTAX INTEGER {
			normal(0),
			alarm(1) }
		MAX-ACCESS read-only
		STATUS current
		DESCRIPTION
		"upsIta2com677Addr9Batdischargeovercurrent status."
		::= { upsIta2comEntry 679 }
upsIta2com679Addr9BatAddrconflict OBJECT-TYPE
		SYNTAX INTEGER {
			normal(0),
			alarm(1) }
		MAX-ACCESS read-only
		STATUS current
		DESCRIPTION
		"upsIta2com678Addr9BatAddrconflict status."
		::= { upsIta2comEntry 680 }
upsIta2com680Addr9Batportreverse OBJECT-TYPE
		SYNTAX INTEGER {
			normal(0),
			alarm(1) }
		MAX-ACCESS read-only
		STATUS current
		DESCRIPTION
		"upsIta2com679Addr9Batportreverse status."
		::= { upsIta2comEntry 681 }
upsIta2com681Addr9BatBMSrelayinvalid OBJECT-TYPE
		SYNTAX INTEGER {
			normal(0),
			alarm(1) }
		MAX-ACCESS read-only
		STATUS current
		DESCRIPTION
		"upsIta2com680Addr9BatBMSrelayinvalid status."
		::= { upsIta2comEntry 682 }
upsIta2com682Addr9Batsafetyundervoltage OBJECT-TYPE
		SYNTAX INTEGER {
			normal(0),
			alarm(1) }
		MAX-ACCESS read-only
		STATUS current
		DESCRIPTION
		"upsIta2com681Addr9Batsafetyundervoltage status."
		::= { upsIta2comEntry 683 }
upsIta2com683Addr9Batdischargehighcelltemp OBJECT-TYPE
		SYNTAX INTEGER {
			normal(0),
			alarm(1) }
		MAX-ACCESS read-only
		STATUS current
		DESCRIPTION
		"upsIta2com682Addr9Batdischargehighcelltemp status."
		::= { upsIta2comEntry 684 }
upsIta2com684Addr9Batdischargelowcelltemp OBJECT-TYPE
		SYNTAX INTEGER {
			normal(0),
			alarm(1) }
		MAX-ACCESS read-only
		STATUS current
		DESCRIPTION
		"upsIta2com683Addr9Batdischargelowcelltemp status."
		::= { upsIta2comEntry 685 }
upsIta2com685Addr9Batparallelchargehightemp OBJECT-TYPE
		SYNTAX INTEGER {
			normal(0),
			alarm(1) }
		MAX-ACCESS read-only
		STATUS current
		DESCRIPTION
		"upsIta2com684Addr9Batparallelchargehightemp status."
		::= { upsIta2comEntry 686 }
upsIta2com686Addr9BatinternalCommabnormal OBJECT-TYPE
		SYNTAX INTEGER {
			normal(0),
			alarm(1) }
		MAX-ACCESS read-only
		STATUS current
		DESCRIPTION
		"upsIta2com685Addr9BatinternalCommabnormal status."
		::= { upsIta2comEntry 687 }
upsIta2com687Addr9Batconditionfail OBJECT-TYPE
		SYNTAX INTEGER {
			normal(0),
			alarm(1) }
		MAX-ACCESS read-only
		STATUS current
		DESCRIPTION
		"upsIta2com686Addr9Batconditionfail status."
		::= { upsIta2comEntry 688 }
upsIta2com688Addr9BatLowinsulationresistance OBJECT-TYPE
		SYNTAX INTEGER {
			normal(0),
			alarm(1) }
		MAX-ACCESS read-only
		STATUS current
		DESCRIPTION
		"upsIta2com687Addr9BatLowinsulationresistance status."
		::= { upsIta2comEntry 689 }
upsIta2com689Addr9BatLargepressurediff OBJECT-TYPE
		SYNTAX INTEGER {
			normal(0),
			alarm(1) }
		MAX-ACCESS read-only
		STATUS current
		DESCRIPTION
		"upsIta2com688Addr9BatLargepressurediff status."
		::= { upsIta2comEntry 690 }
upsIta2com690Addr9BatBatfailure OBJECT-TYPE
		SYNTAX INTEGER {
			normal(0),
			alarm(1) }
		MAX-ACCESS read-only
		STATUS current
		DESCRIPTION
		"upsIta2com689Addr9BatBatfailure status."
		::= { upsIta2comEntry 691 }
upsIta2com691Addr9BatVoltageacquisitfailure OBJECT-TYPE
		SYNTAX INTEGER {
			normal(0),
			alarm(1) }
		MAX-ACCESS read-only
		STATUS current
		DESCRIPTION
		"upsIta2com690Addr9BatVoltageacquisitfailure status."
		::= { upsIta2comEntry 692 }
upsIta2com692Addr9BatCurrentcolllectfailure OBJECT-TYPE
		SYNTAX INTEGER {
			normal(0),
			alarm(1) }
		MAX-ACCESS read-only
		STATUS current
		DESCRIPTION
		"upsIta2com691Addr9BatCurrentcolllectfailure status."
		::= { upsIta2comEntry 693 }
upsIta2com693Addr9BatTempcolllectfailure OBJECT-TYPE
		SYNTAX INTEGER {
			normal(0),
			alarm(1) }
		MAX-ACCESS read-only
		STATUS current
		DESCRIPTION
		"upsIta2com692Addr9BatTempcolllectfailure status."
		::= { upsIta2comEntry 694 }
upsIta2com694Addr9BatAddrSeterror OBJECT-TYPE
		SYNTAX INTEGER {
			normal(0),
			alarm(1) }
		MAX-ACCESS read-only
		STATUS current
		DESCRIPTION
		"upsIta2com693Addr9BatAddrSeterror status."
		::= { upsIta2comEntry 695 }
upsIta2com695Addr9BatLargegrouppressurediff OBJECT-TYPE
		SYNTAX INTEGER {
			normal(0),
			alarm(1) }
		MAX-ACCESS read-only
		STATUS current
		DESCRIPTION
		"upsIta2com694Addr9BatLargegrouppressurediff status."
		::= { upsIta2comEntry 696 }
upsIta2com696Addr9BatMOSFETfailure OBJECT-TYPE
		SYNTAX INTEGER {
			normal(0),
			alarm(1) }
		MAX-ACCESS read-only
		STATUS current
		DESCRIPTION
		"upsIta2com695Addr9BatMOSFETfailure status."
		::= { upsIta2comEntry 697 }
upsIta2com697Addr9Battempabnormal OBJECT-TYPE
		SYNTAX INTEGER {
			normal(0),
			alarm(1) }
		MAX-ACCESS read-only
		STATUS current
		DESCRIPTION
		"upsIta2com696Addr9Battempabnormal status."
		::= { upsIta2comEntry 698 }
upsIta2com698Addr9Batcablefault OBJECT-TYPE
		SYNTAX INTEGER {
			normal(0),
			alarm(1) }
		MAX-ACCESS read-only
		STATUS current
		DESCRIPTION
		"upsIta2com697Addr9Batcablefault status."
		::= { upsIta2comEntry 699 }
upsIta2com699Addr9BatShortcircuit OBJECT-TYPE
		SYNTAX INTEGER {
			normal(0),
			alarm(1) }
		MAX-ACCESS read-only
		STATUS current
		DESCRIPTION
		"upsIta2com698Addr9BatShortcircuit status."
		::= { upsIta2comEntry 700 }
upsIta2com700Addr9BatOtherfailures OBJECT-TYPE
		SYNTAX INTEGER {
			normal(0),
			alarm(1) }
		MAX-ACCESS read-only
		STATUS current
		DESCRIPTION
		"upsIta2com699Addr9BatOtherfailures status."
		::= { upsIta2comEntry 701 }
upsIta2com701Addr9BatCommcablefailure OBJECT-TYPE
		SYNTAX INTEGER {
			normal(0),
			alarm(1) }
		MAX-ACCESS read-only
		STATUS current
		DESCRIPTION
		"upsIta2com700Addr9BatCommcablefailure status."
		::= { upsIta2comEntry 702 }
upsIta2com702Addr9BatMOSFETtempishigh OBJECT-TYPE
		SYNTAX INTEGER {
			normal(0),
			alarm(1) }
		MAX-ACCESS read-only
		STATUS current
		DESCRIPTION
		"upsIta2com701Addr9BatMOSFETtempishigh status."
		::= { upsIta2comEntry 703 }
upsIta2com703Addr9BatFuseblown OBJECT-TYPE
		SYNTAX INTEGER {
			normal(0),
			alarm(1) }
		MAX-ACCESS read-only
		STATUS current
		DESCRIPTION
		"upsIta2com702Addr9BatFuseblown status."
		::= { upsIta2comEntry 704 }
upsIta2com704Addr9BatWaitingforcharging OBJECT-TYPE
		SYNTAX INTEGER {
			normal(0),
			alarm(1) }
		MAX-ACCESS read-only
		STATUS current
		DESCRIPTION
		"upsIta2com703Addr9BatWaitingforcharging status."
		::= { upsIta2comEntry 705 }
upsIta2com705Addr9BatBataging OBJECT-TYPE
		SYNTAX INTEGER {
			normal(0),
			alarm(1) }
		MAX-ACCESS read-only
		STATUS current
		DESCRIPTION
		"upsIta2com704Addr9BatBataging status."
		::= { upsIta2comEntry 706 }
upsIta2com706Addr9Batboxconnectabnormal OBJECT-TYPE
		SYNTAX INTEGER {
			normal(0),
			alarm(1) }
		MAX-ACCESS read-only
		STATUS current
		DESCRIPTION
		"upsIta2com705Addr9Batboxconnectabnormal status."
		::= { upsIta2comEntry 707 }
upsIta2com707Addr9batBatterySoftincompatible OBJECT-TYPE
		SYNTAX INTEGER {
			normal(0),
			alarm(1) }
		MAX-ACCESS read-only
		STATUS current
		DESCRIPTION
		"upsIta2com706Addr9batBatterySoftincompatible status."
		::= { upsIta2comEntry 708 }
upsIta2com708Addr9batEOL OBJECT-TYPE
		SYNTAX INTEGER {
			normal(0),
			alarm(1) }
		MAX-ACCESS read-only
		STATUS current
		DESCRIPTION
		"upsIta2com707Addr9batEOL status."
		::= { upsIta2comEntry 709 }
upsIta2com709Addr9batSamplingfailure OBJECT-TYPE
		SYNTAX INTEGER {
			normal(0),
			alarm(1) }
		MAX-ACCESS read-only
		STATUS current
		DESCRIPTION
		"upsIta2com708Addr9batSamplingfailure status."
		::= { upsIta2comEntry 710 }
upsIta2com710Addr9batHardwareprotection OBJECT-TYPE
		SYNTAX INTEGER {
			normal(0),
			alarm(1) }
		MAX-ACCESS read-only
		STATUS current
		DESCRIPTION
		"upsIta2com709Addr9batHardwareprotection status."
		::= { upsIta2comEntry 711 }
upsIta2com711Addr9batBatterycapacitylow OBJECT-TYPE
		SYNTAX INTEGER {
			normal(0),
			alarm(1) }
		MAX-ACCESS read-only
		STATUS current
		DESCRIPTION
		"upsIta2com710Addr9batBatterycapacitylow status."
		::= { upsIta2comEntry 712 }
upsIta2com712Addr10Batalarmnumber OBJECT-TYPE
		SYNTAX Integer32
		
		MAX-ACCESS read-only
		STATUS current
		DESCRIPTION
		"upsIta2com711Addr10Batalarmnumber stored as 1."
		::= { upsIta2comEntry 713 }
upsIta2com713Addr10Bathighvolt OBJECT-TYPE
		SYNTAX INTEGER {
			normal(0),
			alarm(1) }
		MAX-ACCESS read-only
		STATUS current
		DESCRIPTION
		"upsIta2com712Addr10Bathighvolt status."
		::= { upsIta2comEntry 714 }
upsIta2com714Addr10Batlowvolt OBJECT-TYPE
		SYNTAX INTEGER {
			normal(0),
			alarm(1) }
		MAX-ACCESS read-only
		STATUS current
		DESCRIPTION
		"upsIta2com713Addr10Batlowvolt status."
		::= { upsIta2comEntry 715 }
upsIta2com715Addr10Bathighcellvolt OBJECT-TYPE
		SYNTAX INTEGER {
			normal(0),
			alarm(1) }
		MAX-ACCESS read-only
		STATUS current
		DESCRIPTION
		"upsIta2com714Addr10Bathighcellvolt status."
		::= { upsIta2comEntry 716 }
upsIta2com716Addr10Batlowcellvolt OBJECT-TYPE
		SYNTAX INTEGER {
			normal(0),
			alarm(1) }
		MAX-ACCESS read-only
		STATUS current
		DESCRIPTION
		"upsIta2com715Addr10Batlowcellvolt status."
		::= { upsIta2comEntry 717 }
upsIta2com717Addr10Batchargehighcelltemp OBJECT-TYPE
		SYNTAX INTEGER {
			normal(0),
			alarm(1) }
		MAX-ACCESS read-only
		STATUS current
		DESCRIPTION
		"upsIta2com716Addr10Batchargehighcelltemp status."
		::= { upsIta2comEntry 718 }
upsIta2com718Addr10Batchargelowcelltemp OBJECT-TYPE
		SYNTAX INTEGER {
			normal(0),
			alarm(1) }
		MAX-ACCESS read-only
		STATUS current
		DESCRIPTION
		"upsIta2com717Addr10Batchargelowcelltemp status."
		::= { upsIta2comEntry 719 }
upsIta2com719Addr10Batchargeovercurrent OBJECT-TYPE
		SYNTAX INTEGER {
			normal(0),
			alarm(1) }
		MAX-ACCESS read-only
		STATUS current
		DESCRIPTION
		"upsIta2com718Addr10Batchargeovercurrent status."
		::= { upsIta2comEntry 720 }
upsIta2com720Addr10Batdischargeovercurrent OBJECT-TYPE
		SYNTAX INTEGER {
			normal(0),
			alarm(1) }
		MAX-ACCESS read-only
		STATUS current
		DESCRIPTION
		"upsIta2com719Addr10Batdischargeovercurrent status."
		::= { upsIta2comEntry 721 }
upsIta2com721Addr10BatAddrconflict OBJECT-TYPE
		SYNTAX INTEGER {
			normal(0),
			alarm(1) }
		MAX-ACCESS read-only
		STATUS current
		DESCRIPTION
		"upsIta2com720Addr10BatAddrconflict status."
		::= { upsIta2comEntry 722 }
upsIta2com722Addr10Batportreverse OBJECT-TYPE
		SYNTAX INTEGER {
			normal(0),
			alarm(1) }
		MAX-ACCESS read-only
		STATUS current
		DESCRIPTION
		"upsIta2com721Addr10Batportreverse status."
		::= { upsIta2comEntry 723 }
upsIta2com723Addr10BatBMSrelayinvalid OBJECT-TYPE
		SYNTAX INTEGER {
			normal(0),
			alarm(1) }
		MAX-ACCESS read-only
		STATUS current
		DESCRIPTION
		"upsIta2com722Addr10BatBMSrelayinvalid status."
		::= { upsIta2comEntry 724 }
upsIta2com724Addr10Batsafetyundervoltage OBJECT-TYPE
		SYNTAX INTEGER {
			normal(0),
			alarm(1) }
		MAX-ACCESS read-only
		STATUS current
		DESCRIPTION
		"upsIta2com723Addr10Batsafetyundervoltage status."
		::= { upsIta2comEntry 725 }
upsIta2com725Addr10Batdischargehighcelltemp OBJECT-TYPE
		SYNTAX INTEGER {
			normal(0),
			alarm(1) }
		MAX-ACCESS read-only
		STATUS current
		DESCRIPTION
		"upsIta2com724Addr10Batdischargehighcelltemp status."
		::= { upsIta2comEntry 726 }
upsIta2com726Addr10Batdischargelowcelltemp OBJECT-TYPE
		SYNTAX INTEGER {
			normal(0),
			alarm(1) }
		MAX-ACCESS read-only
		STATUS current
		DESCRIPTION
		"upsIta2com725Addr10Batdischargelowcelltemp status."
		::= { upsIta2comEntry 727 }
upsIta2com727Addr10Batparallelchargehightemp OBJECT-TYPE
		SYNTAX INTEGER {
			normal(0),
			alarm(1) }
		MAX-ACCESS read-only
		STATUS current
		DESCRIPTION
		"upsIta2com726Addr10Batparallelchargehightemp status."
		::= { upsIta2comEntry 728 }
upsIta2com728Addr10BatinternalCommabnormal OBJECT-TYPE
		SYNTAX INTEGER {
			normal(0),
			alarm(1) }
		MAX-ACCESS read-only
		STATUS current
		DESCRIPTION
		"upsIta2com727Addr10BatinternalCommabnormal status."
		::= { upsIta2comEntry 729 }
upsIta2com729Addr10Batconditionfail OBJECT-TYPE
		SYNTAX INTEGER {
			normal(0),
			alarm(1) }
		MAX-ACCESS read-only
		STATUS current
		DESCRIPTION
		"upsIta2com728Addr10Batconditionfail status."
		::= { upsIta2comEntry 730 }
upsIta2com730Addr10BatLowinsulationresistanc OBJECT-TYPE
		SYNTAX INTEGER {
			normal(0),
			alarm(1) }
		MAX-ACCESS read-only
		STATUS current
		DESCRIPTION
		"upsIta2com729Addr10BatLowinsulationresistanc status."
		::= { upsIta2comEntry 731 }
upsIta2com731Addr10BatLargepressurediff OBJECT-TYPE
		SYNTAX INTEGER {
			normal(0),
			alarm(1) }
		MAX-ACCESS read-only
		STATUS current
		DESCRIPTION
		"upsIta2com730Addr10BatLargepressurediff status."
		::= { upsIta2comEntry 732 }
upsIta2com732Addr10BatBatfailure OBJECT-TYPE
		SYNTAX INTEGER {
			normal(0),
			alarm(1) }
		MAX-ACCESS read-only
		STATUS current
		DESCRIPTION
		"upsIta2com731Addr10BatBatfailure status."
		::= { upsIta2comEntry 733 }
upsIta2com733Addr10BatVoltageacquisitfailure OBJECT-TYPE
		SYNTAX INTEGER {
			normal(0),
			alarm(1) }
		MAX-ACCESS read-only
		STATUS current
		DESCRIPTION
		"upsIta2com732Addr10BatVoltageacquisitfailure status."
		::= { upsIta2comEntry 734 }
upsIta2com734Addr10BatCurrentcolllectfailure OBJECT-TYPE
		SYNTAX INTEGER {
			normal(0),
			alarm(1) }
		MAX-ACCESS read-only
		STATUS current
		DESCRIPTION
		"upsIta2com733Addr10BatCurrentcolllectfailure status."
		::= { upsIta2comEntry 735 }
upsIta2com735Addr10BatTempcolllectfailure OBJECT-TYPE
		SYNTAX INTEGER {
			normal(0),
			alarm(1) }
		MAX-ACCESS read-only
		STATUS current
		DESCRIPTION
		"upsIta2com734Addr10BatTempcolllectfailure status."
		::= { upsIta2comEntry 736 }
upsIta2com736Addr10BatAddrSeterror OBJECT-TYPE
		SYNTAX INTEGER {
			normal(0),
			alarm(1) }
		MAX-ACCESS read-only
		STATUS current
		DESCRIPTION
		"upsIta2com735Addr10BatAddrSeterror status."
		::= { upsIta2comEntry 737 }
upsIta2com737Addr10BatLargegrouppressurediff OBJECT-TYPE
		SYNTAX INTEGER {
			normal(0),
			alarm(1) }
		MAX-ACCESS read-only
		STATUS current
		DESCRIPTION
		"upsIta2com736Addr10BatLargegrouppressurediff status."
		::= { upsIta2comEntry 738 }
upsIta2com738Addr10BatMOSFETfailure OBJECT-TYPE
		SYNTAX INTEGER {
			normal(0),
			alarm(1) }
		MAX-ACCESS read-only
		STATUS current
		DESCRIPTION
		"upsIta2com737Addr10BatMOSFETfailure status."
		::= { upsIta2comEntry 739 }
upsIta2com739Addr10Battempabnormal OBJECT-TYPE
		SYNTAX INTEGER {
			normal(0),
			alarm(1) }
		MAX-ACCESS read-only
		STATUS current
		DESCRIPTION
		"upsIta2com738Addr10Battempabnormal status."
		::= { upsIta2comEntry 740 }
upsIta2com740Addr10Batcablefault OBJECT-TYPE
		SYNTAX INTEGER {
			normal(0),
			alarm(1) }
		MAX-ACCESS read-only
		STATUS current
		DESCRIPTION
		"upsIta2com739Addr10Batcablefault status."
		::= { upsIta2comEntry 741 }
upsIta2com741Addr10BatShortcircuit OBJECT-TYPE
		SYNTAX INTEGER {
			normal(0),
			alarm(1) }
		MAX-ACCESS read-only
		STATUS current
		DESCRIPTION
		"upsIta2com740Addr10BatShortcircuit status."
		::= { upsIta2comEntry 742 }
upsIta2com742Addr10BatOtherfailures OBJECT-TYPE
		SYNTAX INTEGER {
			normal(0),
			alarm(1) }
		MAX-ACCESS read-only
		STATUS current
		DESCRIPTION
		"upsIta2com741Addr10BatOtherfailures status."
		::= { upsIta2comEntry 743 }
upsIta2com743Addr10BatCommcablefailure OBJECT-TYPE
		SYNTAX INTEGER {
			normal(0),
			alarm(1) }
		MAX-ACCESS read-only
		STATUS current
		DESCRIPTION
		"upsIta2com742Addr10BatCommcablefailure status."
		::= { upsIta2comEntry 744 }
upsIta2com744Addr10BatMOSFETtempishigh OBJECT-TYPE
		SYNTAX INTEGER {
			normal(0),
			alarm(1) }
		MAX-ACCESS read-only
		STATUS current
		DESCRIPTION
		"upsIta2com743Addr10BatMOSFETtempishigh status."
		::= { upsIta2comEntry 745 }
upsIta2com745Addr10BatFuseblown OBJECT-TYPE
		SYNTAX INTEGER {
			normal(0),
			alarm(1) }
		MAX-ACCESS read-only
		STATUS current
		DESCRIPTION
		"upsIta2com744Addr10BatFuseblown status."
		::= { upsIta2comEntry 746 }
upsIta2com746Addr10BatWaitingforcharging OBJECT-TYPE
		SYNTAX INTEGER {
			normal(0),
			alarm(1) }
		MAX-ACCESS read-only
		STATUS current
		DESCRIPTION
		"upsIta2com745Addr10BatWaitingforcharging status."
		::= { upsIta2comEntry 747 }
upsIta2com747Addr10BatBataging OBJECT-TYPE
		SYNTAX INTEGER {
			normal(0),
			alarm(1) }
		MAX-ACCESS read-only
		STATUS current
		DESCRIPTION
		"upsIta2com746Addr10BatBataging status."
		::= { upsIta2comEntry 748 }
upsIta2com748Addr10Batboxconnectabnormal OBJECT-TYPE
		SYNTAX INTEGER {
			normal(0),
			alarm(1) }
		MAX-ACCESS read-only
		STATUS current
		DESCRIPTION
		"upsIta2com747Addr10Batboxconnectabnormal status."
		::= { upsIta2comEntry 749 }
upsIta2com749Addr10batBatterySoftincompatibl OBJECT-TYPE
		SYNTAX INTEGER {
			normal(0),
			alarm(1) }
		MAX-ACCESS read-only
		STATUS current
		DESCRIPTION
		"upsIta2com748Addr10batBatterySoftincompatibl status."
		::= { upsIta2comEntry 750 }
upsIta2com750Addr10batEOL OBJECT-TYPE
		SYNTAX INTEGER {
			normal(0),
			alarm(1) }
		MAX-ACCESS read-only
		STATUS current
		DESCRIPTION
		"upsIta2com749Addr10batEOL status."
		::= { upsIta2comEntry 751 }
upsIta2com751Addr10batSamplingfailure OBJECT-TYPE
		SYNTAX INTEGER {
			normal(0),
			alarm(1) }
		MAX-ACCESS read-only
		STATUS current
		DESCRIPTION
		"upsIta2com750Addr10batSamplingfailure status."
		::= { upsIta2comEntry 752 }
upsIta2com752Addr10batHardwareprotection OBJECT-TYPE
		SYNTAX INTEGER {
			normal(0),
			alarm(1) }
		MAX-ACCESS read-only
		STATUS current
		DESCRIPTION
		"upsIta2com751Addr10batHardwareprotection status."
		::= { upsIta2comEntry 753 }
upsIta2com753Addr10batBatterycapacitylow OBJECT-TYPE
		SYNTAX INTEGER {
			normal(0),
			alarm(1) }
		MAX-ACCESS read-only
		STATUS current
		DESCRIPTION
		"upsIta2com752Addr10batBatterycapacitylow status."
		::= { upsIta2comEntry 754 }
upsIta2com754Addr11Batalarmnumber OBJECT-TYPE
		SYNTAX Integer32
		
		MAX-ACCESS read-only
		STATUS current
		DESCRIPTION
		"upsIta2com753Addr11Batalarmnumber stored as 1."
		::= { upsIta2comEntry 755 }
upsIta2com755Addr11Bathighvolt OBJECT-TYPE
		SYNTAX INTEGER {
			normal(0),
			alarm(1) }
		MAX-ACCESS read-only
		STATUS current
		DESCRIPTION
		"upsIta2com754Addr11Bathighvolt status."
		::= { upsIta2comEntry 756 }
upsIta2com756Addr11Batlowvolt OBJECT-TYPE
		SYNTAX INTEGER {
			normal(0),
			alarm(1) }
		MAX-ACCESS read-only
		STATUS current
		DESCRIPTION
		"upsIta2com755Addr11Batlowvolt status."
		::= { upsIta2comEntry 757 }
upsIta2com757Addr11Bathighcellvolt OBJECT-TYPE
		SYNTAX INTEGER {
			normal(0),
			alarm(1) }
		MAX-ACCESS read-only
		STATUS current
		DESCRIPTION
		"upsIta2com756Addr11Bathighcellvolt status."
		::= { upsIta2comEntry 758 }
upsIta2com758Addr11Batlowcellvolt OBJECT-TYPE
		SYNTAX INTEGER {
			normal(0),
			alarm(1) }
		MAX-ACCESS read-only
		STATUS current
		DESCRIPTION
		"upsIta2com757Addr11Batlowcellvolt status."
		::= { upsIta2comEntry 759 }
upsIta2com759Addr11Batchargehighcelltemp OBJECT-TYPE
		SYNTAX INTEGER {
			normal(0),
			alarm(1) }
		MAX-ACCESS read-only
		STATUS current
		DESCRIPTION
		"upsIta2com758Addr11Batchargehighcelltemp status."
		::= { upsIta2comEntry 760 }
upsIta2com760Addr11Batchargelowcelltemp OBJECT-TYPE
		SYNTAX INTEGER {
			normal(0),
			alarm(1) }
		MAX-ACCESS read-only
		STATUS current
		DESCRIPTION
		"upsIta2com759Addr11Batchargelowcelltemp status."
		::= { upsIta2comEntry 761 }
upsIta2com761Addr11Batchargeovercurrent OBJECT-TYPE
		SYNTAX INTEGER {
			normal(0),
			alarm(1) }
		MAX-ACCESS read-only
		STATUS current
		DESCRIPTION
		"upsIta2com760Addr11Batchargeovercurrent status."
		::= { upsIta2comEntry 762 }
upsIta2com762Addr11Batdischargeovercurrent OBJECT-TYPE
		SYNTAX INTEGER {
			normal(0),
			alarm(1) }
		MAX-ACCESS read-only
		STATUS current
		DESCRIPTION
		"upsIta2com761Addr11Batdischargeovercurrent status."
		::= { upsIta2comEntry 763 }
upsIta2com763Addr11BatAddrconflict OBJECT-TYPE
		SYNTAX INTEGER {
			normal(0),
			alarm(1) }
		MAX-ACCESS read-only
		STATUS current
		DESCRIPTION
		"upsIta2com762Addr11BatAddrconflict status."
		::= { upsIta2comEntry 764 }
upsIta2com764Addr11Batportreverse OBJECT-TYPE
		SYNTAX INTEGER {
			normal(0),
			alarm(1) }
		MAX-ACCESS read-only
		STATUS current
		DESCRIPTION
		"upsIta2com763Addr11Batportreverse status."
		::= { upsIta2comEntry 765 }
upsIta2com765Addr11BatBMSrelayinvalid OBJECT-TYPE
		SYNTAX INTEGER {
			normal(0),
			alarm(1) }
		MAX-ACCESS read-only
		STATUS current
		DESCRIPTION
		"upsIta2com764Addr11BatBMSrelayinvalid status."
		::= { upsIta2comEntry 766 }
upsIta2com766Addr11Batsafetyundervoltage OBJECT-TYPE
		SYNTAX INTEGER {
			normal(0),
			alarm(1) }
		MAX-ACCESS read-only
		STATUS current
		DESCRIPTION
		"upsIta2com765Addr11Batsafetyundervoltage status."
		::= { upsIta2comEntry 767 }
upsIta2com767Addr11Batdischargehighcelltemp OBJECT-TYPE
		SYNTAX INTEGER {
			normal(0),
			alarm(1) }
		MAX-ACCESS read-only
		STATUS current
		DESCRIPTION
		"upsIta2com766Addr11Batdischargehighcelltemp status."
		::= { upsIta2comEntry 768 }
upsIta2com768Addr11Batdischargelowcelltemp OBJECT-TYPE
		SYNTAX INTEGER {
			normal(0),
			alarm(1) }
		MAX-ACCESS read-only
		STATUS current
		DESCRIPTION
		"upsIta2com767Addr11Batdischargelowcelltemp status."
		::= { upsIta2comEntry 769 }
upsIta2com769Addr11Batparallelchargehightemp OBJECT-TYPE
		SYNTAX INTEGER {
			normal(0),
			alarm(1) }
		MAX-ACCESS read-only
		STATUS current
		DESCRIPTION
		"upsIta2com768Addr11Batparallelchargehightemp status."
		::= { upsIta2comEntry 770 }
upsIta2com770Addr11BatinternalCommabnormal OBJECT-TYPE
		SYNTAX INTEGER {
			normal(0),
			alarm(1) }
		MAX-ACCESS read-only
		STATUS current
		DESCRIPTION
		"upsIta2com769Addr11BatinternalCommabnormal status."
		::= { upsIta2comEntry 771 }
upsIta2com771Addr11Batconditionfail OBJECT-TYPE
		SYNTAX INTEGER {
			normal(0),
			alarm(1) }
		MAX-ACCESS read-only
		STATUS current
		DESCRIPTION
		"upsIta2com770Addr11Batconditionfail status."
		::= { upsIta2comEntry 772 }
upsIta2com772Addr11BatLowinsulationresistanc OBJECT-TYPE
		SYNTAX INTEGER {
			normal(0),
			alarm(1) }
		MAX-ACCESS read-only
		STATUS current
		DESCRIPTION
		"upsIta2com771Addr11BatLowinsulationresistanc status."
		::= { upsIta2comEntry 773 }
upsIta2com773Addr11BatLargepressurediff OBJECT-TYPE
		SYNTAX INTEGER {
			normal(0),
			alarm(1) }
		MAX-ACCESS read-only
		STATUS current
		DESCRIPTION
		"upsIta2com772Addr11BatLargepressurediff status."
		::= { upsIta2comEntry 774 }
upsIta2com774Addr11BatBatfailure OBJECT-TYPE
		SYNTAX INTEGER {
			normal(0),
			alarm(1) }
		MAX-ACCESS read-only
		STATUS current
		DESCRIPTION
		"upsIta2com773Addr11BatBatfailure status."
		::= { upsIta2comEntry 775 }
upsIta2com775Addr11BatVoltageacquisitfailure OBJECT-TYPE
		SYNTAX INTEGER {
			normal(0),
			alarm(1) }
		MAX-ACCESS read-only
		STATUS current
		DESCRIPTION
		"upsIta2com774Addr11BatVoltageacquisitfailure status."
		::= { upsIta2comEntry 776 }
upsIta2com776Addr11BatCurrentcolllectfailure OBJECT-TYPE
		SYNTAX INTEGER {
			normal(0),
			alarm(1) }
		MAX-ACCESS read-only
		STATUS current
		DESCRIPTION
		"upsIta2com775Addr11BatCurrentcolllectfailure status."
		::= { upsIta2comEntry 777 }
upsIta2com777Addr11BatTempcolllectfailure OBJECT-TYPE
		SYNTAX INTEGER {
			normal(0),
			alarm(1) }
		MAX-ACCESS read-only
		STATUS current
		DESCRIPTION
		"upsIta2com776Addr11BatTempcolllectfailure status."
		::= { upsIta2comEntry 778 }
upsIta2com778Addr11BatAddrSeterror OBJECT-TYPE
		SYNTAX INTEGER {
			normal(0),
			alarm(1) }
		MAX-ACCESS read-only
		STATUS current
		DESCRIPTION
		"upsIta2com777Addr11BatAddrSeterror status."
		::= { upsIta2comEntry 779 }
upsIta2com779Addr11BatLargegrouppressurediff OBJECT-TYPE
		SYNTAX INTEGER {
			normal(0),
			alarm(1) }
		MAX-ACCESS read-only
		STATUS current
		DESCRIPTION
		"upsIta2com778Addr11BatLargegrouppressurediff status."
		::= { upsIta2comEntry 780 }
upsIta2com780Addr11BatMOSFETfailure OBJECT-TYPE
		SYNTAX INTEGER {
			normal(0),
			alarm(1) }
		MAX-ACCESS read-only
		STATUS current
		DESCRIPTION
		"upsIta2com779Addr11BatMOSFETfailure status."
		::= { upsIta2comEntry 781 }
upsIta2com781Addr11Battempabnormal OBJECT-TYPE
		SYNTAX INTEGER {
			normal(0),
			alarm(1) }
		MAX-ACCESS read-only
		STATUS current
		DESCRIPTION
		"upsIta2com780Addr11Battempabnormal status."
		::= { upsIta2comEntry 782 }
upsIta2com782Addr11Batcablefault OBJECT-TYPE
		SYNTAX INTEGER {
			normal(0),
			alarm(1) }
		MAX-ACCESS read-only
		STATUS current
		DESCRIPTION
		"upsIta2com781Addr11Batcablefault status."
		::= { upsIta2comEntry 783 }
upsIta2com783Addr11BatShortcircuit OBJECT-TYPE
		SYNTAX INTEGER {
			normal(0),
			alarm(1) }
		MAX-ACCESS read-only
		STATUS current
		DESCRIPTION
		"upsIta2com782Addr11BatShortcircuit status."
		::= { upsIta2comEntry 784 }
upsIta2com784Addr11BatOtherfailures OBJECT-TYPE
		SYNTAX INTEGER {
			normal(0),
			alarm(1) }
		MAX-ACCESS read-only
		STATUS current
		DESCRIPTION
		"upsIta2com783Addr11BatOtherfailures status."
		::= { upsIta2comEntry 785 }
upsIta2com785Addr11BatCommcablefailure OBJECT-TYPE
		SYNTAX INTEGER {
			normal(0),
			alarm(1) }
		MAX-ACCESS read-only
		STATUS current
		DESCRIPTION
		"upsIta2com784Addr11BatCommcablefailure status."
		::= { upsIta2comEntry 786 }
upsIta2com786Addr11BatMOSFETtempishigh OBJECT-TYPE
		SYNTAX INTEGER {
			normal(0),
			alarm(1) }
		MAX-ACCESS read-only
		STATUS current
		DESCRIPTION
		"upsIta2com785Addr11BatMOSFETtempishigh status."
		::= { upsIta2comEntry 787 }
upsIta2com787Addr11BatFuseblown OBJECT-TYPE
		SYNTAX INTEGER {
			normal(0),
			alarm(1) }
		MAX-ACCESS read-only
		STATUS current
		DESCRIPTION
		"upsIta2com786Addr11BatFuseblown status."
		::= { upsIta2comEntry 788 }
upsIta2com788Addr11BatWaitingforcharging OBJECT-TYPE
		SYNTAX INTEGER {
			normal(0),
			alarm(1) }
		MAX-ACCESS read-only
		STATUS current
		DESCRIPTION
		"upsIta2com787Addr11BatWaitingforcharging status."
		::= { upsIta2comEntry 789 }
upsIta2com789Addr11BatBataging OBJECT-TYPE
		SYNTAX INTEGER {
			normal(0),
			alarm(1) }
		MAX-ACCESS read-only
		STATUS current
		DESCRIPTION
		"upsIta2com788Addr11BatBataging status."
		::= { upsIta2comEntry 790 }
upsIta2com790Addr11Batboxconnectabnormal OBJECT-TYPE
		SYNTAX INTEGER {
			normal(0),
			alarm(1) }
		MAX-ACCESS read-only
		STATUS current
		DESCRIPTION
		"upsIta2com789Addr11Batboxconnectabnormal status."
		::= { upsIta2comEntry 791 }
upsIta2com791Addr11batBatterySoftincompatibl OBJECT-TYPE
		SYNTAX INTEGER {
			normal(0),
			alarm(1) }
		MAX-ACCESS read-only
		STATUS current
		DESCRIPTION
		"upsIta2com790Addr11batBatterySoftincompatibl status."
		::= { upsIta2comEntry 792 }
upsIta2com792Addr11batEOL OBJECT-TYPE
		SYNTAX INTEGER {
			normal(0),
			alarm(1) }
		MAX-ACCESS read-only
		STATUS current
		DESCRIPTION
		"upsIta2com791Addr11batEOL status."
		::= { upsIta2comEntry 793 }
upsIta2com793Addr11batSamplingfailure OBJECT-TYPE
		SYNTAX INTEGER {
			normal(0),
			alarm(1) }
		MAX-ACCESS read-only
		STATUS current
		DESCRIPTION
		"upsIta2com792Addr11batSamplingfailure status."
		::= { upsIta2comEntry 794 }
upsIta2com794Addr11batHardwareprotection OBJECT-TYPE
		SYNTAX INTEGER {
			normal(0),
			alarm(1) }
		MAX-ACCESS read-only
		STATUS current
		DESCRIPTION
		"upsIta2com793Addr11batHardwareprotection status."
		::= { upsIta2comEntry 795 }
upsIta2com795Addr11batBatterycapacitylow OBJECT-TYPE
		SYNTAX INTEGER {
			normal(0),
			alarm(1) }
		MAX-ACCESS read-only
		STATUS current
		DESCRIPTION
		"upsIta2com794Addr11batBatterycapacitylow status."
		::= { upsIta2comEntry 796 }
upsIta2com796Addr12Batalarmnumber OBJECT-TYPE
		SYNTAX Integer32
		
		MAX-ACCESS read-only
		STATUS current
		DESCRIPTION
		"upsIta2com795Addr12Batalarmnumber stored as 1."
		::= { upsIta2comEntry 797 }
upsIta2com797Addr12Bathighvolt OBJECT-TYPE
		SYNTAX INTEGER {
			normal(0),
			alarm(1) }
		MAX-ACCESS read-only
		STATUS current
		DESCRIPTION
		"upsIta2com796Addr12Bathighvolt status."
		::= { upsIta2comEntry 798 }
upsIta2com798Addr12Batlowvolt OBJECT-TYPE
		SYNTAX INTEGER {
			normal(0),
			alarm(1) }
		MAX-ACCESS read-only
		STATUS current
		DESCRIPTION
		"upsIta2com797Addr12Batlowvolt status."
		::= { upsIta2comEntry 799 }
upsIta2com799Addr12Bathighcellvolt OBJECT-TYPE
		SYNTAX INTEGER {
			normal(0),
			alarm(1) }
		MAX-ACCESS read-only
		STATUS current
		DESCRIPTION
		"upsIta2com798Addr12Bathighcellvolt status."
		::= { upsIta2comEntry 800 }
upsIta2com800Addr12Batlowcellvolt OBJECT-TYPE
		SYNTAX INTEGER {
			normal(0),
			alarm(1) }
		MAX-ACCESS read-only
		STATUS current
		DESCRIPTION
		"upsIta2com799Addr12Batlowcellvolt status."
		::= { upsIta2comEntry 801 }
upsIta2com801Addr12Batchargehighcelltemp OBJECT-TYPE
		SYNTAX INTEGER {
			normal(0),
			alarm(1) }
		MAX-ACCESS read-only
		STATUS current
		DESCRIPTION
		"upsIta2com800Addr12Batchargehighcelltemp status."
		::= { upsIta2comEntry 802 }
upsIta2com802Addr12Batchargelowcelltemp OBJECT-TYPE
		SYNTAX INTEGER {
			normal(0),
			alarm(1) }
		MAX-ACCESS read-only
		STATUS current
		DESCRIPTION
		"upsIta2com801Addr12Batchargelowcelltemp status."
		::= { upsIta2comEntry 803 }
upsIta2com803Addr12Batchargeovercurrent OBJECT-TYPE
		SYNTAX INTEGER {
			normal(0),
			alarm(1) }
		MAX-ACCESS read-only
		STATUS current
		DESCRIPTION
		"upsIta2com802Addr12Batchargeovercurrent status."
		::= { upsIta2comEntry 804 }
upsIta2com804Addr12Batdischargeovercurrent OBJECT-TYPE
		SYNTAX INTEGER {
			normal(0),
			alarm(1) }
		MAX-ACCESS read-only
		STATUS current
		DESCRIPTION
		"upsIta2com803Addr12Batdischargeovercurrent status."
		::= { upsIta2comEntry 805 }
upsIta2com805Addr12BatAddrconflict OBJECT-TYPE
		SYNTAX INTEGER {
			normal(0),
			alarm(1) }
		MAX-ACCESS read-only
		STATUS current
		DESCRIPTION
		"upsIta2com804Addr12BatAddrconflict status."
		::= { upsIta2comEntry 806 }
upsIta2com806Addr12Batportreverse OBJECT-TYPE
		SYNTAX INTEGER {
			normal(0),
			alarm(1) }
		MAX-ACCESS read-only
		STATUS current
		DESCRIPTION
		"upsIta2com805Addr12Batportreverse status."
		::= { upsIta2comEntry 807 }
upsIta2com807Addr12BatBMSrelayinvalid OBJECT-TYPE
		SYNTAX INTEGER {
			normal(0),
			alarm(1) }
		MAX-ACCESS read-only
		STATUS current
		DESCRIPTION
		"upsIta2com806Addr12BatBMSrelayinvalid status."
		::= { upsIta2comEntry 808 }
upsIta2com808Addr12Batsafetyundervoltage OBJECT-TYPE
		SYNTAX INTEGER {
			normal(0),
			alarm(1) }
		MAX-ACCESS read-only
		STATUS current
		DESCRIPTION
		"upsIta2com807Addr12Batsafetyundervoltage status."
		::= { upsIta2comEntry 809 }
upsIta2com809Addr12Batdischargehighcelltemp OBJECT-TYPE
		SYNTAX INTEGER {
			normal(0),
			alarm(1) }
		MAX-ACCESS read-only
		STATUS current
		DESCRIPTION
		"upsIta2com808Addr12Batdischargehighcelltemp status."
		::= { upsIta2comEntry 810 }
upsIta2com810Addr12Batdischargelowcelltemp OBJECT-TYPE
		SYNTAX INTEGER {
			normal(0),
			alarm(1) }
		MAX-ACCESS read-only
		STATUS current
		DESCRIPTION
		"upsIta2com809Addr12Batdischargelowcelltemp status."
		::= { upsIta2comEntry 811 }
upsIta2com811Addr12Batparallelchargehightemp OBJECT-TYPE
		SYNTAX INTEGER {
			normal(0),
			alarm(1) }
		MAX-ACCESS read-only
		STATUS current
		DESCRIPTION
		"upsIta2com810Addr12Batparallelchargehightemp status."
		::= { upsIta2comEntry 812 }
upsIta2com812Addr12BatinternalCommabnormal OBJECT-TYPE
		SYNTAX INTEGER {
			normal(0),
			alarm(1) }
		MAX-ACCESS read-only
		STATUS current
		DESCRIPTION
		"upsIta2com811Addr12BatinternalCommabnormal status."
		::= { upsIta2comEntry 813 }
upsIta2com813Addr12Batconditionfail OBJECT-TYPE
		SYNTAX INTEGER {
			normal(0),
			alarm(1) }
		MAX-ACCESS read-only
		STATUS current
		DESCRIPTION
		"upsIta2com812Addr12Batconditionfail status."
		::= { upsIta2comEntry 814 }
upsIta2com814Addr12BatLowinsulationresistanc OBJECT-TYPE
		SYNTAX INTEGER {
			normal(0),
			alarm(1) }
		MAX-ACCESS read-only
		STATUS current
		DESCRIPTION
		"upsIta2com813Addr12BatLowinsulationresistanc status."
		::= { upsIta2comEntry 815 }
upsIta2com815Addr12BatLargepressurediff OBJECT-TYPE
		SYNTAX INTEGER {
			normal(0),
			alarm(1) }
		MAX-ACCESS read-only
		STATUS current
		DESCRIPTION
		"upsIta2com814Addr12BatLargepressurediff status."
		::= { upsIta2comEntry 816 }
upsIta2com816Addr12BatBatfailure OBJECT-TYPE
		SYNTAX INTEGER {
			normal(0),
			alarm(1) }
		MAX-ACCESS read-only
		STATUS current
		DESCRIPTION
		"upsIta2com815Addr12BatBatfailure status."
		::= { upsIta2comEntry 817 }
upsIta2com817Addr12BatVoltageacquisitfailure OBJECT-TYPE
		SYNTAX INTEGER {
			normal(0),
			alarm(1) }
		MAX-ACCESS read-only
		STATUS current
		DESCRIPTION
		"upsIta2com816Addr12BatVoltageacquisitfailure status."
		::= { upsIta2comEntry 818 }
upsIta2com818Addr12BatCurrentcolllectfailure OBJECT-TYPE
		SYNTAX INTEGER {
			normal(0),
			alarm(1) }
		MAX-ACCESS read-only
		STATUS current
		DESCRIPTION
		"upsIta2com817Addr12BatCurrentcolllectfailure status."
		::= { upsIta2comEntry 819 }
upsIta2com819Addr12BatTempcolllectfailure OBJECT-TYPE
		SYNTAX INTEGER {
			normal(0),
			alarm(1) }
		MAX-ACCESS read-only
		STATUS current
		DESCRIPTION
		"upsIta2com818Addr12BatTempcolllectfailure status."
		::= { upsIta2comEntry 820 }
upsIta2com820Addr12BatAddrSeterror OBJECT-TYPE
		SYNTAX INTEGER {
			normal(0),
			alarm(1) }
		MAX-ACCESS read-only
		STATUS current
		DESCRIPTION
		"upsIta2com819Addr12BatAddrSeterror status."
		::= { upsIta2comEntry 821 }
upsIta2com821Addr12BatLargegrouppressurediff OBJECT-TYPE
		SYNTAX INTEGER {
			normal(0),
			alarm(1) }
		MAX-ACCESS read-only
		STATUS current
		DESCRIPTION
		"upsIta2com820Addr12BatLargegrouppressurediff status."
		::= { upsIta2comEntry 822 }
upsIta2com822Addr12BatMOSFETfailure OBJECT-TYPE
		SYNTAX INTEGER {
			normal(0),
			alarm(1) }
		MAX-ACCESS read-only
		STATUS current
		DESCRIPTION
		"upsIta2com821Addr12BatMOSFETfailure status."
		::= { upsIta2comEntry 823 }
upsIta2com823Addr12Battempabnormal OBJECT-TYPE
		SYNTAX INTEGER {
			normal(0),
			alarm(1) }
		MAX-ACCESS read-only
		STATUS current
		DESCRIPTION
		"upsIta2com822Addr12Battempabnormal status."
		::= { upsIta2comEntry 824 }
upsIta2com824Addr12Batcablefault OBJECT-TYPE
		SYNTAX INTEGER {
			normal(0),
			alarm(1) }
		MAX-ACCESS read-only
		STATUS current
		DESCRIPTION
		"upsIta2com823Addr12Batcablefault status."
		::= { upsIta2comEntry 825 }
upsIta2com825Addr12BatShortcircuit OBJECT-TYPE
		SYNTAX INTEGER {
			normal(0),
			alarm(1) }
		MAX-ACCESS read-only
		STATUS current
		DESCRIPTION
		"upsIta2com824Addr12BatShortcircuit status."
		::= { upsIta2comEntry 826 }
upsIta2com826Addr12BatOtherfailures OBJECT-TYPE
		SYNTAX INTEGER {
			normal(0),
			alarm(1) }
		MAX-ACCESS read-only
		STATUS current
		DESCRIPTION
		"upsIta2com825Addr12BatOtherfailures status."
		::= { upsIta2comEntry 827 }
upsIta2com827Addr12BatCommcablefailure OBJECT-TYPE
		SYNTAX INTEGER {
			normal(0),
			alarm(1) }
		MAX-ACCESS read-only
		STATUS current
		DESCRIPTION
		"upsIta2com826Addr12BatCommcablefailure status."
		::= { upsIta2comEntry 828 }
upsIta2com828Addr12BatMOSFETtempishigh OBJECT-TYPE
		SYNTAX INTEGER {
			normal(0),
			alarm(1) }
		MAX-ACCESS read-only
		STATUS current
		DESCRIPTION
		"upsIta2com827Addr12BatMOSFETtempishigh status."
		::= { upsIta2comEntry 829 }
upsIta2com829Addr12BatFuseblown OBJECT-TYPE
		SYNTAX INTEGER {
			normal(0),
			alarm(1) }
		MAX-ACCESS read-only
		STATUS current
		DESCRIPTION
		"upsIta2com828Addr12BatFuseblown status."
		::= { upsIta2comEntry 830 }
upsIta2com830Addr12BatWaitingforcharging OBJECT-TYPE
		SYNTAX INTEGER {
			normal(0),
			alarm(1) }
		MAX-ACCESS read-only
		STATUS current
		DESCRIPTION
		"upsIta2com829Addr12BatWaitingforcharging status."
		::= { upsIta2comEntry 831 }
upsIta2com831Addr12BatBataging OBJECT-TYPE
		SYNTAX INTEGER {
			normal(0),
			alarm(1) }
		MAX-ACCESS read-only
		STATUS current
		DESCRIPTION
		"upsIta2com830Addr12BatBataging status."
		::= { upsIta2comEntry 832 }
upsIta2com832Addr12Batboxconnectabnormal OBJECT-TYPE
		SYNTAX INTEGER {
			normal(0),
			alarm(1) }
		MAX-ACCESS read-only
		STATUS current
		DESCRIPTION
		"upsIta2com831Addr12Batboxconnectabnormal status."
		::= { upsIta2comEntry 833 }
upsIta2com833Addr12batBatterySoftincompatibl OBJECT-TYPE
		SYNTAX INTEGER {
			normal(0),
			alarm(1) }
		MAX-ACCESS read-only
		STATUS current
		DESCRIPTION
		"upsIta2com832Addr12batBatterySoftincompatibl status."
		::= { upsIta2comEntry 834 }
upsIta2com834Addr12batEOL OBJECT-TYPE
		SYNTAX INTEGER {
			normal(0),
			alarm(1) }
		MAX-ACCESS read-only
		STATUS current
		DESCRIPTION
		"upsIta2com833Addr12batEOL status."
		::= { upsIta2comEntry 835 }
upsIta2com835Addr12batSamplingfailure OBJECT-TYPE
		SYNTAX INTEGER {
			normal(0),
			alarm(1) }
		MAX-ACCESS read-only
		STATUS current
		DESCRIPTION
		"upsIta2com834Addr12batSamplingfailure status."
		::= { upsIta2comEntry 836 }
upsIta2com836Addr12batHardwareprotection OBJECT-TYPE
		SYNTAX INTEGER {
			normal(0),
			alarm(1) }
		MAX-ACCESS read-only
		STATUS current
		DESCRIPTION
		"upsIta2com835Addr12batHardwareprotection status."
		::= { upsIta2comEntry 837 }
upsIta2com837Addr12batBatterycapacitylow OBJECT-TYPE
		SYNTAX INTEGER {
			normal(0),
			alarm(1) }
		MAX-ACCESS read-only
		STATUS current
		DESCRIPTION
		"upsIta2com836Addr12batBatterycapacitylow status."
		::= { upsIta2comEntry 838 }
upsIta2com838Addr13Batalarmnumber OBJECT-TYPE
		SYNTAX Integer32
		
		MAX-ACCESS read-only
		STATUS current
		DESCRIPTION
		"upsIta2com837Addr13Batalarmnumber stored as 1."
		::= { upsIta2comEntry 839 }
upsIta2com839Addr13Bathighvolt OBJECT-TYPE
		SYNTAX INTEGER {
			normal(0),
			alarm(1) }
		MAX-ACCESS read-only
		STATUS current
		DESCRIPTION
		"upsIta2com838Addr13Bathighvolt status."
		::= { upsIta2comEntry 840 }
upsIta2com840Addr13Batlowvolt OBJECT-TYPE
		SYNTAX INTEGER {
			normal(0),
			alarm(1) }
		MAX-ACCESS read-only
		STATUS current
		DESCRIPTION
		"upsIta2com839Addr13Batlowvolt status."
		::= { upsIta2comEntry 841 }
upsIta2com841Addr13Bathighcellvolt OBJECT-TYPE
		SYNTAX INTEGER {
			normal(0),
			alarm(1) }
		MAX-ACCESS read-only
		STATUS current
		DESCRIPTION
		"upsIta2com840Addr13Bathighcellvolt status."
		::= { upsIta2comEntry 842 }
upsIta2com842Addr13Batlowcellvolt OBJECT-TYPE
		SYNTAX INTEGER {
			normal(0),
			alarm(1) }
		MAX-ACCESS read-only
		STATUS current
		DESCRIPTION
		"upsIta2com841Addr13Batlowcellvolt status."
		::= { upsIta2comEntry 843 }
upsIta2com843Addr13Batchargehighcelltemp OBJECT-TYPE
		SYNTAX INTEGER {
			normal(0),
			alarm(1) }
		MAX-ACCESS read-only
		STATUS current
		DESCRIPTION
		"upsIta2com842Addr13Batchargehighcelltemp status."
		::= { upsIta2comEntry 844 }
upsIta2com844Addr13Batchargelowcelltemp OBJECT-TYPE
		SYNTAX INTEGER {
			normal(0),
			alarm(1) }
		MAX-ACCESS read-only
		STATUS current
		DESCRIPTION
		"upsIta2com843Addr13Batchargelowcelltemp status."
		::= { upsIta2comEntry 845 }
upsIta2com845Addr13Batchargeovercurrent OBJECT-TYPE
		SYNTAX INTEGER {
			normal(0),
			alarm(1) }
		MAX-ACCESS read-only
		STATUS current
		DESCRIPTION
		"upsIta2com844Addr13Batchargeovercurrent status."
		::= { upsIta2comEntry 846 }
upsIta2com846Addr13Batdischargeovercurrent OBJECT-TYPE
		SYNTAX INTEGER {
			normal(0),
			alarm(1) }
		MAX-ACCESS read-only
		STATUS current
		DESCRIPTION
		"upsIta2com845Addr13Batdischargeovercurrent status."
		::= { upsIta2comEntry 847 }
upsIta2com847Addr13BatAddrconflict OBJECT-TYPE
		SYNTAX INTEGER {
			normal(0),
			alarm(1) }
		MAX-ACCESS read-only
		STATUS current
		DESCRIPTION
		"upsIta2com846Addr13BatAddrconflict status."
		::= { upsIta2comEntry 848 }
upsIta2com848Addr13Batportreverse OBJECT-TYPE
		SYNTAX INTEGER {
			normal(0),
			alarm(1) }
		MAX-ACCESS read-only
		STATUS current
		DESCRIPTION
		"upsIta2com847Addr13Batportreverse status."
		::= { upsIta2comEntry 849 }
upsIta2com849Addr13BatBMSrelayinvalid OBJECT-TYPE
		SYNTAX INTEGER {
			normal(0),
			alarm(1) }
		MAX-ACCESS read-only
		STATUS current
		DESCRIPTION
		"upsIta2com848Addr13BatBMSrelayinvalid status."
		::= { upsIta2comEntry 850 }
upsIta2com850Addr13Batsafetyundervoltage OBJECT-TYPE
		SYNTAX INTEGER {
			normal(0),
			alarm(1) }
		MAX-ACCESS read-only
		STATUS current
		DESCRIPTION
		"upsIta2com849Addr13Batsafetyundervoltage status."
		::= { upsIta2comEntry 851 }
upsIta2com851Addr13Batdischargehighcelltemp OBJECT-TYPE
		SYNTAX INTEGER {
			normal(0),
			alarm(1) }
		MAX-ACCESS read-only
		STATUS current
		DESCRIPTION
		"upsIta2com850Addr13Batdischargehighcelltemp status."
		::= { upsIta2comEntry 852 }
upsIta2com852Addr13Batdischargelowcelltemp OBJECT-TYPE
		SYNTAX INTEGER {
			normal(0),
			alarm(1) }
		MAX-ACCESS read-only
		STATUS current
		DESCRIPTION
		"upsIta2com851Addr13Batdischargelowcelltemp status."
		::= { upsIta2comEntry 853 }
upsIta2com853Addr13Batparallelchargehightemp OBJECT-TYPE
		SYNTAX INTEGER {
			normal(0),
			alarm(1) }
		MAX-ACCESS read-only
		STATUS current
		DESCRIPTION
		"upsIta2com852Addr13Batparallelchargehightemp status."
		::= { upsIta2comEntry 854 }
upsIta2com854Addr13BatinternalCommabnormal OBJECT-TYPE
		SYNTAX INTEGER {
			normal(0),
			alarm(1) }
		MAX-ACCESS read-only
		STATUS current
		DESCRIPTION
		"upsIta2com853Addr13BatinternalCommabnormal status."
		::= { upsIta2comEntry 855 }
upsIta2com855Addr13Batconditionfail OBJECT-TYPE
		SYNTAX INTEGER {
			normal(0),
			alarm(1) }
		MAX-ACCESS read-only
		STATUS current
		DESCRIPTION
		"upsIta2com854Addr13Batconditionfail status."
		::= { upsIta2comEntry 856 }
upsIta2com856Addr13BatLowinsulationresistanc OBJECT-TYPE
		SYNTAX INTEGER {
			normal(0),
			alarm(1) }
		MAX-ACCESS read-only
		STATUS current
		DESCRIPTION
		"upsIta2com855Addr13BatLowinsulationresistanc status."
		::= { upsIta2comEntry 857 }
upsIta2com857Addr13BatLargepressurediff OBJECT-TYPE
		SYNTAX INTEGER {
			normal(0),
			alarm(1) }
		MAX-ACCESS read-only
		STATUS current
		DESCRIPTION
		"upsIta2com856Addr13BatLargepressurediff status."
		::= { upsIta2comEntry 858 }
upsIta2com858Addr13BatBatfailure OBJECT-TYPE
		SYNTAX INTEGER {
			normal(0),
			alarm(1) }
		MAX-ACCESS read-only
		STATUS current
		DESCRIPTION
		"upsIta2com857Addr13BatBatfailure status."
		::= { upsIta2comEntry 859 }
upsIta2com859Addr13BatVoltageacquisitfailure OBJECT-TYPE
		SYNTAX INTEGER {
			normal(0),
			alarm(1) }
		MAX-ACCESS read-only
		STATUS current
		DESCRIPTION
		"upsIta2com858Addr13BatVoltageacquisitfailure status."
		::= { upsIta2comEntry 860 }
upsIta2com860Addr13BatCurrentcolllectfailure OBJECT-TYPE
		SYNTAX INTEGER {
			normal(0),
			alarm(1) }
		MAX-ACCESS read-only
		STATUS current
		DESCRIPTION
		"upsIta2com859Addr13BatCurrentcolllectfailure status."
		::= { upsIta2comEntry 861 }
upsIta2com861Addr13BatTempcolllectfailure OBJECT-TYPE
		SYNTAX INTEGER {
			normal(0),
			alarm(1) }
		MAX-ACCESS read-only
		STATUS current
		DESCRIPTION
		"upsIta2com860Addr13BatTempcolllectfailure status."
		::= { upsIta2comEntry 862 }
upsIta2com862Addr13BatAddrSeterror OBJECT-TYPE
		SYNTAX INTEGER {
			normal(0),
			alarm(1) }
		MAX-ACCESS read-only
		STATUS current
		DESCRIPTION
		"upsIta2com861Addr13BatAddrSeterror status."
		::= { upsIta2comEntry 863 }
upsIta2com863Addr13BatLargegrouppressurediff OBJECT-TYPE
		SYNTAX INTEGER {
			normal(0),
			alarm(1) }
		MAX-ACCESS read-only
		STATUS current
		DESCRIPTION
		"upsIta2com862Addr13BatLargegrouppressurediff status."
		::= { upsIta2comEntry 864 }
upsIta2com864Addr13BatMOSFETfailure OBJECT-TYPE
		SYNTAX INTEGER {
			normal(0),
			alarm(1) }
		MAX-ACCESS read-only
		STATUS current
		DESCRIPTION
		"upsIta2com863Addr13BatMOSFETfailure status."
		::= { upsIta2comEntry 865 }
upsIta2com865Addr13Battempabnormal OBJECT-TYPE
		SYNTAX INTEGER {
			normal(0),
			alarm(1) }
		MAX-ACCESS read-only
		STATUS current
		DESCRIPTION
		"upsIta2com864Addr13Battempabnormal status."
		::= { upsIta2comEntry 866 }
upsIta2com866Addr13Batcablefault OBJECT-TYPE
		SYNTAX INTEGER {
			normal(0),
			alarm(1) }
		MAX-ACCESS read-only
		STATUS current
		DESCRIPTION
		"upsIta2com865Addr13Batcablefault status."
		::= { upsIta2comEntry 867 }
upsIta2com867Addr13BatShortcircuit OBJECT-TYPE
		SYNTAX INTEGER {
			normal(0),
			alarm(1) }
		MAX-ACCESS read-only
		STATUS current
		DESCRIPTION
		"upsIta2com866Addr13BatShortcircuit status."
		::= { upsIta2comEntry 868 }
upsIta2com868Addr13BatOtherfailures OBJECT-TYPE
		SYNTAX INTEGER {
			normal(0),
			alarm(1) }
		MAX-ACCESS read-only
		STATUS current
		DESCRIPTION
		"upsIta2com867Addr13BatOtherfailures status."
		::= { upsIta2comEntry 869 }
upsIta2com869Addr13BatCommcablefailure OBJECT-TYPE
		SYNTAX INTEGER {
			normal(0),
			alarm(1) }
		MAX-ACCESS read-only
		STATUS current
		DESCRIPTION
		"upsIta2com868Addr13BatCommcablefailure status."
		::= { upsIta2comEntry 870 }
upsIta2com870Addr13BatMOSFETtempishigh OBJECT-TYPE
		SYNTAX INTEGER {
			normal(0),
			alarm(1) }
		MAX-ACCESS read-only
		STATUS current
		DESCRIPTION
		"upsIta2com869Addr13BatMOSFETtempishigh status."
		::= { upsIta2comEntry 871 }
upsIta2com871Addr13BatFuseblown OBJECT-TYPE
		SYNTAX INTEGER {
			normal(0),
			alarm(1) }
		MAX-ACCESS read-only
		STATUS current
		DESCRIPTION
		"upsIta2com870Addr13BatFuseblown status."
		::= { upsIta2comEntry 872 }
upsIta2com872Addr13BatWaitingforcharging OBJECT-TYPE
		SYNTAX INTEGER {
			normal(0),
			alarm(1) }
		MAX-ACCESS read-only
		STATUS current
		DESCRIPTION
		"upsIta2com871Addr13BatWaitingforcharging status."
		::= { upsIta2comEntry 873 }
upsIta2com873Addr13BatBataging OBJECT-TYPE
		SYNTAX INTEGER {
			normal(0),
			alarm(1) }
		MAX-ACCESS read-only
		STATUS current
		DESCRIPTION
		"upsIta2com872Addr13BatBataging status."
		::= { upsIta2comEntry 874 }
upsIta2com874Addr13Batboxconnectabnormal OBJECT-TYPE
		SYNTAX INTEGER {
			normal(0),
			alarm(1) }
		MAX-ACCESS read-only
		STATUS current
		DESCRIPTION
		"upsIta2com873Addr13Batboxconnectabnormal status."
		::= { upsIta2comEntry 875 }
upsIta2com875Addr13batBatterySoftincompatibl OBJECT-TYPE
		SYNTAX INTEGER {
			normal(0),
			alarm(1) }
		MAX-ACCESS read-only
		STATUS current
		DESCRIPTION
		"upsIta2com874Addr13batBatterySoftincompatibl status."
		::= { upsIta2comEntry 876 }
upsIta2com876Addr13batEOL OBJECT-TYPE
		SYNTAX INTEGER {
			normal(0),
			alarm(1) }
		MAX-ACCESS read-only
		STATUS current
		DESCRIPTION
		"upsIta2com875Addr13batEOL status."
		::= { upsIta2comEntry 877 }
upsIta2com877Addr13batSamplingfailure OBJECT-TYPE
		SYNTAX INTEGER {
			normal(0),
			alarm(1) }
		MAX-ACCESS read-only
		STATUS current
		DESCRIPTION
		"upsIta2com876Addr13batSamplingfailure status."
		::= { upsIta2comEntry 878 }
upsIta2com878Addr13batHardwareprotection OBJECT-TYPE
		SYNTAX INTEGER {
			normal(0),
			alarm(1) }
		MAX-ACCESS read-only
		STATUS current
		DESCRIPTION
		"upsIta2com877Addr13batHardwareprotection status."
		::= { upsIta2comEntry 879 }
upsIta2com879Addr13batBatterycapacitylow OBJECT-TYPE
		SYNTAX INTEGER {
			normal(0),
			alarm(1) }
		MAX-ACCESS read-only
		STATUS current
		DESCRIPTION
		"upsIta2com878Addr13batBatterycapacitylow status."
		::= { upsIta2comEntry 880 }
upsIta2com880Addr14Batalarmnumber OBJECT-TYPE
		SYNTAX Integer32
		
		MAX-ACCESS read-only
		STATUS current
		DESCRIPTION
		"upsIta2com879Addr14Batalarmnumber stored as 1."
		::= { upsIta2comEntry 881 }
upsIta2com881Addr14Bathighvolt OBJECT-TYPE
		SYNTAX INTEGER {
			normal(0),
			alarm(1) }
		MAX-ACCESS read-only
		STATUS current
		DESCRIPTION
		"upsIta2com880Addr14Bathighvolt status."
		::= { upsIta2comEntry 882 }
upsIta2com882Addr14Batlowvolt OBJECT-TYPE
		SYNTAX INTEGER {
			normal(0),
			alarm(1) }
		MAX-ACCESS read-only
		STATUS current
		DESCRIPTION
		"upsIta2com881Addr14Batlowvolt status."
		::= { upsIta2comEntry 883 }
upsIta2com883Addr14Bathighcellvolt OBJECT-TYPE
		SYNTAX INTEGER {
			normal(0),
			alarm(1) }
		MAX-ACCESS read-only
		STATUS current
		DESCRIPTION
		"upsIta2com882Addr14Bathighcellvolt status."
		::= { upsIta2comEntry 884 }
upsIta2com884Addr14Batlowcellvolt OBJECT-TYPE
		SYNTAX INTEGER {
			normal(0),
			alarm(1) }
		MAX-ACCESS read-only
		STATUS current
		DESCRIPTION
		"upsIta2com883Addr14Batlowcellvolt status."
		::= { upsIta2comEntry 885 }
upsIta2com885Addr14Batchargehighcelltemp OBJECT-TYPE
		SYNTAX INTEGER {
			normal(0),
			alarm(1) }
		MAX-ACCESS read-only
		STATUS current
		DESCRIPTION
		"upsIta2com884Addr14Batchargehighcelltemp status."
		::= { upsIta2comEntry 886 }
upsIta2com886Addr14Batchargelowcelltemp OBJECT-TYPE
		SYNTAX INTEGER {
			normal(0),
			alarm(1) }
		MAX-ACCESS read-only
		STATUS current
		DESCRIPTION
		"upsIta2com885Addr14Batchargelowcelltemp status."
		::= { upsIta2comEntry 887 }
upsIta2com887Addr14Batchargeovercurrent OBJECT-TYPE
		SYNTAX INTEGER {
			normal(0),
			alarm(1) }
		MAX-ACCESS read-only
		STATUS current
		DESCRIPTION
		"upsIta2com886Addr14Batchargeovercurrent status."
		::= { upsIta2comEntry 888 }
upsIta2com888Addr14Batdischargeovercurrent OBJECT-TYPE
		SYNTAX INTEGER {
			normal(0),
			alarm(1) }
		MAX-ACCESS read-only
		STATUS current
		DESCRIPTION
		"upsIta2com887Addr14Batdischargeovercurrent status."
		::= { upsIta2comEntry 889 }
upsIta2com889Addr14BatAddrconflict OBJECT-TYPE
		SYNTAX INTEGER {
			normal(0),
			alarm(1) }
		MAX-ACCESS read-only
		STATUS current
		DESCRIPTION
		"upsIta2com888Addr14BatAddrconflict status."
		::= { upsIta2comEntry 890 }
upsIta2com890Addr14Batportreverse OBJECT-TYPE
		SYNTAX INTEGER {
			normal(0),
			alarm(1) }
		MAX-ACCESS read-only
		STATUS current
		DESCRIPTION
		"upsIta2com889Addr14Batportreverse status."
		::= { upsIta2comEntry 891 }
upsIta2com891Addr14BatBMSrelayinvalid OBJECT-TYPE
		SYNTAX INTEGER {
			normal(0),
			alarm(1) }
		MAX-ACCESS read-only
		STATUS current
		DESCRIPTION
		"upsIta2com890Addr14BatBMSrelayinvalid status."
		::= { upsIta2comEntry 892 }
upsIta2com892Addr14Batsafetyundervoltage OBJECT-TYPE
		SYNTAX INTEGER {
			normal(0),
			alarm(1) }
		MAX-ACCESS read-only
		STATUS current
		DESCRIPTION
		"upsIta2com891Addr14Batsafetyundervoltage status."
		::= { upsIta2comEntry 893 }
upsIta2com893Addr14Batdischargehighcelltemp OBJECT-TYPE
		SYNTAX INTEGER {
			normal(0),
			alarm(1) }
		MAX-ACCESS read-only
		STATUS current
		DESCRIPTION
		"upsIta2com892Addr14Batdischargehighcelltemp status."
		::= { upsIta2comEntry 894 }
upsIta2com894Addr14Batdischargelowcelltemp OBJECT-TYPE
		SYNTAX INTEGER {
			normal(0),
			alarm(1) }
		MAX-ACCESS read-only
		STATUS current
		DESCRIPTION
		"upsIta2com893Addr14Batdischargelowcelltemp status."
		::= { upsIta2comEntry 895 }
upsIta2com895Addr14Batparallelchargehightemp OBJECT-TYPE
		SYNTAX INTEGER {
			normal(0),
			alarm(1) }
		MAX-ACCESS read-only
		STATUS current
		DESCRIPTION
		"upsIta2com894Addr14Batparallelchargehightemp status."
		::= { upsIta2comEntry 896 }
upsIta2com896Addr14BatinternalCommabnormal OBJECT-TYPE
		SYNTAX INTEGER {
			normal(0),
			alarm(1) }
		MAX-ACCESS read-only
		STATUS current
		DESCRIPTION
		"upsIta2com895Addr14BatinternalCommabnormal status."
		::= { upsIta2comEntry 897 }
upsIta2com897Addr14Batconditionfail OBJECT-TYPE
		SYNTAX INTEGER {
			normal(0),
			alarm(1) }
		MAX-ACCESS read-only
		STATUS current
		DESCRIPTION
		"upsIta2com896Addr14Batconditionfail status."
		::= { upsIta2comEntry 898 }
upsIta2com898Addr14BatLowinsulationresistanc OBJECT-TYPE
		SYNTAX INTEGER {
			normal(0),
			alarm(1) }
		MAX-ACCESS read-only
		STATUS current
		DESCRIPTION
		"upsIta2com897Addr14BatLowinsulationresistanc status."
		::= { upsIta2comEntry 899 }
upsIta2com899Addr14BatLargepressurediff OBJECT-TYPE
		SYNTAX INTEGER {
			normal(0),
			alarm(1) }
		MAX-ACCESS read-only
		STATUS current
		DESCRIPTION
		"upsIta2com898Addr14BatLargepressurediff status."
		::= { upsIta2comEntry 900 }
upsIta2com900Addr14BatBatfailure OBJECT-TYPE
		SYNTAX INTEGER {
			normal(0),
			alarm(1) }
		MAX-ACCESS read-only
		STATUS current
		DESCRIPTION
		"upsIta2com899Addr14BatBatfailure status."
		::= { upsIta2comEntry 901 }
upsIta2com901Addr14BatVoltageacquisitfailure OBJECT-TYPE
		SYNTAX INTEGER {
			normal(0),
			alarm(1) }
		MAX-ACCESS read-only
		STATUS current
		DESCRIPTION
		"upsIta2com900Addr14BatVoltageacquisitfailure status."
		::= { upsIta2comEntry 902 }
upsIta2com902Addr14BatCurrentcolllectfailure OBJECT-TYPE
		SYNTAX INTEGER {
			normal(0),
			alarm(1) }
		MAX-ACCESS read-only
		STATUS current
		DESCRIPTION
		"upsIta2com901Addr14BatCurrentcolllectfailure status."
		::= { upsIta2comEntry 903 }
upsIta2com903Addr14BatTempcolllectfailure OBJECT-TYPE
		SYNTAX INTEGER {
			normal(0),
			alarm(1) }
		MAX-ACCESS read-only
		STATUS current
		DESCRIPTION
		"upsIta2com902Addr14BatTempcolllectfailure status."
		::= { upsIta2comEntry 904 }
upsIta2com904Addr14BatAddrSeterror OBJECT-TYPE
		SYNTAX INTEGER {
			normal(0),
			alarm(1) }
		MAX-ACCESS read-only
		STATUS current
		DESCRIPTION
		"upsIta2com903Addr14BatAddrSeterror status."
		::= { upsIta2comEntry 905 }
upsIta2com905Addr14BatLargegrouppressurediff OBJECT-TYPE
		SYNTAX INTEGER {
			normal(0),
			alarm(1) }
		MAX-ACCESS read-only
		STATUS current
		DESCRIPTION
		"upsIta2com904Addr14BatLargegrouppressurediff status."
		::= { upsIta2comEntry 906 }
upsIta2com906Addr14BatMOSFETfailure OBJECT-TYPE
		SYNTAX INTEGER {
			normal(0),
			alarm(1) }
		MAX-ACCESS read-only
		STATUS current
		DESCRIPTION
		"upsIta2com905Addr14BatMOSFETfailure status."
		::= { upsIta2comEntry 907 }
upsIta2com907Addr14Battempabnormal OBJECT-TYPE
		SYNTAX INTEGER {
			normal(0),
			alarm(1) }
		MAX-ACCESS read-only
		STATUS current
		DESCRIPTION
		"upsIta2com906Addr14Battempabnormal status."
		::= { upsIta2comEntry 908 }
upsIta2com908Addr14Batcablefault OBJECT-TYPE
		SYNTAX INTEGER {
			normal(0),
			alarm(1) }
		MAX-ACCESS read-only
		STATUS current
		DESCRIPTION
		"upsIta2com907Addr14Batcablefault status."
		::= { upsIta2comEntry 909 }
upsIta2com909Addr14BatShortcircuit OBJECT-TYPE
		SYNTAX INTEGER {
			normal(0),
			alarm(1) }
		MAX-ACCESS read-only
		STATUS current
		DESCRIPTION
		"upsIta2com908Addr14BatShortcircuit status."
		::= { upsIta2comEntry 910 }
upsIta2com910Addr14BatOtherfailures OBJECT-TYPE
		SYNTAX INTEGER {
			normal(0),
			alarm(1) }
		MAX-ACCESS read-only
		STATUS current
		DESCRIPTION
		"upsIta2com909Addr14BatOtherfailures status."
		::= { upsIta2comEntry 911 }
upsIta2com911Addr14BatCommcablefailure OBJECT-TYPE
		SYNTAX INTEGER {
			normal(0),
			alarm(1) }
		MAX-ACCESS read-only
		STATUS current
		DESCRIPTION
		"upsIta2com910Addr14BatCommcablefailure status."
		::= { upsIta2comEntry 912 }
upsIta2com912Addr14BatMOSFETtempishigh OBJECT-TYPE
		SYNTAX INTEGER {
			normal(0),
			alarm(1) }
		MAX-ACCESS read-only
		STATUS current
		DESCRIPTION
		"upsIta2com911Addr14BatMOSFETtempishigh status."
		::= { upsIta2comEntry 913 }
upsIta2com913Addr14BatFuseblown OBJECT-TYPE
		SYNTAX INTEGER {
			normal(0),
			alarm(1) }
		MAX-ACCESS read-only
		STATUS current
		DESCRIPTION
		"upsIta2com912Addr14BatFuseblown status."
		::= { upsIta2comEntry 914 }
upsIta2com914Addr14BatWaitingforcharging OBJECT-TYPE
		SYNTAX INTEGER {
			normal(0),
			alarm(1) }
		MAX-ACCESS read-only
		STATUS current
		DESCRIPTION
		"upsIta2com913Addr14BatWaitingforcharging status."
		::= { upsIta2comEntry 915 }
upsIta2com915Addr14BatBataging OBJECT-TYPE
		SYNTAX INTEGER {
			normal(0),
			alarm(1) }
		MAX-ACCESS read-only
		STATUS current
		DESCRIPTION
		"upsIta2com914Addr14BatBataging status."
		::= { upsIta2comEntry 916 }
upsIta2com916Addr14Batboxconnectabnormal OBJECT-TYPE
		SYNTAX INTEGER {
			normal(0),
			alarm(1) }
		MAX-ACCESS read-only
		STATUS current
		DESCRIPTION
		"upsIta2com915Addr14Batboxconnectabnormal status."
		::= { upsIta2comEntry 917 }
upsIta2com917Addr14batBatterySoftincompatibl OBJECT-TYPE
		SYNTAX INTEGER {
			normal(0),
			alarm(1) }
		MAX-ACCESS read-only
		STATUS current
		DESCRIPTION
		"upsIta2com916Addr14batBatterySoftincompatibl status."
		::= { upsIta2comEntry 918 }
upsIta2com918Addr14batEOL OBJECT-TYPE
		SYNTAX INTEGER {
			normal(0),
			alarm(1) }
		MAX-ACCESS read-only
		STATUS current
		DESCRIPTION
		"upsIta2com917Addr14batEOL status."
		::= { upsIta2comEntry 919 }
upsIta2com919Addr14batSamplingfailure OBJECT-TYPE
		SYNTAX INTEGER {
			normal(0),
			alarm(1) }
		MAX-ACCESS read-only
		STATUS current
		DESCRIPTION
		"upsIta2com918Addr14batSamplingfailure status."
		::= { upsIta2comEntry 920 }
upsIta2com920Addr14batHardwareprotection OBJECT-TYPE
		SYNTAX INTEGER {
			normal(0),
			alarm(1) }
		MAX-ACCESS read-only
		STATUS current
		DESCRIPTION
		"upsIta2com919Addr14batHardwareprotection status."
		::= { upsIta2comEntry 921 }
upsIta2com921Addr14batBatterycapacitylow OBJECT-TYPE
		SYNTAX INTEGER {
			normal(0),
			alarm(1) }
		MAX-ACCESS read-only
		STATUS current
		DESCRIPTION
		"upsIta2com920Addr14batBatterycapacitylow status."
		::= { upsIta2comEntry 922 }
upsIta2com922Addr15Batalarmnumber OBJECT-TYPE
		SYNTAX Integer32
		
		MAX-ACCESS read-only
		STATUS current
		DESCRIPTION
		"upsIta2com921Addr15Batalarmnumber stored as 1."
		::= { upsIta2comEntry 923 }
upsIta2com923Addr15Bathighvolt OBJECT-TYPE
		SYNTAX INTEGER {
			normal(0),
			alarm(1) }
		MAX-ACCESS read-only
		STATUS current
		DESCRIPTION
		"upsIta2com922Addr15Bathighvolt status."
		::= { upsIta2comEntry 924 }
upsIta2com924Addr15Batlowvolt OBJECT-TYPE
		SYNTAX INTEGER {
			normal(0),
			alarm(1) }
		MAX-ACCESS read-only
		STATUS current
		DESCRIPTION
		"upsIta2com923Addr15Batlowvolt status."
		::= { upsIta2comEntry 925 }
upsIta2com925Addr15Bathighcellvolt OBJECT-TYPE
		SYNTAX INTEGER {
			normal(0),
			alarm(1) }
		MAX-ACCESS read-only
		STATUS current
		DESCRIPTION
		"upsIta2com924Addr15Bathighcellvolt status."
		::= { upsIta2comEntry 926 }
upsIta2com926Addr15Batlowcellvolt OBJECT-TYPE
		SYNTAX INTEGER {
			normal(0),
			alarm(1) }
		MAX-ACCESS read-only
		STATUS current
		DESCRIPTION
		"upsIta2com925Addr15Batlowcellvolt status."
		::= { upsIta2comEntry 927 }
upsIta2com927Addr15Batchargehighcelltemp OBJECT-TYPE
		SYNTAX INTEGER {
			normal(0),
			alarm(1) }
		MAX-ACCESS read-only
		STATUS current
		DESCRIPTION
		"upsIta2com926Addr15Batchargehighcelltemp status."
		::= { upsIta2comEntry 928 }
upsIta2com928Addr15Batchargelowcelltemp OBJECT-TYPE
		SYNTAX INTEGER {
			normal(0),
			alarm(1) }
		MAX-ACCESS read-only
		STATUS current
		DESCRIPTION
		"upsIta2com927Addr15Batchargelowcelltemp status."
		::= { upsIta2comEntry 929 }
upsIta2com929Addr15Batchargeovercurrent OBJECT-TYPE
		SYNTAX INTEGER {
			normal(0),
			alarm(1) }
		MAX-ACCESS read-only
		STATUS current
		DESCRIPTION
		"upsIta2com928Addr15Batchargeovercurrent status."
		::= { upsIta2comEntry 930 }
upsIta2com930Addr15Batdischargeovercurrent OBJECT-TYPE
		SYNTAX INTEGER {
			normal(0),
			alarm(1) }
		MAX-ACCESS read-only
		STATUS current
		DESCRIPTION
		"upsIta2com929Addr15Batdischargeovercurrent status."
		::= { upsIta2comEntry 931 }
upsIta2com931Addr15BatAddrconflict OBJECT-TYPE
		SYNTAX INTEGER {
			normal(0),
			alarm(1) }
		MAX-ACCESS read-only
		STATUS current
		DESCRIPTION
		"upsIta2com930Addr15BatAddrconflict status."
		::= { upsIta2comEntry 932 }
upsIta2com932Addr15Batportreverse OBJECT-TYPE
		SYNTAX INTEGER {
			normal(0),
			alarm(1) }
		MAX-ACCESS read-only
		STATUS current
		DESCRIPTION
		"upsIta2com931Addr15Batportreverse status."
		::= { upsIta2comEntry 933 }
upsIta2com933Addr15BatBMSrelayinvalid OBJECT-TYPE
		SYNTAX INTEGER {
			normal(0),
			alarm(1) }
		MAX-ACCESS read-only
		STATUS current
		DESCRIPTION
		"upsIta2com932Addr15BatBMSrelayinvalid status."
		::= { upsIta2comEntry 934 }
upsIta2com934Addr15Batsafetyundervoltage OBJECT-TYPE
		SYNTAX INTEGER {
			normal(0),
			alarm(1) }
		MAX-ACCESS read-only
		STATUS current
		DESCRIPTION
		"upsIta2com933Addr15Batsafetyundervoltage status."
		::= { upsIta2comEntry 935 }
upsIta2com935Addr15Batdischargehighcelltemp OBJECT-TYPE
		SYNTAX INTEGER {
			normal(0),
			alarm(1) }
		MAX-ACCESS read-only
		STATUS current
		DESCRIPTION
		"upsIta2com934Addr15Batdischargehighcelltemp status."
		::= { upsIta2comEntry 936 }
upsIta2com936Addr15Batdischargelowcelltemp OBJECT-TYPE
		SYNTAX INTEGER {
			normal(0),
			alarm(1) }
		MAX-ACCESS read-only
		STATUS current
		DESCRIPTION
		"upsIta2com935Addr15Batdischargelowcelltemp status."
		::= { upsIta2comEntry 937 }
upsIta2com937Addr15Batparallelchargehightemp OBJECT-TYPE
		SYNTAX INTEGER {
			normal(0),
			alarm(1) }
		MAX-ACCESS read-only
		STATUS current
		DESCRIPTION
		"upsIta2com936Addr15Batparallelchargehightemp status."
		::= { upsIta2comEntry 938 }
upsIta2com938Addr15BatinternalCommabnormal OBJECT-TYPE
		SYNTAX INTEGER {
			normal(0),
			alarm(1) }
		MAX-ACCESS read-only
		STATUS current
		DESCRIPTION
		"upsIta2com937Addr15BatinternalCommabnormal status."
		::= { upsIta2comEntry 939 }
upsIta2com939Addr15Batconditionfail OBJECT-TYPE
		SYNTAX INTEGER {
			normal(0),
			alarm(1) }
		MAX-ACCESS read-only
		STATUS current
		DESCRIPTION
		"upsIta2com938Addr15Batconditionfail status."
		::= { upsIta2comEntry 940 }
upsIta2com940Addr15BatLowinsulationresistanc OBJECT-TYPE
		SYNTAX INTEGER {
			normal(0),
			alarm(1) }
		MAX-ACCESS read-only
		STATUS current
		DESCRIPTION
		"upsIta2com939Addr15BatLowinsulationresistanc status."
		::= { upsIta2comEntry 941 }
upsIta2com941Addr15BatLargepressurediff OBJECT-TYPE
		SYNTAX INTEGER {
			normal(0),
			alarm(1) }
		MAX-ACCESS read-only
		STATUS current
		DESCRIPTION
		"upsIta2com940Addr15BatLargepressurediff status."
		::= { upsIta2comEntry 942 }
upsIta2com942Addr15BatBatfailure OBJECT-TYPE
		SYNTAX INTEGER {
			normal(0),
			alarm(1) }
		MAX-ACCESS read-only
		STATUS current
		DESCRIPTION
		"upsIta2com941Addr15BatBatfailure status."
		::= { upsIta2comEntry 943 }
upsIta2com943Addr15BatVoltageacquisitfailure OBJECT-TYPE
		SYNTAX INTEGER {
			normal(0),
			alarm(1) }
		MAX-ACCESS read-only
		STATUS current
		DESCRIPTION
		"upsIta2com942Addr15BatVoltageacquisitfailure status."
		::= { upsIta2comEntry 944 }
upsIta2com944Addr15BatCurrentcolllectfailure OBJECT-TYPE
		SYNTAX INTEGER {
			normal(0),
			alarm(1) }
		MAX-ACCESS read-only
		STATUS current
		DESCRIPTION
		"upsIta2com943Addr15BatCurrentcolllectfailure status."
		::= { upsIta2comEntry 945 }
upsIta2com945Addr15BatTempcolllectfailure OBJECT-TYPE
		SYNTAX INTEGER {
			normal(0),
			alarm(1) }
		MAX-ACCESS read-only
		STATUS current
		DESCRIPTION
		"upsIta2com944Addr15BatTempcolllectfailure status."
		::= { upsIta2comEntry 946 }
upsIta2com946Addr15BatAddrSeterror OBJECT-TYPE
		SYNTAX INTEGER {
			normal(0),
			alarm(1) }
		MAX-ACCESS read-only
		STATUS current
		DESCRIPTION
		"upsIta2com945Addr15BatAddrSeterror status."
		::= { upsIta2comEntry 947 }
upsIta2com947Addr15BatLargegrouppressurediff OBJECT-TYPE
		SYNTAX INTEGER {
			normal(0),
			alarm(1) }
		MAX-ACCESS read-only
		STATUS current
		DESCRIPTION
		"upsIta2com946Addr15BatLargegrouppressurediff status."
		::= { upsIta2comEntry 948 }
upsIta2com948Addr15BatMOSFETfailure OBJECT-TYPE
		SYNTAX INTEGER {
			normal(0),
			alarm(1) }
		MAX-ACCESS read-only
		STATUS current
		DESCRIPTION
		"upsIta2com947Addr15BatMOSFETfailure status."
		::= { upsIta2comEntry 949 }
upsIta2com949Addr15Battempabnormal OBJECT-TYPE
		SYNTAX INTEGER {
			normal(0),
			alarm(1) }
		MAX-ACCESS read-only
		STATUS current
		DESCRIPTION
		"upsIta2com948Addr15Battempabnormal status."
		::= { upsIta2comEntry 950 }
upsIta2com950Addr15Batcablefault OBJECT-TYPE
		SYNTAX INTEGER {
			normal(0),
			alarm(1) }
		MAX-ACCESS read-only
		STATUS current
		DESCRIPTION
		"upsIta2com949Addr15Batcablefault status."
		::= { upsIta2comEntry 951 }
upsIta2com951Addr15BatShortcircuit OBJECT-TYPE
		SYNTAX INTEGER {
			normal(0),
			alarm(1) }
		MAX-ACCESS read-only
		STATUS current
		DESCRIPTION
		"upsIta2com950Addr15BatShortcircuit status."
		::= { upsIta2comEntry 952 }
upsIta2com952Addr15BatOtherfailures OBJECT-TYPE
		SYNTAX INTEGER {
			normal(0),
			alarm(1) }
		MAX-ACCESS read-only
		STATUS current
		DESCRIPTION
		"upsIta2com951Addr15BatOtherfailures status."
		::= { upsIta2comEntry 953 }
upsIta2com953Addr15BatCommcablefailure OBJECT-TYPE
		SYNTAX INTEGER {
			normal(0),
			alarm(1) }
		MAX-ACCESS read-only
		STATUS current
		DESCRIPTION
		"upsIta2com952Addr15BatCommcablefailure status."
		::= { upsIta2comEntry 954 }
upsIta2com954Addr15BatMOSFETtempishigh OBJECT-TYPE
		SYNTAX INTEGER {
			normal(0),
			alarm(1) }
		MAX-ACCESS read-only
		STATUS current
		DESCRIPTION
		"upsIta2com953Addr15BatMOSFETtempishigh status."
		::= { upsIta2comEntry 955 }
upsIta2com955Addr15BatFuseblown OBJECT-TYPE
		SYNTAX INTEGER {
			normal(0),
			alarm(1) }
		MAX-ACCESS read-only
		STATUS current
		DESCRIPTION
		"upsIta2com954Addr15BatFuseblown status."
		::= { upsIta2comEntry 956 }
upsIta2com956Addr15BatWaitingforcharging OBJECT-TYPE
		SYNTAX INTEGER {
			normal(0),
			alarm(1) }
		MAX-ACCESS read-only
		STATUS current
		DESCRIPTION
		"upsIta2com955Addr15BatWaitingforcharging status."
		::= { upsIta2comEntry 957 }
upsIta2com957Addr15BatBataging OBJECT-TYPE
		SYNTAX INTEGER {
			normal(0),
			alarm(1) }
		MAX-ACCESS read-only
		STATUS current
		DESCRIPTION
		"upsIta2com956Addr15BatBataging status."
		::= { upsIta2comEntry 958 }
upsIta2com958Addr15Batboxconnectabnormal OBJECT-TYPE
		SYNTAX INTEGER {
			normal(0),
			alarm(1) }
		MAX-ACCESS read-only
		STATUS current
		DESCRIPTION
		"upsIta2com957Addr15Batboxconnectabnormal status."
		::= { upsIta2comEntry 959 }
upsIta2com959Addr15batBatterySoftincompatibl OBJECT-TYPE
		SYNTAX INTEGER {
			normal(0),
			alarm(1) }
		MAX-ACCESS read-only
		STATUS current
		DESCRIPTION
		"upsIta2com958Addr15batBatterySoftincompatibl status."
		::= { upsIta2comEntry 960 }
upsIta2com960Addr15batEOL OBJECT-TYPE
		SYNTAX INTEGER {
			normal(0),
			alarm(1) }
		MAX-ACCESS read-only
		STATUS current
		DESCRIPTION
		"upsIta2com959Addr15batEOL status."
		::= { upsIta2comEntry 961 }
upsIta2com961Addr15batSamplingfailure OBJECT-TYPE
		SYNTAX INTEGER {
			normal(0),
			alarm(1) }
		MAX-ACCESS read-only
		STATUS current
		DESCRIPTION
		"upsIta2com960Addr15batSamplingfailure status."
		::= { upsIta2comEntry 962 }
upsIta2com962Addr15batHardwareprotection OBJECT-TYPE
		SYNTAX INTEGER {
			normal(0),
			alarm(1) }
		MAX-ACCESS read-only
		STATUS current
		DESCRIPTION
		"upsIta2com961Addr15batHardwareprotection status."
		::= { upsIta2comEntry 963 }
upsIta2com963Addr15batBatterycapacitylow OBJECT-TYPE
		SYNTAX INTEGER {
			normal(0),
			alarm(1) }
		MAX-ACCESS read-only
		STATUS current
		DESCRIPTION
		"upsIta2com962Addr15batBatterycapacitylow status."
		::= { upsIta2comEntry 964 }
upsIta2com964Addr16Batalarmnumber OBJECT-TYPE
		SYNTAX Integer32
		
		MAX-ACCESS read-only
		STATUS current
		DESCRIPTION
		"upsIta2com963Addr16Batalarmnumber stored as 1."
		::= { upsIta2comEntry 965 }
upsIta2com965Addr16Bathighvolt OBJECT-TYPE
		SYNTAX INTEGER {
			normal(0),
			alarm(1) }
		MAX-ACCESS read-only
		STATUS current
		DESCRIPTION
		"upsIta2com964Addr16Bathighvolt status."
		::= { upsIta2comEntry 966 }
upsIta2com966Addr16Batlowvolt OBJECT-TYPE
		SYNTAX INTEGER {
			normal(0),
			alarm(1) }
		MAX-ACCESS read-only
		STATUS current
		DESCRIPTION
		"upsIta2com965Addr16Batlowvolt status."
		::= { upsIta2comEntry 967 }
upsIta2com967Addr16Bathighcellvolt OBJECT-TYPE
		SYNTAX INTEGER {
			normal(0),
			alarm(1) }
		MAX-ACCESS read-only
		STATUS current
		DESCRIPTION
		"upsIta2com966Addr16Bathighcellvolt status."
		::= { upsIta2comEntry 968 }
upsIta2com968Addr16Batlowcellvolt OBJECT-TYPE
		SYNTAX INTEGER {
			normal(0),
			alarm(1) }
		MAX-ACCESS read-only
		STATUS current
		DESCRIPTION
		"upsIta2com967Addr16Batlowcellvolt status."
		::= { upsIta2comEntry 969 }
upsIta2com969Addr16Batchargehighcelltemp OBJECT-TYPE
		SYNTAX INTEGER {
			normal(0),
			alarm(1) }
		MAX-ACCESS read-only
		STATUS current
		DESCRIPTION
		"upsIta2com968Addr16Batchargehighcelltemp status."
		::= { upsIta2comEntry 970 }
upsIta2com970Addr16Batchargelowcelltemp OBJECT-TYPE
		SYNTAX INTEGER {
			normal(0),
			alarm(1) }
		MAX-ACCESS read-only
		STATUS current
		DESCRIPTION
		"upsIta2com969Addr16Batchargelowcelltemp status."
		::= { upsIta2comEntry 971 }
upsIta2com971Addr16Batchargeovercurrent OBJECT-TYPE
		SYNTAX INTEGER {
			normal(0),
			alarm(1) }
		MAX-ACCESS read-only
		STATUS current
		DESCRIPTION
		"upsIta2com970Addr16Batchargeovercurrent status."
		::= { upsIta2comEntry 972 }
upsIta2com972Addr16Batdischargeovercurrent OBJECT-TYPE
		SYNTAX INTEGER {
			normal(0),
			alarm(1) }
		MAX-ACCESS read-only
		STATUS current
		DESCRIPTION
		"upsIta2com971Addr16Batdischargeovercurrent status."
		::= { upsIta2comEntry 973 }
upsIta2com973Addr16BatAddrconflict OBJECT-TYPE
		SYNTAX INTEGER {
			normal(0),
			alarm(1) }
		MAX-ACCESS read-only
		STATUS current
		DESCRIPTION
		"upsIta2com972Addr16BatAddrconflict status."
		::= { upsIta2comEntry 974 }
upsIta2com974Addr16Batportreverse OBJECT-TYPE
		SYNTAX INTEGER {
			normal(0),
			alarm(1) }
		MAX-ACCESS read-only
		STATUS current
		DESCRIPTION
		"upsIta2com973Addr16Batportreverse status."
		::= { upsIta2comEntry 975 }
upsIta2com975Addr16BatBMSrelayinvalid OBJECT-TYPE
		SYNTAX INTEGER {
			normal(0),
			alarm(1) }
		MAX-ACCESS read-only
		STATUS current
		DESCRIPTION
		"upsIta2com974Addr16BatBMSrelayinvalid status."
		::= { upsIta2comEntry 976 }
upsIta2com976Addr16Batsafetyundervoltage OBJECT-TYPE
		SYNTAX INTEGER {
			normal(0),
			alarm(1) }
		MAX-ACCESS read-only
		STATUS current
		DESCRIPTION
		"upsIta2com975Addr16Batsafetyundervoltage status."
		::= { upsIta2comEntry 977 }
upsIta2com977Addr16Batdischargehighcelltemp OBJECT-TYPE
		SYNTAX INTEGER {
			normal(0),
			alarm(1) }
		MAX-ACCESS read-only
		STATUS current
		DESCRIPTION
		"upsIta2com976Addr16Batdischargehighcelltemp status."
		::= { upsIta2comEntry 978 }
upsIta2com978Addr16Batdischargelowcelltemp OBJECT-TYPE
		SYNTAX INTEGER {
			normal(0),
			alarm(1) }
		MAX-ACCESS read-only
		STATUS current
		DESCRIPTION
		"upsIta2com977Addr16Batdischargelowcelltemp status."
		::= { upsIta2comEntry 979 }
upsIta2com979Addr16Batparallelchargehightemp OBJECT-TYPE
		SYNTAX INTEGER {
			normal(0),
			alarm(1) }
		MAX-ACCESS read-only
		STATUS current
		DESCRIPTION
		"upsIta2com978Addr16Batparallelchargehightemp status."
		::= { upsIta2comEntry 980 }
upsIta2com980Addr16BatinternalCommabnormal OBJECT-TYPE
		SYNTAX INTEGER {
			normal(0),
			alarm(1) }
		MAX-ACCESS read-only
		STATUS current
		DESCRIPTION
		"upsIta2com979Addr16BatinternalCommabnormal status."
		::= { upsIta2comEntry 981 }
upsIta2com981Addr16Batconditionfail OBJECT-TYPE
		SYNTAX INTEGER {
			normal(0),
			alarm(1) }
		MAX-ACCESS read-only
		STATUS current
		DESCRIPTION
		"upsIta2com980Addr16Batconditionfail status."
		::= { upsIta2comEntry 982 }
upsIta2com982Addr16BatLowinsulationresistanc OBJECT-TYPE
		SYNTAX INTEGER {
			normal(0),
			alarm(1) }
		MAX-ACCESS read-only
		STATUS current
		DESCRIPTION
		"upsIta2com981Addr16BatLowinsulationresistanc status."
		::= { upsIta2comEntry 983 }
upsIta2com983Addr16BatLargepressurediff OBJECT-TYPE
		SYNTAX INTEGER {
			normal(0),
			alarm(1) }
		MAX-ACCESS read-only
		STATUS current
		DESCRIPTION
		"upsIta2com982Addr16BatLargepressurediff status."
		::= { upsIta2comEntry 984 }
upsIta2com984Addr16BatBatfailure OBJECT-TYPE
		SYNTAX INTEGER {
			normal(0),
			alarm(1) }
		MAX-ACCESS read-only
		STATUS current
		DESCRIPTION
		"upsIta2com983Addr16BatBatfailure status."
		::= { upsIta2comEntry 985 }
upsIta2com985Addr16BatVoltageacquisitfailure OBJECT-TYPE
		SYNTAX INTEGER {
			normal(0),
			alarm(1) }
		MAX-ACCESS read-only
		STATUS current
		DESCRIPTION
		"upsIta2com984Addr16BatVoltageacquisitfailure status."
		::= { upsIta2comEntry 986 }
upsIta2com986Addr16BatCurrentcolllectfailure OBJECT-TYPE
		SYNTAX INTEGER {
			normal(0),
			alarm(1) }
		MAX-ACCESS read-only
		STATUS current
		DESCRIPTION
		"upsIta2com985Addr16BatCurrentcolllectfailure status."
		::= { upsIta2comEntry 987 }
upsIta2com987Addr16BatTempcolllectfailure OBJECT-TYPE
		SYNTAX INTEGER {
			normal(0),
			alarm(1) }
		MAX-ACCESS read-only
		STATUS current
		DESCRIPTION
		"upsIta2com986Addr16BatTempcolllectfailure status."
		::= { upsIta2comEntry 988 }
upsIta2com988Addr16BatAddrSeterror OBJECT-TYPE
		SYNTAX INTEGER {
			normal(0),
			alarm(1) }
		MAX-ACCESS read-only
		STATUS current
		DESCRIPTION
		"upsIta2com987Addr16BatAddrSeterror status."
		::= { upsIta2comEntry 989 }
upsIta2com989Addr16BatLargegrouppressurediff OBJECT-TYPE
		SYNTAX INTEGER {
			normal(0),
			alarm(1) }
		MAX-ACCESS read-only
		STATUS current
		DESCRIPTION
		"upsIta2com988Addr16BatLargegrouppressurediff status."
		::= { upsIta2comEntry 990 }
upsIta2com990Addr16BatMOSFETfailure OBJECT-TYPE
		SYNTAX INTEGER {
			normal(0),
			alarm(1) }
		MAX-ACCESS read-only
		STATUS current
		DESCRIPTION
		"upsIta2com989Addr16BatMOSFETfailure status."
		::= { upsIta2comEntry 991 }
upsIta2com991Addr16Battempabnormal OBJECT-TYPE
		SYNTAX INTEGER {
			normal(0),
			alarm(1) }
		MAX-ACCESS read-only
		STATUS current
		DESCRIPTION
		"upsIta2com990Addr16Battempabnormal status."
		::= { upsIta2comEntry 992 }
upsIta2com992Addr16Batcablefault OBJECT-TYPE
		SYNTAX INTEGER {
			normal(0),
			alarm(1) }
		MAX-ACCESS read-only
		STATUS current
		DESCRIPTION
		"upsIta2com991Addr16Batcablefault status."
		::= { upsIta2comEntry 993 }
upsIta2com993Addr16BatShortcircuit OBJECT-TYPE
		SYNTAX INTEGER {
			normal(0),
			alarm(1) }
		MAX-ACCESS read-only
		STATUS current
		DESCRIPTION
		"upsIta2com992Addr16BatShortcircuit status."
		::= { upsIta2comEntry 994 }
upsIta2com994Addr16BatOtherfailures OBJECT-TYPE
		SYNTAX INTEGER {
			normal(0),
			alarm(1) }
		MAX-ACCESS read-only
		STATUS current
		DESCRIPTION
		"upsIta2com993Addr16BatOtherfailures status."
		::= { upsIta2comEntry 995 }
upsIta2com995Addr16BatCommcablefailure OBJECT-TYPE
		SYNTAX INTEGER {
			normal(0),
			alarm(1) }
		MAX-ACCESS read-only
		STATUS current
		DESCRIPTION
		"upsIta2com994Addr16BatCommcablefailure status."
		::= { upsIta2comEntry 996 }
upsIta2com996Addr16BatMOSFETtempishigh OBJECT-TYPE
		SYNTAX INTEGER {
			normal(0),
			alarm(1) }
		MAX-ACCESS read-only
		STATUS current
		DESCRIPTION
		"upsIta2com995Addr16BatMOSFETtempishigh status."
		::= { upsIta2comEntry 997 }
upsIta2com997Addr16BatFuseblown OBJECT-TYPE
		SYNTAX INTEGER {
			normal(0),
			alarm(1) }
		MAX-ACCESS read-only
		STATUS current
		DESCRIPTION
		"upsIta2com996Addr16BatFuseblown status."
		::= { upsIta2comEntry 998 }
upsIta2com998Addr16BatWaitingforcharging OBJECT-TYPE
		SYNTAX INTEGER {
			normal(0),
			alarm(1) }
		MAX-ACCESS read-only
		STATUS current
		DESCRIPTION
		"upsIta2com997Addr16BatWaitingforcharging status."
		::= { upsIta2comEntry 999 }
upsIta2com999Addr16BatBataging OBJECT-TYPE
		SYNTAX INTEGER {
			normal(0),
			alarm(1) }
		MAX-ACCESS read-only
		STATUS current
		DESCRIPTION
		"upsIta2com998Addr16BatBataging status."
		::= { upsIta2comEntry 1000 }
upsIta2com1000Addr16Batboxconnectabnormal OBJECT-TYPE
		SYNTAX INTEGER {
			normal(0),
			alarm(1) }
		MAX-ACCESS read-only
		STATUS current
		DESCRIPTION
		"upsIta2com999Addr16Batboxconnectabnormal status."
		::= { upsIta2comEntry 1001 }
upsIta2com1001Addr16batBatterySoftincompatibl OBJECT-TYPE
		SYNTAX INTEGER {
			normal(0),
			alarm(1) }
		MAX-ACCESS read-only
		STATUS current
		DESCRIPTION
		"upsIta2com1000Addr16batBatterySoftincompatibl status."
		::= { upsIta2comEntry 1002 }
upsIta2com1002Addr16batEOL OBJECT-TYPE
		SYNTAX INTEGER {
			normal(0),
			alarm(1) }
		MAX-ACCESS read-only
		STATUS current
		DESCRIPTION
		"upsIta2com1001Addr16batEOL status."
		::= { upsIta2comEntry 1003 }
upsIta2com1003Addr16batSamplingfailure OBJECT-TYPE
		SYNTAX INTEGER {
			normal(0),
			alarm(1) }
		MAX-ACCESS read-only
		STATUS current
		DESCRIPTION
		"upsIta2com1002Addr16batSamplingfailure status."
		::= { upsIta2comEntry 1004 }
upsIta2com1004Addr16batHardwareprotection OBJECT-TYPE
		SYNTAX INTEGER {
			normal(0),
			alarm(1) }
		MAX-ACCESS read-only
		STATUS current
		DESCRIPTION
		"upsIta2com1003Addr16batHardwareprotection status."
		::= { upsIta2comEntry 1005 }
upsIta2com1005Addr16batBatterycapacitylow OBJECT-TYPE
		SYNTAX INTEGER {
			normal(0),
			alarm(1) }
		MAX-ACCESS read-only
		STATUS current
		DESCRIPTION
		"upsIta2com1004Addr16batBatterycapacitylow status."
		::= { upsIta2comEntry 1006 }
upsIta2com1006Addr1Batcuralarmnumber OBJECT-TYPE
		SYNTAX Integer32
		
		MAX-ACCESS read-only
		STATUS current
		DESCRIPTION
		"upsIta2com1005Addr1Batcuralarmnumber stored as 1."
		::= { upsIta2comEntry 1007 }
upsIta2com1007Addr2Batcuralarmnumber OBJECT-TYPE
		SYNTAX Integer32
		
		MAX-ACCESS read-only
		STATUS current
		DESCRIPTION
		"upsIta2com1006Addr2Batcuralarmnumber stored as 1."
		::= { upsIta2comEntry 1008 }
upsIta2com1008Addr3Batcuralarmnumber OBJECT-TYPE
		SYNTAX Integer32
		
		MAX-ACCESS read-only
		STATUS current
		DESCRIPTION
		"upsIta2com1007Addr3Batcuralarmnumber stored as 1."
		::= { upsIta2comEntry 1009 }
upsIta2com1009Addr4Batcuralarmnumber OBJECT-TYPE
		SYNTAX Integer32
		
		MAX-ACCESS read-only
		STATUS current
		DESCRIPTION
		"upsIta2com1008Addr4Batcuralarmnumber stored as 1."
		::= { upsIta2comEntry 1010 }
upsIta2com1010Addr5Batcuralarmnumber OBJECT-TYPE
		SYNTAX Integer32
		
		MAX-ACCESS read-only
		STATUS current
		DESCRIPTION
		"upsIta2com1009Addr5Batcuralarmnumber stored as 1."
		::= { upsIta2comEntry 1011 }
upsIta2com1011Addr6Batcuralarmnumber OBJECT-TYPE
		SYNTAX Integer32
		
		MAX-ACCESS read-only
		STATUS current
		DESCRIPTION
		"upsIta2com1010Addr6Batcuralarmnumber stored as 1."
		::= { upsIta2comEntry 1012 }
upsIta2com1012Addr7Batcuralarmnumber OBJECT-TYPE
		SYNTAX Integer32
		
		MAX-ACCESS read-only
		STATUS current
		DESCRIPTION
		"upsIta2com1011Addr7Batcuralarmnumber stored as 1."
		::= { upsIta2comEntry 1013 }
upsIta2com1013Addr8Batcuralarmnumber OBJECT-TYPE
		SYNTAX Integer32
		
		MAX-ACCESS read-only
		STATUS current
		DESCRIPTION
		"upsIta2com1012Addr8Batcuralarmnumber stored as 1."
		::= { upsIta2comEntry 1014 }
upsIta2com1014Addr9Batcuralarmnumber OBJECT-TYPE
		SYNTAX Integer32
		
		MAX-ACCESS read-only
		STATUS current
		DESCRIPTION
		"upsIta2com1013Addr9Batcuralarmnumber stored as 1."
		::= { upsIta2comEntry 1015 }
upsIta2com1015Addr10Batcuralarmnumber OBJECT-TYPE
		SYNTAX Integer32
		
		MAX-ACCESS read-only
		STATUS current
		DESCRIPTION
		"upsIta2com1014Addr10Batcuralarmnumber stored as 1."
		::= { upsIta2comEntry 1016 }
upsIta2com1016Addr11Batcuralarmnumber OBJECT-TYPE
		SYNTAX Integer32
		
		MAX-ACCESS read-only
		STATUS current
		DESCRIPTION
		"upsIta2com1015Addr11Batcuralarmnumber stored as 1."
		::= { upsIta2comEntry 1017 }
upsIta2com1017Addr12Batcuralarmnumber OBJECT-TYPE
		SYNTAX Integer32
		
		MAX-ACCESS read-only
		STATUS current
		DESCRIPTION
		"upsIta2com1016Addr12Batcuralarmnumber stored as 1."
		::= { upsIta2comEntry 1018 }
upsIta2com1018Addr13Batcuralarmnumber OBJECT-TYPE
		SYNTAX Integer32
		
		MAX-ACCESS read-only
		STATUS current
		DESCRIPTION
		"upsIta2com1017Addr13Batcuralarmnumber stored as 1."
		::= { upsIta2comEntry 1019 }
upsIta2com1019Addr14Batcuralarmnumber OBJECT-TYPE
		SYNTAX Integer32
		
		MAX-ACCESS read-only
		STATUS current
		DESCRIPTION
		"upsIta2com1018Addr14Batcuralarmnumber stored as 1."
		::= { upsIta2comEntry 1020 }
upsIta2com1020Addr15Batcuralarmnumber OBJECT-TYPE
		SYNTAX Integer32
		
		MAX-ACCESS read-only
		STATUS current
		DESCRIPTION
		"upsIta2com1019Addr15Batcuralarmnumber stored as 1."
		::= { upsIta2comEntry 1021 }
upsIta2com1021Addr16Batcuralarmnumber OBJECT-TYPE
		SYNTAX Integer32
		
		MAX-ACCESS read-only
		STATUS current
		DESCRIPTION
		"upsIta2com1020Addr16Batcuralarmnumber stored as 1."
		::= { upsIta2comEntry 1022 }
upsIta2com1022StanderBatteryStatus OBJECT-TYPE
		SYNTAX INTEGER {
			nondischargeandrecharge(0),
			floatcharging(1),
			equalizationcharging(2),
			discharging(3) }
		MAX-ACCESS read-only
		STATUS current
		DESCRIPTION
		"upsIta2com1021StanderBatteryStatus status."
		::= { upsIta2comEntry 1023 }
upsIta2com1023Commtatus OBJECT-TYPE
		SYNTAX INTEGER {
			normal(0),
			alarm(1) }
		MAX-ACCESS read-only
		STATUS current
		DESCRIPTION
		"upsIta2com1022Commtatus status."
		::= { upsIta2comEntry 1024 }
upsIta2com1024RemoteBatSelftest OBJECT-TYPE
		SYNTAX INTEGER {
			start(0),
			end(1) }
		MAX-ACCESS read-write
		STATUS current
		DESCRIPTION
		"upsIta2com1023RemoteBatSelftest status."
		::= { upsIta2comEntry 1025 }
upsIta2com1025BatSelfTestCommand OBJECT-TYPE
		SYNTAX INTEGER {
			start(0),
			end(1) }
		MAX-ACCESS read-write
		STATUS current
		DESCRIPTION
		"upsIta2com1024BatSelfTestCommand status."
		::= { upsIta2comEntry 1026 }
upsIta2com1026TurnOffUpsOutput OBJECT-TYPE
		SYNTAX INTEGER {
			yes(0) }
		MAX-ACCESS read-write
		STATUS current
		DESCRIPTION
		"upsIta2com1025TurnOffUpsOutput status."
		::= { upsIta2comEntry 1027 }
upsIta2com1027TurnOnUpsInstantly OBJECT-TYPE
		SYNTAX INTEGER {
			yes(0) }
		MAX-ACCESS read-write
		STATUS current
		DESCRIPTION
		"upsIta2com1026TurnOnUpsInstantly status."
		::= { upsIta2comEntry 1028 }
upsIta2com1028TurnOffUpsInstantly OBJECT-TYPE
		SYNTAX INTEGER {
			yes(0) }
		MAX-ACCESS read-write
		STATUS current
		DESCRIPTION
		"upsIta2com1027TurnOffUpsInstantly status."
		::= { upsIta2comEntry 1029 }
upsIta2com1029SetTime OBJECT-TYPE
		SYNTAX INTEGER {
			yes(0) }
		MAX-ACCESS read-write
		STATUS current
		DESCRIPTION
		"upsIta2com1028SetTime status."
		::= { upsIta2comEntry 1030 }
upsIta2com1030OpenInverterWithDelay OBJECT-TYPE
		SYNTAX INTEGER {
			yes(0) }
		MAX-ACCESS read-write
		STATUS current
		DESCRIPTION
		"upsIta2com1029OpenInverterWithDelay status."
		::= { upsIta2comEntry 1031 }
upsIta2com1031CloseOutputWithDelay OBJECT-TYPE
		SYNTAX INTEGER {
			yes(0) }
		MAX-ACCESS read-write
		STATUS current
		DESCRIPTION
		"upsIta2com1030CloseOutputWithDelay status."
		::= { upsIta2comEntry 1032 }
upsIta2com1032DelayedShutdownCancellation OBJECT-TYPE
		SYNTAX INTEGER {
			yes(0) }
		MAX-ACCESS read-write
		STATUS current
		DESCRIPTION
		"upsIta2com1031DelayedShutdownCancellation status."
		::= { upsIta2comEntry 1033 }
upsIta2com1033ForcedtowakeuplithiumBat OBJECT-TYPE
		SYNTAX INTEGER {
			yes(0) }
		MAX-ACCESS read-write
		STATUS current
		DESCRIPTION
		"upsIta2com1032ForcedtowakeuplithiumBat status."
		::= { upsIta2comEntry 1034 }
upsIta2com1034DelayTimeOfSelfStart OBJECT-TYPE
		SYNTAX Integer32
		
		MAX-ACCESS read-write
		STATUS current
		DESCRIPTION
		"upsIta2com1033DelayTimeOfSelfStart stored as 1s."
		::= { upsIta2comEntry 1035 }
upsIta2com1035DelayTimeOfRemoteShutDown OBJECT-TYPE
		SYNTAX Integer32
		
		MAX-ACCESS read-write
		STATUS current
		DESCRIPTION
		"upsIta2com1034DelayTimeOfRemoteShutDown stored as 1s."
		::= { upsIta2comEntry 1036 }
upsIta2com1036IntervalOfBatSelfTest OBJECT-TYPE
		SYNTAX INTEGER {
			forbidden(0),
			8weeks(1),
			12weeks(2),
			16weeks(3),
			20weeks(4),
			26weeks(5) }
		MAX-ACCESS read-write
		STATUS current
		DESCRIPTION
		"upsIta2com1035IntervalOfBatSelfTest status."
		::= { upsIta2comEntry 1037 }
upsIta2com1037UpsWorkingMode OBJECT-TYPE
		SYNTAX INTEGER {
			normalmode(0),
			ecomode(1) }
		MAX-ACCESS read-write
		STATUS current
		DESCRIPTION
		"upsIta2com1036UpsWorkingMode status."
		::= { upsIta2comEntry 1038 }
upsIta2com1038SelfStartSet OBJECT-TYPE
		SYNTAX INTEGER {
			forbidden(0),
			allow(1) }
		MAX-ACCESS read-write
		STATUS current
		DESCRIPTION
		"upsIta2com1037SelfStartSet status."
		::= { upsIta2comEntry 1039 }
upsIta2com1039SetsRedundance OBJECT-TYPE
		SYNTAX INTEGER {
			no(0),
			yes(1) }
		MAX-ACCESS read-write
		STATUS current
		DESCRIPTION
		"upsIta2com1038SetsRedundance status."
		::= { upsIta2comEntry 1040 }
upsIta2com1040RemoteOpenDelayTime OBJECT-TYPE
		SYNTAX Integer32
		
		MAX-ACCESS read-write
		STATUS current
		DESCRIPTION
		"upsIta2com1039RemoteOpenDelayTime stored as 1s."
		::= { upsIta2comEntry 1041 }
upsIta2com1041LogNumberSet OBJECT-TYPE
		SYNTAX Integer32
		
		MAX-ACCESS read-write
		STATUS current
		DESCRIPTION
		"upsIta2com1040LogNumberSet stored as 1."
		::= { upsIta2comEntry 1042 }

------------------------------------------------------------
-- Mpdu { 13400.3.2 }
------------------------------------------------------------
pdu OBJECT IDENTIFIER ::=  { dcs 2 }


------------------------------------------------------------
-- Mpscom { 13400.3.2.225 }
------------------------------------------------------------
mpdu-Mpscom OBJECT IDENTIFIER ::= { pdu 225 }
mpduMpscomTable OBJECT-TYPE
		SYNTAX			SEQUENCE OF MpduMpscomEntry
		MAX-ACCESS		not-accessible
		STATUS			current
		DESCRIPTION	"mpduMpscomTable"
		::=			{ mpdu-Mpscom 1 }
mpduMpscomEntry OBJECT-TYPE
		SYNTAX			MpduMpscomEntry
		MAX-ACCESS		not-accessible
		STATUS			current
		DESCRIPTION		"mpduMpscomEntry"
		INDEX			{ mpduMpscomIndex }
		::=				{ mpduMpscomTable 1 }
MpduMpscomEntry ::= SEQUENCE {
		mpduMpscomIndex					Integer32,
		mpduMpscom2ProductType					INTEGER,
		mpduMpscom3Voltage					Integer32,
		mpduMpscom4TotalCurrent					Integer32,
		mpduMpscom5Branch1Current					Integer32,
		mpduMpscom6Branch2Current					Integer32,
		mpduMpscom7Branch3Current					Integer32,
		mpduMpscom8ActivePower					Integer32,
		mpduMpscom9ApparentPower					Integer32,
		mpduMpscom10PowerFactor					Integer32,
		mpduMpscom11Frequency					Integer32,
		mpduMpscom12LoadCurrent					Integer32,
		mpduMpscom13PowerConsumption					Integer32,
		mpduMpscom14OutletState116					Integer32,
		mpduMpscom15OutletState1732					Integer32,
		mpduMpscom16TimeS					Integer32,
		mpduMpscom17TimeMin					Integer32,
		mpduMpscom18TimeHour					Integer32,
		mpduMpscom19TimeDay					Integer32,
		mpduMpscom20TimeWeek					Integer32,
		mpduMpscom21TimeMonth					Integer32,
		mpduMpscom22TimeYear					Integer32,
		mpduMpscom23Barcode12					Integer32,
		mpduMpscom24Barcode34					Integer32,
		mpduMpscom25Barcode56					Integer32,
		mpduMpscom26Barcode78					Integer32,
		mpduMpscom27Barcode910					Integer32,
		mpduMpscom28Barcode1112					Integer32,
		mpduMpscom29Barcode1314					Integer32,
		mpduMpscom30Barcode1516					Integer32,
		mpduMpscom31Barcode1718					Integer32,
		mpduMpscom32Barcode1920					Integer32,
		mpduMpscom33C13OutputNumbers					Integer32,
		mpduMpscom34C19OutputNumbers					Integer32,
		mpduMpscom3510AStandard					Integer32,
		mpduMpscom3616AStandard					Integer32,
		mpduMpscom37RatedCurrent					Integer32,
		mpduMpscom38ProductAddress					Integer32,
		mpduMpscom39Voltagedifference					Integer32,
		mpduMpscom40Currentdifference					Integer32,
		mpduMpscom41LoadVoltageLowLimit					INTEGER,
		mpduMpscom42LoadVoltageHighLimit					INTEGER,
		mpduMpscom43LoadCurrentLowLimit					INTEGER,
		mpduMpscom44LoadCurrentHighLimit					INTEGER,
		mpduMpscom45Branch1LoadTotalCurrentLow					INTEGER,
		mpduMpscom46Branch1LoadTotalCurrentHigh					INTEGER,
		mpduMpscom47Branch2LoadTotalCurrentLow					INTEGER,
		mpduMpscom48Branch2LoadTotalCurrentHigh					INTEGER,
		mpduMpscom49Branch3LoadTotalCurrentLow					INTEGER,
		mpduMpscom50Branch3LoadTotalCurrentHigh					INTEGER,
		mpduMpscom51CommunicateStatus					INTEGER,
		mpduMpscom52Outlet1Status					INTEGER,
		mpduMpscom53Outlet2Status					INTEGER,
		mpduMpscom54Outlet3Status					INTEGER,
		mpduMpscom55Outlet4Status					INTEGER,
		mpduMpscom56Outlet5Status					INTEGER,
		mpduMpscom57Outlet6Status					INTEGER,
		mpduMpscom58Outlet7Status					INTEGER,
		mpduMpscom59Outlet8Status					INTEGER,
		mpduMpscom60Outlet9Status					INTEGER,
		mpduMpscom61Outlet10Status					INTEGER,
		mpduMpscom62Outlet11Status					INTEGER,
		mpduMpscom63Outlet12Status					INTEGER,
		mpduMpscom64Outlet13Status					INTEGER,
		mpduMpscom65Outlet14Status					INTEGER,
		mpduMpscom66Outlet15Status					INTEGER,
		mpduMpscom67Outlet16Status					INTEGER,
		mpduMpscom68Outlet17Status					INTEGER,
		mpduMpscom69Outlet18Status					INTEGER,
		mpduMpscom70Outlet19Status					INTEGER,
		mpduMpscom71Outlet20Status					INTEGER,
		mpduMpscom72Outlet21Status					INTEGER,
		mpduMpscom73Outlet22Status					INTEGER,
		mpduMpscom74Outlet23Status					INTEGER,
		mpduMpscom75Outlet24Status					INTEGER,
		mpduMpscom76LoadVoltageLowLimit					Integer32,
		mpduMpscom77LoadVoltageHighLimit					Integer32,
		mpduMpscom78LoadCurrentLowLimit					Integer32,
		mpduMpscom79LoadCurrentHighLimit					Integer32,
		mpduMpscom80Branch1LoadTotalCurrentLow					Integer32,
		mpduMpscom81Branch1LoadTotalCurrentHigh					Integer32,
		mpduMpscom82Branch2LoadTotalCurrentLow					Integer32,
		mpduMpscom83Branch2LoadTotalCurrentHigh					Integer32,
		mpduMpscom84Branch3LoadTotalCurrentLow					Integer32,
		mpduMpscom85Branch3LoadTotalCurrentHigh					Integer32,
		mpduMpscom86Outlet1DelayTime					INTEGER,
		mpduMpscom87Outlet2DelayTime					INTEGER,
		mpduMpscom88Outlet3DelayTime					INTEGER,
		mpduMpscom89Outlet4DelayTime					INTEGER,
		mpduMpscom90Outlet5DelayTime					INTEGER,
		mpduMpscom91Outlet6DelayTime					INTEGER,
		mpduMpscom92Outlet7DelayTime					INTEGER,
		mpduMpscom93Outlet8DelayTime					INTEGER,
		mpduMpscom94Outlet9DelayTime					INTEGER,
		mpduMpscom95Outlet10DelayTime					INTEGER,
		mpduMpscom96Outlet11DelayTime					INTEGER,
		mpduMpscom97Outlet12DelayTime					INTEGER,
		mpduMpscom98Outlet13DelayTime					INTEGER,
		mpduMpscom99Outlet14DelayTime					INTEGER,
		mpduMpscom100Outlet15DelayTime					INTEGER,
		mpduMpscom101Outlet16DelayTime					INTEGER,
		mpduMpscom102Outlet17DelayTime					INTEGER,
		mpduMpscom103Outlet18DelayTime					INTEGER,
		mpduMpscom104Outlet19DelayTime					INTEGER,
		mpduMpscom105Outlet20DelayTime					INTEGER,
		mpduMpscom106Outlet21DelayTime					INTEGER,
		mpduMpscom107Outlet22DelayTime					INTEGER,
		mpduMpscom108Outlet23DelayTime					INTEGER,
		mpduMpscom109Outlet24DelayTime					INTEGER,
		mpduMpscom110PDUPORTNUM					INTEGER }
mpduMpscomIndex OBJECT-TYPE
		SYNTAX Integer32(1..110)
		MAX-ACCESS read-only
		STATUS current
		DESCRIPTION
		"mpduMpscom System Entry Index."
		::= { mpduMpscomEntry 1 }
mpduMpscom2ProductType OBJECT-TYPE
		SYNTAX INTEGER {
			undefined(0),
			totalcurrentcommeter(1),
			totalcurrentcomswitch(2),
			totalcurrentipmeter(3),
			totalcurrentipswitch(4),
			bitcurrentcommeter(5),
			bitcurrentcomswitch(6),
			bitcurrentipmeter(7),
			bitcurrentipswitch(8) }
		MAX-ACCESS read-only
		STATUS current
		DESCRIPTION
		"mpduMpscom1ProductType status."
		::= { mpduMpscomEntry 2 }
mpduMpscom3Voltage OBJECT-TYPE
		SYNTAX Integer32
		
		MAX-ACCESS read-only
		STATUS current
		DESCRIPTION
		"mpduMpscom2Voltage stored as 1V."
		::= { mpduMpscomEntry 3 }
mpduMpscom4TotalCurrent OBJECT-TYPE
		SYNTAX Integer32
		
		MAX-ACCESS read-only
		STATUS current
		DESCRIPTION
		"mpduMpscom3TotalCurrent stored as 0.1A."
		::= { mpduMpscomEntry 4 }
mpduMpscom5Branch1Current OBJECT-TYPE
		SYNTAX Integer32
		
		MAX-ACCESS read-only
		STATUS current
		DESCRIPTION
		"mpduMpscom4Branch1Current stored as 0.1A."
		::= { mpduMpscomEntry 5 }
mpduMpscom6Branch2Current OBJECT-TYPE
		SYNTAX Integer32
		
		MAX-ACCESS read-only
		STATUS current
		DESCRIPTION
		"mpduMpscom5Branch2Current stored as 0.1A."
		::= { mpduMpscomEntry 6 }
mpduMpscom7Branch3Current OBJECT-TYPE
		SYNTAX Integer32
		
		MAX-ACCESS read-only
		STATUS current
		DESCRIPTION
		"mpduMpscom6Branch3Current stored as 0.1A."
		::= { mpduMpscomEntry 7 }
mpduMpscom8ActivePower OBJECT-TYPE
		SYNTAX Integer32
		
		MAX-ACCESS read-only
		STATUS current
		DESCRIPTION
		"mpduMpscom7ActivePower stored as 0.01kW."
		::= { mpduMpscomEntry 8 }
mpduMpscom9ApparentPower OBJECT-TYPE
		SYNTAX Integer32
		
		MAX-ACCESS read-only
		STATUS current
		DESCRIPTION
		"mpduMpscom8ApparentPower stored as 0.01kVA."
		::= { mpduMpscomEntry 9 }
mpduMpscom10PowerFactor OBJECT-TYPE
		SYNTAX Integer32
		
		MAX-ACCESS read-only
		STATUS current
		DESCRIPTION
		"mpduMpscom9PowerFactor stored as 0.01."
		::= { mpduMpscomEntry 10 }
mpduMpscom11Frequency OBJECT-TYPE
		SYNTAX Integer32
		
		MAX-ACCESS read-only
		STATUS current
		DESCRIPTION
		"mpduMpscom10Frequency stored as 0.1Hz."
		::= { mpduMpscomEntry 11 }
mpduMpscom12LoadCurrent OBJECT-TYPE
		SYNTAX Integer32
		
		MAX-ACCESS read-only
		STATUS current
		DESCRIPTION
		"mpduMpscom11LoadCurrent stored as 0.1%."
		::= { mpduMpscomEntry 12 }
mpduMpscom13PowerConsumption OBJECT-TYPE
		SYNTAX Integer32
		
		MAX-ACCESS read-only
		STATUS current
		DESCRIPTION
		"mpduMpscom12PowerConsumption stored as 0.01kWh."
		::= { mpduMpscomEntry 13 }
mpduMpscom14OutletState116 OBJECT-TYPE
		SYNTAX Integer32
		
		MAX-ACCESS read-only
		STATUS current
		DESCRIPTION
		"mpduMpscom13OutletState116 stored as 1."
		::= { mpduMpscomEntry 14 }
mpduMpscom15OutletState1732 OBJECT-TYPE
		SYNTAX Integer32
		
		MAX-ACCESS read-only
		STATUS current
		DESCRIPTION
		"mpduMpscom14OutletState1732 stored as 1."
		::= { mpduMpscomEntry 15 }
mpduMpscom16TimeS OBJECT-TYPE
		SYNTAX Integer32
		
		MAX-ACCESS read-only
		STATUS current
		DESCRIPTION
		"mpduMpscom15TimeS stored as 1S."
		::= { mpduMpscomEntry 16 }
mpduMpscom17TimeMin OBJECT-TYPE
		SYNTAX Integer32
		
		MAX-ACCESS read-only
		STATUS current
		DESCRIPTION
		"mpduMpscom16TimeMin stored as 1Min."
		::= { mpduMpscomEntry 17 }
mpduMpscom18TimeHour OBJECT-TYPE
		SYNTAX Integer32
		
		MAX-ACCESS read-only
		STATUS current
		DESCRIPTION
		"mpduMpscom17TimeHour stored as 1Hour."
		::= { mpduMpscomEntry 18 }
mpduMpscom19TimeDay OBJECT-TYPE
		SYNTAX Integer32
		
		MAX-ACCESS read-only
		STATUS current
		DESCRIPTION
		"mpduMpscom18TimeDay stored as 1Day."
		::= { mpduMpscomEntry 19 }
mpduMpscom20TimeWeek OBJECT-TYPE
		SYNTAX Integer32
		
		MAX-ACCESS read-only
		STATUS current
		DESCRIPTION
		"mpduMpscom19TimeWeek stored as 1Week."
		::= { mpduMpscomEntry 20 }
mpduMpscom21TimeMonth OBJECT-TYPE
		SYNTAX Integer32
		
		MAX-ACCESS read-only
		STATUS current
		DESCRIPTION
		"mpduMpscom20TimeMonth stored as 1Month."
		::= { mpduMpscomEntry 21 }
mpduMpscom22TimeYear OBJECT-TYPE
		SYNTAX Integer32
		
		MAX-ACCESS read-only
		STATUS current
		DESCRIPTION
		"mpduMpscom21TimeYear stored as 1Year."
		::= { mpduMpscomEntry 22 }
mpduMpscom23Barcode12 OBJECT-TYPE
		SYNTAX Integer32
		
		MAX-ACCESS read-only
		STATUS current
		DESCRIPTION
		"mpduMpscom22Barcode12 stored as 1."
		::= { mpduMpscomEntry 23 }
mpduMpscom24Barcode34 OBJECT-TYPE
		SYNTAX Integer32
		
		MAX-ACCESS read-only
		STATUS current
		DESCRIPTION
		"mpduMpscom23Barcode34 stored as 1."
		::= { mpduMpscomEntry 24 }
mpduMpscom25Barcode56 OBJECT-TYPE
		SYNTAX Integer32
		
		MAX-ACCESS read-only
		STATUS current
		DESCRIPTION
		"mpduMpscom24Barcode56 stored as 1."
		::= { mpduMpscomEntry 25 }
mpduMpscom26Barcode78 OBJECT-TYPE
		SYNTAX Integer32
		
		MAX-ACCESS read-only
		STATUS current
		DESCRIPTION
		"mpduMpscom25Barcode78 stored as 1."
		::= { mpduMpscomEntry 26 }
mpduMpscom27Barcode910 OBJECT-TYPE
		SYNTAX Integer32
		
		MAX-ACCESS read-only
		STATUS current
		DESCRIPTION
		"mpduMpscom26Barcode910 stored as 1."
		::= { mpduMpscomEntry 27 }
mpduMpscom28Barcode1112 OBJECT-TYPE
		SYNTAX Integer32
		
		MAX-ACCESS read-only
		STATUS current
		DESCRIPTION
		"mpduMpscom27Barcode1112 stored as 1."
		::= { mpduMpscomEntry 28 }
mpduMpscom29Barcode1314 OBJECT-TYPE
		SYNTAX Integer32
		
		MAX-ACCESS read-only
		STATUS current
		DESCRIPTION
		"mpduMpscom28Barcode1314 stored as 1."
		::= { mpduMpscomEntry 29 }
mpduMpscom30Barcode1516 OBJECT-TYPE
		SYNTAX Integer32
		
		MAX-ACCESS read-only
		STATUS current
		DESCRIPTION
		"mpduMpscom29Barcode1516 stored as 1."
		::= { mpduMpscomEntry 30 }
mpduMpscom31Barcode1718 OBJECT-TYPE
		SYNTAX Integer32
		
		MAX-ACCESS read-only
		STATUS current
		DESCRIPTION
		"mpduMpscom30Barcode1718 stored as 1."
		::= { mpduMpscomEntry 31 }
mpduMpscom32Barcode1920 OBJECT-TYPE
		SYNTAX Integer32
		
		MAX-ACCESS read-only
		STATUS current
		DESCRIPTION
		"mpduMpscom31Barcode1920 stored as 1."
		::= { mpduMpscomEntry 32 }
mpduMpscom33C13OutputNumbers OBJECT-TYPE
		SYNTAX Integer32
		
		MAX-ACCESS read-only
		STATUS current
		DESCRIPTION
		"mpduMpscom32C13OutputNumbers stored as 1."
		::= { mpduMpscomEntry 33 }
mpduMpscom34C19OutputNumbers OBJECT-TYPE
		SYNTAX Integer32
		
		MAX-ACCESS read-only
		STATUS current
		DESCRIPTION
		"mpduMpscom33C19OutputNumbers stored as 1."
		::= { mpduMpscomEntry 34 }
mpduMpscom3510AStandard OBJECT-TYPE
		SYNTAX Integer32
		
		MAX-ACCESS read-only
		STATUS current
		DESCRIPTION
		"mpduMpscom3410AStandard stored as 1."
		::= { mpduMpscomEntry 35 }
mpduMpscom3616AStandard OBJECT-TYPE
		SYNTAX Integer32
		
		MAX-ACCESS read-only
		STATUS current
		DESCRIPTION
		"mpduMpscom3516AStandard stored as 1."
		::= { mpduMpscomEntry 36 }
mpduMpscom37RatedCurrent OBJECT-TYPE
		SYNTAX Integer32
		
		MAX-ACCESS read-only
		STATUS current
		DESCRIPTION
		"mpduMpscom36RatedCurrent stored as 0.1A."
		::= { mpduMpscomEntry 37 }
mpduMpscom38ProductAddress OBJECT-TYPE
		SYNTAX Integer32
		
		MAX-ACCESS read-only
		STATUS current
		DESCRIPTION
		"mpduMpscom37ProductAddress stored as 1."
		::= { mpduMpscomEntry 38 }
mpduMpscom39Voltagedifference OBJECT-TYPE
		SYNTAX Integer32
		
		MAX-ACCESS read-only
		STATUS current
		DESCRIPTION
		"mpduMpscom38Voltagedifference stored as 0.1V."
		::= { mpduMpscomEntry 39 }
mpduMpscom40Currentdifference OBJECT-TYPE
		SYNTAX Integer32
		
		MAX-ACCESS read-only
		STATUS current
		DESCRIPTION
		"mpduMpscom39Currentdifference stored as 0.1A."
		::= { mpduMpscomEntry 40 }
mpduMpscom41LoadVoltageLowLimit OBJECT-TYPE
		SYNTAX INTEGER {
			normal(0),
			alarm(1) }
		MAX-ACCESS read-only
		STATUS current
		DESCRIPTION
		"mpduMpscom40LoadVoltageLowLimit status."
		::= { mpduMpscomEntry 41 }
mpduMpscom42LoadVoltageHighLimit OBJECT-TYPE
		SYNTAX INTEGER {
			normal(0),
			alarm(1) }
		MAX-ACCESS read-only
		STATUS current
		DESCRIPTION
		"mpduMpscom41LoadVoltageHighLimit status."
		::= { mpduMpscomEntry 42 }
mpduMpscom43LoadCurrentLowLimit OBJECT-TYPE
		SYNTAX INTEGER {
			normal(0),
			alarm(1) }
		MAX-ACCESS read-only
		STATUS current
		DESCRIPTION
		"mpduMpscom42LoadCurrentLowLimit status."
		::= { mpduMpscomEntry 43 }
mpduMpscom44LoadCurrentHighLimit OBJECT-TYPE
		SYNTAX INTEGER {
			normal(0),
			alarm(1) }
		MAX-ACCESS read-only
		STATUS current
		DESCRIPTION
		"mpduMpscom43LoadCurrentHighLimit status."
		::= { mpduMpscomEntry 44 }
mpduMpscom45Branch1LoadTotalCurrentLow OBJECT-TYPE
		SYNTAX INTEGER {
			normal(0),
			alarm(1) }
		MAX-ACCESS read-only
		STATUS current
		DESCRIPTION
		"mpduMpscom44Branch1LoadTotalCurrentLow status."
		::= { mpduMpscomEntry 45 }
mpduMpscom46Branch1LoadTotalCurrentHigh OBJECT-TYPE
		SYNTAX INTEGER {
			normal(0),
			alarm(1) }
		MAX-ACCESS read-only
		STATUS current
		DESCRIPTION
		"mpduMpscom45Branch1LoadTotalCurrentHigh status."
		::= { mpduMpscomEntry 46 }
mpduMpscom47Branch2LoadTotalCurrentLow OBJECT-TYPE
		SYNTAX INTEGER {
			normal(0),
			alarm(1) }
		MAX-ACCESS read-only
		STATUS current
		DESCRIPTION
		"mpduMpscom46Branch2LoadTotalCurrentLow status."
		::= { mpduMpscomEntry 47 }
mpduMpscom48Branch2LoadTotalCurrentHigh OBJECT-TYPE
		SYNTAX INTEGER {
			normal(0),
			alarm(1) }
		MAX-ACCESS read-only
		STATUS current
		DESCRIPTION
		"mpduMpscom47Branch2LoadTotalCurrentHigh status."
		::= { mpduMpscomEntry 48 }
mpduMpscom49Branch3LoadTotalCurrentLow OBJECT-TYPE
		SYNTAX INTEGER {
			normal(0),
			alarm(1) }
		MAX-ACCESS read-only
		STATUS current
		DESCRIPTION
		"mpduMpscom48Branch3LoadTotalCurrentLow status."
		::= { mpduMpscomEntry 49 }
mpduMpscom50Branch3LoadTotalCurrentHigh OBJECT-TYPE
		SYNTAX INTEGER {
			normal(0),
			alarm(1) }
		MAX-ACCESS read-only
		STATUS current
		DESCRIPTION
		"mpduMpscom49Branch3LoadTotalCurrentHigh status."
		::= { mpduMpscomEntry 50 }
mpduMpscom51CommunicateStatus OBJECT-TYPE
		SYNTAX INTEGER {
			normal(0),
			alarm(1) }
		MAX-ACCESS read-only
		STATUS current
		DESCRIPTION
		"mpduMpscom50CommunicateStatus status."
		::= { mpduMpscomEntry 51 }
mpduMpscom52Outlet1Status OBJECT-TYPE
		SYNTAX INTEGER {
			poweroff(0),
			poweron(1) }
		MAX-ACCESS read-write
		STATUS current
		DESCRIPTION
		"mpduMpscom51Outlet1Status status."
		::= { mpduMpscomEntry 52 }
mpduMpscom53Outlet2Status OBJECT-TYPE
		SYNTAX INTEGER {
			poweroff(0),
			poweron(1) }
		MAX-ACCESS read-write
		STATUS current
		DESCRIPTION
		"mpduMpscom52Outlet2Status status."
		::= { mpduMpscomEntry 53 }
mpduMpscom54Outlet3Status OBJECT-TYPE
		SYNTAX INTEGER {
			poweroff(0),
			poweron(1) }
		MAX-ACCESS read-write
		STATUS current
		DESCRIPTION
		"mpduMpscom53Outlet3Status status."
		::= { mpduMpscomEntry 54 }
mpduMpscom55Outlet4Status OBJECT-TYPE
		SYNTAX INTEGER {
			poweroff(0),
			poweron(1) }
		MAX-ACCESS read-write
		STATUS current
		DESCRIPTION
		"mpduMpscom54Outlet4Status status."
		::= { mpduMpscomEntry 55 }
mpduMpscom56Outlet5Status OBJECT-TYPE
		SYNTAX INTEGER {
			poweroff(0),
			poweron(1) }
		MAX-ACCESS read-write
		STATUS current
		DESCRIPTION
		"mpduMpscom55Outlet5Status status."
		::= { mpduMpscomEntry 56 }
mpduMpscom57Outlet6Status OBJECT-TYPE
		SYNTAX INTEGER {
			poweroff(0),
			poweron(1) }
		MAX-ACCESS read-write
		STATUS current
		DESCRIPTION
		"mpduMpscom56Outlet6Status status."
		::= { mpduMpscomEntry 57 }
mpduMpscom58Outlet7Status OBJECT-TYPE
		SYNTAX INTEGER {
			poweroff(0),
			poweron(1) }
		MAX-ACCESS read-write
		STATUS current
		DESCRIPTION
		"mpduMpscom57Outlet7Status status."
		::= { mpduMpscomEntry 58 }
mpduMpscom59Outlet8Status OBJECT-TYPE
		SYNTAX INTEGER {
			poweroff(0),
			poweron(1) }
		MAX-ACCESS read-write
		STATUS current
		DESCRIPTION
		"mpduMpscom58Outlet8Status status."
		::= { mpduMpscomEntry 59 }
mpduMpscom60Outlet9Status OBJECT-TYPE
		SYNTAX INTEGER {
			poweroff(0),
			poweron(1) }
		MAX-ACCESS read-write
		STATUS current
		DESCRIPTION
		"mpduMpscom59Outlet9Status status."
		::= { mpduMpscomEntry 60 }
mpduMpscom61Outlet10Status OBJECT-TYPE
		SYNTAX INTEGER {
			poweroff(0),
			poweron(1) }
		MAX-ACCESS read-write
		STATUS current
		DESCRIPTION
		"mpduMpscom60Outlet10Status status."
		::= { mpduMpscomEntry 61 }
mpduMpscom62Outlet11Status OBJECT-TYPE
		SYNTAX INTEGER {
			poweroff(0),
			poweron(1) }
		MAX-ACCESS read-write
		STATUS current
		DESCRIPTION
		"mpduMpscom61Outlet11Status status."
		::= { mpduMpscomEntry 62 }
mpduMpscom63Outlet12Status OBJECT-TYPE
		SYNTAX INTEGER {
			poweroff(0),
			poweron(1) }
		MAX-ACCESS read-write
		STATUS current
		DESCRIPTION
		"mpduMpscom62Outlet12Status status."
		::= { mpduMpscomEntry 63 }
mpduMpscom64Outlet13Status OBJECT-TYPE
		SYNTAX INTEGER {
			poweroff(0),
			poweron(1) }
		MAX-ACCESS read-write
		STATUS current
		DESCRIPTION
		"mpduMpscom63Outlet13Status status."
		::= { mpduMpscomEntry 64 }
mpduMpscom65Outlet14Status OBJECT-TYPE
		SYNTAX INTEGER {
			poweroff(0),
			poweron(1) }
		MAX-ACCESS read-write
		STATUS current
		DESCRIPTION
		"mpduMpscom64Outlet14Status status."
		::= { mpduMpscomEntry 65 }
mpduMpscom66Outlet15Status OBJECT-TYPE
		SYNTAX INTEGER {
			poweroff(0),
			poweron(1) }
		MAX-ACCESS read-write
		STATUS current
		DESCRIPTION
		"mpduMpscom65Outlet15Status status."
		::= { mpduMpscomEntry 66 }
mpduMpscom67Outlet16Status OBJECT-TYPE
		SYNTAX INTEGER {
			poweroff(0),
			poweron(1) }
		MAX-ACCESS read-write
		STATUS current
		DESCRIPTION
		"mpduMpscom66Outlet16Status status."
		::= { mpduMpscomEntry 67 }
mpduMpscom68Outlet17Status OBJECT-TYPE
		SYNTAX INTEGER {
			poweroff(0),
			poweron(1) }
		MAX-ACCESS read-write
		STATUS current
		DESCRIPTION
		"mpduMpscom67Outlet17Status status."
		::= { mpduMpscomEntry 68 }
mpduMpscom69Outlet18Status OBJECT-TYPE
		SYNTAX INTEGER {
			poweroff(0),
			poweron(1) }
		MAX-ACCESS read-write
		STATUS current
		DESCRIPTION
		"mpduMpscom68Outlet18Status status."
		::= { mpduMpscomEntry 69 }
mpduMpscom70Outlet19Status OBJECT-TYPE
		SYNTAX INTEGER {
			poweroff(0),
			poweron(1) }
		MAX-ACCESS read-write
		STATUS current
		DESCRIPTION
		"mpduMpscom69Outlet19Status status."
		::= { mpduMpscomEntry 70 }
mpduMpscom71Outlet20Status OBJECT-TYPE
		SYNTAX INTEGER {
			poweroff(0),
			poweron(1) }
		MAX-ACCESS read-write
		STATUS current
		DESCRIPTION
		"mpduMpscom70Outlet20Status status."
		::= { mpduMpscomEntry 71 }
mpduMpscom72Outlet21Status OBJECT-TYPE
		SYNTAX INTEGER {
			poweroff(0),
			poweron(1) }
		MAX-ACCESS read-write
		STATUS current
		DESCRIPTION
		"mpduMpscom71Outlet21Status status."
		::= { mpduMpscomEntry 72 }
mpduMpscom73Outlet22Status OBJECT-TYPE
		SYNTAX INTEGER {
			poweroff(0),
			poweron(1) }
		MAX-ACCESS read-write
		STATUS current
		DESCRIPTION
		"mpduMpscom72Outlet22Status status."
		::= { mpduMpscomEntry 73 }
mpduMpscom74Outlet23Status OBJECT-TYPE
		SYNTAX INTEGER {
			poweroff(0),
			poweron(1) }
		MAX-ACCESS read-write
		STATUS current
		DESCRIPTION
		"mpduMpscom73Outlet23Status status."
		::= { mpduMpscomEntry 74 }
mpduMpscom75Outlet24Status OBJECT-TYPE
		SYNTAX INTEGER {
			poweroff(0),
			poweron(1) }
		MAX-ACCESS read-write
		STATUS current
		DESCRIPTION
		"mpduMpscom74Outlet24Status status."
		::= { mpduMpscomEntry 75 }
mpduMpscom76LoadVoltageLowLimit OBJECT-TYPE
		SYNTAX Integer32
		
		MAX-ACCESS read-write
		STATUS current
		DESCRIPTION
		"mpduMpscom75LoadVoltageLowLimit stored as 1V."
		::= { mpduMpscomEntry 76 }
mpduMpscom77LoadVoltageHighLimit OBJECT-TYPE
		SYNTAX Integer32
		
		MAX-ACCESS read-write
		STATUS current
		DESCRIPTION
		"mpduMpscom76LoadVoltageHighLimit stored as 1V."
		::= { mpduMpscomEntry 77 }
mpduMpscom78LoadCurrentLowLimit OBJECT-TYPE
		SYNTAX Integer32
		
		MAX-ACCESS read-write
		STATUS current
		DESCRIPTION
		"mpduMpscom77LoadCurrentLowLimit stored as 1A."
		::= { mpduMpscomEntry 78 }
mpduMpscom79LoadCurrentHighLimit OBJECT-TYPE
		SYNTAX Integer32
		
		MAX-ACCESS read-write
		STATUS current
		DESCRIPTION
		"mpduMpscom78LoadCurrentHighLimit stored as 1A."
		::= { mpduMpscomEntry 79 }
mpduMpscom80Branch1LoadTotalCurrentLow OBJECT-TYPE
		SYNTAX Integer32
		
		MAX-ACCESS read-write
		STATUS current
		DESCRIPTION
		"mpduMpscom79Branch1LoadTotalCurrentLow stored as 1A."
		::= { mpduMpscomEntry 80 }
mpduMpscom81Branch1LoadTotalCurrentHigh OBJECT-TYPE
		SYNTAX Integer32
		
		MAX-ACCESS read-write
		STATUS current
		DESCRIPTION
		"mpduMpscom80Branch1LoadTotalCurrentHigh stored as 1A."
		::= { mpduMpscomEntry 81 }
mpduMpscom82Branch2LoadTotalCurrentLow OBJECT-TYPE
		SYNTAX Integer32
		
		MAX-ACCESS read-write
		STATUS current
		DESCRIPTION
		"mpduMpscom81Branch2LoadTotalCurrentLow stored as 1A."
		::= { mpduMpscomEntry 82 }
mpduMpscom83Branch2LoadTotalCurrentHigh OBJECT-TYPE
		SYNTAX Integer32
		
		MAX-ACCESS read-write
		STATUS current
		DESCRIPTION
		"mpduMpscom82Branch2LoadTotalCurrentHigh stored as 1A."
		::= { mpduMpscomEntry 83 }
mpduMpscom84Branch3LoadTotalCurrentLow OBJECT-TYPE
		SYNTAX Integer32
		
		MAX-ACCESS read-write
		STATUS current
		DESCRIPTION
		"mpduMpscom83Branch3LoadTotalCurrentLow stored as 1A."
		::= { mpduMpscomEntry 84 }
mpduMpscom85Branch3LoadTotalCurrentHigh OBJECT-TYPE
		SYNTAX Integer32
		
		MAX-ACCESS read-write
		STATUS current
		DESCRIPTION
		"mpduMpscom84Branch3LoadTotalCurrentHigh stored as 1A."
		::= { mpduMpscomEntry 85 }
mpduMpscom86Outlet1DelayTime OBJECT-TYPE
		SYNTAX Integer32
		
		MAX-ACCESS read-write
		STATUS current
		DESCRIPTION
		"mpduMpscom85Outlet1DelayTime stored as 1s."
		::= { mpduMpscomEntry 86 }
mpduMpscom87Outlet2DelayTime OBJECT-TYPE
		SYNTAX Integer32
		
		MAX-ACCESS read-write
		STATUS current
		DESCRIPTION
		"mpduMpscom86Outlet2DelayTime stored as 1s."
		::= { mpduMpscomEntry 87 }
mpduMpscom88Outlet3DelayTime OBJECT-TYPE
		SYNTAX Integer32
		
		MAX-ACCESS read-write
		STATUS current
		DESCRIPTION
		"mpduMpscom87Outlet3DelayTime stored as 1s."
		::= { mpduMpscomEntry 88 }
mpduMpscom89Outlet4DelayTime OBJECT-TYPE
		SYNTAX Integer32
		
		MAX-ACCESS read-write
		STATUS current
		DESCRIPTION
		"mpduMpscom88Outlet4DelayTime stored as 1s."
		::= { mpduMpscomEntry 89 }
mpduMpscom90Outlet5DelayTime OBJECT-TYPE
		SYNTAX Integer32
		
		MAX-ACCESS read-write
		STATUS current
		DESCRIPTION
		"mpduMpscom89Outlet5DelayTime stored as 1s."
		::= { mpduMpscomEntry 90 }
mpduMpscom91Outlet6DelayTime OBJECT-TYPE
		SYNTAX Integer32
		
		MAX-ACCESS read-write
		STATUS current
		DESCRIPTION
		"mpduMpscom90Outlet6DelayTime stored as 1s."
		::= { mpduMpscomEntry 91 }
mpduMpscom92Outlet7DelayTime OBJECT-TYPE
		SYNTAX Integer32
		
		MAX-ACCESS read-write
		STATUS current
		DESCRIPTION
		"mpduMpscom91Outlet7DelayTime stored as 1s."
		::= { mpduMpscomEntry 92 }
mpduMpscom93Outlet8DelayTime OBJECT-TYPE
		SYNTAX Integer32
		
		MAX-ACCESS read-write
		STATUS current
		DESCRIPTION
		"mpduMpscom92Outlet8DelayTime stored as 1s."
		::= { mpduMpscomEntry 93 }
mpduMpscom94Outlet9DelayTime OBJECT-TYPE
		SYNTAX Integer32
		
		MAX-ACCESS read-write
		STATUS current
		DESCRIPTION
		"mpduMpscom93Outlet9DelayTime stored as 1s."
		::= { mpduMpscomEntry 94 }
mpduMpscom95Outlet10DelayTime OBJECT-TYPE
		SYNTAX Integer32
		
		MAX-ACCESS read-write
		STATUS current
		DESCRIPTION
		"mpduMpscom94Outlet10DelayTime stored as 1s."
		::= { mpduMpscomEntry 95 }
mpduMpscom96Outlet11DelayTime OBJECT-TYPE
		SYNTAX Integer32
		
		MAX-ACCESS read-write
		STATUS current
		DESCRIPTION
		"mpduMpscom95Outlet11DelayTime stored as 1s."
		::= { mpduMpscomEntry 96 }
mpduMpscom97Outlet12DelayTime OBJECT-TYPE
		SYNTAX Integer32
		
		MAX-ACCESS read-write
		STATUS current
		DESCRIPTION
		"mpduMpscom96Outlet12DelayTime stored as 1s."
		::= { mpduMpscomEntry 97 }
mpduMpscom98Outlet13DelayTime OBJECT-TYPE
		SYNTAX Integer32
		
		MAX-ACCESS read-write
		STATUS current
		DESCRIPTION
		"mpduMpscom97Outlet13DelayTime stored as 1s."
		::= { mpduMpscomEntry 98 }
mpduMpscom99Outlet14DelayTime OBJECT-TYPE
		SYNTAX Integer32
		
		MAX-ACCESS read-write
		STATUS current
		DESCRIPTION
		"mpduMpscom98Outlet14DelayTime stored as 1s."
		::= { mpduMpscomEntry 99 }
mpduMpscom100Outlet15DelayTime OBJECT-TYPE
		SYNTAX Integer32
		
		MAX-ACCESS read-write
		STATUS current
		DESCRIPTION
		"mpduMpscom99Outlet15DelayTime stored as 1s."
		::= { mpduMpscomEntry 100 }
mpduMpscom101Outlet16DelayTime OBJECT-TYPE
		SYNTAX Integer32
		
		MAX-ACCESS read-write
		STATUS current
		DESCRIPTION
		"mpduMpscom100Outlet16DelayTime stored as 1s."
		::= { mpduMpscomEntry 101 }
mpduMpscom102Outlet17DelayTime OBJECT-TYPE
		SYNTAX Integer32
		
		MAX-ACCESS read-write
		STATUS current
		DESCRIPTION
		"mpduMpscom101Outlet17DelayTime stored as 1s."
		::= { mpduMpscomEntry 102 }
mpduMpscom103Outlet18DelayTime OBJECT-TYPE
		SYNTAX Integer32
		
		MAX-ACCESS read-write
		STATUS current
		DESCRIPTION
		"mpduMpscom102Outlet18DelayTime stored as 1s."
		::= { mpduMpscomEntry 103 }
mpduMpscom104Outlet19DelayTime OBJECT-TYPE
		SYNTAX Integer32
		
		MAX-ACCESS read-write
		STATUS current
		DESCRIPTION
		"mpduMpscom103Outlet19DelayTime stored as 1s."
		::= { mpduMpscomEntry 104 }
mpduMpscom105Outlet20DelayTime OBJECT-TYPE
		SYNTAX Integer32
		
		MAX-ACCESS read-write
		STATUS current
		DESCRIPTION
		"mpduMpscom104Outlet20DelayTime stored as 1s."
		::= { mpduMpscomEntry 105 }
mpduMpscom106Outlet21DelayTime OBJECT-TYPE
		SYNTAX Integer32
		
		MAX-ACCESS read-write
		STATUS current
		DESCRIPTION
		"mpduMpscom105Outlet21DelayTime stored as 1s."
		::= { mpduMpscomEntry 106 }
mpduMpscom107Outlet22DelayTime OBJECT-TYPE
		SYNTAX Integer32
		
		MAX-ACCESS read-write
		STATUS current
		DESCRIPTION
		"mpduMpscom106Outlet22DelayTime stored as 1s."
		::= { mpduMpscomEntry 107 }
mpduMpscom108Outlet23DelayTime OBJECT-TYPE
		SYNTAX Integer32
		
		MAX-ACCESS read-write
		STATUS current
		DESCRIPTION
		"mpduMpscom107Outlet23DelayTime stored as 1s."
		::= { mpduMpscomEntry 108 }
mpduMpscom109Outlet24DelayTime OBJECT-TYPE
		SYNTAX Integer32
		
		MAX-ACCESS read-write
		STATUS current
		DESCRIPTION
		"mpduMpscom108Outlet24DelayTime stored as 1s."
		::= { mpduMpscomEntry 109 }
mpduMpscom110PDUPORTNUM OBJECT-TYPE
		SYNTAX Integer32
		
		MAX-ACCESS read-only
		STATUS current
		DESCRIPTION
		"mpduMpscom109PDUPORTNUM stored as 1."
		::= { mpduMpscomEntry 110 }

------------------------------------------------------------
-- Acdu { 13400.3.3 }
------------------------------------------------------------
ac OBJECT IDENTIFIER ::=  { dcs 3 }


------------------------------------------------------------
-- Ou { 13400.3.3.3031 }
------------------------------------------------------------
ac-Ou OBJECT IDENTIFIER ::= { ac 3031 }
acOuTable OBJECT-TYPE
		SYNTAX			SEQUENCE OF AcOuEntry
		MAX-ACCESS		not-accessible
		STATUS			current
		DESCRIPTION	"acOuTable"
		::=			{ ac-Ou 1 }
acOuEntry OBJECT-TYPE
		SYNTAX			AcOuEntry
		MAX-ACCESS		not-accessible
		STATUS			current
		DESCRIPTION		"acOuEntry"
		INDEX			{ acOuIndex }
		::=				{ acOuTable 1 }
AcOuEntry ::= SEQUENCE {
		acOuIndex					Integer32,
		acOu2Highwaterlevelswitch					INTEGER,
		acOu3Lowvoltageswitch					INTEGER,
		acOu4Remoteswitch					INTEGER,
		acOu5Compressoroutput					INTEGER,
		acOu6Fanoutput					INTEGER,
		acOu7Commonalarmoutput					INTEGER,
		acOu8Bypasssolenoidvalveoutput					INTEGER,
		acOu9HighPressure					INTEGER,
		acOu10LowPressure					INTEGER,
		acOu11Exhausttemperaturealarm					INTEGER,
		acOu12Returnairhightempalarm					INTEGER,
		acOu13supplyairLowtempalarm					INTEGER,
		acOu14supplyairhightempalarm					INTEGER,
		acOu15Frequenthighpressurealarm					INTEGER,
		acOu16Lowpressurefrequentalarm					INTEGER,
		acOu17Frequenthightempexhaustalar					INTEGER,
		acOu18Powerlossalarm					INTEGER,
		acOu19Powerovervoltagealarm					INTEGER,
		acOu20Powerundervoltagealarm					INTEGER,
		acOu21Highwaterlevelalarm					INTEGER,
		acOu22FilterServiceRequired					INTEGER,
		acOu23RemoteShutdownAlarm					INTEGER,
		acOu24Returnairtempsensorfault					INTEGER,
		acOu25Supplyairtempsensorfault					INTEGER,
		acOu26Highpressuresensorfault					INTEGER,
		acOu27Newalarmflag					INTEGER,
		acOu28PanelOff					INTEGER,
		acOu29Monitorshutdown					INTEGER,
		acOu30Remoteshutdownflag					INTEGER,
		acOu31Remoteswitchinputpolarity					INTEGER,
		acOu32Publicalarmoutputpolarity					INTEGER,
		acOu33Refrigeration					INTEGER,
		acOu34Exhaustgastempsensorfault					INTEGER,
		acOu35EEVcommunicationfailure					INTEGER,
		acOu36Intakeairtemperaturesensorf					INTEGER,
		acOu37Lowpressuresensorfault					INTEGER,
		acOu38Compressordrivecommunication					INTEGER,
		acOu39Module2overtemperature					INTEGER,
		acOu40Busovervoltage					INTEGER,
		acOu41Tempsensor1isfaulty					INTEGER,
		acOu42Tempsensor2isfaulty					INTEGER,
		acOu43Shortcircuit					INTEGER,
		acOu44FrequencyShift					INTEGER,
		acOu45Module1overtemperature					INTEGER,
		acOu46CompressordriveprotectionU04					INTEGER,
		acOu47CompressordriveprotectionU13					INTEGER,
		acOu48CompressordriveprotectionU14					INTEGER,
		acOu49CompressordriveprotectionU11					INTEGER,
		acOu50CompressordriveprotectionU08					INTEGER,
		acOu51CompressordriveprotectionU09					INTEGER,
		acOu52CompressordriveprotectionU10					INTEGER,
		acOu53CompressordriveprotectionU12					INTEGER,
		acOu54CompressordriveprotectionU15					INTEGER,
		acOu55CompressordriveprotectionU06					INTEGER,
		acOu56Supplyairtemperature					Integer32,
		acOu57Returnairtemperature					Integer32,
		acOu58Outsidetemperature					Integer32,
		acOu59Exhausttemperature					Integer32,
		acOu60Inspiratorytemperature					Integer32,
		acOu61Exhaustpressure					Integer32,
		acOu62Inspiratorypressure					Integer32,
		acOu63Monitoraddress					Integer32,
		acOu64Powervoltage					Integer32,
		acOu65Powerfrequency					Integer32,
		acOu66Inspiratorysuperheat					Integer32,
		acOu67Thenumberofalarmstates					Integer32,
		acOu68Numberofalarmhistory					Integer32,
		acOu69Compressorstartandstoprecor					Integer32,
		acOu70Fanstartandstoprecordnumbe					Integer32,
		acOu71Compressorhoursofoperationr					Integer32,
		acOu72CommunicateStatus					INTEGER,
		acOu73Highsoftwareversion					Integer32,
		acOu74Softwareversionlow					Integer32,
		acOu75Airconditioningrunningstatus					INTEGER,
		acOu76Compressorcapacityactualvalu					Integer32,
		acOu77Fanspeed					Integer32,
		acOu78Expansionvalveopening					Integer32,
		acOu79Highpressureabnormalrecordn					Integer32,
		acOu80Controlmode					Integer32,
		acOu81Compressortemperatureintegrat					Integer32,
		acOu82Compressortemperaturedifferen					Integer32,
		acOu83Fantemperatureintegrationtim					Integer32,
		acOu84Fantemperaturedifferentialti					Integer32,
		acOu85Modelselection					Integer32,
		acOu86Returntoruntime					Integer32,
		acOu87Returnoilcapacity					Integer32,
		acOu88Compressorhoppingpoint1					Integer32,
		acOu89Compressorhoppingpoint1band					Integer32,
		acOu90Compressorhoppingpoint2					Integer32,
		acOu91Compressorhoppingpoint2band					Integer32,
		acOu92Compressorhoppingpoint3					Integer32,
		acOu93Compressorhoppingpoint3band					Integer32,
		acOu94Compressorhoppingpoint4					Integer32,
		acOu95Compressorhoppingpoint4band					Integer32,
		acOu96Compressorhoppingpoint5					Integer32,
		acOu97Compressorhoppingpoint5band					Integer32,
		acOu98Indoorfanfrequencyhoppingpo					Integer32,
		acOu99Indoorfanfrequencyhoppingpo					Integer32,
		acOu100Indoorfanfrequencyhoppingpo					Integer32,
		acOu101Indoorfanfrequencyhoppingpo					Integer32,
		acOu102Indoorfanfrequencyhoppingpo					Integer32,
		acOu103Indoorfanfrequencyhoppingpo					Integer32,
		acOu104Indoorfanfrequencyhoppingpo					Integer32,
		acOu105Indoorfanfrequencyhoppingpo					Integer32,
		acOu106Indoorfanfrequencyhoppingpo					Integer32,
		acOu107Indoorfanfrequencyhoppingpo					Integer32,
		acOu108Indoorfanfrequencyhoppingpo					Integer32,
		acOu109Indoorfanfrequencyhoppingpo					Integer32,
		acOu110reset					INTEGER,
		acOu111Filtermaintenance					INTEGER,
		acOu112RemoteOn					INTEGER,
		acOu113RemoteOff					INTEGER,
		acOu114RemoteOff					INTEGER,
		acOu115Supplyairtempcorrectionvalu					Integer32,
		acOu116Returnairtempecorrectionval					Integer32,
		acOu117Exhausttempcorrectionvalue					Integer32,
		acOu118Exhaustpressurecorrectionval					Integer32,
		acOu119Suctionpressurecorrectionval					Integer32,
		acOu120Monitoraddress					Integer32,
		acOu121Compressorshortestrunningtim					Integer32,
		acOu122Minimumcompressordowntime					Integer32,
		acOu123Fanstartdelay					Integer32,
		acOu124Fanstopdelay					Integer32,
		acOu125Deadzonetemperature					Integer32,
		acOu126Returnairtempsetting					Integer32,
		acOu127Compressorcapacityoutputvalu					Integer32,
		acOu128Lowpressurealarmdelay					Integer32,
		acOu129Filtermaintenanceremindertim					Integer32,
		acOu130Highpressurealarmvalue					Integer32,
		acOu131Supplyairtemperaturealarmva					Integer32,
		acOu132Supplyairtemperaturealarmva					Integer32,
		acOu133Returnairtemperaturealarmva					Integer32,
		acOu134Powerovervoltagealarmpoint					Integer32,
		acOu135Powerundervoltagealarmpoint					Integer32,
		acOu136Compressortemperatureproporti					Integer32,
		acOu137Fantemperatureproportionalba					Integer32,
		acOu138Compressorstartuprequirements					Integer32,
		acOu139Compressorstopdemand					Integer32,
		acOu140Compressorminimumcapacity					Integer32,
		acOu141Compressorstandardcapacity					Integer32,
		acOu142Compressorstartupcapacity					Integer32,
		acOu143Compressoroutputdeadzone					Integer32,
		acOu144Returncycle					Integer32,
		acOu145Minimumfanspeed					Integer32,
		acOu146Fanstandardspeed					Integer32,
		acOu147MinimumfanspeedCFC					Integer32,
		acOu148FanstandardspeedCFC					Integer32,
		acOu149Lowspeedfanstep					Integer32,
		acOu150Highspeedfanstep					Integer32,
		acOu151Fandecelerationdelay					Integer32,
		acOu152EEVsuperheatsettingMAX					Integer32,
		acOu153EEVsuperheatsettingMIN					Integer32,
		acOu154EEVMOPpressurelimit					Integer32,
		acOu155EEVvalvebodyshutoffsuperhe					Integer32,
		acOu156Outdoorfanminimumsupplyvolt					Integer32,
		acOu157Outdoorfanmaximumsupplyvolt					Integer32,
		acOu158Outdoorfanpressurecontrolra					Integer32,
		acOu159Outdoorfanstartpressure					Integer32,
		acOu160Outdoorfanstartpressure					Integer32 }
acOuIndex OBJECT-TYPE
		SYNTAX Integer32(1..160)
		MAX-ACCESS read-only
		STATUS current
		DESCRIPTION
		"acOu System Entry Index."
		::= { acOuEntry 1 }
acOu2Highwaterlevelswitch OBJECT-TYPE
		SYNTAX INTEGER {
			shutdown(0),
			open(1) }
		MAX-ACCESS read-only
		STATUS current
		DESCRIPTION
		"acOu1Highwaterlevelswitch status."
		::= { acOuEntry 2 }
acOu3Lowvoltageswitch OBJECT-TYPE
		SYNTAX INTEGER {
			shutdown(0),
			open(1) }
		MAX-ACCESS read-only
		STATUS current
		DESCRIPTION
		"acOu2Lowvoltageswitch status."
		::= { acOuEntry 3 }
acOu4Remoteswitch OBJECT-TYPE
		SYNTAX INTEGER {
			shutdown(0),
			open(1) }
		MAX-ACCESS read-only
		STATUS current
		DESCRIPTION
		"acOu3Remoteswitch status."
		::= { acOuEntry 4 }
acOu5Compressoroutput OBJECT-TYPE
		SYNTAX INTEGER {
			no(0),
			yes(1) }
		MAX-ACCESS read-only
		STATUS current
		DESCRIPTION
		"acOu4Compressoroutput status."
		::= { acOuEntry 5 }
acOu6Fanoutput OBJECT-TYPE
		SYNTAX INTEGER {
			yes(0),
			no(1) }
		MAX-ACCESS read-only
		STATUS current
		DESCRIPTION
		"acOu5Fanoutput status."
		::= { acOuEntry 6 }
acOu7Commonalarmoutput OBJECT-TYPE
		SYNTAX INTEGER {
			no(0),
			yes(1) }
		MAX-ACCESS read-only
		STATUS current
		DESCRIPTION
		"acOu6Commonalarmoutput status."
		::= { acOuEntry 7 }
acOu8Bypasssolenoidvalveoutput OBJECT-TYPE
		SYNTAX INTEGER {
			no(0),
			yes(1) }
		MAX-ACCESS read-only
		STATUS current
		DESCRIPTION
		"acOu7Bypasssolenoidvalveoutput status."
		::= { acOuEntry 8 }
acOu9HighPressure OBJECT-TYPE
		SYNTAX INTEGER {
			normal(0),
			alarm(1) }
		MAX-ACCESS read-only
		STATUS current
		DESCRIPTION
		"acOu8HighPressure status."
		::= { acOuEntry 9 }
acOu10LowPressure OBJECT-TYPE
		SYNTAX INTEGER {
			normal(0),
			alarm(1) }
		MAX-ACCESS read-only
		STATUS current
		DESCRIPTION
		"acOu9LowPressure status."
		::= { acOuEntry 10 }
acOu11Exhausttemperaturealarm OBJECT-TYPE
		SYNTAX INTEGER {
			normal(0),
			alarm(1) }
		MAX-ACCESS read-only
		STATUS current
		DESCRIPTION
		"acOu10Exhausttemperaturealarm status."
		::= { acOuEntry 11 }
acOu12Returnairhightempalarm OBJECT-TYPE
		SYNTAX INTEGER {
			normal(0),
			alarm(1) }
		MAX-ACCESS read-only
		STATUS current
		DESCRIPTION
		"acOu11Returnairhightempalarm status."
		::= { acOuEntry 12 }
acOu13supplyairLowtempalarm OBJECT-TYPE
		SYNTAX INTEGER {
			normal(0),
			alarm(1) }
		MAX-ACCESS read-only
		STATUS current
		DESCRIPTION
		"acOu12supplyairLowtempalarm status."
		::= { acOuEntry 13 }
acOu14supplyairhightempalarm OBJECT-TYPE
		SYNTAX INTEGER {
			normal(0),
			alarm(1) }
		MAX-ACCESS read-only
		STATUS current
		DESCRIPTION
		"acOu13supplyairhightempalarm status."
		::= { acOuEntry 14 }
acOu15Frequenthighpressurealarm OBJECT-TYPE
		SYNTAX INTEGER {
			normal(0),
			alarm(1) }
		MAX-ACCESS read-only
		STATUS current
		DESCRIPTION
		"acOu14Frequenthighpressurealarm status."
		::= { acOuEntry 15 }
acOu16Lowpressurefrequentalarm OBJECT-TYPE
		SYNTAX INTEGER {
			normal(0),
			alarm(1) }
		MAX-ACCESS read-only
		STATUS current
		DESCRIPTION
		"acOu15Lowpressurefrequentalarm status."
		::= { acOuEntry 16 }
acOu17Frequenthightempexhaustalar OBJECT-TYPE
		SYNTAX INTEGER {
			normal(0),
			alarm(1) }
		MAX-ACCESS read-only
		STATUS current
		DESCRIPTION
		"acOu16Frequenthightempexhaustalar status."
		::= { acOuEntry 17 }
acOu18Powerlossalarm OBJECT-TYPE
		SYNTAX INTEGER {
			normal(0),
			alarm(1) }
		MAX-ACCESS read-only
		STATUS current
		DESCRIPTION
		"acOu17Powerlossalarm status."
		::= { acOuEntry 18 }
acOu19Powerovervoltagealarm OBJECT-TYPE
		SYNTAX INTEGER {
			normal(0),
			alarm(1) }
		MAX-ACCESS read-only
		STATUS current
		DESCRIPTION
		"acOu18Powerovervoltagealarm status."
		::= { acOuEntry 19 }
acOu20Powerundervoltagealarm OBJECT-TYPE
		SYNTAX INTEGER {
			normal(0),
			alarm(1) }
		MAX-ACCESS read-only
		STATUS current
		DESCRIPTION
		"acOu19Powerundervoltagealarm status."
		::= { acOuEntry 20 }
acOu21Highwaterlevelalarm OBJECT-TYPE
		SYNTAX INTEGER {
			normal(0),
			alarm(1) }
		MAX-ACCESS read-only
		STATUS current
		DESCRIPTION
		"acOu20Highwaterlevelalarm status."
		::= { acOuEntry 21 }
acOu22FilterServiceRequired OBJECT-TYPE
		SYNTAX INTEGER {
			normal(0),
			alarm(1) }
		MAX-ACCESS read-only
		STATUS current
		DESCRIPTION
		"acOu21FilterServiceRequired status."
		::= { acOuEntry 22 }
acOu23RemoteShutdownAlarm OBJECT-TYPE
		SYNTAX INTEGER {
			normal(0),
			alarm(1) }
		MAX-ACCESS read-only
		STATUS current
		DESCRIPTION
		"acOu22RemoteShutdownAlarm status."
		::= { acOuEntry 23 }
acOu24Returnairtempsensorfault OBJECT-TYPE
		SYNTAX INTEGER {
			normal(0),
			alarm(1) }
		MAX-ACCESS read-only
		STATUS current
		DESCRIPTION
		"acOu23Returnairtempsensorfault status."
		::= { acOuEntry 24 }
acOu25Supplyairtempsensorfault OBJECT-TYPE
		SYNTAX INTEGER {
			normal(0),
			alarm(1) }
		MAX-ACCESS read-only
		STATUS current
		DESCRIPTION
		"acOu24Supplyairtempsensorfault status."
		::= { acOuEntry 25 }
acOu26Highpressuresensorfault OBJECT-TYPE
		SYNTAX INTEGER {
			normal(0),
			alarm(1) }
		MAX-ACCESS read-only
		STATUS current
		DESCRIPTION
		"acOu25Highpressuresensorfault status."
		::= { acOuEntry 26 }
acOu27Newalarmflag OBJECT-TYPE
		SYNTAX INTEGER {
			no(0),
			yes(1) }
		MAX-ACCESS read-only
		STATUS current
		DESCRIPTION
		"acOu26Newalarmflag status."
		::= { acOuEntry 27 }
acOu28PanelOff OBJECT-TYPE
		SYNTAX INTEGER {
			no(0),
			yes(1) }
		MAX-ACCESS read-only
		STATUS current
		DESCRIPTION
		"acOu27PanelOff status."
		::= { acOuEntry 28 }
acOu29Monitorshutdown OBJECT-TYPE
		SYNTAX INTEGER {
			no(0),
			yes(1) }
		MAX-ACCESS read-only
		STATUS current
		DESCRIPTION
		"acOu28Monitorshutdown status."
		::= { acOuEntry 29 }
acOu30Remoteshutdownflag OBJECT-TYPE
		SYNTAX INTEGER {
			no(0),
			yes(1) }
		MAX-ACCESS read-only
		STATUS current
		DESCRIPTION
		"acOu29Remoteshutdownflag status."
		::= { acOuEntry 30 }
acOu31Remoteswitchinputpolarity OBJECT-TYPE
		SYNTAX INTEGER {
			normallyclosed(0),
			normallyopen(1) }
		MAX-ACCESS read-only
		STATUS current
		DESCRIPTION
		"acOu30Remoteswitchinputpolarity status."
		::= { acOuEntry 31 }
acOu32Publicalarmoutputpolarity OBJECT-TYPE
		SYNTAX INTEGER {
			normallyclosed(0),
			normallyopen(1) }
		MAX-ACCESS read-only
		STATUS current
		DESCRIPTION
		"acOu31Publicalarmoutputpolarity status."
		::= { acOuEntry 32 }
acOu33Refrigeration OBJECT-TYPE
		SYNTAX INTEGER {
			yes(0),
			no(1) }
		MAX-ACCESS read-only
		STATUS current
		DESCRIPTION
		"acOu32Refrigeration status."
		::= { acOuEntry 33 }
acOu34Exhaustgastempsensorfault OBJECT-TYPE
		SYNTAX INTEGER {
			normal(0),
			alarm(1) }
		MAX-ACCESS read-only
		STATUS current
		DESCRIPTION
		"acOu33Exhaustgastempsensorfault status."
		::= { acOuEntry 34 }
acOu35EEVcommunicationfailure OBJECT-TYPE
		SYNTAX INTEGER {
			normal(0),
			alarm(1) }
		MAX-ACCESS read-only
		STATUS current
		DESCRIPTION
		"acOu34EEVcommunicationfailure status."
		::= { acOuEntry 35 }
acOu36Intakeairtemperaturesensorf OBJECT-TYPE
		SYNTAX INTEGER {
			normal(0),
			alarm(1) }
		MAX-ACCESS read-only
		STATUS current
		DESCRIPTION
		"acOu35Intakeairtemperaturesensorf status."
		::= { acOuEntry 36 }
acOu37Lowpressuresensorfault OBJECT-TYPE
		SYNTAX INTEGER {
			normal(0),
			alarm(1) }
		MAX-ACCESS read-only
		STATUS current
		DESCRIPTION
		"acOu36Lowpressuresensorfault status."
		::= { acOuEntry 37 }
acOu38Compressordrivecommunication OBJECT-TYPE
		SYNTAX INTEGER {
			normal(0),
			alarm(1) }
		MAX-ACCESS read-only
		STATUS current
		DESCRIPTION
		"acOu37Compressordrivecommunication status."
		::= { acOuEntry 38 }
acOu39Module2overtemperature OBJECT-TYPE
		SYNTAX INTEGER {
			normal(0),
			alarm(1) }
		MAX-ACCESS read-only
		STATUS current
		DESCRIPTION
		"acOu38Module2overtemperature status."
		::= { acOuEntry 39 }
acOu40Busovervoltage OBJECT-TYPE
		SYNTAX INTEGER {
			normal(0),
			alarm(1) }
		MAX-ACCESS read-only
		STATUS current
		DESCRIPTION
		"acOu39Busovervoltage status."
		::= { acOuEntry 40 }
acOu41Tempsensor1isfaulty OBJECT-TYPE
		SYNTAX INTEGER {
			normal(0),
			alarm(1) }
		MAX-ACCESS read-only
		STATUS current
		DESCRIPTION
		"acOu40Tempsensor1isfaulty status."
		::= { acOuEntry 41 }
acOu42Tempsensor2isfaulty OBJECT-TYPE
		SYNTAX INTEGER {
			normal(0),
			alarm(1) }
		MAX-ACCESS read-only
		STATUS current
		DESCRIPTION
		"acOu41Tempsensor2isfaulty status."
		::= { acOuEntry 42 }
acOu43Shortcircuit OBJECT-TYPE
		SYNTAX INTEGER {
			normal(0),
			alarm(1) }
		MAX-ACCESS read-only
		STATUS current
		DESCRIPTION
		"acOu42Shortcircuit status."
		::= { acOuEntry 43 }
acOu44FrequencyShift OBJECT-TYPE
		SYNTAX INTEGER {
			normal(0),
			alarm(1) }
		MAX-ACCESS read-only
		STATUS current
		DESCRIPTION
		"acOu43FrequencyShift status."
		::= { acOuEntry 44 }
acOu45Module1overtemperature OBJECT-TYPE
		SYNTAX INTEGER {
			normal(0),
			alarm(1) }
		MAX-ACCESS read-only
		STATUS current
		DESCRIPTION
		"acOu44Module1overtemperature status."
		::= { acOuEntry 45 }
acOu46CompressordriveprotectionU04 OBJECT-TYPE
		SYNTAX INTEGER {
			normal(0),
			alarm(1) }
		MAX-ACCESS read-only
		STATUS current
		DESCRIPTION
		"acOu45CompressordriveprotectionU04 status."
		::= { acOuEntry 46 }
acOu47CompressordriveprotectionU13 OBJECT-TYPE
		SYNTAX INTEGER {
			normal(0),
			alarm(1) }
		MAX-ACCESS read-only
		STATUS current
		DESCRIPTION
		"acOu46CompressordriveprotectionU13 status."
		::= { acOuEntry 47 }
acOu48CompressordriveprotectionU14 OBJECT-TYPE
		SYNTAX INTEGER {
			normal(0),
			alarm(1) }
		MAX-ACCESS read-only
		STATUS current
		DESCRIPTION
		"acOu47CompressordriveprotectionU14 status."
		::= { acOuEntry 48 }
acOu49CompressordriveprotectionU11 OBJECT-TYPE
		SYNTAX INTEGER {
			normal(0),
			alarm(1) }
		MAX-ACCESS read-only
		STATUS current
		DESCRIPTION
		"acOu48CompressordriveprotectionU11 status."
		::= { acOuEntry 49 }
acOu50CompressordriveprotectionU08 OBJECT-TYPE
		SYNTAX INTEGER {
			normal(0),
			alarm(1) }
		MAX-ACCESS read-only
		STATUS current
		DESCRIPTION
		"acOu49CompressordriveprotectionU08 status."
		::= { acOuEntry 50 }
acOu51CompressordriveprotectionU09 OBJECT-TYPE
		SYNTAX INTEGER {
			normal(0),
			alarm(1) }
		MAX-ACCESS read-only
		STATUS current
		DESCRIPTION
		"acOu50CompressordriveprotectionU09 status."
		::= { acOuEntry 51 }
acOu52CompressordriveprotectionU10 OBJECT-TYPE
		SYNTAX INTEGER {
			normal(0),
			alarm(1) }
		MAX-ACCESS read-only
		STATUS current
		DESCRIPTION
		"acOu51CompressordriveprotectionU10 status."
		::= { acOuEntry 52 }
acOu53CompressordriveprotectionU12 OBJECT-TYPE
		SYNTAX INTEGER {
			normal(0),
			alarm(1) }
		MAX-ACCESS read-only
		STATUS current
		DESCRIPTION
		"acOu52CompressordriveprotectionU12 status."
		::= { acOuEntry 53 }
acOu54CompressordriveprotectionU15 OBJECT-TYPE
		SYNTAX INTEGER {
			normal(0),
			alarm(1) }
		MAX-ACCESS read-only
		STATUS current
		DESCRIPTION
		"acOu53CompressordriveprotectionU15 status."
		::= { acOuEntry 54 }
acOu55CompressordriveprotectionU06 OBJECT-TYPE
		SYNTAX INTEGER {
			normal(0),
			alarm(1) }
		MAX-ACCESS read-only
		STATUS current
		DESCRIPTION
		"acOu54CompressordriveprotectionU06 status."
		::= { acOuEntry 55 }
acOu56Supplyairtemperature OBJECT-TYPE
		SYNTAX Integer32
		
		MAX-ACCESS read-only
		STATUS current
		DESCRIPTION
		"acOu55Supplyairtemperature stored as 0.01℃."
		::= { acOuEntry 56 }
acOu57Returnairtemperature OBJECT-TYPE
		SYNTAX Integer32
		
		MAX-ACCESS read-only
		STATUS current
		DESCRIPTION
		"acOu56Returnairtemperature stored as 0.01℃."
		::= { acOuEntry 57 }
acOu58Outsidetemperature OBJECT-TYPE
		SYNTAX Integer32
		
		MAX-ACCESS read-only
		STATUS current
		DESCRIPTION
		"acOu57Outsidetemperature stored as 0.01℃."
		::= { acOuEntry 58 }
acOu59Exhausttemperature OBJECT-TYPE
		SYNTAX Integer32
		
		MAX-ACCESS read-only
		STATUS current
		DESCRIPTION
		"acOu58Exhausttemperature stored as 0.01℃."
		::= { acOuEntry 59 }
acOu60Inspiratorytemperature OBJECT-TYPE
		SYNTAX Integer32
		
		MAX-ACCESS read-only
		STATUS current
		DESCRIPTION
		"acOu59Inspiratorytemperature stored as 0.01℃."
		::= { acOuEntry 60 }
acOu61Exhaustpressure OBJECT-TYPE
		SYNTAX Integer32
		
		MAX-ACCESS read-only
		STATUS current
		DESCRIPTION
		"acOu60Exhaustpressure stored as 0.01Bar."
		::= { acOuEntry 61 }
acOu62Inspiratorypressure OBJECT-TYPE
		SYNTAX Integer32
		
		MAX-ACCESS read-only
		STATUS current
		DESCRIPTION
		"acOu61Inspiratorypressure stored as 0.01Bar."
		::= { acOuEntry 62 }
acOu63Monitoraddress OBJECT-TYPE
		SYNTAX Integer32
		
		MAX-ACCESS read-only
		STATUS current
		DESCRIPTION
		"acOu62Monitoraddress stored as 0.01."
		::= { acOuEntry 63 }
acOu64Powervoltage OBJECT-TYPE
		SYNTAX Integer32
		
		MAX-ACCESS read-only
		STATUS current
		DESCRIPTION
		"acOu63Powervoltage stored as 0.01V."
		::= { acOuEntry 64 }
acOu65Powerfrequency OBJECT-TYPE
		SYNTAX Integer32
		
		MAX-ACCESS read-only
		STATUS current
		DESCRIPTION
		"acOu64Powerfrequency stored as 0.01Hz."
		::= { acOuEntry 65 }
acOu66Inspiratorysuperheat OBJECT-TYPE
		SYNTAX Integer32
		
		MAX-ACCESS read-only
		STATUS current
		DESCRIPTION
		"acOu65Inspiratorysuperheat stored as 0.01℃."
		::= { acOuEntry 66 }
acOu67Thenumberofalarmstates OBJECT-TYPE
		SYNTAX Integer32
		
		MAX-ACCESS read-only
		STATUS current
		DESCRIPTION
		"acOu66Thenumberofalarmstates stored as 0.01."
		::= { acOuEntry 67 }
acOu68Numberofalarmhistory OBJECT-TYPE
		SYNTAX Integer32
		
		MAX-ACCESS read-only
		STATUS current
		DESCRIPTION
		"acOu67Numberofalarmhistory stored as 0.01."
		::= { acOuEntry 68 }
acOu69Compressorstartandstoprecor OBJECT-TYPE
		SYNTAX Integer32
		
		MAX-ACCESS read-only
		STATUS current
		DESCRIPTION
		"acOu68Compressorstartandstoprecor stored as 0.01."
		::= { acOuEntry 69 }
acOu70Fanstartandstoprecordnumbe OBJECT-TYPE
		SYNTAX Integer32
		
		MAX-ACCESS read-only
		STATUS current
		DESCRIPTION
		"acOu69Fanstartandstoprecordnumbe stored as 0.01."
		::= { acOuEntry 70 }
acOu71Compressorhoursofoperationr OBJECT-TYPE
		SYNTAX Integer32
		
		MAX-ACCESS read-only
		STATUS current
		DESCRIPTION
		"acOu70Compressorhoursofoperationr stored as 0.01Hour."
		::= { acOuEntry 71 }
acOu72CommunicateStatus OBJECT-TYPE
		SYNTAX INTEGER {
			normal(0),
			alarm(1) }
		MAX-ACCESS read-only
		STATUS current
		DESCRIPTION
		"acOu71CommunicateStatus status."
		::= { acOuEntry 72 }
acOu73Highsoftwareversion OBJECT-TYPE
		SYNTAX Integer32
		
		MAX-ACCESS read-only
		STATUS current
		DESCRIPTION
		"acOu72Highsoftwareversion stored as 0.01."
		::= { acOuEntry 73 }
acOu74Softwareversionlow OBJECT-TYPE
		SYNTAX Integer32
		
		MAX-ACCESS read-only
		STATUS current
		DESCRIPTION
		"acOu73Softwareversionlow stored as 0.01."
		::= { acOuEntry 74 }
acOu75Airconditioningrunningstatus OBJECT-TYPE
		SYNTAX INTEGER {
			on(0),
			off(1) }
		MAX-ACCESS read-only
		STATUS current
		DESCRIPTION
		"acOu74Airconditioningrunningstatus status."
		::= { acOuEntry 75 }
acOu76Compressorcapacityactualvalu OBJECT-TYPE
		SYNTAX Integer32
		
		MAX-ACCESS read-only
		STATUS current
		DESCRIPTION
		"acOu75Compressorcapacityactualvalu stored as 0.01%."
		::= { acOuEntry 76 }
acOu77Fanspeed OBJECT-TYPE
		SYNTAX Integer32
		
		MAX-ACCESS read-only
		STATUS current
		DESCRIPTION
		"acOu76Fanspeed stored as 0.01%."
		::= { acOuEntry 77 }
acOu78Expansionvalveopening OBJECT-TYPE
		SYNTAX Integer32
		
		MAX-ACCESS read-only
		STATUS current
		DESCRIPTION
		"acOu77Expansionvalveopening stored as 0.01%."
		::= { acOuEntry 78 }
acOu79Highpressureabnormalrecordn OBJECT-TYPE
		SYNTAX Integer32
		
		MAX-ACCESS read-only
		STATUS current
		DESCRIPTION
		"acOu78Highpressureabnormalrecordn stored as 0.01."
		::= { acOuEntry 79 }
acOu80Controlmode OBJECT-TYPE
		SYNTAX Integer32
		
		MAX-ACCESS read-only
		STATUS current
		DESCRIPTION
		"acOu79Controlmode stored as 0.01."
		::= { acOuEntry 80 }
acOu81Compressortemperatureintegrat OBJECT-TYPE
		SYNTAX Integer32
		
		MAX-ACCESS read-only
		STATUS current
		DESCRIPTION
		"acOu80Compressortemperatureintegrat stored as 0.01Sec."
		::= { acOuEntry 81 }
acOu82Compressortemperaturedifferen OBJECT-TYPE
		SYNTAX Integer32
		
		MAX-ACCESS read-only
		STATUS current
		DESCRIPTION
		"acOu81Compressortemperaturedifferen stored as 0.01Sec."
		::= { acOuEntry 82 }
acOu83Fantemperatureintegrationtim OBJECT-TYPE
		SYNTAX Integer32
		
		MAX-ACCESS read-only
		STATUS current
		DESCRIPTION
		"acOu82Fantemperatureintegrationtim stored as 0.01Sec."
		::= { acOuEntry 83 }
acOu84Fantemperaturedifferentialti OBJECT-TYPE
		SYNTAX Integer32
		
		MAX-ACCESS read-only
		STATUS current
		DESCRIPTION
		"acOu83Fantemperaturedifferentialti stored as 0.01Sec."
		::= { acOuEntry 84 }
acOu85Modelselection OBJECT-TYPE
		SYNTAX Integer32
		
		MAX-ACCESS read-only
		STATUS current
		DESCRIPTION
		"acOu84Modelselection stored as 0.01."
		::= { acOuEntry 85 }
acOu86Returntoruntime OBJECT-TYPE
		SYNTAX Integer32
		
		MAX-ACCESS read-only
		STATUS current
		DESCRIPTION
		"acOu85Returntoruntime stored as 0.01Min."
		::= { acOuEntry 86 }
acOu87Returnoilcapacity OBJECT-TYPE
		SYNTAX Integer32
		
		MAX-ACCESS read-only
		STATUS current
		DESCRIPTION
		"acOu86Returnoilcapacity stored as 0.01%."
		::= { acOuEntry 87 }
acOu88Compressorhoppingpoint1 OBJECT-TYPE
		SYNTAX Integer32
		
		MAX-ACCESS read-only
		STATUS current
		DESCRIPTION
		"acOu87Compressorhoppingpoint1 stored as 0.01%."
		::= { acOuEntry 88 }
acOu89Compressorhoppingpoint1band OBJECT-TYPE
		SYNTAX Integer32
		
		MAX-ACCESS read-only
		STATUS current
		DESCRIPTION
		"acOu88Compressorhoppingpoint1band stored as 0.01%."
		::= { acOuEntry 89 }
acOu90Compressorhoppingpoint2 OBJECT-TYPE
		SYNTAX Integer32
		
		MAX-ACCESS read-only
		STATUS current
		DESCRIPTION
		"acOu89Compressorhoppingpoint2 stored as 0.01%."
		::= { acOuEntry 90 }
acOu91Compressorhoppingpoint2band OBJECT-TYPE
		SYNTAX Integer32
		
		MAX-ACCESS read-only
		STATUS current
		DESCRIPTION
		"acOu90Compressorhoppingpoint2band stored as 0.01%."
		::= { acOuEntry 91 }
acOu92Compressorhoppingpoint3 OBJECT-TYPE
		SYNTAX Integer32
		
		MAX-ACCESS read-only
		STATUS current
		DESCRIPTION
		"acOu91Compressorhoppingpoint3 stored as 0.01%."
		::= { acOuEntry 92 }
acOu93Compressorhoppingpoint3band OBJECT-TYPE
		SYNTAX Integer32
		
		MAX-ACCESS read-only
		STATUS current
		DESCRIPTION
		"acOu92Compressorhoppingpoint3band stored as 0.01%."
		::= { acOuEntry 93 }
acOu94Compressorhoppingpoint4 OBJECT-TYPE
		SYNTAX Integer32
		
		MAX-ACCESS read-only
		STATUS current
		DESCRIPTION
		"acOu93Compressorhoppingpoint4 stored as 0.01%."
		::= { acOuEntry 94 }
acOu95Compressorhoppingpoint4band OBJECT-TYPE
		SYNTAX Integer32
		
		MAX-ACCESS read-only
		STATUS current
		DESCRIPTION
		"acOu94Compressorhoppingpoint4band stored as 0.01%."
		::= { acOuEntry 95 }
acOu96Compressorhoppingpoint5 OBJECT-TYPE
		SYNTAX Integer32
		
		MAX-ACCESS read-only
		STATUS current
		DESCRIPTION
		"acOu95Compressorhoppingpoint5 stored as 0.01%."
		::= { acOuEntry 96 }
acOu97Compressorhoppingpoint5band OBJECT-TYPE
		SYNTAX Integer32
		
		MAX-ACCESS read-only
		STATUS current
		DESCRIPTION
		"acOu96Compressorhoppingpoint5band stored as 0.01%."
		::= { acOuEntry 97 }
acOu98Indoorfanfrequencyhoppingpo OBJECT-TYPE
		SYNTAX Integer32
		
		MAX-ACCESS read-only
		STATUS current
		DESCRIPTION
		"acOu97Indoorfanfrequencyhoppingpo stored as 0.01%."
		::= { acOuEntry 98 }
acOu99Indoorfanfrequencyhoppingpo OBJECT-TYPE
		SYNTAX Integer32
		
		MAX-ACCESS read-only
		STATUS current
		DESCRIPTION
		"acOu98Indoorfanfrequencyhoppingpo stored as 0.01%."
		::= { acOuEntry 99 }
acOu100Indoorfanfrequencyhoppingpo OBJECT-TYPE
		SYNTAX Integer32
		
		MAX-ACCESS read-only
		STATUS current
		DESCRIPTION
		"acOu99Indoorfanfrequencyhoppingpo stored as 0.01%."
		::= { acOuEntry 100 }
acOu101Indoorfanfrequencyhoppingpo OBJECT-TYPE
		SYNTAX Integer32
		
		MAX-ACCESS read-only
		STATUS current
		DESCRIPTION
		"acOu100Indoorfanfrequencyhoppingpo stored as 0.01%."
		::= { acOuEntry 101 }
acOu102Indoorfanfrequencyhoppingpo OBJECT-TYPE
		SYNTAX Integer32
		
		MAX-ACCESS read-only
		STATUS current
		DESCRIPTION
		"acOu101Indoorfanfrequencyhoppingpo stored as 0.01%."
		::= { acOuEntry 102 }
acOu103Indoorfanfrequencyhoppingpo OBJECT-TYPE
		SYNTAX Integer32
		
		MAX-ACCESS read-only
		STATUS current
		DESCRIPTION
		"acOu102Indoorfanfrequencyhoppingpo stored as 0.01%."
		::= { acOuEntry 103 }
acOu104Indoorfanfrequencyhoppingpo OBJECT-TYPE
		SYNTAX Integer32
		
		MAX-ACCESS read-only
		STATUS current
		DESCRIPTION
		"acOu103Indoorfanfrequencyhoppingpo stored as 0.01%."
		::= { acOuEntry 104 }
acOu105Indoorfanfrequencyhoppingpo OBJECT-TYPE
		SYNTAX Integer32
		
		MAX-ACCESS read-only
		STATUS current
		DESCRIPTION
		"acOu104Indoorfanfrequencyhoppingpo stored as 0.01%."
		::= { acOuEntry 105 }
acOu106Indoorfanfrequencyhoppingpo OBJECT-TYPE
		SYNTAX Integer32
		
		MAX-ACCESS read-only
		STATUS current
		DESCRIPTION
		"acOu105Indoorfanfrequencyhoppingpo stored as 0.01%."
		::= { acOuEntry 106 }
acOu107Indoorfanfrequencyhoppingpo OBJECT-TYPE
		SYNTAX Integer32
		
		MAX-ACCESS read-only
		STATUS current
		DESCRIPTION
		"acOu106Indoorfanfrequencyhoppingpo stored as 0.01%."
		::= { acOuEntry 107 }
acOu108Indoorfanfrequencyhoppingpo OBJECT-TYPE
		SYNTAX Integer32
		
		MAX-ACCESS read-only
		STATUS current
		DESCRIPTION
		"acOu107Indoorfanfrequencyhoppingpo stored as 1%."
		::= { acOuEntry 108 }
acOu109Indoorfanfrequencyhoppingpo OBJECT-TYPE
		SYNTAX Integer32
		
		MAX-ACCESS read-only
		STATUS current
		DESCRIPTION
		"acOu108Indoorfanfrequencyhoppingpo stored as 1%."
		::= { acOuEntry 109 }
acOu110reset OBJECT-TYPE
		SYNTAX INTEGER {
			no(0),
			yes(1) }
		MAX-ACCESS read-write
		STATUS current
		DESCRIPTION
		"acOu109reset status."
		::= { acOuEntry 110 }
acOu111Filtermaintenance OBJECT-TYPE
		SYNTAX INTEGER {
			no(0),
			yes(1) }
		MAX-ACCESS read-write
		STATUS current
		DESCRIPTION
		"acOu110Filtermaintenance status."
		::= { acOuEntry 111 }
acOu112RemoteOn OBJECT-TYPE
		SYNTAX INTEGER {
			remoteon(0) }
		MAX-ACCESS read-write
		STATUS current
		DESCRIPTION
		"acOu111RemoteOn status."
		::= { acOuEntry 112 }
acOu113RemoteOff OBJECT-TYPE
		SYNTAX INTEGER {
			remoteoff(0) }
		MAX-ACCESS read-write
		STATUS current
		DESCRIPTION
		"acOu112RemoteOff status."
		::= { acOuEntry 113 }
acOu114RemoteOff OBJECT-TYPE
		SYNTAX INTEGER {
			remoteoff(0) }
		MAX-ACCESS read-write
		STATUS current
		DESCRIPTION
		"acOu113RemoteOff status."
		::= { acOuEntry 114 }
acOu115Supplyairtempcorrectionvalu OBJECT-TYPE
		SYNTAX Integer32
		
		MAX-ACCESS read-write
		STATUS current
		DESCRIPTION
		"acOu114Supplyairtempcorrectionvalu stored as 1℃."
		::= { acOuEntry 115 }
acOu116Returnairtempecorrectionval OBJECT-TYPE
		SYNTAX Integer32
		
		MAX-ACCESS read-write
		STATUS current
		DESCRIPTION
		"acOu115Returnairtempecorrectionval stored as 1℃."
		::= { acOuEntry 116 }
acOu117Exhausttempcorrectionvalue OBJECT-TYPE
		SYNTAX Integer32
		
		MAX-ACCESS read-write
		STATUS current
		DESCRIPTION
		"acOu116Exhausttempcorrectionvalue stored as 1℃."
		::= { acOuEntry 117 }
acOu118Exhaustpressurecorrectionval OBJECT-TYPE
		SYNTAX Integer32
		
		MAX-ACCESS read-write
		STATUS current
		DESCRIPTION
		"acOu117Exhaustpressurecorrectionval stored as 1Bar."
		::= { acOuEntry 118 }
acOu119Suctionpressurecorrectionval OBJECT-TYPE
		SYNTAX Integer32
		
		MAX-ACCESS read-write
		STATUS current
		DESCRIPTION
		"acOu118Suctionpressurecorrectionval stored as 1Bar."
		::= { acOuEntry 119 }
acOu120Monitoraddress OBJECT-TYPE
		SYNTAX Integer32
		
		MAX-ACCESS read-write
		STATUS current
		DESCRIPTION
		"acOu119Monitoraddress stored as 1."
		::= { acOuEntry 120 }
acOu121Compressorshortestrunningtim OBJECT-TYPE
		SYNTAX Integer32
		
		MAX-ACCESS read-write
		STATUS current
		DESCRIPTION
		"acOu120Compressorshortestrunningtim stored as 1Min."
		::= { acOuEntry 121 }
acOu122Minimumcompressordowntime OBJECT-TYPE
		SYNTAX Integer32
		
		MAX-ACCESS read-write
		STATUS current
		DESCRIPTION
		"acOu121Minimumcompressordowntime stored as 1Min."
		::= { acOuEntry 122 }
acOu123Fanstartdelay OBJECT-TYPE
		SYNTAX Integer32
		
		MAX-ACCESS read-write
		STATUS current
		DESCRIPTION
		"acOu122Fanstartdelay stored as 1Sec."
		::= { acOuEntry 123 }
acOu124Fanstopdelay OBJECT-TYPE
		SYNTAX Integer32
		
		MAX-ACCESS read-write
		STATUS current
		DESCRIPTION
		"acOu123Fanstopdelay stored as 1Sec."
		::= { acOuEntry 124 }
acOu125Deadzonetemperature OBJECT-TYPE
		SYNTAX Integer32
		
		MAX-ACCESS read-write
		STATUS current
		DESCRIPTION
		"acOu124Deadzonetemperature stored as 0.1℃."
		::= { acOuEntry 125 }
acOu126Returnairtempsetting OBJECT-TYPE
		SYNTAX Integer32
		
		MAX-ACCESS read-write
		STATUS current
		DESCRIPTION
		"acOu125Returnairtempsetting stored as 1℃."
		::= { acOuEntry 126 }
acOu127Compressorcapacityoutputvalu OBJECT-TYPE
		SYNTAX Integer32
		
		MAX-ACCESS read-write
		STATUS current
		DESCRIPTION
		"acOu126Compressorcapacityoutputvalu stored as 1%."
		::= { acOuEntry 127 }
acOu128Lowpressurealarmdelay OBJECT-TYPE
		SYNTAX Integer32
		
		MAX-ACCESS read-write
		STATUS current
		DESCRIPTION
		"acOu127Lowpressurealarmdelay stored as 1Sec."
		::= { acOuEntry 128 }
acOu129Filtermaintenanceremindertim OBJECT-TYPE
		SYNTAX Integer32
		
		MAX-ACCESS read-write
		STATUS current
		DESCRIPTION
		"acOu128Filtermaintenanceremindertim stored as 1Day."
		::= { acOuEntry 129 }
acOu130Highpressurealarmvalue OBJECT-TYPE
		SYNTAX Integer32
		
		MAX-ACCESS read-write
		STATUS current
		DESCRIPTION
		"acOu129Highpressurealarmvalue stored as 1Bar."
		::= { acOuEntry 130 }
acOu131Supplyairtemperaturealarmva OBJECT-TYPE
		SYNTAX Integer32
		
		MAX-ACCESS read-write
		STATUS current
		DESCRIPTION
		"acOu130Supplyairtemperaturealarmva stored as 1℃."
		::= { acOuEntry 131 }
acOu132Supplyairtemperaturealarmva OBJECT-TYPE
		SYNTAX Integer32
		
		MAX-ACCESS read-write
		STATUS current
		DESCRIPTION
		"acOu131Supplyairtemperaturealarmva stored as 1℃."
		::= { acOuEntry 132 }
acOu133Returnairtemperaturealarmva OBJECT-TYPE
		SYNTAX Integer32
		
		MAX-ACCESS read-write
		STATUS current
		DESCRIPTION
		"acOu132Returnairtemperaturealarmva stored as 1℃."
		::= { acOuEntry 133 }
acOu134Powerovervoltagealarmpoint OBJECT-TYPE
		SYNTAX Integer32
		
		MAX-ACCESS read-write
		STATUS current
		DESCRIPTION
		"acOu133Powerovervoltagealarmpoint stored as 1V."
		::= { acOuEntry 134 }
acOu135Powerundervoltagealarmpoint OBJECT-TYPE
		SYNTAX Integer32
		
		MAX-ACCESS read-write
		STATUS current
		DESCRIPTION
		"acOu134Powerundervoltagealarmpoint stored as 1V."
		::= { acOuEntry 135 }
acOu136Compressortemperatureproporti OBJECT-TYPE
		SYNTAX Integer32
		
		MAX-ACCESS read-write
		STATUS current
		DESCRIPTION
		"acOu135Compressortemperatureproporti stored as 1℃."
		::= { acOuEntry 136 }
acOu137Fantemperatureproportionalba OBJECT-TYPE
		SYNTAX Integer32
		
		MAX-ACCESS read-write
		STATUS current
		DESCRIPTION
		"acOu136Fantemperatureproportionalba stored as 1℃."
		::= { acOuEntry 137 }
acOu138Compressorstartuprequirements OBJECT-TYPE
		SYNTAX Integer32
		
		MAX-ACCESS read-write
		STATUS current
		DESCRIPTION
		"acOu137Compressorstartuprequirements stored as 1%."
		::= { acOuEntry 138 }
acOu139Compressorstopdemand OBJECT-TYPE
		SYNTAX Integer32
		
		MAX-ACCESS read-write
		STATUS current
		DESCRIPTION
		"acOu138Compressorstopdemand stored as 1%."
		::= { acOuEntry 139 }
acOu140Compressorminimumcapacity OBJECT-TYPE
		SYNTAX Integer32
		
		MAX-ACCESS read-write
		STATUS current
		DESCRIPTION
		"acOu139Compressorminimumcapacity stored as 1%."
		::= { acOuEntry 140 }
acOu141Compressorstandardcapacity OBJECT-TYPE
		SYNTAX Integer32
		
		MAX-ACCESS read-write
		STATUS current
		DESCRIPTION
		"acOu140Compressorstandardcapacity stored as 1%."
		::= { acOuEntry 141 }
acOu142Compressorstartupcapacity OBJECT-TYPE
		SYNTAX Integer32
		
		MAX-ACCESS read-write
		STATUS current
		DESCRIPTION
		"acOu141Compressorstartupcapacity stored as 1%."
		::= { acOuEntry 142 }
acOu143Compressoroutputdeadzone OBJECT-TYPE
		SYNTAX Integer32
		
		MAX-ACCESS read-write
		STATUS current
		DESCRIPTION
		"acOu142Compressoroutputdeadzone stored as 0.1%."
		::= { acOuEntry 143 }
acOu144Returncycle OBJECT-TYPE
		SYNTAX Integer32
		
		MAX-ACCESS read-write
		STATUS current
		DESCRIPTION
		"acOu143Returncycle stored as 1h."
		::= { acOuEntry 144 }
acOu145Minimumfanspeed OBJECT-TYPE
		SYNTAX Integer32
		
		MAX-ACCESS read-write
		STATUS current
		DESCRIPTION
		"acOu144Minimumfanspeed stored as 1%."
		::= { acOuEntry 145 }
acOu146Fanstandardspeed OBJECT-TYPE
		SYNTAX Integer32
		
		MAX-ACCESS read-write
		STATUS current
		DESCRIPTION
		"acOu145Fanstandardspeed stored as 1%."
		::= { acOuEntry 146 }
acOu147MinimumfanspeedCFC OBJECT-TYPE
		SYNTAX Integer32
		
		MAX-ACCESS read-write
		STATUS current
		DESCRIPTION
		"acOu146MinimumfanspeedCFC stored as 1%."
		::= { acOuEntry 147 }
acOu148FanstandardspeedCFC OBJECT-TYPE
		SYNTAX Integer32
		
		MAX-ACCESS read-write
		STATUS current
		DESCRIPTION
		"acOu147FanstandardspeedCFC stored as 1%."
		::= { acOuEntry 148 }
acOu149Lowspeedfanstep OBJECT-TYPE
		SYNTAX Integer32
		
		MAX-ACCESS read-write
		STATUS current
		DESCRIPTION
		"acOu148Lowspeedfanstep stored as 0.1%s."
		::= { acOuEntry 149 }
acOu150Highspeedfanstep OBJECT-TYPE
		SYNTAX Integer32
		
		MAX-ACCESS read-write
		STATUS current
		DESCRIPTION
		"acOu149Highspeedfanstep stored as 0.1%s."
		::= { acOuEntry 150 }
acOu151Fandecelerationdelay OBJECT-TYPE
		SYNTAX Integer32
		
		MAX-ACCESS read-write
		STATUS current
		DESCRIPTION
		"acOu150Fandecelerationdelay stored as 1Sec."
		::= { acOuEntry 151 }
acOu152EEVsuperheatsettingMAX OBJECT-TYPE
		SYNTAX Integer32
		
		MAX-ACCESS read-write
		STATUS current
		DESCRIPTION
		"acOu151EEVsuperheatsettingMAX stored as 1℃."
		::= { acOuEntry 152 }
acOu153EEVsuperheatsettingMIN OBJECT-TYPE
		SYNTAX Integer32
		
		MAX-ACCESS read-write
		STATUS current
		DESCRIPTION
		"acOu152EEVsuperheatsettingMIN stored as 1℃."
		::= { acOuEntry 153 }
acOu154EEVMOPpressurelimit OBJECT-TYPE
		SYNTAX Integer32
		
		MAX-ACCESS read-write
		STATUS current
		DESCRIPTION
		"acOu153EEVMOPpressurelimit stored as 1Bar."
		::= { acOuEntry 154 }
acOu155EEVvalvebodyshutoffsuperhe OBJECT-TYPE
		SYNTAX Integer32
		
		MAX-ACCESS read-write
		STATUS current
		DESCRIPTION
		"acOu154EEVvalvebodyshutoffsuperhe stored as 1℃."
		::= { acOuEntry 155 }
acOu156Outdoorfanminimumsupplyvolt OBJECT-TYPE
		SYNTAX Integer32
		
		MAX-ACCESS read-write
		STATUS current
		DESCRIPTION
		"acOu155Outdoorfanminimumsupplyvolt stored as 1%."
		::= { acOuEntry 156 }
acOu157Outdoorfanmaximumsupplyvolt OBJECT-TYPE
		SYNTAX Integer32
		
		MAX-ACCESS read-write
		STATUS current
		DESCRIPTION
		"acOu156Outdoorfanmaximumsupplyvolt stored as 1%."
		::= { acOuEntry 157 }
acOu158Outdoorfanpressurecontrolra OBJECT-TYPE
		SYNTAX Integer32
		
		MAX-ACCESS read-write
		STATUS current
		DESCRIPTION
		"acOu157Outdoorfanpressurecontrolra stored as 1Bar."
		::= { acOuEntry 158 }
acOu159Outdoorfanstartpressure OBJECT-TYPE
		SYNTAX Integer32
		
		MAX-ACCESS read-write
		STATUS current
		DESCRIPTION
		"acOu158Outdoorfanstartpressure stored as 1Bar."
		::= { acOuEntry 159 }
acOu160Outdoorfanstartpressure OBJECT-TYPE
		SYNTAX Integer32
		
		MAX-ACCESS read-write
		STATUS current
		DESCRIPTION
		"acOu159Outdoorfanstartpressure stored as 1Bar."
		::= { acOuEntry 160 }

------------------------------------------------------------
-- Accu { 13400.3.7 }
------------------------------------------------------------
acc OBJECT IDENTIFIER ::=  { dcs 7 }


------------------------------------------------------------
-- Chd2100j5com { 13400.3.7.7008 }
------------------------------------------------------------
acc-Chd2100j5com OBJECT IDENTIFIER ::= { acc 7008 }
accChd2100j5comTable OBJECT-TYPE
		SYNTAX			SEQUENCE OF AccChd2100j5comEntry
		MAX-ACCESS		not-accessible
		STATUS			current
		DESCRIPTION	"accChd2100j5comTable"
		::=			{ acc-Chd2100j5com 1 }
accChd2100j5comEntry OBJECT-TYPE
		SYNTAX			AccChd2100j5comEntry
		MAX-ACCESS		not-accessible
		STATUS			current
		DESCRIPTION		"accChd2100j5comEntry"
		INDEX			{ accChd2100j5comIndex }
		::=				{ accChd2100j5comTable 1 }
AccChd2100j5comEntry ::= SEQUENCE {
		accChd2100j5comIndex					Integer32,
		accChd2100j5com2LogCount					Integer32,
		accChd2100j5com3RealClock					INTEGER,
		accChd2100j5com4Eerom					INTEGER,
		accChd2100j5com5Power					INTEGER,
		accChd2100j5com6DoorMonitor					INTEGER,
		accChd2100j5com7OpenDoorRelayDrive					INTEGER,
		accChd2100j5com8AccessAlarmStatus					INTEGER,
		accChd2100j5com9DoorLockStatus					INTEGER,
		accChd2100j5com10OutButtonStatus					INTEGER,
		accChd2100j5com11GatingRelayDrive					INTEGER,
		accChd2100j5com12DoorStatusMonitor					INTEGER,
		accChd2100j5com13ManuallyLockTheDoor					INTEGER,
		accChd2100j5com14DeviceType					INTEGER,
		accChd2100j5com15DoorStatus					INTEGER,
		accChd2100j5com16InfraredStatus					INTEGER,
		accChd2100j5com17InfraredMonitoringStatus					INTEGER,
		accChd2100j5com18DoorLable					Integer32,
		accChd2100j5com19MaxNumberofDoorLockinCont					Integer32,
		accChd2100j5com20PresentDoorLockNumber					Integer32,
		accChd2100j5com21PresentDoorLockNumber					Integer32,
		accChd2100j5com22RemoteOpenDoor					INTEGER,
		accChd2100j5com23AddUser					INTEGER,
		accChd2100j5com24DeleteUser					INTEGER,
		accChd2100j5com25DeleteAllUser					INTEGER,
		accChd2100j5com26SetTimeSection					INTEGER,
		accChd2100j5com27SetTime					INTEGER,
		accChd2100j5com28ReadLogCount					INTEGER,
		accChd2100j5com29GetLog					INTEGER,
		accChd2100j5com30UpdateUserInfo					INTEGER,
		accChd2100j5com31QueryUserIDExist					INTEGER,
		accChd2100j5com32QueryCardIDExist					INTEGER,
		accChd2100j5com33SetAlwaysOpenTime					INTEGER,
		accChd2100j5com34SetCardAndPasswordTime					INTEGER,
		accChd2100j5com35SetInfraredMonitorTime					INTEGER,
		accChd2100j5com36GetUserCount					INTEGER,
		accChd2100j5com37GetAuthorizationList					INTEGER,
		accChd2100j5com38CardAuthorization					INTEGER,
		accChd2100j5com39DeleteUserCard					INTEGER,
		accChd2100j5com40DeleteUserID					INTEGER,
		accChd2100j5com41DeleteAllUser					INTEGER,
		accChd2100j5com42Readversion					INTEGER,
		accChd2100j5com43Addfingerprintusers					INTEGER,
		accChd2100j5com44Readfingerprintusers					INTEGER,
		accChd2100j5com45Deletefingerprintuser					INTEGER,
		accChd2100j5com46Deletefingerprint					INTEGER,
		accChd2100j5com47Startupsettingsfingerprint					INTEGER,
		accChd2100j5com48Setfingerprint					INTEGER,
		accChd2100j5com49Endsetfingerprint					INTEGER,
		accChd2100j5com50Refreshfingerprintdata					INTEGER,
		accChd2100j5com51Restorethefingerprintreader					INTEGER,
		accChd2100j5com52Restorethefingerprintreader					INTEGER,
		accChd2100j5com53SetRelayOpenTime					INTEGER,
		accChd2100j5com54MonitorDoorStatus					INTEGER,
		accChd2100j5com55NeedInputPassword					INTEGER,
		accChd2100j5com56EnableManualButton					INTEGER,
		accChd2100j5com57EnableKeyboardOpen					INTEGER,
		accChd2100j5com58Setsingleordoublecarddoor					INTEGER,
		accChd2100j5com59Infraredalarmconfirmationtim					INTEGER,
		accChd2100j5com60Infraredmonitoringstatus					INTEGER,
		accChd2100j5com61Magneticlevelsensor					INTEGER,
		accChd2100j5com62Infraredsensorlevel					INTEGER,
		accChd2100j5com63Entertheemergencyaction					INTEGER,
		accChd2100j5com64ALARMoutputwhenthealarmact					INTEGER,
		accChd2100j5com65Passwordtimecontrol					INTEGER,
		accChd2100j5com66Doorcardpasswordtest					INTEGER,
		accChd2100j5com67Checkoutcreditcardpassword					INTEGER,
		accChd2100j5com68Tosetfingerprint1readeraddr					Integer32,
		accChd2100j5com69Fingerprintreader1address					INTEGER,
		accChd2100j5com70Addressfingerprintreader					INTEGER,
		accChd2100j5com71Fingerprintreaderwork					Integer32,
		accChd2100j5com72Fingerprintreaderwork					Integer32 }
accChd2100j5comIndex OBJECT-TYPE
		SYNTAX Integer32(1..72)
		MAX-ACCESS read-only
		STATUS current
		DESCRIPTION
		"accChd2100j5com System Entry Index."
		::= { accChd2100j5comEntry 1 }
accChd2100j5com2LogCount OBJECT-TYPE
		SYNTAX Integer32
		
		MAX-ACCESS read-only
		STATUS current
		DESCRIPTION
		"accChd2100j5com1LogCount stored as 1."
		::= { accChd2100j5comEntry 2 }
accChd2100j5com3RealClock OBJECT-TYPE
		SYNTAX INTEGER {
			normal(0),
			abnormal(1) }
		MAX-ACCESS read-only
		STATUS current
		DESCRIPTION
		"accChd2100j5com2RealClock status."
		::= { accChd2100j5comEntry 3 }
accChd2100j5com4Eerom OBJECT-TYPE
		SYNTAX INTEGER {
			normal(0),
			abnormal(1) }
		MAX-ACCESS read-only
		STATUS current
		DESCRIPTION
		"accChd2100j5com3Eerom status."
		::= { accChd2100j5comEntry 4 }
accChd2100j5com5Power OBJECT-TYPE
		SYNTAX INTEGER {
			normal(0),
			abnormal(1) }
		MAX-ACCESS read-only
		STATUS current
		DESCRIPTION
		"accChd2100j5com4Power status."
		::= { accChd2100j5comEntry 5 }
accChd2100j5com6DoorMonitor OBJECT-TYPE
		SYNTAX INTEGER {
			close(0),
			open(1) }
		MAX-ACCESS read-only
		STATUS current
		DESCRIPTION
		"accChd2100j5com5DoorMonitor status."
		::= { accChd2100j5comEntry 6 }
accChd2100j5com7OpenDoorRelayDrive OBJECT-TYPE
		SYNTAX INTEGER {
			release(0),
			drivers(1) }
		MAX-ACCESS read-only
		STATUS current
		DESCRIPTION
		"accChd2100j5com6OpenDoorRelayDrive status."
		::= { accChd2100j5comEntry 7 }
accChd2100j5com8AccessAlarmStatus OBJECT-TYPE
		SYNTAX INTEGER {
			normal(0),
			alarm(1) }
		MAX-ACCESS read-only
		STATUS current
		DESCRIPTION
		"accChd2100j5com7AccessAlarmStatus status."
		::= { accChd2100j5comEntry 8 }
accChd2100j5com9DoorLockStatus OBJECT-TYPE
		SYNTAX INTEGER {
			close(0),
			open(1) }
		MAX-ACCESS read-only
		STATUS current
		DESCRIPTION
		"accChd2100j5com8DoorLockStatus status."
		::= { accChd2100j5comEntry 9 }
accChd2100j5com10OutButtonStatus OBJECT-TYPE
		SYNTAX INTEGER {
			release(0),
			press(1) }
		MAX-ACCESS read-only
		STATUS current
		DESCRIPTION
		"accChd2100j5com9OutButtonStatus status."
		::= { accChd2100j5comEntry 10 }
accChd2100j5com11GatingRelayDrive OBJECT-TYPE
		SYNTAX INTEGER {
			release(0),
			drivers(1) }
		MAX-ACCESS read-only
		STATUS current
		DESCRIPTION
		"accChd2100j5com10GatingRelayDrive status."
		::= { accChd2100j5comEntry 11 }
accChd2100j5com12DoorStatusMonitor OBJECT-TYPE
		SYNTAX INTEGER {
			close(0),
			open(1) }
		MAX-ACCESS read-only
		STATUS current
		DESCRIPTION
		"accChd2100j5com11DoorStatusMonitor status."
		::= { accChd2100j5comEntry 12 }
accChd2100j5com13ManuallyLockTheDoor OBJECT-TYPE
		SYNTAX INTEGER {
			close(0),
			open(1) }
		MAX-ACCESS read-only
		STATUS current
		DESCRIPTION
		"accChd2100j5com12ManuallyLockTheDoor status."
		::= { accChd2100j5comEntry 13 }
accChd2100j5com14DeviceType OBJECT-TYPE
		SYNTAX INTEGER {
			unknowndevice(0),
			es2000(1),
			es5000(2),
			es5010(3),
			chd2100j3(4) }
		MAX-ACCESS read-only
		STATUS current
		DESCRIPTION
		"accChd2100j5com13DeviceType status."
		::= { accChd2100j5comEntry 14 }
accChd2100j5com15DoorStatus OBJECT-TYPE
		SYNTAX INTEGER {
			normal(0),
			overtimeisnotclosed(1) }
		MAX-ACCESS read-only
		STATUS current
		DESCRIPTION
		"accChd2100j5com14DoorStatus status."
		::= { accChd2100j5comEntry 15 }
accChd2100j5com16InfraredStatus OBJECT-TYPE
		SYNTAX INTEGER {
			normal(0),
			alarm(1) }
		MAX-ACCESS read-only
		STATUS current
		DESCRIPTION
		"accChd2100j5com15InfraredStatus status."
		::= { accChd2100j5comEntry 16 }
accChd2100j5com17InfraredMonitoringStatus OBJECT-TYPE
		SYNTAX INTEGER {
			close(0),
			open(1) }
		MAX-ACCESS read-only
		STATUS current
		DESCRIPTION
		"accChd2100j5com16InfraredMonitoringStatus status."
		::= { accChd2100j5comEntry 17 }
accChd2100j5com18DoorLable OBJECT-TYPE
		SYNTAX Integer32
		
		MAX-ACCESS read-only
		STATUS current
		DESCRIPTION
		"accChd2100j5com17DoorLable stored as 1."
		::= { accChd2100j5comEntry 18 }
accChd2100j5com19MaxNumberofDoorLockinCont OBJECT-TYPE
		SYNTAX Integer32
		
		MAX-ACCESS read-only
		STATUS current
		DESCRIPTION
		"accChd2100j5com18MaxNumberofDoorLockinCont stored as 1."
		::= { accChd2100j5comEntry 19 }
accChd2100j5com20PresentDoorLockNumber OBJECT-TYPE
		SYNTAX Integer32
		
		MAX-ACCESS read-only
		STATUS current
		DESCRIPTION
		"accChd2100j5com19PresentDoorLockNumber stored as 1."
		::= { accChd2100j5comEntry 20 }
accChd2100j5com21PresentDoorLockNumber OBJECT-TYPE
		SYNTAX Integer32
		
		MAX-ACCESS read-only
		STATUS current
		DESCRIPTION
		"accChd2100j5com20PresentDoorLockNumber stored as 1."
		::= { accChd2100j5comEntry 21 }
accChd2100j5com22RemoteOpenDoor OBJECT-TYPE
		SYNTAX INTEGER {
			true(0) }
		MAX-ACCESS read-write
		STATUS current
		DESCRIPTION
		"accChd2100j5com21RemoteOpenDoor status."
		::= { accChd2100j5comEntry 22 }
accChd2100j5com23AddUser OBJECT-TYPE
		SYNTAX INTEGER {
			true(0) }
		MAX-ACCESS read-write
		STATUS current
		DESCRIPTION
		"accChd2100j5com22AddUser status."
		::= { accChd2100j5comEntry 23 }
accChd2100j5com24DeleteUser OBJECT-TYPE
		SYNTAX INTEGER {
			true(0) }
		MAX-ACCESS read-write
		STATUS current
		DESCRIPTION
		"accChd2100j5com23DeleteUser status."
		::= { accChd2100j5comEntry 24 }
accChd2100j5com25DeleteAllUser OBJECT-TYPE
		SYNTAX INTEGER {
			true(0) }
		MAX-ACCESS read-write
		STATUS current
		DESCRIPTION
		"accChd2100j5com24DeleteAllUser status."
		::= { accChd2100j5comEntry 25 }
accChd2100j5com26SetTimeSection OBJECT-TYPE
		SYNTAX INTEGER {
			true(0) }
		MAX-ACCESS read-write
		STATUS current
		DESCRIPTION
		"accChd2100j5com25SetTimeSection status."
		::= { accChd2100j5comEntry 26 }
accChd2100j5com27SetTime OBJECT-TYPE
		SYNTAX INTEGER {
			true(0) }
		MAX-ACCESS read-write
		STATUS current
		DESCRIPTION
		"accChd2100j5com26SetTime status."
		::= { accChd2100j5comEntry 27 }
accChd2100j5com28ReadLogCount OBJECT-TYPE
		SYNTAX INTEGER {
			true(0) }
		MAX-ACCESS read-write
		STATUS current
		DESCRIPTION
		"accChd2100j5com27ReadLogCount status."
		::= { accChd2100j5comEntry 28 }
accChd2100j5com29GetLog OBJECT-TYPE
		SYNTAX INTEGER {
			true(0) }
		MAX-ACCESS read-write
		STATUS current
		DESCRIPTION
		"accChd2100j5com28GetLog status."
		::= { accChd2100j5comEntry 29 }
accChd2100j5com30UpdateUserInfo OBJECT-TYPE
		SYNTAX INTEGER {
			true(0) }
		MAX-ACCESS read-write
		STATUS current
		DESCRIPTION
		"accChd2100j5com29UpdateUserInfo status."
		::= { accChd2100j5comEntry 30 }
accChd2100j5com31QueryUserIDExist OBJECT-TYPE
		SYNTAX INTEGER {
			true(0) }
		MAX-ACCESS read-write
		STATUS current
		DESCRIPTION
		"accChd2100j5com30QueryUserIDExist status."
		::= { accChd2100j5comEntry 31 }
accChd2100j5com32QueryCardIDExist OBJECT-TYPE
		SYNTAX INTEGER {
			true(0) }
		MAX-ACCESS read-write
		STATUS current
		DESCRIPTION
		"accChd2100j5com31QueryCardIDExist status."
		::= { accChd2100j5comEntry 32 }
accChd2100j5com33SetAlwaysOpenTime OBJECT-TYPE
		SYNTAX INTEGER {
			true(0) }
		MAX-ACCESS read-write
		STATUS current
		DESCRIPTION
		"accChd2100j5com32SetAlwaysOpenTime status."
		::= { accChd2100j5comEntry 33 }
accChd2100j5com34SetCardAndPasswordTime OBJECT-TYPE
		SYNTAX INTEGER {
			true(0) }
		MAX-ACCESS read-write
		STATUS current
		DESCRIPTION
		"accChd2100j5com33SetCardAndPasswordTime status."
		::= { accChd2100j5comEntry 34 }
accChd2100j5com35SetInfraredMonitorTime OBJECT-TYPE
		SYNTAX INTEGER {
			true(0) }
		MAX-ACCESS read-write
		STATUS current
		DESCRIPTION
		"accChd2100j5com34SetInfraredMonitorTime status."
		::= { accChd2100j5comEntry 35 }
accChd2100j5com36GetUserCount OBJECT-TYPE
		SYNTAX INTEGER {
			true(0) }
		MAX-ACCESS read-write
		STATUS current
		DESCRIPTION
		"accChd2100j5com35GetUserCount status."
		::= { accChd2100j5comEntry 36 }
accChd2100j5com37GetAuthorizationList OBJECT-TYPE
		SYNTAX INTEGER {
			true(0) }
		MAX-ACCESS read-write
		STATUS current
		DESCRIPTION
		"accChd2100j5com36GetAuthorizationList status."
		::= { accChd2100j5comEntry 37 }
accChd2100j5com38CardAuthorization OBJECT-TYPE
		SYNTAX INTEGER {
			true(0) }
		MAX-ACCESS read-write
		STATUS current
		DESCRIPTION
		"accChd2100j5com37CardAuthorization status."
		::= { accChd2100j5comEntry 38 }
accChd2100j5com39DeleteUserCard OBJECT-TYPE
		SYNTAX INTEGER {
			true(0) }
		MAX-ACCESS read-write
		STATUS current
		DESCRIPTION
		"accChd2100j5com38DeleteUserCard status."
		::= { accChd2100j5comEntry 39 }
accChd2100j5com40DeleteUserID OBJECT-TYPE
		SYNTAX INTEGER {
			true(0) }
		MAX-ACCESS read-write
		STATUS current
		DESCRIPTION
		"accChd2100j5com39DeleteUserID status."
		::= { accChd2100j5comEntry 40 }
accChd2100j5com41DeleteAllUser OBJECT-TYPE
		SYNTAX INTEGER {
			true(0) }
		MAX-ACCESS read-write
		STATUS current
		DESCRIPTION
		"accChd2100j5com40DeleteAllUser status."
		::= { accChd2100j5comEntry 41 }
accChd2100j5com42Readversion OBJECT-TYPE
		SYNTAX INTEGER {
			true(0) }
		MAX-ACCESS read-write
		STATUS current
		DESCRIPTION
		"accChd2100j5com41Readversion status."
		::= { accChd2100j5comEntry 42 }
accChd2100j5com43Addfingerprintusers OBJECT-TYPE
		SYNTAX INTEGER {
			true(0) }
		MAX-ACCESS read-write
		STATUS current
		DESCRIPTION
		"accChd2100j5com42Addfingerprintusers status."
		::= { accChd2100j5comEntry 43 }
accChd2100j5com44Readfingerprintusers OBJECT-TYPE
		SYNTAX INTEGER {
			true(0) }
		MAX-ACCESS read-write
		STATUS current
		DESCRIPTION
		"accChd2100j5com43Readfingerprintusers status."
		::= { accChd2100j5comEntry 44 }
accChd2100j5com45Deletefingerprintuser OBJECT-TYPE
		SYNTAX INTEGER {
			true(0) }
		MAX-ACCESS read-write
		STATUS current
		DESCRIPTION
		"accChd2100j5com44Deletefingerprintuser status."
		::= { accChd2100j5comEntry 45 }
accChd2100j5com46Deletefingerprint OBJECT-TYPE
		SYNTAX INTEGER {
			true(0) }
		MAX-ACCESS read-write
		STATUS current
		DESCRIPTION
		"accChd2100j5com45Deletefingerprint status."
		::= { accChd2100j5comEntry 46 }
accChd2100j5com47Startupsettingsfingerprint OBJECT-TYPE
		SYNTAX INTEGER {
			true(0) }
		MAX-ACCESS read-write
		STATUS current
		DESCRIPTION
		"accChd2100j5com46Startupsettingsfingerprint status."
		::= { accChd2100j5comEntry 47 }
accChd2100j5com48Setfingerprint OBJECT-TYPE
		SYNTAX INTEGER {
			true(0) }
		MAX-ACCESS read-write
		STATUS current
		DESCRIPTION
		"accChd2100j5com47Setfingerprint status."
		::= { accChd2100j5comEntry 48 }
accChd2100j5com49Endsetfingerprint OBJECT-TYPE
		SYNTAX INTEGER {
			true(0) }
		MAX-ACCESS read-write
		STATUS current
		DESCRIPTION
		"accChd2100j5com48Endsetfingerprint status."
		::= { accChd2100j5comEntry 49 }
accChd2100j5com50Refreshfingerprintdata OBJECT-TYPE
		SYNTAX INTEGER {
			true(0) }
		MAX-ACCESS read-write
		STATUS current
		DESCRIPTION
		"accChd2100j5com49Refreshfingerprintdata status."
		::= { accChd2100j5comEntry 50 }
accChd2100j5com51Restorethefingerprintreader OBJECT-TYPE
		SYNTAX INTEGER {
			true(0) }
		MAX-ACCESS read-write
		STATUS current
		DESCRIPTION
		"accChd2100j5com50Restorethefingerprintreader status."
		::= { accChd2100j5comEntry 51 }
accChd2100j5com52Restorethefingerprintreader OBJECT-TYPE
		SYNTAX INTEGER {
			true(0) }
		MAX-ACCESS read-write
		STATUS current
		DESCRIPTION
		"accChd2100j5com51Restorethefingerprintreader status."
		::= { accChd2100j5comEntry 52 }
accChd2100j5com53SetRelayOpenTime OBJECT-TYPE
		SYNTAX Integer32
		
		MAX-ACCESS read-write
		STATUS current
		DESCRIPTION
		"accChd2100j5com52SetRelayOpenTime stored as 1s."
		::= { accChd2100j5comEntry 53 }
accChd2100j5com54MonitorDoorStatus OBJECT-TYPE
		SYNTAX INTEGER {
			close(0),
			open(1) }
		MAX-ACCESS read-write
		STATUS current
		DESCRIPTION
		"accChd2100j5com53MonitorDoorStatus status."
		::= { accChd2100j5comEntry 54 }
accChd2100j5com55NeedInputPassword OBJECT-TYPE
		SYNTAX INTEGER {
			notneed(0),
			need(1) }
		MAX-ACCESS read-write
		STATUS current
		DESCRIPTION
		"accChd2100j5com54NeedInputPassword status."
		::= { accChd2100j5comEntry 55 }
accChd2100j5com56EnableManualButton OBJECT-TYPE
		SYNTAX INTEGER {
			open(0),
			close(1) }
		MAX-ACCESS read-write
		STATUS current
		DESCRIPTION
		"accChd2100j5com55EnableManualButton status."
		::= { accChd2100j5comEntry 56 }
accChd2100j5com57EnableKeyboardOpen OBJECT-TYPE
		SYNTAX INTEGER {
			close(0),
			open(1) }
		MAX-ACCESS read-write
		STATUS current
		DESCRIPTION
		"accChd2100j5com56EnableKeyboardOpen status."
		::= { accChd2100j5comEntry 57 }
accChd2100j5com58Setsingleordoublecarddoor OBJECT-TYPE
		SYNTAX INTEGER {
			singlecard(0),
			doublecard(1) }
		MAX-ACCESS read-write
		STATUS current
		DESCRIPTION
		"accChd2100j5com57Setsingleordoublecarddoor status."
		::= { accChd2100j5comEntry 58 }
accChd2100j5com59Infraredalarmconfirmationtim OBJECT-TYPE
		SYNTAX Integer32
		
		MAX-ACCESS read-write
		STATUS current
		DESCRIPTION
		"accChd2100j5com58Infraredalarmconfirmationtim stored as 1s."
		::= { accChd2100j5comEntry 59 }
accChd2100j5com60Infraredmonitoringstatus OBJECT-TYPE
		SYNTAX INTEGER {
			close(0),
			open(1) }
		MAX-ACCESS read-write
		STATUS current
		DESCRIPTION
		"accChd2100j5com59Infraredmonitoringstatus status."
		::= { accChd2100j5comEntry 60 }
accChd2100j5com61Magneticlevelsensor OBJECT-TYPE
		SYNTAX INTEGER {
			close(0),
			open(1) }
		MAX-ACCESS read-write
		STATUS current
		DESCRIPTION
		"accChd2100j5com60Magneticlevelsensor status."
		::= { accChd2100j5comEntry 61 }
accChd2100j5com62Infraredsensorlevel OBJECT-TYPE
		SYNTAX INTEGER {
			close(0),
			open(1) }
		MAX-ACCESS read-write
		STATUS current
		DESCRIPTION
		"accChd2100j5com61Infraredsensorlevel status."
		::= { accChd2100j5comEntry 62 }
accChd2100j5com63Entertheemergencyaction OBJECT-TYPE
		SYNTAX INTEGER {
			open(0),
			close(1) }
		MAX-ACCESS read-write
		STATUS current
		DESCRIPTION
		"accChd2100j5com62Entertheemergencyaction status."
		::= { accChd2100j5comEntry 63 }
accChd2100j5com64ALARMoutputwhenthealarmact OBJECT-TYPE
		SYNTAX INTEGER {
			close(0),
			open(1) }
		MAX-ACCESS read-write
		STATUS current
		DESCRIPTION
		"accChd2100j5com63ALARMoutputwhenthealarmact status."
		::= { accChd2100j5comEntry 64 }
accChd2100j5com65Passwordtimecontrol OBJECT-TYPE
		SYNTAX INTEGER {
			alwaysneed(0),
			bytime(1) }
		MAX-ACCESS read-write
		STATUS current
		DESCRIPTION
		"accChd2100j5com64Passwordtimecontrol status."
		::= { accChd2100j5comEntry 65 }
accChd2100j5com66Doorcardpasswordtest OBJECT-TYPE
		SYNTAX INTEGER {
			notneed(0),
			need(1) }
		MAX-ACCESS read-write
		STATUS current
		DESCRIPTION
		"accChd2100j5com65Doorcardpasswordtest status."
		::= { accChd2100j5comEntry 66 }
accChd2100j5com67Checkoutcreditcardpassword OBJECT-TYPE
		SYNTAX INTEGER {
			notneed(0),
			need(1) }
		MAX-ACCESS read-write
		STATUS current
		DESCRIPTION
		"accChd2100j5com66Checkoutcreditcardpassword status."
		::= { accChd2100j5comEntry 67 }
accChd2100j5com68Tosetfingerprint1readeraddr OBJECT-TYPE
		SYNTAX Integer32
		
		MAX-ACCESS read-write
		STATUS current
		DESCRIPTION
		"accChd2100j5com67Tosetfingerprint1readeraddr stored as 1."
		::= { accChd2100j5comEntry 68 }
accChd2100j5com69Fingerprintreader1address OBJECT-TYPE
		SYNTAX Integer32
		
		MAX-ACCESS read-write
		STATUS current
		DESCRIPTION
		"accChd2100j5com68Fingerprintreader1address stored as 1."
		::= { accChd2100j5comEntry 69 }
accChd2100j5com70Addressfingerprintreader OBJECT-TYPE
		SYNTAX Integer32
		
		MAX-ACCESS read-write
		STATUS current
		DESCRIPTION
		"accChd2100j5com69Addressfingerprintreader stored as 1."
		::= { accChd2100j5comEntry 70 }
accChd2100j5com71Fingerprintreaderwork OBJECT-TYPE
		SYNTAX Integer32
		
		MAX-ACCESS read-write
		STATUS current
		DESCRIPTION
		"accChd2100j5com70Fingerprintreaderwork stored as 1."
		::= { accChd2100j5comEntry 71 }
accChd2100j5com72Fingerprintreaderwork OBJECT-TYPE
		SYNTAX Integer32
		
		MAX-ACCESS read-write
		STATUS current
		DESCRIPTION
		"accChd2100j5com71Fingerprintreaderwork stored as 1."
		::= { accChd2100j5comEntry 72 }

------------------------------------------------------------
-- Firefighting { 13400.3.5.559 }
------------------------------------------------------------
env-Firefighting OBJECT IDENTIFIER ::= { env 559 }
envFirefightingTable OBJECT-TYPE
		SYNTAX			SEQUENCE OF EnvFirefightingEntry
		MAX-ACCESS		not-accessible
		STATUS			current
		DESCRIPTION	"envFirefightingTable"
		::=			{ env-Firefighting 1 }
envFirefightingEntry OBJECT-TYPE
		SYNTAX			EnvFirefightingEntry
		MAX-ACCESS		not-accessible
		STATUS			current
		DESCRIPTION		"envFirefightingEntry"
		INDEX			{ envFirefightingIndex }
		::=				{ envFirefightingTable 1 }
EnvFirefightingEntry ::= SEQUENCE {
		envFirefightingIndex					Integer32,
		envFirefighting2FireAlarmStatus					INTEGER,
		envFirefighting3FireSensor4DICommStatus					INTEGER,
		envFirefighting4FireAlarmStausAlarmCriterio					INTEGER }
envFirefightingIndex OBJECT-TYPE
		SYNTAX Integer32(1..4)
		MAX-ACCESS read-only
		STATUS current
		DESCRIPTION
		"envFirefighting System Entry Index."
		::= { envFirefightingEntry 1 }
envFirefighting2FireAlarmStatus OBJECT-TYPE
		SYNTAX INTEGER {
			normal(0),
			alarm(1),
			uninstalled(2),
			leave(3) }
		MAX-ACCESS read-only
		STATUS current
		DESCRIPTION
		"envFirefighting1FireAlarmStatus status."
		::= { envFirefightingEntry 2 }
envFirefighting3FireSensor4DICommStatus OBJECT-TYPE
		SYNTAX INTEGER {
			normal(0),
			failure(1) }
		MAX-ACCESS read-only
		STATUS current
		DESCRIPTION
		"envFirefighting2FireSensor4DICommStatus status."
		::= { envFirefightingEntry 3 }
envFirefighting4FireAlarmStausAlarmCriterio OBJECT-TYPE
		SYNTAX INTEGER {
			open(0),
			close(1) }
		MAX-ACCESS read-write
		STATUS current
		DESCRIPTION
		"envFirefighting3FireAlarmStausAlarmCriterio status."
		::= { envFirefightingEntry 4 }



------------------------------------------------------------
-- System Alarm Trap Table { 13400.3.254 }
------------------------------------------------------------
		
systemAlarmTrapTable OBJECT-TYPE
	SYNTAX SEQUENCE OF SystemAlarmTrapEntry
	MAX-ACCESS not-accessible
	STATUS current
	DESCRIPTION "System Table holding information about the submitted alarm traps."
	::= { dcs 254 }

systemAlarmTrapEntry OBJECT-TYPE
	SYNTAX SystemAlarmTrapEntry
	MAX-ACCESS not-accessible
	STATUS current
	DESCRIPTION "An entry (conceptual row) in the systemAlarmTrapTable."
	INDEX { systemAlarmIndex }
	::= { systemAlarmTrapTable 1 }

SystemAlarmTrapEntry ::= SEQUENCE {
	systemAlarmIndex 			Counter32,
	systemAlarmTime 			DisplayString,
	systemAlarmStatusChange 	AlarmStatusChange,
	systemAlarmSeverity 		AlarmSeverity,
	systemAlarmDescription 		DisplayString,
	systemAlarmId 				Integer32,
	systemAlarmEquipId 			Integer32,
	systemAlarmEquipTypeId		Integer32}

systemAlarmIndex OBJECT-TYPE
	SYNTAX Counter32
	MAX-ACCESS read-only
	STATUS current
	DESCRIPTION "The unique sequence number of this alarm trap."
	::= { systemAlarmTrapEntry 1 }

systemAlarmTime OBJECT-TYPE
	SYNTAX DisplayString
	MAX-ACCESS read-only
	STATUS current
	DESCRIPTION "Local date and time when event occured, format as YYYY-MM-DD hh:mm:ss."
	::= { systemAlarmTrapEntry 2 }

systemAlarmStatusChange OBJECT-TYPE
	SYNTAX AlarmStatusChange
	MAX-ACCESS read-only
	STATUS current
	DESCRIPTION "Indicates 'activated' (0) or 'deactivated' (1) alarm events."
	::= { systemAlarmTrapEntry 3 }

systemAlarmSeverity OBJECT-TYPE
	SYNTAX AlarmSeverity
	MAX-ACCESS read-only
	STATUS current
	DESCRIPTION "The severity of the alarm. One of
		(1) informational
		(2) warning
		(3) critical"
	::= { systemAlarmTrapEntry 4 }
	
systemAlarmDescription OBJECT-TYPE
	SYNTAX DisplayString
	MAX-ACCESS read-only
	STATUS current
	DESCRIPTION "Free-text description of alarm."
	::= { systemAlarmTrapEntry 5 }
	
systemAlarmId OBJECT-TYPE
	SYNTAX Integer32
	MAX-ACCESS read-only
	STATUS current
	DESCRIPTION "Alarm id."
	::= { systemAlarmTrapEntry 6 }
	
systemAlarmEquipId OBJECT-TYPE
	SYNTAX Integer32
	MAX-ACCESS read-only
	STATUS current
	DESCRIPTION "Alarm equipment id."
	::= { systemAlarmTrapEntry 7 }	

systemAlarmEquipTypeId OBJECT-TYPE
	SYNTAX Integer32
	MAX-ACCESS read-only
	STATUS current
	DESCRIPTION "Alarm equipment type id."
	::= { systemAlarmTrapEntry 8 }
	
	
------------------------------------------------------------
-- System Alarm Trap { 13400.3.255 }
------------------------------------------------------------

systemAlarmTrap OBJECT IDENTIFIER ::= { dcs 255 }

systemAlarmTrapDefine NOTIFICATION-TYPE
	OBJECTS {
		systemAlarmIndex,
		systemAlarmTime,
		systemAlarmStatusChange,
		systemAlarmSeverity,
		systemAlarmDescription,
		systemAlarmId,
		systemAlarmEquipId,
		systemAlarmEquipTypeId }
	STATUS current
	DESCRIPTION "
		An alarm trap is sent when an alarm occurs (activated) or
		returns to normal state (deactivated). Alarm traps are logged
		in alarmTrapTable. Variables in this trap:
		* systemAlarmIndex - The unique sequence number of this alarm trap.
		* systemAlarmTime - Date and time when event occured (local time).
		* systemAlarmStatusChange - (0) activated or (1) deactivated.
		* systemAlarmSeverity - The severity of the alarm..
		* systemAlarmId - Alarm id.
		* systemAlarmEquipId - Alarm equipment id.
		* systemAlarmEquipTypeId - Alarm equipment type id."
	::= { systemAlarmTrap 1 }
	
	
------------------------------------------------------------
-- End of MIB definitions
------------------------------------------------------------
END
