--  ============================================================================
-- AT-ENVMONv2-MIB, Allied Telesis enterprise MIB:
-- Environment Monitoring MIB objects.
-- 
-- Copyright (c) 2008 by Allied Telesis, Inc.
-- All rights reserved.
-- 
-- ============================================================================

	AT-ENVMONv2-MIB DEFINITIONS ::= BEGIN
 
		IMPORTS
			DisplayStringUnsized			
				FROM AT-SMI-MIB			
			sysinfo			
				FROM AT-SYSINFO-MIB			
			Unsigned32, OBJECT-TYPE, MODULE-IDENTITY, NOTIFICATION-TYPE			
				FROM SNMPv2-SMI;			
	
	
		-- 1.3.6.1.4.1.207.8.4.4.3.12
		atEnvMonv2 MODULE-IDENTITY 
			LAST-UPDATED "200811260000Z"		-- November 26, 2008 at 00:00 GMT
			ORGANIZATION 
				"Allied Telesis, Inc"
			CONTACT-INFO 
				"http://www.alliedtelesis.com"
			DESCRIPTION 
				"The AT Environment Monitoring v2 MIB for managing and
				reporting data relating to voltage rails, fan speeds,
				temperature sensors and power supply units."
			REVISION "200811260000Z"		-- November 26, 2008 at 00:00 GMT
			DESCRIPTION 
				"Removed recently added MIB objects that went against the
				original intent of the environment monitoring MIB."
			REVISION "200809240000Z"		-- September 24, 2008 at 00:00 GMT
			DESCRIPTION 
				"Appended v2 to all object names to clarify
				version number of this mib."
			REVISION "200802070000Z"		-- February 07, 2008 at 00:00 GMT
			DESCRIPTION 
				"Initial Revision"
			::= { sysinfo 12 }

		
	
--
-- Textual conventions
--
	
--  Textual Conventions
		AtEnvMonv2PsbSensorType ::= TEXTUAL-CONVENTION
			STATUS current
			DESCRIPTION 
				"Indicates the type of a Power Supply Bay Device sensor."
			SYNTAX INTEGER
				{
					psbSensorTypeInvalid(0),
					fanSpeedDiscrete(1),
					temperatureDiscrete(2),
					voltageDiscrete(3)
				}

--
-- Node definitions
--
	
--   This section of the MIB contains new generic environment monitoring
-- data. It relates to temperature, fanspeed, voltage and power supply
-- bay device monitors.
-- ---------------------------------------------------------- --
-- The Environment Monitoring Fan Table
-- ---------------------------------------------------------- --
		-- 1.3.6.1.4.1.207.8.4.4.3.12.1
		atEnvMonv2FanTable OBJECT-TYPE
			SYNTAX SEQUENCE OF AtEnvMonv2FanEntry
			MAX-ACCESS not-accessible
			STATUS current
			DESCRIPTION
				"A table of information about fans installed in the device
				that have their fan speeds monitored by environment
				monitoring hardware."
			::= { atEnvMonv2 1 }

		
		-- 1.3.6.1.4.1.207.8.4.4.3.12.1.1
		atEnvMonv2FanEntry OBJECT-TYPE
			SYNTAX AtEnvMonv2FanEntry
			MAX-ACCESS not-accessible
			STATUS current
			DESCRIPTION
				"The description, current speed, lower threshold speed and
				current status of a fan."
			INDEX { atEnvMonv2FanStackMemberId, atEnvMonv2FanBoardIndex, atEnvMonv2FanIndex }
			::= { atEnvMonv2FanTable 1 }

		
		AtEnvMonv2FanEntry ::=
			SEQUENCE { 
				atEnvMonv2FanStackMemberId
					Unsigned32,
				atEnvMonv2FanBoardIndex
					Unsigned32,
				atEnvMonv2FanIndex
					Unsigned32,
				atEnvMonv2FanDescription
					DisplayStringUnsized,
				atEnvMonv2FanCurrentSpeed
					Unsigned32,
				atEnvMonv2FanLowerThreshold
					Unsigned32,
				atEnvMonv2FanStatus
					INTEGER
			 }

		-- 1.3.6.1.4.1.207.8.4.4.3.12.1.1.1
		atEnvMonv2FanStackMemberId OBJECT-TYPE
			SYNTAX Unsigned32
			MAX-ACCESS read-only
			STATUS current
			DESCRIPTION
				"The index of the stack member hosting this fan."
			::= { atEnvMonv2FanEntry 1 }

		
		-- 1.3.6.1.4.1.207.8.4.4.3.12.1.1.2
		atEnvMonv2FanBoardIndex OBJECT-TYPE
			SYNTAX Unsigned32
			MAX-ACCESS read-only
			STATUS current
			DESCRIPTION
				"The index of the board hosting this fan in the board table."
			::= { atEnvMonv2FanEntry 2 }

		
		-- 1.3.6.1.4.1.207.8.4.4.3.12.1.1.3
		atEnvMonv2FanIndex OBJECT-TYPE
			SYNTAX Unsigned32
			MAX-ACCESS read-only
			STATUS current
			DESCRIPTION
				"The numeric identifier of this fan on its host board."
			::= { atEnvMonv2FanEntry 3 }

		
		-- 1.3.6.1.4.1.207.8.4.4.3.12.1.1.4
		atEnvMonv2FanDescription OBJECT-TYPE
			SYNTAX DisplayStringUnsized (SIZE (0..30))
			MAX-ACCESS read-only
			STATUS current
			DESCRIPTION
				"The description of this fan."
			::= { atEnvMonv2FanEntry 4 }

		
		-- 1.3.6.1.4.1.207.8.4.4.3.12.1.1.5
		atEnvMonv2FanCurrentSpeed OBJECT-TYPE
			SYNTAX Unsigned32
			MAX-ACCESS read-only
			STATUS current
			DESCRIPTION
				"The current speed of this fan in revolutions per
				minute."
			::= { atEnvMonv2FanEntry 5 }

		
		-- 1.3.6.1.4.1.207.8.4.4.3.12.1.1.6
		atEnvMonv2FanLowerThreshold OBJECT-TYPE
			SYNTAX Unsigned32
			MAX-ACCESS read-only
			STATUS current
			DESCRIPTION
				"The minimum acceptable speed of the fan in revolutions
				per minute."
			::= { atEnvMonv2FanEntry 6 }

		
		-- 1.3.6.1.4.1.207.8.4.4.3.12.1.1.7
		atEnvMonv2FanStatus OBJECT-TYPE
			SYNTAX INTEGER
			{
				failed(1),
				good(2)
			}
			MAX-ACCESS read-only
			STATUS current
			DESCRIPTION
				"An indication of whether this fan is currently in an
				alarm condition. A value of 'failed' indicates that its
				current speed is too low, 'good' indicates that the
				current speed is acceptable."
			::= { atEnvMonv2FanEntry 7 }

		
--  ---------------------------------------------------------- --
-- The Environment Monitoring Voltage Table
-- ---------------------------------------------------------- --
		-- 1.3.6.1.4.1.207.8.4.4.3.12.2
		atEnvMonv2VoltageTable OBJECT-TYPE
			SYNTAX SEQUENCE OF AtEnvMonv2VoltageEntry
			MAX-ACCESS not-accessible
			STATUS current
			DESCRIPTION
				"A table of information about voltage rails in the device
				that are monitored by environment monitoring hardware."
			::= { atEnvMonv2 2 }

		
		-- 1.3.6.1.4.1.207.8.4.4.3.12.2.1
		atEnvMonv2VoltageEntry OBJECT-TYPE
			SYNTAX AtEnvMonv2VoltageEntry
			MAX-ACCESS not-accessible
			STATUS current
			DESCRIPTION
				"The description, current value, upper & lower threshold
				settings and current status of a voltage rail."
			INDEX { atEnvMonv2VoltageStackMemberId, atEnvMonv2VoltageBoardIndex, atEnvMonv2VoltageIndex }
			::= { atEnvMonv2VoltageTable 1 }

		
		AtEnvMonv2VoltageEntry ::=
			SEQUENCE { 
				atEnvMonv2VoltageStackMemberId
					Unsigned32,
				atEnvMonv2VoltageBoardIndex
					Unsigned32,
				atEnvMonv2VoltageIndex
					Unsigned32,
				atEnvMonv2VoltageDescription
					DisplayStringUnsized,
				atEnvMonv2VoltageCurrent
					INTEGER,
				atEnvMonv2VoltageUpperThreshold
					INTEGER,
				atEnvMonv2VoltageLowerThreshold
					INTEGER,
				atEnvMonv2VoltageStatus
					INTEGER
			 }

		-- 1.3.6.1.4.1.207.8.4.4.3.12.2.1.1
		atEnvMonv2VoltageStackMemberId OBJECT-TYPE
			SYNTAX Unsigned32
			MAX-ACCESS read-only
			STATUS current
			DESCRIPTION
				"The index of the stack member hosting this voltage sensor."
			::= { atEnvMonv2VoltageEntry 1 }

		
		-- 1.3.6.1.4.1.207.8.4.4.3.12.2.1.2
		atEnvMonv2VoltageBoardIndex OBJECT-TYPE
			SYNTAX Unsigned32
			MAX-ACCESS read-only
			STATUS current
			DESCRIPTION
				"The index of the board hosting this voltage sensor in the board table."
			::= { atEnvMonv2VoltageEntry 2 }

		
		-- 1.3.6.1.4.1.207.8.4.4.3.12.2.1.3
		atEnvMonv2VoltageIndex OBJECT-TYPE
			SYNTAX Unsigned32
			MAX-ACCESS read-only
			STATUS current
			DESCRIPTION
				"The numeric identifier of this voltage rail on its host board."
			::= { atEnvMonv2VoltageEntry 3 }

		
		-- 1.3.6.1.4.1.207.8.4.4.3.12.2.1.4
		atEnvMonv2VoltageDescription OBJECT-TYPE
			SYNTAX DisplayStringUnsized (SIZE (0..30))
			MAX-ACCESS read-only
			STATUS current
			DESCRIPTION
				"The description of this voltage rail."
			::= { atEnvMonv2VoltageEntry 4 }

		
		-- 1.3.6.1.4.1.207.8.4.4.3.12.2.1.5
		atEnvMonv2VoltageCurrent OBJECT-TYPE
			SYNTAX INTEGER
			MAX-ACCESS read-only
			STATUS current
			DESCRIPTION
				"The current reading of this voltage rail in millivolts."
			::= { atEnvMonv2VoltageEntry 5 }

		
		-- 1.3.6.1.4.1.207.8.4.4.3.12.2.1.6
		atEnvMonv2VoltageUpperThreshold OBJECT-TYPE
			SYNTAX INTEGER
			MAX-ACCESS read-only
			STATUS current
			DESCRIPTION
				"The maximum acceptable reading of this voltage rail in millivolts."
			::= { atEnvMonv2VoltageEntry 6 }

		
		-- 1.3.6.1.4.1.207.8.4.4.3.12.2.1.7
		atEnvMonv2VoltageLowerThreshold OBJECT-TYPE
			SYNTAX INTEGER
			MAX-ACCESS read-only
			STATUS current
			DESCRIPTION
				"The minimum acceptable reading of this voltage rail in millivolts."
			::= { atEnvMonv2VoltageEntry 7 }

		
		-- 1.3.6.1.4.1.207.8.4.4.3.12.2.1.8
		atEnvMonv2VoltageStatus OBJECT-TYPE
			SYNTAX INTEGER
			{
				outOfRange(1),
				inRange(2)
			}
			MAX-ACCESS read-only
			STATUS current
			DESCRIPTION
				"An indication of whether this voltage rail is currently
				in an alarm condition. A value of 'outOfRange' indicates that
				its current reading is outside its threshold range,
				'inRange' indicates that the current reading is acceptable."
			::= { atEnvMonv2VoltageEntry 8 }

		
--  ---------------------------------------------------------- --
-- The Environment Monitoring Temperature Table
-- ---------------------------------------------------------- --
		-- 1.3.6.1.4.1.207.8.4.4.3.12.3
		atEnvMonv2TemperatureTable OBJECT-TYPE
			SYNTAX SEQUENCE OF AtEnvMonv2TemperatureEntry
			MAX-ACCESS not-accessible
			STATUS current
			DESCRIPTION
				"A table of information about temperature sensors in the device
				that are monitored by environment monitoring hardware."
			::= { atEnvMonv2 3 }

		
		-- 1.3.6.1.4.1.207.8.4.4.3.12.3.1
		atEnvMonv2TemperatureEntry OBJECT-TYPE
			SYNTAX AtEnvMonv2TemperatureEntry
			MAX-ACCESS not-accessible
			STATUS current
			DESCRIPTION
				"The description, current value, upper threshold setting
				and current status of a temperature sensor."
			INDEX { atEnvMonv2TemperatureStackMemberId, atEnvMonv2TemperatureBoardIndex, atEnvMonv2TemperatureIndex }
			::= { atEnvMonv2TemperatureTable 1 }

		
		AtEnvMonv2TemperatureEntry ::=
			SEQUENCE { 
				atEnvMonv2TemperatureStackMemberId
					Unsigned32,
				atEnvMonv2TemperatureBoardIndex
					Unsigned32,
				atEnvMonv2TemperatureIndex
					Unsigned32,
				atEnvMonv2TemperatureDescription
					DisplayStringUnsized,
				atEnvMonv2TemperatureCurrent
					INTEGER,
				atEnvMonv2TemperatureUpperThreshold
					INTEGER,
				atEnvMonv2TemperatureStatus
					INTEGER
			 }

		-- 1.3.6.1.4.1.207.8.4.4.3.12.3.1.1
		atEnvMonv2TemperatureStackMemberId OBJECT-TYPE
			SYNTAX Unsigned32
			MAX-ACCESS read-only
			STATUS current
			DESCRIPTION
				"The index of the stack member hosting this temperature sensor."
			::= { atEnvMonv2TemperatureEntry 1 }

		
		-- 1.3.6.1.4.1.207.8.4.4.3.12.3.1.2
		atEnvMonv2TemperatureBoardIndex OBJECT-TYPE
			SYNTAX Unsigned32
			MAX-ACCESS read-only
			STATUS current
			DESCRIPTION
				"The index of the board hosting this temperature sensor in the board table."
			::= { atEnvMonv2TemperatureEntry 2 }

		
		-- 1.3.6.1.4.1.207.8.4.4.3.12.3.1.3
		atEnvMonv2TemperatureIndex OBJECT-TYPE
			SYNTAX Unsigned32
			MAX-ACCESS read-only
			STATUS current
			DESCRIPTION
				"The numeric identifier of this temperature sensor on its host board."
			::= { atEnvMonv2TemperatureEntry 3 }

		
		-- 1.3.6.1.4.1.207.8.4.4.3.12.3.1.4
		atEnvMonv2TemperatureDescription OBJECT-TYPE
			SYNTAX DisplayStringUnsized (SIZE (0..30))
			MAX-ACCESS read-only
			STATUS current
			DESCRIPTION
				"The description of this temperature sensor."
			::= { atEnvMonv2TemperatureEntry 4 }

		
		-- 1.3.6.1.4.1.207.8.4.4.3.12.3.1.5
		atEnvMonv2TemperatureCurrent OBJECT-TYPE
			SYNTAX INTEGER
			MAX-ACCESS read-only
			STATUS current
			DESCRIPTION
				"The current reading of this temperature sensor in tenths of a degree Celsius."
			::= { atEnvMonv2TemperatureEntry 5 }

		
		-- 1.3.6.1.4.1.207.8.4.4.3.12.3.1.6
		atEnvMonv2TemperatureUpperThreshold OBJECT-TYPE
			SYNTAX INTEGER
			MAX-ACCESS read-only
			STATUS current
			DESCRIPTION
				"The maximum acceptable reading of this temperature
				sensor in tenths of a degree Celsius."
			::= { atEnvMonv2TemperatureEntry 6 }

		
		-- 1.3.6.1.4.1.207.8.4.4.3.12.3.1.7
		atEnvMonv2TemperatureStatus OBJECT-TYPE
			SYNTAX INTEGER
			{
				outOfRange(1),
				inRange(2)
			}
			MAX-ACCESS read-only
			STATUS current
			DESCRIPTION
				"An indication of whether this temperature sensor is
				currently in an alarm condition. A value of 'outOfRange'
				indicates that its current reading is outside its threshold
				range, 'inRange' indicates that the current reading is
				acceptable."
			::= { atEnvMonv2TemperatureEntry 7 }

		
--  ---------------------------------------------------------- --
-- The Environment Monitoring Power Supply Bay Device Table
-- ---------------------------------------------------------- --
		-- 1.3.6.1.4.1.207.8.4.4.3.12.4
		atEnvMonv2PsbObjects OBJECT IDENTIFIER::= { atEnvMonv2 4 }

		
		-- 1.3.6.1.4.1.207.8.4.4.3.12.4.1
		atEnvMonv2PsbTable OBJECT-TYPE
			SYNTAX SEQUENCE OF AtEnvMonv2PsbEntry
			MAX-ACCESS not-accessible
			STATUS current
			DESCRIPTION
				"A table of information about power supply bays in the system and
				any devices that are installed."
			::= { atEnvMonv2PsbObjects 1 }

		
		-- 1.3.6.1.4.1.207.8.4.4.3.12.4.1.1
		atEnvMonv2PsbEntry OBJECT-TYPE
			SYNTAX AtEnvMonv2PsbEntry
			MAX-ACCESS not-accessible
			STATUS current
			DESCRIPTION
				"The description and current status of a power supply
				bay device."
			INDEX { atEnvMonv2PsbHostStackMemberId, atEnvMonv2PsbHostBoardIndex, atEnvMonv2PsbHostSlotIndex }
			::= { atEnvMonv2PsbTable 1 }

		
		AtEnvMonv2PsbEntry ::=
			SEQUENCE { 
				atEnvMonv2PsbHostStackMemberId
					Unsigned32,
				atEnvMonv2PsbHostBoardIndex
					Unsigned32,
				atEnvMonv2PsbHostSlotIndex
					Unsigned32,
				atEnvMonv2PsbHeldBoardIndex
					Unsigned32,
				atEnvMonv2PsbHeldBoardId
					OBJECT IDENTIFIER,
				atEnvMonv2PsbDescription
					DisplayStringUnsized
			 }

		-- 1.3.6.1.4.1.207.8.4.4.3.12.4.1.1.1
		atEnvMonv2PsbHostStackMemberId OBJECT-TYPE
			SYNTAX Unsigned32
			MAX-ACCESS read-only
			STATUS current
			DESCRIPTION
				"The index of the stack member hosting this power supply bay."
			::= { atEnvMonv2PsbEntry 1 }

		
		-- 1.3.6.1.4.1.207.8.4.4.3.12.4.1.1.2
		atEnvMonv2PsbHostBoardIndex OBJECT-TYPE
			SYNTAX Unsigned32
			MAX-ACCESS read-only
			STATUS current
			DESCRIPTION
				"The index of the board hosting this power supply bay in the board table."
			::= { atEnvMonv2PsbEntry 2 }

		
		-- 1.3.6.1.4.1.207.8.4.4.3.12.4.1.1.3
		atEnvMonv2PsbHostSlotIndex OBJECT-TYPE
			SYNTAX Unsigned32
			MAX-ACCESS read-only
			STATUS current
			DESCRIPTION
				"The index of this power supply bay on its host board.
				This index is fixed for each slot, on each type of board."
			::= { atEnvMonv2PsbEntry 3 }

		
		-- 1.3.6.1.4.1.207.8.4.4.3.12.4.1.1.4
		atEnvMonv2PsbHeldBoardIndex OBJECT-TYPE
			SYNTAX Unsigned32
			MAX-ACCESS read-only
			STATUS current
			DESCRIPTION
				"The index of a board installed in this power supply bay.
				This value corresponds to atEnvMonv2PsbSensorBoardIndex for
				each sensor on this board. A value of 0 indicates that a
				board is is either not present or not supported."
			::= { atEnvMonv2PsbEntry 4 }

		
		-- 1.3.6.1.4.1.207.8.4.4.3.12.4.1.1.5
		atEnvMonv2PsbHeldBoardId OBJECT-TYPE
			SYNTAX OBJECT IDENTIFIER
			MAX-ACCESS read-only
			STATUS current
			DESCRIPTION
				"The type of board installed in this power supply bay. The
				values of this object are taken from the pprXxx object IDs
				under the boards sub-tree in the parent MIB. A value of 0
				indicates that a board is either not present or not
				supported."
			::= { atEnvMonv2PsbEntry 5 }

		
		-- 1.3.6.1.4.1.207.8.4.4.3.12.4.1.1.6
		atEnvMonv2PsbDescription OBJECT-TYPE
			SYNTAX DisplayStringUnsized (SIZE (0..30))
			MAX-ACCESS read-only
			STATUS current
			DESCRIPTION
				"The description of this power supply bay."
			::= { atEnvMonv2PsbEntry 6 }

		
		-- 1.3.6.1.4.1.207.8.4.4.3.12.4.2
		atEnvMonv2PsbSensorTable OBJECT-TYPE
			SYNTAX SEQUENCE OF AtEnvMonv2PsbSensorEntry
			MAX-ACCESS not-accessible
			STATUS current
			DESCRIPTION
				"A table of information about environment monitoring sensors
				on devices installed in power supply bays."
			::= { atEnvMonv2PsbObjects 2 }

		
		-- 1.3.6.1.4.1.207.8.4.4.3.12.4.2.1
		atEnvMonv2PsbSensorEntry OBJECT-TYPE
			SYNTAX AtEnvMonv2PsbSensorEntry
			MAX-ACCESS not-accessible
			STATUS current
			DESCRIPTION
				"The description and current status of a device installed
				in a power supply bay."
			INDEX { atEnvMonv2PsbSensorStackMemberId, atEnvMonv2PsbSensorBoardIndex, atEnvMonv2PsbSensorIndex }
			::= { atEnvMonv2PsbSensorTable 1 }

		
		AtEnvMonv2PsbSensorEntry ::=
			SEQUENCE { 
				atEnvMonv2PsbSensorStackMemberId
					Unsigned32,
				atEnvMonv2PsbSensorBoardIndex
					Unsigned32,
				atEnvMonv2PsbSensorIndex
					Unsigned32,
				atEnvMonv2PsbSensorType
					AtEnvMonv2PsbSensorType,
				atEnvMonv2PsbSensorDescription
					DisplayStringUnsized,
				atEnvMonv2PsbSensorStatus
					INTEGER
			 }

		-- 1.3.6.1.4.1.207.8.4.4.3.12.4.2.1.1
		atEnvMonv2PsbSensorStackMemberId OBJECT-TYPE
			SYNTAX Unsigned32
			MAX-ACCESS read-only
			STATUS current
			DESCRIPTION
				"The index of the stack member hosting this sensor."
			::= { atEnvMonv2PsbSensorEntry 1 }

		
		-- 1.3.6.1.4.1.207.8.4.4.3.12.4.2.1.2
		atEnvMonv2PsbSensorBoardIndex OBJECT-TYPE
			SYNTAX Unsigned32
			MAX-ACCESS read-only
			STATUS current
			DESCRIPTION
				"The index of the board hosting this sensor in the board table."
			::= { atEnvMonv2PsbSensorEntry 2 }

		
		-- 1.3.6.1.4.1.207.8.4.4.3.12.4.2.1.3
		atEnvMonv2PsbSensorIndex OBJECT-TYPE
			SYNTAX Unsigned32
			MAX-ACCESS read-only
			STATUS current
			DESCRIPTION
				"The index of this power supply bay environmental sensor on
				its host board."
			::= { atEnvMonv2PsbSensorEntry 3 }

		
		-- 1.3.6.1.4.1.207.8.4.4.3.12.4.2.1.4
		atEnvMonv2PsbSensorType OBJECT-TYPE
			SYNTAX AtEnvMonv2PsbSensorType
			MAX-ACCESS read-only
			STATUS current
			DESCRIPTION
				"The type of environmental variable this sensor detects."
			::= { atEnvMonv2PsbSensorEntry 4 }

		
		-- 1.3.6.1.4.1.207.8.4.4.3.12.4.2.1.5
		atEnvMonv2PsbSensorDescription OBJECT-TYPE
			SYNTAX DisplayStringUnsized (SIZE (0..30))
			MAX-ACCESS read-only
			STATUS current
			DESCRIPTION
				"The description of this power supply bay environmental sensor."
			::= { atEnvMonv2PsbSensorEntry 5 }

		
		-- 1.3.6.1.4.1.207.8.4.4.3.12.4.2.1.6
		atEnvMonv2PsbSensorStatus OBJECT-TYPE
			SYNTAX INTEGER
			{
				failed(1),
				good(2),
				notPowered(3)
			}
			MAX-ACCESS read-only
			STATUS current
			DESCRIPTION
				"An indication of whether this environmental sensor is
				currently in an alarm condition. A value of 'failed' indicates
				that the device is in a failure condition, 'good' indicates
				that the device is functioning normally."
			::= { atEnvMonv2PsbSensorEntry 6 }

		
--  ---------------------------------------------------------- --
-- The Environment Monitoring SNMP Trap Objects
-- ---------------------------------------------------------- --
		-- 1.3.6.1.4.1.207.8.4.4.3.12.5
		atEnvMonv2Traps OBJECT IDENTIFIER::= { atEnvMonv2 5 }

		
		-- 1.3.6.1.4.1.207.8.4.4.3.12.5.1
		atEnvMonv2FanAlarmSetEvent NOTIFICATION-TYPE
			OBJECTS { 	atEnvMonv2FanStackMemberId, atEnvMonv2FanBoardIndex, atEnvMonv2FanIndex,
						atEnvMonv2FanDescription, atEnvMonv2FanLowerThreshold, atEnvMonv2FanCurrentSpeed }
			STATUS current
			DESCRIPTION 
				"A trap generated when the monitored speed of a fan
				drops below its lower threshold."
			::= { atEnvMonv2Traps 1 }

		
		-- 1.3.6.1.4.1.207.8.4.4.3.12.5.2
		atEnvMonv2FanAlarmClearedEvent NOTIFICATION-TYPE
			OBJECTS { 	atEnvMonv2FanStackMemberId, atEnvMonv2FanBoardIndex, atEnvMonv2FanIndex,
						atEnvMonv2FanDescription, atEnvMonv2FanLowerThreshold, atEnvMonv2FanCurrentSpeed }
			STATUS current
			DESCRIPTION 
				"A trap generated when the monitored speed of a fan
				returns to an acceptable value, the fan
				having previously been in an alarm condition."
			::= { atEnvMonv2Traps 2 }

		
		-- 1.3.6.1.4.1.207.8.4.4.3.12.5.3
		atEnvMonv2VoltAlarmSetEvent NOTIFICATION-TYPE
			OBJECTS { 	atEnvMonv2VoltageStackMemberId, atEnvMonv2VoltageBoardIndex, atEnvMonv2VoltageIndex,
						atEnvMonv2VoltageDescription, atEnvMonv2VoltageUpperThreshold, 
						atEnvMonv2VoltageLowerThreshold, atEnvMonv2VoltageCurrent }
			STATUS current
			DESCRIPTION 
				"A trap generated when the voltage of a monitored
				voltage rail goes out of tolerance, either by
				dropping below its lower threshold, or exceeding
				its upper threshold."
			::= { atEnvMonv2Traps 3 }

		
		-- 1.3.6.1.4.1.207.8.4.4.3.12.5.4
		atEnvMonv2VoltAlarmClearedEvent NOTIFICATION-TYPE
			OBJECTS { 	atEnvMonv2VoltageStackMemberId, atEnvMonv2VoltageBoardIndex, atEnvMonv2VoltageIndex,
						atEnvMonv2VoltageDescription, atEnvMonv2VoltageUpperThreshold, 
						atEnvMonv2VoltageLowerThreshold, atEnvMonv2VoltageCurrent }
			STATUS current
			DESCRIPTION 
				"A trap generated when the voltage of a monitored
				voltage rail returns to an acceptable value,
				having previously been in an alarm condition."
			::= { atEnvMonv2Traps 4 }

		
		-- 1.3.6.1.4.1.207.8.4.4.3.12.5.5
		atEnvMonv2TempAlarmSetEvent NOTIFICATION-TYPE
			OBJECTS { 	atEnvMonv2TemperatureStackMemberId, atEnvMonv2TemperatureBoardIndex,
						atEnvMonv2TemperatureIndex, atEnvMonv2TemperatureDescription,
						atEnvMonv2TemperatureUpperThreshold, atEnvMonv2TemperatureCurrent }
			STATUS current
			DESCRIPTION 
				"A trap generated when a monitored temperature
				exceeds its upper threshold."
			::= { atEnvMonv2Traps 5 }

		
		-- 1.3.6.1.4.1.207.8.4.4.3.12.5.6
		atEnvMonv2TempAlarmClearedEvent NOTIFICATION-TYPE
			OBJECTS { 	atEnvMonv2TemperatureStackMemberId, atEnvMonv2TemperatureBoardIndex,
						atEnvMonv2TemperatureIndex, atEnvMonv2TemperatureDescription,
						atEnvMonv2TemperatureUpperThreshold }
			STATUS current
			DESCRIPTION 
				"A trap generated when a monitored temperature
				returns to an acceptable value, having
				previously been in an alarm condition."
			::= { atEnvMonv2Traps 6 }

		
		-- 1.3.6.1.4.1.207.8.4.4.3.12.5.7
		atEnvMonv2PsbAlarmSetEvent NOTIFICATION-TYPE
			OBJECTS { 	atEnvMonv2PsbSensorStackMemberId, atEnvMonv2PsbSensorBoardIndex,
						atEnvMonv2PsbSensorIndex, atEnvMonv2PsbSensorType,
						atEnvMonv2PsbSensorDescription }
			STATUS current
			DESCRIPTION 
				"A trap generated when a monitored parameter of
				a power supply bay device goes out of
				tolerance."
			::= { atEnvMonv2Traps 7 }

		
		-- 1.3.6.1.4.1.207.8.4.4.3.12.5.8
		atEnvMonv2PsbAlarmClearedEvent NOTIFICATION-TYPE
			OBJECTS { 	atEnvMonv2PsbSensorStackMemberId, atEnvMonv2PsbSensorBoardIndex,
						atEnvMonv2PsbSensorIndex, atEnvMonv2PsbSensorType,
						atEnvMonv2PsbSensorDescription }
			STATUS current
			DESCRIPTION 
				"A trap generated when a monitored parameter of
				a power supply bay device returns to an
				acceptable value, having previously been
				in an alarm condition."
			::= { atEnvMonv2Traps 8 }

		
-- ---------------------------------------------------------- --
-- The Environment Monitoring Fault LED Table
-- ---------------------------------------------------------- --
		-- 1.3.6.1.4.1.207.8.4.4.3.12.6
		atEnvMonv2FaultLedTable  OBJECT-TYPE
			SYNTAX      SEQUENCE OF AtEnvMonv2FaultLedEntry
			MAX-ACCESS  not-accessible
			STATUS      current
			DESCRIPTION
				"A table of information detailing any LED fault indications on
				the device."
			::= { atEnvMonv2 6 }

		
		-- 1.3.6.1.4.1.207.8.4.4.3.12.6.1
		atEnvMonv2FaultLedEntry OBJECT-TYPE
			SYNTAX      AtEnvMonv2FaultLedEntry
			MAX-ACCESS  not-accessible
			STATUS      current
			DESCRIPTION
				"An entry pertaining to a given fault LED."
			INDEX { atEnvMonv2FaultLedStackMemberId }
			::= { atEnvMonv2FaultLedTable 1 }

		
		AtEnvMonv2FaultLedEntry ::=
			SEQUENCE {
				atEnvMonv2FaultLedStackMemberId
					Unsigned32,
				atEnvMonv2FaultLed1Flash
					INTEGER,
				atEnvMonv2FaultLed2Flashes
					INTEGER,
				atEnvMonv2FaultLed3Flashes 
					INTEGER,
				atEnvMonv2FaultLed4Flashes
					INTEGER,
				atEnvMonv2FaultLed5Flashes
					INTEGER,
				atEnvMonv2FaultLed6Flashes
					INTEGER
			}

		
		-- 1.3.6.1.4.1.207.8.4.4.3.12.6.1.1
		atEnvMonv2FaultLedStackMemberId OBJECT-TYPE
			SYNTAX      Unsigned32
			MAX-ACCESS  read-only
			STATUS      current
			DESCRIPTION
				"The index of the stack member hosting this fault LED."
			::= { atEnvMonv2FaultLedEntry 1 }

		
		-- 1.3.6.1.4.1.207.8.4.4.3.12.6.1.2
		atEnvMonv2FaultLed1Flash OBJECT-TYPE
			SYNTAX INTEGER
			{
				heatsinkFanFailure(1),
				noFault(2)
			}
			MAX-ACCESS read-only
			STATUS current
			DESCRIPTION
				"This object indicates whether a fault LED is currently showing
				a system failure by flashing once. It indicates that one or
				more heatsink fans have failed, or are operating below the
				recommended speed."
			::= { atEnvMonv2FaultLedEntry 2 }

		
		-- 1.3.6.1.4.1.207.8.4.4.3.12.6.1.3
		atEnvMonv2FaultLed2Flashes OBJECT-TYPE
			SYNTAX INTEGER
			{
				chassisFanFailure(1),
				noFault(2)
			}
			MAX-ACCESS read-only
			STATUS current
			DESCRIPTION
				"This object indicates whether a fault LED is currently showing
				a system failure by flashing twice. It indicates that one or
				both of the chassis fans are not installed, or the fans are
				operating below the recommended speed."
			::= { atEnvMonv2FaultLedEntry 3 }

		
		-- 1.3.6.1.4.1.207.8.4.4.3.12.6.1.4
		atEnvMonv2FaultLed3Flashes OBJECT-TYPE
			SYNTAX INTEGER
			{
				sensorFailure(1),
				noFault(2)
			}
			MAX-ACCESS read-only
			STATUS current
			DESCRIPTION
				"This object indicates whether a fault LED is currently showing
				a system failure by flashing three times. It indicates that the
				ability to monitor temperature or fans has failed."
			::= { atEnvMonv2FaultLedEntry 4 }

		
		-- 1.3.6.1.4.1.207.8.4.4.3.12.6.1.5
		atEnvMonv2FaultLed4Flashes OBJECT-TYPE
			SYNTAX INTEGER
			{
				xemInitialisationFailure(1),
				noFault(2)
			}
			MAX-ACCESS read-only
			STATUS current
			DESCRIPTION
				"This object indicates whether a fault LED is currently showing
				a system failure by flashing four times. It indicates that an
				XEM failed to initialise or is incompatible."
			::= { atEnvMonv2FaultLedEntry 5 }

		
		-- 1.3.6.1.4.1.207.8.4.4.3.12.6.1.6
		atEnvMonv2FaultLed5Flashes OBJECT-TYPE
			SYNTAX INTEGER
			{
				noFault(2)
			}
			MAX-ACCESS read-only
			STATUS current
			DESCRIPTION
				"This object indicates whether a fault LED is currently showing
				a system failure by flashing five times. This flashing
				sequence is not currently in use."
			::= { atEnvMonv2FaultLedEntry 6 }

		
		-- 1.3.6.1.4.1.207.8.4.4.3.12.6.1.7
		atEnvMonv2FaultLed6Flashes OBJECT-TYPE
			SYNTAX INTEGER
			{
				temperatureFailure(1),
				noFault(2)
			}
			MAX-ACCESS read-only
			STATUS current
			DESCRIPTION
				"This object indicates whether a fault LED is currently showing
				a system failure by flashing six times. It indicates that the
				device's temperature has exceeded the recommended threshold."
			::= { atEnvMonv2FaultLedEntry 7 }
	
	END

--
-- at-envmonv2.mib
--
