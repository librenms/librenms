ZSCALER-OSNIC-MIB DEFINITIONS ::= BEGIN

IMPORTS
	MODULE-IDENTITY, OBJECT-TYPE, Counter32, Gauge32, Counter64,
	Integer32, TimeTicks, mib-2,enterprises,
	NOTIFICATION-TYPE                        FROM SNMPv2-SMI
	TEXTUAL-CONVENTION, DisplayString,
	PhysAddress, TruthValue, RowStatus,
	TimeStamp, AutonomousType, TestAndIncr   FROM SNMPv2-TC
	MODULE-COMPLIANCE, OBJECT-GROUP,
	NOTIFICATION-GROUP                       FROM SNMPv2-CONF
	snmpTraps                                FROM SNMPv2-MIB
	IANAifType                               FROM IANAifType-MIB;

osnic MODULE-IDENTITY
	LAST-UPDATED "201704280805Z"
	ORGANIZATION "Zscaler"
	CONTACT-INFO
		"Zscaler Inc.
		US"
	DESCRIPTION
		"This module describes the NIC devices managed by the OS.
		On a Zscaler system, there are NIC devices managed by the 
		Zscaler instances and also by the base OS."
	
	REVISION      "201704280805Z"
	DESCRIPTION
		"Initial revision."
	::= { enterprises 46262 }

zscaler OBJECT IDENTIFIER ::= { enterprises 46262 }

osnics OBJECT IDENTIFIER ::= { zscaler 1 }

osnicNumber  OBJECT-TYPE
	SYNTAX      Integer32
	MAX-ACCESS  read-only
	STATUS      current
	DESCRIPTION
		"The number of osnic present on this system."
	::= { osnics 1 }

osnicTable OBJECT-TYPE
	SYNTAX      SEQUENCE OF OsnicEntry
	MAX-ACCESS  not-accessible
	STATUS      current
	DESCRIPTION
		"A list of osnic entries. The number of entries is
		given by the value of osnicNumber."
	::= { osnics 2 }

osnicEntry OBJECT-TYPE
	SYNTAX      OsnicEntry
	MAX-ACCESS  not-accessible
	STATUS      current
	DESCRIPTION
		"An entry containing management information applicable to a
		particular osnic."
	INDEX   { osnicIndex }
	::= { osnicTable 1 }

OsnicEntry ::=
	SEQUENCE {
		osnicIndex Integer32,
		osnicName OCTET STRING,
		osnicRole OCTET STRING,
		osnicInstance OCTET STRING,
	}

osnicIndex OBJECT-TYPE
	SYNTAX     Integer32
	MAX-ACCESS read-only
	STATUS     current
	DESCRIPTION
		"The index of osnic in the list of such objects"
	::= { osnicEntry 1 }

osnicName OBJECT-TYPE
	SYNTAX     OCTET STRING
	MAX-ACCESS read-only
	STATUS     current
	DESCRIPTION
		"The name of the osnic"
	::= { osnicEntry 2 }

osnicRole OBJECT-TYPE
	SYNTAX     OCTET STRING
	MAX-ACCESS read-only
	STATUS     current
	DESCRIPTION
		"The Zscaler role to which this osnic belongs"
	::= { osnicEntry 3 }

osnicInstance OBJECT-TYPE
	SYNTAX     OCTET STRING
	MAX-ACCESS read-only
	STATUS     current
	DESCRIPTION
		"The Zscaler instance path where this osnic is present"
	::= { osnicEntry 4 }


END
