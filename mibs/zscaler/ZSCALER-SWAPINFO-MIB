ZSCALER-SWAPINFO-MIB DEFINITIONS ::= BEGIN

IMPORTS
	MODULE-IDENTITY, OBJECT-TYPE, Counter32, Gauge32, Counter64, Unsigned32,
	Integer32, TimeTicks, mib-2,enterprises,
	NOTIFICATION-TYPE                        FROM SNMPv2-SMI
	TEXTUAL-CONVENTION, DisplayString,
	PhysAddress, TruthValue, RowStatus,
	TimeStamp, AutonomousType, TestAndIncr   FROM SNMPv2-TC
	MODULE-COMPLIANCE, OBJECT-GROUP,
	NOTIFICATION-GROUP                       FROM SNMPv2-CONF
	snmpTraps                                FROM SNMPv2-MIB
	IANAifType                               FROM IANAifType-MIB;

swapinfo MODULE-IDENTITY
	LAST-UPDATED "201704280805Z"
	ORGANIZATION "Zscaler"
	CONTACT-INFO
		"Zscaler Inc.
		US"
	DESCRIPTION
		"This module describes the status of the swap devices present 
		on the system."
	
	REVISION      "201704280805Z"
	DESCRIPTION
		"Initial revision."
	::= { enterprises 46262 }

zscaler OBJECT IDENTIFIER ::= { enterprises 46262 }

swapinfos OBJECT IDENTIFIER ::= { zscaler 6 }

swapinfoNumber  OBJECT-TYPE
	SYNTAX      Integer32
	MAX-ACCESS  read-only
	STATUS      current
	DESCRIPTION
		"The number of swapinfo present on this system."
	::= { swapinfos 1 }

swapinfoTable OBJECT-TYPE
	SYNTAX      SEQUENCE OF SwapinfoEntry
	MAX-ACCESS  not-accessible
	STATUS      current
	DESCRIPTION
		"A list of swapinfo entries. The number of entries is
		given by the value of swapinfoNumber."
	::= { swapinfos 2 }

swapinfoEntry OBJECT-TYPE
	SYNTAX      SwapinfoEntry
	MAX-ACCESS  not-accessible
	STATUS      current
	DESCRIPTION
		"An entry containing management information applicable to a
		particular swapinfo."
	INDEX   { swapinfoIndex }
	::= { swapinfoTable 1 }

SwapinfoEntry ::=
	SEQUENCE {
		swapinfoIndex Integer32,
		swapinfoName OCTET STRING,
		swapinfoRole OCTET STRING,
		swapinfoInstance OCTET STRING,
		osswap_cur_total_pages Unsigned32,
		osswap_cur_total_MB Unsigned32,
		osswap_cur_used_pages Unsigned32,
		osswap_cur_free_pages Unsigned32,
		osswap_cur_used_MB Unsigned32,
		osswap_cur_free_MB Unsigned32,
		osswap_cur_used_inpercentage Unsigned32,
		osswap_cur_flags Unsigned32,
		osswap_cur_name OCTET STRING,
	}

swapinfoIndex OBJECT-TYPE
	SYNTAX     Integer32
	MAX-ACCESS read-only
	STATUS     current
	DESCRIPTION
		"The index of swapinfo in the list of such objects"
	::= { swapinfoEntry 1 }

swapinfoName OBJECT-TYPE
	SYNTAX     OCTET STRING
	MAX-ACCESS read-only
	STATUS     current
	DESCRIPTION
		"The name of the swapinfo"
	::= { swapinfoEntry 2 }

swapinfoRole OBJECT-TYPE
	SYNTAX     OCTET STRING
	MAX-ACCESS read-only
	STATUS     current
	DESCRIPTION
		"The Zscaler role to which this swapinfo belongs"
	::= { swapinfoEntry 3 }

swapinfoInstance OBJECT-TYPE
	SYNTAX     OCTET STRING
	MAX-ACCESS read-only
	STATUS     current
	DESCRIPTION
		"The Zscaler instance path where this swapinfo is present"
	::= { swapinfoEntry 4 }

osswap_cur_total_pages OBJECT-TYPE
	SYNTAX     Unsigned32
	MAX-ACCESS read-only
	STATUS     current
	DESCRIPTION
		"Total swap space represented as number of pages"
	::= { swapinfoEntry 5 }

osswap_cur_total_MB OBJECT-TYPE
	SYNTAX     Unsigned32
	MAX-ACCESS read-only
	STATUS     current
	DESCRIPTION
		"Total swap space represented in MB"
	::= { swapinfoEntry 6 }

osswap_cur_used_pages OBJECT-TYPE
	SYNTAX     Unsigned32
	MAX-ACCESS read-only
	STATUS     current
	DESCRIPTION
		"Current used swap space represented as number of pages"
	::= { swapinfoEntry 7 }

osswap_cur_free_pages OBJECT-TYPE
	SYNTAX     Unsigned32
	MAX-ACCESS read-only
	STATUS     current
	DESCRIPTION
		"Current free swap space represented as number of pages"
	::= { swapinfoEntry 8 }

osswap_cur_used_MB OBJECT-TYPE
	SYNTAX     Unsigned32
	MAX-ACCESS read-only
	STATUS     current
	DESCRIPTION
		"Current used swap space represented in MB"
	::= { swapinfoEntry 9 }

osswap_cur_free_MB OBJECT-TYPE
	SYNTAX     Unsigned32
	MAX-ACCESS read-only
	STATUS     current
	DESCRIPTION
		"Current free swap space represented in MB"
	::= { swapinfoEntry 10 }

osswap_cur_used_inpercentage OBJECT-TYPE
	SYNTAX     Unsigned32
	MAX-ACCESS read-only
	STATUS     current
	DESCRIPTION
		"Current swap space utilization - To get percentage value, divide by 100"
	::= { swapinfoEntry 11 }

osswap_cur_flags OBJECT-TYPE
	SYNTAX     Unsigned32
	MAX-ACCESS read-only
	STATUS     current
	DESCRIPTION
		"Swap device operation flags"
	::= { swapinfoEntry 12 }

osswap_cur_name OBJECT-TYPE
	SYNTAX     OCTET STRING
	MAX-ACCESS read-only
	STATUS     current
	DESCRIPTION
		"Swap device name"
	::= { swapinfoEntry 13 }


END
