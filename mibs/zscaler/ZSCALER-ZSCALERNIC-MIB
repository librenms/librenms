ZSCALER-ZSCALERNIC-MIB DEFINITIONS ::= BEGIN

IMPORTS
	MODULE-IDENTITY, OBJECT-TYPE, Counter32, Gauge32, Counter64,
	Integer32, TimeTicks, mib-2,enterprises,
	NOTIFICATION-TYPE                        FROM SNMPv2-SMI
	TEXTUAL-CONVENTION, DisplayString,
	PhysAddress, TruthValue, RowStatus,
	TimeStamp, AutonomousType, TestAndIncr   FROM SNMPv2-TC
	MODULE-COMPLIANCE, OBJECT-GROUP,
	NOTIFICATION-GROUP                       FROM SNMPv2-CONF
	snmpTraps                                FROM SNMPv2-MIB
	IANAifType                               FROM IANAifType-MIB;

zscalernic MODULE-IDENTITY
	LAST-UPDATED "201704280805Z"
	ORGANIZATION "Zscaler"
	CONTACT-INFO
		"Zscaler Inc.
		US"
	DESCRIPTION
		"This module describes the NIC devices managed by the Zscaler 
		instance.
		On a Zscaler system, there are NIC devices managed by the 
		Zscaler instances and also by the base OS."
	
	REVISION      "201704280805Z"
	DESCRIPTION
		"Initial revision."
	::= { enterprises 46262 }

zscaler OBJECT IDENTIFIER ::= { enterprises 46262 }

zscalernics OBJECT IDENTIFIER ::= { zscaler 2 }

zscalernicNumber  OBJECT-TYPE
	SYNTAX      Integer32
	MAX-ACCESS  read-only
	STATUS      current
	DESCRIPTION
		"The number of zscalernic present on this system."
	::= { zscalernics 1 }

zscalernicTable OBJECT-TYPE
	SYNTAX      SEQUENCE OF ZscalernicEntry
	MAX-ACCESS  not-accessible
	STATUS      current
	DESCRIPTION
		"A list of zscalernic entries. The number of entries is
		given by the value of zscalernicNumber."
	::= { zscalernics 2 }

zscalernicEntry OBJECT-TYPE
	SYNTAX      ZscalernicEntry
	MAX-ACCESS  not-accessible
	STATUS      current
	DESCRIPTION
		"An entry containing management information applicable to a
		particular zscalernic."
	INDEX   { zscalernicIndex }
	::= { zscalernicTable 1 }

ZscalernicEntry ::=
	SEQUENCE {
		zscalernicIndex Integer32,
		zscalernicName OCTET STRING,
		zscalernicRole OCTET STRING,
		zscalernicInstance OCTET STRING,
	}

zscalernicIndex OBJECT-TYPE
	SYNTAX     Integer32
	MAX-ACCESS read-only
	STATUS     current
	DESCRIPTION
		"The index of zscalernic in the list of such objects"
	::= { zscalernicEntry 1 }

zscalernicName OBJECT-TYPE
	SYNTAX     OCTET STRING
	MAX-ACCESS read-only
	STATUS     current
	DESCRIPTION
		"The name of the zscalernic"
	::= { zscalernicEntry 2 }

zscalernicRole OBJECT-TYPE
	SYNTAX     OCTET STRING
	MAX-ACCESS read-only
	STATUS     current
	DESCRIPTION
		"The Zscaler role to which this zscalernic belongs"
	::= { zscalernicEntry 3 }

zscalernicInstance OBJECT-TYPE
	SYNTAX     OCTET STRING
	MAX-ACCESS read-only
	STATUS     current
	DESCRIPTION
		"The Zscaler instance path where this zscalernic is present"
	::= { zscalernicEntry 4 }


END
