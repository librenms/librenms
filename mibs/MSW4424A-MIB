MSW4424A-MIB DEFINITIONS ::= BEGIN 
  
    IMPORTS
        enterprises,
        NOTIFICATION-TYPE,
        MODULE-IDENTITY,
        OBJECT-TYPE,
        Counter32,
        Integer32,
        Unsigned32,
        Gauge32,
        Counter64,
        IpAddress
            FROM SNMPv2-SMI
        MODULE-COMPLIANCE,
        OBJECT-GROUP,
        NOTIFICATION-GROUP
            FROM SNMPv2-CONF    
        DisplayString,
        DateAndTime,
        MacAddress,
        TruthValue
            FROM SNMPv2-TC       
    ; 
          
     -- 1.3.6.1.4.1.4756
    ctc MODULE-IDENTITY
        LAST-UPDATED "201412180000Z"        
        ORGANIZATION
            " CTC Union Technologies Co., Ltd. "
        CONTACT-INFO
            " Postal: 8F, No.60, ZhouZi Street, NeiHu, Taipei 114, Taiwan
              Tel: +886-2-2659-1021
              Fax: +886-2-2672-5211
              Web: http://www.ctcu.com
              Email: techsupport@ctcu.com " 
        DESCRIPTION
            " MSW4424A-MIB FILE V1.01"
        
               
        REVISION "201412180000Z"        	
        DESCRIPTION
            " V1.01  - Initial Document.
            	add DD Functions"
        ::= { enterprises 4756 }
 
              
-- 
-- Node definitions 
--
    -- 1.3.6.1.4.1.4756.108
    msw4424a OBJECT IDENTIFIER ::= { ctc 108 }	

-- System                              
    -- 1.3.6.1.4.1.4756.108.10
    iSystem OBJECT IDENTIFIER ::= { msw4424a 10 }

	-- 1.3.6.1.4.1.4756.108.10.1
    iModelType OBJECT-TYPE
        SYNTAX      DisplayString
        MAX-ACCESS  read-only
        STATUS      current
        DESCRIPTION
            "This serial Model Type
            "
        ::= { iSystem 1 }

    -- 1.3.6.1.4.1.4756.108.10.2
    iSystemInformation OBJECT IDENTIFIER ::= { iSystem 2 }
                            
    -- 1.3.6.1.4.1.4756.108.10.2.1
    iBaseMacAddress OBJECT-TYPE
        SYNTAX      DisplayString
        MAX-ACCESS  read-only
        STATUS      current
        DESCRIPTION
            "The MAC Address of this switch."
        ::= { iSystemInformation 1 }
             
    -- 1.3.6.1.4.1.4756.108.10.2.2
    iHardWareVersion OBJECT-TYPE
        SYNTAX      DisplayString
        MAX-ACCESS  read-only
        STATUS      current
        DESCRIPTION
            "The hardware version of this switch."
        ::= { iSystemInformation 2 }
    
    -- 1.3.6.1.4.1.4756.108.10.2.3
    iSystemDate OBJECT-TYPE
        SYNTAX      DisplayString
        MAX-ACCESS  read-only
        STATUS      current
        DESCRIPTION
            "The current (GMT) system time and date. The system time is obtained through the Timing server running on the switch, if any."
        ::= { iSystemInformation 3 }
             
    -- 1.3.6.1.4.1.4756.108.10.2.4
    iSoftWareVersion OBJECT-TYPE
        SYNTAX      DisplayString
        MAX-ACCESS  read-only
        STATUS      current
        DESCRIPTION
            "The software version of this switch."
        ::= { iSystemInformation 4 }
    
    -- 1.3.6.1.4.1.4756.108.10.2.5
    iSoftWareDate OBJECT-TYPE
        SYNTAX      DisplayString
        MAX-ACCESS  read-only
        STATUS      current
        DESCRIPTION
            "The date when the switch software was produced."
        ::= { iSystemInformation 5 }
    
    -- 1.3.6.1.4.1.4756.108.10.3
    iIP OBJECT IDENTIFIER ::= { iSystem 3 } 
    
    -- 1.3.6.1.4.1.4756.108.10.3.1
    iMode OBJECT-TYPE
        SYNTAX      INTEGER {
                        host(1),
                        router(2)
                    }
        MAX-ACCESS  read-write
        STATUS      current
        DESCRIPTION
            "Configure whether the IP stack should act as a Host or a Router. In Host mode, 
             IP traffic between interfaces will not be routed. In Router mode traffic is routed between all interfaces. 
			"
        ::= { iIP 1 }
        
    -- 1.3.6.1.4.1.4756.108.10.3.2
    iDNSServerType OBJECT-TYPE
        SYNTAX      INTEGER {
                        from-any-dhcp-interfaces(1),
                        no-DNS-server(2),
                        configured(3),
                        from-this-dhcp-interface(4)
                    }
        MAX-ACCESS  read-write
        STATUS      current
        DESCRIPTION
            "This setting controls the DNS name resolution done by the switch. The following modes are supported: 
				1:From any DHCP interfaces 
					The first DNS server offered from a DHCP lease to a DHCP-enabled interface will be used. 
				
				2:No DNS server 
					No DNS server will be used.
				
				3:Configured 
					Explicitly provide the IP address of the DNS Server in iDNSServerIP Node. 
				
				4:From this DHCP interface 
					Specify from which DHCP-enabled interface a provided DNS server should be preferred. 
			"
        ::= { iIP 2 }
    
    -- 1.3.6.1.4.1.4756.108.10.23.3
    iDNSServerSetting OBJECT-TYPE
        SYNTAX      DisplayString
        MAX-ACCESS  read-write
        STATUS      current
        DESCRIPTION                         
            "
             If iDNSServerType setting '3:Configured',this value must setting IP address format as below:
                Dotted Decimal Notation refers to a method of writing IP addresses using decimal numbers and dots as separators between octets.
			    An IPv4 dotted decimal address has the form x.y.z.w, where x, y, z, and w are decimal numbers between 0 and 255.               
			 
			 If DNSServerType setting '4:From this DHCP interface', this value must setting VLAN ID.(Range 1~4095).
			"
        ::= { iIP 3 }
    
    -- 1.3.6.1.4.1.4756.108.10.3.4
    iDNSproxy OBJECT-TYPE
        SYNTAX      INTEGER {
                        disabled(1),
                        enabled(2)
                    }
        MAX-ACCESS  read-write
        STATUS      current
        DESCRIPTION
            "When DNS proxy is enabled, system will relay DNS requests to the currently configured DNS server, 
             and reply as a DNS resolver to the client devices on the network.  
			"
        ::= { iIP 4 }
    
    -- 1.3.6.1.4.1.4756.108.10.3.5
    iAddInterface OBJECT-TYPE
        SYNTAX      DisplayString
        MAX-ACCESS  read-write
        STATUS      current
        DESCRIPTION
            "Add a new IP VLAN Interface:
             Syntax: [<vlan_list>]
            "
        ::= { iIP 5 }
        
    -- 1.3.6.1.4.1.4756.108.10.3.6
    iDeleteInterface OBJECT-TYPE
        SYNTAX      DisplayString
        MAX-ACCESS  read-write
        STATUS      current
        DESCRIPTION
            "Delete a IP VLAN Interface:
             Syntax: [<vlan_list>]
            "
        ::= { iIP 6 }
    
    -- 1.3.6.1.4.1.4756.108.10.3.7
    iIPinterfaceTable OBJECT-TYPE
        SYNTAX      SEQUENCE OF IIPinterfaceEntry
        MAX-ACCESS  not-accessible
        STATUS      current
        DESCRIPTION
            "The switch system IP Interface."
        ::= { iIP 7 }
    
    -- 1.3.6.1.4.1.4756.108.10.3.7.1
    iIPinterfaceEntry OBJECT-TYPE
        SYNTAX      IIPinterfaceEntry
        MAX-ACCESS  not-accessible
        STATUS      current
        DESCRIPTION
            "The system log entry."
        INDEX { iIPinterfaceVLAN }
        ::= { iIPinterfaceTable 1 }

    IIPinterfaceEntry ::=
        SEQUENCE {
            iIPinterfaceVLAN    Integer32,
            iIPinterfaceDHCP    INTEGER,
            iIPv4Address   		DisplayString,
            iIPv4MaskLenth 		Integer32,     
            iIPv4CurrentLease 	DisplayString,
            iIPv6Address 		DisplayString,
            iIPv6MaskLenth    	Integer32
        }
        
     -- 1.3.6.1.4.1.4756.108.10.3.7.1.1
     iIPinterfaceVLAN OBJECT-TYPE
         SYNTAX	Integer32 (1..4095)
         MAX-ACCESS  read-only
         STATUS      current
         DESCRIPTION
             "The VLAN associated with the IP interface. Only ports in this VLAN will be able to access the IP interface. 
              This field is only available for input when creating an new interface. 
			 "
         ::= { iIPinterfaceEntry 1 }       
         
     -- 1.3.6.1.4.1.4756.108.10.3.7.1.2
     iIPinterfaceDHCP OBJECT-TYPE
         SYNTAX	INTEGER {
                     		disable(1),
                     		enabled(2)
                 		}
         MAX-ACCESS  read-write
         STATUS      current
         DESCRIPTION
             "Enable the DHCP client by checking this box. If this option is enabled, 
              the system will configure the IPv4 address and mask of the interface using the DHCP protocol. 
              The DHCP client will announce the configured System Name as hostname to provide DNS lookup. 
			 "
         ::= { iIPinterfaceEntry 2 }    
     
     -- 1.3.6.1.4.1.4756.108.10.3.7.1.3
     iIPv4Address OBJECT-TYPE
         SYNTAX		 DisplayString
         MAX-ACCESS  read-write
         STATUS      current
         DESCRIPTION
             "The IPv4 address of the interface.
              IP addresses using decimal numbers and dots as separators between octets.
			  An IPv4 dotted decimal address has the form x.y.z.w, where x, y, z, and w are decimal numbers between 0 and 255. 
			  If DHCP is enabled, this field is not used. 
			  The field may also be left blank if IPv4 operation on the interface is not desired. 
			 "
         ::= { iIPinterfaceEntry 3 }     
     
     
     -- 1.3.6.1.4.1.4756.108.10.3.7.1.4
     iIPv4MaskLenth OBJECT-TYPE
         SYNTAX		 Integer32 (0..30)
         MAX-ACCESS  read-write
         STATUS      current
         DESCRIPTION
             "The IPv4 network mask, in number of bits (prefix length). 
              Valid values are between 0 and 30 bits for a IPv4 address. 
			   If DHCP is enabled, this field is not used. 
			   The field may also be left blank if IPv4 operation on the interface is not desired.
			 "
         ::= { iIPinterfaceEntry 4 }    
      
     -- 1.3.6.1.4.1.4756.108.10.3.7.1.5
     iIPv4CurrentLease OBJECT-TYPE
         SYNTAX		 DisplayString
         MAX-ACCESS  read-only
         STATUS      current
         DESCRIPTION
             "For DHCP interfaces with an active lease, this column show the current interface address, as provided by the DHCP server."
         ::= { iIPinterfaceEntry 5 }
         
     -- 1.3.6.1.4.1.4756.108.10.3.7.1.6
     iIPv6Address OBJECT-TYPE
         SYNTAX		 DisplayString
         MAX-ACCESS  read-write
         STATUS      current
         DESCRIPTION
             "The IPv6 address of the interface. 
              A IPv6 address is in 128-bit records represented as eight fields of up to four hexadecimal digits with a colon separating each field (:). For example, fe80::215:c5ff:fe03:4dc7. The symbol :: is a special syntax that can be used as a shorthand way of representing multiple 16-bit groups of contiguous zeros; but it can appear only once. It can also represent a legally valid IPv4 address. For example, ::192.1.2.34. 
              The field may be left blank if IPv6 operation on the interface is not desired. 
			 "
         ::= { iIPinterfaceEntry 6 }
    
      -- 1.3.6.1.4.1.4756.108.10.3.7.1.7
     iIPv6MaskLenth OBJECT-TYPE
         SYNTAX		 Integer32 (1..128)
         MAX-ACCESS  read-write
         STATUS      current
         DESCRIPTION
             "The IPv6 network mask, in number of bits (prefix length). 
              Valid values are between 1 and 128 bits for a IPv6 address. 
			  The field may be left blank if IPv6 operation on the interface is not desired.  
			 "
         ::= { iIPinterfaceEntry 7 }
     
    
    -- 1.3.6.1.4.1.4756.108.10.3.8
    iAddRoutes OBJECT-TYPE
        SYNTAX      DisplayString
        MAX-ACCESS  read-write
        STATUS      current
        DESCRIPTION
            "Add a new IP Routes:
             Syntax: <ip_net> <ip_gateway>
            "
        ::= { iIP 8 }
    
    -- 1.3.6.1.4.1.4756.108.10.3.9
    iDeleteRoutes OBJECT-TYPE
        SYNTAX      DisplayString
        MAX-ACCESS  read-write
        STATUS      current
        DESCRIPTION
            "Delete a IP VLAN Interface:
             Syntax: <ip_net> <ip_gateway>
            "
        ::= { iIP 9 }
     
    -- 1.3.6.1.4.1.4756.108.10.3.10
    iIProuteTable OBJECT-TYPE
        SYNTAX      SEQUENCE OF IIProuteEntry
        MAX-ACCESS  not-accessible
        STATUS      current
        DESCRIPTION
            "The switch system IP Interface."
        ::= { iIP 10 }
    
    -- 1.3.6.1.4.1.4756.108.10.3.10.1
    iIProuteEntry OBJECT-TYPE
        SYNTAX      IIProuteEntry
        MAX-ACCESS  not-accessible
        STATUS      current
        DESCRIPTION
            "The IP route entry."
        INDEX { iIProuteIndex }
        ::= { iIProuteTable 1 }

    IIProuteEntry ::=
        SEQUENCE {
            iIProuteIndex  		Integer32,
            iNetwork     	 	DisplayString,
            iMaskLenth       	Integer32,
            iGateway     	 	DisplayString
        }
     
     -- 1.3.6.1.4.1.4756.108.10.3.10.1.1
     iIProuteIndex OBJECT-TYPE
         SYNTAX      Integer32 (1..8)
         MAX-ACCESS  read-only
         STATUS      current
         DESCRIPTION
             "The Index of the IP routes."
         ::= { iIProuteEntry 1 }
 
     
     -- 1.3.6.1.4.1.4756.108.10.3.10.1.2
     iNetwork OBJECT-TYPE
         SYNTAX	DisplayString
         MAX-ACCESS  read-only
         STATUS      current
         DESCRIPTION
             "The destination IP network or host address of this route. 
              Valid format is dotted decimal notationor a valid IPv6 notation. 
              A default route can use the value 0.0.0.0or IPv6 :: notation. 
             "
         ::= { iIProuteEntry 2 } 
     
     -- 1.3.6.1.4.1.4756.108.10.3.10.1.3
     iMaskLenth OBJECT-TYPE
         SYNTAX	Integer32 (0..128)
         MAX-ACCESS  read-only
         STATUS      current
         DESCRIPTION
             "The destination IP network or host mask, in number of bits (prefix length). 
              It defines how much of a network address that must match, in order to qualify for this route. 
              Valid values are between 0 and 32 bits respectively 128 for IPv6 routes. Only a default route will have a mask length of 0 (as it will match anything). 
			 "
         ::= { iIProuteEntry 3 } 
     
     -- 1.3.6.1.4.1.4756.108.10.3.6.1.4
     iGateway OBJECT-TYPE
         SYNTAX	DisplayString
         MAX-ACCESS  read-only
         STATUS      current
         DESCRIPTION
             "
			   The IP address of the IP gateway. Valid format is dotted decimal notationor a valid IPv6 notation. 
               Gateway and Network must be of the same type. 
			 "
         ::= { iIProuteEntry 4 } 

    -- 1.3.6.1.4.1.4756.108.10.4
    iNTP OBJECT IDENTIFIER ::= { iSystem 4 }

    -- 1.3.6.1.4.1.4756.108.10.4.1
    iNtpMode OBJECT-TYPE
        SYNTAX  INTEGER {
                        enabled(1),
                        disabled(2)
                    }
        MAX-ACCESS  read-write
        STATUS      current
        DESCRIPTION
            "Indicates the NTP mode operation. Possible modes are:
             Enabled: Enable NTP mode operation. When NTP mode operation is enabled,
                      the agent forwards NTP messages between the clients and the server
                      when they are not on the same subnet domain.
             Disabled: Disable NTP mode operation. "
        ::= { iNTP 1 }

    -- 1.3.6.1.4.1.4756.108.10.4.2
    iNtpServerTable OBJECT-TYPE
        SYNTAX      SEQUENCE OF INtpServerEntry
        MAX-ACCESS  not-accessible
        STATUS      current
        DESCRIPTION
            "The switch system log information."
        ::= { iNTP 2 }

    -- 1.3.6.1.4.1.4756.108.10.4.2.1
    iNtpServerEntry OBJECT-TYPE
        SYNTAX      INtpServerEntry
        MAX-ACCESS  not-accessible
        STATUS      current
        DESCRIPTION
            "The NTP Server entry."
        INDEX { iNtpServerIndex }
        ::= { iNtpServerTable 1 }

    INtpServerEntry ::=
        SEQUENCE {
            iNtpServerIndex        Integer32,
            iNtpServerAddress      DisplayString
        }

        -- 1.3.6.1.4.1.4756.108.10.4.1.1
        iNtpServerIndex OBJECT-TYPE
            SYNTAX      Integer32 (1..5)
            MAX-ACCESS  read-only
            STATUS      current
            DESCRIPTION
                "The Index of the NTP server."
            ::= { iNtpServerEntry 1 }

        -- 1.3.6.1.4.1.4756.108.10.4.1.2
        iNtpServerAddress OBJECT-TYPE
            SYNTAX      DisplayString
            MAX-ACCESS  read-write
            STATUS      current
            DESCRIPTION
                "It must either be a valid IP address or a valid hostname.
                 A valid hostname is a string drawn from the alphabet(A-Za-z), digits(0-9), dot(.), dash(-).
                 Spaces are not allowed, the first character must be an alpha character,
                 and the first and last characters must not be a dot or a dash.
                 IPv4 address is in dotted decimal notation ('x.y.z.w').
                 IPv6 address is in 128-bit records represented as eight fields of up to
                 four hexadecimal digits with a colon separating each field (:)."
            ::= { iNtpServerEntry 2 }
 
	    -- 1.3.6.1.4.1.4756.108.10.5
	    iTime OBJECT IDENTIFIER ::= { iSystem 5 }
	             
	    -- 1.3.6.1.4.1.4756.108.10.5.1
	    iTimezone OBJECT-TYPE
	        SYNTAX      Integer32 (-7200..7800)
	        MAX-ACCESS  read-write
	        STATUS      current
	        DESCRIPTION
	            "Lists various Time Zones world wide below.
	             -7200: '(GMT-12:00) International Date Line West',
	             -6600: '(GMT-11:00) Midway Island, Samoa',
	             -6000: '(GMT-10:00) Hawaii',
	             -5400: '(GMT-09:00) Alaska',
	             -4800: '(GMT-08:00) Pacific Time (US and Canada)',
	             -4801: '(GMT-08:00) Tijuana, Baja California',
	             -4200: '(GMT-07:00) Arizona',
	             -4201: '(GMT-07:00) Chihuahua, La Paz, Mazatlan - New',
	             -4202: '(GMT-07:00) Chihuahua, La Paz, Mazatlan - Old',
	             -4203: '(GMT-07:00) Mountain Time (US and Canada)',
	             -3600: '(GMT-06:00) Central America',
	             -3601: '(GMT-06:00) Central Time (US and Canada)',
	             -3602: '(GMT-06:00) Guadalajara, Mexico City, Monterrey - New',
	             -3603: '(GMT-06:00) Guadalajara, Mexico City, Monterrey - Old',
	             -3604: '(GMT-06:00) Saskatchewan',
	             -3000: '(GMT-05:00) Bogota, Lima, Quito, Rio Branco',
	             -3001: '(GMT-05:00) Eastern Time (US and Canada)',
	             -3002: '(GMT-05:00) Indiana (East)',
	             -2700: '(GMT-04:30) Caracas',
	             -2400: '(GMT-04:00) Atlantic Time (Canada)',
	             -2401: '(GMT-04:00) La Paz','(GMT-04:00) Manaus',
	             -2402: '(GMT-04:00) Santiago','(GMT-03:30) Newfoundland',
	             -1800: '(GMT-03:00) Brasilia','(GMT-03:00) Buenos Aires',
	             -1801: '(GMT-03:00) Georgetown','(GMT-03:00) Greenland',
	             -1802: '(GMT-03:00) Montevideo','(GMT-02:00) Mid-Atlantic',
	              -600: '(GMT-01:00) Azores',
	              -601: '(GMT-01:00) Cape Verde Is.',
	                 0: 'None',
	                 1: '(GMT) Casablanca',
	                 2: '(GMT) Greenwich Mean Time : Dublin, Edinburgh, Lisbon, London',
	                 3: '(GMT) Monrovia, Reykjavik',
	               600: '(GMT+01:00) Amsterdam, Berlin, Bern, Rome, Stockholm, Vienna',
	               601: '(GMT+01:00) Belgrade, Bratislava, Budapest, Ljubljana, Prague',
	               602: '(GMT+01:00) Brussels, Copenhagen, Madrid, Paris',
	               603: '(GMT+01:00) Sarajevo, Skopje, Warsaw, Zagreb',
	               604: '(GMT+01:00) West Central Africa',
	              1200: '(GMT+02:00) Amman',
	              1201: '(GMT+02:00) Athens, Bucharest, Istanbul',
	              1202: '(GMT+02:00) Beirut',
	              1203: '(GMT+02:00) Cairo',
	              1204: '(GMT+02:00) Harare, Pretoria',
	              1205: '(GMT+02:00) Helsinki, Kyiv, Riga, Sofia, Tallinn, Vilnius',
	              1206: '(GMT+02:00) Jerusalem',
	              1207: '(GMT+02:00) Minsk',
	              1208: '(GMT+02:00) Windhoek',
	              1800: '(GMT+03:00) Baghdad',
	              1801: '(GMT+03:00) Kuwait, Riyadh',
	              1802: '(GMT+03:00) Moscow, St. Petersburg, Volgograd',
	              1803: '(GMT+03:00) Nairobi',
	              1804: '(GMT+03:00) Tbilisi',
	              2100: '(GMT+03:30) Tehran',
	              2400: '(GMT+04:00) Abu Dhabi, Muscat',
	              2401: '(GMT+04:00) Baku',
	              2402: '(GMT+04:00) Caucasus Standard Time',
	              2403: '(GMT+04:00) Port Louis',
	              2404: '(GMT+04:00) Yerevan',
	              2700: '(GMT+04:30) Kabul',
	              3000: '(GMT+05:00) Ekaterinburg',
	              3001: '(GMT+05:00) Islamabad, Karachi',
	              3002: '(GMT+05:00) Tashkent',
	              3300: '(GMT+05:30) Chennai, Kolkata, Mumbai, New Delhi',
	              3301: '(GMT+05:30) Sri Jayawardenepura',
	              3455: '(GMT+05:45) Kathmandu',
	              3600: '(GMT+06:00) Almaty, Novosibirsk',
	              3601: '(GMT+06:00) Astana, Dhaka',
	              3600: '(GMT+06:30) Yangon (Rangoon)',
	              4200: '(GMT+07:00) Bangkok, Hanoi, Jakarta',
	              4201: '(GMT+07:00) Krasnoyarsk',
	              4800: '(GMT+08:00) Beijing, Chongqing, Hong Kong, Urumqi',
	              4801: '(GMT+08:00) Irkutsk, Ulaan Bataar',
	              4802: '(GMT+08:00) Kuala Lumpur, Singapore',
	              4803: '(GMT+08:00) Perth',
	              4804: '(GMT+08:00) Taipei',
	              5400: '(GMT+09:00) Osaka, Sapporo, Tokyo',
	              5401: '(GMT+09:00) Seoul',
	              5402: '(GMT+09:00) Yakutsk',
	              5700: '(GMT+09:30) Adelaide',
	              5701: '(GMT+09:30) Darwin',
	              6000: '(GMT+10:00) Brisbane',
	              6001: '(GMT+10:00) Canberra, Melbourne, Sydney',
	              6002: '(GMT+10:00) Guam, Port Moresby',
	              6003: '(GMT+10:00) Hobart',
	              6004: '(GMT+10:00) Vladivostok',
	              6600: '(GMT+11:00) Magadan, Solomon Is., New Caledonia',
	              7200: '(GMT+12:00) Auckland, Wellington',
	              7201: '(GMT+12:00) Fiji, Kamchatka, Marshall Is.',
	              7800: '(GMT+13:00) Nuku'alofa'"
	        ::= { iTime 1 }
	
	    -- 1.3.6.1.4.1.4756.108.10.5.2
	    iTimezoneAcronym OBJECT-TYPE
	        SYNTAX      DisplayString
	        MAX-ACCESS  read-write
	        STATUS      current
	        DESCRIPTION
	            "User can set the acronym of the time zone.
	             This is a User configurable acronym to identify the time zone.
	             ( Range : Up to 16 alpha-numeric characters and can contain '-', '_' or '.')"
	        ::= { iTime 2 }
	
	    -- 1.3.6.1.4.1.4756.108.10.5.3 
	    iDaylightSavingTimeMode OBJECT-TYPE
	        SYNTAX      INTEGER {
	                        disabled(1),
	                        recurring(2),
	                        nonRecurring(3)
	                    }
	        MAX-ACCESS  read-write
	        STATUS      current
	        DESCRIPTION
	            "This is used to set the clock forward or backward according to the Daylight Saving Time duration.
	             Select 'Disable' to disable the Daylight Saving Time configuration.
	             Select 'Recurring' and configure the Daylight Saving Time duration to repeat the configuration every year.
	             Select 'Non-Recurring' and configure the Daylight Saving Time duration for single time configuration.
	             ( Default : Disabled )"
	        DEFVAL      { 1 }
	        ::= { iTime 3 }
	             
	    -- 1.3.6.1.4.1.4756.108.10.5.4
	    iDaylightSavingStartingWeek OBJECT-TYPE
	        SYNTAX      Integer32 (1..5)
	        MAX-ACCESS  read-write
	        STATUS      current
	        DESCRIPTION
	            "Select the starting week number."
	        ::= { iTime 4 }
	             
	    -- 1.3.6.1.4.1.4756.108.10.5.5
	    iDaylightSavingStartingDay OBJECT-TYPE
	        SYNTAX      INTEGER {
	                        mon(1),
	                        tue(2),
	                        wed(3),
	                        thu(4),
	                        fri(5),
	                        sat(6),
	                        sun(7)
	                    }
	        MAX-ACCESS  read-write
	        STATUS      current
	        DESCRIPTION
	            "Select the starting day."
	        ::= { iTime 5 }
	             
	    -- 1.3.6.1.4.1.4756.108.10.5.6
	    iDaylightSavingStartingMonth OBJECT-TYPE
	        SYNTAX      INTEGER {
	                        jan(1),
	                        feb(2),
	                        mar(3),
	                        apr(4),
	                        may(5),
	                        jun(6),
	                        jul(7),
	                        aug(8),
	                        sep(9),
	                        oct(10),
	                        nov(11),
	                        dec(12)
	                    }
	        MAX-ACCESS  read-write
	        STATUS      current
	        DESCRIPTION
	            "Select the starting day."
	        ::= { iTime 6 }
	             
	    -- 1.3.6.1.4.1.4756.108.10.5.7
	    iDaylightSavingStartingDate OBJECT-TYPE
	        SYNTAX      Integer32 (1..31)
	        MAX-ACCESS  read-write
	        STATUS      current
	        DESCRIPTION
	            "Select the starting date."
	        ::= { iTime 7 }
	             
	    -- 1.3.6.1.4.1.4756.108.10.5.8
	    iDaylightSavingStartingYear OBJECT-TYPE
	        SYNTAX      Integer32 (2000..2097)
	        MAX-ACCESS  read-write
	        STATUS      current
	        DESCRIPTION
	            "Select the starting year."
	        ::= { iTime 8 }
	            
	    -- 1.3.6.1.4.1.4756.108.10.5.9
	    iDaylightSavingStartingHour OBJECT-TYPE
	        SYNTAX      Integer32 (0..23)
	        MAX-ACCESS  read-write
	        STATUS      current
	        DESCRIPTION
	            "Select the starting Hour."
	        ::= { iTime 9 }
	            
	    -- 1.3.6.1.4.1.4756.108.10.5.10
	    iDaylightSavingStartingMinute OBJECT-TYPE
	        SYNTAX      Integer32 (0..59)
	        MAX-ACCESS  read-write
	        STATUS      current
	        DESCRIPTION
	            "Select the starting Minute."
	        ::= { iTime 10 }
	             
	    -- 1.3.6.1.4.1.4756.108.10.5.11
	    iDaylightSavingEndingWeek OBJECT-TYPE
	        SYNTAX      Integer32 (1..5)
	        MAX-ACCESS  read-write
	        STATUS      current
	        DESCRIPTION
	            "Select the ending week number."
	        ::= { iTime 11 }
	             
	    -- 1.3.6.1.4.1.4756.108.10.5.12
	    iDaylightSavingEndingDay OBJECT-TYPE
	        SYNTAX      INTEGER {
	                        mon(1),
	                        tue(2),
	                        wed(3),
	                        thu(4),
	                        fri(5),
	                        sat(6),
	                        sun(7)
	                    }
	        MAX-ACCESS  read-write
	        STATUS      current
	        DESCRIPTION
	            "Select the ending day."
	        ::= { iTime 12 }
	             
	    -- 1.3.6.1.4.1.4756.108.10.5.13
	    iDaylightSavingEndingMonth OBJECT-TYPE
	        SYNTAX      INTEGER {
	                        jan(1),
	                        feb(2),
	                        mar(3),
	                        apr(4),
	                        may(5),
	                        jun(6),
	                        jul(7),
	                        aug(8),
	                        sep(9),
	                        oct(10),
	                        nov(11),
	                        dec(12)
	                    }
	        MAX-ACCESS  read-write
	        STATUS      current
	        DESCRIPTION
	            "Select the ending day."
	        ::= { iTime 13 }
	             
	    -- 1.3.6.1.4.1.4756.108.10.5.14
	    iDaylightSavingEndingDate OBJECT-TYPE
	        SYNTAX      Integer32 (1..31)
	        MAX-ACCESS  read-write
	        STATUS      current
	        DESCRIPTION
	            "Select the ending date."
	        ::= { iTime 14 }
	             
	    -- 1.3.6.1.4.1.4756.108.10.5.15
	    iDaylightSavingEndingYear OBJECT-TYPE
	        SYNTAX      Integer32 (2000..2097)
	        MAX-ACCESS  read-write
	        STATUS      current
	        DESCRIPTION
	            "Select the ending year."
	        ::= { iTime 15 }
	            
	    -- 1.3.6.1.4.1.4756.108.10.5.16
	    iDaylightSavingEndingHour OBJECT-TYPE
	        SYNTAX      Integer32 (0..23)
	        MAX-ACCESS  read-write
	        STATUS      current
	        DESCRIPTION
	            "Select the ending Hour."
	        ::= { iTime 16 }
	            
	    -- 1.3.6.1.4.1.4756.108.10.5.17
	    iDaylightSavingEndingMinute OBJECT-TYPE
	        SYNTAX      Integer32 (0..59)
	        MAX-ACCESS  read-write
	        STATUS      current
	        DESCRIPTION
	            "Select the ending Minute."
	        ::= { iTime 17 }
	            
	    -- 1.3.6.1.4.1.4756.108.10.5.18
	    iDaylightSavingTimeOffset OBJECT-TYPE
	        SYNTAX      Integer32 (0..1440)
	        MAX-ACCESS  read-write
	        STATUS      current
	        DESCRIPTION
	            "Enter the number of minutes to add during Daylight Saving Time. ( Range: 1 to 1440 )"
	        ::= { iTime 18 }
	
	    iSystemLog OBJECT IDENTIFIER ::= { iSystem 6 }  
	    
	    iSystemLogServTable OBJECT-TYPE
	        SYNTAX      SEQUENCE OF ISystemLogServEntry
	        MAX-ACCESS  not-accessible
	        STATUS      current
	        DESCRIPTION
	            "The switch system log server information."
	        ::= { iSystemLog 1 }
	
	    iSystemLogServEntry OBJECT-TYPE
	        SYNTAX      ISystemLogServEntry
	        MAX-ACCESS  not-accessible
	        STATUS      current
	        DESCRIPTION
	            "The system log server entry."
	        INDEX { iSystemLogServIdx }
	        ::= { iSystemLogServTable 1 }
	
	    ISystemLogServEntry ::=
	        SEQUENCE {
	        	iSystemLogServIdx	        Integer32,
	            iSystemLogServerMode        INTEGER,
	            iSystemLogServerAddress     DisplayString,
	            iSystemLogLevel      		INTEGER
	        }  
	        
	     iSystemLogServIdx OBJECT-TYPE
	        SYNTAX      Integer32 (1..3)
	        MAX-ACCESS  not-accessible
	        STATUS      current
	        DESCRIPTION
	            "The Index of the system log server entry."
	        ::= { iSystemLogServEntry 1 }

	
	    iSystemLogServerMode OBJECT-TYPE
	        SYNTAX      INTEGER {
	                        enabled(1),
	                        disabled(2)
	                    }
	        MAX-ACCESS  read-write
	        STATUS      current
	        DESCRIPTION
	            "Indicates the server mode operation.
	             Enabled: Enable server mode operation.
	             Disabled: Disable server mode operation."
	        ::= { iSystemLogServEntry 2 }
	           
	    iSystemLogServerAddress OBJECT-TYPE
	        SYNTAX      DisplayString
	        MAX-ACCESS  read-write
	        STATUS      current
	        DESCRIPTION
	            "Indicates the IPv4 host address of syslog server.
	             If the switch provide DNS feature, it also can be a Host Name."
	        ::= { iSystemLogServEntry 3 }
	
	    iSystemLogLevel OBJECT-TYPE
	        SYNTAX      INTEGER {
	                        info(1),
	                        warning(2),
	                        error(3)
	                    }
	        MAX-ACCESS  read-write
	        STATUS      current
	        DESCRIPTION
	            "Indicates what kind of message will send to syslog server. Possible modes are:
	             Info: Send informations, warnings and errors.
	             Warning: Send warnings and errors.
	             Error: Send errors."
	        ::= { iSystemLogServEntry 4 }
	
	    -- 1.3.6.1.4.1.4756.108.10.6.4
	    iSystemLogClear OBJECT-TYPE
	        SYNTAX      INTEGER {
	                        trigger(1),
	                        normal(2)
	                    }
	        MAX-ACCESS  read-write
	        STATUS      current
	        DESCRIPTION
	            "Flushes all system log entries."
	        ::= { iSystemLog 2 }
	
	    -- 1.3.6.1.4.1.4756.108.10.6.5
	    iSystemLogTable OBJECT-TYPE
	        SYNTAX      SEQUENCE OF ISystemLogEntry
	        MAX-ACCESS  not-accessible
	        STATUS      current
	        DESCRIPTION
	            "The switch system log information."
	        ::= { iSystemLog 3 }
	
	    -- 1.3.6.1.4.1.4756.108.10.6.5.1
	    iSystemLogEntry OBJECT-TYPE
	        SYNTAX      ISystemLogEntry
	        MAX-ACCESS  not-accessible
	        STATUS      current
	        DESCRIPTION
	            "The system log entry."
	        INDEX { iSystemLogMessageID }
	        ::= { iSystemLogTable 1 }
	
	    ISystemLogEntry ::=
	        SEQUENCE {
	            iSystemLogMessageID        Integer32,
	            iSystemLogMessageLevel     INTEGER,
	            iSystemLogMessageTime      DisplayString,
	            iSystemLogMessage          DisplayString
	        }
	
	    -- 1.3.6.1.4.1.4756.108.10.6.5.1.1
	    iSystemLogMessageID OBJECT-TYPE
	        SYNTAX      Integer32 (1..999)
	        MAX-ACCESS  not-accessible
	        STATUS      current
	        DESCRIPTION
	            "The Index of the system log entry."
	        ::= { iSystemLogEntry 1 }
	                        
	    -- 1.3.6.1.4.1.4756.108.10.6.5.1.2
	    iSystemLogMessageLevel OBJECT-TYPE
	        SYNTAX      INTEGER {
	                        info(1),
	                        warning(2),
	                        error(3)
	                    }
	        MAX-ACCESS  read-only
	        STATUS      current
	        DESCRIPTION
	            "Indicates what kind of message."
	        ::= { iSystemLogEntry 2 }
	
	    -- 1.3.6.1.4.1.4756.108.10.6.5.1.3
	    iSystemLogMessageTime OBJECT-TYPE
	        SYNTAX      DisplayString
	        MAX-ACCESS  read-only
	        STATUS      current
	        DESCRIPTION
	            "The time of the system log entry."
	        ::= { iSystemLogEntry 3 }
	                            
	    -- 1.3.6.1.4.1.4756.108.10.6.5.1.4
	    iSystemLogMessage OBJECT-TYPE
	            SYNTAX      DisplayString
	            MAX-ACCESS  read-only
	            STATUS      current
	            DESCRIPTION
	                "The message of the system log entry."
	            ::= { iSystemLogEntry 4 }
	            
	  
	    -- 1.3.6.1.4.1.4756.108.10.7
	    iMaintenance OBJECT IDENTIFIER ::= { iSystem 7 }
	
	    -- 1.3.6.1.4.1.4756.108.10.7.1
	    iRestartDevice OBJECT-TYPE
	        SYNTAX      INTEGER {
	                        trigger(1),
	                        normal(2)
	                    }
	        MAX-ACCESS  read-write
	        STATUS      current
	        DESCRIPTION
	            "You can restart the device on this node."
	        ::= { iMaintenance 1 }
	        
	    -- 1.3.6.1.4.1.4756.108.10.7.2
	    iIPv4LoadFirmware OBJECT-TYPE
	        SYNTAX      DisplayString
	        MAX-ACCESS  read-write
	        STATUS      current
	        DESCRIPTION
	            "Load new firmware form TFTP Server 
	             Syntax: <ip_addr_string> <file_name>
	            "
	        ::= { iMaintenance 2 }
	    
	    -- 1.3.6.1.4.1.4756.108.10.7.3
	    iIPv6LoadFirmware OBJECT-TYPE
	        SYNTAX      DisplayString
	        MAX-ACCESS  read-write
	        STATUS      current
	        DESCRIPTION
	            "Load new firmware form TFTP Server
	             Syntax: <ipv6_server> <file_name> 
	            "
	        ::= { iMaintenance 3 }
	    
	    -- 1.3.6.1.4.1.4756.108.10.7.4
	    iFirmwareUpgradeStatus OBJECT-TYPE
	        SYNTAX      INTEGER {
	        			 			normal(1),
	        			 			erasing(2),
	        			 			programming(3)
	        			}	        	
	        MAX-ACCESS  read-only
	        STATUS      current
	        DESCRIPTION
	            "Firmware Upgrade Status"
	        ::= { iMaintenance 4 }
	        
	    iSaveStartupConfig OBJECT-TYPE
	        SYNTAX      INTEGER {
	                        trigger(1),
	                        normal(2)
	                    }   	
	        MAX-ACCESS  read-write
	        STATUS      current
	        DESCRIPTION
	            "Save Running Configuration to startup-config"
	        ::= { iMaintenance 5 }
                              
-- Ports
    -- 1.3.6.1.4.1.4756.136.20
    iPorts OBJECT IDENTIFIER ::= { msw4424a 30 }
    
    -- 1.3.6.1.4.1.4756.108.30.1
    iPortsConfigTable OBJECT-TYPE
        SYNTAX      SEQUENCE OF IPortsConfigEntry
        MAX-ACCESS  not-accessible
        STATUS      current
        DESCRIPTION
            "This table shows current port configurations. Ports can also be configured here."
        ::= { iPorts 1 }

    -- 1.3.6.1.4.1.4756.108.30.1.1
    iPortsConfigEntry OBJECT-TYPE
        SYNTAX      IPortsConfigEntry
        MAX-ACCESS  not-accessible
        STATUS      current
        DESCRIPTION
            "The entry of ports."
        INDEX { iPortIndex }
        ::= { iPortsConfigTable 1 }

    IPortsConfigEntry ::=
        SEQUENCE {
            iPortLink              INTEGER,
            iPortSpeedCurrent      DisplayString,
            iPortSpeedMode         INTEGER,
            iPortMaxFrameSize      Integer32,
            iPortExcCollMode       INTEGER
        }
                         
        -- 1.3.6.1.4.1.4756.108.30.1.1.1    
        iPortLink OBJECT-TYPE
            SYNTAX      INTEGER {
                            linkUp(1),
                            linkDown(2),
                            linkDownByACL(3),
                            linkDownByThermalProtect(4),
                            linkDownByLoopProtect(5)
                        }
            MAX-ACCESS  read-only
            STATUS      current
            DESCRIPTION
                "The current link state.
                	1: linkUp
                	2: linkDown
                	3: linkDownByACL
                	4: linkDownByThermalProtect
                	5: linkDownByLoopProtect
                "
            ::= { iPortsConfigEntry 1 }
                  
        -- 1.3.6.1.4.1.4756.108.30.1.1.2    
        iPortSpeedCurrent OBJECT-TYPE
            SYNTAX      DisplayString
            MAX-ACCESS  read-only
            STATUS      current
            DESCRIPTION
                "Provides the current link speed of the port.

                "
            ::= { iPortsConfigEntry 2 }
                  
        -- 1.3.6.1.4.1.4756.108.30.1.1.3    
        iPortSpeedMode OBJECT-TYPE
            SYNTAX      INTEGER {
                            disabled(1),
                            auto(2),
                            speed100Mfdx(6),
                            speed1Gfdx(7),
                            speed10G(13)                           
                        }
            MAX-ACCESS  read-write
            STATUS      current
            DESCRIPTION
                "Select link speed for the switch port."
            ::= { iPortsConfigEntry 3 }                   
                  
        -- 1.3.6.1.4.1.4756.108.30.1.1.7    
        iPortMaxFrameSize OBJECT-TYPE
            SYNTAX      Integer32 (1518..10056)
            MAX-ACCESS  read-write
            STATUS      current
            DESCRIPTION
                "The maximum frame size allowed for the switch port, including FCS."
            ::= { iPortsConfigEntry 7 }
                  
        -- 1.3.6.1.4.1.4756.108.30.1.1.8    
        iPortExcCollMode OBJECT-TYPE
            SYNTAX      INTEGER {
            								none(0),
                            discard(1),
                            restart(2)
                        }
            MAX-ACCESS  read-write
            STATUS      current
            DESCRIPTION
                "Configure port transmit collision behavior.
                 Discard: Discard frame after 16 collisions (default).
                 Restart: Restart backoff algorithm after 16 collisions."
            DEFVAL      { 1 }
            ::= { iPortsConfigEntry 8 }

    -- 1.3.6.1.4.1.4756.108.30.2
    iPortsTrafficClear OBJECT-TYPE
        SYNTAX      INTEGER {
                        trigger(1),
                        normal(2)
                    }
        MAX-ACCESS  read-write
        STATUS      current
        DESCRIPTION
            "Clears the counters for all ports."
        ::= { iPorts 2 }

    -- 1.3.6.1.4.1.4756.108.30.3
    iPortsTrafficOverviewTable OBJECT-TYPE
        SYNTAX      SEQUENCE OF IPortsTrafficOverviewEntry
        MAX-ACCESS  not-accessible
        STATUS      current
        DESCRIPTION
            "This table provides an overview of general traffic statistics for all switch ports."
        ::= { iPorts 3 }

    -- 1.3.6.1.4.1.4756.108.30.3.1
    iPortsTrafficOverviewEntry OBJECT-TYPE
        SYNTAX      IPortsTrafficOverviewEntry
        MAX-ACCESS  not-accessible
        STATUS      current
        DESCRIPTION
            "The entry of ports."
        INDEX { iPortIndex }
        ::= { iPortsTrafficOverviewTable 1 }

    IPortsTrafficOverviewEntry ::=
        SEQUENCE {
            iReceivedPackets       DisplayString,
            iTransmittedPackets    DisplayString,
            iReceivedBytes         DisplayString,
            iTransmittedBytes      DisplayString,
            iReceivedErrors        DisplayString,
            iTransmittedErrors     DisplayString,
            iReceivedDrops         DisplayString,
            iTransmittedDrops      DisplayString,
            iReceivedFiltered      DisplayString
        }
                  
        -- 1.3.6.1.4.1.4756.108.30.3.1.1    
        iReceivedPackets OBJECT-TYPE
            SYNTAX      DisplayString
            UNITS       "Packets"
            MAX-ACCESS  read-only
            STATUS      current
            DESCRIPTION
                "The number of received packets per port."
            ::= { iPortsTrafficOverviewEntry 1 }

        -- 1.3.6.1.4.1.4756.108.30.3.1.2    
        iTransmittedPackets OBJECT-TYPE
            SYNTAX      DisplayString
            UNITS       "Packets"
            MAX-ACCESS  read-only
            STATUS      current
            DESCRIPTION
                "The number of transmitted packets per port."
            ::= { iPortsTrafficOverviewEntry 2 }
                  
        -- 1.3.6.1.4.1.4756.108.30.3.1.3    
        iReceivedBytes OBJECT-TYPE
            SYNTAX      DisplayString
            UNITS       "Bytes"
            MAX-ACCESS  read-only
            STATUS      current
            DESCRIPTION
                "The number of received bytes per port."
            ::= { iPortsTrafficOverviewEntry 3 }
                  
        -- 1.3.6.1.4.1.4756.108.30.3.1.4    
        iTransmittedBytes OBJECT-TYPE
            SYNTAX      DisplayString
            UNITS       "Bytes"
            MAX-ACCESS  read-only
            STATUS      current
            DESCRIPTION
                "The number of transmitted bytes per port."
            ::= { iPortsTrafficOverviewEntry 4 }
                  
        -- 1.3.6.1.4.1.4756.108.30.3.1.5    
        iReceivedErrors OBJECT-TYPE
            SYNTAX      DisplayString
            UNITS       "Packets"
            MAX-ACCESS  read-only
            STATUS      current
            DESCRIPTION
                "The number of frames received in error."
            ::= { iPortsTrafficOverviewEntry 5 }
                  
        -- 1.3.6.1.4.1.4756.108.30.3.1.6    
        iTransmittedErrors OBJECT-TYPE
            SYNTAX      DisplayString
            UNITS       "Packets"
            MAX-ACCESS  read-only
            STATUS      current
            DESCRIPTION
                "The number of incomplete transmissions per port."
            ::= { iPortsTrafficOverviewEntry 6 }
                  
        -- 1.3.6.1.4.1.4756.108.30.3.1.7    
        iReceivedDrops OBJECT-TYPE
            SYNTAX      DisplayString
            UNITS       "Packets"
            MAX-ACCESS  read-only
            STATUS      current
            DESCRIPTION
                "The number of frames discarded due to ingress congestion."
            ::= { iPortsTrafficOverviewEntry 7 }
                  
        -- 1.3.6.1.4.1.4756.108.30.3.1.8    
        iTransmittedDrops OBJECT-TYPE
            SYNTAX      DisplayString
            UNITS       "Packets"
            MAX-ACCESS  read-only
            STATUS      current
            DESCRIPTION
                "The number of frames discarded due to egress congestion."
            ::= { iPortsTrafficOverviewEntry 8 }
                  
        -- 1.3.6.1.4.1.4756.108.30.3.1.9    
        iReceivedFiltered OBJECT-TYPE
            SYNTAX      DisplayString
            UNITS       "Packets"
            MAX-ACCESS  read-only
            STATUS      current
            DESCRIPTION
                "The number of received frames filtered by the forwarding process."
            ::= { iPortsTrafficOverviewEntry 9 }

    -- 1.3.6.1.4.1.4756.108.30.4
    iPortsQosStatisticsClear OBJECT-TYPE
        SYNTAX      INTEGER {
                        trigger(1),
                        normal(2)
                    }
        MAX-ACCESS  read-write
        STATUS      current
        DESCRIPTION
            "Clears the counters for all ports."
        ::= { iPorts 4 }

    -- 1.3.6.1.4.1.4756.108.30.5
    iPortsQosStatisticsTable OBJECT-TYPE
        SYNTAX      SEQUENCE OF IPortsQosStatisticsEntry
        MAX-ACCESS  not-accessible
        STATUS      current
        DESCRIPTION
            "This table provides statistics for the different queues for all switch ports."
        ::= { iPorts 5 }

    -- 1.3.6.1.4.1.4756.108.30.5.1
    iPortsQosStatisticsEntry OBJECT-TYPE
        SYNTAX      IPortsQosStatisticsEntry
        MAX-ACCESS  not-accessible
        STATUS      current
        DESCRIPTION
            "Each entry contains 8 QoS queues per port."
        INDEX { iPortIndex, iQueueIndex }
        ::= { iPortsQosStatisticsTable 1 }

    IPortsQosStatisticsEntry ::=
        SEQUENCE {
            iQueueIndex            Integer32,
            iQueueRxPackets        DisplayString,
            iQueueTxPackets        DisplayString
        }

        -- 1.3.6.1.4.1.4756.108.30.5.1.1
        iQueueIndex OBJECT-TYPE
            SYNTAX      Integer32 (0..7)
            MAX-ACCESS  read-only
            STATUS      current
            DESCRIPTION
                "There are 8 QoS queues per port. Q0 is the lowest priority queue."
            ::= { iPortsQosStatisticsEntry 1 }
                  
        -- 1.3.6.1.4.1.4756.108.30.5.1.2    
        iQueueRxPackets OBJECT-TYPE
            SYNTAX      DisplayString
            MAX-ACCESS  read-only
            STATUS      current
            DESCRIPTION
                "The number of received packets per queue."
            ::= { iPortsQosStatisticsEntry 2 }
                  
        -- 1.3.6.1.4.1.4756.108.30.5.1.3    
        iQueueTxPackets OBJECT-TYPE
            SYNTAX      DisplayString
            MAX-ACCESS  read-only
            STATUS      current
            DESCRIPTION
                "The number of transmitted  packets per queue."
            ::= { iPortsQosStatisticsEntry 3 }

    -- 1.3.6.1.4.1.4756.108.30.6
    iPortsQclResolveConflict  OBJECT-TYPE
        SYNTAX      INTEGER {
                        trigger(1),
                        normal(2)
                    }
        MAX-ACCESS  read-write
        STATUS      current
        DESCRIPTION
            "Resolves conflict by releaseing the resource required by the QCE."
        ::= { iPorts 6 }

    -- 1.3.6.1.4.1.4756.108.30.7
    iPortsQclStatusTable OBJECT-TYPE
        SYNTAX      SEQUENCE OF IPortsQclStatusEntry
        MAX-ACCESS  not-accessible
        STATUS      current
        DESCRIPTION
            "This table shows the QCL status by different QCL users."
        ::= { iPorts 7 }

    -- 1.3.6.1.4.1.4756.108.30.7.1
    iPortsQclStatusEntry OBJECT-TYPE
        SYNTAX      IPortsQclStatusEntry
        MAX-ACCESS  not-accessible
        STATUS      current
        DESCRIPTION
            "Each entry describes the QCE that is defined."
        INDEX { iQclStatusIndex }
        ::= { iPortsQclStatusTable 1 }

    IPortsQclStatusEntry ::=
        SEQUENCE {
            iQclStatusIndex    Integer32,
            iQclUser           INTEGER,
            iQCEntryNumber     Integer32,
            iQclFrameType      INTEGER,
            iQclPort           DisplayString,
            iQclActionClass    Integer32,
            iQclActionDPL      Integer32,
            iQclActionDSCP     Integer32,
            iQclConflict       TruthValue
        }

        -- 1.3.6.1.4.1.4756.108.30.7.1.1
        iQclStatusIndex OBJECT-TYPE
            SYNTAX      Integer32 (1..240)
            MAX-ACCESS  read-only
            STATUS      current
            DESCRIPTION
                "The index of QoS Control List Status."
            ::= { iPortsQclStatusEntry 1 }
                  
        -- 1.3.6.1.4.1.4756.108.30.7.1.2    
        iQclUser OBJECT-TYPE
            SYNTAX      INTEGER {
                            static(1),
                            u-ring(2)
                        }
            MAX-ACCESS  read-only
            STATUS      current
            DESCRIPTION
                "Indicates the QCL user."
            ::= { iPortsQclStatusEntry 2 }
                  
        -- 1.3.6.1.4.1.4756.108.30.7.1.3    
        iQCEntryNumber OBJECT-TYPE
            SYNTAX      Integer32
            MAX-ACCESS  read-only
            STATUS      current
            DESCRIPTION
                "Indicates the index of QCE."
            ::= { iPortsQclStatusEntry 3 }
                  
        -- 1.3.6.1.4.1.4756.108.30.7.1.4    
        iQclFrameType OBJECT-TYPE
            SYNTAX      INTEGER {
                            any(1),
                            ethernet(2),
                            llc(3),
                            snap(4),
                            ipv4(5),
                            ipv6(6)
                        }
            MAX-ACCESS  read-only
            STATUS      current
            DESCRIPTION
                "Indicates the type of frame to look for incomming frames. Possible frame types are:
                 Any: The QCE will match all frame type.
                 Ethernet: Only Ethernet frames (with Ether Type 0x600-0xFFFF) are allowed.
                 LLC: Only (LLC) frames are allowed.
                 LLC: Only (SNAP) frames are allowed.
                 IPv4: The QCE will match only IPV4 frames.
                 IPv6: The QCE will match only IPV6 frames."
            ::= { iPortsQclStatusEntry 4 }
                  
        -- 1.3.6.1.4.1.4756.108.30.7.1.5    
        iQclPort OBJECT-TYPE
            SYNTAX      DisplayString (SIZE (1..128))
            MAX-ACCESS  read-only
            STATUS      current
            DESCRIPTION
                "Indicates the list of ports configured with the QCE."
            ::= { iPortsQclStatusEntry 5 }     
                  
        -- 1.3.6.1.4.1.4756.108.30.7.1.6    
        iQclActionClass OBJECT-TYPE
            SYNTAX      Integer32  (-1 | 0..7)
            MAX-ACCESS  read-only
            STATUS      current
            DESCRIPTION
                "Classified QoS Class, if a frame matches the QCE it will be put in the queue.
                 -1: default
                 0 to 7: class0 to class7"
            DEFVAL      { -1 }
            ::= { iPortsQclStatusEntry 6 }
                  
        -- 1.3.6.1.4.1.4756.108.30.7.1.7    
        iQclActionDPL OBJECT-TYPE
            SYNTAX      Integer32 (-1 | 0..1)
            MAX-ACCESS  read-only
            STATUS      current
            DESCRIPTION
                "Drop Precedence Level,
                 if a frame matches the QCE then DP level will set to value displayed under DPL column.
                 -1: default
                 0, 1: DPL0 and DPL1"
            DEFVAL      { -1 }
            ::= { iPortsQclStatusEntry 7 }
                  
        -- 1.3.6.1.4.1.4756.108.4.7.1.8    
        iQclActionDSCP OBJECT-TYPE
            SYNTAX      Integer32 (-1 | 0..63)
            MAX-ACCESS  read-only
            STATUS      current
            DESCRIPTION
                "If a frame matches the QCE then DSCP will be classified with the value displayed under DSCP column.
                 -1: default
                 0 to 63: DSCP0 to DSCP63"
            DEFVAL      { -1 }
            ::= { iPortsQclStatusEntry 8 }
                  
        -- 1.3.6.1.4.1.4756.108.30.7.1.9    
        iQclConflict OBJECT-TYPE
            SYNTAX      TruthValue
            MAX-ACCESS  read-only
            STATUS      current
            DESCRIPTION
                "Displays QCE status. It may happen that resources required to add a QCE may not available."
            ::= { iPortsQclStatusEntry 9 }

	    -- 1.3.6.1.4.1.4756.108.30.8
	    iPortStatus OBJECT IDENTIFIER ::= { iPorts 8 }
	    
	    -- 1.3.6.1.4.1.4756.108.30.8.1
	    iPower1Status OBJECT-TYPE
	        SYNTAX      INTEGER {
	                        on(1),
	                        off(2)
	                    }
	        MAX-ACCESS  read-only
	        STATUS      current
	        DESCRIPTION
				"The Switch Power 1 Status
	            	1:Power ON
	                2:Power OFF
	            "
	        ::= { iPortStatus 1 }     
	        
	    -- 1.3.6.1.4.1.4756.108.30.8.2
	    iPower2Status OBJECT-TYPE
	        SYNTAX      INTEGER {
	                        on(1),
	                        off(2)
	                    }
	        MAX-ACCESS  read-only
	        STATUS      current
	        DESCRIPTION
				"The Switch Power 2 Status
	            	1:Power ON
	                2:Power OFF
	            "
	        ::= { iPortStatus 2 }     
	        
	    -- 1.3.6.1.4.1.4756.108.30.8.3
	    iFaultAlarmStatus OBJECT-TYPE
	        SYNTAX      INTEGER {
	                        on(1),
	                        off(2)
	                    }
	        MAX-ACCESS  read-only
	        STATUS      current
	        DESCRIPTION
				"The Switch Fault Alarm Status
	            	1:Fault Alarm ON
	                2:Fault Alarm OFF
	            "
	        ::= { iPortStatus 3 }
	    
	    -- 1.3.6.1.4.1.4756.108.30.8.4    
	    iCPUActiveStatus OBJECT-TYPE
	        SYNTAX      INTEGER {
	                        on(1),
	                        off(2)
	                    }
	        MAX-ACCESS  read-only
	        STATUS      current
	        DESCRIPTION
				"The Switch CPU Active Status
	            	1:CPU ON
	                2:CPU OFF
	            "
	        ::= { iPortStatus 4 }
	        
		-- 1.3.6.1.4.1.4756.108.30.8.5
	    iRingMasterStatus OBJECT-TYPE
	        SYNTAX      INTEGER {
	                        on(1),
	                        off(2)
	                    }
	        MAX-ACCESS  read-only
	        STATUS      current
	        DESCRIPTION
				"The Switch Ring Master Status
	            	1:Ring Master ON
	                2:Ring Master OFF
	            "
	        ::= { iPortStatus 5 }

    -- 1.3.6.1.4.1.4756.136.30.20
    iSFPTable OBJECT-TYPE
        SYNTAX      SEQUENCE OF ISFPEntry
        MAX-ACCESS  not-accessible
        STATUS      current
        DESCRIPTION
            "This table shows current port configurations. Ports can also be configured here."
        ::= { iPorts 20 }

    -- 1.3.6.1.4.1.4756.136.30.20.1
    iSFPEntry OBJECT-TYPE
        SYNTAX      ISFPEntry
        MAX-ACCESS  not-accessible
        STATUS      current
        DESCRIPTION
            "The entry of ports."
        INDEX { iPortIndex }
        ::= { iSFPTable 1 }

    ISFPEntry ::=
        SEQUENCE {
        		iPortIndex			    Integer32,
            iSfpModule              INTEGER,
            iSfpVendorName      	DisplayString,
            iSfpVendorPartNumber    DisplayString,
            iSfpType 			    INTEGER,
            iSfpWaveLength   		DisplayString,
            iSfpWaveLength2      	DisplayString,
            iSfpLinkLength          DisplayString,
            iSfpTXPower       	    DisplayString,
            iSfpRXPower       		DisplayString,
            iSfpRXSensitivity       DisplayString,
            iSfpTemperature         DisplayString
        }
    
    	-- 1.3.6.1.4.1.4756.136.30.20.1
        iPortIndex OBJECT-TYPE
            SYNTAX      Integer32 (1..29)
            MAX-ACCESS  read-only
            STATUS      current
            DESCRIPTION
                "
                "
            ::= { iSFPEntry 1 }
    
    	-- 1.3.6.1.4.1.4756.136.30.20.2
    	iSfpModule  OBJECT-TYPE
        SYNTAX      INTEGER {
                        inserted(1),
                        removed(2)
                    }
        MAX-ACCESS  read-only
        STATUS      current
        DESCRIPTION
            "Indicate the SFP module is existent or not."
        ::= { iSFPEntry 2 }

	    -- 1.3.6.1.4.1.4756.136.30.20.3
	    iSfpVendorName  OBJECT-TYPE
	        SYNTAX      DisplayString
	        MAX-ACCESS  read-only
	        STATUS      current
	        DESCRIPTION
	            "The name of SFP vendor."
	        ::= { iSFPEntry 3 }
	
	    -- 1.3.6.1.4.1.4756.136.30.20.4
	    iSfpVendorPartNumber  OBJECT-TYPE
	        SYNTAX      DisplayString
	        MAX-ACCESS  read-only
	        STATUS      current
	        DESCRIPTION
	            "The part number provided by SFP vendor."
	        ::= { iSFPEntry 4 }
		
	    -- 1.3.6.1.4.1.4756.136.30.20.5
	    iSfpType  OBJECT-TYPE
	        SYNTAX      INTEGER {
	                        none(0),
	                        singleMode(1),
	                        multiMode(2)
	                    }
	        MAX-ACCESS  read-only
	        STATUS      current
	        DESCRIPTION
	            "The type of fibre channel transmission media."
	        ::= { iSFPEntry 5 }
	        	
	    -- 1.3.6.1.4.1.4756.136.30.20.6
	    iSfpWaveLength  OBJECT-TYPE
	        SYNTAX      DisplayString
	        MAX-ACCESS  read-only
	        STATUS      current
	        DESCRIPTION
	            "The transceiver Laser wavelength tx."
	        ::= { iSFPEntry 6}
	
	    -- 1.3.6.1.4.1.4756.136.30.20.7
	    iSfpWaveLength2  OBJECT-TYPE
	        SYNTAX      DisplayString
	        MAX-ACCESS  read-only
	        STATUS      current
	        DESCRIPTION
	            "The transceiver Laser wavelength rx."
	        ::= { iSFPEntry 7 }
	
	    -- 1.3.6.1.4.1.4756.136.30.20.8
	    iSfpLinkLength  OBJECT-TYPE
	        SYNTAX      DisplayString
	        MAX-ACCESS  read-only
	        STATUS      current
	        DESCRIPTION
	            "The transceiver Link Length."
	        ::= { iSFPEntry 8 }
	
	    -- 1.3.6.1.4.1.4756.136.30.20.9
	    iSfpTXPower  OBJECT-TYPE
	        SYNTAX      DisplayString
	        MAX-ACCESS  read-only
	        STATUS      current
	        DESCRIPTION
	            "The transceiver TX Power."
	        ::= { iSFPEntry 9 }
        
        -- 1.3.6.1.4.1.4756.136.30.20.10
	    iSfpRXPower  OBJECT-TYPE
	        SYNTAX      DisplayString
	        MAX-ACCESS  read-only
	        STATUS      current
	        DESCRIPTION
	            "The transceiver RX Power."
	        ::= { iSFPEntry 10 }
	    
	    -- 1.3.6.1.4.1.4756.136.30.20.11
	    iSfpRXSensitivity  OBJECT-TYPE
	        SYNTAX      DisplayString
	        MAX-ACCESS  read-only
	        STATUS      current
	        DESCRIPTION
	            "The transceiver RX Sensitivity."
	        ::= { iSFPEntry 11 }    
	        
	    -- 1.3.6.1.4.1.4756.136.30.20.13
	    iSfpTemperature  OBJECT-TYPE
	        SYNTAX      DisplayString
	        MAX-ACCESS  read-only
	        STATUS      current
	        DESCRIPTION
	            "The transceiver temperature in degree C."
	        ::= { iSFPEntry 12 }  


-- Security
    -- 1.3.6.1.4.1.4756.108.40
    iSecurity OBJECT IDENTIFIER ::= { msw4424a 40 }

    -- 1.3.6.1.4.1.4756.108.40.1
    iSecuritySwitch OBJECT IDENTIFIER ::= { iSecurity 1 }

    -- 1.3.6.1.4.1.4756.108.40.1.1    
    iAddUser OBJECT-TYPE
        SYNTAX      OCTET STRING (SIZE (1..32))
        MAX-ACCESS  read-write
        STATUS      current
        DESCRIPTION
            "A string identifying the user name that this entry should belong to.
             The allowed string length is 1 to 32.
             The valid user name is a combination of letters, numbers and underscores.
            "
        ::= { iSecuritySwitch 1 }

    -- 1.3.6.1.4.1.4756.108.40.1.2    
    iDeleteUser OBJECT-TYPE
        SYNTAX      DisplayString
        MAX-ACCESS  read-write
        STATUS      current
        DESCRIPTION
            "Delete the user by name.
             Syntax: 
             		<user_name>
            "
        ::= { iSecuritySwitch 2 }

    -- 1.3.6.1.4.1.4756.108.40.1.3
    iUserConfigTable OBJECT-TYPE
        SYNTAX      SEQUENCE OF IUserConfigEntry
        MAX-ACCESS  not-accessible
        STATUS      current
        DESCRIPTION
            "This table provides User Configurations."
        ::= { iSecuritySwitch 3 }

    -- 1.3.6.1.4.1.4756.108.40.1.3.1
    iUserConfigEntry OBJECT-TYPE
        SYNTAX      IUserConfigEntry
        MAX-ACCESS  not-accessible
        STATUS      current
        DESCRIPTION
            "The Entry of User Configurations."
        INDEX { iUserIndex }
        ::= { iUserConfigTable 1 }

    IUserConfigEntry ::=
        SEQUENCE {
            iUserIndex             Integer32,
            iUserName              OCTET STRING,
            iUserPassword          OCTET STRING,
            iUserPrivilegeLevel    Integer32
        }

        -- 1.3.6.1.4.1.4756.108.40.1.3.1.1
        iUserIndex OBJECT-TYPE
            SYNTAX      Integer32 (1..20)
            MAX-ACCESS  read-only
            STATUS      current
            DESCRIPTION
                "The index of user entries."
            ::= { iUserConfigEntry 1 }

        -- 1.3.6.1.4.1.4756.108.40.1.3.1.2
        iUserName OBJECT-TYPE
            SYNTAX      OCTET STRING (SIZE (1..32))
            MAX-ACCESS  read-only
            STATUS      current
            DESCRIPTION
                "The name identifying the user."
            ::= { iUserConfigEntry 2 }

        -- 1.3.6.1.4.1.4756.108.40.1.3.1.3
        iUserPassword OBJECT-TYPE
            SYNTAX      OCTET STRING (SIZE (0..32))
            MAX-ACCESS  read-write
            STATUS      current
            DESCRIPTION
                "The password of the user. The allowed string length is 0 to 32."
            ::= { iUserConfigEntry 3 }

        -- 1.3.6.1.4.1.4756.108.40.1.3.1.4
        iUserPrivilegeLevel OBJECT-TYPE
            SYNTAX      Integer32 (1..15)
            MAX-ACCESS  read-write
            STATUS      current
            DESCRIPTION
                "The privilege level of the user. The allowed range is 1 to 15.
                 If the privilege level value is 15, it can access all groups,
                 i.e. that is granted the fully control of the device.
                 But others value need to refer to each group privilege level.
                 User's privilege should be same or greater than the group privilege level to have the access of that group.
                 By default setting, most groups privilege level 5 has the read-only access
                 and privilege level 10 has the read-write access. And the system maintenance
                 (software upload, factory defaults and etc.) need user privilege level 15.
                 Generally, the privilege level 15 can be used for an administrator account,
                 privilege level 10 for a standard user account and privilege level 5 for a guest account."
            ::= { iUserConfigEntry 4 }

    -- 1.3.6.1.4.1.4756.108.40.1.4
    iPrivilegeLevelTable OBJECT-TYPE
        SYNTAX      SEQUENCE OF IPrivilegeLevelEntry
        MAX-ACCESS  not-accessible
        STATUS      current
        DESCRIPTION
            "This table provides privilege levels configurations."
        ::= { iSecuritySwitch 4 }

    -- 1.3.6.1.4.1.4756.108.40.1.4.1
    iPrivilegeLevelEntry OBJECT-TYPE
        SYNTAX      IPrivilegeLevelEntry
        MAX-ACCESS  not-accessible
        STATUS      current
        DESCRIPTION
            "The entry of privilege groups."
        INDEX { iPrivilegeGroupID }
        ::= { iPrivilegeLevelTable 1 }

    IPrivilegeLevelEntry ::=
        SEQUENCE {
            iPrivilegeGroupID                  Integer32,
            iPrivilegeGroupName                DisplayString,
            iPrivilegeConfigReadOnlyLevel      Integer32,
            iPrivilegeConfigReadWriteLevel     Integer32,
            iPrivilegeStatusReadOnlyLevel      Integer32,
            iPrivilegeStatusReadWriteLevel     Integer32
        }

        -- 1.3.6.1.4.1.4756.108.40.1.4.1.1
        iPrivilegeGroupID OBJECT-TYPE
            SYNTAX      Integer32 (1..26)
            MAX-ACCESS  read-only
            STATUS      current
            DESCRIPTION
                "The ID of privilege groups."
            ::= { iPrivilegeLevelEntry 1 }

        -- 1.3.6.1.4.1.4756.108.40.1.4.1.2
        iPrivilegeGroupName OBJECT-TYPE
            SYNTAX      DisplayString
            MAX-ACCESS  read-only
            STATUS      current
            DESCRIPTION
                "The name identifying the privilege group. In most cases,
                 a privilege level group consists of a single module (e.g. LACP, RSTP or QoS),
                 but a few of them contains more than one."
            ::= { iPrivilegeLevelEntry 2 }

        -- 1.3.6.1.4.1.4756.108.40.1.4.1.3
        iPrivilegeConfigReadOnlyLevel OBJECT-TYPE
            SYNTAX      Integer32 (1..15)
            MAX-ACCESS  read-write
            STATUS      current
            DESCRIPTION
                "The authorization privilege level for configuration read-only of the group.
                 The privilege level of 'Read-only' should be less or equal 'Read/write'."
            ::= { iPrivilegeLevelEntry 3 }

        -- 1.3.6.1.4.1.4756.108.40.1.4.1.4
        iPrivilegeConfigReadWriteLevel OBJECT-TYPE
            SYNTAX      Integer32 (1..15)
            MAX-ACCESS  read-write
            STATUS      current
            DESCRIPTION
                "The authorization privilege level for configuration/execute read-write of the group.
                 The privilege level of 'Configuration/Execute Read/write'
                 should be great or equal 'Status/Statistics Read-only'"
            ::= { iPrivilegeLevelEntry 4 }

        -- 1.3.6.1.4.1.4756.108.40.1.4.1.5
        iPrivilegeStatusReadOnlyLevel OBJECT-TYPE
            SYNTAX      Integer32 (1..15)
            MAX-ACCESS  read-write
            STATUS      current
            DESCRIPTION
                "The authorization privilege level for status/statistics read-only of the group.
                 The privilege level of 'Read-only' should be less or equal 'Read/write'."
            ::= { iPrivilegeLevelEntry 5 }

        -- 1.3.6.1.4.1.4756.108.40.1.4.1.6
        iPrivilegeStatusReadWriteLevel OBJECT-TYPE
            SYNTAX      Integer32 (1..15)
            MAX-ACCESS  read-write
            STATUS      current
            DESCRIPTION
                "The authorization privilege level for status/statistics read-write
                 (e.g. for clearing of statistics) of the group."
            ::= { iPrivilegeLevelEntry 6 }

    -- 1.3.6.1.4.1.4756.108.40.1.5
    iAuthenticationMethodTable OBJECT-TYPE
        SYNTAX      SEQUENCE OF IAuthenticationMethodEntry
        MAX-ACCESS  not-accessible
        STATUS      current
        DESCRIPTION
            "This table allows you to configure how a user is authenticated when
             he logs into the switch via one of the management client interfaces."
        ::= { iSecuritySwitch 5 }

    -- 1.3.6.1.4.1.4756.108.40.1.5.1
    iAuthenticationMethodEntry OBJECT-TYPE
        SYNTAX      IAuthenticationMethodEntry
        MAX-ACCESS  not-accessible
        STATUS      current
        DESCRIPTION
            "The entry of the management client interfaces."
        INDEX { iAuthenticationClientIndex }
        ::= { iAuthenticationMethodTable 1 }

    IAuthenticationMethodEntry ::=
        SEQUENCE {
            iAuthenticationClientIndex         Integer32,
            iAuthenticationClientInterface     DisplayString,
            iAuthenticationMethod1             INTEGER,
            iAuthenticationMethod2             INTEGER,
            iAuthenticationMethod3             INTEGER
        }

        -- 1.3.6.1.4.1.4756.108.40.1.5.1.1
        iAuthenticationClientIndex OBJECT-TYPE
            SYNTAX      Integer32 (1..4)
            MAX-ACCESS  read-only
            STATUS      current
            DESCRIPTION
                "The index of the management client interfaces."
            ::= { iAuthenticationMethodEntry 1 }

        -- 1.3.6.1.4.1.4756.108.40.1.5.1.2
        iAuthenticationClientInterface OBJECT-TYPE
            SYNTAX      DisplayString
            MAX-ACCESS  read-only
            STATUS      current
            DESCRIPTION
                "The management client interface."
            ::= { iAuthenticationMethodEntry 2 }

        -- 1.3.6.1.4.1.4756.108.40.1.5.1.3
        iAuthenticationMethod1 OBJECT-TYPE
            SYNTAX      INTEGER {
                            none(1),
                            local(2),
                            radius(3),
                            tacacsPlus(4)
                        }
            MAX-ACCESS  read-write
            STATUS      current
            DESCRIPTION
                "Authentication Method can be set to one of the following values:
                 none : authentication is disabled and login is not possible.
                 local : use the local user database on the switch for authentication.
                 radius : use a remote RADIUS server for authentication.
                 tacacs+ : use a remote TACACS+ server for authentication."
            ::= { iAuthenticationMethodEntry 3 }
        
        -- 1.3.6.1.4.1.4756.108.40.1.5.1.4
        iAuthenticationMethod2 OBJECT-TYPE
            SYNTAX      INTEGER {
                            none(1),
                            local(2),
                            radius(3),
                            tacacsPlus(4)
                        }
            MAX-ACCESS  read-write
            STATUS      current
            DESCRIPTION
                "Authentication Method can be set to one of the following values:
                 none : authentication is disabled and login is not possible.
                 local : use the local user database on the switch for authentication.
                 radius : use a remote RADIUS server for authentication.
                 tacacs+ : use a remote TACACS+ server for authentication."
            ::= { iAuthenticationMethodEntry 4 }
         
         -- 1.3.6.1.4.1.4756.108.40.1.5.1.5
        iAuthenticationMethod3 OBJECT-TYPE
            SYNTAX      INTEGER {
                            none(1),
                            local(2),
                            radius(3),
                            tacacsPlus(4)
                        }
            MAX-ACCESS  read-write
            STATUS      current
            DESCRIPTION
                "Authentication Method can be set to one of the following values:
                 none : authentication is disabled and login is not possible.
                 local : use the local user database on the switch for authentication.
                 radius : use a remote RADIUS server for authentication.
                 tacacs+ : use a remote TACACS+ server for authentication."
            ::= { iAuthenticationMethodEntry 5 }

    -- 1.3.6.1.4.1.4756.108.40.1.6    
    iSshMode OBJECT-TYPE
        SYNTAX      INTEGER {
                        enabled(1),
                        disabled(2)
                    }
        MAX-ACCESS  read-write
        STATUS      current
        DESCRIPTION
            "Indicates the SSH mode operation. Possible modes are: 
             Enabled: Enable SSH mode operation. 
             Disabled: Disable SSH mode operation."
        ::= { iSecuritySwitch 6 }

    -- 1.3.6.1.4.1.4756.108.40.1.7    
    iHttpsMode OBJECT-TYPE
        SYNTAX      INTEGER {
                        enabled(1),
                        disabled(2)
                    }
        MAX-ACCESS  read-write
        STATUS      current
        DESCRIPTION
            "Indicates the HTTPS mode operation. Possible modes are: 
             Enabled: Enable HTTPS mode operation. 
             Disabled: Disable HTTPS mode operation."
        ::= { iSecuritySwitch 7 }

    -- 1.3.6.1.4.1.4756.108.40.1.8    
    iHttpsAutomaticRedirect OBJECT-TYPE
        SYNTAX      INTEGER {
                        enabled(1),
                        disabled(2)
                    }
        MAX-ACCESS  read-write
        STATUS      current
        DESCRIPTION
            "Indicates the HTTPS redirect mode operation.
             Automatically redirect web browser to HTTPS when HTTPS mode is enabled. Possible modes are: 
             Enabled: Enable HTTPS redirect mode operation. 
             Disabled: Disable HTTPS redirect mode operation."
        ::= { iSecuritySwitch 8 }

    -- 1.3.6.1.4.1.4756.108.40.1.9
    iAccessManagement OBJECT IDENTIFIER ::= { iSecuritySwitch 9 }

    -- 1.3.6.1.4.1.4756.108.40.1.9.1    
    iAccessMgmtProtocolMode OBJECT-TYPE
        SYNTAX      INTEGER {
                        enabled(1),
                        disabled(2)
                    }
        MAX-ACCESS  read-write
        STATUS      current
        DESCRIPTION
            "Indicates the access management protocol mode operation. Possible modes are: 
             Enabled: Enable access management protocol mode operation,
                      and there must at least one entry provide SNMP service. 
             Disabled: Disable access management protocol mode operation."
        ::= { iAccessManagement 1 }

    -- 1.3.6.1.4.1.4756.108.40.1.9.2    
    iAddAccessMgmtProtocol OBJECT-TYPE
        SYNTAX      DisplayString
        MAX-ACCESS  read-write
        STATUS      current
        DESCRIPTION
            "Add a new access management entry: 
             Value 1~4094: Insert new entry by this VLAN ID."
        ::= { iAccessManagement 2 }

    -- 1.3.6.1.4.1.4756.108.40.1.9.3    
    iDeleteAccessMgmtProtocol OBJECT-TYPE
        SYNTAX      DisplayString
        MAX-ACCESS  read-write
        STATUS      current
        DESCRIPTION
            "Delete entry by given VLAN ID."
        ::= { iAccessManagement 3 }

    -- 1.3.6.1.4.1.4756.108.40.1.9.4
    iAccessMgmtProtocolTable OBJECT-TYPE
        SYNTAX      SEQUENCE OF IAccessMgmtProtocolEntry
        MAX-ACCESS  not-accessible
        STATUS      current
        DESCRIPTION
            "Configure access management protocol on this table."
        ::= { iAccessManagement 4 }

    -- 1.3.6.1.4.1.4756.108.40.1.9.4.1
    iAccessMgmtProtocolEntry OBJECT-TYPE
        SYNTAX      IAccessMgmtProtocolEntry
        MAX-ACCESS  not-accessible
        STATUS      current
        DESCRIPTION
            "The entry of the access management protocol table."
        INDEX { iAccessMgmtIndex }
        ::= { iAccessMgmtProtocolTable 1 }

    IAccessMgmtProtocolEntry ::=
        SEQUENCE {
        	iAccessMgmtIndex               Integer32,
            iAccessMgmtVID                 Integer32,
            iAccessMgmtProtocolStartIP     DisplayString,
            iAccessMgmtProtocolEndIP       DisplayString,
            iAccessMgmtHttpHttpsEnable     TruthValue,
            iAccessMgmtSnmpEnable          TruthValue,
            iAccessMgmtTelnetSshEnable     TruthValue
        }
        
        -- 1.3.6.1.4.1.4756.108.40.1.9.4.1.1
        iAccessMgmtIndex OBJECT-TYPE
            SYNTAX      Integer32 (1..16)
            MAX-ACCESS  read-only
            STATUS      current
            DESCRIPTION
                "The index of the access management entry."
            ::= { iAccessMgmtProtocolEntry 1 }
        
        -- 1.3.6.1.4.1.4756.108.40.1.9.4.1.2
        iAccessMgmtVID OBJECT-TYPE
            SYNTAX      Integer32 (1..4094)
            MAX-ACCESS  read-write
            STATUS      current
            DESCRIPTION
                "The VLAN ID of the access management entry."
            ::= { iAccessMgmtProtocolEntry 2 }

        -- 1.3.6.1.4.1.4756.108.40.1.9.4.1.3
        iAccessMgmtProtocolStartIP OBJECT-TYPE
            SYNTAX      DisplayString
            MAX-ACCESS  read-write
            STATUS      current
            DESCRIPTION
                "Indicates the start IP address for the access management entry.
                 It must either be a valid IPv4 or IPv6 address.
                 IPv4 address is in dotted decimal notation ('x.y.z.w').
                 IPv6 address is in 128-bit records represented as eight fields of up to
                 four hexadecimal digits with a colon separating each field (:)."
            ::= { iAccessMgmtProtocolEntry 3 }

        -- 1.3.6.1.4.1.4756.108.40.1.9.4.1.4
        iAccessMgmtProtocolEndIP OBJECT-TYPE
            SYNTAX      DisplayString
            MAX-ACCESS  read-write
            STATUS      current
            DESCRIPTION
                "Indicates the end IP address for the access management entry..
                 It must either be a valid IPv4 or IPv6 address.
                 IPv4 address is in dotted decimal notation ('x.y.z.w').
                 IPv6 address is in 128-bit records represented as eight fields of up to
                 four hexadecimal digits with a colon separating each field (:)."
            ::= { iAccessMgmtProtocolEntry 4 }

        -- 1.3.6.1.4.1.4756.108.40.1.9.4.1.5
        iAccessMgmtHttpHttpsEnable OBJECT-TYPE
            SYNTAX      TruthValue
            MAX-ACCESS  read-write
            STATUS      current
            DESCRIPTION
                "Indicates that the host can access the switch from HTTP/HTTPS interface if
                 the host IP address matches the IP address range provided in the entry."
            ::= { iAccessMgmtProtocolEntry 5 }

        -- 1.3.6.1.4.1.4756.108.40.1.9.4.1.6
        iAccessMgmtSnmpEnable OBJECT-TYPE
            SYNTAX      TruthValue
            MAX-ACCESS  read-write
            STATUS      current
            DESCRIPTION
                "Indicates that the host can access the switch from SNMP interface if
                 the host IP address matches the IP address range provided in the entry."
            ::= { iAccessMgmtProtocolEntry 6 }

        -- 1.3.6.1.4.1.4756.108.40.1.9.4.1.7
        iAccessMgmtTelnetSshEnable OBJECT-TYPE
            SYNTAX      TruthValue
            MAX-ACCESS  read-write
            STATUS      current
            DESCRIPTION
                "Indicates that the host can access the switch from TELNET/SSH interface if
                 the host IP address matches the IP address range provided in the entry."
            ::= { iAccessMgmtProtocolEntry 7 }

    -- 1.3.6.1.4.1.4756.108.40.1.9.5
    iAccessMgmtStatisticsClear OBJECT-TYPE
        SYNTAX      INTEGER {
                        trigger(1),
                        normal(2)
                    }
        MAX-ACCESS  read-write
        STATUS      current
        DESCRIPTION
            "Clear all Access Management statistics"
        ::= { iAccessManagement 5 }

    -- 1.3.6.1.4.1.4756.108.40.1.9.6
    iAccessMgmtStatisticsTable OBJECT-TYPE
        SYNTAX      SEQUENCE OF IAccessMgmtStatisticsEntry
        MAX-ACCESS  not-accessible
        STATUS      current
        DESCRIPTION
            "Configure access management protocol on this table."
        ::= { iAccessManagement 6 }

    -- 1.3.6.1.4.1.4756.108.40.1.9.6.1
    iAccessMgmtStatisticsEntry OBJECT-TYPE
        SYNTAX      IAccessMgmtStatisticsEntry
        MAX-ACCESS  not-accessible
        STATUS      current
        DESCRIPTION
            "The entry of the access management protocol table."
        INDEX { iAccessMgmtInterfaceIndex }
        ::= { iAccessMgmtStatisticsTable 1 }

    IAccessMgmtStatisticsEntry ::=
        SEQUENCE {
            iAccessMgmtInterfaceIndex      Integer32,
            iAccessMgmtInterface           DisplayString,
            iAccessMgmtReceivedPackets     Counter32,
            iAccessMgmtAllowedPackets      Counter32,
            iAccessMgmtDiscardedPackets    Counter32
        }

        -- 1.3.6.1.4.1.4756.108.40.1.9.6.1.1
        iAccessMgmtInterfaceIndex OBJECT-TYPE
            SYNTAX      Integer32 (1..5)
            MAX-ACCESS  read-only
            STATUS      current
            DESCRIPTION
                "The Id of the access management entry."
            ::= { iAccessMgmtStatisticsEntry 1 }

        -- 1.3.6.1.4.1.4756.108.40.1.9.6.1.2
        iAccessMgmtInterface OBJECT-TYPE
            SYNTAX      DisplayString
            MAX-ACCESS  read-only
            STATUS      current
            DESCRIPTION
                "The Id of the access management entry."
            ::= { iAccessMgmtStatisticsEntry 2 }

        -- 1.3.6.1.4.1.4756.108.40.1.9.6.1.3
        iAccessMgmtReceivedPackets OBJECT-TYPE
            SYNTAX      Counter32
            MAX-ACCESS  read-only
            STATUS      current
            DESCRIPTION
                "The Id of the access management entry."
            ::= { iAccessMgmtStatisticsEntry 3 }

        -- 1.3.6.1.4.1.4756.108.40.1.9.6.1.4
        iAccessMgmtAllowedPackets OBJECT-TYPE
            SYNTAX      Counter32
            MAX-ACCESS  read-only
            STATUS      current
            DESCRIPTION
                "The Id of the access management entry."
            ::= { iAccessMgmtStatisticsEntry 4 }

        -- 1.3.6.1.4.1.4756.108.40.1.9.6.1.5
        iAccessMgmtDiscardedPackets OBJECT-TYPE
            SYNTAX      Counter32
            MAX-ACCESS  read-only
            STATUS      current
            DESCRIPTION
                "The Id of the access management entry."
            ::= { iAccessMgmtStatisticsEntry 5 }

    
    -- 1.3.6.1.4.1.4756.108.40.2
    iSecurityNetwork OBJECT IDENTIFIER ::= { iSecurity 2 }
    
    -- 1.3.6.1.4.1.4756.108.40.2.1
    iPortSecurity OBJECT IDENTIFIER ::= { iSecurityNetwork 1 }

    -- 1.3.6.1.4.1.4756.108.40.2.1.1    
    iPsecLimitControlMode OBJECT-TYPE
        SYNTAX      INTEGER {
                        enabled(1),
                        disabled(2)
                    }
        MAX-ACCESS  read-write
        STATUS      current
        DESCRIPTION
            "Indicates if Limit Control is globally enabled or disabled on the switch."
        ::= { iPortSecurity 1 }

    -- 1.3.6.1.4.1.4756.108.40.2.1.2    
    iPsecLimitControlAgingEnabled OBJECT-TYPE
        SYNTAX      TruthValue
        MAX-ACCESS  read-write
        STATUS      current
        DESCRIPTION
            "If enabled, secured MAC addresses are subject to aging as discussed under Aging Period."
        ::= { iPortSecurity 2 }

    -- 1.3.6.1.4.1.4756.108.40.2.1.3    
    iPsecLimitControlAgingPeriod OBJECT-TYPE
        SYNTAX      Integer32 (10..10000000)
        UNITS       "Seconds"
        MAX-ACCESS  read-write
        STATUS      current
        DESCRIPTION
            "If 'Aging' is Enabled, then the aging period is controlled with this value."
        ::= { iPortSecurity 3 }

    -- 1.3.6.1.4.1.4756.108.40.2.1.4
    iPsecLimitControlPortConfigTable OBJECT-TYPE
        SYNTAX      SEQUENCE OF IPsecLimitControlPortConfigEntry
        MAX-ACCESS  not-accessible
        STATUS      current
        DESCRIPTION
            "This table provides Port Security Limit Control Configurations."
        ::= { iPortSecurity 4 }

    -- 1.3.6.1.4.1.4756.108.40.2.1.4.1
    iPsecLimitControlPortConfigEntry OBJECT-TYPE
        SYNTAX      IPsecLimitControlPortConfigEntry
        MAX-ACCESS  not-accessible
        STATUS      current
        DESCRIPTION
            "The Entry of Port Security Limit Control Configurations."
        INDEX { iPortIndex }
        ::= { iPsecLimitControlPortConfigTable 1 }

    IPsecLimitControlPortConfigEntry ::=
        SEQUENCE {
            iPsecLimitControlPortMode      INTEGER,
            iPsecLimitControlMacLimit      Integer32,
            iPsecLimitControlAction        INTEGER,
            iPsecLimitControlPortReopen    INTEGER
        }

        -- 1.3.6.1.4.1.4756.108.40.2.1.4.1.1
        iPsecLimitControlPortMode OBJECT-TYPE
            SYNTAX      INTEGER {
                            enable(1),
                            disable(2)
                        }
            MAX-ACCESS  read-write
            STATUS      current
            DESCRIPTION
                "Controls whether Limit Control is enabled on this port.
                 Both this and the Global Mode must be set to Enabled for Limit Control to be in effect.
                 Notice that other modules may still use the underlying port security features
                 without enabling Limit Control on a given port."
            ::= { iPsecLimitControlPortConfigEntry 1 }

        -- 1.3.6.1.4.1.4756.108.40.2.1.4.1.2
        iPsecLimitControlMacLimit OBJECT-TYPE
            SYNTAX      Integer32 (1..1024)
            MAX-ACCESS  read-write
            STATUS      current
            DESCRIPTION
                "The maximum number of MAC addresses that can be secured on this port.
                 This number cannot exceed 1024.
                 If the limit is exceeded, the corresponding action is taken.
                 The switch is 'born' with a total number of MAC addresses from which all ports draw
                 whenever a new MAC address is seen on a Port Security-enabled port.
                 Since all ports draw from the same pool,
                 it may happen that a configured maximum cannot be granted,
                 if the remaining ports have already used all available MAC addresses."
            ::= { iPsecLimitControlPortConfigEntry 2 }

        -- 1.3.6.1.4.1.4756.108.40.2.1.4.1.3
        iPsecLimitControlAction OBJECT-TYPE
            SYNTAX      INTEGER {
                            none(1),
                            trap(2),
                            shutdown(3),
                            trapAndShutdown(4)
                        }
            MAX-ACCESS  read-write
            STATUS      current
            DESCRIPTION
                "If Limit is reached, the switch can take one of the following actions:
                 None: Do not allow more than Limit MAC addresses on the port,
                       but take no further action.
                 Trap: If Limit + 1 MAC addresses is seen on the port,
                       send an SNMP trap. If Aging is disabled,
                       only one SNMP trap will be sent, but with Aging enabled,
                       new SNMP traps will be sent everytime the limit gets exceeded.
                 Shutdown: If Limit + 1 MAC addresses is seen on the port, shut down the port.
                           This implies that all secured MAC addresses will be removed from the port,
                           and no new address will be learned.
                           Even if the link is physically disconnected and reconnected on the port
                           (by disconnecting the cable), the port will remain shut down.
                           There are three ways to re-open the port:
                           1) Boot the switch,
                           2) Disable and re-enable Limit Control on the port or the switch,
                           3) Trigger Reopen node.
                 Trap & Shutdown: If Limit + 1 MAC addresses is seen on the port, both the 'Trap' and
                                  the 'Shutdown' actions described above will be taken."
            ::= { iPsecLimitControlPortConfigEntry 3 }

        -- 1.3.6.1.4.1.4756.108.40.2.1.4.1.4
        iPsecLimitControlPortReopen OBJECT-TYPE
            SYNTAX      INTEGER {
                            trigger(1),
                            normal(2)
                        }
            MAX-ACCESS  read-write
            STATUS      current
            DESCRIPTION
                "If a port is shutdown by this module, you may reopen it by triggering this node."
            ::= { iPsecLimitControlPortConfigEntry 4 }

    -- 1.3.6.1.4.1.4756.108.40.2.1.5
    iPsecSwitchStatusTable OBJECT-TYPE
        SYNTAX      SEQUENCE OF IPsecSwitchStatusEntry
        MAX-ACCESS  not-accessible
        STATUS      current
        DESCRIPTION
            "This table provides Port Security Limit Control Switch Status."
        ::= { iPortSecurity 5 }

    -- 1.3.6.1.4.1.4756.108.40.2.1.5.1
    iPsecSwitchStatusEntry OBJECT-TYPE
        SYNTAX      IPsecSwitchStatusEntry
        MAX-ACCESS  not-accessible
        STATUS      current
        DESCRIPTION
            "The Entry of Port Security Limit Control Switch Status."
        INDEX { iPortIndex }
        ::= { iPsecSwitchStatusTable 1 }

    IPsecSwitchStatusEntry ::=
        SEQUENCE {
            iPsecSwitchStatusPortUsers     DisplayString,
            iPsecSwitchStatusPortState     INTEGER,
            iPsecSwitchStatusMacCount      Integer32
        }

        -- 1.3.6.1.4.1.4756.108.40.2.1.5.1.1
        iPsecSwitchStatusPortUsers OBJECT-TYPE
            SYNTAX      DisplayString
            MAX-ACCESS  read-only
            STATUS      current
            DESCRIPTION
                "Each of the user modules has a column that shows whether that module has enabled
                 Port Security or not. A '-' means that the corresponding user module is not enabled,
                 whereas a letter indicates that the user module abbreviated by that letter (see below)
                 has enabled port security.
                 Limit Control: L
                 802.1X       : 8
                 DHCP Snooping: D
                 Voice VLAN   : V "
            ::= { iPsecSwitchStatusEntry 1 }

        -- 1.3.6.1.4.1.4756.108.40.2.1.5.1.2
        iPsecSwitchStatusPortState OBJECT-TYPE
            SYNTAX      INTEGER {
                            disabled(1),
                            ready(2),
                            limitReached(3),
                            shutdown(4)
                        }
            MAX-ACCESS  read-only
            STATUS      current
            DESCRIPTION
                "This node shows the current state of the port.
                 The state takes one of four values:
                 Disabled: Limit Control is either globally disabled or disabled on the port.
                 Ready: The limit is not yet reached. This can be shown for all actions.
                 Limit Reached: Indicates that the limit is reached on this port.
                                This state can only be shown if Action is set to None or Trap.
                 Shutdown: Indicates that the port is shut down by the Limit Control module.
                           This state can only be shown if Action is set to Shutdown or Trap & Shutdown."
            ::= { iPsecSwitchStatusEntry 2 }

        -- 1.3.6.1.4.1.4756.108.40.2.1.5.1.3
        iPsecSwitchStatusMacCount OBJECT-TYPE
            SYNTAX      Integer32 (-1 | 0..1024) 
            MAX-ACCESS  read-only
            STATUS      current
            DESCRIPTION
                "This indicate the number of currently learned MAC addresses(forwarding as well as blocked)
                 If no user modules are enabled on the port, the Current Count will show a value(-1)."
            ::= { iPsecSwitchStatusEntry 3 }

    -- 1.3.6.1.4.1.4756.108.40.2.1.6
    iPsecPortStatusTable OBJECT-TYPE
        SYNTAX      SEQUENCE OF IPsecPortStatusEntry
        MAX-ACCESS  not-accessible
        STATUS      current
        DESCRIPTION
            "This table provides Port Security Port Status."
        ::= { iPortSecurity 6 }

    -- 1.3.6.1.4.1.4756.108.40.2.1.6.1
    iPsecPortStatusEntry OBJECT-TYPE
        SYNTAX      IPsecPortStatusEntry
        MAX-ACCESS  not-accessible
        STATUS      current
        DESCRIPTION
            "The Entry of Port Security Port Status."
        INDEX { iPortIndex, iPsecMacIndex }
        ::= { iPsecPortStatusTable 1 }

    IPsecPortStatusEntry ::=
        SEQUENCE {
            iPsecMacIndex          Integer32,
            iPsecMacAddress        MacAddress,
            iPsecMacVlanID         Integer32,
            iPsecMacState          INTEGER,
            iPsecMacAdditionTime   DisplayString,
            iPsecMacAge            Integer32
        }

        -- 1.3.6.1.4.1.4756.108.40.2.1.6.1.1
        iPsecMacIndex OBJECT-TYPE
            SYNTAX      Integer32 (1..1024) 
            MAX-ACCESS  read-only
            STATUS      current
            DESCRIPTION
                "The mac address index of the port."
            ::= { iPsecPortStatusEntry 1 }

        -- 1.3.6.1.4.1.4756.108.40.2.1.6.1.2
        iPsecMacAddress OBJECT-TYPE
            SYNTAX      MacAddress 
            MAX-ACCESS  read-only
            STATUS      current
            DESCRIPTION
                "The MAC address that is seen on this port."
            ::= { iPsecPortStatusEntry 2 }

        -- 1.3.6.1.4.1.4756.108.40.2.1.6.1.3
        iPsecMacVlanID OBJECT-TYPE
            SYNTAX      Integer32 (1..4095) 
            MAX-ACCESS  read-only
            STATUS      current
            DESCRIPTION
                "The VLAN ID that is seen on this port."
            ::= { iPsecPortStatusEntry 3 }

        -- 1.3.6.1.4.1.4756.108.40.2.1.6.1.4
        iPsecMacState OBJECT-TYPE
            SYNTAX      INTEGER {
                            blocked(1),
                            forwarding(2)
                        }     
            MAX-ACCESS  read-only
            STATUS      current
            DESCRIPTION
                "Indicates whether the corresponding MAC address is blocked or forwarding.
                 In the blocked state, it will not be allowed to transmit or receive traffic."
            ::= { iPsecPortStatusEntry 4 }

        -- 1.3.6.1.4.1.4756.108.40.2.1.6.1.5
        iPsecMacAdditionTime OBJECT-TYPE
            SYNTAX      DisplayString     
            MAX-ACCESS  read-only
            STATUS      current
            DESCRIPTION
                "Shows the date and time when this MAC address was first seen on the port."
            ::= { iPsecPortStatusEntry 5 }

        -- 1.3.6.1.4.1.4756.108.40.2.1.6.1.6
        iPsecMacAge OBJECT-TYPE
            SYNTAX      Integer32 (-1 | 0..1000000)     
            MAX-ACCESS  read-only
            STATUS      current
            DESCRIPTION
                "If at least one user module has decided to block this MAC address,
                 it will stay in the blocked state until the hold time(measured in seconds) expires.
                 If all user modules have decided to allow this MAC address to forward, and aging is enabled,
                 the Port Security module will periodically check that this MAC address still forwards traffic.
                 If the age period (measured in seconds) expires and no frames have been seen,
                 the MAC address will be removed from the MAC table. Otherwise a new age period will begin.
                 If aging is disabled or a user module has decided to hold the MAC address indefinitely,
                 a value (-1) will be shown."
            ::= { iPsecPortStatusEntry 6 }
        
                
    -- 1.3.6.1.4.1.4756.108.40.2.2
    iNAS OBJECT IDENTIFIER ::= { iSecurityNetwork 2 }

    -- 1.3.6.1.4.1.4756.108.40.2.2.1    
    iNasMode OBJECT-TYPE
        SYNTAX      INTEGER {
                        enabled(1),
                        disabled(2)
                    }
        MAX-ACCESS  read-write
        STATUS      current
        DESCRIPTION
            "Indicates if NAS is globally enabled or disabled on the switch.
             If globally disabled, all ports are allowed forwarding of frames."
        ::= { iNAS 1 }

    -- 1.3.6.1.4.1.4756.108.40.2.2.2    
    iNasReauthenticationEnabled OBJECT-TYPE
        SYNTAX      TruthValue
        MAX-ACCESS  read-write
        STATUS      current
        DESCRIPTION
            "If enabled, successfully authenticated supplicants/clients are reauthenticated
             after the interval specified by the Reauthentication Period.
             Reauthentication for 802.1X-enabled ports can be used to detect if a new device
             is plugged into a switch port or if a supplicant is no longer attached. 
             For MAC-based ports, reauthentication is only useful if the RADIUS server configuration has changed.
             It does not involve communication between the switch and the client,
             and therefore doesn't imply that a client is still present on a port."
        ::= { iNAS 2 }

    -- 1.3.6.1.4.1.4756.108.40.2.2.3    
    iNasReauthenticationPeriod OBJECT-TYPE
        SYNTAX      Integer32 (1..3600)
        UNITS       "Seconds"
        MAX-ACCESS  read-write
        STATUS      current
        DESCRIPTION
            "Determines the period, in seconds,
             after which a connected client must be reauthenticated.
             This is only active if the Reauthentication is Enabled.
             Valid values are in the range 1 to 3600 seconds."
        ::= { iNAS 3 }

    -- 1.3.6.1.4.1.4756.108.40.2.2.4    
    iNasEapolTimeout OBJECT-TYPE
        SYNTAX      Integer32 (1..65535)
        UNITS       "Seconds"
        MAX-ACCESS  read-write
        STATUS      current
        DESCRIPTION
            "Determines the time for retransmission of Request Identity EAPOL frames.
             Valid values are in the range 1 to 65535 seconds.
             This has no effect for MAC-based ports."
        ::= { iNAS 4 }

    -- 1.3.6.1.4.1.4756.108.40.2.2.5    
    iNasAgingPeriod OBJECT-TYPE
        SYNTAX      Integer32 (10..1000000)
        UNITS       "Seconds"
        MAX-ACCESS  read-write
        STATUS      current
        DESCRIPTION
            "This setting applies to the following modes,
             i.e. modes using the Port Security functionality to secure MAC addresses:
             Single 802.1X, Multi 802.1X or MAC-Based Auth.
             When the NAS module uses the Port Security module to secure MAC addresses,
             the Port Security module needs to check for activity on the MAC address in question at
             regular intervals and free resources if no activity is seen within a given period of time.
             This parameter controls exactly this period and can be set to a number between 10 and 1000000 seconds.
             If reauthentication is enabled and the port is in an 802.1X-based mode,
             this is not so critical, since supplicants that are no longer attached to
             the port will get removed upon the next reauthentication, which will fail.
             But if reauthentication is not enabled, the only way to free resources is by aging the entries.
             For ports in MAC-based Auth. mode, reauthentication doesn't cause direct communication between
             the switch and the client, so this will not detect whether the client is still attached or not,
             and the only way to free any resources is to age the entry."
        ::= { iNAS 5 }

    -- 1.3.6.1.4.1.4756.108.40.2.2.6    
    iNasHoldTime OBJECT-TYPE
        SYNTAX      Integer32 (10..1000000)
        UNITS       "Seconds"
        MAX-ACCESS  read-write
        STATUS      current
        DESCRIPTION
            "This setting applies to the following modes,
             i.e. modes using the Port Security functionality to secure MAC addresses:
             Single 802.1X, Multi 802.1X or MAC-Based Auth.
             If a client is denied access - either because the RADIUS server denies the client access or
             because the RADIUS server request times out, the client is put on hold in the Unauthorized state.
             The hold timer does not count during an on-going authentication.
             In MAC-based Auth. mode, the switch will ignore new frames coming from the client during the hold time.
             The Hold Time can be set to a number between 10 and 1000000 seconds."
        ::= { iNAS 6 }

    -- 1.3.6.1.4.1.4756.108.40.2.2.7    
    iNasRadiusAssignedQosEnabled OBJECT-TYPE
        SYNTAX      TruthValue
        MAX-ACCESS  read-write
        STATUS      current
        DESCRIPTION
            "RADIUS-assigned QoS provides a means to centrally control the traffic class to which traffic
             coming from a successfully authenticated supplicant is assigned on the switch.
             The RADIUS server must be configured to transmit special RADIUS attributes to
             take advantage of this feature."
        ::= { iNAS 7 }

    -- 1.3.6.1.4.1.4756.108.40.2.2.8    
    iNasRadiusAssignedVlanEnabled OBJECT-TYPE
        SYNTAX      TruthValue
        MAX-ACCESS  read-write
        STATUS      current
        DESCRIPTION
            "RADIUS-assigned VLAN provides a means to centrally control the VLAN on which a
             successfully authenticated supplicant is placed on the switch.
             Incoming traffic will be classified to and switched on the RADIUS-assigned VLAN.
             The RADIUS server must be configured to transmit special RADIUS attributes to
             take advantage of this feature."
        ::= { iNAS 8 }

    -- 1.3.6.1.4.1.4756.108.40.2.2.9    
    iNasGuestVlanEnabled OBJECT-TYPE
        SYNTAX      TruthValue
        MAX-ACCESS  read-write
        STATUS      current
        DESCRIPTION
            "A Guest VLAN is a special VLAN - typically with limited network access - on which
             802.1X-unaware clients are placed after a network administrator-defined timeout.
             The switch follows a set of rules for entering and leaving the Guest VLAN."
        ::= { iNAS 9 }

    -- 1.3.6.1.4.1.4756.108.40.2.2.10    
    iNasGuestVlanID OBJECT-TYPE
        SYNTAX      Integer32 (1..4095)
        MAX-ACCESS  read-write
        STATUS      current
        DESCRIPTION
            "This is the value that a port's Port VLAN ID is set to if a port is moved into the Guest VLAN.
             It is only changeable if the Guest VLAN option is globally enabled.
             Valid values are in the range 1 to 4095."
        ::= { iNAS 10 }

    -- 1.3.6.1.4.1.4756.108.40.2.2.11    
    iNasMaxReauthenticationCount OBJECT-TYPE
        SYNTAX      Integer32 (1..255)
        MAX-ACCESS  read-write
        STATUS      current
        DESCRIPTION
            "The number of times the switch transmits an EAPOL Request Identity frame without response
             before considering entering the Guest VLAN is adjusted with this setting.
             The value can only be changed if the Guest VLAN option is globally enabled.
             Valid values are in the range 1 to 255."
        ::= { iNAS 11 }

    -- 1.3.6.1.4.1.4756.108.40.2.2.12    
    iNasAllowGuestVlanIfEapolSeen OBJECT-TYPE
        SYNTAX      TruthValue
        MAX-ACCESS  read-write
        STATUS      current
        DESCRIPTION
            "The switch remembers if an EAPOL frame has been received on the port for the life-time
             of the port. Once the switch considers whether to enter the Guest VLAN,
             it will first check if this option is enabled or disabled.
             If disabled, the switch will only enter the Guest VLAN if an EAPOL frame has not been
             received on the port for the life-time of the port.
             If enabled, the switch will consider entering the Guest VLAN even if an EAPOL frame has
             been received on the port for the life-time of the port."
        ::= { iNAS 12 }

    -- 1.3.6.1.4.1.4756.108.40.2.2.13
    iNasPortConfigTable OBJECT-TYPE
        SYNTAX      SEQUENCE OF INasPortConfigEntry
        MAX-ACCESS  not-accessible
        STATUS      current
        DESCRIPTION
            "This table provides Network Access Server Port Configurations."
        ::= { iNAS 13 }

    -- 1.3.6.1.4.1.4756.108.40.2.2.13.1
    iNasPortConfigEntry OBJECT-TYPE
        SYNTAX      INasPortConfigEntry
        MAX-ACCESS  not-accessible
        STATUS      current
        DESCRIPTION
            "The Entry of Network Access Server Port Configurations."
        INDEX { iPortIndex }
        ::= { iNasPortConfigTable 1 }

    INasPortConfigEntry ::=
        SEQUENCE {
            iNasPortAdminState                 INTEGER,
            iNasPortRadiusAssignedQosEnabled   TruthValue,
            iNasPortRadiusAssignedVlanEnabled  TruthValue,
            iNasPortGuestVlanEnabled           TruthValue,
            iNasPortReauthenticateRestart      INTEGER,
            iNasPortReinitializeRestart        INTEGER
        }

        -- 1.3.6.1.4.1.4756.108.40.2.2.13.1.1
        iNasPortAdminState OBJECT-TYPE
            SYNTAX      INTEGER {
                            forceAuthorized(1),
                            forceUnauthorized(2),
                            portBased802dot1X(3),
                            single802dot1X(4),
                            multi802dot1X(5),
                            macBasedAuthentication(6)
                        }
            MAX-ACCESS  read-write
            STATUS      current
            DESCRIPTION
                "If NAS is globally enabled, this node controls the port's authentication mode."
            ::= { iNasPortConfigEntry 1 }

        -- 1.3.6.1.4.1.4756.108.40.2.2.13.1.2
        iNasPortRadiusAssignedQosEnabled OBJECT-TYPE
            SYNTAX      TruthValue
            MAX-ACCESS  read-write
            STATUS      current
            DESCRIPTION
                "When RADIUS-Assigned QoS is both globally enabled and enabled on a given port,
                 the switch reacts to QoS Class information carried in the RADIUS Access-Accept
                 packet transmitted by the RADIUS server when a supplicant is successfully authenticated.
                 If present and valid, traffic received on the supplicant's port will be classified to
                 the given QoS Class. If (re-)authentication fails or the RADIUS Access-Accept packet
                 no longer carries a QoS Class or it's invalid, or the supplicant is otherwise no longer
                 present on the port, the port's QoS Class is immediately reverted to the original QoS Class
                 (which may be changed by the administrator in the meanwhile without affecting the RADIUS-assigned).
                 This option is only available for single-client modes, i.e. Port-based 802.1X or Single 802.1X."
            ::= { iNasPortConfigEntry 2 }

        -- 1.3.6.1.4.1.4756.108.40.2.2.13.1.3
        iNasPortRadiusAssignedVlanEnabled OBJECT-TYPE
            SYNTAX      TruthValue
            MAX-ACCESS  read-write
            STATUS      current
            DESCRIPTION
                "When RADIUS-Assigned VLAN is both globally enabled and enabled for a given port,
                 the switch reacts to VLAN ID information carried in the RADIUS Access-Accept
                 packet transmitted by the RADIUS server when a supplicant is successfully authenticated.
                 If present and valid, the port's Port VLAN ID will be changed to this VLAN ID,
                 the port will be set to be a member of that VLAN ID, and the port will be forced into
                 VLAN unaware mode. Once assigned, all traffic arriving on the port will be classified and
                 switched on the RADIUS-assigned VLAN ID. If (re-)authentication fails or the RADIUS Access-Accept
                 packet no longer carries a VLAN ID or it's invalid, or the supplicant is otherwise no longer
                 present on the port, the port's VLAN ID is immediately reverted to the original VLAN ID
                 (which may be changed by the administrator in the meanwhile without affecting the RADIUS-assigned).
                 This option is only available for single-client modes, i.e. Port-based 802.1X or Single 802.1X."
            ::= { iNasPortConfigEntry 3 }

        -- 1.3.6.1.4.1.4756.108.40.2.2.13.1.4
        iNasPortGuestVlanEnabled OBJECT-TYPE
            SYNTAX      TruthValue
            MAX-ACCESS  read-write
            STATUS      current
            DESCRIPTION
                "When Guest VLAN is both globally enabled and enabled for a given port,
                 the switch considers moving the port into the Guest VLAN according to the rules outlined below.
                 This option is only available for EAPOL-based modes, i.e.:
                 Port-based 802.1X, Single 802.1X or Multi 802.1X."
            ::= { iNasPortConfigEntry 4 }

        -- 1.3.6.1.4.1.4756.108.40.2.2.13.1.5
        iNasPortReauthenticateRestart OBJECT-TYPE
            SYNTAX      INTEGER {
                            trigger(1),
                            normal(2)
                        }
            MAX-ACCESS  read-write
            STATUS      current
            DESCRIPTION
                "Schedules a reauthentication whenever the quiet-period of the port runs out
                 (EAPOL-based authentication). For MAC-based authentication,
                 reauthentication will be attempted immediately.
                 The node is only has effect when authentication is globally enabled and
                 the port's Admin State is in an EAPOL-based or MAC-based mode."
            ::= { iNasPortConfigEntry 5 }

        -- 1.3.6.1.4.1.4756.108.40.2.2.13.1.6
        iNasPortReinitializeRestart OBJECT-TYPE
            SYNTAX      INTEGER {
                            trigger(1),
                            normal(2)
                        }
            MAX-ACCESS  read-write
            STATUS      current
            DESCRIPTION
                "Forces a reinitialization of the clients on the port and thereby a reauthentication immediately.
                 The clients will transfer to the unauthorized state while the reauthentication is in progress.
                 The node is only has effect when authentication is globally enabled and
                 the port's Admin State is in an EAPOL-based or MAC-based mode."
            ::= { iNasPortConfigEntry 6 }

    -- 1.3.6.1.4.1.4756.108.40.2.2.14
    iNasSwitchStatusTable OBJECT-TYPE
        SYNTAX      SEQUENCE OF INasSwitchStatusEntry
        MAX-ACCESS  not-accessible
        STATUS      current
        DESCRIPTION
            "This page provides an overview of the current NAS port states."
        ::= { iNAS 14 }

    -- 1.3.6.1.4.1.4756.108.40.2.2.14.1
    iNasSwitchStatusEntry OBJECT-TYPE
        SYNTAX      INasSwitchStatusEntry
        MAX-ACCESS  not-accessible
        STATUS      current
        DESCRIPTION
            "The Entry of Network Access Server Switch Status."
        INDEX { iPortIndex }
        ::= { iNasSwitchStatusTable 1 }

    INasSwitchStatusEntry ::=
        SEQUENCE {
            iNasSwitchPortAdminState   INTEGER,
            iNasSwitchPortState        DisplayString,
            iNasSwitchPortLastSource   DisplayString,
            iNasSwitchPortLastID       DisplayString,
            iNasSwitchPortQosClass     DisplayString,
            iNasSwitchPortVlanID       DisplayString
        }

        -- 1.3.6.1.4.1.4756.108.40.2.2.14.1.1
        iNasSwitchPortAdminState OBJECT-TYPE
            SYNTAX      INTEGER {
                            forceAuthorized(1),
                            forceUnauthorized(2),
                            portBased802dot1X(3),
                            single802dot1X(4),
                            multi802dot1X(5),
                            macBasedAuthentication(6)
                        }
            MAX-ACCESS  read-only
            STATUS      current
            DESCRIPTION
                "The port's current administrative state."
            ::= { iNasSwitchStatusEntry 1 }

        -- 1.3.6.1.4.1.4756.108.40.2.2.14.1.2
        iNasSwitchPortState OBJECT-TYPE
            SYNTAX      DisplayString
            MAX-ACCESS  read-only
            STATUS      current
            DESCRIPTION
                "The current state of the port. It can undertake one of the following values:
                 Globally Disabled: NAS is globally disabled.
                 Link Down: NAS is globally enabled, but there is no link on the port.
                 Authorized: The port is in Force Authorized or a single-supplicant mode and
                             the supplicant is authorized.
                 Unauthorized: The port is in Force Unauthorized or a single-supplicant mode and
                               the supplicant is not successfully authorized by the RADIUS server.
                 X Auth/Y Unauth: The port is in a multi-supplicant mode.
                                  Currently X clients are authorized and Y are unauthorized."
            ::= { iNasSwitchStatusEntry 2 }

        -- 1.3.6.1.4.1.4756.108.40.2.2.14.1.3
        iNasSwitchPortLastSource OBJECT-TYPE
            SYNTAX      DisplayString
            MAX-ACCESS  read-only
            STATUS      current
            DESCRIPTION
                "The source MAC address carried in the most recently received EAPOL frame for
                 EAPOL-based authentication, and the most recently received frame from a
                 new client for MAC-based authentication."
            ::= { iNasSwitchStatusEntry 3 }

        -- 1.3.6.1.4.1.4756.108.40.2.2.14.1.4
        iNasSwitchPortLastID OBJECT-TYPE
            SYNTAX      DisplayString
            MAX-ACCESS  read-only
            STATUS      current
            DESCRIPTION
                "The user name (supplicant identity) carried in the most recently received
                 Response Identity EAPOL frame for EAPOL-based authentication,
                 and the source MAC address from the most recently received frame from a
                 new client for MAC-based authentication."
            ::= { iNasSwitchStatusEntry 4 }

        -- 1.3.6.1.4.1.4756.108.40.2.2.14.1.5
        iNasSwitchPortQosClass OBJECT-TYPE
            SYNTAX      DisplayString
            MAX-ACCESS  read-only
            STATUS      current
            DESCRIPTION
                "QoS Class assigned to the port by the RADIUS server if enabled."
            ::= { iNasSwitchStatusEntry 5 }

        -- 1.3.6.1.4.1.4756.108.40.2.2.14.1.6
        iNasSwitchPortVlanID OBJECT-TYPE
            SYNTAX      DisplayString
            MAX-ACCESS  read-only
            STATUS      current
            DESCRIPTION
                "The VLAN ID that NAS has put the port in.
                 The return string is blank, if the Port VLAN ID is not overridden by NAS."
            ::= { iNasSwitchStatusEntry 6 }

    -- 1.3.6.1.4.1.4756.108.40.2.2.15
    iNasPortStatisticsTable OBJECT-TYPE
        SYNTAX      SEQUENCE OF INasPortStatisticsEntry
        MAX-ACCESS  not-accessible
        STATUS      current
        DESCRIPTION
            "This page provides an overview of the current NAS port states."
        ::= { iNAS 15 }

    -- 1.3.6.1.4.1.4756.108.40.2.2.15.1
    iNasPortStatisticsEntry OBJECT-TYPE
        SYNTAX      INasPortStatisticsEntry
        MAX-ACCESS  not-accessible
        STATUS      current
        DESCRIPTION
            "The Entry of Network Access Server Switch Status."
        INDEX { iPortIndex }
        ::= { iNasPortStatisticsTable 1 }

    INasPortStatisticsEntry ::=
        SEQUENCE {
            iNasPortStatisticsClearAll     INTEGER,
            iNasRxEapolTotal               Counter32,
            iNasRxEapolResponseID          Counter32,
            iNasRxEapolResponses           Counter32,
            iNasRxEapolStart               Counter32,
            iNasRxEapolLogoff              Counter32,
            iNasRxEapolInvalidType         Counter32,
            iNasRxEapolInvalidLength       Counter32,
            iNasTxEapolTotal               Counter32,
            iNasTxEapolRequestID           Counter32,
            iNasTxEapolRequests            Counter32,
            iNasRxBackendAccessChallenges  Counter32,
            iNasRxBackendOtherRequests     Counter32,
            iNasRxBackendAuthSuccesses     Counter32,
            iNasRxBackendAuthFailures      Counter32,
            iNasTxBackendResponeses        Counter32
        }

        -- 1.3.6.1.4.1.4756.108.40.2.2.15.1.1
        iNasPortStatisticsClearAll OBJECT-TYPE
            SYNTAX      INTEGER {
                            trigger(1),
                            normal(2)
                        }
            MAX-ACCESS  read-write
            STATUS      current
            DESCRIPTION
                "Triggers to clear both the port counters and all of the attached client's counters."
            ::= { iNasPortStatisticsEntry 1 }

        -- 1.3.6.1.4.1.4756.108.40.2.2.15.1.2
        iNasRxEapolTotal OBJECT-TYPE
            SYNTAX      Counter32
            MAX-ACCESS  read-only
            STATUS      current
            DESCRIPTION
                "The number of valid EAPOL frames of any type that have been received by the switch."
            ::= { iNasPortStatisticsEntry 2 }

        -- 1.3.6.1.4.1.4756.108.40.2.2.15.1.3
        iNasRxEapolResponseID OBJECT-TYPE
            SYNTAX      Counter32
            MAX-ACCESS  read-only
            STATUS      current
            DESCRIPTION
                "The number of valid EAPOL Response Identity frames that have been received by the switch."
            ::= { iNasPortStatisticsEntry 3 }

        -- 1.3.6.1.4.1.4756.108.40.2.2.15.1.4
        iNasRxEapolResponses OBJECT-TYPE
            SYNTAX      Counter32
            MAX-ACCESS  read-only
            STATUS      current
            DESCRIPTION
                "The number of valid EAPOL response frames (other than Response Identity frames)
                 that have been received by the switch."
            ::= { iNasPortStatisticsEntry 4 }

        -- 1.3.6.1.4.1.4756.108.40.2.2.15.1.5
        iNasRxEapolStart OBJECT-TYPE
            SYNTAX      Counter32
            MAX-ACCESS  read-only
            STATUS      current
            DESCRIPTION
                "The number of EAPOL Start frames that have been received by the switch."
            ::= { iNasPortStatisticsEntry 5 }

        -- 1.3.6.1.4.1.4756.108.40.2.2.15.1.6
        iNasRxEapolLogoff OBJECT-TYPE
            SYNTAX      Counter32
            MAX-ACCESS  read-only
            STATUS      current
            DESCRIPTION
                "The number of valid EAPOL Logoff frames that have been received by the switch."
            ::= { iNasPortStatisticsEntry 6 }

        -- 1.3.6.1.4.1.4756.108.40.2.2.15.1.7
        iNasRxEapolInvalidType OBJECT-TYPE
            SYNTAX      Counter32
            MAX-ACCESS  read-only
            STATUS      current
            DESCRIPTION
                "The number of EAPOL frames that have been received by the switch in which
                 the frame type is not recognized."
            ::= { iNasPortStatisticsEntry 7 }

        -- 1.3.6.1.4.1.4756.108.40.2.2.15.1.8
        iNasRxEapolInvalidLength OBJECT-TYPE
            SYNTAX      Counter32
            MAX-ACCESS  read-only
            STATUS      current
            DESCRIPTION
                "The number of EAPOL frames that have been received by the switch in which
                 the Packet Body Length field is invalid."
            ::= { iNasPortStatisticsEntry 8 }

        -- 1.3.6.1.4.1.4756.108.40.2.2.15.1.9
        iNasTxEapolTotal OBJECT-TYPE
            SYNTAX      Counter32
            MAX-ACCESS  read-only
            STATUS      current
            DESCRIPTION
                "The number of EAPOL frames of any type that have been transmitted by the switch."
            ::= { iNasPortStatisticsEntry 9 }

        -- 1.3.6.1.4.1.4756.108.40.2.2.15.1.10
        iNasTxEapolRequestID OBJECT-TYPE
            SYNTAX      Counter32
            MAX-ACCESS  read-only
            STATUS      current
            DESCRIPTION
                "The number of EAPOL Request Identity frames that have been transmitted by the switch."
            ::= { iNasPortStatisticsEntry 10 }

        -- 1.3.6.1.4.1.4756.108.40.2.2.15.1.11
        iNasTxEapolRequests OBJECT-TYPE
            SYNTAX      Counter32
            MAX-ACCESS  read-only
            STATUS      current
            DESCRIPTION
                "The number of valid EAPOL Request frames (other than Request Identity frames)
                 that have been transmitted by the switch."
            ::= { iNasPortStatisticsEntry 11 }

        -- 1.3.6.1.4.1.4756.108.40.2.2.15.1.12
        iNasRxBackendAccessChallenges OBJECT-TYPE
            SYNTAX      Counter32
            MAX-ACCESS  read-only
            STATUS      current
            DESCRIPTION
                "802.1X-based: Counts the number of times that the switch receives the first request from
                               the backend server following the first response from the supplicant.
                               Indicates that the backend server has communication with the switch.
                 MAC-based: Counts all Access Challenges received from the backend server for this port
                           (left-most table) or client (right-most table)."
            ::= { iNasPortStatisticsEntry 12 }

        -- 1.3.6.1.4.1.4756.108.40.2.2.15.1.13
        iNasRxBackendOtherRequests OBJECT-TYPE
            SYNTAX      Counter32
            MAX-ACCESS  read-only
            STATUS      current
            DESCRIPTION
                "802.1X-based: Counts the number of times that the switch sends an EAP Request packet
                               following the first to the supplicant.
                               Indicates that the backend server chose an EAP-method.
                 MAC-based: Not applicable."
            ::= { iNasPortStatisticsEntry 13 }

        -- 1.3.6.1.4.1.4756.108.40.2.2.15.1.14
        iNasRxBackendAuthSuccesses OBJECT-TYPE
            SYNTAX      Counter32
            MAX-ACCESS  read-only
            STATUS      current
            DESCRIPTION
                "802.1X- and MAC-based: Counts the number of times that the switch receives a
                                        success indication. Indicates that the supplicant/client
                                        has successfully authenticated to the backend server."
            ::= { iNasPortStatisticsEntry 14 }

        -- 1.3.6.1.4.1.4756.108.40.2.2.15.1.15
        iNasRxBackendAuthFailures OBJECT-TYPE
            SYNTAX      Counter32
            MAX-ACCESS  read-only
            STATUS      current
            DESCRIPTION
                "802.1X- and MAC-based: Counts the number of times that the switch receives a
                                        failure message. This indicates that the supplicant/client
                                        has not authenticated to the backend server."
            ::= { iNasPortStatisticsEntry 15 }

        -- 1.3.6.1.4.1.4756.108.40.2.2.15.1.16
        iNasTxBackendResponeses OBJECT-TYPE
            SYNTAX      Counter32
            MAX-ACCESS  read-only
            STATUS      current
            DESCRIPTION
                "802.1X-based: Counts the number of times that the switch attempts to send a
                               supplicant's first response packet to the backend server.
                               Indicates the switch attempted communication with the backend server.
                               Possible retransmissions are not counted.
                 MAC-based: Counts all the backend server packets sent from the switch towards
                            the backend server for a given port (left-most table) or client (right-most table).
                            Possible retransmissions are not counted."
            ::= { iNasPortStatisticsEntry 16 }

    
    -- 1.3.6.1.4.1.4756.108.40.2.3
    iACL OBJECT IDENTIFIER ::= { iSecurityNetwork 3 }

    -- 1.3.6.1.4.1.4756.108.40.2.3.1
    iAclPortCounterClear OBJECT-TYPE
        SYNTAX      INTEGER {
                        trigger(1),
                        normal(2)
                    }
        MAX-ACCESS  read-write
        STATUS      current
        DESCRIPTION
            "Clear the counters."
        ::= { iACL 1 }

    -- 1.3.6.1.4.1.4756.108.40.2.3.2
    iAclPortConfigTable OBJECT-TYPE
        SYNTAX      SEQUENCE OF IAclPortConfigEntry
        MAX-ACCESS  not-accessible
        STATUS      current
        DESCRIPTION
            "This table configure the ACL parameters (ACE) of each switch port.
             These parameters will affect frames received on a port unless the frame matches a specific ACE."
        ::= { iACL 2 }

    -- 1.3.6.1.4.1.4756.108.40.2.3.2.1
    iAclPortConfigEntry OBJECT-TYPE
        SYNTAX      IAclPortConfigEntry
        MAX-ACCESS  not-accessible
        STATUS      current
        DESCRIPTION
            "The Entry of ACL ports configuration."
        INDEX { iPortIndex }
        ::= { iAclPortConfigTable 1 }

    IAclPortConfigEntry ::=
        SEQUENCE {
            iAclPortPollcyID           Integer32,
            iAclPortAction             INTEGER,
            iAclPortRateLimiterID      Integer32,
            iAclPortRedirectPorts      Integer32,
            
            iAclPortLogging            INTEGER,
            iAclPortShutdown           INTEGER,
            iAclPortState              INTEGER,
            iAclPortCounter            Counter32
        }

        -- 1.3.6.1.4.1.4756.108.40.2.3.2.1.1
        iAclPortPollcyID OBJECT-TYPE
            SYNTAX      Integer32 (0..255)
            MAX-ACCESS  read-write
            STATUS      current
            DESCRIPTION
                "Select the policy to apply to this port. 
                 The allowed values are 0 through 255. 
                 The default value is 0."
            ::= { iAclPortConfigEntry 1 }

        -- 1.3.6.1.4.1.4756.108.40.2.3.2.1.2
        iAclPortAction OBJECT-TYPE
            SYNTAX      INTEGER {
                            deny(1),
                            permit(2)
                        }
            MAX-ACCESS  read-write
            STATUS      current
            DESCRIPTION
                "Select whether forwarding is permitted (permit) or denied (deny).
                 The default value is permit."
            ::= { iAclPortConfigEntry 2 }

        -- 1.3.6.1.4.1.4756.108.40.2.3.2.1.3
        iAclPortRateLimiterID OBJECT-TYPE
            SYNTAX      Integer32 (0 | 1..16)
            MAX-ACCESS  read-write
            STATUS      current
            DESCRIPTION
                "Select which rate limiter to apply on this port.
                 The allowed values are 0(Disabled) or the values 1 through 16.
                 The default value is 0(Disabled)."
            ::= { iAclPortConfigEntry 3 }

        -- 1.3.6.1.4.1.4756.108.40.2.3.2.1.4
        iAclPortRedirectPorts OBJECT-TYPE
            SYNTAX      Integer32
            MAX-ACCESS  read-write
            STATUS      current
            DESCRIPTION
                "Select which port frames are redirected on.
                 The allowed values are Disabled or a specific port number and
                 it can't be set when action is permitted. The default value is 'Disabled'."
            ::= { iAclPortConfigEntry 4 }



        -- 1.3.6.1.4.1.4756.108.40.2.3.2.1.6
        iAclPortLogging OBJECT-TYPE
            SYNTAX      INTEGER {
                            enable(1),
                            disable(2)
                        }
            MAX-ACCESS  read-write
            STATUS      current
            DESCRIPTION
                "Specify the logging operation of this port. The allowed values are:
                 Enabled: Frames received on the port are stored in the System Log.
                 Disabled: Frames received on the port are not logged.
                 The default value is Disabled.
                 Please note that the System Log memory size and logging rate is limited."
            ::= { iAclPortConfigEntry 6 }

        -- 1.3.6.1.4.1.4756.108.40.2.3.2.1.7
        iAclPortShutdown OBJECT-TYPE
            SYNTAX      INTEGER {
                            enable(1),
                            disable(2)
                        }
            MAX-ACCESS  read-write
            STATUS      current
            DESCRIPTION
                "Specify the port shut down operation of this port. The allowed values are:
                 Enabled: If a frame is received on the port, the port will be disabled.
                 Disabled: Port shut down is disabled.
                 The default value is Disabled."
            ::= { iAclPortConfigEntry 7 }

        -- 1.3.6.1.4.1.4756.108.40.2.3.2.1.8
        iAclPortState OBJECT-TYPE
            SYNTAX      INTEGER {
                            enable(1),
                            disable(2)
                        }
            MAX-ACCESS  read-write
            STATUS      current            
            DESCRIPTION
                "Specify the port state of this port. The allowed values are:
                 Enabled: To reopen ports by changing the volatile port configuration of the ACL user module.
                 Disabled: To close ports by changing the volatile port configuration of the ACL user module.
                 The default value is Enabled."
            DEFVAL      { 1 }     
            ::= { iAclPortConfigEntry 8 }

        -- 1.3.6.1.4.1.4756.108.40.2.3.2.1.9
        iAclPortCounter OBJECT-TYPE
            SYNTAX      Counter32
            UNITS       "Frames"
            MAX-ACCESS  read-only
            STATUS      current
            DESCRIPTION
                "Counts the number of frames that match this ACE."
            ::= { iAclPortConfigEntry 9 }

    -- 1.3.6.1.4.1.4756.108.40.2.3.3
    iAclRateLimiterConfigTable OBJECT-TYPE
        SYNTAX      SEQUENCE OF IAclRateLimiterConfigEntry
        MAX-ACCESS  not-accessible
        STATUS      current
        DESCRIPTION
            "This table configure the rate limiter for the ACL of the switch."
        ::= { iACL 3 }

    -- 1.3.6.1.4.1.4756.108.40.2.3.3.1
    iAclRateLimiterConfigEntry OBJECT-TYPE
        SYNTAX      IAclRateLimiterConfigEntry
        MAX-ACCESS  not-accessible
        STATUS      current
        DESCRIPTION
            "The Entry of ACL Rate Limiter Configuration."
        INDEX { iAclRateLimiterID }
        ::= { iAclRateLimiterConfigTable 1 }

    IAclRateLimiterConfigEntry ::=
        SEQUENCE {
            iAclRateLimiterID          Integer32,
            iAclLimitedRate            Integer32
        }

        -- 1.3.6.1.4.1.4756.108.40.2.3.3.1.1
        iAclRateLimiterID OBJECT-TYPE
            SYNTAX      Integer32 (1..16)
            MAX-ACCESS  read-only
            STATUS      current
            DESCRIPTION
                "The ID of rate limiter entry."
            ::= { iAclRateLimiterConfigEntry 1 }

        -- 1.3.6.1.4.1.4756.108.40.2.3.3.1.2
        iAclLimitedRate OBJECT-TYPE
            SYNTAX      Integer32 (0..3276700)
            MAX-ACCESS  read-write
            STATUS      current
            DESCRIPTION
                "The allowed values are: 0-3276700 in pps 
                 or 0, 100, 200, 300, ..., 1000000 in kbps."
            ::= { iAclRateLimiterConfigEntry 2 }



    -- 1.3.6.1.4.1.4756.108.40.2.3.4
    iAddACE OBJECT-TYPE
        SYNTAX      DisplayString
        MAX-ACCESS  read-write
        STATUS      current
        DESCRIPTION                                  
            "Inserts a new ACE to list.
             Value 0: Add ACE to end of list.
             Value 1 ~ 256: Insert new ACE before this ACE index."
        ::= { iACL 4 }

    -- 1.3.6.1.4.1.4756.108.40.2.3.5
    iDeleteACE OBJECT-TYPE
        SYNTAX      DisplayString
        MAX-ACCESS  read-write
        STATUS      current
        DESCRIPTION
            "Deletes the ACE by Index."
        ::= { iACL 5 }

    -- 1.3.6.1.4.1.4756.108.40.2.3.6
    iRemoveAllACE OBJECT-TYPE
        SYNTAX      INTEGER {
                        trigger(1),
                        normal(2)
                    }
        MAX-ACCESS  read-write
        STATUS      current
        DESCRIPTION
            "Remove all ACEs."
        ::= { iACL 6 }

    -- 1.3.6.1.4.1.4756.108.40.2.3.7
    iMoveAceDown OBJECT-TYPE
        SYNTAX      DisplayString
        MAX-ACCESS  read-write
        STATUS      current
        DESCRIPTION
            "Moves the ACE down the list."
        ::= { iACL 7 }

    -- 1.3.6.1.4.1.4756.108.40.2.3.8
    iAceCounterClear OBJECT-TYPE
        SYNTAX      INTEGER {
                        trigger(1),
                        normal(2)
                    }
        MAX-ACCESS  read-write
        STATUS      current
        DESCRIPTION
            "Clear the counters."
        ::= { iACL 8 }

    -- 1.3.6.1.4.1.4756.108.40.2.3.9
    iAceConfigTable OBJECT-TYPE
        SYNTAX      SEQUENCE OF IAceConfigEntry
        MAX-ACCESS  not-accessible
        STATUS      current
        DESCRIPTION
            "Configure an ACE (Access Control Entry) on this table.
             An ACE consists of several parameters.
             These parameters vary according to the frame type that you select."
        ::= { iACL 9 }

    -- 1.3.6.1.4.1.4756.108.40.2.3.9.1
    iAceConfigEntry OBJECT-TYPE
        SYNTAX      IAceConfigEntry
        MAX-ACCESS  not-accessible
        STATUS      current
        DESCRIPTION
            "The entry of ACE List."
        INDEX { iAceIndex }
        ::= { iAceConfigTable 1 }

    IAceConfigEntry ::=
        SEQUENCE {
        	iAceIndex                         Integer32,        -- 1
        	iAceID						      Integer32,
            iAceIngressPort                   Integer32,
            iAcePolicyFilter                  INTEGER,
            iAcePolicyValue                   Integer32,
            iAcePolicyBitmask                 DisplayString,
            iAceFrameType                     INTEGER,
            iAceSMacFilter                    INTEGER,
            iAceSMacValue                     MacAddress,
            iAceDMacFilter                    INTEGER,         -- 10
            iAceDMacValue                     MacAddress,      
            
            iAceVlanIdFilter                  INTEGER,
            iAceVlanID                        Integer32,       
            iAceTagPriority                   Integer32,
            iAceEtherTypeFilter               INTEGER,
            iAceEtherTypeValue                DisplayString,
            iAceArpFlagArpRarp                INTEGER,
            iAceArpFlagRequestRelay           INTEGER,
            iAceArpSenderIpFilter             INTEGER,         -- 20
            iAceArpSenderIpAddress            IpAddress,
            iAceArpSenderIpMask               IpAddress,
            iAceArpTargetIpFilter             INTEGER,
            iAceArpTargetIpAddress            IpAddress,       
            iAceArpTargetIpMask               IpAddress,
            iAceArpSMacMatch                  INTEGER,
            iAceRarpDMacMatch                 INTEGER,
            iAceArpIpEthernetLength           INTEGER,
            iAceArpIp                         INTEGER,
            iAceArpEthernet                   INTEGER,         -- 30       
            iAceIpProtocolFilter              INTEGER,
            iAceIpProtocolValue               Integer32,
            iAceIpTTL                         INTEGER,
            iAceIpFragment                    INTEGER,         
            iAceIpOption                      INTEGER,
            iAceSIpFilter                     INTEGER,
            iAceSIpAddress                    IpAddress,
            iAceSIpMask                       IpAddress,
            iAceDIpFilter                     INTEGER,
            iAceDIpAddress                    IpAddress,       -- 40
            iAceDIpMask                       IpAddress,
            iAceIcmpTypeFilter                INTEGER,
            iAceIcmpTypeValue                 Integer32,
            iAceIcmpCodeFilter                INTEGER,         
            iAceIcmpCodeValue                 Integer32,
            iAceUdpSPortFilter                INTEGER,
            iAceUdpSPortNumberSpecific        Integer32,
            iAceUdpSPortNumberStart           Integer32,
            iAceUdpSPortNumberLast            Integer32,
            iAceUdpDPortFilter                INTEGER,         -- 50
            iAceUdpDPortNumberSpecific        Integer32,
            iAceUdpDPortNumberStart           Integer32,
            iAceUdpDPortNumberLast            Integer32,
            iAceTcpSPortFilter                INTEGER,         
            iAceTcpSPortNumberSpecific        Integer32,
            iAceTcpSPortNumberStart           Integer32,
            iAceTcpSPortNumberLast            Integer32,
            iAceTcpDPortFilter                INTEGER,
            iAceTcpDPortNumberSpecific        Integer32,
            iAceTcpDPortNumberStart           Integer32,       -- 60
            iAceTcpDPortNumberLast            Integer32,
            iAceTcpFIN                        INTEGER,
            iAceTcpSYN                        INTEGER,
            iAceTcpRST                        INTEGER,         
            iAceTcpPSH                        INTEGER,
            iAceTcpACK                        INTEGER,
            iAceTcpURG                        INTEGER,
            iAceAction                        INTEGER,

            iAceRateLimiterID                 Integer32,       -- 70
            iAcePortRedirect                  DisplayString,

            iAceLogging                       INTEGER,
            iAceShutdown                      INTEGER
        }
        
        -- 1.3.6.1.4.1.4756.108.40.2.3.9.1.1
        iAceIndex OBJECT-TYPE
            SYNTAX      Integer32 (1..256)
            MAX-ACCESS  read-only
            STATUS      current
            DESCRIPTION
                "Indicates the Index of ACE entries."
            ::= { iAceConfigEntry 1 }
        
        -- 1.3.6.1.4.1.4756.108.40.2.3.9.1.2
        iAceID OBJECT-TYPE
            SYNTAX      Integer32 (1..256)
            MAX-ACCESS  read-only
            STATUS      current
            DESCRIPTION
                "Indicates the ID of ACE"
            ::= { iAceConfigEntry 2 }
                        
        -- 1.3.6.1.4.1.4756.108.40.2.3.9.1.3
        iAceIngressPort OBJECT-TYPE
            SYNTAX      Integer32    
            MAX-ACCESS  read-write
            STATUS      current
            DESCRIPTION
                ""
            ::= { iAceConfigEntry 3 }

        -- 1.3.6.1.4.1.4756.108.40.2.3.9.1.4
        iAcePolicyFilter OBJECT-TYPE
            SYNTAX      INTEGER {
                            any(1),
                            specific(2)
                        }    
            MAX-ACCESS  read-write
            STATUS      current
            DESCRIPTION
                "Specify the policy number filter for this ACE. 
                 Any: No policy filter is specified. (policy filter status is 'don't-care'.) 
                 Specific: If you want to filter a specific policy with this ACE, choose this value."
            ::= { iAceConfigEntry 4 }

        -- 1.3.6.1.4.1.4756.108.40.2.3.9.1.5
        iAcePolicyValue OBJECT-TYPE
            SYNTAX      Integer32 (0..255)    
            MAX-ACCESS  read-write
            STATUS      current
            DESCRIPTION
                "When 'Specific' is selected for the policy filter, you can enter a specific policy value.
                 The allowed range is 0 to 255."
            ::= { iAceConfigEntry 5 }

        -- 1.3.6.1.4.1.4756.108.40.2.3.9.1.6   
        iAcePolicyBitmask OBJECT-TYPE
            SYNTAX      DisplayString    
            MAX-ACCESS  read-write
            STATUS      current
            DESCRIPTION
                "When 'Specific' is selected for the policy filter, you can enter a specific policy bitmask.
                 The allowed range is 0x0 to 0xff."
            ::= { iAceConfigEntry 6 }

        -- 1.3.6.1.4.1.4756.108.40.2.3.9.1.7    
        iAceFrameType OBJECT-TYPE
            SYNTAX      INTEGER {
                            any(1),
                            ethernetType(2),
                            arp(3),
                            ipv4(4)
                        }    
            MAX-ACCESS  read-write
            STATUS      current
            DESCRIPTION
                "Select the ingress port for which this ACE applies.
                 Any: The ACE applies to any port.
                 Port n: The ACE applies to this port number, where n is the number of the switch port.
                 Policy n: The ACE applies to this policy number, where n can range from 1 through 8.
                 The default value is 'Any'."
            ::= { iAceConfigEntry 7 }

        -- 1.3.6.1.4.1.4756.108.40.2.3.9.1.8
        iAceSMacFilter OBJECT-TYPE
            SYNTAX      INTEGER {
                            any(1),
                            specific(2)
                        }    
            MAX-ACCESS  read-write
            STATUS      current
            DESCRIPTION
                "(Only effected when the frame type is Ethernet Type or ARP.)
                 Specify the source MAC filter for this ACE.
                 Any: No SMAC filter is specified. (SMAC filter status is don't-care.)
                 Specific: Filter a specific source MAC address with this ACE.
                 The default value is 'Any'."
            ::= { iAceConfigEntry 8 }

        -- 1.3.6.1.4.1.4756.108.40.2.3.9.1.9
        iAceSMacValue OBJECT-TYPE
            SYNTAX      MacAddress    
            MAX-ACCESS  read-write
            STATUS      current
            DESCRIPTION
                "When 'Specific' is selected for the SMAC filter,
                 you can enter a specific source MAC address.
                 The legal format is 'xx-xx-xx-xx-xx-xx'.
                 A frame that hits this ACE matches this SMAC value."
            ::= { iAceConfigEntry 9 }

        -- 1.3.6.1.4.1.4756.108.40.2.3.9.1.10
        iAceDMacFilter OBJECT-TYPE
            SYNTAX      INTEGER {
                            any(1),
                            multicast(2),
                            broadcast(3),
                            unicast(4),
                            specific(5)
                        }    
            MAX-ACCESS  read-write
            STATUS      current
            DESCRIPTION
                "Specify the destination MAC filter for this ACE.
                 Any: No DMAC filter is specified. (DMAC filter status is don't-care.)
                 Multicast: Frame must be multicast.
                 Broadcast: Frame must be broadcast.
                 Unicast: Frame must be unicast.
                 Specific: If you want to filter a specific destination MAC address with this ACE.
                 The default value is 'Any'."
            ::= { iAceConfigEntry 10 }

        -- 1.3.6.1.4.1.4756.108.40.2.3.9.1.11
        iAceDMacValue OBJECT-TYPE
            SYNTAX      MacAddress    
            MAX-ACCESS  read-write
            STATUS      current
            DESCRIPTION
                "When 'Specific' is selected for the DMAC filter,
                 you can enter a specific destination MAC address.
                 The legal format is 'xx-xx-xx-xx-xx-xx'.
                 A frame that hits this ACE matches this DMAC value."
            ::= { iAceConfigEntry 11 }



        -- 1.3.6.1.4.1.4756.108.40.2.3.9.1.13    
        iAceVlanIdFilter OBJECT-TYPE
            SYNTAX      INTEGER {
                            any(1),
                            specific(2)
                        }    
            MAX-ACCESS  read-write
            STATUS      current
            DESCRIPTION
                "Specify the VLAN ID filter for this ACE.
                 Any: No VLAN ID filter is specified. (VLAN ID filter status is don't-care.)
                 Specific: Filter a specific VLAN ID with this ACE.
                 The default value is 'Any'."
            ::= { iAceConfigEntry 13 }

        -- 1.3.6.1.4.1.4756.108.40.2.3.9.1.14    
        iAceVlanID OBJECT-TYPE
            SYNTAX      Integer32 (1..4095)    
            MAX-ACCESS  read-write
            STATUS      current
            DESCRIPTION
                "When Specific is selected for the VLAN ID filter, you can enter a specific VLAN ID number.
                 The allowed range is 1 to 4095. A frame that hits this ACE matches this VLAN ID value."
            ::= { iAceConfigEntry 14 }

        -- 1.3.6.1.4.1.4756.108.40.2.3.9.1.15    
        iAceTagPriority OBJECT-TYPE
            SYNTAX      Integer32 (-1..7)    
            MAX-ACCESS  read-write
            STATUS      current
            DESCRIPTION
                "Specify the tag priority for this ACE.
                 A frame that hits this ACE matches this tag priority.
                 The allowed number range is -1 to 7.
                 The value -1(Any) means that no tag priority is specified (tag priority is don't-care.)
                 The default value is -1(Any)."
            ::= { iAceConfigEntry 15 }

        -- 1.3.6.1.4.1.4756.108.40.2.3.9.1.16    
        iAceEtherTypeFilter OBJECT-TYPE
            SYNTAX      INTEGER {
                            any(1),
                            specific(2)
                        }    
            MAX-ACCESS  read-write
            STATUS      current
            DESCRIPTION
                "Specify the Ethernet type filter for this ACE.
                 Any: No EtherType filter is specified (EtherType filter status is don't-care).
                 Specific: Filter a specific EtherType filter with this ACE.
                 The default value is 'Any'."
            ::= { iAceConfigEntry 16 }

        -- 1.3.6.1.4.1.4756.108.40.2.3.9.1.17    
        iAceEtherTypeValue OBJECT-TYPE
            SYNTAX      DisplayString    
            MAX-ACCESS  read-write
            STATUS      current
            DESCRIPTION
                "When 'Specific' is selected for the EtherType filter,
                 you can enter a specific EtherType value.
                 The allowed range is 0x600 to 0xFFFF but excluding 0x800(IPv4), 0x806(ARP) and 0x86DD(IPv6).
                 A frame that hits this ACE matches this EtherType value."
            ::= { iAceConfigEntry 17 }

        -- 1.3.6.1.4.1.4756.108.40.2.3.9.1.18    
        iAceArpFlagArpRarp OBJECT-TYPE
            SYNTAX      INTEGER {
                            any(1),
                            arp(2),
                            rarp(3),
                            other(4)
                        }    
            MAX-ACCESS  read-write
            STATUS      current
            DESCRIPTION
                "Specify the available ARP/RARP opcode (OP) flag for this ACE.
                 Any: No ARP/RARP OP flag is specified. (OP is don't-care.)
                 ARP: Frame must have ARP/RARP opcode set to ARP.
                 RARP: Frame must have ARP/RARP opcode set to RARP.
                 Other: Frame has unknown ARP/RARP Opcode flag. 
                 The default value is 'Any'."
            ::= { iAceConfigEntry 18 }

        -- 1.3.6.1.4.1.4756.108.40.2.3.9.1.19    
        iAceArpFlagRequestRelay OBJECT-TYPE
            SYNTAX      INTEGER {
                            any(1),
                            request(2),
                            reply(3)
                        }    
            MAX-ACCESS  read-write
            STATUS      current
            DESCRIPTION
                "Specify the available ARP/RARP opcode (OP) flag for this ACE.
                 Any: No ARP/RARP OP flag is specified. (OP is 'don't-care'.)
                 Request: Frame must have ARP Request or RARP Request OP flag set.
                 Reply: Frame must have ARP Reply or RARP Reply OP flag.  
                 The default value is 'Any'."
            ::= { iAceConfigEntry 19 }

        -- 1.3.6.1.4.1.4756.108.40.2.3.9.1.20    
        iAceArpSenderIpFilter OBJECT-TYPE
            SYNTAX      INTEGER {
                            any(1),
                            host(2),
                            network(3)
                        }    
            MAX-ACCESS  read-write
            STATUS      current
            DESCRIPTION
                "Specify the sender IP filter for this ACE.
                 Any: No sender IP filter is specified. (Sender IP filter is don't-care.)
                 Host: Sender IP filter is set to Host.
                       Specify the sender IP address in the SIP Address field that appears.
                 Network: Sender IP filter is set to Network.
                          Specify the sender IP address and sender IP mask in the SIP Address
                          and SIP Mask fields that appear.  
                 The default value is 'Any'."
            ::= { iAceConfigEntry 20 }

        -- 1.3.6.1.4.1.4756.108.40.2.3.9.1.21    
        iAceArpSenderIpAddress OBJECT-TYPE
            SYNTAX      IpAddress    
            MAX-ACCESS  read-write
            STATUS      current
            DESCRIPTION
                "When 'Host' or 'Network' is selected for the sender IP filter,
                 you can enter a specific sender IP address in dotted decimal notation."
            ::= { iAceConfigEntry 21 }

        -- 1.3.6.1.4.1.4756.108.40.2.3.9.1.22    
        iAceArpSenderIpMask OBJECT-TYPE
            SYNTAX      IpAddress    
            MAX-ACCESS  read-write
            STATUS      current
            DESCRIPTION
                "When 'Network' is selected for the sender IP filter,
                 you can enter a specific sender IP mask in dotted decimal notation."
            ::= { iAceConfigEntry 22 }

        -- 1.3.6.1.4.1.4756.108.40.2.3.9.1.23    
        iAceArpTargetIpFilter OBJECT-TYPE
            SYNTAX      INTEGER {
                            any(1),
                            host(2),
                            network(3)
                        }    
            MAX-ACCESS  read-write
            STATUS      current
            DESCRIPTION
                "Specify the target IP filter for this specific ACE.
                 Any: No target IP filter is specified. (Target IP filter is don't-care.)
                 Host: Target IP filter is set to Host.
                       Specify the target IP address in the Target IP Address field that appears.
                 Network: Target IP filter is set to Network.
                          Specify the target IP address and target IP mask in the Target IP Address
                          and Target IP Mask fields that appear.  
                 The default value is 'Any'."
            ::= { iAceConfigEntry 23 }

        -- 1.3.6.1.4.1.4756.108.40.2.3.9.1.24    
        iAceArpTargetIpAddress OBJECT-TYPE
            SYNTAX      IpAddress    
            MAX-ACCESS  read-write
            STATUS      current
            DESCRIPTION
                "When 'Host' or 'Network' is selected for the target IP filter,
                 you can enter a specific target IP address in dotted decimal notation."
            ::= { iAceConfigEntry 24 }

        -- 1.3.6.1.4.1.4756.108.40.2.3.9.1.25    
        iAceArpTargetIpMask OBJECT-TYPE
            SYNTAX      IpAddress    
            MAX-ACCESS  read-write
            STATUS      current
            DESCRIPTION
                "When 'Network' is selected for the target IP filter,
                 you can enter a specific target IP mask in dotted decimal notation."
            ::= { iAceConfigEntry 25 }

        -- 1.3.6.1.4.1.4756.108.40.2.3.9.1.26    
        iAceArpSMacMatch OBJECT-TYPE
            SYNTAX      INTEGER {
                            any(1),
                            unequal(2),
                            equal(3)
                        }    
            MAX-ACCESS  read-write
            STATUS      current
            DESCRIPTION
                "Specify whether frames can hit the action according to
                 their sender hardware address field (SHA) settings.
                 Unequal: ARP frames where SHA is not equal to the SMAC address.
                 Equal: ARP frames where SHA is equal to the SMAC address.
                 Any: Any value is allowed (don't-care).   
                 The default value is 'Any'."
            ::= { iAceConfigEntry 26 }

        -- 1.3.6.1.4.1.4756.108.40.2.3.9.1.27    
        iAceRarpDMacMatch OBJECT-TYPE
            SYNTAX      INTEGER {
                            any(1),
                            unequal(2),
                            equal(3)
                        }    
            MAX-ACCESS  read-write
            STATUS      current
            DESCRIPTION
                "Specify whether frames can hit the action according to
                 their target hardware address field (THA) settings.
                 Unequal: RARP frames where THA is not equal to the DMAC address.
                 Equal: RARP frames where THA is equal to the DMAC address.
                 Any: Any value is allowed (don't-care).    
                 The default value is 'Any'."
            ::= { iAceConfigEntry 27 }

        -- 1.3.6.1.4.1.4756.108.40.2.3.9.1.28    
        iAceArpIpEthernetLength OBJECT-TYPE
            SYNTAX      INTEGER {
                            any(1),
                            unequal(2),
                            equal(3)
                        }    
            MAX-ACCESS  read-write
            STATUS      current
            DESCRIPTION
                "Specify whether frames can hit the action according to their
                 ARP/RARP hardware address length (HLN) and protocol address length (PLN) settings.
                 Unequal: ARP/RARP frames where the HLN is not equal to Ethernet (0x06) or
                          the (PLN) is not equal to IPv4 (0x04).
                 Equal: ARP/RARP frames where the HLN is equal to Ethernet (0x06) and
                        the (PLN) is equal to IPv4 (0x04).
                 Any: Any value is allowed (don't-care).     
                 The default value is 'Any'."
            ::= { iAceConfigEntry 28 }

        -- 1.3.6.1.4.1.4756.108.40.2.3.9.1.29    
        iAceArpIp OBJECT-TYPE
            SYNTAX      INTEGER {
                            any(1),
                            unequal(2),
                            equal(3)
                        }    
            MAX-ACCESS  read-write
            STATUS      current
            DESCRIPTION
                "Specify whether frames can hit the action according to
                 their ARP/RARP hardware address space (HRD) settings.
                 Unequal: ARP/RARP frames where the HLD is not equal to Ethernet (1).
                 Equal: ARP/RARP frames where the HLD is equal to Ethernet (1).
                 Any: Any value is allowed (don't-care).      
                 The default value is 'Any'."
            ::= { iAceConfigEntry 29 }

        -- 1.3.6.1.4.1.4756.108.40.2.3.9.1.30
        iAceArpEthernet OBJECT-TYPE
            SYNTAX      INTEGER {
                            any(1),
                            unequal(2),
                            equal(3)
                        }    
            MAX-ACCESS  read-write
            STATUS      current
            DESCRIPTION
                "Specify whether frames can hit the action according to
                 their ARP/RARP protocol address space (PRO) settings.
                 Unequal: ARP/RARP frames where the PRO is not equal to IP (0x800).
                 Equal: ARP/RARP frames where the PRO is equal to IP (0x800).
                 Any: Any value is allowed (don't-care).       
                 The default value is 'Any'."
            ::= { iAceConfigEntry 30 }

        -- 1.3.6.1.4.1.4756.108.40.2.3.9.1.31
        iAceIpProtocolFilter OBJECT-TYPE
            SYNTAX      INTEGER {
                            any(1),
                            icmp(2),
                            udp(3),
                            tcp(4),
                            other(5)
                        }    
            MAX-ACCESS  read-write
            STATUS      current
            DESCRIPTION
                "Specify the IP protocol filter for this ACE.
                 Any: No IP protocol filter is specified (don't-care).
                 
                 ICMP: Select ICMP to filter IPv4 ICMP protocol frames.
                       Extra fields for defining ICMP parameters will appear.
                       These fields are explained later in this help file.
                 UDP: Select UDP to filter IPv4 UDP protocol frames.
                      Extra fields for defining UDP parameters will appear.
                      These fields are explained later in this help file.
                 TCP: Select TCP to filter IPv4 TCP protocol frames.
                      Extra fields for defining TCP parameters will appear.
                      These fields are explained later in this help file.
                 Specific: Filter a specific IP protocol filter with this ACE.             
                 The default value is 'Any'."
            ::= { iAceConfigEntry 31 }

        -- 1.3.6.1.4.1.4756.108.40.2.3.9.1.32
        iAceIpProtocolValue OBJECT-TYPE
            SYNTAX      Integer32 (0..255)   
            MAX-ACCESS  read-write
            STATUS      current
            DESCRIPTION
                "When 'Specific' is selected for the IP protocol value,
                 you can enter a specific value. The allowed range is 0 to 255.
                 A frame that hits this ACE matches this IP protocol value."
            ::= { iAceConfigEntry 32 }

        -- 1.3.6.1.4.1.4756.108.40.2.3.9.1.33   
        iAceIpTTL OBJECT-TYPE
            SYNTAX      INTEGER {
                            any(1),
                            nonZero(2),
                            zero(3)
                        }    
            MAX-ACCESS  read-write
            STATUS      current
            DESCRIPTION
                "Specify the Time-to-Live settings for this ACE.
                 Zero: IPv4 frames with a Time-to-Live field greater than zero must not be able to match this entry.
                 Non-zero: IPv4 frames with a Time-to-Live field greater than zero must be able to match this entry.
                 Any: Any value is allowed (don't-care).        
                 The default value is 'Any'."
            ::= { iAceConfigEntry 33 }

        -- 1.3.6.1.4.1.4756.108.40.2.3.9.1.34   
        iAceIpFragment OBJECT-TYPE
            SYNTAX      INTEGER {
                            any(1),
                            yes(2),
                            no(3)
                        }    
            MAX-ACCESS  read-write
            STATUS      current
            DESCRIPTION
                "Specify the fragment offset settings for this ACE.
                 This involves the settings for the More Fragments (MF) bit
                 and the Fragment Offset (FRAG OFFSET) field for an IPv4 frame.
                 No: IPv4 frames where the MF bit is set or the FRAG OFFSET field is greater than
                     zero must not be able to match this entry.
                 Yes: IPv4 frames where the MF bit is set or the FRAG OFFSET field is greater than
                      zero must be able to match this entry.
                 Any: Any value is allowed (don't-care).      
                 The default value is 'Any'."
            ::= { iAceConfigEntry 34 }

        -- 1.3.6.1.4.1.4756.108.40.2.3.9.1.35
        iAceIpOption OBJECT-TYPE
            SYNTAX      INTEGER {
                            any(1),
                            yes(2),
                            no(3)
                        }    
            MAX-ACCESS  read-write
            STATUS      current
            DESCRIPTION
                "Specify the options flag setting for this ACE.
                 No: IPv4 frames where the options flag is set must not be able to match this entry.
                 Yes: IPv4 frames where the options flag is set must be able to match this entry.
                 Any: Any value is allowed (don't-care).       
                 The default value is 'Any'."
            ::= { iAceConfigEntry 35 }

        -- 1.3.6.1.4.1.4756.108.40.2.3.9.1.36
        iAceSIpFilter OBJECT-TYPE
            SYNTAX      INTEGER {
                            any(1),
                            host(2),
                            network(3)
                        }    
            MAX-ACCESS  read-write
            STATUS      current
            DESCRIPTION
                "Specify the source IP filter for this ACE.
                 Any: No source IP filter is specified. (Source IP filter is don't-care.)
                 Host: Source IP filter is set to Host.
                       Specify the source IP address in the SIP Address field that appears.
                 Network: Source IP filter is set to Network.
                          Specify the source IP address and source IP mask in the SIP Address
                          and SIP Mask fields that appear.   
                 The default value is 'Any'."
            ::= { iAceConfigEntry 36 }

        -- 1.3.6.1.4.1.4756.108.40.2.3.9.1.37
        iAceSIpAddress OBJECT-TYPE
            SYNTAX      IpAddress    
            MAX-ACCESS  read-write
            STATUS      current
            DESCRIPTION
                "When 'Host' or 'Network' is selected for the source IP filter,
                 you can enter a specific SIP address in dotted decimal notation."
            ::= { iAceConfigEntry 37 }

        -- 1.3.6.1.4.1.4756.108.40.2.3.9.1.38
        iAceSIpMask OBJECT-TYPE
            SYNTAX      IpAddress    
            MAX-ACCESS  read-write
            STATUS      current
            DESCRIPTION
                "When 'Network' is selected for the source IP filter,
                 you can enter a specific SIP mask in dotted decimal notation."
            ::= { iAceConfigEntry 38 }

        -- 1.3.6.1.4.1.4756.108.40.2.3.9.1.39    
        iAceDIpFilter OBJECT-TYPE
            SYNTAX      INTEGER {
                            any(1),
                            host(2),
                            network(3)
                        }    
            MAX-ACCESS  read-write
            STATUS      current
            DESCRIPTION
                "Specify the destination IP filter for this ACE.
                 Any: No destination IP filter is specified. (Destination IP filter is don't-care.)
                 Host: Destination IP filter is set to Host.
                       Specify the destination IP address in the DIP Address field that appears.
                 Network: Destination IP filter is set to Network.
                          Specify the destination IP address and destination IP mask in the DIP Address
                          and DIP Mask fields that appear.   
                 The default value is 'Any'."
            ::= { iAceConfigEntry 39 }

        -- 1.3.6.1.4.1.4756.108.40.2.3.9.1.40
        iAceDIpAddress OBJECT-TYPE
            SYNTAX      IpAddress    
            MAX-ACCESS  read-write
            STATUS      current
            DESCRIPTION
                "When 'Host' or 'Network' is selected for the destination IP filter,
                 you can enter a specific DIP address in dotted decimal notation."
            ::= { iAceConfigEntry 40 }

        -- 1.3.6.1.4.1.4756.108.40.2.3.9.1.41
        iAceDIpMask OBJECT-TYPE
            SYNTAX      IpAddress    
            MAX-ACCESS  read-write
            STATUS      current
            DESCRIPTION
                "When 'Network' is selected for the destination IP filter,
                 you can enter a specific DIP mask in dotted decimal notation. "
            ::= { iAceConfigEntry 41 }

        -- 1.3.6.1.4.1.4756.108.40.2.3.9.1.42
        iAceIcmpTypeFilter OBJECT-TYPE
            SYNTAX      INTEGER {
                            any(1),
                            specific(2)
                        }    
            MAX-ACCESS  read-write
            STATUS      current
            DESCRIPTION
                "Specify the ICMP filter for this ACE.
                 Any: No ICMP filter is specified (ICMP filter status is don't-care).
                 Specific: If you want to filter a specific ICMP filter with this ACE,
                           you can enter a specific ICMP value.
                           A field for entering an ICMP value appears.    
                 The default value is 'Any'."
            ::= { iAceConfigEntry 42 }

        -- 1.3.6.1.4.1.4756.108.40.2.3.9.1.43
        iAceIcmpTypeValue OBJECT-TYPE
            SYNTAX      Integer32 (0..255)   
            MAX-ACCESS  read-write
            STATUS      current
            DESCRIPTION
                "When 'Specific' is selected for the ICMP filter,
                 you can enter a specific ICMP value. The allowed range is 0 to 255.
                 A frame that hits this ACE matches this ICMP value."
            ::= { iAceConfigEntry 43 }

        -- 1.3.6.1.4.1.4756.108.40.2.3.9.1.44
        iAceIcmpCodeFilter OBJECT-TYPE
            SYNTAX      INTEGER {
                            any(1),
                            specific(2)
                        }    
            MAX-ACCESS  read-write
            STATUS      current
            DESCRIPTION
                "Specify the ICMP code filter for this ACE.
                 Any: No ICMP code filter is specified (ICMP code filter status is don't-care).
                 Specific: If you want to filter a specific ICMP code filter with this ACE,
                           you can enter a specific ICMP code value.
                           A field for entering an ICMP code value appears.     
                 The default value is 'Any'."
            ::= { iAceConfigEntry 44 }

        -- 1.3.6.1.4.1.4756.108.40.2.3.9.1.45
        iAceIcmpCodeValue OBJECT-TYPE
            SYNTAX      Integer32 (0..255)   
            MAX-ACCESS  read-write
            STATUS      current
            DESCRIPTION
                "When 'Specific' is selected for the ICMP code filter,
                 you can enter a specific ICMP code value. The allowed range is 0 to 255.
                 A frame that hits this ACE matches this ICMP code value."
            ::= { iAceConfigEntry 45 }

        -- 1.3.6.1.4.1.4756.108.40.2.3.9.1.46    
        iAceUdpSPortFilter OBJECT-TYPE
            SYNTAX      INTEGER {
                            any(1),
                            specific(2),
                            range(3)
                        }    
            MAX-ACCESS  read-write
            STATUS      current
            DESCRIPTION
                "Specify the UDP source filter for this ACE.
                 Any: No UDP source filter is specified (UDP source filter status is don't-care).
                 Specific: Filter a specific UDP source filter with this ACE.
                 Range: Filter a specific UDP source range filter with this ACE.    
                 The default value is 'Any'."
            ::= { iAceConfigEntry 46 }

        -- 1.3.6.1.4.1.4756.108.40.2.3.9.1.47    
        iAceUdpSPortNumberSpecific OBJECT-TYPE
            SYNTAX      Integer32 (0..65535)   
            MAX-ACCESS  read-write
            STATUS      current
            DESCRIPTION
                "When 'Specific' is selected for the UDP source filter,
                 you can enter a specific UDP source value. The allowed range is 0 to 65535.
                 A frame that hits this ACE matches this UDP source value."
            ::= { iAceConfigEntry 47 }

        -- 1.3.6.1.4.1.4756.108.40.2.3.9.1.48    
        iAceUdpSPortNumberStart OBJECT-TYPE
            SYNTAX      Integer32 (0..65534)   
            MAX-ACCESS  read-write
            STATUS      current
            DESCRIPTION
                "When 'Range' is selected for the UDP source filter,
                 the starting Source UDP port number of range can be configured here.
                 The allowed range is 0 to 65534."
            ::= { iAceConfigEntry 48 }

        -- 1.3.6.1.4.1.4756.108.40.2.3.9.1.49    
        iAceUdpSPortNumberLast OBJECT-TYPE
            SYNTAX      Integer32 (1..65535)   
            MAX-ACCESS  read-write
            STATUS      current
            DESCRIPTION
                "When 'Range' is selected for the UDP source filter,
                 the last Source UDP port number of range can be configured here.
                 The allowed range is 1 to 65535."
            ::= { iAceConfigEntry 49 }

        -- 1.3.6.1.4.1.4756.108.40.2.3.9.1.50
        iAceUdpDPortFilter OBJECT-TYPE
            SYNTAX      INTEGER {
                            any(1),
                            specific(2),
                            range(3)
                        }    
            MAX-ACCESS  read-write
            STATUS      current
            DESCRIPTION
                "Specify the UDP destination filter for this ACE.
                 Any: No UDP destination filter is specified (UDP destination filter status is don't-care).
                 Specific: Filter a specific UDP destination filter with this ACE.
                 Range: Filter a specific range UDP destination filter with this ACE.
                 The default value is 'Any'."
            ::= { iAceConfigEntry 50 }

        -- 1.3.6.1.4.1.4756.108.40.2.3.9.1.51
        iAceUdpDPortNumberSpecific OBJECT-TYPE
            SYNTAX      Integer32 (0..65535)   
            MAX-ACCESS  read-write
            STATUS      current
            DESCRIPTION
                "When 'Specific' is selected for the UDP destination filter,
                 you can enter a specific UDP destination value. The allowed range is 0 to 65535.
                 A frame that hits this ACE matches this UDP destination value."
            ::= { iAceConfigEntry 51 }

        -- 1.3.6.1.4.1.4756.108.40.2.3.9.1.52    
        iAceUdpDPortNumberStart OBJECT-TYPE
            SYNTAX      Integer32 (0..65534)   
            MAX-ACCESS  read-write
            STATUS      current
            DESCRIPTION
                "When 'Range' is selected for the UDP destination filter,
                 the starting Destination UDP port number of range can be configured here.
                 The allowed range is 0 to 65534."
            ::= { iAceConfigEntry 52 }

        -- 1.3.6.1.4.1.4756.108.40.2.3.9.1.53    
        iAceUdpDPortNumberLast OBJECT-TYPE
            SYNTAX      Integer32 (1..65535)   
            MAX-ACCESS  read-write
            STATUS      current
            DESCRIPTION
                "When 'Range' is selected for the UDP destination filter,
                 the last Destination UDP port number of range can be configured here.
                 The allowed range is 1 to 65535."
            ::= { iAceConfigEntry 53 }

        -- 1.3.6.1.4.1.4756.108.40.2.3.9.1.54    
        iAceTcpSPortFilter OBJECT-TYPE
            SYNTAX      INTEGER {
                            any(1),
                            specific(2),
                            range(3)
                        }    
            MAX-ACCESS  read-write
            STATUS      current
            DESCRIPTION
                "Specify the TCP source filter for this ACE.
                 Any: No TCP source filter is specified (TCP source filter status is don't-care).
                 Specific: Filter a specific TCP source filter with this ACE.
                 Range: Filter a specific TCP source range filter with this ACE.    
                 The default value is 'Any'."
            ::= { iAceConfigEntry 54 }

        -- 1.3.6.1.4.1.4756.108.40.2.3.9.1.55    
        iAceTcpSPortNumberSpecific OBJECT-TYPE
            SYNTAX      Integer32 (0..65535)   
            MAX-ACCESS  read-write
            STATUS      current
            DESCRIPTION
                "When 'Specific' is selected for the TCP source filter,
                 you can enter a specific TCP source value. The allowed range is 0 to 65535.
                 A frame that hits this ACE matches this TCP source value."
            ::= { iAceConfigEntry 55 }

        -- 1.3.6.1.4.1.4756.108.40.2.3.9.1.56    
        iAceTcpSPortNumberStart OBJECT-TYPE
            SYNTAX      Integer32 (0..65534)   
            MAX-ACCESS  read-write
            STATUS      current
            DESCRIPTION
                "When 'Range' is selected for the TCP source filter,
                 the starting Source TCP port number of range can be configured here.
                 The allowed range is 0 to 65534."
            ::= { iAceConfigEntry 56 }

        -- 1.3.6.1.4.1.4756.108.40.2.3.9.1.57    
        iAceTcpSPortNumberLast OBJECT-TYPE
            SYNTAX      Integer32 (1..65535)   
            MAX-ACCESS  read-write
            STATUS      current
            DESCRIPTION
                "When 'Range' is selected for the TCP source filter,
                 the last Source TCP port number of range can be configured here.
                 The allowed range is 1 to 65535."
            ::= { iAceConfigEntry 57 }

        -- 1.3.6.1.4.1.4756.108.40.2.3.9.1.58
        iAceTcpDPortFilter OBJECT-TYPE
            SYNTAX      INTEGER {
                            any(1),
                            specific(2),
                            range(3)
                        }    
            MAX-ACCESS  read-write
            STATUS      current
            DESCRIPTION
                "Specify the TCP destination filter for this ACE.
                 Any: No TCP destination filter is specified (TCP destination filter status is don't-care).
                 Specific: Filter a specific TCP destination filter with this ACE.
                 Range: Filter a specific range TCP destination filter with this ACE.
                 The default value is 'Any'."
            ::= { iAceConfigEntry 58 }

        -- 1.3.6.1.4.1.4756.108.40.2.3.9.1.59    
        iAceTcpDPortNumberSpecific OBJECT-TYPE
            SYNTAX      Integer32 (0..65535)   
            MAX-ACCESS  read-write
            STATUS      current
            DESCRIPTION
                "When 'Specific' is selected for the TCP destination filter,
                 you can enter a specific TCP destination value. The allowed range is 0 to 65535.
                 A frame that hits this ACE matches this TCP destination value."
            ::= { iAceConfigEntry 59 }

        -- 1.3.6.1.4.1.4756.108.40.2.3.9.1.60    
        iAceTcpDPortNumberStart OBJECT-TYPE
            SYNTAX      Integer32 (0..65534)   
            MAX-ACCESS  read-write
            STATUS      current
            DESCRIPTION
                "When 'Range' is selected for the TCP destination filter,
                 the starting Destination TCP port number of range can be configured here.
                 The allowed range is 0 to 65534."
            ::= { iAceConfigEntry 60 }

        -- 1.3.6.1.4.1.4756.108.40.2.3.9.1.61
        iAceTcpDPortNumberLast OBJECT-TYPE
            SYNTAX      Integer32 (1..65535)   
            MAX-ACCESS  read-write
            STATUS      current
            DESCRIPTION
                "When 'Range' is selected for the TCP destination filter,
                 the last Destination TCP port number of range can be configured here.
                 The allowed range is 1 to 65535."
            ::= { iAceConfigEntry 61 }

        -- 1.3.6.1.4.1.4756.108.40.2.3.9.1.62
        iAceTcpFIN OBJECT-TYPE
            SYNTAX      INTEGER {
                            any(1),
                            unable(2),
                            able(3)
                        }    
            MAX-ACCESS  read-write
            STATUS      current
            DESCRIPTION
                "Specify the TCP 'No more data from sender' (FIN) value for this ACE.
                 Unable: TCP frames where the FIN field is set must not be able to match this entry.
                 Able: TCP frames where the FIN field is set must be able to match this entry.
                 Any: Any value is allowed (don't-care).
                 The default value is 'Any'"
            ::= { iAceConfigEntry 62 }

        -- 1.3.6.1.4.1.4756.108.40.2.3.9.1.63
        iAceTcpSYN OBJECT-TYPE
            SYNTAX      INTEGER {
                            any(1),
                            unable(2),
                            able(3)
                        }    
            MAX-ACCESS  read-write
            STATUS      current
            DESCRIPTION
                "Specify the TCP 'Synchronize sequence numbers' (SYN) value for this ACE.
                 Unable: TCP frames where the SYN field is set must not be able to match this entry.
                 Able: TCP frames where the SYN field is set must be able to match this entry.
                 Any: Any value is allowed (don't-care). 
                 The default value is 'Any'"
            ::= { iAceConfigEntry 63 }

        -- 1.3.6.1.4.1.4756.108.40.2.3.9.1.64    
        iAceTcpRST OBJECT-TYPE
            SYNTAX      INTEGER {
                            any(1),
                            unable(2),
                            able(3)
                        }    
            MAX-ACCESS  read-write
            STATUS      current
            DESCRIPTION
                "Specify the TCP 'Reset the connection' (RST) value for this ACE.
                 Unable: TCP frames where the RST field is set must not be able to match this entry.
                 Able: TCP frames where the RST field is set must be able to match this entry.
                 Any: Any value is allowed (don't-care).  
                 The default value is 'Any'"
            ::= { iAceConfigEntry 64 }

        -- 1.3.6.1.4.1.4756.108.40.2.3.9.1.65
        iAceTcpPSH OBJECT-TYPE
            SYNTAX      INTEGER {
                            any(1),
                            unable(2),
                            able(3)
                        }    
            MAX-ACCESS  read-write
            STATUS      current
            DESCRIPTION
                "Specify the TCP 'Push Function' (PSH) value for this ACE.
                 Unable: TCP frames where the PSH field is set must not be able to match this entry.
                 Able: TCP frames where the PSH field is set must be able to match this entry.
                 Any: Any value is allowed (don't-care).   
                 The default value is 'Any'"
            ::= { iAceConfigEntry 65 }

        -- 1.3.6.1.4.1.4756.108.40.2.3.9.1.66    
        iAceTcpACK OBJECT-TYPE
            SYNTAX      INTEGER {
                            any(1),
                            unable(2),
                            able(3)
                        }    
            MAX-ACCESS  read-write
            STATUS      current
            DESCRIPTION
                "Specify the TCP 'Acknowledgment field significant' (ACK) value for this ACE.
                 Unable: TCP frames where the ACK field is set must not be able to match this entry.
                 Able: TCP frames where the ACK field is set must be able to match this entry.
                 Any: Any value is allowed (don't-care).    
                 The default value is 'Any'"
            ::= { iAceConfigEntry 66 }

        -- 1.3.6.1.4.1.4756.108.40.2.3.9.1.67    
        iAceTcpURG OBJECT-TYPE
            SYNTAX      INTEGER {
                            any(1),
                            unable(2),
                            able(3)
                        }    
            MAX-ACCESS  read-write
            STATUS      current
            DESCRIPTION
                "Specify the TCP 'Urgent Pointer field significant' (URG) value for this ACE.
                 Unable: TCP frames where the URG field is set must not be able to match this entry.
                 Able: TCP frames where the URG field is set must be able to match this entry.
                 Any: Any value is allowed (don't-care).     
                 The default value is 'Any'"
            ::= { iAceConfigEntry 67 }

        -- 1.3.6.1.4.1.4756.108.40.2.3.9.1.68
        iAceAction OBJECT-TYPE
            SYNTAX      INTEGER {
                            deny(1),
                            permit(2)
                        }
            MAX-ACCESS  read-write
            STATUS      current
            DESCRIPTION
                "Specify the action to take with a frame that hits this ACE.
                 Permit: The frame that hits this ACE is granted permission for the ACE operation.
                 Deny: The frame that hits this ACE is dropped.
                 Filter: Frames matching the ACE are filtered. 
                 The default value is 'Permit'."
            ::= { iAceConfigEntry 68 }
        

            
        -- 1.3.6.1.4.1.4756.108.40.2.3.9.1.70
        iAceRateLimiterID OBJECT-TYPE
            SYNTAX      Integer32 (0 | 1..16)
            MAX-ACCESS  read-write
            STATUS      current
            DESCRIPTION
                "Specify the rate limiter in number of base units.
                 The allowed range is 0{Disabled) to 16.
                 The value 0(Disabled) indicates that the rate limiter operation is disabled.
                 The default value is 0(Disabled)."
            ::= { iAceConfigEntry 70 }

        -- 1.3.6.1.4.1.4756.108.40.2.3.9.1.71
        iAcePortRedirect OBJECT-TYPE
            SYNTAX      DisplayString
            MAX-ACCESS  read-write
            STATUS      current
            DESCRIPTION
                "Frames that hit the ACE are redirected to the port number specified here.
                 The allowed range is the same as the switch port number range.
                 Disabled indicates that the port redirect operation is disabled and
                 the specific port number of 'Port Redirect' can't be set when action is permitted."
            ::= { iAceConfigEntry 71 }

 

        -- 1.3.6.1.4.1.4756.108.40.2.3.9.1.73
        iAceLogging OBJECT-TYPE
            SYNTAX      INTEGER {
                            enable(1),
                            disable(2)
                        }
            MAX-ACCESS  read-write
            STATUS      current
            DESCRIPTION
                "Specify the logging operation of the ACE. The allowed values are:
                 Enabled: Frames matching the ACE are stored in the System Log.
                 Disabled: Frames matching the ACE are not logged. 
                 The default value is Disabled.
                 Please note that the System Log memory size and logging rate is limited."
            ::= { iAceConfigEntry 73 }

        -- 1.3.6.1.4.1.4756.108.40.2.3.9.1.74
        iAceShutdown OBJECT-TYPE
            SYNTAX      INTEGER {
                            enable(1),
                            disable(2)
                        }
            MAX-ACCESS  read-write
            STATUS      current
            DESCRIPTION
                "Specify the port shut down operation of the ACE. The allowed values are:
                 Enabled: If a frame matches the ACE, the ingress port will be disabled.
                 Disabled: Port shut down is disabled for the ACE. 
                 The default value is Disabled."
            ::= { iAceConfigEntry 74 }

    -- 1.3.6.1.4.1.4756.108.40.2.3.10
    iAclStatusTable OBJECT-TYPE
        SYNTAX      SEQUENCE OF IAclStatusEntry
        MAX-ACCESS  not-accessible
        STATUS      current
        DESCRIPTION
            "This table shows the ACL status."
        ::= { iACL 10 }

    -- 1.3.6.1.4.1.4756.108.40.2.3.10.1
    iAclStatusEntry OBJECT-TYPE
        SYNTAX      IAclStatusEntry
        MAX-ACCESS  not-accessible
        STATUS      current
        DESCRIPTION
            "The Entry of ACL status."
        INDEX { iAclStatusIndex }
        ::= { iAclStatusTable 1 }

    IAclStatusEntry ::=
        SEQUENCE {
            iAclStatusIndex        Integer32,
            iAclUser               INTEGER,
            iAclStatusAceID        Integer32,
            iAclFrameType          DisplayString,
            iAclAction             INTEGER,
            iAclRateLimiter        Integer32,

            iAclToCPU              INTEGER,
            iAclCounter            Counter32,
            iAclConflict           INTEGER
        }

        -- 1.3.6.1.4.1.4756.108.40.2.3.10.1.1    
        iAclStatusIndex OBJECT-TYPE
            SYNTAX      Integer32 (1..256)
            MAX-ACCESS  read-only
            STATUS      current
            DESCRIPTION
                "Indicates the Index of ACL Status entries."
            ::= { iAclStatusEntry 1 }
            
        -- 1.3.6.1.4.1.4756.108.40.2.3.10.1.2    
        iAclUser OBJECT-TYPE
            SYNTAX      INTEGER {
                            static(1),
                            ipSourceGuard(2),
                            ipmc(3),
                            mep(4),
                            arpInspection(5),
                            upnp(6),
                            ptp(7),
                            dhcp(8),
                            loopProtect(9),
                            u-Ring(10)
                        }    
            MAX-ACCESS  read-only
            STATUS      current
            DESCRIPTION
                "Indicates the ACL user."
            ::= { iAclStatusEntry 2 }
        
        -- 1.3.6.1.4.1.4756.108.40.2.3.10.1.3    
        iAclStatusAceID OBJECT-TYPE
            SYNTAX      Integer32 (1..256)
            MAX-ACCESS  read-only
            STATUS      current
            DESCRIPTION
                "Indicates the AceID of ACL Status entries."
            ::= { iAclStatusEntry 3 }

        -- 1.3.6.1.4.1.4756.108.40.2.3.10.1.4    
        iAclFrameType OBJECT-TYPE
            SYNTAX      DisplayString    
            MAX-ACCESS  read-only
            STATUS      current
            DESCRIPTION
                "Indicates the frame type of the ACE. Possible values are:
                 Any: The ACE will match any frame type.
                 EType: The ACE will match Ethernet Type frames.
                        Note that an Ethernet Type based ACE will not get matched by IP and ARP frames.
                 ARP: The ACE will match ARP/RARP frames.
                 IPv4: The ACE will match all IPv4 frames.
                 IPv4/ICMP: The ACE will match IPv4 frames with ICMP protocol.
                 IPv4/UDP: The ACE will match IPv4 frames with UDP protocol.
                 IPv4/TCP: The ACE will match IPv4 frames with TCP protocol.
                 IPv4/Other: The ACE will match IPv4 frames, which are not ICMP/UDP/TCP."
            ::= { iAclStatusEntry 4 }

        -- 1.3.6.1.4.1.4756.108.40.2.3.10.1.5
        iAclAction OBJECT-TYPE
            SYNTAX      INTEGER {
                            deny(1),
                            permit(2),
                            filter(3)
                        }
            MAX-ACCESS  read-only
            STATUS      current
            DESCRIPTION
                "Indicates the forwarding action of the ACE.
                 Permit: Frames matching the ACE may be forwarded and learned.
                 Deny: Frames matching the ACE are dropped.
                 Filter: Frames matching the ACE are filtered.
                "
            ::= { iAclStatusEntry 5 }

        -- 1.3.6.1.4.1.4756.108.40.2.3.10.1.6
        iAclRateLimiter OBJECT-TYPE
            SYNTAX      Integer32 (0..16)
            MAX-ACCESS  read-only
            STATUS      current
            DESCRIPTION
                "Indicates the rate limiter number of the ACE.
                 The allowed range is 0(Disable) to 16.
                 When 0(Disabled) is displayed, the rate limiter operation is disabled."
            ::= { iAclStatusEntry 6 }



        -- 1.3.6.1.4.1.4756.108.40.2.3.10.1.8
        iAclToCPU OBJECT-TYPE
            SYNTAX      INTEGER {
                            yes(1),
                            no(2)
                        }
            MAX-ACCESS  read-only
            STATUS      current
            DESCRIPTION
                "Forward packet that matched the specific ACE to CPU."
            ::= { iAclStatusEntry 8 }

        -- 1.3.6.1.4.1.4756.108.40.2.3.10.1.9
        iAclCounter OBJECT-TYPE
            SYNTAX      Counter32
            UNITS       "Frames"
            MAX-ACCESS  read-only
            STATUS      current
            DESCRIPTION
                "The counter indicates the number of times the ACE was hit by a frame."
            ::= { iAclStatusEntry 9 }

        -- 1.3.6.1.4.1.4756.108.40.2.3.10.1.10
        iAclConflict OBJECT-TYPE
            SYNTAX      INTEGER {
                            yes(1),
                            no(2)
                        }
            MAX-ACCESS  read-only
            STATUS      current
            DESCRIPTION
                "Indicates the hardware status of the specific ACE.
                 The specific ACE is not applied to the hardware due to hardware limitations."
            ::= { iAclStatusEntry 10 }


    -- 1.3.6.1.4.1.4756.108.40.2.4
    iDHCP OBJECT IDENTIFIER ::= { iSecurityNetwork 4 }

    -- 1.3.6.1.4.1.4756.108.40.2.4.1    
    iDhcpSnoopingMode OBJECT-TYPE
        SYNTAX      INTEGER {
                        enabled(1),
                        disabled(2)
                    }
        MAX-ACCESS  read-write
        STATUS      current
        DESCRIPTION
            "Indicates the DHCP snooping mode operation. Possible modes are:
             Enabled: Enable DHCP snooping mode operation.
                      When DHCP snooping mode operation is enabled,
                      the DHCP request messages will be forwarded to trusted ports
                      and only allow reply packets from trusted ports.
             Disabled: Disable DHCP snooping mode operation."
        ::= { iDHCP 1 }

    -- 1.3.6.1.4.1.4756.108.40.2.4.2
    iDhcpSnoopingPortConfigTable OBJECT-TYPE
        SYNTAX      SEQUENCE OF IDhcpSnoopingPortConfigEntry
        MAX-ACCESS  not-accessible
        STATUS      current
        DESCRIPTION
            "Configure DHCP Snooping on this table."
        ::= { iDHCP 2 }

    -- 1.3.6.1.4.1.4756.108.40.2.4.2.1
    iDhcpSnoopingPortConfigEntry OBJECT-TYPE
        SYNTAX      IDhcpSnoopingPortConfigEntry
        MAX-ACCESS  not-accessible
        STATUS      current
        DESCRIPTION
            "The Entry of DHCP Snooping ports."
        INDEX { iPortIndex }
        ::= { iDhcpSnoopingPortConfigTable 1 }

    IDhcpSnoopingPortConfigEntry ::=
        SEQUENCE {
            iDhcpSnoopingPortMode             INTEGER
        }

        -- 1.3.6.1.4.1.4756.108.40.2.4.2.1.1
        iDhcpSnoopingPortMode OBJECT-TYPE
            SYNTAX      INTEGER {
                            trusted(1),
                            untrusted(2)
                        }
            MAX-ACCESS  read-write
            STATUS      current
            DESCRIPTION
                "Indicates the DHCP snooping port mode. Possible port modes are:
                 Trusted: Configures the port as trusted source of the DHCP messages.
                 Untrusted: Configures the port as untrusted source of the DHCP messages."
            ::= { iDhcpSnoopingPortConfigEntry 1 }

    -- 1.3.6.1.4.1.4756.108.40.2.4.4    
    iDhcpRelayMode OBJECT-TYPE
        SYNTAX      INTEGER {
                        enabled(1),
                        disabled(2)
                    }
        MAX-ACCESS  read-write
        STATUS      current
        DESCRIPTION
            "Indicates the DHCP relay mode operation. Possible modes are:
             Enabled:Enable DHCP relay mode operation.
                     When DHCP relay mode operation is enabled,
                     the agent forwards and transfers DHCP messages between the clients
                     and the server when they are not in the same subnet domain.
                     And the DHCP broadcast message won't be flooded for security considerations.
             Disabled: Disable DHCP relay mode operation.
             Relay mode doesn't allowed enabled when 'Relay Server' is '0.0.0.0'"
        ::= { iDHCP 4 }

    -- 1.3.6.1.4.1.4756.108.40.2.4.5    
    iDhcpRelayServerIP OBJECT-TYPE
        SYNTAX      IpAddress
        MAX-ACCESS  read-write
        STATUS      current
        DESCRIPTION
            "Indicates the DHCP relay server IP address.
             A DHCP relay agent is used to forward and to transfer DHCP messages between the clients
             and the server when they are not in the same subnet domain.
             'Relay Server' doesn't allowed '0.0.0.0' when relay mode is enabled."
        ::= { iDHCP 5 }

    -- 1.3.6.1.4.1.4756.108.40.2.4.6    
    iDhcpRelayInformationMode OBJECT-TYPE
        SYNTAX      INTEGER {
                        enabled(1),
                        disabled(2)
                    }
        MAX-ACCESS  read-write
        STATUS      current
        DESCRIPTION
            "Indicates the DHCP relay information mode option operation.
             The option 82 circuit ID format as '[vlan_id][module_id][port_no]'.
             The first four characters represent the VLAN ID,
             the fifth and sixth characters are the module ID,
             and the last two characters are the port number. Possible modes are:
             Enabled: Enable DHCP relay information mode operation.
                      When DHCP relay information mode operation is enabled,
                      the agent inserts specific information (option 82) into a DHCP message when forwarding
                      to DHCP server and removes it from a DHCP message when transferring to DHCP client.
                      It only works when DHCP relay operation mode is enabled.
             Disabled: Disable DHCP relay information mode operation."
        ::= { iDHCP 6 }

    -- 1.3.6.1.4.1.4756.108.40.2.4.7    
    iDhcpRelayInformationPolicy OBJECT-TYPE
        SYNTAX      INTEGER {
                        replace(1),
                        keep(2),
                        drop(3)
                    }
        MAX-ACCESS  read-write
        STATUS      current
        DESCRIPTION
            "Indicates the DHCP relay information option policy.
             When DHCP relay information mode operation is enabled,
             if agent receives a DHCP message that already contains
             relay agent information it will enforce the policy.
             And it only works under DHCP if relay information operation mode is enabled.
             Possible policies are:
             Replace:Replace the original relay information when a DHCP message that already contains it is received.
             Keep:Keep the original relay information when a DHCP message that already contains it is received.
             Drop:Drop the package when a DHCP message that already contains relay information is received."
        ::= { iDHCP 7 }

    -- 1.3.6.1.4.1.4756.108.40.2.4.9
    iDhcpRelayStatisticsClear OBJECT-TYPE
        SYNTAX      INTEGER {
                        trigger(1),
                        normal(2)
                    }
        MAX-ACCESS  read-write
        STATUS      current
        DESCRIPTION
            "Clear all statistics."
        ::= { iDHCP 9 }

    -- 1.3.6.1.4.1.4756.108.40.2.4.10
    iDhcpRelayServerStatistics OBJECT IDENTIFIER ::= { iDHCP 10 }

    -- 1.3.6.1.4.1.4756.108.40.2.4.10.1
    iDhcpRelayServerTxToServer OBJECT-TYPE
        SYNTAX      Counter32
        UNITS       "Packets"
        MAX-ACCESS  read-only
        STATUS      current
        DESCRIPTION
            "The number of packets that are relayed from client to server."
        ::= { iDhcpRelayServerStatistics 1 }

    -- 1.3.6.1.4.1.4756.108.40.2.4.10.2
    iDhcpRelayServerTxError OBJECT-TYPE
        SYNTAX      Counter32
        UNITS       "Packets"
        MAX-ACCESS  read-only
        STATUS      current
        DESCRIPTION
            "The number of packets that resulted in errors while being sent to clients."
        ::= { iDhcpRelayServerStatistics 2 }

    -- 1.3.6.1.4.1.4756.108.40.2.4.10.3
    iDhcpRelayServerRxFromServer OBJECT-TYPE
        SYNTAX      Counter32
        UNITS       "Packets"
        MAX-ACCESS  read-only
        STATUS      current
        DESCRIPTION
            "The number of packets received from server."
        ::= { iDhcpRelayServerStatistics 3 }

    -- 1.3.6.1.4.1.4756.108.40.2.4.10.4
    iDhcpRelayServerRxMissingAgentOption OBJECT-TYPE
        SYNTAX      Counter32
        UNITS       "Packets"
        MAX-ACCESS  read-only
        STATUS      current
        DESCRIPTION
            "The number of packets received without agent information options."
        ::= { iDhcpRelayServerStatistics 4 }

    -- 1.3.6.1.4.1.4756.108.40.2.4.10.5
    iDhcpRelayServerRxMissingCircuitID OBJECT-TYPE
        SYNTAX      Counter32
        UNITS       "Packets"
        MAX-ACCESS  read-only
        STATUS      current
        DESCRIPTION
            "The number of packets received with the Circuit ID option missing."
        ::= { iDhcpRelayServerStatistics 5 }

    -- 1.3.6.1.4.1.4756.108.40.2.4.10.6
    iDhcpRelayServerRxMissingRemoteID OBJECT-TYPE
        SYNTAX      Counter32
        UNITS       "Packets"
        MAX-ACCESS  read-only
        STATUS      current
        DESCRIPTION
            "The number of packets received with the Remote ID option missing."
        ::= { iDhcpRelayServerStatistics 6 }

    -- 1.3.6.1.4.1.4756.108.40.2.4.10.7
    iDhcpRelayServerRxBadCircuitID OBJECT-TYPE
        SYNTAX      Counter32
        UNITS       "Packets"
        MAX-ACCESS  read-only
        STATUS      current
        DESCRIPTION
            "The number of packets whose Circuit ID option did not match known circuit ID."
        ::= { iDhcpRelayServerStatistics 7 }

    -- 1.3.6.1.4.1.4756.108.40.2.4.10.8
    iDhcpRelayServerRxBadRemoteID OBJECT-TYPE
        SYNTAX      Counter32
        UNITS       "Packets"
        MAX-ACCESS  read-only
        STATUS      current
        DESCRIPTION
            "The number of packets whose Remote ID option did not match known Remote ID."
        ::= { iDhcpRelayServerStatistics 8 }

    -- 1.3.6.1.4.1.4756.108.40.2.4.11
    iDhcpRelayClientStatistics OBJECT IDENTIFIER ::= { iDHCP 11 }

    -- 1.3.6.1.4.1.4756.108.40.2.4.11.1
    iDhcpRelayClientTxToClient OBJECT-TYPE
        SYNTAX      Counter32
        UNITS       "Packets"
        MAX-ACCESS  read-only
        STATUS      current
        DESCRIPTION
            "The number of relayed packets from server to client."
        ::= { iDhcpRelayClientStatistics 1 }

    -- 1.3.6.1.4.1.4756.108.40.2.4.11.2
    iDhcpRelayClientTxError OBJECT-TYPE
        SYNTAX      Counter32
        UNITS       "Packets"
        MAX-ACCESS  read-only
        STATUS      current
        DESCRIPTION
            "The number of packets that resulted in error while being sent to servers."
        ::= { iDhcpRelayClientStatistics 2 }

    -- 1.3.6.1.4.1.4756.108.40.2.4.11.3
    iDhcpRelayClientRxFromClient OBJECT-TYPE
        SYNTAX      Counter32
        UNITS       "Packets"
        MAX-ACCESS  read-only
        STATUS      current
        DESCRIPTION
            "The number of received packets from server."
        ::= { iDhcpRelayClientStatistics 3 }

    -- 1.3.6.1.4.1.4756.108.40.2.4.11.4
     iDhcpRelayClientRxAgentOption OBJECT-TYPE
        SYNTAX      Counter32
        UNITS       "Packets"
        MAX-ACCESS  read-only
        STATUS      current
        DESCRIPTION
            "The number of received packets with relay agent information option."
        ::= { iDhcpRelayClientStatistics 4 }

    -- 1.3.6.1.4.1.4756.108.40.2.4.11.5
    iDhcpRelayClientReplaceAgentOption OBJECT-TYPE
        SYNTAX      Counter32
        UNITS       "Packets"
        MAX-ACCESS  read-only
        STATUS      current
        DESCRIPTION
            "The number of packets which were replaced with relay agent information option."
        ::= { iDhcpRelayClientStatistics 5 }

    -- 1.3.6.1.4.1.4756.108.40.2.4.11.6
    iDhcpRelayClientKeepAgentOption OBJECT-TYPE
        SYNTAX      Counter32
        UNITS       "Packets"
        MAX-ACCESS  read-only
        STATUS      current
        DESCRIPTION
            "The number of packets whose relay agent information was retained."
        ::= { iDhcpRelayClientStatistics 6 }

    -- 1.3.6.1.4.1.4756.108.40.2.4.11.7
    iDhcpRelayClientDropAgentOption OBJECT-TYPE
        SYNTAX      Counter32
        UNITS       "Packets"
        MAX-ACCESS  read-only
        STATUS      current
        DESCRIPTION
            "The number of packets that were dropped which were received with relay agent information."
        ::= { iDhcpRelayClientStatistics 7 }


    
    -- 1.3.6.1.4.1.4756.108.40.2.5
    iIpSourceGuard OBJECT IDENTIFIER ::= { iSecurityNetwork 5 }

    -- 1.3.6.1.4.1.4756.108.40.2.5.1    
    iIpSourceGuardMode OBJECT-TYPE
        SYNTAX      INTEGER {
                        enabled(1),
                        disabled(2)
                    }
        MAX-ACCESS  read-write
        STATUS      current
        DESCRIPTION
            "Enable the Global IP Source Guard or disable the Global IP Source Guard."
        ::= { iIpSourceGuard 1 }

    -- 1.3.6.1.4.1.4756.108.40.2.5.2    
    iIpTranslateDynamicToStatic OBJECT-TYPE
        SYNTAX      INTEGER {
                        trigger(1),
                        normal(2)
                    }
        MAX-ACCESS  read-write
        STATUS      current
        DESCRIPTION
            "To translate all dynamic IP Source Guard entries to static entries."
        ::= { iIpSourceGuard 2 }

    -- 1.3.6.1.4.1.4756.108.40.2.5.3
    iIpSourceGuardPortConfigTable OBJECT-TYPE
        SYNTAX      SEQUENCE OF IIpSourceGuardPortConfigEntry
        MAX-ACCESS  not-accessible
        STATUS      current
        DESCRIPTION
            "This table provides IP Source Guard port configuration."
        ::= { iIpSourceGuard 3 }

    -- 1.3.6.1.4.1.4756.108.40.2.5.3.1
    iIpSourceGuardPortConfigEntry OBJECT-TYPE
        SYNTAX      IIpSourceGuardPortConfigEntry
        MAX-ACCESS  not-accessible
        STATUS      current
        DESCRIPTION
            "The Entry of IP Source Guard ports."
        INDEX { iPortIndex }
        ::= { iIpSourceGuardPortConfigTable 1 }

    IIpSourceGuardPortConfigEntry ::=
        SEQUENCE {
            iIpSourceGuardPortMode             INTEGER,
            iIpSourceGuardMaxDynamicClients    INTEGER
        }

        -- 1.3.6.1.4.1.4756.108.40.2.5.3.1.1
        iIpSourceGuardPortMode OBJECT-TYPE
            SYNTAX      INTEGER {
                            enable(1),
                            disable(2)
                        }
            MAX-ACCESS  read-write
            STATUS      current
            DESCRIPTION
                "Specify IP Source Guard is enabled on which ports.
                 Only when both Global Mode and Port Mode on a given port are enabled,
                 IP Source Guard is enabled on this given port."
            ::= { iIpSourceGuardPortConfigEntry 1 }

        -- 1.3.6.1.4.1.4756.108.40.2.5.3.1.2
        iIpSourceGuardMaxDynamicClients OBJECT-TYPE
            SYNTAX      INTEGER {
                            unlimited(1),
                            limited0(2),
                            limited1(3),
                            limited2(4)
                        }
            MAX-ACCESS  read-write
            STATUS      current
            DESCRIPTION
                "Specify the maximum number of dynamic clients that can be learned on given port.
                 This value can be 0, 1, 2 or unlimited.
                 If the port mode is enabled and the value of max dynamic client is equal to 0,
                 it means only allow the IP packets forwarding that are matched in static entries
                 on the specific port."
            ::= { iIpSourceGuardPortConfigEntry 2 }

    -- 1.3.6.1.4.1.4756.108.40.2.5.4
    iAddStaticIpSourceGuard OBJECT-TYPE
        SYNTAX      DisplayString
        MAX-ACCESS  read-write
        STATUS      current
        DESCRIPTION                                  
            "Add a new entry to the Static IP Source Guard table.
             Specify the Port, VLAN ID, IP address, and MAC address for the new entry.
             Syntax: <port_no> <vid> <allowed_ip> <allowed_mac> 
             The Static ARP Inspection table can support maximum 64 entries per port."
        ::= { iIpSourceGuard 4 }

    -- 1.3.6.1.4.1.4756.108.40.2.5.5
    iDeleteStaticIpSourceGuard OBJECT-TYPE
        SYNTAX      DisplayString
        MAX-ACCESS  read-write
        STATUS      current
        DESCRIPTION
            "Delete a Static IP Source Guard from table.
             Syntax: <port_no> <vid> <allowed_ip> <allowed_mac>"
        ::= { iIpSourceGuard 5 }

    -- 1.3.6.1.4.1.4756.108.40.2.5.6
    iStaticIpSourceGuardTable OBJECT-TYPE
        SYNTAX      SEQUENCE OF IStaticIpSourceGuardEntry
        MAX-ACCESS  not-accessible
        STATUS      current
        DESCRIPTION
            "This table provides Static IP Source Guard status."
        ::= { iIpSourceGuard 6 }

    -- 1.3.6.1.4.1.4756.108.40.2.5.6.1
    iStaticIpSourceGuardEntry OBJECT-TYPE
        SYNTAX      IStaticIpSourceGuardEntry
        MAX-ACCESS  not-accessible
        STATUS      current
        DESCRIPTION
            "The Entry of Static IP Source Guard."
        INDEX { iStaticIpSourceGuardIndex }
        ::= { iStaticIpSourceGuardTable 1 }

    IStaticIpSourceGuardEntry ::=
        SEQUENCE {
            iStaticIpSourceGuardIndex      Integer32,
            iStaticIpSourceGuardPort       Integer32,
            iStaticIpSourceGuardVlanID     Integer32,
            iStaticIpSourceGuardIP         IpAddress,
            iStaticIpSourceGuardMAC        MacAddress                
        }

        -- 1.3.6.1.4.1.4756.108.40.2.5.6.1.1
        iStaticIpSourceGuardIndex OBJECT-TYPE
            SYNTAX      Integer32 (1..112)
            MAX-ACCESS  read-only
            STATUS      current
            DESCRIPTION
                "The index of Static IP Source Guard entries."
            ::= { iStaticIpSourceGuardEntry 1 }

        -- 1.3.6.1.4.1.4756.108.40.2.5.6.1.2
        iStaticIpSourceGuardPort OBJECT-TYPE
            SYNTAX      Integer32 (1..11)
            MAX-ACCESS  read-only
            STATUS      current
            DESCRIPTION
                "The logical port number of the entry."
            ::= { iStaticIpSourceGuardEntry 2 }

        -- 1.3.6.1.4.1.4756.108.40.2.5.6.1.3
        iStaticIpSourceGuardVlanID OBJECT-TYPE
            SYNTAX      Integer32 (1..4095)
            MAX-ACCESS  read-only
            STATUS      current
            DESCRIPTION
                "The VLAN ID of the entry."
            ::= { iStaticIpSourceGuardEntry 3 }

        -- 1.3.6.1.4.1.4756.108.40.2.5.6.1.4
        iStaticIpSourceGuardIP OBJECT-TYPE
            SYNTAX      IpAddress
            MAX-ACCESS  read-only
            STATUS      current
            DESCRIPTION
                "Allowed Source IP address."
            ::= { iStaticIpSourceGuardEntry 4 }

        -- 1.3.6.1.4.1.4756.108.40.2.5.6.1.5
        iStaticIpSourceGuardMAC OBJECT-TYPE
            SYNTAX      MacAddress
            MAX-ACCESS  read-only
            STATUS      current
            DESCRIPTION
                "Allowed Source MAC address."
            ::= { iStaticIpSourceGuardEntry 5 }

    -- 1.3.6.1.4.1.4756.108.40.2.5.6
    iDynamicIpSourceGuardTable OBJECT-TYPE
        SYNTAX      SEQUENCE OF IDynamicIpSourceGuardEntry
        MAX-ACCESS  not-accessible
        STATUS      current
        DESCRIPTION
            "This table provides Dynamic IP Source Guard status."
        ::= { iIpSourceGuard 7 }

    -- 1.3.6.1.4.1.4756.108.40.2.5.7.1
    iDynamicIpSourceGuardEntry OBJECT-TYPE
        SYNTAX      IDynamicIpSourceGuardEntry
        MAX-ACCESS  not-accessible
        STATUS      current
        DESCRIPTION
            "The Entry of Dynamic IP Source Guard."
        INDEX { iDynamicIpSourceGuardIndex }
        ::= { iDynamicIpSourceGuardTable 1 }

    IDynamicIpSourceGuardEntry ::=
        SEQUENCE {
            iDynamicIpSourceGuardIndex     Integer32,
            iDynamicIpSourceGuardPort      Integer32,
            iDynamicIpSourceGuardVlanID    Integer32,
            iDynamicIpSourceGuardIP        IpAddress,
            iDynamicIpSourceGuardMAC       MacAddress   
        }

        -- 1.3.6.1.4.1.4756.108.40.2.5.7.1.1
        iDynamicIpSourceGuardIndex OBJECT-TYPE
            SYNTAX      Integer32 (1..112)
            MAX-ACCESS  read-only
            STATUS      current
            DESCRIPTION
                "The index of Dynamic IP Source Guard entries."
            ::= { iDynamicIpSourceGuardEntry 1 }

        -- 1.3.6.1.4.1.4756.108.40.2.5.7.1.2
        iDynamicIpSourceGuardPort OBJECT-TYPE
            SYNTAX      Integer32 (1..11)
            MAX-ACCESS  read-only
            STATUS      current
            DESCRIPTION
                "The logical port number of the entry."
            ::= { iDynamicIpSourceGuardEntry 2 }

        -- 1.3.6.1.4.1.4756.108.40.2.5.7.1.3
        iDynamicIpSourceGuardVlanID OBJECT-TYPE
            SYNTAX      Integer32 (1..4095)
            MAX-ACCESS  read-only
            STATUS      current
            DESCRIPTION
                "The VLAN ID the IP traffic is permitted."
            ::= { iDynamicIpSourceGuardEntry 3 }

        -- 1.3.6.1.4.1.4756.108.40.2.5.7.1.4
        iDynamicIpSourceGuardIP OBJECT-TYPE
            SYNTAX      IpAddress
            MAX-ACCESS  read-only
            STATUS      current
            DESCRIPTION
                "User IP address of the entry."
            ::= { iDynamicIpSourceGuardEntry 4 }

        -- 1.3.6.1.4.1.4756.108.40.2.5.7.1.5
        iDynamicIpSourceGuardMAC OBJECT-TYPE
            SYNTAX      MacAddress
            MAX-ACCESS  read-only
            STATUS      current
            DESCRIPTION
                "User MAC address of the entry."
            ::= { iDynamicIpSourceGuardEntry 5 }

    
    -- 1.3.6.1.4.1.4756.108.40.2.6
    iArpInspection OBJECT IDENTIFIER ::= { iSecurityNetwork 6 }

    -- 1.3.6.1.4.1.4756.108.40.2.6.1    
    iArpInspectionMode OBJECT-TYPE
        SYNTAX      INTEGER {
                        enabled(1),
                        disabled(2)
                    }
        MAX-ACCESS  read-write
        STATUS      current
        DESCRIPTION
            "Enable the Global ARP Inspection or disable the Global ARP Inspection."
        ::= { iArpInspection 1 }

    -- 1.3.6.1.4.1.4756.108.40.2.6.2    
    iArpTranslateDynamicToStatic OBJECT-TYPE
        SYNTAX      INTEGER {
                        trigger(1),
                        normal(2)
                    }
        MAX-ACCESS  read-write
        STATUS      current
        DESCRIPTION
            "To translate all dynamic entries to static entries."
        ::= { iArpInspection 2 }

    -- 1.3.6.1.4.1.4756.108.40.2.6.3
    iArpInspectionPortConfigTable OBJECT-TYPE
        SYNTAX      SEQUENCE OF IArpInspectionPortConfigEntry
        MAX-ACCESS  not-accessible
        STATUS      current
        DESCRIPTION
            "This table provides ARP Inspection port configuration."
        ::= { iArpInspection 3 }

    -- 1.3.6.1.4.1.4756.108.40.2.6.3.1
    iArpInspectionPortConfigEntry OBJECT-TYPE
        SYNTAX      IArpInspectionPortConfigEntry
        MAX-ACCESS  not-accessible
        STATUS      current
        DESCRIPTION
            "The Entry of ARP Inspection ports."
        INDEX { iPortIndex }
        ::= { iArpInspectionPortConfigTable 1 }

    IArpInspectionPortConfigEntry ::=
        SEQUENCE {
            iArpInspectionPortMode         INTEGER,    
            iArpInspectionCheckVLAN        INTEGER,
            iArpInspectionLogType         INTEGER
        }

        -- 1.3.6.1.4.1.4756.108.40.2.6.3.1.1
        iArpInspectionPortMode OBJECT-TYPE
            SYNTAX      INTEGER {
                            enable(1),
                            disable(2)
                        }
            MAX-ACCESS  read-write
            STATUS      current
            DESCRIPTION
                "Specify ARP Inspection is enabled on this port.
                 Only when both Global Mode and Port Mode on a given port are enabled,
                 ARP Inspection is enabled on this given port."
            ::= { iArpInspectionPortConfigEntry 1 }
        
        -- 1.3.6.1.4.1.4756.108.40.2.6.3.1.2
        iArpInspectionCheckVLAN OBJECT-TYPE
            SYNTAX      INTEGER {
                            enable(1),
                            disable(2)
                        }
            MAX-ACCESS  read-write
            STATUS      current
            DESCRIPTION
                "If you want to inspect the VLAN configuration, you have to enable the setting of 'Check VLAN'. 
                 The default setting of 'Check VLAN' is disabled. 
                 When the setting of 'Check VLAN' is disabled, the log type of ARP Inspection will refer to the port setting. 
                 And the setting of 'Check VLAN' is enabled, the log type of ARP Inspection will refer to the VLAN setting. 
                 Possible setting of 'Check VLAN' are: 
					Enabled: Enable check VLAN operation. 
					Disabled: Disable check VLAN operation. 
				"
            ::= { iArpInspectionPortConfigEntry 2 }

		-- 1.3.6.1.4.1.4756.108.40.2.6.3.1.3
        iArpInspectionLogType OBJECT-TYPE
            SYNTAX      INTEGER {
                            none(1),
                            deny(2),
                            permit(3),
                            all(4)
                        }
            MAX-ACCESS  read-write
            STATUS      current
            DESCRIPTION
                "Only the Global Mode and Port Mode on a given port are enabled, and the setting of 'Check VLAN' is disabled, the log type of ARP Inspection will refer to the port setting. There are four log types and possible types are: 
					None: Log nothing. 
					Deny: Log denied entries. 
					Permit: Log permitted entries. 
					ALL: Log all entries. 
				"
            ::= { iArpInspectionPortConfigEntry 3 }
	
	-- 1.3.6.1.4.1.4756.108.40.2.6.4
    iAddArpInspectionVLANConfiguration  OBJECT-TYPE
        SYNTAX      DisplayString
        MAX-ACCESS  read-write
        STATUS      current
        DESCRIPTION                                  
            "Add a new VLAN to the ARP Inspection VLAN table
             Syntax: <vid> <[none|deny|permit|all]>
            "
        ::= { iArpInspection 4 }

    -- 1.3.6.1.4.1.4756.108.40.2.6.5
    iDeleteArpInspectionVLANConfiguration OBJECT-TYPE
        SYNTAX      DisplayString
        MAX-ACCESS  read-write
        STATUS      current
        DESCRIPTION
            "Delete a VLAN to the ARP Inspection VLAN table
             Syntax: <vid>
            "
        ::= { iArpInspection 5 }
	
	-- 1.3.6.1.4.1.4756.108.40.2.6.6
    iArpInspectionVLANConfigTable OBJECT-TYPE
        SYNTAX      SEQUENCE OF IArpInspectionVLANConfigEntry
        MAX-ACCESS  not-accessible
        STATUS      current
        DESCRIPTION
            "This table provides ARP Inspection VLAN Configuration table."
        ::= { iArpInspection 6 }

    -- 1.3.6.1.4.1.4756.108.40.2.6.6.1
    iArpInspectionVLANConfigEntry OBJECT-TYPE
        SYNTAX      IArpInspectionVLANConfigEntry
        MAX-ACCESS  not-accessible
        STATUS      current
        DESCRIPTION
            "The Entry of Static ARP Inspection."
        INDEX { iArpInspectionVLANID }
        ::= { iArpInspectionVLANConfigTable 1 }

    IArpInspectionVLANConfigEntry ::=
        SEQUENCE {
            iArpInspectionVLANID  		  Integer32,
            iArpInspectionVLANLogType     INTEGER
        }
    
        -- 1.3.6.1.4.1.4756.108.40.2.6.6.1
        iArpInspectionVLANID OBJECT-TYPE
        SYNTAX      Integer32 (1..4095)
        MAX-ACCESS  read-only
        STATUS      current
        DESCRIPTION                                  
            "Show the setting VLAN ID"
        ::= { iArpInspectionVLANConfigEntry 1 }
        
        -- 1.3.6.1.4.1.4756.108.40.2.6.6.2
        iArpInspectionVLANLogType OBJECT-TYPE
        SYNTAX      INTEGER {
        			         none(1),
        			         deny(2),
        			         permit(3),
        			         all(4)
        			}
        MAX-ACCESS  read-only
        STATUS      current
        DESCRIPTION                                  
            "Specify ARP Inspection is enabled on which VLANs. 
             First, you have to enable the port setting on Port mode configuration web page. 
             Only when both Global Mode and Port Mode on a given port are enabled, ARP Inspection is enabled on this given port. 
             Second, you can specify which VLAN will be inspected on VLAN mode configuration web page. 
             The log type also can be configured on per VLAN setting. 
			 Possible types are: 
			 None: Log nothing. 
			 Deny: Log denied entries. 
			 Permit: Log permitted entries. 
			 ALL: Log all entries. 
			"
        ::= { iArpInspectionVLANConfigEntry 2 }
	
    -- 1.3.6.1.4.1.4756.108.40.2.6.7
    iAddStaticArpInspection OBJECT-TYPE
        SYNTAX      DisplayString
        MAX-ACCESS  read-write
        STATUS      current
        DESCRIPTION                                  
            "Add a new entry to the Static ARP Inspection table.
             Specify the Port, VLAN ID, MAC address, and IP address for the new entry.
             Syntax: <port_no> <vid> <allowed_mac> <allowed_ip> 
             The Static ARP Inspection table can support maximum 64 entries per port."
        ::= { iArpInspection 7 }

    -- 1.3.6.1.4.1.4756.108.40.2.6.8
    iDeleteStaticArpInspection OBJECT-TYPE
        SYNTAX      DisplayString
        MAX-ACCESS  read-write
        STATUS      current
        DESCRIPTION
            "Delete a Static ARP Inspection from table.
             Syntax: <port_no> <vid> <allowed_mac> <allowed_ip>"
        ::= { iArpInspection 8 }

    -- 1.3.6.1.4.1.4756.108.40.2.6.9
    iStaticArpInspectionTable OBJECT-TYPE
        SYNTAX      SEQUENCE OF IStaticArpInspectionEntry
        MAX-ACCESS  not-accessible
        STATUS      current
        DESCRIPTION
            "This table provides Static ARP Inspection status."
        ::= { iArpInspection 9 }

    -- 1.3.6.1.4.1.4756.108.40.2.6.9.1
    iStaticArpInspectionEntry OBJECT-TYPE
        SYNTAX      IStaticArpInspectionEntry
        MAX-ACCESS  not-accessible
        STATUS      current
        DESCRIPTION
            "The Entry of Static ARP Inspection."
        INDEX { iStaticArpInspectionIndex }
        ::= { iStaticArpInspectionTable 1 }

    IStaticArpInspectionEntry ::=
        SEQUENCE {
            iStaticArpInspectionIndex      Integer32,
            iStaticArpInspectionPort       Integer32,
            iStaticArpInspectionVlanID     Integer32,
            iStaticArpInspectionMAC        MacAddress,
            iStaticArpInspectionIP         IpAddress    
        }

        -- 1.3.6.1.4.1.4756.108.40.2.6.9.1.1
        iStaticArpInspectionIndex OBJECT-TYPE
            SYNTAX      Integer32 (1..256)
            MAX-ACCESS  read-only
            STATUS      current
            DESCRIPTION
                "The index of Static ARP Inspection entries."
            ::= { iStaticArpInspectionEntry 1 }

        -- 1.3.6.1.4.1.4756.108.40.2.6.9.1.2
        iStaticArpInspectionPort OBJECT-TYPE
            SYNTAX      Integer32 (1..11)
            MAX-ACCESS  read-only
            STATUS      current
            DESCRIPTION
                "The logical port number of the entry."
            ::= { iStaticArpInspectionEntry 2 }

        -- 1.3.6.1.4.1.4756.108.40.2.6.9.1.3
        iStaticArpInspectionVlanID OBJECT-TYPE
            SYNTAX      Integer32 (1..4095)
            MAX-ACCESS  read-only
            STATUS      current
            DESCRIPTION
                "The VLAN ID of the entry."
            ::= { iStaticArpInspectionEntry 3 }

        -- 1.3.6.1.4.1.4756.108.40.2.6.9.1.4
        iStaticArpInspectionMAC OBJECT-TYPE
            SYNTAX      MacAddress
            MAX-ACCESS  read-only
            STATUS      current
            DESCRIPTION
                "Allowed Source MAC address in ARP request packets."
            ::= { iStaticArpInspectionEntry 4 }

        -- 1.3.6.1.4.1.4756.108.40.2.6.9.1.5
        iStaticArpInspectionIP OBJECT-TYPE
            SYNTAX      IpAddress
            MAX-ACCESS  read-only
            STATUS      current
            DESCRIPTION
                "Allowed Source IP address in ARP request packets."
            ::= { iStaticArpInspectionEntry 5 }

    -- 1.3.6.1.4.1.4756.108.40.2.6.10
    iDynamicArpInspectionTable OBJECT-TYPE
        SYNTAX      SEQUENCE OF IDynamicArpInspectionEntry
        MAX-ACCESS  not-accessible
        STATUS      current
        DESCRIPTION
            "This table provides Dynamic ARP Inspection status."
        ::= { iArpInspection 10 }

    -- 1.3.6.1.4.1.4756.108.40.2.6.10.1
    iDynamicArpInspectionEntry OBJECT-TYPE
        SYNTAX      IDynamicArpInspectionEntry
        MAX-ACCESS  not-accessible
        STATUS      current
        DESCRIPTION
            "The Entry of Dynamic ARP Inspection."
        INDEX { iDynamicArpInspectionIndex }
        ::= { iDynamicArpInspectionTable 1 }

    IDynamicArpInspectionEntry ::=
        SEQUENCE {
            iDynamicArpInspectionIndex     Integer32,
            iDynamicArpInspectionPort      Integer32,
            iDynamicArpInspectionVlanID    Integer32,
            iDynamicArpInspectionMAC       MacAddress,
            iDynamicArpInspectionIP        IpAddress    
        }

        -- 1.3.6.1.4.1.4756.108.40.2.6.10.1.1
        iDynamicArpInspectionIndex OBJECT-TYPE
            SYNTAX      Integer32 (1..256)
            MAX-ACCESS  read-only
            STATUS      current
            DESCRIPTION
                "The index of Dynamic ARP Inspection entries."
            ::= { iDynamicArpInspectionEntry 1 }

        -- 1.3.6.1.4.1.4756.108.40.2.6.10.1.2
        iDynamicArpInspectionPort OBJECT-TYPE
            SYNTAX      Integer32 (1..11)
            MAX-ACCESS  read-only
            STATUS      current
            DESCRIPTION
                "The logical port number of the entry."
            ::= { iDynamicArpInspectionEntry 2 }

        -- 1.3.6.1.4.1.4756.108.40.2.6.10.1.3
        iDynamicArpInspectionVlanID OBJECT-TYPE
            SYNTAX      Integer32 (1..4095)
            MAX-ACCESS  read-only
            STATUS      current
            DESCRIPTION
                "The VLAN ID in which the ARP traffic is permitted."
            ::= { iDynamicArpInspectionEntry 3 }

        -- 1.3.6.1.4.1.4756.108.40.2.6.10.1.4
        iDynamicArpInspectionMAC OBJECT-TYPE
            SYNTAX      MacAddress
            MAX-ACCESS  read-only
            STATUS      current
            DESCRIPTION
                "User MAC address of the entry."
            ::= { iDynamicArpInspectionEntry 4 }

        -- 1.3.6.1.4.1.4756.108.40.2.6.10.1.5
        iDynamicArpInspectionIP OBJECT-TYPE
            SYNTAX      IpAddress
            MAX-ACCESS  read-only
            STATUS      current
            DESCRIPTION
                "User IP address of the entry."
            ::= { iDynamicArpInspectionEntry 5 }


-- 1.3.6.1.4.1.4756.108.40.3
    iSecurityRADIUS OBJECT IDENTIFIER ::= { iSecurity 3 }

    -- 1.3.6.1.4.1.4756.108.40.3.1    
    iServerTimeout OBJECT-TYPE
        SYNTAX      Integer32 (1..1000)
        UNITS       "Seconds"
        MAX-ACCESS  read-write
        STATUS      current
        DESCRIPTION
            "Timeout is the number of seconds, in the range 1 to 1000, to wait for a reply from a RADIUS server before retransmitting the request."
        ::= { iSecurityRADIUS 1 }

    -- 1.3.6.1.4.1.4756.108.40.3.2    
    iServerRetransmit OBJECT-TYPE
        SYNTAX      Integer32 (1..1000)
        UNITS       "Seconds"
        MAX-ACCESS  read-write
        STATUS      current
        DESCRIPTION
            "Retransmit is the number of times, in the range 1 to 1000, a RADIUS request is retransmitted to a server that is not responding. 
             If the server has not responded after the last retransmit it is considered to be dead. "
        ::= { iSecurityRADIUS 2 }
    
    -- 1.3.6.1.4.1.4756.108.40.3.10
    iServerDeadTime OBJECT-TYPE
        SYNTAX      Integer32 (0..1440)
        UNITS       "Seconds"
        MAX-ACCESS  read-write
        STATUS      current
        DESCRIPTION
            "Deadtime, which can be set to a number between 0 to 1440 minutes, is the period during which the switch will not send new requests to a server that has failed to respond to a previous request. 
            This will stop the switch from continually trying to contact a server that it has already determined as dead.
						 Setting the Deadtime to a value greater than 0 (zero) will enable this feature, but only if more than one server has been configured. 
					  "
        ::= { iSecurityRADIUS 3 }
    
    -- 1.3.6.1.4.1.4756.108.40.3.4
    iServerKey OBJECT-TYPE
            SYNTAX      DisplayString
            MAX-ACCESS  read-write
            STATUS      current
            DESCRIPTION 
           	    "The secret key - up to 63 characters long - shared between the RADIUS server and the switch."
        ::= { iSecurityRADIUS 4 }
    
    -- 1.3.6.1.4.1.4756.108.40.3.12
    iServerNasIpAddress OBJECT-TYPE
            SYNTAX      DisplayString    
            MAX-ACCESS  read-write
            STATUS      current
            DESCRIPTION
            "The IPv4 address to be used as attribute 4 in RADIUS Access-Request packets. 
             If this field is left blank, the IP address of the outgoing interface is used."
        ::= { iSecurityRADIUS 5 }
    
    -- 1.3.6.1.4.1.4756.108.40.3.6
    iServerNasIPv6Address OBJECT-TYPE
            SYNTAX      DisplayString
            MAX-ACCESS  read-write
            STATUS      current
            DESCRIPTION
            "The IPv6 address to be used as attribute 95 in RADIUS Access-Request packets. 
             If this field is left blank, the IP address of the outgoing interface is used. "
        ::= { iSecurityRADIUS 6 }
    
    -- 1.3.6.1.4.1.4756.108.40.3.7
    iServerNasIdentifier OBJECT-TYPE
            SYNTAX      DisplayString    
            MAX-ACCESS  read-write
            STATUS      current
            DESCRIPTION
            "The identifier - up to 255 characters long - to be used as attribute 32 in RADIUS Access-Request packets. 
            If this field is left blank, the NAS-Identifier is not included in the packet."
        ::= { iSecurityRADIUS 7 }
        
    -- 1.3.6.1.4.1.4756.108.40.3.8
    iAddRadiusServer OBJECT-TYPE
            SYNTAX      DisplayString
            MAX-ACCESS  read-write
            STATUS      current
            DESCRIPTION 
           	    "Add a new RADIUS server. An empty row is added to the table, and the RADIUS server can be configured as needed. 
           	     Up to 5 servers are supported.
           	     Syntax: <ip_addr_string> [<auth_port>] [<acct_port>] [<timeout>] [<retransmit>] [<key>] 
           	    "
        ::= { iSecurityRADIUS 8 }

		-- 1.3.6.1.4.1.4756.108.40.3.9
    iDeleteRadiusServer OBJECT-TYPE
            SYNTAX      DisplayString
            MAX-ACCESS  read-write
            STATUS      current
            DESCRIPTION 
           	    "Delete can be used to undo the addition of the new server.
           	     Syntax: <ip_addr_string> [<auth_port>] [<acct_port>]
           	    "
        ::= { iSecurityRADIUS 9 }

    -- 1.3.6.1.4.1.4756.108.40.3.10
    iAuthServerConfigTable OBJECT-TYPE
        SYNTAX      SEQUENCE OF IAuthServerConfigEntry
        MAX-ACCESS  not-accessible
        STATUS      current
        DESCRIPTION
            "The table allows you to configure the Authentication Servers."
        ::= { iSecurityRADIUS 10 }

    -- 1.3.6.1.4.1.4756.108.40.3.10.1
    iAuthServerConfigEntry OBJECT-TYPE
        SYNTAX      IAuthServerConfigEntry
        MAX-ACCESS  not-accessible
        STATUS      current
        DESCRIPTION
            "The Entry of the Authentication Server configuration."
        INDEX { iRadiusServerIndex }
        ::= { iAuthServerConfigTable 1 }

    IAuthServerConfigEntry ::=
        SEQUENCE {
            iRadiusServerIndex             Integer32,
            iRadiusServerHostname      	   DisplayString,
            iRadiusAuthServerPort          Integer32,
            iRadiusAccountingServerPort    Integer32,
            iRadiusServerTimeout    	   Integer32,
            iRadiusServerRetransmit    	   Integer32,
            iRadiusAuthkey                 DisplayString
        }

        -- 1.3.6.1.4.1.4756.108.40.3.10.1.1
        iRadiusServerIndex OBJECT-TYPE
            SYNTAX      Integer32 (1..5)
            MAX-ACCESS  read-only
            STATUS      current
            DESCRIPTION
                "The RADIUS Server number index."
            ::= { iAuthServerConfigEntry 1 }

        -- 1.3.6.1.4.1.4756.108.40.3.10.1.2
        iRadiusServerHostname OBJECT-TYPE
            SYNTAX      DisplayString
            MAX-ACCESS  read-only
            STATUS      current
            DESCRIPTION
                "The IP address or hostname of the RADIUS server."
            ::= { iAuthServerConfigEntry 2 }

        -- 1.3.6.1.4.1.4756.108.40.3.10.1.3
        iRadiusAuthServerPort OBJECT-TYPE
            SYNTAX      Integer32 (0..65535)
            MAX-ACCESS  read-only
            STATUS      current
            DESCRIPTION
                "The UDP port to use on the RADIUS Authentication Server.
                 If the port is set to 0(zero),
                 the default port(1812) is used on the RADIUS Authentication Server."
            ::= { iAuthServerConfigEntry 3 }        

        -- 1.3.6.1.4.1.4756.108.40.3.10.1.4
        iRadiusAccountingServerPort OBJECT-TYPE
            SYNTAX      Integer32 (0..65535)
            MAX-ACCESS  read-only
            STATUS      current
            DESCRIPTION
                "The UDP port to use on the RADIUS Accounting Server.
                 If the port is set to 0(zero),
                 the default port(1813) is used on the RADIUS Accounting Server."
            ::= { iAuthServerConfigEntry 4 }

		-- 1.3.6.1.4.1.4756.108.40.3.10.1.5
		iRadiusServerTimeout 	OBJECT-TYPE
            SYNTAX      Integer32 (1..1000)
            MAX-ACCESS  read-write
            STATUS      current
            DESCRIPTION
                "This optional setting overrides the global timeout value. Leaving it blank will use the global timeout value."
            ::= { iAuthServerConfigEntry 5 }
        
        -- 1.3.6.1.4.1.4756.108.40.3.10.1.6
        iRadiusServerRetransmit 	OBJECT-TYPE
            SYNTAX      Integer32 (0..1440)
            MAX-ACCESS  read-write
            STATUS      current
            DESCRIPTION
                "This optional setting overrides the global retransmit value. Leaving it blank will use the global retransmit value."
            ::= { iAuthServerConfigEntry 6 }    
            
        -- 1.3.6.1.4.1.4756.108.40.3.10.1.7
        iRadiusAuthkey OBJECT-TYPE
            SYNTAX      DisplayString
            MAX-ACCESS  read-write
            STATUS      current
            DESCRIPTION
                "This optional setting overrides the global key. Leaving it blank will use the global key."
            ::= { iAuthServerConfigEntry 7 }


    -- 1.3.6.1.4.1.4756.108.40.3.11
    iRadiusServerStatusTable OBJECT-TYPE
        SYNTAX      SEQUENCE OF IRadiusServerStatusEntry
        MAX-ACCESS  not-accessible
        STATUS      current
        DESCRIPTION
            "This table provides the status of the RADIUS servers."
        ::= { iSecurityRADIUS 11 }

    -- 1.3.6.1.4.1.4756.108.40.3.11.1
    iRadiusServerStatusEntry OBJECT-TYPE
        SYNTAX      IRadiusServerStatusEntry
        MAX-ACCESS  not-accessible
        STATUS      current
        DESCRIPTION
            "The Entry of RADIUS Server status."
        INDEX { iRadiusServerIndex }
        ::= { iRadiusServerStatusTable 1 }

    IRadiusServerStatusEntry ::=
        SEQUENCE {
            iRadiusAuthIpAddress           DisplayString,
            iRadiusAuthState               INTEGER,
            iRadiusAccountingIpAddress     DisplayString,
            iRadiusAccountingState         INTEGER
        }

        -- 1.3.6.1.4.1.4756.108.40.3.11.1.1
        iRadiusAuthIpAddress OBJECT-TYPE
            SYNTAX      DisplayString
            MAX-ACCESS  read-only
            STATUS      current
            DESCRIPTION
                "The IP address of the RADIUS Authentication server."
            ::= { iRadiusServerStatusEntry 1 }

        -- 1.3.6.1.4.1.4756.108.40.3.11.1.2
        iRadiusAuthState OBJECT-TYPE
            SYNTAX      INTEGER {
                            disabled(1),
                            notReady(2),
                            ready(3),
                            dead(4)
                        }
            MAX-ACCESS  read-only
            STATUS      current
            DESCRIPTION
                "The current state of the server. This node takes one of the following values:
                 Disabled: The server is disabled.
                 Not Ready: The server is enabled, but IP communication is not yet up and running.
                 Ready: The server is enabled, IP communication is up and running,
                        and the RADIUS module is ready to accept access attempts.
                 Dead: Access attempts were made to this server,
                       but it did not reply within the configured timeout.
                       The server has temporarily been disabled,
                       but will get re-enabled when the dead-time expires.
                       The number of seconds left before this occurs is displayed in parentheses.
                       This state is only reachable when more than one server is enabled."
            ::= { iRadiusServerStatusEntry 2 }        

        -- 1.3.6.1.4.1.4756.108.40.3.11.1.3
        iRadiusAccountingIpAddress OBJECT-TYPE
            SYNTAX      DisplayString
            MAX-ACCESS  read-only
            STATUS      current
            DESCRIPTION
                "The IP address of the RADIUS Accounting server."
            ::= { iRadiusServerStatusEntry 3 }

        -- 1.3.6.1.4.1.4756.108.40.3.11.1.4
        iRadiusAccountingState OBJECT-TYPE
            SYNTAX      INTEGER {
                            disabled(1),
                            notReady(2),
                            ready(3),
                            dead(4)
                        }
            MAX-ACCESS  read-only
            STATUS      current
            DESCRIPTION
                "The current state of the server. This node takes one of the following values:
                 Disabled: The server is disabled.
                 Not Ready: The server is enabled, but IP communication is not yet up and running.
                 Ready: The server is enabled, IP communication is up and running,
                        and the RADIUS module is ready to accept access attempts.
                 Dead: Access attempts were made to this server,
                       but it did not reply within the configured timeout.
                       The server has temporarily been disabled,
                       but will get re-enabled when the dead-time expires.
                       The number of seconds left before this occurs is displayed in parentheses.
                       This state is only reachable when more than one server is enabled."
            ::= { iRadiusServerStatusEntry 4 }
        

    -- 1.3.6.1.4.1.4756.108.40.3.12
    iRadiusAuthStatisticsTable OBJECT-TYPE
        SYNTAX      SEQUENCE OF IRadiusAuthStatisticsEntry
        MAX-ACCESS  not-accessible
        STATUS      current
        DESCRIPTION
            "This table provides the status of the RADIUS servers."
        ::= { iSecurityRADIUS 12 }

    -- 1.3.6.1.4.1.4756.108.40.3.12.1
    iRadiusAuthStatisticsEntry OBJECT-TYPE
        SYNTAX      IRadiusAuthStatisticsEntry
        MAX-ACCESS  not-accessible
        STATUS      current
        DESCRIPTION
            "The Entry of RADIUS Authentication Server status."
        INDEX { iRadiusServerIndex }
        ::= { iRadiusAuthStatisticsTable 1 }

    IRadiusAuthStatisticsEntry ::=
        SEQUENCE {
            iRadiusStatisticsClear                  INTEGER,
            iRadiusAuthRxAccessAccepts              Counter32,
            iRadiusAuthRxAccessRejects              Counter32,
            iRadiusAuthRxAccessChallenges           Counter32,
            iRadiusAuthRxMalformedAccessRespones    Counter32,
            iRadiusAuthRxBadAuthentications         Counter32,
            iRadiusAuthRxUnknowTypes                Counter32,
            iRadiusAuthRxDroppeds                   Counter32,
            iRadiusAuthTxAccessRequests             Counter32,
            iRadiusAuthTxAccessRetransmissions      Counter32,
            iRadiusAuthTxPendingRequests            Counter32,
            iRadiusAuthTxTimeouts                   Counter32,
            iRadiusAuthOtherInfoIPAddress		    DisplayString,
            iRadiusAuthOtherInfoStatus				INTEGER,
            iRadiusAuthOtherInfoRoundTripTime		DisplayString,
            iRadiusAccountingRxResponses            Counter32,
            iRadiusAccountingRxMalformedResponses   Counter32,
            iRadiusAccountingRxBadAuthentications   Counter32,
            iRadiusAccountingRxUnknowTypes          Counter32,
            iRadiusAccountingRxDroppeds             Counter32,
            iRadiusAccountingTxRequests             Counter32,
            iRadiusAccountingTxRetransmissions      Counter32,
            iRadiusAccountingTxPendingRequests      Counter32,
            iRadiusAccountingTxTimeouts            	Counter32,
            iRadiusAccountingOtherInfoIPAddress			DisplayString,
            iRadiusAccountingOtherInfoStatus				INTEGER,
            iRadiusAccountingOtherInfoRoundTripTime	DisplayString
        }

        -- 1.3.6.1.4.1.4756.108.40.3.12.1.1
        iRadiusStatisticsClear OBJECT-TYPE
            SYNTAX      INTEGER {
                            trigger(1),
                            normal(2)
                        }
            MAX-ACCESS  read-write
            STATUS      current
            DESCRIPTION
                "Clears the counters for all ports."
            ::= { iRadiusAuthStatisticsEntry 1 }

        -- 1.3.6.1.4.1.4756.108.40.3.12.1.2
        iRadiusAuthRxAccessAccepts OBJECT-TYPE
            SYNTAX      Counter32
            UNITS       "Packets"
            MAX-ACCESS  read-only
            STATUS      current
            DESCRIPTION
                "The number of RADIUS Access-Accept packets(valid or invalid) received from the server."
            ::= { iRadiusAuthStatisticsEntry 2 }

        -- 1.3.6.1.4.1.4756.108.40.3.12.1.3
        iRadiusAuthRxAccessRejects OBJECT-TYPE
            SYNTAX      Counter32
            UNITS       "Packets"
            MAX-ACCESS  read-only
            STATUS      current
            DESCRIPTION
                "The number of RADIUS Access-Reject packets(valid or invalid) received from the server."
            ::= { iRadiusAuthStatisticsEntry 3 }

        -- 1.3.6.1.4.1.4756.108.40.3.12.1.4
        iRadiusAuthRxAccessChallenges OBJECT-TYPE
            SYNTAX      Counter32
            UNITS       "Packets"
            MAX-ACCESS  read-only
            STATUS      current
            DESCRIPTION
                "The number of RADIUS Access-Challenge packets(valid or invalid) received from the server."
            ::= { iRadiusAuthStatisticsEntry 4 }

        -- 1.3.6.1.4.1.4756.108.40.3.12.1.5
        iRadiusAuthRxMalformedAccessRespones OBJECT-TYPE
            SYNTAX      Counter32
            UNITS       "Packets"
            MAX-ACCESS  read-only
            STATUS      current
            DESCRIPTION
                "The number of malformed RADIUS Access-Response packets received from the server.
                 Malformed packets include packets with an invalid length.
                 Bad authenticators or Message Authenticator attributes or
                 unknown types are not included as malformed access responses."
            ::= { iRadiusAuthStatisticsEntry 5 }

        -- 1.3.6.1.4.1.4756.108.40.3.12.1.6
        iRadiusAuthRxBadAuthentications OBJECT-TYPE
            SYNTAX      Counter32
            UNITS       "Packets"
            MAX-ACCESS  read-only
            STATUS      current
            DESCRIPTION
                "The number of RADIUS Access-Response packets containing invalid authenticators or
                 Message Authenticator attributes received from the server."
            ::= { iRadiusAuthStatisticsEntry 6 }

        -- 1.3.6.1.4.1.4756.108.40.3.12.1.7
        iRadiusAuthRxUnknowTypes OBJECT-TYPE
            SYNTAX      Counter32
            UNITS       "Packets"
            MAX-ACCESS  read-only
            STATUS      current
            DESCRIPTION
                "The number of RADIUS packets that were received with unknown types from
                 the server on the authentication port and dropped."
            ::= { iRadiusAuthStatisticsEntry 7 }

        -- 1.3.6.1.4.1.4756.108.40.3.12.1.8
        iRadiusAuthRxDroppeds OBJECT-TYPE
            SYNTAX      Counter32
            UNITS       "Packets"
            MAX-ACCESS  read-only
            STATUS      current
            DESCRIPTION
                "The number of RADIUS packets that were received from the server on
                 the authentication port and dropped for some other reason."
            ::= { iRadiusAuthStatisticsEntry 8 }

        -- 1.3.6.1.4.1.4756.108.40.3.12.1.9
        iRadiusAuthTxAccessRequests OBJECT-TYPE
            SYNTAX      Counter32
            UNITS       "Packets"
            MAX-ACCESS  read-only
            STATUS      current
            DESCRIPTION
                "The number of RADIUS Access-Request packets sent to the server.
                 This does not include retransmissions."
            ::= { iRadiusAuthStatisticsEntry 9 }

        -- 1.3.6.1.4.1.4756.108.40.3.12.1.10
        iRadiusAuthTxAccessRetransmissions OBJECT-TYPE
            SYNTAX      Counter32
            UNITS       "Packets"
            MAX-ACCESS  read-only
            STATUS      current
            DESCRIPTION
                "The number of RADIUS Access-Request packets retransmitted to
                 the RADIUS authentication server."
            ::= { iRadiusAuthStatisticsEntry 10 }

        -- 1.3.6.1.4.1.4756.108.40.3.12.1.11
        iRadiusAuthTxPendingRequests OBJECT-TYPE
            SYNTAX      Counter32
            UNITS       "Packets"
            MAX-ACCESS  read-only
            STATUS      current
            DESCRIPTION
                "The number of RADIUS Access-Request packets destined for the server
                 that have not yet timed out or received a response.
                 This variable is incremented when an Access-Request is sent and decremented due to
                 receipt of an Access-Accept, Access-Reject, Access-Challenge, timeout, or retransmission."
            ::= { iRadiusAuthStatisticsEntry 11 }

        -- 1.3.6.1.4.1.4756.108.40.3.12.1.12
        iRadiusAuthTxTimeouts OBJECT-TYPE
            SYNTAX      Counter32
            UNITS       "Packets"
            MAX-ACCESS  read-only
            STATUS      current
            DESCRIPTION
                "The number of authentication timeouts to the server. After a timeout,
                 the client may retry to the same server, send to a different server, or give up.
                 A retry to the same server is counted as a retransmit as well as a timeout.
                 A send to a different server is counted as a Request as well as a timeout."
            ::= { iRadiusAuthStatisticsEntry 12 }

				 -- 1.3.6.1.4.1.4756.108.40.3.12.1.13
        iRadiusAuthOtherInfoIPAddress OBJECT-TYPE
            SYNTAX      DisplayString
            MAX-ACCESS  read-only
            STATUS      current
            DESCRIPTION
                "The IP address of the RADIUS Authentication server."
            ::= { iRadiusAuthStatisticsEntry 13 }

        -- 1.3.6.1.4.1.4756.108.40.3.12.1.14
        iRadiusAuthOtherInfoStatus OBJECT-TYPE
            SYNTAX      INTEGER {
                            disabled(1),
                            notReady(2),
                            ready(3),
                            dead(4)
                        }
            MAX-ACCESS  read-only
            STATUS      current
            DESCRIPTION
                "The current state of the server. This node takes one of the following values:
                 Disabled: The server is disabled.
                 Not Ready: The server is enabled, but IP communication is not yet up and running.
                 Ready: The server is enabled, IP communication is up and running,
                        and the RADIUS module is ready to accept access attempts.
                 Dead: Access attempts were made to this server,
                       but it did not reply within the configured timeout.
                       The server has temporarily been disabled,
                       but will get re-enabled when the dead-time expires.
                       The number of seconds left before this occurs is displayed in parentheses.
                       This state is only reachable when more than one server is enabled."
            ::= { iRadiusAuthStatisticsEntry 14 }
				
				 -- 1.3.6.1.4.1.4756.108.40.3.12.1.15
        iRadiusAuthOtherInfoRoundTripTime OBJECT-TYPE
            SYNTAX      DisplayString
            MAX-ACCESS  read-only
            STATUS      current
            DESCRIPTION
                "The time interval (measured in milliseconds) between the most recent Access-Reply/Access-Challenge and the Access-Request that matched it from the RADIUS authentication server. 
                 The granularity of this measurement is 100 ms. A value of 0 ms indicates that there hasn't been round-trip communication with the server yet. "
            ::= { iRadiusAuthStatisticsEntry 15 }

        -- 1.3.6.1.4.1.4756.108.40.3.12.1.16
        iRadiusAccountingRxResponses OBJECT-TYPE
            SYNTAX      Counter32
            UNITS       "Packets"
            MAX-ACCESS  read-only
            STATUS      current
            DESCRIPTION
                "The number of RADIUS packets(valid or invalid) received from the server."
            ::= { iRadiusAuthStatisticsEntry 16 }

        -- 1.3.6.1.4.1.4756.108.40.3.12.1.17
        iRadiusAccountingRxMalformedResponses OBJECT-TYPE
            SYNTAX      Counter32
            UNITS       "Packets"
            MAX-ACCESS  read-only
            STATUS      current
            DESCRIPTION
                "The number of malformed RADIUS packets received from the server.
                 Malformed packets include packets with an invalid length.
                 Bad authenticators or unknown types are not included as malformed access responses."
            ::= { iRadiusAuthStatisticsEntry 17 }

        -- 1.3.6.1.4.1.4756.108.40.3.12.1.18
        iRadiusAccountingRxBadAuthentications OBJECT-TYPE
            SYNTAX      Counter32
            UNITS       "Packets"
            MAX-ACCESS  read-only
            STATUS      current
            DESCRIPTION
                "The number of RADIUS packets containing invalid authenticators received from the server."
            ::= { iRadiusAuthStatisticsEntry 18 }

        -- 1.3.6.1.4.1.4756.108.40.3.12.1.19
        iRadiusAccountingRxUnknowTypes OBJECT-TYPE
            SYNTAX      Counter32
            UNITS       "Packets"
            MAX-ACCESS  read-only
            STATUS      current
            DESCRIPTION
                "The number of RADIUS packets of unknown types that were received from
                 the server on the accounting port."
            ::= { iRadiusAuthStatisticsEntry 19 }

        -- 1.3.6.1.4.1.4756.108.40.3.12.1.20
        iRadiusAccountingRxDroppeds OBJECT-TYPE
            SYNTAX      Counter32
            UNITS       "Packets"
            MAX-ACCESS  read-only
            STATUS      current
            DESCRIPTION
                "The number of RADIUS packets that were received from the server on
                 the accounting port and dropped for some other reason."
            ::= { iRadiusAuthStatisticsEntry 20 }

        -- 1.3.6.1.4.1.4756.108.40.3.12.1.21
        iRadiusAccountingTxRequests OBJECT-TYPE
            SYNTAX      Counter32
            UNITS       "Packets"
            MAX-ACCESS  read-only
            STATUS      current
            DESCRIPTION
                "The number of RADIUS packets sent to the server.
                 This does not include retransmissions."
            ::= { iRadiusAuthStatisticsEntry 21 }

        -- 1.3.6.1.4.1.4756.108.40.3.12.1.22
        iRadiusAccountingTxRetransmissions OBJECT-TYPE
            SYNTAX      Counter32
            UNITS       "Packets"
            MAX-ACCESS  read-only
            STATUS      current
            DESCRIPTION
                "The number of RADIUS packets retransmitted to the RADIUS accounting server."
            ::= { iRadiusAuthStatisticsEntry 22 }

        -- 1.3.6.1.4.1.4756.108.40.3.12.1.23
        iRadiusAccountingTxPendingRequests OBJECT-TYPE
            SYNTAX      Counter32
            UNITS       "Packets"
            MAX-ACCESS  read-only
            STATUS      current
            DESCRIPTION
                "The number of RADIUS packets destined for the server
                 that have not yet timed out or received a response.
                 This variable is incremented when a Request is sent and decremented due to
                 receipt of a Response, timeout, or retransmission."
            ::= { iRadiusAuthStatisticsEntry 23 }

        -- 1.3.6.1.4.1.4756.108.40.3.12.1.24
        iRadiusAccountingTxTimeouts OBJECT-TYPE
            SYNTAX      Counter32
            UNITS       "Packets"
            MAX-ACCESS  read-only
            STATUS      current
            DESCRIPTION
                "The number of accounting timeouts to the server. After a timeout,
                 the client may retry to the same server, send to a different server, or give up.
                 A retry to the same server is counted as a retransmit as well as a timeout.
                 A send to a different server is counted as a Request as well as a timeout."
            ::= { iRadiusAuthStatisticsEntry 24 }
        
        -- 1.3.6.1.4.1.4756.108.40.3.12.1.25
        iRadiusAccountingOtherInfoIPAddress OBJECT-TYPE
            SYNTAX      DisplayString
            MAX-ACCESS  read-only
            STATUS      current
            DESCRIPTION
                "IP address and UDP port for the accounting server in question."
            ::= { iRadiusAuthStatisticsEntry 25 }

        -- 1.3.6.1.4.1.4756.108.40.3.12.1.26
        iRadiusAccountingOtherInfoStatus OBJECT-TYPE
            SYNTAX      INTEGER {
                            disabled(1),
                            notReady(2),
                            ready(3),
                            dead(4)
                        }
            MAX-ACCESS  read-only
            STATUS      current
            DESCRIPTION
                "The current state of the server. This node takes one of the following values:
                 Disabled: The server is disabled.
                 Not Ready: The server is enabled, but IP communication is not yet up and running.
                 Ready: The server is enabled, IP communication is up and running,
                        and the RADIUS module is ready to accept access attempts.
                 Dead: Access attempts were made to this server,
                       but it did not reply within the configured timeout.
                       The server has temporarily been disabled,
                       but will get re-enabled when the dead-time expires.
                       The number of seconds left before this occurs is displayed in parentheses.
                       This state is only reachable when more than one server is enabled."
            ::= { iRadiusAuthStatisticsEntry 26 }
				
				 -- 1.3.6.1.4.1.4756.108.40.3.12.1.27
        iRadiusAccountingOtherInfoRoundTripTime OBJECT-TYPE
            SYNTAX      DisplayString
            MAX-ACCESS  read-only
            STATUS      current
            DESCRIPTION
                "The time interval (measured in milliseconds) between the most recent Response and the Request that matched it from the RADIUS accounting server. 
                 The granularity of this measurement is 100 ms. A value of 0 ms indicates that there hasn't been round-trip communication with the server yet. "
            ::= { iRadiusAuthStatisticsEntry 27 }
       
    -- 1.3.6.1.4.1.4756.108.40.3.13    
    iTACACSPlusGlobalTimeout OBJECT-TYPE
        SYNTAX      Integer32 (1..1000)
        UNITS       "Seconds"
        MAX-ACCESS  read-write
        STATUS      current
        DESCRIPTION
            "Timeout is the number of seconds, in the range 1 to 1000, to wait for a reply from a TACACS+ server before it is considered to be dead."
        ::= { iSecurityRADIUS 13 }

    
    -- 1.3.6.1.4.1.4756.108.40.3.14
    iTACACSPlusGlobalDeadTime OBJECT-TYPE
        SYNTAX      Integer32 (0..1440)
        UNITS       "Seconds"
        MAX-ACCESS  read-write
        STATUS      current
        DESCRIPTION
            "Deadtime, which can be set to a number between 0 to 1440 minutes, is the period during which the switch will not send new requests to a server that has failed to respond to a previous request. This will stop the switch from continually trying to contact a server that it has already determined as dead.
						 Setting the Deadtime to a value greater than 0 (zero) will enable this feature, but only if more than one server has been configured."
        ::= { iSecurityRADIUS 14 }
    
    -- 1.3.6.1.4.1.4756.108.40.3.15
    iTACACSPlusGlobalKey OBJECT-TYPE
            SYNTAX      DisplayString
            MAX-ACCESS  read-write
            STATUS      current
            DESCRIPTION 
           	    "The secret key - up to 63 characters long - shared between the TACACS+ server and the switch."
        ::= { iSecurityRADIUS 15 }
            
    -- 1.3.6.1.4.1.4756.108.40.3.16
	iAddTACACSPlusServer OBJECT-TYPE
		SYNTAX      DisplayString
		MAX-ACCESS  read-write
		STATUS      current
		DESCRIPTION 
			"Add a new RADIUS server. An empty row is added to the table, and the RADIUS server can be configured as needed. 
		     Up to 5 servers are supported.
		     Syntax: <ip_addr_string> [<port>] [<timeout>] [<key>]"
        ::= { iSecurityRADIUS 16 }
		
	-- 1.3.6.1.4.1.4756.108.40.3.17
	iDeleteTACACSPlusServer OBJECT-TYPE
		SYNTAX      DisplayString
		MAX-ACCESS  read-write
		STATUS      current
		DESCRIPTION 
			"Delete can be used to undo the addition of the new server.
			 Syntax: <ip_addr_string> [<port>]
			"
	   ::= { iSecurityRADIUS 17 }
		   
		-- 1.3.6.1.4.1.4756.108.40.3.18
    iTACACSPlusServerConfigTable OBJECT-TYPE
        SYNTAX      SEQUENCE OF ITACACSPlusServerConfigEntry
        MAX-ACCESS  not-accessible
        STATUS      current
        DESCRIPTION
            "The table allows you to configure the Authentication Servers."
        ::= { iSecurityRADIUS 18 }

    -- 1.3.6.1.4.1.4756.108.40.3.18.1
    iTACACSPlusServerConfigEntry OBJECT-TYPE
        SYNTAX      ITACACSPlusServerConfigEntry
        MAX-ACCESS  not-accessible
        STATUS      current
        DESCRIPTION
            "The Entry of the TACACS+ Server configuration."
        INDEX { iRadiusServerIndex }
        ::= { iTACACSPlusServerConfigTable 1 }

    ITACACSPlusServerConfigEntry ::=
        SEQUENCE {
            iTACACSPlusServerHostname      DisplayString,
            iTACACSPlusServerPort          Integer32,
            iTACACSPlusServerTimeout       Integer32,
            iTACACSPlusKey                 DisplayString
        }
        
   			-- 1.3.6.1.4.1.4756.108.40.3.18.1.1
        iTACACSPlusServerHostname OBJECT-TYPE
            SYNTAX      DisplayString
            MAX-ACCESS  read-only
            STATUS      current
            DESCRIPTION
                "The IP address or hostname of the TACACS+ server."
            ::= { iTACACSPlusServerConfigEntry 1 }

        -- 1.3.6.1.4.1.4756.108.40.3.18.1.2
        iTACACSPlusServerPort OBJECT-TYPE
            SYNTAX      Integer32 (0..65535)
            MAX-ACCESS  read-only
            STATUS      current
            DESCRIPTION
                "The TCP port to use on the TACACS+ server for authentication."
            ::= { iTACACSPlusServerConfigEntry 2 }        

		-- 1.3.6.1.4.1.4756.108.40.3.18.1.3
		iTACACSPlusServerTimeout 	OBJECT-TYPE
            SYNTAX      Integer32 (1..1000)
            MAX-ACCESS  read-write
            STATUS      current
            DESCRIPTION
                "This optional setting overrides the global timeout value. Leaving it blank will use the global timeout value."
            ::= { iTACACSPlusServerConfigEntry 3 }
            
        -- 1.3.6.1.4.1.4756.108.40.3.18.1.4
        iTACACSPlusKey OBJECT-TYPE
            SYNTAX      DisplayString
            MAX-ACCESS  read-write
            STATUS      current
            DESCRIPTION
                "This optional setting overrides the global key. Leaving it blank will use the global key."
            ::= { iTACACSPlusServerConfigEntry 4 }

-- Link OAM
    -- 1.3.6.1.4.1.4756.108.45
    iLinkOAM OBJECT IDENTIFIER ::= { msw4424a 45 }
    



    -- 1.3.6.1.4.1.4756.136.50.20
    iLinkOAMStatisticsTable OBJECT-TYPE
        SYNTAX      SEQUENCE OF ILinkOAMStatisticsEntry
        MAX-ACCESS  not-accessible
        STATUS      current
        DESCRIPTION
            "This table shows current port configurations. Ports can also be configured here."
        ::= { iLinkOAM 4 }

    -- 1.3.6.1.4.1.4756.136.50.4.1
    iLinkOAMStatisticsEntry OBJECT-TYPE
        SYNTAX      ILinkOAMStatisticsEntry
        MAX-ACCESS  not-accessible
        STATUS      current
        DESCRIPTION
            "The entry of ports."
        INDEX { iPortIndex }
        ::= { iLinkOAMStatisticsTable 1 }

    ILinkOAMStatisticsEntry ::=
        SEQUENCE {
--        		iPortIndex			    Integer32,
        		iLinkOAMInformationTx              Counter32,
						iLinkOAMInformationRx              Counter32,
						iLinkOAMUniqueEventNotificationTx              Counter32,
						iLinkOAMUniqueEventNotificationRx              Counter32,
						iLinkOAMDuplicateEventNotificationTx              Counter32,
						iLinkOAMDuplicateEventNotificationRx              Counter32,
						iLinkOAMLoopbackControlTx              Counter32,
						iLinkOAMLoopbackControlRx              Counter32,
						iLinkOAMVariableRequestTx              Counter32,
						iLinkOAMVariableRequestRx              Counter32,
						iLinkOAMVariableResponseTx              Counter32,
						iLinkOAMVariableResponseRx              Counter32,
						iLinkOAMOrgSpecificTx              Counter32,
						iLinkOAMOrgSpecificRx              Counter32,
						iLinkOAMUnsupportedCodesTx              Counter32,
						iLinkOAMUnsupportedCodesRx              Counter32,
						iLinkOAMLinkFaultTx              Counter32,
						iLinkOAMLinkFaultRx              Counter32,
						iLinkOAMUDyingGaspTx              Counter32,
						iLinkOAMUDyingGaspRx              Counter32,
						iLinkOAMCriticalEventTx              Counter32,
						iLinkOAMCriticalEventRx              Counter32      		

        }
    
    	-- 1.3.6.1.4.1.4756.136.50.4.1.1
--        iPortIndex OBJECT-TYPE
--            SYNTAX      Integer32 (1..29)
--            MAX-ACCESS  read-only
--            STATUS      current
--            DESCRIPTION
--                "
--                "
--            ::= { iLinkOAMStatisticsEntry 1 }
    
    	-- 1.3.6.1.4.1.4756.136.50.4.1.2
        iLinkOAMInformationTx OBJECT-TYPE
            SYNTAX      Counter32
            MAX-ACCESS  read-only
            STATUS      current
            DESCRIPTION
                "."
            ::= { iLinkOAMStatisticsEntry 2 }

    	-- 1.3.6.1.4.1.4756.136.50.4.1.3
        iLinkOAMInformationRx OBJECT-TYPE
            SYNTAX      Counter32
            MAX-ACCESS  read-only
            STATUS      current
            DESCRIPTION
                "."
            ::= { iLinkOAMStatisticsEntry 3 }

    	-- 1.3.6.1.4.1.4756.136.50.4.1.4
        iLinkOAMUniqueEventNotificationTx OBJECT-TYPE
            SYNTAX      Counter32
            MAX-ACCESS  read-only
            STATUS      current
            DESCRIPTION
                "."
            ::= { iLinkOAMStatisticsEntry 4 }
            	
    	-- 1.3.6.1.4.1.4756.136.50.4.1.5
        iLinkOAMUniqueEventNotificationRx OBJECT-TYPE
            SYNTAX      Counter32
            MAX-ACCESS  read-only
            STATUS      current
            DESCRIPTION
                "."
            ::= { iLinkOAMStatisticsEntry 5 }
            	
    	-- 1.3.6.1.4.1.4756.136.50.4.1.6
        iLinkOAMDuplicateEventNotificationTx OBJECT-TYPE
            SYNTAX      Counter32
            MAX-ACCESS  read-only
            STATUS      current
            DESCRIPTION
                "."
            ::= { iLinkOAMStatisticsEntry 6 }
            	
    	-- 1.3.6.1.4.1.4756.136.50.4.1.7
        iLinkOAMDuplicateEventNotificationRx OBJECT-TYPE
            SYNTAX      Counter32
            MAX-ACCESS  read-only
            STATUS      current
            DESCRIPTION
                "."
            ::= { iLinkOAMStatisticsEntry 7 }
            	
    	-- 1.3.6.1.4.1.4756.136.50.4.1.8
        iLinkOAMLoopbackControlTx OBJECT-TYPE
            SYNTAX      Counter32
            MAX-ACCESS  read-only
            STATUS      current
            DESCRIPTION
                "."
            ::= { iLinkOAMStatisticsEntry 8 }
            	
    	-- 1.3.6.1.4.1.4756.136.50.4.1.9
        iLinkOAMLoopbackControlRx OBJECT-TYPE
            SYNTAX      Counter32
            MAX-ACCESS  read-only
            STATUS      current
            DESCRIPTION
                "."
            ::= { iLinkOAMStatisticsEntry 9 }
            	
    	-- 1.3.6.1.4.1.4756.136.50.4.1.10
        iLinkOAMVariableRequestTx OBJECT-TYPE
            SYNTAX      Counter32
            MAX-ACCESS  read-only
            STATUS      current
            DESCRIPTION
                "."
            ::= { iLinkOAMStatisticsEntry 10 }
            	
    	-- 1.3.6.1.4.1.4756.136.50.4.1.11
        iLinkOAMVariableRequestRx OBJECT-TYPE
            SYNTAX      Counter32
            MAX-ACCESS  read-only
            STATUS      current
            DESCRIPTION
                "."
            ::= { iLinkOAMStatisticsEntry 11 }
            	
    	-- 1.3.6.1.4.1.4756.136.50.4.1.12
        iLinkOAMVariableResponseTx OBJECT-TYPE
            SYNTAX      Counter32
            MAX-ACCESS  read-only
            STATUS      current
            DESCRIPTION
                "."
            ::= { iLinkOAMStatisticsEntry 12 }
            	
    	-- 1.3.6.1.4.1.4756.136.50.4.1.13
        iLinkOAMVariableResponseRx OBJECT-TYPE
            SYNTAX      Counter32
            MAX-ACCESS  read-only
            STATUS      current
            DESCRIPTION
                "."
            ::= { iLinkOAMStatisticsEntry 13 }
            	
    	-- 1.3.6.1.4.1.4756.136.50.4.1.14
        iLinkOAMOrgSpecificTx OBJECT-TYPE
            SYNTAX      Counter32
            MAX-ACCESS  read-only
            STATUS      current
            DESCRIPTION
                "."
            ::= { iLinkOAMStatisticsEntry 14 }
            	
    	-- 1.3.6.1.4.1.4756.136.50.4.1.15
        iLinkOAMOrgSpecificRx OBJECT-TYPE
            SYNTAX      Counter32
            MAX-ACCESS  read-only
            STATUS      current
            DESCRIPTION
                "."
            ::= { iLinkOAMStatisticsEntry 15 }
            	
    	-- 1.3.6.1.4.1.4756.136.50.4.1.16
        iLinkOAMUnsupportedCodesTx OBJECT-TYPE
            SYNTAX      Counter32
            MAX-ACCESS  read-only
            STATUS      current
            DESCRIPTION
                "."
            ::= { iLinkOAMStatisticsEntry 16 }
            	
    	-- 1.3.6.1.4.1.4756.136.50.4.1.17
        iLinkOAMUnsupportedCodesRx OBJECT-TYPE
            SYNTAX      Counter32
            MAX-ACCESS  read-only
            STATUS      current
            DESCRIPTION
                "."
            ::= { iLinkOAMStatisticsEntry 17 }
            	
    	-- 1.3.6.1.4.1.4756.136.50.4.1.18
        iLinkOAMLinkFaultTx OBJECT-TYPE
            SYNTAX      Counter32
            MAX-ACCESS  read-only
            STATUS      current
            DESCRIPTION
                "."
            ::= { iLinkOAMStatisticsEntry 18 }           
    	-- 1.3.6.1.4.1.4756.136.50.4.1.19
        iLinkOAMLinkFaultRx OBJECT-TYPE
            SYNTAX      Counter32
            MAX-ACCESS  read-only
            STATUS      current
            DESCRIPTION
                "."
            ::= { iLinkOAMStatisticsEntry 19 }
    	-- 1.3.6.1.4.1.4756.136.50.4.1.20
        iLinkOAMUDyingGaspTx OBJECT-TYPE
            SYNTAX      Counter32
            MAX-ACCESS  read-only
            STATUS      current
            DESCRIPTION
                "."
            ::= { iLinkOAMStatisticsEntry 20 }
    	-- 1.3.6.1.4.1.4756.136.50.4.1.21
        iLinkOAMUDyingGaspRx OBJECT-TYPE
            SYNTAX      Counter32
            MAX-ACCESS  read-only
            STATUS      current
            DESCRIPTION
                "."
            ::= { iLinkOAMStatisticsEntry 21 }
    	-- 1.3.6.1.4.1.4756.136.50.4.1.22
        iLinkOAMCriticalEventTx OBJECT-TYPE
            SYNTAX      Counter32
            MAX-ACCESS  read-only
            STATUS      current
            DESCRIPTION
                "."
            ::= { iLinkOAMStatisticsEntry 22 }
    	-- 1.3.6.1.4.1.4756.136.50.4.1.23
        iLinkOAMCriticalEventRx OBJECT-TYPE
            SYNTAX      Counter32
            MAX-ACCESS  read-only
            STATUS      current
            DESCRIPTION
                "."
            ::= { iLinkOAMStatisticsEntry 23 } 

-- Aggregation
    iAggregation  OBJECT IDENTIFIER ::= { msw4424a 50 }

    -- 1.3.6.1.4.1.4756.108.50.10.10
    iStaticAggregation  OBJECT IDENTIFIER ::= { iAggregation 10 }

    -- 1.3.6.1.4.1.4756.108.50.10.1    
    iAggrHashSA OBJECT-TYPE
        SYNTAX      TruthValue
        MAX-ACCESS  read-write
        STATUS      current
        DESCRIPTION
            "The number of received packets per queue."
        ::= { iStaticAggregation 1 }
 
    -- 1.3.6.1.4.1.4756.108.50.10.2    
    iAggrHashDA OBJECT-TYPE
        SYNTAX      TruthValue
        MAX-ACCESS  read-write
        STATUS      current
        DESCRIPTION
            "The number of received packets per queue."
        ::= { iStaticAggregation 2 }
 
    -- 1.3.6.1.4.1.4756.108.50.10.3    
    iAggrHashIP OBJECT-TYPE
        SYNTAX      TruthValue
        MAX-ACCESS  read-write
        STATUS      current
        DESCRIPTION
            "The number of received packets per queue."
        ::= { iStaticAggregation 3 }

    -- 1.3.6.1.4.1.4756.108.50.10.4    
    iAggrHashPortNumber OBJECT-TYPE
        SYNTAX      TruthValue
        MAX-ACCESS  read-write
        STATUS      current
        DESCRIPTION
            "The TCP/UDP port number can be used to calculate the destination port for the frame."
        DEFVAL      { true }
        ::= { iStaticAggregation 4 }

    -- 1.3.6.1.4.1.4756.108.50.10.5
    iAggrGroupTable OBJECT-TYPE
        SYNTAX      SEQUENCE OF IAggrGroupEntry
        MAX-ACCESS  not-accessible
        STATUS      current
        DESCRIPTION
            "This table is used to configure the aggregation group."
        ::= { iStaticAggregation 5 }

    -- 1.3.6.1.4.1.4756.108.50.10.5.1
    iAggrGroupEntry OBJECT-TYPE
        SYNTAX      IAggrGroupEntry
        MAX-ACCESS  not-accessible
        STATUS      current
        DESCRIPTION
            "The Entry of aggregation group configuration."
        INDEX { iAggrGroupID }
        ::= { iAggrGroupTable 1 }

    IAggrGroupEntry ::=
        SEQUENCE {
            iAggrGroupID       Integer32,
            iAggrMemberPort    DisplayString
        }

        -- 1.3.6.1.4.1.4756.108.50.10.5.1.1
        iAggrGroupID OBJECT-TYPE
            SYNTAX      Integer32 (1..3)
            MAX-ACCESS  read-only
            STATUS      current
            DESCRIPTION
                "Indicates the group ID for the settings contained in the same row.
                 Only one group ID is valid per port."
            ::= { iAggrGroupEntry 1 }

        -- 1.3.6.1.4.1.4756.108.50.10.5.1.2    
        iAggrMemberPort OBJECT-TYPE
            SYNTAX      DisplayString
            MAX-ACCESS  read-write
            STATUS      current
            DESCRIPTION
                "Each switch port is listed for each group ID.
                 Only full duplex ports can join an aggregation and ports must be in the same speed in each group,
                 Static aggregation and LACP can not both be enabled on the same ports,
                 Static aggregation can not be enabed on ports whose 802.1X Admin State is not Authorized"
            ::= { iAggrGroupEntry 2 }

-- LACP
    -- 1.3.6.1.4.1.4756.108.50.20
    iLACP OBJECT IDENTIFIER ::= { iAggregation 20 }
    
    -- 1.3.6.1.4.1.4756.108.50.20.1
    iLacpPortConfigTable OBJECT-TYPE
        SYNTAX      SEQUENCE OF ILacpPortConfigEntry
        MAX-ACCESS  not-accessible
        STATUS      current
        DESCRIPTION
            "This table provides LACP configurations for all ports."
        ::= { iLACP 1 }

    -- 1.3.6.1.4.1.4756.108.50.20.1.1
    iLacpPortConfigEntry OBJECT-TYPE
        SYNTAX      ILacpPortConfigEntry
        MAX-ACCESS  not-accessible
        STATUS      current
        DESCRIPTION
            "The Entry of LACP port configurations."
        INDEX { iPortIndex }
        ::= { iLacpPortConfigTable 1 }

    ILacpPortConfigEntry ::=
        SEQUENCE {
            iLacpPortEnabled      TruthValue,          
            iLacpKey              Integer32,
            iLacpRole             INTEGER,
            iLacpTimeout          INTEGER,
            iLacpPriority         Integer32
        }

        -- 1.3.6.1.4.1.4756.108.50.20.1.1.1    
        iLacpPortEnabled OBJECT-TYPE
            SYNTAX      TruthValue
            MAX-ACCESS  read-write
            STATUS      current
            DESCRIPTION
                "Controls whether LACP is enabled on this switch port.
                 LACP will form an aggregation when 2 or more ports are connected to the same partner."
            ::= { iLacpPortConfigEntry 1 }

        -- 1.3.6.1.4.1.4756.108.50.20.1.1.2    
        iLacpKey OBJECT-TYPE
            SYNTAX      Integer32 (0..65535)
            MAX-ACCESS  read-write
            STATUS      current
            DESCRIPTION
                "The Key value incurred by the port, range 0-65535.
                 The 0(Zero) setting will set the key as appropriate by the physical link speed, 10Mb = 1, 100Mb = 2, 1Gb = 3.
                 Ports with the same Key value can participate in the same aggregation group,
                 while ports with different keys cannot."
            ::= { iLacpPortConfigEntry 2 }
            
        -- 1.3.6.1.4.1.4756.108.50.20.1.1.3    
        iLacpRole OBJECT-TYPE
            SYNTAX      INTEGER {
                            active(1),
                            passive(2)
                        }
            MAX-ACCESS  read-write
            STATUS      current
            DESCRIPTION
                "The Active will transmit LACP packets each second,
                 while Passive will wait for a LACP packet from a partner (speak if spoken to)."
            ::= { iLacpPortConfigEntry 3 }
            
        -- 1.3.6.1.4.1.4756.108.50.20.1.1.4   
        iLacpTimeout OBJECT-TYPE
            SYNTAX      INTEGER {
                            slow(1),
                            fast(2)
                        }
            MAX-ACCESS  read-write
            STATUS      current
            DESCRIPTION
                "The Timeout controls the period between BPDU transmissions.
                 Fast will transmit LACP packets each second,
                 while Slow will wait for 30 seconds before sending a LACP packet."
            ::= { iLacpPortConfigEntry 4 }

        -- 1.3.6.1.4.1.4756.108.50.20.1.1.5   
        iLacpPriority OBJECT-TYPE
            SYNTAX      Integer32 (1..65535)
            MAX-ACCESS  read-write
            STATUS      current
            DESCRIPTION
                "The Prio controls the priority of the port.
                 If the LACP partner wants to form a larger group than is supported by this device then
                 this parameter will control which ports will be active and which ports will be in a backup role.
                 Lower number means greater priority."
            ::= { iLacpPortConfigEntry 5 }
   
    -- 1.3.6.1.4.1.4756.108.50.20.2
    iLacpSystemStatusTable OBJECT-TYPE
        SYNTAX      SEQUENCE OF ILacpSystemStatusEntry
        MAX-ACCESS  not-accessible
        STATUS      current
        DESCRIPTION
            "This table provides a status overview for all LACP instances."
        ::= { iLACP 2 }

    -- 1.3.6.1.4.1.4756.108.50.20.2.1
    iLacpSystemStatusEntry OBJECT-TYPE
        SYNTAX      ILacpSystemStatusEntry
        MAX-ACCESS  not-accessible
        STATUS      current
        DESCRIPTION
            "The Entry of LACP System Status."
        INDEX { iLacpAggrID }
        ::= { iLacpSystemStatusTable 1 }

    ILacpSystemStatusEntry ::=
        SEQUENCE {
        	iLacpAggrID				Integer32,
            iLacpPartnerSystemID      DisplayString,          
            iLacpPartnerKey           Integer32,
            iLacpPartnerSystemPrio    Integer32,
            iLacpLastChangedTime      DisplayString,
            iLacpLocalPorts           DisplayString
        }

        -- 1.3.6.1.4.1.4756.108.50.20.2.1.1
        iLacpAggrID OBJECT-TYPE
            SYNTAX      Integer32 (1..3)
            MAX-ACCESS  read-only
            STATUS      current
            DESCRIPTION
                "The Aggregation ID associated with this aggregation instance."
            ::= { iLacpSystemStatusEntry 1 }

        -- 1.3.6.1.4.1.4756.108.50.20.2.1.2
        iLacpPartnerSystemID OBJECT-TYPE
            SYNTAX      DisplayString
            MAX-ACCESS  read-only
            STATUS      current
            DESCRIPTION
                "The system ID (MAC address) of the aggregation partner. "
            ::= { iLacpSystemStatusEntry 2 }

        -- 1.3.6.1.4.1.4756.108.50.20.2.1.3    
        iLacpPartnerKey OBJECT-TYPE
            SYNTAX      Integer32 (0..65535)
            MAX-ACCESS  read-only
            STATUS      current
            DESCRIPTION
                "The Key that the partner has assigned to this aggregation ID. "
            ::= { iLacpSystemStatusEntry 3 }

        -- 1.3.6.1.4.1.4756.108.50.20.2.1.4   
        iLacpPartnerSystemPrio OBJECT-TYPE
            SYNTAX      Integer32 (1..65535)
            MAX-ACCESS  read-only
            STATUS      current
            DESCRIPTION
                "The Priority that the partner has assigned to the system."
            ::= { iLacpSystemStatusEntry 4 }

        -- 1.3.6.1.4.1.4756.108.50.20.2.1.5
        iLacpLastChangedTime OBJECT-TYPE
            SYNTAX      DisplayString
            MAX-ACCESS  read-only
            STATUS      current
            DESCRIPTION
                "The time since this aggregation changed."
            ::= { iLacpSystemStatusEntry 5 }

        -- 1.3.6.1.4.1.4756.108.50.20.2.1.6
        iLacpLocalPorts OBJECT-TYPE
            SYNTAX      DisplayString
            MAX-ACCESS  read-only
            STATUS      current
            DESCRIPTION
                "The ports are a part of this aggregation for this switch."
            ::= { iLacpSystemStatusEntry 6 }
   
    -- 1.3.6.1.4.1.4756.108.50.20.3
    iLacpPortStatusTable OBJECT-TYPE
        SYNTAX      SEQUENCE OF ILacpPortStatusEntry
        MAX-ACCESS  not-accessible
        STATUS      current
        DESCRIPTION
            "This table provides a status overview for LACP status for all ports."
        ::= { iLACP 3 }

    -- 1.3.6.1.4.1.4756.108.50.20.3.1
    iLacpPortStatusEntry OBJECT-TYPE
        SYNTAX      ILacpPortStatusEntry
        MAX-ACCESS  not-accessible
        STATUS      current
        DESCRIPTION
            "The Entry of LACP status for all ports."
        INDEX { iPortIndex }
        ::= { iLacpPortStatusTable 1 }

    ILacpPortStatusEntry ::=
        SEQUENCE {
        	iLacpPortEnabledState		    INTEGER,
            iLacpPortKeyState             Integer32,          
            iLacpPortAggrID           	Integer32,
            iLacpPortPartnerSystemID      DisplayString,
            iLacpPortPartnerPort      	Integer32,
            iLacpPortPartnerPriority      Integer32
        }

        -- 1.3.6.1.4.1.4756.108.50.20.3.1.1    
        iLacpPortEnabledState OBJECT-TYPE
            SYNTAX      INTEGER {
                            no(1),
                            yes(2),
                            standby(3)
                        }
            MAX-ACCESS  read-only
            STATUS      current
            DESCRIPTION
                "'Yes' means that LACP is enabled and the port link is up.
                 'No' means that LACP is not enabled or that the port link is down.
                 'Standby' means that the port could not join the aggregation group but will join if other port leaves.
                  Meanwhile it's LACP status is disabled."
            ::= { iLacpPortStatusEntry 1 }

        -- 1.3.6.1.4.1.4756.108.50.20.3.1.2    
        iLacpPortKeyState OBJECT-TYPE
            SYNTAX      Integer32 (0..65535)
            MAX-ACCESS  read-only
            STATUS      current
            DESCRIPTION
                "The key assigned to this port. Only ports with the same key can aggregate together."
            ::= { iLacpPortStatusEntry 2 }

        -- 1.3.6.1.4.1.4756.108.50.20.3.1.3
        iLacpPortAggrID OBJECT-TYPE
            SYNTAX      Integer32 (1..3)
            MAX-ACCESS  read-only
            STATUS      current
            DESCRIPTION
                "The Aggregation ID assigned to this aggregation group."
            ::= { iLacpPortStatusEntry 3 }

        -- 1.3.6.1.4.1.4756.108.50.20.3.1.4
        iLacpPortPartnerSystemID OBJECT-TYPE
            SYNTAX      DisplayString
            MAX-ACCESS  read-only
            STATUS      current
            DESCRIPTION
                "The partner's System ID (MAC address)."
            ::= { iLacpPortStatusEntry 4 }

        -- 1.3.6.1.4.1.4756.108.50.20.3.1.5
        iLacpPortPartnerPort OBJECT-TYPE
            SYNTAX      Integer32 (1..11)
            MAX-ACCESS  read-only
            STATUS      current
            DESCRIPTION
                "The partner's port number connected to this port."
            ::= { iLacpPortStatusEntry 5 }

        -- 1.3.6.1.4.1.4756.108.50.20.3.1.6    
        iLacpPortPartnerPriority OBJECT-TYPE
            SYNTAX      Integer32 (1..65535)
            MAX-ACCESS  read-only
            STATUS      current
            DESCRIPTION
                "The partner's port priority."
            ::= { iLacpPortStatusEntry 6 }

    -- 1.3.6.1.4.1.4756.108.50.20.4
    iLacpPortStatisticsClear OBJECT-TYPE
        SYNTAX      INTEGER {
                        trigger(1),
                        normal(2)
                    }
        MAX-ACCESS  read-write
        STATUS      current
        DESCRIPTION
            "Clears the counters for all ports."
        ::= { iLACP 4 }
   
    -- 1.3.6.1.4.1.4756.108.50.20.5
    iLacpPortStatisticsTable OBJECT-TYPE
        SYNTAX      SEQUENCE OF ILacpPortStatisticsEntry
        MAX-ACCESS  not-accessible
        STATUS      current
        DESCRIPTION
            "This table provides an overview for LACP statistics for all ports."
        ::= { iLACP 5 }

    -- 1.3.6.1.4.1.4756.108.50.20.5.1
    iLacpPortStatisticsEntry OBJECT-TYPE
        SYNTAX      ILacpPortStatisticsEntry
        MAX-ACCESS  not-accessible
        STATUS      current
        DESCRIPTION
            "The Entry of LACP statistics for all ports."
        INDEX { iPortIndex }
        ::= { iLacpPortStatisticsTable 1 }

    ILacpPortStatisticsEntry ::=
        SEQUENCE {
        	iLacpPortReceived		    	Counter32,
            iLacpPortTransmitted          Counter32,          
            iLacpPortUnknownDiscarded     Counter32,
            iLacpPortIllegalDiscarded     Counter32
        }

        -- 1.3.6.1.4.1.4756.108.50.20.5.1.1   
        iLacpPortReceived OBJECT-TYPE
            SYNTAX      Counter32
            MAX-ACCESS  read-only
            STATUS      current
            DESCRIPTION
                "Shows how many LACP frames have been received at each port."
            ::= { iLacpPortStatisticsEntry 1 }

        -- 1.3.6.1.4.1.4756.108.50.20.3.1.2    
        iLacpPortTransmitted OBJECT-TYPE
            SYNTAX      Counter32
            MAX-ACCESS  read-only
            STATUS      current
            DESCRIPTION
                "Shows how many LACP frames have been sent from each port. "
            ::= { iLacpPortStatisticsEntry 2 }

        -- 1.3.6.1.4.1.4756.108.50.20.3.1.3    
        iLacpPortUnknownDiscarded OBJECT-TYPE
            SYNTAX      Counter32
            MAX-ACCESS  read-only
            STATUS      current
            DESCRIPTION
                "Shows how many unknown frames have been discarded at each port. "
            ::= { iLacpPortStatisticsEntry 3 }

        -- 1.3.6.1.4.1.4756.108.50.20.3.1.4    
        iLacpPortIllegalDiscarded OBJECT-TYPE
            SYNTAX      Counter32
            MAX-ACCESS  read-only
            STATUS      current
            DESCRIPTION
                "Shows how illegal LACP frames have been discarded at each port. "
            ::= { iLacpPortStatisticsEntry 4 }
            
            
-- IPMC
    -- 1.3.6.1.4.1.4756.108.110
    iIPMC  OBJECT IDENTIFIER ::= { msw4424a 110 }

    -- 1.3.6.1.4.1.4756.108.110.1
    iIgmpSnooping  OBJECT IDENTIFIER ::= { iIPMC 1 }

    -- 1.3.6.1.4.1.4756.108.110.1.1
    iIgmpSnoopingEnabled OBJECT-TYPE
        SYNTAX      TruthValue
        MAX-ACCESS  read-write
        STATUS      current
        DESCRIPTION                                  
            "Enable the Global IGMP Snooping."
        ::= { iIgmpSnooping 1 }

    -- 1.3.6.1.4.1.4756.108.110.1.2
    iUnregisteredIpmcV4FloodingEnabled OBJECT-TYPE
        SYNTAX      TruthValue
        MAX-ACCESS  read-write
        STATUS      current
        DESCRIPTION                                  
            "Enable unregistered IPMC traffic flooding."
        ::= { iIgmpSnooping 2 }

    -- 1.3.6.1.4.1.4756.108.110.1.3
    iIgmpSsmRange OBJECT-TYPE
        SYNTAX      DisplayString
        MAX-ACCESS  read-write
        STATUS      current
        DESCRIPTION                                  
            "SSM (Source-Specific Multicast) Range allows the SSM-aware hosts and
             routers run the SSM service model for the groups in the address range.
             Syntax: (Range <mask_len>)"
        ::= { iIgmpSnooping 3 }

    -- 1.3.6.1.4.1.4756.108.110.1.4
    iIgmpLeaveProxyEnabled OBJECT-TYPE
        SYNTAX      TruthValue
        MAX-ACCESS  read-write
        STATUS      current
        DESCRIPTION                                  
            "Enable IGMP Leave Proxy.
             This feature can be used to avoid forwarding unnecessary leave messages to
             the router side."
        ::= { iIgmpSnooping 4 }

    -- 1.3.6.1.4.1.4756.108.110.1.5
    iIgmpProxyEnabled OBJECT-TYPE
        SYNTAX      TruthValue
        MAX-ACCESS  read-write
        STATUS      current
        DESCRIPTION                                  
            "Enable IGMP Proxy.
             This feature can be used to avoid forwarding unnecessary join and
             leave messages to the router side."
        ::= { iIgmpSnooping 5 }

    -- 1.3.6.1.4.1.4756.108.110.1.10
    iIgmpPortRelatedTable OBJECT-TYPE
        SYNTAX      SEQUENCE OF IIgmpPortRelatedEntry
        MAX-ACCESS  not-accessible
        STATUS      current
        DESCRIPTION
            "This table is used for configuring the Port Related."
        ::= { iIgmpSnooping 10 }

    -- 1.3.6.1.4.1.4756.108.110.1.10.1
    iIgmpPortRelatedEntry OBJECT-TYPE
        SYNTAX      IIgmpPortRelatedEntry
        MAX-ACCESS  not-accessible
        STATUS      current
        DESCRIPTION
            "The Entry of Port Related configurations."
        INDEX { iPortIndex }
        ::= { iIgmpPortRelatedTable 1 }

    IIgmpPortRelatedEntry ::=
        SEQUENCE {
            iIgmpRouterPortEnabled TruthValue,                
            iIgmpFastLeaveEnabled  TruthValue,
            iIgmpThrottling        Integer32
        }

        -- 1.3.6.1.4.1.4756.108.110.1.10.1.1    
        iIgmpRouterPortEnabled OBJECT-TYPE
            SYNTAX      TruthValue
            MAX-ACCESS  read-write
            STATUS      current
            DESCRIPTION
                "Specify which ports act as router ports.
                 A router port is a port on the Ethernet switch that
                 leads towards the Layer 3 multicast device or IGMP querier.
                 If an aggregation member port is selected as a router port,
                 the whole aggregation will act as a router port."
            ::= { iIgmpPortRelatedEntry 1 }


        -- 1.3.6.1.4.1.4756.108.110.1.10.1.3    
        iIgmpFastLeaveEnabled OBJECT-TYPE
            SYNTAX      TruthValue
            MAX-ACCESS  read-write
            STATUS      current
            DESCRIPTION
                "Enable the fast leave on the port."
            ::= { iIgmpPortRelatedEntry 3 }

        -- 1.3.6.1.4.1.4756.108.110.1.10.1.4    
        iIgmpThrottling OBJECT-TYPE
            SYNTAX      Integer32 (0..10)
            MAX-ACCESS  read-write
            STATUS      current
            DESCRIPTION
                "Enable to limit the number of multicast groups to which a switch port can belong.
                 Set to zero for unlimited."
            ::= { iIgmpPortRelatedEntry 4 }



    -- 1.3.6.1.4.1.4756.108.110.1.20
    iAddIgmpVlan OBJECT-TYPE
        SYNTAX      Integer32 (1..4095)
        MAX-ACCESS  read-write
        STATUS      current
        DESCRIPTION                                  
            "Add a new entry to the IGMP VLAN table.
             Specify the VID and configure the new entry.
             The specific IGMP VLAN starts working after the corresponding static VLAN is also created."
        ::= { iIgmpSnooping 20 }

    -- 1.3.6.1.4.1.4756.108.110.1.21
    iDeleteIgmpVlan OBJECT-TYPE
        SYNTAX      Integer32 (1..4095)
        MAX-ACCESS  read-write
        STATUS      current
        DESCRIPTION
            "Delete an IGMP VLAN from table."
        ::= { iIgmpSnooping 21 }

    -- 1.3.6.1.4.1.4756.108.110.1.22
    iIgmpVlanConfigTable OBJECT-TYPE
        SYNTAX      SEQUENCE OF IIgmpVlanConfigEntry
        MAX-ACCESS  not-accessible
        STATUS      current
        DESCRIPTION
            "This table allows for configure IGMP snooping VLAN."
        ::= { iIgmpSnooping 22 }

    -- 1.3.6.1.4.1.4756.108.110.1.22.1
    iIgmpVlanConfigEntry OBJECT-TYPE
        SYNTAX      IIgmpVlanConfigEntry
        MAX-ACCESS  not-accessible
        STATUS      current
        DESCRIPTION
            "The Entry of IGMP snooping VLAN."
        INDEX { iIgmpVlanID }
        ::= { iIgmpVlanConfigTable 1 }

    IIgmpVlanConfigEntry ::=
        SEQUENCE {     
            iIgmpVlanID            Integer32,
            iIgmpPerVlanEnabled    TruthValue,
            iIgmpQuerierEnabled    TruthValue,
            iIgmpCompatibility     INTEGER,
            iIgmpRV                Integer32,
            iIgmpQI                Integer32,
            iIgmpQRI               Integer32,
            iIgmpLLQI              Integer32,
            iIgmpURI               Integer32,
            iIgmpQuerierAddress    IpAddress,
            iIgmpPRI            	 Integer32
        }

        -- 1.3.6.1.4.1.4756.108.110.1.22.1.1    
        iIgmpVlanID OBJECT-TYPE
            SYNTAX      Integer32 (1..4095)
            MAX-ACCESS  read-only
            STATUS      current
            DESCRIPTION
                "Indicates the ID of this particular IGMP snooping VLAN."
            ::= { iIgmpVlanConfigEntry 1 }

        -- 1.3.6.1.4.1.4756.108.110.1.22.1.2    
        iIgmpPerVlanEnabled OBJECT-TYPE
            SYNTAX      TruthValue
            MAX-ACCESS  read-write
            STATUS      current
            DESCRIPTION
                "Enable the per-VLAN IGMP Snooping. Only up to 64 VLANs can be selected."
            ::= { iIgmpVlanConfigEntry 2 }

        -- 1.3.6.1.4.1.4756.108.110.1.22.1.3    
        iIgmpQuerierEnabled OBJECT-TYPE
            SYNTAX      TruthValue
            MAX-ACCESS  read-write
            STATUS      current
            DESCRIPTION
                "Enable the IGMP Querier in the VLAN."
            ::= { iIgmpVlanConfigEntry 3 }

        -- 1.3.6.1.4.1.4756.108.110.1.22.1.4    
        iIgmpCompatibility OBJECT-TYPE
            SYNTAX      INTEGER {
                            forcedIgmpV1(1),
                            forcedIgmpV2(2),
                            forcedIgmpV3(3),
            	            igmpAuto(4)
            	        }
            MAX-ACCESS  read-write
            STATUS      current
            DESCRIPTION
                "Compatibility is maintained by hosts and routers taking appropriate actions depending on
                 the versions of IGMP operating on hosts and routers within a network.
                 The allowed selection is IGMP-Auto, Forced IGMPv1, Forced IGMPv2, Forced IGMPv3,
                 default compatibility value is IGMP-Auto."
            DEFVAL      { igmpAuto }
            ::= { iIgmpVlanConfigEntry 4 }

        -- 1.3.6.1.4.1.4756.108.110.1.22.1.5    
        iIgmpRV OBJECT-TYPE
            SYNTAX      Integer32 (1..255)
            MAX-ACCESS  read-write
            STATUS      current
            DESCRIPTION
                "Robustness Variable.
                 The Robustness Variable allows tuning for the expected packet loss on a network.
                 The allowed range is 1 to 255, default robustness variable value is 2,
                 Robustness Variable SHOULD NOT be one."
            DEFVAL     { 2 }
            ::= { iIgmpVlanConfigEntry 5 }

        -- 1.3.6.1.4.1.4756.108.110.1.22.1.6    
        iIgmpQI OBJECT-TYPE
            SYNTAX      Integer32 (1..255)
            UNITS       "Seconds"
            MAX-ACCESS  read-write
            STATUS      current
            DESCRIPTION
                "Query Interval.
                 The Query Interval is the interval between General Queries sent by the Querier.
                 The allowed range is 1 to 255 seconds, default query interval is 125 seconds.
                 Note: The number of seconds represented by QRI must be less than QI!"
            DEFVAL     { 125 }     
            ::= { iIgmpVlanConfigEntry 6 }

        -- 1.3.6.1.4.1.4756.108.110.1.22.1.7    
        iIgmpQRI OBJECT-TYPE
            SYNTAX      Integer32 (0..31744)
            UNITS       "100 millisecond"
            MAX-ACCESS  read-write
            STATUS      current
            DESCRIPTION
                "Query Response Interval.
                 The Max Response Time used to calculate the Max Resp Code inserted into the periodic General Queries.
                 The allowed range is 0 to 31744 in tenths of seconds,
                 default query response interval is 100 in tenths of seconds (10 seconds).
                 The number of seconds represented by QRI must be less than QI!"
            DEFVAL     { 100 }     
            ::= { iIgmpVlanConfigEntry 7 }

        -- 1.3.6.1.4.1.4756.108.110.1.22.1.8    
        iIgmpLLQI OBJECT-TYPE
            SYNTAX      Integer32 (0..31744)
            UNITS       "100 millisecond"
            MAX-ACCESS  read-write
            STATUS      current
            DESCRIPTION
                "Last Member Query Interval.
                 The Last Member Query Time is the time value represented by the Last Member Query Interval,
                 multiplied by the Last Member Query Count.
                 The allowed range is 0 to 31744 in tenths of seconds,
                 default last member query interval is 10 in tenths of seconds (1 second)."
            DEFVAL     { 10 }     
            ::= { iIgmpVlanConfigEntry 8 }

        -- 1.3.6.1.4.1.4756.108.110.1.22.1.9    
        iIgmpURI OBJECT-TYPE
            SYNTAX      Integer32 (0..31744)
            UNITS       "Seconds"
            MAX-ACCESS  read-write
            STATUS      current
            DESCRIPTION
                "Unsolicited Report Interval.
                 The Unsolicited Report Interval is the time between repetitions of
                 a host's initial report of membership in a group.
                 The allowed range is 0 to 31744 seconds,
                 default unsolicited report interval is 1 second."
            DEFVAL     { 1 }     
            ::= { iIgmpVlanConfigEntry 9 }

        -- 1.3.6.1.4.1.4756.108.110.1.22.1.10       
        iIgmpQuerierAddress OBJECT-TYPE
            SYNTAX      IpAddress
            MAX-ACCESS  read-write
            STATUS      current                          
            DESCRIPTION
                "
                "
            ::= { iIgmpVlanConfigEntry 10 }

        -- 1.3.6.1.4.1.4756.108.110.1.22.1.11   
        iIgmpPRI OBJECT-TYPE
            SYNTAX      Integer32 (0..7)
            MAX-ACCESS  read-write
            STATUS      current
            DESCRIPTION
                "
                "
            ::= { iIgmpVlanConfigEntry 11 }



    -- 1.3.6.1.4.1.4756.108.110.1.32
    iIgmpPortGroupFilteringTable OBJECT-TYPE
        SYNTAX      SEQUENCE OF IIgmpPortGroupFilteringEntry
        MAX-ACCESS  not-accessible
        STATUS      current
        DESCRIPTION
            "This table is used for configuring the port group filtering."
        ::= { iIgmpSnooping 32 }

    -- 1.3.6.1.4.1.4756.108.110.1.32.1
    iIgmpPortGroupFilteringEntry OBJECT-TYPE
        SYNTAX      IIgmpPortGroupFilteringEntry
        MAX-ACCESS  not-accessible
        STATUS      current
        DESCRIPTION
            "The Entry of port group filtering configurations."
        INDEX { iIgmpPortGroupFilteringIndex }
        ::= { iIgmpPortGroupFilteringTable 1 }

    IIgmpPortGroupFilteringEntry ::=
        SEQUENCE {
						iIgmpPortGroupFilteringIndex    Integer32,
            iIgmpPortGroupFilteringPort   DisplayString
            
        }

    	-- 1.3.6.1.4.1.4756.108.110.1.32.1.1  
        iIgmpPortGroupFilteringIndex OBJECT-TYPE
            SYNTAX      Integer32 (1..29)
            MAX-ACCESS  read-only
            STATUS      current
            DESCRIPTION
                "

                "
            ::= { iIgmpPortGroupFilteringEntry 1 }


        -- 1.3.6.1.4.1.4756.108.110.1.32.1.2    
        iIgmpPortGroupFilteringPort OBJECT-TYPE
            SYNTAX      DisplayString
            MAX-ACCESS  read-write
            STATUS      current
            DESCRIPTION
                " "
            ::= { iIgmpPortGroupFilteringEntry 2 }








    -- 1.3.6.1.4.1.4756.108.110.1.40
    iIgmpSnoopingStatisticsClear OBJECT-TYPE
        SYNTAX      INTEGER {
                        trigger(1),
                        normal(2)
                    }
        MAX-ACCESS  read-write
        STATUS      current
        DESCRIPTION
            "Clears all Statistics counters."
        ::= { iIgmpSnooping 40 }

    -- 1.3.6.1.4.1.4756.108.110.1.41
    iIgmpSnoopingStatisticsTable OBJECT-TYPE
        SYNTAX      SEQUENCE OF IIgmpSnoopingStatisticsEntry
        MAX-ACCESS  not-accessible
        STATUS      current
        DESCRIPTION
            "This table provides IGMP Snooping status."
        ::= { iIgmpSnooping 41 }

    -- 1.3.6.1.4.1.4756.108.110.1.41.1
    iIgmpSnoopingStatisticsEntry OBJECT-TYPE
        SYNTAX      IIgmpSnoopingStatisticsEntry
        MAX-ACCESS  not-accessible
        STATUS      current
        DESCRIPTION
            "The Entry of VLAN ID."
        INDEX { iIgmpSnoopingVlanID }
        ::= { iIgmpSnoopingStatisticsTable 1 }

    IIgmpSnoopingStatisticsEntry ::=
        SEQUENCE {       
            iIgmpSnoopingVlanID        Integer32,
            iIgmpQuerierVersion        Integer32,
            iIgmpHostVersion           Integer32,
            iIgmpQuerierStatus         INTEGER,
            iIgmpQueriesTransmitted    Counter32,
            iIgmpQueriesReceived       Counter32,
            iIgmpV1ReportsReceived     Counter32,
            iIgmpV2ReportsReceived     Counter32,
            iIgmpV3ReportsReceived     Counter32,
            iIgmpV2LeavesReceived      Counter32
        }
        
        -- 1.3.6.1.4.1.4756.108.110.1.41.1.1    
        iIgmpSnoopingVlanID OBJECT-TYPE
            SYNTAX      Integer32 (1..4095)
            MAX-ACCESS  read-only
            STATUS      current
            DESCRIPTION
                 "The VLAN ID of the entry."
            ::= { iIgmpSnoopingStatisticsEntry 1 }

        -- 1.3.6.1.4.1.4756.108.110.1.41.1.2    
        iIgmpQuerierVersion OBJECT-TYPE
            SYNTAX      Integer32 (1..3)
            MAX-ACCESS  read-only
            STATUS      current
            DESCRIPTION
                "Working Querier Version currently."
            ::= { iIgmpSnoopingStatisticsEntry 2 }

        -- 1.3.6.1.4.1.4756.108.110.1.41.1.3    
        iIgmpHostVersion OBJECT-TYPE
            SYNTAX      Integer32 (1..3)
            MAX-ACCESS  read-only
            STATUS      current
            DESCRIPTION
                "Working Host Version currently."
            ::= { iIgmpSnoopingStatisticsEntry 3 }

        -- 1.3.6.1.4.1.4756.108.110.1.41.1.4    
        iIgmpQuerierStatus OBJECT-TYPE
            SYNTAX      INTEGER {
                            idle(1),
                            active(2),
                            disable(3)
                        }
            MAX-ACCESS  read-only
            STATUS      current
            DESCRIPTION
                "Shows the Querier status is ACTIVE or IDLE.
                 DISABLE denotes the specific interface is administratively disabled."
            ::= { iIgmpSnoopingStatisticsEntry 4 }

        -- 1.3.6.1.4.1.4756.108.110.1.41.1.5    
        iIgmpQueriesTransmitted OBJECT-TYPE
            SYNTAX      Counter32
            UNITS       "Packets"
            MAX-ACCESS  read-only
            STATUS      current
            DESCRIPTION
                "The number of Transmitted Queries."
            ::= { iIgmpSnoopingStatisticsEntry 5 }

        -- 1.3.6.1.4.1.4756.108.110.1.41.1.6    
        iIgmpQueriesReceived OBJECT-TYPE
            SYNTAX      Counter32
            UNITS       "Packets"
            MAX-ACCESS  read-only
            STATUS      current
            DESCRIPTION
                "The number of Received Queries."
            ::= { iIgmpSnoopingStatisticsEntry 6 }

        -- 1.3.6.1.4.1.4756.108.110.1.41.1.7    
        iIgmpV1ReportsReceived OBJECT-TYPE
            SYNTAX      Counter32
            UNITS       "Packets"
            MAX-ACCESS  read-only
            STATUS      current
            DESCRIPTION
                "The number of Received V1 Reports."
            ::= { iIgmpSnoopingStatisticsEntry 7 }

        -- 1.3.6.1.4.1.4756.108.110.1.41.1.8    
        iIgmpV2ReportsReceived OBJECT-TYPE
            SYNTAX      Counter32
            UNITS       "Packets"
            MAX-ACCESS  read-only
            STATUS      current
            DESCRIPTION
                "The number of Received V2 Reports."
            ::= { iIgmpSnoopingStatisticsEntry 8 }

        -- 1.3.6.1.4.1.4756.108.110.1.41.1.9    
        iIgmpV3ReportsReceived OBJECT-TYPE
            SYNTAX      Counter32
            UNITS       "Packets"
            MAX-ACCESS  read-only
            STATUS      current
            DESCRIPTION
                "The number of Received V3 Reports."
            ::= { iIgmpSnoopingStatisticsEntry 9 }

        -- 1.3.6.1.4.1.4756.108.110.1.41.1.10    
        iIgmpV2LeavesReceived OBJECT-TYPE
            SYNTAX      Counter32
            UNITS       "Packets"
            MAX-ACCESS  read-only
            STATUS      current
            DESCRIPTION
                "The number of Received V2 Leaves."
            ::= { iIgmpSnoopingStatisticsEntry 10 }

    -- 1.3.6.1.4.1.4756.108.110.1.50
    iIgmpGroupsInfoTable OBJECT-TYPE
        SYNTAX      SEQUENCE OF IIgmpGroupsInfoEntry
        MAX-ACCESS  not-accessible
        STATUS      current
        DESCRIPTION
            "This table shows IGMP snooping groups information."
        ::= { iIgmpSnooping 50 }

    -- 1.3.6.1.4.1.4756.108.110.1.50.1
    iIgmpGroupsInfoEntry OBJECT-TYPE
        SYNTAX      IIgmpGroupsInfoEntry
        MAX-ACCESS  not-accessible
        STATUS      current
        DESCRIPTION
            "The Entry of IGMP snooping groups information."
        INDEX { iIgmpGroupsInfoIndex }
        ::= { iIgmpGroupsInfoTable 1 }

    IIgmpGroupsInfoEntry ::=
        SEQUENCE {
            iIgmpGroupsInfoIndex    Integer32,
            iIgmpGroupsInfoVlanID   Integer32,          
            iIgmpGroupsInfo         IpAddress,
            iIgmpGroupsPortMembers  DisplayString
        }

        -- 1.3.6.1.4.1.4756.108.110.1.50.1.1    
        iIgmpGroupsInfoIndex OBJECT-TYPE
            SYNTAX      Integer32 (1..4095)
            MAX-ACCESS  read-only
            STATUS      current
            DESCRIPTION
                "Entries in the IGMP group table."
            ::= { iIgmpGroupsInfoEntry 1 }

        -- 1.3.6.1.4.1.4756.108.110.1.50.1.2    
        iIgmpGroupsInfoVlanID OBJECT-TYPE
            SYNTAX      Integer32 (1..4095)
            MAX-ACCESS  read-only
            STATUS      current
            DESCRIPTION
                "VLAN ID of the group."
            ::= { iIgmpGroupsInfoEntry 2 }

        -- 1.3.6.1.4.1.4756.108.110.1.50.1.3    
        iIgmpGroupsInfo OBJECT-TYPE
            SYNTAX      IpAddress
            MAX-ACCESS  read-only
            STATUS      current
            DESCRIPTION
                "Group address of the entry."
            ::= { iIgmpGroupsInfoEntry 3 }

        -- 1.3.6.1.4.1.4756.108.110.1.50.1.4    
        iIgmpGroupsPortMembers OBJECT-TYPE
            SYNTAX      DisplayString
            MAX-ACCESS  read-only
            STATUS      current
            DESCRIPTION
                "Ports under this group."
            ::= { iIgmpGroupsInfoEntry 4 }

    -- 1.3.6.1.4.1.4756.108.110.1.60
    iIgmpSfmInfoTable OBJECT-TYPE
        SYNTAX      SEQUENCE OF IIgmpSfmInfoEntry
        MAX-ACCESS  not-accessible
        STATUS      current
        DESCRIPTION
            "This table shows IGMP SSM(Source-Filtered Multicast) information.
             The IGMP SFM Information Table also contains the SSM(Source-Specific Multicast) information."
        ::= { iIgmpSnooping 60 }

    -- 1.3.6.1.4.1.4756.108.110.1.60.1
    iIgmpSfmInfoEntry OBJECT-TYPE
        SYNTAX      IIgmpSfmInfoEntry
        MAX-ACCESS  not-accessible
        STATUS      current
        DESCRIPTION
            "The Entry of IGMP SSM information."
        INDEX { iIgmpSfmInfoIndex }
        ::= { iIgmpSfmInfoTable 1 }

    IIgmpSfmInfoEntry ::=
        SEQUENCE {
            iIgmpSfmInfoIndex              Integer32,
            iIgmpSfmInfoVlanID             Integer32,
            iIgmpSfmInfoGroup              IpAddress,          
            iIgmpSfmPortNumber             Integer32,
            iIgmpSfmMode                   INTEGER,
            iIgmpSfmSourceAddress          IpAddress,
            iIgmpSfmType                   INTEGER,
            iIgmpSfmHardwareFilterSwitch   INTEGER
        }

        -- 1.3.6.1.4.1.4756.108.110.1.60.1.1    
        iIgmpSfmInfoIndex OBJECT-TYPE
            SYNTAX      Integer32 (1..4095)
            MAX-ACCESS  read-only
            STATUS      current
            DESCRIPTION
                "Entries in the IGMP SSM information table."
            ::= { iIgmpSfmInfoEntry 1 }

        -- 1.3.6.1.4.1.4756.108.110.1.60.1.2    
        iIgmpSfmInfoVlanID OBJECT-TYPE
            SYNTAX      Integer32 (1..4095)
            MAX-ACCESS  read-only
            STATUS      current
            DESCRIPTION
                "VLAN ID of the group."
            ::= { iIgmpSfmInfoEntry 2 }

        -- 1.3.6.1.4.1.4756.108.110.1.60.1.3    
        iIgmpSfmInfoGroup OBJECT-TYPE
            SYNTAX      IpAddress
            MAX-ACCESS  read-only
            STATUS      current
            DESCRIPTION
                "Group address of the entry."
            ::= { iIgmpSfmInfoEntry 3 }

        -- 1.3.6.1.4.1.4756.108.110.1.60.1.4    
        iIgmpSfmPortNumber OBJECT-TYPE
            SYNTAX      Integer32 (1..6)
            MAX-ACCESS  read-only
            STATUS      current
            DESCRIPTION
                "Switch port number."
            ::= { iIgmpSfmInfoEntry 4 }

        -- 1.3.6.1.4.1.4756.108.110.1.60.1.5    
        iIgmpSfmMode OBJECT-TYPE
            SYNTAX      INTEGER {
                            exclude(1),
                            include(2)
                        }
            MAX-ACCESS  read-only
            STATUS      current
            DESCRIPTION
                "Indicates the filtering mode maintained per (VLAN ID, port number, Group Address) basis.
                 It can be either Include or Exclude."
            ::= { iIgmpSfmInfoEntry 5 }

        -- 1.3.6.1.4.1.4756.108.110.1.60.1.6    
        iIgmpSfmSourceAddress OBJECT-TYPE
            SYNTAX      IpAddress
            MAX-ACCESS  read-only
            STATUS      current
            DESCRIPTION
                "IP Address of the source.
                 Currently, system limits the total number of IP source addresses for filtering to be 128."
            ::= { iIgmpSfmInfoEntry 6 }

        -- 1.3.6.1.4.1.4756.108.110.1.60.1.7    
        iIgmpSfmType OBJECT-TYPE
            SYNTAX      INTEGER {
                            deny(1),
                            allow(2)
                        }
            MAX-ACCESS  read-only
            STATUS      current
            DESCRIPTION
                "Indicates the Type. It can be either Allow or Deny."
            ::= { iIgmpSfmInfoEntry 7 }

        -- 1.3.6.1.4.1.4756.108.110.1.60.1.8    
        iIgmpSfmHardwareFilterSwitch OBJECT-TYPE
            SYNTAX      INTEGER {
                            no(1),
                            yes(2)
                        }
            MAX-ACCESS  read-only
            STATUS      current
            DESCRIPTION
                "Indicates whether data plane destined to the specific group address from
                 the source IPv4 address could be handled by chip or not."
            ::= { iIgmpSfmInfoEntry 8 }

-- Redundancy
	iRedundancy  OBJECT IDENTIFIER ::= { msw4424a 60 }

-- uRing
    
    -- 1.3.6.1.4.1.4756.108.60.10
    uRing  OBJECT IDENTIFIER ::= { iRedundancy 10 }
    
    -- 1.3.6.1.4.1.4756.108.60.10.1
    uRingInstanceAdd OBJECT-TYPE
        SYNTAX      DisplayString
        MAX-ACCESS  read-write
        STATUS      current
        DESCRIPTION
            "Added a new uRing Instance.
             	Syntax: <ring|sub|chain> <port east> <port west>
             	port east , the value is the switch port (range 1 ~ 29)
             	Port west , the value is the switch port (range 1 ~ 29)
            "
        ::= { uRing 1 }
        
     -- 1.3.6.1.4.1.4756.108.60.60.2
    uRingInstanceDelete OBJECT-TYPE
        SYNTAX      DisplayString
        MAX-ACCESS  read-write
        STATUS      current
        DESCRIPTION
            "Deleted a uRing Instance.
            	Syntax: <uRing Instance>
            "
        ::= { uRing 2 }
    
    -- 1.3.6.1.4.1.4756.108.60.60.3
    uRingConfigTable OBJECT-TYPE
        SYNTAX      SEQUENCE OF URingConfigEntry
        MAX-ACCESS  not-accessible
        STATUS      current
        DESCRIPTION
            "The uRing Instance config Table."
        ::= { uRing 3 }
     
    -- 1.3.6.1.4.1.4756.108.60.60.3.1
    uRingConfigEntry OBJECT-TYPE
        SYNTAX      URingConfigEntry
        MAX-ACCESS  not-accessible
        STATUS      current
        DESCRIPTION
            "The uRing Instance configuration Entry."
        INDEX { uRingInstance }
        ::= { uRingConfigTable 1 }

    URingConfigEntry ::= 
    SEQUENCE {
				    uRingInstance 				Integer32,
				    uRingType				    INTEGER,
				    uRingMaster					TruthValue,
				    uRingPortEast 				INTEGER,
				    uRingPortEastEdge			INTEGER,
				    uRingPortWest 				INTEGER,
				    uRingPortWestEdge			INTEGER
        }
        
        -- 1.3.6.1.4.1.4756.108.60.60.3.1.1
        uRingInstance OBJECT-TYPE
        SYNTAX      Integer32 (1..5)
        MAX-ACCESS  read-only
        STATUS      current
        DESCRIPTION
            "uRing Instance."
        ::= { uRingConfigEntry 1 }
       
        -- 1.3.6.1.4.1.4756.108.60.60.3.1.2
        uRingType OBJECT-TYPE
        SYNTAX      INTEGER {
                             u-ring(1),
                             sub-ring(2),
                             u-chain(3)
        			}
        MAX-ACCESS  read-only
        STATUS      current
        DESCRIPTION
            "Select device uRing Type."
        ::= { uRingConfigEntry 2 }

		-- 1.3.6.1.4.1.4756.108.60.60.3.1.3
        uRingMaster OBJECT-TYPE
        SYNTAX      TruthValue
        MAX-ACCESS  read-write
        STATUS      current
        DESCRIPTION
            "Assign this device become master or not."
        ::= { uRingConfigEntry 3 }

		-- 1.3.6.1.4.1.4756.108.60.60.3.1.4
        uRingPortEast OBJECT-TYPE
        SYNTAX      INTEGER {
                     		none(0),
                     		port1(1),
                     		port2(2),
                     		port3(3),
                     		port4(4),
                     		port5(5),
                     		port6(6),
                     		port7(7),
                     		port8(8),
                     		port9(9),
                     		port10(10),
                     		port11(11),
                     		port12(12),
                     		port13(13),
                     		port14(14),
                     		port15(15),
                     		port16(16),
                     		port17(17),
                     		port18(18),
                     		port19(19),
                     		port20(20),
                     		port21(21),
                     		port22(22),
                     		port23(23),
                     		port24(24),
                     		port25(25),
                     		port26(26),
                     		port27(27),
                     		port28(28),
                     		port29(29) 
        			}
        MAX-ACCESS  read-write
        STATUS      current
        DESCRIPTION
            "uRing Port East Select."
        ::= { uRingConfigEntry 4 }
       
        -- 1.3.6.1.4.1.4756.108.60.60.3.1.5
        uRingPortEastEdge OBJECT-TYPE
        SYNTAX      TruthValue
        MAX-ACCESS  read-write
        STATUS      current
        DESCRIPTION
            "uRing Port East Edge Select. Only uRingType is 'chain' mode can be setting."
        ::= { uRingConfigEntry 5 }
        
        -- 1.3.6.1.4.1.4756.108.60.60.3.1.6
        uRingPortWest OBJECT-TYPE
        SYNTAX      INTEGER {
                     		none(0),
                     		port1(1),
                     		port2(2),
                     		port3(3),
                     		port4(4),
                     		port5(5),
                     		port6(6),
                     		port7(7),
                     		port8(8),
                     		port9(9),
                     		port10(10),
                     		port11(11),
                     		port12(12),
                     		port13(13),
                     		port14(14),
                     		port15(15),
                     		port16(16),
                     		port17(17),
                     		port18(18),
                     		port19(19),
                     		port20(20),
                     		port21(21),
                     		port22(22),
                     		port23(23),
                     		port24(24),
                     		port25(25),
                     		port26(26),
                     		port27(27),
                     		port28(28),
                     		port29(29) 
        			}
        MAX-ACCESS  read-write
        STATUS      current
        DESCRIPTION
            "uRing Port West Select. Only uRing Type is 'ring' or 'chain' can be setting."
        ::= { uRingConfigEntry 6 }
       
        -- 1.3.6.1.4.1.4756.108.60.60.3.1.7
        uRingPortWestEdge OBJECT-TYPE
        SYNTAX      TruthValue
        MAX-ACCESS  read-write
        STATUS      current
        DESCRIPTION
            "uRing Port West Edge Select. Only uRingType is 'chain' mode can be setting."
        ::= { uRingConfigEntry 7 }
        
    -- 1.3.6.1.4.1.4756.108.60.60.4
	uRingStatusTable OBJECT-TYPE
        SYNTAX      SEQUENCE OF URingStatusEntry
        MAX-ACCESS  not-accessible
        STATUS      current
        DESCRIPTION
            "The uRing Instance status Table."
        ::= { uRing 4 }
     
    -- 1.3.6.1.4.1.4756.108.60.60.4.1
    uRingStatusEntry OBJECT-TYPE
        SYNTAX      URingStatusEntry
        MAX-ACCESS  not-accessible
        STATUS      current
        DESCRIPTION
            "The uRing Instance status Entry."
        INDEX { uRingInstance }
        ::= { uRingStatusTable 1 }

    URingStatusEntry ::= 
    SEQUENCE {
				    uRingStatusType				DisplayString,
				    uRingStatusRole				DisplayString,
				    uRingStatusEastPortNumber	DisplayString,
				    uRingStatusEastPortState	DisplayString,
				    uRingStatusEastPortEdge 	INTEGER,
				    uRingStatusWestPortNumber	DisplayString,
				    uRingStatusWestPortState	DisplayString,
				    uRingStatusWestPortEdge 	INTEGER,
				    uRingStatusHealthy          INTEGER
        }
         
        -- 1.3.6.1.4.1.4756.108.60.60.4.1.1 
        uRingStatusType OBJECT-TYPE
        SYNTAX      DisplayString
        MAX-ACCESS  read-only
        STATUS      current
        DESCRIPTION
            "uRing Stats Type"
        ::= { uRingStatusEntry 1 }
        
        -- 1.3.6.1.4.1.4756.108.60.60.4.1.2 
        uRingStatusRole OBJECT-TYPE
        SYNTAX      DisplayString
        MAX-ACCESS  read-only
        STATUS      current
        DESCRIPTION
            "uRing Status Role"
        ::= { uRingStatusEntry 2 }
        
        -- 1.3.6.1.4.1.4756.108.60.60.4.1.3 
        uRingStatusEastPortNumber OBJECT-TYPE
        SYNTAX      DisplayString
        MAX-ACCESS  read-only
        STATUS      current
        DESCRIPTION
            "uRing Status East Port Number"
        ::= { uRingStatusEntry 3 }
        
        -- 1.3.6.1.4.1.4756.108.60.60.4.1.4
        uRingStatusEastPortState OBJECT-TYPE
        SYNTAX      DisplayString
        MAX-ACCESS  read-only
        STATUS      current
        DESCRIPTION
            "uRing Status East Port State"
        ::= { uRingStatusEntry 4 }
        
        -- 1.3.6.1.4.1.4756.108.60.60.4.1.5
        uRingStatusEastPortEdge OBJECT-TYPE
        SYNTAX      INTEGER { 
        					none(0),
                     		yes(1),
                     		no(2)
        			}
        MAX-ACCESS  read-only
        STATUS      current
        DESCRIPTION
            "uRing Status East Port Edge"
        ::= { uRingStatusEntry 5 }

        -- 1.3.6.1.4.1.4756.108.60.60.4.1.6
        uRingStatusWestPortNumber OBJECT-TYPE
        SYNTAX      DisplayString
        MAX-ACCESS  read-only
        STATUS      current
        DESCRIPTION
            "uRing Status West Port Number"
        ::= { uRingStatusEntry 6 }
        
        -- 1.3.6.1.4.1.4756.108.60.60.4.1.7
        uRingStatusWestPortState OBJECT-TYPE
        SYNTAX      DisplayString
        MAX-ACCESS  read-only
        STATUS      current
        DESCRIPTION
            "uRing Status West Port State"
        ::= { uRingStatusEntry 7 }
        
        -- 1.3.6.1.4.1.4756.108.60.60.4.1.8
        uRingStatusWestPortEdge OBJECT-TYPE
        SYNTAX      INTEGER { 
        					none(0),
                     		yes(1),
                     		no(2)
        			}
        MAX-ACCESS  read-only
        STATUS      current
        DESCRIPTION
            "uRing Status West Port Edge"
        ::= { uRingStatusEntry 8 }
        
        -- 1.3.6.1.4.1.4756.108.60.60.4.1.9
        uRingStatusHealthy OBJECT-TYPE
        SYNTAX      INTEGER {
        					none(0),
                     		fine(1),
                     		fault(2)
        			}
        MAX-ACCESS  read-only
        STATUS      current
        DESCRIPTION
            "uRing Status Healthy
            	0: none
            	1: fine
            	2: falut
            "
        ::= { uRingStatusEntry 9 }
	
-- Loop Protection
    -- 1.3.6.1.4.1.4756.108.60.20
    iLoopProtection  OBJECT IDENTIFIER ::= { iRedundancy 20 }

    -- 1.3.6.1.4.1.4756.108.60.20.1
    iLoopProtectionEnable OBJECT-TYPE
        SYNTAX      TruthValue
        MAX-ACCESS  read-write
        STATUS      current
        DESCRIPTION
            "Controls whether loop protections is enabled (as a whole)."
        ::= { iLoopProtection 1 }

    -- 1.3.6.1.4.1.4756.108.60.20.2
    iLoopProtectionTxTime OBJECT-TYPE
        SYNTAX      Integer32 (1..10)
        UNITS       "Seconds"
        MAX-ACCESS  read-write
        STATUS      current
        DESCRIPTION
            "The interval between each loop protection PDU sent on each port.
             valid values are 1 to 10 seconds."
       ::= { iLoopProtection 2 }

    -- 1.3.6.1.4.1.4756.108.60.20.3
    iLoopProtectionShutdownTime OBJECT-TYPE
        SYNTAX      Integer32 (10..50)
        MAX-ACCESS  read-write
        STATUS      current
        DESCRIPTION
            "The period (in seconds) for which a port will be kept disabled in the event of
             a loop is detected (and the port action shuts down the port).
             Valid values are 0 to 604800 seconds (7 days).
             A value of zero will keep a port disabled (until next device restart)."
        ::= { iLoopProtection 3 }

    -- 1.3.6.1.4.1.4756.108.60.20.4
    iLoopProtectionPortConfigTable OBJECT-TYPE
        SYNTAX      SEQUENCE OF ILoopProtectionPortConfigEntry
        MAX-ACCESS  not-accessible
        STATUS      current
        DESCRIPTION
            "This table provides Loop Protection configurations for all ports."
        ::= { iLoopProtection 4 }

    -- 1.3.6.1.4.1.4756.108.60.20.4.1
    iLoopProtectionPortConfigEntry OBJECT-TYPE
        SYNTAX      ILoopProtectionPortConfigEntry
        MAX-ACCESS  not-accessible
        STATUS      current
        DESCRIPTION
            "The Entry of Loop Protection port configurations."
        INDEX { iPortIndex }
        ::= { iLoopProtectionPortConfigTable 1 }

    ILoopProtectionPortConfigEntry ::=
        SEQUENCE {
            iLoopProtectionPortEnabled     TruthValue,          
            iLoopProtectionPortAction      INTEGER,
            iLoopProtectionPortTxMode      INTEGER 
        }

        -- 1.3.6.1.4.1.4756.108.60.20.4.1.1    
        iLoopProtectionPortEnabled OBJECT-TYPE
            SYNTAX      TruthValue
            MAX-ACCESS  read-write
            STATUS      current
            DESCRIPTION
                "Controls whether loop protection is enabled on this switch port."
            ::= { iLoopProtectionPortConfigEntry 1 }

        -- 1.3.6.1.4.1.4756.108.60.20.4.1.2    
        iLoopProtectionPortAction OBJECT-TYPE
            SYNTAX      INTEGER {
                            shutdownPort(1),
                            shutdownPortAndLog(2),
                            logOnly(3)
                        }
            MAX-ACCESS  read-write
            STATUS      current
            DESCRIPTION
                "Configures the action performed when a loop is detected on a port.
                 Valid values are Shutdown Port, Shutdown Port and Log or Log Only."
            ::= { iLoopProtectionPortConfigEntry 2 }
            
        -- 1.3.6.1.4.1.4756.108.60.20.4.1.3    
        iLoopProtectionPortTxMode OBJECT-TYPE
            SYNTAX      INTEGER {
                            enabled(1),
                            disabled(2)
                        }
            MAX-ACCESS  read-write
            STATUS      current
            DESCRIPTION
                "Controls whether the port is actively generating loop protection PDU's,
                 or whether it is just passively looking for looped PDU's."
            ::= { iLoopProtectionPortConfigEntry 3 }

    -- 1.3.6.1.4.1.4756.108.60.20.5
    iLoopProtectionPortStatusTable OBJECT-TYPE
        SYNTAX      SEQUENCE OF ILoopProtectionPortStatusEntry
        MAX-ACCESS  not-accessible
        STATUS      current
        DESCRIPTION
            "This table provides Loop Protection status for all ports."
        ::= { iLoopProtection 5 }

    -- 1.3.6.1.4.1.4756.108.60.20.5.1
    iLoopProtectionPortStatusEntry OBJECT-TYPE
        SYNTAX      ILoopProtectionPortStatusEntry
        MAX-ACCESS  not-accessible
        STATUS      current
        DESCRIPTION
            "The Entry of Loop Protection port status."
        INDEX { iPortIndex }
        ::= { iLoopProtectionPortStatusTable 1 }

    ILoopProtectionPortStatusEntry ::=
        SEQUENCE {
            iLoopProtectionPortLoops     Integer32,          
            iLoopProtectionPortStatus    INTEGER,
            iLoopProtectionPortLoop      INTEGER,
            iLoopProtectionPortLastLoop  DisplayString
        }

        -- 1.3.6.1.4.1.4756.108.60.20.5.1.1    
        iLoopProtectionPortLoops OBJECT-TYPE
            SYNTAX      Integer32
            MAX-ACCESS  read-only
            STATUS      current
            DESCRIPTION
                "The number of loops detected on this port."
            ::= { iLoopProtectionPortStatusEntry 1 }

        -- 1.3.6.1.4.1.4756.108.60.20.5.1.2    
        iLoopProtectionPortStatus OBJECT-TYPE
            SYNTAX      INTEGER {
                            up(1),
                            down(2),
                            disabled(3)
                        }
            MAX-ACCESS  read-only
            STATUS      current
            DESCRIPTION
                "The current loop protection status of the port."
            ::= { iLoopProtectionPortStatusEntry 2 }
            
        -- 1.3.6.1.4.1.4756.108.60.20.5.1.3    
        iLoopProtectionPortLoop OBJECT-TYPE
            SYNTAX      INTEGER {
                            loop(1),
                            noLoop(2)
                        }
            MAX-ACCESS  read-only
            STATUS      current
            DESCRIPTION
                "Whether a loop is currently detected on the port."
            ::= { iLoopProtectionPortStatusEntry 3 }
            
        -- 1.3.6.1.4.1.4756.108.60.20.5.1.4    
        iLoopProtectionPortLastLoop OBJECT-TYPE
            SYNTAX      DisplayString
            MAX-ACCESS  read-only
            STATUS      current
            DESCRIPTION
                "The time of the last loop event detected."
            ::= { iLoopProtectionPortStatusEntry 4 }

-- Spanning Tree
    -- 1.3.6.1.4.1.4756.108.60.30
    iSpanningTree  OBJECT IDENTIFIER ::= { iRedundancy 30 }

		-- 1.3.6.1.4.1.4756.108.60.30.1
    iBridgeSettings OBJECT IDENTIFIER ::= { iSpanningTree 1 }
    
    -- 1.3.6.1.4.1.4756.108.60.30.1.1
    iProtocolVersion OBJECT-TYPE
        SYNTAX      INTEGER {
	                        stp(1),
	                        rstp(2),
	                        mstp(3)
	                    }

        MAX-ACCESS  read-write
        STATUS      current
        DESCRIPTION                                  
            "The MSTP / RSTP / STP protocol version setting."
        ::= { iBridgeSettings 1 }
        
    -- 1.3.6.1.4.1.4756.108.60.30.1.2
    iBridgePriority OBJECT-TYPE
        SYNTAX      INTEGER {
	                        priority-0(1),
	                        priority-4096(2),
	                        priority-8192(3),
	                        priority-12288(4),
	                        priority-16384(5),
	                        priority-20480(6),
	                        priority-24576(7),
	                        priority-28672(8),
	                        priority-32768(9),
	                        priority-36864(10),
	                        priority-40960(11),
	                        priority-45056(12),
	                        priority-49152(13),
	                        priority-53248(14),
	                        priority-57344(15),
	                        priority-61440(16)
	                    }

        MAX-ACCESS  read-write
        STATUS      current
        DESCRIPTION                                  
            "Controls the bridge priority. Lower numeric values have better priority. 
             The bridge priority plus the MSTI instance number, concatenated with the 6-byte MAC address of the switch forms a Bridge Identifier. 
						 For MSTP operation, this is the priority of the CIST. Otherwise, this is the priority of the STP/RSTP bridge. "
        ::= { iBridgeSettings 2 }
        
    -- 1.3.6.1.4.1.4756.108.60.30.1.3
    iForwardDelay OBJECT-TYPE
        SYNTAX      Integer32 (4..30)
        MAX-ACCESS  read-write
        STATUS      current
        DESCRIPTION                                  
            "The delay used by STP Bridges to transit Root and Designated Ports to Forwarding (used in STP compatible mode). 
             Valid values are in the range 4 to 30 seconds. "
        ::= { iBridgeSettings 3 }
        
    -- 1.3.6.1.4.1.4756.108.60.30.1.4
    iMaxAge OBJECT-TYPE
        SYNTAX      Integer32 (6..40)
        MAX-ACCESS  read-write
        STATUS      current
        DESCRIPTION                                  
            "The maximum age of the information transmitted by the Bridge when it is the Root Bridge. 
             Valid values are in the range 6 to 40 seconds, and MaxAge must be <= (FwdDelay-1)*2.
            "
        ::= { iBridgeSettings 4 }
        
    -- 1.3.6.1.4.1.4756.108.60.30.1.5
    iMaximumHopCount OBJECT-TYPE
        SYNTAX      Integer32 (6..40)
        MAX-ACCESS  read-write
        STATUS      current
        DESCRIPTION                                  
            "This defines the initial value of remaining Hops for MSTI information generated at the boundary of an MSTI region. 
             It defines how many bridges a root bridge can distribute its BPDU information to. Valid values are in the range 6 to 40 hops.
            "
        ::= { iBridgeSettings 5 }
        
    -- 1.3.6.1.4.1.4756.108.60.30.1.6
    iTransmitHoldCount OBJECT-TYPE
        SYNTAX      Integer32 (1..10)
        MAX-ACCESS  read-write
        STATUS      current
        DESCRIPTION                                  
            "	The number of BPDU's a bridge port can send per second. When exceeded, transmission of the next BPDU will be delayed. 
    					Valid values are in the range 1 to 10 BPDU's per second. 
            "
        ::= { iBridgeSettings 6 }

		-- 1.3.6.1.4.1.4756.108.60.30.1.7
    iEdgePortBPDUFiltering OBJECT-TYPE
        SYNTAX      TruthValue
        MAX-ACCESS  read-write
        STATUS      current
        DESCRIPTION                                  
            "Control whether a port explicitly configured as Edge will transmit and receive BPDUs."
        ::= { iBridgeSettings 7 }

	  -- 1.3.6.1.4.1.4756.108.60.30.1.8
    iEdgePortBPDUGuard OBJECT-TYPE
        SYNTAX      TruthValue
        MAX-ACCESS  read-write
        STATUS      current
        DESCRIPTION                                  
            "Control whether a port explicitly configured as Edge will disable itself upon reception of a BPDU.
             The port will enter the error-disabled state, and will be removed from the active topology."
        ::= { iBridgeSettings 8 }

		-- 1.3.6.1.4.1.4756.108.60.30.1.9
    iPortErrorRecovery OBJECT-TYPE
        SYNTAX      TruthValue
        MAX-ACCESS  read-write
        STATUS      current
        DESCRIPTION                                  
            "Control whether a port in the error-disabled state automatically will be enabled after a certain time. 
             If recovery is not enabled, ports have to be disabled and re-enabled for normal STP operation. The condition is also cleared by a system reboot. 
						"
        ::= { iBridgeSettings 9 }

		-- 1.3.6.1.4.1.4756.108.60.30.1.10
    iPortErrorRecoveryTimeout OBJECT-TYPE
        SYNTAX      Integer32 (30..86400)
        MAX-ACCESS  read-write
        STATUS      current
        DESCRIPTION                                  
            "The time to pass before a port in the error-disabled state can be enabled. Valid values are between 30 and 86400 seconds (24 hours). "
        ::= { iBridgeSettings 10 }

		-- 1.3.6.1.4.1.4756.108.60.30.2
    iMSTIConfigurationName OBJECT-TYPE
        SYNTAX      DisplayString
        MAX-ACCESS  read-write
        STATUS      current
        DESCRIPTION                                  
            "The name identifying the VLAN to MSTI mapping. 
             Bridges must share the name and revision (see below), as well as the VLAN-to-MSTI mapping configuration in order to share spanning trees for MSTI's (Intra-region). 
             The name is at most 32 characters. "
        ::= { iSpanningTree 2 }

		-- 1.3.6.1.4.1.4756.108.60.30.3
    iMSTIConfigurationRevision OBJECT-TYPE
        SYNTAX      Integer32 (0..65535)
        MAX-ACCESS  read-write
        STATUS      current
        DESCRIPTION                                  
            "The revision of the MSTI configuration named above. This must be an integer between 0 and 65535. "
        ::= { iSpanningTree 3 }

		-- 1.3.6.1.4.1.4756.108.60.30.4
    iMSTIMappingTable OBJECT-TYPE
        SYNTAX      SEQUENCE OF IMSTIMappingEntry
        MAX-ACCESS  not-accessible
        STATUS      current
        DESCRIPTION
            "This table provides configurations of MSTI Mapping."
        ::= { iSpanningTree 4 }

    -- 1.3.6.1.4.1.4756.108.60.30.4.1
    iMSTIMappingEntry OBJECT-TYPE
        SYNTAX      IMSTIMappingEntry
        MAX-ACCESS  not-accessible
        STATUS      current
        DESCRIPTION
            "The Entry of MSTI configurations."
        INDEX { iMSTIIndex }
        ::= { iMSTIMappingTable 1 }

    IMSTIMappingEntry ::=
        SEQUENCE {
						iMSTIIndex      Integer32,
            iVLANsMapped   	DisplayString
        }
		
				-- 1.3.6.1.4.1.4756.108.60.30.4.1.1
        iMSTIIndex OBJECT-TYPE
            SYNTAX      Integer32 (1..7)
            MAX-ACCESS  read-only
            STATUS      current
            DESCRIPTION
                "The bridge instance. The CIST is not available for explicit mapping, as it will receive the VLANs not explicitly mapped. "
            ::= { iMSTIMappingEntry 1 }
            
        -- 1.3.6.1.4.1.4756.108.60.30.4.1.2
        iVLANsMapped 		OBJECT-TYPE
            SYNTAX      DisplayString
            MAX-ACCESS  read-write
            STATUS      current
            DESCRIPTION
                "The list of VLANs mapped to the MSTI. 
                 The VLANs can be given as a single (xx, xx being between 1 and 4094) VLAN, or a range (xx-yy), each of which must be separated with comma and/or space. 
                 A VLAN can only be mapped to one MSTI. 
                 An unused MSTI should just be left empty. (I.e. not having any VLANs mapped to it.) Example: 2,5,20-40.
                "
            ::= { iMSTIMappingEntry 2 }    

		-- 1.3.6.1.4.1.4756.108.60.30.5
    iMSTIPrioritiesTable OBJECT-TYPE
        SYNTAX      SEQUENCE OF IMSTIPrioritiesEntry
        MAX-ACCESS  not-accessible
        STATUS      current
        DESCRIPTION
            "This table provides configurations for MSTI Priorities."
        ::= { iSpanningTree 5 }

    -- 1.3.6.1.4.1.4756.108.60.30.5.1
    iMSTIPrioritiesEntry OBJECT-TYPE
        SYNTAX      IMSTIPrioritiesEntry
        MAX-ACCESS  not-accessible
        STATUS      current
        DESCRIPTION
            "The Entry of MSTI Priorities configurations."
        INDEX { iMSTIPrioritiesIndex }
        ::= { iMSTIPrioritiesTable 1 }

    IMSTIPrioritiesEntry ::=
        SEQUENCE {
					iMSTIPrioritiesIndex 	Integer32,
					iMSTIName 				DisplayString,
					iMSTIPriorities			INTEGER
        }

				-- 1.3.6.1.4.1.4756.108.60.30.5.1.1
        iMSTIPrioritiesIndex OBJECT-TYPE
            SYNTAX      Integer32 (1..8)
            MAX-ACCESS  read-only
            STATUS      current
            DESCRIPTION
                "MSTI Priorities Index"
            ::= { iMSTIPrioritiesEntry 1 }
            
        -- 1.3.6.1.4.1.4756.108.60.30.5.1.2
        iMSTIName OBJECT-TYPE
            SYNTAX      DisplayString
            MAX-ACCESS  read-only
            STATUS      current
            DESCRIPTION
                "MSTI Interface Name"
            ::= { iMSTIPrioritiesEntry 2 }
        
        -- 1.3.6.1.4.1.4756.108.60.30.5.1.3
        iMSTIPriorities OBJECT-TYPE
            SYNTAX      INTEGER {
	                        priority-0(1),
	                        priority-4096(2),
	                        priority-8192(3),
	                        priority-12288(4),
	                        priority-16384(5),
	                        priority-20480(6),
	                        priority-24576(7),
	                        priority-28672(8),
	                        priority-32768(9),
	                        priority-36864(10),
	                        priority-40960(11),
	                        priority-45056(12),
	                        priority-49152(13),
	                        priority-53248(14),
	                        priority-57344(15),
	                        priority-61440(16)
	                    }
            MAX-ACCESS  read-write
            STATUS      current
            DESCRIPTION
                "Controls the bridge priority. Lower numeric values have better priority. 
                 The bridge priority plus the MSTI instance number, concatenated with the 6-byte MAC address of the switch forms a Bridge Identifier. "
            ::= { iMSTIPrioritiesEntry 3 }

	-- 1.3.6.1.4.1.4756.108.60.30.6
    iCISTPorts OBJECT IDENTIFIER ::= { iSpanningTree 6 }
	
	  -- 1.3.6.1.4.1.4756.108.60.30.6.1
      iCISTAggregatedPort OBJECT-TYPE
            SYNTAX      DisplayString
            MAX-ACCESS  read-only
            STATUS      current
            DESCRIPTION
                "The switch port number of the logical STP port. "
            ::= { iCISTPorts 1 }
      
      -- 1.3.6.1.4.1.4756.108.60.30.6.2
      iCISTAggregatedSTPEnabled OBJECT-TYPE
            SYNTAX    	TruthValue
            MAX-ACCESS  read-write
            STATUS      current
            DESCRIPTION
                "Controls whether STP is enabled on this switch port.  "
            ::= { iCISTPorts 2 }
	
			-- 1.3.6.1.4.1.4756.108.60.30.6.3
      iCISTAggregatedPathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iCISTPorts 3 }
			
			-- 1.3.6.1.4.1.4756.108.60.30.6.4
      iCISTAggregatedPriority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iCISTPorts 4 }
	
			-- 1.3.6.1.4.1.4756.108.60.30.6.5
      iCISTAggregatedAdminEdge OBJECT-TYPE
            SYNTAX      INTEGER {
	                        non-edge(1),
	                        edge(2)
	                    }
            MAX-ACCESS  read-write
            STATUS      current
            DESCRIPTION
                "Operational flag describing whether the port is connecting directly to edge devices. 
                (No Bridges attached). Transition to the forwarding state is faster for edge ports (having operEdge true) than for other ports. 
                 The value of this flag is based on AdminEdge and AutoEdge fields. 
                 This flag is displayed as Edge in Monitor->Spanning Tree -> STP Detailed Bridge Status. 
                 Controls whether the operEdge flag should start as set or cleared. "
            ::= { iCISTPorts 5 }
	
			-- 1.3.6.1.4.1.4756.108.60.30.6.6
      iCISTAggregatedAutoEdge OBJECT-TYPE
            SYNTAX    	TruthValue
            MAX-ACCESS  read-write
            STATUS      current
            DESCRIPTION
                "Controls whether the bridge should enable automatic edge detection on the bridge port. 
                 This allows operEdge to be derived from whether BPDU's are received on the port or not"
            ::= { iCISTPorts 6 }
            
      -- 1.3.6.1.4.1.4756.108.60.30.6.7
      iCISTAggregatedRestrictedRole OBJECT-TYPE
            SYNTAX    	TruthValue
            MAX-ACCESS  read-write
            STATUS      current
            DESCRIPTION
                "If enabled, causes the port not to be selected as Root Port for the CIST or any MSTI, even if it has the best spanning tree priority vector. 
                 Such a port will be selected as an Alternate Port after the Root Port has been selected. 
                 If set, it can cause lack of spanning tree connectivity. 
                 It can be set by a network administrator to prevent bridges external to a core region of the network influence the spanning tree active topology, possibly because those bridges are not under the full control of the administrator. 
                 This feature is also known as Root Guard. 
								"
            ::= { iCISTPorts 7 }
            
      -- 1.3.6.1.4.1.4756.108.60.30.6.8
      iCISTAggregatedRestrictedTCN OBJECT-TYPE
            SYNTAX    	TruthValue
            MAX-ACCESS  read-write
            STATUS      current
            DESCRIPTION
                "If enabled, causes the port not to propagate received topology change notifications and topology changes to other ports. 
                 If set it can cause temporary loss of connectivity after changes in a spanning tree's active topology as a result of persistently incorrect learned station location information. 
                 It is set by a network administrator to prevent bridges external to a core region of the network, causing address flushing in that region, possibly because those bridges are not under the full control of the administrator or the physical link state of the attached LANs transits frequently. 
								"
            ::= { iCISTPorts 8 }
            
      -- 1.3.6.1.4.1.4756.108.60.30.6.9
      iCISTAggregatedBPDUGuard OBJECT-TYPE
            SYNTAX    	TruthValue
            MAX-ACCESS  read-write
            STATUS      current
            DESCRIPTION
                "If enabled, causes the port to disable itself upon receiving valid BPDU's. 
                 Contrary to the similar bridge setting, the port Edge status does not effect this setting. 
								 A port entering error-disabled state due to this setting is subject to the bridge Port Error Recovery setting as well. 
								"
            ::= { iCISTPorts 9 }
	
			-- 1.3.6.1.4.1.4756.108.60.30.6.10
      iCISTAggregatedPointToPoint OBJECT-TYPE
            SYNTAX      INTEGER {
	                        forced-true(1),
	                        forced-false(2),
	                        auto(3)
	                    }
            MAX-ACCESS  read-write
            STATUS      current
            DESCRIPTION
                "Controls whether the port connects to a point-to-point LAN rather than to a shared medium. 
                 This can be automatically determined, or forced either true or false. 
                 Transition to the forwarding state is faster for point-to-point LANs than for shared media. 
								"
            ::= { iCISTPorts 10 }
	
    -- 1.3.6.1.4.1.4756.108.60.30.6.11
    iCISTNormalPortConfigTable OBJECT-TYPE
        SYNTAX      SEQUENCE OF ICISTNormalPortConfigEntry
        MAX-ACCESS  not-accessible
        STATUS      current
        DESCRIPTION
            "This table provides CIST Normal configurations for all ports."
        ::= { iCISTPorts 11 }

    -- 1.3.6.1.4.1.4756.108.60.30.6.11.1
    iCISTNormalPortConfigEntry OBJECT-TYPE
        SYNTAX      ICISTNormalPortConfigEntry
        MAX-ACCESS  not-accessible
        STATUS      current
        DESCRIPTION
            "The Entry of CIST Normal Port Configuration."
        INDEX { iPortIndex }
        ::= { iCISTNormalPortConfigTable 1 }

    ICISTNormalPortConfigEntry ::=
        SEQUENCE {
        	iCISTPortSTPEnabled				TruthValue,
					iCISTPortPathCost		Integer32,
					iCISTPortPriority       INTEGER,
					iCISTPortAdminEdge		INTEGER,
					iCISTPortAutoEdge       TruthValue,
					iCISTPortRestrictedRole TruthValue,
					iCISTPortRestrictedTCN  TruthValue,
					iCISTPortBPDUGuard 		TruthValue,
					iCISTPortPointToPoint   INTEGER
        }
        
      
      -- 1.3.6.1.4.1.4756.108.60.30.6.11.1
      iCISTPortSTPEnabled OBJECT-TYPE
            SYNTAX    	TruthValue
            MAX-ACCESS  read-write
            STATUS      current
            DESCRIPTION
                "Controls whether STP is enabled on this switch port.  "
            ::= { iCISTNormalPortConfigEntry 1 }
	
			-- 1.3.6.1.4.1.4756.108.60.30.6.11.2
      iCISTPortPathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iCISTNormalPortConfigEntry 2 }
			
			-- 1.3.6.1.4.1.4756.108.60.30.6.11.3
      iCISTPortPriority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iCISTNormalPortConfigEntry 3 }
	
			-- 1.3.6.1.4.1.4756.108.60.30.6.11.4
      iCISTPortAdminEdge OBJECT-TYPE
            SYNTAX      INTEGER {
	                        non-edge(1),
	                        edge(2)
	                    }
            MAX-ACCESS  read-write
            STATUS      current
            DESCRIPTION
                "Operational flag describing whether the port is connecting directly to edge devices. 
                (No Bridges attached). Transition to the forwarding state is faster for edge ports (having operEdge true) than for other ports. 
                 The value of this flag is based on AdminEdge and AutoEdge fields. 
                 This flag is displayed as Edge in Monitor->Spanning Tree -> STP Detailed Bridge Status. 
                 Controls whether the operEdge flag should start as set or cleared. "
            ::= { iCISTNormalPortConfigEntry 4 }
	
			-- 1.3.6.1.4.1.4756.108.60.30.6.11.5
      iCISTPortAutoEdge OBJECT-TYPE
            SYNTAX    	TruthValue
            MAX-ACCESS  read-write
            STATUS      current
            DESCRIPTION
                "Controls whether the bridge should enable automatic edge detection on the bridge port. 
                 This allows operEdge to be derived from whether BPDU's are received on the port or not"
            ::= { iCISTNormalPortConfigEntry 5 }
            
      -- 1.3.6.1.4.1.4756.108.60.30.6.11.6
      iCISTPortRestrictedRole OBJECT-TYPE
            SYNTAX    	TruthValue
            MAX-ACCESS  read-write
            STATUS      current
            DESCRIPTION
                "If enabled, causes the port not to be selected as Root Port for the CIST or any MSTI, even if it has the best spanning tree priority vector. 
                 Such a port will be selected as an Alternate Port after the Root Port has been selected. 
                 If set, it can cause lack of spanning tree connectivity. 
                 It can be set by a network administrator to prevent bridges external to a core region of the network influence the spanning tree active topology, possibly because those bridges are not under the full control of the administrator. 
                 This feature is also known as Root Guard. 
								"
            ::= { iCISTNormalPortConfigEntry 6 }
            
      -- 1.3.6.1.4.1.4756.108.60.30.6.11.7
      iCISTPortRestrictedTCN OBJECT-TYPE
            SYNTAX    	TruthValue
            MAX-ACCESS  read-write
            STATUS      current
            DESCRIPTION
                "If enabled, causes the port not to propagate received topology change notifications and topology changes to other ports. 
                 If set it can cause temporary loss of connectivity after changes in a spanning tree's active topology as a result of persistently incorrect learned station location information. 
                 It is set by a network administrator to prevent bridges external to a core region of the network, causing address flushing in that region, possibly because those bridges are not under the full control of the administrator or the physical link state of the attached LANs transits frequently. 
								"
            ::= { iCISTNormalPortConfigEntry 7 }
            
      -- 1.3.6.1.4.1.4756.108.60.30.6.11.8
      iCISTPortBPDUGuard OBJECT-TYPE
            SYNTAX    	TruthValue
            MAX-ACCESS  read-write
            STATUS      current
            DESCRIPTION
                "If enabled, causes the port to disable itself upon receiving valid BPDU's. 
                 Contrary to the similar bridge setting, the port Edge status does not effect this setting. 
								 A port entering error-disabled state due to this setting is subject to the bridge Port Error Recovery setting as well. 
								"
            ::= { iCISTNormalPortConfigEntry 8 }
	
			-- 1.3.6.1.4.1.4756.108.60.30.6.11.9
      iCISTPortPointToPoint OBJECT-TYPE
            SYNTAX      INTEGER {
	                        forced-true(1),
	                        forced-false(2),
	                        auto(3)
	                    }
            MAX-ACCESS  read-write
            STATUS      current
            DESCRIPTION
                "Controls whether the port connects to a point-to-point LAN rather than to a shared medium. 
                 This can be automatically determined, or forced either true or false. 
                 Transition to the forwarding state is faster for point-to-point LANs than for shared media. 
								"
            ::= { iCISTNormalPortConfigEntry 9 }
            
    -- 1.3.6.1.4.1.4756.108.60.30.7
    iMSTIPortsTable OBJECT-TYPE
        SYNTAX      SEQUENCE OF IMSTIPortsEntry
        MAX-ACCESS  not-accessible
        STATUS      current
        DESCRIPTION
            "This table provides configurations for MSTI."
        ::= { iSpanningTree 7 }

    -- 1.3.6.1.4.1.4756.108.60.30.7.1
    iMSTIPortsEntry OBJECT-TYPE
        SYNTAX      IMSTIPortsEntry
        MAX-ACCESS  not-accessible
        STATUS      current
        DESCRIPTION
            "The Entry of MSTI configurations."
        INDEX { iMSTIIndex }
        ::= { iMSTIPortsTable 1 }

    IMSTIPortsEntry ::=
        SEQUENCE {
					iMSTIAggregatedPorts 		DisplayString,
					iMSTIAggregatedPathCost 	Integer32,
					iMSTIAggregatedPriority		INTEGER,
					iMSTIPort1PathCost 			Integer32,
					iMSTIPort1Priority			INTEGER,
					iMSTIPort2PathCost 			Integer32,
					iMSTIPort2Priority			INTEGER,
					iMSTIPort3PathCost 			Integer32,
					iMSTIPort3Priority			INTEGER,
					iMSTIPort4PathCost 			Integer32,
					iMSTIPort4Priority			INTEGER,
					iMSTIPort5PathCost 			Integer32,
					iMSTIPort5Priority			INTEGER,
					iMSTIPort6PathCost 			Integer32,
					iMSTIPort6Priority			INTEGER,
					iMSTIPort7PathCost 			Integer32,
					iMSTIPort7Priority			INTEGER,
					iMSTIPort8PathCost 			Integer32,
					iMSTIPort8Priority			INTEGER,
					iMSTIPort9PathCost 			Integer32,
					iMSTIPort9Priority			INTEGER,
					iMSTIPort10PathCost 		Integer32,
					iMSTIPort10Priority			INTEGER,
					iMSTIPort11PathCost 		Integer32,
					iMSTIPort11Priority			INTEGER,
					iMSTIPort12PathCost 			Integer32,
					iMSTIPort12Priority			INTEGER,
					iMSTIPort13PathCost 			Integer32,
					iMSTIPort13Priority			INTEGER,
					iMSTIPort14PathCost 			Integer32,
					iMSTIPort14Priority			INTEGER,
					iMSTIPort15PathCost 			Integer32,
					iMSTIPort15Priority			INTEGER,
					iMSTIPort16PathCost 			Integer32,
					iMSTIPort16Priority			INTEGER,
					iMSTIPort17PathCost 			Integer32,
					iMSTIPort17Priority			INTEGER,
					iMSTIPort18PathCost 			Integer32,
					iMSTIPort18Priority			INTEGER,
					iMSTIPort19PathCost 			Integer32,
					iMSTIPort19Priority			INTEGER,
					iMSTIPort20PathCost 		Integer32,
					iMSTIPort20Priority			INTEGER,
					iMSTIPort21PathCost 		Integer32,
					iMSTIPort21Priority			INTEGER,
					iMSTIPort22PathCost 		Integer32,
					iMSTIPort22Priority			INTEGER,
					iMSTIPort23PathCost 		Integer32,
					iMSTIPort23Priority			INTEGER,
					iMSTIPort24PathCost 		Integer32,
					iMSTIPort24Priority			INTEGER,
					iMSTIPort25PathCost 		Integer32,
					iMSTIPort25Priority			INTEGER,
					iMSTIPort26PathCost 		Integer32,
					iMSTIPort26Priority			INTEGER,
					iMSTIPort27PathCost 		Integer32,
					iMSTIPort27Priority			INTEGER,
					iMSTIPort28PathCost 		Integer32,
					iMSTIPort28Priority			INTEGER,
					iMSTIPort29PathCost 		Integer32,
					iMSTIPort29Priority			INTEGER																									
        }
        
        -- 1.3.6.1.4.1.4756.108.60.30.7.1.1
	      iMSTIAggregatedPorts OBJECT-TYPE
	            SYNTAX      DisplayString
	            MAX-ACCESS  read-only
	            STATUS      current
	            DESCRIPTION
	                "The switch port number of the logical STP port. "
	            ::= { iMSTIPortsEntry 1 }
        
   			-- 1.3.6.1.4.1.4756.108.60.30.7.1.2
      	iMSTIAggregatedPathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 2 }
			
				-- 1.3.6.1.4.1.4756.108.60.30.7.1.3
      	iMSTIAggregatedPriority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 3 }
            
        -- 1.3.6.1.4.1.4756.108.60.30.7.1.4
      	iMSTIPort1PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 4 }
			
				-- 1.3.6.1.4.1.4756.108.60.30.7.1.5
      	iMSTIPort1Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 5 }
            
         -- 1.3.6.1.4.1.4756.108.60.30.7.1.6
      	iMSTIPort2PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 6 }
			
				-- 1.3.6.1.4.1.4756.108.60.30.7.1.7
      	iMSTIPort2Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 7 }
            
         -- 1.3.6.1.4.1.4756.108.60.30.7.1.8
      	iMSTIPort3PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 8 }
			
				-- 1.3.6.1.4.1.4756.108.60.30.7.1.9
      	iMSTIPort3Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 9 }
            
        -- 1.3.6.1.4.1.4756.108.60.30.7.1.10
      	iMSTIPort4PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 10 }
			
				-- 1.3.6.1.4.1.4756.108.60.30.7.1.11
      	iMSTIPort4Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 11 }
            
       -- 1.3.6.1.4.1.4756.108.60.30.7.1.12
      	iMSTIPort5PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 12 }
			
				-- 1.3.6.1.4.1.4756.108.60.30.7.1.13
      	iMSTIPort5Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 13 }
            
         -- 1.3.6.1.4.1.4756.108.60.30.7.1.14
      	iMSTIPort6PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 14 }
			
				-- 1.3.6.1.4.1.4756.108.60.30.7.1.15
      	iMSTIPort6Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 15 }
            
        -- 1.3.6.1.4.1.4756.108.60.30.7.1.16
      	iMSTIPort7PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 16 }
			
				-- 1.3.6.1.4.1.4756.108.60.30.7.1.17
      	iMSTIPort7Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 17 }
            
        -- 1.3.6.1.4.1.4756.108.60.30.7.1.18
      	iMSTIPort8PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 18 }
			
				-- 1.3.6.1.4.1.4756.108.60.30.7.1.19
      	iMSTIPort8Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 19 }
            
        -- 1.3.6.1.4.1.4756.108.60.30.7.1.20
      	iMSTIPort9PathCost OBJECT-TYPE
            SYNTAX     Integer32 (0..200000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 20 }
			
				-- 1.3.6.1.4.1.4756.108.60.30.7.1.21
      	iMSTIPort9Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 21 }
            
        -- 1.3.6.1.4.1.4756.108.60.30.7.1.22
      	iMSTIPort10PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 20000000000 means path cost.
								"
            ::= { iMSTIPortsEntry 22 }
			
				-- 1.3.6.1.4.1.4756.108.60.30.7.1.23
      	iMSTIPort10Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 23 }
            
        -- 1.3.6.1.4.1.4756.108.60.30.7.1.24
      	iMSTIPort11PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 20000000000 means path cost.
								"
            ::= { iMSTIPortsEntry 24 }
			
				-- 1.3.6.1.4.1.4756.108.60.30.7.1.25
      	iMSTIPort11Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 25 }
            
        -- 1.3.6.1.4.1.4756.108.60.30.7.1.4
      	iMSTIPort12PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 26 }
			
				-- 1.3.6.1.4.1.4756.108.60.30.7.1.5
      	iMSTIPort12Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 27 }
            
         -- 1.3.6.1.4.1.4756.108.60.30.7.1.6
      	iMSTIPort13PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 28 }
			
				-- 1.3.6.1.4.1.4756.108.60.30.7.1.7
      	iMSTIPort13Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 29 }
            
         -- 1.3.6.1.4.1.4756.108.60.30.7.1.8
      	iMSTIPort14PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 30 }
			
				-- 1.3.6.1.4.1.4756.108.60.30.7.1.9
      	iMSTIPort14Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 31 }
            
        -- 1.3.6.1.4.1.4756.108.60.30.7.1.10
      	iMSTIPort15PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 32 }
			
				-- 1.3.6.1.4.1.4756.108.60.30.7.1.11
      	iMSTIPort15Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 33 }
            
       -- 1.3.6.1.4.1.4756.108.60.30.7.1.12
      	iMSTIPort16PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 34 }
			
				-- 1.3.6.1.4.1.4756.108.60.30.7.1.13
      	iMSTIPort16Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 35 }
            
         -- 1.3.6.1.4.1.4756.108.60.30.7.1.14
      	iMSTIPort17PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 36 }
			
				-- 1.3.6.1.4.1.4756.108.60.30.7.1.15
      	iMSTIPort17Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 37 }
            
        -- 1.3.6.1.4.1.4756.108.60.30.7.1.16
      	iMSTIPort18PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 38 }
			
				-- 1.3.6.1.4.1.4756.108.60.30.7.1.17
      	iMSTIPort18Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 39 }
            
        -- 1.3.6.1.4.1.4756.108.60.30.7.1.18
      	iMSTIPort19PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 40 }
			
				-- 1.3.6.1.4.1.4756.108.60.30.7.1.19
      	iMSTIPort19Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 41 }
            
        -- 1.3.6.1.4.1.4756.108.60.30.7.1.20
      	iMSTIPort20PathCost OBJECT-TYPE
            SYNTAX     Integer32 (0..200000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 42 }
			
				-- 1.3.6.1.4.1.4756.108.60.30.7.1.21
      	iMSTIPort20Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 43 }
            
        -- 1.3.6.1.4.1.4756.108.60.30.7.1.22
      	iMSTIPort21PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 20000000000 means path cost.
								"
            ::= { iMSTIPortsEntry 44 }
			
				-- 1.3.6.1.4.1.4756.108.60.30.7.1.23
      	iMSTIPort21Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 45 }
            
        -- 1.3.6.1.4.1.4756.108.60.30.7.1.24
      	iMSTIPort22PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 20000000000 means path cost.
								"
            ::= { iMSTIPortsEntry 46 }
			
				-- 1.3.6.1.4.1.4756.108.60.30.7.1.25
      	iMSTIPort22Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 47 }

        -- 1.3.6.1.4.1.4756.108.60.30.7.1.4
      	iMSTIPort23PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 48 }
			
				-- 1.3.6.1.4.1.4756.108.60.30.7.1.5
      	iMSTIPort23Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 49 }
            
         -- 1.3.6.1.4.1.4756.108.60.30.7.1.6
      	iMSTIPort24PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 50 }
			
				-- 1.3.6.1.4.1.4756.108.60.30.7.1.7
      	iMSTIPort24Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 51 }
            
         -- 1.3.6.1.4.1.4756.108.60.30.7.1.8
      	iMSTIPort25PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 52 }
			
				-- 1.3.6.1.4.1.4756.108.60.30.7.1.9
      	iMSTIPort25Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 53 }
            
        -- 1.3.6.1.4.1.4756.108.60.30.7.1.10
      	iMSTIPort26PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 54 }
			
				-- 1.3.6.1.4.1.4756.108.60.30.7.1.11
      	iMSTIPort26Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 55 }
            
       -- 1.3.6.1.4.1.4756.108.60.30.7.1.12
      	iMSTIPort27PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 56 }
			
				-- 1.3.6.1.4.1.4756.108.60.30.7.1.13
      	iMSTIPort27Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 57 }
            
         -- 1.3.6.1.4.1.4756.108.60.30.7.1.14
      	iMSTIPort28PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 58 }
			
				-- 1.3.6.1.4.1.4756.108.60.30.7.1.15
      	iMSTIPort28Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 59 }
            
        -- 1.3.6.1.4.1.4756.108.60.30.7.1.16
      	iMSTIPort29PathCost OBJECT-TYPE
            SYNTAX     Integer32 (0..2000000000)
            MAX-ACCESS  read-write
            STATUS      current
            DESCRIPTION
                "Controls the path cost incurred by the port. 
                 The Auto setting will set the path cost as appropriate by the physical link speed, using the 802.1D recommended values. 
                 Using the Specific setting, a user-defined value can be entered. 
                 The path cost is used when establishing the active topology of the network. 
                 Lower path cost ports are chosen as forwarding ports in favour of higher path cost ports.                  
                 Valid values are in the range 0 to 200000000.
                 Setting 0 means Auto path cost.
                 Setting 1 ~ 2000000000 means path cost.
								"
            ::= { iMSTIPortsEntry 60 }
			
				-- 1.3.6.1.4.1.4756.108.60.30.7.1.17
      	iMSTIPort29Priority OBJECT-TYPE
            SYNTAX      INTEGER {
	                        priority-0(1),
	                        priority-16(2),
	                        priority-32(3),
	                        priority-48(4),
	                        priority-64(5),
	                        priority-80(6),
	                        priority-96(7),
	                        priority-112(8),
	                        priority-128(9),
	                        priority-144(10),
	                        priority-160(11),
	                        priority-176(12),
	                        priority-192(13),
	                        priority-208(14),
	                        priority-224(15),
	                        priority-240(16)
	                    }
            MAX-ACCESS  read-write
            STATUS      current
            DESCRIPTION
                "Controls the port priority. This can be used to control priority of ports having identical port cost."
            ::= { iMSTIPortsEntry 61 }
            



		-- 1.3.6.1.4.1.4756.108.60.30.8
    iBridgeStatusTable OBJECT-TYPE
        SYNTAX      SEQUENCE OF IBridgeStatusEntry
        MAX-ACCESS  not-accessible
        STATUS      current
        DESCRIPTION
            "This table provides status of bridge."
        ::= { iSpanningTree 8 }

    -- 1.3.6.1.4.1.4756.108.60.30.8.1
    iBridgeStatusEntry OBJECT-TYPE
        SYNTAX      IBridgeStatusEntry
        MAX-ACCESS  not-accessible
        STATUS      current
        DESCRIPTION
            "The Entry of MSTI configurations."
        INDEX { iMSTIPrioritiesIndex }
        ::= { iBridgeStatusTable 1 }

    IBridgeStatusEntry ::=
        SEQUENCE {
						iBridgeStatusMSTIName		DisplayString,
						iBridgeID					DisplayString,
						iRootID						DisplayString,
						iRootCost					Integer32,
						iRootPort					DisplayString,
						iRegionalRoot				DisplayString,
						iInternalRootCost			Integer32,
						iTopologyFlag				DisplayString,
						iTopologyChangeCount		Integer32,
						iTopologyChangeLast     	DisplayString
        }
        
        -- 1.3.6.1.4.1.4756.108.60.30.8.1.1
        iBridgeStatusMSTIName OBJECT-TYPE
            SYNTAX      DisplayString
            MAX-ACCESS  read-only
            STATUS      current
            DESCRIPTION
                "The Bridge instance - CIST, MST1, ... "
            ::= { iBridgeStatusEntry 1 }
        
        -- 1.3.6.1.4.1.4756.108.60.30.8.1.2
        iBridgeID OBJECT-TYPE
            SYNTAX      DisplayString
            MAX-ACCESS  read-only
            STATUS      current
            DESCRIPTION
                "The Bridge ID of this Bridge instance."
            ::= { iBridgeStatusEntry 2 }
            
        -- 1.3.6.1.4.1.4756.108.60.30.8.1.3
        iRootID OBJECT-TYPE
            SYNTAX      DisplayString
            MAX-ACCESS  read-only
            STATUS      current
            DESCRIPTION
                "The Bridge ID of the currently elected root bridge. "
            ::= { iBridgeStatusEntry 3 }
            
        -- 1.3.6.1.4.1.4756.108.60.30.8.1.4
        iRootCost OBJECT-TYPE
            SYNTAX      Integer32
            MAX-ACCESS  read-only
            STATUS      current
            DESCRIPTION
                "Root Path Cost. For the Root Bridge this is zero. 
                 For all other Bridges, it is the sum of the Port Path Costs on the least cost path to the Root Bridge. "
            ::= { iBridgeStatusEntry 4 }
            
        -- 1.3.6.1.4.1.4756.108.60.30.8.1.5
        iRootPort OBJECT-TYPE
            SYNTAX      DisplayString
            MAX-ACCESS  read-only
            STATUS      current
            DESCRIPTION
                "The switch port currently assigned the root port role."
            ::= { iBridgeStatusEntry 5 }
            
        -- 1.3.6.1.4.1.4756.108.60.30.8.1.6
        iRegionalRoot OBJECT-TYPE
            SYNTAX      DisplayString
            MAX-ACCESS  read-only
            STATUS      current
            DESCRIPTION
                "The Bridge ID of the currently elected regional root bridge, inside the MSTP region of this bridge. (For the CIST instance only)."
            ::= { iBridgeStatusEntry 6 }
            
        -- 1.3.6.1.4.1.4756.108.60.30.8.1.7
        iInternalRootCost OBJECT-TYPE
            SYNTAX      Integer32
            MAX-ACCESS  read-only
            STATUS      current
            DESCRIPTION
                "The Regional Root Path Cost. For the Regional Root Bridge this is zero. 
                 For all other CIST instances in the same MSTP region, 
                 it is the sum of the Internal Port Path Costs on the least cost path to the Internal Root Bridge. (For the CIST instance only). "
            ::= { iBridgeStatusEntry 7 }
            
        -- 1.3.6.1.4.1.4756.108.60.30.8.1.8
        iTopologyFlag OBJECT-TYPE
            SYNTAX      DisplayString
            MAX-ACCESS  read-only
            STATUS      current
            DESCRIPTION
                "The current state of the Topology Change Flag of this Bridge instance. "
            ::= { iBridgeStatusEntry 8 }
            
       	-- 1.3.6.1.4.1.4756.108.60.30.8.1.9
        iTopologyChangeCount OBJECT-TYPE
            SYNTAX      Integer32
            MAX-ACCESS  read-only
            STATUS      current
            DESCRIPTION
                "The number of times where the topology change flag has been set (during a one-second interval). "
            ::= { iBridgeStatusEntry 9 }
        
        -- 1.3.6.1.4.1.4756.108.60.30.8.1.10
        iTopologyChangeLast OBJECT-TYPE
            SYNTAX      DisplayString
            MAX-ACCESS  read-only
            STATUS      current
            DESCRIPTION
                "The time passed since the Topology Flag was last set."
            ::= { iBridgeStatusEntry 10 }

		-- 1.3.6.1.4.1.4756.108.60.30.9
    iPortsAndAggregationsStateTable OBJECT-TYPE
        SYNTAX      SEQUENCE OF IPortsAndAggregationsStateEntry
        MAX-ACCESS  not-accessible
        STATUS      current
        DESCRIPTION
            "This table provides detailed information on a single STP bridge instance, along with port state for all active ports associateds for all ports."
        ::= { iSpanningTree 9 }

    -- 1.3.6.1.4.1.4756.108.60.30.9.1
    iPortsAndAggregationsStateEntry OBJECT-TYPE
        SYNTAX      IPortsAndAggregationsStateEntry
        MAX-ACCESS  not-accessible
        STATUS      current
        DESCRIPTION
            "The Entry of CIST Ports & Aggregations State"
        INDEX { iMSTIPrioritiesIndex, iPortIndex }
        ::= { iPortsAndAggregationsStateTable 1 }

    IPortsAndAggregationsStateEntry ::=
        SEQUENCE {              
        				iPortMSTIName			DisplayString,
						iPortID					DisplayString,
						iPortRole				DisplayString,
						iPortState				DisplayString,
						iPortPathCost			DisplayString,
						iPortEdge				DisplayString,
						iPortPointToPoint		DisplayString,
						iPortUpTime				DisplayString
        }
        
        -- 1.3.6.1.4.1.4756.108.60.30.8.1.1
        iPortMSTIName OBJECT-TYPE
            SYNTAX      DisplayString
            MAX-ACCESS  read-only
            STATUS      current
            DESCRIPTION
                "The Bridge instance - CIST, MST1, ... "
            ::= { iPortsAndAggregationsStateEntry 1 }

        
        -- 1.3.6.1.4.1.4756.108.60.30.9.1.2
        iPortID OBJECT-TYPE
            SYNTAX      DisplayString
            MAX-ACCESS  read-only
            STATUS      current
            DESCRIPTION
                "The port id as used by the STP protocol. This is the priority part and the logical port index of the bridge port."
            ::= { iPortsAndAggregationsStateEntry 2 }
            
        -- 1.3.6.1.4.1.4756.108.60.30.9.1.3
        iPortRole OBJECT-TYPE
            SYNTAX      DisplayString
            MAX-ACCESS  read-only
            STATUS      current
            DESCRIPTION
                "The current STP port role. The port role can be one of the following values: AlternatePort BackupPort RootPort DesignatedPort. "
            ::= { iPortsAndAggregationsStateEntry 3 }
            
        -- 1.3.6.1.4.1.4756.108.60.30.9.1.4
        iPortState OBJECT-TYPE
            SYNTAX      DisplayString
            MAX-ACCESS  read-only
            STATUS      current
            DESCRIPTION
                "The current STP port state. The port state can be one of the following values: Discarding Learning Forwarding. "
            ::= { iPortsAndAggregationsStateEntry 4 }
            
        -- 1.3.6.1.4.1.4756.108.60.30.9.1.5
        iPortPathCost OBJECT-TYPE
            SYNTAX      DisplayString
            MAX-ACCESS  read-only
            STATUS      current
            DESCRIPTION
                "The current STP port path cost. This will either be a value computed from the Auto setting, or any explicitly configured value."
            ::= { iPortsAndAggregationsStateEntry 5 }
            
        -- 1.3.6.1.4.1.4756.108.60.30.9.1.6
        iPortEdge OBJECT-TYPE
            SYNTAX      DisplayString
            MAX-ACCESS  read-only
            STATUS      current
            DESCRIPTION
                "The current STP port (operational) Edge Flag. An Edge Port is a switch port to which no Bridges are attached. 
                 The flag may be automatically computed or explicitly configured. 
                 Each Edge Port transits directly to the Forwarding Port State, since there is no possibility of it participating in a loop. "
            ::= { iPortsAndAggregationsStateEntry 6 }
            
        -- 1.3.6.1.4.1.4756.108.60.30.9.1.7
        iPortPointToPoint OBJECT-TYPE
            SYNTAX      DisplayString
            MAX-ACCESS  read-only
            STATUS      current
            DESCRIPTION
                "The current STP port point-to-point flag. A point-to-point port connects to a non-shared LAN media. 
                 The flag may be automatically computed or explicitly configured. 
                 The point-to-point properties of a port affect how fast it can transit to STP state. 
                "
            ::= { iPortsAndAggregationsStateEntry 7 }
            
        -- 1.3.6.1.4.1.4756.108.60.30.9.1.8
        iPortUpTime OBJECT-TYPE
            SYNTAX      DisplayString
            MAX-ACCESS  read-only
            STATUS      current
            DESCRIPTION
                "The time since the bridge port was last initialized."
            ::= { iPortsAndAggregationsStateEntry 8 }
            
		-- 1.3.6.1.4.1.4756.108.60.30.10
    iSTPPortStatusTable OBJECT-TYPE
        SYNTAX      SEQUENCE OF ISTPPortStatusEntry
        MAX-ACCESS  not-accessible
        STATUS      current
        DESCRIPTION
            "The table displays the STP CIST port status for physical ports of the currently selected switch."
        ::= { iSpanningTree 10 }

    -- 1.3.6.1.4.1.4756.108.60.30.10.1
    iSTPPortStatusEntry OBJECT-TYPE
        SYNTAX      ISTPPortStatusEntry
        MAX-ACCESS  not-accessible
        STATUS      current
        DESCRIPTION
            "The entry displays the STP CIST port status for physical ports of the currently selected switch."
        INDEX { iPortIndex }
        ::= { iSTPPortStatusTable 1 }

    ISTPPortStatusEntry ::=
        SEQUENCE {
						iPortCISTRole						DisplayString,
						iPortCISTState					DisplayString,
						iPortCISTUptime					DisplayString
        }
        
        -- 1.3.6.1.4.1.4756.108.60.30.10.1.1
        iPortCISTRole OBJECT-TYPE
            SYNTAX      DisplayString
            MAX-ACCESS  read-only
            STATUS      current
            DESCRIPTION
                "The current STP port role of the CIST port. 
                 The port role can be one of the following values: AlternatePort BackupPort RootPort DesignatedPort Disabled.
                "
            ::= { iSTPPortStatusEntry 1 }
            
        -- 1.3.6.1.4.1.4756.108.60.30.10.1.2
        iPortCISTState OBJECT-TYPE
            SYNTAX      DisplayString
            MAX-ACCESS  read-only
            STATUS      current
            DESCRIPTION
                "The current STP port state of the CIST port. The port state can be one of the following values: Discarding Learning Forwarding."
            ::= { iSTPPortStatusEntry 2 }
            
        -- 1.3.6.1.4.1.4756.108.60.30.10.1.3
        iPortCISTUptime OBJECT-TYPE
            SYNTAX      DisplayString
            MAX-ACCESS  read-only
            STATUS      current
            DESCRIPTION
                "The time since the bridge port was last initialized."
            ::= { iSTPPortStatusEntry 3 }
    
    -- 1.3.6.1.4.1.4756.108.60.30.11
    iSTPStatistics OBJECT IDENTIFIER ::= { iSpanningTree 11 }

	-- 1.3.6.1.4.1.4756.108.60.30.11.1
      iSTPStatisticsClear OBJECT-TYPE
      		SYNTAX      INTEGER {
                        trigger(1),
                        normal(2)
                    }
            MAX-ACCESS  read-write
            STATUS      current
            DESCRIPTION
                "Reset the counters"
            ::= { iSTPStatistics 1 }
            
	-- 1.3.6.1.4.1.4756.108.60.30.11.2
    iSTPStatisticsTable OBJECT-TYPE
        SYNTAX      SEQUENCE OF ISTPStatisticsEntry
        MAX-ACCESS  not-accessible
        STATUS      current
        DESCRIPTION
            "The table displays the STP port statistics counters of bridge ports in the currently selected switch."
        ::= { iSTPStatistics 2 }

    -- 1.3.6.1.4.1.4756.108.60.30.11.2.1
    iSTPStatisticsEntry OBJECT-TYPE
        SYNTAX      ISTPStatisticsEntry
        MAX-ACCESS  not-accessible
        STATUS      current
        DESCRIPTION
            "The entry displays the STP port statistics counters of bridge ports in the currently selected switch."
        INDEX { iPortIndex }
        ::= { iSTPStatisticsTable 1 }

    ISTPStatisticsEntry ::=
        SEQUENCE {
						iTransmittedMSTP				Counter32,
						iTransmittedRSTP				Counter32,
						iTransmittedSTP					Counter32,
						iTransmittedTCN					Counter32,
						iReceivedMSTP					Counter32,
						iReceivedRSTP					Counter32,
						iReceivedSTP					Counter32,
						iReceivedTCN					Counter32,
						iDiscardedUnknown				Counter32,
						iDiscardedIllegal				Counter32
        		}
        
        -- 1.3.6.1.4.1.4756.108.60.30.11.2.1.1    
        iTransmittedMSTP OBJECT-TYPE
            SYNTAX      Counter32
            MAX-ACCESS  read-only
            STATUS      current
            DESCRIPTION
                "The number of MSTP BPDU's transmitted on the port."
            ::= { iSTPStatisticsEntry 1 }
            
        -- 1.3.6.1.4.1.4756.108.60.30.11.2.1.2    
        iTransmittedRSTP OBJECT-TYPE
            SYNTAX      Counter32
            MAX-ACCESS  read-only
            STATUS      current
            DESCRIPTION
                "The number of RSTP BPDU's transmitted on the port."
            ::= { iSTPStatisticsEntry 2 }
            
        -- 1.3.6.1.4.1.4756.108.60.30.11.2.1.3
        iTransmittedSTP OBJECT-TYPE
            SYNTAX      Counter32
            MAX-ACCESS  read-only
            STATUS      current
            DESCRIPTION
                "The number of legacy STP Configuration BPDU's transmitted on the port."
            ::= { iSTPStatisticsEntry 3 }
            
        -- 1.3.6.1.4.1.4756.108.60.30.11.2.1.4
        iTransmittedTCN OBJECT-TYPE
            SYNTAX      Counter32
            MAX-ACCESS  read-only
            STATUS      current
            DESCRIPTION
                "The number of (legacy) Topology Change Notification BPDU's transmitted on the port. "
            ::= { iSTPStatisticsEntry 4 }
            
        -- 1.3.6.1.4.1.4756.108.60.30.11.2.1.5    
        iReceivedMSTP OBJECT-TYPE
            SYNTAX      Counter32
            MAX-ACCESS  read-only
            STATUS      current
            DESCRIPTION
                "The number of MSTP BPDU's received on the port."
            ::= { iSTPStatisticsEntry 5 }
            
        -- 1.3.6.1.4.1.4756.108.60.30.11.2.1.6
        iReceivedRSTP OBJECT-TYPE
            SYNTAX      Counter32
            MAX-ACCESS  read-only
            STATUS      current
            DESCRIPTION
                "The number of RSTP BPDU's received on the port."
            ::= { iSTPStatisticsEntry 6 }
            
        -- 1.3.6.1.4.1.4756.108.60.30.11.2.1.7
        iReceivedSTP OBJECT-TYPE
            SYNTAX      Counter32
            MAX-ACCESS  read-only
            STATUS      current
            DESCRIPTION
                "The number of legacy STP Configuration BPDU's received on the port."
            ::= { iSTPStatisticsEntry 7 }
            
        -- 1.3.6.1.4.1.4756.108.60.30.11.2.1.8
        iReceivedTCN OBJECT-TYPE
            SYNTAX      Counter32
            MAX-ACCESS  read-only
            STATUS      current
            DESCRIPTION
                "The number of (legacy) Topology Change Notification BPDU's received on the port. "
            ::= { iSTPStatisticsEntry 8 }
        
        -- 1.3.6.1.4.1.4756.108.60.30.11.2.1.9
        iDiscardedUnknown OBJECT-TYPE
            SYNTAX      Counter32
            MAX-ACCESS  read-only
            STATUS      current
            DESCRIPTION
                "The number of unknown Spanning Tree BPDU's received (and discarded) on the port. "
            ::= { iSTPStatisticsEntry 9 }
            
        -- 1.3.6.1.4.1.4756.108.60.30.11.2.1.10
        iDiscardedIllegal OBJECT-TYPE
            SYNTAX      Counter32
            MAX-ACCESS  read-only
            STATUS      current
            DESCRIPTION
                "The number of illegal Spanning Tree BPDU's received (and discarded) on the port. "
            ::= { iSTPStatisticsEntry 10 }            

-- MEP
    
    -- 1.3.6.1.4.1.4756.108.60.40                        
    iMEP  OBJECT IDENTIFIER ::= { iRedundancy 40 }
       
    -- 1.3.6.1.4.1.4756.108.60.40.1
    iAddNewMEP OBJECT-TYPE
        SYNTAX      DisplayString
        MAX-ACCESS  read-write
        STATUS      current
        DESCRIPTION
            "Added a new instance of MEP.
             Syntax: <Instance> <Flow Instance> <Tagged ID>
           	 Instance range: 1 ~ 100
             Flow Instance : Switch port number
             Tagged ID     : 1 ~ 4095
            "
        ::= { iMEP 1 }
        
     -- 1.3.6.1.4.1.4756.108.60.40.2
    iDeleteMEP OBJECT-TYPE
        SYNTAX      DisplayString
        MAX-ACCESS  read-write
        STATUS      current
        DESCRIPTION
            "Deleted a instance of MEP.
            	Syntax: <Instance>
            "
        ::= { iMEP 2 }
        
    -- 1.3.6.1.4.1.4756.108.60.40.3
    iMEPConfigTable OBJECT-TYPE
        SYNTAX      SEQUENCE OF IMEPConfigEntry
        MAX-ACCESS  not-accessible
        STATUS      current
        DESCRIPTION
            "The Maintenance Entity Point instances Table."
        ::= { iMEP 3 }
     
     -- 1.3.6.1.4.1.4756.108.60.40.3.1
    iMEPConfigEntry OBJECT-TYPE
        SYNTAX      IMEPConfigEntry
        MAX-ACCESS  not-accessible
        STATUS      current
        DESCRIPTION
            "The Maintenance Entity Point instances Entry."
        INDEX { iMEPInstanceIndex }
        ::= { iMEPConfigTable 1 }

    IMEPConfigEntry ::= 
    SEQUENCE {
        	iMEPInstanceIndex		  Integer32,
            iMEPDomain      	  	  INTEGER,
            iMEPMode				  INTEGER,
            iMEPDirection			  INTEGER,
            iMEPResidencePort		  Integer32,
            iMEPFlowInstance		  Integer32,
			iMEPThisMAC				  DisplayString,
			iMEPAlarm				  INTEGER,
			iMEPLevel				  Integer32,
			iMEPFormat				  INTEGER,
			iMEPDomainName			  DisplayString,
			iMEGID				  	  DisplayString,
			iMEPID                    Integer32,
			iMEPTaggedID			  Integer32,
			icLevel					  INTEGER,
			icMEG					  INTEGER,
			icMEP					  INTEGER,
			icAIS					  INTEGER,
			icLCK					  INTEGER,
			icSSF					  INTEGER,
			iaBLK					  INTEGER,
			iaTSF 					  INTEGER
        }
        
    	-- 1.3.6.1.4.1.4756.108.60.40.3.1.1    
        iMEPInstanceIndex OBJECT-TYPE
         	SYNTAX Integer32 (1..100)
            MAX-ACCESS  read-only
            STATUS      current
            DESCRIPTION
                "The ID of the MEP. Click on the ID of a MEP."
            ::= { iMEPConfigEntry 1 }
            
        -- 1.3.6.1.4.1.4756.108.60.40.3.1.2
        iMEPDomain OBJECT-TYPE
         	SYNTAX INTEGER {
         					  port(1)
         				   }
            MAX-ACCESS  read-only
            STATUS      current
            DESCRIPTION
                "Port: This is a MEP in the Port Domain. 'Flow Instance' is a Port."
            ::= { iMEPConfigEntry 2 }
            
        -- 1.3.6.1.4.1.4756.108.60.40.3.1.3
        iMEPMode OBJECT-TYPE
         	SYNTAX INTEGER {
         						mep(1),
         						mip(2)
         				   }
            MAX-ACCESS  read-only
            STATUS      current
            DESCRIPTION
                "MEP: This is a Maintenance Entity End Point.
				 MIP: This is a Maintenance Entity Intermediate Point.
                "
            ::= { iMEPConfigEntry 3 }
            
        -- 1.3.6.1.4.1.4756.108.60.40.3.1.4
        iMEPDirection OBJECT-TYPE
         	SYNTAX INTEGER {
         						down(1),
         						up(2)
         				   }
            MAX-ACCESS  read-only
            STATUS      current
            DESCRIPTION
                "Ingress: This is a Ingress (down) MEP - monitoring ingress traffic on 'Residence Port'.
				 Egress: This is a Egress (up) MEP - monitoring egress traffic on 'Residence Port'.
                "
            ::= { iMEPConfigEntry 4 }
            
        -- 1.3.6.1.4.1.4756.108.60.40.3.1.5
        iMEPResidencePort OBJECT-TYPE
         	SYNTAX Integer32 (1..11)
            MAX-ACCESS  read-only
            STATUS      current
            DESCRIPTION
                "The port where MEP is monitoring - see 'iMEPDirection'."
            ::= { iMEPConfigEntry 5 }

		-- 1.3.6.1.4.1.4756.108.60.40.3.1.6
        iMEPFlowInstance OBJECT-TYPE
         	SYNTAX Integer32 (1..11)
            MAX-ACCESS  read-only
            STATUS      current
            DESCRIPTION
                "The MEP is related to this flow - See 'iMEPDomain'."
            ::= { iMEPConfigEntry 6 }
            
        -- 1.3.6.1.4.1.4756.108.60.40.3.1.7
        iMEPThisMAC OBJECT-TYPE
         	SYNTAX DisplayString
            MAX-ACCESS  read-only
            STATUS      current
            DESCRIPTION
                "The MAC of this MEP - can be used by other MEP when unicast is selected (Info only)."
            ::= { iMEPConfigEntry 7 }
            
        -- 1.3.6.1.4.1.4756.108.60.40.3.1.8
        iMEPAlarm OBJECT-TYPE
         	SYNTAX INTEGER {
         						active(1),
         						inactive(2)
         				   }
            MAX-ACCESS  read-only
            STATUS      current
            DESCRIPTION
                "There is an active alarm on the MEP."
            ::= { iMEPConfigEntry 8 }
        
        -- 1.3.6.1.4.1.4756.108.60.40.3.1.9
        iMEPLevel OBJECT-TYPE
         	SYNTAX Integer32 (0..7)
            MAX-ACCESS  read-write
            STATUS      current
            DESCRIPTION
                "The MEG level of this MEP."
            ::= { iMEPConfigEntry 9 }

        -- 1.3.6.1.4.1.4756.108.60.40.3.1.10
        iMEPFormat OBJECT-TYPE
         	SYNTAX INTEGER {
         						itu-icc(1),
         						ieee-string(2),
         						itu-cc-icc(3)
         				   }
            MAX-ACCESS  read-write
            STATUS      current
            DESCRIPTION
                "This is the configuration of the two possible Maintenance Association Identifier formats. 
				 ITU ICC: This is defined by ITU (Y1731 Fig. A3). 'Domain Name' is not used. 'MEG id' must be max. 13 char.
				 IEEE String: This is defined by IEEE (802.1ag Section 21.6.5). 'Domain Name' can be max. 16 char. 'MEG id' (Short MA Name) can be max. 16 char.
				 ITU CC ICC: This is defined by ITU (Y1731 Fig. A5). 'Domain Name' is not used. 'MEG id' must be max. 15 char.
				"
            ::= { iMEPConfigEntry 10 }
        
        -- 1.3.6.1.4.1.4756.108.60.40.3.1.11   
        iMEPDomainName OBJECT-TYPE
         	SYNTAX DisplayString
            MAX-ACCESS  read-write
            STATUS      current
            DESCRIPTION
                "This is the IEEE Maintenance Domain Name and is only used in case of 'IEEE String' format. 
                 This string can be empty giving Maintenance Domain Name Format 1 - Not present. This can be max 16 char. 
				"
            ::= { iMEPConfigEntry 11 }
            
        -- 1.3.6.1.4.1.4756.108.60.40.3.1.12
        iMEGID OBJECT-TYPE
         	SYNTAX DisplayString
            MAX-ACCESS  read-write
            STATUS      current
            DESCRIPTION
                "This is either ITU MEG ID or IEEE Short MA Name - depending on 'Format'. See 'Format'. 
                 In case of ITU ICC format this must be 13 char. In case of ITU CC ICC format this must be 15 char. 
                 In case of IEEE String format this can be max 16 char. 
				"
            ::= { iMEPConfigEntry 12 }
            
        -- 1.3.6.1.4.1.4756.108.60.40.3.1.13
        iMEPID OBJECT-TYPE
         	SYNTAX Integer32 (0..8191)
            MAX-ACCESS  read-write
            STATUS      current
            DESCRIPTION
                "This value will become the transmitted two byte CCM MEP ID."
            ::= { iMEPConfigEntry 13 }
            
        -- 1.3.6.1.4.1.4756.108.60.40.3.1.14
        iMEPTaggedID OBJECT-TYPE
         	SYNTAX Integer32 (0..4095)
            MAX-ACCESS  read-write
            STATUS      current
            DESCRIPTION
                "This value will be the VID of a TAG added to the OAM PDU."
            ::= { iMEPConfigEntry 14 }
        
        -- 1.3.6.1.4.1.4756.108.60.40.3.1.15
        icLevel OBJECT-TYPE
         	SYNTAX INTEGER {
         						success(1),
         						fail(2)
         				   }
            MAX-ACCESS  read-only
            STATUS      current
            DESCRIPTION
                "Fault Cause indicating that a CCM is received with a lower level than the configured for this MEP."
            ::= { iMEPConfigEntry 15 }
            
        -- 1.3.6.1.4.1.4756.108.60.40.3.1.16
        icMEG OBJECT-TYPE
         	SYNTAX INTEGER {
         						success(1),
         						fail(2)
         				   }
            MAX-ACCESS  read-only
            STATUS      current
            DESCRIPTION
                "Fault Cause indicating that a CCM is received with a MEG ID different from configured for this MEP."
            ::= { iMEPConfigEntry 16 }
            
        -- 1.3.6.1.4.1.4756.108.60.40.3.1.17
        icMEP OBJECT-TYPE
         	SYNTAX INTEGER {
         						success(1),
         						fail(2)
         				   }
            MAX-ACCESS  read-only
            STATUS      current
            DESCRIPTION
                "Fault Cause indicating that a CCM is received with a MEP ID different from all 'Peer MEP ID' configured for this MEP."
            ::= { iMEPConfigEntry 17 }
        
        -- 1.3.6.1.4.1.4756.108.60.40.3.1.18
        icAIS OBJECT-TYPE
         	SYNTAX INTEGER {
         						success(1),
         						fail(2)
         				   }
            MAX-ACCESS  read-only
            STATUS      current
            DESCRIPTION
                "Fault Cause indicating that AIS PDU is received."
            ::= { iMEPConfigEntry 18 }
        
        -- 1.3.6.1.4.1.4756.108.60.40.3.1.19
        icLCK OBJECT-TYPE
         	SYNTAX INTEGER {
         						success(1),
         						fail(2)
         				   }
            MAX-ACCESS  read-only
            STATUS      current
            DESCRIPTION
                "Fault Cause indicating that LCK PDU is received."
            ::= { iMEPConfigEntry 19 }
        
        -- 1.3.6.1.4.1.4756.108.60.40.3.1.20
        icSSF OBJECT-TYPE
         	SYNTAX INTEGER {
         						success(1),
         						fail(2)
         				   }
            MAX-ACCESS  read-only
            STATUS      current
            DESCRIPTION
                "Fault Cause indicating that server layer is indicating Signal Fail."
            ::= { iMEPConfigEntry 20 }
        
        -- 1.3.6.1.4.1.4756.108.60.40.3.1.21
        iaBLK OBJECT-TYPE
         	SYNTAX INTEGER {
         						success(1),
         						fail(2)
         				   }
            MAX-ACCESS  read-only
            STATUS      current
            DESCRIPTION
                "The consequent action of blocking service frames in this flow is active."
            ::= { iMEPConfigEntry 21 }
            
        -- 1.3.6.1.4.1.4756.108.60.40.3.1.22
        iaTSF OBJECT-TYPE
         	SYNTAX INTEGER {
         						success(1),
         						fail(2)
         				   }
            MAX-ACCESS  read-only
            STATUS      current
            DESCRIPTION
                "The consequent action of indicating Trail Signal Fail to-wards protection is active."
            ::= { iMEPConfigEntry 22 }
                     
    -- 1.3.6.1.4.1.4756.108.60.40.4
    iAddPeerMEPIDTable OBJECT-TYPE
        SYNTAX      SEQUENCE OF IAddPeerMEPIDEntry
        MAX-ACCESS  not-accessible
        STATUS      current
        DESCRIPTION
            "Added the Peer MEP ID Table."
        ::= { iMEP 4 }
     
    -- 1.3.6.1.4.1.4756.108.60.40.4.1
    iAddPeerMEPIDEntry OBJECT-TYPE
        SYNTAX      IAddPeerMEPIDEntry
        MAX-ACCESS  not-accessible
        STATUS      current
        DESCRIPTION
            "Added the Peer MEP ID Entry."
        INDEX { iMEPInstanceIndex }
        ::= { iAddPeerMEPIDTable 1 }

    IAddPeerMEPIDEntry ::= 
    SEQUENCE {
    			iAddNewPeerMEPID	DisplayString
    		 }
    
    	-- 1.3.6.1.4.1.4756.108.60.40.4.1.1
	    iAddNewPeerMEPID OBJECT-TYPE
	        SYNTAX      DisplayString
	        MAX-ACCESS  read-write
	        STATUS      current
	        DESCRIPTION
	            "Added a new peer MEP id.
	            	Syntax: <MEP id>
	            	MEP id range: 1 ~ 8191
            	"
	        ::= { iAddPeerMEPIDEntry 1 }
    
	-- 1.3.6.1.4.1.4756.108.60.40.5
    iPeerMEPConfigTable OBJECT-TYPE
        SYNTAX      SEQUENCE OF IPeerMEPConfigEntry
        MAX-ACCESS  not-accessible
        STATUS      current
        DESCRIPTION
            "The Peer MEP config Table."
        ::= { iMEP 5 }
     
    -- 1.3.6.1.4.1.4756.108.60.40.5.1
    iPeerMEPConfigEntry OBJECT-TYPE
        SYNTAX      IPeerMEPConfigEntry
        MAX-ACCESS  not-accessible
        STATUS      current
        DESCRIPTION
            "The Peer MEP config Entry."
        INDEX { iMEPInstanceIndex , iPeerMEPIndex }
        ::= { iPeerMEPConfigTable 1 }

    IPeerMEPConfigEntry ::= 
    SEQUENCE {
    		iPeerMEPIndex       Integer32,
    		iDeletePeerMEPID	TruthValue,
    		iPeerMEPID			Integer32,
    		iUnicastPeerMAC		DisplayString,
			icLOC 				INTEGER,
			icRDI 				INTEGER,
			icPeriod 			INTEGER,
			icPriority 			INTEGER
    	}
    	
    	-- 1.3.6.1.4.1.4756.108.60.40.5.1.1
        iPeerMEPIndex OBJECT-TYPE
         	SYNTAX Integer32 (1..5)
            MAX-ACCESS  read-only
            STATUS      current
            DESCRIPTION
                "This value will become an expected MEP ID in a received CCM - see 'cMEP'."
            ::= { iPeerMEPConfigEntry 1 }
    	
    	-- 1.3.6.1.4.1.4756.108.60.40.5.1.2
		iDeletePeerMEPID OBJECT-TYPE
		    SYNTAX      TruthValue
		    MAX-ACCESS  read-write
		    STATUS      current
		    DESCRIPTION
		        "Deleted this peer MEP id."
		    ::= { iPeerMEPConfigEntry 2 }
		    
    	-- 1.3.6.1.4.1.4756.108.60.40.5.1.3
        iPeerMEPID OBJECT-TYPE
         	SYNTAX Integer32 (1..8191)
            MAX-ACCESS  read-only
            STATUS      current
            DESCRIPTION
                "This value will become an expected MEP ID in a received CCM - see 'cMEP'."
            ::= { iPeerMEPConfigEntry 3 }
        
        
		    
        -- 1.3.6.1.4.1.4756.108.60.40.5.1.4
        iUnicastPeerMAC OBJECT-TYPE
         	SYNTAX DisplayString
            MAX-ACCESS  read-write
            STATUS      current
            DESCRIPTION
                "This MAC will be used when unicast is selected with this peer MEP. 
                 Also this MAC is used to create HW checking of receiving CCM PDU (LOC detection) from this MEP.
                "
            ::= { iPeerMEPConfigEntry 4 }
            
        -- 1.3.6.1.4.1.4756.108.60.40.5.1.5
        icLOC OBJECT-TYPE
         	SYNTAX INTEGER {
         						success(1),
         						fail(2)
         				   }
            MAX-ACCESS  read-only
            STATUS      current
            DESCRIPTION
                "Fault Cause indicating that no CCM has been received (in 3,5 periods) - from this peer MEP."
            ::= { iPeerMEPConfigEntry 5 }
        
        -- 1.3.6.1.4.1.4756.108.60.40.5.1.6
        icRDI OBJECT-TYPE
         	SYNTAX INTEGER {
         						success(1),
         						fail(2)
         				   }
            MAX-ACCESS  read-only
            STATUS      current
            DESCRIPTION
                "Fault Cause indicating that a CCM is received with Remote Defect Indication - from this peer MEP."
            ::= { iPeerMEPConfigEntry 6 }
            
        -- 1.3.6.1.4.1.4756.108.60.40.5.1.7
        icPeriod OBJECT-TYPE
         	SYNTAX INTEGER {
         						success(1),
         						fail(2)
         				   }
            MAX-ACCESS  read-only
            STATUS      current
            DESCRIPTION
                "Fault Cause indicating that a CCM is received with a period different what is configured for this MEP - from this peer MEP."
            ::= { iPeerMEPConfigEntry 7 }

        -- 1.3.6.1.4.1.4756.108.60.40.5.1.8
        icPriority OBJECT-TYPE
         	SYNTAX INTEGER {
         						success(1),
         						fail(2)
         				   }
            MAX-ACCESS  read-only
            STATUS      current
            DESCRIPTION
                "Fault Cause indicating that a CCM is received with a priority different what is configured for this MEP - from this peer MEP."
            ::= { iPeerMEPConfigEntry 8 }

		-- 1.3.6.1.4.1.4756.108.60.40.6
    iMEPFunctionalConfigTable OBJECT-TYPE
        SYNTAX      SEQUENCE OF IMEPFunctionalConfigEntry
        MAX-ACCESS  not-accessible
        STATUS      current
        DESCRIPTION
            "The Peer MEP config Table."
        ::= { iMEP 6 }
     
    -- 1.3.6.1.4.1.4756.108.60.40.6.1
    iMEPFunctionalConfigEntry OBJECT-TYPE
        SYNTAX      IMEPFunctionalConfigEntry
        MAX-ACCESS  not-accessible
        STATUS      current
        DESCRIPTION
            "The Peer MEP config Entry."
        INDEX { iMEPInstanceIndex }
        ::= { iMEPFunctionalConfigTable 1 }

    IMEPFunctionalConfigEntry ::= 
    SEQUENCE {
    			iContinuityCheckEnable			TruthValue,
    			iContinuityCheckPriority		Integer32,
    			iContinuityCheckFrameRate		INTEGER,
    			iAPSProtocolEnable				TruthValue,
    			iAPSProtocolPriority			Integer32,
    			iAPSProtocolCast				INTEGER,
    			iAPSProtocolType				INTEGER,
    			iAPSProtocolLastOctet			Integer32
    		}
    		
    		-- 1.3.6.1.4.1.4756.108.60.40.6.1.1
        iContinuityCheckEnable OBJECT-TYPE
            SYNTAX      TruthValue
            MAX-ACCESS  read-write
            STATUS      current
            DESCRIPTION
                "Continuity Check based on transmitting/receiving CCM PDU can be enabled/disabled. 
                 The CCM PDU is always transmitted as Multi-cast Class 1."
            ::= { iMEPFunctionalConfigEntry 1 } 
            
        -- 1.3.6.1.4.1.4756.108.60.40.6.1.2
        iContinuityCheckPriority OBJECT-TYPE
            SYNTAX      Integer32 (0..9) 
            MAX-ACCESS  read-write
            STATUS      current
            DESCRIPTION
                "The priority to be inserted as PCP bits in TAG (if any).
                 In case of enable of Continuity Check and Loss Measurement both implemented on SW based CCM, 'Priority' has to be the same."
            ::= { iMEPFunctionalConfigEntry 2 }
        
        -- 1.3.6.1.4.1.4756.108.60.40.6.1.3
        iContinuityCheckFrameRate OBJECT-TYPE
            SYNTAX      INTEGER {
                            tx-300FramesPerSecond(1),
                            tx-100FramesPerSecond(2),
                            tx-10FramesPerSecond(3),
                            tx-1FramesPerSecond(4),
                            tx-6FramesPerMinute(5),
                            tx-1FramesPerMinute(6),
                            tx-6FramesPerHour(7)
                        }
            MAX-ACCESS  read-write
            STATUS      current
            DESCRIPTION
                "Selecting the frame rate of CCM PDU. This is the inverse of transmission period as described in Y.1731. 
                 This value has the following uses: 
				 * The transmission rate of the CCM PDU.
				 * Fault Cause cLOC is declared if no CCM PDU has been received within 3.5 periods - see 'cLOC'.
				 * Fault Cause cPeriod is declared if a CCM PDU has been received with different period - see 'cPeriod'.
				 
				 Selecting 300f/sec or 100f/sec will configure HW based CCM (if possible). 
				 Selecting other frame rates will configure SW based CCM. 
				 In case of enable of Continuity Check and Loss Measurement both implemented on SW based CCM, 'Frame Rate' has to be the same. 
				"
            ::= { iMEPFunctionalConfigEntry 3 }
            
        -- 1.3.6.1.4.1.4756.108.60.40.6.1.4
        iAPSProtocolEnable OBJECT-TYPE
            SYNTAX      TruthValue
            MAX-ACCESS  read-write
            STATUS      current
            DESCRIPTION
                "Automatic Protection Switching protocol information transportation based on transmitting/receiving R-APS/L-APS PDU can be enabled/disabled.
                 Must be enabled to support ERPS/ELPS implementing APS. This is only valid with one Peer MEP configured. 
								"
            ::= { iMEPFunctionalConfigEntry 4 }
            
        -- 1.3.6.1.4.1.4756.108.60.40.6.1.5
        iAPSProtocolPriority OBJECT-TYPE
            SYNTAX      Integer32 (0..9) 
            MAX-ACCESS  read-write
            STATUS      current
            DESCRIPTION
                "The priority to be inserted as PCP bits in TAG (if any)."
            ::= { iMEPFunctionalConfigEntry 5 }
            
        -- 1.3.6.1.4.1.4756.108.60.40.6.1.6
        iAPSProtocolCast OBJECT-TYPE
            SYNTAX      INTEGER {
                            unicast(1),
                            multicast(2)
                        }
            MAX-ACCESS  read-write
            STATUS      current
            DESCRIPTION
                "Selection of APS PDU transmitted unicast or multi-cast. 
                 The unicast MAC will be taken from the 'Unicast Peer MAC' configuration. Unicast is only valid for L-APS - see 'Type'. 
                 The R-APS PDU is always transmitted with multi-cast MAC described in G.8032. 
								"
            ::= { iMEPFunctionalConfigEntry 6 }

		-- 1.3.6.1.4.1.4756.108.60.40.6.1.7
        iAPSProtocolType OBJECT-TYPE
            SYNTAX      INTEGER {
                            liniar-aps(1),
                            ring-aps(2)
                        }
            MAX-ACCESS  read-write
            STATUS      current
            DESCRIPTION
                "L-APS: APS PDU is transmitted as L-APS - this is for ELPS.
                 R-APS: APS PDU is transmitted as R-APS - this is for ERPS.
				"
            ::= { iMEPFunctionalConfigEntry 7 }            

		-- 1.3.6.1.4.1.4756.108.60.40.6.1.8
        iAPSProtocolLastOctet OBJECT-TYPE
            SYNTAX      Integer32 (0..255) 
            MAX-ACCESS  read-write
            STATUS      current
            DESCRIPTION
                "This is the last octet of the transmitted and expected RAPS multi-cast MAC. 
                 In G.8031 (03/2010) a RAPS multi-cast MAC is defined as 01-19-A7-00-00-XX. 
                 In current standard the value for this last octet is '01' and the usage of other values is for further study. 
								"
            ::= { iMEPFunctionalConfigEntry 8 }

-- ERPS
    
    -- 1.3.6.1.4.1.4756.108.60.10
    iERPS  OBJECT IDENTIFIER ::= { iRedundancy 50 }
    
    -- 1.3.6.1.4.1.4756.108.60.10.1
    iAddNewERPSID OBJECT-TYPE
        SYNTAX      DisplayString
        MAX-ACCESS  read-write
        STATUS      current
        DESCRIPTION
            "Added a new ERPS ID.
             	Syntax: <ERPS ID> <Port0> <Port1>
             	Port0 means east , the value is the switch port (range 1 ~ 11)
             	Port1 means west , the value is the switch port (range 1 ~ 11)
            "
        ::= { iERPS 1 }
        
     -- 1.3.6.1.4.1.4756.108.60.10.2
    iDeleteERPSID OBJECT-TYPE
        SYNTAX      DisplayString
        MAX-ACCESS  read-write
        STATUS      current
        DESCRIPTION
            "Deleted a ERPS ID.
            	Syntax: <ERPS ID>
            "
        ::= { iERPS 2 }
    
    -- 1.3.6.1.4.1.4756.108.60.10.3
    iERPSIDTable OBJECT-TYPE
        SYNTAX      SEQUENCE OF IERPSIDEntry
        MAX-ACCESS  not-accessible
        STATUS      current
        DESCRIPTION
            "The ERPS ID Table."
        ::= { iERPS 3 }
     
     -- 1.3.6.1.4.1.4756.108.60.10.3.1
    iERPSIDEntry OBJECT-TYPE
        SYNTAX      IERPSIDEntry
        MAX-ACCESS  not-accessible
        STATUS      current
        DESCRIPTION
            "The ERPS ID Entry."
        INDEX { iERPSIDIndex }
        ::= { iERPSIDTable 1 }

    IERPSIDEntry ::= 
    SEQUENCE {        
    		iERPSIDIndex	 			 Integer32,
    		iERPSIDPort0	 	 		 Integer32,
    		iERPSIDPort1	 	 		 Integer32,
    		iERPSIDPort0APSMEP	 		 Integer32,
    		iERPSIDPort1APSMEP	 		 Integer32,
    		iERPSIDPort0SFMEP	 		 Integer32, 
    		iERPSIDPort1SFMEP			 Integer32,
    		iERPSIDRingType	 			 INTEGER,
    		iERPSIDInterconnectedNode	 INTEGER,
    		iERPSIDVirtualChannel	 	 INTEGER,
    		iERPSIDMajorID	 			 DisplayString,
    		iERPSIDAlarm	 	 		 INTEGER
    	}
        
        -- 1.3.6.1.4.1.4756.108.60.10.3.1.1    
        iERPSIDIndex OBJECT-TYPE
         	SYNTAX Integer32 (1..64)
            MAX-ACCESS  read-only
            STATUS      current
            DESCRIPTION
                "The ID of the Protection group."
            ::= { iERPSIDEntry 1 }
        
        -- 1.3.6.1.4.1.4756.108.60.10.3.1.2    
        iERPSIDPort0 OBJECT-TYPE
         	SYNTAX Integer32 (1..11)
            MAX-ACCESS  read-only
            STATUS      current
            DESCRIPTION
                "This will create a Port 0 of the switch in the ring."
            ::= { iERPSIDEntry 2 }
        
        -- 1.3.6.1.4.1.4756.108.60.10.3.1.3    
        iERPSIDPort1 OBJECT-TYPE
         	SYNTAX Integer32 (1..11)
            MAX-ACCESS  read-only
            STATUS      current
            DESCRIPTION
                "This will create 'Port 1' of the switch in the Ring. 
                 As interconnected sub-ring will have only one ring port, 'Port 1' is configured as '0' for interconnected sub-ring. 
                 '0' in this field indicates that no 'Port 1' is associated with this instance"
            ::= { iERPSIDEntry 3 }
            
        -- 1.3.6.1.4.1.4756.108.60.10.3.1.4    
        iERPSIDPort0APSMEP OBJECT-TYPE
         	SYNTAX Integer32 (1..99)
            MAX-ACCESS  read-write
            STATUS      current
            DESCRIPTION
                "The Port 0 APS PDU handling MEP."
            ::= { iERPSIDEntry 4 }
        
        -- 1.3.6.1.4.1.4756.108.60.10.3.1.5    
        iERPSIDPort1APSMEP OBJECT-TYPE
         	SYNTAX Integer32 (1..99)
            MAX-ACCESS  read-write
            STATUS      current
            DESCRIPTION
                "The Port 1 APS PDU handling MEP. As only one APS MEP is associated with interconnected sub-ring without virtual channel, it is configured as '0' for such ring instances.
                 '0' in this field indicates that no Port 1 APS MEP is associated with this instance."
            ::= { iERPSIDEntry 5 }
            
        -- 1.3.6.1.4.1.4756.108.60.10.3.1.6
        iERPSIDPort0SFMEP OBJECT-TYPE
         	SYNTAX Integer32 (1..99)
            MAX-ACCESS  read-write
            STATUS      current
            DESCRIPTION
                "The Port 0 Signal Fail reporting MEP."
            ::= { iERPSIDEntry 6 } 
            
        -- 1.3.6.1.4.1.4756.108.60.10.3.1.7
        iERPSIDPort1SFMEP OBJECT-TYPE
         	SYNTAX Integer32 (1..99)
            MAX-ACCESS  read-write
            STATUS      current
            DESCRIPTION
                "The Port 1 Signal Fail reporting MEP. 
                 As only one SF MEP is associated with interconnected sub-ring without virtual channel, it is configured as '0' for such ring instances. 
                 '0' in this field indicates that no Port 1 SF MEP is associated with this instance."
            ::= { iERPSIDEntry 7 }
       	 
       	-- 1.3.6.1.4.1.4756.108.60.10.3.1.8
        iERPSIDRingType OBJECT-TYPE
         	SYNTAX INTEGER   {
         	         			major(1),
         	         			sub(2)
         				}
            MAX-ACCESS  read-write
            STATUS      current
            DESCRIPTION
                "Interconnected Node indicates that the ring instance is interconnected. 
                 'Yes' indicates it is an interconnected node for this instance.
                 'No' indicates that the configured instance is not interconnected."
            ::= { iERPSIDEntry 8 }
       	    
        -- 1.3.6.1.4.1.4756.108.60.10.3.1.9
        iERPSIDInterconnectedNode OBJECT-TYPE
         	SYNTAX INTEGER   {
         	         			yes(1),
         	         			no(2)
         				}
            MAX-ACCESS  read-write
            STATUS      current
            DESCRIPTION
                "Interconnected Node indicates that the ring instance is interconnected. 
                 'Yes' indicates it is an interconnected node for this instance.
                 'No' indicates that the configured instance is not interconnected."
            ::= { iERPSIDEntry 9 }
            
        -- 1.3.6.1.4.1.4756.108.60.10.3.1.10
        iERPSIDVirtualChannel OBJECT-TYPE
         	SYNTAX INTEGER	{
         	         			yes(1),
         	         			no(2)
         				}
            MAX-ACCESS  read-write
            STATUS      current
            DESCRIPTION
                "Sub-rings can either have virtual channel or not on the interconnected node. 
                 'Yes' indicates it is a sub-ring with virtual channel. 
                 'No' indicates, sub-ring doesn't have virtual channel. 
                "
            ::= { iERPSIDEntry 10 }
            
        -- 1.3.6.1.4.1.4756.108.60.10.3.1.11
        iERPSIDMajorID OBJECT-TYPE
         	SYNTAX DisplayString
            MAX-ACCESS  read-only
            STATUS      current
            DESCRIPTION
                "The ID of the Protection group."
            ::= { iERPSIDEntry 11 }
        
        -- 1.3.6.1.4.1.4756.108.60.10.3.1.12
        iERPSIDAlarm OBJECT-TYPE
         	SYNTAX INTEGER {
         	                active(1),
         	                inactive(2)
         				}
            MAX-ACCESS  read-only
            STATUS      current
            DESCRIPTION
                "There is an active alarm on the ERPS."
            ::= { iERPSIDEntry 12 }
        
        
    -- 1.3.6.1.4.1.4756.108.60.10.4
    iERPSIDConfigTable OBJECT-TYPE
        SYNTAX      SEQUENCE OF IERPSIDConfigEntry
        MAX-ACCESS  not-accessible
        STATUS      current
        DESCRIPTION
            "The ERPS config Table."
        ::= { iERPS 4 }
     
     -- 1.3.6.1.4.1.4756.108.60.10.4.1
    iERPSIDConfigEntry OBJECT-TYPE
        SYNTAX      IERPSIDConfigEntry
        MAX-ACCESS  not-accessible
        STATUS      current
        DESCRIPTION
            "The ERPS config Entry."
        INDEX { iERPSIDIndex }
        ::= { iERPSIDConfigTable 1 }

    IERPSIDConfigEntry ::= 
    SEQUENCE {
           	iERPSConfigStatus		INTEGER,
        	iERPSGuardTime			Integer32,
        	iERPSWTRTime			INTEGER,
        	iERPSHoldOffTime		Integer32,
        	iERPSVersion			INTEGER,
        	iERPSRevertive			TruthValue
        }
                
        -- 1.3.6.1.4.1.4756.108.60.10.4.1.1    
        iERPSConfigStatus OBJECT-TYPE
         	SYNTAX INTEGER {
         						active(1),
         						inactive(2)
         				}
            MAX-ACCESS  read-only
            STATUS      current
            DESCRIPTION
                " active: This ERPS is configured - is active.
                  inactive: This ERPS is only created and has not yet been configured - is not active.
				"
            ::= { iERPSIDConfigEntry 1 }
            
        -- 1.3.6.1.4.1.4756.108.60.10.4.1.2
        iERPSGuardTime OBJECT-TYPE
         	SYNTAX Integer32 (10..2000)
            MAX-ACCESS  read-write
            STATUS      current
            DESCRIPTION
                " Guard timeout value to be used to prevent ring nodes from receiving outdated R-APS messages.
				  The period of the guard timer can be configured in 10 ms steps between 10 ms and 2 seconds, with a default value of 500 ms 
				"
            ::= { iERPSIDConfigEntry 2 }
        
        -- 1.3.6.1.4.1.4756.108.60.10.4.1.3
        iERPSWTRTime OBJECT-TYPE
         	SYNTAX INTEGER {
         						one-minute(1),
         						five-minutes(2),
         						six-minutes(3),
         						seven-minutes(4),
         						eight-minutes(5),
         						nine-minutes(6),
         						ten-minutes(7),
         						eleven-minutes(8),
         						twelve-minutes(9)
         				}
            MAX-ACCESS  read-write
            STATUS      current
            DESCRIPTION
                " The Wait To Restore timing value to be used in revertive switching.
				  The period of the WTR time can be configured by the operator in 1 minute steps between 5 and 12 minutes with a default value of 5 minutes.
				"
            ::= { iERPSIDConfigEntry 3 }
            
        -- 1.3.6.1.4.1.4756.108.60.10.4.1.4
        iERPSHoldOffTime OBJECT-TYPE
         	SYNTAX Integer32 (0..10000)
            MAX-ACCESS  read-write
            STATUS      current
            DESCRIPTION
                " The timing value to be used to make persistent check on Signal Fail before switching.
				  The range of the hold off timer is 0 to 10 seconds in steps of 100 ms.
				"
            ::= { iERPSIDConfigEntry 4 }
            
        -- 1.3.6.1.4.1.4756.108.60.10.4.1.5
        iERPSVersion OBJECT-TYPE
         	SYNTAX INTEGER {
         						v1(1),
         						v2(2)
						}
            MAX-ACCESS  read-write
            STATUS      current
            DESCRIPTION
                " ERPS Protocol Version - v1 or v2"
            ::= { iERPSIDConfigEntry 5 }
            
        -- 1.3.6.1.4.1.4756.108.60.10.4.1.6
        iERPSRevertive OBJECT-TYPE
         	SYNTAX TruthValue
            MAX-ACCESS  read-write
            STATUS      current
            DESCRIPTION
                "In Revertive mode, after the conditions causing a protection switch has cleared, the traffic channel is restored to the working transport entity, i.e., blocked on the RPL.
				 In Non-Revertive mode, the traffic channel continues to use the RPL, if it is not failed, after a protection switch condition has cleared.
				"
            ::= { iERPSIDConfigEntry 6 }
    
    -- 1.3.6.1.4.1.4756.108.60.40.5
    iAddERPSVID OBJECT-TYPE
        SYNTAX      DisplayString
        MAX-ACCESS  read-write
        STATUS      current
        DESCRIPTION
            "Added a new vid of ERPS ID.
             Syntax: <ERPS ID> <vid>
            "
        ::= { iERPS 5 }
        
    -- 1.3.6.1.4.1.4756.108.60.40.6
    iDeleteERPSVID OBJECT-TYPE
        SYNTAX      DisplayString
        MAX-ACCESS  read-write
        STATUS      current
        DESCRIPTION
            "Deleted a vid of ERPS ID.
            	Syntax: <ERPS ID> <vid>
            "
        ::= { iERPS 6 }

		-- 1.3.6.1.4.1.4756.108.60.10.7
    iERPSVLANTable OBJECT-TYPE
        SYNTAX      SEQUENCE OF IERPSVLANEntry
        MAX-ACCESS  not-accessible
        STATUS      current
        DESCRIPTION
            "The ERPS VLAN Table."
        ::= { iERPS 7 }
     
    -- 1.3.6.1.4.1.4756.108.60.10.7.1
    iERPSVLANEntry OBJECT-TYPE
        SYNTAX      IERPSVLANEntry
        MAX-ACCESS  not-accessible
        STATUS      current
        DESCRIPTION
            "The ERPS config Entry."
        INDEX { iERPSIDIndex , iERPSVLANIDIndex}
        ::= { iERPSVLANTable 1 }

    IERPSVLANEntry ::= 
    	SEQUENCE {
    		  	iERPSVLANIDIndex		Integer32,
			  	iERPSVLANID				Integer32
        	}
        
        -- 1.3.6.1.4.1.4756.108.60.10.7.1.1
        iERPSVLANIDIndex OBJECT-TYPE
         	SYNTAX Integer32 (1..63)
            MAX-ACCESS  read-only
            STATUS      current
            DESCRIPTION
                "The vlan id index of ERPS"
            ::= { iERPSVLANEntry 1 }
        
        -- 1.3.6.1.4.1.4756.108.60.10.7.1.2
        iERPSVLANID OBJECT-TYPE
         	SYNTAX Integer32 (1..4095)
            MAX-ACCESS  read-only
            STATUS      current
            DESCRIPTION
                " VLAN configuration of the Protection Group."
            ::= { iERPSVLANEntry 2 }
    
    -- 1.3.6.1.4.1.4756.108.60.10.8
    iRPLOwnerSetting OBJECT-TYPE
        SYNTAX      DisplayString
        MAX-ACCESS  read-write
        STATUS      current
        DESCRIPTION
            "Setting RPL Port of RPL Owner
            	Synatx: <ERPS ID> <RPL Port>
            	RPL Port value 
            		'0' mens port0
            	    '1' mens port1
            "
        ::= { iERPS 8 }
        
    -- 1.3.6.1.4.1.4756.108.60.10.9
    iRPLOwnerClear OBJECT-TYPE
        SYNTAX      DisplayString
        MAX-ACCESS  read-write
        STATUS      current
        DESCRIPTION
            "Setting clear of RPL Owner
            	Synatx: <ERPS ID> 
            "
        ::= { iERPS 9 }
        
    -- 1.3.6.1.4.1.4756.108.60.10.10
    iRPLNeighbourSetting OBJECT-TYPE
        SYNTAX      DisplayString
        MAX-ACCESS  read-write
        STATUS      current
        DESCRIPTION
            "Setting RPL Port of RPL Neighbour
            	Synatx: <ERPS ID> <RPL Port>
            	RPL Port value 
            		'0' mens port0
            	    '1' mens port1
            "
        ::= { iERPS 10 }
        
    -- 1.3.6.1.4.1.4756.108.60.10.11
    iRPLNeighbourClear OBJECT-TYPE
        SYNTAX      DisplayString
        MAX-ACCESS  read-write
        STATUS      current
        DESCRIPTION
            "Setting clear of RPL Neighbour
            	Synatx: <ERPS ID>
            "
        ::= { iERPS 11 }
    
	-- 1.3.6.1.4.1.4756.108.60.10.12
    iRPLConfigTable OBJECT-TYPE
        SYNTAX      SEQUENCE OF IRPLConfigEntry
        MAX-ACCESS  not-accessible
        STATUS      current
        DESCRIPTION
            "The RPL config Table."
        ::= { iERPS 12 }
     
     -- 1.3.6.1.4.1.4756.108.60.10.12.1
    iRPLConfigEntry OBJECT-TYPE
        SYNTAX      IRPLConfigEntry
        MAX-ACCESS  not-accessible
        STATUS      current
        DESCRIPTION
            "The ERPS config Entry."
        INDEX { iERPSIDIndex }
        ::= { iRPLConfigTable 1 }

    IRPLConfigEntry ::= 
    	SEQUENCE {
    				iRPLRole		INTEGER,
    				iRPLPort		INTEGER
        		}
        
    	-- 1.3.6.1.4.1.4756.108.60.10.12.1.1
        iRPLRole OBJECT-TYPE
         	SYNTAX INTEGER {
         						none(1),
         						rpl-owner(2),
         						rpl-neighbour(3)
         				}
            MAX-ACCESS  read-only
            STATUS      current
            DESCRIPTION
                "It can be either RPL owner or RPL Neighbour."
            ::= { iRPLConfigEntry 1 }
            
        -- 1.3.6.1.4.1.4756.108.60.10.12.1.2
        iRPLPort OBJECT-TYPE
         	SYNTAX INTEGER {
         						none(1),
         						port0(2),
         						port1(3)
         				}
            MAX-ACCESS  read-only
            STATUS      current
            DESCRIPTION
                "This allows to select the port0 or port1 as the RPL block."
            ::= { iRPLConfigEntry 2 }
         
            
	-- 1.3.6.1.4.1.4756.108.60.10.13
    iERPSIDStatusTable OBJECT-TYPE
        SYNTAX      SEQUENCE OF IERPSIDStatusEntry
        MAX-ACCESS  not-accessible
        STATUS      current
        DESCRIPTION
            "The ERPS ID status Table."
        ::= { iERPS 13 }
     
    -- 1.3.6.1.4.1.4756.108.60.10.13.1
    iERPSIDStatusEntry OBJECT-TYPE
        SYNTAX      IERPSIDStatusEntry
        MAX-ACCESS  not-accessible
        STATUS      current
        DESCRIPTION
            "The ERPS ID status Entry."
        INDEX { iERPSIDIndex }
        ::= { iERPSIDStatusTable 1 }

    IERPSIDStatusEntry ::= 
    SEQUENCE {
				    iProtectionState 				DisplayString,
				    iPort0State						INTEGER,
				    iPort1State						INTEGER,
				    iTransmitAPS 					DisplayString,
				    iPort0ReceiveAPS				DisplayString,
				    iPort1ReceiveAPS				DisplayString,
				    iWTRRemaining					DisplayString,
				    iRPLunblocked 					INTEGER,
				    iNoAPSReceived					INTEGER,
				    iPort0BlockStatus				DisplayString,
				    iPort1BlockStatus				DisplayString,
				    iFOPAlarm						INTEGER
        }
        
        -- 1.3.6.1.4.1.4756.108.60.10.13.1.1
        iProtectionState OBJECT-TYPE
         	SYNTAX DisplayString
            MAX-ACCESS  read-only
            STATUS      current
            DESCRIPTION
                "ERPS state according to State Transition Tables in G.8032."
            ::= { iERPSIDStatusEntry 1 }
        
        -- 1.3.6.1.4.1.4756.108.60.10.13.1.2
        iPort0State OBJECT-TYPE
         		SYNTAX INTEGER {        
         							none(1),
         							ok(2),
         							sf(3)
         				 	}
            MAX-ACCESS  read-only
            STATUS      current
            DESCRIPTION
                "OK: State of port0 is ok
				 SF: State of port0 is Signal Fail
				"
            ::= { iERPSIDStatusEntry 2 }
            
       	-- 1.3.6.1.4.1.4756.108.60.10.13.1.3
        iPort1State OBJECT-TYPE
         		SYNTAX INTEGER {
         							none(1),
         							ok(2),
         							sf(3)
         				 	}
            MAX-ACCESS  read-only
            STATUS      current
            DESCRIPTION
                "OK: State of port1 is ok
				 SF: State of port1 is Signal Fail
			    "
            ::= { iERPSIDStatusEntry 3 }
            
        -- 1.3.6.1.4.1.4756.108.60.10.13.1.4
        iTransmitAPS OBJECT-TYPE
         		SYNTAX DisplayString
            MAX-ACCESS  read-only
            STATUS      current
            DESCRIPTION
                "The transmitted APS according to State Transition Tables in G.8032."
            ::= { iERPSIDStatusEntry 4 }
            
        -- 1.3.6.1.4.1.4756.108.60.10.13.1.5
        iPort0ReceiveAPS OBJECT-TYPE
         		SYNTAX DisplayString
            MAX-ACCESS  read-only
            STATUS      current
            DESCRIPTION
                "The received APS on Port 0 according to State Transition Tables in G.8032."
            ::= { iERPSIDStatusEntry 5 }
       
        -- 1.3.6.1.4.1.4756.108.60.10.13.1.6
        iPort1ReceiveAPS OBJECT-TYPE
         		SYNTAX DisplayString
            MAX-ACCESS  read-only
            STATUS      current
            DESCRIPTION
                "The received APS on Port 1 according to State Transition Tables in G.8032."
            ::= { iERPSIDStatusEntry 6 }
            
        -- 1.3.6.1.4.1.4756.108.60.10.13.1.7
        iWTRRemaining OBJECT-TYPE
         		SYNTAX DisplayString
            MAX-ACCESS  read-only
            STATUS      current
            DESCRIPTION
                "Remaining WTR timeout in milliseconds. "
            ::= { iERPSIDStatusEntry 7 }
            
        -- 1.3.6.1.4.1.4756.108.60.10.13.1.8
        iRPLunblocked OBJECT-TYPE
         		SYNTAX INTEGER{
         						up(1),
         						down(2)
         					}
            MAX-ACCESS  read-only
            STATUS      current
            DESCRIPTION
                "APS is received on the working flow."
            ::= { iERPSIDStatusEntry 8 }
            
        -- 1.3.6.1.4.1.4756.108.60.10.13.1.9
        iNoAPSReceived OBJECT-TYPE
         		SYNTAX INTEGER{
         							up(1),
         							down(2)
         					}
            MAX-ACCESS  read-only
            STATUS      current
            DESCRIPTION
                "RAPS PDU is not received from the other end."
            ::= { iERPSIDStatusEntry 9 }
        
        -- 1.3.6.1.4.1.4756.108.60.10.13.1.10
        iPort0BlockStatus OBJECT-TYPE
         		SYNTAX DisplayString
            MAX-ACCESS  read-only
            STATUS      current
            DESCRIPTION
                "Block status for Port 0 (Both traffic and R-APS block status). R-APS channel is never blocked on sub-rings without virtual channel."
            ::= { iERPSIDStatusEntry 10 }
            
        -- 1.3.6.1.4.1.4756.108.60.10.13.1.11
        iPort1BlockStatus OBJECT-TYPE
         		SYNTAX DisplayString
            MAX-ACCESS  read-only
            STATUS      current
            DESCRIPTION
                "Block status for Port 1 (Both traffic and R-APS block status). R-APS channel is never blocked on sub-rings without virtual channel."
            ::= { iERPSIDStatusEntry 11 }
            
       -- 1.3.6.1.4.1.4756.108.60.10.13.1.12
        iFOPAlarm OBJECT-TYPE
         		SYNTAX INTEGER{
         							detected(1),
         							not-detected(2)
         				}
            MAX-ACCESS  read-only
            STATUS      current
            DESCRIPTION
                "Failure of Protocol Defect(FOP) status. If FOP is detected, red LED glows; else green LED glows."
            ::= { iERPSIDStatusEntry 12 }


-- MAC Table             
    -- 1.3.6.1.4.1.4756.108.120
    iMacTableInfo  OBJECT IDENTIFIER ::= { msw4424a 120 }

    -- 1.3.6.1.4.1.4756.108.120.1
    iDisableAutoAging OBJECT-TYPE
        SYNTAX      TruthValue
        MAX-ACCESS  read-write
        STATUS      current
        DESCRIPTION                                  
            "Disable the automatic aging of dynamic entries."
        ::= { iMacTableInfo 1 }

    -- 1.3.6.1.4.1.4756.108.120.2
    iAgingTime OBJECT-TYPE
        SYNTAX      Integer32 (10..1000000)
        UNITS       "seconds"
        MAX-ACCESS  read-write
        STATUS      current
        DESCRIPTION                                  
            "By default, dynamic entries are removed from the MAC table after 300 seconds.
             This removal is also called aging.
             Configure aging time by entering a value here in seconds,
             The allowed range is 10 to 1000000 seconds."
        DEFVAL     { 300 }     
        ::= { iMacTableInfo 2 }
 
    -- 1.3.6.1.4.1.4756.108.120.3
    iMacTableLearningTable OBJECT-TYPE
        SYNTAX      SEQUENCE OF IMacTableLearningEntry
        MAX-ACCESS  not-accessible
        STATUS      current
        DESCRIPTION
            "This table allows for configure port learning mode."
        ::= { iMacTableInfo 3 }

    -- 1.3.6.1.4.1.4756.108.120.3.1
    iMacTableLearningEntry OBJECT-TYPE
        SYNTAX      IMacTableLearningEntry
        MAX-ACCESS  not-accessible
        STATUS      current
        DESCRIPTION
            "The entry of ports."
        INDEX { iPortIndex }
        ::= { iMacTableLearningTable 1 }

    IMacTableLearningEntry ::=
        SEQUENCE {       
            iPortLearningMode      INTEGER
        }

        -- 1.3.6.1.4.1.4756.108.120.3.1.1    
        iPortLearningMode OBJECT-TYPE
            SYNTAX      INTEGER {
                            auto(1),
                            disable(2),
                            secure(3)
                        }    
            MAX-ACCESS  read-write
            STATUS      current
            DESCRIPTION
                "If another module is in control of the mode, then it cannot be changed by the user.
                 An example of such a module is the MAC-Based Authentication under 802.1X.
                 Each port can do learning based upon the following settings:
                 Auto: Learning is done automatically as soon as a frame with unknown SMAC is received.
                 Disable: No learning is done.
                 Secure: Only static MAC entries are learned, all other frames are dropped.
                         <NOTE> Make sure that the link used for managing the switch is added to
                                the Static Mac Table before changing to secure learning mode,
                                otherwise the management link is lost and can only be restored by
                                using another non-secure port"
            ::= { iMacTableLearningEntry 1 }

    -- 1.3.6.1.4.1.4756.108.120.4
    iAddStaticMAC OBJECT-TYPE
        SYNTAX      DisplayString
        MAX-ACCESS  read-write
        STATUS      current
        DESCRIPTION                                  
            "Add a new entry to the static MAC table. The static MAC table can contain 64 entries.
             By default, no ports are members.
             Syntax: <mac_addr> [<vid>]"
        ::= { iMacTableInfo 4 }

    -- 1.3.6.1.4.1.4756.108.120.5
    iDeleteStaticMAC OBJECT-TYPE
        SYNTAX      DisplayString
        MAX-ACCESS  read-write
        STATUS      current
        DESCRIPTION
            "Delete an entry from the static MAC table.
             Syntax: <mac_addr> [<vid>]"
        ::= { iMacTableInfo 5 }

    -- 1.3.6.1.4.1.4756.108.120.6
    iStaticMacTable OBJECT-TYPE
        SYNTAX      SEQUENCE OF IStaticMacEntry
        MAX-ACCESS  not-accessible
        STATUS      current
        DESCRIPTION
            "The static entries in the MAC table are shown in this table."
        ::= { iMacTableInfo 6 }

    -- 1.3.6.1.4.1.4756.108.120.6.1
    iStaticMacEntry OBJECT-TYPE
        SYNTAX      IStaticMacEntry
        MAX-ACCESS  not-accessible
        STATUS      current
        DESCRIPTION
            "The entry of static MAC addresses of table."
        INDEX { iStaticMacVlanID, iStaticMacAddress }
        ::= { iStaticMacTable 1 }

    IStaticMacEntry ::=
        SEQUENCE {        
            iStaticMacVlanID       Integer32,
            iStaticMacAddress      MacAddress,
            iStaticMacPortMembers  DisplayString
        }

        -- 1.3.6.1.4.1.4756.108.120.6.1.1    
        iStaticMacVlanID OBJECT-TYPE
            SYNTAX      Integer32 (1..4095)
            MAX-ACCESS  read-only
            STATUS      current
            DESCRIPTION
                "The VLAN ID of the entry."
            ::= { iStaticMacEntry 1 }

        -- 1.3.6.1.4.1.4756.108.120.6.1.2    
        iStaticMacAddress OBJECT-TYPE
            SYNTAX      MacAddress
            MAX-ACCESS  read-only
            STATUS      current
            DESCRIPTION
                "The MAC address of the entry."
            ::= { iStaticMacEntry 2 }

        -- 1.3.6.1.4.1.4756.108.120.6.1.3    
        iStaticMacPortMembers OBJECT-TYPE
            SYNTAX      DisplayString
            MAX-ACCESS  read-write
            STATUS      current
            DESCRIPTION
                "Indicates which ports are members of the entry."
            ::= { iStaticMacEntry 3 }

    -- 1.3.6.1.4.1.4756.108.120.7
    iFlushDynamicMacEntries OBJECT-TYPE
        SYNTAX      INTEGER {
                        trigger(1),
                        normal(2)
                    }
        MAX-ACCESS  read-write
        STATUS      current
        DESCRIPTION
            "Flushes all dynamic entries."
        ::= { iMacTableInfo 7 }

    -- 1.3.6.1.4.1.4756.108.120.8
    iMacAddressTable OBJECT-TYPE
        SYNTAX      SEQUENCE OF IMacAddressEntry
        MAX-ACCESS  not-accessible
        STATUS      current
        DESCRIPTION
            "The entries in the MAC addresses table are shown in this table."
        ::= { iMacTableInfo 8 }

    -- 1.3.6.1.4.1.4756.108.120.8.1
    iMacAddressEntry OBJECT-TYPE
        SYNTAX      IMacAddressEntry
        MAX-ACCESS  not-accessible
        STATUS      current
        DESCRIPTION
            "The entry of MAC addresses table."
        INDEX { iMacAddressVlanID, iMacAddress }
        ::= { iMacAddressTable 1 }

    IMacAddressEntry ::=
        SEQUENCE {
            iMacAddressVlanID          Integer32,   
            iMacAddress                MacAddress,
            iMacAddressType            INTEGER,           
            iMacAddressPortMembers     DisplayString
        }

        -- 1.3.6.1.4.1.4756.108.120.8.1.1    
        iMacAddressVlanID OBJECT-TYPE
            SYNTAX      Integer32 (1..4095)
            MAX-ACCESS  read-only
            STATUS      current
            DESCRIPTION
                "The VLAN ID of the entry."
            ::= { iMacAddressEntry 1 }

        -- 1.3.6.1.4.1.4756.108.120.8.1.2    
        iMacAddress OBJECT-TYPE
            SYNTAX      MacAddress
            MAX-ACCESS  read-only
            STATUS      current
            DESCRIPTION
                "The MAC address of the entry."
            ::= { iMacAddressEntry 2 }

        -- 1.3.6.1.4.1.4756.108.120.8.1.3    
        iMacAddressType OBJECT-TYPE
            SYNTAX      INTEGER {
                            static(1),
                            dynamic(2)
                        }
            MAX-ACCESS  read-only
            STATUS      current
            DESCRIPTION
                "Indicates whether the entry is a static or a dynamic entry."
            ::= { iMacAddressEntry 3 }

        -- 1.3.6.1.4.1.4756.108.120.8.1.4    
        iMacAddressPortMembers OBJECT-TYPE
            SYNTAX      DisplayString
            MAX-ACCESS  read-only
            STATUS      current
            DESCRIPTION
                "The ports that are members of the entry."
            ::= { iMacAddressEntry 4 }

-- VLAN Translation
    -- 1.3.6.1.4.1.4756.108.130
    iVlanTranslation  OBJECT IDENTIFIER ::= { msw4424a 130 }

    -- 1.3.6.1.4.1.4756.108.130.1
    iAddVlanTransPortToGroup OBJECT-TYPE
        SYNTAX      DisplayString
        MAX-ACCESS  read-write
        STATUS      current
        DESCRIPTION                                  
            "Add a new entry in Port to Group Mapping Table.
             Note that if a VLAN translation is enabled on a management port for management VLAN,
             it may disrupt the management connectivity in some cases.
             Syntax: <port_list> <group_id>"
        ::= { iVlanTranslation 1 }

    -- 1.3.6.1.4.1.4756.108.130.2
    iVlanTransPortToGroupMappingTable OBJECT-TYPE
        SYNTAX      SEQUENCE OF IVlanTransPortToGroupMappingEntry
        MAX-ACCESS  not-accessible
        STATUS      current
        DESCRIPTION
            "This table allows you to map set of Port members to a Group ID for all switch ports."
        ::= { iVlanTranslation 2 }

    -- 1.3.6.1.4.1.4756.108.130.2.1
    iVlanTransPortToGroupMappingEntry OBJECT-TYPE
        SYNTAX      IVlanTransPortToGroupMappingEntry
        MAX-ACCESS  not-accessible
        STATUS      current
        DESCRIPTION
            "The Entry of Port to Group mapping Table."
        INDEX { iVlanTransGroupID }
        ::= { iVlanTransPortToGroupMappingTable 1 }

    IVlanTransPortToGroupMappingEntry ::=
        SEQUENCE {       
            iVlanTransGroupID                  Integer32,
            iVlanTransPortToGroupPortMembers   DisplayString
        }

        -- 1.3.6.1.4.1.4756.108.130.2.1.1    
        iVlanTransGroupID OBJECT-TYPE
            SYNTAX      Integer32 (1..11)
            MAX-ACCESS  read-only
            STATUS      current
            DESCRIPTION
                "A valid Group ID is an integer value form 1 to 6.
                 A set of VLAN Translations are mapped to a group Id.
                 This way a port is mapped to a list of VLAN Translations easily by
                 mapping it to a group."
            ::= { iVlanTransPortToGroupMappingEntry 1 }

        -- 1.3.6.1.4.1.4756.108.130.2.1.2    
        iVlanTransPortToGroupPortMembers OBJECT-TYPE
            SYNTAX      DisplayString
            MAX-ACCESS  read-write
            STATUS      current
            DESCRIPTION
                "A port can be mapped to any of the groups.
                 Multiple ports can also be mapped to a group with same group Id.
                 Note: By default, each port is mapped to a group with a group Id equal to the port number.
                       For example, port 1 is mapped to the group with ID=1."
            ::= { iVlanTransPortToGroupMappingEntry 2 }

    -- 1.3.6.1.4.1.4756.108.130.3
    iAddVlanTransMapping OBJECT-TYPE
        SYNTAX      DisplayString
        MAX-ACCESS  read-write
        STATUS      current
        DESCRIPTION                                  
            "Add a new entry in VLAN Translation table.
             Syntax: <group_id> <vid> <trans_vid>"
        ::= { iVlanTranslation 3 }

    -- 1.3.6.1.4.1.4756.108.130.4
    iDeleteVlanTransMapping OBJECT-TYPE
        SYNTAX      DisplayString
        MAX-ACCESS  read-write
        STATUS      current
        DESCRIPTION                                  
            "To delete a VLAN Translation Group database entry.
             Syntax: <group_id> <vid>"
        ::= { iVlanTranslation 4 }

    -- 1.3.6.1.4.1.4756.108.130.5
    iVlanTransVidMappingTable OBJECT-TYPE
        SYNTAX      SEQUENCE OF IVlanTransVidMappingEntry
        MAX-ACCESS  not-accessible
        STATUS      current
        DESCRIPTION
            "This table allows you to map set of Port members to a Group ID for all switch ports."
        ::= { iVlanTranslation 5 }

    -- 1.3.6.1.4.1.4756.108.130.5.1
    iVlanTransVidMappingEntry OBJECT-TYPE
        SYNTAX      IVlanTransVidMappingEntry
        MAX-ACCESS  not-accessible
        STATUS      current
        DESCRIPTION
            "The Entry of Port to Group mapping Table."
        INDEX { iVlanTransGroupID, iVlanTransMappedVID }
        ::= { iVlanTransVidMappingTable 1 }

    IVlanTransVidMappingEntry ::=
        SEQUENCE {       
            iVlanTransMappedVID    Integer32,
            iVlanTranslatedToVID   Integer32
        }

        -- 1.3.6.1.4.1.4756.108.130.5.1.1    
        iVlanTransMappedVID OBJECT-TYPE
            SYNTAX      Integer32 (1..4095)
            MAX-ACCESS  read-only
            STATUS      current
            DESCRIPTION
                "Indicates the ID to which Group ID will be mapped.
                 A valid VLAN ID ranges from 1-4095."
            ::= { iVlanTransVidMappingEntry 1 }

        -- 1.3.6.1.4.1.4756.108.130.5.1.2    
        iVlanTranslatedToVID OBJECT-TYPE
            SYNTAX      Integer32 (1..4095)
            MAX-ACCESS  read-write
            STATUS      current
            DESCRIPTION
                "Indicates the VID to which VLAN ID of ingress frames will be changed."
            ::= { iVlanTransVidMappingEntry 2 }

-- VLANs                     
	-- 1.3.6.1.4.1.4756.108.140
    iVLANs  OBJECT IDENTIFIER ::= { msw4424a 140 }
    	
    	-- 1.3.6.1.4.1.4756.108.140.1
        iVlanAllowedAccessVLANs OBJECT-TYPE
        SYNTAX      DisplayString
        MAX-ACCESS  read-write
        STATUS      current
        DESCRIPTION
            "This field shows the allowed Access VLANs, i.e. it only affects ports configured as Access ports. 
            Ports in other modes are members of all VLANs specified in the Allowed VLANs field. 
            By default, only VLAN 1 is enabled. 
            More VLANs may be created by using a list syntax where the individual elements are separated by commas. 
            Ranges are specified with a dash separating the lower and upper bound.
			The following example will create VLANs 1, 10, 11, 12, 13, 200, and 300: 1,10-13,200,300. 
			Spaces are allowed in between the delimiters."
        ::= { iVLANs 1 }           
        
	-- 1.3.6.1.4.1.4756.108.140.2
    iVlanEthertype OBJECT-TYPE
        SYNTAX      DisplayString
        MAX-ACCESS  read-write
        STATUS      current
        DESCRIPTION
            "The ether type used for Custom S-ports.
             This is a global setting for all the Custom S-ports.
             The format of 'Ethernet Type' is restricted to 0x600-0xFFFF"
        ::= { iVLANs 2 }             
        
	-- 1.3.6.1.4.1.4756.108.140.3
    iVlanConfTable OBJECT-TYPE
        SYNTAX      SEQUENCE OF IVlanConfEntry
        MAX-ACCESS  not-accessible
        STATUS      current
        DESCRIPTION
            "The VLAN configuration can be monitored and modified here."
        ::= { iVLANs 3 }

    -- 1.3.6.1.4.1.4756.108.140.3.1
    iVlanConfEntry OBJECT-TYPE
        SYNTAX      IVlanConfEntry
        MAX-ACCESS  not-accessible
        STATUS      current
        DESCRIPTION
            "The Entry of VLAN configuration."
        INDEX { iPortIndex }
        ::= { iVlanConfTable 1 }

    IVlanConfEntry ::=
        SEQUENCE {       
            iVlanConfMode          INTEGER,          
            iVlanConfVlanID		   Integer32,
            iVlanConfPortType      INTEGER,
            iVlanConfRxFiltering   TruthValue,
            iVlanConfRxAccept      INTEGER,
            iVlanConfTxtag		   INTEGER,
            iVlanConfAllowVLANs    DisplayString,
            iVlanConfForbidVLANs   DisplayString
        }
        
        -- 1.3.6.1.4.1.4756.108.140.3.1.1
        iVlanConfMode OBJECT-TYPE
        SYNTAX      INTEGER {
                        access(1),
                        trunk(2),
                        hybird(3)
                     }
            MAX-ACCESS  read-write
            STATUS      current
            DESCRIPTION
                "Indicates the port vlan mode."
            ::= { iVlanConfEntry 1 }

		-- 1.3.6.1.4.1.4756.108.140.3.1.2
        iVlanConfVlanID OBJECT-TYPE
		SYNTAX      Integer32 (1..4095)
            MAX-ACCESS  read-write
            STATUS      current
            DESCRIPTION
                "Indicates the VLAN ID of this particular port."
            ::= { iVlanConfEntry 2 }     
            
		-- 1.3.6.1.4.1.4756.108.140.3.1.3
        iVlanConfPortType OBJECT-TYPE
        SYNTAX      INTEGER {
                        unaware(1),
                        c-port(2),
                        s-port(3),
                        s-custom-port(4)
                     }
            MAX-ACCESS  read-write
            STATUS      current
            DESCRIPTION
                "Indicates the port vlan type."
            ::= { iVlanConfEntry 3 }      
            
		 -- 1.3.6.1.4.1.4756.108.140.3.1.4
         iVlanConfRxFiltering OBJECT-TYPE
        	SYNTAX      TruthValue
            MAX-ACCESS  read-write
            STATUS      current
            DESCRIPTION
                "Indicates the port vlan rx filtering."
            ::= { iVlanConfEntry 4 } 
 
 		 -- 1.3.6.1.4.1.4756.108.140.3.1.5
         iVlanConfRxAccept OBJECT-TYPE
        	SYNTAX      INTEGER {
                        all(1),
                        tag-only(2),
                        untag-only(3)
                     }
            MAX-ACCESS  read-write
            STATUS      current
            DESCRIPTION
                "Indicates the port vlan rx acceptance."
            ::= { iVlanConfEntry 5 }
         
         -- 1.3.6.1.4.1.4756.108.140.3.1.6
         iVlanConfTxtag OBJECT-TYPE
        	SYNTAX      INTEGER {
                        untag-pvid(1),
                        tag-all(2),
                        untag-all(3)
                     }
            MAX-ACCESS  read-write
            STATUS      current
            DESCRIPTION
                "Indicates the port vlan tx tagging."
            ::= { iVlanConfEntry 6 }        
         
         -- 1.3.6.1.4.1.4756.108.140.3.1.7
         iVlanConfAllowVLANs OBJECT-TYPE
        	SYNTAX      DisplayString
            MAX-ACCESS  read-write
            STATUS      current
            DESCRIPTION
                "Ports in Trunk and Hybrid mode may control which VLANs they are allowed to become members of. 
                Access ports can only be member of one VLAN, the Access VLAN.
				The field's syntax is identical to the syntax used in the Enabled VLANs field. By default, 
				a Trunk or Hybrid port will become member of all VLANs, and is therefore set to 1-4095.
				The field may be left empty, which means that the port will not become member of any VLANs. "
            ::= { iVlanConfEntry 7 }  
         
         -- 1.3.6.1.4.1.4756.108.140.3.1.8
         iVlanConfForbidVLANs OBJECT-TYPE
        	SYNTAX      DisplayString
            MAX-ACCESS  read-write
            STATUS      current
            DESCRIPTION
                "A port may be configured to never be member of one or more VLANs. 
                By default, the field is left blank, which means that the port may become a member of all possible VLANs.  "
            ::= { iVlanConfEntry 8 }                          
     
     -- 1.3.6.1.4.1.4756.108.140.4.1.1
     iVlanMembershipTableUser OBJECT-TYPE
        SYNTAX      INTEGER {
                        combined(1),
                        admin(2),
                        nas(3),
                        gvrp(4),
                        mvr(5),
                        mep(6)
                     }
            MAX-ACCESS  read-write
            STATUS      current
            DESCRIPTION
                "Indicates the which one of VLAN membership table of user will be displayed."
      ::= { iVLANs 4 }

    -- 1.3.6.1.4.1.4756.108.140.5
    iVlanMembershipTable OBJECT-TYPE
        SYNTAX      SEQUENCE OF IVlanMembershipEntry
        MAX-ACCESS  not-accessible
        STATUS      current
        DESCRIPTION
            "The VLAN membership configuration can be monitored and modified here."
        ::= { iVLANs 5 }

    -- 1.3.6.1.4.1.4756.108.140.5.1
    iVlanMembershipEntry OBJECT-TYPE
        SYNTAX      IVlanMembershipEntry
        MAX-ACCESS  not-accessible
        STATUS      current
        DESCRIPTION
            "The Entry of VLAN memberships."
        INDEX { iVlanConfVlanID, iPortIndex }
        ::= { iVlanMembershipTable 1 }

    IVlanMembershipEntry ::=
        SEQUENCE {       
            iVlanMember            INTEGER
        }
         
        -- 1.3.6.1.4.1.4756.108.140.5.1.1
        iVlanMember OBJECT-TYPE
        SYNTAX      INTEGER {
        				nonmember(1),
                        member(2),
                        forbid(3),
                        conflict(4)
                    }
            MAX-ACCESS  read-only
            STATUS      current
            DESCRIPTION
               "A value for each port is displayed for each VLAN ID.
                If a port is not member in a VLAN , the following value is 1.
				If a port is included in a VLAN, the following value is 2.
				If a port is in the forbidden port list, the following value is 3.
				If a port is in the forbidden port list and at the same time attempted included in the VLAN, the following is 4. 
			   "
            ::= { iVlanMembershipEntry 1 }
        
    -- 1.3.6.1.4.1.4756.108.140.6
    iVlanPortTableUser OBJECT-TYPE
        SYNTAX      INTEGER {
                        combined(1),
                        admin(2),
                        nas(3),
                        gvrp(4),
                        mvr(5),
                        mstp(6),
                        erps(7),
                        vcl(8)
                     }
            MAX-ACCESS  read-write
            STATUS      current
            DESCRIPTION
                "Indicates the which one of VLAN port table of user will be displayed."
      ::= { iVLANs 6 }

    -- 1.3.6.1.4.1.4756.108.140.7
    iVlanPortTable OBJECT-TYPE
        SYNTAX      SEQUENCE OF IVlanPortEntry
        MAX-ACCESS  not-accessible
        STATUS      current
        DESCRIPTION
            "This table is used for showing status of the switch VLAN port."
        ::= { iVLANs 7 }

    -- 1.3.6.1.4.1.4756.108.140.7.1
    iVlanPortEntry OBJECT-TYPE
        SYNTAX      IVlanPortEntry
        MAX-ACCESS  not-accessible
        STATUS      current
        DESCRIPTION
            "The Entry of VLAN ports."
        INDEX { iPortIndex }
        ::= { iVlanPortTable 1 }

    IVlanPortEntry ::=
        SEQUENCE {
            iVlanPortType          		INTEGER,          
            iVlanPortIngressFiltering   TruthValue,
            iVlanPortFrameType     		INTEGER,
            iVlanPortVlanID        		Integer32,
            iVlanPortTxTag         		INTEGER,
            iVlanPortUntagVlanID   		Integer32,
            iVlanPortConflicts     		TruthValue
        }

        -- 1.3.6.1.4.1.4756.108.140.7.1.1    
        iVlanPortType OBJECT-TYPE
            SYNTAX      INTEGER {
                            unaware(1),
                            cPort(2),
                            sPort(3),
                            sCustomPort(4)
                        }
            MAX-ACCESS  read-only
            STATUS      current
            DESCRIPTION
                "Port can be one of the following types:
                 Unaware, Customer port(C-port), Service port(S-port), Custom Service port(S-custom-port)
                 If Port Type is Unaware, all frames are classified to the Port VLAN ID and tags are not removed."
            ::= { iVlanPortEntry 1 }

        -- 1.3.6.1.4.1.4756.108.140.7.1.2    
        iVlanPortIngressFiltering OBJECT-TYPE
            SYNTAX      TruthValue
            MAX-ACCESS  read-only
            STATUS      current
            DESCRIPTION
                "This parameter affects VLAN ingress processing.
                 If ingress filtering is checked and the ingress port is not a member of
                 the classified VLAN of the frame,
                 the frame is discarded. By default, ingress filtering is unchecked."   
            ::= { iVlanPortEntry 2 }

        -- 1.3.6.1.4.1.4756.108.140.7.1.3    
        iVlanPortFrameType OBJECT-TYPE
            SYNTAX      INTEGER {
                            all(1),
                            tagged(2),
                            untagged(3)
                        }
            MAX-ACCESS  read-only
            STATUS      current
            DESCRIPTION
                "Determines whether the port accepts all frames or only tagged/untagged frames.
                 This parameter affects VLAN ingress processing.
                 If the port only accepts tagged frames, untagged frames received on the port are discarded.
                 By default, the frame type is set to All."
            DEFVAL      { all }     
            ::= { iVlanPortEntry 3 }

        -- 1.3.6.1.4.1.4756.108.140.7.1.4    
        iVlanPortVlanID OBJECT-TYPE
            SYNTAX      Integer32 (0..4095)
            MAX-ACCESS  read-only
            STATUS      current
            DESCRIPTION
                "Configures the VLAN identifier for the port.
                 The allowed values are 0 through 4095. The default value is 1.
                 
                 If the value is 0, a VLAN tag with the classified VLAN ID is inserted in frames transmitted on the port.                 
                 This mode is normally used for ports connected to VLAN aware switches.
                 IMPORTANT: 'Port Tx Tag' should be set to 'untagPvid(1)' when this value is used.
                 
                 If the value are 1 through 4095, untagged frames received on the port are classified to the Port VLAN ID.
                 If VLAN awareness is disabled, all frames received on the port are classified to the Port VLAN ID.
                 If the classified VLAN ID of a frame transmitted on the port is different from the Port VLAN ID,
                 a VLAN tag with the classified VLAN ID is inserted in the frame."
            DEFVAL      { 1 }     
            ::= { iVlanPortEntry 4 }

        -- 1.3.6.1.4.1.4756.108.140.7.1.5
        iVlanPortTxTag OBJECT-TYPE
            SYNTAX      INTEGER {
            				untagUvid(1),
                            untagPvid(2),
                            tagUvid(3),
                            tagPvid(4),
                            tagAll(5),
                            untagAll(6)
                        }
            MAX-ACCESS  read-only
            STATUS      current
            DESCRIPTION
                "Determines egress tagging of a port.
                 Untag_pvid - All VLANs except the configured PVID will be tagged.
                 Tag_pvid -  The configured PVID will be tagged. 
                 Tag_all - All VLANs are tagged.
                 Untag_all - All VLANs are untagged."
            DEFVAL      { untagPvid }     
            ::= { iVlanPortEntry 5 }
        
        -- 1.3.6.1.4.1.4756.108.140.7.1.6
        iVlanPortUntagVlanID OBJECT-TYPE
            SYNTAX      Integer32 (0..4095)
            MAX-ACCESS  read-only
            STATUS      current
            DESCRIPTION
                "If Tx Tag is overridden by the selected user and is set to Tag or Untag UVID, 
                then this field will show the VLAN ID the user wants to tag or untag on egress.
				The field is empty if not overridden by the selected user. "
            DEFVAL      { 1 }     
            ::= { iVlanPortEntry 6 }
            
        -- 1.3.6.1.4.1.4756.108.140.7.1.7
        iVlanPortConflicts OBJECT-TYPE
            SYNTAX      TruthValue
            MAX-ACCESS  read-only
            STATUS      current
            DESCRIPTION
                "Shows status of Conflicts whether exists or not.
                 When a Volatile VLAN User requests to set VLAN membership or VLAN port configuration,
                 the following conflicts can occur:
                 Functional Conflicts between features.
                 Conflicts due to hardware limitation.
                 Direct conflict between user modules."
            ::= { iVlanPortEntry 7 }
            
-- Private VLAN
    -- 1.3.6.1.4.1.4756.108.150
    iPrivateVLAN  OBJECT IDENTIFIER ::= { msw4424a 150 }

    -- 1.3.6.1.4.1.4756.108.150.1
    iAddPrivateVlanID OBJECT-TYPE
        SYNTAX      DisplayString
        MAX-ACCESS  read-write
        STATUS      current
        DESCRIPTION                                  
            "Add a new private VLAN ID, and the private VLAN can be configured as needed.
             The allowed range for a private VLAN ID is the same as the switch port number range.
             and for every new private VLAN entry all ports are member."
        ::= { iPrivateVLAN 1 }

    -- 1.3.6.1.4.1.4756.108.150.2
    iDeletePrivateVlanID OBJECT-TYPE
        SYNTAX      DisplayString
        MAX-ACCESS  read-write
        STATUS      current
        DESCRIPTION
            "Delete a private VLAN from indicated ID."
        ::= { iPrivateVLAN 2 }

    -- 1.3.6.1.4.1.4756.108.150.3
    iPrivateVlanPortMemberTable OBJECT-TYPE
        SYNTAX      SEQUENCE OF IPrivateVlanPortMemberEntry
        MAX-ACCESS  not-accessible
        STATUS      current
        DESCRIPTION
            "Private VLANs are based on the source port mask, and there are no connections to VLANs.
             This means that VLAN IDs and Private VLAN IDs can be identical.
             A port must be a member of both a VLAN and a Private VLAN to be able to forward packets.
             By default, all ports are VLAN unaware and members of VLAN 1 and Private VLAN 1.
             A VLAN unaware port can only be a member of one VLAN,
             but it can be a member of multiple Private VLANs."
        ::= { iPrivateVLAN 3 }

    -- 1.3.6.1.4.1.4756.108.150.3.1
    iPrivateVlanPortMemberEntry OBJECT-TYPE
        SYNTAX      IPrivateVlanPortMemberEntry
        MAX-ACCESS  not-accessible
        STATUS      current
        DESCRIPTION
            "The Entry of private VLAN."
        INDEX { iPrivateVlanID }
        ::= { iPrivateVlanPortMemberTable 1 }

    IPrivateVlanPortMemberEntry ::=
        SEQUENCE {       
            iPrivateVlanID             Integer32,
            iPrivateVlanPortMembers    DisplayString
        }

        -- 1.3.6.1.4.1.4756.108.150.3.1.1    
        iPrivateVlanID OBJECT-TYPE
            SYNTAX      Integer32 (1..11)
            MAX-ACCESS  read-only
            STATUS      current
            DESCRIPTION
                "Indicates the ID of this particular private VLAN."
            ::= { iPrivateVlanPortMemberEntry 1 }

        -- 1.3.6.1.4.1.4756.108.150.3.1.2    
        iPrivateVlanPortMembers OBJECT-TYPE
            SYNTAX      DisplayString
            MAX-ACCESS  read-write
            STATUS      current
            DESCRIPTION
                "Add or modify member port list of private VLAN."
            ::= { iPrivateVlanPortMemberEntry 2 }

    -- 1.3.6.1.4.1.4756.108.150.4    
    iIsolationPorts OBJECT-TYPE
        SYNTAX      DisplayString
        MAX-ACCESS  read-write
        STATUS      current
        DESCRIPTION
            "A port member of a VLAN can be isolated to other isolated ports on the same VLAN and Private VLAN.
             By default, port isolation is disabled on all ports."
        ::= { iPrivateVLAN 4 }            

-- GVRP
    -- 1.3.6.1.4.1.4756.108.155
    iGVRP  OBJECT IDENTIFIER ::= { msw4424a 155 }  
    
    -- 1.3.6.1.4.1.4756.108.155.1
    iEnableGVRP OBJECT-TYPE
        SYNTAX      TruthValue
        MAX-ACCESS  read-write
        STATUS      current
        DESCRIPTION                                  
            "Enable GVRP setting"
        ::= { iGVRP 1 }
    
    -- 1.3.6.1.4.1.4756.108.155.2
    iGVRPJoinTime OBJECT-TYPE
        SYNTAX      Integer32 (1..20)
        MAX-ACCESS  read-write
        STATUS      current
        DESCRIPTION                                  
            "Join-time is a value in the range 1-20 in the units of centi seconds, i.e. in units of one hundredth of a second. The default is 20."
        ::= { iGVRP 2 }
    
    -- 1.3.6.1.4.1.4756.108.155.3
    iGVRPLeaveTime OBJECT-TYPE
        SYNTAX      Integer32 (60..300)
        MAX-ACCESS  read-write
        STATUS      current
        DESCRIPTION                                  
            "Leave-time is a value in the range 60-300 in the units of centi seconds, i.e. in units of one hundredth of a second.The default is 60."
        ::= { iGVRP 3 }
    
    -- 1.3.6.1.4.1.4756.108.155.4
    iGVRPLeaveAllTime OBJECT-TYPE
        SYNTAX      Integer32 (1000..5000)
        MAX-ACCESS  read-write
        STATUS      current
        DESCRIPTION                                  
            "LeaveAll-time is a value in the range 1000-5000 in the units of centi seconds, i.e. in units of one hundredth of a second. The default is 1000."
        ::= { iGVRP 4 }
    
    -- 1.3.6.1.4.1.4756.108.155.5
    iGVRPMaxVLAN OBJECT-TYPE
        SYNTAX      Integer32 (1..65535)
        MAX-ACCESS  read-write
        STATUS      current
        DESCRIPTION                                  
            "When GVRP is enabled a maximum number of VLANs supported by GVRP is specified. 
             By default this number is 20. This number can only be changed when GVRP is turned off. "
        ::= { iGVRP 5 }
    
    -- 1.3.6.1.4.1.4756.108.155.6
    iGVRPPortConfigTable OBJECT-TYPE
        SYNTAX      SEQUENCE OF IGVRPPortConfigEntry
        MAX-ACCESS  not-accessible
        STATUS      current
        DESCRIPTION
            "This table provides GVRP enable configurations for all ports."
        ::= { iGVRP 6 }

    -- 1.3.6.1.4.1.4756.108.155.6.1
    iGVRPPortConfigEntry OBJECT-TYPE
        SYNTAX      IGVRPPortConfigEntry
        MAX-ACCESS  not-accessible
        STATUS      current
        DESCRIPTION
            "The Entry of GVRP port enable configurations."
        INDEX { iPortIndex }
        ::= { iGVRPPortConfigTable 1 }

    IGVRPPortConfigEntry ::=
        SEQUENCE {
            iGVRPPortEnabled     INTEGER
        }
    
    	-- 1.3.6.1.4.1.4756.108.155.6.1.1    
        iGVRPPortEnabled OBJECT-TYPE
            SYNTAX      INTEGER {
                            gvrp-enabled(1),
                            disabled(2)
                        }
            MAX-ACCESS  read-write
            STATUS      current
            DESCRIPTION
                "Controls whether GVRP is enabled on this switch port."
            ::= { iGVRPPortConfigEntry 1 }	

-- VCL
    -- 1.3.6.1.4.1.4756.108.160
    iVCL  OBJECT IDENTIFIER ::= { msw4424a 160 }

    -- 1.3.6.1.4.1.4756.108.160.1
    iMacBasedVLAN  OBJECT IDENTIFIER ::= { iVCL 1 }

    -- 1.3.6.1.4.1.4756.108.160.1.1
    iAddMacBasedVLAN OBJECT-TYPE
        SYNTAX      DisplayString
        MAX-ACCESS  read-write
        STATUS      current
        DESCRIPTION                                  
            "Add a new MAC-based VLAN entry and the MAC-based VLAN entry can be configured as needed.
             Any unicast MAC address can be configured for the MAC-based VLAN entry.
             No broadcast or multicast MAC addresses are allowed.
             Syntax: <mac_addr>
             By default, VLAN ID is 1 and all ports are members"
        ::= { iMacBasedVLAN 1 }

    -- 1.3.6.1.4.1.4756.108.160.1.2
    iDeleteMacBasedVLAN OBJECT-TYPE
        SYNTAX      DisplayString
        MAX-ACCESS  read-write
        STATUS      current
        DESCRIPTION
            "To delete a MAC-based VLAN entry.
             Syntax: <mac_addr>"
        ::= { iMacBasedVLAN 2 }

    -- 1.3.6.1.4.1.4756.108.160.1.3
    iMacBasedVlanConfigTable OBJECT-TYPE
        SYNTAX      SEQUENCE OF IMacBasedVlanConfigEntry
        MAX-ACCESS  not-accessible
        STATUS      current
        DESCRIPTION
            "The MAC-based VLAN enties can be configured here."
        ::= { iMacBasedVLAN 3 }

    -- 1.3.6.1.4.1.4756.108.160.1.3.1
    iMacBasedVlanConfigEntry OBJECT-TYPE
        SYNTAX      IMacBasedVlanConfigEntry
        MAX-ACCESS  not-accessible
        STATUS      current
        DESCRIPTION
            "The Entry of MAC-based VLAN."
        INDEX { iMacBasedVlanConfigIndex }
        ::= { iMacBasedVlanConfigTable 1 }

    IMacBasedVlanConfigEntry ::=
        SEQUENCE {
            iMacBasedVlanConfigIndex         Integer32,
            iMacBasedVlanMacAddressConfig    MacAddress,
            iMacBasedVlanIDConfig            Integer32,
            iMacBasedVlanPortMembersConfig   DisplayString
        }

        -- 1.3.6.1.4.1.4756.108.160.1.3.1.1    
        iMacBasedVlanConfigIndex OBJECT-TYPE
            SYNTAX      Integer32 (1..256)
            MAX-ACCESS  read-only
            STATUS      current
            DESCRIPTION
                "Indicates the Index of MAC-based VLAN."
            ::= { iMacBasedVlanConfigEntry 1 }

        -- 1.3.6.1.4.1.4756.108.160.1.3.1.2    
        iMacBasedVlanMacAddressConfig OBJECT-TYPE
            SYNTAX      MacAddress
            MAX-ACCESS  read-only
            STATUS      current
            DESCRIPTION
                "Indicates the MAC address."
            ::= { iMacBasedVlanConfigEntry 2 }

        -- 1.3.6.1.4.1.4756.108.160.1.3.1.3    
        iMacBasedVlanIDConfig OBJECT-TYPE
            SYNTAX      Integer32 (1..4095)
            MAX-ACCESS  read-write
            STATUS      current
            DESCRIPTION
                "Indicates the VLAN ID.
                Legal values for a VLAN ID are 1 through 4095."
            ::= { iMacBasedVlanConfigEntry 3 }

        -- 1.3.6.1.4.1.4756.108.160.1.3.1.4    
        iMacBasedVlanPortMembersConfig OBJECT-TYPE
            SYNTAX      DisplayString
            MAX-ACCESS  read-write
            STATUS      current
            DESCRIPTION
                "To include or remove a port in a MAC-based VLAN."
            ::= { iMacBasedVlanConfigEntry 4 }

    -- 1.3.6.1.4.1.4756.108.160.1.4
    iMacBasedVlanStatusTable OBJECT-TYPE
        SYNTAX      SEQUENCE OF IMacBasedVlanStatusEntry
        MAX-ACCESS  not-accessible
        STATUS      current
        DESCRIPTION
            "The table shows MAC-based VLAN enties status."
        ::= { iMacBasedVLAN 4 }

    -- 1.3.6.1.4.1.4756.108.160.1.4.1
    iMacBasedVlanStatusEntry OBJECT-TYPE
        SYNTAX      IMacBasedVlanStatusEntry
        MAX-ACCESS  not-accessible
        STATUS      current
        DESCRIPTION
            "The Entry of MAC-based VLAN."
        INDEX { iMacBasedVlanStatusIndex }
        ::= { iMacBasedVlanStatusTable 1 }

    IMacBasedVlanStatusEntry ::=
        SEQUENCE {
            iMacBasedVlanStatusIndex         Integer32,
            iMacBasedVlanUserType            INTEGER,
            iMacBasedVlanMacAddressStatus    MacAddress,
            iMacBasedVlanIDStatus            Integer32,
            iMacBasedVlanPortMembersStatus   DisplayString
        }

        -- 1.3.6.1.4.1.4756.108.160.1.4.1.1    
        iMacBasedVlanStatusIndex OBJECT-TYPE
            SYNTAX      Integer32 (1..256)
            MAX-ACCESS  read-only
            STATUS      current
            DESCRIPTION
                "Indicates the Index of MAC-based VLAN."
            ::= { iMacBasedVlanStatusEntry 1 }

        -- 1.3.6.1.4.1.4756.108.160.1.4.1.2    
        iMacBasedVlanUserType OBJECT-TYPE
            SYNTAX      INTEGER {
                            static(1),
                            nas(2)
                        }
            MAX-ACCESS  read-only
            STATUS      current
            DESCRIPTION
                "There are two supported VLAN user types:
                 CLI/Web/SNMP : These are referred to as static.
                 NAS : NAS provides port-based authentication,
                       which involves communications between a Supplicant, Authenticator,
                       and an Authentication Server."
            ::= { iMacBasedVlanStatusEntry 2 }

        -- 1.3.6.1.4.1.4756.108.160.1.4.1.3    
        iMacBasedVlanMacAddressStatus OBJECT-TYPE
            SYNTAX      MacAddress
            MAX-ACCESS  read-only
            STATUS      current
            DESCRIPTION
                "Indicates the MAC address."
            ::= { iMacBasedVlanStatusEntry 3 }

        -- 1.3.6.1.4.1.4756.108.160.1.4.1.4    
        iMacBasedVlanIDStatus OBJECT-TYPE
            SYNTAX      Integer32 (1..4095)
            MAX-ACCESS  read-only
            STATUS      current
            DESCRIPTION
                "Indicates the VLAN ID."
            ::= { iMacBasedVlanStatusEntry 4 }

        -- 1.3.6.1.4.1.4756.108.160.1.4.1.5    
        iMacBasedVlanPortMembersStatus OBJECT-TYPE
            SYNTAX      DisplayString
            MAX-ACCESS  read-only
            STATUS      current
            DESCRIPTION
                "To include or remove a port in a MAC-based VLAN."
            ::= { iMacBasedVlanStatusEntry 5 }

    -- 1.3.6.1.4.1.4756.108.160.2
    iProtocolBasedVLAN  OBJECT IDENTIFIER ::= { iVCL 2 }

    -- 1.3.6.1.4.1.4756.108.160.2.1
    iAddProtocolEthernetToGroup OBJECT-TYPE
        SYNTAX      DisplayString
        MAX-ACCESS  read-write
        STATUS      current
        DESCRIPTION                                  
            "To add a new Ethernet type entry in Protocol to Group Mapping table.
             Syntax: <ether_type> <group_name>
             Valid values for ether_type ranges from 0x0600-0xffff."
        ::= { iProtocolBasedVLAN 1 }

    -- 1.3.6.1.4.1.4756.108.160.2.2
    iAddProtocolSnapToGroup OBJECT-TYPE
        SYNTAX      DisplayString
        MAX-ACCESS  read-write
        STATUS      current
        DESCRIPTION                                  
            "To add a new SNAP type entry in Protocol to Group Mapping table.
             Syntax: <oui> <pid> <group_name>
             Valid value in this case is comprised of two different sub-values.
                 a. OUI: OUI (Organizationally Unique Identifier) is value in format of xx-xx-xx
                         where each pair (xx) in string is a hexadecimal value ranges from 0x00-0xff.
                 b. PID: If the OUI is hexadecimal 00-00-00, the protocol ID is the Ethernet
                         type(EtherType) field value for the protocol running on top of SNAP;
                         if the OUI is an OUI for a particular organization, the protocol ID is
                         a value assigned by that organization to the protocol running on top of SNAP.
                         In other words, if value of OUI field is 00-00-00 then value of PID will be
                         etype (0x0600-0xffff) and if value of OUI is other than 00-00-00 then
                         valid value of PID will be any value from 0x0000 to 0xffff."
        ::= { iProtocolBasedVLAN 2 }

    -- 1.3.6.1.4.1.4756.108.160.2.3
    iAddProtocolLlcToGroup OBJECT-TYPE
        SYNTAX      DisplayString
        MAX-ACCESS  read-write
        STATUS      current
        DESCRIPTION                                  
            "To add a new LLC type entry in Protocol to Group Mapping table.
             Syntax: <dsap> <ssap> <group_name>
             Valid value in this case is comprised of two different sub-values.
                 a. DSAP: 1-byte long string (0x00-0xff)
                 b. SSAP: 1-byte long string (0x00-0xff)."
        ::= { iProtocolBasedVLAN 3 }

    -- 1.3.6.1.4.1.4756.108.160.2.4
    iDeleteProtocolEthernetToGroup OBJECT-TYPE
        SYNTAX      DisplayString
        MAX-ACCESS  read-write
        STATUS      current
        DESCRIPTION
            "To delete a Ethernet type to Group Name map entry.
             Syntax: <ether_type>"
        ::= { iProtocolBasedVLAN 4 }

    -- 1.3.6.1.4.1.4756.108.160.2.5
    iDeleteProtocolSnapToGroup OBJECT-TYPE
        SYNTAX      DisplayString
        MAX-ACCESS  read-write
        STATUS      current
        DESCRIPTION
            "To delete a SNAP type to Group Name map entry.
             Syntax: <oui> <pid>"
        ::= { iProtocolBasedVLAN 5 }

    -- 1.3.6.1.4.1.4756.108.160.2.6
    iDeleteProtocolLlcToGroup OBJECT-TYPE
        SYNTAX      DisplayString
        MAX-ACCESS  read-write
        STATUS      current
        DESCRIPTION
            "To delete a LLC type to Group Name map entry.
             Syntax: <dsap> <ssap>"
        ::= { iProtocolBasedVLAN 6 }

    -- 1.3.6.1.4.1.4756.108.160.2.7
    iProtocolToGroupMappingTable OBJECT-TYPE
        SYNTAX      SEQUENCE OF IProtocolToGroupMappingEntry
        MAX-ACCESS  not-accessible
        STATUS      current
        DESCRIPTION
            "This table shows protocol to group mapped entries."
        ::= { iProtocolBasedVLAN 7 }

    -- 1.3.6.1.4.1.4756.108.160.2.7.1
    iProtocolToGroupMappingEntry OBJECT-TYPE
        SYNTAX      IProtocolToGroupMappingEntry
        MAX-ACCESS  not-accessible
        STATUS      current
        DESCRIPTION
            "The Entry of Protocol to Group Mapping table."
        INDEX { iProtocolToGroupMappingIndex }
        ::= { iProtocolToGroupMappingTable 1 }

    IProtocolToGroupMappingEntry ::=
        SEQUENCE {
            iProtocolToGroupMappingIndex   Integer32,
            iProtocolToGroupFrameType      INTEGER,
            iProtocolToGroupValue          DisplayString,
            iProtocolToGroupName           DisplayString
        }

        -- 1.3.6.1.4.1.4756.108.160.2.7.1.1    
        iProtocolToGroupMappingIndex OBJECT-TYPE
            SYNTAX      Integer32 (1..64)
            MAX-ACCESS  read-only
            STATUS      current
            DESCRIPTION
                "Indicates the Index of Protocol to Group Mapping table."
            ::= { iProtocolToGroupMappingEntry 1 }

        -- 1.3.6.1.4.1.4756.108.160.2.7.1.2    
        iProtocolToGroupFrameType OBJECT-TYPE
            SYNTAX      INTEGER {
                            ethernet(1),
                            snap(2),
                            llc(3)
                        }
            MAX-ACCESS  read-only
            STATUS      current
            DESCRIPTION
                "Frame Type can have one of Ethernet, SNAP or LLC."
            ::= { iProtocolToGroupMappingEntry 2 }

        -- 1.3.6.1.4.1.4756.108.160.2.7.1.3    
        iProtocolToGroupValue OBJECT-TYPE
            SYNTAX      DisplayString
            MAX-ACCESS  read-only
            STATUS      current
            DESCRIPTION
                "This value depends on the three different Frame Types:
                 Ethernet, LLC and SNAP."
            ::= { iProtocolToGroupMappingEntry 3 }

        -- 1.3.6.1.4.1.4756.108.160.2.7.1.4    
        iProtocolToGroupName OBJECT-TYPE
            SYNTAX      DisplayString
            MAX-ACCESS  read-only
            STATUS      current
            DESCRIPTION
                "A valid Group Name is a unique 16-character long string for every entry which
                 consists of a combination of alphabets (a-z or A-Z) and integers(0-9).
                 Note: special character and underscore(_) are not allowed."
            ::= { iProtocolToGroupMappingEntry 4 }

    -- 1.3.6.1.4.1.4756.108.160.2.8
    iAddProtocolGroupToVLAN  OBJECT-TYPE
        SYNTAX      DisplayString
        MAX-ACCESS  read-write
        STATUS      current
        DESCRIPTION                                  
            "To add a new entry in Group-to-VLAN Mapping table.
             Syntax: <group_name> <vid>
             A valid Group Name is a string of atmost 16 characters which consists of
             a combination of alphabets (a-z or A-Z) and integers(0-9),
             no special character is allowed. whichever Group name you try map to a VLAN must be
             present in Protocol to Group mapping table and must not be
             preused by any other existing mapping entry on the table.
             Legal values for a VLAN ID are 1 through 4095."
        ::= { iProtocolBasedVLAN 8 }

    -- 1.3.6.1.4.1.4756.108.160.2.9
    iDeleteProtocolGroupToVLAN OBJECT-TYPE
        SYNTAX      DisplayString
        MAX-ACCESS  read-write
        STATUS      current
        DESCRIPTION                                  
            "To delete a Group-to-VLAN Mapping entry.
             Syntax: <group_name>"
        ::= { iProtocolBasedVLAN 9 }

    -- 1.3.6.1.4.1.4756.108.160.2.10
    iGroupToVlanMappingTable OBJECT-TYPE
        SYNTAX      SEQUENCE OF IGroupToVlanMappingEntry
        MAX-ACCESS  not-accessible
        STATUS      current
        DESCRIPTION
            "This table shows protocol to group mapped entries."
        ::= { iProtocolBasedVLAN 10 }

    -- 1.3.6.1.4.1.4756.108.160.2.10.1
    iGroupToVlanMappingEntry OBJECT-TYPE
        SYNTAX      IGroupToVlanMappingEntry
        MAX-ACCESS  not-accessible
        STATUS      current
        DESCRIPTION
            "The Entry of Protocol to Group Mapping table."
        INDEX { iGroupToVlanMappingIndex }
        ::= { iGroupToVlanMappingTable 1 }

    IGroupToVlanMappingEntry ::=
        SEQUENCE {
            iGroupToVlanMappingIndex       Integer32,
            iGroupToVlanMappingGroupName   DisplayString,
            iGroupToVlanMappingVlanID      Integer32,
            iGroupToVlanMappingPortMembers DisplayString
        }

        -- 1.3.6.1.4.1.4756.108.160.2.10.1.1    
        iGroupToVlanMappingIndex OBJECT-TYPE
            SYNTAX      Integer32 (1..128)
            MAX-ACCESS  read-only
            STATUS      current
            DESCRIPTION
                "Indicates the Index of Group to VLAN Mapping table."
            ::= { iGroupToVlanMappingEntry 1 }

        -- 1.3.6.1.4.1.4756.108.160.2.10.1.2    
        iGroupToVlanMappingGroupName OBJECT-TYPE
            SYNTAX      DisplayString
            MAX-ACCESS  read-only
            STATUS      current
            DESCRIPTION
                "Indicates Group name map to a VLAN."
            ::= { iGroupToVlanMappingEntry 2 }

        -- 1.3.6.1.4.1.4756.108.160.2.10.1.3    
        iGroupToVlanMappingVlanID OBJECT-TYPE
            SYNTAX      Integer32 (1..4095)
            MAX-ACCESS  read-only
            STATUS      current
            DESCRIPTION
                "Indicates the ID to which Group Name will be mapped."
            ::= { iGroupToVlanMappingEntry 3 }

        -- 1.3.6.1.4.1.4756.108.160.2.10.1.4    
        iGroupToVlanMappingPortMembers OBJECT-TYPE
            SYNTAX      DisplayString
            MAX-ACCESS  read-write
            STATUS      current
            DESCRIPTION
                "To include or exclude the port from the mapping entry."
            ::= { iGroupToVlanMappingEntry 4 }

    -- 1.3.6.1.4.1.4756.108.160.3
    iIpSubnetBasedVLAN  OBJECT IDENTIFIER ::= { iVCL 3 }

    -- 1.3.6.1.4.1.4756.108.160.3.1
    iAddIpSubnetBasedVce OBJECT-TYPE
        SYNTAX      DisplayString
        MAX-ACCESS  read-write
        STATUS      current
        DESCRIPTION                                  
            "Add a new IP subnet-based VLAN entry.
             Syntax: <vce_id> <ip_addr> <mask_length> 
             By default, VLAN ID is 1 and all ports are members"
        ::= { iIpSubnetBasedVLAN 1 }

    -- 1.3.6.1.4.1.4756.108.160.3.2
    iDeleteIpSubnetBasedVce OBJECT-TYPE
        SYNTAX      DisplayString
        MAX-ACCESS  read-write
        STATUS      current
        DESCRIPTION
            "To delete a IP subnet-based VLAN entry.
             Syntax: <vce_id>"
        ::= { iIpSubnetBasedVLAN 2 }

    -- 1.3.6.1.4.1.4756.108.160.3.3
    iIpSubnetBasedVlanConfigTable OBJECT-TYPE
        SYNTAX      SEQUENCE OF IIpSubnetBasedVlanConfigEntry
        MAX-ACCESS  not-accessible
        STATUS      current
        DESCRIPTION
            "The IP subnet-based VLAN enties can be configured here."
        ::= { iIpSubnetBasedVLAN 3 }

    -- 1.3.6.1.4.1.4756.108.160.3.3.1
    iIpSubnetBasedVlanConfigEntry OBJECT-TYPE
        SYNTAX      IIpSubnetBasedVlanConfigEntry
        MAX-ACCESS  not-accessible
        STATUS      current
        DESCRIPTION
            "The Entry of IP subnet-based VLAN table."
        INDEX { iIpSubnetBasedVceId }
        ::= { iIpSubnetBasedVlanConfigTable 1 }

    IIpSubnetBasedVlanConfigEntry ::=
        SEQUENCE {
            iIpSubnetBasedVceId              Integer32,
            iIpSubnetBasedVceIpAddress       IpAddress,
            iIpSubnetBasedVceMaskLength      Integer32,
            iIpSubnetBasedVceVlanId          Integer32,
            iIpSubnetBasedVcePortMembers     DisplayString
        }

        -- 1.3.6.1.4.1.4756.108.160.3.3.1.1    
        iIpSubnetBasedVceId OBJECT-TYPE
            SYNTAX      Integer32 (1..128)
            MAX-ACCESS  read-only
            STATUS      current
            DESCRIPTION
                "Indicates the index of the entry table."
            ::= { iIpSubnetBasedVlanConfigEntry 1 }

        -- 1.3.6.1.4.1.4756.108.160.3.3.1.2    
        iIpSubnetBasedVceIpAddress OBJECT-TYPE
            SYNTAX      IpAddress
            MAX-ACCESS  read-only
            STATUS      current                          
            DESCRIPTION
                "Indicates the IP address.
                 The IP address is in the format x.y.z.w where x, y, z, and w
                 are decimal numbers between 0 and 255."
            ::= { iIpSubnetBasedVlanConfigEntry 2 }

        -- 1.3.6.1.4.1.4756.108.160.3.3.1.3    
        iIpSubnetBasedVceMaskLength OBJECT-TYPE
            SYNTAX      Integer32 (1..32)
            MAX-ACCESS  read-only
            STATUS      current
            DESCRIPTION
                "Indicates the network mask length."
            ::= { iIpSubnetBasedVlanConfigEntry 3 }

        -- 1.3.6.1.4.1.4756.108.160.3.3.1.4    
        iIpSubnetBasedVceVlanId OBJECT-TYPE
            SYNTAX      Integer32 (1..4095)
            MAX-ACCESS  read-write
            STATUS      current
            DESCRIPTION
                "Indicates the VLAN ID. VLAN ID can be changed for the existing entries."
            ::= { iIpSubnetBasedVlanConfigEntry 4 }

        -- 1.3.6.1.4.1.4756.108.160.3.3.1.5    
        iIpSubnetBasedVcePortMembers OBJECT-TYPE
            SYNTAX      DisplayString
            MAX-ACCESS  read-write
            STATUS      current
            DESCRIPTION
                "To include or exclude the port from IP subnet-based VLAN entry."
            ::= { iIpSubnetBasedVlanConfigEntry 5 }
            
-- QoS
    -- 1.3.6.1.4.1.4756.108.170
    iQoS  OBJECT IDENTIFIER ::= { msw4424a 170 }

    -- 1.3.6.1.4.1.4756.108.170.1
    iQosPorts  OBJECT IDENTIFIER ::= { iQoS 1 }

    -- 1.3.6.1.4.1.4756.108.170.1.1
    iQosRxPortClassifiedTable OBJECT-TYPE
        SYNTAX      SEQUENCE OF IQosRxPortClassifiedEntry
        MAX-ACCESS  not-accessible
        STATUS      current
        DESCRIPTION
            "This table allows you to configure the basic QoS Ingress Classification settings for all ports."
        ::= { iQosPorts 1 }

    -- 1.3.6.1.4.1.4756.108.170.1.1.1
    iQosRxPortClassifiedEntry OBJECT-TYPE
        SYNTAX      IQosRxPortClassifiedEntry
        MAX-ACCESS  not-accessible
        STATUS      current
        DESCRIPTION
            "The port entry for which the configuration in table."
        INDEX { iPortIndex }
        ::= { iQosRxPortClassifiedTable 1 }

    IQosRxPortClassifiedEntry ::=
        SEQUENCE {
            iQosRxPortQosClass         Integer32,
            iQosRxPortDpLevel          Integer32,
            iQosRxPortPCP              Integer32,
            iQosRxPortDEI              Integer32,
            iQosRxPortTagClassified    INTEGER,
            iQosRxPortDscpBased        TruthValue
        }

        -- 1.3.6.1.4.1.4756.108.170.1.1.1.1    
        iQosRxPortQosClass OBJECT-TYPE
            SYNTAX      Integer32 (0..7)
            MAX-ACCESS  read-write
            STATUS      current
            DESCRIPTION
                "Controls the default QoS class,
                 i.e., the QoS class for frames not classified in any other way.
                 There is a one to one mapping between QoS class, queue and priority.
                 A QoS class of 0 (zero) has the lowest priority."
            ::= { iQosRxPortClassifiedEntry 1 }

        -- 1.3.6.1.4.1.4756.108.170.1.1.1.2    
        iQosRxPortDpLevel OBJECT-TYPE
            SYNTAX      Integer32 (0..1)
            MAX-ACCESS  read-write
            STATUS      current
            DESCRIPTION
                "Controls the default DP(Drop Precedence) level,
                 i.e., the DP level for frames not classified in any other way."
            ::= { iQosRxPortClassifiedEntry 2 }

        -- 1.3.6.1.4.1.4756.108.170.1.1.1.3    
        iQosRxPortPCP OBJECT-TYPE
            SYNTAX      Integer32 (0..7)
            MAX-ACCESS  read-write
            STATUS      current
            DESCRIPTION
                "Controls the default PCP(Priority Code Point) for untagged frames."
            ::= { iQosRxPortClassifiedEntry 3 }

        -- 1.3.6.1.4.1.4756.108.170.1.1.1.4    
        iQosRxPortDEI OBJECT-TYPE
            SYNTAX      Integer32 (0..1)
            MAX-ACCESS  read-write
            STATUS      current
            DESCRIPTION
                "Controls the default DEI(Data Encryption Standard) for untagged frames."
            ::= { iQosRxPortClassifiedEntry 4 }

        -- 1.3.6.1.4.1.4756.108.170.1.1.1.5    
        iQosRxPortTagClassified OBJECT-TYPE
            SYNTAX      INTEGER {
                            enabled(1),
                            disabled(2)
                        }
            MAX-ACCESS  read-write
            STATUS      current
            DESCRIPTION
                "The classification mode for tagged frames on this port.
                 Disabled: Use default QoS class and DP level for tagged frames.
                 Enabled: Use mapped versions of PCP and DEI for tagged frames."
            ::= { iQosRxPortClassifiedEntry 5 }

        -- 1.3.6.1.4.1.4756.108.170.1.1.1.6    
        iQosRxPortDscpBased OBJECT-TYPE
            SYNTAX      TruthValue
            MAX-ACCESS  read-write
            STATUS      current
            DESCRIPTION
                "To enable DSCP Based QoS Ingress Port Classification."
            ::= { iQosRxPortClassifiedEntry 6 }

    -- 1.3.6.1.4.1.4756.108.170.1.2
    iQosRxPortTagMappingTable OBJECT-TYPE
        SYNTAX      SEQUENCE OF IQosRxPortTagMappingEntry
        MAX-ACCESS  not-accessible
        STATUS      current
        DESCRIPTION
            "The clasification mode for tagged frames are configured on this table."
        ::= { iQosPorts 2 }

    -- 1.3.6.1.4.1.4756.108.170.1.2.1
    iQosRxPortTagMappingEntry OBJECT-TYPE
        SYNTAX      IQosRxPortTagMappingEntry
        MAX-ACCESS  not-accessible
        STATUS      current
        DESCRIPTION
            "The port entry for which the configuration in table."
        INDEX { iPortIndex, iQosRxPortMappingOfPCP, iQosRxPortMappingOfDEI }
        ::= { iQosRxPortTagMappingTable 1 }

    IQosRxPortTagMappingEntry ::=
        SEQUENCE {
            iQosRxPortMappingOfPCP         Integer32,
            iQosRxPortMappingOfDEI         Integer32,
            iQosRxPortMappingToQosClass    Integer32,
            iQosRxPortMappingToDpLevel     Integer32
        }

        -- 1.3.6.1.4.1.4756.108.170.1.2.1.1    
        iQosRxPortMappingOfPCP OBJECT-TYPE
            SYNTAX      Integer32 (0..7)
            MAX-ACCESS  read-only
            STATUS      current
            DESCRIPTION
                "Controls the mapping of the PCP classified."
            ::= { iQosRxPortTagMappingEntry 1 }

        -- 1.3.6.1.4.1.4756.108.170.1.2.1.2    
        iQosRxPortMappingOfDEI OBJECT-TYPE
            SYNTAX      Integer32 (0..1)
            MAX-ACCESS  read-only
            STATUS      current
            DESCRIPTION
                "Controls the mapping of the DEI classified."
            ::= { iQosRxPortTagMappingEntry 2 }

        -- 1.3.6.1.4.1.4756.108.170.1.2.1.3    
        iQosRxPortMappingToQosClass OBJECT-TYPE
            SYNTAX      Integer32 (0..7)
            MAX-ACCESS  read-write
            STATUS      current
            DESCRIPTION
                "Controls the mapping to QoS class values."
            ::= { iQosRxPortTagMappingEntry 3 }

        -- 1.3.6.1.4.1.4756.108.170.1.2.1.4    
        iQosRxPortMappingToDpLevel OBJECT-TYPE
            SYNTAX      Integer32 (0..1)
            MAX-ACCESS  read-write
            STATUS      current
            DESCRIPTION
                "Controls the mapping to DP level values."
            ::= { iQosRxPortTagMappingEntry 4 }

    -- 1.3.6.1.4.1.4756.108.170.1.3
    iQosRxPortPolicersTable OBJECT-TYPE
        SYNTAX      SEQUENCE OF IQosRxPortPolicersEntry
        MAX-ACCESS  not-accessible
        STATUS      current
        DESCRIPTION
            "This table allows you to configure the Policer settings for all ports."
        ::= { iQosPorts 3 }

    -- 1.3.6.1.4.1.4756.108.170.1.3.1
    iQosRxPortPolicersEntry OBJECT-TYPE
        SYNTAX      IQosRxPortPolicersEntry
        MAX-ACCESS  not-accessible
        STATUS      current
        DESCRIPTION
            "The port entry for which the configuration in table."
        INDEX { iPortIndex }
        ::= { iQosRxPortPolicersTable 1 }

    IQosRxPortPolicersEntry ::=
        SEQUENCE {
            iQosRxPortPolicyEnabled        TruthValue,
            iQosRxPortPolicyRate           Integer32,
            iQosRxPortPolicyUnit           INTEGER
        }

        -- 1.3.6.1.4.1.4756.108.170.1.3.1.1    
        iQosRxPortPolicyEnabled OBJECT-TYPE
            SYNTAX      TruthValue
            MAX-ACCESS  read-write
            STATUS      current
            DESCRIPTION
                "Controls whether the policer is enabled on this switch port."
            ::= { iQosRxPortPolicersEntry 1 }

        -- 1.3.6.1.4.1.4756.108.170.1.3.1.2    
        iQosRxPortPolicyRate OBJECT-TYPE
            SYNTAX      Integer32 (100..3300000)
            MAX-ACCESS  read-write
            STATUS      current
            DESCRIPTION
                "Controls the rate for the policer. The default value is 500.
                 This value is restricted to 100-3300000."
            DEFVAL     { 500 }     
            ::= { iQosRxPortPolicersEntry 2 }

        -- 1.3.6.1.4.1.4756.108.170.1.3.1.3    
        iQosRxPortPolicyUnit OBJECT-TYPE
            SYNTAX      INTEGER {
                            kbps(1),
                            fps(2)
                        }
            MAX-ACCESS  read-write
            STATUS      current
            DESCRIPTION
                "Controls the unit of measure for the policer rate as kbps or fps.
                 The default value is 'kbps'."
            DEFVAL     { kbps }     
            ::= { iQosRxPortPolicersEntry 3 }

    -- 1.3.6.1.4.1.4756.108.170.1.4
    iQosTxPortSchedulerAndShaperTable OBJECT-TYPE
        SYNTAX      SEQUENCE OF IQosTxPortSchedulerAndShaperEntry
        MAX-ACCESS  not-accessible
        STATUS      current
        DESCRIPTION
            "This table allows you to configure the Scheduler Mode and Shaper for all ports."
        ::= { iQosPorts 4 }

    -- 1.3.6.1.4.1.4756.108.170.1.4.1
    iQosTxPortSchedulerAndShaperEntry OBJECT-TYPE
        SYNTAX      IQosTxPortSchedulerAndShaperEntry
        MAX-ACCESS  not-accessible
        STATUS      current
        DESCRIPTION
            "The port entry for which the configuration in table."
        INDEX { iPortIndex }
        ::= { iQosTxPortSchedulerAndShaperTable 1 }

    IQosTxPortSchedulerAndShaperEntry ::=
        SEQUENCE {
            iQosTxPortSchedulerMode    INTEGER,
            iQosTxPortShaperEnabled    TruthValue,
            iQosTxPortShaperRate       Integer32
        }

        -- 1.3.6.1.4.1.4756.108.170.1.4.1.1    
        iQosTxPortSchedulerMode OBJECT-TYPE
            SYNTAX      INTEGER {
                            strictPriority(1),
                            weighted(2)
                        }
            MAX-ACCESS  read-write
            STATUS      current
            DESCRIPTION
                "Controls whether the scheduler mode is 'Strict Priority' or 'Weighted' on this port."
            ::= { iQosTxPortSchedulerAndShaperEntry 1 }

        -- 1.3.6.1.4.1.4756.108.170.1.4.1.2    
        iQosTxPortShaperEnabled OBJECT-TYPE
            SYNTAX      TruthValue
            MAX-ACCESS  read-write
            STATUS      current
            DESCRIPTION
                "Controls whether the port shaper is enabled for this port."
            ::= { iQosTxPortSchedulerAndShaperEntry 2 }

        -- 1.3.6.1.4.1.4756.108.170.1.4.1.3    
        iQosTxPortShaperRate OBJECT-TYPE
            SYNTAX      Integer32 (100..3300000)
            UNITS       "kbps"
            MAX-ACCESS  read-write
            STATUS      current
            DESCRIPTION
                "Controls the rate for the shaper. The default value is 500 kbps.
                 This value is restricted to 100-3300000 kbps."
            DEFVAL     { 500 }     
            ::= { iQosTxPortSchedulerAndShaperEntry 3 }

    -- 1.3.6.1.4.1.4756.108.170.1.5
    iQosTxPortQueueSchedulerTable OBJECT-TYPE
        SYNTAX      SEQUENCE OF IQosTxPortQueueSchedulerEntry
        MAX-ACCESS  not-accessible
        STATUS      current
        DESCRIPTION
            "This table allows you to configure the Queue Scheduler Weight for all ports."
        ::= { iQosPorts 5 }

    -- 1.3.6.1.4.1.4756.108.170.1.5.1
    iQosTxPortQueueSchedulerEntry OBJECT-TYPE
        SYNTAX      IQosTxPortQueueSchedulerEntry
        MAX-ACCESS  not-accessible
        STATUS      current
        DESCRIPTION
            "The port entry for which the configuration in table."
        INDEX { iPortIndex, iQosTxPortQueueIndex }
        ::= { iQosTxPortQueueSchedulerTable 1 }

    IQosTxPortQueueSchedulerEntry ::=
        SEQUENCE {
            iQosTxPortQueueIndex       Integer32,
            iQosTxPortQueueWeight      Integer32,
            iQosTxPortQueuePercent     DisplayString
        }

        -- 1.3.6.1.4.1.4756.108.170.1.5.1.1    
        iQosTxPortQueueIndex OBJECT-TYPE
            SYNTAX      Integer32 (0..5)
            MAX-ACCESS  read-only
            STATUS      current
            DESCRIPTION
                "The egress Queue Scheduler index."
            ::= { iQosTxPortQueueSchedulerEntry 1 }

        -- 1.3.6.1.4.1.4756.108.170.1.5.1.2    
        iQosTxPortQueueWeight OBJECT-TYPE
            SYNTAX      Integer32 (1..100)
            MAX-ACCESS  read-write
            STATUS      current
            DESCRIPTION
                "Controls the weight for this queue. The default value is 17.
                 This value is restricted to 1-100.
                 This parameter is only affected if Scheduler Mode is set to 'Weighted'." 
            DEFVAL     { 17 }     
            ::= { iQosTxPortQueueSchedulerEntry 2 }

        -- 1.3.6.1.4.1.4756.108.170.1.5.1.3    
        iQosTxPortQueuePercent OBJECT-TYPE
            SYNTAX      DisplayString
            MAX-ACCESS  read-only
            STATUS      current
            DESCRIPTION
                "Shows the weight in percent for this queue.
                 This parameter is only shown if Scheduler Mode is set to 'Weighted'."
            ::= { iQosTxPortQueueSchedulerEntry 3 }

    -- 1.3.6.1.4.1.4756.108.170.1.6
    iQosTxPortQueueShapersTable OBJECT-TYPE
        SYNTAX      SEQUENCE OF IQosTxPortQueueShapersEntry
        MAX-ACCESS  not-accessible
        STATUS      current
        DESCRIPTION
            "This table allows you to configure the Scheduler Mode and Shaper for all ports."
        ::= { iQosPorts 6 }

    -- 1.3.6.1.4.1.4756.108.170.1.6.1
    iQosTxPortQueueShapersEntry OBJECT-TYPE
        SYNTAX      IQosTxPortQueueShapersEntry
        MAX-ACCESS  not-accessible
        STATUS      current
        DESCRIPTION
            "The port entry for which the configuration in table."
        INDEX { iPortIndex, iQosTxPortQueueIndex }
        ::= { iQosTxPortQueueShapersTable 1 }

    IQosTxPortQueueShapersEntry ::=
        SEQUENCE {
            iQosTxPortQueueShaperEnabled   TruthValue,
            iQosTxPortQueueShaperRate      Integer32,
            iQosTxPortQueueShaperExcess    TruthValue
        }

        -- 1.3.6.1.4.1.4756.108.170.1.6.1.1    
        iQosTxPortQueueShaperEnabled OBJECT-TYPE
            SYNTAX      TruthValue
            MAX-ACCESS  read-write
            STATUS      current
            DESCRIPTION
                "Controls whether the queue shaper is enabled for this queue on this port."
            ::= { iQosTxPortQueueShapersEntry 1 }

        -- 1.3.6.1.4.1.4756.108.170.1.6.1.2    
        iQosTxPortQueueShaperRate OBJECT-TYPE
            SYNTAX      Integer32 (100..3300000)
            UNITS       "kbps"
            MAX-ACCESS  read-write
            STATUS      current
            DESCRIPTION
                "Controls the rate for the queue shaper.
                 This parameter is only affected if Port Queue Mode is enabled.
                 This value is restricted to 100-3300000 kbps.
                 The default value is 500 kbps."
            DEFVAL     { 500 }     
            ::= { iQosTxPortQueueShapersEntry 2 }

        -- 1.3.6.1.4.1.4756.108.170.1.6.1.3    
        iQosTxPortQueueShaperExcess OBJECT-TYPE
            SYNTAX      TruthValue
            MAX-ACCESS  read-write
            STATUS      current
            DESCRIPTION
                "Controls whether the queue is allowed to use excess bandwidth.
                 This parameter is only affected if Port Queue Mode is enabled."
            ::= { iQosTxPortQueueShapersEntry 3 }

    -- 1.3.6.1.4.1.4756.108.170.1.7
    iQosTxPortTagRemarkingTable OBJECT-TYPE
        SYNTAX      SEQUENCE OF IQosTxPortTagRemarkingEntry
        MAX-ACCESS  not-accessible
        STATUS      current
        DESCRIPTION
            "This table allows you to configure the egress Port Tag Remarking for all ports."
        ::= { iQosPorts 7 }

    -- 1.3.6.1.4.1.4756.108.170.1.7.1
    iQosTxPortTagRemarkingEntry OBJECT-TYPE
        SYNTAX      IQosTxPortTagRemarkingEntry
        MAX-ACCESS  not-accessible
        STATUS      current
        DESCRIPTION
            "The port entry for which the configuration in table."
        INDEX { iPortIndex }
        ::= { iQosTxPortTagRemarkingTable 1 }

    IQosTxPortTagRemarkingEntry ::=
        SEQUENCE {
            iQosTxPortTagRemarkingMode     INTEGER
        }

        -- 1.3.6.1.4.1.4756.108.170.1.7.1.1    
        iQosTxPortTagRemarkingMode OBJECT-TYPE
            SYNTAX      INTEGER {
                            classified(1),
                            default(2),
                            mapped(3)
                        }
            MAX-ACCESS  read-write
            STATUS      current
            DESCRIPTION
                "Controls the tag remarking mode for this port.
                 Classified: Use classified PCP/DEI values.
                 Default: Use default PCP/DEI values.
                 Mapped: Use mapped versions of QoS class and DP level."
            ::= { iQosTxPortTagRemarkingEntry 1 }

    -- 1.3.6.1.4.1.4756.108.170.1.8
    iQosTxPortDefaultTagRemarkingTable OBJECT-TYPE
        SYNTAX      SEQUENCE OF IQosTxPortDefaultTagRemarkingEntry
        MAX-ACCESS  not-accessible
        STATUS      current
        DESCRIPTION
            "This table Controls the default PCP and DEI values used
             when the Remarking Mode is set to 'Default'."
        ::= { iQosPorts 8 }

    -- 1.3.6.1.4.1.4756.108.170.1.8.1
    iQosTxPortDefaultTagRemarkingEntry OBJECT-TYPE
        SYNTAX      IQosTxPortDefaultTagRemarkingEntry
        MAX-ACCESS  not-accessible
        STATUS      current
        DESCRIPTION
            "The port entry for which the configuration in table."
        INDEX { iPortIndex }
        ::= { iQosTxPortDefaultTagRemarkingTable 1 }

    IQosTxPortDefaultTagRemarkingEntry ::=
        SEQUENCE {
            iQosTxPortDefaultPcpRemarking  Integer32,
            iQosTxPortDefaultDeiRemarking  Integer32
        }

        -- 1.3.6.1.4.1.4756.108.170.1.8.1.1    
        iQosTxPortDefaultPcpRemarking OBJECT-TYPE
            SYNTAX      Integer32 (0..7)
            MAX-ACCESS  read-write
            STATUS      current
            DESCRIPTION
                "Controls the default PCP values used."
            ::= { iQosTxPortDefaultTagRemarkingEntry 1 }

        -- 1.3.6.1.4.1.4756.108.170.1.8.1.2    
        iQosTxPortDefaultDeiRemarking OBJECT-TYPE
            SYNTAX      Integer32 (0..1)
            MAX-ACCESS  read-write
            STATUS      current
            DESCRIPTION
                "Controls the default DEI values used."
            ::= { iQosTxPortDefaultTagRemarkingEntry 2 }

    -- 1.3.6.1.4.1.4756.108.170.1.9
    iQosTxPortMappingTagRemarkingTable OBJECT-TYPE
        SYNTAX      SEQUENCE OF IQosTxPortMappingTagRemarkingEntry
        MAX-ACCESS  not-accessible
        STATUS      current
        DESCRIPTION
            "This table controls the mapping of the classified (QoS class, DP level) to
             (PCP, DEI) values when the Remarking Mode is set to 'Mapped'"
        ::= { iQosPorts 9 }

    -- 1.3.6.1.4.1.4756.108.170.1.9.1
    iQosTxPortMappingTagRemarkingEntry OBJECT-TYPE
        SYNTAX      IQosTxPortMappingTagRemarkingEntry
        MAX-ACCESS  not-accessible
        STATUS      current
        DESCRIPTION
            "The port entry for which the configuration in table."
        INDEX { iPortIndex, iQosTxPortMappingOfQosClass, iQosTxPortMappingOfDpLevel }
        ::= { iQosTxPortMappingTagRemarkingTable 1 }

    IQosTxPortMappingTagRemarkingEntry ::=
        SEQUENCE {
            iQosTxPortMappingOfQosClass    Integer32,
            iQosTxPortMappingOfDpLevel     Integer32,
            iQosTxPortMappingToPCP         Integer32,
            iQosTxPortMappingToDEI         Integer32            
        }

        -- 1.3.6.1.4.1.4756.108.170.1.9.1.1    
        iQosTxPortMappingOfQosClass OBJECT-TYPE
            SYNTAX      Integer32 (0..7)
            MAX-ACCESS  read-only
            STATUS      current
            DESCRIPTION
                "Controls the mapping of the QoS class."
            ::= { iQosTxPortMappingTagRemarkingEntry 1 }

        -- 1.3.6.1.4.1.4756.108.170.1.9.1.2    
        iQosTxPortMappingOfDpLevel OBJECT-TYPE
            SYNTAX      Integer32 (0..1)
            MAX-ACCESS  read-only
            STATUS      current
            DESCRIPTION
                "Controls the mapping of the DP level."
            ::= { iQosTxPortMappingTagRemarkingEntry 2 }

        -- 1.3.6.1.4.1.4756.108.170.1.9.1.3    
        iQosTxPortMappingToPCP OBJECT-TYPE
            SYNTAX      Integer32 (0..7)
            MAX-ACCESS  read-write
            STATUS      current
            DESCRIPTION
                "Controls the mapping to PCP values."
            ::= { iQosTxPortMappingTagRemarkingEntry 3 }

        -- 1.3.6.1.4.1.4756.108.170.1.9.1.4    
        iQosTxPortMappingToDEI OBJECT-TYPE
            SYNTAX      Integer32 (0..1)
            MAX-ACCESS  read-write
            STATUS      current
            DESCRIPTION
                "Controls the mapping to DEI values."
            ::= { iQosTxPortMappingTagRemarkingEntry 4 }

    -- 1.3.6.1.4.1.4756.108.170.1.10
    iQosPortDscpConfigTable OBJECT-TYPE
        SYNTAX      SEQUENCE OF IQosPortDscpConfigEntry
        MAX-ACCESS  not-accessible
        STATUS      current
        DESCRIPTION
            "This table allows you to configure the basic QoS Port DSCP Configuration settings
             for all ports."
        ::= { iQosPorts 10 }

    -- 1.3.6.1.4.1.4756.108.170.1.10.1
    iQosPortDscpConfigEntry OBJECT-TYPE
        SYNTAX      IQosPortDscpConfigEntry
        MAX-ACCESS  not-accessible
        STATUS      current
        DESCRIPTION
            "The port entry for which the configuration in table."
        INDEX { iPortIndex }
        ::= { iQosPortDscpConfigTable 1 }

    IQosPortDscpConfigEntry ::=
        SEQUENCE {
            iQosPortDscpRxTranlateEnabled  TruthValue,
            iQosPortDscpRxClassifyMode     INTEGER,
            iQosPortDscpTxRewriteMode      INTEGER            
        }

        -- 1.3.6.1.4.1.4756.108.170.1.10.1.1    
        iQosPortDscpRxTranlateEnabled OBJECT-TYPE
            SYNTAX      TruthValue
            MAX-ACCESS  read-write
            STATUS      current
            DESCRIPTION
                "To Enable the Ingress Translation."
            ::= { iQosPortDscpConfigEntry 1 }

        -- 1.3.6.1.4.1.4756.108.170.1.10.1.2    
        iQosPortDscpRxClassifyMode OBJECT-TYPE
            SYNTAX      INTEGER {
                            disabled(1),
                            dscp0(2),
                            selected(3),
                            all(4)
                        }
            MAX-ACCESS  read-write
            STATUS      current
            DESCRIPTION
                "Classification for a port have 4 different values:
                 Disable: No Ingress DSCP Classification.
                 DSCP=0: Classify if incoming (or translated if enabled) DSCP is 0.
                 Selected: Classify only selected DSCP for which classification is enabled as
                           specified in DSCP Translation window for the specific DSCP.
                 All: Classify all DSCP."
            ::= { iQosPortDscpConfigEntry 2 }

        -- 1.3.6.1.4.1.4756.108.170.1.10.1.3    
        iQosPortDscpTxRewriteMode OBJECT-TYPE
            SYNTAX      INTEGER {
                            disabled(1),
                            enabled(2),
                            remap(3)
                        }
            MAX-ACCESS  read-write
            STATUS      current
            DESCRIPTION
                "Port Egress Rewriting can be one of -
                 Disable: No Egress rewrite.
                 Enable: Rewrite enable without remapped.
                 Remap : DSCP from analyzer is remapped and frame is remarked with remapped DSCP value.
                 "
            ::= { iQosPortDscpConfigEntry 3 }


    -- 1.3.6.1.4.1.4756.108.170.2
    iQosDSCP  OBJECT IDENTIFIER ::= { iQoS 2 }

    -- 1.3.6.1.4.1.4756.108.170.2.1
    iQosDscpBasedRxClassifiedTable OBJECT-TYPE
        SYNTAX      SEQUENCE OF IQosDscpBasedRxClassifiedEntry
        MAX-ACCESS  not-accessible
        STATUS      current
        DESCRIPTION
            "This table allows you to configure
             the basic QoS DSCP based QoS Ingress Classification settings for all switches."
        ::= { iQosDSCP 1 }

    -- 1.3.6.1.4.1.4756.108.170.2.1.1
    iQosDscpBasedRxClassifiedEntry OBJECT-TYPE
        SYNTAX      IQosDscpBasedRxClassifiedEntry
        MAX-ACCESS  not-accessible
        STATUS      current
        DESCRIPTION
            "The DSCP values in table."
        INDEX { iQosDscpRx }
        ::= { iQosDscpBasedRxClassifiedTable 1 }

    IQosDscpBasedRxClassifiedEntry ::=
        SEQUENCE {
            iQosDscpRx             Integer32,
            iQosDscpRxTrusted      TruthValue,
            iQosDscpRxToQosClass   Integer32,
            iQosDscpRxToDPL        Integer32            
        }

        -- 1.3.6.1.4.1.4756.108.170.2.1.1.1    
        iQosDscpRx OBJECT-TYPE
            SYNTAX      Integer32 (0..63)
            MAX-ACCESS  read-only
            STATUS      current
            DESCRIPTION
                "Maximum number of supported DSCP values are 64
                 and valid DSCP value ranges from 0 to 63."
            ::= { iQosDscpBasedRxClassifiedEntry 1 }

        -- 1.3.6.1.4.1.4756.108.170.2.1.1.2    
        iQosDscpRxTrusted OBJECT-TYPE
            SYNTAX      TruthValue
            MAX-ACCESS  read-write
            STATUS      current
            DESCRIPTION
                "The DSCP value is trusted."
            ::= { iQosDscpBasedRxClassifiedEntry 2 }

        -- 1.3.6.1.4.1.4756.108.170.2.1.1.3    
        iQosDscpRxToQosClass OBJECT-TYPE
            SYNTAX      Integer32 (0..7)
            MAX-ACCESS  read-write
            STATUS      current
            DESCRIPTION
                "QoS Class value can be any of (0-7)."
            ::= { iQosDscpBasedRxClassifiedEntry 3 }

        -- 1.3.6.1.4.1.4756.108.170.2.1.1.4    
        iQosDscpRxToDPL OBJECT-TYPE
            SYNTAX      Integer32 (0..3)
            MAX-ACCESS  read-write
            STATUS      current
            DESCRIPTION
                "Drop Precedence Level (0-1)."
            ::= { iQosDscpBasedRxClassifiedEntry 4 }

    -- 1.3.6.1.4.1.4756.108.170.2.2
    iDscpTranslationTable OBJECT-TYPE
        SYNTAX      SEQUENCE OF IDscpTranslationEntry
        MAX-ACCESS  not-accessible
        STATUS      current
        DESCRIPTION
            "This table allows you to configure
             the basic QoS DSCP based QoS Ingress Classification settings for all switches."
        ::= { iQosDSCP 2 }

    -- 1.3.6.1.4.1.4756.108.170.2.2.1
    iDscpTranslationEntry OBJECT-TYPE
        SYNTAX      IDscpTranslationEntry
        MAX-ACCESS  not-accessible
        STATUS      current
        DESCRIPTION
            "The DSCP values in table."
        INDEX { iTranslatedDSCP }
        ::= { iDscpTranslationTable 1 }

    IDscpTranslationEntry ::=
        SEQUENCE {
            iTranslatedDSCP        Integer32,
            iDscpRxTranslation     Integer32,
            iDscpRxClassify        TruthValue,
            iDscpTxRemapDP0        Integer32,
            iDscpTxRemapDP1        Integer32            
        }

        -- 1.3.6.1.4.1.4756.108.170.2.2.1.1    
        iTranslatedDSCP OBJECT-TYPE
            SYNTAX      Integer32 (0..63)
            MAX-ACCESS  read-only
            STATUS      current
            DESCRIPTION
                "Maximum number of supported DSCP values are 64
                 and valid DSCP value ranges from 0 to 63."
            ::= { iDscpTranslationEntry 1 }

        -- 1.3.6.1.4.1.4756.108.170.2.2.1.2    
        iDscpRxTranslation OBJECT-TYPE
            SYNTAX      Integer32 (0..63)
            MAX-ACCESS  read-write
            STATUS      current
            DESCRIPTION
                "DSCP at Ingress side can be translated to any of (0-63) DSCP values."
            ::= { iDscpTranslationEntry 2 }

        -- 1.3.6.1.4.1.4756.108.170.2.1.1.3    
        iDscpRxClassify OBJECT-TYPE
            SYNTAX      TruthValue
            MAX-ACCESS  read-write
            STATUS      current
            DESCRIPTION
                "Enable Classification at Ingress side."
            ::= { iDscpTranslationEntry 3 }

        -- 1.3.6.1.4.1.4756.108.170.2.2.1.4    
        iDscpTxRemapDP0 OBJECT-TYPE
            SYNTAX      Integer32 (0..63)
            MAX-ACCESS  read-write
            STATUS      current
            DESCRIPTION
                "Select the DSCP value from select menu to which you want to remap.
                 DSCP value ranges form 0 to 63."
            ::= { iDscpTranslationEntry 4 }

        -- 1.3.6.1.4.1.4756.108.170.2.2.1.5    
        iDscpTxRemapDP1 OBJECT-TYPE
            SYNTAX      Integer32 (0..63)
            MAX-ACCESS  read-write
            STATUS      current
            DESCRIPTION
                "Select the DSCP value from select menu to which you want to remap.
                 DSCP value ranges form 0 to 63."
            ::= { iDscpTranslationEntry 5 }

    -- 1.3.6.1.4.1.4756.108.170.2.3
    iDscpClassificationTable OBJECT-TYPE
        SYNTAX      SEQUENCE OF IDscpClassificationEntry
        MAX-ACCESS  not-accessible
        STATUS      current
        DESCRIPTION
            "This table allows you to map DSCP value to a QoS Class and DPL value."
        ::= { iQosDSCP 3 }

    -- 1.3.6.1.4.1.4756.108.170.2.3.1
    iDscpClassificationEntry OBJECT-TYPE
        SYNTAX      IDscpClassificationEntry
        MAX-ACCESS  not-accessible
        STATUS      current
        DESCRIPTION
            "The entry of QoS Class and DPL value."
        INDEX { iMapedQosClass, iMapedDPL }
        ::= { iDscpClassificationTable 1 }

    IDscpClassificationEntry ::=
        SEQUENCE {
            iMapedQosClass     Integer32,
            iMapedDPL          Integer32,
            iClassifyDSCP      Integer32           
        }

        -- 1.3.6.1.4.1.4756.108.170.2.3.1.1    
        iMapedQosClass OBJECT-TYPE
            SYNTAX      Integer32 (0..7)
            MAX-ACCESS  read-only
            STATUS      current
            DESCRIPTION
                "Available QoS Class value ranges from 0 to 7."
            ::= { iDscpClassificationEntry 1 }

        -- 1.3.6.1.4.1.4756.108.170.2.3.1.2    
        iMapedDPL OBJECT-TYPE
            SYNTAX      Integer32 (0..1)
            MAX-ACCESS  read-only
            STATUS      current
            DESCRIPTION
                "Drop Precedence Level (0-1) can be configured for all available QoS Classes."
            ::= { iDscpClassificationEntry 2 }

        -- 1.3.6.1.4.1.4756.108.170.2.3.1.3    
        iClassifyDSCP OBJECT-TYPE
            SYNTAX      Integer32 (0..63)
            MAX-ACCESS  read-write
            STATUS      current
            DESCRIPTION
                "Select DSCP value (0-63) to map DSCP to corresponding QoS Class and DPL value."
            ::= { iDscpClassificationEntry 3 }


    -- 1.3.6.1.4.1.4756.108.170.3
    iQosControlList  OBJECT IDENTIFIER ::= { iQoS 3 }

    -- 1.3.6.1.4.1.4756.108.170.3.1
    iInsertQCE OBJECT-TYPE
        SYNTAX      DisplayString
        MAX-ACCESS  read-write
        STATUS      current
        DESCRIPTION                                  
            "Inserts a new QCE to list.
             Value 0: Add QCE to end of list.
             Value 1 ~ 256: Insert new QCE before this QCE ID."
        ::= { iQosControlList 1 }

    -- 1.3.6.1.4.1.4756.108.170.3.2
    iDeleteQCE OBJECT-TYPE
        SYNTAX      DisplayString
        MAX-ACCESS  read-write
        STATUS      current
        DESCRIPTION
            "Deletes the QCE by ID. "
        ::= { iQosControlList 2 }

    -- 1.3.6.1.4.1.4756.108.170.3.3
    iMoveQceDown OBJECT-TYPE
        SYNTAX      DisplayString
        MAX-ACCESS  read-write
        STATUS      current
        DESCRIPTION
            "Moves the QCE down the list."
        ::= { iQosControlList 3 }

    -- 1.3.6.1.4.1.4756.108.170.3.4
    iQceConfigTable OBJECT-TYPE
        SYNTAX      SEQUENCE OF IQceConfigEntry
        MAX-ACCESS  not-accessible
        STATUS      current
        DESCRIPTION
            "This table allows to edit QoS Control Entry.
             An QCE consists of several parameters.
             These parameters vary according to the frame type that you select."
        ::= { iQosControlList 4 }

    -- 1.3.6.1.4.1.4756.108.170.3.4.1
    iQceConfigEntry OBJECT-TYPE
        SYNTAX      IQceConfigEntry
        MAX-ACCESS  not-accessible
        STATUS      current
        DESCRIPTION
            "The entry of QoS Control List."
        INDEX { iQceIndex }
        ::= { iQceConfigTable 1 }

    IQceConfigEntry ::=
        SEQUENCE {
            iQceIndex                      Integer32,     -- row 1
            iQceID                         Integer32,
            iQcePortMembers                DisplayString,
            iQceKeyTagType                 INTEGER,
            iQceKeyVidMode                 INTEGER,
            iQceKeyVidSpecific             Integer32,
            iQceKeyVidStart                Integer32,
            iQceKeyVidLast                 Integer32,
            iQceKeyPCP                     INTEGER,
            iQceKeyDEI                     INTEGER,        -- row 10
            iQceKeySMacMode                INTEGER,        
            iQceKeySMacSpecific            DisplayString,  
            iQceKeyDMacType                INTEGER,
            iQceKeyFrameType               INTEGER,
            iQceKeyFrameEtherTypeMode      INTEGER,
            iQceKeyFrameEtherTypeSpecific  DisplayString,
            iQceKeyFrameLlcSSapMode        INTEGER,
            iQceKeyFrameLlcSSapAddress     DisplayString,
            iQceKeyFrameLlcDSapMode        INTEGER,
            iQceKeyFrameLlcDSapAddress     DisplayString,  -- row 20
            iQceKeyFrameLlcControlMode     INTEGER,        
            iQceKeyFrameLlcControl         DisplayString,  
            iQceKeyFrameSnapPidMode        INTEGER,
            iQceKeyFrameSnapPidSpecific    DisplayString,
            iQceKeyFrameIPv4Protocol       INTEGER,
            iQceKeyFrameIPv4SportMode      INTEGER,
            iQceKeyFrameIPv4SportSpecific  Integer32,
            iQceKeyFrameIPv4SportStart     Integer32,
            iQceKeyFrameIPv4SportLast      Integer32,
            iQceKeyFrameIPv4DportMode      INTEGER,        -- row 30
            iQceKeyFrameIPv4DportSpecific  Integer32,      
            iQceKeyFrameIPv4DportStart     Integer32,      
            iQceKeyFrameIPv4DportLast      Integer32,
            iQceKeyFrameIPv4OtherValue     Integer32,
            iQceKeyFrameIPv4SourceIpMode   INTEGER,
            iQceKeyFrameIPv4SourceIP       IpAddress,
            iQceKeyFrameIPv4SourceIpMask   IpAddress,
            iQceKeyFrameIPv4FragmentOption INTEGER,
            iQceKeyFrameIPv4DscpMode       INTEGER, 
            iQceKeyFrameIPv4DscpSpecific   Integer32,      -- row 40
            iQceKeyFrameIPv4DscpStart      Integer32,      
            iQceKeyFrameIPv4DscpLast       Integer32,      
            iQceKeyFrameIPv6Protocol       INTEGER,
            iQceKeyFrameIPv6SportMode      INTEGER,
            iQceKeyFrameIPv6SportSpecific  Integer32,
            iQceKeyFrameIPv6SportStart     Integer32,
            iQceKeyFrameIPv6SportLast      Integer32,
            iQceKeyFrameIPv6DportMode      INTEGER,
            iQceKeyFrameIPv6DportSpecific  Integer32,
            iQceKeyFrameIPv6DportStart     Integer32,      -- row 50
            iQceKeyFrameIPv6DportLast      Integer32,      
            iQceKeyFrameIPv6OtherValue     Integer32,      
            iQceKeyFrameIPv6SourceIpMode   INTEGER,
            iQceKeyFrameIPv6SourceIP       IpAddress,
            iQceKeyFrameIPv6SourceIpMask   IpAddress,
            iQceKeyFrameIPv6DscpMode       INTEGER, 
            iQceKeyFrameIPv6DscpSpecific   Integer32,
            iQceKeyFrameIPv6DscpStart      Integer32,
            iQceKeyFrameIPv6DscpLast       Integer32,
            iQceActionClass                Integer32,      -- row 60
            iQceActionDPL                  Integer32,      
            iQceActionDSCP                 Integer32       -- row 62
        }

        -- 1.3.6.1.4.1.4756.108.170.3.4.1.1    
        iQceIndex OBJECT-TYPE
            SYNTAX      Integer32 (1..256)
            MAX-ACCESS  read-only
            STATUS      current
            DESCRIPTION
                "Indicates the Index of QCE entry."
            ::= { iQceConfigEntry 1 }
        
        -- 1.3.6.1.4.1.4756.108.170.3.4.1.2    
        iQceID OBJECT-TYPE
            SYNTAX      Integer32 (1..256)
            MAX-ACCESS  read-only
            STATUS      current
            DESCRIPTION
                "Indicates the ID of QCE entry."
            ::= { iQceConfigEntry 2 }

        -- 1.3.6.1.4.1.4756.108.170.3.4.1.3    
        iQcePortMembers OBJECT-TYPE
            SYNTAX      DisplayString
            MAX-ACCESS  read-write
            STATUS      current                          
            DESCRIPTION
                "Indicates the port member of the QCL entry. By default all ports will be member."
            ::= { iQceConfigEntry 3 }

        -- 1.3.6.1.4.1.4756.108.170.3.4.1.4
        iQceKeyTagType OBJECT-TYPE
            SYNTAX      INTEGER {
                            any(1),
                            untag(2),
                            tag(3)
                        }
            MAX-ACCESS  read-write
            STATUS      current                          
            DESCRIPTION
                "Tag Type can be 'Any', 'Untag' or 'Tag'."
            ::= { iQceConfigEntry 4 }

        -- 1.3.6.1.4.1.4756.108.170.3.4.1.5    
        iQceKeyVidMode OBJECT-TYPE
            SYNTAX      INTEGER {
                            any(1),
                            specific(2),
                            range(3)
                        }
            MAX-ACCESS  read-write
            STATUS      current                          
            DESCRIPTION
                "VID Mode can be 'Any', 'Specific' or 'Range'."
            ::= { iQceConfigEntry 5 }

        -- 1.3.6.1.4.1.4756.108.170.3.4.1.6    
        iQceKeyVidSpecific OBJECT-TYPE
            SYNTAX      Integer32 (1..4095)
            MAX-ACCESS  read-write
            STATUS      current                          
            DESCRIPTION
                "VLAN ID can be any value in the range 1-4095 when Key VID Mode is 'Specific'."
            ::= { iQceConfigEntry 6 }

        -- 1.3.6.1.4.1.4756.108.170.3.4.1.7    
        iQceKeyVidStart OBJECT-TYPE
            SYNTAX      Integer32 (1..4094)
            MAX-ACCESS  read-write
            STATUS      current                          
            DESCRIPTION
                "The starting VID of range if Key VID Mode is 'Range'."
            ::= { iQceConfigEntry 7 }

        -- 1.3.6.1.4.1.4756.108.170.3.4.1.8    
        iQceKeyVidLast OBJECT-TYPE
            SYNTAX      Integer32 (2..4095)
            MAX-ACCESS  read-write
            STATUS      current                          
            DESCRIPTION
                "The last VID of range if Key VID Mode is 'Range'."
            ::= { iQceConfigEntry 8 }

        -- 1.3.6.1.4.1.4756.108.170.3.4.1.9    
        iQceKeyPCP OBJECT-TYPE
            SYNTAX      INTEGER {
                            any(1),
                            specific0(2),
                            specific1(3),
                            specific2(4),
                            specific3(5),
                            specific4(6),
                            specific5(7),
                            specific6(8),
                            specific7(9),
                            range0To1(10),
                            range2To3(11),
                            range4To5(12),
                            range6To7(13),
                            range0To3(14),
                            range4To7(15)
                        }   
            MAX-ACCESS  read-write
            STATUS      current                          
            DESCRIPTION
                "Priority Code Point: Valid value PCP are specific(0, 1, 2, 3, 4, 5, 6, 7) or
                 range(0-1, 2-3, 4-5, 6-7, 0-3, 4-7) or 'Any'."
            ::= { iQceConfigEntry 9 }

        -- 1.3.6.1.4.1.4756.108.170.3.4.1.10    
        iQceKeyDEI OBJECT-TYPE
            SYNTAX      INTEGER {
                            any(1),
                            specific0(2),
                            specific1(3)
                        }   
            MAX-ACCESS  read-write
            STATUS      current                          
            DESCRIPTION
                "Drop Eligible Indicator: Valid value of DEI can be any of values between 0, 1 or 'Any'."
            ::= { iQceConfigEntry 10 }

        -- 1.3.6.1.4.1.4756.108.170.3.4.1.11    
        iQceKeySMacMode OBJECT-TYPE
            SYNTAX      INTEGER {
                            any(1),
                            specific(2)
                        }   
            MAX-ACCESS  read-write
            STATUS      current                          
            DESCRIPTION
                "Source MAC address Mode: Valid value can be 'Any' or 'Specific'."
            ::= { iQceConfigEntry 11 }

        -- 1.3.6.1.4.1.4756.108.170.3.4.1.12    
        iQceKeySMacSpecific OBJECT-TYPE
            SYNTAX      DisplayString   
            MAX-ACCESS  read-write
            STATUS      current                          
            DESCRIPTION
                "Source MAC address: xx-xx-xx-xx-xx-xx or 'Any'. 
                 If a port is configured to match on DMAC/DIP, this field is the Destination MAC address
                "
            ::= { iQceConfigEntry 12 }

        -- 1.3.6.1.4.1.4756.108.170.3.4.1.13    
        iQceKeyDMacType OBJECT-TYPE
            SYNTAX      INTEGER {
                            any(1),
                            unicast(2),
                            multicast(3),
                            broadcast(4)
                        }   
            MAX-ACCESS  read-write
            STATUS      current                          
            DESCRIPTION
                "Destination MAC type: possible values are
                 'Unicast', 'Multicast', 'Broadcast' or 'Any'."
            ::= { iQceConfigEntry 13 }

        -- 1.3.6.1.4.1.4756.108.170.3.4.1.14    
        iQceKeyFrameType OBJECT-TYPE
            SYNTAX      INTEGER {
                            any(1),
                            ethernet(2),
                            llc(3),
                            snap(4),
                            ipv4(5),
                            ipv6(6)
                        }   
            MAX-ACCESS  read-write
            STATUS      current                          
            DESCRIPTION
                "Frame Type can have any of the following values:
                 Any, Ethernet, LLC, SNAP, IPv4 or IPv6"
            ::= { iQceConfigEntry 14 }

        -- 1.3.6.1.4.1.4756.108.170.3.4.1.15    
        iQceKeyFrameEtherTypeMode OBJECT-TYPE
            SYNTAX      INTEGER {
                            any(1),
                            specific(2)
                        }   
            MAX-ACCESS  read-write
            STATUS      current                          
            DESCRIPTION
                "If Key Frame Type is 'Ethernet', The Ether Type can be configured here.
                 Valid value can be 'Any' or 'Specific'.
                 The default value is 'Any'."
            DEFVAL     { any }     
            ::= { iQceConfigEntry 15 }

        -- 1.3.6.1.4.1.4756.108.170.3.4.1.16    
        iQceKeyFrameEtherTypeSpecific OBJECT-TYPE
            SYNTAX      DisplayString   
            MAX-ACCESS  read-write
            STATUS      current                          
            DESCRIPTION
                "If Key Frame Type is 'Ethernet', The Ether Type value can be configured here.
                 Valid ethernet type can have value within 0x600-0xFFFF,
                 but excluding 0x800(IPv4) and 0x86DD(IPv6)."
            ::= { iQceConfigEntry 16 }

        -- 1.3.6.1.4.1.4756.108.170.3.4.1.17    
        iQceKeyFrameLlcSSapMode OBJECT-TYPE
            SYNTAX      INTEGER {
                            any(1),
                            specific(2)
                        }   
            MAX-ACCESS  read-write
            STATUS      current                          
            DESCRIPTION
                "If Key Frame Type is 'LLC', The SSAP Address Mode can be configured here.
                 Valid value can be 'Any' or 'Specific'.
                 the default value is 'Any'."
            DEFVAL     { any }     
            ::= { iQceConfigEntry 17 }

        -- 1.3.6.1.4.1.4756.108.170.3.4.1.18    
        iQceKeyFrameLlcSSapAddress OBJECT-TYPE
            SYNTAX      DisplayString   
            MAX-ACCESS  read-write
            STATUS      current                          
            DESCRIPTION
                "If Key Frame Type is 'LLC', The SSAP Address can be configured here.
                 Valid SSAP(Source Service Access Point) can vary from 0x00 to 0xFF"
            ::= { iQceConfigEntry 18 }

        -- 1.3.6.1.4.1.4756.108.170.3.4.1.19    
        iQceKeyFrameLlcDSapMode OBJECT-TYPE
            SYNTAX      INTEGER {
                            any(1),
                            specific(2)
                        }   
            MAX-ACCESS  read-write
            STATUS      current                          
            DESCRIPTION
                "If Key Frame Type is 'LLC', The DSAP Address Mode can be configured here.
                 Valid value can be 'Any' or 'Specific'.
                 the default value is 'Any'."
            DEFVAL     { any }     
            ::= { iQceConfigEntry 19 }

        -- 1.3.6.1.4.1.4756.108.170.3.4.1.20    
        iQceKeyFrameLlcDSapAddress OBJECT-TYPE
            SYNTAX      DisplayString   
            MAX-ACCESS  read-write
            STATUS      current                          
            DESCRIPTION
                "If Key Frame Type is 'LLC', The DSAP Address can be configured here.
                 Valid DSAP(Destination  Service Access Point) can vary from 0x00 to 0xFF."
            ::= { iQceConfigEntry 20 }

        -- 1.3.6.1.4.1.4756.108.170.3.4.1.21    
        iQceKeyFrameLlcControlMode OBJECT-TYPE
            SYNTAX      INTEGER {
                            any(1),
                            specific(2)
                        }   
            MAX-ACCESS  read-write
            STATUS      current                          
            DESCRIPTION
                "If Key Frame Type is 'LLC', The Control Mode can be configured here.
                 Valid value can be 'Any' or 'Specific'.
                 the default value is 'Any'."
            DEFVAL     { any }     
            ::= { iQceConfigEntry 21 }

        -- 1.3.6.1.4.1.4756.108.170.3.4.1.22    
        iQceKeyFrameLlcControl OBJECT-TYPE
            SYNTAX      DisplayString   
            MAX-ACCESS  read-write
            STATUS      current                          
            DESCRIPTION
                "If Key Frame Type is 'LLC', The Control Address can be configured here.
                 Valid Control Address can vary from 0x00 to 0xFF."
            ::= { iQceConfigEntry 22 }

        -- 1.3.6.1.4.1.4756.108.170.3.4.1.23    
        iQceKeyFrameSnapPidMode OBJECT-TYPE
            SYNTAX      INTEGER {
                            any(1),
                            specific(2)
                        }   
            MAX-ACCESS  read-write
            STATUS      current                          
            DESCRIPTION
                "If Key Frame Type is 'SNAP', The SNAP PID Mode can be configured here.
                 Valid value can be 'Any' or 'Specific'.
                 The default value is 'Any'."
            DEFVAL     { any }     
            ::= { iQceConfigEntry 23 }

        -- 1.3.6.1.4.1.4756.108.170.3.4.1.24    
        iQceKeyFrameSnapPidSpecific OBJECT-TYPE
            SYNTAX      DisplayString   
            MAX-ACCESS  read-write
            STATUS      current                          
            DESCRIPTION
                "If Key Frame Type is 'SNAP', The PID can be configured here.
                 Valid PID(a.k.a ethernet type) can have value within 0x00-0xFFFF"
            ::= { iQceConfigEntry 24 }

        -- 1.3.6.1.4.1.4756.108.170.3.4.1.25    
        iQceKeyFrameIPv4Protocol OBJECT-TYPE
            SYNTAX      INTEGER {
                            any(1),
                            udp(2),
                            tcp(3),
                            other(4)
                        }   
            MAX-ACCESS  read-write
            STATUS      current                          
            DESCRIPTION
                "If Key Frame Type is 'IPv4', The Protocol Number can be configured here.
                 IP protocol number can be 'Other'(0-255), 'TCP', 'UDP' or 'Any',
                 the default value is 'Any'"
            DEFVAL     { any }     
            ::= { iQceConfigEntry 25 }

        -- 1.3.6.1.4.1.4756.108.170.3.4.1.26    
        iQceKeyFrameIPv4SportMode OBJECT-TYPE
            SYNTAX      INTEGER {
                            any(1),
                            specific(2),
                            range(3)
                        }
            MAX-ACCESS  read-write
            STATUS      current                          
            DESCRIPTION
                "If Key Frame Type is 'IPv4' and Protocol is either TCP or UDP,
                 the Source TCP/UDP port mode can be configured here.
                 Source TCP/UDP port Mode can be 'Any', 'Specific' or 'Range',
                 the default value is 'Any'"
            DEFVAL     { any }     
            ::= { iQceConfigEntry 26 }

        -- 1.3.6.1.4.1.4756.108.170.3.4.1.27    
        iQceKeyFrameIPv4SportSpecific OBJECT-TYPE
            SYNTAX      Integer32 (0..65535)
            MAX-ACCESS  read-write
            STATUS      current                          
            DESCRIPTION
                "If Key Frame Type is 'IPv4' and Protocol is either TCP or UDP,
                 the Source TCP/UDP port number can be configured here.
                 The Source TCP/UDP port number can be any value in the range 0-65535
                 when Source TCP/UDP port Mode is 'Specific'."
            ::= { iQceConfigEntry 27 }

        -- 1.3.6.1.4.1.4756.108.170.3.4.1.28    
        iQceKeyFrameIPv4SportStart OBJECT-TYPE
            SYNTAX      Integer32 (0..65534)
            MAX-ACCESS  read-write
            STATUS      current                          
            DESCRIPTION
                "If Key Frame Type is 'IPv4' and Protocol is either TCP or UDP,
                 the starting Source TCP/UDP port number of range can be configured here.
                 It is effectively when Source TCP/UDP port Mode is 'Range'."
            ::= { iQceConfigEntry 28 }

        -- 1.3.6.1.4.1.4756.108.170.3.4.1.29    
        iQceKeyFrameIPv4SportLast OBJECT-TYPE
            SYNTAX      Integer32 (1..65535)
            MAX-ACCESS  read-write
            STATUS      current                          
            DESCRIPTION
                "If Key Frame Type is 'IPv4' and Protocol is either TCP or UDP,
                 the last Source TCP/UDP port number of range can be configured here.
                 It is effectively when Source TCP/UDP port Mode is 'Range'."
            ::= { iQceConfigEntry 29 }

        -- 1.3.6.1.4.1.4756.108.170.3.4.1.30    
        iQceKeyFrameIPv4DportMode OBJECT-TYPE
            SYNTAX      INTEGER {
                            any(1),
                            specific(2),
                            range(3)
                        }
            MAX-ACCESS  read-write
            STATUS      current                          
            DESCRIPTION
                "If Key Frame Type is 'IPv4' and Protocol is either TCP or UDP,
                 the Destination TCP/UDP port mode can be configured here.
                 Destination TCP/UDP port Mode can be 'Any', 'Specific' or 'Range',
                 the default value is 'Any'"
            DEFVAL     { any }     
            ::= { iQceConfigEntry 30 }

        -- 1.3.6.1.4.1.4756.108.170.3.4.1.31
        iQceKeyFrameIPv4DportSpecific OBJECT-TYPE
            SYNTAX      Integer32 (0..65535)
            MAX-ACCESS  read-write
            STATUS      current                          
            DESCRIPTION
                "If Key Frame Type is 'IPv4' and Protocol is either TCP or UDP,
                 the Destination TCP/UDP port number can be configured here.
                 The Destination TCP/UDP port number can be any value in the range 0-65535
                 when Destination TCP/UDP port Mode is 'Specific'."
            ::= { iQceConfigEntry 31 }

        -- 1.3.6.1.4.1.4756.108.170.3.4.1.32    
        iQceKeyFrameIPv4DportStart OBJECT-TYPE
            SYNTAX      Integer32 (0..65534)
            MAX-ACCESS  read-write
            STATUS      current                          
            DESCRIPTION
                "If Key Frame Type is 'IPv4' and Protocol is either TCP or UDP,
                 the starting Destination TCP/UDP port number of range can be configured here.
                 It is effectively when Destination TCP/UDP port Mode is 'Range'."
            ::= { iQceConfigEntry 32 }

        -- 1.3.6.1.4.1.4756.108.170.3.4.1.33    
        iQceKeyFrameIPv4DportLast OBJECT-TYPE
            SYNTAX      Integer32 (1..65535)
            MAX-ACCESS  read-write
            STATUS      current                          
            DESCRIPTION
                "If Key Frame Type is 'IPv4' and Protocol is either TCP or UDP,
                 the last Destination TCP/UDP port number of range can be configured here.
                 It is effectively when Destination TCP/UDP port Mode is 'Range'."
            ::= { iQceConfigEntry 33 }

        -- 1.3.6.1.4.1.4756.108.170.3.4.1.34    
        iQceKeyFrameIPv4OtherValue OBJECT-TYPE
            SYNTAX      Integer32 (0..255)
            MAX-ACCESS  read-write
            STATUS      current                          
            DESCRIPTION
                "The other IPv4 protocol numbercan be any value in the range 0-255
                 when IP Protocol is 'Other'."
            ::= { iQceConfigEntry 34 }

        -- 1.3.6.1.4.1.4756.108.170.3.4.1.35    
        iQceKeyFrameIPv4SourceIpMode OBJECT-TYPE
            SYNTAX      INTEGER {
                            any(1),
                            specific(2)
                        }
            MAX-ACCESS  read-write
            STATUS      current                          
            DESCRIPTION
                "IPv4 Source Address Mode can be 'Any' or 'Specific', default value is 'Any'"
            DEFVAL     { any }    
            ::= { iQceConfigEntry 35 }

        -- 1.3.6.1.4.1.4756.108.170.3.4.1.36    
        iQceKeyFrameIPv4SourceIP OBJECT-TYPE
            SYNTAX      IpAddress
            MAX-ACCESS  read-write
            STATUS      current                          
            DESCRIPTION
                "When IPv4 Source Address Mode is 'Specific',
                 The Source IP address can be configured here.
                 Source IP address is in the format x.y.z.w where x, y, z, and w
                 are decimal numbers between 0 and 255."
            ::= { iQceConfigEntry 36 }

        -- 1.3.6.1.4.1.4756.108.170.3.4.1.37    
        iQceKeyFrameIPv4SourceIpMask OBJECT-TYPE
            SYNTAX      IpAddress
            MAX-ACCESS  read-write
            STATUS      current                          
            DESCRIPTION
                "When IPv4 Source Address Mode is 'Specific',
                 The Source IP Address Mask can be configured here.
                 Mask is in the format x.y.z.w where x, y, z, and w are decimal numbers between 0 and 255.
                 When Mask is converted to a 32-bit binary string and read from left to right,
                 all bits following the first zero must also be zero."
            ::= { iQceConfigEntry 37 }

        -- 1.3.6.1.4.1.4756.108.170.3.4.1.38    
        iQceKeyFrameIPv4FragmentOption OBJECT-TYPE
            SYNTAX      INTEGER {
                            any(1),
                            yes(2),
                            no(3)
                        }
            MAX-ACCESS  read-write
            STATUS      current                          
            DESCRIPTION
                "IPv4 frame fragmented option can be 'Yes', 'No' or 'Any', default value is 'Any'"
            DEFVAL     { any }    
            ::= { iQceConfigEntry 38 }

        -- 1.3.6.1.4.1.4756.108.170.3.4.1.39    
        iQceKeyFrameIPv4DscpMode OBJECT-TYPE
            SYNTAX      INTEGER {
                            any(1),
                            specific(2),
                            range(3)
                        }
            MAX-ACCESS  read-write
            STATUS      current                          
            DESCRIPTION
                "Diffserv Code Point(DSCP) Mode can be 'Any', 'Specific' or 'Range',
                 default value is 'Any'"
            DEFVAL     { any }     
            ::= { iQceConfigEntry 39 }

        -- 1.3.6.1.4.1.4756.108.170.3.4.1.40
        iQceKeyFrameIPv4DscpSpecific OBJECT-TYPE
            SYNTAX      Integer32 (0..63)
            MAX-ACCESS  read-write
            STATUS      current                          
            DESCRIPTION
                "The DSCP can be any value in the range 0-63 when DSCP Mode is 'Specific'."
            ::= { iQceConfigEntry 40 }

        -- 1.3.6.1.4.1.4756.108.170.3.4.1.41
        iQceKeyFrameIPv4DscpStart OBJECT-TYPE
            SYNTAX      Integer32 (0..62)
            MAX-ACCESS  read-write
            STATUS      current                          
            DESCRIPTION
                "The starting DSCP value of range,
                 it is effectively when IPv4 DSCP Mode is 'Range'."
            ::= { iQceConfigEntry 41 }

        -- 1.3.6.1.4.1.4756.108.170.3.4.1.42    
        iQceKeyFrameIPv4DscpLast OBJECT-TYPE
            SYNTAX      Integer32 (1..63)
            MAX-ACCESS  read-write
            STATUS      current                          
            DESCRIPTION
                "The last DSCP value of range,
                 it is effectively when IPv4 DSCP Mode is 'Range'."
            ::= { iQceConfigEntry 42 }

        -- 1.3.6.1.4.1.4756.108.170.3.4.1.43    
        iQceKeyFrameIPv6Protocol OBJECT-TYPE
            SYNTAX      INTEGER {
                            any(1),
                            udp(2),
                            tcp(3),
                            other(4)
                        }   
            MAX-ACCESS  read-write
            STATUS      current                          
            DESCRIPTION
                "If Key Frame Type is 'IPv6', The Protocol Number can be configured here.
                 IPv6 protocol number can be 'Other'(0-255), 'TCP', 'UDP' or 'Any',
                 the default value is 'Any'"
            DEFVAL     { any }     
            ::= { iQceConfigEntry 43 }

        -- 1.3.6.1.4.1.4756.108.170.3.4.1.44    
        iQceKeyFrameIPv6SportMode OBJECT-TYPE
            SYNTAX      INTEGER {
                            any(1),
                            specific(2),
                            range(3)
                        }
            MAX-ACCESS  read-write
            STATUS      current                          
            DESCRIPTION
                "If Key Frame Type is 'IPv6' and Protocol is either TCP or UDP,
                 the Source TCP/UDP port mode can be configured here.
                 Source TCP/UDP port Mode can be 'Any', 'Specific' or 'Range',
                 the default value is 'Any'"
            DEFVAL     { any }     
            ::= { iQceConfigEntry 44 }

        -- 1.3.6.1.4.1.4756.108.170.3.4.1.45    
        iQceKeyFrameIPv6SportSpecific OBJECT-TYPE
            SYNTAX      Integer32 (0..65535)
            MAX-ACCESS  read-write
            STATUS      current                          
            DESCRIPTION
                "If Key Frame Type is 'IPv6' and Protocol is either TCP or UDP,
                 the Source TCP/UDP port number can be configured here.
                 The Source TCP/UDP port number can be any value in the range 0-65535
                 when Source TCP/UDP port Mode is 'Specific'."
            ::= { iQceConfigEntry 45 }

        -- 1.3.6.1.4.1.4756.108.170.3.4.1.46    
        iQceKeyFrameIPv6SportStart OBJECT-TYPE
            SYNTAX      Integer32 (0..65534)
            MAX-ACCESS  read-write
            STATUS      current                          
            DESCRIPTION
                "If Key Frame Type is 'IPv6' and Protocol is either TCP or UDP,
                 the starting Source TCP/UDP port number of range can be configured here.
                 It is effectively when Source TCP/UDP port Mode is 'Range'."
            ::= { iQceConfigEntry 46 }

        -- 1.3.6.1.4.1.4756.108.170.3.4.1.47    
        iQceKeyFrameIPv6SportLast OBJECT-TYPE
            SYNTAX      Integer32 (1..65535)
            MAX-ACCESS  read-write
            STATUS      current                          
            DESCRIPTION
                "If Key Frame Type is 'IPv6' and Protocol is either TCP or UDP,
                 the last Source TCP/UDP port number of range can be configured here.
                 It is effectively when Source TCP/UDP port Mode is 'Range'."
            ::= { iQceConfigEntry 47 }

        -- 1.3.6.1.4.1.4756.108.170.3.4.1.48    
        iQceKeyFrameIPv6DportMode OBJECT-TYPE
            SYNTAX      INTEGER {
                            any(1),
                            specific(2),
                            range(3)
                        }
            MAX-ACCESS  read-write
            STATUS      current                          
            DESCRIPTION
                "If Key Frame Type is 'IPv6' and Protocol is either TCP or UDP,
                 the Destination TCP/UDP port mode can be configured here.
                 Destination TCP/UDP port Mode can be 'Any', 'Specific' or 'Range',
                 the default value is 'Any'"
            DEFVAL     { any }     
            ::= { iQceConfigEntry 48 }

        -- 1.3.6.1.4.1.4756.108.170.3.4.1.49    
        iQceKeyFrameIPv6DportSpecific OBJECT-TYPE
            SYNTAX      Integer32 (0..65535)
            MAX-ACCESS  read-write
            STATUS      current                          
            DESCRIPTION
                "If Key Frame Type is 'IPv6' and Protocol is either TCP or UDP,
                 the Destination TCP/UDP port number can be configured here.
                 The Destination TCP/UDP port number can be any value in the range 0-65535
                 when Destination TCP/UDP port Mode is 'Specific'."
            ::= { iQceConfigEntry 49 }

        -- 1.3.6.1.4.1.4756.108.170.3.4.1.50    
        iQceKeyFrameIPv6DportStart OBJECT-TYPE
            SYNTAX      Integer32 (0..65534)
            MAX-ACCESS  read-write
            STATUS      current                          
            DESCRIPTION
                "If Key Frame Type is 'IPv6' and Protocol is either TCP or UDP,
                 the starting Destination TCP/UDP port number of range can be configured here.
                 It is effectively when Destination TCP/UDP port Mode is 'Range'."
            ::= { iQceConfigEntry 50 }

        -- 1.3.6.1.4.1.4756.108.170.3.4.1.51    
        iQceKeyFrameIPv6DportLast OBJECT-TYPE
            SYNTAX      Integer32 (1..65535)
            MAX-ACCESS  read-write
            STATUS      current                          
            DESCRIPTION
                "If Key Frame Type is 'IPv6' and Protocol is either TCP or UDP,
                 the last Destination TCP/UDP port number of range can be configured here.
                 It is effectively when Destination TCP/UDP port Mode is 'Range'."
            ::= { iQceConfigEntry 51 }

        -- 1.3.6.1.4.1.4756.108.170.3.4.1.52    
        iQceKeyFrameIPv6OtherValue OBJECT-TYPE
            SYNTAX      Integer32 (0..255)
            MAX-ACCESS  read-write
            STATUS      current                          
            DESCRIPTION
                "The other IPv6 protocol numbercan be any value in the range 0-255
                 when IP Protocol is 'Other'."
            ::= { iQceConfigEntry 52 }

        -- 1.3.6.1.4.1.4756.108.170.3.4.1.53    
        iQceKeyFrameIPv6SourceIpMode OBJECT-TYPE
            SYNTAX      INTEGER {
                            any(1),
                            specific(2)
                        }
            MAX-ACCESS  read-write
            STATUS      current                          
            DESCRIPTION
                "IPv6 Source Address Mode can be 'Any' or 'Specific', default value is 'Any'"
            DEFVAL     { any }    
            ::= { iQceConfigEntry 53 }
                                           
        -- 1.3.6.1.4.1.4756.108.170.3.4.1.54
        iQceKeyFrameIPv6SourceIP OBJECT-TYPE
            SYNTAX      IpAddress
            MAX-ACCESS  read-write
            STATUS      current                          
            DESCRIPTION
                "When IPv6 Source Address Mode is 'Specific',
                 The Source IPv6 address(32 LS bits) can be configured here.
                 Source IPv6 address(32 LS bits) is in the format a.b.c.d."
            ::= { iQceConfigEntry 54 }

        -- 1.3.6.1.4.1.4756.108.170.3.4.1.55    
        iQceKeyFrameIPv6SourceIpMask OBJECT-TYPE
            SYNTAX      IpAddress
            MAX-ACCESS  read-write
            STATUS      current                          
            DESCRIPTION
                "When IPv6 Source Address Mode is 'Specific',
                 The Source IPv6 Address Mask(32 LS bits) can be configured here.
                 IP Mask(32 LS bits) is in the format a.b.c.d where a, b, c, and d
                 are decimal numbers between 0 and 255.
                 When Mask is converted to a 32-bit binary string and read from left to right,
                 all bits following the first zero must also be zero."
            ::= { iQceConfigEntry 55 }

        -- 1.3.6.1.4.1.4756.108.170.3.4.1.56    
        iQceKeyFrameIPv6DscpMode OBJECT-TYPE
            SYNTAX      INTEGER {
                            any(1),
                            specific(2),
                            range(3)
                        }
            MAX-ACCESS  read-write
            STATUS      current                          
            DESCRIPTION
                "Diffserv Code Point(DSCP) Mode can be 'Any', 'Specific' or 'Range',
                 default value is 'Any'"
            DEFVAL     { any }     
            ::= { iQceConfigEntry 56 }

        -- 1.3.6.1.4.1.4756.108.170.3.4.1.57    
        iQceKeyFrameIPv6DscpSpecific OBJECT-TYPE
            SYNTAX      Integer32 (0..63)
            MAX-ACCESS  read-write
            STATUS      current                          
            DESCRIPTION
                "The DSCP can be any value in the range 0-63 when DSCP Mode is 'Specific'."
            ::= { iQceConfigEntry 57 }

        -- 1.3.6.1.4.1.4756.108.170.3.4.1.58    
        iQceKeyFrameIPv6DscpStart OBJECT-TYPE
            SYNTAX      Integer32 (0..62)
            MAX-ACCESS  read-write
            STATUS      current                          
            DESCRIPTION
                "The starting DSCP value of range,
                 it is effectively when IPv6 DSCP Mode is 'Range'."
            ::= { iQceConfigEntry 58 }

        -- 1.3.6.1.4.1.4756.108.170.3.4.1.59
        iQceKeyFrameIPv6DscpLast OBJECT-TYPE
            SYNTAX      Integer32 (1..63)
            MAX-ACCESS  read-write
            STATUS      current                          
            DESCRIPTION
                "The last DSCP value of range,
                 it is effectively when IPv6 DSCP Mode is 'Range'."
            ::= { iQceConfigEntry 59 }

        -- 1.3.6.1.4.1.4756.108.170.3.4.1.60
        iQceActionClass OBJECT-TYPE
            SYNTAX      Integer32 (-1 | 0..7)
            MAX-ACCESS  read-write
            STATUS      current                          
            DESCRIPTION
                "Valid QoS Class can be (0-7), the value -1 for default,
                 At least one of the Action Node(rcQceActionClass, iQceActionDPL and iQceActionDSCP)
                 must have non-default value!"
            ::= { iQceConfigEntry 60 }

        -- 1.3.6.1.4.1.4756.108.170.3.4.1.61    
        iQceActionDPL OBJECT-TYPE
            SYNTAX      Integer32 (-1 | 0..1)
            MAX-ACCESS  read-write
            STATUS      current                          
            DESCRIPTION
                "Valid DP Level can be (0-1), the value -1 for default,
                 At least one of the Action Node(rcQceActionClass, iQceActionDPL and iQceActionDSCP)
                 must have non-default value!"
            ::= { iQceConfigEntry 61 }

        -- 1.3.6.1.4.1.4756.108.170.3.4.1.62    
        iQceActionDSCP OBJECT-TYPE
            SYNTAX      Integer32 (-1 | 0..63)
            MAX-ACCESS  read-write
            STATUS      current                          
            DESCRIPTION
                "Valid DSCP value can be (0-63), the value -1 for default,
                 At least one of the Action Node(rcQceActionClass, iQceActionDPL and iQceActionDSCP)
                 must have non-default value!"
            ::= { iQceConfigEntry 62 }


    -- 1.3.6.1.4.1.4756.108.170.4
    iStormControl   OBJECT IDENTIFIER ::= { iQoS 4 }

    -- 1.3.6.1.4.1.4756.108.170.4.1
    iStormControlTable OBJECT-TYPE
        SYNTAX      SEQUENCE OF IStormControlEntry
        MAX-ACCESS  not-accessible
        STATUS      current
        DESCRIPTION
            "Storm control for the switch is configured on this table.
             There is a unicast storm rate control, multicast storm rate control,
             and a broadcast storm rate control. These only affect flooded frames,
             i.e. frames with a (VLAN ID, DMAC) pair not present on the MAC Address table.
             The configuration indicates the permitted packet rate for unicast, multicast or
             broadcast traffic across the switch."
        ::= { iStormControl 3 }

    -- 1.3.6.1.4.1.4756.108.170.4.1.1
    iStormControlEntry OBJECT-TYPE
        SYNTAX      IStormControlEntry
        MAX-ACCESS  not-accessible
        STATUS      current
        DESCRIPTION
            "The entry of frame type."
        INDEX { iStormControlIndex }
        ::= { iStormControlTable 1 }

    IStormControlEntry ::=
        SEQUENCE {
        		iStormControlIndex     Integer32,
            iStormControlUuicastEnable    TruthValue,
            iStormControlUuicastRate      INTEGER,
            iStormControlUuicastUnit      INTEGER,
            iStormControlBroadcastEnable    TruthValue,
            iStormControlBroadcastRate      INTEGER,
            iStormControlBroadcastUnit      INTEGER,
            iStormControlUnknownEnable    TruthValue,
            iStormControlUnknownRate      INTEGER,
            iStormControlUnknownUnit      INTEGER                        
        }
        
    	  -- 1.3.6.1.4.1.4756.108.170.4.1.1.1
        iStormControlIndex OBJECT-TYPE
            SYNTAX      Integer32 (1..29)
            MAX-ACCESS  read-only
            STATUS      current
            DESCRIPTION
                "The Index of the StormContro Port

                "
            ::= { iStormControlEntry 1 }
            

        -- 1.3.6.1.4.1.4756.108.170.4.1.1.2    
        iStormControlUuicastEnable OBJECT-TYPE
            SYNTAX      TruthValue
            MAX-ACCESS  read-write
            STATUS      current
            DESCRIPTION
                "Enable or disable the storm control status for the given frame type."
            ::= { iStormControlEntry 2 }

    	  -- 1.3.6.1.4.1.4756.108.170.4.1.1.3
        iStormControlUuicastRate OBJECT-TYPE
            SYNTAX      INTEGER 
            MAX-ACCESS  read-write
            STATUS      current
            DESCRIPTION
                "The default value is 500. This value is restricted to 100-1000000 when the Unit is kbps or fps

                "
            ::= { iStormControlEntry 3 }       

        -- 1.3.6.1.4.1.4756.108.170.4.1.1.4    
        iStormControlUuicastUnit OBJECT-TYPE
            SYNTAX      INTEGER {
                            kbps(1),                            
                            fps(2)
                        }
            MAX-ACCESS  read-write
            STATUS      current
            DESCRIPTION
                "Controls the unit of measure for the storm control rate as kbps or fps.
                "
            ::= { iStormControlEntry 4 }            

        -- 1.3.6.1.4.1.4756.108.170.4.1.1.5    
        iStormControlBroadcastEnable OBJECT-TYPE
            SYNTAX      TruthValue
            MAX-ACCESS  read-write
            STATUS      current
            DESCRIPTION
                "Enable or disable the storm control status for the given frame type."
            ::= { iStormControlEntry 5 }

    	  -- 1.3.6.1.4.1.4756.108.170.4.1.1.6
        iStormControlBroadcastRate OBJECT-TYPE
            SYNTAX      INTEGER 
            MAX-ACCESS  read-write
            STATUS      current
            DESCRIPTION
                "The default value is 500. This value is restricted to 100-1000000 when the Unit is kbps or fps

                "
            ::= { iStormControlEntry 6 }       

        -- 1.3.6.1.4.1.4756.108.170.4.1.1.7    
        iStormControlBroadcastUnit OBJECT-TYPE
            SYNTAX      INTEGER {
                            kbps(1),                            
                            fps(2)
                        }
            MAX-ACCESS  read-write
            STATUS      current
            DESCRIPTION
                "Controls the unit of measure for the storm control rate as kbps or fps.
                "
            ::= { iStormControlEntry 7 }
            
        -- 1.3.6.1.4.1.4756.108.170.4.1.1.8    
        iStormControlUnknownEnable OBJECT-TYPE
            SYNTAX      TruthValue
            MAX-ACCESS  read-write
            STATUS      current
            DESCRIPTION
                "Enable or disable the storm control status for the given frame type."
            ::= { iStormControlEntry 8 }

    	  -- 1.3.6.1.4.1.4756.108.170.4.1.1.9
        iStormControlUnknownRate OBJECT-TYPE
            SYNTAX      INTEGER 
            MAX-ACCESS  read-write
            STATUS      current
            DESCRIPTION
                "The default value is 500. This value is restricted to 100-1000000 when the Unit is kbps or fps

                "
            ::= { iStormControlEntry 9 }       

        -- 1.3.6.1.4.1.4756.108.170.4.1.1.10    
        iStormControlUnknownUnit OBJECT-TYPE
            SYNTAX      INTEGER {
                            kbps(1),                            
                            fps(2)
                        }
            MAX-ACCESS  read-write
            STATUS      current
            DESCRIPTION
                "Controls the unit of measure for the storm control rate as kbps or fps.
                "
            ::= { iStormControlEntry 10 }              
            
-- Mirroring
    -- 1.3.6.1.4.1.4756.108.180
    iMirror  OBJECT IDENTIFIER ::= { msw4424a 180 }

    -- 1.3.6.1.4.1.4756.108.180.1
    iPortToMirrorOn OBJECT-TYPE
        SYNTAX      Integer32 (0..29)
        MAX-ACCESS  read-write
        STATUS      current
        DESCRIPTION
            "Port to mirror also known as the mirror port.
             Frames from ports that have either source(rx) or destination(tx)
             mirroring enabled are mirrored on this port.
             Sets zero to disables mirroring."
        ::= { iMirror 1 }

    -- 1.3.6.1.4.1.4756.108.180.2
    iPortMirrorTable OBJECT-TYPE
        SYNTAX      SEQUENCE OF IPortMirrorEntry
        MAX-ACCESS  not-accessible
        STATUS      current
        DESCRIPTION
            "This table is used for Rx and Tx enabling."
        ::= { iMirror 2 }

    -- 1.3.6.1.4.1.4756.108.180.2.1
    iPortMirrorEntry OBJECT-TYPE
        SYNTAX      IPortMirrorEntry
        MAX-ACCESS  not-accessible
        STATUS      current
        DESCRIPTION
            "The Entry of mirroring ports."
        INDEX { iPortIndex }
        ::= { iPortMirrorTable 1 }

    IPortMirrorEntry ::=
        SEQUENCE {
            iPortMirrorMode          INTEGER
        }

        -- 1.3.6.1.4.1.4756.108.180.2.1.1    
        iPortMirrorMode OBJECT-TYPE
            SYNTAX      INTEGER {
                            disabled(1),
                            enabled(2),
                            rxOnly(3),
                            txOnly(4)
                        }
            MAX-ACCESS  read-write
            STATUS      current
            DESCRIPTION
                "Select mirror mode.
                 Rx only: Frames received on this port are mirrored on the mirror port.
                          Frames transmitted are not mirrored.
                 Tx only: Frames transmitted on this port are mirrored on the mirror port.
                          Frames received are not mirrored.
                 Disabled: Neither frames transmitted nor frames received are mirrored.
                 Enabled: Frames received and frames transmitted are mirrored on the mirror port. 
                 Note: For a given port, a frame is only transmitted once.
                 It is therefore not possible to mirror Tx frames on the mirror port.
                 Because of this, mode for the selected mirror port is limited to Disabled or Rx only."
            ::= { iPortMirrorEntry 1 }

    -- 1.3.6.1.4.1.4756.108.180.3    
    iPortMirrorCpuPortMode OBJECT-TYPE
        SYNTAX      INTEGER {
                        disabled(1),
                        enabled(2),
                        rxOnly(3),
                        txOnly(4)
                    }
        MAX-ACCESS  read-write
        STATUS      current
        DESCRIPTION
            "Select mirror mode of CPU port.
             Rx only: Frames received on this port are mirrored on the mirror port.
                      Frames transmitted are not mirrored.
             Tx only: Frames transmitted on this port are mirrored on the mirror port.
                      Frames received are not mirrored.
             Disabled: Neither frames transmitted nor frames received are mirrored.
             Enabled: Frames received and frames transmitted are mirrored on the mirror port. 
             Note: For a given port, a frame is only transmitted once.
             It is therefore not possible to mirror Tx frames on the mirror port.
             Because of this, mode for the selected mirror port is limited to Disabled or Rx only."
        ::= { iMirror 3 }


-- UPnP
    -- 1.3.6.1.4.1.4756.108.190
    iUPnP  OBJECT IDENTIFIER ::= { msw4424a 190 }

    -- 1.3.6.1.4.1.4756.108.190.1
    iUpnpMode OBJECT-TYPE
        SYNTAX      INTEGER {
                        enabled(1),
                        disabled(2)
                    }
        MAX-ACCESS  read-write
        STATUS      current
        DESCRIPTION
            "Indicates the UPnP operation mode. Possible modes are:
             Enabled: Enable UPnP mode operation.
             Disabled: Disable UPnP mode operation.
             When the mode is enabled,
             two ACEs are added automatically to trap UPNP related packets to CPU.
             The ACEs are automatically removed when the mode is disabled."
        ::= { iUPnP 1 }

    -- 1.3.6.1.4.1.4756.108.190.2
    iUpnpTTL OBJECT-TYPE
        SYNTAX      Integer32 (1..255)
        MAX-ACCESS  read-write
        STATUS      current
        DESCRIPTION
            "The TTL value is used by UPnP to send SSDP advertisement messages.
             Valid values are in the range 1 to 255."
        ::= { iUPnP 2 }

    -- 1.3.6.1.4.1.4756.108.190.3
    iUpnpAdvertisingDuration OBJECT-TYPE
        SYNTAX      Integer32 (100..86400)
        UNITS       "Seconds"
        MAX-ACCESS  read-write
        STATUS      current       
        DESCRIPTION
            "The duration, carried in SSDP packets,
             is used to inform a control point or control points how often it or they
             should receive an SSDP advertisement message from this switch.
             If a control point does not receive any message within the duration,
             it will think that the switch no longer exists. Due to the unreliable nature of UDP,
             in the standard it is recommended that such refreshing of advertisements to be done
             at less than one-half of the advertising duration. In the implementation,
             the switch sends SSDP messages periodically at the interval one-half of
             the advertising duration minus 30 seconds. Valid values are in the range 100 to 86400."
        ::= { iUPnP 3 }



-- L2CP
    -- 1.3.6.1.4.1.4756.108.210
    iL2CP  OBJECT IDENTIFIER ::= { msw4424a 210 }
    
	-- 1.3.6.1.4.1.4756.108.210.1
    iL2CPPortConfigTable OBJECT-TYPE
        SYNTAX      SEQUENCE OF IL2CPPortConfigEntry
        MAX-ACCESS  not-accessible
        STATUS      current
        DESCRIPTION
            "L2CP Port configurations Table"
        ::= { iL2CP 1 }

    -- 1.3.6.1.4.1.4756.108.200.1.1
    iL2CPPortConfigEntry OBJECT-TYPE
        SYNTAX      IL2CPPortConfigEntry
        MAX-ACCESS  not-accessible
        STATUS      current
        DESCRIPTION
            "L2CP Port configurations Entry"
        INDEX { iPortIndex }
        ::= { iL2CPPortConfigTable 1 }

    IL2CPPortConfigEntry ::=
        SEQUENCE {
            dmac-01-80-C2-00-00-00-Mode 	 INTEGER,
            dmac-01-80-C2-00-00-01-Mode 	 INTEGER,
            dmac-01-80-C2-00-00-02-Mode 	 INTEGER,
            dmac-01-80-C2-00-00-03-Mode 	 INTEGER,
            dmac-01-80-C2-00-00-04-Mode 	 INTEGER,
            dmac-01-80-C2-00-00-05-Mode 	 INTEGER,
            dmac-01-80-C2-00-00-06-Mode 	 INTEGER,
            dmac-01-80-C2-00-00-07-Mode 	 INTEGER,
            dmac-01-80-C2-00-00-08-Mode 	 INTEGER,
            dmac-01-80-C2-00-00-09-Mode 	 INTEGER,
            dmac-01-80-C2-00-00-0A-Mode 	 INTEGER,
            dmac-01-80-C2-00-00-0B-Mode 	 INTEGER,
            dmac-01-80-C2-00-00-0C-Mode 	 INTEGER,
            dmac-01-80-C2-00-00-0D-Mode 	 INTEGER,
            dmac-01-80-C2-00-00-0E-Mode 	 INTEGER,
            dmac-01-80-C2-00-00-0F-Mode 	 INTEGER,
--            dmac-01-80-C2-00-00-10-Mode 	 INTEGER,
            dmac-01-80-C2-00-00-20-Mode 	 INTEGER,
            dmac-01-80-C2-00-00-21-Mode 	 INTEGER,
            dmac-01-80-C2-00-00-22-Mode 	 INTEGER,
            dmac-01-80-C2-00-00-23-Mode 	 INTEGER,
            dmac-01-80-C2-00-00-24-Mode 	 INTEGER,
            dmac-01-80-C2-00-00-25-Mode 	 INTEGER,
            dmac-01-80-C2-00-00-26-Mode 	 INTEGER,
            dmac-01-80-C2-00-00-27-Mode 	 INTEGER,
            dmac-01-80-C2-00-00-28-Mode 	 INTEGER,
            dmac-01-80-C2-00-00-29-Mode 	 INTEGER,
            dmac-01-80-C2-00-00-2A-Mode 	 INTEGER,
            dmac-01-80-C2-00-00-2B-Mode 	 INTEGER,
            dmac-01-80-C2-00-00-2C-Mode 	 INTEGER,
            dmac-01-80-C2-00-00-2D-Mode 	 INTEGER,
            dmac-01-80-C2-00-00-2E-Mode 	 INTEGER,
            dmac-01-80-C2-00-00-2F-Mode 	 INTEGER
        }	
        
        -- 1.3.6.1.4.1.4756.108.210.1.1.1
        dmac-01-80-C2-00-00-00-Mode OBJECT-TYPE
        SYNTAX      INTEGER {
                               forward(1),
                               discard(2),
                               peer(4)
        					}
        MAX-ACCESS  read-write
        STATUS      current
        DESCRIPTION
            " 1:Forward: MAC address forward. 
			  2:Peer: MAC address redirect to CPU.
			  
              Spanning Tree Protocol (for bridges) IEEE 802.1D.
            "
        ::= { iL2CPPortConfigEntry 1 }
        
        -- 1.3.6.1.4.1.4756.108.210.1.1.2
        dmac-01-80-C2-00-00-01-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
			  
              Ethernet flow control (Pause frame) IEEE 802.3x.
            "
        ::= { iL2CPPortConfigEntry 2 }
        
        -- 1.3.6.1.4.1.4756.108.210.1.1.3
        dmac-01-80-C2-00-00-02-Mode OBJECT-TYPE
        SYNTAX      INTEGER {
                               forward(1),
                               discard(2),
                               peer(4)
        					}
        MAX-ACCESS  read-write
        STATUS      current
        DESCRIPTION
            " 1:Forward: MAC address forward. 
			  2:Peer: MAC address redirect to CPU.

              Slow protocol address: 802.3ad LACP, 802.3ah OAM, Cisco Discovery Protocol, DTP, PagP, UDLD, VTP.
            "
        ::= { iL2CPPortConfigEntry 3 }
        
        -- 1.3.6.1.4.1.4756.108.210.1.1.4
        dmac-01-80-C2-00-00-03-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.

              Ethernet flow control (Pause frame) IEEE 802.1x.
            "
        ::= { iL2CPPortConfigEntry 4 }
        
        -- 1.3.6.1.4.1.4756.108.210.1.1.5
        dmac-01-80-C2-00-00-04-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.

              BPDU MAC address.
            "
        ::= { iL2CPPortConfigEntry 5 }
        
        -- 1.3.6.1.4.1.4756.108.210.1.1.6
        dmac-01-80-C2-00-00-05-Mode OBJECT-TYPE
        SYNTAX      INTEGER {
                               forward(1),
                               discard(2),
                               peer(4)
        					}
        MAX-ACCESS  read-write
        STATUS      current
        DESCRIPTION
            " 1:Forward: MAC address forward. 
			  2:Peer: MAC address redirect to CPU.
 			  
              BPDU MAC address.
            "
        ::= { iL2CPPortConfigEntry 6 }
        
       -- 1.3.6.1.4.1.4756.108.210.1.1.7
       dmac-01-80-C2-00-00-06-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
			  
              BPDU MAC address.
            "
        ::= { iL2CPPortConfigEntry 7 }

       -- 1.3.6.1.4.1.4756.108.210.1.1.8
       dmac-01-80-C2-00-00-07-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Ethernet local management interface (E-LMI).
            "
        ::= { iL2CPPortConfigEntry 8 }
              
       -- 1.3.6.1.4.1.4756.108.210.1.1.9
       dmac-01-80-C2-00-00-08-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Spanning Tree Protocol (for provider bridges) IEEE 802.1AD.
            "
        ::= { iL2CPPortConfigEntry 9 }
        
       -- 1.3.6.1.4.1.4756.108.210.1.1.10
       dmac-01-80-C2-00-00-09-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              BPDU MAC address.
            "
        ::= { iL2CPPortConfigEntry 10 }
        
       -- 1.3.6.1.4.1.4756.108.210.1.1.11
       dmac-01-80-C2-00-00-0A-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              BPDU MAC address.
            "
        ::= { iL2CPPortConfigEntry 11 }      
       
       -- 1.3.6.1.4.1.4756.108.210.1.1.12
       dmac-01-80-C2-00-00-0B-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              BPDU MAC address.
            "
        ::= { iL2CPPortConfigEntry 12 } 
        
       -- 1.3.6.1.4.1.4756.108.210.1.1.13
       dmac-01-80-C2-00-00-0C-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              BPDU MAC address.
            "
        ::= { iL2CPPortConfigEntry 13 }
        
      -- 1.3.6.1.4.1.4756.108.210.1.1.14
      dmac-01-80-C2-00-00-0D-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.

              Provider bridge GVRP address.
            "
        ::= { iL2CPPortConfigEntry 14 }  
        
      -- 1.3.6.1.4.1.4756.108.210.1.1.15
      dmac-01-80-C2-00-00-0E-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
			  
              Link Layer Discovery Protocol.
            "
        ::= { iL2CPPortConfigEntry 15 }  

      -- 1.3.6.1.4.1.4756.108.210.1.1.16
      dmac-01-80-C2-00-00-0F-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              BPDU MAC addresses.
            "
        ::= { iL2CPPortConfigEntry 16 }
      
      -- 1.3.6.1.4.1.4756.108.210.1.1.17
--      dmac-01-80-C2-00-00-10-Mode OBJECT-TYPE
--        SYNTAX      INTEGER {
--                               forward(1),
--                               discard(2),
--                               peer(4)
--        					}
--        MAX-ACCESS  read-write
--        STATUS      current
--        DESCRIPTION
--            " 1:Forward: MAC address forward.  
--			  2:Peer: MAC address redirect to CPU.
-- 			  
--              All bridges address.
--            "
--        ::= { iL2CPPortConfigEntry 17 }
        
        -- 1.3.6.1.4.1.4756.108.210.1.1.18
        dmac-01-80-C2-00-00-20-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 18 }
        
        -- 1.3.6.1.4.1.4756.108.210.1.1.19
        dmac-01-80-C2-00-00-21-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
			  
              Reserved for use by Multiple Registration Protocol (MRP) applications.
            "
        ::= { iL2CPPortConfigEntry 19 }
        
        -- 1.3.6.1.4.1.4756.108.210.1.1.20
        dmac-01-80-C2-00-00-22-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 20 }
        
        -- 1.3.6.1.4.1.4756.108.210.1.1.21
        dmac-01-80-C2-00-00-23-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Ethernet flow control (Pause frame) IEEE 802.1x.
            "
        ::= { iL2CPPortConfigEntry 21 }
        
        -- 1.3.6.1.4.1.4756.108.210.1.1.22
        dmac-01-80-C2-00-00-24-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 22 }
        
        -- 1.3.6.1.4.1.4756.108.210.1.1.23
        dmac-01-80-C2-00-00-25-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 23 }
        
       -- 1.3.6.1.4.1.4756.108.210.1.1.24
       dmac-01-80-C2-00-00-26-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
			  
              Reserved for use by Multiple Registration Protocol (MRP) applications.
            "
        ::= { iL2CPPortConfigEntry 24 }

       -- 1.3.6.1.4.1.4756.108.210.1.1.25
       dmac-01-80-C2-00-00-27-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
			  
              Reserved for use by Multiple Registration Protocol (MRP) applications.
            "
        ::= { iL2CPPortConfigEntry 25 }
              
       -- 1.3.6.1.4.1.4756.108.210.1.1.26
       dmac-01-80-C2-00-00-28-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 26 }
        
       -- 1.3.6.1.4.1.4756.108.210.1.1.27
       dmac-01-80-C2-00-00-29-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 27 }
        
       -- 1.3.6.1.4.1.4756.108.210.1.1.28
       dmac-01-80-C2-00-00-2A-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 28 }      
       
       -- 1.3.6.1.4.1.4756.108.210.1.1.29
       dmac-01-80-C2-00-00-2B-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 29 } 
        
       -- 1.3.6.1.4.1.4756.108.210.1.1.30
       dmac-01-80-C2-00-00-2C-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 30 }
        
      -- 1.3.6.1.4.1.4756.108.210.1.1.31
      dmac-01-80-C2-00-00-2D-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
			  
              Reserved for use by Multiple Registration Protocol (MRP) applications.
            "
        ::= { iL2CPPortConfigEntry 31 }  
        
      -- 1.3.6.1.4.1.4756.108.210.1.1.32
      dmac-01-80-C2-00-00-2E-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 32 }  

      -- 1.3.6.1.4.1.4756.108.210.1.1.33
      dmac-01-80-C2-00-00-2F-Mode OBJECT-TYPE
        SYNTAX      INTEGER {
                               forward(1),
                               discard(2),
                               peer(4)
        					}
        MAX-ACCESS  read-write
        STATUS      current
        DESCRIPTION
            " 1:Forward: MAC address forward.  
			  2:Peer: MAC address redirect to CPU.
 			  
              Reserved for use by Multiple Registration Protocol (MRP) applications.
            "
        ::= { iL2CPPortConfigEntry 33 } 



                       	            
END
