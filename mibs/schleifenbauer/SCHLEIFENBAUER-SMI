-------------------------------------------------------------------------------
--
-- SCHLEIFENBAUER-DATABUS-MIB.txt: Schleifenbauer Enterprise Structure of Management Information
--
-- Copyright (c) 2021 by Schleifenbauer Holding BV
-- All rights reserved.
--
-------------------------------------------------------------------------------

SCHLEIFENBAUER-SMI DEFINITIONS ::= BEGIN

IMPORTS
    MODULE-IDENTITY,
    OBJECT-IDENTITY,
    enterprises
        FROM SNMPv2-SMI;

schleifenbauer MODULE-IDENTITY
    LAST-UPDATED
        "202106160000Z" -- June 16th, 2021
    ORGANIZATION
        "Schleifenbauer Engineering"
    CONTACT-INFO
        "Schleifenbauer Engineering
         Rietwaard 15
         5236 WC 's-Hertogenbosch
         The Netherlands
         t +31 (0)73 5230256
         support@schleifenbauer.eu
         www.schleifenbauer.eu"
    DESCRIPTION
        "The Structure of Management Information for the Schleifenbauer
         enterprise.

         Copyright (c) 2021 by Schleifenbauer Products BV"
    REVISION
        "202106160000Z" -- June 16th, 2021
    DESCRIPTION
        "The initial revision of this MIB module"
    ::= { enterprises 31034 }

schleifenbauerProducts OBJECT-IDENTITY
    STATUS current
    DESCRIPTION
        "schleifenbauerProducts is the root OBJECT IDENTIFIER from which
         sysObjectId values are assigned. Acutal values are defined in
         SCHLEIFENBAUER-PRODUCTS-MIB."
    ::= { schleifenbauer 11 }

schleifenbauerMgmt OBJECT-IDENTITY
    STATUS current
    DESCRIPTION
        "schleifenbauerMgmt is the main subtree for new mib development."
    ::= { schleifenbauer 12 }

schleifenbauerModules OBJECT-IDENTITY
    STATUS current
    DESCRIPTION
        "schleifenbauerModules provides a root object identifier from which
         MODULE-IDENTITY values may be assigned."
    ::= { schleifenbauer 13 }

END
