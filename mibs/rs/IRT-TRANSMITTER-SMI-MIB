--
-- IRT-TRANSMITTER-SMI-MIB.my
-- MIB generated by MG-SOFT Visual MIB Builder Version 6.0  Build 88
-- Thursday, May 03, 2007 at 17:54:59
--

	IRT-TRANSMITTER-SMI-MIB DEFINITIONS ::= BEGIN
 
		IMPORTS
			enterprises, MODULE-IDENTITY			
				FROM SNMPv2-SMI			
			TEXTUAL-CONVENTION			
				FROM SNMPv2-TC;
	
	
		-- 1.3.6.1.4.1.19831
		irt MODULE-IDENTITY 
			LAST-UPDATED "200705041400Z"		-- May 04, 2007 at 14:00 GMT
			ORGANIZATION 
				"IRT for WORKING-GROUP-TC-MIB"
			CONTACT-INFO 
				"Contact-info:
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"***************************************************
				Description: IRT-TRANSMITTER-SMI-MIB General structure
				
				This MIB defines the structure of a SNMP-Agent 
				for all kinds of reserve Transmitters
				
				PROJECT:    TC-MIB - TRANSMITTER-CONTROL-MIB
				OID:        1.3.6.1.4.1.19831
				FILE:       IRT-TRANSMITTER-SMI-MIB.*
				AUTHOR:     Ludmilla Leidag and Andreas Metz
				            for WORKING-GROUP-TC-MIB 
				
				  
				***************************************************"
			REVISION "200705041400Z"		-- May 04, 2007 at 14:00 GMT
			DESCRIPTION 
				"change LocalRemote
				add SFNMFN
				"
			REVISION "200612201400Z"		-- December 20, 2006 at 14:00 GMT
			DESCRIPTION 
				"Correction"
			REVISION "200609071400Z"		-- September 07, 2006 at 14:00 GMT
			DESCRIPTION 
				"Relocation of the TC-MIB from the standard OID area at IEC into the private OID area of the IRT "
			::= { enterprises 19831 }

		
	
--
-- Textual conventions
--
	
		SelectManualAuto ::= TEXTUAL-CONVENTION
			STATUS current
			DESCRIPTION 
				"Description. Auto/Manual selection"
			SYNTAX INTEGER
				{
				undefined(0),
				manual(1),
				automatic(2)
				}

		SelectOnOff ::= TEXTUAL-CONVENTION
			STATUS current
			DESCRIPTION 
				"Description. On/Off selection"
			SYNTAX INTEGER
				{
				undefined(0),
				on(1),
				off(2)
				}

		Input1Input2 ::= TEXTUAL-CONVENTION
			STATUS current
			DESCRIPTION 
				"Description.Input1/Input2"
			SYNTAX INTEGER
				{
				undefined(0),
				input1(1),
				input2(2)
				}

		OkNotOk ::= TEXTUAL-CONVENTION
			STATUS current
			DESCRIPTION 
				"Description.OK/NotOK"
			SYNTAX INTEGER
				{
				undefined(0),
				ok(1),
				notok(2)
				}

		FaultOK ::= TEXTUAL-CONVENTION
			STATUS current
			DESCRIPTION 
				"Description.Fault/OK"
			SYNTAX INTEGER
				{
				undefined(0),
				fault(1),
				ok(2)
				}

		WarningOK ::= TEXTUAL-CONVENTION
			STATUS current
			DESCRIPTION 
				"Description.Warning/OK"
			SYNTAX INTEGER
				{
				undefined(0),
				warning(1),
				ok(2)
				}

		LocalRemote ::= TEXTUAL-CONVENTION
			STATUS current
			DESCRIPTION 
				"Description.Local/Remote"
			SYNTAX INTEGER
				{
				undefined(0),
				local(1),
				remote(2)
				}

		MuteOk ::= TEXTUAL-CONVENTION
			STATUS current
			DESCRIPTION 
				"Description. Mute/OK"
			SYNTAX INTEGER
				{
				undefined(0),
				mute(1),
				ok(2)
				}

		ReadyNotReady ::= TEXTUAL-CONVENTION
			STATUS current
			DESCRIPTION 
				"Description. Ready/Not ready"
			SYNTAX INTEGER
				{
				undefined(0),
				ready(1),
				notready(2)
				}

		ExecutedNotExecuted ::= TEXTUAL-CONVENTION
			STATUS current
			DESCRIPTION 
				"Description. Executed/Not Executed"
			SYNTAX INTEGER
				{
				undefined(0),
				executed(1),
				notexecuted(2)
				}

		PresentNotPresent ::= TEXTUAL-CONVENTION
			STATUS current
			DESCRIPTION 
				"Description. Present/NotPresent"
			SYNTAX INTEGER
				{
				undefined(0),
				present(1),
				notpresent(2)
				}

		SFNMFN ::= TEXTUAL-CONVENTION
			STATUS current
			DESCRIPTION 
				"Description: SFN/MFN Mode"
			SYNTAX INTEGER
				{
				undefined(0),
				sfn(1),
				mfn(2)
				}

	
--
-- Node definitions
--
	
-- Broadcast
		-- 1.3.6.1.4.1.19831.1
		broadcast OBJECT IDENTIFIER ::= { irt 1 }

		
-- Transmitter
		-- 1.3.6.1.4.1.19831.1.1
		transmitter OBJECT IDENTIFIER ::= { broadcast 1 }

		
-- Digital videobroadcast terrestrial
		-- 1.3.6.1.4.1.19831.1.1.1
		dvbT OBJECT IDENTIFIER ::= { transmitter 1 }
-- List of assigned devices
-- 
-- dvbSingleTransmitter OBJECT IDENTIFIER ::=  { dvbT 1 }
-- dvbActiveReserve     OBJECT IDENTIFIER ::=  { dvbT 2 }
-- dvbPassiveReserve    OBJECT IDENTIFIER ::=  { dvbT 3 }
-- dvbDualDrive         OBJECT IDENTIFIER ::=  { dvbT 4 }
-- dvbnPlus1            OBJECT IDENTIFIER ::=  { dvbT 5 }
-- dvbCommon            OBJECT IDENTIFIER ::=  { dvbT 255 }
		
-- Digital audiobroadcast
		-- 1.3.6.1.4.1.19831.1.1.2
		dab OBJECT IDENTIFIER ::= { transmitter 2 }
-- List of assigned devices
-- 
-- dabSingleTransmitter OBJECT IDENTIFIER ::=  { dab 1 }
-- dabActiveReserve     OBJECT IDENTIFIER ::=  { dab 2 }
-- dabPassiveReserve    OBJECT IDENTIFIER ::=  { dab 3 }
-- dabDualDrive         OBJECT IDENTIFIER ::=  { dab 4 }
-- dabnPlus1            OBJECT IDENTIFIER ::=  { dab 5 }
-- dabCommon            OBJECT IDENTIFIER ::=  { dab 255 }
		
-- FM transmitters
		-- 1.3.6.1.4.1.19831.1.1.3
		fm OBJECT IDENTIFIER ::= { transmitter 3 }
-- List of assigned devices
-- 
-- fmSingleTransmitter OBJECT IDENTIFIER ::=  { fm 1 }
-- fmActiveReserve     OBJECT IDENTIFIER ::=  { fm 2 }
-- fmPassiveReserve    OBJECT IDENTIFIER ::=  { fm 3 }
-- fmDualDrive         OBJECT IDENTIFIER ::=  { fm 4 }
-- fmnPlus1            OBJECT IDENTIFIER ::=  { fm 5 }
-- fmCommon            OBJECT IDENTIFIER ::=  { fm 255 }
		
-- Digital radio mondiale
		-- 1.3.6.1.4.1.19831.1.1.4
		drm OBJECT IDENTIFIER ::= { transmitter 4 }

		
-- Common values for all transmittertypes
		-- 1.3.6.1.4.1.19831.1.1.7
		common OBJECT IDENTIFIER ::= { transmitter 7 }
-- Common values used by all transmittertypes (eg special Varbinds)
		
	
	END

--
-- IRT-TRANSMITTER-SMI-MIB.my
--
