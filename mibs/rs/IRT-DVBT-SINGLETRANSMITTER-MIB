--
-- IRT-DVBT-SINGLETRANSMITTER-MIB.my
-- MIB generated by MG-SOFT Visual MIB Builder Version 6.0  Build 88
-- Thursday, May 03, 2007 at 21:05:21
--

	IRT-DVBT-SINGLETRANSMITTER-MIB DEFINITIONS ::= BEGIN
 
		IMPORTS
			eventTimeStamp, eventPriority, eventCounter, mibRelease			
				FROM IRT-COMMONVARBINDS-MIB			
			dvbT, Input1Input2, SelectManualAuto, SelectOnOff, PresentNotPresent, 
			FaultOK, WarningOK, OkNotOk, MuteOk, SFNMFN, 
			LocalRemote			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DisplayString, TruthValue			
				FROM SNMPv2-TC;
	
	
		-- 1.3.6.1.4.1.19831.1.1.1.1
		dvbSingleTransmitter MODULE-IDENTITY 
			LAST-UPDATED "200705041400Z"		-- May 04, 2007 at 14:00 GMT
			ORGANIZATION 
				"IRT for WORKING-GROUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"DVB Single Transmitter
				
				branch definition
				
				1st level
				
				events               OBJECT IDENTIFIER ::= { dvbSingleTransmitter 0 }
				dvbSTGeneral         OBJECT IDENTIFIER ::= { dvbSingleTransmitter 1 }
				dvbSTEventEnable     OBJECT IDENTIFIER ::= { dvbSingleTransmitter 2 }
				dvbSTEventPriority   OBJECT IDENTIFIER ::= { dvbSingleTransmitter 3 }
				groups               OBJECT IDENTIFIER ::= { dvbSingleTransmitter 4 }
				
				2nd level
				
				dvbSTEventEnableGeneral     OBJECT IDENTIFIER ::= { dvbSTEventEnable 1 }
				dvbSTEventPriorityGeneral   OBJECT IDENTIFIER ::= { dvbSTEventPriority 1 }
				
				end branch
				
				"
			REVISION "200705041400Z"		-- May 04, 2007 at 14:00 GMT
			DESCRIPTION 
				"change SFNMode,LocalMode (description) and Module-COMPLIANCE"
			REVISION "200612201400Z"		-- December 20, 2006 at 14:00 GMT
			DESCRIPTION 
				"Corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dvbT 1 }

		
	
	
--
-- Node definitions
--
	
-- dvb single transmitter events
		-- 1.3.6.1.4.1.19831.1.1.1.1.0
		dvbEventsST OBJECT IDENTIFIER ::= { dvbSingleTransmitter 0 }

		
		-- 1.3.6.1.4.1.19831.1.1.1.1.0.1
		dvbSTInputPreselectionEvent NOTIFICATION-TYPE
			OBJECTS { sysDescr, sysName, sysLocation, eventTimeStamp, eventPriority, 
				eventCounter, dvbSTInputPreselection }
			STATUS current
			DESCRIPTION 
				"Description.dvbSTInputPreselection notification"
			::= { dvbEventsST 1 }

		
		-- 1.3.6.1.4.1.19831.1.1.1.1.0.2
		dvbSTInputAutomaticEvent NOTIFICATION-TYPE
			OBJECTS { sysDescr, sysName, sysLocation, eventTimeStamp, eventPriority, 
				eventCounter, dvbSTInputAutomatic }
			STATUS current
			DESCRIPTION 
				"Description. dvbSTInputAutomatic notification"
			::= { dvbEventsST 2 }

		
		-- 1.3.6.1.4.1.19831.1.1.1.1.0.3
		dvbSTTransmitterOpModeEvent NOTIFICATION-TYPE
			OBJECTS { sysDescr, sysName, sysLocation, eventTimeStamp, eventPriority, 
				eventCounter, dvbSTTransmitterOpMode }
			STATUS current
			DESCRIPTION 
				"Description. dvbSTTransmitterOpMode notification"
			::= { dvbEventsST 3 }

		
		-- 1.3.6.1.4.1.19831.1.1.1.1.0.4
		dvbSTRFPresentEvent NOTIFICATION-TYPE
			OBJECTS { sysDescr, sysName, sysLocation, eventTimeStamp, eventPriority, 
				eventCounter, dvbSTRFPresent }
			STATUS current
			DESCRIPTION 
				"Description. dvbSTRFPresent notification"
			::= { dvbEventsST 4 }

		
		-- 1.3.6.1.4.1.19831.1.1.1.1.0.5
		dvbSTResetFaultEvent NOTIFICATION-TYPE
			OBJECTS { sysDescr, sysName, sysLocation, eventTimeStamp, eventPriority, 
				eventCounter, dvbSTResetFault }
			STATUS obsolete
			DESCRIPTION 
				"Notification is inctive!
				
				Description.dvbSTResetFault notification"
			::= { dvbEventsST 5 }

		
		-- 1.3.6.1.4.1.19831.1.1.1.1.0.6
		dvbSTFaultEvent NOTIFICATION-TYPE
			OBJECTS { sysDescr, sysName, sysLocation, eventTimeStamp, eventPriority, 
				eventCounter, dvbSTFault }
			STATUS current
			DESCRIPTION 
				"Description. dvbSTFault notification"
			::= { dvbEventsST 6 }

		
		-- 1.3.6.1.4.1.19831.1.1.1.1.0.7
		dvbSTWarningEvent NOTIFICATION-TYPE
			OBJECTS { sysDescr, sysName, sysLocation, eventTimeStamp, eventPriority, 
				eventCounter, dvbSTWarning }
			STATUS current
			DESCRIPTION 
				"Description. dvbSTWarning notification"
			::= { dvbEventsST 7 }

		
		-- 1.3.6.1.4.1.19831.1.1.1.1.0.8
		dvbSTInput1OKEvent NOTIFICATION-TYPE
			OBJECTS { sysDescr, sysName, sysLocation, eventTimeStamp, eventPriority, 
				eventCounter, dvbSTInput1OK }
			STATUS current
			DESCRIPTION 
				"Description.vdvbSTInput1OK notification"
			::= { dvbEventsST 8 }

		
		-- 1.3.6.1.4.1.19831.1.1.1.1.0.9
		dvbSTInput2OKEvent NOTIFICATION-TYPE
			OBJECTS { sysDescr, sysName, sysLocation, eventTimeStamp, eventPriority, 
				eventCounter, dvbSTInput2OK }
			STATUS current
			DESCRIPTION 
				"Description.dvbSTInput2OK notification"
			::= { dvbEventsST 9 }

		
		-- 1.3.6.1.4.1.19831.1.1.1.1.0.10
		dvbSTLocalModeEvent NOTIFICATION-TYPE
			OBJECTS { sysDescr, sysName, sysLocation, eventTimeStamp, eventPriority, 
				eventCounter, dvbSTLocalMode }
			STATUS current
			DESCRIPTION 
				"Description. dvbSTLocalMode notification"
			::= { dvbEventsST 10 }

		
		-- 1.3.6.1.4.1.19831.1.1.1.1.0.11
		dvbSTActiveInputEvent NOTIFICATION-TYPE
			OBJECTS { sysDescr, sysName, sysLocation, eventTimeStamp, eventPriority, 
				eventCounter, dvbSTActiveInput }
			STATUS current
			DESCRIPTION 
				"Description. dvbSTActiveInput notification"
			::= { dvbEventsST 11 }

		
		-- 1.3.6.1.4.1.19831.1.1.1.1.0.12
		dvbSTSFNModeEvent NOTIFICATION-TYPE
			OBJECTS { sysDescr, sysName, sysLocation, eventTimeStamp, eventPriority, 
				eventCounter, dvbSTSFNMode }
			STATUS current
			DESCRIPTION 
				"Description. dvbSTSFNMode notification"
			::= { dvbEventsST 12 }

		
		-- 1.3.6.1.4.1.19831.1.1.1.1.0.13
		dvbSTRefFaultEvent NOTIFICATION-TYPE
			OBJECTS { sysDescr, sysName, sysLocation, eventTimeStamp, eventPriority, 
				eventCounter, dvbSTRefFault }
			STATUS current
			DESCRIPTION 
				"Description. dvbSTRefFault notification"
			::= { dvbEventsST 13 }

		
		-- 1.3.6.1.4.1.19831.1.1.1.1.0.14
		dvbSTMuteEvent NOTIFICATION-TYPE
			OBJECTS { sysDescr, sysName, sysLocation, eventTimeStamp, eventPriority, 
				eventCounter, dvbSTMute }
			STATUS current
			DESCRIPTION 
				"Description. dvbSTMute notification"
			::= { dvbEventsST 14 }

		
		-- 1.3.6.1.4.1.19831.1.1.1.1.0.15
		dvbSTFaultMIPEvent NOTIFICATION-TYPE
			OBJECTS { sysDescr, sysName, sysLocation, eventTimeStamp, eventPriority, 
				eventCounter, dvbSTFaultMIP }
			STATUS current
			DESCRIPTION 
				"Description. dvbSTFaultMIP notification"
			::= { dvbEventsST 15 }

		
		-- 1.3.6.1.4.1.19831.1.1.1.1.0.16
		dvbSTStuffingModeEvent NOTIFICATION-TYPE
			OBJECTS { sysDescr, sysName, sysLocation, eventTimeStamp, eventPriority, 
				eventCounter, dvbSTStuffingMode }
			STATUS current
			DESCRIPTION 
				"Description. dvbSTSStuffingMode notification"
			::= { dvbEventsST 16 }

		
-- dvb single transmitter general
		-- 1.3.6.1.4.1.19831.1.1.1.1.1
		dvbSTGeneral OBJECT IDENTIFIER ::= { dvbSingleTransmitter 1 }

		
		-- 1.3.6.1.4.1.19831.1.1.1.1.1.1
		dvbSTInputPreselection OBJECT-TYPE
			SYNTAX Input1Input2
			UNITS " "
			MAX-ACCESS read-write
			STATUS current
			DESCRIPTION
				"Single transmitter. Preselection input of single transmitter
				
				(0) undefined
				(1) Input 1
				(2) Input 2"
			::= { dvbSTGeneral 1 }

		
		-- 1.3.6.1.4.1.19831.1.1.1.1.1.2
		dvbSTInputAutomatic OBJECT-TYPE
			SYNTAX SelectManualAuto
			UNITS " "
			MAX-ACCESS read-write
			STATUS current
			DESCRIPTION
				"Single transmitter. Input selection mode of single  transmitter:  manual or automatic
				
				(0) undefined
				(1) manual 
				(2) automatic"
			::= { dvbSTGeneral 2 }

		
		-- 1.3.6.1.4.1.19831.1.1.1.1.1.3
		dvbSTTransmitterOpMode OBJECT-TYPE
			SYNTAX SelectOnOff
			UNITS " "
			MAX-ACCESS read-write
			STATUS current
			DESCRIPTION
				"Single transmitter. Transmitter control of single  transmitter
				
				(0) undefined
				(1) ON
				(2) OFF"
			::= { dvbSTGeneral 3 }

		
		-- 1.3.6.1.4.1.19831.1.1.1.1.1.4
		dvbSTRFPresent OBJECT-TYPE
			SYNTAX PresentNotPresent
			MAX-ACCESS read-only
			STATUS current
			DESCRIPTION
				"Single  transmitter. Describes if  the output power is present
				
				(0) undefined
				(1) present
				(2) not present
				"
			::= { dvbSTGeneral 4 }

		
		-- 1.3.6.1.4.1.19831.1.1.1.1.1.5
		dvbSTResetFault OBJECT-TYPE
			SYNTAX Unsigned32
			MAX-ACCESS read-write
			STATUS obsolete
			DESCRIPTION
				"Description.  Massage is inctive!
				
				
				Single  transmitter. Reset fault. Trigger for reset the sum fault
				
				<1>
				
				1: reset sum fault
				
				"
			::= { dvbSTGeneral 5 }

		
		-- 1.3.6.1.4.1.19831.1.1.1.1.1.6
		dvbSTFault OBJECT-TYPE
			SYNTAX FaultOK
			MAX-ACCESS read-only
			STATUS current
			DESCRIPTION
				"Single transmitter. Fault state of transmitter
				
				(0) undefined
				(1) fault
				(2) ok"
			::= { dvbSTGeneral 6 }

		
		-- 1.3.6.1.4.1.19831.1.1.1.1.1.7
		dvbSTWarning OBJECT-TYPE
			SYNTAX WarningOK
			MAX-ACCESS read-only
			STATUS current
			DESCRIPTION
				"Single transmitter. Warning state of single transmitter
				
				(0) undefined
				(1) warning
				(2) ok"
			::= { dvbSTGeneral 7 }

		
		-- 1.3.6.1.4.1.19831.1.1.1.1.1.8
		dvbSTInput1OK OBJECT-TYPE
			SYNTAX OkNotOk
			MAX-ACCESS read-only
			STATUS current
			DESCRIPTION
				"Single transmitter.Describes if the input signal at the input 1 of single transmitter  is ok
				
				(0) undefined
				(1) signal ok
				(2) signal is not ok "
			::= { dvbSTGeneral 8 }

		
		-- 1.3.6.1.4.1.19831.1.1.1.1.1.9
		dvbSTInput2OK OBJECT-TYPE
			SYNTAX OkNotOk
			MAX-ACCESS read-only
			STATUS current
			DESCRIPTION
				"Describes if the input signal at the input 2 of single transmitters  is ok
				
				(0) undefined
				(1) signal ok
				(2) signal is not ok "
			::= { dvbSTGeneral 9 }

		
		-- 1.3.6.1.4.1.19831.1.1.1.1.1.10
		dvbSTLocalMode OBJECT-TYPE
			SYNTAX LocalRemote
			MAX-ACCESS read-only
			STATUS current
			DESCRIPTION
				"Single transmitter. Local  mode
				
				(0) undefined
				(1) local
				(2) remote"
			::= { dvbSTGeneral 10 }

		
		-- 1.3.6.1.4.1.19831.1.1.1.1.1.11
		dvbSTActiveInput OBJECT-TYPE
			SYNTAX INTEGER
				{
				undefined(0),
				input1(1),
				input2(2),
				seamless(3),
				hmHierarchicalModulation(4)
				}
			MAX-ACCESS read-only
			STATUS current
			DESCRIPTION
				"Single transmitter.Active input of the single transmitter 
				
				"
			::= { dvbSTGeneral 11 }

		
		-- 1.3.6.1.4.1.19831.1.1.1.1.1.12
		dvbSTSFNMode OBJECT-TYPE
			SYNTAX SFNMFN
			MAX-ACCESS read-only
			STATUS current
			DESCRIPTION
				"Single transmitter. SFN mode of single transmitter 
				
				(0) undefined
				(1) SFN
				(2) MFN
				
				
				"
			::= { dvbSTGeneral 12 }

		
		-- 1.3.6.1.4.1.19831.1.1.1.1.1.13
		dvbSTRefFault OBJECT-TYPE
			SYNTAX FaultOK
			MAX-ACCESS read-only
			STATUS current
			DESCRIPTION
				"Single transmitter.Fault state of the GPS input or the reference frequency of single transmitter 
				
				(0) undefined
				(1) fault
				(2) ok"
			::= { dvbSTGeneral 13 }

		
		-- 1.3.6.1.4.1.19831.1.1.1.1.1.14
		dvbSTMute OBJECT-TYPE
			SYNTAX MuteOk
			MAX-ACCESS read-only
			STATUS current
			DESCRIPTION
				"Single transmitter. Mute state of single transmitter
				
				(0) undefined
				(1) mute
				(2) ok"
			::= { dvbSTGeneral 14 }

		
		-- 1.3.6.1.4.1.19831.1.1.1.1.1.15
		dvbSTFaultMIP OBJECT-TYPE
			SYNTAX FaultOK
			MAX-ACCESS read-only
			STATUS current
			DESCRIPTION
				"MIP fault state of single transmitter
				
				(0) undefined
				(1) fault
				(2) ok"
			::= { dvbSTGeneral 15 }

		
		-- 1.3.6.1.4.1.19831.1.1.1.1.1.16
		dvbSTStuffingMode OBJECT-TYPE
			SYNTAX SelectOnOff
			MAX-ACCESS read-only
			STATUS current
			DESCRIPTION
				"Stuffing state of single transmitter
				
				(0) undefined
				(1) ON 
				(2) OFF "
			::= { dvbSTGeneral 16 }

		
-- dvb single transmitter
		-- 1.3.6.1.4.1.19831.1.1.1.1.2
		dvbSTEventEnable OBJECT IDENTIFIER ::= { dvbSingleTransmitter 2 }

		
		-- 1.3.6.1.4.1.19831.1.1.1.1.2.1
		dvbSTEventEnableGeneral OBJECT IDENTIFIER ::= { dvbSTEventEnable 1 }

		
		-- 1.3.6.1.4.1.19831.1.1.1.1.2.1.1
		dvbSTInputPreselectionEnable OBJECT-TYPE
			SYNTAX TruthValue
			MAX-ACCESS read-write
			STATUS current
			DESCRIPTION
				"Description.Enable/Disable switch for dvbSTInputPreselection event"
			::= { dvbSTEventEnableGeneral 1 }

		
		-- 1.3.6.1.4.1.19831.1.1.1.1.2.1.2
		dvbSTInputAutomaticEnable OBJECT-TYPE
			SYNTAX TruthValue
			MAX-ACCESS read-write
			STATUS current
			DESCRIPTION
				"Description.Enable/Disable switch for dvbSTInputAutomatic event"
			::= { dvbSTEventEnableGeneral 2 }

		
		-- 1.3.6.1.4.1.19831.1.1.1.1.2.1.3
		dvbSTTransmitterOpModeEnable OBJECT-TYPE
			SYNTAX TruthValue
			MAX-ACCESS read-write
			STATUS current
			DESCRIPTION
				"Description.Enable/Disable switch for dvbSTTransmitterOpMode event"
			::= { dvbSTEventEnableGeneral 3 }

		
		-- 1.3.6.1.4.1.19831.1.1.1.1.2.1.4
		dvbSTRFPresentEnable OBJECT-TYPE
			SYNTAX TruthValue
			MAX-ACCESS read-write
			STATUS current
			DESCRIPTION
				"Description.Enable/Disable switch for dvbSTRFPresent event"
			::= { dvbSTEventEnableGeneral 4 }

		
		-- 1.3.6.1.4.1.19831.1.1.1.1.2.1.5
		dvbSTResetFaultEnable OBJECT-TYPE
			SYNTAX TruthValue
			MAX-ACCESS read-write
			STATUS obsolete
			DESCRIPTION
				"Massage ist inactive!
				
				Description. Enable/Disable switch for dvbSTResetFault event"
			::= { dvbSTEventEnableGeneral 5 }

		
		-- 1.3.6.1.4.1.19831.1.1.1.1.2.1.6
		dvbSTFaultEnable OBJECT-TYPE
			SYNTAX TruthValue
			MAX-ACCESS read-write
			STATUS current
			DESCRIPTION
				"Description.Enable/Disable switch for dvbSTFault event"
			::= { dvbSTEventEnableGeneral 6 }

		
		-- 1.3.6.1.4.1.19831.1.1.1.1.2.1.7
		dvbSTWarningEnable OBJECT-TYPE
			SYNTAX TruthValue
			MAX-ACCESS read-write
			STATUS current
			DESCRIPTION
				"Description.Enable/Disable switch for dvbSTWarning event"
			::= { dvbSTEventEnableGeneral 7 }

		
		-- 1.3.6.1.4.1.19831.1.1.1.1.2.1.8
		dvbSTInput1OKEnable OBJECT-TYPE
			SYNTAX TruthValue
			MAX-ACCESS read-write
			STATUS current
			DESCRIPTION
				"Description.Enable/Disable switch for dvbSTInput1OK event"
			::= { dvbSTEventEnableGeneral 8 }

		
		-- 1.3.6.1.4.1.19831.1.1.1.1.2.1.9
		dvbSTInput2OKEnable OBJECT-TYPE
			SYNTAX TruthValue
			MAX-ACCESS read-write
			STATUS current
			DESCRIPTION
				"Description.Enable/Disable switch for dvbSTInput2OK event"
			::= { dvbSTEventEnableGeneral 9 }

		
		-- 1.3.6.1.4.1.19831.1.1.1.1.2.1.10
		dvbSTLocalModeEnable OBJECT-TYPE
			SYNTAX TruthValue
			MAX-ACCESS read-write
			STATUS current
			DESCRIPTION
				"Description.Enable/Disable switch for dvbSTLocalMode event"
			::= { dvbSTEventEnableGeneral 10 }

		
		-- 1.3.6.1.4.1.19831.1.1.1.1.2.1.11
		dvbSTActiveInputEnable OBJECT-TYPE
			SYNTAX TruthValue
			MAX-ACCESS read-write
			STATUS current
			DESCRIPTION
				"Description.Enable/Disable switch for dvbSTActiveInput event"
			::= { dvbSTEventEnableGeneral 11 }

		
		-- 1.3.6.1.4.1.19831.1.1.1.1.2.1.12
		dvbSTSFNModeEnable OBJECT-TYPE
			SYNTAX TruthValue
			MAX-ACCESS read-write
			STATUS current
			DESCRIPTION
				"Description.Enable/Disable switch for dvbSTSFNMode event"
			::= { dvbSTEventEnableGeneral 12 }

		
		-- 1.3.6.1.4.1.19831.1.1.1.1.2.1.13
		dvbSTRefFaultEnable OBJECT-TYPE
			SYNTAX TruthValue
			MAX-ACCESS read-write
			STATUS current
			DESCRIPTION
				"Description.Enable/Disable switch for dvbSTRefFault event"
			::= { dvbSTEventEnableGeneral 13 }

		
		-- 1.3.6.1.4.1.19831.1.1.1.1.2.1.14
		dvbSTMuteEnable OBJECT-TYPE
			SYNTAX TruthValue
			MAX-ACCESS read-write
			STATUS current
			DESCRIPTION
				"Description.Enable/Disable switch for dvbSTMute event"
			::= { dvbSTEventEnableGeneral 14 }

		
		-- 1.3.6.1.4.1.19831.1.1.1.1.2.1.15
		dvbSTFaultMIPEnable OBJECT-TYPE
			SYNTAX TruthValue
			MAX-ACCESS read-write
			STATUS current
			DESCRIPTION
				"Description.Enable/Disable switch for dvbSTFaultMIP event"
			::= { dvbSTEventEnableGeneral 15 }

		
		-- 1.3.6.1.4.1.19831.1.1.1.1.2.1.16
		dvbSTStuffingModeEnable OBJECT-TYPE
			SYNTAX TruthValue
			MAX-ACCESS read-write
			STATUS current
			DESCRIPTION
				"Description.Enable/Disable switch for dvbSTStuffingMode event"
			::= { dvbSTEventEnableGeneral 16 }

		
-- dvb single transmitter event priority
		-- 1.3.6.1.4.1.19831.1.1.1.1.3
		dvbSTEventPriority OBJECT IDENTIFIER ::= { dvbSingleTransmitter 3 }

		
		-- 1.3.6.1.4.1.19831.1.1.1.1.3.1
		dvbSTEventPriorityGeneral OBJECT IDENTIFIER ::= { dvbSTEventPriority 1 }

		
		-- 1.3.6.1.4.1.19831.1.1.1.1.3.1.1
		dvbSTInputPreselectionPriority OBJECT-TYPE
			SYNTAX Unsigned32
			MAX-ACCESS read-write
			STATUS current
			DESCRIPTION
				"Description.Priority for dvbSTInputPreselection event"
			::= { dvbSTEventPriorityGeneral 1 }

		
		-- 1.3.6.1.4.1.19831.1.1.1.1.3.1.2
		dvbSTInputAutomaticPriority OBJECT-TYPE
			SYNTAX Unsigned32
			MAX-ACCESS read-write
			STATUS current
			DESCRIPTION
				"Description.Priority for dvbSTInputAutomatic event"
			::= { dvbSTEventPriorityGeneral 2 }

		
		-- 1.3.6.1.4.1.19831.1.1.1.1.3.1.3
		dvbSTTransmitterOpModePriority OBJECT-TYPE
			SYNTAX Unsigned32
			MAX-ACCESS read-write
			STATUS current
			DESCRIPTION
				"Description.Priority for dvbSTTransmitterOpMode event"
			::= { dvbSTEventPriorityGeneral 3 }

		
		-- 1.3.6.1.4.1.19831.1.1.1.1.3.1.4
		dvbSTRFPresentPriority OBJECT-TYPE
			SYNTAX Unsigned32
			MAX-ACCESS read-write
			STATUS current
			DESCRIPTION
				"Description.Priority for dvbSTRFPresent event"
			::= { dvbSTEventPriorityGeneral 4 }

		
		-- 1.3.6.1.4.1.19831.1.1.1.1.3.1.5
		dvbSTResetFaultPriority OBJECT-TYPE
			SYNTAX Unsigned32
			MAX-ACCESS read-write
			STATUS obsolete
			DESCRIPTION
				"Massage ist inactive!
				
				
				Description. Priority for dvbSTResetFault event"
			::= { dvbSTEventPriorityGeneral 5 }

		
		-- 1.3.6.1.4.1.19831.1.1.1.1.3.1.6
		dvbSTFaultPriority OBJECT-TYPE
			SYNTAX Unsigned32
			MAX-ACCESS read-write
			STATUS current
			DESCRIPTION
				"Description.Priority for dvbSTFault event"
			::= { dvbSTEventPriorityGeneral 6 }

		
		-- 1.3.6.1.4.1.19831.1.1.1.1.3.1.7
		dvbSTWarningPriority OBJECT-TYPE
			SYNTAX Unsigned32
			MAX-ACCESS read-write
			STATUS current
			DESCRIPTION
				"Description.Priority for dvbSTWarning event"
			::= { dvbSTEventPriorityGeneral 7 }

		
		-- 1.3.6.1.4.1.19831.1.1.1.1.3.1.8
		dvbSTInput1OKPriority OBJECT-TYPE
			SYNTAX Unsigned32
			MAX-ACCESS read-write
			STATUS current
			DESCRIPTION
				"Description.Priority for dvbSTInput1OK event"
			::= { dvbSTEventPriorityGeneral 8 }

		
		-- 1.3.6.1.4.1.19831.1.1.1.1.3.1.9
		dvbSTInput2OKPriority OBJECT-TYPE
			SYNTAX Unsigned32
			MAX-ACCESS read-write
			STATUS current
			DESCRIPTION
				"Description.Priority for dvbSTInput2OK event"
			::= { dvbSTEventPriorityGeneral 9 }

		
		-- 1.3.6.1.4.1.19831.1.1.1.1.3.1.10
		dvbSTLocalModePriority OBJECT-TYPE
			SYNTAX Unsigned32
			MAX-ACCESS read-write
			STATUS current
			DESCRIPTION
				"Description.Priority for dvbSTLocalMode event"
			::= { dvbSTEventPriorityGeneral 10 }

		
		-- 1.3.6.1.4.1.19831.1.1.1.1.3.1.11
		dvbSTActiveInputPriority OBJECT-TYPE
			SYNTAX Unsigned32
			MAX-ACCESS read-write
			STATUS current
			DESCRIPTION
				"Description.Priority for dvbSTActiveInput event"
			::= { dvbSTEventPriorityGeneral 11 }

		
		-- 1.3.6.1.4.1.19831.1.1.1.1.3.1.12
		dvbSTSFNModePriority OBJECT-TYPE
			SYNTAX Unsigned32
			MAX-ACCESS read-write
			STATUS current
			DESCRIPTION
				"Description.Priority for dvbSTSFNMode event"
			::= { dvbSTEventPriorityGeneral 12 }

		
		-- 1.3.6.1.4.1.19831.1.1.1.1.3.1.13
		dvbSTRefFaultPriority OBJECT-TYPE
			SYNTAX Unsigned32
			MAX-ACCESS read-write
			STATUS current
			DESCRIPTION
				"Description.Priority for dvbSTRefFault event"
			::= { dvbSTEventPriorityGeneral 13 }

		
		-- 1.3.6.1.4.1.19831.1.1.1.1.3.1.14
		dvbSTMutePriority OBJECT-TYPE
			SYNTAX Unsigned32
			MAX-ACCESS read-write
			STATUS current
			DESCRIPTION
				"Description.Priority for dvbSTMute event"
			::= { dvbSTEventPriorityGeneral 14 }

		
		-- 1.3.6.1.4.1.19831.1.1.1.1.3.1.15
		dvbSTFaultMIPPriority OBJECT-TYPE
			SYNTAX Unsigned32
			MAX-ACCESS read-write
			STATUS current
			DESCRIPTION
				"Description.Priority for dvbSTFaultMIP event"
			::= { dvbSTEventPriorityGeneral 15 }

		
		-- 1.3.6.1.4.1.19831.1.1.1.1.3.1.16
		dvbSTStuffingModePriority OBJECT-TYPE
			SYNTAX Unsigned32
			MAX-ACCESS read-write
			STATUS current
			DESCRIPTION
				"Description.Priority for dvbSTStuffingMode event"
			::= { dvbSTEventPriorityGeneral 16 }

		
		-- 1.3.6.1.4.1.19831.1.1.1.1.4
		groupST OBJECT IDENTIFIER ::= { dvbSingleTransmitter 4 }

		
		-- 1.3.6.1.4.1.19831.1.1.1.1.4.1
		objectGroupST OBJECT-GROUP
			OBJECTS { dvbSTInputPreselection, dvbSTInputAutomatic, dvbSTTransmitterOpMode, dvbSTRFPresent, dvbSTFault, 
				dvbSTWarning, dvbSTInput1OK, dvbSTInput2OK, dvbSTLocalMode, dvbSTActiveInput, 
				dvbSTSFNMode, dvbSTRefFault, dvbSTMute, dvbSTFaultMIP, dvbSTStuffingMode, 
				dvbSTInputPreselectionEnable, dvbSTInputAutomaticEnable, dvbSTTransmitterOpModeEnable, dvbSTRFPresentEnable, dvbSTFaultEnable, 
				dvbSTWarningEnable, dvbSTInput1OKEnable, dvbSTInput2OKEnable, dvbSTLocalModeEnable, dvbSTActiveInputEnable, 
				dvbSTSFNModeEnable, dvbSTRefFaultEnable, dvbSTMuteEnable, dvbSTFaultMIPEnable, dvbSTStuffingModeEnable, 
				dvbSTInputPreselectionPriority, dvbSTInputAutomaticPriority, dvbSTTransmitterOpModePriority, dvbSTRFPresentPriority, dvbSTFaultPriority, 
				dvbSTWarningPriority, dvbSTFaultMIPPriority, dvbSTMutePriority, dvbSTRefFaultPriority, dvbSTSFNModePriority, 
				dvbSTStuffingModePriority, dvbSTInput1OKPriority, dvbSTInput2OKPriority, dvbSTLocalModePriority, dvbSTActiveInputPriority
				 }
			STATUS current
			DESCRIPTION 
				"Description. dvb single transmitter  objects"
			::= { groupST 1 }

		
		-- 1.3.6.1.4.1.19831.1.1.1.1.4.2
		eventGroupST NOTIFICATION-GROUP
			NOTIFICATIONS { dvbSTInputPreselectionEvent, dvbSTInputAutomaticEvent, dvbSTTransmitterOpModeEvent, dvbSTRFPresentEvent, dvbSTFaultEvent, 
				dvbSTWarningEvent, dvbSTInput1OKEvent, dvbSTInput2OKEvent, dvbSTLocalModeEvent, dvbSTActiveInputEvent, 
				dvbSTSFNModeEvent, dvbSTRefFaultEvent, dvbSTStuffingModeEvent, dvbSTMuteEvent, dvbSTFaultMIPEvent
				 }
			STATUS current
			DESCRIPTION 
				"Description. dvb single transmitter  events"
			::= { groupST 2 }

		
		-- 1.3.6.1.4.1.19831.1.1.1.1.4.3
		objectGroupSTobsolete OBJECT-GROUP
			OBJECTS { dvbSTResetFault, dvbSTResetFaultEnable, dvbSTResetFaultPriority }
			STATUS obsolete
			DESCRIPTION 
				"Description. Inactive objects"
			::= { groupST 3 }

		
		-- 1.3.6.1.4.1.19831.1.1.1.1.4.4
		eventGroupSTobsolete NOTIFICATION-GROUP
			NOTIFICATIONS { dvbSTResetFaultEvent }
			STATUS obsolete
			DESCRIPTION 
				"Description. Inactive notifications"
			::= { groupST 4 }

		
		-- 1.3.6.1.4.1.19831.1.1.1.1.5
		complianceST OBJECT IDENTIFIER ::= { dvbSingleTransmitter 5 }

		
		-- 1.3.6.1.4.1.19831.1.1.1.1.5.1
		dvbSingleTransmitterCompliance MODULE-COMPLIANCE
			STATUS current
			DESCRIPTION 
				"Compliance Statement"
			MODULE -- this module
				MANDATORY-GROUPS { objectGroupST, eventGroupST }
			::= { complianceST 1 }

		
	
	END

--
-- IRT-DVBT-SINGLETRANSMITTER-MIB.my
--
