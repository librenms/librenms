DEVHW-MIB DEFINITIONS ::= BEGIN

	IMPORTS
		OBJECT-TYPE, Integer32, MODULE-IDENTITY
			FROM SNMPv2-SMI
		DisplayString
			FROM SNMPv2-TC
		device
			FROM ANIROOT-MIB;


-- the aniDevHardware group

aniDevHardware  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	"This group provides information specific to the device hardware.
	 These objects are common to both BSU and SU.
	"
	::= { device 3 }

aniDevHwRevision OBJECT-TYPE
	SYNTAX      Integer32
	MAX-ACCESS  read-only
	STATUS      current
	DESCRIPTION
	   "The Hardware Revision Number.
	   "
	--DEFAULT next-function-async     std_next_async
	::= { aniDevHardware 1 }

aniDevHwSpeed OBJECT-TYPE
	SYNTAX      DisplayString
	MAX-ACCESS  read-only
	STATUS      current
	DESCRIPTION
	   "The Hardware Speed.
	   "
	--DEFAULT next-function-async     std_next_async
	::= { aniDevHardware 2 }

aniDevHwBuildDate OBJECT-TYPE
	SYNTAX      DisplayString (SIZE (0..22))
	MAX-ACCESS  read-only
	STATUS      current
	DESCRIPTION
	   "The Hardware Date.
	   "
	--DEFAULT next-function-async     std_next_async
	::= { aniDevHardware 3 }

aniDevHwSerialNum OBJECT-TYPE
	SYNTAX      DisplayString (SIZE (0..15))
	MAX-ACCESS  read-only
	STATUS      current
	DESCRIPTION
	   "Serial Number for the Hardware.
	   "
	--DEFAULT next-function-async     std_next_async
	::= { aniDevHardware 4 }

aniDevHwBoardRevision OBJECT-TYPE
	SYNTAX      Integer32
	MAX-ACCESS  read-only
	STATUS      current
	DESCRIPTION
	   "The Revision Number of the board.
	   "
	--DEFAULT next-function-async     std_next_async
	::= { aniDevHardware 5 }

END
