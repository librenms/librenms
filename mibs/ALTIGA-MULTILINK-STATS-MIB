-- *------------------------------------------------------------------
-- * ALTIGA-MULTILINK-STATS-MIB.my:  Altiga MultiLink Statistics MIB.
-- *
-- * Altiga Networks was acquired by Cisco Systems on March 29, 2000
-- *
-- * Copyright (c) 2002 by Cisco Systems, Inc.
-- * All rights reserved.
-- *
-- *------------------------------------------------------------------

ALTIGA-MULTILINK-STATS-MIB DEFINITIONS ::= BEGIN

   IMPORTS
      MODULE-IDENTITY, OBJECT-TYPE, Integer32, Unsigned32, Gauge32
         FROM SNMPv2-SMI
      RowStatus
         FROM SNMPv2-TC
      OBJECT-GROUP, MODULE-COMPLIANCE
         FROM SNMPv2-CONF
      alStatsMultiLink, alMultiLinkGroup
         FROM ALTIGA-MIB
      alMultiLinkMibModule
         FROM ALTIGA-GLOBAL-REG;

   altigaMultiLinkStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga MultiLink Statistics MIB models counters and
          objects that are of management interest for multilinks.
         
          Acronyms
          The following acronyms are used in this document:

            MIB:        Management Information Base

            MLP:        MultiLink Protocol

         "

        REVISION "200209051300Z"
        DESCRIPTION
           "Added module compliance."

        REVISION "200207100000Z"
        DESCRIPTION
           "Updated with new header"

      ::= { alMultiLinkMibModule 2 }

-- +++++++++++++++++++++++++++++++++++++++++++++++++++++++
-- MIB Objects
-- +++++++++++++++++++++++++++++++++++++++++++++++++++++++

alStatsMultiLinkGlobal  OBJECT IDENTIFIER ::= { alStatsMultiLink 1 }

alMultiLinkStatsTable   OBJECT-TYPE
   SYNTAX         SEQUENCE OF AlMultiLinkStatsEntry
   MAX-ACCESS     not-accessible
   STATUS         current
   DESCRIPTION
      "List of active bundles sessions."
   ::= { alStatsMultiLink 2 }

alMultiLinkStatsEntry   OBJECT-TYPE
   SYNTAX         AlMultiLinkStatsEntry
   MAX-ACCESS     not-accessible
   STATUS         current
   DESCRIPTION
      "An entry in the alMultiLinkStatsTable."
   INDEX       { alMultiLinkStatsIndex }
   ::= { alMultiLinkStatsTable 1 }

AlMultiLinkStatsEntry ::= SEQUENCE {
   alMultiLinkStatsRowStatus           RowStatus,
   alMultiLinkStatsIndex               Integer32,
   alMultiLinkStatsTxOctets            Unsigned32,
   alMultiLinkStatsTxPackets           Unsigned32,
   alMultiLinkStatsTxMlpFragments      Unsigned32,
   alMultiLinkStatsTxMlpPackets        Unsigned32,
   alMultiLinkStatsTxNonMlpPackets     Unsigned32,
   alMultiLinkStatsTxThroughput        Gauge32,
   alMultiLinkStatsRxOctets            Unsigned32,
   alMultiLinkStatsRxPackets           Unsigned32,
   alMultiLinkStatsRxMlpFragments      Unsigned32,
   alMultiLinkStatsRxMlpPackets        Unsigned32,
   alMultiLinkStatsRxNonMlpPackets     Unsigned32,
   alMultiLinkStatsRxThroughput        Gauge32,
   alMultiLinkStatsRxLostEnd           Unsigned32,
   alMultiLinkStatsRxStalePackets      Unsigned32,
   alMultiLinkStatsRxStaleFragments    Unsigned32,
   alMultiLinkStatsRxDroppedFragments  Unsigned32,
   alMultiLinkStatsRxOOSFragments      Unsigned32,
   alMultiLinkStatsIdleTmrCleanup      Unsigned32
}

alMultiLinkStatsRowStatus  OBJECT-TYPE
   SYNTAX         RowStatus
   MAX-ACCESS     read-write
   STATUS         current     
   DESCRIPTION
      "The status of this row."
   ::= { alMultiLinkStatsEntry 1 }

alMultiLinkStatsIndex           OBJECT-TYPE
   SYNTAX         Integer32 (0..2147483647)
   MAX-ACCESS     read-only
   STATUS         current
   DESCRIPTION
      "The unique MultiLink Bundle index for this row."
   ::= { alMultiLinkStatsEntry 2 }

alMultiLinkStatsTxOctets        OBJECT-TYPE
   SYNTAX         Unsigned32
   MAX-ACCESS     read-only
   STATUS         current
   DESCRIPTION
      "The number of transmitted octets." 
   ::= { alMultiLinkStatsEntry 3 }

alMultiLinkStatsTxPackets       OBJECT-TYPE
   SYNTAX         Unsigned32
   MAX-ACCESS     read-only
   STATUS         current
   DESCRIPTION
      "The number of transmitted packets." 
   ::= { alMultiLinkStatsEntry 4 }

alMultiLinkStatsTxMlpFragments  OBJECT-TYPE
   SYNTAX         Unsigned32
   MAX-ACCESS     read-only
   STATUS         current
   DESCRIPTION
      "The number of transmitted MLP packet fragments." 
   ::= { alMultiLinkStatsEntry 5 }

alMultiLinkStatsTxMlpPackets    OBJECT-TYPE
   SYNTAX         Unsigned32
   MAX-ACCESS     read-only
   STATUS         current
   DESCRIPTION
      "The number of transmitted MLP complete packets." 
   ::= { alMultiLinkStatsEntry 6 }

alMultiLinkStatsTxNonMlpPackets OBJECT-TYPE
   SYNTAX         Unsigned32
   MAX-ACCESS     read-only
   STATUS         current
   DESCRIPTION
      "The number of transmitted non-MLP complete packets." 
   ::= { alMultiLinkStatsEntry 7 }

alMultiLinkStatsTxThroughput    OBJECT-TYPE
   SYNTAX         Gauge32
   MAX-ACCESS     read-only
   STATUS         current
   DESCRIPTION
      "The number of transmitted bits per second" 
   ::= { alMultiLinkStatsEntry 8 }

alMultiLinkStatsRxOctets        OBJECT-TYPE
   SYNTAX         Unsigned32
   MAX-ACCESS     read-only
   STATUS         current
   DESCRIPTION
      "The number of received octets." 
   ::= { alMultiLinkStatsEntry 9 }

alMultiLinkStatsRxPackets       OBJECT-TYPE
   SYNTAX         Unsigned32
   MAX-ACCESS     read-only
   STATUS         current
   DESCRIPTION
      "The number of received packets." 
   ::= { alMultiLinkStatsEntry 10 }

alMultiLinkStatsRxMlpFragments  OBJECT-TYPE
   SYNTAX         Unsigned32
   MAX-ACCESS     read-only
   STATUS         current
   DESCRIPTION
      "The number of received MLP packet fragments." 
   ::= { alMultiLinkStatsEntry 11 }

alMultiLinkStatsRxMlpPackets    OBJECT-TYPE
   SYNTAX         Unsigned32
   MAX-ACCESS     read-only
   STATUS         current
   DESCRIPTION
      "The number of received MLP complete packets." 
   ::= { alMultiLinkStatsEntry 12 }

alMultiLinkStatsRxNonMlpPackets OBJECT-TYPE
   SYNTAX         Unsigned32
   MAX-ACCESS     read-only
   STATUS         current
   DESCRIPTION
      "The number of received non-MLP complete packets." 
   ::= { alMultiLinkStatsEntry 13 }

alMultiLinkStatsRxThroughput    OBJECT-TYPE
   SYNTAX         Gauge32
   MAX-ACCESS     read-only
   STATUS         current
   DESCRIPTION
      "The number of received bits per second" 
   ::= { alMultiLinkStatsEntry 14 }

alMultiLinkStatsRxLostEnd       OBJECT-TYPE
   SYNTAX         Unsigned32
   MAX-ACCESS     read-only
   STATUS         current
   DESCRIPTION
      "The number of missing MLP packets with no end bit." 
   ::= { alMultiLinkStatsEntry 15 }

alMultiLinkStatsRxStalePackets OBJECT-TYPE
   SYNTAX         Unsigned32
   MAX-ACCESS     read-only
   STATUS         current
   DESCRIPTION
      "The number of received MLP packet fragments gone stale." 
   ::= { alMultiLinkStatsEntry 16 }

alMultiLinkStatsRxStaleFragments OBJECT-TYPE
   SYNTAX         Unsigned32
   MAX-ACCESS     read-only
   STATUS         current
   DESCRIPTION
      "The number of received MLP fragments orphans gone stale." 
   ::= { alMultiLinkStatsEntry 17 }

alMultiLinkStatsRxDroppedFragments OBJECT-TYPE
   SYNTAX         Unsigned32
   MAX-ACCESS     read-only
   STATUS         current
   DESCRIPTION
      "The number of received MLP packet fragments discarded." 
   ::= { alMultiLinkStatsEntry 18 }

alMultiLinkStatsRxOOSFragments   OBJECT-TYPE
   SYNTAX         Unsigned32
   MAX-ACCESS     read-only
   STATUS         current
   DESCRIPTION
      "The number of received out-of-sequence MLP packet fragments" 
   ::= { alMultiLinkStatsEntry 19 }

alMultiLinkStatsIdleTmrCleanup OBJECT-TYPE
   SYNTAX         Unsigned32
   MAX-ACCESS     read-only
   STATUS         current
   DESCRIPTION
      "The number of times idle timer forwarded MLP complete packets." 
   ::= { alMultiLinkStatsEntry 20 }

altigaMultiLinkStatsMibConformance OBJECT IDENTIFIER
   ::= { altigaMultiLinkStatsMibModule 1 }

altigaMultiLinkStatsMibCompliances OBJECT IDENTIFIER
   ::= { altigaMultiLinkStatsMibConformance 1 }

altigaMultiLinkStatsMibCompliance MODULE-COMPLIANCE
   STATUS         current
   DESCRIPTION
      "The compliance statement for agents which 
       implement the Altiga MultiLink Statistics MIB."
   MODULE
   MANDATORY-GROUPS { 
      altigaMultiLinkStatsGroup
   }
   ::= { altigaMultiLinkStatsMibCompliances 1 }

altigaMultiLinkStatsGroup OBJECT-GROUP
   OBJECTS
   {
      alMultiLinkStatsRowStatus,
      alMultiLinkStatsIndex,
      alMultiLinkStatsTxOctets,
      alMultiLinkStatsTxPackets,
      alMultiLinkStatsTxMlpFragments,
      alMultiLinkStatsTxMlpPackets,
      alMultiLinkStatsTxNonMlpPackets,
      alMultiLinkStatsTxThroughput,
      alMultiLinkStatsRxOctets,
      alMultiLinkStatsRxPackets,
      alMultiLinkStatsRxMlpFragments,
      alMultiLinkStatsRxMlpPackets,
      alMultiLinkStatsRxNonMlpPackets,
      alMultiLinkStatsRxThroughput,
      alMultiLinkStatsRxLostEnd,
      alMultiLinkStatsRxStalePackets,
      alMultiLinkStatsRxStaleFragments,
      alMultiLinkStatsRxDroppedFragments,
      alMultiLinkStatsRxOOSFragments,
      alMultiLinkStatsIdleTmrCleanup
   }
   STATUS   current
   DESCRIPTION
      "The objects for the MultiLink Bundle statistics."
   ::= { alMultiLinkGroup 2 }

END
