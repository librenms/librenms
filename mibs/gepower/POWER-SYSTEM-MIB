POWER-SYSTEM-MIB DEFINITIONS ::= BEGIN
IMPORTS
     enterprises, MODULE-IDENTITY, OBJECT-TYPE, Integer32, NOTIFICATION-TYPE 
         FROM SNMPv2-SMI
     DisplayString
         FROM SNMPv2-TC;


lucent                 OBJECT IDENTIFIER ::= { enterprises 1751 }
lucentProduct          OBJECT IDENTIFIER ::= { lucent 1 }
lucentmibs             OBJECT IDENTIFIER ::= { lucent 2 }
esmibs                 OBJECT IDENTIFIER ::= { lucentmibs 71 }
release                OBJECT IDENTIFIER ::= { esmibs 1 }
prototypes             OBJECT IDENTIFIER ::= { esmibs 2 }
psprototypes           OBJECT IDENTIFIER ::= { prototypes 1 }

powerSystem MODULE-IDENTITY
   LAST-UPDATED "201708022018Z"
   ORGANIZATION "Lineage Power"
   CONTACT-INFO "Chris Brooke - Power Systems

                 Phone: +1 972 244 9288

                 Postal: Power Systems
                         601 Shiloh Road
                         Plano, TX 75074
                         USA"

   DESCRIPTION " MIB for Power Systems DC Power Plants
                 including Galaxy, Vector and CPS products."

   REVISION "201708022018Z"
   DESCRIPTION "Added Inverter Plant Power"

   REVISION "201703241958Z"
   DESCRIPTION "Changed PIC relay names to be Disabled/Enabled vs. None/Enabled"

   REVISION "201703212044Z"
   DESCRIPTION "Added Enable/Disable for TCC and TIC alarms"

   REVISION "201611041412Z"
   DESCRIPTION "Added BDFB/BDCBB duplicate id"

   REVISION "201609121939Z"
   DESCRIPTION "Added Battery Shunt Trip disconnects"

   REVISION "201602292100Z"
   DESCRIPTION "Added Distribution Bays and Panels and Inverters"

   REVISION "201506231449Z"
   DESCRIPTION "Added minimum BD duation for auto boost"

   REVISION "201504161530Z"
   DESCRIPTION "Added probe temperature readings"
   
   REVISION "201406172214Z"
   DESCRIPTION "Added PICs"

   REVISION "201405142003Z"
   DESCRIPTION "Clarify some descriptions"
  
   REVISION "201404142153Z"
   DESCRIPTION "Added DCP HRT atribute"

   REVISION "201312132005Z"
   DESCRIPTION "Added NTP protocol"
 
   REVISION "201302222217Z"
   DESCRIPTION "Add new attributes for new controller application release"


   REVISION "201202092143Z"
   DESCRIPTION "Add new objects and attributes for new controller application release"

   REVISION "200906181845Z"
   DESCRIPTION "Switch to unique object names"

   REVISION "200905041637Z"
   DESCRIPTION "Fix syntax error"

   REVISION "200806031351Z"
   DESCRIPTION "Add objects and attributes to support the Millennium II"

   REVISION "0504081852Z"
   DESCRIPTION "Add new attributes"

   REVISION "0404081819Z"
   DESCRIPTION "Add retire Traps"

   REVISION "0102132012Z"
   DESCRIPTION "Add trapInfo and trapUserDefined"

   REVISION "0011071534Z"
   DESCRIPTION "Initial release"

   ::= { release 1 }

--
-- object psDc1
--

psDc1 OBJECT IDENTIFIER  ::= { powerSystem  1 }

psDc1Ide OBJECT-TYPE
SYNTAX      DisplayString
MAX-ACCESS  read-only
STATUS      current
DESCRIPTION
"Identifier"
 ::= { psDc1  1 }

psDc1Des OBJECT-TYPE
SYNTAX      DisplayString
MAX-ACCESS  read-write
STATUS      current
DESCRIPTION
"Description"
 ::= { psDc1  2 }

psDc1Typ OBJECT-TYPE
SYNTAX      DisplayString
MAX-ACCESS  read-only
STATUS      current
DESCRIPTION
"Type"
 ::= { psDc1  3 }

psDc1Vdc OBJECT-TYPE
SYNTAX      Integer32
MAX-ACCESS  read-only
STATUS      current
DESCRIPTION
"Voltage"
 ::= { psDc1  4 }

psDc1Adc OBJECT-TYPE
SYNTAX      Integer32
MAX-ACCESS  read-only
STATUS      current
DESCRIPTION
"Current"
 ::= { psDc1  5 }

psDc1Cap OBJECT-TYPE
SYNTAX      Integer32
MAX-ACCESS  read-only
STATUS      current
DESCRIPTION
"Capacity"
 ::= { psDc1  6 }

psDc1Trd OBJECT-TYPE
SYNTAX      Integer32
MAX-ACCESS  read-only
STATUS      current
DESCRIPTION
"Total Rectifier Drain"
 ::= { psDc1  7 }

psDc1Sht OBJECT-TYPE
SYNTAX      DisplayString
MAX-ACCESS  read-write
STATUS      current
DESCRIPTION
"Shunt Type
Values:
LOAD,
BATTERY,
NONE
"
 ::= { psDc1  8 }

psDc1Sha OBJECT-TYPE
SYNTAX      Integer32
MAX-ACCESS  read-write
STATUS      current
DESCRIPTION
"Shunt Current"
 ::= { psDc1  9 }

psDc1Shv OBJECT-TYPE
SYNTAX      Integer32(1..150)
MAX-ACCESS  read-write
STATUS      current
DESCRIPTION
"Shunt Voltage"
 ::= { psDc1  10 }

psDc1Sha1 OBJECT-TYPE
SYNTAX      Integer32
MAX-ACCESS  read-write
STATUS      current
DESCRIPTION
"Shunt1 Size"
 ::= { psDc1  11 }

psDc1Sha2 OBJECT-TYPE
SYNTAX      Integer32
MAX-ACCESS  read-write
STATUS      current
DESCRIPTION
"Shunt2 Size"
 ::= { psDc1  12 }

psDc1Stt OBJECT-TYPE
SYNTAX      DisplayString
MAX-ACCESS  read-write
STATUS      current
DESCRIPTION
"State
Values:
FLOAT,
BOOST,
BTP
"
 ::= { psDc1  13 }

psDc1Bhv OBJECT-TYPE
SYNTAX      Integer32
MAX-ACCESS  read-only
STATUS      current
DESCRIPTION
"Backup HV Threshold"
 ::= { psDc1  14 }

psDc1Bod OBJECT-TYPE
SYNTAX      DisplayString
MAX-ACCESS  read-only
STATUS      current
DESCRIPTION
"Battery On Discharge"
 ::= { psDc1  15 }

psDc1Ems OBJECT-TYPE
SYNTAX      DisplayString
MAX-ACCESS  read-only
STATUS      current
DESCRIPTION
"Energy Management State"
 ::= { psDc1  16 }

psDc1Eme OBJECT-TYPE
SYNTAX      INTEGER {
disable(0),
enable(1)
}
MAX-ACCESS  read-write
STATUS      current
DESCRIPTION
"Energy Management Enable
Values:
disable(0),
enable(1)
"
 ::= { psDc1  17 }

psDc1Rss OBJECT-TYPE
SYNTAX      INTEGER {
off(0),
on(1)
}
MAX-ACCESS  read-write
STATUS      current
DESCRIPTION
"Rectifier Restart
Values:
off(0),
on(1)
"
 ::= { psDc1  18 }

psDc1Rse OBJECT-TYPE
SYNTAX      INTEGER {
disable(0),
enable(1)
}
MAX-ACCESS  read-write
STATUS      current
DESCRIPTION
"Rectifier Restart Enable
Values:
disable(0),
enable(1)
"
 ::= { psDc1  19 }

psDc1Rsq OBJECT-TYPE
SYNTAX      INTEGER {
disable(0),
enable(1)
}
MAX-ACCESS  read-write
STATUS      current
DESCRIPTION
"Rectifier Sequencing
Values:
disable(0),
enable(1)
"
 ::= { psDc1  20 }

psDc1Rot OBJECT-TYPE
SYNTAX      Integer32(20000..50000)
MAX-ACCESS  read-write
STATUS      current
DESCRIPTION
"All Rectifier On Threshold"
 ::= { psDc1  21 }

psDc1Rod OBJECT-TYPE
SYNTAX      Integer32(0..60)
MAX-ACCESS  read-write
STATUS      current
DESCRIPTION
"Rectifier On Delay"
 ::= { psDc1  22 }

psDc1Trf OBJECT-TYPE
SYNTAX      DisplayString
MAX-ACCESS  read-only
STATUS      current
DESCRIPTION
"Transfer"
 ::= { psDc1  23 }

psDc1Itd OBJECT-TYPE
SYNTAX      Integer32(1..600)
MAX-ACCESS  read-write
STATUS      current
DESCRIPTION
"Initial Engine Transfer Delay"
 ::= { psDc1  24 }

psDc1Tsi OBJECT-TYPE
SYNTAX      Integer32(0..600)
MAX-ACCESS  read-write
STATUS      current
DESCRIPTION
"Transfer Sequence Interval"
 ::= { psDc1  25 }

psDc1Bti OBJECT-TYPE
SYNTAX      DisplayString
MAX-ACCESS  read-only
STATUS      current
DESCRIPTION
"Battery Thermal Integrity"
 ::= { psDc1  26 }

psDc1Ubt OBJECT-TYPE
SYNTAX      DisplayString
MAX-ACCESS  read-only
STATUS      current
DESCRIPTION
"Battery Temperature"
 ::= { psDc1  27 }

psDc1Tpp OBJECT-TYPE
SYNTAX      DisplayString
MAX-ACCESS  read-only
STATUS      current
DESCRIPTION
"Temperature Probe Present"
 ::= { psDc1  28 }

psDc1Nst OBJECT-TYPE
SYNTAX      Integer32(1..32)
MAX-ACCESS  read-write
STATUS      current
DESCRIPTION
"Number of Battery Strings"
 ::= { psDc1  29 }

psDc1Cps OBJECT-TYPE
SYNTAX      Integer32(1..75)
MAX-ACCESS  read-write
STATUS      current
DESCRIPTION
"Number of Cells per String"
 ::= { psDc1  30 }

psDc1Bty OBJECT-TYPE
SYNTAX      DisplayString
MAX-ACCESS  read-write
STATUS      current
DESCRIPTION
"Battery Type
Values:
L1S,
IR30,
IR40,
12IR125,
4VR125,
2VR375,
L508,
GU41
"
 ::= { psDc1  31 }

psDc1Rtm OBJECT-TYPE
SYNTAX      DisplayString
MAX-ACCESS  read-only
STATUS      current
DESCRIPTION
"Reserve Time"
 ::= { psDc1  32 }

psDc1Btj OBJECT-TYPE
SYNTAX      DisplayString
MAX-ACCESS  read-only
STATUS      current
DESCRIPTION
"Battery Thermal Major
Value:
Alarm report from BTJ1
"
 ::= { psDc1  33 }

psDc1Btn OBJECT-TYPE
SYNTAX      DisplayString
MAX-ACCESS  read-only
STATUS      current
DESCRIPTION
"Battery Thermal Minor
Value:
Alarm report from BTN1
"
 ::= { psDc1  34 }

psDc1Amj OBJECT-TYPE
SYNTAX      DisplayString
MAX-ACCESS  read-only
STATUS      current
DESCRIPTION
"Auxiliary Fuse Major
Value:
Alarm report from AMJ1
"
 ::= { psDc1  35 }

psDc1Amn OBJECT-TYPE
SYNTAX      DisplayString
MAX-ACCESS  read-only
STATUS      current
DESCRIPTION
"Auxiliary Fuse Minor
Value:
Alarm report from AMN1
"
 ::= { psDc1  36 }

psDc1Faj OBJECT-TYPE
SYNTAX      DisplayString
MAX-ACCESS  read-only
STATUS      current
DESCRIPTION
"External Fuse Major
Value:
Alarm report from FAJ1
"
 ::= { psDc1  37 }

psDc1Fan OBJECT-TYPE
SYNTAX      DisplayString
MAX-ACCESS  read-only
STATUS      current
DESCRIPTION
"External Fuse Minor
Value:
Alarm report from FAN1
"
 ::= { psDc1  38 }

psDc1Rbf OBJECT-TYPE
SYNTAX      DisplayString
MAX-ACCESS  read-only
STATUS      current
DESCRIPTION
"Regulation Battery Fuse
Value:
Alarm report from RBF1
"
 ::= { psDc1  39 }

psDc1Btf OBJECT-TYPE
SYNTAX      DisplayString
MAX-ACCESS  read-only
STATUS      current
DESCRIPTION
"Battery Thermal Fuse
Value:
Alarm report from BTF1
"
 ::= { psDc1  40 }

psDc1Bpf OBJECT-TYPE
SYNTAX      DisplayString
MAX-ACCESS  read-only
STATUS      current
DESCRIPTION
"Battery Power Fuse
Value:
Alarm report from BPF1
"
 ::= { psDc1  41 }

psDc1Abs OBJECT-TYPE
SYNTAX      DisplayString
MAX-ACCESS  read-only
STATUS      current
DESCRIPTION
"Alarm Battery Supply
Value:
Alarm report from ABS1
"
 ::= { psDc1  42 }

psDc1Vsf OBJECT-TYPE
SYNTAX      DisplayString
MAX-ACCESS  read-only
STATUS      current
DESCRIPTION
"Sense/Control Fuse
Value:
Alarm report from VSF1
"
 ::= { psDc1  43 }

psDc1Lvda OBJECT-TYPE
SYNTAX      DisplayString
MAX-ACCESS  read-only
STATUS      current
DESCRIPTION
"Low Voltage Disconnect Fail
Value:
Alarm report from LVDA1
"
 ::= { psDc1  44 }

psDc1Lvd OBJECT-TYPE
SYNTAX      DisplayString
MAX-ACCESS  read-only
STATUS      current
DESCRIPTION
"Low Voltage Disconnect
Value:
Alarm report from LVD1
"
 ::= { psDc1  45 }

psDc1Osa OBJECT-TYPE
SYNTAX      DisplayString
MAX-ACCESS  read-only
STATUS      current
DESCRIPTION
"Open String
Value:
Alarm report from OSA1
"
 ::= { psDc1  46 }

psDc1Emd OBJECT-TYPE
SYNTAX      DisplayString
MAX-ACCESS  read-only
STATUS      current
DESCRIPTION
"Energy Management Disabled
Value:
Alarm report from EMD1
"
 ::= { psDc1  47 }

psDc1Epd OBJECT-TYPE
SYNTAX      DisplayString
MAX-ACCESS  read-only
STATUS      current
DESCRIPTION
"Excess Plant Drain
Value:
Alarm report from EPD1
"
 ::= { psDc1  48 }

psDc1Snc OBJECT-TYPE
SYNTAX      DisplayString
MAX-ACCESS  read-only
STATUS      current
DESCRIPTION
"Shunt Not Configured
Value:
Alarm report from SNC1
"
 ::= { psDc1  49 }

psDc1Urc OBJECT-TYPE
SYNTAX      DisplayString
MAX-ACCESS  read-only
STATUS      current
DESCRIPTION
"User Relay Conflict
Value:
Alarm report from URC1
"
 ::= { psDc1  50 }

psDc1Zid OBJECT-TYPE
SYNTAX      DisplayString
MAX-ACCESS  read-only
STATUS      current
DESCRIPTION
"ID Not Configured
Value:
Alarm report from ZID1
"
 ::= { psDc1  51 }

psDc1Tpa OBJECT-TYPE
SYNTAX      DisplayString
MAX-ACCESS  read-only
STATUS      current
DESCRIPTION
"Thermal Probe Alarm
Value:
Alarm report from TPA1
"
 ::= { psDc1  52 }

psDc1Cma OBJECT-TYPE
SYNTAX      DisplayString
MAX-ACCESS  read-only
STATUS      current
DESCRIPTION
"Minor Communication Failure
Value:
Alarm report from CMA1
"
 ::= { psDc1  53 }

psDc1Mcm OBJECT-TYPE
SYNTAX      DisplayString
MAX-ACCESS  read-only
STATUS      current
DESCRIPTION
"Major Communication Failure
Value:
Alarm report from MCM1
"
 ::= { psDc1  54 }

psDc1Bid OBJECT-TYPE
SYNTAX      DisplayString
MAX-ACCESS  read-only
STATUS      current
DESCRIPTION
"Bay Interface ID Conflict
Value:
Alarm report from BID1
"
 ::= { psDc1  55 }

psDc1Rfa OBJECT-TYPE
SYNTAX      DisplayString
MAX-ACCESS  read-only
STATUS      current
DESCRIPTION
"Rectifier Fail
Value:
Alarm report from RFA1
"
 ::= { psDc1  56 }

psDc1Did OBJECT-TYPE
SYNTAX      DisplayString
MAX-ACCESS  read-only
STATUS      current
DESCRIPTION
"ID Conflict
Value:
Alarm report from DID1
"
 ::= { psDc1  57 }

psDc1Clm OBJECT-TYPE
SYNTAX      DisplayString
MAX-ACCESS  read-only
STATUS      current
DESCRIPTION
"Rectifier Current Limit
Value:
Alarm report from CLM1
"
 ::= { psDc1  58 }

psDc1Vla OBJECT-TYPE
SYNTAX      DisplayString
MAX-ACCESS  read-only
STATUS      current
DESCRIPTION
"Very Low Voltage
Value:
Alarm report from VLA1
"
 ::= { psDc1  59 }

psDc1Acf OBJECT-TYPE
SYNTAX      DisplayString
MAX-ACCESS  read-only
STATUS      current
DESCRIPTION
"AC Fail
Value:
Alarm report from ACF1
"
 ::= { psDc1  60 }

psDc1Pha OBJECT-TYPE
SYNTAX      DisplayString
MAX-ACCESS  read-only
STATUS      current
DESCRIPTION
"Phase or Low Output
Value:
Alarm report from PHA1
"
 ::= { psDc1  61 }

psDc1Lca OBJECT-TYPE
SYNTAX      DisplayString
MAX-ACCESS  read-only
STATUS      current
DESCRIPTION
"Low Current
Value:
Alarm report from LCA1
"
 ::= { psDc1  62 }

psDc1Lsf OBJECT-TYPE
SYNTAX      DisplayString
MAX-ACCESS  read-only
STATUS      current
DESCRIPTION
"Load Share Fuse
Value:
Alarm report from LSF1
"
 ::= { psDc1  63 }

psDc1Man OBJECT-TYPE
SYNTAX      DisplayString
MAX-ACCESS  read-only
STATUS      current
DESCRIPTION
"Manual Off
Value:
Alarm report from MAN1
"
 ::= { psDc1  64 }

psDc1Ets OBJECT-TYPE
SYNTAX      DisplayString
MAX-ACCESS  read-only
STATUS      current
DESCRIPTION
"External Transfer Shutdown
Value:
Alarm report from ETS1
"
 ::= { psDc1  65 }

psDc1Ric OBJECT-TYPE
SYNTAX      DisplayString
MAX-ACCESS  read-only
STATUS      current
DESCRIPTION
"Rectifier Incomplete Configuration
Value:
Alarm report from RIC1
"
 ::= { psDc1  66 }

psDc1Hpa OBJECT-TYPE
SYNTAX      DisplayString
MAX-ACCESS  read-only
STATUS      current
DESCRIPTION
"Half Power
Value:
Alarm report from HPA1
"
 ::= { psDc1  67 }

psDc1Mfa OBJECT-TYPE
SYNTAX      DisplayString
MAX-ACCESS  read-only
STATUS      current
DESCRIPTION
"Multiple Rectifier Fail
Value:
Alarm report from MFA1
"
 ::= { psDc1  68 }

psDc1Lmr OBJECT-TYPE
SYNTAX      DisplayString
MAX-ACCESS  read-only
STATUS      current
DESCRIPTION
"Limited Recharge
Value:
Alarm report from LMR1
"
 ::= { psDc1  69 }

psDc1Erd OBJECT-TYPE
SYNTAX      DisplayString
MAX-ACCESS  read-only
STATUS      current
DESCRIPTION
"Excess Rectifier Drain
Value:
Alarm report from ERD1
"
 ::= { psDc1  70 }

psDc1Eto OBJECT-TYPE
SYNTAX      DisplayString
MAX-ACCESS  read-only
STATUS      current
DESCRIPTION
"Engine Transfer Timeout
Value:
Alarm report from ETO1
"
 ::= { psDc1  71 }

psDc1Rpi OBJECT-TYPE
SYNTAX      DisplayString
MAX-ACCESS  read-only
STATUS      current
DESCRIPTION
"Rectifier/Plant Inconsistency
Value:
Alarm report from RPI1
"
 ::= { psDc1  72 }

psDc1Rtl OBJECT-TYPE
SYNTAX      DisplayString
MAX-ACCESS  read-only
STATUS      current
DESCRIPTION
"Reserve Time Low
Value:
Alarm report from RTL1
"
 ::= { psDc1  73 }

psDc1Bda OBJECT-TYPE
SYNTAX      DisplayString
MAX-ACCESS  read-only
STATUS      current
DESCRIPTION
"Battery On Discharge
Value:
Alarm report from BDA1
"
 ::= { psDc1  74 }

psDc1Hva OBJECT-TYPE
SYNTAX      DisplayString
MAX-ACCESS  read-only
STATUS      current
DESCRIPTION
"High Voltage
Value:
Alarm report from HVA1
"
 ::= { psDc1  75 }

psDc1Hfv OBJECT-TYPE
SYNTAX      DisplayString
MAX-ACCESS  read-only
STATUS      current
DESCRIPTION
"High Float Voltage
Value:
Alarm report from HFV1
"
 ::= { psDc1  76 }

psDc1Bst OBJECT-TYPE
SYNTAX      DisplayString
MAX-ACCESS  read-only
STATUS      current
DESCRIPTION
"Boost"
 ::= { psDc1  77 }

psDc1Olcap OBJECT-TYPE
SYNTAX      DisplayString
MAX-ACCESS  read-only
STATUS      current
DESCRIPTION
"Online Capacity"
 ::= { psDc1  78 }

psDc1Isd OBJECT-TYPE
SYNTAX      INTEGER {
disable(0),
enable(1)
}
MAX-ACCESS  read-write
STATUS      current
DESCRIPTION
"Imminent Shutdown Enable
Values:
disable(0),
enable(1)
"
 ::= { psDc1  79 }

psDc1Vmf OBJECT-TYPE
SYNTAX      DisplayString
MAX-ACCESS  read-only
STATUS      current
DESCRIPTION
"Voltage Module Failure
Value:
Alarm report from VMF1
"
 ::= { psDc1  80 }

psDc1Epo OBJECT-TYPE
SYNTAX      DisplayString
MAX-ACCESS  read-only
STATUS      current
DESCRIPTION
"Emergency Power Off
Value:
Alarm report from EPO1
"
 ::= { psDc1  81 }

psDc1Icr OBJECT-TYPE
SYNTAX      DisplayString
MAX-ACCESS  read-only
STATUS      current
DESCRIPTION
"Incompatible Rectifier
Value:
Alarm report from ICR1
"
 ::= { psDc1  82 }

psDc1Rfn OBJECT-TYPE
SYNTAX      DisplayString
MAX-ACCESS  read-only
STATUS      current
DESCRIPTION
"Rectifier Fan Failure
Value:
Alarm report from RFN1
"
 ::= { psDc1  83 }

psDc1Bdt OBJECT-TYPE
SYNTAX      DisplayString
MAX-ACCESS  read-only
STATUS      current
DESCRIPTION
"BD Duration"
 ::= { psDc1  84 }

psDc1Poc OBJECT-TYPE
SYNTAX      DisplayString
UNITS       "%"
MAX-ACCESS  read-only
STATUS      current
DESCRIPTION
"Percent of Charge (%)"
 ::= { psDc1  85 }

psDc1Rrtl OBJECT-TYPE
SYNTAX      DisplayString
MAX-ACCESS  read-only
STATUS      current
DESCRIPTION
"Real-Time Reserve Low
Value:
Alarm report from RRTL1
"
 ::= { psDc1  86 }

psDc1Rls OBJECT-TYPE
SYNTAX      DisplayString
MAX-ACCESS  read-only
STATUS      current
DESCRIPTION
"Redundancy Loss
Value:
Alarm report from RLS1
"
 ::= { psDc1  87 }

psDc1Macf OBJECT-TYPE
SYNTAX      DisplayString
MAX-ACCESS  read-only
STATUS      current
DESCRIPTION
"Multiple AC Fail
Value:
Alarm report from MACF1
"
 ::= { psDc1  88 }

psDc1Mman OBJECT-TYPE
SYNTAX      DisplayString
MAX-ACCESS  read-only
STATUS      current
DESCRIPTION
"Multiple Manual Off
Value:
Alarm report from MMAN1
"
 ::= { psDc1  89 }

psDc1Faj2 OBJECT-TYPE
SYNTAX      DisplayString
MAX-ACCESS  read-only
STATUS      current
DESCRIPTION
"External Fuse Major 2
Value:
Alarm report from FAJ2
"
 ::= { psDc1  90 }

psDc1Mls OBJECT-TYPE
SYNTAX      INTEGER {
disable(0),
enable(1)
}
MAX-ACCESS  read-write
STATUS      current
DESCRIPTION
"All Load Shunts are Monitored
Values:
disable(0),
enable(1)
"
 ::= { psDc1  91 }

psDc1Emt OBJECT-TYPE
SYNTAX      Integer32(0..100)
UNITS       "Percent"
MAX-ACCESS  read-write
STATUS      current
DESCRIPTION
"Efficiency Target Threshold(Percent)"
 ::= { psDc1  92 }

psDc1Emo OBJECT-TYPE
SYNTAX      Integer32(0..100)
UNITS       "Percent"
MAX-ACCESS  read-write
STATUS      current
DESCRIPTION
"Efficiency On Threshold (Percent)"
 ::= { psDc1  93 }

psDc1Emi OBJECT-TYPE
SYNTAX      Integer32(1..30)
UNITS       "Minutes"
MAX-ACCESS  read-write
STATUS      current
DESCRIPTION
"Efficiency Initial Delay (Minutes)"
 ::= { psDc1  94 }

psDc1Emw OBJECT-TYPE
SYNTAX      Integer32(1..30)
UNITS       "Minutes"
MAX-ACCESS  read-write
STATUS      current
DESCRIPTION
"Efficiency Delay (Minutes)"
 ::= { psDc1  95 }

psDc1Ete OBJECT-TYPE
SYNTAX      INTEGER {
disable(0),
enable(1)
}
MAX-ACCESS  read-write
STATUS      current
DESCRIPTION
"External TR Enable
Values:
disable(0),
enable(1)
"
 ::= { psDc1  96 }

psDc1Aseq OBJECT-TYPE
SYNTAX      INTEGER {
disable(0),
enable(1)
}
MAX-ACCESS  read-write
STATUS      current
DESCRIPTION
"Automatic Sequencing
Values:
disable(0),
enable(1)
"
 ::= { psDc1  97 }

psDc1Res OBJECT-TYPE
SYNTAX      DisplayString
MAX-ACCESS  read-only
STATUS      current
DESCRIPTION
"Reserve Time Error"
 ::= { psDc1  98 }

psDc1Pfs OBJECT-TYPE
SYNTAX      DisplayString
MAX-ACCESS  read-only
STATUS      current
DESCRIPTION
"Thermal Probe Fail Safe
Value:
Alarm report from PFS1
"
 ::= { psDc1  99 }

psDc1Rif OBJECT-TYPE
SYNTAX      DisplayString
MAX-ACCESS  read-only
STATUS      current
DESCRIPTION
"Rectifier Internal Fault
Value:
Alarm report from RIF1
"
 ::= { psDc1  100 }

psDc1Isy OBJECT-TYPE
SYNTAX      DisplayString
MAX-ACCESS  read-write
STATUS      current
DESCRIPTION
"Imminent Shutdown Delay"
 ::= { psDc1  101 }

psDc1Hrt OBJECT-TYPE
SYNTAX      INTEGER {
disable(0),
enable(1)
}
MAX-ACCESS  read-write
STATUS      current
DESCRIPTION
"Display Reserve Time Enable
Values:
disable(0),
enable(1)
"
 ::= { psDc1  102 }

psDc1Pid OBJECT-TYPE
SYNTAX      DisplayString
MAX-ACCESS  read-only
STATUS      current
DESCRIPTION
"Panel Interface ID Conflict
Value:
Alarm report from PID1
"
 ::= { psDc1  103 }

psDc1Rtl2 OBJECT-TYPE
SYNTAX      DisplayString
MAX-ACCESS  read-only
STATUS      current
DESCRIPTION
"Reserve Time Low 2
Value:
Alarm report from RTL2
"
 ::= { psDc1  104 }

psDc1Faja OBJECT-TYPE
SYNTAX      DisplayString
MAX-ACCESS  read-only
STATUS      current
DESCRIPTION
"Distribution Fuse A
Value:
Alarm report from FAJA1
"
 ::= { psDc1  105 }

psDc1Fajb OBJECT-TYPE
SYNTAX      DisplayString
MAX-ACCESS  read-only
STATUS      current
DESCRIPTION
"Distribution Fuse B
Value:
Alarm report from FAJB1
"
 ::= { psDc1  106 }

psDc1Vlva OBJECT-TYPE
SYNTAX      DisplayString
MAX-ACCESS  read-only
STATUS      current
DESCRIPTION
"VA Power Loss
Value:
Alarm report from VLVA1
"
 ::= { psDc1  107 }

psDc1Vlvb OBJECT-TYPE
SYNTAX      DisplayString
MAX-ACCESS  read-only
STATUS      current
DESCRIPTION
"VB Power Loss
Value:
Alarm report from VLBB1
"
 ::= { psDc1  108 }

psDc1Ovla OBJECT-TYPE
SYNTAX      DisplayString
MAX-ACCESS  read-only
STATUS      current
DESCRIPTION
"IA Overload
Value:
Alarm report from OVLA1
"
 ::= { psDc1  109 }

psDc1Ovlb OBJECT-TYPE
SYNTAX      DisplayString
MAX-ACCESS  read-only
STATUS      current
DESCRIPTION
"IB Overload
Value:
Alarm report from OVLB1
"
 ::= { psDc1  110 }

psDc1Smw OBJECT-TYPE
SYNTAX      DisplayString
MAX-ACCESS  read-only
STATUS      current
DESCRIPTION
"Shunt Mis-wired
Value:
Alarm report from SMW1
"
 ::= { psDc1  111 }

psDc1Cca OBJECT-TYPE
SYNTAX      DisplayString
MAX-ACCESS  read-only
STATUS      current
DESCRIPTION
"Circuit Assignment
Value:
Alarm report from CCA1
"
 ::= { psDc1  112 }

psDc1Rrtl2 OBJECT-TYPE
SYNTAX      DisplayString
MAX-ACCESS  read-only
STATUS      current
DESCRIPTION
"Real-Time Reserve Low
Value:
Alarm report from RRTL2
"
 ::= { psDc1  113 }

psDc1Vhav OBJECT-TYPE
SYNTAX      DisplayString
MAX-ACCESS  read-only
STATUS      current
DESCRIPTION
"Very High AC Voltage
Value:
Alarm report from VHAV1
"
 ::= { psDc1  114 }

psDc1Hav OBJECT-TYPE
SYNTAX      DisplayString
MAX-ACCESS  read-only
STATUS      current
DESCRIPTION
"High AC Voltage
Value:
Alarm report from HAV1
"
 ::= { psDc1  115 }

psDc1Vlav OBJECT-TYPE
SYNTAX      DisplayString
MAX-ACCESS  read-only
STATUS      current
DESCRIPTION
"Very Low AC Voltage
Value:
Alarm report from VLAV1
"
 ::= { psDc1  116 }

psDc1Lav OBJECT-TYPE
SYNTAX      DisplayString
MAX-ACCESS  read-only
STATUS      current
DESCRIPTION
"Low AC Voltage
Value:
Alarm report from LAV1
"
 ::= { psDc1  117 }

psDc1Tic OBJECT-TYPE
SYNTAX      DisplayString
MAX-ACCESS  read-only
STATUS      current
DESCRIPTION
"Total Installed Capacity
Value:
Alarm report from TIC1
"
 ::= { psDc1  118 }

psDc1Tcc OBJECT-TYPE
SYNTAX      DisplayString
MAX-ACCESS  read-only
STATUS      current
DESCRIPTION
"Total Configured Capacity
Value:
Alarm report from TIC1
"
 ::= { psDc1  119 }

psDc1Nvac OBJECT-TYPE
SYNTAX      Integer32(0..530)
MAX-ACCESS  read-write
STATUS      current
DESCRIPTION
"Nominal AC Voltage"
 ::= { psDc1  120 }

psDc1Ccap OBJECT-TYPE
SYNTAX      DisplayString
MAX-ACCESS  read-write
STATUS      current
DESCRIPTION
"Configured Capacity"
 ::= { psDc1  121 }

psDc1Ticl OBJECT-TYPE
SYNTAX      INTEGER {
disable(0),
enable(1)
}
MAX-ACCESS  read-write
STATUS      current
DESCRIPTION
"Total Installed Capacity Latch Enable
Values:
disable(0),
enable(1)
"
 ::= { psDc1  122 }

psDc1Tccl OBJECT-TYPE
SYNTAX      INTEGER {
disable(0),
enable(1)
}
MAX-ACCESS  read-write
STATUS      current
DESCRIPTION
"Total Configured Capacity Latch Enable
Values:
disable(0),
enable(1)
"
 ::= { psDc1  123 }

psDc1Bod1 OBJECT-TYPE
SYNTAX      INTEGER {
inactive(0),
active(1)
}
MAX-ACCESS  read-only
STATUS      current
DESCRIPTION
"Battery On Discharge
Values:
inactive(0),
active(1)
"
 ::= { psDc1  124 }

psDc1Bdt1 OBJECT-TYPE
SYNTAX      Integer32
UNITS       "Seconds"
MAX-ACCESS  read-only
STATUS      current
DESCRIPTION
"BD Duration (Seconds)"
 ::= { psDc1  125 }

psDc1Poc1 OBJECT-TYPE
SYNTAX      Integer32(0..100)
UNITS       "%"
MAX-ACCESS  read-only
STATUS      current
DESCRIPTION
"Percent of Charge (%)"
 ::= { psDc1  126 }

psDc1Rtm1 OBJECT-TYPE
SYNTAX      Integer32
UNITS       "Seconds"
MAX-ACCESS  read-only
STATUS      current
DESCRIPTION
"Reserve Time (Seconds)"
 ::= { psDc1  127 }

psDc1Pcaux OBJECT-TYPE
SYNTAX      DisplayString
MAX-ACCESS  read-only
STATUS      current
DESCRIPTION
"PIC Auxiliary
Value:
Alarm report from PCAUX1
"
 ::= { psDc1  128 }

psDc1Slot OBJECT-TYPE
SYNTAX      DisplayString
MAX-ACCESS  read-only
STATUS      current
DESCRIPTION
"PIC Slot
Value:
Alarm report from SLOT1
"
 ::= { psDc1  129 }

psDc1Vid OBJECT-TYPE
SYNTAX      DisplayString
MAX-ACCESS  read-only
STATUS      current
DESCRIPTION
"BDFB/BDCBB ID Conflict
Value:
Alarm report from VID1
"
 ::= { psDc1  130 }

psDc1Tice OBJECT-TYPE
SYNTAX      INTEGER {
disable(0),
enable(1)
}
MAX-ACCESS  read-write
STATUS      current
DESCRIPTION
"Total Installed Capacity Enable
Values:
disable(0),
enable(1)
"
 ::= { psDc1  131 }

psDc1Tcce OBJECT-TYPE
SYNTAX      INTEGER {
disable(0),
enable(1)
}
MAX-ACCESS  read-write
STATUS      current
DESCRIPTION
"Total Configured Capacity Enable
Values:
disable(0),
enable(1)
"
 ::= { psDc1  132 }


--
-- object psPs1
--

psPs1 OBJECT IDENTIFIER  ::= { powerSystem  2 }

psPs1Ide OBJECT-TYPE
SYNTAX      DisplayString
MAX-ACCESS  read-only
STATUS      current
DESCRIPTION
"Identifier"
 ::= { psPs1  1 }

psPs1Des OBJECT-TYPE
SYNTAX      DisplayString
MAX-ACCESS  read-write
STATUS      current
DESCRIPTION
"Description"
 ::= { psPs1  2 }

psPs1Sid OBJECT-TYPE
SYNTAX      DisplayString
MAX-ACCESS  read-write
STATUS      current
DESCRIPTION
"Site ID"
 ::= { psPs1  3 }

psPs1Sde OBJECT-TYPE
SYNTAX      DisplayString
MAX-ACCESS  read-write
STATUS      current
DESCRIPTION
"Site Description"
 ::= { psPs1  4 }

psPs1Cty OBJECT-TYPE
SYNTAX      DisplayString
MAX-ACCESS  read-only
STATUS      current
DESCRIPTION
"Controller Type"
 ::= { psPs1  5 }

psPs1Swv OBJECT-TYPE
SYNTAX      DisplayString
MAX-ACCESS  read-only
STATUS      current
DESCRIPTION
"Software Versions"
 ::= { psPs1  6 }

psPs1Dow OBJECT-TYPE
SYNTAX      DisplayString
MAX-ACCESS  read-only
STATUS      current
DESCRIPTION
"Day of Week"
 ::= { psPs1  7 }

psPs1Dat OBJECT-TYPE
SYNTAX      DisplayString
MAX-ACCESS  read-write
STATUS      current
DESCRIPTION
"System Date"
 ::= { psPs1  8 }

psPs1Dtf OBJECT-TYPE
SYNTAX      DisplayString
MAX-ACCESS  read-write
STATUS      current
DESCRIPTION
"Date Format
Values:
mm/dd/yyyy,
dd/mm/yyyy,
yyyy/mm/dd
"
 ::= { psPs1  9 }

psPs1Tim OBJECT-TYPE
SYNTAX      DisplayString
MAX-ACCESS  read-write
STATUS      current
DESCRIPTION
"System Time"
 ::= { psPs1  10 }

psPs1Tmf OBJECT-TYPE
SYNTAX      INTEGER {
h12(12),
h24(24)
}
MAX-ACCESS  read-write
STATUS      current
DESCRIPTION
"System Time Format
Values:
h12(12),
h24(24)
"
 ::= { psPs1  11 }

psPs1Dls OBJECT-TYPE
SYNTAX      INTEGER {
off(0),
on(1)
}
MAX-ACCESS  read-write
STATUS      current
DESCRIPTION
"Daylight Savings
Values:
off(0),
on(1)
"
 ::= { psPs1  12 }

psPs1Lng OBJECT-TYPE
SYNTAX      DisplayString
MAX-ACCESS  read-write
STATUS      current
DESCRIPTION
"Front Panel Language
Values:
ENGLISH,
SYMBOLIC,
OTHER
"
 ::= { psPs1  13 }

psPs1Tun OBJECT-TYPE
SYNTAX      DisplayString
MAX-ACCESS  read-write
STATUS      current
DESCRIPTION
"Temperature Units
Values:
C,
F
"
 ::= { psPs1  14 }

psPs1Cem OBJECT-TYPE
SYNTAX      INTEGER {
no(0),
yes(1)
}
MAX-ACCESS  read-write
STATUS      current
DESCRIPTION
"Critical Equals Major
Values:
no(0),
yes(1)
"
 ::= { psPs1  15 }

psPs1Fpc OBJECT-TYPE
SYNTAX      INTEGER {
disable(0),
enable(1)
}
MAX-ACCESS  read-write
STATUS      current
DESCRIPTION
"Front Panel Configuration
Values:
disable(0),
enable(1)
"
 ::= { psPs1  16 }

psPs1Spc OBJECT-TYPE
SYNTAX      INTEGER {
disable(0),
enable(1)
}
MAX-ACCESS  read-write
STATUS      current
DESCRIPTION
"Serial Port Configuration
Values:
disable(0),
enable(1)
"
 ::= { psPs1  17 }

psPs1Rrn OBJECT-TYPE
SYNTAX      INTEGER {
disable(0),
enable(1)
}
MAX-ACCESS  read-write
STATUS      current
DESCRIPTION
"Remote Rectifier On
Values:
disable(0),
enable(1)
"
 ::= { psPs1  18 }

psPs1Rrf OBJECT-TYPE
SYNTAX      INTEGER {
disable(0),
enable(1)
}
MAX-ACCESS  read-write
STATUS      current
DESCRIPTION
"Remote Rectifier Off
Values:
disable(0),
enable(1)
"
 ::= { psPs1  19 }

psPs1Cra OBJECT-TYPE
SYNTAX      DisplayString
MAX-ACCESS  read-only
STATUS      current
DESCRIPTION
"Intelligent Controller Fail
Value:
Alarm report from CRA1
"
 ::= { psPs1  20 }

psPs1Crf OBJECT-TYPE
SYNTAX      DisplayString
MAX-ACCESS  read-only
STATUS      current
DESCRIPTION
"Intelligent Controller Fuse
Value:
Alarm report from CRF1
"
 ::= { psPs1  21 }

psPs1Cpa OBJECT-TYPE
SYNTAX      DisplayString
MAX-ACCESS  read-only
STATUS      current
DESCRIPTION
"Circuit Pack Fail
Value:
Alarm report from CPA1
"
 ::= { psPs1  22 }

psPs1Rpf OBJECT-TYPE
SYNTAX      DisplayString
MAX-ACCESS  read-only
STATUS      current
DESCRIPTION
"Remote Peripheral Fuse
Value:
Alarm report from RPF1
"
 ::= { psPs1  23 }

psPs1Pcf OBJECT-TYPE
SYNTAX      DisplayString
MAX-ACCESS  read-only
STATUS      current
DESCRIPTION
"PC Power Fuse
Value:
Alarm report from PCF1
"
 ::= { psPs1  24 }

psPs1Epr OBJECT-TYPE
SYNTAX      DisplayString
MAX-ACCESS  read-only
STATUS      current
DESCRIPTION
"External Password Reset
Value:
Alarm report from EPR1
"
 ::= { psPs1  25 }

psPs1Pfd OBJECT-TYPE
SYNTAX      DisplayString
MAX-ACCESS  read-only
STATUS      current
DESCRIPTION
"Passwords At Default
Value:
Alarm report from PFD1
"
 ::= { psPs1  26 }

psPs1Exl OBJECT-TYPE
SYNTAX      DisplayString
MAX-ACCESS  read-only
STATUS      current
DESCRIPTION
"Excessive Login Attempts
Value:
Alarm report from EXL1
"
 ::= { psPs1  27 }

psPs1Bbl OBJECT-TYPE
SYNTAX      DisplayString
MAX-ACCESS  read-only
STATUS      current
DESCRIPTION
"Memory Backup Battery Low
Value:
Alarm report from BBL1
"
 ::= { psPs1  28 }

psPs1Pht OBJECT-TYPE
SYNTAX      DisplayString
MAX-ACCESS  read-only
STATUS      current
DESCRIPTION
"Processor Halt
Value:
Alarm report from PHT1
"
 ::= { psPs1  29 }

psPs1Clc OBJECT-TYPE
SYNTAX      DisplayString
MAX-ACCESS  read-only
STATUS      current
DESCRIPTION
"Clock Changed
Value:
Alarm report from CLC1
"
 ::= { psPs1  30 }

psPs1Stf OBJECT-TYPE
SYNTAX      DisplayString
MAX-ACCESS  read-only
STATUS      current
DESCRIPTION
"Self Test Failed
Value:
Alarm report from STF1
"
 ::= { psPs1  31 }

psPs1Pgi OBJECT-TYPE
SYNTAX      DisplayString
MAX-ACCESS  read-only
STATUS      current
DESCRIPTION
"Program Line Invalid
Value:
Alarm report from PGI1
"
 ::= { psPs1  32 }

psPs1Cch OBJECT-TYPE
SYNTAX      DisplayString
MAX-ACCESS  read-only
STATUS      current
DESCRIPTION
"Configuration Changed
Value:
Alarm report from CCH1
"
 ::= { psPs1  33 }

psPs1Hcl OBJECT-TYPE
SYNTAX      DisplayString
MAX-ACCESS  read-only
STATUS      current
DESCRIPTION
"History Cleared
Value:
Alarm report from HCL1
"
 ::= { psPs1  34 }

psPs1Mor OBJECT-TYPE
SYNTAX      DisplayString
MAX-ACCESS  read-only
STATUS      current
DESCRIPTION
"Measurement Out Of Range
Value:
Alarm report from MOR1
"
 ::= { psPs1  35 }

psPs1Mtc OBJECT-TYPE
SYNTAX      DisplayString
MAX-ACCESS  read-only
STATUS      current
DESCRIPTION
"Module Type Conflict
Value:
Alarm report from MTC1
"
 ::= { psPs1  36 }

psPs1Mdf OBJECT-TYPE
SYNTAX      DisplayString
MAX-ACCESS  read-only
STATUS      current
DESCRIPTION
"Module Failure
Value:
Alarm report from MDF1
"
 ::= { psPs1  37 }

psPs1Ats OBJECT-TYPE
SYNTAX      DisplayString
MAX-ACCESS  read-only
STATUS      current
DESCRIPTION
"System Alarm Test"
 ::= { psPs1  38 }

psPs1Amt OBJECT-TYPE
SYNTAX      DisplayString
MAX-ACCESS  read-only
STATUS      current
DESCRIPTION
"Ambient Temperature"
 ::= { psPs1  39 }

psPs1Mrm OBJECT-TYPE
SYNTAX      DisplayString
MAX-ACCESS  read-only
STATUS      current
DESCRIPTION
"Maintenance Reminders"
 ::= { psPs1  40 }

psPs1Sn OBJECT-TYPE
SYNTAX      DisplayString
MAX-ACCESS  read-only
STATUS      current
DESCRIPTION
"Serial Number"
 ::= { psPs1  41 }

psPs1Sys OBJECT-TYPE
SYNTAX      DisplayString
MAX-ACCESS  read-only
STATUS      current
DESCRIPTION
"System Name"
 ::= { psPs1  42 }

psPs1Verw OBJECT-TYPE
SYNTAX      DisplayString
MAX-ACCESS  read-only
STATUS      current
DESCRIPTION
"Web Page Version"
 ::= { psPs1  43 }

psPs1Verb OBJECT-TYPE
SYNTAX      DisplayString
MAX-ACCESS  read-only
STATUS      current
DESCRIPTION
"Boot Block Version"
 ::= { psPs1  44 }

psPs1Brc OBJECT-TYPE
SYNTAX      DisplayString
MAX-ACCESS  read-only
STATUS      current
DESCRIPTION
"Board Code"
 ::= { psPs1  45 }

psPs1Ptt OBJECT-TYPE
SYNTAX      DisplayString
MAX-ACCESS  read-only
STATUS      current
DESCRIPTION
"Local Port Type"
 ::= { psPs1  46 }

psPs1Ast OBJECT-TYPE
SYNTAX      DisplayString
MAX-ACCESS  read-only
STATUS      current
DESCRIPTION
"Alarm State"
 ::= { psPs1  47 }

psPs1Dss OBJECT-TYPE
SYNTAX      DisplayString
MAX-ACCESS  read-only
STATUS      current
DESCRIPTION
"Daylight Saving Start"
 ::= { psPs1  48 }

psPs1Dse OBJECT-TYPE
SYNTAX      DisplayString
MAX-ACCESS  read-only
STATUS      current
DESCRIPTION
"Daylight Saving End"
 ::= { psPs1  49 }

psPs1Ax1 OBJECT-TYPE
SYNTAX      DisplayString
MAX-ACCESS  read-only
STATUS      current
DESCRIPTION
"Auxiliary Event 1
Value:
Alarm report from AUX1
"
 ::= { psPs1  50 }

psPs1Ax2 OBJECT-TYPE
SYNTAX      DisplayString
MAX-ACCESS  read-only
STATUS      current
DESCRIPTION
"Auxiliary Event 2
Value:
Alarm report from AUX2
"
 ::= { psPs1  51 }

psPs1Ax3 OBJECT-TYPE
SYNTAX      DisplayString
MAX-ACCESS  read-only
STATUS      current
DESCRIPTION
"Auxiliary Event 3
Value:
Alarm report from AUX3
"
 ::= { psPs1  52 }

psPs1Ax4 OBJECT-TYPE
SYNTAX      DisplayString
MAX-ACCESS  read-only
STATUS      current
DESCRIPTION
"Auxiliary Event 4
Value:
Alarm report from AUX4
"
 ::= { psPs1  53 }

psPs1Ax5 OBJECT-TYPE
SYNTAX      DisplayString
MAX-ACCESS  read-only
STATUS      current
DESCRIPTION
"Auxiliary Event 5
Value:
Alarm report from AUX5
"
 ::= { psPs1  54 }

psPs1Ax6 OBJECT-TYPE
SYNTAX      DisplayString
MAX-ACCESS  read-only
STATUS      current
DESCRIPTION
"Auxiliary Event 6
Value:
Alarm report from AUX6
"
 ::= { psPs1  55 }

psPs1Dflt OBJECT-TYPE
SYNTAX      DisplayString
MAX-ACCESS  read-only
STATUS      current
DESCRIPTION
"Defaults Version"
 ::= { psPs1  56 }

psPs1Lngl OBJECT-TYPE
SYNTAX      DisplayString
MAX-ACCESS  read-only
STATUS      current
DESCRIPTION
"Installed Languages"
 ::= { psPs1  57 }

psPs1Fst OBJECT-TYPE
SYNTAX      DisplayString
MAX-ACCESS  read-write
STATUS      current
DESCRIPTION
"Factory Defaults"
 ::= { psPs1  58 }

psPs1Fstl OBJECT-TYPE
SYNTAX      DisplayString
MAX-ACCESS  read-only
STATUS      current
DESCRIPTION
"Factory Defaults List"
 ::= { psPs1  59 }

psPs1Fpe OBJECT-TYPE
SYNTAX      INTEGER {
disable(0),
enable(1)
}
MAX-ACCESS  read-write
STATUS      current
DESCRIPTION
"Front Panel Pin Enable
Values:
disable(0),
enable(1)
"
 ::= { psPs1  60 }

psPs1Fpt OBJECT-TYPE
SYNTAX      Integer32
MAX-ACCESS  read-write
STATUS      current
DESCRIPTION
"Front Panel Pin Timeout"
 ::= { psPs1  61 }

psPs1Amtl OBJECT-TYPE
SYNTAX      DisplayString
MAX-ACCESS  read-only
STATUS      current
DESCRIPTION
"Low Ambient Temperature
Value:
Alarm report from AMTL1
"
 ::= { psPs1  62 }

psPs1Amth OBJECT-TYPE
SYNTAX      DisplayString
MAX-ACCESS  read-only
STATUS      current
DESCRIPTION
"High Ambient Temperature
Value:
Alarm report from AMTH1
"
 ::= { psPs1  63 }

psPs1Cc OBJECT-TYPE
SYNTAX      DisplayString
MAX-ACCESS  read-only
STATUS      current
DESCRIPTION
"Comcode"
 ::= { psPs1  64 }

psPs1Clei OBJECT-TYPE
SYNTAX      DisplayString
MAX-ACCESS  read-only
STATUS      current
DESCRIPTION
"CLEI Code"
 ::= { psPs1  65 }

psPs1Ser OBJECT-TYPE
SYNTAX      DisplayString
MAX-ACCESS  read-only
STATUS      current
DESCRIPTION
"Series Number"
 ::= { psPs1  66 }

psPs1Hamt OBJECT-TYPE
SYNTAX      DisplayString
MAX-ACCESS  read-only
STATUS      current
DESCRIPTION
"Highest Ambient Temperature"
 ::= { psPs1  67 }

psPs1Lamt OBJECT-TYPE
SYNTAX      DisplayString
MAX-ACCESS  read-only
STATUS      current
DESCRIPTION
"Lowest Ambient Temperature"
 ::= { psPs1  68 }

psPs1Nat OBJECT-TYPE
SYNTAX      DisplayString
MAX-ACCESS  read-only
STATUS      current
DESCRIPTION
"Number of Ambient Probes"
 ::= { psPs1  69 }

psPs1Tzo OBJECT-TYPE
SYNTAX      Integer32
UNITS       "Minutes"
MAX-ACCESS  read-write
STATUS      current
DESCRIPTION
"Timezone Offset (Minutes)"
 ::= { psPs1  70 }

psPs1Cid OBJECT-TYPE
SYNTAX      INTEGER {
disable(0),
enable(1)
}
MAX-ACCESS  read-write
STATUS      current
DESCRIPTION
"Controller Assignes IDs
Values:
disable(0),
enable(1)
"
 ::= { psPs1  71 }

psPs1Nal OBJECT-TYPE
SYNTAX      Integer32
MAX-ACCESS  read-only
STATUS      current
DESCRIPTION
"Number of Total Alarms Active"
 ::= { psPs1  72 }

psPs1Ncr OBJECT-TYPE
SYNTAX      Integer32
MAX-ACCESS  read-only
STATUS      current
DESCRIPTION
"Number of Total Critical Alarms Active"
 ::= { psPs1  73 }

psPs1Nmj OBJECT-TYPE
SYNTAX      Integer32
MAX-ACCESS  read-only
STATUS      current
DESCRIPTION
"Number of Total Major Alarms Active"
 ::= { psPs1  74 }

psPs1Nmn OBJECT-TYPE
SYNTAX      Integer32
MAX-ACCESS  read-only
STATUS      current
DESCRIPTION
"Number of Total Minor Alarms Active"
 ::= { psPs1  75 }

psPs1Nwa OBJECT-TYPE
SYNTAX      Integer32
MAX-ACCESS  read-only
STATUS      current
DESCRIPTION
"Number of Total Warnings Active"
 ::= { psPs1  76 }

psPs1Nre OBJECT-TYPE
SYNTAX      Integer32
MAX-ACCESS  read-only
STATUS      current
DESCRIPTION
"Number of Total Record Only Events Active"
 ::= { psPs1  77 }


--
-- object psAt1
--

psAt1 OBJECT IDENTIFIER  ::= { powerSystem  3 }

psAt1Ide OBJECT-TYPE
SYNTAX      DisplayString
MAX-ACCESS  read-only
STATUS      current
DESCRIPTION
"Identifier"
 ::= { psAt1  1 }

psAt1Des OBJECT-TYPE
SYNTAX      DisplayString
MAX-ACCESS  read-write
STATUS      current
DESCRIPTION
"Description"
 ::= { psAt1  2 }

psAt1Stt OBJECT-TYPE
SYNTAX      INTEGER {
inactive(0),
active(1)
}
MAX-ACCESS  read-write
STATUS      current
DESCRIPTION
"Alarm Test Active
Values:
inactive(0),
active(1)
"
 ::= { psAt1  3 }

psAt1Stg OBJECT-TYPE
SYNTAX      DisplayString
MAX-ACCESS  read-only
STATUS      current
DESCRIPTION
"Stage"
 ::= { psAt1  4 }

psAt1Rtf OBJECT-TYPE
SYNTAX      DisplayString
MAX-ACCESS  read-only
STATUS      current
DESCRIPTION
"Rectifier Test Failure"
 ::= { psAt1  5 }

psAt1Lte OBJECT-TYPE
SYNTAX      INTEGER {
disable(0),
enable(1)
}
MAX-ACCESS  read-write
STATUS      current
DESCRIPTION
"Alarm Test Enable
Values:
disable(0),
enable(1)
"
 ::= { psAt1  6 }

psAt1Rte OBJECT-TYPE
SYNTAX      INTEGER {
disable(0),
enable(1)
}
MAX-ACCESS  read-write
STATUS      current
DESCRIPTION
"Remote Alarm Test Enable
Values:
disable(0),
enable(1)
"
 ::= { psAt1  7 }

psAt1Hvs OBJECT-TYPE
SYNTAX      INTEGER {
disable(0),
enable(1)
}
MAX-ACCESS  read-write
STATUS      current
DESCRIPTION
"HV Shutdown Enable
Values:
disable(0),
enable(1)
"
 ::= { psAt1  8 }

psAt1Dur OBJECT-TYPE
SYNTAX      Integer32(5..300)
MAX-ACCESS  read-write
STATUS      current
DESCRIPTION
"Alarm Contact Duration"
 ::= { psAt1  9 }

psAt1Pcr OBJECT-TYPE
SYNTAX      INTEGER {
no(0),
yes(1)
}
MAX-ACCESS  read-write
STATUS      current
DESCRIPTION
"Power Critical
Values:
no(0),
yes(1)
"
 ::= { psAt1  10 }

psAt1Pmj OBJECT-TYPE
SYNTAX      INTEGER {
no(0),
yes(1)
}
MAX-ACCESS  read-write
STATUS      current
DESCRIPTION
"Power Major
Values:
no(0),
yes(1)
"
 ::= { psAt1  11 }

psAt1Pmn OBJECT-TYPE
SYNTAX      INTEGER {
no(0),
yes(1)
}
MAX-ACCESS  read-write
STATUS      current
DESCRIPTION
"Power Minor
Values:
no(0),
yes(1)
"
 ::= { psAt1  12 }

psAt1Mjf OBJECT-TYPE
SYNTAX      INTEGER {
no(0),
yes(1)
}
MAX-ACCESS  read-write
STATUS      current
DESCRIPTION
"Major Fuse
Values:
no(0),
yes(1)
"
 ::= { psAt1  13 }

psAt1Mnf OBJECT-TYPE
SYNTAX      INTEGER {
no(0),
yes(1)
}
MAX-ACCESS  read-write
STATUS      current
DESCRIPTION
"Minor Fuse
Values:
no(0),
yes(1)
"
 ::= { psAt1  14 }

psAt1Bd OBJECT-TYPE
SYNTAX      INTEGER {
no(0),
yes(1)
}
MAX-ACCESS  read-write
STATUS      current
DESCRIPTION
"Battery on Discharge
Values:
no(0),
yes(1)
"
 ::= { psAt1  15 }

psAt1Acf OBJECT-TYPE
SYNTAX      INTEGER {
no(0),
yes(1)
}
MAX-ACCESS  read-write
STATUS      current
DESCRIPTION
"AC Fail
Values:
no(0),
yes(1)
"
 ::= { psAt1  16 }

psAt1Rfa OBJECT-TYPE
SYNTAX      INTEGER {
no(0),
yes(1)
}
MAX-ACCESS  read-write
STATUS      current
DESCRIPTION
"Rectifier Fail Alarm
Values:
no(0),
yes(1)
"
 ::= { psAt1  17 }

psAt1Hv OBJECT-TYPE
SYNTAX      INTEGER {
no(0),
yes(1)
}
MAX-ACCESS  read-write
STATUS      current
DESCRIPTION
"High Voltage
Values:
no(0),
yes(1)
"
 ::= { psAt1  18 }

psAt1Ctlr OBJECT-TYPE
SYNTAX      INTEGER {
no(0),
yes(1)
}
MAX-ACCESS  read-write
STATUS      current
DESCRIPTION
"Controller
Values:
no(0),
yes(1)
"
 ::= { psAt1  19 }

psAt1Ur1 OBJECT-TYPE
SYNTAX      INTEGER {
no(0),
yes(1)
}
MAX-ACCESS  read-write
STATUS      current
DESCRIPTION
"User Relay 1
Values:
no(0),
yes(1)
"
 ::= { psAt1  20 }

psAt1Ur2 OBJECT-TYPE
SYNTAX      INTEGER {
no(0),
yes(1)
}
MAX-ACCESS  read-write
STATUS      current
DESCRIPTION
"User Relay 2
Values:
no(0),
yes(1)
"
 ::= { psAt1  21 }

psAt1Ur3 OBJECT-TYPE
SYNTAX      INTEGER {
no(0),
yes(1)
}
MAX-ACCESS  read-write
STATUS      current
DESCRIPTION
"User Relay 3
Values:
no(0),
yes(1)
"
 ::= { psAt1  22 }

psAt1Ata OBJECT-TYPE
SYNTAX      DisplayString
MAX-ACCESS  read-only
STATUS      current
DESCRIPTION
"Alarm Test Active
Value:
Alarm report from ATA1
"
 ::= { psAt1  23 }

psAt1Atf OBJECT-TYPE
SYNTAX      DisplayString
MAX-ACCESS  read-only
STATUS      current
DESCRIPTION
"Alarm Test Failed
Value:
Alarm report from ATF1
"
 ::= { psAt1  24 }

psAt1Atb OBJECT-TYPE
SYNTAX      DisplayString
MAX-ACCESS  read-only
STATUS      current
DESCRIPTION
"Alarm Test Aborted
Value:
Alarm report from ATB1
"
 ::= { psAt1  25 }

psAt1Ems OBJECT-TYPE
SYNTAX      DisplayString
MAX-ACCESS  read-only
STATUS      current
DESCRIPTION
"Email Status"
 ::= { psAt1  26 }

psAt1Ets OBJECT-TYPE
SYNTAX      INTEGER {
inactive(0),
active(1)
}
MAX-ACCESS  read-write
STATUS      current
DESCRIPTION
"Perform Email Test
Values:
inactive(0),
active(1)
"
 ::= { psAt1  27 }

psAt1Snt OBJECT-TYPE
SYNTAX      INTEGER {
inactive(0),
active(1)
}
MAX-ACCESS  read-write
STATUS      current
DESCRIPTION
"Perform SNMP Trap Test
Values:
inactive(0),
active(1)
"
 ::= { psAt1  28 }


--
-- table TRS
--

psTrsTable    OBJECT-TYPE
SYNTAX SEQUENCE OF PsTrsEntry
MAX-ACCESS not-accessible
STATUS current
DESCRIPTION
        "Table of all Trend data"
 ::= { powerSystem  4 }

psTrsEntry OBJECT-TYPE
SYNTAX     PsTrsEntry
MAX-ACCESS  not-accessible
STATUS      current
DESCRIPTION
       "Entry of information for one Trend"
INDEX { psTrsEntryIndex }
 ::= { psTrsTable  1 }

PsTrsEntry ::= SEQUENCE {
psTrsEntryIndex   INTEGER,
psTrsEntryIde   DisplayString,
psTrsEntryDes   DisplayString,
psTrsEntrySrc   DisplayString
}

psTrsEntryIndex OBJECT-TYPE
SYNTAX      INTEGER (0..2147483647)
MAX-ACCESS  read-only
STATUS      current
DESCRIPTION
"Table Index"
 ::= { psTrsEntry  1 }

psTrsEntryIde OBJECT-TYPE
SYNTAX      DisplayString
MAX-ACCESS  read-only
STATUS      current
DESCRIPTION
"Identifier"
 ::= { psTrsEntry  2 }

psTrsEntryDes OBJECT-TYPE
SYNTAX      DisplayString
MAX-ACCESS  read-write
STATUS      current
DESCRIPTION
"Description"
 ::= { psTrsEntry  3 }

psTrsEntrySrc OBJECT-TYPE
SYNTAX      DisplayString
MAX-ACCESS  read-write
STATUS      current
DESCRIPTION
"Source"
 ::= { psTrsEntry  4 }



--
-- table BHS
--

psBhsTable    OBJECT-TYPE
SYNTAX SEQUENCE OF PsBhsEntry
MAX-ACCESS not-accessible
STATUS current
DESCRIPTION
        "Table of all Busy Hour Statistic data"
 ::= { powerSystem  5 }

psBhsEntry OBJECT-TYPE
SYNTAX     PsBhsEntry
MAX-ACCESS  not-accessible
STATUS      current
DESCRIPTION
       "Entry of information for one Busy Hour Statistic"
INDEX { psBhsEntryIndex }
 ::= { psBhsTable  1 }

PsBhsEntry ::= SEQUENCE {
psBhsEntryIndex   INTEGER,
psBhsEntryIde   DisplayString,
psBhsEntryDes   DisplayString,
psBhsEntrySrc   DisplayString,
psBhsEntrySdt   DisplayString,
psBhsEntryShr   Integer32
}

psBhsEntryIndex OBJECT-TYPE
SYNTAX      INTEGER (0..2147483647)
MAX-ACCESS  read-only
STATUS      current
DESCRIPTION
"Table Index"
 ::= { psBhsEntry  1 }

psBhsEntryIde OBJECT-TYPE
SYNTAX      DisplayString
MAX-ACCESS  read-only
STATUS      current
DESCRIPTION
"Identifier"
 ::= { psBhsEntry  2 }

psBhsEntryDes OBJECT-TYPE
SYNTAX      DisplayString
MAX-ACCESS  read-write
STATUS      current
DESCRIPTION
"Description"
 ::= { psBhsEntry  3 }

psBhsEntrySrc OBJECT-TYPE
SYNTAX      DisplayString
MAX-ACCESS  read-write
STATUS      current
DESCRIPTION
"Source"
 ::= { psBhsEntry  4 }

psBhsEntrySdt OBJECT-TYPE
SYNTAX      DisplayString
MAX-ACCESS  read-write
STATUS      current
DESCRIPTION
"Start Date"
 ::= { psBhsEntry  5 }

psBhsEntryShr OBJECT-TYPE
SYNTAX      Integer32(0..23)
MAX-ACCESS  read-write
STATUS      current
DESCRIPTION
"Start Hour"
 ::= { psBhsEntry  6 }



--
-- object psGm1
--

psGm1 OBJECT IDENTIFIER  ::= { powerSystem  6 }

psGm1Ide OBJECT-TYPE
SYNTAX      DisplayString
MAX-ACCESS  read-only
STATUS      current
DESCRIPTION
"Identifier"
 ::= { psGm1  1 }

psGm1Des OBJECT-TYPE
SYNTAX      DisplayString
MAX-ACCESS  read-write
STATUS      current
DESCRIPTION
"Description"
 ::= { psGm1  2 }

psGm1Lse OBJECT-TYPE
SYNTAX      INTEGER {
disable(0),
enable(1)
}
MAX-ACCESS  read-write
STATUS      current
DESCRIPTION
"Load Share Enable
Values:
disable(0),
enable(1)
"
 ::= { psGm1  3 }

psGm1Fsd OBJECT-TYPE
SYNTAX      Integer32(25000..60000)
MAX-ACCESS  read-write
STATUS      current
DESCRIPTION
"Float High Voltage Shutdown"
 ::= { psGm1  4 }

psGm1Bsd OBJECT-TYPE
SYNTAX      Integer32(26000..60000)
MAX-ACCESS  read-write
STATUS      current
DESCRIPTION
"Boost High Voltage Shutdown"
 ::= { psGm1  5 }

psGm1Fsp OBJECT-TYPE
SYNTAX      Integer32(22000..56000)
MAX-ACCESS  read-write
STATUS      current
DESCRIPTION
"Float Set Point"
 ::= { psGm1  6 }

psGm1Bsp OBJECT-TYPE
SYNTAX      Integer32(22000..60000)
MAX-ACCESS  read-write
STATUS      current
DESCRIPTION
"Boost Set Point"
 ::= { psGm1  7 }

psGm1Fcl OBJECT-TYPE
SYNTAX      Integer32(30..110)
MAX-ACCESS  read-write
STATUS      current
DESCRIPTION
"Float Current Limit"
 ::= { psGm1  8 }

psGm1Bcl OBJECT-TYPE
SYNTAX      Integer32(30..110)
MAX-ACCESS  read-write
STATUS      current
DESCRIPTION
"Boost Current Limit"
 ::= { psGm1  9 }

psGm1Rone OBJECT-TYPE
SYNTAX      Integer32(1..24)
MAX-ACCESS  read-write
STATUS      current
DESCRIPTION
"Rectifiers on While on Engine"
 ::= { psGm1  10 }

psGm1Rme OBJECT-TYPE
SYNTAX      INTEGER {
disable(0),
enable(1)
}
MAX-ACCESS  read-write
STATUS      current
DESCRIPTION
"Redundancy Loss Enable
Values:
disable(0),
enable(1)
"
 ::= { psGm1  11 }

psGm1Oft OBJECT-TYPE
SYNTAX      INTEGER {
disable(0),
enable(1)
}
MAX-ACCESS  read-write
STATUS      current
DESCRIPTION
"Oring Fet Test Enable
Values:
disable(0),
enable(1)
"
 ::= { psGm1  12 }

psGm1Wie OBJECT-TYPE
SYNTAX      INTEGER {
disable(0),
enable(1)
}
MAX-ACCESS  read-write
STATUS      current
DESCRIPTION
"Walk-In Enable
Values:
disable(0),
enable(1)
"
 ::= { psGm1  13 }

psGm1Nri OBJECT-TYPE
SYNTAX      DisplayString
MAX-ACCESS  read-only
STATUS      current
DESCRIPTION
"Number of Rectifiers Installed"
 ::= { psGm1  14 }


--
-- table REC
--

psRecTable    OBJECT-TYPE
SYNTAX SEQUENCE OF PsRecEntry
MAX-ACCESS not-accessible
STATUS current
DESCRIPTION
        "Table of all Rectifier data"
 ::= { powerSystem  7 }

psRecEntry OBJECT-TYPE
SYNTAX     PsRecEntry
MAX-ACCESS  not-accessible
STATUS      current
DESCRIPTION
       "Entry of information for one Rectifier"
INDEX { psRecEntryIndex }
 ::= { psRecTable  1 }

PsRecEntry ::= SEQUENCE {
psRecEntryIndex   INTEGER,
psRecEntryIde   DisplayString,
psRecEntryDes   DisplayString,
psRecEntryTyp   DisplayString,
psRecEntryAdc   DisplayString,
psRecEntryVdc   DisplayString,
psRecEntryStt   DisplayString,
psRecEntryShv   Integer32,
psRecEntryCap   DisplayString,
psRecEntryTmp   DisplayString,
psRecEntryMnt   DisplayString,
psRecEntrySeq   INTEGER,
psRecEntryOcb   DisplayString,
psRecEntryRfa   DisplayString,
psRecEntryAcf   DisplayString,
psRecEntryPha   DisplayString,
psRecEntryLca   DisplayString,
psRecEntryLsf   DisplayString,
psRecEntryMan   DisplayString,
psRecEntryErd   DisplayString,
psRecEntryEts   DisplayString,
psRecEntryRic   DisplayString,
psRecEntryHpa   DisplayString,
psRecEntryDid   DisplayString,
psRecEntryClm   DisplayString,
psRecEntryRcf   DisplayString,
psRecEntryIcb   DisplayString,
psRecEntrySn   DisplayString,
psRecEntryVac   Integer32,
psRecEntryVac1   Integer32,
psRecEntryVac2   Integer32,
psRecEntryVac3   Integer32,
psRecEntryAac   Integer32,
psRecEntryAac1   Integer32,
psRecEntryAac2   Integer32,
psRecEntryAac3   Integer32,
psRecEntrySha   Integer32,
psRecEntryRtm   DisplayString,
psRecEntryRif   DisplayString,
psRecEntryCc   DisplayString,
psRecEntryClei   DisplayString,
psRecEntrySer   DisplayString,
psRecEntryVerp   DisplayString,
psRecEntryVers   DisplayString,
psRecEntryVhav   DisplayString,
psRecEntryHav   DisplayString,
psRecEntryVlav   DisplayString,
psRecEntryLav   DisplayString,
psRecEntryRfa1   INTEGER,
psRecEntryAcf1   INTEGER,
psRecEntryPha1   INTEGER,
psRecEntryLca1   INTEGER,
psRecEntryLsf1   INTEGER,
psRecEntryMan1   INTEGER,
psRecEntryErd1   INTEGER,
psRecEntryEts1   INTEGER,
psRecEntryRic1   INTEGER,
psRecEntryHpa1   INTEGER,
psRecEntryDid1   INTEGER,
psRecEntryClm1   INTEGER,
psRecEntryRif1   INTEGER,
psRecEntryRcf1   INTEGER
}

psRecEntryIndex OBJECT-TYPE
SYNTAX      INTEGER (0..2147483647)
MAX-ACCESS  read-only
STATUS      current
DESCRIPTION
"Table Index"
 ::= { psRecEntry  1 }

psRecEntryIde OBJECT-TYPE
SYNTAX      DisplayString
MAX-ACCESS  read-only
STATUS      current
DESCRIPTION
"Identifier"
 ::= { psRecEntry  2 }

psRecEntryDes OBJECT-TYPE
SYNTAX      DisplayString
MAX-ACCESS  read-write
STATUS      current
DESCRIPTION
"Description"
 ::= { psRecEntry  3 }

psRecEntryTyp OBJECT-TYPE
SYNTAX      DisplayString
MAX-ACCESS  read-write
STATUS      current
DESCRIPTION
"Type"
 ::= { psRecEntry  4 }

psRecEntryAdc OBJECT-TYPE
SYNTAX      DisplayString
MAX-ACCESS  read-only
STATUS      current
DESCRIPTION
"DC Current"
 ::= { psRecEntry  5 }

psRecEntryVdc OBJECT-TYPE
SYNTAX      DisplayString
MAX-ACCESS  read-only
STATUS      current
DESCRIPTION
"DC Voltage"
 ::= { psRecEntry  6 }

psRecEntryStt OBJECT-TYPE
SYNTAX      DisplayString
MAX-ACCESS  read-write
STATUS      current
DESCRIPTION
"State
Values:
ON,
OFF,
STANDBY,
VACANT
"
 ::= { psRecEntry  7 }

psRecEntryShv OBJECT-TYPE
SYNTAX      Integer32(1..5000)
MAX-ACCESS  read-write
STATUS      current
DESCRIPTION
"Shunt Voltage"
 ::= { psRecEntry  8 }

psRecEntryCap OBJECT-TYPE
SYNTAX      DisplayString
MAX-ACCESS  read-only
STATUS      current
DESCRIPTION
"Capacity"
 ::= { psRecEntry  9 }

psRecEntryTmp OBJECT-TYPE
SYNTAX      DisplayString
MAX-ACCESS  read-only
STATUS      current
DESCRIPTION
"Temperature"
 ::= { psRecEntry  10 }

psRecEntryMnt OBJECT-TYPE
SYNTAX      DisplayString
MAX-ACCESS  read-write
STATUS      current
DESCRIPTION
"MAN Type
Values:
NONE,
CC,
CO
"
 ::= { psRecEntry  11 }

psRecEntrySeq OBJECT-TYPE
SYNTAX      INTEGER {
no(0),
yes(1)
}
MAX-ACCESS  read-write
STATUS      current
DESCRIPTION
"Use in Sequence Enable
Values:
no(0),
yes(1)
"
 ::= { psRecEntry  12 }

psRecEntryOcb OBJECT-TYPE
SYNTAX      DisplayString
MAX-ACCESS  read-only
STATUS      current
DESCRIPTION
"Output Breaker State"
 ::= { psRecEntry  13 }

psRecEntryRfa OBJECT-TYPE
SYNTAX      DisplayString
MAX-ACCESS  read-only
STATUS      current
DESCRIPTION
"Rectifier Fail"
 ::= { psRecEntry  14 }

psRecEntryAcf OBJECT-TYPE
SYNTAX      DisplayString
MAX-ACCESS  read-only
STATUS      current
DESCRIPTION
"AC Fail"
 ::= { psRecEntry  15 }

psRecEntryPha OBJECT-TYPE
SYNTAX      DisplayString
MAX-ACCESS  read-only
STATUS      current
DESCRIPTION
"Phase Fail or Limited Output"
 ::= { psRecEntry  16 }

psRecEntryLca OBJECT-TYPE
SYNTAX      DisplayString
MAX-ACCESS  read-only
STATUS      current
DESCRIPTION
"Low Current"
 ::= { psRecEntry  17 }

psRecEntryLsf OBJECT-TYPE
SYNTAX      DisplayString
MAX-ACCESS  read-only
STATUS      current
DESCRIPTION
"Load Share Fuse"
 ::= { psRecEntry  18 }

psRecEntryMan OBJECT-TYPE
SYNTAX      DisplayString
MAX-ACCESS  read-only
STATUS      current
DESCRIPTION
"Standby or Manual Off"
 ::= { psRecEntry  19 }

psRecEntryErd OBJECT-TYPE
SYNTAX      DisplayString
MAX-ACCESS  read-only
STATUS      current
DESCRIPTION
"Excess Rectifier Drain"
 ::= { psRecEntry  20 }

psRecEntryEts OBJECT-TYPE
SYNTAX      DisplayString
MAX-ACCESS  read-only
STATUS      current
DESCRIPTION
"External Transfer Shutdown"
 ::= { psRecEntry  21 }

psRecEntryRic OBJECT-TYPE
SYNTAX      DisplayString
MAX-ACCESS  read-only
STATUS      current
DESCRIPTION
"Rectifier Incomplete Configuration"
 ::= { psRecEntry  22 }

psRecEntryHpa OBJECT-TYPE
SYNTAX      DisplayString
MAX-ACCESS  read-only
STATUS      current
DESCRIPTION
"Half Power"
 ::= { psRecEntry  23 }

psRecEntryDid OBJECT-TYPE
SYNTAX      DisplayString
MAX-ACCESS  read-only
STATUS      current
DESCRIPTION
"ID Conflict"
 ::= { psRecEntry  24 }

psRecEntryClm OBJECT-TYPE
SYNTAX      DisplayString
MAX-ACCESS  read-only
STATUS      current
DESCRIPTION
"Current Limit"
 ::= { psRecEntry  25 }

psRecEntryRcf OBJECT-TYPE
SYNTAX      DisplayString
MAX-ACCESS  read-only
STATUS      current
DESCRIPTION
"Communication Failure"
 ::= { psRecEntry  26 }

psRecEntryIcb OBJECT-TYPE
SYNTAX      DisplayString
MAX-ACCESS  read-only
STATUS      current
DESCRIPTION
"Input Breaker State"
 ::= { psRecEntry  27 }

psRecEntrySn OBJECT-TYPE
SYNTAX      DisplayString
MAX-ACCESS  read-only
STATUS      current
DESCRIPTION
"Serial Number"
 ::= { psRecEntry  28 }

psRecEntryVac OBJECT-TYPE
SYNTAX      Integer32
UNITS       "Volts"
MAX-ACCESS  read-only
STATUS      current
DESCRIPTION
"AC Voltage (Volts)"
 ::= { psRecEntry  29 }

psRecEntryVac1 OBJECT-TYPE
SYNTAX      Integer32
UNITS       "Volts"
MAX-ACCESS  read-only
STATUS      current
DESCRIPTION
"AC Phase Voltage (Volts)"
 ::= { psRecEntry  30 }

psRecEntryVac2 OBJECT-TYPE
SYNTAX      Integer32
UNITS       "Volts"
MAX-ACCESS  read-only
STATUS      current
DESCRIPTION
"AC Phase Voltage (Volts)"
 ::= { psRecEntry  31 }

psRecEntryVac3 OBJECT-TYPE
SYNTAX      Integer32
UNITS       "Volts"
MAX-ACCESS  read-only
STATUS      current
DESCRIPTION
"AC Phase Voltage (Volts)"
 ::= { psRecEntry  32 }

psRecEntryAac OBJECT-TYPE
SYNTAX      Integer32
UNITS       "mA"
MAX-ACCESS  read-only
STATUS      current
DESCRIPTION
"AC Current (mA)"
 ::= { psRecEntry  33 }

psRecEntryAac1 OBJECT-TYPE
SYNTAX      Integer32
UNITS       "mA"
MAX-ACCESS  read-only
STATUS      current
DESCRIPTION
"AC Phase Current (mA)"
 ::= { psRecEntry  34 }

psRecEntryAac2 OBJECT-TYPE
SYNTAX      Integer32
UNITS       "mA"
MAX-ACCESS  read-only
STATUS      current
DESCRIPTION
"AC Phase Current (mA)"
 ::= { psRecEntry  35 }

psRecEntryAac3 OBJECT-TYPE
SYNTAX      Integer32
UNITS       "mA"
MAX-ACCESS  read-only
STATUS      current
DESCRIPTION
"AC Phase Current (mA)"
 ::= { psRecEntry  36 }

psRecEntrySha OBJECT-TYPE
SYNTAX      Integer32
MAX-ACCESS  read-write
STATUS      current
DESCRIPTION
"Shunt Current"
 ::= { psRecEntry  37 }

psRecEntryRtm OBJECT-TYPE
SYNTAX      DisplayString
MAX-ACCESS  read-only
STATUS      current
DESCRIPTION
"Run Time"
 ::= { psRecEntry  38 }

psRecEntryRif OBJECT-TYPE
SYNTAX      DisplayString
MAX-ACCESS  read-only
STATUS      current
DESCRIPTION
"Internal Fault"
 ::= { psRecEntry  39 }

psRecEntryCc OBJECT-TYPE
SYNTAX      DisplayString
MAX-ACCESS  read-only
STATUS      current
DESCRIPTION
"Comcode"
 ::= { psRecEntry  40 }

psRecEntryClei OBJECT-TYPE
SYNTAX      DisplayString
MAX-ACCESS  read-only
STATUS      current
DESCRIPTION
"CLEI Code"
 ::= { psRecEntry  41 }

psRecEntrySer OBJECT-TYPE
SYNTAX      DisplayString
MAX-ACCESS  read-only
STATUS      current
DESCRIPTION
"Series Number"
 ::= { psRecEntry  42 }

psRecEntryVerp OBJECT-TYPE
SYNTAX      DisplayString
MAX-ACCESS  read-only
STATUS      current
DESCRIPTION
"Primary Software Version"
 ::= { psRecEntry  43 }

psRecEntryVers OBJECT-TYPE
SYNTAX      DisplayString
MAX-ACCESS  read-only
STATUS      current
DESCRIPTION
"Secondary Software Version"
 ::= { psRecEntry  44 }

psRecEntryVhav OBJECT-TYPE
SYNTAX      DisplayString
MAX-ACCESS  read-only
STATUS      current
DESCRIPTION
"Very High AC"
 ::= { psRecEntry  45 }

psRecEntryHav OBJECT-TYPE
SYNTAX      DisplayString
MAX-ACCESS  read-only
STATUS      current
DESCRIPTION
"High AC"
 ::= { psRecEntry  46 }

psRecEntryVlav OBJECT-TYPE
SYNTAX      DisplayString
MAX-ACCESS  read-only
STATUS      current
DESCRIPTION
"Very Low AC"
 ::= { psRecEntry  47 }

psRecEntryLav OBJECT-TYPE
SYNTAX      DisplayString
MAX-ACCESS  read-only
STATUS      current
DESCRIPTION
"Low AC"
 ::= { psRecEntry  48 }

psRecEntryRfa1 OBJECT-TYPE
SYNTAX      INTEGER {
inactive(0),
active(1)
}
MAX-ACCESS  read-only
STATUS      current
DESCRIPTION
"Rectifier Fail
Values:
inactive(0),
active(1)
"
 ::= { psRecEntry  49 }

psRecEntryAcf1 OBJECT-TYPE
SYNTAX      INTEGER {
inactive(0),
active(1)
}
MAX-ACCESS  read-only
STATUS      current
DESCRIPTION
"AC Fail
Values:
inactive(0),
active(1)
"
 ::= { psRecEntry  50 }

psRecEntryPha1 OBJECT-TYPE
SYNTAX      INTEGER {
inactive(0),
active(1)
}
MAX-ACCESS  read-only
STATUS      current
DESCRIPTION
"Phase Fail or Limited Output
Values:
inactive(0),
active(1)
"
 ::= { psRecEntry  51 }

psRecEntryLca1 OBJECT-TYPE
SYNTAX      INTEGER {
inactive(0),
active(1)
}
MAX-ACCESS  read-only
STATUS      current
DESCRIPTION
"Low Current
Values:
inactive(0),
active(1)
"
 ::= { psRecEntry  52 }

psRecEntryLsf1 OBJECT-TYPE
SYNTAX      INTEGER {
inactive(0),
active(1)
}
MAX-ACCESS  read-only
STATUS      current
DESCRIPTION
"Load Share Fuse
Values:
inactive(0),
active(1)
"
 ::= { psRecEntry  53 }

psRecEntryMan1 OBJECT-TYPE
SYNTAX      INTEGER {
inactive(0),
active(1)
}
MAX-ACCESS  read-only
STATUS      current
DESCRIPTION
"Standby or Manual Off
Values:
inactive(0),
active(1)
"
 ::= { psRecEntry  54 }

psRecEntryErd1 OBJECT-TYPE
SYNTAX      INTEGER {
inactive(0),
active(1)
}
MAX-ACCESS  read-only
STATUS      current
DESCRIPTION
"Excess Rectifier Drain
Values:
inactive(0),
active(1)
"
 ::= { psRecEntry  55 }

psRecEntryEts1 OBJECT-TYPE
SYNTAX      INTEGER {
inactive(0),
active(1)
}
MAX-ACCESS  read-only
STATUS      current
DESCRIPTION
"External Transfer Shutdown
Values:
inactive(0),
active(1)
"
 ::= { psRecEntry  56 }

psRecEntryRic1 OBJECT-TYPE
SYNTAX      INTEGER {
inactive(0),
active(1)
}
MAX-ACCESS  read-only
STATUS      current
DESCRIPTION
"Rectifier Incomplete Configuration
Values:
inactive(0),
active(1)
"
 ::= { psRecEntry  57 }

psRecEntryHpa1 OBJECT-TYPE
SYNTAX      INTEGER {
inactive(0),
active(1)
}
MAX-ACCESS  read-only
STATUS      current
DESCRIPTION
"Half Power
Values:
inactive(0),
active(1)
"
 ::= { psRecEntry  58 }

psRecEntryDid1 OBJECT-TYPE
SYNTAX      INTEGER {
inactive(0),
active(1)
}
MAX-ACCESS  read-only
STATUS      current
DESCRIPTION
"ID Conflict
Values:
inactive(0),
active(1)
"
 ::= { psRecEntry  59 }

psRecEntryClm1 OBJECT-TYPE
SYNTAX      INTEGER {
inactive(0),
active(1)
}
MAX-ACCESS  read-only
STATUS      current
DESCRIPTION
"Current Limit
Values:
inactive(0),
active(1)
"
 ::= { psRecEntry  60 }

psRecEntryRif1 OBJECT-TYPE
SYNTAX      INTEGER {
inactive(0),
active(1)
}
MAX-ACCESS  read-only
STATUS      current
DESCRIPTION
"Internal Fault
Values:
inactive(0),
active(1)
"
 ::= { psRecEntry  61 }

psRecEntryRcf1 OBJECT-TYPE
SYNTAX      INTEGER {
inactive(0),
active(1)
}
MAX-ACCESS  read-only
STATUS      current
DESCRIPTION
"Communication Failure
Values:
inactive(0),
active(1)
"
 ::= { psRecEntry  62 }



--
-- table RBY
--

psRbyTable    OBJECT-TYPE
SYNTAX SEQUENCE OF PsRbyEntry
MAX-ACCESS not-accessible
STATUS current
DESCRIPTION
        "Table of all Rectifier Bay data"
 ::= { powerSystem  8 }

psRbyEntry OBJECT-TYPE
SYNTAX     PsRbyEntry
MAX-ACCESS  not-accessible
STATUS      current
DESCRIPTION
       "Entry of information for one Rectifier Bay"
INDEX { psRbyEntryIndex }
 ::= { psRbyTable  1 }

PsRbyEntry ::= SEQUENCE {
psRbyEntryIndex   INTEGER,
psRbyEntryIde   DisplayString,
psRbyEntryDes   DisplayString,
psRbyEntryTmp   DisplayString,
psRbyEntryIcb   DisplayString,
psRbyEntryRec   DisplayString
}

psRbyEntryIndex OBJECT-TYPE
SYNTAX      INTEGER (0..2147483647)
MAX-ACCESS  read-only
STATUS      current
DESCRIPTION
"Table Index"
 ::= { psRbyEntry  1 }

psRbyEntryIde OBJECT-TYPE
SYNTAX      DisplayString
MAX-ACCESS  read-only
STATUS      current
DESCRIPTION
"Identifier"
 ::= { psRbyEntry  2 }

psRbyEntryDes OBJECT-TYPE
SYNTAX      DisplayString
MAX-ACCESS  read-write
STATUS      current
DESCRIPTION
"Description"
 ::= { psRbyEntry  3 }

psRbyEntryTmp OBJECT-TYPE
SYNTAX      DisplayString
MAX-ACCESS  read-only
STATUS      current
DESCRIPTION
"Bay Temperature"
 ::= { psRbyEntry  4 }

psRbyEntryIcb OBJECT-TYPE
SYNTAX      DisplayString
MAX-ACCESS  read-only
STATUS      current
DESCRIPTION
"AC Circuit Breaker Alarm
Value:
Alarm report from linked object"
 ::= { psRbyEntry  5 }

psRbyEntryRec OBJECT-TYPE
SYNTAX      DisplayString
MAX-ACCESS  read-only
STATUS      current
DESCRIPTION
"Rectifiers"
 ::= { psRbyEntry  6 }



--
-- object psCp1
--

psCp1 OBJECT IDENTIFIER  ::= { powerSystem  9 }

psCp1Ide OBJECT-TYPE
SYNTAX      DisplayString
MAX-ACCESS  read-only
STATUS      current
DESCRIPTION
"Identifier"
 ::= { psCp1  1 }

psCp1Des OBJECT-TYPE
SYNTAX      DisplayString
MAX-ACCESS  read-write
STATUS      current
DESCRIPTION
"Description"
 ::= { psCp1  2 }

psCp1Vdc OBJECT-TYPE
SYNTAX      DisplayString
MAX-ACCESS  read-only
STATUS      current
DESCRIPTION
"DC Voltage"
 ::= { psCp1  3 }

psCp1Adc OBJECT-TYPE
SYNTAX      DisplayString
MAX-ACCESS  read-only
STATUS      current
DESCRIPTION
"DC Current"
 ::= { psCp1  4 }

psCp1Cap OBJECT-TYPE
SYNTAX      DisplayString
MAX-ACCESS  read-only
STATUS      current
DESCRIPTION
"Capacity"
 ::= { psCp1  5 }

psCp1Vsp OBJECT-TYPE
SYNTAX      Integer32(22000..55000)
MAX-ACCESS  read-write
STATUS      current
DESCRIPTION
"Voltage Set Point"
 ::= { psCp1  6 }

psCp1Dth OBJECT-TYPE
SYNTAX      Integer32(20000..50000)
MAX-ACCESS  read-write
STATUS      current
DESCRIPTION
"Low Voltage Disconnect"
 ::= { psCp1  7 }

psCp1Rth OBJECT-TYPE
SYNTAX      Integer32(22000..54000)
MAX-ACCESS  read-write
STATUS      current
DESCRIPTION
"Low Voltage Reconnect"
 ::= { psCp1  8 }

psCp1Lvd OBJECT-TYPE
SYNTAX      INTEGER {
disable(0),
enable(1)
}
MAX-ACCESS  read-write
STATUS      current
DESCRIPTION
"Low Voltage Disconnect Enable
Values:
disable(0),
enable(1)
"
 ::= { psCp1  9 }

psCp1Cfa OBJECT-TYPE
SYNTAX      DisplayString
MAX-ACCESS  read-only
STATUS      current
DESCRIPTION
"Converter Fail
Value:
Alarm report from CFA1
"
 ::= { psCp1  10 }

psCp1Dfa OBJECT-TYPE
SYNTAX      DisplayString
MAX-ACCESS  read-only
STATUS      current
DESCRIPTION
"Distribution Fail
Value:
Alarm report from CDFA1
"
 ::= { psCp1  11 }

psCp1Did OBJECT-TYPE
SYNTAX      DisplayString
MAX-ACCESS  read-only
STATUS      current
DESCRIPTION
"ID Conflict
Value:
Alarm report from CDID1
"
 ::= { psCp1  12 }

psCp1Mfa OBJECT-TYPE
SYNTAX      DisplayString
MAX-ACCESS  read-only
STATUS      current
DESCRIPTION
"Multiple Converter Fail
Value:
Alarm report from CMFA1
"
 ::= { psCp1  13 }

psCp1Olcap OBJECT-TYPE
SYNTAX      DisplayString
MAX-ACCESS  read-only
STATUS      current
DESCRIPTION
"Online Capacity"
 ::= { psCp1  14 }

psCp1Vsd OBJECT-TYPE
SYNTAX      Integer32(25000..60000)
MAX-ACCESS  read-write
STATUS      current
DESCRIPTION
"High Voltage Shutdown"
 ::= { psCp1  15 }

psCp1Rof OBJECT-TYPE
SYNTAX      INTEGER {
disable(0),
enable(1)
}
MAX-ACCESS  read-write
STATUS      current
DESCRIPTION
"Remote Converter Off
Values:
disable(0),
enable(1)
"
 ::= { psCp1  16 }

psCp1Rme OBJECT-TYPE
SYNTAX      INTEGER {
disable(0),
enable(1)
}
MAX-ACCESS  read-write
STATUS      current
DESCRIPTION
"Redundancy Loss
Values:
disable(0),
enable(1)
"
 ::= { psCp1  17 }

psCp1Rss OBJECT-TYPE
SYNTAX      INTEGER {
off(0),
on(1)
}
MAX-ACCESS  read-write
STATUS      current
DESCRIPTION
"Converter Restart
Values:
off(0),
on(1)
"
 ::= { psCp1  18 }

psCp1Clm OBJECT-TYPE
SYNTAX      Integer32(30..100)
MAX-ACCESS  read-write
STATUS      current
DESCRIPTION
"Current Limit"
 ::= { psCp1  19 }

psCp1Cfn OBJECT-TYPE
SYNTAX      DisplayString
MAX-ACCESS  read-only
STATUS      current
DESCRIPTION
"Converter Fan Minor
Value:
Alarm report from CFN1
"
 ::= { psCp1  20 }

psCp1Cfj OBJECT-TYPE
SYNTAX      DisplayString
MAX-ACCESS  read-only
STATUS      current
DESCRIPTION
"Converter Fan Major
Value:
Alarm report from CFJ1
"
 ::= { psCp1  21 }

psCp1Icc OBJECT-TYPE
SYNTAX      DisplayString
MAX-ACCESS  read-only
STATUS      current
DESCRIPTION
"Incompatible Converter
Value:
Alarm report from ICC1
"
 ::= { psCp1  22 }

psCp1Hfv OBJECT-TYPE
SYNTAX      DisplayString
MAX-ACCESS  read-only
STATUS      current
DESCRIPTION
"Converter High Voltage Minor
Value:
Alarm report from CHFV1
"
 ::= { psCp1  23 }

psCp1Hva OBJECT-TYPE
SYNTAX      DisplayString
MAX-ACCESS  read-only
STATUS      current
DESCRIPTION
"Converter High Voltage Major
Value:
Alarm report from CHVA1
"
 ::= { psCp1  24 }

psCp1Vla OBJECT-TYPE
SYNTAX      DisplayString
MAX-ACCESS  read-only
STATUS      current
DESCRIPTION
"Converter Low Voltage Alarm
Value:
Alarm report from CVLA1
"
 ::= { psCp1  25 }

psCp1Rl OBJECT-TYPE
SYNTAX      DisplayString
MAX-ACCESS  read-only
STATUS      current
DESCRIPTION
"Converter Redundancy Loss
Value:
Alarm report from CRL1
"
 ::= { psCp1  26 }

psCp1Typ OBJECT-TYPE
SYNTAX      DisplayString
MAX-ACCESS  read-only
STATUS      current
DESCRIPTION
"Type"
 ::= { psCp1  27 }

psCp1Cin OBJECT-TYPE
SYNTAX      DisplayString
MAX-ACCESS  read-only
STATUS      current
DESCRIPTION
"Converter Input Fail
Value:
Alarm report from CIN1
"
 ::= { psCp1  28 }

psCp1Nci OBJECT-TYPE
SYNTAX      DisplayString
MAX-ACCESS  read-only
STATUS      current
DESCRIPTION
"Number of Converters Installed"
 ::= { psCp1  29 }


--
-- table DCC
--

psDccTable    OBJECT-TYPE
SYNTAX SEQUENCE OF PsDccEntry
MAX-ACCESS not-accessible
STATUS current
DESCRIPTION
        "Table of all Converter data"
 ::= { powerSystem  10 }

psDccEntry OBJECT-TYPE
SYNTAX     PsDccEntry
MAX-ACCESS  not-accessible
STATUS      current
DESCRIPTION
       "Entry of information for one Converter"
INDEX { psDccEntryIndex }
 ::= { psDccTable  1 }

PsDccEntry ::= SEQUENCE {
psDccEntryIndex   INTEGER,
psDccEntryIde   DisplayString,
psDccEntryDes   DisplayString,
psDccEntryTyp   DisplayString,
psDccEntryAdc   DisplayString,
psDccEntryCap   DisplayString,
psDccEntryStt   DisplayString,
psDccEntryCfa   DisplayString,
psDccEntryDfa   DisplayString,
psDccEntryDid   DisplayString,
psDccEntryCcf   DisplayString,
psDccEntrySn   DisplayString,
psDccEntryCfn   DisplayString,
psDccEntryCfj   DisplayString
}

psDccEntryIndex OBJECT-TYPE
SYNTAX      INTEGER (0..2147483647)
MAX-ACCESS  read-only
STATUS      current
DESCRIPTION
"Table Index"
 ::= { psDccEntry  1 }

psDccEntryIde OBJECT-TYPE
SYNTAX      DisplayString
MAX-ACCESS  read-only
STATUS      current
DESCRIPTION
"Identifier"
 ::= { psDccEntry  2 }

psDccEntryDes OBJECT-TYPE
SYNTAX      DisplayString
MAX-ACCESS  read-write
STATUS      current
DESCRIPTION
"Description"
 ::= { psDccEntry  3 }

psDccEntryTyp OBJECT-TYPE
SYNTAX      DisplayString
MAX-ACCESS  read-only
STATUS      current
DESCRIPTION
"Type"
 ::= { psDccEntry  4 }

psDccEntryAdc OBJECT-TYPE
SYNTAX      DisplayString
MAX-ACCESS  read-only
STATUS      current
DESCRIPTION
"DC Current"
 ::= { psDccEntry  5 }

psDccEntryCap OBJECT-TYPE
SYNTAX      DisplayString
MAX-ACCESS  read-only
STATUS      current
DESCRIPTION
"Capacity"
 ::= { psDccEntry  6 }

psDccEntryStt OBJECT-TYPE
SYNTAX      DisplayString
MAX-ACCESS  read-write
STATUS      current
DESCRIPTION
"State
Values:
ON,
OFF,
STANDBY,
VACANT
"
 ::= { psDccEntry  7 }

psDccEntryCfa OBJECT-TYPE
SYNTAX      DisplayString
MAX-ACCESS  read-only
STATUS      current
DESCRIPTION
"Converter Fail"
 ::= { psDccEntry  8 }

psDccEntryDfa OBJECT-TYPE
SYNTAX      DisplayString
MAX-ACCESS  read-only
STATUS      current
DESCRIPTION
"Distribution Fuse Fail"
 ::= { psDccEntry  9 }

psDccEntryDid OBJECT-TYPE
SYNTAX      DisplayString
MAX-ACCESS  read-only
STATUS      current
DESCRIPTION
"ID Conflict"
 ::= { psDccEntry  10 }

psDccEntryCcf OBJECT-TYPE
SYNTAX      DisplayString
MAX-ACCESS  read-only
STATUS      current
DESCRIPTION
"Communication Failure"
 ::= { psDccEntry  11 }

psDccEntrySn OBJECT-TYPE
SYNTAX      DisplayString
MAX-ACCESS  read-only
STATUS      current
DESCRIPTION
"Serial Number"
 ::= { psDccEntry  12 }

psDccEntryCfn OBJECT-TYPE
SYNTAX      DisplayString
MAX-ACCESS  read-only
STATUS      current
DESCRIPTION
"Fan Minor"
 ::= { psDccEntry  13 }

psDccEntryCfj OBJECT-TYPE
SYNTAX      DisplayString
MAX-ACCESS  read-only
STATUS      current
DESCRIPTION
"Fan Major"
 ::= { psDccEntry  14 }



--
-- object psBs1
--

psBs1 OBJECT IDENTIFIER  ::= { powerSystem  11 }

psBs1Ide OBJECT-TYPE
SYNTAX      DisplayString
MAX-ACCESS  read-only
STATUS      current
DESCRIPTION
"Identifier"
 ::= { psBs1  1 }

psBs1Des OBJECT-TYPE
SYNTAX      DisplayString
MAX-ACCESS  read-write
STATUS      current
DESCRIPTION
"Description"
 ::= { psBs1  2 }

psBs1Stt OBJECT-TYPE
SYNTAX      DisplayString
MAX-ACCESS  read-only
STATUS      current
DESCRIPTION
"State
Values:
QRCT,
MANUAL,
BTP,
TIMED AUTO,
OFF
"
 ::= { psBs1  3 }

psBs1Bse OBJECT-TYPE
SYNTAX      INTEGER {
disable(0),
enable(1)
}
MAX-ACCESS  read-write
STATUS      current
DESCRIPTION
"Boost Enable
Values:
disable(0),
enable(1)
"
 ::= { psBs1  4 }

psBs1Tbe OBJECT-TYPE
SYNTAX      INTEGER {
disable(0),
enable(1)
}
MAX-ACCESS  read-write
STATUS      current
DESCRIPTION
"External Timer Boost Enable
Values:
disable(0),
enable(1)
"
 ::= { psBs1  5 }

psBs1Btp OBJECT-TYPE
SYNTAX      INTEGER {
disable(0),
enable(1)
}
MAX-ACCESS  read-write
STATUS      current
DESCRIPTION
"Battery Thermal Protect Enable
Values:
disable(0),
enable(1)
"
 ::= { psBs1  6 }

psBs1Abe OBJECT-TYPE
SYNTAX      INTEGER {
disable(0),
enable(1)
}
MAX-ACCESS  read-write
STATUS      current
DESCRIPTION
"Auto Boost Enable
Values:
disable(0),
enable(1)
"
 ::= { psBs1  7 }

psBs1Atm OBJECT-TYPE
SYNTAX      DisplayString
MAX-ACCESS  read-write
STATUS      current
DESCRIPTION
"Auto Mode
Values:
OFF,
QRCT,
TIMED
"
 ::= { psBs1  8 }

psBs1Tmd OBJECT-TYPE
SYNTAX      Integer32(1..80)
MAX-ACCESS  read-write
STATUS      current
DESCRIPTION
"Timed Manual Duration"
 ::= { psBs1  9 }

psBs1Amf OBJECT-TYPE
SYNTAX      Integer32(1..9)
MAX-ACCESS  read-write
STATUS      current
DESCRIPTION
"Auto Multiplication Factor"
 ::= { psBs1  10 }

psBs1Ctv OBJECT-TYPE
SYNTAX      Integer32(20000..60000)
MAX-ACCESS  read-write
STATUS      current
DESCRIPTION
"Current Terminated Voltage Threshold"
 ::= { psBs1  11 }

psBs1Cta OBJECT-TYPE
SYNTAX      Integer32(0..100)
MAX-ACCESS  read-write
STATUS      current
DESCRIPTION
"Current Terminated Current Threshold"
 ::= { psBs1  12 }

psBs1Ctr OBJECT-TYPE
SYNTAX      Integer32(0..100)
MAX-ACCESS  read-write
STATUS      current
DESCRIPTION
"Current vs Time Ratio"
 ::= { psBs1  13 }

psBs1Bsa OBJECT-TYPE
SYNTAX      DisplayString
MAX-ACCESS  read-only
STATUS      current
DESCRIPTION
"Boost State Alarm
Value:
Alarm report from linked object"
 ::= { psBs1  14 }

psBs1Bdt OBJECT-TYPE
SYNTAX      DisplayString
MAX-ACCESS  read-write
STATUS      current
DESCRIPTION
"Minimum BD Duration for Auto Boost"
 ::= { psBs1  15 }


--
-- object psSc1
--

psSc1 OBJECT IDENTIFIER  ::= { powerSystem  12 }

psSc1Ide OBJECT-TYPE
SYNTAX      DisplayString
MAX-ACCESS  read-only
STATUS      current
DESCRIPTION
"Identifier"
 ::= { psSc1  1 }

psSc1Des OBJECT-TYPE
SYNTAX      DisplayString
MAX-ACCESS  read-write
STATUS      current
DESCRIPTION
"Description"
 ::= { psSc1  2 }

psSc1Stt OBJECT-TYPE
SYNTAX      INTEGER {
disable(0),
enable(1)
}
MAX-ACCESS  read-write
STATUS      current
DESCRIPTION
"State
Values:
disable(0),
enable(1)
"
 ::= { psSc1  3 }

psSc1Rve OBJECT-TYPE
SYNTAX      INTEGER {
disable(0),
enable(1)
}
MAX-ACCESS  read-write
STATUS      current
DESCRIPTION
"Raise Voltage Enable
Values:
disable(0),
enable(1)
"
 ::= { psSc1  4 }

psSc1Ltt OBJECT-TYPE
SYNTAX      Integer32
MAX-ACCESS  read-write
STATUS      current
DESCRIPTION
"Lower Temperature Threshold"
 ::= { psSc1  5 }

psSc1Ntt OBJECT-TYPE
SYNTAX      Integer32
MAX-ACCESS  read-write
STATUS      current
DESCRIPTION
"Nominal Temperature Threshold"
 ::= { psSc1  6 }

psSc1Utt OBJECT-TYPE
SYNTAX      Integer32
MAX-ACCESS  read-write
STATUS      current
DESCRIPTION
"Upper Temperature Threshold"
 ::= { psSc1  7 }

psSc1Spt OBJECT-TYPE
SYNTAX      Integer32
MAX-ACCESS  read-write
STATUS      current
DESCRIPTION
"Step Temperature"
 ::= { psSc1  8 }

psSc1Lsp OBJECT-TYPE
SYNTAX      Integer32
MAX-ACCESS  read-write
STATUS      current
DESCRIPTION
"Lower Temperature Slope/Cell"
 ::= { psSc1  9 }

psSc1Usp OBJECT-TYPE
SYNTAX      Integer32
MAX-ACCESS  read-write
STATUS      current
DESCRIPTION
"Upper Temperature Slope/Cell"
 ::= { psSc1  10 }

psSc1Fse OBJECT-TYPE
SYNTAX      INTEGER {
disable(0),
enable(1)
}
MAX-ACCESS  read-write
STATUS      current
DESCRIPTION
"Fail Safe Enable
Values:
disable(0),
enable(1)
"
 ::= { psSc1  11 }


--
-- table BTD
--

psBtdTable    OBJECT-TYPE
SYNTAX SEQUENCE OF PsBtdEntry
MAX-ACCESS not-accessible
STATUS current
DESCRIPTION
        "Table of all Battery Type Definition data"
 ::= { powerSystem  13 }

psBtdEntry OBJECT-TYPE
SYNTAX     PsBtdEntry
MAX-ACCESS  not-accessible
STATUS      current
DESCRIPTION
       "Entry of information for one Battery Type Definition"
INDEX { psBtdEntryIndex }
 ::= { psBtdTable  1 }

PsBtdEntry ::= SEQUENCE {
psBtdEntryIndex   INTEGER,
psBtdEntryIde   DisplayString,
psBtdEntryDes   DisplayString,
psBtdEntryBty   DisplayString,
psBtdEntryBtc   DisplayString,
psBtdEntryCap   DisplayString,
psBtdEntryD01   DisplayString,
psBtdEntryD02   DisplayString,
psBtdEntryD03   DisplayString,
psBtdEntryD04   DisplayString,
psBtdEntryD05   DisplayString,
psBtdEntryD06   DisplayString,
psBtdEntryD07   DisplayString,
psBtdEntryD08   DisplayString,
psBtdEntryD09   DisplayString,
psBtdEntryD10   DisplayString,
psBtdEntryD11   DisplayString,
psBtdEntryD12   DisplayString,
psBtdEntryD13   DisplayString,
psBtdEntryD14   DisplayString,
psBtdEntryD15   DisplayString,
psBtdEntryD16   DisplayString,
psBtdEntryD17   DisplayString,
psBtdEntryFrm   DisplayString,
psBtdEntryLev   DisplayString,
psBtdEntryHev   DisplayString,
psBtdEntryLtm   DisplayString,
psBtdEntryHtm   DisplayString
}

psBtdEntryIndex OBJECT-TYPE
SYNTAX      INTEGER (0..2147483647)
MAX-ACCESS  read-only
STATUS      current
DESCRIPTION
"Table Index"
 ::= { psBtdEntry  1 }

psBtdEntryIde OBJECT-TYPE
SYNTAX      DisplayString
MAX-ACCESS  read-only
STATUS      current
DESCRIPTION
"Identifier"
 ::= { psBtdEntry  2 }

psBtdEntryDes OBJECT-TYPE
SYNTAX      DisplayString
MAX-ACCESS  read-write
STATUS      current
DESCRIPTION
"Description"
 ::= { psBtdEntry  3 }

psBtdEntryBty OBJECT-TYPE
SYNTAX      DisplayString
MAX-ACCESS  read-write
STATUS      current
DESCRIPTION
"Battery Type"
 ::= { psBtdEntry  4 }

psBtdEntryBtc OBJECT-TYPE
SYNTAX      DisplayString
MAX-ACCESS  read-write
STATUS      current
DESCRIPTION
"Battery Class
Values:
FLOODED,
SEALED
"
 ::= { psBtdEntry  5 }

psBtdEntryCap OBJECT-TYPE
SYNTAX      DisplayString
MAX-ACCESS  read-write
STATUS      current
DESCRIPTION
"Capacity"
 ::= { psBtdEntry  6 }

psBtdEntryD01 OBJECT-TYPE
SYNTAX      DisplayString
MAX-ACCESS  read-write
STATUS      current
DESCRIPTION
"Parameter 1"
 ::= { psBtdEntry  7 }

psBtdEntryD02 OBJECT-TYPE
SYNTAX      DisplayString
MAX-ACCESS  read-write
STATUS      current
DESCRIPTION
"Parameter 2"
 ::= { psBtdEntry  8 }

psBtdEntryD03 OBJECT-TYPE
SYNTAX      DisplayString
MAX-ACCESS  read-write
STATUS      current
DESCRIPTION
"Parameter 3"
 ::= { psBtdEntry  9 }

psBtdEntryD04 OBJECT-TYPE
SYNTAX      DisplayString
MAX-ACCESS  read-write
STATUS      current
DESCRIPTION
"Parameter 4"
 ::= { psBtdEntry  10 }

psBtdEntryD05 OBJECT-TYPE
SYNTAX      DisplayString
MAX-ACCESS  read-write
STATUS      current
DESCRIPTION
"Parameter 5"
 ::= { psBtdEntry  11 }

psBtdEntryD06 OBJECT-TYPE
SYNTAX      DisplayString
MAX-ACCESS  read-write
STATUS      current
DESCRIPTION
"Parameter 6"
 ::= { psBtdEntry  12 }

psBtdEntryD07 OBJECT-TYPE
SYNTAX      DisplayString
MAX-ACCESS  read-write
STATUS      current
DESCRIPTION
"Parameter 7"
 ::= { psBtdEntry  13 }

psBtdEntryD08 OBJECT-TYPE
SYNTAX      DisplayString
MAX-ACCESS  read-write
STATUS      current
DESCRIPTION
"Parameter 8"
 ::= { psBtdEntry  14 }

psBtdEntryD09 OBJECT-TYPE
SYNTAX      DisplayString
MAX-ACCESS  read-write
STATUS      current
DESCRIPTION
"Parameter 9"
 ::= { psBtdEntry  15 }

psBtdEntryD10 OBJECT-TYPE
SYNTAX      DisplayString
MAX-ACCESS  read-write
STATUS      current
DESCRIPTION
"Parameter 10"
 ::= { psBtdEntry  16 }

psBtdEntryD11 OBJECT-TYPE
SYNTAX      DisplayString
MAX-ACCESS  read-write
STATUS      current
DESCRIPTION
"Parameter 11"
 ::= { psBtdEntry  17 }

psBtdEntryD12 OBJECT-TYPE
SYNTAX      DisplayString
MAX-ACCESS  read-write
STATUS      current
DESCRIPTION
"Parameter 12"
 ::= { psBtdEntry  18 }

psBtdEntryD13 OBJECT-TYPE
SYNTAX      DisplayString
MAX-ACCESS  read-write
STATUS      current
DESCRIPTION
"Parameter 13"
 ::= { psBtdEntry  19 }

psBtdEntryD14 OBJECT-TYPE
SYNTAX      DisplayString
MAX-ACCESS  read-write
STATUS      current
DESCRIPTION
"Parameter 14"
 ::= { psBtdEntry  20 }

psBtdEntryD15 OBJECT-TYPE
SYNTAX      DisplayString
MAX-ACCESS  read-write
STATUS      current
DESCRIPTION
"Parameter 15"
 ::= { psBtdEntry  21 }

psBtdEntryD16 OBJECT-TYPE
SYNTAX      DisplayString
MAX-ACCESS  read-write
STATUS      current
DESCRIPTION
"Parameter 16"
 ::= { psBtdEntry  22 }

psBtdEntryD17 OBJECT-TYPE
SYNTAX      DisplayString
MAX-ACCESS  read-write
STATUS      current
DESCRIPTION
"Parameter 17"
 ::= { psBtdEntry  23 }

psBtdEntryFrm OBJECT-TYPE
SYNTAX      DisplayString
MAX-ACCESS  read-write
STATUS      current
DESCRIPTION
"Formula Number"
 ::= { psBtdEntry  24 }

psBtdEntryLev OBJECT-TYPE
SYNTAX      DisplayString
MAX-ACCESS  read-write
STATUS      current
DESCRIPTION
"Lower End Volts"
 ::= { psBtdEntry  25 }

psBtdEntryHev OBJECT-TYPE
SYNTAX      DisplayString
MAX-ACCESS  read-write
STATUS      current
DESCRIPTION
"Higher End Volts"
 ::= { psBtdEntry  26 }

psBtdEntryLtm OBJECT-TYPE
SYNTAX      DisplayString
MAX-ACCESS  read-write
STATUS      current
DESCRIPTION
"Lower Time"
 ::= { psBtdEntry  27 }

psBtdEntryHtm OBJECT-TYPE
SYNTAX      DisplayString
MAX-ACCESS  read-write
STATUS      current
DESCRIPTION
"Higher Time"
 ::= { psBtdEntry  28 }



--
-- object psBr1
--

psBr1 OBJECT IDENTIFIER  ::= { powerSystem  14 }

psBr1Ide OBJECT-TYPE
SYNTAX      DisplayString
MAX-ACCESS  read-only
STATUS      current
DESCRIPTION
"Identifier"
 ::= { psBr1  1 }

psBr1Des OBJECT-TYPE
SYNTAX      DisplayString
MAX-ACCESS  read-write
STATUS      current
DESCRIPTION
"Description"
 ::= { psBr1  2 }

psBr1Tth OBJECT-TYPE
SYNTAX      Integer32(30..194)
MAX-ACCESS  read-write
STATUS      current
DESCRIPTION
"High Temperature Threshold"
 ::= { psBr1  3 }

psBr1Cle OBJECT-TYPE
SYNTAX      INTEGER {
disable(0),
enable(1)
}
MAX-ACCESS  read-write
STATUS      current
DESCRIPTION
"Current Limit Enable
Values:
disable(0),
enable(1)
"
 ::= { psBr1  4 }

psBr1Clt OBJECT-TYPE
SYNTAX      Integer32(10..1000)
MAX-ACCESS  read-write
STATUS      current
DESCRIPTION
"Current Limit Threshold"
 ::= { psBr1  5 }

psBr1Cev OBJECT-TYPE
SYNTAX      Integer32(1750..1950)
MAX-ACCESS  read-write
STATUS      current
DESCRIPTION
"End Volts per Cell"
 ::= { psBr1  6 }

psBr1Btc OBJECT-TYPE
SYNTAX      DisplayString
MAX-ACCESS  read-write
STATUS      current
DESCRIPTION
"Battery Test Class
Values:
FLOODED,
SEALED
"
 ::= { psBr1  7 }

psBr1Bts OBJECT-TYPE
SYNTAX      INTEGER {
inactive(0),
active(1)
}
MAX-ACCESS  read-write
STATUS      current
DESCRIPTION
"Battery Test State
Values:
inactive(0),
active(1)
"
 ::= { psBr1  8 }

psBr1Bte OBJECT-TYPE
SYNTAX      DisplayString
MAX-ACCESS  read-write
STATUS      current
DESCRIPTION
"Automatic Test Type
Values:
DISABLE,
20%,
TIMED
"
 ::= { psBr1  9 }

psBr1Btr OBJECT-TYPE
SYNTAX      DisplayString
MAX-ACCESS  read-only
STATUS      current
DESCRIPTION
"Battery Test Results"
 ::= { psBr1  10 }

psBr1Epe OBJECT-TYPE
SYNTAX      INTEGER {
disable(0),
enable(1)
}
MAX-ACCESS  read-write
STATUS      current
DESCRIPTION
"Enhanced Prediction Enable
Values:
disable(0),
enable(1)
"
 ::= { psBr1  11 }

psBr1Bta OBJECT-TYPE
SYNTAX      DisplayString
MAX-ACCESS  read-only
STATUS      current
DESCRIPTION
"Battery Test Active
Value:
Alarm report from BTA1
"
 ::= { psBr1  12 }

psBr1Bfa OBJECT-TYPE
SYNTAX      DisplayString
MAX-ACCESS  read-only
STATUS      current
DESCRIPTION
"Battery Test Failed
Value:
Alarm report from BFA1
"
 ::= { psBr1  13 }

psBr1Bca OBJECT-TYPE
SYNTAX      DisplayString
MAX-ACCESS  read-only
STATUS      current
DESCRIPTION
"Battery Type Conflict
Value:
Alarm report from BCA1
"
 ::= { psBr1  14 }

psBr1Adc OBJECT-TYPE
SYNTAX      DisplayString
MAX-ACCESS  read-only
STATUS      current
DESCRIPTION
"Battery Type Conflict"
 ::= { psBr1  15 }

psBr1Cap OBJECT-TYPE
SYNTAX      DisplayString
UNITS       "Amps"
MAX-ACCESS  read-only
STATUS      current
DESCRIPTION
"Installed Battery Capacity (Amps)"
 ::= { psBr1  16 }

psBr1Olcap OBJECT-TYPE
SYNTAX      DisplayString
UNITS       "Amps"
MAX-ACCESS  read-only
STATUS      current
DESCRIPTION
"Online Battery Capacity (Amps)"
 ::= { psBr1  17 }

psBr1Hbt OBJECT-TYPE
SYNTAX      DisplayString
MAX-ACCESS  read-only
STATUS      current
DESCRIPTION
"Highest Battery Temperature"
 ::= { psBr1  18 }

psBr1Nvm OBJECT-TYPE
SYNTAX      DisplayString
MAX-ACCESS  read-only
STATUS      current
DESCRIPTION
"Number of Voltage Modules"
 ::= { psBr1  19 }

psBr1Ntm OBJECT-TYPE
SYNTAX      DisplayString
MAX-ACCESS  read-only
STATUS      current
DESCRIPTION
"Number of Temperature Modules"
 ::= { psBr1  20 }

psBr1Scd OBJECT-TYPE
SYNTAX      INTEGER {
disable(0),
enable(1)
}
MAX-ACCESS  read-write
STATUS      current
DESCRIPTION
"Shorted Cell Detection
Values:
disable(0),
enable(1)
"
 ::= { psBr1  21 }

psBr1Scv OBJECT-TYPE
SYNTAX      Integer32(1500..3000)
UNITS       "Volts"
MAX-ACCESS  read-write
STATUS      current
DESCRIPTION
"Shorted Cell Threshold (Volts)"
 ::= { psBr1  22 }

psBr1Ath OBJECT-TYPE
SYNTAX      Integer32(0..23)
MAX-ACCESS  read-write
STATUS      current
DESCRIPTION
"Auto Test Run Hour"
 ::= { psBr1  23 }

psBr1Atd OBJECT-TYPE
SYNTAX      DisplayString
MAX-ACCESS  read-write
STATUS      current
DESCRIPTION
"Auto Test Date"
 ::= { psBr1  24 }

psBr1Atw OBJECT-TYPE
SYNTAX      Integer32(0..240)
MAX-ACCESS  read-write
STATUS      current
DESCRIPTION
"Auto Test Minimum Hours after BD"
 ::= { psBr1  25 }

psBr1Btv OBJECT-TYPE
SYNTAX      Integer32(21000..52000)
MAX-ACCESS  read-write
STATUS      current
DESCRIPTION
"Battery Test Rectifier Voltage"
 ::= { psBr1  26 }

psBr1Tin OBJECT-TYPE
SYNTAX      Integer32(1..18)
UNITS       "Months"
MAX-ACCESS  read-write
STATUS      current
DESCRIPTION
"Auto Test Interval (Months)"
 ::= { psBr1  27 }

psBr1Tmd OBJECT-TYPE
SYNTAX      DisplayString
MAX-ACCESS  read-write
STATUS      current
DESCRIPTION
"Manual Test Duration"
 ::= { psBr1  28 }

psBr1Tev OBJECT-TYPE
SYNTAX      Integer32(36000..48000)
UNITS       "mV"
MAX-ACCESS  read-write
STATUS      current
DESCRIPTION
"Manual Test Alarm Voltage (mV)"
 ::= { psBr1  29 }

psBr1Mtt OBJECT-TYPE
SYNTAX      DisplayString
MAX-ACCESS  read-write
STATUS      current
DESCRIPTION
"Manual Test Type
Values:
DISABLE,
20%,
TIMED
"
 ::= { psBr1  30 }

psBr1Scda OBJECT-TYPE
SYNTAX      DisplayString
MAX-ACCESS  read-only
STATUS      current
DESCRIPTION
"Shorted Cell Detected
Value:
Alarm report from SCD1
"
 ::= { psBr1  31 }

psBr1Isda OBJECT-TYPE
SYNTAX      DisplayString
MAX-ACCESS  read-only
STATUS      current
DESCRIPTION
"Imminent Low Voltage Shutdown
Value:
Alarm report from ISD1
"
 ::= { psBr1  32 }

psBr1Mdp OBJECT-TYPE
SYNTAX      DisplayString
MAX-ACCESS  read-only
STATUS      current
DESCRIPTION
"Voltage Module Duplicate ID
Value:
Alarm report from MDP1
"
 ::= { psBr1  33 }

psBr1Mzd OBJECT-TYPE
SYNTAX      DisplayString
MAX-ACCESS  read-only
STATUS      current
DESCRIPTION
"Voltage Module Zero ID
Value:
Alarm report from MZD1
"
 ::= { psBr1  34 }

psBr1Btha OBJECT-TYPE
SYNTAX      DisplayString
MAX-ACCESS  read-only
STATUS      current
DESCRIPTION
"High Battery Temperature
Value:
Alarm report from BTHA1
"
 ::= { psBr1  35 }

psBr1Lbt OBJECT-TYPE
SYNTAX      DisplayString
MAX-ACCESS  read-only
STATUS      current
DESCRIPTION
"Lowest Battery Temperature"
 ::= { psBr1  36 }

psBr1Btla OBJECT-TYPE
SYNTAX      DisplayString
MAX-ACCESS  read-only
STATUS      current
DESCRIPTION
"Low Battery Temperature
Value:
Alarm report from BTLA1
"
 ::= { psBr1  37 }

psBr1Btvh OBJECT-TYPE
SYNTAX      DisplayString
MAX-ACCESS  read-only
STATUS      current
DESCRIPTION
"Very High Battery Temperature
Value:
Alarm report from BTVH1
"
 ::= { psBr1  38 }

psBr1Btvl OBJECT-TYPE
SYNTAX      DisplayString
MAX-ACCESS  read-only
STATUS      current
DESCRIPTION
"Very Low Battery Temperature
Value:
Alarm report from BTVL1
"
 ::= { psBr1  39 }


--
-- table BBY
--

psBbyTable    OBJECT-TYPE
SYNTAX SEQUENCE OF PsBbyEntry
MAX-ACCESS not-accessible
STATUS current
DESCRIPTION
        "Table of all Battery Bay data"
 ::= { powerSystem  15 }

psBbyEntry OBJECT-TYPE
SYNTAX     PsBbyEntry
MAX-ACCESS  not-accessible
STATUS      current
DESCRIPTION
       "Entry of information for one Battery Bay"
INDEX { psBbyEntryIndex }
 ::= { psBbyTable  1 }

PsBbyEntry ::= SEQUENCE {
psBbyEntryIndex   INTEGER,
psBbyEntryIde   DisplayString,
psBbyEntryDes   DisplayString,
psBbyEntryTmp   DisplayString,
psBbyEntryBat   DisplayString
}

psBbyEntryIndex OBJECT-TYPE
SYNTAX      INTEGER (0..2147483647)
MAX-ACCESS  read-only
STATUS      current
DESCRIPTION
"Table Index"
 ::= { psBbyEntry  1 }

psBbyEntryIde OBJECT-TYPE
SYNTAX      DisplayString
MAX-ACCESS  read-only
STATUS      current
DESCRIPTION
"Identifier"
 ::= { psBbyEntry  2 }

psBbyEntryDes OBJECT-TYPE
SYNTAX      DisplayString
MAX-ACCESS  read-write
STATUS      current
DESCRIPTION
"Description"
 ::= { psBbyEntry  3 }

psBbyEntryTmp OBJECT-TYPE
SYNTAX      DisplayString
MAX-ACCESS  read-only
STATUS      current
DESCRIPTION
"Temperature"
 ::= { psBbyEntry  4 }

psBbyEntryBat OBJECT-TYPE
SYNTAX      DisplayString
MAX-ACCESS  read-only
STATUS      current
DESCRIPTION
"Battery Sections"
 ::= { psBbyEntry  5 }



--
-- table BAT
--

psBatTable    OBJECT-TYPE
SYNTAX SEQUENCE OF PsBatEntry
MAX-ACCESS not-accessible
STATUS current
DESCRIPTION
        "Table of all Battery Section data"
 ::= { powerSystem  16 }

psBatEntry OBJECT-TYPE
SYNTAX     PsBatEntry
MAX-ACCESS  not-accessible
STATUS      current
DESCRIPTION
       "Entry of information for one Battery Section"
INDEX { psBatEntryIndex }
 ::= { psBatTable  1 }

PsBatEntry ::= SEQUENCE {
psBatEntryIndex   INTEGER,
psBatEntryIde   DisplayString,
psBatEntryDes   DisplayString,
psBatEntryCon   DisplayString,
psBatEntryStt   DisplayString,
psBatEntryNst   Integer32,
psBatEntryBty   DisplayString,
psBatEntryCap   DisplayString,
psBatEntryRtm   DisplayString,
psBatEntryAdc   DisplayString,
psBatEntryRes   DisplayString,
psBatEntryRtm1   Integer32
}

psBatEntryIndex OBJECT-TYPE
SYNTAX      INTEGER (0..2147483647)
MAX-ACCESS  read-only
STATUS      current
DESCRIPTION
"Table Index"
 ::= { psBatEntry  1 }

psBatEntryIde OBJECT-TYPE
SYNTAX      DisplayString
MAX-ACCESS  read-only
STATUS      current
DESCRIPTION
"Identifier"
 ::= { psBatEntry  2 }

psBatEntryDes OBJECT-TYPE
SYNTAX      DisplayString
MAX-ACCESS  read-write
STATUS      current
DESCRIPTION
"Description"
 ::= { psBatEntry  3 }

psBatEntryCon OBJECT-TYPE
SYNTAX      DisplayString
MAX-ACCESS  read-write
STATUS      current
DESCRIPTION
"Contactor
Values:
CN1,
CN2,
CN3
"
 ::= { psBatEntry  4 }

psBatEntryStt OBJECT-TYPE
SYNTAX      DisplayString
MAX-ACCESS  read-only
STATUS      current
DESCRIPTION
"State"
 ::= { psBatEntry  5 }

psBatEntryNst OBJECT-TYPE
SYNTAX      Integer32(1..32)
MAX-ACCESS  read-write
STATUS      current
DESCRIPTION
"Number of Strings"
 ::= { psBatEntry  6 }

psBatEntryBty OBJECT-TYPE
SYNTAX      DisplayString
MAX-ACCESS  read-write
STATUS      current
DESCRIPTION
"Section Battery Type
Values:
L1S,
IR30,
IR40,
12IR125,
4VR125,
2VR375,
L508,
GU41
"
 ::= { psBatEntry  7 }

psBatEntryCap OBJECT-TYPE
SYNTAX      DisplayString
MAX-ACCESS  read-only
STATUS      current
DESCRIPTION
"Section Nominal Capacity"
 ::= { psBatEntry  8 }

psBatEntryRtm OBJECT-TYPE
SYNTAX      DisplayString
MAX-ACCESS  read-only
STATUS      current
DESCRIPTION
"Reserve Time"
 ::= { psBatEntry  9 }

psBatEntryAdc OBJECT-TYPE
SYNTAX      DisplayString
MAX-ACCESS  read-only
STATUS      current
DESCRIPTION
"DC Current"
 ::= { psBatEntry  10 }

psBatEntryRes OBJECT-TYPE
SYNTAX      DisplayString
MAX-ACCESS  read-only
STATUS      current
DESCRIPTION
"Reserve Time Error"
 ::= { psBatEntry  11 }

psBatEntryRtm1 OBJECT-TYPE
SYNTAX      Integer32
UNITS       "Seconds"
MAX-ACCESS  read-only
STATUS      current
DESCRIPTION
"Reserve Time (Seconds)"
 ::= { psBatEntry  12 }



--
-- object psLda
--

psLda OBJECT IDENTIFIER  ::= { powerSystem  17 }

psLdaIde OBJECT-TYPE
SYNTAX      DisplayString
MAX-ACCESS  read-only
STATUS      current
DESCRIPTION
"Identifier"
 ::= { psLda  1 }

psLdaDes OBJECT-TYPE
SYNTAX      DisplayString
MAX-ACCESS  read-write
STATUS      current
DESCRIPTION
"Description"
 ::= { psLda  2 }

psLdaDfa OBJECT-TYPE
SYNTAX      DisplayString
MAX-ACCESS  read-only
STATUS      current
DESCRIPTION
"Distribution Fuse
Value:
Alarm report from linked object"
 ::= { psLda  3 }


--
-- object psAcd1
--

psAcd1 OBJECT IDENTIFIER  ::= { powerSystem  18 }

psAcd1Ide OBJECT-TYPE
SYNTAX      DisplayString
MAX-ACCESS  read-only
STATUS      current
DESCRIPTION
"Identifier"
 ::= { psAcd1  1 }

psAcd1Des OBJECT-TYPE
SYNTAX      DisplayString
MAX-ACCESS  read-write
STATUS      current
DESCRIPTION
"Description"
 ::= { psAcd1  2 }

psAcd1Prv OBJECT-TYPE
SYNTAX      DisplayString
MAX-ACCESS  read-only
STATUS      current
DESCRIPTION
"Phase R Voltage"
 ::= { psAcd1  3 }

psAcd1Psv OBJECT-TYPE
SYNTAX      DisplayString
MAX-ACCESS  read-only
STATUS      current
DESCRIPTION
"Phase S Voltage"
 ::= { psAcd1  4 }

psAcd1Ptv OBJECT-TYPE
SYNTAX      DisplayString
MAX-ACCESS  read-only
STATUS      current
DESCRIPTION
"Phase T Voltage"
 ::= { psAcd1  5 }

psAcd1Rsv OBJECT-TYPE
SYNTAX      DisplayString
MAX-ACCESS  read-only
STATUS      current
DESCRIPTION
"Voltage Between RS"
 ::= { psAcd1  6 }

psAcd1Stv OBJECT-TYPE
SYNTAX      DisplayString
MAX-ACCESS  read-only
STATUS      current
DESCRIPTION
"Voltage Between ST"
 ::= { psAcd1  7 }

psAcd1Trv OBJECT-TYPE
SYNTAX      DisplayString
MAX-ACCESS  read-only
STATUS      current
DESCRIPTION
"Voltage Between TR"
 ::= { psAcd1  8 }

psAcd1Pra OBJECT-TYPE
SYNTAX      DisplayString
MAX-ACCESS  read-only
STATUS      current
DESCRIPTION
"Phase R Current"
 ::= { psAcd1  9 }

psAcd1Psa OBJECT-TYPE
SYNTAX      DisplayString
MAX-ACCESS  read-only
STATUS      current
DESCRIPTION
"Phase S Current"
 ::= { psAcd1  10 }

psAcd1Pta OBJECT-TYPE
SYNTAX      DisplayString
MAX-ACCESS  read-only
STATUS      current
DESCRIPTION
"Phase T Current"
 ::= { psAcd1  11 }

psAcd1Prf OBJECT-TYPE
SYNTAX      DisplayString
MAX-ACCESS  read-only
STATUS      current
DESCRIPTION
"Phase R Fail
Value:
Alarm report from linked object"
 ::= { psAcd1  12 }

psAcd1Psf OBJECT-TYPE
SYNTAX      DisplayString
MAX-ACCESS  read-only
STATUS      current
DESCRIPTION
"Phase S Fail
Value:
Alarm report from linked object"
 ::= { psAcd1  13 }

psAcd1Ptf OBJECT-TYPE
SYNTAX      DisplayString
MAX-ACCESS  read-only
STATUS      current
DESCRIPTION
"Phase T Fail
Value:
Alarm report from linked object"
 ::= { psAcd1  14 }

psAcd1Msa OBJECT-TYPE
SYNTAX      DisplayString
MAX-ACCESS  read-only
STATUS      current
DESCRIPTION
"Master Switch Alarm
Value:
Alarm report from linked object"
 ::= { psAcd1  15 }


--
-- object psCn1
--

psCn1 OBJECT IDENTIFIER  ::= { powerSystem  19 }

psCn1Ide OBJECT-TYPE
SYNTAX      DisplayString
MAX-ACCESS  read-only
STATUS      current
DESCRIPTION
"Identifier"
 ::= { psCn1  1 }

psCn1Des OBJECT-TYPE
SYNTAX      DisplayString
MAX-ACCESS  read-write
STATUS      current
DESCRIPTION
"Description"
 ::= { psCn1  2 }

psCn1Stt OBJECT-TYPE
SYNTAX      DisplayString
MAX-ACCESS  read-write
STATUS      current
DESCRIPTION
"Status
Values:
NONE,
DISCON,
CONNECT,
FAILED
"
 ::= { psCn1  3 }

psCn1Typ OBJECT-TYPE
SYNTAX      DisplayString
MAX-ACCESS  read-write
STATUS      current
DESCRIPTION
"Type
Values:
NONE,
BATTERY,
LOAD
"
 ::= { psCn1  4 }

psCn1Dth OBJECT-TYPE
SYNTAX      Integer32(20000..50000)
MAX-ACCESS  read-write
STATUS      current
DESCRIPTION
"Disconnect Threshold"
 ::= { psCn1  5 }

psCn1Rth OBJECT-TYPE
SYNTAX      Integer32(22000..55000)
UNITS       "mV"
MAX-ACCESS  read-write
STATUS      current
DESCRIPTION
"Reconnect Threshold (mV)"
 ::= { psCn1  6 }

psCn1Cno OBJECT-TYPE
SYNTAX      DisplayString
MAX-ACCESS  read-only
STATUS      current
DESCRIPTION
"Contactor Open
Value:
Alarm report from CNO1
"
 ::= { psCn1  7 }

psCn1Cnf OBJECT-TYPE
SYNTAX      DisplayString
MAX-ACCESS  read-only
STATUS      current
DESCRIPTION
"Contactor Failed
Value:
Alarm report from CNF1
"
 ::= { psCn1  8 }

psCn1Ena OBJECT-TYPE
SYNTAX      INTEGER {
disable(0),
enable(1)
}
MAX-ACCESS  read-write
STATUS      current
DESCRIPTION
"Control
Values:
disable(0),
enable(1)
"
 ::= { psCn1  9 }

psCn1Ddy OBJECT-TYPE
SYNTAX      Integer32(0..300)
UNITS       "Seconds"
MAX-ACCESS  read-write
STATUS      current
DESCRIPTION
"Disconnect Delay (Seconds)"
 ::= { psCn1  10 }

psCn1Dam OBJECT-TYPE
SYNTAX      INTEGER {
none(0),
voltage(1),
voltageAndTime(2)
}
MAX-ACCESS  read-write
STATUS      current
DESCRIPTION
"Disconnect Automode
Values:
none(0),
voltage(1),
voltageAndTime(2)
"
 ::= { psCn1  11 }

psCn1Dtm OBJECT-TYPE
SYNTAX      Integer32
UNITS       "Minutes"
MAX-ACCESS  read-only
STATUS      current
DESCRIPTION
"Disconnect Time Remaining (Minutes)"
 ::= { psCn1  12 }

psCn1Rdy OBJECT-TYPE
SYNTAX      Integer32(0..300)
UNITS       "Seconds"
MAX-ACCESS  read-write
STATUS      current
DESCRIPTION
"Reconnect Delay (Seconds)"
 ::= { psCn1  13 }

psCn1Ram OBJECT-TYPE
SYNTAX      INTEGER {
none(0),
voltage(1),
voltageAndTime(2)
}
MAX-ACCESS  read-write
STATUS      current
DESCRIPTION
"Reconnect Automode
Values:
none(0),
voltage(1),
voltageAndTime(2)
"
 ::= { psCn1  14 }

psCn1Rtm OBJECT-TYPE
SYNTAX      Integer32
UNITS       "Seconds"
MAX-ACCESS  read-only
STATUS      current
DESCRIPTION
"Reconnect Time Remaining (Seconds)"
 ::= { psCn1  15 }


--
-- object psCn2
--

psCn2 OBJECT IDENTIFIER  ::= { powerSystem  20 }

psCn2Ide OBJECT-TYPE
SYNTAX      DisplayString
MAX-ACCESS  read-only
STATUS      current
DESCRIPTION
"Identifier"
 ::= { psCn2  1 }

psCn2Des OBJECT-TYPE
SYNTAX      DisplayString
MAX-ACCESS  read-write
STATUS      current
DESCRIPTION
"Description"
 ::= { psCn2  2 }

psCn2Stt OBJECT-TYPE
SYNTAX      DisplayString
MAX-ACCESS  read-write
STATUS      current
DESCRIPTION
"Status
Values:
NONE,
DISCON,
CONNECT,
FAILED
"
 ::= { psCn2  3 }

psCn2Typ OBJECT-TYPE
SYNTAX      DisplayString
MAX-ACCESS  read-write
STATUS      current
DESCRIPTION
"Type
Values:
NONE,
BATTERY,
LOAD
"
 ::= { psCn2  4 }

psCn2Dth OBJECT-TYPE
SYNTAX      Integer32(20000..50000)
MAX-ACCESS  read-write
STATUS      current
DESCRIPTION
"Disconnect Threshold"
 ::= { psCn2  5 }

psCn2Rth OBJECT-TYPE
SYNTAX      Integer32(22000..55000)
UNITS       "mV"
MAX-ACCESS  read-write
STATUS      current
DESCRIPTION
"Reconnect Threshold (mV)"
 ::= { psCn2  6 }

psCn2Cno OBJECT-TYPE
SYNTAX      DisplayString
MAX-ACCESS  read-only
STATUS      current
DESCRIPTION
"Contactor Open
Value:
Alarm report from CNO2
"
 ::= { psCn2  7 }

psCn2Cnf OBJECT-TYPE
SYNTAX      DisplayString
MAX-ACCESS  read-only
STATUS      current
DESCRIPTION
"Contactor Failed
Value:
Alarm report from CNF2
"
 ::= { psCn2  8 }

psCn2Ena OBJECT-TYPE
SYNTAX      INTEGER {
disable(0),
enable(1)
}
MAX-ACCESS  read-write
STATUS      current
DESCRIPTION
"Control
Values:
disable(0),
enable(1)
"
 ::= { psCn2  9 }

psCn2Ddy OBJECT-TYPE
SYNTAX      Integer32(0..300)
UNITS       "Seconds"
MAX-ACCESS  read-write
STATUS      current
DESCRIPTION
"Disconnect Delay (Seconds)"
 ::= { psCn2  10 }

psCn2Dam OBJECT-TYPE
SYNTAX      INTEGER {
none(0),
voltage(1),
voltageAndTime(2)
}
MAX-ACCESS  read-write
STATUS      current
DESCRIPTION
"Disconnect Automode
Values:
none(0),
voltage(1),
voltageAndTime(2)
"
 ::= { psCn2  11 }

psCn2Dtm OBJECT-TYPE
SYNTAX      Integer32
UNITS       "Minutes"
MAX-ACCESS  read-only
STATUS      current
DESCRIPTION
"Disconnect Time Remaining (Minutes)"
 ::= { psCn2  12 }

psCn2Rdy OBJECT-TYPE
SYNTAX      Integer32(0..300)
UNITS       "Seconds"
MAX-ACCESS  read-write
STATUS      current
DESCRIPTION
"Reconnect Delay (Seconds)"
 ::= { psCn2  13 }

psCn2Ram OBJECT-TYPE
SYNTAX      INTEGER {
none(0),
voltage(1),
voltageAndTime(2)
}
MAX-ACCESS  read-write
STATUS      current
DESCRIPTION
"Reconnect Automode
Values:
none(0),
voltage(1),
voltageAndTime(2)
"
 ::= { psCn2  14 }

psCn2Rtm OBJECT-TYPE
SYNTAX      Integer32
UNITS       "Seconds"
MAX-ACCESS  read-only
STATUS      current
DESCRIPTION
"Reconnect Time Remaining (Seconds)"
 ::= { psCn2  15 }


--
-- object psCn3
--

psCn3 OBJECT IDENTIFIER  ::= { powerSystem  21 }

psCn3Ide OBJECT-TYPE
SYNTAX      DisplayString
MAX-ACCESS  read-only
STATUS      current
DESCRIPTION
"Identifier"
 ::= { psCn3  1 }

psCn3Des OBJECT-TYPE
SYNTAX      DisplayString
MAX-ACCESS  read-write
STATUS      current
DESCRIPTION
"Description"
 ::= { psCn3  2 }

psCn3Stt OBJECT-TYPE
SYNTAX      DisplayString
MAX-ACCESS  read-write
STATUS      current
DESCRIPTION
"Status
Values:
NONE,
DISCON,
CONNECT,
FAILED
"
 ::= { psCn3  3 }

psCn3Typ OBJECT-TYPE
SYNTAX      DisplayString
MAX-ACCESS  read-write
STATUS      current
DESCRIPTION
"Type
Values:
NONE,
BATTERY,
LOAD
"
 ::= { psCn3  4 }

psCn3Dth OBJECT-TYPE
SYNTAX      Integer32(20000..50000)
MAX-ACCESS  read-write
STATUS      current
DESCRIPTION
"Disconnect Threshold"
 ::= { psCn3  5 }

psCn3Rth OBJECT-TYPE
SYNTAX      Integer32(22000..55000)
UNITS       "mV"
MAX-ACCESS  read-write
STATUS      current
DESCRIPTION
"Reconnect Threshold (mV)"
 ::= { psCn3  6 }

psCn3Cno OBJECT-TYPE
SYNTAX      DisplayString
MAX-ACCESS  read-only
STATUS      current
DESCRIPTION
"Contactor Open
Value:
Alarm report from CNO3
"
 ::= { psCn3  7 }

psCn3Cnf OBJECT-TYPE
SYNTAX      DisplayString
MAX-ACCESS  read-only
STATUS      current
DESCRIPTION
"Contactor Failed
Value:
Alarm report from CNF3
"
 ::= { psCn3  8 }

psCn3Ena OBJECT-TYPE
SYNTAX      INTEGER {
disable(0),
enable(1)
}
MAX-ACCESS  read-write
STATUS      current
DESCRIPTION
"Control
Values:
disable(0),
enable(1)
"
 ::= { psCn3  9 }

psCn3Ddy OBJECT-TYPE
SYNTAX      Integer32(0..300)
UNITS       "Seconds"
MAX-ACCESS  read-write
STATUS      current
DESCRIPTION
"Disconnect Delay (Seconds)"
 ::= { psCn3  10 }

psCn3Dam OBJECT-TYPE
SYNTAX      INTEGER {
none(0),
voltage(1),
voltageAndTime(2)
}
MAX-ACCESS  read-write
STATUS      current
DESCRIPTION
"Disconnect Automode
Values:
none(0),
voltage(1),
voltageAndTime(2)
"
 ::= { psCn3  11 }

psCn3Dtm OBJECT-TYPE
SYNTAX      Integer32
UNITS       "Minutes"
MAX-ACCESS  read-only
STATUS      current
DESCRIPTION
"Disconnect Time Remaining (Minutes)"
 ::= { psCn3  12 }

psCn3Rdy OBJECT-TYPE
SYNTAX      Integer32(0..300)
UNITS       "Seconds"
MAX-ACCESS  read-write
STATUS      current
DESCRIPTION
"Reconnect Delay (Seconds)"
 ::= { psCn3  13 }

psCn3Ram OBJECT-TYPE
SYNTAX      INTEGER {
none(0),
voltage(1),
voltageAndTime(2)
}
MAX-ACCESS  read-write
STATUS      current
DESCRIPTION
"Reconnect Automode
Values:
none(0),
voltage(1),
voltageAndTime(2)
"
 ::= { psCn3  14 }

psCn3Rtm OBJECT-TYPE
SYNTAX      Integer32
UNITS       "Seconds"
MAX-ACCESS  read-only
STATUS      current
DESCRIPTION
"Reconnect Time Remaining (Seconds)"
 ::= { psCn3  15 }


--
-- table BIC
--

psBicTable    OBJECT-TYPE
SYNTAX SEQUENCE OF PsBicEntry
MAX-ACCESS not-accessible
STATUS current
DESCRIPTION
        "Table of all Bay Interface Card data"
 ::= { powerSystem  22 }

psBicEntry OBJECT-TYPE
SYNTAX     PsBicEntry
MAX-ACCESS  not-accessible
STATUS      current
DESCRIPTION
       "Entry of information for one Bay Interface Card"
INDEX { psBicEntryIndex }
 ::= { psBicTable  1 }

PsBicEntry ::= SEQUENCE {
psBicEntryIndex   INTEGER,
psBicEntryIde   DisplayString,
psBicEntryDes   DisplayString,
psBicEntryStt   DisplayString,
psBicEntryBid   DisplayString,
psBicEntryBcf   DisplayString,
psBicEntrySn   DisplayString
}

psBicEntryIndex OBJECT-TYPE
SYNTAX      INTEGER (0..2147483647)
MAX-ACCESS  read-only
STATUS      current
DESCRIPTION
"Table Index"
 ::= { psBicEntry  1 }

psBicEntryIde OBJECT-TYPE
SYNTAX      DisplayString
MAX-ACCESS  read-only
STATUS      current
DESCRIPTION
"Identifier"
 ::= { psBicEntry  2 }

psBicEntryDes OBJECT-TYPE
SYNTAX      DisplayString
MAX-ACCESS  read-write
STATUS      current
DESCRIPTION
"Description"
 ::= { psBicEntry  3 }

psBicEntryStt OBJECT-TYPE
SYNTAX      DisplayString
MAX-ACCESS  read-write
STATUS      current
DESCRIPTION
"State
Values:
PRESENT,
MISSING,
VACANT
"
 ::= { psBicEntry  4 }

psBicEntryBid OBJECT-TYPE
SYNTAX      DisplayString
MAX-ACCESS  read-only
STATUS      current
DESCRIPTION
"ID Conflict"
 ::= { psBicEntry  5 }

psBicEntryBcf OBJECT-TYPE
SYNTAX      DisplayString
MAX-ACCESS  read-only
STATUS      current
DESCRIPTION
"Communication Failure"
 ::= { psBicEntry  6 }

psBicEntrySn OBJECT-TYPE
SYNTAX      DisplayString
MAX-ACCESS  read-only
STATUS      current
DESCRIPTION
"Serial Number"
 ::= { psBicEntry  7 }



--
-- object psAco1
--

psAco1 OBJECT IDENTIFIER  ::= { powerSystem  23 }

psAco1Ide OBJECT-TYPE
SYNTAX      DisplayString
MAX-ACCESS  read-only
STATUS      current
DESCRIPTION
"Identifier"
 ::= { psAco1  1 }

psAco1Des OBJECT-TYPE
SYNTAX      DisplayString
MAX-ACCESS  read-write
STATUS      current
DESCRIPTION
"Description"
 ::= { psAco1  2 }

psAco1Stt OBJECT-TYPE
SYNTAX      INTEGER {
disable(0),
enable(1)
}
MAX-ACCESS  read-write
STATUS      current
DESCRIPTION
"State
Values:
disable(0),
enable(1)
"
 ::= { psAco1  3 }

psAco1Cst OBJECT-TYPE
SYNTAX      INTEGER {
inactive(0),
active(1)
}
MAX-ACCESS  read-only
STATUS      current
DESCRIPTION
"Critical ACO State
Values:
inactive(0),
active(1)
"
 ::= { psAco1  4 }

psAco1Cae OBJECT-TYPE
SYNTAX      INTEGER {
disable(0),
enable(1)
}
MAX-ACCESS  read-write
STATUS      current
DESCRIPTION
"Critical ACO Enable
Values:
disable(0),
enable(1)
"
 ::= { psAco1  5 }

psAco1Cto OBJECT-TYPE
SYNTAX      Integer32(1..4)
MAX-ACCESS  read-write
STATUS      current
DESCRIPTION
"Critical ACO Timeout"
 ::= { psAco1  6 }

psAco1Jst OBJECT-TYPE
SYNTAX      INTEGER {
inactive(0),
active(1)
}
MAX-ACCESS  read-only
STATUS      current
DESCRIPTION
"Major ACO State
Values:
inactive(0),
active(1)
"
 ::= { psAco1  7 }

psAco1Jae OBJECT-TYPE
SYNTAX      INTEGER {
disable(0),
enable(1)
}
MAX-ACCESS  read-write
STATUS      current
DESCRIPTION
"Major ACO Enable
Values:
disable(0),
enable(1)
"
 ::= { psAco1  8 }

psAco1Jto OBJECT-TYPE
SYNTAX      Integer32(1..4)
MAX-ACCESS  read-write
STATUS      current
DESCRIPTION
"Major ACO Timeout"
 ::= { psAco1  9 }

psAco1Nst OBJECT-TYPE
SYNTAX      INTEGER {
inactive(0),
active(1)
}
MAX-ACCESS  read-only
STATUS      current
DESCRIPTION
"Minor ACO State
Values:
inactive(0),
active(1)
"
 ::= { psAco1  10 }

psAco1Nae OBJECT-TYPE
SYNTAX      INTEGER {
disable(0),
enable(1)
}
MAX-ACCESS  read-write
STATUS      current
DESCRIPTION
"Minor ACO Enable
Values:
disable(0),
enable(1)
"
 ::= { psAco1  11 }

psAco1Nto OBJECT-TYPE
SYNTAX      Integer32(1..72)
MAX-ACCESS  read-write
STATUS      current
DESCRIPTION
"Minor ACO Timeout"
 ::= { psAco1  12 }

psAco1Aac OBJECT-TYPE
SYNTAX      DisplayString
MAX-ACCESS  read-only
STATUS      current
DESCRIPTION
"ACO Active
Value:
Alarm report from AAC1
"
 ::= { psAco1  13 }

psAco1Lbe OBJECT-TYPE
SYNTAX      INTEGER {
disable(0),
enable(1)
}
MAX-ACCESS  read-write
STATUS      current
DESCRIPTION
"Local Buzzer Enable
Values:
disable(0),
enable(1)
"
 ::= { psAco1  14 }


--
-- table UDE
--

psUdeTable    OBJECT-TYPE
SYNTAX SEQUENCE OF PsUdeEntry
MAX-ACCESS not-accessible
STATUS current
DESCRIPTION
        "Table of all User Defined Event data"
 ::= { powerSystem  24 }

psUdeEntry OBJECT-TYPE
SYNTAX     PsUdeEntry
MAX-ACCESS  not-accessible
STATUS      current
DESCRIPTION
       "Entry of information for one User Defined Event"
INDEX { psUdeEntryIndex }
 ::= { psUdeTable  1 }

PsUdeEntry ::= SEQUENCE {
psUdeEntryIndex   INTEGER,
psUdeEntryIde   DisplayString,
psUdeEntryDes   DisplayString,
psUdeEntryAst   DisplayString,
psUdeEntrySev   DisplayString,
psUdeEntryPrg   DisplayString,
psUdeEntryDur   DisplayString,
psUdeEntryLat   INTEGER,
psUdeEntryLed   DisplayString,
psUdeEntryAcc   DisplayString,
psUdeEntryDly   Integer32,
psUdeEntryNoo   INTEGER,
psUdeEntryNor   INTEGER,
psUdeEntryNag   INTEGER,
psUdeEntryDst   DisplayString,
psUdeEntryAst1   INTEGER
}

psUdeEntryIndex OBJECT-TYPE
SYNTAX      INTEGER (0..2147483647)
MAX-ACCESS  read-only
STATUS      current
DESCRIPTION
"Table Index"
 ::= { psUdeEntry  1 }

psUdeEntryIde OBJECT-TYPE
SYNTAX      DisplayString
MAX-ACCESS  read-only
STATUS      current
DESCRIPTION
"Identifier"
 ::= { psUdeEntry  2 }

psUdeEntryDes OBJECT-TYPE
SYNTAX      DisplayString
MAX-ACCESS  read-write
STATUS      current
DESCRIPTION
"Description"
 ::= { psUdeEntry  3 }

psUdeEntryAst OBJECT-TYPE
SYNTAX      DisplayString
MAX-ACCESS  read-only
STATUS      current
DESCRIPTION
"Alarm State"
 ::= { psUdeEntry  4 }

psUdeEntrySev OBJECT-TYPE
SYNTAX      DisplayString
MAX-ACCESS  read-write
STATUS      current
DESCRIPTION
"Severity
Values:
CRIT,
MAJ,
MIN,
WRN,
RO
"
 ::= { psUdeEntry  5 }

psUdeEntryPrg OBJECT-TYPE
SYNTAX      DisplayString
MAX-ACCESS  read-write
STATUS      current
DESCRIPTION
"Program Line"
 ::= { psUdeEntry  6 }

psUdeEntryDur OBJECT-TYPE
SYNTAX      DisplayString
MAX-ACCESS  read-write
STATUS      current
DESCRIPTION
"Minimum Duration"
 ::= { psUdeEntry  7 }

psUdeEntryLat OBJECT-TYPE
SYNTAX      INTEGER {
no(0),
yes(1)
}
MAX-ACCESS  read-write
STATUS      current
DESCRIPTION
"Latched
Values:
no(0),
yes(1)
"
 ::= { psUdeEntry  8 }

psUdeEntryLed OBJECT-TYPE
SYNTAX      DisplayString
MAX-ACCESS  read-write
STATUS      current
DESCRIPTION
"LED
Values:
BATT,
BD,
DIST,
RECT,
AC,
RM,
CTLR
"
 ::= { psUdeEntry  9 }

psUdeEntryAcc OBJECT-TYPE
SYNTAX      DisplayString
MAX-ACCESS  read-write
STATUS      current
DESCRIPTION
"Contact Closure
Values:
ACF,
MJF,
MNF,
RFA,
VLV,
HV,
BD,
CTLR,
UR1,
UR2
"
 ::= { psUdeEntry  10 }

psUdeEntryDly OBJECT-TYPE
SYNTAX      Integer32(0..540)
MAX-ACCESS  read-write
STATUS      current
DESCRIPTION
"Notify Delay"
 ::= { psUdeEntry  11 }

psUdeEntryNoo OBJECT-TYPE
SYNTAX      INTEGER {
no(0),
yes(1)
}
MAX-ACCESS  read-write
STATUS      current
DESCRIPTION
"Notify on Occur
Values:
no(0),
yes(1)
"
 ::= { psUdeEntry  12 }

psUdeEntryNor OBJECT-TYPE
SYNTAX      INTEGER {
no(0),
yes(1)
}
MAX-ACCESS  read-write
STATUS      current
DESCRIPTION
"Notify on Retire
Values:
no(0),
yes(1)
"
 ::= { psUdeEntry  13 }

psUdeEntryNag OBJECT-TYPE
SYNTAX      INTEGER {
no(0),
yes(1)
}
MAX-ACCESS  read-write
STATUS      current
DESCRIPTION
"NAG on Occur
Values:
no(0),
yes(1)
"
 ::= { psUdeEntry  14 }

psUdeEntryDst OBJECT-TYPE
SYNTAX      DisplayString
MAX-ACCESS  read-write
STATUS      current
DESCRIPTION
"Notify Destination
Values:
P1,
P2,
P3,
P4
"
 ::= { psUdeEntry  15 }

psUdeEntryAst1 OBJECT-TYPE
SYNTAX      INTEGER {
inactive(0),
active(1)
}
MAX-ACCESS  read-only
STATUS      current
DESCRIPTION
"Alarm State
Values:
inactive(0),
active(1)
"
 ::= { psUdeEntry  16 }



--
-- table TME
--

psTmeTable    OBJECT-TYPE
SYNTAX SEQUENCE OF PsTmeEntry
MAX-ACCESS not-accessible
STATUS current
DESCRIPTION
        "Table of all Timer Event data"
 ::= { powerSystem  25 }

psTmeEntry OBJECT-TYPE
SYNTAX     PsTmeEntry
MAX-ACCESS  not-accessible
STATUS      current
DESCRIPTION
       "Entry of information for one Timer Event"
INDEX { psTmeEntryIndex }
 ::= { psTmeTable  1 }

PsTmeEntry ::= SEQUENCE {
psTmeEntryIndex   INTEGER,
psTmeEntryIde   DisplayString,
psTmeEntryDes   DisplayString,
psTmeEntryStt   DisplayString,
psTmeEntryDat   DisplayString,
psTmeEntryTim   DisplayString,
psTmeEntryDur   Integer32
}

psTmeEntryIndex OBJECT-TYPE
SYNTAX      INTEGER (0..2147483647)
MAX-ACCESS  read-only
STATUS      current
DESCRIPTION
"Table Index"
 ::= { psTmeEntry  1 }

psTmeEntryIde OBJECT-TYPE
SYNTAX      DisplayString
MAX-ACCESS  read-only
STATUS      current
DESCRIPTION
"Identifier"
 ::= { psTmeEntry  2 }

psTmeEntryDes OBJECT-TYPE
SYNTAX      DisplayString
MAX-ACCESS  read-write
STATUS      current
DESCRIPTION
"Description"
 ::= { psTmeEntry  3 }

psTmeEntryStt OBJECT-TYPE
SYNTAX      DisplayString
MAX-ACCESS  read-only
STATUS      current
DESCRIPTION
"State"
 ::= { psTmeEntry  4 }

psTmeEntryDat OBJECT-TYPE
SYNTAX      DisplayString
MAX-ACCESS  read-write
STATUS      current
DESCRIPTION
"Date"
 ::= { psTmeEntry  5 }

psTmeEntryTim OBJECT-TYPE
SYNTAX      DisplayString
MAX-ACCESS  read-write
STATUS      current
DESCRIPTION
"Time"
 ::= { psTmeEntry  6 }

psTmeEntryDur OBJECT-TYPE
SYNTAX      Integer32(0..1440)
UNITS       "minutes"
MAX-ACCESS  read-write
STATUS      current
DESCRIPTION
"Duration (minutes)"
 ::= { psTmeEntry  7 }



--
-- table MRM
--

psMrmTable    OBJECT-TYPE
SYNTAX SEQUENCE OF PsMrmEntry
MAX-ACCESS not-accessible
STATUS current
DESCRIPTION
        "Table of all Maintenance Reminder data"
 ::= { powerSystem  26 }

psMrmEntry OBJECT-TYPE
SYNTAX     PsMrmEntry
MAX-ACCESS  not-accessible
STATUS      current
DESCRIPTION
       "Entry of information for one Maintenance Reminder"
INDEX { psMrmEntryIndex }
 ::= { psMrmTable  1 }

PsMrmEntry ::= SEQUENCE {
psMrmEntryIndex   INTEGER,
psMrmEntryIde   DisplayString,
psMrmEntryDes   DisplayString,
psMrmEntryAst   DisplayString,
psMrmEntrySev   DisplayString,
psMrmEntryNoo   INTEGER,
psMrmEntryNor   INTEGER,
psMrmEntryNag   INTEGER,
psMrmEntryDst   DisplayString,
psMrmEntryDat   DisplayString,
psMrmEntryTim   DisplayString,
psMrmEntryTxt   DisplayString
}

psMrmEntryIndex OBJECT-TYPE
SYNTAX      INTEGER (0..2147483647)
MAX-ACCESS  read-only
STATUS      current
DESCRIPTION
"Table Index"
 ::= { psMrmEntry  1 }

psMrmEntryIde OBJECT-TYPE
SYNTAX      DisplayString
MAX-ACCESS  read-only
STATUS      current
DESCRIPTION
"Identifier"
 ::= { psMrmEntry  2 }

psMrmEntryDes OBJECT-TYPE
SYNTAX      DisplayString
MAX-ACCESS  read-write
STATUS      current
DESCRIPTION
"Description"
 ::= { psMrmEntry  3 }

psMrmEntryAst OBJECT-TYPE
SYNTAX      DisplayString
MAX-ACCESS  read-only
STATUS      current
DESCRIPTION
"Alarm State"
 ::= { psMrmEntry  4 }

psMrmEntrySev OBJECT-TYPE
SYNTAX      DisplayString
MAX-ACCESS  read-only
STATUS      current
DESCRIPTION
"Severity"
 ::= { psMrmEntry  5 }

psMrmEntryNoo OBJECT-TYPE
SYNTAX      INTEGER {
no(0),
yes(1)
}
MAX-ACCESS  read-write
STATUS      current
DESCRIPTION
"Notify on Occur
Values:
no(0),
yes(1)
"
 ::= { psMrmEntry  6 }

psMrmEntryNor OBJECT-TYPE
SYNTAX      INTEGER {
no(0),
yes(1)
}
MAX-ACCESS  read-write
STATUS      current
DESCRIPTION
"Notify on Retire
Values:
no(0),
yes(1)
"
 ::= { psMrmEntry  7 }

psMrmEntryNag OBJECT-TYPE
SYNTAX      INTEGER {
no(0),
yes(1)
}
MAX-ACCESS  read-write
STATUS      current
DESCRIPTION
"NAG on Occur
Values:
no(0),
yes(1)
"
 ::= { psMrmEntry  8 }

psMrmEntryDst OBJECT-TYPE
SYNTAX      DisplayString
MAX-ACCESS  read-write
STATUS      current
DESCRIPTION
"Notify Destination
Values:
P1,
P2,
P3,
P4
"
 ::= { psMrmEntry  9 }

psMrmEntryDat OBJECT-TYPE
SYNTAX      DisplayString
MAX-ACCESS  read-write
STATUS      current
DESCRIPTION
"Notification Date"
 ::= { psMrmEntry  10 }

psMrmEntryTim OBJECT-TYPE
SYNTAX      DisplayString
MAX-ACCESS  read-write
STATUS      current
DESCRIPTION
"Notification Time"
 ::= { psMrmEntry  11 }

psMrmEntryTxt OBJECT-TYPE
SYNTAX      DisplayString
MAX-ACCESS  read-write
STATUS      current
DESCRIPTION
"Notification Text"
 ::= { psMrmEntry  12 }



--
-- table CEA
--

psCeaTable    OBJECT-TYPE
SYNTAX SEQUENCE OF PsCeaEntry
MAX-ACCESS not-accessible
STATUS current
DESCRIPTION
        "Table of all Connected Equipment Alarm data"
 ::= { powerSystem  27 }

psCeaEntry OBJECT-TYPE
SYNTAX     PsCeaEntry
MAX-ACCESS  not-accessible
STATUS      current
DESCRIPTION
       "Entry of information for one Connected Equipment Alarm"
INDEX { psCeaEntryIndex }
 ::= { psCeaTable  1 }

PsCeaEntry ::= SEQUENCE {
psCeaEntryIndex   INTEGER,
psCeaEntryIde   DisplayString,
psCeaEntryDes   DisplayString,
psCeaEntryAst   DisplayString,
psCeaEntrySev   DisplayString,
psCeaEntryDly   INTEGER,
psCeaEntryNoo   INTEGER,
psCeaEntryNor   INTEGER,
psCeaEntryNag   INTEGER,
psCeaEntryDst   DisplayString
}

psCeaEntryIndex OBJECT-TYPE
SYNTAX      INTEGER (0..2147483647)
MAX-ACCESS  read-only
STATUS      current
DESCRIPTION
"Table Index"
 ::= { psCeaEntry  1 }

psCeaEntryIde OBJECT-TYPE
SYNTAX      DisplayString
MAX-ACCESS  read-only
STATUS      current
DESCRIPTION
"Identifier"
 ::= { psCeaEntry  2 }

psCeaEntryDes OBJECT-TYPE
SYNTAX      DisplayString
MAX-ACCESS  read-write
STATUS      current
DESCRIPTION
"Description"
 ::= { psCeaEntry  3 }

psCeaEntryAst OBJECT-TYPE
SYNTAX      DisplayString
MAX-ACCESS  read-only
STATUS      current
DESCRIPTION
"Alarm State"
 ::= { psCeaEntry  4 }

psCeaEntrySev OBJECT-TYPE
SYNTAX      DisplayString
MAX-ACCESS  read-write
STATUS      current
DESCRIPTION
"Severity
Values:
CRIT,
MAJ,
MIN,
WRN,
RO
"
 ::= { psCeaEntry  5 }

psCeaEntryDly OBJECT-TYPE
SYNTAX      INTEGER {
no(0),
yes(1)
}
MAX-ACCESS  read-write
STATUS      current
DESCRIPTION
"Notify Delay
Values:
no(0),
yes(1)
"
 ::= { psCeaEntry  6 }

psCeaEntryNoo OBJECT-TYPE
SYNTAX      INTEGER {
no(0),
yes(1)
}
MAX-ACCESS  read-write
STATUS      current
DESCRIPTION
"Notify on Occur
Values:
no(0),
yes(1)
"
 ::= { psCeaEntry  7 }

psCeaEntryNor OBJECT-TYPE
SYNTAX      INTEGER {
no(0),
yes(1)
}
MAX-ACCESS  read-write
STATUS      current
DESCRIPTION
"Notify on Retire
Values:
no(0),
yes(1)
"
 ::= { psCeaEntry  8 }

psCeaEntryNag OBJECT-TYPE
SYNTAX      INTEGER {
no(0),
yes(1)
}
MAX-ACCESS  read-write
STATUS      current
DESCRIPTION
"NAG on Occur
Values:
no(0),
yes(1)
"
 ::= { psCeaEntry  9 }

psCeaEntryDst OBJECT-TYPE
SYNTAX      DisplayString
MAX-ACCESS  read-write
STATUS      current
DESCRIPTION
"Notify Destination
Values:
P1,
P2,
P3,
P4
"
 ::= { psCeaEntry  10 }



--
-- object psCm1
--

psCm1 OBJECT IDENTIFIER  ::= { powerSystem  28 }

psCm1Ide OBJECT-TYPE
SYNTAX      DisplayString
MAX-ACCESS  read-only
STATUS      current
DESCRIPTION
"Identifier"
 ::= { psCm1  1 }

psCm1Des OBJECT-TYPE
SYNTAX      DisplayString
MAX-ACCESS  read-write
STATUS      current
DESCRIPTION
"Description"
 ::= { psCm1  2 }

psCm1Ngi OBJECT-TYPE
SYNTAX      Integer32(15..60)
MAX-ACCESS  read-write
STATUS      current
DESCRIPTION
"Nag Interval"
 ::= { psCm1  3 }

psCm1Cof OBJECT-TYPE
SYNTAX      DisplayString
MAX-ACCESS  read-only
STATUS      current
DESCRIPTION
"Queue Overflow
Value:
Alarm report from COF1
"
 ::= { psCm1  4 }

psCm1Cor OBJECT-TYPE
SYNTAX      DisplayString
MAX-ACCESS  read-only
STATUS      current
DESCRIPTION
"Number Did Not Respond
Value:
Alarm report from COR1
"
 ::= { psCm1  5 }

psCm1Nnc OBJECT-TYPE
SYNTAX      DisplayString
MAX-ACCESS  read-only
STATUS      current
DESCRIPTION
"Number Not Configured
Value:
Alarm report from NNC1
"
 ::= { psCm1  6 }

psCm1Cop OBJECT-TYPE
SYNTAX      DisplayString
MAX-ACCESS  read-only
STATUS      current
DESCRIPTION
"Phone Numbers"
 ::= { psCm1  7 }


--
-- table COP
--

psCopTable    OBJECT-TYPE
SYNTAX SEQUENCE OF PsCopEntry
MAX-ACCESS not-accessible
STATUS current
DESCRIPTION
        "Table of all Call Out Phone Number data"
 ::= { powerSystem  29 }

psCopEntry OBJECT-TYPE
SYNTAX     PsCopEntry
MAX-ACCESS  not-accessible
STATUS      current
DESCRIPTION
       "Entry of information for one Call Out Phone Number"
INDEX { psCopEntryIndex }
 ::= { psCopTable  1 }

PsCopEntry ::= SEQUENCE {
psCopEntryIndex   INTEGER,
psCopEntryIde   DisplayString,
psCopEntryDes   DisplayString,
psCopEntryTyp   DisplayString,
psCopEntryPhn   DisplayString,
psCopEntryBdr   INTEGER,
psCopEntryDbt   INTEGER,
psCopEntryPry   DisplayString,
psCopEntrySbt   INTEGER,
psCopEntryDly   Integer32,
psCopEntryPgr   DisplayString,
psCopEntryMsg   DisplayString
}

psCopEntryIndex OBJECT-TYPE
SYNTAX      INTEGER (0..2147483647)
MAX-ACCESS  read-only
STATUS      current
DESCRIPTION
"Table Index"
 ::= { psCopEntry  1 }

psCopEntryIde OBJECT-TYPE
SYNTAX      DisplayString
MAX-ACCESS  read-only
STATUS      current
DESCRIPTION
"Identifier"
 ::= { psCopEntry  2 }

psCopEntryDes OBJECT-TYPE
SYNTAX      DisplayString
MAX-ACCESS  read-write
STATUS      current
DESCRIPTION
"Description"
 ::= { psCopEntry  3 }

psCopEntryTyp OBJECT-TYPE
SYNTAX      DisplayString
MAX-ACCESS  read-write
STATUS      current
DESCRIPTION
"Type
Values:
DATA,
PAGER
"
 ::= { psCopEntry  4 }

psCopEntryPhn OBJECT-TYPE
SYNTAX      DisplayString
MAX-ACCESS  read-write
STATUS      current
DESCRIPTION
"Phone Number"
 ::= { psCopEntry  5 }

psCopEntryBdr OBJECT-TYPE
SYNTAX      INTEGER {
b300(300),
b1200(1200),
b2400(2400),
b4800(4800),
b9600(9600),
b19200(19200)
}
MAX-ACCESS  read-write
STATUS      current
DESCRIPTION
"Connect Baudrate
Values:
b300(300),
b1200(1200),
b2400(2400),
b4800(4800),
b9600(9600),
b19200(19200)
"
 ::= { psCopEntry  6 }

psCopEntryDbt OBJECT-TYPE
SYNTAX      INTEGER {
d7(7),
d8(8)
}
MAX-ACCESS  read-write
STATUS      current
DESCRIPTION
"Data Bits
Values:
d7(7),
d8(8)
"
 ::= { psCopEntry  7 }

psCopEntryPry OBJECT-TYPE
SYNTAX      DisplayString
MAX-ACCESS  read-write
STATUS      current
DESCRIPTION
"Parity
Values:
O,
E,
N
"
 ::= { psCopEntry  8 }

psCopEntrySbt OBJECT-TYPE
SYNTAX      INTEGER {
s1(1),
s2(2)
}
MAX-ACCESS  read-write
STATUS      current
DESCRIPTION
"Stop Bits
Values:
s1(1),
s2(2)
"
 ::= { psCopEntry  9 }

psCopEntryDly OBJECT-TYPE
SYNTAX      Integer32(0..9)
MAX-ACCESS  read-write
STATUS      current
DESCRIPTION
"Pager ID Delay"
 ::= { psCopEntry  10 }

psCopEntryPgr OBJECT-TYPE
SYNTAX      DisplayString
MAX-ACCESS  read-write
STATUS      current
DESCRIPTION
"Pager ID"
 ::= { psCopEntry  11 }

psCopEntryMsg OBJECT-TYPE
SYNTAX      DisplayString
MAX-ACCESS  read-write
STATUS      current
DESCRIPTION
"Pager Message"
 ::= { psCopEntry  12 }



--
-- object psPo1
--

psPo1 OBJECT IDENTIFIER  ::= { powerSystem  30 }

psPo1Ide OBJECT-TYPE
SYNTAX      DisplayString
MAX-ACCESS  read-only
STATUS      current
DESCRIPTION
"Identifier"
 ::= { psPo1  1 }

psPo1Des OBJECT-TYPE
SYNTAX      DisplayString
MAX-ACCESS  read-write
STATUS      current
DESCRIPTION
"Description"
 ::= { psPo1  2 }

psPo1Phn OBJECT-TYPE
SYNTAX      DisplayString
MAX-ACCESS  read-write
STATUS      current
DESCRIPTION
"Phone Number"
 ::= { psPo1  3 }

psPo1Bdr OBJECT-TYPE
SYNTAX      INTEGER {
b300(300),
b1200(1200),
b2400(2400),
b4800(4800),
b9600(9600),
b19200(19200)
}
MAX-ACCESS  read-write
STATUS      current
DESCRIPTION
"Connect Baudrate
Values:
b300(300),
b1200(1200),
b2400(2400),
b4800(4800),
b9600(9600),
b19200(19200)
"
 ::= { psPo1  4 }

psPo1Dbt OBJECT-TYPE
SYNTAX      INTEGER {
d7(7),
d8(8)
}
MAX-ACCESS  read-write
STATUS      current
DESCRIPTION
"Data Bits
Values:
d7(7),
d8(8)
"
 ::= { psPo1  5 }

psPo1Pry OBJECT-TYPE
SYNTAX      DisplayString
MAX-ACCESS  read-write
STATUS      current
DESCRIPTION
"Parity
Values:
O,
E,
N
"
 ::= { psPo1  6 }

psPo1Sbt OBJECT-TYPE
SYNTAX      INTEGER {
s1(1),
s2(2)
}
MAX-ACCESS  read-write
STATUS      current
DESCRIPTION
"Stop Bits
Values:
s1(1),
s2(2)
"
 ::= { psPo1  7 }

psPo1Int OBJECT-TYPE
SYNTAX      DisplayString
MAX-ACCESS  read-write
STATUS      current
DESCRIPTION
"Interval
Values:
Sunday,
Monday,
Tuesday,
Wednesday,
Thursday,
Friday,
Saturday,
Daily,
Monthly,
Quarterly,
Never
"
 ::= { psPo1  8 }

psPo1Tim OBJECT-TYPE
SYNTAX      DisplayString
MAX-ACCESS  read-write
STATUS      current
DESCRIPTION
"Time"
 ::= { psPo1  9 }

psPo1Cl01 OBJECT-TYPE
SYNTAX      DisplayString
MAX-ACCESS  read-write
STATUS      current
DESCRIPTION
"Command Line 1"
 ::= { psPo1  10 }

psPo1Cl02 OBJECT-TYPE
SYNTAX      DisplayString
MAX-ACCESS  read-write
STATUS      current
DESCRIPTION
"Command Line 2"
 ::= { psPo1  11 }

psPo1Cl03 OBJECT-TYPE
SYNTAX      DisplayString
MAX-ACCESS  read-write
STATUS      current
DESCRIPTION
"Command Line 3"
 ::= { psPo1  12 }

psPo1Cl04 OBJECT-TYPE
SYNTAX      DisplayString
MAX-ACCESS  read-write
STATUS      current
DESCRIPTION
"Command Line 4"
 ::= { psPo1  13 }

psPo1Cl05 OBJECT-TYPE
SYNTAX      DisplayString
MAX-ACCESS  read-write
STATUS      current
DESCRIPTION
"Command Line 5"
 ::= { psPo1  14 }

psPo1Cl06 OBJECT-TYPE
SYNTAX      DisplayString
MAX-ACCESS  read-write
STATUS      current
DESCRIPTION
"Command Line 6"
 ::= { psPo1  15 }

psPo1Cl07 OBJECT-TYPE
SYNTAX      DisplayString
MAX-ACCESS  read-write
STATUS      current
DESCRIPTION
"Command Line 7"
 ::= { psPo1  16 }

psPo1Cl08 OBJECT-TYPE
SYNTAX      DisplayString
MAX-ACCESS  read-write
STATUS      current
DESCRIPTION
"Command Line 8"
 ::= { psPo1  17 }

psPo1Cl09 OBJECT-TYPE
SYNTAX      DisplayString
MAX-ACCESS  read-write
STATUS      current
DESCRIPTION
"Command Line 9"
 ::= { psPo1  18 }

psPo1Cl10 OBJECT-TYPE
SYNTAX      DisplayString
MAX-ACCESS  read-write
STATUS      current
DESCRIPTION
"Command Line 10"
 ::= { psPo1  19 }

psPo1Por OBJECT-TYPE
SYNTAX      DisplayString
MAX-ACCESS  read-only
STATUS      current
DESCRIPTION
"Number Did Not Respond
Value:
Alarm report from POR1
"
 ::= { psPo1  20 }

psPo1E01 OBJECT-TYPE
SYNTAX      DisplayString
MAX-ACCESS  read-write
STATUS      current
DESCRIPTION
"Email Address 1"
 ::= { psPo1  21 }

psPo1E02 OBJECT-TYPE
SYNTAX      DisplayString
MAX-ACCESS  read-write
STATUS      current
DESCRIPTION
"Email Address 2"
 ::= { psPo1  22 }

psPo1E03 OBJECT-TYPE
SYNTAX      DisplayString
MAX-ACCESS  read-write
STATUS      current
DESCRIPTION
"Email Address 3"
 ::= { psPo1  23 }

psPo1E04 OBJECT-TYPE
SYNTAX      DisplayString
MAX-ACCESS  read-write
STATUS      current
DESCRIPTION
"Email Address 4"
 ::= { psPo1  24 }

psPo1D01 OBJECT-TYPE
SYNTAX      DisplayString
MAX-ACCESS  read-write
STATUS      current
DESCRIPTION
"Description for Command Line 1"
 ::= { psPo1  25 }

psPo1D02 OBJECT-TYPE
SYNTAX      DisplayString
MAX-ACCESS  read-write
STATUS      current
DESCRIPTION
"Description for Command Line 2"
 ::= { psPo1  26 }

psPo1D03 OBJECT-TYPE
SYNTAX      DisplayString
MAX-ACCESS  read-write
STATUS      current
DESCRIPTION
"Description for Command Line 3"
 ::= { psPo1  27 }

psPo1D04 OBJECT-TYPE
SYNTAX      DisplayString
MAX-ACCESS  read-write
STATUS      current
DESCRIPTION
"Description for Command Line 4"
 ::= { psPo1  28 }

psPo1D05 OBJECT-TYPE
SYNTAX      DisplayString
MAX-ACCESS  read-write
STATUS      current
DESCRIPTION
"Description for Command Line 5"
 ::= { psPo1  29 }

psPo1D06 OBJECT-TYPE
SYNTAX      DisplayString
MAX-ACCESS  read-write
STATUS      current
DESCRIPTION
"Description for Command Line 6"
 ::= { psPo1  30 }

psPo1D07 OBJECT-TYPE
SYNTAX      DisplayString
MAX-ACCESS  read-write
STATUS      current
DESCRIPTION
"Description for Command Line 7"
 ::= { psPo1  31 }

psPo1D08 OBJECT-TYPE
SYNTAX      DisplayString
MAX-ACCESS  read-write
STATUS      current
DESCRIPTION
"Description for Command Line 8"
 ::= { psPo1  32 }

psPo1D09 OBJECT-TYPE
SYNTAX      DisplayString
MAX-ACCESS  read-write
STATUS      current
DESCRIPTION
"Description for Command Line 9"
 ::= { psPo1  33 }

psPo1D10 OBJECT-TYPE
SYNTAX      DisplayString
MAX-ACCESS  read-write
STATUS      current
DESCRIPTION
"Description for Command Line 10"
 ::= { psPo1  34 }


--
-- object psCb1
--

psCb1 OBJECT IDENTIFIER  ::= { powerSystem  31 }

psCb1Ide OBJECT-TYPE
SYNTAX      DisplayString
MAX-ACCESS  read-only
STATUS      current
DESCRIPTION
"Identifier"
 ::= { psCb1  1 }

psCb1Des OBJECT-TYPE
SYNTAX      DisplayString
MAX-ACCESS  read-write
STATUS      current
DESCRIPTION
"Description"
 ::= { psCb1  2 }

psCb1Stt OBJECT-TYPE
SYNTAX      INTEGER {
off(0),
on(1)
}
MAX-ACCESS  read-write
STATUS      current
DESCRIPTION
"State
Values:
off(0),
on(1)
"
 ::= { psCb1  3 }

psCb1Ph1 OBJECT-TYPE
SYNTAX      DisplayString
MAX-ACCESS  read-write
STATUS      current
DESCRIPTION
"Call-Back Phone Number 1"
 ::= { psCb1  4 }

psCb1Br1 OBJECT-TYPE
SYNTAX      INTEGER {
b300(300),
b1200(1200),
b2400(2400),
b4800(4800),
b9600(9600),
b19200(19200)
}
MAX-ACCESS  read-write
STATUS      current
DESCRIPTION
"Connect Baudrate 1
Values:
b300(300),
b1200(1200),
b2400(2400),
b4800(4800),
b9600(9600),
b19200(19200)
"
 ::= { psCb1  5 }

psCb1Ph2 OBJECT-TYPE
SYNTAX      DisplayString
MAX-ACCESS  read-write
STATUS      current
DESCRIPTION
"Call-Back Phone Number 2"
 ::= { psCb1  6 }

psCb1Br2 OBJECT-TYPE
SYNTAX      INTEGER {
b300(300),
b1200(1200),
b2400(2400),
b4800(4800),
b9600(9600),
b19200(19200)
}
MAX-ACCESS  read-write
STATUS      current
DESCRIPTION
"Connect Baudrate 2
Values:
b300(300),
b1200(1200),
b2400(2400),
b4800(4800),
b9600(9600),
b19200(19200)
"
 ::= { psCb1  7 }

psCb1Ph3 OBJECT-TYPE
SYNTAX      DisplayString
MAX-ACCESS  read-write
STATUS      current
DESCRIPTION
"Call-Back Phone Number 3"
 ::= { psCb1  8 }

psCb1Br3 OBJECT-TYPE
SYNTAX      INTEGER {
b300(300),
b1200(1200),
b2400(2400),
b4800(4800),
b9600(9600),
b19200(19200)
}
MAX-ACCESS  read-write
STATUS      current
DESCRIPTION
"Connect Baudrate 3
Values:
b300(300),
b1200(1200),
b2400(2400),
b4800(4800),
b9600(9600),
b19200(19200)
"
 ::= { psCb1  9 }

psCb1Ph4 OBJECT-TYPE
SYNTAX      DisplayString
MAX-ACCESS  read-write
STATUS      current
DESCRIPTION
"Call-Back Phone Number 4"
 ::= { psCb1  10 }

psCb1Br4 OBJECT-TYPE
SYNTAX      INTEGER {
b300(300),
b1200(1200),
b2400(2400),
b4800(4800),
b9600(9600),
b19200(19200)
}
MAX-ACCESS  read-write
STATUS      current
DESCRIPTION
"Connect Baudrate 4
Values:
b300(300),
b1200(1200),
b2400(2400),
b4800(4800),
b9600(9600),
b19200(19200)
"
 ::= { psCb1  11 }

psCb1Ph5 OBJECT-TYPE
SYNTAX      DisplayString
MAX-ACCESS  read-write
STATUS      current
DESCRIPTION
"Call-Back Phone Number 5"
 ::= { psCb1  12 }

psCb1Br5 OBJECT-TYPE
SYNTAX      INTEGER {
b300(300),
b1200(1200),
b2400(2400),
b4800(4800),
b9600(9600),
b19200(19200)
}
MAX-ACCESS  read-write
STATUS      current
DESCRIPTION
"Connect Baudrate 5
Values:
b300(300),
b1200(1200),
b2400(2400),
b4800(4800),
b9600(9600),
b19200(19200)
"
 ::= { psCb1  13 }


--
-- object psMp1
--

psMp1 OBJECT IDENTIFIER  ::= { powerSystem  32 }

psMp1Ide OBJECT-TYPE
SYNTAX      DisplayString
MAX-ACCESS  read-only
STATUS      current
DESCRIPTION
"Identifier"
 ::= { psMp1  1 }

psMp1Des OBJECT-TYPE
SYNTAX      DisplayString
MAX-ACCESS  read-write
STATUS      current
DESCRIPTION
"Description"
 ::= { psMp1  2 }

psMp1Stt OBJECT-TYPE
SYNTAX      DisplayString
MAX-ACCESS  read-only
STATUS      current
DESCRIPTION
"State"
 ::= { psMp1  3 }

psMp1Dbt OBJECT-TYPE
SYNTAX      INTEGER {
d7(7),
d8(8)
}
MAX-ACCESS  read-write
STATUS      current
DESCRIPTION
"Data Bits
Values:
d7(7),
d8(8)
"
 ::= { psMp1  4 }

psMp1Pry OBJECT-TYPE
SYNTAX      DisplayString
MAX-ACCESS  read-write
STATUS      current
DESCRIPTION
"Parity
Values:
O,
E,
N
"
 ::= { psMp1  5 }

psMp1Sbt OBJECT-TYPE
SYNTAX      INTEGER {
s1(1),
s2(2)
}
MAX-ACCESS  read-write
STATUS      current
DESCRIPTION
"Stop Bits
Values:
s1(1),
s2(2)
"
 ::= { psMp1  6 }

psMp1Tmo OBJECT-TYPE
SYNTAX      Integer32(0..45)
MAX-ACCESS  read-write
STATUS      current
DESCRIPTION
"Time-Out"
 ::= { psMp1  7 }

psMp1Hsh OBJECT-TYPE
SYNTAX      DisplayString
MAX-ACCESS  read-write
STATUS      current
DESCRIPTION
"Handshaking
Values:
NO,
SW
"
 ::= { psMp1  8 }

psMp1Nrg OBJECT-TYPE
SYNTAX      Integer32(2..15)
MAX-ACCESS  read-write
STATUS      current
DESCRIPTION
"Number of Rings Before Answer"
 ::= { psMp1  9 }

psMp1Wre OBJECT-TYPE
SYNTAX      INTEGER {
disable(0),
enable(1)
}
MAX-ACCESS  read-write
STATUS      current
DESCRIPTION
"Write Enable
Values:
disable(0),
enable(1)
"
 ::= { psMp1  10 }

psMp1Ins OBJECT-TYPE
SYNTAX      DisplayString
MAX-ACCESS  read-write
STATUS      current
DESCRIPTION
"Modem Init String"
 ::= { psMp1  11 }


--
-- object psLp1
--

psLp1 OBJECT IDENTIFIER  ::= { powerSystem  33 }

psLp1Ide OBJECT-TYPE
SYNTAX      DisplayString
MAX-ACCESS  read-only
STATUS      current
DESCRIPTION
"Identifier"
 ::= { psLp1  1 }

psLp1Des OBJECT-TYPE
SYNTAX      DisplayString
MAX-ACCESS  read-write
STATUS      current
DESCRIPTION
"Description"
 ::= { psLp1  2 }

psLp1Stt OBJECT-TYPE
SYNTAX      DisplayString
MAX-ACCESS  read-only
STATUS      current
DESCRIPTION
"State"
 ::= { psLp1  3 }

psLp1Bdr OBJECT-TYPE
SYNTAX      INTEGER {
b300(300),
b1200(1200),
b2400(2400),
b4800(4800),
b9600(9600),
b19200(19200)
}
MAX-ACCESS  read-write
STATUS      current
DESCRIPTION
"Baudrate
Values:
b300(300),
b1200(1200),
b2400(2400),
b4800(4800),
b9600(9600),
b19200(19200)
"
 ::= { psLp1  4 }

psLp1Dbt OBJECT-TYPE
SYNTAX      INTEGER {
d7(7),
d8(8)
}
MAX-ACCESS  read-write
STATUS      current
DESCRIPTION
"Data Bits
Values:
d7(7),
d8(8)
"
 ::= { psLp1  5 }

psLp1Pry OBJECT-TYPE
SYNTAX      DisplayString
MAX-ACCESS  read-write
STATUS      current
DESCRIPTION
"Parity
Values:
O,
E,
N
"
 ::= { psLp1  6 }

psLp1Sbt OBJECT-TYPE
SYNTAX      INTEGER {
s1(1),
s2(2)
}
MAX-ACCESS  read-write
STATUS      current
DESCRIPTION
"Stop Bits
Values:
s1(1),
s2(2)
"
 ::= { psLp1  7 }

psLp1Tmo OBJECT-TYPE
SYNTAX      Integer32(0..45)
MAX-ACCESS  read-write
STATUS      current
DESCRIPTION
"Time-Out"
 ::= { psLp1  8 }

psLp1Hsh OBJECT-TYPE
SYNTAX      DisplayString
MAX-ACCESS  read-write
STATUS      current
DESCRIPTION
"Handshaking
Values:
NO,
HW,
SW
"
 ::= { psLp1  9 }

psLp1App OBJECT-TYPE
SYNTAX      DisplayString
MAX-ACCESS  read-write
STATUS      current
DESCRIPTION
"Application
Values:
TERMINAL,
EVENT LOG
"
 ::= { psLp1  10 }

psLp1Wre OBJECT-TYPE
SYNTAX      INTEGER {
disable(0),
enable(1)
}
MAX-ACCESS  read-write
STATUS      current
DESCRIPTION
"Write Enable
Values:
disable(0),
enable(1)
"
 ::= { psLp1  11 }


--
-- object psAu1
--

psAu1 OBJECT IDENTIFIER  ::= { powerSystem  34 }

psAu1Ide OBJECT-TYPE
SYNTAX      DisplayString
MAX-ACCESS  read-only
STATUS      current
DESCRIPTION
"Identifier"
 ::= { psAu1  1 }

psAu1Des OBJECT-TYPE
SYNTAX      DisplayString
MAX-ACCESS  read-write
STATUS      current
DESCRIPTION
"Description"
 ::= { psAu1  2 }

psAu1Stt OBJECT-TYPE
SYNTAX      DisplayString
MAX-ACCESS  read-only
STATUS      current
DESCRIPTION
"State"
 ::= { psAu1  3 }

psAu1Bdr OBJECT-TYPE
SYNTAX      INTEGER {
b300(300),
b1200(1200),
b2400(2400),
b4800(4800),
b9600(9600),
b19200(19200)
}
MAX-ACCESS  read-write
STATUS      current
DESCRIPTION
"Baudrate
Values:
b300(300),
b1200(1200),
b2400(2400),
b4800(4800),
b9600(9600),
b19200(19200)
"
 ::= { psAu1  4 }

psAu1Dbt OBJECT-TYPE
SYNTAX      INTEGER {
d7(7),
d8(8)
}
MAX-ACCESS  read-write
STATUS      current
DESCRIPTION
"Data Bits
Values:
d7(7),
d8(8)
"
 ::= { psAu1  5 }

psAu1Pry OBJECT-TYPE
SYNTAX      DisplayString
MAX-ACCESS  read-write
STATUS      current
DESCRIPTION
"Parity
Values:
O,
E,
N
"
 ::= { psAu1  6 }

psAu1Sbt OBJECT-TYPE
SYNTAX      INTEGER {
s1(1),
s2(2)
}
MAX-ACCESS  read-write
STATUS      current
DESCRIPTION
"Stop Bits
Values:
s1(1),
s2(2)
"
 ::= { psAu1  7 }

psAu1Tmo OBJECT-TYPE
SYNTAX      Integer32(0..45)
MAX-ACCESS  read-write
STATUS      current
DESCRIPTION
"Time-Out"
 ::= { psAu1  8 }

psAu1Hsh OBJECT-TYPE
SYNTAX      DisplayString
MAX-ACCESS  read-write
STATUS      current
DESCRIPTION
"Handshaking
Values:
NO,
HW,
SW
"
 ::= { psAu1  9 }

psAu1App OBJECT-TYPE
SYNTAX      DisplayString
MAX-ACCESS  read-write
STATUS      current
DESCRIPTION
"Application
Values:
TERMINAL,
TL1,
SAPO
"
 ::= { psAu1  10 }

psAu1Wre OBJECT-TYPE
SYNTAX      INTEGER {
disable(0),
enable(1)
}
MAX-ACCESS  read-write
STATUS      current
DESCRIPTION
"Write Enable
Values:
disable(0),
enable(1)
"
 ::= { psAu1  11 }


--
-- table NPD
--

psNpdTable    OBJECT-TYPE
SYNTAX SEQUENCE OF PsNpdEntry
MAX-ACCESS not-accessible
STATUS current
DESCRIPTION
        "Table of all Notepad data"
 ::= { powerSystem  35 }

psNpdEntry OBJECT-TYPE
SYNTAX     PsNpdEntry
MAX-ACCESS  not-accessible
STATUS      current
DESCRIPTION
       "Entry of information for one Notepad"
INDEX { psNpdEntryIndex }
 ::= { psNpdTable  1 }

PsNpdEntry ::= SEQUENCE {
psNpdEntryIndex   INTEGER,
psNpdEntryIde   DisplayString,
psNpdEntryDes   DisplayString,
psNpdEntryStt   INTEGER,
psNpdEntryCl01   DisplayString,
psNpdEntryCl02   DisplayString,
psNpdEntryCl03   DisplayString,
psNpdEntryCl04   DisplayString,
psNpdEntryCl05   DisplayString,
psNpdEntryCl06   DisplayString,
psNpdEntryCl07   DisplayString,
psNpdEntryCl08   DisplayString,
psNpdEntryCl09   DisplayString,
psNpdEntryCl10   DisplayString,
psNpdEntryCl11   DisplayString,
psNpdEntryCl12   DisplayString,
psNpdEntryCl13   DisplayString,
psNpdEntryCl14   DisplayString,
psNpdEntryCl15   DisplayString
}

psNpdEntryIndex OBJECT-TYPE
SYNTAX      INTEGER (0..2147483647)
MAX-ACCESS  read-only
STATUS      current
DESCRIPTION
"Table Index"
 ::= { psNpdEntry  1 }

psNpdEntryIde OBJECT-TYPE
SYNTAX      DisplayString
MAX-ACCESS  read-only
STATUS      current
DESCRIPTION
"Identifier"
 ::= { psNpdEntry  2 }

psNpdEntryDes OBJECT-TYPE
SYNTAX      DisplayString
MAX-ACCESS  read-write
STATUS      current
DESCRIPTION
"Description"
 ::= { psNpdEntry  3 }

psNpdEntryStt OBJECT-TYPE
SYNTAX      INTEGER {
no(0),
yes(1)
}
MAX-ACCESS  read-write
STATUS      current
DESCRIPTION
"Notify
Values:
no(0),
yes(1)
"
 ::= { psNpdEntry  4 }

psNpdEntryCl01 OBJECT-TYPE
SYNTAX      DisplayString
MAX-ACCESS  read-write
STATUS      current
DESCRIPTION
"Comment Line 1"
 ::= { psNpdEntry  5 }

psNpdEntryCl02 OBJECT-TYPE
SYNTAX      DisplayString
MAX-ACCESS  read-write
STATUS      current
DESCRIPTION
"Comment Line 2"
 ::= { psNpdEntry  6 }

psNpdEntryCl03 OBJECT-TYPE
SYNTAX      DisplayString
MAX-ACCESS  read-write
STATUS      current
DESCRIPTION
"Comment Line 3"
 ::= { psNpdEntry  7 }

psNpdEntryCl04 OBJECT-TYPE
SYNTAX      DisplayString
MAX-ACCESS  read-write
STATUS      current
DESCRIPTION
"Comment Line 4"
 ::= { psNpdEntry  8 }

psNpdEntryCl05 OBJECT-TYPE
SYNTAX      DisplayString
MAX-ACCESS  read-write
STATUS      current
DESCRIPTION
"Comment Line 5"
 ::= { psNpdEntry  9 }

psNpdEntryCl06 OBJECT-TYPE
SYNTAX      DisplayString
MAX-ACCESS  read-write
STATUS      current
DESCRIPTION
"Comment Line 6"
 ::= { psNpdEntry  10 }

psNpdEntryCl07 OBJECT-TYPE
SYNTAX      DisplayString
MAX-ACCESS  read-write
STATUS      current
DESCRIPTION
"Comment Line 7"
 ::= { psNpdEntry  11 }

psNpdEntryCl08 OBJECT-TYPE
SYNTAX      DisplayString
MAX-ACCESS  read-write
STATUS      current
DESCRIPTION
"Comment Line 8"
 ::= { psNpdEntry  12 }

psNpdEntryCl09 OBJECT-TYPE
SYNTAX      DisplayString
MAX-ACCESS  read-write
STATUS      current
DESCRIPTION
"Comment Line 9"
 ::= { psNpdEntry  13 }

psNpdEntryCl10 OBJECT-TYPE
SYNTAX      DisplayString
MAX-ACCESS  read-write
STATUS      current
DESCRIPTION
"Comment Line 10"
 ::= { psNpdEntry  14 }

psNpdEntryCl11 OBJECT-TYPE
SYNTAX      DisplayString
MAX-ACCESS  read-write
STATUS      current
DESCRIPTION
"Comment Line 11"
 ::= { psNpdEntry  15 }

psNpdEntryCl12 OBJECT-TYPE
SYNTAX      DisplayString
MAX-ACCESS  read-write
STATUS      current
DESCRIPTION
"Comment Line 12"
 ::= { psNpdEntry  16 }

psNpdEntryCl13 OBJECT-TYPE
SYNTAX      DisplayString
MAX-ACCESS  read-write
STATUS      current
DESCRIPTION
"Comment Line 13"
 ::= { psNpdEntry  17 }

psNpdEntryCl14 OBJECT-TYPE
SYNTAX      DisplayString
MAX-ACCESS  read-write
STATUS      current
DESCRIPTION
"Comment Line 14"
 ::= { psNpdEntry  18 }

psNpdEntryCl15 OBJECT-TYPE
SYNTAX      DisplayString
MAX-ACCESS  read-write
STATUS      current
DESCRIPTION
"Comment Line 15"
 ::= { psNpdEntry  19 }



--
-- table DSW
--

psDswTable    OBJECT-TYPE
SYNTAX SEQUENCE OF PsDswEntry
MAX-ACCESS not-accessible
STATUS current
DESCRIPTION
        "Table of all Data Switch data"
 ::= { powerSystem  36 }

psDswEntry OBJECT-TYPE
SYNTAX     PsDswEntry
MAX-ACCESS  not-accessible
STATUS      current
DESCRIPTION
       "Entry of information for one Data Switch"
INDEX { psDswEntryIndex }
 ::= { psDswTable  1 }

PsDswEntry ::= SEQUENCE {
psDswEntryIndex   INTEGER,
psDswEntryIde   DisplayString,
psDswEntryDes   DisplayString,
psDswEntryCid   DisplayString,
psDswEntryStt   DisplayString,
psDswEntryRen   INTEGER,
psDswEntryBdr   INTEGER,
psDswEntryDbt   INTEGER,
psDswEntryPry   DisplayString,
psDswEntrySbt   INTEGER,
psDswEntryHsh   DisplayString,
psDswEntryDsr   DisplayString,
psDswEntryHdr   DisplayString,
psDswEntryApr   DisplayString,
psDswEntryPwd   DisplayString,
psDswEntryAcm   DisplayString,
psDswEntryHuc   DisplayString,
psDswEntryCea   DisplayString
}

psDswEntryIndex OBJECT-TYPE
SYNTAX      INTEGER (0..2147483647)
MAX-ACCESS  read-only
STATUS      current
DESCRIPTION
"Table Index"
 ::= { psDswEntry  1 }

psDswEntryIde OBJECT-TYPE
SYNTAX      DisplayString
MAX-ACCESS  read-only
STATUS      current
DESCRIPTION
"Identifier"
 ::= { psDswEntry  2 }

psDswEntryDes OBJECT-TYPE
SYNTAX      DisplayString
MAX-ACCESS  read-write
STATUS      current
DESCRIPTION
"Description"
 ::= { psDswEntry  3 }

psDswEntryCid OBJECT-TYPE
SYNTAX      DisplayString
MAX-ACCESS  read-write
STATUS      current
DESCRIPTION
"Connected Equipment ID"
 ::= { psDswEntry  4 }

psDswEntryStt OBJECT-TYPE
SYNTAX      DisplayString
MAX-ACCESS  read-write
STATUS      current
DESCRIPTION
"State
Values:
IDLE,
REPORTING,
PASS-THRU,
N/A
"
 ::= { psDswEntry  5 }

psDswEntryRen OBJECT-TYPE
SYNTAX      INTEGER {
disable(0),
enable(1)
}
MAX-ACCESS  read-write
STATUS      current
DESCRIPTION
"Reporting Enable
Values:
disable(0),
enable(1)
"
 ::= { psDswEntry  6 }

psDswEntryBdr OBJECT-TYPE
SYNTAX      INTEGER {
b300(300),
b1200(1200),
b2400(2400),
b4800(4800),
b9600(9600),
b19200(19200)
}
MAX-ACCESS  read-write
STATUS      current
DESCRIPTION
"Connect Baudrate
Values:
b300(300),
b1200(1200),
b2400(2400),
b4800(4800),
b9600(9600),
b19200(19200)
"
 ::= { psDswEntry  7 }

psDswEntryDbt OBJECT-TYPE
SYNTAX      INTEGER {
d7(7),
d8(8)
}
MAX-ACCESS  read-write
STATUS      current
DESCRIPTION
"Data Bits
Values:
d7(7),
d8(8)
"
 ::= { psDswEntry  8 }

psDswEntryPry OBJECT-TYPE
SYNTAX      DisplayString
MAX-ACCESS  read-write
STATUS      current
DESCRIPTION
"Parity
Values:
O,
E,
N
"
 ::= { psDswEntry  9 }

psDswEntrySbt OBJECT-TYPE
SYNTAX      INTEGER {
s1(1),
s2(2)
}
MAX-ACCESS  read-write
STATUS      current
DESCRIPTION
"Stop Bits
Values:
s1(1),
s2(2)
"
 ::= { psDswEntry  10 }

psDswEntryHsh OBJECT-TYPE
SYNTAX      DisplayString
MAX-ACCESS  read-write
STATUS      current
DESCRIPTION
"Handshake
Values:
NO,
HW,
SW
"
 ::= { psDswEntry  11 }

psDswEntryDsr OBJECT-TYPE
SYNTAX      DisplayString
MAX-ACCESS  read-write
STATUS      current
DESCRIPTION
"Monitor DSR Signal"
 ::= { psDswEntry  12 }

psDswEntryHdr OBJECT-TYPE
SYNTAX      DisplayString
MAX-ACCESS  read-write
STATUS      current
DESCRIPTION
"Alarm Header Length"
 ::= { psDswEntry  13 }

psDswEntryApr OBJECT-TYPE
SYNTAX      DisplayString
MAX-ACCESS  read-write
STATUS      current
DESCRIPTION
"Attention Prompt"
 ::= { psDswEntry  14 }

psDswEntryPwd OBJECT-TYPE
SYNTAX      DisplayString
MAX-ACCESS  read-write
STATUS      current
DESCRIPTION
"Password"
 ::= { psDswEntry  15 }

psDswEntryAcm OBJECT-TYPE
SYNTAX      DisplayString
MAX-ACCESS  read-write
STATUS      current
DESCRIPTION
"Alarms Command"
 ::= { psDswEntry  16 }

psDswEntryHuc OBJECT-TYPE
SYNTAX      DisplayString
MAX-ACCESS  read-write
STATUS      current
DESCRIPTION
"Hangup Command"
 ::= { psDswEntry  17 }

psDswEntryCea OBJECT-TYPE
SYNTAX      DisplayString
MAX-ACCESS  read-only
STATUS      current
DESCRIPTION
"Connected Equipment Alarm"
 ::= { psDswEntry  18 }



--
-- object psNcc1
--

psNcc1 OBJECT IDENTIFIER  ::= { powerSystem  37 }

psNcc1Brd OBJECT-TYPE
SYNTAX      DisplayString
MAX-ACCESS  read-only
STATUS      current
DESCRIPTION
"Board Code"
 ::= { psNcc1  1 }

psNcc1Sn OBJECT-TYPE
SYNTAX      DisplayString
MAX-ACCESS  read-only
STATUS      current
DESCRIPTION
"Serial Number"
 ::= { psNcc1  2 }

psNcc1Key OBJECT-TYPE
SYNTAX      DisplayString
MAX-ACCESS  read-write
STATUS      current
DESCRIPTION
"Feature Key"
 ::= { psNcc1  3 }

psNcc1Post OBJECT-TYPE
SYNTAX      DisplayString
MAX-ACCESS  read-only
STATUS      current
DESCRIPTION
"Power-on Self Test"
 ::= { psNcc1  4 }


--
-- object psNet1
--

psNet1 OBJECT IDENTIFIER  ::= { powerSystem  38 }

psNet1Ead OBJECT-TYPE
SYNTAX      DisplayString
MAX-ACCESS  read-only
STATUS      current
DESCRIPTION
"Ethernet Address"
 ::= { psNet1  1 }

psNet1Ip OBJECT-TYPE
SYNTAX      DisplayString
MAX-ACCESS  read-write
STATUS      current
DESCRIPTION
"IP Address"
 ::= { psNet1  2 }

psNet1Sub OBJECT-TYPE
SYNTAX      DisplayString
MAX-ACCESS  read-write
STATUS      current
DESCRIPTION
"Subnet Mask"
 ::= { psNet1  3 }

psNet1Gtwy OBJECT-TYPE
SYNTAX      DisplayString
MAX-ACCESS  read-write
STATUS      current
DESCRIPTION
"Default Gateway"
 ::= { psNet1  4 }

psNet1Host OBJECT-TYPE
SYNTAX      DisplayString
MAX-ACCESS  read-write
STATUS      current
DESCRIPTION
"Host Name"
 ::= { psNet1  5 }

psNet1Dhcp OBJECT-TYPE
SYNTAX      INTEGER {
static(0),
client(1),
server(3)
}
MAX-ACCESS  read-write
STATUS      current
DESCRIPTION
"DHCP Mode
Values:
static(0),
client(1),
server(3)
"
 ::= { psNet1  6 }

psNet1Wip OBJECT-TYPE
SYNTAX      DisplayString
MAX-ACCESS  read-write
STATUS      current
DESCRIPTION
"Working IP address"
 ::= { psNet1  7 }

psNet1Msrv OBJECT-TYPE
SYNTAX      DisplayString
MAX-ACCESS  read-write
STATUS      current
DESCRIPTION
"Mailhost IP Address"
 ::= { psNet1  8 }

psNet1Dns OBJECT-TYPE
SYNTAX      DisplayString
MAX-ACCESS  read-write
STATUS      current
DESCRIPTION
"DNS Server IP Address"
 ::= { psNet1  9 }

psNet1Dom OBJECT-TYPE
SYNTAX      DisplayString
MAX-ACCESS  read-write
STATUS      current
DESCRIPTION
"Domain Name"
 ::= { psNet1  10 }

psNet1Tmo OBJECT-TYPE
SYNTAX      Integer32(1..45)
UNITS       "Minutes"
MAX-ACCESS  read-write
STATUS      current
DESCRIPTION
"Session Timeout (Minutes)"
 ::= { psNet1  11 }

psNet1Wre OBJECT-TYPE
SYNTAX      INTEGER {
disable(0),
enable(1)
}
MAX-ACCESS  read-write
STATUS      current
DESCRIPTION
"Write Enable
Values:
disable(0),
enable(1)
"
 ::= { psNet1  12 }

psNet1Ntp OBJECT-TYPE
SYNTAX      DisplayString
MAX-ACCESS  read-write
STATUS      current
DESCRIPTION
"Time Server Address"
 ::= { psNet1  13 }


--
-- object psNam1
--

psNam1 OBJECT IDENTIFIER  ::= { powerSystem  39 }

psNam1Sev OBJECT-TYPE
SYNTAX      DisplayString
MAX-ACCESS  read-write
STATUS      current
DESCRIPTION
"Notification Severity
Values:
NONE,
CRIT,
MAJ+,
MIN+
"
 ::= { psNam1  1 }

psNam1Psh1 OBJECT-TYPE
SYNTAX      DisplayString
MAX-ACCESS  read-write
STATUS      current
DESCRIPTION
"Push Address 1"
 ::= { psNam1  2 }

psNam1Psh2 OBJECT-TYPE
SYNTAX      DisplayString
MAX-ACCESS  read-write
STATUS      current
DESCRIPTION
"Push Address 2"
 ::= { psNam1  3 }

psNam1Psh3 OBJECT-TYPE
SYNTAX      DisplayString
MAX-ACCESS  read-write
STATUS      current
DESCRIPTION
"Push Address 3"
 ::= { psNam1  4 }

psNam1Msrv OBJECT-TYPE
SYNTAX      DisplayString
MAX-ACCESS  read-write
STATUS      current
DESCRIPTION
"Mail Server Address"
 ::= { psNam1  5 }

psNam1Em1 OBJECT-TYPE
SYNTAX      DisplayString
MAX-ACCESS  read-write
STATUS      current
DESCRIPTION
"Email Address 1"
 ::= { psNam1  6 }

psNam1Em2 OBJECT-TYPE
SYNTAX      DisplayString
MAX-ACCESS  read-write
STATUS      current
DESCRIPTION
"Email Address 2"
 ::= { psNam1  7 }

psNam1Em3 OBJECT-TYPE
SYNTAX      DisplayString
MAX-ACCESS  read-write
STATUS      current
DESCRIPTION
"Email Address 3"
 ::= { psNam1  8 }

psNam1Pg1 OBJECT-TYPE
SYNTAX      DisplayString
MAX-ACCESS  read-write
STATUS      current
DESCRIPTION
"Pager Address 1"
 ::= { psNam1  9 }

psNam1Pg2 OBJECT-TYPE
SYNTAX      DisplayString
MAX-ACCESS  read-write
STATUS      current
DESCRIPTION
"Pager Address 2"
 ::= { psNam1  10 }

psNam1Pg3 OBJECT-TYPE
SYNTAX      DisplayString
MAX-ACCESS  read-write
STATUS      current
DESCRIPTION
"Pager Address 3"
 ::= { psNam1  11 }


--
-- object psNsm1
--

psNsm1 OBJECT IDENTIFIER  ::= { powerSystem  40 }

psNsm1Idle OBJECT-TYPE
SYNTAX      DisplayString
MAX-ACCESS  read-write
STATUS      current
DESCRIPTION
"Idle Connection Time-out"
 ::= { psNsm1  1 }

psNsm1Suse OBJECT-TYPE
SYNTAX      INTEGER {
disable(0),
enable(1)
}
MAX-ACCESS  read-write
STATUS      current
DESCRIPTION
"Super-user IP Source Enable
Values:
disable(0),
enable(1)
"
 ::= { psNsm1  2 }

psNsm1Sus1 OBJECT-TYPE
SYNTAX      DisplayString
MAX-ACCESS  read-write
STATUS      current
DESCRIPTION
"Super-user IP Source 1"
 ::= { psNsm1  3 }

psNsm1Sus2 OBJECT-TYPE
SYNTAX      DisplayString
MAX-ACCESS  read-write
STATUS      current
DESCRIPTION
"Super-user IP Source 2"
 ::= { psNsm1  4 }

psNsm1Sus3 OBJECT-TYPE
SYNTAX      DisplayString
MAX-ACCESS  read-write
STATUS      current
DESCRIPTION
"Super-user IP Source 3"
 ::= { psNsm1  5 }

psNsm1Sus4 OBJECT-TYPE
SYNTAX      DisplayString
MAX-ACCESS  read-write
STATUS      current
DESCRIPTION
"Super-user IP Source 4"
 ::= { psNsm1  6 }

psNsm1Sus5 OBJECT-TYPE
SYNTAX      DisplayString
MAX-ACCESS  read-write
STATUS      current
DESCRIPTION
"Super-user IP Source 5"
 ::= { psNsm1  7 }


--
-- table DRC
--

psDrcTable    OBJECT-TYPE
SYNTAX SEQUENCE OF PsDrcEntry
MAX-ACCESS not-accessible
STATUS current
DESCRIPTION
        "Table of all Derived Channel data"
 ::= { powerSystem  41 }

psDrcEntry OBJECT-TYPE
SYNTAX     PsDrcEntry
MAX-ACCESS  not-accessible
STATUS      current
DESCRIPTION
       "Entry of information for one Derived Channel"
INDEX { psDrcEntryIndex }
 ::= { psDrcTable  1 }

PsDrcEntry ::= SEQUENCE {
psDrcEntryIndex   INTEGER,
psDrcEntryIde   DisplayString,
psDrcEntryDes   DisplayString,
psDrcEntryVal   DisplayString,
psDrcEntryPrg   DisplayString,
psDrcEntryUni   DisplayString
}

psDrcEntryIndex OBJECT-TYPE
SYNTAX      INTEGER (0..2147483647)
MAX-ACCESS  read-only
STATUS      current
DESCRIPTION
"Table Index"
 ::= { psDrcEntry  1 }

psDrcEntryIde OBJECT-TYPE
SYNTAX      DisplayString
MAX-ACCESS  read-only
STATUS      current
DESCRIPTION
"Identifier"
 ::= { psDrcEntry  2 }

psDrcEntryDes OBJECT-TYPE
SYNTAX      DisplayString
MAX-ACCESS  read-write
STATUS      current
DESCRIPTION
"Description"
 ::= { psDrcEntry  3 }

psDrcEntryVal OBJECT-TYPE
SYNTAX      DisplayString
MAX-ACCESS  read-only
STATUS      current
DESCRIPTION
"Value"
 ::= { psDrcEntry  4 }

psDrcEntryPrg OBJECT-TYPE
SYNTAX      DisplayString
MAX-ACCESS  read-write
STATUS      current
DESCRIPTION
"Program Line"
 ::= { psDrcEntry  5 }

psDrcEntryUni OBJECT-TYPE
SYNTAX      DisplayString
MAX-ACCESS  read-write
STATUS      current
DESCRIPTION
"Unit"
 ::= { psDrcEntry  6 }



--
-- table BCM
--

psBcmTable    OBJECT-TYPE
SYNTAX SEQUENCE OF PsBcmEntry
MAX-ACCESS not-accessible
STATUS current
DESCRIPTION
        "Table of all Bay Current Monitor data"
 ::= { powerSystem  42 }

psBcmEntry OBJECT-TYPE
SYNTAX     PsBcmEntry
MAX-ACCESS  not-accessible
STATUS      current
DESCRIPTION
       "Entry of information for one Bay Current Monitor"
INDEX { psBcmEntryIndex }
 ::= { psBcmTable  1 }

PsBcmEntry ::= SEQUENCE {
psBcmEntryIndex   INTEGER,
psBcmEntryIde   DisplayString,
psBcmEntryDes   DisplayString,
psBcmEntryVal   DisplayString,
psBcmEntrySht   DisplayString,
psBcmEntrySha   Integer32,
psBcmEntryShv   Integer32
}

psBcmEntryIndex OBJECT-TYPE
SYNTAX      INTEGER (0..2147483647)
MAX-ACCESS  read-only
STATUS      current
DESCRIPTION
"Table Index"
 ::= { psBcmEntry  1 }

psBcmEntryIde OBJECT-TYPE
SYNTAX      DisplayString
MAX-ACCESS  read-only
STATUS      current
DESCRIPTION
"Identifier"
 ::= { psBcmEntry  2 }

psBcmEntryDes OBJECT-TYPE
SYNTAX      DisplayString
MAX-ACCESS  read-write
STATUS      current
DESCRIPTION
"Description"
 ::= { psBcmEntry  3 }

psBcmEntryVal OBJECT-TYPE
SYNTAX      DisplayString
MAX-ACCESS  read-only
STATUS      current
DESCRIPTION
"Value"
 ::= { psBcmEntry  4 }

psBcmEntrySht OBJECT-TYPE
SYNTAX      DisplayString
MAX-ACCESS  read-write
STATUS      current
DESCRIPTION
"Shunt Type
Values:
LOAD,
BATTERY,
NONE
"
 ::= { psBcmEntry  5 }

psBcmEntrySha OBJECT-TYPE
SYNTAX      Integer32
MAX-ACCESS  read-write
STATUS      current
DESCRIPTION
"Shunt Current"
 ::= { psBcmEntry  6 }

psBcmEntryShv OBJECT-TYPE
SYNTAX      Integer32(1..150)
MAX-ACCESS  read-write
STATUS      current
DESCRIPTION
"Shunt Voltage"
 ::= { psBcmEntry  7 }



--
-- table BVM
--

psBvmTable    OBJECT-TYPE
SYNTAX SEQUENCE OF PsBvmEntry
MAX-ACCESS not-accessible
STATUS current
DESCRIPTION
        "Table of all Bay Voltage Monitor data"
 ::= { powerSystem  43 }

psBvmEntry OBJECT-TYPE
SYNTAX     PsBvmEntry
MAX-ACCESS  not-accessible
STATUS      current
DESCRIPTION
       "Entry of information for one Bay Voltage Monitor"
INDEX { psBvmEntryIndex }
 ::= { psBvmTable  1 }

PsBvmEntry ::= SEQUENCE {
psBvmEntryIndex   INTEGER,
psBvmEntryIde   DisplayString,
psBvmEntryDes   DisplayString,
psBvmEntryVal   Integer32
}

psBvmEntryIndex OBJECT-TYPE
SYNTAX      INTEGER (0..2147483647)
MAX-ACCESS  read-only
STATUS      current
DESCRIPTION
"Table Index"
 ::= { psBvmEntry  1 }

psBvmEntryIde OBJECT-TYPE
SYNTAX      DisplayString
MAX-ACCESS  read-only
STATUS      current
DESCRIPTION
"Identifier"
 ::= { psBvmEntry  2 }

psBvmEntryDes OBJECT-TYPE
SYNTAX      DisplayString
MAX-ACCESS  read-write
STATUS      current
DESCRIPTION
"Description"
 ::= { psBvmEntry  3 }

psBvmEntryVal OBJECT-TYPE
SYNTAX      Integer32
MAX-ACCESS  read-only
STATUS      current
DESCRIPTION
"Value"
 ::= { psBvmEntry  4 }



--
-- table BTM
--

psBtmTable    OBJECT-TYPE
SYNTAX SEQUENCE OF PsBtmEntry
MAX-ACCESS not-accessible
STATUS current
DESCRIPTION
        "Table of all Bay Temperature Monitor data"
 ::= { powerSystem  44 }

psBtmEntry OBJECT-TYPE
SYNTAX     PsBtmEntry
MAX-ACCESS  not-accessible
STATUS      current
DESCRIPTION
       "Entry of information for one Bay Temperature Monitor"
INDEX { psBtmEntryIndex }
 ::= { psBtmTable  1 }

PsBtmEntry ::= SEQUENCE {
psBtmEntryIndex   INTEGER,
psBtmEntryIde   DisplayString,
psBtmEntryDes   DisplayString,
psBtmEntryVal   DisplayString,
psBtmEntryIbt   INTEGER
}

psBtmEntryIndex OBJECT-TYPE
SYNTAX      INTEGER (0..2147483647)
MAX-ACCESS  read-only
STATUS      current
DESCRIPTION
"Table Index"
 ::= { psBtmEntry  1 }

psBtmEntryIde OBJECT-TYPE
SYNTAX      DisplayString
MAX-ACCESS  read-only
STATUS      current
DESCRIPTION
"Identifier"
 ::= { psBtmEntry  2 }

psBtmEntryDes OBJECT-TYPE
SYNTAX      DisplayString
MAX-ACCESS  read-write
STATUS      current
DESCRIPTION
"Description"
 ::= { psBtmEntry  3 }

psBtmEntryVal OBJECT-TYPE
SYNTAX      DisplayString
MAX-ACCESS  read-only
STATUS      current
DESCRIPTION
"Value"
 ::= { psBtmEntry  4 }

psBtmEntryIbt OBJECT-TYPE
SYNTAX      INTEGER {
disable(0),
enable(1)
}
MAX-ACCESS  read-write
STATUS      current
DESCRIPTION
"Battery Temperature
Values:
disable(0),
enable(1)
"
 ::= { psBtmEntry  5 }



--
-- table RPM
--

psRpmTable    OBJECT-TYPE
SYNTAX SEQUENCE OF PsRpmEntry
MAX-ACCESS not-accessible
STATUS current
DESCRIPTION
        "Table of all Remote Peripheral Monitor data"
 ::= { powerSystem  45 }

psRpmEntry OBJECT-TYPE
SYNTAX     PsRpmEntry
MAX-ACCESS  not-accessible
STATUS      current
DESCRIPTION
       "Entry of information for one Remote Peripheral Monitor"
INDEX { psRpmEntryIndex }
 ::= { psRpmTable  1 }

PsRpmEntry ::= SEQUENCE {
psRpmEntryIndex   INTEGER,
psRpmEntryIde   DisplayString,
psRpmEntryDes   DisplayString,
psRpmEntrySer   DisplayString,
psRpmEntryStt   DisplayString,
psRpmEntryTyp   DisplayString,
psRpmEntryTlk   INTEGER,
psRpmEntryMor   DisplayString,
psRpmEntryMtc   DisplayString
}

psRpmEntryIndex OBJECT-TYPE
SYNTAX      INTEGER (0..2147483647)
MAX-ACCESS  read-only
STATUS      current
DESCRIPTION
"Table Index"
 ::= { psRpmEntry  1 }

psRpmEntryIde OBJECT-TYPE
SYNTAX      DisplayString
MAX-ACCESS  read-only
STATUS      current
DESCRIPTION
"Identifier"
 ::= { psRpmEntry  2 }

psRpmEntryDes OBJECT-TYPE
SYNTAX      DisplayString
MAX-ACCESS  read-write
STATUS      current
DESCRIPTION
"Description"
 ::= { psRpmEntry  3 }

psRpmEntrySer OBJECT-TYPE
SYNTAX      DisplayString
MAX-ACCESS  read-only
STATUS      current
DESCRIPTION
"Serial Number"
 ::= { psRpmEntry  4 }

psRpmEntryStt OBJECT-TYPE
SYNTAX      DisplayString
MAX-ACCESS  read-only
STATUS      current
DESCRIPTION
"Status"
 ::= { psRpmEntry  5 }

psRpmEntryTyp OBJECT-TYPE
SYNTAX      DisplayString
MAX-ACCESS  read-only
STATUS      current
DESCRIPTION
"Module Type"
 ::= { psRpmEntry  6 }

psRpmEntryTlk OBJECT-TYPE
SYNTAX      INTEGER {
no(0),
yes(1)
}
MAX-ACCESS  read-write
STATUS      current
DESCRIPTION
"Type Lock
Values:
no(0),
yes(1)
"
 ::= { psRpmEntry  7 }

psRpmEntryMor OBJECT-TYPE
SYNTAX      DisplayString
MAX-ACCESS  read-only
STATUS      current
DESCRIPTION
"Out of Range"
 ::= { psRpmEntry  8 }

psRpmEntryMtc OBJECT-TYPE
SYNTAX      DisplayString
MAX-ACCESS  read-only
STATUS      current
DESCRIPTION
"Type Conflict"
 ::= { psRpmEntry  9 }



--
-- table RPMC
--

psRpmcTable    OBJECT-TYPE
SYNTAX SEQUENCE OF PsRpmcEntry
MAX-ACCESS not-accessible
STATUS current
DESCRIPTION
        "Table of all RPM Channel data"
 ::= { powerSystem  46 }

psRpmcEntry OBJECT-TYPE
SYNTAX     PsRpmcEntry
MAX-ACCESS  not-accessible
STATUS      current
DESCRIPTION
       "Entry of information for one RPM Channel"
INDEX { psRpmcEntryIndex }
 ::= { psRpmcTable  1 }

PsRpmcEntry ::= SEQUENCE {
psRpmcEntryIndex   INTEGER,
psRpmcEntryIde   DisplayString,
psRpmcEntryDes   DisplayString,
psRpmcEntryStt   DisplayString,
psRpmcEntryTyp   DisplayString,
psRpmcEntryRng   DisplayString,
psRpmcEntryVal   DisplayString,
psRpmcEntryUni   DisplayString,
psRpmcEntryOfs   DisplayString,
psRpmcEntryScf   DisplayString,
psRpmcEntrySha   DisplayString,
psRpmcEntryShv   DisplayString,
psRpmcEntryPrg   DisplayString,
psRpmcEntryMor   DisplayString,
psRpmcEntryIbt   INTEGER
}

psRpmcEntryIndex OBJECT-TYPE
SYNTAX      INTEGER (0..2147483647)
MAX-ACCESS  read-only
STATUS      current
DESCRIPTION
"Table Index"
 ::= { psRpmcEntry  1 }

psRpmcEntryIde OBJECT-TYPE
SYNTAX      DisplayString
MAX-ACCESS  read-only
STATUS      current
DESCRIPTION
"Identifier"
 ::= { psRpmcEntry  2 }

psRpmcEntryDes OBJECT-TYPE
SYNTAX      DisplayString
MAX-ACCESS  read-write
STATUS      current
DESCRIPTION
"Description"
 ::= { psRpmcEntry  3 }

psRpmcEntryStt OBJECT-TYPE
SYNTAX      DisplayString
MAX-ACCESS  read-only
STATUS      current
DESCRIPTION
"Status"
 ::= { psRpmcEntry  4 }

psRpmcEntryTyp OBJECT-TYPE
SYNTAX      DisplayString
MAX-ACCESS  read-only
STATUS      current
DESCRIPTION
"Channel Type"
 ::= { psRpmcEntry  5 }

psRpmcEntryRng OBJECT-TYPE
SYNTAX      DisplayString
MAX-ACCESS  read-only
STATUS      current
DESCRIPTION
"Range"
 ::= { psRpmcEntry  6 }

psRpmcEntryVal OBJECT-TYPE
SYNTAX      DisplayString
MAX-ACCESS  read-only
STATUS      current
DESCRIPTION
"Value"
 ::= { psRpmcEntry  7 }

psRpmcEntryUni OBJECT-TYPE
SYNTAX      DisplayString
MAX-ACCESS  read-write
STATUS      current
DESCRIPTION
"Unit"
 ::= { psRpmcEntry  8 }

psRpmcEntryOfs OBJECT-TYPE
SYNTAX      DisplayString
MAX-ACCESS  read-write
STATUS      current
DESCRIPTION
"Offset"
 ::= { psRpmcEntry  9 }

psRpmcEntryScf OBJECT-TYPE
SYNTAX      DisplayString
MAX-ACCESS  read-write
STATUS      current
DESCRIPTION
"Scale Factor"
 ::= { psRpmcEntry  10 }

psRpmcEntrySha OBJECT-TYPE
SYNTAX      DisplayString
MAX-ACCESS  read-write
STATUS      current
DESCRIPTION
"Shunt Current"
 ::= { psRpmcEntry  11 }

psRpmcEntryShv OBJECT-TYPE
SYNTAX      DisplayString
MAX-ACCESS  read-write
STATUS      current
DESCRIPTION
"Shunt Voltage"
 ::= { psRpmcEntry  12 }

psRpmcEntryPrg OBJECT-TYPE
SYNTAX      DisplayString
MAX-ACCESS  read-write
STATUS      current
DESCRIPTION
"Program Line"
 ::= { psRpmcEntry  13 }

psRpmcEntryMor OBJECT-TYPE
SYNTAX      DisplayString
MAX-ACCESS  read-only
STATUS      current
DESCRIPTION
"Out of Range"
 ::= { psRpmcEntry  14 }

psRpmcEntryIbt OBJECT-TYPE
SYNTAX      INTEGER {
disable(0),
enable(1)
}
MAX-ACCESS  read-write
STATUS      current
DESCRIPTION
"Battery Temperature
Values:
disable(0),
enable(1)
"
 ::= { psRpmcEntry  15 }



--
-- table ALARM
--

psAlarmTable    OBJECT-TYPE
SYNTAX SEQUENCE OF PsAlarmEntry
MAX-ACCESS not-accessible
STATUS current
DESCRIPTION
        "Table of all Alarm data"
 ::= { powerSystem  47 }

psAlarmEntry OBJECT-TYPE
SYNTAX     PsAlarmEntry
MAX-ACCESS  not-accessible
STATUS      current
DESCRIPTION
       "Entry of information for one Alarm"
INDEX { psAlarmEntryIndex }
 ::= { psAlarmTable  1 }

PsAlarmEntry ::= SEQUENCE {
psAlarmEntryIndex   INTEGER,
psAlarmEntryDes   DisplayString,
psAlarmEntryAst   INTEGER,
psAlarmEntrySev   DisplayString,
psAlarmEntryLed   DisplayString,
psAlarmEntryAcc   DisplayString,
psAlarmEntryThr   DisplayString,
psAlarmEntryFth   DisplayString,
psAlarmEntryBth   DisplayString,
psAlarmEntryDly   Integer32,
psAlarmEntryNoo   INTEGER,
psAlarmEntryNor   INTEGER,
psAlarmEntryNag   INTEGER,
psAlarmEntryDst   DisplayString
}

psAlarmEntryIndex OBJECT-TYPE
SYNTAX      INTEGER (0..2147483647)
MAX-ACCESS  read-only
STATUS      current
DESCRIPTION
"Table Index"
 ::= { psAlarmEntry  1 }

psAlarmEntryDes OBJECT-TYPE
SYNTAX      DisplayString
MAX-ACCESS  read-write
STATUS      current
DESCRIPTION
"Description"
 ::= { psAlarmEntry  2 }

psAlarmEntryAst OBJECT-TYPE
SYNTAX      INTEGER {
inactive(0),
active(1)
}
MAX-ACCESS  read-only
STATUS      current
DESCRIPTION
"State
Values:
inactive(0),
active(1)
"
 ::= { psAlarmEntry  3 }

psAlarmEntrySev OBJECT-TYPE
SYNTAX      DisplayString
MAX-ACCESS  read-write
STATUS      current
DESCRIPTION
"Severity"
 ::= { psAlarmEntry  4 }

psAlarmEntryLed OBJECT-TYPE
SYNTAX      DisplayString
MAX-ACCESS  read-write
STATUS      current
DESCRIPTION
"LED"
 ::= { psAlarmEntry  5 }

psAlarmEntryAcc OBJECT-TYPE
SYNTAX      DisplayString
MAX-ACCESS  read-write
STATUS      current
DESCRIPTION
"Contact Closure"
 ::= { psAlarmEntry  6 }

psAlarmEntryThr OBJECT-TYPE
SYNTAX      DisplayString
MAX-ACCESS  read-write
STATUS      current
DESCRIPTION
"Threshold"
 ::= { psAlarmEntry  7 }

psAlarmEntryFth OBJECT-TYPE
SYNTAX      DisplayString
MAX-ACCESS  read-write
STATUS      current
DESCRIPTION
"Float Threshold"
 ::= { psAlarmEntry  8 }

psAlarmEntryBth OBJECT-TYPE
SYNTAX      DisplayString
MAX-ACCESS  read-write
STATUS      current
DESCRIPTION
"Boost Threshold"
 ::= { psAlarmEntry  9 }

psAlarmEntryDly OBJECT-TYPE
SYNTAX      Integer32(0..540)
MAX-ACCESS  read-write
STATUS      current
DESCRIPTION
"Notify Delay"
 ::= { psAlarmEntry  10 }

psAlarmEntryNoo OBJECT-TYPE
SYNTAX      INTEGER {
no(0),
yes(1)
}
MAX-ACCESS  read-write
STATUS      current
DESCRIPTION
"Notify On Occur
Values:
no(0),
yes(1)
"
 ::= { psAlarmEntry  11 }

psAlarmEntryNor OBJECT-TYPE
SYNTAX      INTEGER {
no(0),
yes(1)
}
MAX-ACCESS  read-write
STATUS      current
DESCRIPTION
"Notify On Retire
Values:
no(0),
yes(1)
"
 ::= { psAlarmEntry  12 }

psAlarmEntryNag OBJECT-TYPE
SYNTAX      INTEGER {
no(0),
yes(1)
}
MAX-ACCESS  read-write
STATUS      current
DESCRIPTION
"Nag on Occur
Values:
no(0),
yes(1)
"
 ::= { psAlarmEntry  13 }

psAlarmEntryDst OBJECT-TYPE
SYNTAX      DisplayString
MAX-ACCESS  read-write
STATUS      current
DESCRIPTION
"Notify Destination"
 ::= { psAlarmEntry  14 }



--
-- object psTrap
--

psTrap OBJECT IDENTIFIER  ::= { powerSystem  48 }


trapInfo OBJECT-TYPE
SYNTAX      DisplayString
MAX-ACCESS  accessible-for-notify
STATUS      current
DESCRIPTION
        "Supplemental alarm information"
 ::= { powerSystem  49 }
psTrapDc1Btj   NOTIFICATION-TYPE
OBJECTS     { trapInfo }
STATUS      current
DESCRIPTION
        "Battery Thermal Major"
 ::= { psTrap  1 }

psTrapDc1Btn   NOTIFICATION-TYPE
OBJECTS     { trapInfo }
STATUS      current
DESCRIPTION
        "Battery Thermal Minor"
 ::= { psTrap  2 }

psTrapDc1Amj   NOTIFICATION-TYPE
OBJECTS     { trapInfo }
STATUS      current
DESCRIPTION
        "Auxiliary Fuse Major"
 ::= { psTrap  3 }

psTrapDc1Amn   NOTIFICATION-TYPE
OBJECTS     { trapInfo }
STATUS      current
DESCRIPTION
        "Auxiliary Fuse Minor"
 ::= { psTrap  4 }

psTrapDc1Faj   NOTIFICATION-TYPE
OBJECTS     { trapInfo }
STATUS      current
DESCRIPTION
        "External Fuse Major"
 ::= { psTrap  5 }

psTrapDc1Fan   NOTIFICATION-TYPE
OBJECTS     { trapInfo }
STATUS      current
DESCRIPTION
        "External Fuse Minor"
 ::= { psTrap  6 }

psTrapDc1Rbf   NOTIFICATION-TYPE
OBJECTS     { trapInfo }
STATUS      current
DESCRIPTION
        "Regulation Battery Fuse"
 ::= { psTrap  7 }

psTrapDc1Btf   NOTIFICATION-TYPE
OBJECTS     { trapInfo }
STATUS      current
DESCRIPTION
        "Battery Thermal Fuse"
 ::= { psTrap  8 }

psTrapDc1Bpf   NOTIFICATION-TYPE
OBJECTS     { trapInfo }
STATUS      current
DESCRIPTION
        "Battery Power Fuse"
 ::= { psTrap  9 }

psTrapDc1Abs   NOTIFICATION-TYPE
OBJECTS     { trapInfo }
STATUS      current
DESCRIPTION
        "Alarm Battery Supply"
 ::= { psTrap  10 }

psTrapDc1Vsf   NOTIFICATION-TYPE
OBJECTS     { trapInfo }
STATUS      current
DESCRIPTION
        "Sense/Control Fuse"
 ::= { psTrap  11 }

psTrapDc1Lvda   NOTIFICATION-TYPE
OBJECTS     { trapInfo }
STATUS      current
DESCRIPTION
        "Low Voltage Disconnect Fail"
 ::= { psTrap  12 }

psTrapDc1Lvd   NOTIFICATION-TYPE
OBJECTS     { trapInfo }
STATUS      current
DESCRIPTION
        "Low Voltage Disconnect"
 ::= { psTrap  13 }

psTrapDc1Osa   NOTIFICATION-TYPE
OBJECTS     { trapInfo }
STATUS      current
DESCRIPTION
        "Open String"
 ::= { psTrap  14 }

psTrapDc1Emd   NOTIFICATION-TYPE
OBJECTS     { trapInfo }
STATUS      current
DESCRIPTION
        "Energy Management Disabled"
 ::= { psTrap  15 }

psTrapDc1Epd   NOTIFICATION-TYPE
OBJECTS     { trapInfo }
STATUS      current
DESCRIPTION
        "Excess Plant Drain"
 ::= { psTrap  16 }

psTrapDc1Snc   NOTIFICATION-TYPE
OBJECTS     { trapInfo }
STATUS      current
DESCRIPTION
        "Shunt Not Configured"
 ::= { psTrap  17 }

psTrapDc1Urc   NOTIFICATION-TYPE
OBJECTS     { trapInfo }
STATUS      current
DESCRIPTION
        "User Relay Conflict"
 ::= { psTrap  18 }

psTrapDc1Zid   NOTIFICATION-TYPE
OBJECTS     { trapInfo }
STATUS      current
DESCRIPTION
        "ID Not Configured"
 ::= { psTrap  19 }

psTrapDc1Tpa   NOTIFICATION-TYPE
OBJECTS     { trapInfo }
STATUS      current
DESCRIPTION
        "Thermal Probe Alarm"
 ::= { psTrap  20 }

psTrapDc1Cma   NOTIFICATION-TYPE
OBJECTS     { trapInfo }
STATUS      current
DESCRIPTION
        "Minor Communication Failure"
 ::= { psTrap  21 }

psTrapDc1Mcm   NOTIFICATION-TYPE
OBJECTS     { trapInfo }
STATUS      current
DESCRIPTION
        "Major Communication Failure"
 ::= { psTrap  22 }

psTrapDc1Bid   NOTIFICATION-TYPE
OBJECTS     { trapInfo }
STATUS      current
DESCRIPTION
        "Bay Interface ID Conflict"
 ::= { psTrap  23 }

psTrapDc1Rfa   NOTIFICATION-TYPE
OBJECTS     { trapInfo }
STATUS      current
DESCRIPTION
        "Rectifier Fail"
 ::= { psTrap  24 }

psTrapDc1Did   NOTIFICATION-TYPE
OBJECTS     { trapInfo }
STATUS      current
DESCRIPTION
        "ID Conflict"
 ::= { psTrap  25 }

psTrapDc1Clm   NOTIFICATION-TYPE
OBJECTS     { trapInfo }
STATUS      current
DESCRIPTION
        "Rectifier Current Limit"
 ::= { psTrap  26 }

psTrapDc1Vla   NOTIFICATION-TYPE
OBJECTS     { trapInfo }
STATUS      current
DESCRIPTION
        "Very Low Voltage"
 ::= { psTrap  27 }

psTrapDc1Acf   NOTIFICATION-TYPE
OBJECTS     { trapInfo }
STATUS      current
DESCRIPTION
        "AC Fail"
 ::= { psTrap  28 }

psTrapDc1Pha   NOTIFICATION-TYPE
OBJECTS     { trapInfo }
STATUS      current
DESCRIPTION
        "Phase or Low Output"
 ::= { psTrap  29 }

psTrapDc1Lca   NOTIFICATION-TYPE
OBJECTS     { trapInfo }
STATUS      current
DESCRIPTION
        "Low Current"
 ::= { psTrap  30 }

psTrapDc1Lsf   NOTIFICATION-TYPE
OBJECTS     { trapInfo }
STATUS      current
DESCRIPTION
        "Load Share Fuse"
 ::= { psTrap  31 }

psTrapDc1Man   NOTIFICATION-TYPE
OBJECTS     { trapInfo }
STATUS      current
DESCRIPTION
        "Manual Off"
 ::= { psTrap  32 }

psTrapDc1Ets   NOTIFICATION-TYPE
OBJECTS     { trapInfo }
STATUS      current
DESCRIPTION
        "External Transfer Shutdown"
 ::= { psTrap  33 }

psTrapDc1Ric   NOTIFICATION-TYPE
OBJECTS     { trapInfo }
STATUS      current
DESCRIPTION
        "Rectifier Incomplete Configuration"
 ::= { psTrap  34 }

psTrapDc1Hpa   NOTIFICATION-TYPE
OBJECTS     { trapInfo }
STATUS      current
DESCRIPTION
        "Half Power"
 ::= { psTrap  35 }

psTrapDc1Mfa   NOTIFICATION-TYPE
OBJECTS     { trapInfo }
STATUS      current
DESCRIPTION
        "Multiple Rectifier Fail"
 ::= { psTrap  36 }

psTrapDc1Lmr   NOTIFICATION-TYPE
OBJECTS     { trapInfo }
STATUS      current
DESCRIPTION
        "Limited Recharge"
 ::= { psTrap  37 }

psTrapDc1Erd   NOTIFICATION-TYPE
OBJECTS     { trapInfo }
STATUS      current
DESCRIPTION
        "Excess Rectifier Drain"
 ::= { psTrap  38 }

psTrapDc1Eto   NOTIFICATION-TYPE
OBJECTS     { trapInfo }
STATUS      current
DESCRIPTION
        "Engine Transfer Timeout"
 ::= { psTrap  39 }

psTrapDc1Rpi   NOTIFICATION-TYPE
OBJECTS     { trapInfo }
STATUS      current
DESCRIPTION
        "Rectifier/Plant Inconsistency"
 ::= { psTrap  40 }

psTrapDc1Rtl   NOTIFICATION-TYPE
OBJECTS     { trapInfo }
STATUS      current
DESCRIPTION
        "Reserve Time Low"
 ::= { psTrap  41 }

psTrapDc1Bda   NOTIFICATION-TYPE
OBJECTS     { trapInfo }
STATUS      current
DESCRIPTION
        "Battery On Discharge"
 ::= { psTrap  42 }

psTrapDc1Hva   NOTIFICATION-TYPE
OBJECTS     { trapInfo }
STATUS      current
DESCRIPTION
        "High Voltage"
 ::= { psTrap  43 }

psTrapDc1Hfv   NOTIFICATION-TYPE
OBJECTS     { trapInfo }
STATUS      current
DESCRIPTION
        "High Float Voltage"
 ::= { psTrap  44 }

psTrapPs1Cra   NOTIFICATION-TYPE
OBJECTS     { trapInfo }
STATUS      current
DESCRIPTION
        "Intelligent Controller Fail"
 ::= { psTrap  45 }

psTrapPs1Crf   NOTIFICATION-TYPE
OBJECTS     { trapInfo }
STATUS      current
DESCRIPTION
        "Intelligent Controller Fuse"
 ::= { psTrap  46 }

psTrapPs1Cpa   NOTIFICATION-TYPE
OBJECTS     { trapInfo }
STATUS      current
DESCRIPTION
        "Circuit Pack Fail"
 ::= { psTrap  47 }

psTrapPs1Rpf   NOTIFICATION-TYPE
OBJECTS     { trapInfo }
STATUS      current
DESCRIPTION
        "Remote Peripheral Fuse"
 ::= { psTrap  48 }

psTrapPs1Pcf   NOTIFICATION-TYPE
OBJECTS     { trapInfo }
STATUS      current
DESCRIPTION
        "PC Power Fuse"
 ::= { psTrap  49 }

psTrapPs1Epr   NOTIFICATION-TYPE
OBJECTS     { trapInfo }
STATUS      current
DESCRIPTION
        "External Password Reset"
 ::= { psTrap  50 }

psTrapPs1Pfd   NOTIFICATION-TYPE
OBJECTS     { trapInfo }
STATUS      current
DESCRIPTION
        "Passwords At Default"
 ::= { psTrap  51 }

psTrapPs1Exl   NOTIFICATION-TYPE
OBJECTS     { trapInfo }
STATUS      current
DESCRIPTION
        "Excessive Login Attempts"
 ::= { psTrap  52 }

psTrapPs1Bbl   NOTIFICATION-TYPE
OBJECTS     { trapInfo }
STATUS      current
DESCRIPTION
        "Memory Backup Battery Low"
 ::= { psTrap  53 }

psTrapPs1Pht   NOTIFICATION-TYPE
OBJECTS     { trapInfo }
STATUS      current
DESCRIPTION
        "Processor Halt"
 ::= { psTrap  54 }

psTrapPs1Clc   NOTIFICATION-TYPE
OBJECTS     { trapInfo }
STATUS      current
DESCRIPTION
        "Clock Changed"
 ::= { psTrap  55 }

psTrapPs1Stf   NOTIFICATION-TYPE
OBJECTS     { trapInfo }
STATUS      current
DESCRIPTION
        "Self Test Failed"
 ::= { psTrap  56 }

psTrapPs1Pgi   NOTIFICATION-TYPE
OBJECTS     { trapInfo }
STATUS      current
DESCRIPTION
        "Program Line Invalid"
 ::= { psTrap  57 }

psTrapPs1Cch   NOTIFICATION-TYPE
OBJECTS     { trapInfo }
STATUS      current
DESCRIPTION
        "Configuration Changed"
 ::= { psTrap  58 }

psTrapPs1Hcl   NOTIFICATION-TYPE
OBJECTS     { trapInfo }
STATUS      current
DESCRIPTION
        "History Cleared"
 ::= { psTrap  59 }

psTrapPs1Mor   NOTIFICATION-TYPE
OBJECTS     { trapInfo }
STATUS      current
DESCRIPTION
        "Measurement Out Of Range"
 ::= { psTrap  60 }

psTrapPs1Mtc   NOTIFICATION-TYPE
OBJECTS     { trapInfo }
STATUS      current
DESCRIPTION
        "Module Type Conflict"
 ::= { psTrap  61 }

psTrapPs1Mdf   NOTIFICATION-TYPE
OBJECTS     { trapInfo }
STATUS      current
DESCRIPTION
        "Module Failure"
 ::= { psTrap  62 }

psTrapAt1Ata   NOTIFICATION-TYPE
OBJECTS     { trapInfo }
STATUS      current
DESCRIPTION
        "Alarm Test Active"
 ::= { psTrap  63 }

psTrapAt1Atf   NOTIFICATION-TYPE
OBJECTS     { trapInfo }
STATUS      current
DESCRIPTION
        "Alarm Test Failed"
 ::= { psTrap  64 }

psTrapAt1Atb   NOTIFICATION-TYPE
OBJECTS     { trapInfo }
STATUS      current
DESCRIPTION
        "Alarm Test Aborted"
 ::= { psTrap  65 }

psTrapCp1Cfa   NOTIFICATION-TYPE
OBJECTS     { trapInfo }
STATUS      current
DESCRIPTION
        "Converter Fail"
 ::= { psTrap  66 }

psTrapCp1Dfa   NOTIFICATION-TYPE
OBJECTS     { trapInfo }
STATUS      current
DESCRIPTION
        "Distribution Fail"
 ::= { psTrap  67 }

psTrapCp1Did   NOTIFICATION-TYPE
OBJECTS     { trapInfo }
STATUS      current
DESCRIPTION
        "ID Conflict"
 ::= { psTrap  68 }

psTrapCp1Mfa   NOTIFICATION-TYPE
OBJECTS     { trapInfo }
STATUS      current
DESCRIPTION
        "Multiple Converter Fail"
 ::= { psTrap  69 }

psTrapBs1Bsa   NOTIFICATION-TYPE
OBJECTS     { trapInfo }
STATUS      current
DESCRIPTION
        "Boost State Alarm"
 ::= { psTrap  70 }

psTrapBr1Bta   NOTIFICATION-TYPE
OBJECTS     { trapInfo }
STATUS      current
DESCRIPTION
        "Battery Test Active"
 ::= { psTrap  71 }

psTrapBr1Bfa   NOTIFICATION-TYPE
OBJECTS     { trapInfo }
STATUS      current
DESCRIPTION
        "Battery Test Failed"
 ::= { psTrap  72 }

psTrapBr1Bca   NOTIFICATION-TYPE
OBJECTS     { trapInfo }
STATUS      current
DESCRIPTION
        "Battery Type Conflict"
 ::= { psTrap  73 }

psTrapLdaDfa   NOTIFICATION-TYPE
OBJECTS     { trapInfo }
STATUS      current
DESCRIPTION
        "Distribution Fuse"
 ::= { psTrap  74 }

psTrapAcd1Prf   NOTIFICATION-TYPE
OBJECTS     { trapInfo }
STATUS      current
DESCRIPTION
        "Phase R Fail"
 ::= { psTrap  75 }

psTrapAcd1Psf   NOTIFICATION-TYPE
OBJECTS     { trapInfo }
STATUS      current
DESCRIPTION
        "Phase S Fail"
 ::= { psTrap  76 }

psTrapAcd1Ptf   NOTIFICATION-TYPE
OBJECTS     { trapInfo }
STATUS      current
DESCRIPTION
        "Phase T Fail"
 ::= { psTrap  77 }

psTrapAcd1Msa   NOTIFICATION-TYPE
OBJECTS     { trapInfo }
STATUS      current
DESCRIPTION
        "Master Switch Alarm"
 ::= { psTrap  78 }

psTrapCn1Cno   NOTIFICATION-TYPE
OBJECTS     { trapInfo }
STATUS      current
DESCRIPTION
        "Contactor Open"
 ::= { psTrap  79 }

psTrapCn1Cnf   NOTIFICATION-TYPE
OBJECTS     { trapInfo }
STATUS      current
DESCRIPTION
        "Contactor Failed"
 ::= { psTrap  80 }

psTrapCn2Cno   NOTIFICATION-TYPE
OBJECTS     { trapInfo }
STATUS      current
DESCRIPTION
        "Contactor Open"
 ::= { psTrap  81 }

psTrapCn2Cnf   NOTIFICATION-TYPE
OBJECTS     { trapInfo }
STATUS      current
DESCRIPTION
        "Contactor Failed"
 ::= { psTrap  82 }

psTrapCn3Cno   NOTIFICATION-TYPE
OBJECTS     { trapInfo }
STATUS      current
DESCRIPTION
        "Contactor Open"
 ::= { psTrap  83 }

psTrapCn3Cnf   NOTIFICATION-TYPE
OBJECTS     { trapInfo }
STATUS      current
DESCRIPTION
        "Contactor Failed"
 ::= { psTrap  84 }

psTrapAco1Aac   NOTIFICATION-TYPE
OBJECTS     { trapInfo }
STATUS      current
DESCRIPTION
        "ACO Active"
 ::= { psTrap  85 }

psTrapCm1Cof   NOTIFICATION-TYPE
OBJECTS     { trapInfo }
STATUS      current
DESCRIPTION
        "Queue Overflow"
 ::= { psTrap  86 }

psTrapCm1Cor   NOTIFICATION-TYPE
OBJECTS     { trapInfo }
STATUS      current
DESCRIPTION
        "Number Did Not Respond"
 ::= { psTrap  87 }

psTrapCm1Nnc   NOTIFICATION-TYPE
OBJECTS     { trapInfo }
STATUS      current
DESCRIPTION
        "Number Not Configured"
 ::= { psTrap  88 }

psTrapPo1Por   NOTIFICATION-TYPE
OBJECTS     { trapInfo }
STATUS      current
DESCRIPTION
        "Number Did Not Respond"
 ::= { psTrap  89 }

psTrapDs1Cea   NOTIFICATION-TYPE
OBJECTS     { trapInfo }
STATUS      current
DESCRIPTION
        "Connected Equipment Alarm"
 ::= { psTrap  90 }

psTrapDs2Cea   NOTIFICATION-TYPE
OBJECTS     { trapInfo }
STATUS      current
DESCRIPTION
        "Connected Equipment Alarm"
 ::= { psTrap  91 }

psTrapDs3Cea   NOTIFICATION-TYPE
OBJECTS     { trapInfo }
STATUS      current
DESCRIPTION
        "Connected Equipment Alarm"
 ::= { psTrap  92 }

psTrapDs4Cea   NOTIFICATION-TYPE
OBJECTS     { trapInfo }
STATUS      current
DESCRIPTION
        "Connected Equipment Alarm"
 ::= { psTrap  93 }

psTrapDs5Cea   NOTIFICATION-TYPE
OBJECTS     { trapInfo }
STATUS      current
DESCRIPTION
        "Connected Equipment Alarm"
 ::= { psTrap  94 }

psTrapDs6Cea   NOTIFICATION-TYPE
OBJECTS     { trapInfo }
STATUS      current
DESCRIPTION
        "Connected Equipment Alarm"
 ::= { psTrap  95 }

psTrapUserDefined   NOTIFICATION-TYPE
OBJECTS     { trapInfo }
STATUS      current
DESCRIPTION
        "This may be a user defined event, or a new controller event."
 ::= { psTrap  96 }

psTrapCn4Cno   NOTIFICATION-TYPE
OBJECTS     { trapInfo }
STATUS      current
DESCRIPTION
        "Contactor Open"
 ::= { psTrap  97 }

psTrapCn4Cnf   NOTIFICATION-TYPE
OBJECTS     { trapInfo }
STATUS      current
DESCRIPTION
        "Contactor Failed"
 ::= { psTrap  98 }

psTrapDc1Vmf   NOTIFICATION-TYPE
OBJECTS     { trapInfo }
STATUS      current
DESCRIPTION
        "Voltage Module Failure"
 ::= { psTrap  99 }

psTrapDc1Epo   NOTIFICATION-TYPE
OBJECTS     { trapInfo }
STATUS      current
DESCRIPTION
        "Emergency Power Off"
 ::= { psTrap  100 }

psTrapDc1Icr   NOTIFICATION-TYPE
OBJECTS     { trapInfo }
STATUS      current
DESCRIPTION
        "Incompatible Rectifier"
 ::= { psTrap  101 }

psTrapDc1Rfn   NOTIFICATION-TYPE
OBJECTS     { trapInfo }
STATUS      current
DESCRIPTION
        "Rectifier Fan Failure"
 ::= { psTrap  102 }

psTrapPs1Ax1   NOTIFICATION-TYPE
OBJECTS     { trapInfo }
STATUS      current
DESCRIPTION
        "Auxiliary Event 1"
 ::= { psTrap  103 }

psTrapPs1Ax2   NOTIFICATION-TYPE
OBJECTS     { trapInfo }
STATUS      current
DESCRIPTION
        "Auxiliary Event 2"
 ::= { psTrap  104 }

psTrapPs1Ax3   NOTIFICATION-TYPE
OBJECTS     { trapInfo }
STATUS      current
DESCRIPTION
        "Auxiliary Event 3"
 ::= { psTrap  105 }

psTrapPs1Ax4   NOTIFICATION-TYPE
OBJECTS     { trapInfo }
STATUS      current
DESCRIPTION
        "Auxiliary Event 4"
 ::= { psTrap  106 }

psTrapPs1Ax5   NOTIFICATION-TYPE
OBJECTS     { trapInfo }
STATUS      current
DESCRIPTION
        "Auxiliary Event 5"
 ::= { psTrap  107 }

psTrapPs1Ax6   NOTIFICATION-TYPE
OBJECTS     { trapInfo }
STATUS      current
DESCRIPTION
        "Auxiliary Event 6"
 ::= { psTrap  108 }

psTrapCp1Cfn   NOTIFICATION-TYPE
OBJECTS     { trapInfo }
STATUS      current
DESCRIPTION
        "Converter Fan Minor"
 ::= { psTrap  109 }

psTrapCp1Cfj   NOTIFICATION-TYPE
OBJECTS     { trapInfo }
STATUS      current
DESCRIPTION
        "Converter Fan Major"
 ::= { psTrap  110 }

psTrapCp1Icc   NOTIFICATION-TYPE
OBJECTS     { trapInfo }
STATUS      current
DESCRIPTION
        "Incompatible Converter"
 ::= { psTrap  111 }

psTrapCp1Hfv   NOTIFICATION-TYPE
OBJECTS     { trapInfo }
STATUS      current
DESCRIPTION
        "Converter High Voltage Minor"
 ::= { psTrap  112 }

psTrapCp1Hva   NOTIFICATION-TYPE
OBJECTS     { trapInfo }
STATUS      current
DESCRIPTION
        "Converter High Voltage Major"
 ::= { psTrap  113 }

psTrapCp1Vla   NOTIFICATION-TYPE
OBJECTS     { trapInfo }
STATUS      current
DESCRIPTION
        "Converter Low Voltage Alarm"
 ::= { psTrap  114 }

psTrapCp1Rl   NOTIFICATION-TYPE
OBJECTS     { trapInfo }
STATUS      current
DESCRIPTION
        "Converter Redundancy Loss"
 ::= { psTrap  115 }

psTrapBr1Scda   NOTIFICATION-TYPE
OBJECTS     { trapInfo }
STATUS      current
DESCRIPTION
        "Shorted Cell Detected"
 ::= { psTrap  116 }

psTrapBr1Isda   NOTIFICATION-TYPE
OBJECTS     { trapInfo }
STATUS      current
DESCRIPTION
        "Imminent Low Voltage Shutdown"
 ::= { psTrap  117 }

psTrapBr1Mdp   NOTIFICATION-TYPE
OBJECTS     { trapInfo }
STATUS      current
DESCRIPTION
        "Voltage Module Duplicate ID"
 ::= { psTrap  118 }

psTrapBr1Mzd   NOTIFICATION-TYPE
OBJECTS     { trapInfo }
STATUS      current
DESCRIPTION
        "Voltage Module Zero ID"
 ::= { psTrap  119 }

psTrapBr1Btha   NOTIFICATION-TYPE
OBJECTS     { trapInfo }
STATUS      current
DESCRIPTION
        "High Battery Temperature"
 ::= { psTrap  120 }

psTrapDc1Rrtl   NOTIFICATION-TYPE
OBJECTS     { trapInfo }
STATUS      current
DESCRIPTION
        "Real-Time Reserve Low"
 ::= { psTrap  121 }

psTrapDc1Rls   NOTIFICATION-TYPE
OBJECTS     { trapInfo }
STATUS      current
DESCRIPTION
        "Redundancy Loss"
 ::= { psTrap  122 }

psTrapDc1Macf   NOTIFICATION-TYPE
OBJECTS     { trapInfo }
STATUS      current
DESCRIPTION
        "Multiple AC Fail"
 ::= { psTrap  123 }

psTrapDc1Mman   NOTIFICATION-TYPE
OBJECTS     { trapInfo }
STATUS      current
DESCRIPTION
        "Multiple Manual Off"
 ::= { psTrap  124 }

psTrapDc1Faj2   NOTIFICATION-TYPE
OBJECTS     { trapInfo }
STATUS      current
DESCRIPTION
        "External Fuse Major 2"
 ::= { psTrap  125 }

psTrapPs1Amtl   NOTIFICATION-TYPE
OBJECTS     { trapInfo }
STATUS      current
DESCRIPTION
        "Low Ambient Temperature"
 ::= { psTrap  126 }

psTrapPs1Amth   NOTIFICATION-TYPE
OBJECTS     { trapInfo }
STATUS      current
DESCRIPTION
        "High Ambient Temperature"
 ::= { psTrap  127 }

psTrapRp1Rf   NOTIFICATION-TYPE
OBJECTS     { trapInfo }
STATUS      current
DESCRIPTION
        "Ringer Minor Fail"
 ::= { psTrap  128 }

psTrapRp1Rpff   NOTIFICATION-TYPE
OBJECTS     { trapInfo }
STATUS      current
DESCRIPTION
        "Ringer Fan Fail"
 ::= { psTrap  129 }

psTrapRp1Rpxj   NOTIFICATION-TYPE
OBJECTS     { trapInfo }
STATUS      current
DESCRIPTION
        "Ringer Major External Fault"
 ::= { psTrap  130 }

psTrapRp1Rpxn   NOTIFICATION-TYPE
OBJECTS     { trapInfo }
STATUS      current
DESCRIPTION
        "Ringer Minor External Fault"
 ::= { psTrap  131 }

psTrapRp1Rprl   NOTIFICATION-TYPE
OBJECTS     { trapInfo }
STATUS      current
DESCRIPTION
        "Ringer Redundancy Loss"
 ::= { psTrap  132 }

psTrapRp1Rpfj   NOTIFICATION-TYPE
OBJECTS     { trapInfo }
STATUS      current
DESCRIPTION
        "Ringer Major Fail"
 ::= { psTrap  133 }

psTrapRp1Rcdp   NOTIFICATION-TYPE
OBJECTS     { trapInfo }
STATUS      current
DESCRIPTION
        "Ringer ID Conflict"
 ::= { psTrap  134 }

psTrapDc1Pfs   NOTIFICATION-TYPE
OBJECTS     { trapInfo }
STATUS      current
DESCRIPTION
        "Thermal Probe Fail Safe"
 ::= { psTrap  135 }

psTrapDc1Rif   NOTIFICATION-TYPE
OBJECTS     { trapInfo }
STATUS      current
DESCRIPTION
        "Rectifier Internal Fault"
 ::= { psTrap  136 }

psTrapCp1Cin   NOTIFICATION-TYPE
OBJECTS     { trapInfo }
STATUS      current
DESCRIPTION
        "Converter Input Fail"
 ::= { psTrap  137 }

psTrapBr1Btla   NOTIFICATION-TYPE
OBJECTS     { trapInfo }
STATUS      current
DESCRIPTION
        "Low Battery Temperature"
 ::= { psTrap  138 }

psTrapBr1Btvh   NOTIFICATION-TYPE
OBJECTS     { trapInfo }
STATUS      current
DESCRIPTION
        "Very High Battery Temperature"
 ::= { psTrap  139 }

psTrapBr1Btvl   NOTIFICATION-TYPE
OBJECTS     { trapInfo }
STATUS      current
DESCRIPTION
        "Very Low Battery Temperature"
 ::= { psTrap  140 }

psTrapDc1Pid   NOTIFICATION-TYPE
OBJECTS     { trapInfo }
STATUS      current
DESCRIPTION
        "Panel Interface ID Conflict"
 ::= { psTrap  141 }

psTrapIvp1Ilvi   NOTIFICATION-TYPE
OBJECTS     { trapInfo }
STATUS      current
DESCRIPTION
        "Inverter Low Input"
 ::= { psTrap  142 }

psTrapIvp1Ihvi   NOTIFICATION-TYPE
OBJECTS     { trapInfo }
STATUS      current
DESCRIPTION
        "Inverter High Input"
 ::= { psTrap  143 }

psTrapIvp1Ita   NOTIFICATION-TYPE
OBJECTS     { trapInfo }
STATUS      current
DESCRIPTION
        "Inverter High Temperature"
 ::= { psTrap  144 }

psTrapIvp1If   NOTIFICATION-TYPE
OBJECTS     { trapInfo }
STATUS      current
DESCRIPTION
        "Inverter Fail"
 ::= { psTrap  145 }

psTrapIvp1Ilv   NOTIFICATION-TYPE
OBJECTS     { trapInfo }
STATUS      current
DESCRIPTION
        "Inverter Low Output"
 ::= { psTrap  146 }

psTrapIvp1Ifa   NOTIFICATION-TYPE
OBJECTS     { trapInfo }
STATUS      current
DESCRIPTION
        "Inverter Frequency Lock"
 ::= { psTrap  147 }

psTrapIvp1Ihv   NOTIFICATION-TYPE
OBJECTS     { trapInfo }
STATUS      current
DESCRIPTION
        "Inverter High Output"
 ::= { psTrap  148 }

psTrapIvp1Ida   NOTIFICATION-TYPE
OBJECTS     { trapInfo }
STATUS      current
DESCRIPTION
        "Inverter Distribution Alarm"
 ::= { psTrap  149 }

psTrapIvp1Iof   NOTIFICATION-TYPE
OBJECTS     { trapInfo }
STATUS      current
DESCRIPTION
        "Inverter Output Fuse"
 ::= { psTrap  150 }

psTrapIvp1Idid   NOTIFICATION-TYPE
OBJECTS     { trapInfo }
STATUS      current
DESCRIPTION
        "Inverter ID Conflict"
 ::= { psTrap  151 }

psTrapIvp1Iirm   NOTIFICATION-TYPE
OBJECTS     { trapInfo }
STATUS      current
DESCRIPTION
        "Inverter High RMS Current"
 ::= { psTrap  152 }

psTrapIvp1Iipk   NOTIFICATION-TYPE
OBJECTS     { trapInfo }
STATUS      current
DESCRIPTION
        "Inverter High Peak Current"
 ::= { psTrap  153 }

psTrapIvp1Icf   NOTIFICATION-TYPE
OBJECTS     { trapInfo }
STATUS      current
DESCRIPTION
        "Inverter High Crest Factor"
 ::= { psTrap  154 }

psTrapIvp1Mif   NOTIFICATION-TYPE
OBJECTS     { trapInfo }
STATUS      current
DESCRIPTION
        "Multiple Inverter Fail"
 ::= { psTrap  155 }

psTrapIvp1Irls   NOTIFICATION-TYPE
OBJECTS     { trapInfo }
STATUS      current
DESCRIPTION
        "Inverter Redundancy Loss"
 ::= { psTrap  156 }

psTrapIvp1Milv   NOTIFICATION-TYPE
OBJECTS     { trapInfo }
STATUS      current
DESCRIPTION
        "Multiple Inverter Low Input Voltage"
 ::= { psTrap  157 }

psTrapDc1Rtl2   NOTIFICATION-TYPE
OBJECTS     { trapInfo }
STATUS      current
DESCRIPTION
        "Reserve Time Low 2"
 ::= { psTrap  158 }

psTrapDc1Faja   NOTIFICATION-TYPE
OBJECTS     { trapInfo }
STATUS      current
DESCRIPTION
        "Distribution Fuse A"
 ::= { psTrap  159 }

psTrapDc1Fajb   NOTIFICATION-TYPE
OBJECTS     { trapInfo }
STATUS      current
DESCRIPTION
        "Distribution Fuse B"
 ::= { psTrap  160 }

psTrapDc1Vlva   NOTIFICATION-TYPE
OBJECTS     { trapInfo }
STATUS      current
DESCRIPTION
        "VA Power Loss"
 ::= { psTrap  161 }

psTrapDc1Vlvb   NOTIFICATION-TYPE
OBJECTS     { trapInfo }
STATUS      current
DESCRIPTION
        "VB Power Loss"
 ::= { psTrap  162 }

psTrapDc1Ovla   NOTIFICATION-TYPE
OBJECTS     { trapInfo }
STATUS      current
DESCRIPTION
        "IA Overload"
 ::= { psTrap  163 }

psTrapDc1Ovlb   NOTIFICATION-TYPE
OBJECTS     { trapInfo }
STATUS      current
DESCRIPTION
        "IB Overload"
 ::= { psTrap  164 }

psTrapDc1Smw   NOTIFICATION-TYPE
OBJECTS     { trapInfo }
STATUS      current
DESCRIPTION
        "Shunt Mis-wired"
 ::= { psTrap  165 }

psTrapDc1Cca   NOTIFICATION-TYPE
OBJECTS     { trapInfo }
STATUS      current
DESCRIPTION
        "Circuit Assignment"
 ::= { psTrap  166 }

psTrapDc1Rrtl2   NOTIFICATION-TYPE
OBJECTS     { trapInfo }
STATUS      current
DESCRIPTION
        "Real-Time Reserve Low"
 ::= { psTrap  167 }

psTrapDc1Vhav   NOTIFICATION-TYPE
OBJECTS     { trapInfo }
STATUS      current
DESCRIPTION
        "Very High AC Voltage"
 ::= { psTrap  168 }

psTrapDc1Hav   NOTIFICATION-TYPE
OBJECTS     { trapInfo }
STATUS      current
DESCRIPTION
        "High AC Voltage"
 ::= { psTrap  169 }

psTrapDc1Vlav   NOTIFICATION-TYPE
OBJECTS     { trapInfo }
STATUS      current
DESCRIPTION
        "Very Low AC Voltage"
 ::= { psTrap  170 }

psTrapDc1Lav   NOTIFICATION-TYPE
OBJECTS     { trapInfo }
STATUS      current
DESCRIPTION
        "Low AC Voltage"
 ::= { psTrap  171 }

psTrapDc1Tic   NOTIFICATION-TYPE
OBJECTS     { trapInfo }
STATUS      current
DESCRIPTION
        "Total Installed Capacity"
 ::= { psTrap  172 }

psTrapDc1Tcc   NOTIFICATION-TYPE
OBJECTS     { trapInfo }
STATUS      current
DESCRIPTION
        "Total Configured Capacity"
 ::= { psTrap  173 }

psTrapCn5Cno   NOTIFICATION-TYPE
OBJECTS     { trapInfo }
STATUS      current
DESCRIPTION
        "Battery Shunt Trip Open"
 ::= { psTrap  174 }

psTrapCn5Cnf   NOTIFICATION-TYPE
OBJECTS     { trapInfo }
STATUS      current
DESCRIPTION
        "Battery Shunt Trip Failed"
 ::= { psTrap  175 }

psTrapDc1Pcaux   NOTIFICATION-TYPE
OBJECTS     { trapInfo }
STATUS      current
DESCRIPTION
        "PIC Auxiliary"
 ::= { psTrap  176 }

psTrapDc1Slot   NOTIFICATION-TYPE
OBJECTS     { trapInfo }
STATUS      current
DESCRIPTION
        "PIC Slot"
 ::= { psTrap  177 }

psTrapDc1Vid   NOTIFICATION-TYPE
OBJECTS     { trapInfo }
STATUS      current
DESCRIPTION
        "BDFB/BDCBB ID Conflict"
 ::= { psTrap  178 }

--
-- object psRetire
--

psRetire OBJECT IDENTIFIER  ::= { powerSystem  50 }


psRetireDc1Btj   NOTIFICATION-TYPE
OBJECTS     { trapInfo }
STATUS      current
DESCRIPTION
        "Battery Thermal Major"
 ::= { psRetire  1 }

psRetireDc1Btn   NOTIFICATION-TYPE
OBJECTS     { trapInfo }
STATUS      current
DESCRIPTION
        "Battery Thermal Minor"
 ::= { psRetire  2 }

psRetireDc1Amj   NOTIFICATION-TYPE
OBJECTS     { trapInfo }
STATUS      current
DESCRIPTION
        "Auxiliary Fuse Major"
 ::= { psRetire  3 }

psRetireDc1Amn   NOTIFICATION-TYPE
OBJECTS     { trapInfo }
STATUS      current
DESCRIPTION
        "Auxiliary Fuse Minor"
 ::= { psRetire  4 }

psRetireDc1Faj   NOTIFICATION-TYPE
OBJECTS     { trapInfo }
STATUS      current
DESCRIPTION
        "External Fuse Major"
 ::= { psRetire  5 }

psRetireDc1Fan   NOTIFICATION-TYPE
OBJECTS     { trapInfo }
STATUS      current
DESCRIPTION
        "External Fuse Minor"
 ::= { psRetire  6 }

psRetireDc1Rbf   NOTIFICATION-TYPE
OBJECTS     { trapInfo }
STATUS      current
DESCRIPTION
        "Regulation Battery Fuse"
 ::= { psRetire  7 }

psRetireDc1Btf   NOTIFICATION-TYPE
OBJECTS     { trapInfo }
STATUS      current
DESCRIPTION
        "Battery Thermal Fuse"
 ::= { psRetire  8 }

psRetireDc1Bpf   NOTIFICATION-TYPE
OBJECTS     { trapInfo }
STATUS      current
DESCRIPTION
        "Battery Power Fuse"
 ::= { psRetire  9 }

psRetireDc1Abs   NOTIFICATION-TYPE
OBJECTS     { trapInfo }
STATUS      current
DESCRIPTION
        "Alarm Battery Supply"
 ::= { psRetire  10 }

psRetireDc1Vsf   NOTIFICATION-TYPE
OBJECTS     { trapInfo }
STATUS      current
DESCRIPTION
        "Sense/Control Fuse"
 ::= { psRetire  11 }

psRetireDc1Lvda   NOTIFICATION-TYPE
OBJECTS     { trapInfo }
STATUS      current
DESCRIPTION
        "Low Voltage Disconnect Fail"
 ::= { psRetire  12 }

psRetireDc1Lvd   NOTIFICATION-TYPE
OBJECTS     { trapInfo }
STATUS      current
DESCRIPTION
        "Low Voltage Disconnect"
 ::= { psRetire  13 }

psRetireDc1Osa   NOTIFICATION-TYPE
OBJECTS     { trapInfo }
STATUS      current
DESCRIPTION
        "Open String"
 ::= { psRetire  14 }

psRetireDc1Emd   NOTIFICATION-TYPE
OBJECTS     { trapInfo }
STATUS      current
DESCRIPTION
        "Energy Management Disabled"
 ::= { psRetire  15 }

psRetireDc1Epd   NOTIFICATION-TYPE
OBJECTS     { trapInfo }
STATUS      current
DESCRIPTION
        "Excess Plant Drain"
 ::= { psRetire  16 }

psRetireDc1Snc   NOTIFICATION-TYPE
OBJECTS     { trapInfo }
STATUS      current
DESCRIPTION
        "Shunt Not Configured"
 ::= { psRetire  17 }

psRetireDc1Urc   NOTIFICATION-TYPE
OBJECTS     { trapInfo }
STATUS      current
DESCRIPTION
        "User Relay Conflict"
 ::= { psRetire  18 }

psRetireDc1Zid   NOTIFICATION-TYPE
OBJECTS     { trapInfo }
STATUS      current
DESCRIPTION
        "ID Not Configured"
 ::= { psRetire  19 }

psRetireDc1Tpa   NOTIFICATION-TYPE
OBJECTS     { trapInfo }
STATUS      current
DESCRIPTION
        "Thermal Probe Alarm"
 ::= { psRetire  20 }

psRetireDc1Cma   NOTIFICATION-TYPE
OBJECTS     { trapInfo }
STATUS      current
DESCRIPTION
        "Minor Communication Failure"
 ::= { psRetire  21 }

psRetireDc1Mcm   NOTIFICATION-TYPE
OBJECTS     { trapInfo }
STATUS      current
DESCRIPTION
        "Major Communication Failure"
 ::= { psRetire  22 }

psRetireDc1Bid   NOTIFICATION-TYPE
OBJECTS     { trapInfo }
STATUS      current
DESCRIPTION
        "Bay Interface ID Conflict"
 ::= { psRetire  23 }

psRetireDc1Rfa   NOTIFICATION-TYPE
OBJECTS     { trapInfo }
STATUS      current
DESCRIPTION
        "Rectifier Fail"
 ::= { psRetire  24 }

psRetireDc1Did   NOTIFICATION-TYPE
OBJECTS     { trapInfo }
STATUS      current
DESCRIPTION
        "ID Conflict"
 ::= { psRetire  25 }

psRetireDc1Clm   NOTIFICATION-TYPE
OBJECTS     { trapInfo }
STATUS      current
DESCRIPTION
        "Rectifier Current Limit"
 ::= { psRetire  26 }

psRetireDc1Vla   NOTIFICATION-TYPE
OBJECTS     { trapInfo }
STATUS      current
DESCRIPTION
        "Very Low Voltage"
 ::= { psRetire  27 }

psRetireDc1Acf   NOTIFICATION-TYPE
OBJECTS     { trapInfo }
STATUS      current
DESCRIPTION
        "AC Fail"
 ::= { psRetire  28 }

psRetireDc1Pha   NOTIFICATION-TYPE
OBJECTS     { trapInfo }
STATUS      current
DESCRIPTION
        "Phase or Low Output"
 ::= { psRetire  29 }

psRetireDc1Lca   NOTIFICATION-TYPE
OBJECTS     { trapInfo }
STATUS      current
DESCRIPTION
        "Low Current"
 ::= { psRetire  30 }

psRetireDc1Lsf   NOTIFICATION-TYPE
OBJECTS     { trapInfo }
STATUS      current
DESCRIPTION
        "Load Share Fuse"
 ::= { psRetire  31 }

psRetireDc1Man   NOTIFICATION-TYPE
OBJECTS     { trapInfo }
STATUS      current
DESCRIPTION
        "Manual Off"
 ::= { psRetire  32 }

psRetireDc1Ets   NOTIFICATION-TYPE
OBJECTS     { trapInfo }
STATUS      current
DESCRIPTION
        "External Transfer Shutdown"
 ::= { psRetire  33 }

psRetireDc1Ric   NOTIFICATION-TYPE
OBJECTS     { trapInfo }
STATUS      current
DESCRIPTION
        "Rectifier Incomplete Configuration"
 ::= { psRetire  34 }

psRetireDc1Hpa   NOTIFICATION-TYPE
OBJECTS     { trapInfo }
STATUS      current
DESCRIPTION
        "Half Power"
 ::= { psRetire  35 }

psRetireDc1Mfa   NOTIFICATION-TYPE
OBJECTS     { trapInfo }
STATUS      current
DESCRIPTION
        "Multiple Rectifier Fail"
 ::= { psRetire  36 }

psRetireDc1Lmr   NOTIFICATION-TYPE
OBJECTS     { trapInfo }
STATUS      current
DESCRIPTION
        "Limited Recharge"
 ::= { psRetire  37 }

psRetireDc1Erd   NOTIFICATION-TYPE
OBJECTS     { trapInfo }
STATUS      current
DESCRIPTION
        "Excess Rectifier Drain"
 ::= { psRetire  38 }

psRetireDc1Eto   NOTIFICATION-TYPE
OBJECTS     { trapInfo }
STATUS      current
DESCRIPTION
        "Engine Transfer Timeout"
 ::= { psRetire  39 }

psRetireDc1Rpi   NOTIFICATION-TYPE
OBJECTS     { trapInfo }
STATUS      current
DESCRIPTION
        "Rectifier/Plant Inconsistency"
 ::= { psRetire  40 }

psRetireDc1Rtl   NOTIFICATION-TYPE
OBJECTS     { trapInfo }
STATUS      current
DESCRIPTION
        "Reserve Time Low"
 ::= { psRetire  41 }

psRetireDc1Bda   NOTIFICATION-TYPE
OBJECTS     { trapInfo }
STATUS      current
DESCRIPTION
        "Battery On Discharge"
 ::= { psRetire  42 }

psRetireDc1Hva   NOTIFICATION-TYPE
OBJECTS     { trapInfo }
STATUS      current
DESCRIPTION
        "High Voltage"
 ::= { psRetire  43 }

psRetireDc1Hfv   NOTIFICATION-TYPE
OBJECTS     { trapInfo }
STATUS      current
DESCRIPTION
        "High Float Voltage"
 ::= { psRetire  44 }

psRetirePs1Cra   NOTIFICATION-TYPE
OBJECTS     { trapInfo }
STATUS      current
DESCRIPTION
        "Intelligent Controller Fail"
 ::= { psRetire  45 }

psRetirePs1Crf   NOTIFICATION-TYPE
OBJECTS     { trapInfo }
STATUS      current
DESCRIPTION
        "Intelligent Controller Fuse"
 ::= { psRetire  46 }

psRetirePs1Cpa   NOTIFICATION-TYPE
OBJECTS     { trapInfo }
STATUS      current
DESCRIPTION
        "Circuit Pack Fail"
 ::= { psRetire  47 }

psRetirePs1Rpf   NOTIFICATION-TYPE
OBJECTS     { trapInfo }
STATUS      current
DESCRIPTION
        "Remote Peripheral Fuse"
 ::= { psRetire  48 }

psRetirePs1Pcf   NOTIFICATION-TYPE
OBJECTS     { trapInfo }
STATUS      current
DESCRIPTION
        "PC Power Fuse"
 ::= { psRetire  49 }

psRetirePs1Epr   NOTIFICATION-TYPE
OBJECTS     { trapInfo }
STATUS      current
DESCRIPTION
        "External Password Reset"
 ::= { psRetire  50 }

psRetirePs1Pfd   NOTIFICATION-TYPE
OBJECTS     { trapInfo }
STATUS      current
DESCRIPTION
        "Passwords At Default"
 ::= { psRetire  51 }

psRetirePs1Exl   NOTIFICATION-TYPE
OBJECTS     { trapInfo }
STATUS      current
DESCRIPTION
        "Excessive Login Attempts"
 ::= { psRetire  52 }

psRetirePs1Bbl   NOTIFICATION-TYPE
OBJECTS     { trapInfo }
STATUS      current
DESCRIPTION
        "Memory Backup Battery Low"
 ::= { psRetire  53 }

psRetirePs1Pht   NOTIFICATION-TYPE
OBJECTS     { trapInfo }
STATUS      current
DESCRIPTION
        "Processor Halt"
 ::= { psRetire  54 }

psRetirePs1Clc   NOTIFICATION-TYPE
OBJECTS     { trapInfo }
STATUS      current
DESCRIPTION
        "Clock Changed"
 ::= { psRetire  55 }

psRetirePs1Stf   NOTIFICATION-TYPE
OBJECTS     { trapInfo }
STATUS      current
DESCRIPTION
        "Self Test Failed"
 ::= { psRetire  56 }

psRetirePs1Pgi   NOTIFICATION-TYPE
OBJECTS     { trapInfo }
STATUS      current
DESCRIPTION
        "Program Line Invalid"
 ::= { psRetire  57 }

psRetirePs1Cch   NOTIFICATION-TYPE
OBJECTS     { trapInfo }
STATUS      current
DESCRIPTION
        "Configuration Changed"
 ::= { psRetire  58 }

psRetirePs1Hcl   NOTIFICATION-TYPE
OBJECTS     { trapInfo }
STATUS      current
DESCRIPTION
        "History Cleared"
 ::= { psRetire  59 }

psRetirePs1Mor   NOTIFICATION-TYPE
OBJECTS     { trapInfo }
STATUS      current
DESCRIPTION
        "Measurement Out Of Range"
 ::= { psRetire  60 }

psRetirePs1Mtc   NOTIFICATION-TYPE
OBJECTS     { trapInfo }
STATUS      current
DESCRIPTION
        "Module Type Conflict"
 ::= { psRetire  61 }

psRetirePs1Mdf   NOTIFICATION-TYPE
OBJECTS     { trapInfo }
STATUS      current
DESCRIPTION
        "Module Failure"
 ::= { psRetire  62 }

psRetireAt1Ata   NOTIFICATION-TYPE
OBJECTS     { trapInfo }
STATUS      current
DESCRIPTION
        "Alarm Test Active"
 ::= { psRetire  63 }

psRetireAt1Atf   NOTIFICATION-TYPE
OBJECTS     { trapInfo }
STATUS      current
DESCRIPTION
        "Alarm Test Failed"
 ::= { psRetire  64 }

psRetireAt1Atb   NOTIFICATION-TYPE
OBJECTS     { trapInfo }
STATUS      current
DESCRIPTION
        "Alarm Test Aborted"
 ::= { psRetire  65 }

psRetireCp1Cfa   NOTIFICATION-TYPE
OBJECTS     { trapInfo }
STATUS      current
DESCRIPTION
        "Converter Fail"
 ::= { psRetire  66 }

psRetireCp1Dfa   NOTIFICATION-TYPE
OBJECTS     { trapInfo }
STATUS      current
DESCRIPTION
        "Distribution Fail"
 ::= { psRetire  67 }

psRetireCp1Did   NOTIFICATION-TYPE
OBJECTS     { trapInfo }
STATUS      current
DESCRIPTION
        "ID Conflict"
 ::= { psRetire  68 }

psRetireCp1Mfa   NOTIFICATION-TYPE
OBJECTS     { trapInfo }
STATUS      current
DESCRIPTION
        "Multiple Converter Fail"
 ::= { psRetire  69 }

psRetireBs1Bsa   NOTIFICATION-TYPE
OBJECTS     { trapInfo }
STATUS      current
DESCRIPTION
        "Boost State Alarm"
 ::= { psRetire  70 }

psRetireBr1Bta   NOTIFICATION-TYPE
OBJECTS     { trapInfo }
STATUS      current
DESCRIPTION
        "Battery Test Active"
 ::= { psRetire  71 }

psRetireBr1Bfa   NOTIFICATION-TYPE
OBJECTS     { trapInfo }
STATUS      current
DESCRIPTION
        "Battery Test Failed"
 ::= { psRetire  72 }

psRetireBr1Bca   NOTIFICATION-TYPE
OBJECTS     { trapInfo }
STATUS      current
DESCRIPTION
        "Battery Type Conflict"
 ::= { psRetire  73 }

psRetireLdaDfa   NOTIFICATION-TYPE
OBJECTS     { trapInfo }
STATUS      current
DESCRIPTION
        "Distribution Fuse"
 ::= { psRetire  74 }

psRetireAcd1Prf   NOTIFICATION-TYPE
OBJECTS     { trapInfo }
STATUS      current
DESCRIPTION
        "Phase R Fail"
 ::= { psRetire  75 }

psRetireAcd1Psf   NOTIFICATION-TYPE
OBJECTS     { trapInfo }
STATUS      current
DESCRIPTION
        "Phase S Fail"
 ::= { psRetire  76 }

psRetireAcd1Ptf   NOTIFICATION-TYPE
OBJECTS     { trapInfo }
STATUS      current
DESCRIPTION
        "Phase T Fail"
 ::= { psRetire  77 }

psRetireAcd1Msa   NOTIFICATION-TYPE
OBJECTS     { trapInfo }
STATUS      current
DESCRIPTION
        "Master Switch Alarm"
 ::= { psRetire  78 }

psRetireCn1Cno   NOTIFICATION-TYPE
OBJECTS     { trapInfo }
STATUS      current
DESCRIPTION
        "Contactor Open"
 ::= { psRetire  79 }

psRetireCn1Cnf   NOTIFICATION-TYPE
OBJECTS     { trapInfo }
STATUS      current
DESCRIPTION
        "Contactor Failed"
 ::= { psRetire  80 }

psRetireCn2Cno   NOTIFICATION-TYPE
OBJECTS     { trapInfo }
STATUS      current
DESCRIPTION
        "Contactor Open"
 ::= { psRetire  81 }

psRetireCn2Cnf   NOTIFICATION-TYPE
OBJECTS     { trapInfo }
STATUS      current
DESCRIPTION
        "Contactor Failed"
 ::= { psRetire  82 }

psRetireCn3Cno   NOTIFICATION-TYPE
OBJECTS     { trapInfo }
STATUS      current
DESCRIPTION
        "Contactor Open"
 ::= { psRetire  83 }

psRetireCn3Cnf   NOTIFICATION-TYPE
OBJECTS     { trapInfo }
STATUS      current
DESCRIPTION
        "Contactor Failed"
 ::= { psRetire  84 }

psRetireAco1Aac   NOTIFICATION-TYPE
OBJECTS     { trapInfo }
STATUS      current
DESCRIPTION
        "ACO Active"
 ::= { psRetire  85 }

psRetireCm1Cof   NOTIFICATION-TYPE
OBJECTS     { trapInfo }
STATUS      current
DESCRIPTION
        "Queue Overflow"
 ::= { psRetire  86 }

psRetireCm1Cor   NOTIFICATION-TYPE
OBJECTS     { trapInfo }
STATUS      current
DESCRIPTION
        "Number Did Not Respond"
 ::= { psRetire  87 }

psRetireCm1Nnc   NOTIFICATION-TYPE
OBJECTS     { trapInfo }
STATUS      current
DESCRIPTION
        "Number Not Configured"
 ::= { psRetire  88 }

psRetirePo1Por   NOTIFICATION-TYPE
OBJECTS     { trapInfo }
STATUS      current
DESCRIPTION
        "Number Did Not Respond"
 ::= { psRetire  89 }

psRetireDs1Cea   NOTIFICATION-TYPE
OBJECTS     { trapInfo }
STATUS      current
DESCRIPTION
        "Connected Equipment Alarm"
 ::= { psRetire  90 }

psRetireDs2Cea   NOTIFICATION-TYPE
OBJECTS     { trapInfo }
STATUS      current
DESCRIPTION
        "Connected Equipment Alarm"
 ::= { psRetire  91 }

psRetireDs3Cea   NOTIFICATION-TYPE
OBJECTS     { trapInfo }
STATUS      current
DESCRIPTION
        "Connected Equipment Alarm"
 ::= { psRetire  92 }

psRetireDs4Cea   NOTIFICATION-TYPE
OBJECTS     { trapInfo }
STATUS      current
DESCRIPTION
        "Connected Equipment Alarm"
 ::= { psRetire  93 }

psRetireDs5Cea   NOTIFICATION-TYPE
OBJECTS     { trapInfo }
STATUS      current
DESCRIPTION
        "Connected Equipment Alarm"
 ::= { psRetire  94 }

psRetireDs6Cea   NOTIFICATION-TYPE
OBJECTS     { trapInfo }
STATUS      current
DESCRIPTION
        "Connected Equipment Alarm"
 ::= { psRetire  95 }

psRetireUserDefined   NOTIFICATION-TYPE
OBJECTS     { trapInfo }
STATUS      current
DESCRIPTION
        "This may be a user defined event, or a new controller event."
 ::= { psRetire  96 }

psRetireCn4Cno   NOTIFICATION-TYPE
OBJECTS     { trapInfo }
STATUS      current
DESCRIPTION
        "Contactor Open"
 ::= { psRetire  97 }

psRetireCn4Cnf   NOTIFICATION-TYPE
OBJECTS     { trapInfo }
STATUS      current
DESCRIPTION
        "Contactor Failed"
 ::= { psRetire  98 }

psRetireDc1Vmf   NOTIFICATION-TYPE
OBJECTS     { trapInfo }
STATUS      current
DESCRIPTION
        "Voltage Module Failure"
 ::= { psRetire  99 }

psRetireDc1Epo   NOTIFICATION-TYPE
OBJECTS     { trapInfo }
STATUS      current
DESCRIPTION
        "Emergency Power Off"
 ::= { psRetire  100 }

psRetireDc1Icr   NOTIFICATION-TYPE
OBJECTS     { trapInfo }
STATUS      current
DESCRIPTION
        "Incompatible Rectifier"
 ::= { psRetire  101 }

psRetireDc1Rfn   NOTIFICATION-TYPE
OBJECTS     { trapInfo }
STATUS      current
DESCRIPTION
        "Rectifier Fan Failure"
 ::= { psRetire  102 }

psRetirePs1Ax1   NOTIFICATION-TYPE
OBJECTS     { trapInfo }
STATUS      current
DESCRIPTION
        "Auxiliary Event 1"
 ::= { psRetire  103 }

psRetirePs1Ax2   NOTIFICATION-TYPE
OBJECTS     { trapInfo }
STATUS      current
DESCRIPTION
        "Auxiliary Event 2"
 ::= { psRetire  104 }

psRetirePs1Ax3   NOTIFICATION-TYPE
OBJECTS     { trapInfo }
STATUS      current
DESCRIPTION
        "Auxiliary Event 3"
 ::= { psRetire  105 }

psRetirePs1Ax4   NOTIFICATION-TYPE
OBJECTS     { trapInfo }
STATUS      current
DESCRIPTION
        "Auxiliary Event 4"
 ::= { psRetire  106 }

psRetirePs1Ax5   NOTIFICATION-TYPE
OBJECTS     { trapInfo }
STATUS      current
DESCRIPTION
        "Auxiliary Event 5"
 ::= { psRetire  107 }

psRetirePs1Ax6   NOTIFICATION-TYPE
OBJECTS     { trapInfo }
STATUS      current
DESCRIPTION
        "Auxiliary Event 6"
 ::= { psRetire  108 }

psRetireCp1Cfn   NOTIFICATION-TYPE
OBJECTS     { trapInfo }
STATUS      current
DESCRIPTION
        "Converter Fan Minor"
 ::= { psRetire  109 }

psRetireCp1Cfj   NOTIFICATION-TYPE
OBJECTS     { trapInfo }
STATUS      current
DESCRIPTION
        "Converter Fan Major"
 ::= { psRetire  110 }

psRetireCp1Icc   NOTIFICATION-TYPE
OBJECTS     { trapInfo }
STATUS      current
DESCRIPTION
        "Incompatible Converter"
 ::= { psRetire  111 }

psRetireCp1Hfv   NOTIFICATION-TYPE
OBJECTS     { trapInfo }
STATUS      current
DESCRIPTION
        "Converter High Voltage Minor"
 ::= { psRetire  112 }

psRetireCp1Hva   NOTIFICATION-TYPE
OBJECTS     { trapInfo }
STATUS      current
DESCRIPTION
        "Converter High Voltage Major"
 ::= { psRetire  113 }

psRetireCp1Vla   NOTIFICATION-TYPE
OBJECTS     { trapInfo }
STATUS      current
DESCRIPTION
        "Converter Low Voltage Alarm"
 ::= { psRetire  114 }

psRetireCp1Rl   NOTIFICATION-TYPE
OBJECTS     { trapInfo }
STATUS      current
DESCRIPTION
        "Converter Redundancy Loss"
 ::= { psRetire  115 }

psRetireBr1Scda   NOTIFICATION-TYPE
OBJECTS     { trapInfo }
STATUS      current
DESCRIPTION
        "Shorted Cell Detected"
 ::= { psRetire  116 }

psRetireBr1Isda   NOTIFICATION-TYPE
OBJECTS     { trapInfo }
STATUS      current
DESCRIPTION
        "Imminent Low Voltage Shutdown"
 ::= { psRetire  117 }

psRetireBr1Mdp   NOTIFICATION-TYPE
OBJECTS     { trapInfo }
STATUS      current
DESCRIPTION
        "Voltage Module Duplicate ID"
 ::= { psRetire  118 }

psRetireBr1Mzd   NOTIFICATION-TYPE
OBJECTS     { trapInfo }
STATUS      current
DESCRIPTION
        "Voltage Module Zero ID"
 ::= { psRetire  119 }

psRetireBr1Btha   NOTIFICATION-TYPE
OBJECTS     { trapInfo }
STATUS      current
DESCRIPTION
        "High Battery Temperature"
 ::= { psRetire  120 }

psRetireDc1Rrtl   NOTIFICATION-TYPE
OBJECTS     { trapInfo }
STATUS      current
DESCRIPTION
        "Real-Time Reserve Low"
 ::= { psRetire  121 }

psRetireDc1Rls   NOTIFICATION-TYPE
OBJECTS     { trapInfo }
STATUS      current
DESCRIPTION
        "Redundancy Loss"
 ::= { psRetire  122 }

psRetireDc1Macf   NOTIFICATION-TYPE
OBJECTS     { trapInfo }
STATUS      current
DESCRIPTION
        "Multiple AC Fail"
 ::= { psRetire  123 }

psRetireDc1Mman   NOTIFICATION-TYPE
OBJECTS     { trapInfo }
STATUS      current
DESCRIPTION
        "Multiple Manual Off"
 ::= { psRetire  124 }

psRetireDc1Faj2   NOTIFICATION-TYPE
OBJECTS     { trapInfo }
STATUS      current
DESCRIPTION
        "External Fuse Major 2"
 ::= { psRetire  125 }

psRetirePs1Amtl   NOTIFICATION-TYPE
OBJECTS     { trapInfo }
STATUS      current
DESCRIPTION
        "Low Ambient Temperature"
 ::= { psRetire  126 }

psRetirePs1Amth   NOTIFICATION-TYPE
OBJECTS     { trapInfo }
STATUS      current
DESCRIPTION
        "High Ambient Temperature"
 ::= { psRetire  127 }

psRetireRp1Rf   NOTIFICATION-TYPE
OBJECTS     { trapInfo }
STATUS      current
DESCRIPTION
        "Ringer Minor Fail"
 ::= { psRetire  128 }

psRetireRp1Rpff   NOTIFICATION-TYPE
OBJECTS     { trapInfo }
STATUS      current
DESCRIPTION
        "Ringer Fan Fail"
 ::= { psRetire  129 }

psRetireRp1Rpxj   NOTIFICATION-TYPE
OBJECTS     { trapInfo }
STATUS      current
DESCRIPTION
        "Ringer Major External Fault"
 ::= { psRetire  130 }

psRetireRp1Rpxn   NOTIFICATION-TYPE
OBJECTS     { trapInfo }
STATUS      current
DESCRIPTION
        "Ringer Minor External Fault"
 ::= { psRetire  131 }

psRetireRp1Rprl   NOTIFICATION-TYPE
OBJECTS     { trapInfo }
STATUS      current
DESCRIPTION
        "Ringer Redundancy Loss"
 ::= { psRetire  132 }

psRetireRp1Rpfj   NOTIFICATION-TYPE
OBJECTS     { trapInfo }
STATUS      current
DESCRIPTION
        "Ringer Major Fail"
 ::= { psRetire  133 }

psRetireRp1Rcdp   NOTIFICATION-TYPE
OBJECTS     { trapInfo }
STATUS      current
DESCRIPTION
        "Ringer ID Conflict"
 ::= { psRetire  134 }

psRetireDc1Pfs   NOTIFICATION-TYPE
OBJECTS     { trapInfo }
STATUS      current
DESCRIPTION
        "Thermal Probe Fail Safe"
 ::= { psRetire  135 }

psRetireDc1Rif   NOTIFICATION-TYPE
OBJECTS     { trapInfo }
STATUS      current
DESCRIPTION
        "Rectifier Internal Fault"
 ::= { psRetire  136 }

psRetireCp1Cin   NOTIFICATION-TYPE
OBJECTS     { trapInfo }
STATUS      current
DESCRIPTION
        "Converter Input Fail"
 ::= { psRetire  137 }

psRetireBr1Btla   NOTIFICATION-TYPE
OBJECTS     { trapInfo }
STATUS      current
DESCRIPTION
        "Low Battery Temperature"
 ::= { psRetire  138 }

psRetireBr1Btvh   NOTIFICATION-TYPE
OBJECTS     { trapInfo }
STATUS      current
DESCRIPTION
        "Very High Battery Temperature"
 ::= { psRetire  139 }

psRetireBr1Btvl   NOTIFICATION-TYPE
OBJECTS     { trapInfo }
STATUS      current
DESCRIPTION
        "Very Low Battery Temperature"
 ::= { psRetire  140 }

psRetireDc1Pid   NOTIFICATION-TYPE
OBJECTS     { trapInfo }
STATUS      current
DESCRIPTION
        "Panel Interface ID Conflict"
 ::= { psRetire  141 }

psRetireIvp1Ilvi   NOTIFICATION-TYPE
OBJECTS     { trapInfo }
STATUS      current
DESCRIPTION
        "Inverter Low Input"
 ::= { psRetire  142 }

psRetireIvp1Ihvi   NOTIFICATION-TYPE
OBJECTS     { trapInfo }
STATUS      current
DESCRIPTION
        "Inverter High Input"
 ::= { psRetire  143 }

psRetireIvp1Ita   NOTIFICATION-TYPE
OBJECTS     { trapInfo }
STATUS      current
DESCRIPTION
        "Inverter High Temperature"
 ::= { psRetire  144 }

psRetireIvp1If   NOTIFICATION-TYPE
OBJECTS     { trapInfo }
STATUS      current
DESCRIPTION
        "Inverter Fail"
 ::= { psRetire  145 }

psRetireIvp1Ilv   NOTIFICATION-TYPE
OBJECTS     { trapInfo }
STATUS      current
DESCRIPTION
        "Inverter Low Output"
 ::= { psRetire  146 }

psRetireIvp1Ifa   NOTIFICATION-TYPE
OBJECTS     { trapInfo }
STATUS      current
DESCRIPTION
        "Inverter Frequency Lock"
 ::= { psRetire  147 }

psRetireIvp1Ihv   NOTIFICATION-TYPE
OBJECTS     { trapInfo }
STATUS      current
DESCRIPTION
        "Inverter High Output"
 ::= { psRetire  148 }

psRetireIvp1Ida   NOTIFICATION-TYPE
OBJECTS     { trapInfo }
STATUS      current
DESCRIPTION
        "Inverter Distribution Alarm"
 ::= { psRetire  149 }

psRetireIvp1Iof   NOTIFICATION-TYPE
OBJECTS     { trapInfo }
STATUS      current
DESCRIPTION
        "Inverter Output Fuse"
 ::= { psRetire  150 }

psRetireIvp1Idid   NOTIFICATION-TYPE
OBJECTS     { trapInfo }
STATUS      current
DESCRIPTION
        "Inverter ID Conflict"
 ::= { psRetire  151 }

psRetireIvp1Iirm   NOTIFICATION-TYPE
OBJECTS     { trapInfo }
STATUS      current
DESCRIPTION
        "Inverter High RMS Current"
 ::= { psRetire  152 }

psRetireIvp1Iipk   NOTIFICATION-TYPE
OBJECTS     { trapInfo }
STATUS      current
DESCRIPTION
        "Inverter High Peak Current"
 ::= { psRetire  153 }

psRetireIvp1Icf   NOTIFICATION-TYPE
OBJECTS     { trapInfo }
STATUS      current
DESCRIPTION
        "Inverter High Crest Factor"
 ::= { psRetire  154 }

psRetireIvp1Mif   NOTIFICATION-TYPE
OBJECTS     { trapInfo }
STATUS      current
DESCRIPTION
        "Multiple Inverter Fail"
 ::= { psRetire  155 }

psRetireIvp1Irls   NOTIFICATION-TYPE
OBJECTS     { trapInfo }
STATUS      current
DESCRIPTION
        "Inverter Redundancy Loss"
 ::= { psRetire  156 }

psRetireIvp1Milv   NOTIFICATION-TYPE
OBJECTS     { trapInfo }
STATUS      current
DESCRIPTION
        "Multiple Inverter Low Input Voltage"
 ::= { psRetire  157 }

psRetireDc1Rtl2   NOTIFICATION-TYPE
OBJECTS     { trapInfo }
STATUS      current
DESCRIPTION
        "Reserve Time Low 2"
 ::= { psRetire  158 }

psRetireDc1Faja   NOTIFICATION-TYPE
OBJECTS     { trapInfo }
STATUS      current
DESCRIPTION
        "Distribution Fuse A"
 ::= { psRetire  159 }

psRetireDc1Fajb   NOTIFICATION-TYPE
OBJECTS     { trapInfo }
STATUS      current
DESCRIPTION
        "Distribution Fuse B"
 ::= { psRetire  160 }

psRetireDc1Vlva   NOTIFICATION-TYPE
OBJECTS     { trapInfo }
STATUS      current
DESCRIPTION
        "VA Power Loss"
 ::= { psRetire  161 }

psRetireDc1Vlvb   NOTIFICATION-TYPE
OBJECTS     { trapInfo }
STATUS      current
DESCRIPTION
        "VB Power Loss"
 ::= { psRetire  162 }

psRetireDc1Ovla   NOTIFICATION-TYPE
OBJECTS     { trapInfo }
STATUS      current
DESCRIPTION
        "IA Overload"
 ::= { psRetire  163 }

psRetireDc1Ovlb   NOTIFICATION-TYPE
OBJECTS     { trapInfo }
STATUS      current
DESCRIPTION
        "IB Overload"
 ::= { psRetire  164 }

psRetireDc1Smw   NOTIFICATION-TYPE
OBJECTS     { trapInfo }
STATUS      current
DESCRIPTION
        "Shunt Mis-wired"
 ::= { psRetire  165 }

psRetireDc1Cca   NOTIFICATION-TYPE
OBJECTS     { trapInfo }
STATUS      current
DESCRIPTION
        "Circuit Assignment"
 ::= { psRetire  166 }

psRetireDc1Rrtl2   NOTIFICATION-TYPE
OBJECTS     { trapInfo }
STATUS      current
DESCRIPTION
        "Real-Time Reserve Low"
 ::= { psRetire  167 }

psRetireDc1Vhav   NOTIFICATION-TYPE
OBJECTS     { trapInfo }
STATUS      current
DESCRIPTION
        "Very High AC Voltage"
 ::= { psRetire  168 }

psRetireDc1Hav   NOTIFICATION-TYPE
OBJECTS     { trapInfo }
STATUS      current
DESCRIPTION
        "High AC Voltage"
 ::= { psRetire  169 }

psRetireDc1Vlav   NOTIFICATION-TYPE
OBJECTS     { trapInfo }
STATUS      current
DESCRIPTION
        "Very Low AC Voltage"
 ::= { psRetire  170 }

psRetireDc1Lav   NOTIFICATION-TYPE
OBJECTS     { trapInfo }
STATUS      current
DESCRIPTION
        "Low AC Voltage"
 ::= { psRetire  171 }

psRetireDc1Tic   NOTIFICATION-TYPE
OBJECTS     { trapInfo }
STATUS      current
DESCRIPTION
        "Total Installed Capacity"
 ::= { psRetire  172 }

psRetireDc1Tcc   NOTIFICATION-TYPE
OBJECTS     { trapInfo }
STATUS      current
DESCRIPTION
        "Total Configured Capacity"
 ::= { psRetire  173 }

psRetireCn5Cno   NOTIFICATION-TYPE
OBJECTS     { trapInfo }
STATUS      current
DESCRIPTION
        "Battery Shunt Trip Open"
 ::= { psRetire  174 }

psRetireCn5Cnf   NOTIFICATION-TYPE
OBJECTS     { trapInfo }
STATUS      current
DESCRIPTION
        "Battery Shunt Trip Failed"
 ::= { psRetire  175 }

psRetireDc1Pcaux   NOTIFICATION-TYPE
OBJECTS     { trapInfo }
STATUS      current
DESCRIPTION
        "PIC Auxiliary"
 ::= { psRetire  176 }

psRetireDc1Slot   NOTIFICATION-TYPE
OBJECTS     { trapInfo }
STATUS      current
DESCRIPTION
        "PIC Slot"
 ::= { psRetire  177 }

psRetireDc1Vid   NOTIFICATION-TYPE
OBJECTS     { trapInfo }
STATUS      current
DESCRIPTION
        "BDFB/BDCBB ID Conflict"
 ::= { psRetire  178 }

--
-- table COE
--

psCoeTable    OBJECT-TYPE
SYNTAX SEQUENCE OF PsCoeEntry
MAX-ACCESS not-accessible
STATUS current
DESCRIPTION
        "Table of all Email Address data"
 ::= { powerSystem  51 }

psCoeEntry OBJECT-TYPE
SYNTAX     PsCoeEntry
MAX-ACCESS  not-accessible
STATUS      current
DESCRIPTION
       "Entry of information for one Email Address"
INDEX { psCoeEntryIndex }
 ::= { psCoeTable  1 }

PsCoeEntry ::= SEQUENCE {
psCoeEntryIndex   INTEGER,
psCoeEntryIde   DisplayString,
psCoeEntryDes   DisplayString,
psCoeEntryAdr   DisplayString,
psCoeEntryTyp   DisplayString
}

psCoeEntryIndex OBJECT-TYPE
SYNTAX      INTEGER (0..2147483647)
MAX-ACCESS  read-only
STATUS      current
DESCRIPTION
"Table Index"
 ::= { psCoeEntry  1 }

psCoeEntryIde OBJECT-TYPE
SYNTAX      DisplayString
MAX-ACCESS  read-only
STATUS      current
DESCRIPTION
"Identifier"
 ::= { psCoeEntry  2 }

psCoeEntryDes OBJECT-TYPE
SYNTAX      DisplayString
MAX-ACCESS  read-write
STATUS      current
DESCRIPTION
"Description"
 ::= { psCoeEntry  3 }

psCoeEntryAdr OBJECT-TYPE
SYNTAX      DisplayString
MAX-ACCESS  read-write
STATUS      current
DESCRIPTION
"Email Address"
 ::= { psCoeEntry  4 }

psCoeEntryTyp OBJECT-TYPE
SYNTAX      DisplayString
MAX-ACCESS  read-write
STATUS      current
DESCRIPTION
"Address Type"
 ::= { psCoeEntry  5 }



--
-- table SND
--

psSndTable    OBJECT-TYPE
SYNTAX SEQUENCE OF PsSndEntry
MAX-ACCESS not-accessible
STATUS current
DESCRIPTION
        "Table of all SNMP Trap Destination data"
 ::= { powerSystem  52 }

psSndEntry OBJECT-TYPE
SYNTAX     PsSndEntry
MAX-ACCESS  not-accessible
STATUS      current
DESCRIPTION
       "Entry of information for one SNMP Trap Destination"
INDEX { psSndEntryIndex }
 ::= { psSndTable  1 }

PsSndEntry ::= SEQUENCE {
psSndEntryIndex   INTEGER,
psSndEntryIde   DisplayString,
psSndEntryDes   DisplayString,
psSndEntryIp   DisplayString,
psSndEntryCs   DisplayString
}

psSndEntryIndex OBJECT-TYPE
SYNTAX      INTEGER (0..2147483647)
MAX-ACCESS  read-only
STATUS      current
DESCRIPTION
"Table Index"
 ::= { psSndEntry  1 }

psSndEntryIde OBJECT-TYPE
SYNTAX      DisplayString
MAX-ACCESS  read-only
STATUS      current
DESCRIPTION
"Identifier"
 ::= { psSndEntry  2 }

psSndEntryDes OBJECT-TYPE
SYNTAX      DisplayString
MAX-ACCESS  read-write
STATUS      current
DESCRIPTION
"Description"
 ::= { psSndEntry  3 }

psSndEntryIp OBJECT-TYPE
SYNTAX      DisplayString
MAX-ACCESS  read-write
STATUS      current
DESCRIPTION
"IP Address"
 ::= { psSndEntry  4 }

psSndEntryCs OBJECT-TYPE
SYNTAX      DisplayString
MAX-ACCESS  read-write
STATUS      current
DESCRIPTION
"Community String"
 ::= { psSndEntry  5 }



--
-- table CC
--

psCcTable    OBJECT-TYPE
SYNTAX SEQUENCE OF PsCcEntry
MAX-ACCESS not-accessible
STATUS current
DESCRIPTION
        "Table of all Controller Channel data"
 ::= { powerSystem  53 }

psCcEntry OBJECT-TYPE
SYNTAX     PsCcEntry
MAX-ACCESS  not-accessible
STATUS      current
DESCRIPTION
       "Entry of information for one Controller Channel"
INDEX { psCcEntryIndex }
 ::= { psCcTable  1 }

PsCcEntry ::= SEQUENCE {
psCcEntryIndex   INTEGER,
psCcEntryIde   DisplayString,
psCcEntryDes   DisplayString,
psCcEntryVal   DisplayString,
psCcEntryUni   DisplayString,
psCcEntryOfs   DisplayString,
psCcEntryScf   DisplayString,
psCcEntryIbt   INTEGER,
psCcEntryRng   INTEGER
}

psCcEntryIndex OBJECT-TYPE
SYNTAX      INTEGER (0..2147483647)
MAX-ACCESS  read-only
STATUS      current
DESCRIPTION
"Table Index"
 ::= { psCcEntry  1 }

psCcEntryIde OBJECT-TYPE
SYNTAX      DisplayString
MAX-ACCESS  read-only
STATUS      current
DESCRIPTION
"Identifier"
 ::= { psCcEntry  2 }

psCcEntryDes OBJECT-TYPE
SYNTAX      DisplayString
MAX-ACCESS  read-write
STATUS      current
DESCRIPTION
"Description"
 ::= { psCcEntry  3 }

psCcEntryVal OBJECT-TYPE
SYNTAX      DisplayString
MAX-ACCESS  read-only
STATUS      current
DESCRIPTION
"Value"
 ::= { psCcEntry  4 }

psCcEntryUni OBJECT-TYPE
SYNTAX      DisplayString
MAX-ACCESS  read-write
STATUS      current
DESCRIPTION
"Units"
 ::= { psCcEntry  5 }

psCcEntryOfs OBJECT-TYPE
SYNTAX      DisplayString
MAX-ACCESS  read-write
STATUS      current
DESCRIPTION
"Offset"
 ::= { psCcEntry  6 }

psCcEntryScf OBJECT-TYPE
SYNTAX      DisplayString
MAX-ACCESS  read-write
STATUS      current
DESCRIPTION
"Scale Factor"
 ::= { psCcEntry  7 }

psCcEntryIbt OBJECT-TYPE
SYNTAX      INTEGER {
disable(0),
enable(1)
}
MAX-ACCESS  read-write
STATUS      current
DESCRIPTION
"Battery Temperature
Values:
disable(0),
enable(1)
"
 ::= { psCcEntry  8 }

psCcEntryRng OBJECT-TYPE
SYNTAX      INTEGER {
r5V(5),
r30V(30),
r60V(60)
}
MAX-ACCESS  read-write
STATUS      current
DESCRIPTION
"Input Range
Values:
r5V(5),
r30V(30),
r60V(60)
"
 ::= { psCcEntry  9 }



--
-- table INP
--

psInpTable    OBJECT-TYPE
SYNTAX SEQUENCE OF PsInpEntry
MAX-ACCESS not-accessible
STATUS current
DESCRIPTION
        "Table of all Input Management data"
 ::= { powerSystem  54 }

psInpEntry OBJECT-TYPE
SYNTAX     PsInpEntry
MAX-ACCESS  not-accessible
STATUS      current
DESCRIPTION
       "Entry of information for one Input Management"
INDEX { psInpEntryIndex }
 ::= { psInpTable  1 }

PsInpEntry ::= SEQUENCE {
psInpEntryIndex   INTEGER,
psInpEntryIde   DisplayString,
psInpEntryDes   DisplayString,
psInpEntryStt   INTEGER,
psInpEntryTyp   DisplayString,
psInpEntryPol   DisplayString,
psInpEntryBrc   DisplayString,
psInpEntrySn   DisplayString
}

psInpEntryIndex OBJECT-TYPE
SYNTAX      INTEGER (0..2147483647)
MAX-ACCESS  read-only
STATUS      current
DESCRIPTION
"Table Index"
 ::= { psInpEntry  1 }

psInpEntryIde OBJECT-TYPE
SYNTAX      DisplayString
MAX-ACCESS  read-only
STATUS      current
DESCRIPTION
"Identifier"
 ::= { psInpEntry  2 }

psInpEntryDes OBJECT-TYPE
SYNTAX      DisplayString
MAX-ACCESS  read-write
STATUS      current
DESCRIPTION
"Description"
 ::= { psInpEntry  3 }

psInpEntryStt OBJECT-TYPE
SYNTAX      INTEGER {
alarming(1),
nonAlarming(0)
}
MAX-ACCESS  read-only
STATUS      current
DESCRIPTION
"Input State
Values:
alarming(1),
nonAlarming(0)
"
 ::= { psInpEntry  4 }

psInpEntryTyp OBJECT-TYPE
SYNTAX      DisplayString
MAX-ACCESS  read-write
STATUS      current
DESCRIPTION
"Type Alarm Object ID or, REMLVD for Remote LVD"
 ::= { psInpEntry  5 }

psInpEntryPol OBJECT-TYPE
SYNTAX      DisplayString
MAX-ACCESS  read-write
STATUS      current
DESCRIPTION
"Input Alarming Polarity
Values:
OPEN,
CLOSED
"
 ::= { psInpEntry  6 }

psInpEntryBrc OBJECT-TYPE
SYNTAX      DisplayString
MAX-ACCESS  read-only
STATUS      current
DESCRIPTION
"Board Code"
 ::= { psInpEntry  7 }

psInpEntrySn OBJECT-TYPE
SYNTAX      DisplayString
MAX-ACCESS  read-only
STATUS      current
DESCRIPTION
"Serial Number"
 ::= { psInpEntry  8 }



--
-- object psCn4
--

psCn4 OBJECT IDENTIFIER  ::= { powerSystem  55 }

psCn4Ide OBJECT-TYPE
SYNTAX      DisplayString
MAX-ACCESS  read-only
STATUS      current
DESCRIPTION
"Identifier"
 ::= { psCn4  1 }

psCn4Des OBJECT-TYPE
SYNTAX      DisplayString
MAX-ACCESS  read-write
STATUS      current
DESCRIPTION
"Description"
 ::= { psCn4  2 }

psCn4Stt OBJECT-TYPE
SYNTAX      DisplayString
MAX-ACCESS  read-write
STATUS      current
DESCRIPTION
"Status
Values:
NONE,
DISCON,
CONNECT,
FAILED
"
 ::= { psCn4  3 }

psCn4Typ OBJECT-TYPE
SYNTAX      DisplayString
MAX-ACCESS  read-write
STATUS      current
DESCRIPTION
"Type
Values:
NONE,
BATTERY,
LOAD
"
 ::= { psCn4  4 }

psCn4Dth OBJECT-TYPE
SYNTAX      Integer32(20000..50000)
MAX-ACCESS  read-write
STATUS      current
DESCRIPTION
"Disconnect Threshold"
 ::= { psCn4  5 }

psCn4Rth OBJECT-TYPE
SYNTAX      Integer32(22000..55000)
UNITS       "mV"
MAX-ACCESS  read-write
STATUS      current
DESCRIPTION
"Reconnect Threshold (mV)"
 ::= { psCn4  6 }

psCn4Cno OBJECT-TYPE
SYNTAX      DisplayString
MAX-ACCESS  read-only
STATUS      current
DESCRIPTION
"Contactor Open
Value:
Alarm report from CNO4
"
 ::= { psCn4  7 }

psCn4Cnf OBJECT-TYPE
SYNTAX      DisplayString
MAX-ACCESS  read-only
STATUS      current
DESCRIPTION
"Contactor Failed
Value:
Alarm report from CNF4
"
 ::= { psCn4  8 }

psCn4Ena OBJECT-TYPE
SYNTAX      INTEGER {
disable(0),
enable(1)
}
MAX-ACCESS  read-write
STATUS      current
DESCRIPTION
"Control
Values:
disable(0),
enable(1)
"
 ::= { psCn4  9 }

psCn4Ddy OBJECT-TYPE
SYNTAX      Integer32(0..300)
UNITS       "Seconds"
MAX-ACCESS  read-write
STATUS      current
DESCRIPTION
"Disconnect Delay (Seconds)"
 ::= { psCn4  10 }

psCn4Dam OBJECT-TYPE
SYNTAX      INTEGER {
none(0),
voltage(1),
voltageAndTime(2)
}
MAX-ACCESS  read-write
STATUS      current
DESCRIPTION
"Disconnect Automode
Values:
none(0),
voltage(1),
voltageAndTime(2)
"
 ::= { psCn4  11 }

psCn4Dtm OBJECT-TYPE
SYNTAX      Integer32
UNITS       "Minutes"
MAX-ACCESS  read-only
STATUS      current
DESCRIPTION
"Disconnect Time Remaining (Minutes)"
 ::= { psCn4  12 }

psCn4Rdy OBJECT-TYPE
SYNTAX      Integer32(0..300)
UNITS       "Seconds"
MAX-ACCESS  read-write
STATUS      current
DESCRIPTION
"Reconnect Delay (Seconds)"
 ::= { psCn4  13 }

psCn4Ram OBJECT-TYPE
SYNTAX      INTEGER {
none(0),
voltage(1),
voltageAndTime(2)
}
MAX-ACCESS  read-write
STATUS      current
DESCRIPTION
"Reconnect Automode
Values:
none(0),
voltage(1),
voltageAndTime(2)
"
 ::= { psCn4  14 }

psCn4Rtm OBJECT-TYPE
SYNTAX      Integer32
UNITS       "Seconds"
MAX-ACCESS  read-only
STATUS      current
DESCRIPTION
"Reconnect Time Remaining (Seconds)"
 ::= { psCn4  15 }


--
-- table MSV
--

psMsvTable    OBJECT-TYPE
SYNTAX SEQUENCE OF PsMsvEntry
MAX-ACCESS not-accessible
STATUS current
DESCRIPTION
        "Table of all Midstring Voltage Monitor data"
 ::= { powerSystem  56 }

psMsvEntry OBJECT-TYPE
SYNTAX     PsMsvEntry
MAX-ACCESS  not-accessible
STATUS      current
DESCRIPTION
       "Entry of information for one Midstring Voltage Monitor"
INDEX { psMsvEntryIndex }
 ::= { psMsvTable  1 }

PsMsvEntry ::= SEQUENCE {
psMsvEntryIndex   INTEGER,
psMsvEntryIde   DisplayString,
psMsvEntryDes   DisplayString,
psMsvEntryStt   DisplayString,
psMsvEntryVal   DisplayString,
psMsvEntryDid   DisplayString,
psMsvEntryDid1   INTEGER
}

psMsvEntryIndex OBJECT-TYPE
SYNTAX      INTEGER (0..2147483647)
MAX-ACCESS  read-only
STATUS      current
DESCRIPTION
"Table Index"
 ::= { psMsvEntry  1 }

psMsvEntryIde OBJECT-TYPE
SYNTAX      DisplayString
MAX-ACCESS  read-only
STATUS      current
DESCRIPTION
"Identifier"
 ::= { psMsvEntry  2 }

psMsvEntryDes OBJECT-TYPE
SYNTAX      DisplayString
MAX-ACCESS  read-write
STATUS      current
DESCRIPTION
"Description"
 ::= { psMsvEntry  3 }

psMsvEntryStt OBJECT-TYPE
SYNTAX      DisplayString
MAX-ACCESS  read-only
STATUS      current
DESCRIPTION
"State"
 ::= { psMsvEntry  4 }

psMsvEntryVal OBJECT-TYPE
SYNTAX      DisplayString
UNITS       "Volts"
MAX-ACCESS  read-only
STATUS      current
DESCRIPTION
"Value (Volts)"
 ::= { psMsvEntry  5 }

psMsvEntryDid OBJECT-TYPE
SYNTAX      DisplayString
MAX-ACCESS  read-only
STATUS      current
DESCRIPTION
"ID Conflict"
 ::= { psMsvEntry  6 }

psMsvEntryDid1 OBJECT-TYPE
SYNTAX      INTEGER {
inactive(0),
active(1)
}
MAX-ACCESS  read-only
STATUS      current
DESCRIPTION
"Duplicate ID
Values:
inactive(0),
active(1)
"
 ::= { psMsvEntry  7 }



--
-- table DCM
--

psDcmTable    OBJECT-TYPE
SYNTAX SEQUENCE OF PsDcmEntry
MAX-ACCESS not-accessible
STATUS current
DESCRIPTION
        "Table of all Distribution Current Monitor data"
 ::= { powerSystem  57 }

psDcmEntry OBJECT-TYPE
SYNTAX     PsDcmEntry
MAX-ACCESS  not-accessible
STATUS      current
DESCRIPTION
       "Entry of information for one Distribution Current Monitor"
INDEX { psDcmEntryIndex }
 ::= { psDcmTable  1 }

PsDcmEntry ::= SEQUENCE {
psDcmEntryIndex   INTEGER,
psDcmEntryIde   DisplayString,
psDcmEntryDes   DisplayString,
psDcmEntryStt   DisplayString,
psDcmEntryTyp   DisplayString,
psDcmEntryVal   Integer32,
psDcmEntrySha   Integer32,
psDcmEntryShv   Integer32,
psDcmEntryBrc   DisplayString,
psDcmEntrySn   DisplayString
}

psDcmEntryIndex OBJECT-TYPE
SYNTAX      INTEGER (0..2147483647)
MAX-ACCESS  read-only
STATUS      current
DESCRIPTION
"Table Index"
 ::= { psDcmEntry  1 }

psDcmEntryIde OBJECT-TYPE
SYNTAX      DisplayString
MAX-ACCESS  read-only
STATUS      current
DESCRIPTION
"Identifier"
 ::= { psDcmEntry  2 }

psDcmEntryDes OBJECT-TYPE
SYNTAX      DisplayString
MAX-ACCESS  read-write
STATUS      current
DESCRIPTION
"Description"
 ::= { psDcmEntry  3 }

psDcmEntryStt OBJECT-TYPE
SYNTAX      DisplayString
MAX-ACCESS  read-only
STATUS      current
DESCRIPTION
"State
Values:
NONE,
MISSING,
PRESENT
"
 ::= { psDcmEntry  4 }

psDcmEntryTyp OBJECT-TYPE
SYNTAX      DisplayString
MAX-ACCESS  read-write
STATUS      current
DESCRIPTION
"Shunt Type
Values:
NONE,
LOAD,
BATTERY
"
 ::= { psDcmEntry  5 }

psDcmEntryVal OBJECT-TYPE
SYNTAX      Integer32
UNITS       "Amps x 1000"
MAX-ACCESS  read-only
STATUS      current
DESCRIPTION
"Reading (Amps x 1000)"
 ::= { psDcmEntry  6 }

psDcmEntrySha OBJECT-TYPE
SYNTAX      Integer32
UNITS       "Amps"
MAX-ACCESS  read-write
STATUS      current
DESCRIPTION
"Shunt Rating (Amps)"
 ::= { psDcmEntry  7 }

psDcmEntryShv OBJECT-TYPE
SYNTAX      Integer32(1..150)
UNITS       "mV"
MAX-ACCESS  read-write
STATUS      current
DESCRIPTION
"Shunt Rating (mV)"
 ::= { psDcmEntry  8 }

psDcmEntryBrc OBJECT-TYPE
SYNTAX      DisplayString
MAX-ACCESS  read-only
STATUS      current
DESCRIPTION
"Board Code"
 ::= { psDcmEntry  9 }

psDcmEntrySn OBJECT-TYPE
SYNTAX      DisplayString
MAX-ACCESS  read-only
STATUS      current
DESCRIPTION
"Serial Number"
 ::= { psDcmEntry  10 }



--
-- table DCN
--

psDcnTable    OBJECT-TYPE
SYNTAX SEQUENCE OF PsDcnEntry
MAX-ACCESS not-accessible
STATUS current
DESCRIPTION
        "Table of all Distribution Contactor Interface data"
 ::= { powerSystem  58 }

psDcnEntry OBJECT-TYPE
SYNTAX     PsDcnEntry
MAX-ACCESS  not-accessible
STATUS      current
DESCRIPTION
       "Entry of information for one Distribution Contactor Interface"
INDEX { psDcnEntryIndex }
 ::= { psDcnTable  1 }

PsDcnEntry ::= SEQUENCE {
psDcnEntryIndex   INTEGER,
psDcnEntryIde   DisplayString,
psDcnEntryDes   DisplayString,
psDcnEntryStt   DisplayString,
psDcnEntryTyp   DisplayString,
psDcnEntryBrc   DisplayString,
psDcnEntrySn   DisplayString
}

psDcnEntryIndex OBJECT-TYPE
SYNTAX      INTEGER (0..2147483647)
MAX-ACCESS  read-only
STATUS      current
DESCRIPTION
"Table Index"
 ::= { psDcnEntry  1 }

psDcnEntryIde OBJECT-TYPE
SYNTAX      DisplayString
MAX-ACCESS  read-only
STATUS      current
DESCRIPTION
"Identifier"
 ::= { psDcnEntry  2 }

psDcnEntryDes OBJECT-TYPE
SYNTAX      DisplayString
MAX-ACCESS  read-write
STATUS      current
DESCRIPTION
"Description"
 ::= { psDcnEntry  3 }

psDcnEntryStt OBJECT-TYPE
SYNTAX      DisplayString
MAX-ACCESS  read-only
STATUS      current
DESCRIPTION
"State
Values:
NONE,
MISSING,
PRESENT
"
 ::= { psDcnEntry  4 }

psDcnEntryTyp OBJECT-TYPE
SYNTAX      DisplayString
MAX-ACCESS  read-write
STATUS      current
DESCRIPTION
"Contactor Interface Type
Values:
NONE,
LVBD1,
LVLD1,
LVLD2,
LVLD3
"
 ::= { psDcnEntry  5 }

psDcnEntryBrc OBJECT-TYPE
SYNTAX      DisplayString
MAX-ACCESS  read-only
STATUS      current
DESCRIPTION
"Board Code"
 ::= { psDcnEntry  6 }

psDcnEntrySn OBJECT-TYPE
SYNTAX      DisplayString
MAX-ACCESS  read-only
STATUS      current
DESCRIPTION
"Serial Number"
 ::= { psDcnEntry  7 }



--
-- object psRp1
--

psRp1 OBJECT IDENTIFIER  ::= { powerSystem  59 }

psRp1Ide OBJECT-TYPE
SYNTAX      DisplayString
MAX-ACCESS  read-only
STATUS      current
DESCRIPTION
"Identifier"
 ::= { psRp1  1 }

psRp1Des OBJECT-TYPE
SYNTAX      DisplayString
MAX-ACCESS  read-write
STATUS      current
DESCRIPTION
"Description"
 ::= { psRp1  2 }

psRp1Frq OBJECT-TYPE
SYNTAX      Integer32(15..50)
UNITS       "Hz"
MAX-ACCESS  read-write
STATUS      current
DESCRIPTION
"Frequency (Hz)"
 ::= { psRp1  3 }

psRp1Vsp OBJECT-TYPE
SYNTAX      Integer32(65..100)
UNITS       "Volts"
MAX-ACCESS  read-write
STATUS      current
DESCRIPTION
"Voltage Set-point (Volts)"
 ::= { psRp1  4 }

psRp1Ofe OBJECT-TYPE
SYNTAX      INTEGER {
disable(0),
enable(1)
}
MAX-ACCESS  read-write
STATUS      current
DESCRIPTION
"Offset
Values:
disable(0),
enable(1)
"
 ::= { psRp1  5 }

psRp1Rme OBJECT-TYPE
SYNTAX      INTEGER {
disable(0),
enable(1)
}
MAX-ACCESS  read-write
STATUS      current
DESCRIPTION
"Redundancy Monitor
Values:
disable(0),
enable(1)
"
 ::= { psRp1  6 }

psRp1Rrf OBJECT-TYPE
SYNTAX      INTEGER {
disable(0),
enable(1)
}
MAX-ACCESS  read-write
STATUS      current
DESCRIPTION
"Remote Ringer Off
Values:
disable(0),
enable(1)
"
 ::= { psRp1  7 }

psRp1Rss OBJECT-TYPE
SYNTAX      INTEGER {
restart(1)
}
MAX-ACCESS  read-write
STATUS      current
DESCRIPTION
"Restart
Values:
restart(1)
"
 ::= { psRp1  8 }

psRp1Cap OBJECT-TYPE
SYNTAX      Integer32
UNITS       "VA"
MAX-ACCESS  read-only
STATUS      current
DESCRIPTION
"Capacity (VA)"
 ::= { psRp1  9 }

psRp1Olcap OBJECT-TYPE
SYNTAX      Integer32
UNITS       "VA"
MAX-ACCESS  read-only
STATUS      current
DESCRIPTION
"On Line Capacity (VA)"
 ::= { psRp1  10 }

psRp1Va OBJECT-TYPE
SYNTAX      Integer32
UNITS       "VA"
MAX-ACCESS  read-only
STATUS      current
DESCRIPTION
"Total (VA)"
 ::= { psRp1  11 }

psRp1Rf OBJECT-TYPE
SYNTAX      DisplayString
MAX-ACCESS  read-only
STATUS      current
DESCRIPTION
"Ringer Minor Fail"
 ::= { psRp1  12 }

psRp1Rpff OBJECT-TYPE
SYNTAX      DisplayString
MAX-ACCESS  read-only
STATUS      current
DESCRIPTION
"Ringer Fan Fail"
 ::= { psRp1  13 }

psRp1Rpxj OBJECT-TYPE
SYNTAX      DisplayString
MAX-ACCESS  read-only
STATUS      current
DESCRIPTION
"Ringer Major External Fault"
 ::= { psRp1  14 }

psRp1Rpxn OBJECT-TYPE
SYNTAX      DisplayString
MAX-ACCESS  read-only
STATUS      current
DESCRIPTION
"Ringer Minor External Fault"
 ::= { psRp1  15 }

psRp1Rprl OBJECT-TYPE
SYNTAX      DisplayString
MAX-ACCESS  read-only
STATUS      current
DESCRIPTION
"Ringer Redundancy Loss"
 ::= { psRp1  16 }

psRp1Rpfj OBJECT-TYPE
SYNTAX      DisplayString
MAX-ACCESS  read-only
STATUS      current
DESCRIPTION
"Ringer Major Fail"
 ::= { psRp1  17 }

psRp1Rcdp OBJECT-TYPE
SYNTAX      DisplayString
MAX-ACCESS  read-only
STATUS      current
DESCRIPTION
"Ringer ID Conflict
Value:
Alarm report from RCDP1
"
 ::= { psRp1  18 }


--
-- table RCH
--

psRchTable    OBJECT-TYPE
SYNTAX SEQUENCE OF PsRchEntry
MAX-ACCESS not-accessible
STATUS current
DESCRIPTION
        "Table of all Ringer Chassis data"
 ::= { powerSystem  60 }

psRchEntry OBJECT-TYPE
SYNTAX     PsRchEntry
MAX-ACCESS  not-accessible
STATUS      current
DESCRIPTION
       "Entry of information for one Ringer Chassis"
INDEX { psRchEntryIndex }
 ::= { psRchTable  1 }

PsRchEntry ::= SEQUENCE {
psRchEntryIndex   INTEGER,
psRchEntryIde   DisplayString,
psRchEntryDes   DisplayString,
psRchEntryStt   DisplayString,
psRchEntryVa   Integer32,
psRchEntryPri   DisplayString,
psRchEntrySec   DisplayString,
psRchEntryPsn   DisplayString,
psRchEntryPtyp   DisplayString,
psRchEntryPstt   DisplayString,
psRchEntrySsn   DisplayString,
psRchEntryStyp   DisplayString,
psRchEntrySstt   DisplayString,
psRchEntryCap   Integer32,
psRchEntryRf   INTEGER,
psRchEntryRpff   INTEGER,
psRchEntryRpxj   INTEGER,
psRchEntryRpxn   INTEGER,
psRchEntryRprl   INTEGER,
psRchEntryRpfj   INTEGER,
psRchEntryRcdp   INTEGER
}

psRchEntryIndex OBJECT-TYPE
SYNTAX      INTEGER (0..2147483647)
MAX-ACCESS  read-only
STATUS      current
DESCRIPTION
"Table Index"
 ::= { psRchEntry  1 }

psRchEntryIde OBJECT-TYPE
SYNTAX      DisplayString
MAX-ACCESS  read-only
STATUS      current
DESCRIPTION
"Identifier"
 ::= { psRchEntry  2 }

psRchEntryDes OBJECT-TYPE
SYNTAX      DisplayString
MAX-ACCESS  read-write
STATUS      current
DESCRIPTION
"Description"
 ::= { psRchEntry  3 }

psRchEntryStt OBJECT-TYPE
SYNTAX      DisplayString
MAX-ACCESS  read-write
STATUS      current
DESCRIPTION
"Ringer Group State"
 ::= { psRchEntry  4 }

psRchEntryVa OBJECT-TYPE
SYNTAX      Integer32
MAX-ACCESS  read-only
STATUS      current
DESCRIPTION
"Ringer Output VA"
 ::= { psRchEntry  5 }

psRchEntryPri OBJECT-TYPE
SYNTAX      DisplayString
MAX-ACCESS  read-only
STATUS      current
DESCRIPTION
"Primary Ringer"
 ::= { psRchEntry  6 }

psRchEntrySec OBJECT-TYPE
SYNTAX      DisplayString
MAX-ACCESS  read-only
STATUS      current
DESCRIPTION
"Secondary Ringer"
 ::= { psRchEntry  7 }

psRchEntryPsn OBJECT-TYPE
SYNTAX      DisplayString
MAX-ACCESS  read-only
STATUS      current
DESCRIPTION
"Primary Serial Number"
 ::= { psRchEntry  8 }

psRchEntryPtyp OBJECT-TYPE
SYNTAX      DisplayString
MAX-ACCESS  read-only
STATUS      current
DESCRIPTION
"Primary Type"
 ::= { psRchEntry  9 }

psRchEntryPstt OBJECT-TYPE
SYNTAX      DisplayString
MAX-ACCESS  read-write
STATUS      current
DESCRIPTION
"Primary Ringer State"
 ::= { psRchEntry  10 }

psRchEntrySsn OBJECT-TYPE
SYNTAX      DisplayString
MAX-ACCESS  read-only
STATUS      current
DESCRIPTION
"Secondary Serial Number"
 ::= { psRchEntry  11 }

psRchEntryStyp OBJECT-TYPE
SYNTAX      DisplayString
MAX-ACCESS  read-only
STATUS      current
DESCRIPTION
"Secondary Type"
 ::= { psRchEntry  12 }

psRchEntrySstt OBJECT-TYPE
SYNTAX      DisplayString
MAX-ACCESS  read-write
STATUS      current
DESCRIPTION
"Secondary Ringer State"
 ::= { psRchEntry  13 }

psRchEntryCap OBJECT-TYPE
SYNTAX      Integer32
UNITS       "VA"
MAX-ACCESS  read-only
STATUS      current
DESCRIPTION
"Capacity (VA)"
 ::= { psRchEntry  14 }

psRchEntryRf OBJECT-TYPE
SYNTAX      INTEGER {
inactive(0),
active(1)
}
MAX-ACCESS  read-only
STATUS      current
DESCRIPTION
"Ringer Minor Fail
Values:
inactive(0),
active(1)
"
 ::= { psRchEntry  15 }

psRchEntryRpff OBJECT-TYPE
SYNTAX      INTEGER {
inactive(0),
active(1)
}
MAX-ACCESS  read-only
STATUS      current
DESCRIPTION
"Ringer Fan Fail
Values:
inactive(0),
active(1)
"
 ::= { psRchEntry  16 }

psRchEntryRpxj OBJECT-TYPE
SYNTAX      INTEGER {
inactive(0),
active(1)
}
MAX-ACCESS  read-only
STATUS      current
DESCRIPTION
"Ringer Major External Fault
Values:
inactive(0),
active(1)
"
 ::= { psRchEntry  17 }

psRchEntryRpxn OBJECT-TYPE
SYNTAX      INTEGER {
inactive(0),
active(1)
}
MAX-ACCESS  read-only
STATUS      current
DESCRIPTION
"Ringer Minor External Fault
Values:
inactive(0),
active(1)
"
 ::= { psRchEntry  18 }

psRchEntryRprl OBJECT-TYPE
SYNTAX      INTEGER {
inactive(0),
active(1)
}
MAX-ACCESS  read-only
STATUS      current
DESCRIPTION
"Ringer Redundancy Loss
Values:
inactive(0),
active(1)
"
 ::= { psRchEntry  19 }

psRchEntryRpfj OBJECT-TYPE
SYNTAX      INTEGER {
inactive(0),
active(1)
}
MAX-ACCESS  read-only
STATUS      current
DESCRIPTION
"Ringer Major Fail
Values:
inactive(0),
active(1)
"
 ::= { psRchEntry  20 }

psRchEntryRcdp OBJECT-TYPE
SYNTAX      INTEGER {
inactive(0),
active(1)
}
MAX-ACCESS  read-only
STATUS      current
DESCRIPTION
"Ringer ID Conflict
Values:
inactive(0),
active(1)
"
 ::= { psRchEntry  21 }



--
-- table BRD
--

psBrdTable    OBJECT-TYPE
SYNTAX SEQUENCE OF PsBrdEntry
MAX-ACCESS not-accessible
STATUS current
DESCRIPTION
        "Table of all Ferro bridge data"
 ::= { powerSystem  61 }

psBrdEntry OBJECT-TYPE
SYNTAX     PsBrdEntry
MAX-ACCESS  not-accessible
STATUS      current
DESCRIPTION
       "Entry of information for one Ferro bridge"
INDEX { psBrdEntryIndex }
 ::= { psBrdTable  1 }

PsBrdEntry ::= SEQUENCE {
psBrdEntryIndex   INTEGER,
psBrdEntryIde   DisplayString,
psBrdEntryDes   DisplayString,
psBrdEntryStt   DisplayString,
psBrdEntrySn   DisplayString,
psBrdEntryTyp   DisplayString
}

psBrdEntryIndex OBJECT-TYPE
SYNTAX      INTEGER (0..2147483647)
MAX-ACCESS  read-only
STATUS      current
DESCRIPTION
"Table Index"
 ::= { psBrdEntry  1 }

psBrdEntryIde OBJECT-TYPE
SYNTAX      DisplayString
MAX-ACCESS  read-only
STATUS      current
DESCRIPTION
"Identifier"
 ::= { psBrdEntry  2 }

psBrdEntryDes OBJECT-TYPE
SYNTAX      DisplayString
MAX-ACCESS  read-write
STATUS      current
DESCRIPTION
"Description"
 ::= { psBrdEntry  3 }

psBrdEntryStt OBJECT-TYPE
SYNTAX      DisplayString
MAX-ACCESS  read-only
STATUS      current
DESCRIPTION
"State"
 ::= { psBrdEntry  4 }

psBrdEntrySn OBJECT-TYPE
SYNTAX      DisplayString
MAX-ACCESS  read-only
STATUS      current
DESCRIPTION
"Serial Number"
 ::= { psBrdEntry  5 }

psBrdEntryTyp OBJECT-TYPE
SYNTAX      DisplayString
MAX-ACCESS  read-only
STATUS      current
DESCRIPTION
"Board Type"
 ::= { psBrdEntry  6 }



--
-- table PIC
--

psPicTable    OBJECT-TYPE
SYNTAX SEQUENCE OF PsPicEntry
MAX-ACCESS not-accessible
STATUS current
DESCRIPTION
        "Table of all Panel Interface Card data"
 ::= { powerSystem  62 }

psPicEntry OBJECT-TYPE
SYNTAX     PsPicEntry
MAX-ACCESS  not-accessible
STATUS      current
DESCRIPTION
       "Entry of information for one Panel Interface Card"
INDEX { psPicEntryIndex }
 ::= { psPicTable  1 }

PsPicEntry ::= SEQUENCE {
psPicEntryIndex   INTEGER,
psPicEntryIde   DisplayString,
psPicEntryDes   DisplayString,
psPicEntryStt   DisplayString,
psPicEntryVera   DisplayString,
psPicEntryPid   DisplayString,
psPicEntryPcf   DisplayString,
psPicEntrySn   DisplayString,
psPicEntryCc   DisplayString,
psPicEntrySer   DisplayString,
psPicEntryClei   DisplayString,
psPicEntryCustpn2   DisplayString,
psPicEntryAsstag2   DisplayString,
psPicEntryTyp   DisplayString,
psPicEntryNst   Integer32,
psPicEntryNvt   Integer32,
psPicEntryVera1   DisplayString,
psPicEntryPid1   DisplayString,
psPicEntryPcf1   DisplayString,
psPicEntryNumslot   Integer32,
psPicEntryCbf   DisplayString,
psPicEntryFajae   INTEGER,
psPicEntryFajrly   DisplayString,
psPicEntryOsae   INTEGER,
psPicEntryOsarly   DisplayString,
psPicEntryTmpe   INTEGER,
psPicEntryTmprly   DisplayString,
psPicEntryVlvs   DisplayString,
psPicEntryVlvlat   DisplayString,
psPicEntryVlvae   INTEGER,
psPicEntryVlvath   Integer32,
psPicEntryVlvbe   INTEGER,
psPicEntryVlvbth   Integer32,
psPicEntryVlvrly   DisplayString,
psPicEntryOvls   DisplayString,
psPicEntryOlvlat   DisplayString,
psPicEntryOvlae   INTEGER,
psPicEntryOvlath   Integer32,
psPicEntryOvlbe   INTEGER,
psPicEntryOvlbth   Integer32,
psPicEntryOvlrly   DisplayString,
psPicEntryEpoe   INTEGER,
psPicEntryEporly   DisplayString,
psPicEntryPcauxe   INTEGER,
psPicEntryPcauxr   DisplayString,
psPicEntrySlote   INTEGER,
psPicEntrySlotrly   DisplayString,
psPicEntryDpmode   DisplayString,
psPicEntryPnldes   DisplayString,
psPicEntryMdl   DisplayString,
psPicEntryPnlsn   DisplayString,
psPicEntryPnlcc   DisplayString,
psPicEntryPnlser   DisplayString,
psPicEntryPnlclei   DisplayString,
psPicEntryCustpn1   DisplayString,
psPicEntryAsstag1   DisplayString,
psPicEntryRtng   DisplayString,
psPicEntryPnlsize   DisplayString,
psPicEntryLvdo   DisplayString,
psPicEntryLvdf   DisplayString
}

psPicEntryIndex OBJECT-TYPE
SYNTAX      INTEGER (0..2147483647)
MAX-ACCESS  read-only
STATUS      current
DESCRIPTION
"Table Index"
 ::= { psPicEntry  1 }

psPicEntryIde OBJECT-TYPE
SYNTAX      DisplayString
MAX-ACCESS  read-only
STATUS      current
DESCRIPTION
"Identifier"
 ::= { psPicEntry  2 }

psPicEntryDes OBJECT-TYPE
SYNTAX      DisplayString
MAX-ACCESS  read-write
STATUS      current
DESCRIPTION
"Description"
 ::= { psPicEntry  3 }

psPicEntryStt OBJECT-TYPE
SYNTAX      DisplayString
MAX-ACCESS  read-write
STATUS      current
DESCRIPTION
"State
Values:
PRESENT,
MISSING,
VACANT
"
 ::= { psPicEntry  4 }

psPicEntryVera OBJECT-TYPE
SYNTAX      DisplayString
MAX-ACCESS  read-only
STATUS      current
DESCRIPTION
"Application Software Version"
 ::= { psPicEntry  5 }

psPicEntryPid OBJECT-TYPE
SYNTAX      DisplayString
MAX-ACCESS  read-only
STATUS      current
DESCRIPTION
"ID Conflict"
 ::= { psPicEntry  6 }

psPicEntryPcf OBJECT-TYPE
SYNTAX      DisplayString
MAX-ACCESS  read-only
STATUS      current
DESCRIPTION
"Communication Failure"
 ::= { psPicEntry  7 }

psPicEntrySn OBJECT-TYPE
SYNTAX      DisplayString
MAX-ACCESS  read-only
STATUS      current
DESCRIPTION
"Serial Number"
 ::= { psPicEntry  8 }

psPicEntryCc OBJECT-TYPE
SYNTAX      DisplayString
MAX-ACCESS  read-only
STATUS      current
DESCRIPTION
"Comcode"
 ::= { psPicEntry  9 }

psPicEntrySer OBJECT-TYPE
SYNTAX      DisplayString
MAX-ACCESS  read-only
STATUS      current
DESCRIPTION
"Series"
 ::= { psPicEntry  10 }

psPicEntryClei OBJECT-TYPE
SYNTAX      DisplayString
MAX-ACCESS  read-only
STATUS      current
DESCRIPTION
"Clei Code"
 ::= { psPicEntry  11 }

psPicEntryCustpn2 OBJECT-TYPE
SYNTAX      DisplayString
MAX-ACCESS  read-only
STATUS      current
DESCRIPTION
"Customer PIC Part Number"
 ::= { psPicEntry  12 }

psPicEntryAsstag2 OBJECT-TYPE
SYNTAX      DisplayString
MAX-ACCESS  read-only
STATUS      current
DESCRIPTION
"PIC Asset Tag"
 ::= { psPicEntry  13 }

psPicEntryTyp OBJECT-TYPE
SYNTAX      DisplayString
MAX-ACCESS  read-write
STATUS      current
DESCRIPTION
"PIC Type
Values:
LOAD,
BATT
"
 ::= { psPicEntry  14 }

psPicEntryNst OBJECT-TYPE
SYNTAX      Integer32
MAX-ACCESS  read-write
STATUS      current
DESCRIPTION
"Number of Shunts"
 ::= { psPicEntry  15 }

psPicEntryNvt OBJECT-TYPE
SYNTAX      Integer32
MAX-ACCESS  read-write
STATUS      current
DESCRIPTION
"Number of Voltages"
 ::= { psPicEntry  16 }

psPicEntryVera1 OBJECT-TYPE
SYNTAX      DisplayString
MAX-ACCESS  read-only
STATUS      current
DESCRIPTION
"Application Software Version"
 ::= { psPicEntry  17 }

psPicEntryPid1 OBJECT-TYPE
SYNTAX      DisplayString
MAX-ACCESS  read-only
STATUS      current
DESCRIPTION
"ID Conflict"
 ::= { psPicEntry  18 }

psPicEntryPcf1 OBJECT-TYPE
SYNTAX      DisplayString
MAX-ACCESS  read-only
STATUS      current
DESCRIPTION
"Communication Failure"
 ::= { psPicEntry  19 }

psPicEntryNumslot OBJECT-TYPE
SYNTAX      Integer32
MAX-ACCESS  read-only
STATUS      current
DESCRIPTION
"Number of Slots"
 ::= { psPicEntry  20 }

psPicEntryCbf OBJECT-TYPE
SYNTAX      DisplayString
MAX-ACCESS  read-write
STATUS      current
DESCRIPTION
"CB or Fuse
Values:
CB,
FUSE
"
 ::= { psPicEntry  21 }

psPicEntryFajae OBJECT-TYPE
SYNTAX      INTEGER {
disable(0),
enable(1)
}
MAX-ACCESS  read-write
STATUS      current
DESCRIPTION
"External Fuse Enable
Values:
disable(0),
enable(1)
"
 ::= { psPicEntry  22 }

psPicEntryFajrly OBJECT-TYPE
SYNTAX      DisplayString
MAX-ACCESS  read-write
STATUS      current
DESCRIPTION
"External Fuse Relay
Values:
Disabled,
Enabled
"
 ::= { psPicEntry  23 }

psPicEntryOsae OBJECT-TYPE
SYNTAX      INTEGER {
disable(0),
enable(1)
}
MAX-ACCESS  read-write
STATUS      current
DESCRIPTION
"Open String Enable
Values:
disable(0),
enable(1)
"
 ::= { psPicEntry  24 }

psPicEntryOsarly OBJECT-TYPE
SYNTAX      DisplayString
MAX-ACCESS  read-write
STATUS      current
DESCRIPTION
"Open String Relay
Values:
Disabled,
Enabled
"
 ::= { psPicEntry  25 }

psPicEntryTmpe OBJECT-TYPE
SYNTAX      INTEGER {
disable(0),
enable(1)
}
MAX-ACCESS  read-write
STATUS      current
DESCRIPTION
"Temperature Enable
Values:
disable(0),
enable(1)
"
 ::= { psPicEntry  26 }

psPicEntryTmprly OBJECT-TYPE
SYNTAX      DisplayString
MAX-ACCESS  read-write
STATUS      current
DESCRIPTION
"Temperature Relay
Values:
Disabled,
Enabled
"
 ::= { psPicEntry  27 }

psPicEntryVlvs OBJECT-TYPE
SYNTAX      DisplayString
MAX-ACCESS  read-write
STATUS      current
DESCRIPTION
"Power Loss Severity
Values:
CRIT,
MAJ,
MIN,
WRN,
RO
"
 ::= { psPicEntry  28 }

psPicEntryVlvlat OBJECT-TYPE
SYNTAX      DisplayString
MAX-ACCESS  read-write
STATUS      current
DESCRIPTION
"Power Loss Latched"
 ::= { psPicEntry  29 }

psPicEntryVlvae OBJECT-TYPE
SYNTAX      INTEGER {
disable(0),
enable(1)
}
MAX-ACCESS  read-write
STATUS      current
DESCRIPTION
"VA Power Loss Enable
Values:
disable(0),
enable(1)
"
 ::= { psPicEntry  30 }

psPicEntryVlvath OBJECT-TYPE
SYNTAX      Integer32
MAX-ACCESS  read-write
STATUS      current
DESCRIPTION
"VB Power Loss Threshold"
 ::= { psPicEntry  31 }

psPicEntryVlvbe OBJECT-TYPE
SYNTAX      INTEGER {
disable(0),
enable(1)
}
MAX-ACCESS  read-write
STATUS      current
DESCRIPTION
"VB Power Loss Enable
Values:
disable(0),
enable(1)
"
 ::= { psPicEntry  32 }

psPicEntryVlvbth OBJECT-TYPE
SYNTAX      Integer32
MAX-ACCESS  read-write
STATUS      current
DESCRIPTION
"VB Power Loss Threshold"
 ::= { psPicEntry  33 }

psPicEntryVlvrly OBJECT-TYPE
SYNTAX      DisplayString
MAX-ACCESS  read-write
STATUS      current
DESCRIPTION
"Power Loss Relay
Values:
Disabled,
Enabled
"
 ::= { psPicEntry  34 }

psPicEntryOvls OBJECT-TYPE
SYNTAX      DisplayString
MAX-ACCESS  read-write
STATUS      current
DESCRIPTION
"Overload Severity
Values:
CRIT,
MAJ,
MIN,
WRN,
RO
"
 ::= { psPicEntry  35 }

psPicEntryOlvlat OBJECT-TYPE
SYNTAX      DisplayString
MAX-ACCESS  read-write
STATUS      current
DESCRIPTION
"Overload Latched"
 ::= { psPicEntry  36 }

psPicEntryOvlae OBJECT-TYPE
SYNTAX      INTEGER {
disable(0),
enable(1)
}
MAX-ACCESS  read-write
STATUS      current
DESCRIPTION
"IA Overload Enabled
Values:
disable(0),
enable(1)
"
 ::= { psPicEntry  37 }

psPicEntryOvlath OBJECT-TYPE
SYNTAX      Integer32
MAX-ACCESS  read-write
STATUS      current
DESCRIPTION
"IA Overload Threshold"
 ::= { psPicEntry  38 }

psPicEntryOvlbe OBJECT-TYPE
SYNTAX      INTEGER {
disable(0),
enable(1)
}
MAX-ACCESS  read-write
STATUS      current
DESCRIPTION
"IB Overload Enabled
Values:
disable(0),
enable(1)
"
 ::= { psPicEntry  39 }

psPicEntryOvlbth OBJECT-TYPE
SYNTAX      Integer32
MAX-ACCESS  read-write
STATUS      current
DESCRIPTION
"IB Overload Threshold"
 ::= { psPicEntry  40 }

psPicEntryOvlrly OBJECT-TYPE
SYNTAX      DisplayString
MAX-ACCESS  read-write
STATUS      current
DESCRIPTION
"Overload Relay
Values:
Disabled,
Enabled
"
 ::= { psPicEntry  41 }

psPicEntryEpoe OBJECT-TYPE
SYNTAX      INTEGER {
disable(0),
enable(1)
}
MAX-ACCESS  read-write
STATUS      current
DESCRIPTION
"Emergency Power Off Enabled
Values:
disable(0),
enable(1)
"
 ::= { psPicEntry  42 }

psPicEntryEporly OBJECT-TYPE
SYNTAX      DisplayString
MAX-ACCESS  read-write
STATUS      current
DESCRIPTION
"Emergency Power Off Relay
Values:
Disabled,
Enabled
"
 ::= { psPicEntry  43 }

psPicEntryPcauxe OBJECT-TYPE
SYNTAX      INTEGER {
disable(0),
enable(1)
}
MAX-ACCESS  read-write
STATUS      current
DESCRIPTION
"PIC Auxiliary Enabled
Values:
disable(0),
enable(1)
"
 ::= { psPicEntry  44 }

psPicEntryPcauxr OBJECT-TYPE
SYNTAX      DisplayString
MAX-ACCESS  read-write
STATUS      current
DESCRIPTION
"PIC Auxiliary Relay
Values:
Disabled,
Enabled
"
 ::= { psPicEntry  45 }

psPicEntrySlote OBJECT-TYPE
SYNTAX      INTEGER {
disable(0),
enable(1)
}
MAX-ACCESS  read-write
STATUS      current
DESCRIPTION
"Slot Enabled
Values:
disable(0),
enable(1)
"
 ::= { psPicEntry  46 }

psPicEntrySlotrly OBJECT-TYPE
SYNTAX      DisplayString
MAX-ACCESS  read-write
STATUS      current
DESCRIPTION
"Slot Relay
Values:
Disabled,
Enabled
"
 ::= { psPicEntry  47 }

psPicEntryDpmode OBJECT-TYPE
SYNTAX      DisplayString
MAX-ACCESS  read-write
STATUS      current
DESCRIPTION
"Display Mode
Values:
SCAN,
STATIC
"
 ::= { psPicEntry  48 }

psPicEntryPnldes OBJECT-TYPE
SYNTAX      DisplayString
MAX-ACCESS  read-write
STATUS      current
DESCRIPTION
"Panel Description"
 ::= { psPicEntry  49 }

psPicEntryMdl OBJECT-TYPE
SYNTAX      DisplayString
MAX-ACCESS  read-write
STATUS      current
DESCRIPTION
"Panel Model"
 ::= { psPicEntry  50 }

psPicEntryPnlsn OBJECT-TYPE
SYNTAX      DisplayString
MAX-ACCESS  read-write
STATUS      current
DESCRIPTION
"Panel Serial Number"
 ::= { psPicEntry  51 }

psPicEntryPnlcc OBJECT-TYPE
SYNTAX      DisplayString
MAX-ACCESS  read-write
STATUS      current
DESCRIPTION
"Panel Comcode"
 ::= { psPicEntry  52 }

psPicEntryPnlser OBJECT-TYPE
SYNTAX      DisplayString
MAX-ACCESS  read-write
STATUS      current
DESCRIPTION
"Panel Series"
 ::= { psPicEntry  53 }

psPicEntryPnlclei OBJECT-TYPE
SYNTAX      DisplayString
MAX-ACCESS  read-write
STATUS      current
DESCRIPTION
"Panel Clei Code"
 ::= { psPicEntry  54 }

psPicEntryCustpn1 OBJECT-TYPE
SYNTAX      DisplayString
MAX-ACCESS  read-write
STATUS      current
DESCRIPTION
"Panel Customer Part Number"
 ::= { psPicEntry  55 }

psPicEntryAsstag1 OBJECT-TYPE
SYNTAX      DisplayString
MAX-ACCESS  read-write
STATUS      current
DESCRIPTION
"Panel Customer Asset Tag"
 ::= { psPicEntry  56 }

psPicEntryRtng OBJECT-TYPE
SYNTAX      DisplayString
MAX-ACCESS  read-write
STATUS      current
DESCRIPTION
"Panel Rating"
 ::= { psPicEntry  57 }

psPicEntryPnlsize OBJECT-TYPE
SYNTAX      DisplayString
MAX-ACCESS  read-write
STATUS      current
DESCRIPTION
"Panel Size"
 ::= { psPicEntry  58 }

psPicEntryLvdo OBJECT-TYPE
SYNTAX      DisplayString
MAX-ACCESS  read-only
STATUS      current
DESCRIPTION
"LVD Open"
 ::= { psPicEntry  59 }

psPicEntryLvdf OBJECT-TYPE
SYNTAX      DisplayString
MAX-ACCESS  read-only
STATUS      current
DESCRIPTION
"LVD Fail"
 ::= { psPicEntry  60 }



--
-- table PCM
--

psPcmTable    OBJECT-TYPE
SYNTAX SEQUENCE OF PsPcmEntry
MAX-ACCESS not-accessible
STATUS current
DESCRIPTION
        "Table of all Panel Current Monitor data"
 ::= { powerSystem  63 }

psPcmEntry OBJECT-TYPE
SYNTAX     PsPcmEntry
MAX-ACCESS  not-accessible
STATUS      current
DESCRIPTION
       "Entry of information for one Panel Current Monitor"
INDEX { psPcmEntryIndex }
 ::= { psPcmTable  1 }

PsPcmEntry ::= SEQUENCE {
psPcmEntryIndex   INTEGER,
psPcmEntryIde   DisplayString,
psPcmEntryDes   DisplayString,
psPcmEntryVal   DisplayString,
psPcmEntrySht   DisplayString,
psPcmEntrySha   Integer32,
psPcmEntryShv   Integer32
}

psPcmEntryIndex OBJECT-TYPE
SYNTAX      INTEGER (0..2147483647)
MAX-ACCESS  read-only
STATUS      current
DESCRIPTION
"Table Index"
 ::= { psPcmEntry  1 }

psPcmEntryIde OBJECT-TYPE
SYNTAX      DisplayString
MAX-ACCESS  read-only
STATUS      current
DESCRIPTION
"Identifier"
 ::= { psPcmEntry  2 }

psPcmEntryDes OBJECT-TYPE
SYNTAX      DisplayString
MAX-ACCESS  read-write
STATUS      current
DESCRIPTION
"Description"
 ::= { psPcmEntry  3 }

psPcmEntryVal OBJECT-TYPE
SYNTAX      DisplayString
MAX-ACCESS  read-only
STATUS      current
DESCRIPTION
"Value"
 ::= { psPcmEntry  4 }

psPcmEntrySht OBJECT-TYPE
SYNTAX      DisplayString
MAX-ACCESS  read-write
STATUS      current
DESCRIPTION
"Shunt Type
Values:
LOAD,
BATTERY,
NONE
"
 ::= { psPcmEntry  5 }

psPcmEntrySha OBJECT-TYPE
SYNTAX      Integer32
MAX-ACCESS  read-write
STATUS      current
DESCRIPTION
"Shunt Current"
 ::= { psPcmEntry  6 }

psPcmEntryShv OBJECT-TYPE
SYNTAX      Integer32(1..150)
MAX-ACCESS  read-write
STATUS      current
DESCRIPTION
"Shunt Voltage"
 ::= { psPcmEntry  7 }



--
-- table PVM
--

psPvmTable    OBJECT-TYPE
SYNTAX SEQUENCE OF PsPvmEntry
MAX-ACCESS not-accessible
STATUS current
DESCRIPTION
        "Table of all Panel Voltage Monitor data"
 ::= { powerSystem  64 }

psPvmEntry OBJECT-TYPE
SYNTAX     PsPvmEntry
MAX-ACCESS  not-accessible
STATUS      current
DESCRIPTION
       "Entry of information for one Panel Voltage Monitor"
INDEX { psPvmEntryIndex }
 ::= { psPvmTable  1 }

PsPvmEntry ::= SEQUENCE {
psPvmEntryIndex   INTEGER,
psPvmEntryIde   DisplayString,
psPvmEntryDes   DisplayString,
psPvmEntryVal   Integer32
}

psPvmEntryIndex OBJECT-TYPE
SYNTAX      INTEGER (0..2147483647)
MAX-ACCESS  read-only
STATUS      current
DESCRIPTION
"Table Index"
 ::= { psPvmEntry  1 }

psPvmEntryIde OBJECT-TYPE
SYNTAX      DisplayString
MAX-ACCESS  read-only
STATUS      current
DESCRIPTION
"Identifier"
 ::= { psPvmEntry  2 }

psPvmEntryDes OBJECT-TYPE
SYNTAX      DisplayString
MAX-ACCESS  read-write
STATUS      current
DESCRIPTION
"Description"
 ::= { psPvmEntry  3 }

psPvmEntryVal OBJECT-TYPE
SYNTAX      Integer32
MAX-ACCESS  read-only
STATUS      current
DESCRIPTION
"Value"
 ::= { psPvmEntry  4 }



--
-- table PTM
--

psPtmTable    OBJECT-TYPE
SYNTAX SEQUENCE OF PsPtmEntry
MAX-ACCESS not-accessible
STATUS current
DESCRIPTION
        "Table of all Panel Temperature Monitor data"
 ::= { powerSystem  65 }

psPtmEntry OBJECT-TYPE
SYNTAX     PsPtmEntry
MAX-ACCESS  not-accessible
STATUS      current
DESCRIPTION
       "Entry of information for one Panel Temperature Monitor"
INDEX { psPtmEntryIndex }
 ::= { psPtmTable  1 }

PsPtmEntry ::= SEQUENCE {
psPtmEntryIndex   INTEGER,
psPtmEntryIde   DisplayString,
psPtmEntryDes   DisplayString,
psPtmEntryBamt   Integer32,
psPtmEntryNat   Integer32,
psPtmEntryHamt   Integer32,
psPtmEntryLamt   Integer32,
psPtmEntryNtm   Integer32,
psPtmEntryHbt   Integer32,
psPtmEntryLbt   Integer32,
psPtmEntryNbut   Integer32,
psPtmEntryHbut   Integer32,
psPtmEntryLbut   Integer32
}

psPtmEntryIndex OBJECT-TYPE
SYNTAX      INTEGER (0..2147483647)
MAX-ACCESS  read-only
STATUS      current
DESCRIPTION
"Table Index"
 ::= { psPtmEntry  1 }

psPtmEntryIde OBJECT-TYPE
SYNTAX      DisplayString
MAX-ACCESS  read-only
STATUS      current
DESCRIPTION
"Identifier"
 ::= { psPtmEntry  2 }

psPtmEntryDes OBJECT-TYPE
SYNTAX      DisplayString
MAX-ACCESS  read-write
STATUS      current
DESCRIPTION
"Description"
 ::= { psPtmEntry  3 }

psPtmEntryBamt OBJECT-TYPE
SYNTAX      Integer32
MAX-ACCESS  read-only
STATUS      current
DESCRIPTION
"Board Ambient Temperature"
 ::= { psPtmEntry  4 }

psPtmEntryNat OBJECT-TYPE
SYNTAX      Integer32
MAX-ACCESS  read-only
STATUS      current
DESCRIPTION
"Number of Ambient Temperature Probes"
 ::= { psPtmEntry  5 }

psPtmEntryHamt OBJECT-TYPE
SYNTAX      Integer32
MAX-ACCESS  read-only
STATUS      current
DESCRIPTION
"Hi Ambient Temperature"
 ::= { psPtmEntry  6 }

psPtmEntryLamt OBJECT-TYPE
SYNTAX      Integer32
MAX-ACCESS  read-only
STATUS      current
DESCRIPTION
"Low Ambient Temperature"
 ::= { psPtmEntry  7 }

psPtmEntryNtm OBJECT-TYPE
SYNTAX      Integer32
MAX-ACCESS  read-only
STATUS      current
DESCRIPTION
"Number of Battery Temperature Probes"
 ::= { psPtmEntry  8 }

psPtmEntryHbt OBJECT-TYPE
SYNTAX      Integer32
MAX-ACCESS  read-only
STATUS      current
DESCRIPTION
"Hi Battery Temperature"
 ::= { psPtmEntry  9 }

psPtmEntryLbt OBJECT-TYPE
SYNTAX      Integer32
MAX-ACCESS  read-only
STATUS      current
DESCRIPTION
"Low Battery Temperature"
 ::= { psPtmEntry  10 }

psPtmEntryNbut OBJECT-TYPE
SYNTAX      Integer32
MAX-ACCESS  read-only
STATUS      current
DESCRIPTION
"Number of Bus Temperature Probes"
 ::= { psPtmEntry  11 }

psPtmEntryHbut OBJECT-TYPE
SYNTAX      Integer32
MAX-ACCESS  read-only
STATUS      current
DESCRIPTION
"Hi Bus Temperature"
 ::= { psPtmEntry  12 }

psPtmEntryLbut OBJECT-TYPE
SYNTAX      Integer32
MAX-ACCESS  read-only
STATUS      current
DESCRIPTION
"Low Bust Temperature"
 ::= { psPtmEntry  13 }



--
-- table DBY
--

psDbyTable    OBJECT-TYPE
SYNTAX SEQUENCE OF PsDbyEntry
MAX-ACCESS not-accessible
STATUS current
DESCRIPTION
        "Table of all Distribution Bay data"
 ::= { powerSystem  66 }

psDbyEntry OBJECT-TYPE
SYNTAX     PsDbyEntry
MAX-ACCESS  not-accessible
STATUS      current
DESCRIPTION
       "Entry of information for one Distribution Bay"
INDEX { psDbyEntryIndex }
 ::= { psDbyTable  1 }

PsDbyEntry ::= SEQUENCE {
psDbyEntryIndex   INTEGER,
psDbyEntryIde   DisplayString,
psDbyEntryDes   DisplayString,
psDbyEntrySn   DisplayString,
psDbyEntryStt   DisplayString,
psDbyEntrySha   Integer32,
psDbyEntryNpl   Integer32,
psDbyEntryPmt   DisplayString,
psDbyEntryIds   DisplayString,
psDbyEntryBze   INTEGER,
psDbyEntryOle   INTEGER,
psDbyEntryOri   DisplayString,
psDbyEntryCmb   INTEGER,
psDbyEntryFaja   DisplayString,
psDbyEntryFajb   DisplayString,
psDbyEntrySmw   DisplayString,
psDbyEntryCca   DisplayString,
psDbyEntryOvl   INTEGER,
psDbyEntryPid   DisplayString
}

psDbyEntryIndex OBJECT-TYPE
SYNTAX      INTEGER (0..2147483647)
MAX-ACCESS  read-only
STATUS      current
DESCRIPTION
"Table Index"
 ::= { psDbyEntry  1 }

psDbyEntryIde OBJECT-TYPE
SYNTAX      DisplayString
MAX-ACCESS  read-only
STATUS      current
DESCRIPTION
"Identifier"
 ::= { psDbyEntry  2 }

psDbyEntryDes OBJECT-TYPE
SYNTAX      DisplayString
MAX-ACCESS  read-write
STATUS      current
DESCRIPTION
"Description"
 ::= { psDbyEntry  3 }

psDbyEntrySn OBJECT-TYPE
SYNTAX      DisplayString
MAX-ACCESS  read-only
STATUS      current
DESCRIPTION
"Serial Number"
 ::= { psDbyEntry  4 }

psDbyEntryStt OBJECT-TYPE
SYNTAX      DisplayString
MAX-ACCESS  read-only
STATUS      current
DESCRIPTION
"State"
 ::= { psDbyEntry  5 }

psDbyEntrySha OBJECT-TYPE
SYNTAX      Integer32(0..4000)
UNITS       "Amps"
MAX-ACCESS  read-write
STATUS      current
DESCRIPTION
"Shunt Rating (Amps)"
 ::= { psDbyEntry  6 }

psDbyEntryNpl OBJECT-TYPE
SYNTAX      Integer32(1..8)
MAX-ACCESS  read-write
STATUS      current
DESCRIPTION
"Number of Panels"
 ::= { psDbyEntry  7 }

psDbyEntryPmt OBJECT-TYPE
SYNTAX      DisplayString
MAX-ACCESS  read-write
STATUS      current
DESCRIPTION
"Measurement Type"
 ::= { psDbyEntry  8 }

psDbyEntryIds OBJECT-TYPE
SYNTAX      DisplayString
MAX-ACCESS  read-write
STATUS      current
DESCRIPTION
"Identification Style"
 ::= { psDbyEntry  9 }

psDbyEntryBze OBJECT-TYPE
SYNTAX      INTEGER {
disable(0),
enable(1)
}
MAX-ACCESS  read-write
STATUS      current
DESCRIPTION
"Buzzer Enable
Values:
disable(0),
enable(1)
"
 ::= { psDbyEntry  10 }

psDbyEntryOle OBJECT-TYPE
SYNTAX      INTEGER {
disable(0),
enable(1)
}
MAX-ACCESS  read-write
STATUS      current
DESCRIPTION
"Overload Latch Enable
Values:
disable(0),
enable(1)
"
 ::= { psDbyEntry  11 }

psDbyEntryOri OBJECT-TYPE
SYNTAX      DisplayString
MAX-ACCESS  read-write
STATUS      current
DESCRIPTION
"Panel Orientation"
 ::= { psDbyEntry  12 }

psDbyEntryCmb OBJECT-TYPE
SYNTAX      INTEGER {
disable(0),
enable(1)
}
MAX-ACCESS  read-write
STATUS      current
DESCRIPTION
"Combine Panels
Values:
disable(0),
enable(1)
"
 ::= { psDbyEntry  13 }

psDbyEntryFaja OBJECT-TYPE
SYNTAX      DisplayString
MAX-ACCESS  read-only
STATUS      current
DESCRIPTION
"Distribution Fuse A"
 ::= { psDbyEntry  14 }

psDbyEntryFajb OBJECT-TYPE
SYNTAX      DisplayString
MAX-ACCESS  read-only
STATUS      current
DESCRIPTION
"Distribution Fuse B"
 ::= { psDbyEntry  15 }

psDbyEntrySmw OBJECT-TYPE
SYNTAX      DisplayString
MAX-ACCESS  read-only
STATUS      current
DESCRIPTION
"Shunt Miswired"
 ::= { psDbyEntry  16 }

psDbyEntryCca OBJECT-TYPE
SYNTAX      DisplayString
MAX-ACCESS  read-only
STATUS      current
DESCRIPTION
"Circuit Assignment"
 ::= { psDbyEntry  17 }

psDbyEntryOvl OBJECT-TYPE
SYNTAX      INTEGER {
clear(1)
}
MAX-ACCESS  read-write
STATUS      current
DESCRIPTION
"Clear Latched Overload
Values:
clear(1)
"
 ::= { psDbyEntry  18 }

psDbyEntryPid OBJECT-TYPE
SYNTAX      DisplayString
MAX-ACCESS  read-only
STATUS      current
DESCRIPTION
"ID Conflict"
 ::= { psDbyEntry  19 }



--
-- table DPN
--

psDpnTable    OBJECT-TYPE
SYNTAX SEQUENCE OF PsDpnEntry
MAX-ACCESS not-accessible
STATUS current
DESCRIPTION
        "Table of all Distribution Panel data"
 ::= { powerSystem  67 }

psDpnEntry OBJECT-TYPE
SYNTAX     PsDpnEntry
MAX-ACCESS  not-accessible
STATUS      current
DESCRIPTION
       "Entry of information for one Distribution Panel"
INDEX { psDpnEntryIndex }
 ::= { psDpnTable  1 }

PsDpnEntry ::= SEQUENCE {
psDpnEntryIndex   INTEGER,
psDpnEntryIde   DisplayString,
psDpnEntryDes   DisplayString,
psDpnEntryAdc   Integer32,
psDpnEntryVdc   Integer32,
psDpnEntryStt   DisplayString,
psDpnEntryPid   Integer32,
psDpnEntryEna   INTEGER,
psDpnEntryOld   Integer32,
psDpnEntryOlt   Integer32,
psDpnEntryOlr   INTEGER,
psDpnEntryPlt   Integer32,
psDpnEntryCct   Integer32,
psDpnEntryVlv   DisplayString,
psDpnEntryOvl   DisplayString
}

psDpnEntryIndex OBJECT-TYPE
SYNTAX      INTEGER (0..2147483647)
MAX-ACCESS  read-only
STATUS      current
DESCRIPTION
"Table Index"
 ::= { psDpnEntry  1 }

psDpnEntryIde OBJECT-TYPE
SYNTAX      DisplayString
MAX-ACCESS  read-only
STATUS      current
DESCRIPTION
"Identifier"
 ::= { psDpnEntry  2 }

psDpnEntryDes OBJECT-TYPE
SYNTAX      DisplayString
MAX-ACCESS  read-write
STATUS      current
DESCRIPTION
"Description"
 ::= { psDpnEntry  3 }

psDpnEntryAdc OBJECT-TYPE
SYNTAX      Integer32
UNITS       "Amps"
MAX-ACCESS  read-only
STATUS      current
DESCRIPTION
"Current (Amps)"
 ::= { psDpnEntry  4 }

psDpnEntryVdc OBJECT-TYPE
SYNTAX      Integer32
UNITS       "mV"
MAX-ACCESS  read-only
STATUS      current
DESCRIPTION
"Voltage (mV)"
 ::= { psDpnEntry  5 }

psDpnEntryStt OBJECT-TYPE
SYNTAX      DisplayString
MAX-ACCESS  read-only
STATUS      current
DESCRIPTION
"State"
 ::= { psDpnEntry  6 }

psDpnEntryPid OBJECT-TYPE
SYNTAX      Integer32(1..8)
MAX-ACCESS  read-only
STATUS      current
DESCRIPTION
"Panel ID"
 ::= { psDpnEntry  7 }

psDpnEntryEna OBJECT-TYPE
SYNTAX      INTEGER {
disable(0),
enable(1)
}
MAX-ACCESS  read-write
STATUS      current
DESCRIPTION
"Enable
Values:
disable(0),
enable(1)
"
 ::= { psDpnEntry  8 }

psDpnEntryOld OBJECT-TYPE
SYNTAX      Integer32(0..300)
UNITS       "Seconds"
MAX-ACCESS  read-write
STATUS      current
DESCRIPTION
"Overload Delay (Seconds)"
 ::= { psDpnEntry  9 }

psDpnEntryOlt OBJECT-TYPE
SYNTAX      Integer32(0..4000)
UNITS       "amps"
MAX-ACCESS  read-write
STATUS      current
DESCRIPTION
"Overload Threshold (amps)"
 ::= { psDpnEntry  10 }

psDpnEntryOlr OBJECT-TYPE
SYNTAX      INTEGER {
disable(0),
enable(1)
}
MAX-ACCESS  read-write
STATUS      current
DESCRIPTION
"Redundant Overload
Values:
disable(0),
enable(1)
"
 ::= { psDpnEntry  11 }

psDpnEntryPlt OBJECT-TYPE
SYNTAX      Integer32(40000..60000)
UNITS       "mV"
MAX-ACCESS  read-write
STATUS      current
DESCRIPTION
"Power Loss Threshold (mV)"
 ::= { psDpnEntry  12 }

psDpnEntryCct OBJECT-TYPE
SYNTAX      Integer32(1..8)
MAX-ACCESS  read-write
STATUS      current
DESCRIPTION
"Input Circuit"
 ::= { psDpnEntry  13 }

psDpnEntryVlv OBJECT-TYPE
SYNTAX      DisplayString
MAX-ACCESS  read-only
STATUS      current
DESCRIPTION
"Power Loss"
 ::= { psDpnEntry  14 }

psDpnEntryOvl OBJECT-TYPE
SYNTAX      DisplayString
MAX-ACCESS  read-only
STATUS      current
DESCRIPTION
"Overload"
 ::= { psDpnEntry  15 }



--
-- object psIvp1
--

psIvp1 OBJECT IDENTIFIER  ::= { powerSystem  68 }

psIvp1Ide OBJECT-TYPE
SYNTAX      DisplayString
MAX-ACCESS  read-only
STATUS      current
DESCRIPTION
"Identifier"
 ::= { psIvp1  1 }

psIvp1Des OBJECT-TYPE
SYNTAX      DisplayString
MAX-ACCESS  read-write
STATUS      current
DESCRIPTION
"Description"
 ::= { psIvp1  2 }

psIvp1Cap OBJECT-TYPE
SYNTAX      Integer32
UNITS       "Amps"
MAX-ACCESS  read-only
STATUS      current
DESCRIPTION
"Total Installed Inverter Capacity (Amps)"
 ::= { psIvp1  3 }

psIvp1Irm OBJECT-TYPE
SYNTAX      Integer32
MAX-ACCESS  read-only
STATUS      current
DESCRIPTION
"RMS Current"
 ::= { psIvp1  4 }

psIvp1Vac OBJECT-TYPE
SYNTAX      Integer32
MAX-ACCESS  read-only
STATUS      current
DESCRIPTION
"AC Output voltage"
 ::= { psIvp1  5 }

psIvp1Adc OBJECT-TYPE
SYNTAX      Integer32
MAX-ACCESS  read-only
STATUS      current
DESCRIPTION
"DC Current"
 ::= { psIvp1  6 }

psIvp1Vdc OBJECT-TYPE
SYNTAX      Integer32
MAX-ACCESS  read-only
STATUS      current
DESCRIPTION
"DC Voltage"
 ::= { psIvp1  7 }

psIvp1Frq OBJECT-TYPE
SYNTAX      Integer32
MAX-ACCESS  read-only
STATUS      current
DESCRIPTION
"Frequency"
 ::= { psIvp1  8 }

psIvp1Lst OBJECT-TYPE
SYNTAX      Integer32
MAX-ACCESS  read-only
STATUS      current
DESCRIPTION
"Load Share Target Percentage"
 ::= { psIvp1  9 }

psIvp1Ste OBJECT-TYPE
SYNTAX      INTEGER {
disable(0),
enable(1)
}
MAX-ACCESS  read-write
STATUS      current
DESCRIPTION
"Standby Enabled
Values:
disable(0),
enable(1)
"
 ::= { psIvp1  10 }

psIvp1Rlse OBJECT-TYPE
SYNTAX      INTEGER {
disable(0),
enable(1)
}
MAX-ACCESS  read-write
STATUS      current
DESCRIPTION
"Redundancy Loss Enabled
Values:
disable(0),
enable(1)
"
 ::= { psIvp1  11 }

psIvp1Dth OBJECT-TYPE
SYNTAX      Integer32(20..25|40..50)
MAX-ACCESS  read-write
STATUS      current
DESCRIPTION
"Low Voltage Disconnect Threshold"
 ::= { psIvp1  12 }

psIvp1Rth OBJECT-TYPE
SYNTAX      Integer32(22..27|44..54)
MAX-ACCESS  read-write
STATUS      current
DESCRIPTION
"Low Voltage Reconnect Threshold"
 ::= { psIvp1  13 }

psIvp1Lvd OBJECT-TYPE
SYNTAX      INTEGER {
disable(0),
enable(1)
}
MAX-ACCESS  read-write
STATUS      current
DESCRIPTION
"Low Voltage Disconnect Enabled
Values:
disable(0),
enable(1)
"
 ::= { psIvp1  14 }

psIvp1Hce OBJECT-TYPE
SYNTAX      INTEGER {
disable(0),
enable(1)
}
MAX-ACCESS  read-write
STATUS      current
DESCRIPTION
"Hi Crest Factor Enabled
Values:
disable(0),
enable(1)
"
 ::= { psIvp1  15 }

psIvp1Hipe OBJECT-TYPE
SYNTAX      INTEGER {
disable(0),
enable(1)
}
MAX-ACCESS  read-write
STATUS      current
DESCRIPTION
"Hi IPeak Current Enabled
Values:
disable(0),
enable(1)
"
 ::= { psIvp1  16 }

psIvp1Hrme OBJECT-TYPE
SYNTAX      INTEGER {
disable(0),
enable(1)
}
MAX-ACCESS  read-write
STATUS      current
DESCRIPTION
"Hi IRMS Currrent Enabled
Values:
disable(0),
enable(1)
"
 ::= { psIvp1  17 }

psIvp1Ilvi OBJECT-TYPE
SYNTAX      DisplayString
MAX-ACCESS  read-only
STATUS      current
DESCRIPTION
"Inverter Low Input
Value:
Alarm report from ILVI1
"
 ::= { psIvp1  18 }

psIvp1Ihvi OBJECT-TYPE
SYNTAX      DisplayString
MAX-ACCESS  read-only
STATUS      current
DESCRIPTION
"Inverter High Input
Value:
Alarm report from IHVI1
"
 ::= { psIvp1  19 }

psIvp1Ita OBJECT-TYPE
SYNTAX      DisplayString
MAX-ACCESS  read-only
STATUS      current
DESCRIPTION
"Inverter High Temperature
Value:
Alarm report from ITA1
"
 ::= { psIvp1  20 }

psIvp1If OBJECT-TYPE
SYNTAX      DisplayString
MAX-ACCESS  read-only
STATUS      current
DESCRIPTION
"Inverter Fail
Value:
Alarm report from IF1
"
 ::= { psIvp1  21 }

psIvp1Ilv OBJECT-TYPE
SYNTAX      DisplayString
MAX-ACCESS  read-only
STATUS      current
DESCRIPTION
"Inverter Low Output
Value:
Alarm report from ILV1
"
 ::= { psIvp1  22 }

psIvp1Ifa OBJECT-TYPE
SYNTAX      DisplayString
MAX-ACCESS  read-only
STATUS      current
DESCRIPTION
"Inverter Frequency Lock
Value:
Alarm report from IFA1
"
 ::= { psIvp1  23 }

psIvp1Ihv OBJECT-TYPE
SYNTAX      DisplayString
MAX-ACCESS  read-only
STATUS      current
DESCRIPTION
"Inverter High Output
Value:
Alarm report from IHV1
"
 ::= { psIvp1  24 }

psIvp1Ida OBJECT-TYPE
SYNTAX      DisplayString
MAX-ACCESS  read-only
STATUS      current
DESCRIPTION
"Inverter Distribution Alarm
Value:
Alarm report from IDA1
"
 ::= { psIvp1  25 }

psIvp1Iof OBJECT-TYPE
SYNTAX      DisplayString
MAX-ACCESS  read-only
STATUS      current
DESCRIPTION
"Inverter Output Fuse
Value:
Alarm report from IOF1
"
 ::= { psIvp1  26 }

psIvp1Idid OBJECT-TYPE
SYNTAX      DisplayString
MAX-ACCESS  read-only
STATUS      current
DESCRIPTION
"Inverter ID Conflict
Value:
Alarm report from IDID1
"
 ::= { psIvp1  27 }

psIvp1Iirm OBJECT-TYPE
SYNTAX      DisplayString
MAX-ACCESS  read-only
STATUS      current
DESCRIPTION
"Inverter High RMS Current
Value:
Alarm report from IIRM1
"
 ::= { psIvp1  28 }

psIvp1Iipk OBJECT-TYPE
SYNTAX      DisplayString
MAX-ACCESS  read-only
STATUS      current
DESCRIPTION
"Inverter High Peak Current
Value:
Alarm report from IIPK1
"
 ::= { psIvp1  29 }

psIvp1Icf OBJECT-TYPE
SYNTAX      DisplayString
MAX-ACCESS  read-only
STATUS      current
DESCRIPTION
"Inverter High Crest Factor
Value:
Alarm report from ICF1
"
 ::= { psIvp1  30 }

psIvp1Mif OBJECT-TYPE
SYNTAX      DisplayString
MAX-ACCESS  read-only
STATUS      current
DESCRIPTION
"Multiple Inverter Fail
Value:
Alarm report from MIF1
"
 ::= { psIvp1  31 }

psIvp1Irls OBJECT-TYPE
SYNTAX      DisplayString
MAX-ACCESS  read-only
STATUS      current
DESCRIPTION
"Inverter Redundancy Loss
Value:
Alarm report from IRLS1
"
 ::= { psIvp1  32 }

psIvp1Milv OBJECT-TYPE
SYNTAX      DisplayString
MAX-ACCESS  read-only
STATUS      current
DESCRIPTION
"Multiple Inverter Low Input Voltage
Value:
Alarm report from MILV1
"
 ::= { psIvp1  33 }

psIvp1Pwr OBJECT-TYPE
SYNTAX      Integer32
MAX-ACCESS  read-only
STATUS      current
DESCRIPTION
"Frequency"
 ::= { psIvp1  34 }


--
-- table INV
--

psInvTable    OBJECT-TYPE
SYNTAX SEQUENCE OF PsInvEntry
MAX-ACCESS not-accessible
STATUS current
DESCRIPTION
        "Table of all Inverter data"
 ::= { powerSystem  69 }

psInvEntry OBJECT-TYPE
SYNTAX     PsInvEntry
MAX-ACCESS  not-accessible
STATUS      current
DESCRIPTION
       "Entry of information for one Inverter"
INDEX { psInvEntryIndex }
 ::= { psInvTable  1 }

PsInvEntry ::= SEQUENCE {
psInvEntryIndex   INTEGER,
psInvEntryIde   DisplayString,
psInvEntryDes   DisplayString,
psInvEntryTyp   DisplayString,
psInvEntrySn   DisplayString,
psInvEntryAdc   Integer32,
psInvEntryVdc   Integer32,
psInvEntryVac   Integer32,
psInvEntryStt   DisplayString,
psInvEntryCap   Integer32,
psInvEntryCva   Integer32,
psInvEntryIpk   Integer32,
psInvEntryIrm   Integer32,
psInvEntryFrq   Integer32,
psInvEntryCf   Integer32,
psInvEntryPwr   Integer32,
psInvEntryVnom   Integer32,
psInvEntryNcl   INTEGER,
psInvEntryIlvi   DisplayString,
psInvEntryIta   DisplayString,
psInvEntryIf   DisplayString,
psInvEntryIlv   DisplayString,
psInvEntryIfa   DisplayString,
psInvEntryDid   DisplayString,
psInvEntryIcmf   DisplayString,
psInvEntryIcf   DisplayString,
psInvEntryIda   DisplayString,
psInvEntryIhv   DisplayString,
psInvEntryIhvi   DisplayString,
psInvEntryIipk   DisplayString,
psInvEntryIirm   DisplayString,
psInvEntryIof   DisplayString,
psInvEntryIlvi1   INTEGER,
psInvEntryIta1   INTEGER,
psInvEntryIf1   INTEGER,
psInvEntryIlv1   INTEGER,
psInvEntryIfa1   INTEGER,
psInvEntryDid1   INTEGER,
psInvEntryIcmf1   INTEGER,
psInvEntryIcf1   INTEGER,
psInvEntryIda1   INTEGER,
psInvEntryIhv1   INTEGER,
psInvEntryIhvi1   INTEGER,
psInvEntryIipk1   INTEGER,
psInvEntryIirm1   INTEGER,
psInvEntryIof1   INTEGER
}

psInvEntryIndex OBJECT-TYPE
SYNTAX      INTEGER (0..2147483647)
MAX-ACCESS  read-only
STATUS      current
DESCRIPTION
"Table Index"
 ::= { psInvEntry  1 }

psInvEntryIde OBJECT-TYPE
SYNTAX      DisplayString
MAX-ACCESS  read-only
STATUS      current
DESCRIPTION
"Identifier"
 ::= { psInvEntry  2 }

psInvEntryDes OBJECT-TYPE
SYNTAX      DisplayString
MAX-ACCESS  read-write
STATUS      current
DESCRIPTION
"Description"
 ::= { psInvEntry  3 }

psInvEntryTyp OBJECT-TYPE
SYNTAX      DisplayString
MAX-ACCESS  read-write
STATUS      current
DESCRIPTION
"Type"
 ::= { psInvEntry  4 }

psInvEntrySn OBJECT-TYPE
SYNTAX      DisplayString
MAX-ACCESS  read-only
STATUS      current
DESCRIPTION
"Serial Number"
 ::= { psInvEntry  5 }

psInvEntryAdc OBJECT-TYPE
SYNTAX      Integer32
UNITS       "Amps"
MAX-ACCESS  read-only
STATUS      current
DESCRIPTION
"DC Current (Amps)"
 ::= { psInvEntry  6 }

psInvEntryVdc OBJECT-TYPE
SYNTAX      Integer32
MAX-ACCESS  read-only
STATUS      current
DESCRIPTION
"DC Voltage"
 ::= { psInvEntry  7 }

psInvEntryVac OBJECT-TYPE
SYNTAX      Integer32
UNITS       "Volts"
MAX-ACCESS  read-only
STATUS      current
DESCRIPTION
"AC Voltage (Volts)"
 ::= { psInvEntry  8 }

psInvEntryStt OBJECT-TYPE
SYNTAX      DisplayString
MAX-ACCESS  read-write
STATUS      current
DESCRIPTION
"State
Values:
ON,
OFF,
STANDBY,
VACANT
"
 ::= { psInvEntry  9 }

psInvEntryCap OBJECT-TYPE
SYNTAX      Integer32
UNITS       "Amps"
MAX-ACCESS  read-only
STATUS      current
DESCRIPTION
"Capacity (Amps)"
 ::= { psInvEntry  10 }

psInvEntryCva OBJECT-TYPE
SYNTAX      Integer32
MAX-ACCESS  read-only
STATUS      current
DESCRIPTION
"Capacity in VA"
 ::= { psInvEntry  11 }

psInvEntryIpk OBJECT-TYPE
SYNTAX      Integer32
MAX-ACCESS  read-only
STATUS      current
DESCRIPTION
"Peak Current"
 ::= { psInvEntry  12 }

psInvEntryIrm OBJECT-TYPE
SYNTAX      Integer32
MAX-ACCESS  read-only
STATUS      current
DESCRIPTION
"RMS Current"
 ::= { psInvEntry  13 }

psInvEntryFrq OBJECT-TYPE
SYNTAX      Integer32
MAX-ACCESS  read-only
STATUS      current
DESCRIPTION
"Output Frequency"
 ::= { psInvEntry  14 }

psInvEntryCf OBJECT-TYPE
SYNTAX      Integer32
MAX-ACCESS  read-only
STATUS      current
DESCRIPTION
"Crest Factor"
 ::= { psInvEntry  15 }

psInvEntryPwr OBJECT-TYPE
SYNTAX      Integer32
MAX-ACCESS  read-only
STATUS      current
DESCRIPTION
"Output Power"
 ::= { psInvEntry  16 }

psInvEntryVnom OBJECT-TYPE
SYNTAX      Integer32
MAX-ACCESS  read-only
STATUS      current
DESCRIPTION
"Nominal Output Voltage"
 ::= { psInvEntry  17 }

psInvEntryNcl OBJECT-TYPE
SYNTAX      INTEGER {
disable(0),
enable(1)
}
UNITS       "for LVD"
MAX-ACCESS  read-write
STATUS      current
DESCRIPTION
"Non-Critical Load (for LVD)
Values:
disable(0),
enable(1)
"
 ::= { psInvEntry  18 }

psInvEntryIlvi OBJECT-TYPE
SYNTAX      DisplayString
MAX-ACCESS  read-only
STATUS      current
DESCRIPTION
"Low Voltage Input"
 ::= { psInvEntry  19 }

psInvEntryIta OBJECT-TYPE
SYNTAX      DisplayString
MAX-ACCESS  read-only
STATUS      current
DESCRIPTION
"Temperature Alarm"
 ::= { psInvEntry  20 }

psInvEntryIf OBJECT-TYPE
SYNTAX      DisplayString
MAX-ACCESS  read-only
STATUS      current
DESCRIPTION
"Inverter Fail"
 ::= { psInvEntry  21 }

psInvEntryIlv OBJECT-TYPE
SYNTAX      DisplayString
MAX-ACCESS  read-only
STATUS      current
DESCRIPTION
"Low Output Voltage"
 ::= { psInvEntry  22 }

psInvEntryIfa OBJECT-TYPE
SYNTAX      DisplayString
MAX-ACCESS  read-only
STATUS      current
DESCRIPTION
"Inverter Frequency Lock Fail"
 ::= { psInvEntry  23 }

psInvEntryDid OBJECT-TYPE
SYNTAX      DisplayString
MAX-ACCESS  read-only
STATUS      current
DESCRIPTION
"ID Conflict"
 ::= { psInvEntry  24 }

psInvEntryIcmf OBJECT-TYPE
SYNTAX      DisplayString
MAX-ACCESS  read-only
STATUS      current
DESCRIPTION
"Communication Failure"
 ::= { psInvEntry  25 }

psInvEntryIcf OBJECT-TYPE
SYNTAX      DisplayString
MAX-ACCESS  read-only
STATUS      current
DESCRIPTION
"Hi Crest Factor Status"
 ::= { psInvEntry  26 }

psInvEntryIda OBJECT-TYPE
SYNTAX      DisplayString
MAX-ACCESS  read-only
STATUS      current
DESCRIPTION
"Distribution Alarm Status"
 ::= { psInvEntry  27 }

psInvEntryIhv OBJECT-TYPE
SYNTAX      DisplayString
MAX-ACCESS  read-only
STATUS      current
DESCRIPTION
"High Output Status"
 ::= { psInvEntry  28 }

psInvEntryIhvi OBJECT-TYPE
SYNTAX      DisplayString
MAX-ACCESS  read-only
STATUS      current
DESCRIPTION
"High Input Status"
 ::= { psInvEntry  29 }

psInvEntryIipk OBJECT-TYPE
SYNTAX      DisplayString
MAX-ACCESS  read-only
STATUS      current
DESCRIPTION
"High IPeak Status"
 ::= { psInvEntry  30 }

psInvEntryIirm OBJECT-TYPE
SYNTAX      DisplayString
MAX-ACCESS  read-only
STATUS      current
DESCRIPTION
"High IRMS Status"
 ::= { psInvEntry  31 }

psInvEntryIof OBJECT-TYPE
SYNTAX      DisplayString
MAX-ACCESS  read-only
STATUS      current
DESCRIPTION
"Output Fuse Status"
 ::= { psInvEntry  32 }

psInvEntryIlvi1 OBJECT-TYPE
SYNTAX      INTEGER {
inactive(0),
active(1)
}
MAX-ACCESS  read-only
STATUS      current
DESCRIPTION
"Low Voltage Input
Values:
inactive(0),
active(1)
"
 ::= { psInvEntry  33 }

psInvEntryIta1 OBJECT-TYPE
SYNTAX      INTEGER {
inactive(0),
active(1)
}
MAX-ACCESS  read-only
STATUS      current
DESCRIPTION
"Temperature Alarm
Values:
inactive(0),
active(1)
"
 ::= { psInvEntry  34 }

psInvEntryIf1 OBJECT-TYPE
SYNTAX      INTEGER {
inactive(0),
active(1)
}
MAX-ACCESS  read-only
STATUS      current
DESCRIPTION
"Inverter Fail
Values:
inactive(0),
active(1)
"
 ::= { psInvEntry  35 }

psInvEntryIlv1 OBJECT-TYPE
SYNTAX      INTEGER {
inactive(0),
active(1)
}
MAX-ACCESS  read-only
STATUS      current
DESCRIPTION
"Low Output Voltage
Values:
inactive(0),
active(1)
"
 ::= { psInvEntry  36 }

psInvEntryIfa1 OBJECT-TYPE
SYNTAX      INTEGER {
inactive(0),
active(1)
}
MAX-ACCESS  read-only
STATUS      current
DESCRIPTION
"Inverter Frequency Lock Fail
Values:
inactive(0),
active(1)
"
 ::= { psInvEntry  37 }

psInvEntryDid1 OBJECT-TYPE
SYNTAX      INTEGER {
inactive(0),
active(1)
}
MAX-ACCESS  read-only
STATUS      current
DESCRIPTION
"ID Conflict
Values:
inactive(0),
active(1)
"
 ::= { psInvEntry  38 }

psInvEntryIcmf1 OBJECT-TYPE
SYNTAX      INTEGER {
inactive(0),
active(1)
}
MAX-ACCESS  read-only
STATUS      current
DESCRIPTION
"Communication Failure
Values:
inactive(0),
active(1)
"
 ::= { psInvEntry  39 }

psInvEntryIcf1 OBJECT-TYPE
SYNTAX      INTEGER {
inactive(0),
active(1)
}
MAX-ACCESS  read-only
STATUS      current
DESCRIPTION
"Hi Crest Factor Status
Values:
inactive(0),
active(1)
"
 ::= { psInvEntry  40 }

psInvEntryIda1 OBJECT-TYPE
SYNTAX      INTEGER {
inactive(0),
active(1)
}
MAX-ACCESS  read-only
STATUS      current
DESCRIPTION
"Distribution Alarm Status
Values:
inactive(0),
active(1)
"
 ::= { psInvEntry  41 }

psInvEntryIhv1 OBJECT-TYPE
SYNTAX      INTEGER {
inactive(0),
active(1)
}
MAX-ACCESS  read-only
STATUS      current
DESCRIPTION
"High Output Status
Values:
inactive(0),
active(1)
"
 ::= { psInvEntry  42 }

psInvEntryIhvi1 OBJECT-TYPE
SYNTAX      INTEGER {
inactive(0),
active(1)
}
MAX-ACCESS  read-only
STATUS      current
DESCRIPTION
"High Input Status
Values:
inactive(0),
active(1)
"
 ::= { psInvEntry  43 }

psInvEntryIipk1 OBJECT-TYPE
SYNTAX      INTEGER {
inactive(0),
active(1)
}
MAX-ACCESS  read-only
STATUS      current
DESCRIPTION
"High IPeak Status
Values:
inactive(0),
active(1)
"
 ::= { psInvEntry  44 }

psInvEntryIirm1 OBJECT-TYPE
SYNTAX      INTEGER {
inactive(0),
active(1)
}
MAX-ACCESS  read-only
STATUS      current
DESCRIPTION
"High IRMS Status
Values:
inactive(0),
active(1)
"
 ::= { psInvEntry  45 }

psInvEntryIof1 OBJECT-TYPE
SYNTAX      INTEGER {
inactive(0),
active(1)
}
MAX-ACCESS  read-only
STATUS      current
DESCRIPTION
"Output Fuse Status
Values:
inactive(0),
active(1)
"
 ::= { psInvEntry  46 }



--
-- object psCn5
--

psCn5 OBJECT IDENTIFIER  ::= { powerSystem  70 }

psCn5Ide OBJECT-TYPE
SYNTAX      DisplayString
MAX-ACCESS  read-only
STATUS      current
DESCRIPTION
"Identifier"
 ::= { psCn5  1 }

psCn5Des OBJECT-TYPE
SYNTAX      DisplayString
MAX-ACCESS  read-write
STATUS      current
DESCRIPTION
"Description"
 ::= { psCn5  2 }

psCn5Stt OBJECT-TYPE
SYNTAX      DisplayString
MAX-ACCESS  read-write
STATUS      current
DESCRIPTION
"Status
Values:
NONE,
DISCON,
CONNECT,
FAILED
"
 ::= { psCn5  3 }

psCn5Typ OBJECT-TYPE
SYNTAX      DisplayString
MAX-ACCESS  read-write
STATUS      current
DESCRIPTION
"Type
Values:
NONE,
BATTERY,
LOAD
"
 ::= { psCn5  4 }

psCn5Dth OBJECT-TYPE
SYNTAX      Integer32(20000..50000)
MAX-ACCESS  read-write
STATUS      current
DESCRIPTION
"Disconnect Threshold"
 ::= { psCn5  5 }

psCn5Rth OBJECT-TYPE
SYNTAX      Integer32(22000..55000)
UNITS       "mV"
MAX-ACCESS  read-write
STATUS      current
DESCRIPTION
"Reconnect Threshold (mV)"
 ::= { psCn5  6 }

psCn5Ena OBJECT-TYPE
SYNTAX      INTEGER {
disable(0),
enable(1)
}
MAX-ACCESS  read-write
STATUS      current
DESCRIPTION
"Control
Values:
disable(0),
enable(1)
"
 ::= { psCn5  7 }

psCn5Dam OBJECT-TYPE
SYNTAX      INTEGER {
none(0),
voltage(1),
voltageAndTime(2)
}
MAX-ACCESS  read-write
STATUS      current
DESCRIPTION
"Disconnect Automode
Values:
none(0),
voltage(1),
voltageAndTime(2)
"
 ::= { psCn5  8 }

psCn5Dtm OBJECT-TYPE
SYNTAX      Integer32
UNITS       "Minutes"
MAX-ACCESS  read-only
STATUS      current
DESCRIPTION
"Disconnect Time Remaining (Minutes)"
 ::= { psCn5  9 }

psCn5Ram OBJECT-TYPE
SYNTAX      INTEGER {
none(0),
voltage(1),
voltageAndTime(2)
}
MAX-ACCESS  read-write
STATUS      current
DESCRIPTION
"Reconnect Automode
Values:
none(0),
voltage(1),
voltageAndTime(2)
"
 ::= { psCn5  10 }

psCn5Cno OBJECT-TYPE
SYNTAX      DisplayString
MAX-ACCESS  read-only
STATUS      current
DESCRIPTION
"Battery Shunt Trip Open
Value:
Alarm report from CNO4
"
 ::= { psCn5  11 }

psCn5Cnf OBJECT-TYPE
SYNTAX      DisplayString
MAX-ACCESS  read-only
STATUS      current
DESCRIPTION
"Battery Shunt Trip Failed
Value:
Alarm report from CNF4
"
 ::= { psCn5  12 }

psCn5Ddy OBJECT-TYPE
SYNTAX      Integer32(0..300)
UNITS       "Seconds"
MAX-ACCESS  read-write
STATUS      current
DESCRIPTION
"Disconnect Delay (Seconds)"
 ::= { psCn5  13 }

psCn5Rdy OBJECT-TYPE
SYNTAX      Integer32(0..300)
UNITS       "Seconds"
MAX-ACCESS  read-write
STATUS      current
DESCRIPTION
"Reconnect Delay (Seconds)"
 ::= { psCn5  14 }

psCn5Rtm OBJECT-TYPE
SYNTAX      Integer32
UNITS       "Seconds"
MAX-ACCESS  read-only
STATUS      current
DESCRIPTION
"Reconnect Time Remaining (Seconds)"
 ::= { psCn5  15 }


--
-- table PCS
--

psPcsTable    OBJECT-TYPE
SYNTAX SEQUENCE OF PsPcsEntry
MAX-ACCESS not-accessible
STATUS current
DESCRIPTION
        "Table of all PIC Slot data"
 ::= { powerSystem  71 }

psPcsEntry OBJECT-TYPE
SYNTAX     PsPcsEntry
MAX-ACCESS  not-accessible
STATUS      current
DESCRIPTION
       "Entry of information for one PIC Slot"
INDEX { psPcsEntryIndex }
 ::= { psPcsTable  1 }

PsPcsEntry ::= SEQUENCE {
psPcsEntryIndex   INTEGER,
psPcsEntryIde   DisplayString,
psPcsEntryDes   DisplayString,
psPcsEntryStt   DisplayString,
psPcsEntryTyp   DisplayString,
psPcsEntryPole   Integer32,
psPcsEntryPolp   Integer32,
psPcsEntryPopn   DisplayString,
psPcsEntryTrp   INTEGER,
psPcsEntryBad   INTEGER,
psPcsEntryCbf   DisplayString,
psPcsEntrySlv   INTEGER,
psPcsEntryRtng   Integer32
}

psPcsEntryIndex OBJECT-TYPE
SYNTAX      INTEGER (0..2147483647)
MAX-ACCESS  read-only
STATUS      current
DESCRIPTION
"Table Index"
 ::= { psPcsEntry  1 }

psPcsEntryIde OBJECT-TYPE
SYNTAX      DisplayString
MAX-ACCESS  read-only
STATUS      current
DESCRIPTION
"Identifier"
 ::= { psPcsEntry  2 }

psPcsEntryDes OBJECT-TYPE
SYNTAX      DisplayString
MAX-ACCESS  read-write
STATUS      current
DESCRIPTION
"Description"
 ::= { psPcsEntry  3 }

psPcsEntryStt OBJECT-TYPE
SYNTAX      DisplayString
MAX-ACCESS  read-only
STATUS      current
DESCRIPTION
"Status"
 ::= { psPcsEntry  4 }

psPcsEntryTyp OBJECT-TYPE
SYNTAX      DisplayString
MAX-ACCESS  read-write
STATUS      current
DESCRIPTION
"Type
Values:
Load,
Batt,
picType
"
 ::= { psPcsEntry  5 }

psPcsEntryPole OBJECT-TYPE
SYNTAX      Integer32
MAX-ACCESS  read-write
STATUS      current
DESCRIPTION
"Number of Poles"
 ::= { psPcsEntry  6 }

psPcsEntryPolp OBJECT-TYPE
SYNTAX      Integer32
MAX-ACCESS  read-write
STATUS      current
DESCRIPTION
"Slot Pole Position"
 ::= { psPcsEntry  7 }

psPcsEntryPopn OBJECT-TYPE
SYNTAX      DisplayString
MAX-ACCESS  read-write
STATUS      current
DESCRIPTION
"Slot Pole Open/Closed
Values:
Open,
Closed
"
 ::= { psPcsEntry  8 }

psPcsEntryTrp OBJECT-TYPE
SYNTAX      INTEGER {
off(0),
on(1)
}
MAX-ACCESS  read-write
STATUS      current
DESCRIPTION
"Slot Tripped
Values:
off(0),
on(1)
"
 ::= { psPcsEntry  9 }

psPcsEntryBad OBJECT-TYPE
SYNTAX      INTEGER {
off(0),
on(1)
}
MAX-ACCESS  read-write
STATUS      current
DESCRIPTION
"Slot Bad
Values:
off(0),
on(1)
"
 ::= { psPcsEntry  10 }

psPcsEntryCbf OBJECT-TYPE
SYNTAX      DisplayString
MAX-ACCESS  read-write
STATUS      current
DESCRIPTION
"Slot CB or Fuse
Values:
CB,
Fuse
"
 ::= { psPcsEntry  11 }

psPcsEntrySlv OBJECT-TYPE
SYNTAX      INTEGER {
off(0),
on(1)
}
MAX-ACCESS  read-write
STATUS      current
DESCRIPTION
"Slot Slave
Values:
off(0),
on(1)
"
 ::= { psPcsEntry  12 }

psPcsEntryRtng OBJECT-TYPE
SYNTAX      Integer32
MAX-ACCESS  read-write
STATUS      current
DESCRIPTION
"Slot Rtng"
 ::= { psPcsEntry  13 }



END
