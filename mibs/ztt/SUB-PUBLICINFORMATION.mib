SUB-PUBLICINFORMATION DEFINITIONS ::= BEGIN
	
	IMPORTS
		StorageType,
		RowStatus,
		DisplayString,
		TEXTUAL-CONVENTION
	FROM SNMPv2-TC
		OBJECT-GROUP,
		MODULE-COMPLIANCE
	FROM SNMPv2-CONF
		publicInformation
	FROM ZTT-GLOBAL
		experimental,
		MODULE-IDENTITY,
		OBJECT-IDENTITY,
		OBJECT-TYPE,
		Integer32,
		TimeTicks
	FROM SNMPv2-SMI;
	
	publicInformationTable OBJECT-TYPE
		SYNTAX SEQUENCE OF PublicInformationEntry
		MAX-ACCESS not-accessible
		STATUS current
		DESCRIPTION
			"The table of publicInformation devices."
	-- 1.3.6.1.4.1.49692.1.3.1 --  ::= { publicInformation 1 }
	
	publicInformationEntry OBJECT-TYPE
		SYNTAX PublicInformationEntry
		MAX-ACCESS not-accessible
		STATUS current
		DESCRIPTION
			"The publicInformation entry."
		INDEX {
			devIndex }
	-- 1.3.6.1.4.1.49692.1.3.1.1 --  ::= { publicInformationTable 1 }
	
	PublicInformationEntry ::= SEQUENCE {
		devIndex	Integer32,
		devId	OCTET STRING,
		Energysavingallowed001	Integer32,
		minimumnumberofworkingmodules001	Integer32,
		Modulecycleswitchingperioddays001	Integer32,
		ModuleBestEfficiencyPoint001	Integer32,
		moduleredundancypoint001	Integer32,
		Energysavingtestallowed001	Integer32,
		systemtime001	OCTET STRING,
		Energysavingsetting001	Integer32,
		Minimumnumberofworkingmodulesmodulesetting001	Integer32,
		Modulebestefficiencypointsetting001	Integer32,
		Moduleredundancypointsetting001	Integer32,
		Energysavingtestallowssetting001	Integer32,
		Modulecycleswitchcyclesetting001	Integer32,
		timesetting001	OCTET STRING,
		languagetypesetting001	Integer32,
		DCvoltagecalibrationcoefficientsetting001	Integer32,
		AC1-wayA-phasevoltagecalibrationcoefficientsetting001	Integer32,
		AC1-wayB-phasevoltagecalibrationcoefficientsetting001	Integer32,
		AC1-wayC-phasevoltagecalibrationcoefficientsetting001	Integer32 }
	
	devIndex OBJECT-TYPE
		SYNTAX Integer32
		MAX-ACCESS not-accessible
		STATUS current
		DESCRIPTION
			"The index of the device."
	-- 1.3.6.1.4.1.49692.1.3.1.1.1 --  ::= { publicInformationEntry 1 }
	
	devId OBJECT-TYPE
		SYNTAX OCTET STRING
		MAX-ACCESS read-only
		STATUS current
		DESCRIPTION
			"The deviceId of the device."
	-- 1.3.6.1.4.1.49692.1.3.1.1.2 --  ::= { publicInformationEntry 2 }
	
	Energysavingallowed001 OBJECT-TYPE
		SYNTAX Integer32
		MAX-ACCESS read-only
		STATUS current
		DESCRIPTION
			"Energy saving allowed(001), meterId(433716001)."
	-- 1.3.6.1.4.1.49692.1.3.1.1.3 --  ::= { publicInformationEntry 3 }
	
	minimumnumberofworkingmodules001 OBJECT-TYPE
		SYNTAX Integer32
		MAX-ACCESS read-only
		STATUS current
		DESCRIPTION
			"minimum number of working modules(001), meterId(433717001)."
	-- 1.3.6.1.4.1.49692.1.3.1.1.4 --  ::= { publicInformationEntry 4 }
	
	Modulecycleswitchingperioddays001 OBJECT-TYPE
		SYNTAX Integer32
		MAX-ACCESS read-only
		STATUS current
		DESCRIPTION
			"Module cycle switching period (days)(001), meterId(433718001)."
	-- 1.3.6.1.4.1.49692.1.3.1.1.5 --  ::= { publicInformationEntry 5 }
	
	ModuleBestEfficiencyPoint001 OBJECT-TYPE
		SYNTAX Integer32
		MAX-ACCESS read-only
		STATUS current
		DESCRIPTION
			"Module Best Efficiency Point(001), meterId(433719001)."
	-- 1.3.6.1.4.1.49692.1.3.1.1.6 --  ::= { publicInformationEntry 6 }
	
	moduleredundancypoint001 OBJECT-TYPE
		SYNTAX Integer32
		MAX-ACCESS read-only
		STATUS current
		DESCRIPTION
			"module redundancy point(001), meterId(433720001)."
	-- 1.3.6.1.4.1.49692.1.3.1.1.7 --  ::= { publicInformationEntry 7 }
	
	Energysavingtestallowed001 OBJECT-TYPE
		SYNTAX Integer32
		MAX-ACCESS read-only
		STATUS current
		DESCRIPTION
			"Energy saving test allowed(001), meterId(433721001)."
	-- 1.3.6.1.4.1.49692.1.3.1.1.8 --  ::= { publicInformationEntry 8 }
	
	systemtime001 OBJECT-TYPE
		SYNTAX OCTET STRING
		MAX-ACCESS read-only
		STATUS current
		DESCRIPTION
			"system time(001), meterId(433701001)."
	-- 1.3.6.1.4.1.49692.1.3.1.1.9 --  ::= { publicInformationEntry 9 }
	
	Energysavingsetting001 OBJECT-TYPE
		SYNTAX Integer32
		MAX-ACCESS read-write
		STATUS current
		DESCRIPTION
			"Energy saving setting(001), meterId(433741001)."
	-- 1.3.6.1.4.1.49692.1.3.1.1.10 --  ::= { publicInformationEntry 10 }
	
	Minimumnumberofworkingmodulesmodulesetting001 OBJECT-TYPE
		SYNTAX Integer32
		MAX-ACCESS read-write
		STATUS current
		DESCRIPTION
			"Minimum number of working modules module setting(001), meterId(433742001)."
	-- 1.3.6.1.4.1.49692.1.3.1.1.11 --  ::= { publicInformationEntry 11 }
	
	Modulebestefficiencypointsetting001 OBJECT-TYPE
		SYNTAX Integer32
		MAX-ACCESS read-write
		STATUS current
		DESCRIPTION
			"Module best efficiency point setting(001), meterId(433744001)."
	-- 1.3.6.1.4.1.49692.1.3.1.1.12 --  ::= { publicInformationEntry 12 }
	
	Moduleredundancypointsetting001 OBJECT-TYPE
		SYNTAX Integer32
		MAX-ACCESS read-write
		STATUS current
		DESCRIPTION
			"Module redundancy point setting(001), meterId(433745001)."
	-- 1.3.6.1.4.1.49692.1.3.1.1.13 --  ::= { publicInformationEntry 13 }
	
	Energysavingtestallowssetting001 OBJECT-TYPE
		SYNTAX Integer32
		MAX-ACCESS read-write
		STATUS current
		DESCRIPTION
			"Energy saving test allows setting(001), meterId(433746001)."
	-- 1.3.6.1.4.1.49692.1.3.1.1.14 --  ::= { publicInformationEntry 14 }
	
	Modulecycleswitchcyclesetting001 OBJECT-TYPE
		SYNTAX Integer32
		MAX-ACCESS read-write
		STATUS current
		DESCRIPTION
			"Module cycle switch cycle setting(001), meterId(433743001)."
	-- 1.3.6.1.4.1.49692.1.3.1.1.15 --  ::= { publicInformationEntry 15 }
	
	timesetting001 OBJECT-TYPE
		SYNTAX OCTET STRING
		MAX-ACCESS read-write
		STATUS current
		DESCRIPTION
			"time setting(001), meterId(433702001)."
	-- 1.3.6.1.4.1.49692.1.3.1.1.16 --  ::= { publicInformationEntry 16 }
	
	languagetypesetting001 OBJECT-TYPE
		SYNTAX Integer32
		MAX-ACCESS read-write
		STATUS current
		DESCRIPTION
			"language type setting(001), meterId(433763001)."
	-- 1.3.6.1.4.1.49692.1.3.1.1.17 --  ::= { publicInformationEntry 17 }
	
	DCvoltagecalibrationcoefficientsetting001 OBJECT-TYPE
		SYNTAX Integer32
		MAX-ACCESS read-write
		STATUS current
		DESCRIPTION
			"DC voltage calibration coefficient setting(001), meterId(433730001), scale:1000."
	-- 1.3.6.1.4.1.49692.1.3.1.1.18 --  ::= { publicInformationEntry 18 }
	
	AC1-wayA-phasevoltagecalibrationcoefficientsetting001 OBJECT-TYPE
		SYNTAX Integer32
		MAX-ACCESS read-write
		STATUS current
		DESCRIPTION
			"AC 1-way A-phase voltage calibration coefficient setting(001), meterId(433731001), scale:1000."
	-- 1.3.6.1.4.1.49692.1.3.1.1.19 --  ::= { publicInformationEntry 19 }
	
	AC1-wayB-phasevoltagecalibrationcoefficientsetting001 OBJECT-TYPE
		SYNTAX Integer32
		MAX-ACCESS read-write
		STATUS current
		DESCRIPTION
			"AC 1-way B-phase voltage calibration coefficient setting(001), meterId(433732001), scale:1000."
	-- 1.3.6.1.4.1.49692.1.3.1.1.20 --  ::= { publicInformationEntry 20 }
	
	AC1-wayC-phasevoltagecalibrationcoefficientsetting001 OBJECT-TYPE
		SYNTAX Integer32
		MAX-ACCESS read-write
		STATUS current
		DESCRIPTION
			"AC 1-way C-phase voltage calibration coefficient setting(001), meterId(433733001), scale:1000."
	-- 1.3.6.1.4.1.49692.1.3.1.1.21 --  ::= { publicInformationEntry 21 }
	
	
	END
