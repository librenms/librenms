--
-- CAREL-vak-cx-bms-snmp-1.MIB
-- MIB generated by CAREL
-- Monday, 22 January 2024
--
-- NOTE: The vendor-supplied MIB uses object descriptors containing "."
-- (for example "inputscheck.rettemp-val"). A period is not a legal character
-- in an ASN.1/SMI descriptor and makes the module fail to parse ("Bad operator
-- (.)"). Hyphens are legal, so this module keeps the vendor names as-is except
-- for the periods: where the "." is a group.object separator the group prefix
-- is dropped (outputs.glbalrm-doutval -> glbalrm-doutval); where it is an
-- object.field separator the "." becomes "-" (al-hirettemp.active ->
-- al-hirettemp-active). The original vendor descriptor is noted in a comment
-- above each object. OID assignments, syntax and descriptions are verbatim and
-- all objects from the vendor MIB are present.
--

    CAREL-vak-cx-bms-snmp-1-MIB DEFINITIONS ::= BEGIN

        IMPORTS
            MODULE-IDENTITY, OBJECT-TYPE, Integer32, enterprises
                FROM SNMPv2-SMI;

        vak-cx-bms-snmp-1MIB MODULE-IDENTITY
            LAST-UPDATED  "202401221515Z"     -- January 22, 2024 at 15:15 GMT
            ORGANIZATION  "CAREL Industries S.r.l."
            CONTACT-INFO
                "
                        Carel Industries S.r.l.
                        Via dell'Industria, 11
                        35020 Brugine (PD) Italy
                        Tel: +39 049 9716611
                        E-mail: carel@carel.com
                "
            DESCRIPTION
                "This is the MIB module for the vak-cx-bms-snmp-1 device."
            REVISION "202401221515Z"
            DESCRIPTION
                "version4pCOweb"
            ::= { instruments 1 }

--
-- Node definitions
--

        -- 1.3.6.1.4.1.9839
        carel OBJECT IDENTIFIER ::= { enterprises 9839 }

        -- 1.3.6.1.4.1.9839.1
        systm OBJECT IDENTIFIER ::= { carel 1 }

        -- 1.3.6.1.4.1.9839.1.1
        agentRelease OBJECT-TYPE
            SYNTAX Integer32
            UNITS "N/A"
            MAX-ACCESS read-only
            STATUS current
            DESCRIPTION "Release of the Agent."
            ::= { systm 1 }

        -- 1.3.6.1.4.1.9839.1.2
        agentCode OBJECT-TYPE
            SYNTAX Integer32
            UNITS "N/A"
            MAX-ACCESS read-only
            STATUS current
            DESCRIPTION "Code of the Agent. 2=pCOWeb."
            ::= { systm 2 }

        -- 1.3.6.1.4.1.9839.2
        instruments OBJECT IDENTIFIER ::= { carel 2 }

        -- 1.3.6.1.4.1.9839.2.0
        pCOWebInfo OBJECT IDENTIFIER ::= { instruments 0 }

        -- 1.3.6.1.4.1.9839.2.0.10
        pCOStatusgroup OBJECT IDENTIFIER ::= { pCOWebInfo 10 }

        -- 1.3.6.1.4.1.9839.2.0.10.1
        -- ... You will have how many pCOIdX-Status objects as the pCOs connected to pCOWeb.
        pCOId1-Status OBJECT-TYPE
            SYNTAX Integer32
            UNITS "N/A"
            MAX-ACCESS read-only
            STATUS current
            DESCRIPTION "Status of pCOId1. 0=Offline, 1=Init, 2=Online"
            ::= { pCOStatusgroup 1 }

        -- 1.3.6.1.4.1.9839.2.0.11
        pCOErrorsNumbergroup OBJECT IDENTIFIER ::= { pCOWebInfo 11 }

        -- 1.3.6.1.4.1.9839.2.0.11.1
        -- ... You will have how many pCOIdX-ErrorsNumber objects as the pCOs connected to pCOWeb.
        pCOId1-ErrorsNumber OBJECT-TYPE
            SYNTAX Integer32
            UNITS "N/A"
            MAX-ACCESS read-only
            STATUS current
            DESCRIPTION "Number of Communication Errors from pCOId1 to pCOWeb."
            ::= { pCOErrorsNumbergroup 1 }

        -- 1.3.6.1.4.1.9839.2.1.1
        digitalObjects OBJECT IDENTIFIER ::= { vak-cx-bms-snmp-1MIB 1 }

        -- 1.3.6.1.4.1.9839.2.1.1.1
        -- vendor descriptor: onoffunitmng.keybonoff
        keybonoff OBJECT-TYPE
            SYNTAX Integer32 (0..1)
            UNITS "N/A"
            MAX-ACCESS read-write
            STATUS current
            DESCRIPTION "Unit on/off by keyboard ( 0-off, 1-on)"
            DEFVAL { 0 }
            ::= { digitalObjects 1 }

        -- 1.3.6.1.4.1.9839.2.1.1.2
        -- vendor descriptor: outputs.heater-doutval
        heater-doutval OBJECT-TYPE
            SYNTAX Integer32 (0..1)
            UNITS "N/A"
            MAX-ACCESS read-write
            STATUS current
            DESCRIPTION "NO2-Heater output value"
            DEFVAL { 0 }
            ::= { digitalObjects 2 }

        -- 1.3.6.1.4.1.9839.2.1.1.3
        -- vendor descriptor: outputs.glbalrm-doutval
        glbalrm-doutval OBJECT-TYPE
            SYNTAX Integer32 (0..1)
            UNITS "N/A"
            MAX-ACCESS read-write
            STATUS current
            DESCRIPTION "NO7-Global alarm output value"
            DEFVAL { 0 }
            ::= { digitalObjects 3 }

        -- 1.3.6.1.4.1.9839.2.1.1.4
        -- vendor descriptor: inputscheck.lowp-pstat-din
        lowp-pstat-din OBJECT-TYPE
            SYNTAX Integer32 (0..1)
            UNITS "N/A"
            MAX-ACCESS read-write
            STATUS current
            DESCRIPTION "ID3-Low pressure input status"
            DEFVAL { 0 }
            ::= { digitalObjects 4 }

        -- 1.3.6.1.4.1.9839.2.1.1.5
        -- vendor descriptor: inputscheck.hip-pstat-din
        hip-pstat-din OBJECT-TYPE
            SYNTAX Integer32 (0..1)
            UNITS "N/A"
            MAX-ACCESS read-write
            STATUS current
            DESCRIPTION "ID2-High pressure input status"
            DEFVAL { 0 }
            ::= { digitalObjects 5 }

        -- 1.3.6.1.4.1.9839.2.1.1.6
        -- vendor descriptor: al-lowrettemp.active
        al-lowrettemp-active OBJECT-TYPE
            SYNTAX Integer32 (0..1)
            UNITS "N/A"
            MAX-ACCESS read-write
            STATUS current
            DESCRIPTION "Low return temperature alarm - Alarm status"
            DEFVAL { 0 }
            ::= { digitalObjects 6 }

        -- 1.3.6.1.4.1.9839.2.1.1.7
        -- vendor descriptor: al-hirettemp.active
        al-hirettemp-active OBJECT-TYPE
            SYNTAX Integer32 (0..1)
            UNITS "N/A"
            MAX-ACCESS read-write
            STATUS current
            DESCRIPTION "High return temperature alarm - Alarm status"
            DEFVAL { 0 }
            ::= { digitalObjects 7 }

        -- 1.3.6.1.4.1.9839.2.1.1.8
        -- vendor descriptor: al-compdriboard-offline.active
        al-compdriboard-offline-active OBJECT-TYPE
            SYNTAX Integer32 (0..1)
            UNITS "N/A"
            MAX-ACCESS read-write
            STATUS current
            DESCRIPTION "Compressor drive board offline alarm - Alarm status"
            DEFVAL { 0 }
            ::= { digitalObjects 8 }

        -- 1.3.6.1.4.1.9839.2.1.1.9
        -- vendor descriptor: outputs.condheater-doutval
        condheater-doutval OBJECT-TYPE
            SYNTAX Integer32 (0..1)
            UNITS "N/A"
            MAX-ACCESS read-write
            STATUS current
            DESCRIPTION "NO8-Condenser heater output value"
            DEFVAL { 0 }
            ::= { digitalObjects 9 }

        -- 1.3.6.1.4.1.9839.2.1.1.10
        -- vendor descriptor: outputs.condfan-doutval
        condfan-doutval OBJECT-TYPE
            SYNTAX Integer32 (0..1)
            UNITS "N/A"
            MAX-ACCESS read-write
            STATUS current
            DESCRIPTION "NO3-Condenser fan output value"
            DEFVAL { 0 }
            ::= { digitalObjects 10 }

        -- 1.3.6.1.4.1.9839.2.1.1.11
        -- vendor descriptor: outputs.comp-doutval
        comp-doutval OBJECT-TYPE
            SYNTAX Integer32 (0..1)
            UNITS "N/A"
            MAX-ACCESS read-write
            STATUS current
            DESCRIPTION "NO1-Compressor output value"
            DEFVAL { 0 }
            ::= { digitalObjects 11 }

        -- 1.3.6.1.4.1.9839.2.1.1.12
        -- vendor descriptor: outputs.evapfan-doutval
        evapfan-doutval OBJECT-TYPE
            SYNTAX Integer32 (0..1)
            UNITS "N/A"
            MAX-ACCESS read-write
            STATUS current
            DESCRIPTION "NO9-Evaporating fan output value"
            DEFVAL { 0 }
            ::= { digitalObjects 12 }

        -- 1.3.6.1.4.1.9839.2.1.1.13
        -- vendor descriptor: inputscheck.condwatersw-din
        condwatersw-din OBJECT-TYPE
            SYNTAX Integer32 (0..1)
            UNITS "N/A"
            MAX-ACCESS read-write
            STATUS current
            DESCRIPTION "ID6/U6-Condenser water switch input status"
            DEFVAL { 0 }
            ::= { digitalObjects 13 }

        -- 1.3.6.1.4.1.9839.2.1.1.14
        -- vendor descriptor: lowp-pstat
        lowp-pstat OBJECT-TYPE
            SYNTAX Integer32 (0..1)
            UNITS "N/A"
            MAX-ACCESS read-write
            STATUS current
            DESCRIPTION "ID2-Low pressure status"
            DEFVAL { 0 }
            ::= { digitalObjects 14 }

        -- 1.3.6.1.4.1.9839.2.1.1.15
        -- vendor descriptor: hip-pstat
        hip-pstat OBJECT-TYPE
            SYNTAX Integer32 (0..1)
            UNITS "N/A"
            MAX-ACCESS read-write
            STATUS current
            DESCRIPTION "ID1-High pressure status"
            DEFVAL { 0 }
            ::= { digitalObjects 15 }

        -- 1.3.6.1.4.1.9839.2.1.1.16
        -- vendor descriptor: heater-on
        heater-on OBJECT-TYPE
            SYNTAX Integer32 (0..1)
            UNITS "N/A"
            MAX-ACCESS read-write
            STATUS current
            DESCRIPTION "Heater status"
            DEFVAL { 0 }
            ::= { digitalObjects 16 }

        -- 1.3.6.1.4.1.9839.2.1.1.17
        -- vendor descriptor: evapfan-on
        evapfan-on OBJECT-TYPE
            SYNTAX Integer32 (0..1)
            UNITS "N/A"
            MAX-ACCESS read-write
            STATUS current
            DESCRIPTION "Evaporating fan status"
            DEFVAL { 0 }
            ::= { digitalObjects 17 }

        -- 1.3.6.1.4.1.9839.2.1.1.18
        -- vendor descriptor: inputscheck.dinonoff-din
        dinonoff-din OBJECT-TYPE
            SYNTAX Integer32 (0..1)
            UNITS "N/A"
            MAX-ACCESS read-write
            STATUS current
            DESCRIPTION "ID1-Digital input status(0: system on; 1: system off)"
            DEFVAL { 0 }
            ::= { digitalObjects 18 }

        -- 1.3.6.1.4.1.9839.2.1.1.19
        -- vendor descriptor: comp-on
        comp-on OBJECT-TYPE
            SYNTAX Integer32 (0..1)
            UNITS "N/A"
            MAX-ACCESS read-write
            STATUS current
            DESCRIPTION "Compressor status"
            DEFVAL { 0 }
            ::= { digitalObjects 19 }

        -- 1.3.6.1.4.1.9839.2.1.1.20
        -- vendor descriptor: al-lowunitvol.active
        al-lowunitvol-active OBJECT-TYPE
            SYNTAX Integer32 (0..1)
            UNITS "N/A"
            MAX-ACCESS read-write
            STATUS current
            DESCRIPTION "Low unit voltage alarm - Alarm status"
            DEFVAL { 0 }
            ::= { digitalObjects 20 }

        -- 1.3.6.1.4.1.9839.2.1.1.21
        -- vendor descriptor: al-comprecedataerr.active
        al-comprecedataerr-active OBJECT-TYPE
            SYNTAX Integer32 (0..1)
            UNITS "N/A"
            MAX-ACCESS read-write
            STATUS current
            DESCRIPTION "Reveive data error alarm from drive board  - Alarm status"
            DEFVAL { 0 }
            ::= { digitalObjects 21 }

        -- 1.3.6.1.4.1.9839.2.1.1.22
        -- vendor descriptor: al-compmodcomerr.active
        al-compmodcomerr-active OBJECT-TYPE
            SYNTAX Integer32 (0..1)
            UNITS "N/A"
            MAX-ACCESS read-write
            STATUS current
            DESCRIPTION "Compressor modbus communication error alarm from drive board  - Alarm status"
            DEFVAL { 0 }
            ::= { digitalObjects 22 }

        -- 1.3.6.1.4.1.9839.2.1.2
        analogObjects OBJECT IDENTIFIER ::= { vak-cx-bms-snmp-1MIB 2 }

        -- 1.3.6.1.4.1.9839.2.1.2.1
        -- vendor descriptor: regulation.offs-coolsetp
        offs-coolsetp OBJECT-TYPE
            SYNTAX Integer32 (-32768..32767)
            UNITS "N/A"
            MAX-ACCESS read-write
            STATUS current
            DESCRIPTION "Regulate temperature setpoint difference in cooling mode"
            DEFVAL { 0 }
            ::= { analogObjects 1 }

        -- 1.3.6.1.4.1.9839.2.1.2.2
        -- vendor descriptor: offs-heatsetp
        offs-heatsetp OBJECT-TYPE
            SYNTAX Integer32 (-32768..32767)
            UNITS "N/A"
            MAX-ACCESS read-write
            STATUS current
            DESCRIPTION "Regulate temperature setpoint difference in heating mode"
            DEFVAL { 0 }
            ::= { analogObjects 2 }

        -- 1.3.6.1.4.1.9839.2.1.2.3
        heatsetp OBJECT-TYPE
            SYNTAX Integer32 (-32768..32767)
            UNITS "N/A"
            MAX-ACCESS read-write
            STATUS current
            DESCRIPTION "Regulate setpoint in heating mode"
            DEFVAL { 0 }
            ::= { analogObjects 3 }

        -- 1.3.6.1.4.1.9839.2.1.2.4
        coolsetp OBJECT-TYPE
            SYNTAX Integer32 (-32768..32767)
            UNITS "N/A"
            MAX-ACCESS read-write
            STATUS current
            DESCRIPTION "Regulate setpoint in cooling mode"
            DEFVAL { 0 }
            ::= { analogObjects 4 }

        -- 1.3.6.1.4.1.9839.2.1.2.5
        -- vendor descriptor: outputs.evapfan-aoutval
        evapfan-aoutval OBJECT-TYPE
            SYNTAX Integer32 (-32768..32767)
            UNITS "N/A"
            MAX-ACCESS read-write
            STATUS current
            DESCRIPTION "Y3-Evaporating fan analog output value"
            DEFVAL { 0 }
            ::= { analogObjects 5 }

        -- 1.3.6.1.4.1.9839.2.1.2.6
        -- vendor descriptor: outputs.condfan-aoutval
        condfan-aoutval OBJECT-TYPE
            SYNTAX Integer32 (-32768..32767)
            UNITS "N/A"
            MAX-ACCESS read-write
            STATUS current
            DESCRIPTION "Y2-Condenser fan analog output value"
            DEFVAL { 0 }
            ::= { analogObjects 6 }

        -- 1.3.6.1.4.1.9839.2.1.2.7
        -- vendor descriptor: inputscheck.rettemp-val
        rettemp-val OBJECT-TYPE
            SYNTAX Integer32 (-32768..32767)
            UNITS "N/A"
            MAX-ACCESS read-write
            STATUS current
            DESCRIPTION "B1/U1-Return temperature input"
            DEFVAL { 0 }
            ::= { analogObjects 7 }

        -- 1.3.6.1.4.1.9839.2.1.2.8
        condsrcoiltemp OBJECT-TYPE
            SYNTAX Integer32 (-32768..32767)
            UNITS "N/A"
            MAX-ACCESS read-write
            STATUS current
            DESCRIPTION "B2/U2-Condenser coil temperature"
            DEFVAL { 0 }
            ::= { analogObjects 8 }

        -- 1.3.6.1.4.1.9839.2.1.2.12
        rettemp OBJECT-TYPE
            SYNTAX Integer32 (-32768..32767)
            UNITS "N/A"
            MAX-ACCESS read-write
            STATUS current
            DESCRIPTION "B1/U1-Return temperature"
            DEFVAL { 0 }
            ::= { analogObjects 12 }

        -- 1.3.6.1.4.1.9839.2.1.2.13
        -- vendor descriptor: inputscheck.condsrcoiltemp-val
        condsrcoiltemp-val OBJECT-TYPE
            SYNTAX Integer32 (-32768..32767)
            UNITS "N/A"
            MAX-ACCESS read-write
            STATUS current
            DESCRIPTION "B2/U2-Condenser coil temperature input"
            DEFVAL { 0 }
            ::= { analogObjects 13 }

        -- 1.3.6.1.4.1.9839.2.1.2.14
        -- vendor descriptor: inputscheck.comptemp-val
        comptemp-val OBJECT-TYPE
            SYNTAX Integer32 (-32768..32767)
            UNITS "N/A"
            MAX-ACCESS read-write
            STATUS current
            DESCRIPTION "B5/U5-Compressor temperature input"
            DEFVAL { 0 }
            ::= { analogObjects 14 }

        -- 1.3.6.1.4.1.9839.2.1.2.15
        -- vendor descriptor: inputscheck.ambtemp-val
        ambtemp-val OBJECT-TYPE
            SYNTAX Integer32 (-32768..32767)
            UNITS "N/A"
            MAX-ACCESS read-write
            STATUS current
            DESCRIPTION "B6/U6-Ambient temerature input"
            DEFVAL { 0 }
            ::= { analogObjects 15 }

        -- 1.3.6.1.4.1.9839.2.1.3
        integerObjects OBJECT IDENTIFIER ::= { vak-cx-bms-snmp-1MIB 3 }

        -- 1.3.6.1.4.1.9839.2.1.3.9
        -- vendor descriptor: comp-vol-in
        comp-vol-in OBJECT-TYPE
            SYNTAX Integer32 (-32768..32767)
            UNITS "N/A"
            MAX-ACCESS read-write
            STATUS current
            DESCRIPTION "Compressor voltage from drive board"
            DEFVAL { 0 }
            ::= { integerObjects 9 }

        -- 1.3.6.1.4.1.9839.2.1.3.10
        -- vendor descriptor: comp-actspeed
        comp-actspeed OBJECT-TYPE
            SYNTAX Integer32 (-2147483648..2147483647)
            UNITS "N/A"
            MAX-ACCESS read-write
            STATUS current
            DESCRIPTION "Compressor actual speed"
            DEFVAL { 0 }
            ::= { integerObjects 10 }

        -- 1.3.6.1.4.1.9839.2.1.3.16
        -- vendor descriptor: comp-speedfb
        comp-speedfb OBJECT-TYPE
            SYNTAX Integer32 (-32768..32767)
            UNITS "N/A"
            MAX-ACCESS read-write
            STATUS current
            DESCRIPTION "Compressor feedback speed"
            DEFVAL { 0 }
            ::= { integerObjects 16 }

    END

--
-- CAREL-vak-cx-bms-snmp-1.MIB
--
