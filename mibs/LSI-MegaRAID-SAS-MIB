-- Copyright(c) 2006-2007, Avago Technologies
-- MIB file for MegaRAID SAS controllers
-- File Ver: 1.42-01
-- Previous: 1.42-00
-- Revision : Medusa Phase 1
-- Revision : Dimmer Switch II Changes
-- Revision : New Events added for Block HDD  
-- Revision : Added new PD State  
-- Revision : For Battery Type Description
-- Revision : For PRL and SRL description changes for RAID Level
-- Revision : New Attributes added for Bad Block Management
-- Revision : Description changed for hostName
-- Revision : Added Description for Trap Attributes "OldState" and "NewState" for PDTraps and VDTraps.
-- Revision : Added new attributes and traps for MegaRaid Encryption Solution.
-- Revision : Added Support Drive Speed Down(Phase 1).
-- Revision : Added Support for SSD Devices,link speed and device speed.
-- Revision : Replaced LSI Corporation with Avago Technologies 
-- Revision : Multipath support Feature added.
-- Revision : CopyBack Feature,CopyBack is Enabled or Disabled added.
-- Revision : Multipath Feature,Parther Device Id is added.
-- Revision : Trap Section is modified to support Multipath and FRU Traps.
-- Revision : FRU feature added bbuFRU ,revisionIdentifier
-- Revision : to support Increase VD added partitionsInDDF ,maxLdsPerArray    
-- Revision : abortCConError and abortCConErrorSupported added.
-- Revision : Temperature unit added in the description of enclosureTemperature, and spareType description has been updated
-- Revision : clusterSupported was previously clusterSupportedSupported
-- Revision : pdtInserted summary has been modified. 
-- Revision : Trap Section is modified to support HP-OV.
-- Revision : compatibilityFlag, compatibilityInfo attribute added.
-- Revision : Node description modified.
-- Revision : DriverVersion Description updated and MIB updated according to MIB Review.
-- Revision : firmwareVersion description updated
-- Revision : Value Range implemented for read-write object.
-- Revision : For LSI SAS support

LSI-MegaRAID-SAS-MIB DEFINITIONS ::= BEGIN
IMPORTS
    private, enterprises, Counter, Gauge    FROM RFC1155-SMI
    PhysAddress,DisplayString               FROM RFC1213-MIB
    OBJECT-TYPE                 FROM RFC-1212
    TRAP-TYPE                   FROM RFC-1215;

-- LSI specific object identifiers.
lsi   OBJECT IDENTIFIER ::= {enterprises 3582}
storageComponents    OBJECT IDENTIFIER ::= { lsi 4 }
lsiRAIDServer              OBJECT IDENTIFIER ::= { storageComponents 1 }

-- Server Information group.
hostName                     OBJECT-TYPE
    SYNTAX                     DisplayString (SIZE(0..63))
    ACCESS                     read-only
    STATUS                     mandatory
    DESCRIPTION                "Name of the host system."
    ::= { lsiRAIDServer 1 }
hostOSInfo                     OBJECT-TYPE
    SYNTAX                     DisplayString (SIZE(0..63))
    ACCESS                     read-only
    STATUS                     mandatory
    DESCRIPTION                "Operating System description where SNMP agent is running."
    ::= { lsiRAIDServer 2 }
-- Version Information group.
versionInfo                     OBJECT IDENTIFIER ::= {lsiRAIDServer 3}

mibVersion                      OBJECT-TYPE
    SYNTAX                      DisplayString (SIZE(0..63))
    ACCESS                      read-only
    STATUS                      mandatory
    DESCRIPTION                 "The MIB version no. (xx.yy)"
    ::= { versionInfo 1 }

agentModuleName                 OBJECT-TYPE
    SYNTAX                      DisplayString (SIZE(0..63))
    ACCESS                      read-only
    STATUS                      mandatory
    DESCRIPTION                 "The agent module name"
    ::= { versionInfo 2 }

agentModuleVersion              OBJECT-TYPE
    SYNTAX                      DisplayString (SIZE(0..63))
    ACCESS                      read-only
    STATUS                      mandatory
    DESCRIPTION                 "The module version in xx.yy format. Where xx is the major version number and yy is the minor version number(without build information)."
    ::= { versionInfo 3 }

releaseDate                     OBJECT-TYPE
    SYNTAX                      DisplayString (SIZE(0..63))
    ACCESS                      read-only
    STATUS                      mandatory
    DESCRIPTION                 "Module Release Date"
    ::= { versionInfo 4 }

megaRAID-SAS                           OBJECT IDENTIFIER ::= { lsiRAIDServer 4 }
--------------------------------------------------------------------------------
adapter                         OBJECT IDENTIFIER ::= {megaRAID-SAS 1}
-- Adapter Table Definition----------------------------------------------------

adpNumber                       OBJECT-TYPE
    SYNTAX                      Gauge
    ACCESS                      read-only
    STATUS                      mandatory
    DESCRIPTION                 "The total no of SAS adapters present."
    ::= { adapter 1 }

adapterPropertiesTable               OBJECT-TYPE
    SYNTAX                      SEQUENCE OF AdapterPropertiesEntry
    ACCESS                      not-accessible
    STATUS                      optional
    DESCRIPTION                 "A List of adapter Entries containing Information/Properties about the adapters."
    ::= { adapter 2 }

    adapterPropertiesEntry                OBJECT-TYPE
    SYNTAX                      AdapterPropertiesEntry
    ACCESS                      not-accessible
    STATUS                      mandatory
    DESCRIPTION                 "An Entry in the adapter table."
    INDEX                       { adapterID }
    ::= { adapterPropertiesTable 1 }

    AdapterPropertiesEntry ::=
        SEQUENCE {
        adapterID-APT               INTEGER,
        rebuildRate             INTEGER,
        reconstructionRate      INTEGER,
        alarmState              INTEGER,
        cacheFlushInterval       INTEGER,
        clusterState            INTEGER,
	predFailPollInterval    INTEGER,
	intThrottleCount        INTEGER,
	intThrottleTimeUs       INTEGER,
	patrolReadRate          INTEGER,
	bgiRate                 INTEGER,
	spinupDelay             INTEGER,
	spinupDriveCount        INTEGER,
	coercionMode            INTEGER,
	nvramSize            INTEGER,
	memorySize            INTEGER,
	flashSize            INTEGER,
	vdPresentCount       INTEGER,
	vdDegradedCount       INTEGER,
	vdOfflineCount       INTEGER,
	pdPresentCount       INTEGER,
	pdDiskPresentCount       INTEGER,
	pdDiskPredFailureCount       INTEGER,
	pdDiskFailedCount       INTEGER,
	ccRate                  INTEGER,
	compatibilityFlag       INTEGER,
    	compatibilityInfo       DisplayString,
    	abortCConError			INTEGER,
	  copyBackState          INTEGER,
          multipathSupport       INTEGER,
	  revisionIdentifier     DisplayString,
	ssdSMARTerEnabled 	 INTEGER,
   	enableSpinDownUnconfigured INTEGER,
	disableSpinDownHotSpare INTEGER,
	spinDownTime INTEGER,
	supportBreakMirror INTEGER,
    spinupEnclDriveCount		INTEGER,
	spinupEnclDelay			INTEGER,
	defaultLdPSPolicy		INTEGER,
	disableLdPSInterval		INTEGER,
	disableLdPSTime			INTEGER,
	temperatureROC 			INTEGER,
	temperatureCtrl 		INTEGER,
	preventPIImport			INTEGER,
	enablePI			INTEGER,
    	totalSpaceformetadata		INTEGER,
	useEmergencySpare               DisplayString,
	useEmergencySparesforSMARTer	INTEGER,
    	supportShieldState		INTEGER,
    	writeCacheCapable		INTEGER,
		totalCacheSize			INTEGER,
		maximumCacheSize		INTEGER,
		ctrlSasAddr                 DisplayString,
        domainId 		        DisplayString,
        peerControllerStatus    DisplayString,
        maximumControllerNodes  INTEGER,
        incompatibilityDetails  	DisplayString,
        topologyType  		    DisplayString,
	supportOnlineFWUpdate		INTEGER,
	supportFastPathWB			INTEGER,
	supportConfigAutoBalance	INTEGER,
	maintenanceMode		DisplayString,
	disableLargeIO		INTEGER
    }

-- defines for each attribute in AdapterEntry

adapterID-APT                       OBJECT-TYPE
    SYNTAX                      INTEGER
    ACCESS                      read-only
    STATUS                      optional
    DESCRIPTION                 "AdapterID for this Adapter.(Unique)"
    ::= { adapterPropertiesEntry 1 }

rebuildRate                     OBJECT-TYPE
    SYNTAX                      INTEGER (0..100)
    ACCESS                      read-write
    STATUS                      optional
    DESCRIPTION                 "Rebuild rate on this Adapter."
    ::= { adapterPropertiesEntry 2 }

reconstructionRate              OBJECT-TYPE
    SYNTAX                      INTEGER (0..100)
    ACCESS                      read-write
    STATUS                      optional
    DESCRIPTION                 "Reconstruction rate on this Adapter."
    ::= { adapterPropertiesEntry 3 }

alarmState                      OBJECT-TYPE
    SYNTAX                      INTEGER (0..1)
    ACCESS                      read-write
    STATUS                      optional
    DESCRIPTION                 "Alarm is enabled or disabled on this adapter. Values: disabled(0),enabled(1)"
    ::= { adapterPropertiesEntry 4 }

cacheFlushInterval                     OBJECT-TYPE
    SYNTAX                      INTEGER
    ACCESS                      read-only
    STATUS                      optional
    DESCRIPTION                 "Cache flush interval in seconds for this adapter."
    ::= { adapterPropertiesEntry 5 }
    
clusterState                     OBJECT-TYPE
    SYNTAX                      INTEGER
    ACCESS                      read-only
    STATUS                      optional
    DESCRIPTION                 "Cluster is enabled or disabled on this adapter. Values: disabled(0),enabled(1)"
    ::= { adapterPropertiesEntry 6 }

predFailPollInterval            OBJECT-TYPE
    SYNTAX                      INTEGER
    ACCESS                      read-write
    STATUS                      optional
    DESCRIPTION                 "Number of seconds between precdictive fail polls on this adapter."
    ::= { adapterPropertiesEntry 7 }

intThrottleCount                OBJECT-TYPE
    SYNTAX                      INTEGER
    ACCESS                      read-write
    STATUS                      optional
    DESCRIPTION                 "Interrupt throttle active count on this adapter."
    ::= { adapterPropertiesEntry 8 }

intThrottleTimeUs               OBJECT-TYPE
    SYNTAX                      INTEGER
    ACCESS                      read-write
    STATUS                      optional
    DESCRIPTION                 "Interrupt throttle completion hold time on this adapter."
    ::= { adapterPropertiesEntry 9 }

patrolReadRate                  OBJECT-TYPE
    SYNTAX                      INTEGER (0..100)
    ACCESS                      read-write
    STATUS                      optional
    DESCRIPTION                 "Patrol Read Rate for this adapter."
    ::= { adapterPropertiesEntry 10 }

bgiRate                         OBJECT-TYPE
    SYNTAX                      INTEGER (0..100)
    ACCESS                      read-write
    STATUS                      optional
    DESCRIPTION                 "Background initialization rate for this adapter."
    ::= { adapterPropertiesEntry 11 }

spinupDelay                     OBJECT-TYPE
    SYNTAX                      INTEGER
    ACCESS                      read-write
    STATUS                      optional
    DESCRIPTION                 "Number of seconds to delay among spinup groups for this adapter."
    ::= { adapterPropertiesEntry 12 }

spinupDriveCount                OBJECT-TYPE
    SYNTAX                      INTEGER
    ACCESS                      read-write
    STATUS                      optional
    DESCRIPTION                 "Maximum number of drives to spin up at one time for this adapter."
    ::= { adapterPropertiesEntry 13 }
    
coercionMode                OBJECT-TYPE
    SYNTAX                      INTEGER
    ACCESS                      read-only
    STATUS                      optional
    DESCRIPTION                 "Drive capacity coercion mode. 0->None; 1->128MB; 2->1GB"
    ::= { adapterPropertiesEntry 14 }

nvramSize                OBJECT-TYPE
    SYNTAX                      INTEGER
    ACCESS                      read-only
    STATUS                      optional
    DESCRIPTION                 "NVRAM size in KB for this adapter."
    ::= { adapterPropertiesEntry 15 }

memorySize                OBJECT-TYPE
    SYNTAX                      INTEGER
    ACCESS                      read-only
    STATUS                      optional
    DESCRIPTION                 "Memory size in MB for this adapter."
    ::= { adapterPropertiesEntry 16 }

flashSize                OBJECT-TYPE
    SYNTAX                      INTEGER
    ACCESS                      read-only
    STATUS                      optional
    DESCRIPTION                 "Flash size in MB for this adapter."
    ::= { adapterPropertiesEntry 17 }
vdPresentCount                OBJECT-TYPE
    SYNTAX                      INTEGER
    ACCESS                      read-only
    STATUS                      optional
    DESCRIPTION                 "Virtual  devices present in this adapter."
    ::= { adapterPropertiesEntry 18 }
vdDegradedCount                OBJECT-TYPE
    SYNTAX                      INTEGER
    ACCESS                      read-only
    STATUS                      optional
    DESCRIPTION                 "Number of virtual  devices in this adapter that are critical"
    ::= { adapterPropertiesEntry 19 }
vdOfflineCount                OBJECT-TYPE
    SYNTAX                      INTEGER
    ACCESS                      read-only
    STATUS                      optional
    DESCRIPTION                 "Number of virtual  devices in this adapter that are offline"
    ::= { adapterPropertiesEntry 20 }
pdPresentCount                OBJECT-TYPE
    SYNTAX                      INTEGER
    ACCESS                      read-only
    STATUS                      optional
    DESCRIPTION                 "Physical devices present in this adapter."
    ::= { adapterPropertiesEntry 21 }
pdDiskPresentCount                OBJECT-TYPE
    SYNTAX                      INTEGER
    ACCESS                      read-only
    STATUS                      optional
    DESCRIPTION                 "Physical disk devices present in this adapter."
    ::= { adapterPropertiesEntry 22 }
pdDiskPredFailureCount                OBJECT-TYPE
    SYNTAX                      INTEGER
    ACCESS                      read-only
    STATUS                      optional
    DESCRIPTION                 "Number of disk devices in this adapter that are critical"
    ::= { adapterPropertiesEntry 23 }
pdDiskFailedCount                OBJECT-TYPE
    SYNTAX                      INTEGER
    ACCESS                      read-only
    STATUS                      optional
    DESCRIPTION                 "Number of disk devices in this adapter that are failed"
    ::= { adapterPropertiesEntry 24 }
ccRate                OBJECT-TYPE
    SYNTAX                      INTEGER (0..100)
    ACCESS                      read-write
    STATUS                      optional
    DESCRIPTION                 "Consistency Check rate on this Adapter."
    ::= { adapterPropertiesEntry 25 }
compatibilityFlag                OBJECT-TYPE
    SYNTAX                      INTEGER
    ACCESS                      read-only
    STATUS                      optional
    DESCRIPTION                 "To inform compatibilities between Applications and FW. 0->incompatible; 1->compatible"
    ::= { adapterPropertiesEntry 26 } 
compatibilityInfo                OBJECT-TYPE
    SYNTAX                      DisplayString
    ACCESS                      read-only
    STATUS                      optional
    DESCRIPTION                 "Compatibility Information. Format->(Firmware Forward compatibility flag:Firmware Backward compatibility flag:Firmware version flag:Application Forward compatibility flag:Application Backward compatibility flag:Application version flag)"
    ::= { adapterPropertiesEntry 27 }
abortCConError                OBJECT-TYPE
    SYNTAX                      INTEGER (0..1)
    ACCESS                      read-write
    STATUS                      optional
    DESCRIPTION                 "Abort CC on detecting error is enabled or disabled on this adapter.
    Values: No(0),Yes(1),NA(2)"
    ::= { adapterPropertiesEntry 28 }  
copyBackState                  OBJECT-TYPE
    SYNTAX                      INTEGER
    ACCESS                      read-only
    STATUS                      optional
    DESCRIPTION                 "CopyBack is enabled or disabled on this adapter.Values: disabled(0),enabled(1)"
    ::= { adapterPropertiesEntry 29 }
-- adding revision ID
revisionIdentifier                OBJECT-TYPE
    SYNTAX                      DisplayString
    ACCESS                      read-only
    STATUS                      optional
    DESCRIPTION                 "Board revision ID for this Adapter."
    ::= { adapterPropertiesEntry 30 }
multipathSupport                OBJECT-TYPE
    SYNTAX                      INTEGER
    ACCESS                      read-only
    STATUS                      optional
    DESCRIPTION                 "Multipath is supported or not supported on this adapter.Values: not supported(0),supported(1)"
    ::= { adapterPropertiesEntry 31 }

ssdSMARTerEnabled            OBJECT-TYPE
    SYNTAX                      INTEGER
    ACCESS                      read-only
    STATUS                      optional
    DESCRIPTION                 "Copyback to SSD on SMART error. Values Enabled(0),Disabled(1)"
    ::= { adapterPropertiesEntry 32 }

enableSpinDownUnconfigured      OBJECT-TYPE
    SYNTAX                      INTEGER
    ACCESS                      read-only
    STATUS                      optional
    DESCRIPTION                 "Spin Down Unconfigured Drives(1), Do Not Spin Down Unconfigured Drives(0)"
    ::= { adapterPropertiesEntry 33 }
disableSpinDownHotSpare			OBJECT-TYPE
    SYNTAX                      INTEGER
    ACCESS                      read-only
    STATUS                      optional
    DESCRIPTION                 "Spin Down Hotspares(0), Do Not Spin Down Hotspares(1)"
    ::= { adapterPropertiesEntry 34 }
spinDownTime					OBJECT-TYPE
    SYNTAX                      INTEGER
    ACCESS                      read-only
    STATUS                      optional
    DESCRIPTION                 "SpinDownTime in minutes"
    ::= { adapterPropertiesEntry 35 }
spinupEnclDriveCount			OBJECT-TYPE
    SYNTAX                      INTEGER
    ACCESS                      read-only
    STATUS                      optional
    DESCRIPTION                 "Maximum number of drives that can be spin up in an enclosure"
    ::= { adapterPropertiesEntry 36 }
spinupEnclDelay		OBJECT-TYPE
    SYNTAX                      INTEGER
    ACCESS                      read-only
    STATUS                      optional
    DESCRIPTION                 "Delay between drive spin up for drives within an enclosure"
    ::= { adapterPropertiesEntry 37 }
defaultLdPSPolicy				OBJECT-TYPE
    SYNTAX                      INTEGER
    ACCESS                      read-only
    STATUS                      optional
    DESCRIPTION                 "power saving policy.values:controller default power saving policy=0, AUTO=1, MAX=2, Max with no cache=6, NONE=255"
    ::= { adapterPropertiesEntry 38 }
disableLdPSInterval				OBJECT-TYPE
    SYNTAX                      INTEGER
    ACCESS                      read-only
    STATUS                      optional
    DESCRIPTION                 "LD power savings are disabled for yy hours beginning at disableLdPSTime."
    ::= { adapterPropertiesEntry 39 }
disableLdPSTime				OBJECT-TYPE
    SYNTAX                      INTEGER
    ACCESS                      read-only
    STATUS                      optional
    DESCRIPTION                 "LD power savings shall be disabled at xx minutes from 12:00am."
    ::= { adapterPropertiesEntry 40}
supportBreakMirror			OBJECT-TYPE
    SYNTAX                      INTEGER
    ACCESS                      read-only
    STATUS                      optional
    DESCRIPTION                 "1=Support break mirror operation,0=Do not Support break mirror operation"
    ::= { adapterPropertiesEntry 41 } 
    
temperatureROC			OBJECT-TYPE
    SYNTAX                      INTEGER
    ACCESS                      read-only
    STATUS                      optional
    DESCRIPTION                 "temperature of RAID On Chip in Celsius"
    ::= { adapterPropertiesEntry 42 }

temperatureCtrl			OBJECT-TYPE
    SYNTAX                      INTEGER
    ACCESS                      read-only
    STATUS                      optional
    DESCRIPTION                 "temperature of controller in Celsius"
    ::= { adapterPropertiesEntry 43 }   
    
preventPIImport			OBJECT-TYPE
    SYNTAX                      INTEGER
    ACCESS                      read-only
    STATUS                      optional
    DESCRIPTION                 "1=Prevent import of SAS PI protected logical disks , 0=Not Prevent import of SAS PI protected logical disks"
    ::= { adapterPropertiesEntry 44 }

enablePI			OBJECT-TYPE
    SYNTAX                      INTEGER
    ACCESS                      read-only
    STATUS                      optional
    DESCRIPTION                 "1 = Enable SAS PI for controller , 0 = Disable SAS PI for controller"
    ::= { adapterPropertiesEntry 45 }

totalSpaceformetadata		OBJECT-TYPE
    SYNTAX                      INTEGER
    ACCESS                      read-only
    STATUS                      optional
    DESCRIPTION                 "Total Space used for MetaData"
    ::= { adapterPropertiesEntry 46 }

useEmergencySpare	         OBJECT-TYPE
    SYNTAX                      DisplayString
    ACCESS                      read-only
    STATUS                      optional
    DESCRIPTION                 "This field give the information about Emergency Spare possible Drive types(Uncongiured Good/Global Hotspare)"
    ::= { adapterPropertiesEntry 47 }

useEmergencySparesforSMARTer		OBJECT-TYPE
    SYNTAX                      INTEGER
    ACCESS                      read-only
    STATUS                      optional
    DESCRIPTION                 "1 = Use Emergency spares for SMARTer ,0 = Not Use Emergency spares for SMARTer"
    ::= { adapterPropertiesEntry 48 }

supportShieldState		OBJECT-TYPE
    SYNTAX                      INTEGER
    ACCESS                      read-only
    STATUS                      optional
    DESCRIPTION                 "1 =Support PD shield state ,0 = Not Support PD shield state"
    ::= { adapterPropertiesEntry 49 }
    
writeCacheCapable		OBJECT-TYPE
    SYNTAX                      INTEGER
    ACCESS                      read-only
    STATUS                      optional
    DESCRIPTION                 "1 = SSC support write caching IOs ,0 = SSC not support write caching IOs"
    ::= { adapterPropertiesEntry 50 }

totalCacheSize		OBJECT-TYPE
    SYNTAX                      INTEGER
    ACCESS                      read-only
    STATUS                      optional
    DESCRIPTION                 "This field give the information about total Size of currently configured SSC,in GB"
    ::= { adapterPropertiesEntry 51 }

maximumCacheSize		OBJECT-TYPE
    SYNTAX                      INTEGER
    ACCESS                      read-only
    STATUS                      optional
    DESCRIPTION                 "This field give the information about maxmium Size of SSC that can yet be configured,in GB"
    ::= { adapterPropertiesEntry 52 }
     
ctrlSasAddr		            OBJECT-TYPE
    SYNTAX                      DisplayString
    ACCESS                      read-only
    STATUS                      optional
    DESCRIPTION                 "This field gives the controller SAS address"
    ::= { adapterPropertiesEntry 53 }	

domainId		OBJECT-TYPE
    SYNTAX                      DisplayString
    ACCESS                      read-only
    STATUS                      optional
    DESCRIPTION                 "This field gives the Domain ID"
    ::= { adapterPropertiesEntry 54 }	
	
peerControllerStatus		OBJECT-TYPE
    SYNTAX                      DisplayString
    ACCESS                      read-only
    STATUS                      optional
    DESCRIPTION                 "This field gives the Peer controller Status"
    ::= { adapterPropertiesEntry 55 }
	
maximumControllerNodes           OBJECT-TYPE
    SYNTAX                      INTEGER
    ACCESS                      read-only
    STATUS                      optional
    DESCRIPTION                 "This field gives the HA nodes this FW supports"
    ::= { adapterPropertiesEntry 56 }
	
incompatibilityDetails           OBJECT-TYPE
    SYNTAX                      DisplayString
    ACCESS                      read-only
    STATUS                      optional
    DESCRIPTION                 "This field gives the Incompatibility Details"
    ::= { adapterPropertiesEntry 57 }	
	
topologyType           OBJECT-TYPE
    SYNTAX                      DisplayString
    ACCESS                      read-only
    STATUS                      optional
    DESCRIPTION                 "This field gives the Topology Type"
    ::= { adapterPropertiesEntry 58 }	 
      
supportOnlineFWUpdate	OBJECT-TYPE
	SYNTAX                      INTEGER
    ACCESS                      read-only
    STATUS                      optional
    DESCRIPTION                 "1 = Online firmware update is supported, 0 = Online firmware update is not supported"
    ::= { adapterPropertiesEntry 59 }

supportFastPathWB		OBJECT-TYPE
    SYNTAX                      INTEGER
    ACCESS                      read-only
    STATUS                      optional
    DESCRIPTION                 "1 = Support Fast Path WB on Raptor Type Ld ,0 = Does not support Fast Path WB on Raptor Type Ld"
    ::= { adapterPropertiesEntry 60 }
 
supportConfigAutoBalance		OBJECT-TYPE
    SYNTAX                      INTEGER
    ACCESS                      read-only
	    STATUS                      optional
    DESCRIPTION                 "0 = no configuration auto balance support, 1 = configuration auto balance support is present"
    ::= { adapterPropertiesEntry 61 }
  
maintenanceMode		OBJECT-TYPE
    SYNTAX                      DisplayString
    ACCESS                      read-only
	    STATUS                      optional
    DESCRIPTION                 "1=FW supports maintenance mode"
    ::= { adapterPropertiesEntry 62 }

disableLargeIO		OBJECT-TYPE
    SYNTAX                      INTEGER
    ACCESS                      read-only
	    STATUS                      optional
    DESCRIPTION                 "0 = Large IO is supported, 1 = Large IO is unsupported"
    ::= { adapterPropertiesEntry 63 }
   
--------------start adp info-------------------------------------
adapterInfoTable                    OBJECT-TYPE
    SYNTAX                      SEQUENCE OF AdapterInfoEntry
    ACCESS                      not-accessible
    STATUS                      optional
    DESCRIPTION                 "A List of adapter Entries containing Information/Properties about the adapters on the Controller."
    ::= { adapter 3 }

    adapterInfoEntry                OBJECT-TYPE
    SYNTAX                      AdapterInfoEntry
    ACCESS                      not-accessible
    STATUS                      mandatory
    DESCRIPTION                 "An Entry in the adapterInfo table."
    INDEX                       { adapterID }
    ::= { adapterInfoTable 1 }

    AdapterInfoEntry ::=
        SEQUENCE {
            adapterID-AIT           INTEGER,
            adapterVendorID         DisplayString,
            devID         DisplayString,
            subVendorID         DisplayString,
            subDevID         DisplayString,
            hostInterface    INTEGER,
	    hostInterfacePortCnt         INTEGER,
	    hostInterfacePortAddr         DisplayString,
            devInterface    DisplayString,
	    devInterfacePortCnt         INTEGER,
	    devInterfacePortAddr         DisplayString,
	    productName         DisplayString,
	    serialNo         DisplayString,
	    firmwareVersion         DisplayString,
	    driverVersion         DisplayString,
	    expanderFirmwareVersion DisplayString,
	    lockKeyBinding	INTEGER,
	    maxDAPdCountSpinup60		INTEGER

        }

-- defines for each attribute in AdapterEntry

adapterID-AIT                       OBJECT-TYPE
    SYNTAX                      INTEGER
    ACCESS                      read-only
    STATUS                      optional
    DESCRIPTION                 "AdapterID for this Adapter.(Unique)"
    ::= { adapterInfoEntry 1 }

adapterVendorID                OBJECT-TYPE
    SYNTAX                      DisplayString
    ACCESS                      read-only
    STATUS                      optional
    DESCRIPTION                 "PCI Vendor ID for this Adapter."
    ::= { adapterInfoEntry 2 }

devID                     OBJECT-TYPE
    SYNTAX                      DisplayString
    ACCESS                      read-only
    STATUS                      optional
    DESCRIPTION                 "PCI Device ID for this Adapter."
    ::= { adapterInfoEntry 3 }

subVendorID                 OBJECT-TYPE
    SYNTAX                      DisplayString
    ACCESS                      read-only
    STATUS                      optional
    DESCRIPTION                 "PCI Sub-Vendor ID for this adapter."
    ::= { adapterInfoEntry 4 }
subDevID                 OBJECT-TYPE
    SYNTAX                      DisplayString
    ACCESS                      read-only
    STATUS                      optional
    DESCRIPTION                 "PCI Sub-Device ID for this adapter."
    ::= { adapterInfoEntry 5 }
hostInterface                 OBJECT-TYPE
    SYNTAX                      INTEGER
    ACCESS                      read-only
    STATUS                      optional
    DESCRIPTION                 "Host interface information for this adapter.
Values: N/A(0),PCIX(1),PCIE(2),iSCSI(3),SAS-3G(4)"
    ::= { adapterInfoEntry 6 }
hostInterfacePortCnt                 OBJECT-TYPE
    SYNTAX                      INTEGER
    ACCESS                      read-only
    STATUS                      optional
    DESCRIPTION                 "Port Count on this adapter."
    ::= { adapterInfoEntry 7 }
hostInterfacePortAddr                 OBJECT-TYPE
    SYNTAX                      DisplayString
    ACCESS                      read-only
    STATUS                      optional
    DESCRIPTION                 "Port address comma delimited"
    ::= { adapterInfoEntry 8 }
devInterface                 OBJECT-TYPE
    SYNTAX                      DisplayString
    ACCESS                      read-only
    STATUS                      optional
    DESCRIPTION                 "Multiple device interface support values separated by space."
    ::= { adapterInfoEntry 9 }
devInterfacePortCnt           OBJECT-TYPE
    SYNTAX                      INTEGER
    ACCESS                      read-only
    STATUS                      optional
    DESCRIPTION                 "Device Port Count on this adapter."
    ::= { adapterInfoEntry 10 }
devInterfacePortAddr                 OBJECT-TYPE
    SYNTAX                      DisplayString
    ACCESS                      read-only
    STATUS                      optional
    DESCRIPTION                 "Device Port address comma delimited"
    ::= { adapterInfoEntry 11 }
productName                 OBJECT-TYPE
    SYNTAX                      DisplayString
    ACCESS                      read-only
    STATUS                      optional
    DESCRIPTION                 "Product name e.g. MegaRAID SAS-8E, MegaRAID SAS-4X, etc."
    ::= { adapterInfoEntry 12 }
serialNo                 OBJECT-TYPE
    SYNTAX                      DisplayString
    ACCESS                      read-only
    STATUS                      optional
    DESCRIPTION                 "Controller serial number"
    ::= { adapterInfoEntry 13 }

firmwareVersion                 OBJECT-TYPE
    SYNTAX                      DisplayString
    ACCESS                      read-only
    STATUS                      optional
    DESCRIPTION                 "Firmware version Format->(Firmware Package Version:Version:Date:Time)"
    ::= { adapterInfoEntry 14 }
    
driverVersion                 OBJECT-TYPE
    SYNTAX                      DisplayString
    ACCESS                      read-only
    STATUS                      optional
    DESCRIPTION                 "Driver version Format->(Driver Name:Version)"
    ::= { adapterInfoEntry 15 }


expanderFirmwareVersion       OBJECT-TYPE
    SYNTAX                      DisplayString
    ACCESS                      read-only
    STATUS                      optional
    DESCRIPTION                 "Expander firmware version - Not Available if expander is not present on the controller"
    ::= { adapterInfoEntry 16 }


lockKeyBinding                 OBJECT-TYPE
    SYNTAX                      INTEGER
    ACCESS                      read-only
    STATUS                      optional
    DESCRIPTION                 "Type of lock key binding. lock key is not bound(0),lock key bound to FW secret key(1), lock key bound to user(2), lock key bound to a TPM(3)"
    ::= { adapterInfoEntry 17 }
    
maxDAPdCountSpinup60               OBJECT-TYPE
    SYNTAX                      INTEGER
    ACCESS                      read-only
    STATUS                      optional
    DESCRIPTION                 "Maximum number of drives to spinup within 60 sec for direct attached drives"
    ::= { adapterInfoEntry 18 }



    


--------------end adp info
--------------start adp support info
adapterSupportInfoTable                    OBJECT-TYPE
    SYNTAX                      SEQUENCE OF AdapterSupportInfoEntry
    ACCESS                      not-accessible
    STATUS                      optional
    DESCRIPTION                 "A List of adapter Entries containing Information/Properties about the adapters on the Controller."
    ::= { adapter 4 }

    adapterSupportInfoEntry                OBJECT-TYPE
    SYNTAX                      AdapterSupportInfoEntry
    ACCESS                      not-accessible
    STATUS                      mandatory
    DESCRIPTION                 "An Entry in the adapter table."
    INDEX                       { adapterID }
    ::= { adapterSupportInfoTable 1 }

    AdapterSupportInfoEntry ::=
        SEQUENCE {
            adapterID-ASIT           INTEGER,
            maxArms         INTEGER,
            maxSpans         INTEGER,
            maxArrays         INTEGER,
            maxVDs         INTEGER,
            hardwarePresent    DisplayString,
			maxConcurrentCmds         INTEGER,
			maxSGECount         INTEGER,
			maxRequestSize         INTEGER,
			maxLdsPerArray        INTEGER,
			partitionsInDDF       INTEGER,
			allowSSDMixInLD INTEGER,
			allowMixSSDHDDInLD INTEGER
			
        }

-- defines for each attribute in AdapterEntry

adapterID-ASIT                       OBJECT-TYPE
    SYNTAX                      INTEGER
    ACCESS                      read-only
    STATUS                      optional
    DESCRIPTION                 "AdapterID for this Adapter.(Unique)"
    ::= { adapterSupportInfoEntry 1 }

maxArms                OBJECT-TYPE
    SYNTAX                      INTEGER
    ACCESS                      read-only
    STATUS                      optional
    DESCRIPTION                 "Maximum arms per Virtual Drive supported for this Adapter."
    ::= { adapterSupportInfoEntry 2 }

maxSpans                     OBJECT-TYPE
    SYNTAX                      INTEGER
    ACCESS                      read-only
    STATUS                      optional
    DESCRIPTION                 "Maximum spans per Virtual Drive supported for this Adapter."
    ::= { adapterSupportInfoEntry 3 }

maxArrays                 OBJECT-TYPE
    SYNTAX                      INTEGER
    ACCESS                      read-only
    STATUS                      optional
    DESCRIPTION                 "Maximum no of arrays supported for this adapter."
    ::= { adapterSupportInfoEntry 4 }
maxVDs                 OBJECT-TYPE
    SYNTAX                      INTEGER
    ACCESS                      read-only
    STATUS                      optional
    DESCRIPTION                 "Maximum number of Virtual Drive s supported for this adapter."
    ::= { adapterSupportInfoEntry 5 }

hardwarePresent                 OBJECT-TYPE
    SYNTAX                      DisplayString
    ACCESS                      read-only
    STATUS                      optional
    DESCRIPTION                 "Supported Hardware on this adapter. bbu(1),alarm(2),nvram(3),uart(4),TPM(5),expander(6). For multiple hw support a space delimited list will appear."
    ::= { adapterSupportInfoEntry 6 }
maxConcurrentCmds                 OBJECT-TYPE
    SYNTAX                      INTEGER
    ACCESS                      read-only
    STATUS                      optional
    DESCRIPTION                 "The maximum parallel commands supported on this adapter."
    ::= { adapterSupportInfoEntry 7 }
maxSGECount                 OBJECT-TYPE
    SYNTAX                      INTEGER
    ACCESS                      read-only
    STATUS                      optional
    DESCRIPTION                 "The maximum Scatter Gather Element count allowed on this adapter."
    ::= { adapterSupportInfoEntry 8 }
maxRequestSize                 OBJECT-TYPE
    SYNTAX                      INTEGER
    ACCESS                      read-only
    STATUS                      optional
    DESCRIPTION                 "The maximum data transfer size in sectors, on this adapter."
    ::= { adapterSupportInfoEntry 9 }

maxLdsPerArray                 OBJECT-TYPE
    SYNTAX                      INTEGER
    ACCESS                      read-only
    STATUS                      optional
    DESCRIPTION                 "Max Ld's per array in adapter"
    ::= { adapterSupportInfoEntry 10 }
partitionsInDDF                 OBJECT-TYPE
    SYNTAX                      INTEGER
    ACCESS                      read-only
    STATUS                      optional
    DESCRIPTION                 "Max LD's per Array in configuration"
    ::= { adapterSupportInfoEntry 11 }

allowSSDMixInLD              OBJECT-TYPE
    SYNTAX                      INTEGER
    ACCESS                      read-only
    STATUS                      mandatory
    DESCRIPTION                 "allow SAS/SATA SSD mix within an LD. allow(1), not allow(0)"
    ::= { adapterSupportInfoEntry 12 }

allowMixSSDHDDInLD              OBJECT-TYPE
    SYNTAX                      INTEGER
    ACCESS                      read-only
    STATUS                      mandatory
    DESCRIPTION                 "allow SSD/HDD mix within an LD.allow(1), not allow(0)"
    ::= { adapterSupportInfoEntry 13 }
    
--------------end adp info
--------------start adp operations support info
adapterOperationsSupportInfoTable                    OBJECT-TYPE
    SYNTAX                      SEQUENCE OF AdapterOperationsSupportInfoEntry
    ACCESS                      not-accessible
    STATUS                      optional
    DESCRIPTION                 "A List of adapter Entries containing Information/Properties about the adapters on the Controller."
    ::= { adapter 5 }

    adapterOperationsSupportInfoEntry                OBJECT-TYPE
    SYNTAX                      AdapterOperationsSupportInfoEntry
    ACCESS                      not-accessible
    STATUS                      mandatory
    DESCRIPTION                 "An Entry in the adapter table."
    INDEX                       { adapterID }
    ::= { adapterOperationsSupportInfoTable 1 }

    AdapterOperationsSupportInfoEntry ::=
        SEQUENCE {
            adapterID           INTEGER,
            rbldRateSupported         INTEGER,
            ccRateSupported         INTEGER,
            bgiRateSupported         INTEGER,
            reconRateSupported         INTEGER,
            patrolRateSupported    INTEGER,
			alarmControlSupported         INTEGER,
			clusterSupported         INTEGER,
            bbuSupported    INTEGER,
			spanningAllowedSupported         INTEGER,
			dedicatedHotSparesSupported         INTEGER,
			revertibleHotSparesSupported         INTEGER,
			foreignConfigImportSupported         INTEGER,
			selfDiagnosticSupported         INTEGER,
			allowMixedRedundancyOnArraySupported         INTEGER,
			abortCConErrorSupported		INTEGER,
                  securitySupported               INTEGER,
			supportPIcontroller 	  INTEGER
		
        }

-- defines for each attribute in AdapterEntry

adapterID                       OBJECT-TYPE
    SYNTAX                      INTEGER
    ACCESS                      read-only
    STATUS                      optional
    DESCRIPTION                 "AdapterID for this Adapter.(Unique)"
    ::= { adapterOperationsSupportInfoEntry 1 }

rbldRateSupported                OBJECT-TYPE
    SYNTAX                      INTEGER
    ACCESS                      read-only
    STATUS                      optional
    DESCRIPTION                 "Rebuilding rate change support for this Adapter. Values: false(0),true(1)"
    ::= { adapterOperationsSupportInfoEntry 2 }

ccRateSupported                     OBJECT-TYPE
    SYNTAX                      INTEGER
    ACCESS                      read-only
    STATUS                      optional
    DESCRIPTION                 "Consistency Check rate change support for this Adapter. Values: false(0),true(1)"
    ::= { adapterOperationsSupportInfoEntry 3 }

bgiRateSupported                 OBJECT-TYPE
    SYNTAX                      INTEGER
    ACCESS                      read-only
    STATUS                      optional
    DESCRIPTION                 "Background initialization rate change support for this adapter. Values: false(0),true(1)"
    ::= { adapterOperationsSupportInfoEntry 4 }
reconRateSupported                 OBJECT-TYPE
    SYNTAX                      INTEGER
    ACCESS                      read-only
    STATUS                      optional
    DESCRIPTION                 "Reconstruction rate change support for this adapter. Values: false(0),true(1)"
    ::= { adapterOperationsSupportInfoEntry 5 }
patrolRateSupported                 OBJECT-TYPE
    SYNTAX                      INTEGER
    ACCESS                      read-only
    STATUS                      optional
    DESCRIPTION                 "Patrol read rate change support for this adapter. Values: false(0),true(1)"
    ::= { adapterOperationsSupportInfoEntry 6 }
alarmControlSupported                 OBJECT-TYPE
    SYNTAX                      INTEGER
    ACCESS                      read-only
    STATUS                      optional
    DESCRIPTION                 "Alarm control support for this adapter. Values: false(0),true(1)"
    ::= { adapterOperationsSupportInfoEntry 7 }
clusterSupported                 OBJECT-TYPE
    SYNTAX                      INTEGER
    ACCESS                      read-only
    STATUS                      optional
    DESCRIPTION                 "Cluster support for this adapter. Values: false(0),true(1)"
    ::= { adapterOperationsSupportInfoEntry 8 }
bbuSupported                 OBJECT-TYPE
    SYNTAX                      INTEGER
    ACCESS                      read-only
    STATUS                      optional
    DESCRIPTION                 "BBU support for this adapter. Values: false(0),true(1)"
    ::= { adapterOperationsSupportInfoEntry 9 }
spanningAllowedSupported                 OBJECT-TYPE
    SYNTAX                      INTEGER
    ACCESS                      read-only
    STATUS                      optional
    DESCRIPTION                 "Spanning support for this adapter. Values: false(0),true(1)"
    ::= { adapterOperationsSupportInfoEntry 10 }
dedicatedHotSparesSupported                 OBJECT-TYPE
    SYNTAX                      INTEGER
    ACCESS                      read-only
    STATUS                      optional
    DESCRIPTION                 "Dedicated HotSpares support for this adapter. Values: false(0),true(1)"
    ::= { adapterOperationsSupportInfoEntry 11 }
revertibleHotSparesSupported                 OBJECT-TYPE
    SYNTAX                      INTEGER
    ACCESS                      read-only
    STATUS                      optional
    DESCRIPTION                 "Revertible HotSpares support for this adapter. Values: false(0),true(1)"
    ::= { adapterOperationsSupportInfoEntry 12 }
foreignConfigImportSupported                 OBJECT-TYPE
    SYNTAX                      INTEGER
    ACCESS                      read-only
    STATUS                      optional
    DESCRIPTION                 "Support foreign config import on this adapter. Values: false(0),true(1)"
    ::= { adapterOperationsSupportInfoEntry 13 }
selfDiagnosticSupported                 OBJECT-TYPE
    SYNTAX                      INTEGER
    ACCESS                      read-only
    STATUS                      optional
    DESCRIPTION                 "Controller supports self diagnostic. Values: false(0),true(1)"
    ::= { adapterOperationsSupportInfoEntry 14 }
allowMixedRedundancyOnArraySupported                 OBJECT-TYPE
    SYNTAX                      INTEGER
    ACCESS                      read-only
    STATUS                      optional
    DESCRIPTION                 "Allow different Virtual Disk on the same array to have different redundancy levels.
Values: false(0),true(1)"
    ::= { adapterOperationsSupportInfoEntry 15 }

abortCConErrorSupported                 OBJECT-TYPE
	SYNTAX						INTEGER 
	ACCESS                      read-only
    STATUS                      optional
    DESCRIPTION                 "Abort CC on detecting error is supported on this adapter.
Values: No(0),Yes(1)"
    ::= { adapterOperationsSupportInfoEntry	 16 }

securitySupported                 OBJECT-TYPE
    SYNTAX                      INTEGER
    ACCESS                      read-only
    STATUS                      optional
    DESCRIPTION                 "Displays the security support. if supported (1) , not supported (0)"
    ::= { adapterOperationsSupportInfoEntry 17 } 

supportPIcontroller                  OBJECT-TYPE
    SYNTAX                      INTEGER
    ACCESS                      read-only
    STATUS                      optional
    DESCRIPTION                 "Displays the support PI. 1=LD SAS PI Type 0, 0=LD Not SAS PI Type 0"
    ::= { adapterOperationsSupportInfoEntry 18 } 

--------------end adp info
-- BBU Information.
bbuInfo                      OBJECT IDENTIFIER ::= {adapter 6}

bbuNumber                       OBJECT-TYPE
    SYNTAX                      Gauge
    ACCESS                      read-only
    STATUS                      mandatory
    DESCRIPTION                 "The present number of rows in the BBU Table."
    ::= { bbuInfo 1 }
bbuTable                    OBJECT-TYPE
    SYNTAX                      SEQUENCE OF BBUEntry
    ACCESS                      not-accessible
    STATUS                      optional
    DESCRIPTION                 "A List of BBU Entries containing Information/Properties about the BBU."
    ::= { bbuInfo 2 }


    bbuEntry                OBJECT-TYPE
    SYNTAX                      BBUEntry
    ACCESS                      not-accessible
    STATUS                      mandatory
    DESCRIPTION                 "An Entry in the BBU table."
    INDEX                       { bbuID }
    ::= { bbuTable 1 }

    BBUEntry ::=
        SEQUENCE {
            bbuID           INTEGER,
            batteryType    DisplayString,
            nextLearnTime         INTEGER,
            absStateOfCharge     INTEGER,
            fullChargeCapacity         INTEGER,
            averageEmptyTime         INTEGER,
            cycleCount         INTEGER,
            firmwareStatus         DisplayString,
            voltage         INTEGER,
            autoLearnPeriod         INTEGER,
            relStateOfCharge         INTEGER,
            capacityRemain         INTEGER,
            runTimeToEmpty         INTEGER,
            avgTimeToFull         INTEGER,
            errorMargin         INTEGER,
            temperature         DisplayString,
            mfgName             DisplayString,
            deviceName             DisplayString,
            serialNumber             DisplayString,
            chargerStatus        INTEGER,
            adpID        INTEGER,
            remainingCapAlarm        INTEGER,
            remainingTimeAlarm        INTEGER,
            bbu-current        INTEGER,
            gasGaugeStatus     INTEGER,
            bbuFRU             DisplayString,
	    batteryReplacement 		INTEGER,
	    bbuRetentiontime		DisplayString,
	    bbuState		DisplayString,
	    memoryModuleFRU             DisplayString,
	    bbumoduleVersion		DisplayString,
		autoLearnMode           DisplayString,
		chargingStatus          DisplayString,
		capacitance             INTEGER
    }

-- defines for each attribute in BBUEntry

bbuID                       OBJECT-TYPE
    SYNTAX                      INTEGER
    ACCESS                      read-only
    STATUS                      optional
    DESCRIPTION                 "BBUID for this BBU.(Unique)"
    ::= { bbuEntry 1 }

batteryType                OBJECT-TYPE
    SYNTAX                      DisplayString
    ACCESS                      read-only
    STATUS                      optional
    DESCRIPTION                 "BBU Type."
    ::= { bbuEntry 2 }
nextLearnTime                OBJECT-TYPE
    SYNTAX                      INTEGER
    ACCESS                      read-only
    STATUS                      optional
    DESCRIPTION                 "Time of next scheduled learn cycle (seconds past 1/1/2000)"
    ::= { bbuEntry 3 }
absStateOfCharge                OBJECT-TYPE
    SYNTAX                      INTEGER(0..100)
    ACCESS                      read-only
    STATUS                      optional
    DESCRIPTION                 "Predicted remaining capacity expressed as % of DesignCapacity() (0-100). Value of -1 means not supported"
    ::= { bbuEntry 4 }
fullChargeCapacity                OBJECT-TYPE
    SYNTAX                      INTEGER
    ACCESS                      read-only
    STATUS                      optional
    DESCRIPTION                 "Predicted pack capacity when it is fully charged in joules"
    ::= { bbuEntry 5 }
averageEmptyTime                OBJECT-TYPE
    SYNTAX                      INTEGER
    ACCESS                      read-only
    STATUS                      optional
    DESCRIPTION                 "One-minute rolling average of the predicted remaining battery life. Value of -1 means not supported"
    ::= { bbuEntry 6 }
cycleCount                OBJECT-TYPE
    SYNTAX                      INTEGER
    ACCESS                      read-only
    STATUS                      optional
    DESCRIPTION                 "Number of charge cycles the battery has experienced. Value of -1 means not supported"
    ::= { bbuEntry 7 }
firmwareStatus                OBJECT-TYPE
    SYNTAX                      DisplayString
    ACCESS                      read-only
    STATUS                      optional
    DESCRIPTION                 "Condition of battery in following order:
                                 packMissing(0/1)           
                                 voltageLow(0/1)            
                                 temperatureHigh(0/1)       
                                 chargeActive(0/1)          
                                 dischargeActive(0/1)       
                                 learnCycleRequested(0/1)   
                                 learnCycleActive(0/1)      
                                 learnCycleFailed(0/1)      
                                 learnCycleTimeout(0/1)     
                                 i2cErrorsDetected(0/1)
				 noSpace(0/1)
				 predictiveFailure(0/1)
				 premiumFeatureReqd(0/1)
				 microcodeUpdateReqd(0/1)
                                 Only enabled(1) values will be shown"     
    
    ::= { bbuEntry 8 }
voltage                OBJECT-TYPE
    SYNTAX                      INTEGER
    ACCESS                      read-only
    STATUS                      optional
    DESCRIPTION                 "Accurate battery terminal voltage in mV, resolution of 1mV"
    ::= { bbuEntry 9 }
autoLearnPeriod                OBJECT-TYPE
    SYNTAX                      INTEGER
    ACCESS                      read-only
    STATUS                      optional
    DESCRIPTION                 "Time (in seconds) between learn cycles (0 to disable auto learn)"
    ::= { bbuEntry 10 }
relStateOfCharge                OBJECT-TYPE
    SYNTAX                      INTEGER(0..100)
    ACCESS                      read-only
    STATUS                      optional
    DESCRIPTION                 "Predicted remaining capacity expressed as % of FullChargeCapacity() (0-100). Value of -1 means not supported"
    ::= { bbuEntry 11 }
capacityRemain                OBJECT-TYPE
    SYNTAX                      INTEGER
    ACCESS                      read-only
    STATUS                      optional
    DESCRIPTION                 "Predicted charge or energy remaining in the battery in joules"
    ::= { bbuEntry 12 }
runTimeToEmpty                OBJECT-TYPE
    SYNTAX                      INTEGER
    ACCESS                      read-only
    STATUS                      optional
    DESCRIPTION                 "Relative gain or loss in remaining life in response to change in power policy represent in minute. Value of -1 means not supported"
    ::= { bbuEntry 13 }
avgTimeToFull                OBJECT-TYPE
    SYNTAX                      INTEGER
    ACCESS                      read-only
    STATUS                      optional
    DESCRIPTION                 "One-minute rolling average of predicted remaining time to full charge. Value of -1 means not supported"
    ::= { bbuEntry 14 }
errorMargin                OBJECT-TYPE
    SYNTAX                      INTEGER(2..100)
    ACCESS                      read-only
    STATUS                      optional
    DESCRIPTION                 "Expected margin of error (%) in charge calculation (2-100). Value of -1 means not supported"
    ::= { bbuEntry 15 }
temperature                OBJECT-TYPE
    SYNTAX                      DisplayString
    ACCESS                      read-only
    STATUS                      optional
    DESCRIPTION                 "Battery temperature in degree Centigrade"
    ::= { bbuEntry 16 }
mfgName                OBJECT-TYPE
    SYNTAX                      DisplayString
    ACCESS                      read-only
    STATUS                      optional
    DESCRIPTION                 "Battery manufacturer's name"
    ::= { bbuEntry 17 }
deviceName                OBJECT-TYPE
    SYNTAX                      DisplayString
    ACCESS                      read-only
    STATUS                      optional
    DESCRIPTION                 "Battery name"
    ::= { bbuEntry 18 }
serialNumber                OBJECT-TYPE
    SYNTAX                      DisplayString
    ACCESS                      read-only
    STATUS                      optional
    DESCRIPTION                 "Battery serialNumber"
    ::= { bbuEntry 19 }
chargerStatus                OBJECT-TYPE
    SYNTAX                      INTEGER
    ACCESS                      read-only
    STATUS                      optional
    DESCRIPTION                 "Battery charger status. Values: N/A(-1), off(0), complete(1), progress(2)"
    ::= { bbuEntry 20 }
adpID                OBJECT-TYPE
    SYNTAX                      INTEGER
    ACCESS                      read-only
    STATUS                      optional
    DESCRIPTION                 "The adapter id where BBU is attached"
    ::= { bbuEntry 21 }
remainingCapAlarm                OBJECT-TYPE
    SYNTAX                      INTEGER
    ACCESS                      read-only
    STATUS                      optional
    DESCRIPTION                 "Remaining capacity to alarm. Value of -1 means not supported"
    ::= { bbuEntry 22 }
remainingTimeAlarm                OBJECT-TYPE
    SYNTAX                      INTEGER
    ACCESS                      read-only
    STATUS                      optional
    DESCRIPTION                 "Remaining time to alarm. Value of -1 means not supported"
    ::= { bbuEntry 23 }
bbu-current                OBJECT-TYPE
    SYNTAX                      INTEGER
    ACCESS                      read-only
    STATUS                      optional
    DESCRIPTION                 "Current(In mA) being supplied (or accepted) through the battery terminals"
    ::= { bbuEntry 24 }
gasGaugeStatus                OBJECT-TYPE
    SYNTAX                      INTEGER
    ACCESS                      read-only
    STATUS                      optional
    DESCRIPTION                 "Gas gauge status"
    ::= { bbuEntry 25 }
bbuFRU                OBJECT-TYPE
    SYNTAX                      DisplayString
    ACCESS                      read-only
    STATUS                      optional
    DESCRIPTION                 "bbu FRU"
    ::= { bbuEntry 26 }

batteryReplacement                OBJECT-TYPE
    SYNTAX                      INTEGER
    ACCESS                      read-only
    STATUS                      optional
    DESCRIPTION                 "This property denotes whether the Battery needs to be replaced or not.1 =battery needs to be replaced ,0 =battery needs not to be replaced"
    ::= { bbuEntry 27 }

bbuRetentiontime                OBJECT-TYPE
    SYNTAX                      DisplayString
    ACCESS                      read-only
    STATUS                      optional
    DESCRIPTION                 "The total no. of hours the battery can support the current capacity reserve. Undefined(0),48 hours+(>48),the exact no of hours(<=48)"
    ::= { bbuEntry 28 }

bbuState                OBJECT-TYPE
    SYNTAX                      DisplayString
    ACCESS                      read-only
    STATUS                      optional
    DESCRIPTION                 "This property gives the Information about BBU state. Operational = if BBU is working fine, Non-Operational = if BBU is not working fine"
    ::= { bbuEntry 29 }
    
memoryModuleFRU                OBJECT-TYPE
    SYNTAX                      DisplayString
    ACCESS                      read-only
    STATUS                      optional
    DESCRIPTION                 "tmm FRU"
    ::= { bbuEntry 30 }

bbumoduleVersion                OBJECT-TYPE
    SYNTAX                      DisplayString
    ACCESS                      read-only
    STATUS                      optional
    DESCRIPTION                 "Battery Firmware Version"
    ::= { bbuEntry 31 }

autoLearnMode                OBJECT-TYPE
    SYNTAX                      DisplayString
    ACCESS                      read-only
    STATUS                      optional
    DESCRIPTION                 "Automatic Learn Mode"
    ::= { bbuEntry 32 }
	
chargingStatus                OBJECT-TYPE
    SYNTAX                      DisplayString
    ACCESS                      read-only
    STATUS                      optional
    DESCRIPTION                 "Charging Status"
    ::= { bbuEntry 33 }
	
capacitance                OBJECT-TYPE
    SYNTAX                      INTEGER
    ACCESS                      read-only
    STATUS                      optional
    DESCRIPTION                 "Capacitance"
    ::= { bbuEntry 34 }


-- starts adapterStatusSupportInfoTable -------------------------

adapterStatusSupportInfoTable                    OBJECT-TYPE
    SYNTAX                      SEQUENCE OF AdapterStatusSupportInfoEntry
    ACCESS                      not-accessible
    STATUS                      optional
    DESCRIPTION                 "A List of adapter Entries containing Information/Properties about the adapters on the Controller."
    ::= { adapter 9 }

    adapterStatusSupportInfoEntry                OBJECT-TYPE
    SYNTAX                      AdapterStatusSupportInfoEntry
    ACCESS                      not-accessible
    STATUS                      mandatory
    DESCRIPTION                 "An Entry in the adapter table."
    INDEX                       { adapterID-ASSIT }
    ::= { adapterStatusSupportInfoTable 1 }

    AdapterStatusSupportInfoEntry ::=
        SEQUENCE {
            adapterID-ASSIT            INTEGER,
            lockKeyAssigned     INTEGER,
            lockKeyFailed       INTEGER,
            lockKeyNotBackedup  INTEGER,
            biosNotDetected     INTEGER,
            cacheIsPinned       INTEGER               

     }


adapterID-ASSIT                       OBJECT-TYPE
    SYNTAX                      INTEGER
    ACCESS                      read-only
    STATUS                      optional
    DESCRIPTION                 "AdapterID for this Adapter.(Unique)"
    ::= { adapterStatusSupportInfoEntry 1 }

lockKeyAssigned                OBJECT-TYPE
    SYNTAX                      INTEGER
    ACCESS                      read-only
    STATUS                      optional
    DESCRIPTION                 "Lock key Assigned support for this Adapter. Values: false(0),true(1)"
    ::= { adapterStatusSupportInfoEntry 2 }


lockKeyFailed                OBJECT-TYPE
    SYNTAX                      INTEGER
    ACCESS                      read-only
    STATUS                      optional
    DESCRIPTION                 "lock Key Failed support for this Adapter. Values: false(0),true(1)"
    ::= { adapterStatusSupportInfoEntry 3 }


lockKeyNotBackedup                OBJECT-TYPE
    SYNTAX                      INTEGER
    ACCESS                      read-only
    STATUS                      optional
    DESCRIPTION                 "lock Key Not Backedup support for this Adapter. Values: false(0),true(1)"
    ::= { adapterStatusSupportInfoEntry 4 }


biosNotDetected                OBJECT-TYPE
    SYNTAX                      INTEGER
    ACCESS                      read-only
    STATUS                      optional
    DESCRIPTION                 "bios Not Detected support for this Adapter. Values: false(0),true(1)"
    ::= { adapterStatusSupportInfoEntry 5 }
    
cacheIsPinned                OBJECT-TYPE
    SYNTAX                      INTEGER
    ACCESS                      read-only
    STATUS                      optional
    DESCRIPTION                 " 1=controller cache is pinned for missing or offline LDs"
    ::= { adapterStatusSupportInfoEntry 6 }
    
    
    --cacheIsPinned


-- ends adapterStatusSupportInfoTable


-- starts adapterLdOperationSupportInfoTable 


adapterLdOperationSupportInfoTable                    OBJECT-TYPE
    SYNTAX                      SEQUENCE OF AdapterLdOperationSupportInfoEntry
    ACCESS                      not-accessible
    STATUS                      optional
    DESCRIPTION                 "A List of adapter Entries containing Information/Properties about the adapters on the Controller."
    ::= { adapter 10 }

    adapterLdOperationSupportInfoEntry                OBJECT-TYPE
    SYNTAX                      AdapterLdOperationSupportInfoEntry
    ACCESS                      not-accessible
    STATUS                      mandatory
    DESCRIPTION                 "An Entry in the adapter table."
    INDEX                       { adapterID-ALSIT }
    ::= { adapterLdOperationSupportInfoTable 1 }

    AdapterLdOperationSupportInfoEntry ::=
        SEQUENCE {
            adapterID-ALSIT           INTEGER,
            allowCtrlEncryption     INTEGER   
            

     }


adapterID-ALSIT                       OBJECT-TYPE
    SYNTAX                      INTEGER
    ACCESS                      read-only
    STATUS                      optional
    DESCRIPTION                 "AdapterID for this Adapter.(Unique)"
    ::= { adapterLdOperationSupportInfoEntry 1 }

allowCtrlEncryption                       OBJECT-TYPE
    SYNTAX                      INTEGER
    ACCESS                      read-only
    STATUS                      optional
    DESCRIPTION                 "if it is set (1) supports controller encryption"
    ::= { adapterLdOperationSupportInfoEntry 2 }

-- ends adapterLdOperationSupportInfoTable    
                         

device                          OBJECT IDENTIFIER ::= {megaRAID-SAS 2}

physicalDriveInfo                      OBJECT IDENTIFIER ::= {device 1}
--
-- PD Information group.
commonDeviceInfoTable               OBJECT-TYPE
    SYNTAX                      SEQUENCE OF CommonDeviceInfoEntry
    ACCESS                      not-accessible
    STATUS                      optional
    DESCRIPTION                 "A List of general Physical Disk info"
    ::= { adapter 7 }

    commonDeviceInfoEntry          OBJECT-TYPE
    SYNTAX                      CommonDeviceInfoEntry
    ACCESS                      not-accessible
    STATUS                      mandatory
    DESCRIPTION                 "An Entry in the CommonDeviceInfo table."
    INDEX                       { adapterID }
    ::= { commonDeviceInfoTable 1 }

    CommonDeviceInfoEntry ::=
        SEQUENCE {
        adapterID-CDIT               INTEGER,
        forceOnline               INTEGER,
        forceOffline             INTEGER,
        forceRebuild      INTEGER,
        supportsSAS              INTEGER,
        supportsSATA       INTEGER,
        allowMixInEnclosure            INTEGER,
	allowMixInVD       INTEGER,
	allowSataInCluster  INTEGER,
	setPowerStateForCfg INTEGER

    }

-----------
adapterID-CDIT                     OBJECT-TYPE
    SYNTAX                      INTEGER
    ACCESS                      read-only
    STATUS                      mandatory
    DESCRIPTION                 "Unique adapter ID"
    ::= { commonDeviceInfoEntry 1 }

forceOnline                     OBJECT-TYPE
    SYNTAX                      INTEGER
    ACCESS                      read-only
    STATUS                      mandatory
    DESCRIPTION                 "Physical drive force Online operation support. Values: notSupported(0), supported(1)"
    ::= { commonDeviceInfoEntry 2 }

forceOffline                 OBJECT-TYPE
    SYNTAX                      INTEGER
    ACCESS                      read-only
    STATUS                      mandatory
    DESCRIPTION                 "Physical drive force Offline operation support. Values: notSupported(0), supported(1)"
    ::= { commonDeviceInfoEntry 3 }

forceRebuild              OBJECT-TYPE
    SYNTAX                      INTEGER
    ACCESS                      read-only
    STATUS                      mandatory
    DESCRIPTION                 "Physical drive force Rebuild operation support. Values: notSupported(0), supported(1)"
    ::= { commonDeviceInfoEntry 4 }
supportsSAS              OBJECT-TYPE
    SYNTAX                      INTEGER
    ACCESS                      read-only
    STATUS                      mandatory
    DESCRIPTION                 "SAS physical drive support. Values: notSupported(0), supported(1)"
    ::= { commonDeviceInfoEntry 5 }
supportsSATA              OBJECT-TYPE
    SYNTAX                      INTEGER
    ACCESS                      read-only
    STATUS                      mandatory
    DESCRIPTION                 "SATA physical drive support. Values: notSupported(0), supported(1)"
    ::= { commonDeviceInfoEntry 6 }
allowMixInEnclosure              OBJECT-TYPE
    SYNTAX                      INTEGER
    ACCESS                      read-only
    STATUS                      mandatory
    DESCRIPTION                 "Mix InEnclosure support. Values: notSupported(0), supported(1)"
    ::= { commonDeviceInfoEntry 7 }
allowMixInVD              OBJECT-TYPE
    SYNTAX                      INTEGER
    ACCESS                      read-only
    STATUS                      mandatory
    DESCRIPTION                 "MixInVIRTUALDRIVE support. Values: notSupported(0), supported(1)"
    ::= { commonDeviceInfoEntry 8 }
allowSataInCluster              OBJECT-TYPE
    SYNTAX                      INTEGER
    ACCESS                      read-only
    STATUS                      mandatory
    DESCRIPTION                 "SataInCluster support. Values: notSupported(0), supported(1)"
    ::= { commonDeviceInfoEntry 9 }

setPowerStateForCfg             OBJECT-TYPE
    SYNTAX                      INTEGER
    ACCESS                      read-only
    STATUS                      mandatory
    DESCRIPTION                 "FW requires application to set power state before configuration changes. Required(1), Not Required(0)"
    ::= { commonDeviceInfoEntry 10 }
    
    

--------------------------------------
pdNumber                        OBJECT-TYPE
    SYNTAX                      Gauge
    ACCESS                      read-only
    STATUS                      mandatory
    DESCRIPTION                 "The present number of rows in the physical drive table."
    ::= { physicalDriveInfo 1 }

physicalDriveTable                    OBJECT-TYPE
    SYNTAX                      SEQUENCE OF PhysicalDriveEntry
    ACCESS                      not-accessible
    STATUS                      optional
    DESCRIPTION                 "A List of physical drive Entries containing Information/Properties about the drives"
    ::= { physicalDriveInfo 2 }

physicalDriveEntry                     OBJECT-TYPE
        SYNTAX                  PhysicalDriveEntry
        ACCESS                  not-accessible
        STATUS                  optional
        DESCRIPTION             "An Entry in the Device Table."
        INDEX                   { physDevID  }
    ::= { physicalDriveTable 1 }

    PhysicalDriveEntry ::=
        SEQUENCE {
		    pdIndex           INTEGER,
            physDevID           INTEGER,
--            physDevSeq           INTEGER,
            oemSupported       INTEGER,	    
            scsiDevType            INTEGER,
            connectedAdapterPort       DisplayString,
            deviceSpeed                 INTEGER,
            mediaErrCount                 INTEGER,
            otherErrCount                 INTEGER,
            predFailCount                 INTEGER,
            pdState                 INTEGER,
            disabledForRemoval                 INTEGER,
            linkSpeed                 INTEGER,
            pdSupportFlags                 DisplayString,
            sasAddr                 DisplayString,
            rawSize                 INTEGER,
            nonCoercedSize                 INTEGER,
            coercedSize                 INTEGER,
            enclDeviceId                 INTEGER,
            enclIndex                 INTEGER,
            slotNumber                 INTEGER,
            operationProgress            DisplayString,
            adpID-PDT                      INTEGER,
            operationSupport                DisplayString,
            pdVendorID                DisplayString,
            pdProductID                DisplayString,
	    pdFwversion		DisplayString,
            diskType             INTEGER,
			partnerDevId  INTEGER,
			mediatype INTEGER,
    	    powerState INTEGER,
			secured        INTEGER,
			locked          INTEGER,
			foreign         INTEGER,
			oemCertified       INTEGER,
			foreignImportNotAllowed       INTEGER,
            pdTemperature			INTEGER,
            pdSerialNumber		DisplayString,
		piEligible		INTEGER,
		piType			INTEGER,
		piFormatted		INTEGER,
		userDataBlockSize       INTEGER,
		commissionedSpare	DisplayString,
		emergencySpare		DisplayString,
		shieldCounter		INTEGER,
		shieldDiagCompletionTime 	DisplayString,
		ineligibleForSSCD	INTEGER,
		ineligibleForLd		INTEGER,
		serviceable		INTEGER
        }

-- defines for each attribute in PhysicaldriveEntry
pdIndex                       OBJECT-TYPE
    SYNTAX                      INTEGER
    ACCESS                      read-only
    STATUS                      optional
    DESCRIPTION                 "The unique ID"
    ::= { physicalDriveEntry 1 }

physDevID                       OBJECT-TYPE
    SYNTAX                      INTEGER
    ACCESS                      read-only
    STATUS                      optional
    DESCRIPTION                 "The Device ID"
    ::= { physicalDriveEntry 2 }

oemSupported                   OBJECT-TYPE
    SYNTAX                      INTEGER
    ACCESS                      read-only
    STATUS                      optional
    DESCRIPTION                 "Is the drive supported by the OEM (OEM-specific checks). Values: notSupported(1), supported(0)"
    ::= { physicalDriveEntry 3 }

scsiDevType                        OBJECT-TYPE
    SYNTAX                      INTEGER
    ACCESS                      read-only
    STATUS                      optional
    DESCRIPTION                 "Type of this Device.
Values: disk(0),tape(1),printer(2),processor(3),cdrom(5),scanner(6),optical(7),enclosure(13),dvd(10),unknown(31)"
    ::= { physicalDriveEntry 4 }

connectedAdapterPort                             OBJECT-TYPE
    SYNTAX                      DisplayString
    ACCESS                      read-only
    STATUS                      optional
    DESCRIPTION                 "Adapter port(s) to which the device is connected."
    ::= { physicalDriveEntry 5 }

deviceSpeed                     OBJECT-TYPE
    SYNTAX                      INTEGER
    ACCESS                      read-only
    STATUS                      optional
    DESCRIPTION                 "Maximum supported speed. Values: speed-unknown(0),speed-1p5G(1),speed-3G(2),speed-6G(3)"
    ::= { physicalDriveEntry 6 }
mediaErrCount                   OBJECT-TYPE
    SYNTAX                      INTEGER
    ACCESS                      read-only
    STATUS                      optional
    DESCRIPTION                 "Error count of the device"
    ::= { physicalDriveEntry 7 }
otherErrCount                             OBJECT-TYPE
    SYNTAX                      INTEGER
    ACCESS                      read-only
    STATUS                      optional
    DESCRIPTION                 "Other error count of the device"
    ::= { physicalDriveEntry 8 }
predFailCount                             OBJECT-TYPE
    SYNTAX                      INTEGER
    ACCESS                      read-only
    STATUS                      optional
    DESCRIPTION                 "Predictive fail count of the device"
    ::= { physicalDriveEntry 9 }
pdState                             OBJECT-TYPE
    SYNTAX                      INTEGER
    ACCESS                      read-only
    STATUS                      optional
    DESCRIPTION                 "Firmware's interpretation of drive state.
Values: unconfigured-good(0),unconfigured-bad(1),hot-spare(2),offline(16),failed(17),rebuild(20),online(24),copyback(32),system(64),UNCONFIGURED-SHIELDED(128),HOTSPARE-SHIELDED(130),CONFIGURED-SHIELDED(144)"
    ::= { physicalDriveEntry 10 }
disabledForRemoval              OBJECT-TYPE
    SYNTAX                      INTEGER
    ACCESS                      read-only
    STATUS                      optional
    DESCRIPTION                 "If true, drive is ready for removal. Values: false(0),true(1)"
    ::= { physicalDriveEntry 11 }
linkSpeed                             OBJECT-TYPE
    SYNTAX                      INTEGER
    ACCESS                      read-only
    STATUS                      optional
    DESCRIPTION                 "Negotiated link speed. Values: speed-unknown(0),speed-1p5G(1),speed-3G(2),speed-6G(3)"
    ::= { physicalDriveEntry 12 }
pdSupportFlags                   OBJECT-TYPE
    SYNTAX                      DisplayString
    ACCESS                      read-only
    STATUS                      optional
    DESCRIPTION                 "1st Byte:forcedPDGUID(0/1),2nd Byte:inVD(0/1),3rd Byte:isGlobalSpare(0/1),4th Byte:isSpare(0/1),5th Byte:isForeign(0/1),6th Byte:intf(0-Unknown, 1-parallel SCSI, 2-SAS, 3-SATA, 4-FC).A comma delimited list will appear."
    ::= { physicalDriveEntry 13 }
sasAddr                             OBJECT-TYPE
    SYNTAX                      DisplayString
    ACCESS                      read-only
    STATUS                      optional
    DESCRIPTION                 "Device SAS addresses. Comma separeted for multiple address"
    ::= { physicalDriveEntry 14 }
rawSize                             OBJECT-TYPE
    SYNTAX                      INTEGER
    ACCESS                      read-only
    STATUS                      optional
    DESCRIPTION                 "Size(MB) before COD and coercion"
    ::= { physicalDriveEntry 15 }
nonCoercedSize                             OBJECT-TYPE
    SYNTAX                      INTEGER
    ACCESS                      read-only
    STATUS                      optional
    DESCRIPTION                 "Size(MB) after COD is reserved but before coercion"
    ::= { physicalDriveEntry 16 }
coercedSize                             OBJECT-TYPE
    SYNTAX                      INTEGER
    ACCESS                      read-only
    STATUS                      optional
    DESCRIPTION                 "Size(MB) after COD is reserved and after coercion"
    ::= { physicalDriveEntry 17 }
enclDeviceId                             OBJECT-TYPE
    SYNTAX                      INTEGER
    ACCESS                      read-only
    STATUS                      optional
    DESCRIPTION                 "Enclosure's device Id (in decimal); if device is not within enclosure value is -1"
    ::= { physicalDriveEntry 18 }
enclIndex                             OBJECT-TYPE
    SYNTAX                      INTEGER
    ACCESS                      read-only
    STATUS                      optional
    DESCRIPTION                 "Firmware internal enclosure index"
    ::= { physicalDriveEntry 19 }
slotNumber                             OBJECT-TYPE
    SYNTAX                      INTEGER(0..255)
    ACCESS                      read-only
    STATUS                      optional
    DESCRIPTION                 "Slot number of this drive, if the Physical Disk is part of an enclosure then -1"
    ::= { physicalDriveEntry 20 }
operationProgress                             OBJECT-TYPE
    SYNTAX                      DisplayString
    ACCESS                      read-only
    STATUS                      optional
    DESCRIPTION                 "Operation progress in %. e.g. Rebuild progress is 10%"
    ::= { physicalDriveEntry 21 }
adpID-PDT                             OBJECT-TYPE
    SYNTAX                      INTEGER
    ACCESS                      read-only
    STATUS                      optional
    DESCRIPTION                 "Controller id where this Physical Drive is attached"
    ::= { physicalDriveEntry 22 }
operationSupport                             OBJECT-TYPE
    SYNTAX                      DisplayString
    ACCESS                      read-only
    STATUS                      optional
    DESCRIPTION                 "
MakeOnline,MakeOffline,MakeFailed,MakeBad,MakeUncofigured,
MakeSpare,RemoveSpare,replaceMissing,markMissing,startRebuild,
stopRebuild,locate,pdclear,foreignImportNotAllowed,ForeignImportAllowed,
startCopyBack,stopCopyBack,fwDownloadNotAllowed,fwDownloadAllowed,makeSystem"
    ::= { physicalDriveEntry 23 }
pdVendorID                             OBJECT-TYPE
    SYNTAX                      DisplayString
    ACCESS                      read-only
    STATUS                      optional
    DESCRIPTION                 "Vendor ID"
    ::= { physicalDriveEntry 24 }
pdProductID                             OBJECT-TYPE
    SYNTAX                      DisplayString
    ACCESS                      read-only
    STATUS                      optional
    DESCRIPTION                 "Product ID"
    ::= { physicalDriveEntry 25 }

pdFwversion			OBJECT-TYPE
    SYNTAX			DisplayString
    ACCESS			read-only
    STATUS			optional
    DESCRIPTION			"PD firmware version"
    ::= { physicalDriveEntry 26}

diskType                        OBJECT-TYPE
    SYNTAX                      INTEGER
    ACCESS                      read-only
    STATUS                      optional
    DESCRIPTION                 "Type of the disk : 0-Unknown, 1-parallel SCSI, 2-SAS, 3-SATA, 4-FC"
    ::= { physicalDriveEntry 27 }

partnerDevId                    OBJECT-TYPE
    SYNTAX                      INTEGER
    ACCESS                      read-only
    STATUS                      optional
    DESCRIPTION                 "If drive is in an enclosure with dual paths,This is Partner Device ID.				 
                                 In all other cases INVALID(-1)"
    ::= { physicalDriveEntry 28 }
    
mediatype                    OBJECT-TYPE
    SYNTAX                      INTEGER
    ACCESS                      read-only
    STATUS                      optional
    DESCRIPTION                 "Media Type HDD(0),SSD(1),Solid state flash module(2)"
    ::= { physicalDriveEntry 29 }

powerState                    OBJECT-TYPE
    SYNTAX                      INTEGER
    ACCESS                      read-only
    STATUS                      optional
    DESCRIPTION                 "Power condition of the device. Values are device is active(0),device is stopped(1),device is transitioning between power states(255)"
    ::= { physicalDriveEntry 30 }

    
secured                    OBJECT-TYPE
    SYNTAX                      INTEGER
    ACCESS                      read-only
    STATUS                      optional
    DESCRIPTION                 "1=drive is secured, 0=not secured"
    ::= { physicalDriveEntry 31 }

locked                    OBJECT-TYPE
    SYNTAX                      INTEGER
    ACCESS                      read-only
    STATUS                      optional
    DESCRIPTION                 "1=drive is locked, 0=unlocked"
    ::= { physicalDriveEntry 32 }

foreign                    OBJECT-TYPE
    SYNTAX                      INTEGER
    ACCESS                      read-only
    STATUS                      optional
    DESCRIPTION                 "1=drive is secured by a foreign lock key, 0=drive is not secured by a foreign lock key"
    ::= { physicalDriveEntry 33 }

oemCertified                   OBJECT-TYPE
    SYNTAX                      INTEGER
    ACCESS                      read-only
    STATUS                      optional
    DESCRIPTION                 "Is the drive certified by the OEM (OEM-specific checks). Values: notCertified(1), Certified(0)"
    ::= { physicalDriveEntry 34 }

foreignImportNotAllowed        OBJECT-TYPE
    SYNTAX                      INTEGER
    ACCESS                      read-only
    STATUS                      optional
    DESCRIPTION                 "1=Drive is not allowed foreignImport operation, 0=Drive is allowed foreignImport operation"
    ::= { physicalDriveEntry 35 }
    
pdTemperature                  OBJECT-TYPE
    SYNTAX                      INTEGER
    ACCESS                      read-only
    STATUS                      optional
    DESCRIPTION                 "Physical Drive temperature in Celsius"
    ::= { physicalDriveEntry 36 }
    
pdSerialNumber                 OBJECT-TYPE
    SYNTAX                      DisplayString
    ACCESS                      read-only
    STATUS                      optional
    DESCRIPTION                 "Physical Drives serial number"
    ::= { physicalDriveEntry 37}

piEligible                  OBJECT-TYPE
    SYNTAX                      INTEGER
    ACCESS                      read-only
    STATUS                      optional
    DESCRIPTION                 "Protection Information eligibility.1=drive can be used for PD Enabled LD , 0=drive can't  be used for PD Enabled LD "
    ::= { physicalDriveEntry 38 }

piType                  OBJECT-TYPE
    SYNTAX                      INTEGER
    ACCESS                      read-only
    STATUS                      optional
    DESCRIPTION                 "SAS Protection Information Type .No SAS protection type used(0) ,SAS PI Type 1(1) ,SAS PI Type 2(2) ,SAS PI Type 3(3) ,Reserved SAS PI Type 4(4) ,Reserved SAS PI Type 5(5) ,Reserved SAS PI Type 6(6) ,Reserved SAS PI Type 7(7)."
    ::= { physicalDriveEntry 39 }

piFormatted                 OBJECT-TYPE
    SYNTAX                      INTEGER
    ACCESS                      read-only
    STATUS                      optional
    DESCRIPTION                 "formatted for PI information. 1=drive is formatted for PI information, 0=no PI data."
    ::= { physicalDriveEntry 40 }

userDataBlockSize                 OBJECT-TYPE
    SYNTAX                      INTEGER
    ACCESS                      read-only
    STATUS                      optional
    DESCRIPTION                 "Number of bytes of user data in LBA"
    ::= { physicalDriveEntry 41 }

commissionedSpare                 OBJECT-TYPE
    SYNTAX                      DisplayString
    ACCESS                      read-only
    STATUS                      optional
    DESCRIPTION                 "Yes = this PD is a commissioned spare, No = this PD is not a commissioned spare."
    ::= { physicalDriveEntry 42}

emergencySpare                 OBJECT-TYPE
    SYNTAX                      DisplayString
    ACCESS                      read-only
    STATUS                      optional
    DESCRIPTION                 "Eligible = this PD is a emergency spare, Ineligible = this PD is not a emergency spare."
    ::= { physicalDriveEntry 43}

shieldCounter                 OBJECT-TYPE
    SYNTAX                      INTEGER
    ACCESS                      read-only
    STATUS                      optional
    DESCRIPTION                 "How many times the shield diagnostics was run before it was marked failed"
    ::= { physicalDriveEntry 44}

shieldDiagCompletionTime                 OBJECT-TYPE
    SYNTAX                      DisplayString
    ACCESS                      read-only
    STATUS                      optional
    DESCRIPTION                 "Last successful Diagnostics completion time. 0 is N/A"
    ::= { physicalDriveEntry 45}

ineligibleForSSCD               OBJECT-TYPE
    SYNTAX                      INTEGER
    ACCESS                      read-only
    STATUS                      optional
    DESCRIPTION                 "Whether PD cannot be used for an SSCD. PD can not be used for an SSCD(1), PD can be used for an SSCD(0)"
    ::= { physicalDriveEntry 46}

ineligibleForLd                 OBJECT-TYPE
    SYNTAX                      INTEGER
    ACCESS                      read-only
    STATUS                      optional
    DESCRIPTION                 "Whether PD cannot be used for a regular LD. PD can not be used for a regular LD(1), PD can be used for a regular LD(0)"
    ::= { physicalDriveEntry 47}

serviceable	                OBJECT-TYPE
    SYNTAX                      INTEGER
    ACCESS                      read-only
    STATUS                      optional
    DESCRIPTION                 "Whether PD is removeable for service. PD is removeable for service(1), PD is not removeable for service(0)"
    ::= { physicalDriveEntry 48}


--Virtual Devices
virtualDevice                   OBJECT IDENTIFIER ::= {megaRAID-SAS 3}
    
commonVirtualDeviceInfoTable               OBJECT-TYPE
    SYNTAX                      SEQUENCE OF CommonVirtualDeviceInfoEntry
    ACCESS                      not-accessible
    STATUS                      optional
    DESCRIPTION                 "A List of general Virtual Drive info"
    ::= { adapter 8 }

    commonVirtualDeviceInfoEntry          OBJECT-TYPE
    SYNTAX                      CommonVirtualDeviceInfoEntry
    ACCESS                      not-accessible
    STATUS                      mandatory
    DESCRIPTION                 "An Entry in the CommonVirtualDeviceInfo table."
    INDEX                       { adapterID }
    ::= { commonVirtualDeviceInfoTable 1 }


    CommonVirtualDeviceInfoEntry ::=
        SEQUENCE {
        adapterID-CVDIT               INTEGER,
        supportedReadPolicy               INTEGER,
        supportedWritePolicy             INTEGER,
        supportedIOPolicy      INTEGER,
        supportedAccessPolicy              INTEGER,
        supportedMinSize       INTEGER,
        supportedMaxSize            INTEGER,
		ldbbm			INTEGER 

    }

adapterID-CVDIT                     OBJECT-TYPE
    SYNTAX                      INTEGER
    ACCESS                      read-only
    STATUS                      mandatory
    DESCRIPTION                 "Unique adapter ID"
    ::= { commonVirtualDeviceInfoEntry 1 }
    

supportedReadPolicy                     OBJECT-TYPE
    SYNTAX                      INTEGER
    ACCESS                      read-only
    STATUS                      mandatory
    DESCRIPTION                 "Read policy support. Values: false(0),true(1)"
    ::= { commonVirtualDeviceInfoEntry 2 }

supportedWritePolicy                 OBJECT-TYPE
    SYNTAX                      INTEGER
    ACCESS                      read-only
    STATUS                      mandatory
    DESCRIPTION                 "Write policy support. Values: false(0),true(1)"
    ::= { commonVirtualDeviceInfoEntry 3 }

supportedIOPolicy              OBJECT-TYPE
    SYNTAX                      INTEGER
    ACCESS                      read-only
    STATUS                      mandatory
    DESCRIPTION                 "IO policy support. Values: false(0),true(1)"
    ::= { commonVirtualDeviceInfoEntry 4 }
supportedAccessPolicy              OBJECT-TYPE
    SYNTAX                      INTEGER
    ACCESS                      read-only
    STATUS                      mandatory
    DESCRIPTION                 "Access policy support. Values: false(0),true(1)"
    ::= { commonVirtualDeviceInfoEntry 5 }


supportedMinSize                     OBJECT-TYPE
    SYNTAX                      INTEGER
    ACCESS                      read-only
    STATUS                      mandatory
    DESCRIPTION                 "Minimum stripe size supported. 0(512B),1(1K),2(2K),3(4K),4(8K),5(16K),6(32),7(64K),8(128K) ... 11(1MB) etc"
    ::= { commonVirtualDeviceInfoEntry 6 }

supportedMaxSize                 OBJECT-TYPE
    SYNTAX                      INTEGER
    ACCESS                      read-only
    STATUS                      mandatory
    DESCRIPTION                 "Maximum stripe size supported. 0(512B),1(1K),2(2K),3(4K),4(8K),5(16K),6(32),7(64K),8(128K) ... 11(1MB) etc"
    ::= { commonVirtualDeviceInfoEntry 7 }

ldbbm				 OBJECT-TYPE
    SYNTAX                      INTEGER
    ACCESS                      read-only
    STATUS                      mandatory
    DESCRIPTION                 "1=LD bad block management is enabled, 0=LD bad block management is not enabled"
    ::= { commonVirtualDeviceInfoEntry 8 }

vdInfo                     OBJECT IDENTIFIER ::= {virtualDevice 1}

vdNumbers                        OBJECT-TYPE
    SYNTAX                      Gauge
    ACCESS                      read-only
    STATUS                      mandatory
    DESCRIPTION                 "The present number of rows in the virtualDrive table."
    ::= { vdInfo 1 }

virtualDriveTable                    OBJECT-TYPE
    SYNTAX                      SEQUENCE OF VirtualDriveEntry
    ACCESS                      not-accessible
    STATUS                      optional
    DESCRIPTION                 "A List of Virtual Drives Entries containing Information/Properties about the virtualDrive."
    ::= { vdInfo 2 }

virtualDriveEntry                     OBJECT-TYPE
        SYNTAX                  VirtualDriveEntry
        ACCESS                  not-accessible
        STATUS                  optional
        DESCRIPTION             "An Entry in the virtualDrive Table."
        INDEX                   { virtualDevID  }
    ::= { virtualDriveTable 1 }

    VirtualDriveEntry ::=
        SEQUENCE {
            virtualDevID           INTEGER,
            size       INTEGER,
            clusterOwnerDeviceId       INTEGER,
            targetId       INTEGER,
            state       INTEGER,
            name       DisplayString,
            defaultCachePolicy       DisplayString,
            accessPolicy       INTEGER,
            diskCachePolicy       INTEGER,
            bgiState       INTEGER,
            prl       INTEGER,
            rLQ       INTEGER,
            sRL       INTEGER,
            stripeSize       INTEGER,
            numDrives       INTEGER,
            spanDepth       INTEGER,
            initState       INTEGER,
            vdOperationProgress       DisplayString,
            currentCachePolicy     DisplayString,
            adapterID-VDT       INTEGER,
            encryptionType      INTEGER,
            vdOperationSupport    DisplayString,
	      badBlocksExist	INTEGER, 
	   
	    defaultPSPolicy 	INTEGER,
	    currentPSPolicy 	INTEGER,
	    breakMirror 	INTEGER,
	    joinMirror	 	INTEGER,
	    mirrorPdInfo	DisplayString,
	    vdPiType		INTEGER,	
	    mirrorDataSize   INTEGER,
	    cacheCadeType		INTEGER,
	    currentWritePolicy		DisplayString,
	    defaultWritePolicy		DisplayString,
            associatedVD		DisplayString,
			hostAccessPolicy       DisplayString,
			guid                DisplayString,
	    fastPathWBEnabled  		INTEGER,
			peerHasNoAccess		DisplayString
	    		 
        }
        
-- defines for each attribute in PhysicaldriveEntry

virtualDevID                       OBJECT-TYPE
    SYNTAX                      INTEGER
    ACCESS                      read-only
    STATUS                      optional
    DESCRIPTION                 "The unique Virtual Drives ID"
    ::= { virtualDriveEntry 1 }
size                       OBJECT-TYPE
    SYNTAX                      INTEGER
    ACCESS                      read-only
    STATUS                      optional
    DESCRIPTION                 "Total size in MB of the drive"
    ::= { virtualDriveEntry 2 }
clusterOwnerDeviceId                       OBJECT-TYPE
    SYNTAX                      INTEGER
    ACCESS                      read-only
    STATUS                      optional
    DESCRIPTION                 "VD owner's device Id"
    ::= { virtualDriveEntry 3 }
targetId                       OBJECT-TYPE
    SYNTAX                      INTEGER
    ACCESS                      read-only
    STATUS                      optional
    DESCRIPTION                 "Virtual Drive target id (i.e. 0 to 63)"
    ::= { virtualDriveEntry 4 }
state                       OBJECT-TYPE
    SYNTAX                      INTEGER
    ACCESS                      read-only
    STATUS                      optional
    DESCRIPTION                 "The Device state: Values: offline(0),partially-degraded(1),degraded(2),optimal(3)"
    ::= { virtualDriveEntry 5 }
name                       OBJECT-TYPE
    SYNTAX                      DisplayString
    ACCESS                      read-only
    STATUS                      optional
    DESCRIPTION                 "Virtual Drive name"
    ::= { virtualDriveEntry 6 }
defaultCachePolicy              OBJECT-TYPE
    SYNTAX                      DisplayString
    ACCESS                      read-only
    STATUS                      optional
    DESCRIPTION                  "Default cache policy settings. Values: WriteBack, WriteThrough, ReadAdaptive, ReadAhead, ReadAheadNone, Cached, Direct, Write Cache OK if Bad BBU, No Write Cache if Bad BBU."
    ::= { virtualDriveEntry 7 }
accessPolicy                       OBJECT-TYPE
    SYNTAX                      INTEGER
    ACCESS                      read-only
    STATUS                      optional
    DESCRIPTION                 "Access policy settings. Values: access-rw(0), access-read-only(2), access-blocked(3)"
    ::= { virtualDriveEntry 8 }
diskCachePolicy                       OBJECT-TYPE
    SYNTAX                      INTEGER
    ACCESS                      read-only
    STATUS                      optional
    DESCRIPTION                 "Physical disk cache policy. Values: unchanged(0),enable(1),disable(2)"
    ::= { virtualDriveEntry 9 }
bgiState                       OBJECT-TYPE
    SYNTAX                      INTEGER
    ACCESS                      read-only
    STATUS                      optional
    DESCRIPTION                 "Disable/Enable Back Groung Initialization on this Virtual Drive. Values: disable(1),enable(0)"
    ::= { virtualDriveEntry 10 }
prl                       OBJECT-TYPE
    SYNTAX                      INTEGER
    ACCESS                      read-only
    STATUS                      optional
    DESCRIPTION                 "Primay raid level. Values: 0(RAID-0), 1(RAID-1), 3(RAID-3), 4(RAID-4), 5(RAID-5), 6(RAID-6),15(Single Disk or JBOD), 
				17(RAID-1E), 21(RAID-5E), 31(Concatenation),37(RAID-5EEE)"
    ::= { virtualDriveEntry 11 }
rLQ                       OBJECT-TYPE
    SYNTAX                      INTEGER
    ACCESS                      read-only
    STATUS                      optional
    DESCRIPTION                 "Raid level qualifier"
    ::= { virtualDriveEntry 12 }
sRL                       OBJECT-TYPE
    SYNTAX                      INTEGER
    ACCESS                      read-only
    STATUS                      optional
    DESCRIPTION                 "Secondary raid level. Values: 0(Stripped), 1(Mirrored), 2(Concatenated), 3(Spanned)"
    ::= { virtualDriveEntry 13 }
stripeSize                       OBJECT-TYPE
    SYNTAX                      INTEGER
    ACCESS                      read-only
    STATUS                      optional
    DESCRIPTION                 "Stripe Size. 0(512B),1(1K),2(2K),3(4K),4(8K),5(16K),6(32),7(64K),8(128K) ... 11(1MB) etc"
    ::= { virtualDriveEntry 14 }
numDrives                       OBJECT-TYPE
    SYNTAX                      INTEGER
    ACCESS                      read-only
    STATUS                      optional
    DESCRIPTION                 "Number of drivers per span"
    ::= { virtualDriveEntry 15 }
spanDepth                       OBJECT-TYPE
    SYNTAX                      INTEGER
    ACCESS                      read-only
    STATUS                      optional
    DESCRIPTION                 "Number of spans. If only one array then it is considered as 1 span"
    ::= { virtualDriveEntry 16 }
initState                       OBJECT-TYPE
    SYNTAX                      INTEGER
    ACCESS                      read-only
    STATUS                      optional
    DESCRIPTION                 "0=no init, 1=quick init, 2=full init"
    ::= { virtualDriveEntry 17 }
vdOperationProgress                       OBJECT-TYPE
    SYNTAX                      DisplayString
    ACCESS                      read-only
    STATUS                      optional
    DESCRIPTION                 "Progress % for an operation / No operation in progress"
    ::= { virtualDriveEntry 18 }
currentCachePolicy                       OBJECT-TYPE
    SYNTAX                      DisplayString
    ACCESS                      read-only
    STATUS                      optional
    DESCRIPTION                 "Cache policy settings. Values:WriteBack, WriteThrough, ReadAdaptive, ReadAhead, ReadAheadNone, Cached, Direct, Write Cache OK if Bad BBU, No Write Cache if Bad BBU."
    ::= { virtualDriveEntry 19 } 
adapterID-VDT                       OBJECT-TYPE
    SYNTAX                      INTEGER
    ACCESS                      read-only
    STATUS                      optional
    DESCRIPTION                 "Adapter ID"
    ::= { virtualDriveEntry 20 }     

encryptionType                       OBJECT-TYPE
    SYNTAX                      INTEGER
    ACCESS                      read-only
    STATUS                      optional
    DESCRIPTION                 "logical drive encryption type. Values No Encryption(0), FDE drive encryption(1), Controller-based encryption(2)"
    ::= { virtualDriveEntry 21 }

vdOperationSupport                             OBJECT-TYPE
    SYNTAX                      DisplayString
    ACCESS                      read-only
    STATUS                      optional
    DESCRIPTION                 "startFGI,stopFGI,startCC,stopCC,startRecon,deleteLD"
    ::= { virtualDriveEntry 22 }    

badBlocksExist                  OBJECT-TYPE
    SYNTAX                      INTEGER
    ACCESS                      read-only
    STATUS                      optional
    DESCRIPTION                 "0 = LD bad block table is empty, 1 = LD bad block table is not empty"
    ::= { virtualDriveEntry 23 }


defaultPSPolicy                 OBJECT-TYPE
    SYNTAX                      INTEGER
    ACCESS                      read-only
    STATUS                      optional
    DESCRIPTION                 "Power Savings policy set for this LD.Values:controller default power saving policy=0, AUTO=1, MAX=2, MAX with no cache=6, NONE=255"
    ::= { virtualDriveEntry 24 }
currentPSPolicy                 OBJECT-TYPE
    SYNTAX                      INTEGER
    ACCESS                      read-only
    STATUS                      optional
    DESCRIPTION                 "Power Savings policy set for this LD.Values:controller default power saving policy=0, AUTO=1, MAX=2, MAX with no cache=6, NONE=255"
    ::= { virtualDriveEntry 25 }
    
breakMirror                 	OBJECT-TYPE
    SYNTAX                      INTEGER
    ACCESS                      read-only
    STATUS                      optional
    DESCRIPTION                 "Break Mirror Policy set for this LD.Values:1=break mirror is allowed, 0=break mirror not is allowed"
    ::= { virtualDriveEntry 26 }
joinMirror                 	OBJECT-TYPE
    SYNTAX                      INTEGER
    ACCESS                      read-only
    STATUS                      optional
    DESCRIPTION                 "Join Mirror policy set for this LD.Values:1=join mirror is allowed, 0=join mirror not is allowed"
    ::= { virtualDriveEntry 27 }
    
mirrorPdInfo              	OBJECT-TYPE
    SYNTAX                      DisplayString
    ACCESS                      read-only
    STATUS                      optional
    DESCRIPTION                  "Mirror Info Property give the Information about mirror of PD and PD state respectively."
    ::= { virtualDriveEntry 28 }

vdPiType                 	OBJECT-TYPE
    SYNTAX                      INTEGER
    ACCESS                      read-only
    STATUS                      optional
    DESCRIPTION                 "Information about logical drive protection type . No SAS protection type used(0) ,SAS PI Type 1(1) ,SAS PI Type 2(2) ,SAS PI Type 3(3) ,Reserved SAS PI Type 4(4) ,Reserved SAS PI Type 5(5) ,Reserved SAS PI Type 6(6) ,Reserved SAS PI Type 7(7) ,SAS PI Type 8(8)."
    ::= { virtualDriveEntry 29 }

mirrorDataSize                 	OBJECT-TYPE
    SYNTAX                      INTEGER
    ACCESS                      read-only
    STATUS                      optional
    DESCRIPTION                 "Total Space used for mirrorData or Parity information"
    ::= { virtualDriveEntry 30 }
    
cacheCadeType                 	OBJECT-TYPE
    SYNTAX                      INTEGER
    ACCESS                      read-only
    STATUS                      optional
    DESCRIPTION                 "0= Non-CacheCade VD, 1= CacheCade Type is Read & Write, 2= CacheCade Type is Read only, 3= R1-EC"
    ::= { virtualDriveEntry 31 } 

currentWritePolicy              	OBJECT-TYPE
    SYNTAX                      DisplayString
    ACCESS                      read-only
    STATUS                      optional
    DESCRIPTION                  "Current write policy settings. Values: WriteBack, WriteThrough, AlwaysWriteBack"
    ::= { virtualDriveEntry 32 }

defaultWritePolicy              	OBJECT-TYPE
    SYNTAX                      DisplayString
    ACCESS                      read-only
    STATUS                      optional
    DESCRIPTION                  "Default write policy settings. Values: WriteBack, WriteThrough, AlwaysWriteBack"
    ::= { virtualDriveEntry 33 }

associatedVD              	OBJECT-TYPE
    SYNTAX                      DisplayString
    ACCESS                      read-only
    STATUS                      optional
    DESCRIPTION                  "This property gives the Information about VD is Cached or VD is not cached."
    ::= { virtualDriveEntry 34 }  
	
hostAccessPolicy                   	OBJECT-TYPE
    SYNTAX                      DisplayString
    ACCESS                      read-only
    STATUS                      optional
    DESCRIPTION                 "This property gives the Host Access Policy"
    ::= { virtualDriveEntry 35 }
	
guid                        	OBJECT-TYPE
    SYNTAX                      DisplayString
    ACCESS                      read-only
    STATUS                      optional
    DESCRIPTION                  "This property gives the LD GUID."
    ::= { virtualDriveEntry 36 }

fastPathWBEnabled              	OBJECT-TYPE
    SYNTAX                      INTEGER
    ACCESS                      read-only
    STATUS                      optional
    DESCRIPTION                 "0= FastPathWB disabled, not a Raptor like LD, 1= FastPathWB enabled, Raptor like LD"
    ::= { virtualDriveEntry 37 }

peerHasNoAccess              	OBJECT-TYPE
    SYNTAX                      DisplayString
    ACCESS                      read-only
    STATUS                      optional
    DESCRIPTION                 "Peer can't access this shared ld, not applicable for exclusive LD"
    ::= { virtualDriveEntry 38 }

--VD Span
vdSpanInfoTable                    OBJECT-TYPE
    SYNTAX                      SEQUENCE OF VDSpanInfoEntry
    ACCESS                      not-accessible
    STATUS                      optional
    DESCRIPTION                 "A List of span Entries containing Information/Properties vd span."
    ::= { vdInfo 3 }

vdSpanInfoEntry                     OBJECT-TYPE
        SYNTAX                  VDSpanInfoEntry
        ACCESS                  not-accessible
        STATUS                  optional
        DESCRIPTION             "An Entry in the vdSpan Table."
        INDEX                   { spanID  }
    ::= { vdSpanInfoTable 1 }

    VDSpanInfoEntry ::=
        SEQUENCE {
            spanID              INTEGER,
            vdID-VSIT           INTEGER,
            startBlock           INTEGER,
            numBlocks           DisplayString,
            vdSpanArrayRef           INTEGER,
            adapterID-VSIT		   INTEGER
        }
        
spanID                       OBJECT-TYPE
    SYNTAX                      INTEGER
    ACCESS                      read-only
    STATUS                      optional
    DESCRIPTION                 "The unique Span ID"
    ::= { vdSpanInfoEntry 1 }

vdID-VSIT                       OBJECT-TYPE
    SYNTAX                      INTEGER
    ACCESS                      read-only
    STATUS                      optional
    DESCRIPTION                 "The Virtual Device ID"
    ::= { vdSpanInfoEntry 2 }
startBlock                       OBJECT-TYPE
    SYNTAX                     INTEGER
    ACCESS                      read-only
    STATUS                      optional
    DESCRIPTION                 "Span physical disk starting block"
    ::= { vdSpanInfoEntry 3 }
numBlocks                       OBJECT-TYPE
    SYNTAX                      DisplayString
    ACCESS                      read-only
    STATUS                      optional
    DESCRIPTION                 "Span physical disk block count"
    ::= { vdSpanInfoEntry 4 }
vdSpanArrayRef                       OBJECT-TYPE
    SYNTAX                      INTEGER
    ACCESS                      read-only
    STATUS                      optional
    DESCRIPTION                 "Array reference (index)"
    ::= { vdSpanInfoEntry 5 }  
adapterID-VSIT                       OBJECT-TYPE
    SYNTAX                      INTEGER
    ACCESS                      read-only
    STATUS                      optional
    DESCRIPTION                 "Adapter ID"
    ::= { vdSpanInfoEntry 6 }    
---------------
arrayInfo                     OBJECT IDENTIFIER ::= {virtualDevice 4}

arrayNumber                        OBJECT-TYPE
    SYNTAX                      Gauge
    ACCESS                      read-only
    STATUS                      mandatory
    DESCRIPTION                 "The present number of rows in the array table."
    ::= { arrayInfo 1 }

arrayTable                    OBJECT-TYPE
    SYNTAX                      SEQUENCE OF ArrayEntry
    ACCESS                      not-accessible
    STATUS                      optional
    DESCRIPTION                 "A List of array Entries containing Information/Properties about the arrays."
    ::= { arrayInfo 2 }

arrayEntry                     OBJECT-TYPE
        SYNTAX                  ArrayEntry
        ACCESS                  not-accessible
        STATUS                  optional
        DESCRIPTION             "An Entry in the array Table."
        INDEX                   { arrayID  }
    ::= { arrayTable 1 }

    ArrayEntry ::=
        SEQUENCE {
            arrayID           INTEGER,
            arraySize           INTEGER,
            arrayNumDrives           INTEGER,
            arrayRef           INTEGER,
            pdList         DisplayString,
            adapterID-AT		INTEGER
        }
-- defines for each attribute in PhysicaldriveEntry

arrayID                       OBJECT-TYPE
    SYNTAX                      INTEGER
    ACCESS                      read-only
    STATUS                      optional
    DESCRIPTION                 "The unique array ID"
    ::= { arrayEntry 1 }
arraySize                       OBJECT-TYPE
    SYNTAX                      INTEGER
    ACCESS                      read-only
    STATUS                      optional
    DESCRIPTION                 "Size in MB"
    ::= { arrayEntry 2 }
arrayNumDrives                       OBJECT-TYPE
    SYNTAX                      INTEGER
    ACCESS                      read-only
    STATUS                      optional
    DESCRIPTION                 "Number of drives for this array"
    ::= { arrayEntry 3 }
arrayRef                       OBJECT-TYPE
    SYNTAX                      INTEGER
    ACCESS                      read-only
    STATUS                      optional
    DESCRIPTION                 "Tag for the array"
    ::= { arrayEntry 4 }
pdList                       OBJECT-TYPE
    SYNTAX                      DisplayString
    ACCESS                      read-only
    STATUS                      optional
    DESCRIPTION                 "Space separated Physical Drive identification. e.g. {devID devID devID} etc "
    ::= { arrayEntry 5 }
adapterID-AT                       OBJECT-TYPE
    SYNTAX                      INTEGER
    ACCESS                      read-only
    STATUS                      optional
    DESCRIPTION                 "Adapter ID."
    ::= { arrayEntry 6 }
---------------
spareInfo                     OBJECT IDENTIFIER ::= {virtualDevice 5}

spareDevNumber                        OBJECT-TYPE
    SYNTAX                      Gauge
    ACCESS                      read-only
    STATUS                      mandatory
    DESCRIPTION                 "The present number of rows in the sparepool table."
    ::= { spareInfo 1 }

spareTable                    OBJECT-TYPE
    SYNTAX                      SEQUENCE OF SpareEntry
    ACCESS                      not-accessible
    STATUS                      optional
    DESCRIPTION                 "A List of sparepool Entries containing Information/Properties about the spare drive"
    ::= { spareInfo 2 }

spareEntry                     OBJECT-TYPE
        SYNTAX                  SpareEntry
        ACCESS                  not-accessible
        STATUS                  optional
        DESCRIPTION             "An Entry in the sparepool Table."
        INDEX                   { spareID  }
    ::= { spareTable 1 }

    SpareEntry ::=
        SEQUENCE {
            spareID           INTEGER,
            deviceIdentification           INTEGER,
            spareType           DisplayString,
            arrayCount           INTEGER,
            arrayIDs         DisplayString,
            adapterID-ST		INTEGER
        }
-- defines for each attribute in PhysicaldriveEntry

spareID                       OBJECT-TYPE
    SYNTAX                      INTEGER
    ACCESS                      read-only
    STATUS                      optional
    DESCRIPTION                 "The unique Device ID"
    ::= { spareEntry 1 }
deviceIdentification                       OBJECT-TYPE
    SYNTAX                      INTEGER
    ACCESS                      read-only
    STATUS                      optional
    DESCRIPTION                 "The unique Device ID"
    ::= { spareEntry 2 }
spareType                       OBJECT-TYPE
    SYNTAX                      DisplayString
    ACCESS                      read-only
    STATUS                      optional
    DESCRIPTION                 "Spare type. isDedicated(0/1)isRevertible(0/1)isEnclAffinity(0/1). 1 implies particular feature is enable and 0 represent feature is disable."
    ::= { spareEntry 3 }
arrayCount                       OBJECT-TYPE
    SYNTAX                      INTEGER
    ACCESS                      read-only
    STATUS                      optional
    DESCRIPTION                 "The number of arrays to which the Physical Drive can be dedicated"
    ::= { spareEntry 4 }
arrayIDs                       OBJECT-TYPE
    SYNTAX                      DisplayString
    ACCESS                      read-only
    STATUS                      optional
    DESCRIPTION                 "Comma separated array ids. e.g. 2,4,5 etc "
    ::= { spareEntry 5 } 
adapterID-ST                       OBJECT-TYPE
    SYNTAX                      INTEGER
    ACCESS                      read-only
    STATUS                      optional
    DESCRIPTION                 "Adapter ID."
    ::= { spareEntry 6 }    


-- Enclosure Information.
enclosureInfo                      OBJECT IDENTIFIER ::= {lsiRAIDServer 5}

enclosureNumber                       OBJECT-TYPE
    SYNTAX                      Gauge
    ACCESS                      read-only
    STATUS                      mandatory
    DESCRIPTION                 "The present number of rows in the enclosure table."
    ::= { enclosureInfo 1 }
enclosureTable                    OBJECT-TYPE
    SYNTAX                      SEQUENCE OF EnclosureEntry
    ACCESS                      not-accessible
    STATUS                      optional
    DESCRIPTION                 "A List of Enclosure Entries containing Information/Properties about the enclosures in the system."
    ::= { enclosureInfo 2 }


    enclosureEntry                OBJECT-TYPE
    SYNTAX                      EnclosureEntry
    ACCESS                      not-accessible
    STATUS                      mandatory
    DESCRIPTION                 "An Entry in the enclosure table."
    INDEX                       { enclosureID }
    ::= { enclosureTable 1 }

    EnclosureEntry ::=
        SEQUENCE {
            enclosureID           INTEGER,
            deviceId    INTEGER,
            enclosureIndex         INTEGER,
            slotCount     INTEGER,
            psCount         INTEGER,
            fanCount         INTEGER,
            tempSensorCount         INTEGER,
            alarmCount         INTEGER,
            simCount         INTEGER,
            isFault         INTEGER,
            pdCount         INTEGER,
            pdIds         DisplayString,
            adapterID-ET		INTEGER,
            pdCountSpinup60		INTEGER,
	    enclosureType		INTEGER,
	    enclFirmwareVersion    DisplayString,
	    enclSerialNumber       DisplayString,
	    vendorID			DisplayString,
	    productID			DisplayString,
	    eSMSerialNumber		DisplayString,
	    eSMFRU			DisplayString,
	    enclosureZoningMode		DisplayString,
		eSMFRUPartInfo	DisplayString
    }

-- defines for each attribute in EnclosureEntry

enclosureID                       OBJECT-TYPE
    SYNTAX                      INTEGER
    ACCESS                      read-only
    STATUS                      optional
    DESCRIPTION                 "EnclosureID for this enclosure.(Unique)"
    ::= { enclosureEntry 1 }

deviceId                OBJECT-TYPE
    SYNTAX                      INTEGER
    ACCESS                      read-only
    STATUS                      optional
    DESCRIPTION                 "Enclosure device Id."
    ::= { enclosureEntry 2 }
enclosureIndex                OBJECT-TYPE
    SYNTAX                      INTEGER
    ACCESS                      read-only
    STATUS                      optional
    DESCRIPTION                 "Firmware internal enclosure index"
    ::= { enclosureEntry 3 }
slotCount                OBJECT-TYPE
    SYNTAX                      INTEGER
    ACCESS                      read-only
    STATUS                      optional
    DESCRIPTION                 "Number of slots"
    ::= { enclosureEntry 4 }
psCount                OBJECT-TYPE
    SYNTAX                      INTEGER
    ACCESS                      read-only
    STATUS                      optional
    DESCRIPTION                 "Number of power supplies"
    ::= { enclosureEntry 5 }
fanCount                OBJECT-TYPE
    SYNTAX                      INTEGER
    ACCESS                      read-only
    STATUS                      optional
    DESCRIPTION                 "Number of fans"
    ::= { enclosureEntry 6 }
tempSensorCount                OBJECT-TYPE
    SYNTAX                      INTEGER
    ACCESS                      read-only
    STATUS                      optional
    DESCRIPTION                 "Number of temperature sensors"
    ::= { enclosureEntry 7 }
alarmCount                OBJECT-TYPE
    SYNTAX                      INTEGER
    ACCESS                      read-only
    STATUS                      optional
    DESCRIPTION                 "Number of alarms"
    ::= { enclosureEntry 8 }
simCount                OBJECT-TYPE
    SYNTAX                      INTEGER
    ACCESS                      read-only
    STATUS                      optional
    DESCRIPTION                 "Number of SIM modules"
    ::= { enclosureEntry 9 }
isFault                OBJECT-TYPE
    SYNTAX                      INTEGER
    ACCESS                      read-only
    STATUS                      optional
    DESCRIPTION                 "Enclosure has entered a FAULT state or not. Values: false(0),true(1)"
    ::= { enclosureEntry 10 }
pdCount                OBJECT-TYPE
    SYNTAX                      INTEGER
    ACCESS                      read-only
    STATUS                      optional
    DESCRIPTION                 "Number of physical drives present"
    ::= { enclosureEntry 11 }
pdIds                OBJECT-TYPE
    SYNTAX                      DisplayString
    ACCESS                      read-only
    STATUS                      optional
    DESCRIPTION                 "Physical drive deviceIds space separated."
    ::= { enclosureEntry 12 } 
adapterID-ET                OBJECT-TYPE
    SYNTAX                      INTEGER
    ACCESS                      read-only
    STATUS                      optional
    DESCRIPTION                 "Adapter ID."
    ::= { enclosureEntry 13 } 
    
pdCountSpinup60              OBJECT-TYPE
    SYNTAX                      INTEGER
    ACCESS                      read-only
    STATUS                      optional
    DESCRIPTION                 "Number of drives that can spun up in 60 sec."
    ::= { enclosureEntry 14 } 

enclosureType              OBJECT-TYPE
    SYNTAX                      INTEGER
    ACCESS                      read-only
    STATUS                      optional
    DESCRIPTION                 "Information about type of enclosure : 0= UNKNOWN ,1= SAFTE ,2=SES ,3= SGPIO ,4=OEM specific"
    ::= { enclosureEntry 15 }

enclFirmwareVersion                OBJECT-TYPE
    SYNTAX                      DisplayString
    ACCESS                      read-only
    STATUS                      optional
    DESCRIPTION                 "Information about enclosure FW Version"
    ::= { enclosureEntry 16 }

enclSerialNumber                OBJECT-TYPE
    SYNTAX                      DisplayString
    ACCESS                      read-only
    STATUS                      optional
    DESCRIPTION                 "Enclosure Serial Number"
    ::= { enclosureEntry 17 }

vendorID                OBJECT-TYPE
    SYNTAX                      DisplayString
    ACCESS                      read-only
    STATUS                      optional
    DESCRIPTION                 "Enclosure Vendor ID"
    ::= { enclosureEntry 18 } 

productID                OBJECT-TYPE
    SYNTAX                      DisplayString
    ACCESS                      read-only
    STATUS                      optional
    DESCRIPTION                 "Enclosure Product ID"
    ::= { enclosureEntry 19 }

eSMSerialNumber                OBJECT-TYPE
    SYNTAX                      DisplayString
    ACCESS                      read-only
    STATUS                      optional
    DESCRIPTION                 "IBM Enclosure ESM Serial Number"
    ::= { enclosureEntry 20 }

eSMFRU                OBJECT-TYPE
    SYNTAX                      DisplayString
    ACCESS                      read-only
    STATUS                      optional
    DESCRIPTION                 "Information about IBM Enclosure ESM FRU"
    ::= { enclosureEntry 21 }

enclosureZoningMode             OBJECT-TYPE
    SYNTAX                      DisplayString
    ACCESS                      read-only
    STATUS                      optional
    DESCRIPTION                 "Enclosure IBM Zoning Mode"
    ::= { enclosureEntry 22 }  
	
eSMFRUPartInfo                OBJECT-TYPE
    SYNTAX                      DisplayString
    ACCESS                      read-only
    STATUS                      optional
    DESCRIPTION                 "Information about IBM Enclosure ESM FRU Part"
    ::= { enclosureEntry 23 }
    
----------------------
enclosureFanTable                    OBJECT-TYPE
    SYNTAX                      SEQUENCE OF EnclosureFanEntry
    ACCESS                      not-accessible
    STATUS                      optional
    DESCRIPTION                 "A List of fan Entries containing Information/Properties about the enclosureFan."
    ::= { enclosureInfo 3 }


    enclosureFanEntry                OBJECT-TYPE
    SYNTAX                      EnclosureFanEntry
    ACCESS                      not-accessible
    STATUS                      mandatory
    DESCRIPTION                 "An Entry in the enclosureFan table."
    INDEX                       { fanID }
    ::= { enclosureFanTable 1 }

    EnclosureFanEntry ::=
        SEQUENCE {
            fanID           INTEGER,
            enclosureId    INTEGER,
            fanStatus         INTEGER
    }

-- defines for each attribute in EnclosureEntry

fanID                       OBJECT-TYPE
    SYNTAX                      INTEGER
    ACCESS                      read-only
    STATUS                      optional
    DESCRIPTION                 "ID for this EnclosureFan.(Unique)"
    ::= { enclosureFanEntry 1 }

enclosureId                OBJECT-TYPE
    SYNTAX                      INTEGER
    ACCESS                      read-only
    STATUS                      optional
    DESCRIPTION                 "Enclosure ID where the fan is attached"
    ::= { enclosureFanEntry 2 }
fanStatus                OBJECT-TYPE
    SYNTAX                      INTEGER{
                                status-invalid(1),
                                status-ok(2),
                                status-critical(3),
                                status-nonCritical(4),
                                status-unrecoverable(5),
                                status-not-installed(6),
                                status-unknown(7),
                                status-not-available(8)
                                }
    ACCESS                      read-only
    STATUS                      optional
    DESCRIPTION                 "status of the fan"
    ::= { enclosureFanEntry 3 }

----------------------
enclosureSlotTable                    OBJECT-TYPE
    SYNTAX                      SEQUENCE OF EnclosureSlotEntry
    ACCESS                      not-accessible
    STATUS                      optional
    DESCRIPTION                 "A List of slot Entries containing Information/Properties about the enclosure slots."
    ::= { enclosureInfo 4 }


    enclosureSlotEntry                OBJECT-TYPE
    SYNTAX                      EnclosureSlotEntry
    ACCESS                      not-accessible
    STATUS                      mandatory
    DESCRIPTION                 "An Entry in the enclosureSlot table."
    INDEX                       { slotID }
    ::= { enclosureSlotTable 1 }

    EnclosureSlotEntry ::=
        SEQUENCE {
            slotID           INTEGER,
            enclosureId-EST    INTEGER,
            slotStatus         INTEGER
    }

-- defines for each attribute in EnclosureEntry

slotID                       OBJECT-TYPE
    SYNTAX                      INTEGER
    ACCESS                      read-only
    STATUS                      optional
    DESCRIPTION                 "ID for this slot.(Unique)"
    ::= { enclosureSlotEntry 1 }

enclosureId-EST                OBJECT-TYPE
    SYNTAX                      INTEGER
    ACCESS                      read-only
    STATUS                      optional
    DESCRIPTION                 "enclosure ID"
    ::= { enclosureSlotEntry 2 }
slotStatus                OBJECT-TYPE
    SYNTAX                      INTEGER{
    							status-invalid(1),
                                status-ok(2),
                                status-critical(3),
                                status-nonCritical(4),
                                status-unrecoverable(5),
                                status-not-installed(6),
                                status-unknown(7),
                                status-not-available(8)
                                }
    ACCESS                      read-only
    STATUS                      optional
    DESCRIPTION                 "status of the device"
    ::= { enclosureSlotEntry 3 }
----------------------
enclosurePowerSupplyTable                    OBJECT-TYPE
    SYNTAX                      SEQUENCE OF EnclosurePowerSupplyEntry
    ACCESS                      not-accessible
    STATUS                      optional
    DESCRIPTION                 "A List of powerSupply Entries containing Information/Properties about the enclosure powerSupply"
    ::= { enclosureInfo 5 }


    enclosurePowerSupplyEntry                OBJECT-TYPE
    SYNTAX                      EnclosurePowerSupplyEntry
    ACCESS                      not-accessible
    STATUS                      mandatory
    DESCRIPTION                 "An Entry in the powerSupply table."
    INDEX                       { powerSupplyID }
    ::= { enclosurePowerSupplyTable 1 }

    EnclosurePowerSupplyEntry ::=
        SEQUENCE {
            powerSupplyID           INTEGER,
            enclosureId-EPST    INTEGER,
            powerSupplyStatus         INTEGER
    }

-- defines for each attribute in EnclosureEntry

powerSupplyID                       OBJECT-TYPE
    SYNTAX                      INTEGER
    ACCESS                      read-only
    STATUS                      optional
    DESCRIPTION                 "ID for this powerSupply.(Unique)"
    ::= { enclosurePowerSupplyEntry 1 }

enclosureId-EPST                OBJECT-TYPE
    SYNTAX                      INTEGER
    ACCESS                      read-only
    STATUS                      optional
    DESCRIPTION                 "Enclosure id for the powerSupply"
    ::= { enclosurePowerSupplyEntry 2 }
powerSupplyStatus                OBJECT-TYPE
    SYNTAX                      INTEGER{
    							status-invalid(1),
                                status-ok(2),
                                status-critical(3),
                                status-nonCritical(4),
                                status-unrecoverable(5),
                                status-not-installed(6),
                                status-unknown(7),
                                status-not-available(8)
                                }
    ACCESS                      read-only
    STATUS                      optional
    DESCRIPTION                 "Status of the power Supply"
    ::= { enclosurePowerSupplyEntry 3 }
----------------------
enclosureTempSensorTable              OBJECT-TYPE
    SYNTAX                      SEQUENCE OF EnclosureTempSensorEntry
    ACCESS                      not-accessible
    STATUS                      optional
    DESCRIPTION                 "A List of TempSensor Entries containing Information/Properties about the enclosure TempSensor"
    ::= { enclosureInfo 6 }


    enclosureTempSensorEntry     OBJECT-TYPE
    SYNTAX                      EnclosureTempSensorEntry
    ACCESS                      not-accessible
    STATUS                      mandatory
    DESCRIPTION                 "An Entry in the adapter table."
    INDEX                       { tempSensorID }
    ::= { enclosureTempSensorTable 1 }

    EnclosureTempSensorEntry ::=
        SEQUENCE {
            tempSensorID           INTEGER,
            enclosureId-ETST    INTEGER,
            tempSensorStatus         INTEGER,
            enclosureTemperature         INTEGER
    }

-- defines for each attribute in EnclosureEntry

tempSensorID                       OBJECT-TYPE
    SYNTAX                      INTEGER
    ACCESS                      read-only
    STATUS                      optional
    DESCRIPTION                 "ID for this TempSensor.(Unique)"
    ::= { enclosureTempSensorEntry 1 }

enclosureId-ETST                OBJECT-TYPE
    SYNTAX                      INTEGER
    ACCESS                      read-only
    STATUS                      optional
    DESCRIPTION                 "Enclosure id for this TempSensor"
    ::= { enclosureTempSensorEntry 2 }
tempSensorStatus                OBJECT-TYPE
    SYNTAX                      INTEGER{
    							status-invalid(1),
                                status-ok(2),
                                status-critical(3),
                                status-nonCritical(4),
                                status-unrecoverable(5),
                                status-not-installed(6),
                                status-unknown(7),
                                status-not-available(8)
                                }
    ACCESS                      read-only
    STATUS                      optional
    DESCRIPTION                 "Status of the Temparature Sensor"
    ::= { enclosureTempSensorEntry 3 }
enclosureTemperature                OBJECT-TYPE
    SYNTAX                      INTEGER
    ACCESS                      read-only
    STATUS                      optional
    DESCRIPTION                 "Current temperature in degree Centigrade"
    ::= { enclosureTempSensorEntry 4 }
    
----------------------
enclosureAlarmTable                    OBJECT-TYPE
    SYNTAX                      SEQUENCE OF EnclosureAlarmEntry
    ACCESS                      not-accessible
    STATUS                      optional
    DESCRIPTION                 "A List of Alarm Entries containing Information/Properties about enclosure Alarms"
    ::= { enclosureInfo 7 }


    enclosureAlarmEntry                OBJECT-TYPE
    SYNTAX                      EnclosureAlarmEntry
    ACCESS                      not-accessible
    STATUS                      mandatory
    DESCRIPTION                 "An Entry in the enclosureAlarm table."
    INDEX                       { alarmID }
    ::= { enclosureAlarmTable 1 }

    EnclosureAlarmEntry ::=
        SEQUENCE {
            alarmID           INTEGER,
            enclosureId-EAT     INTEGER,
            alarmStatus         INTEGER
    }

-- defines for each attribute in EnclosureAlarmEntry

alarmID                       OBJECT-TYPE
    SYNTAX                      INTEGER
    ACCESS                      read-only
    STATUS                      optional
    DESCRIPTION                 "ID for this Alarm.(Unique)"
    ::= { enclosureAlarmEntry 1 }

enclosureId-EAT                OBJECT-TYPE
    SYNTAX                      INTEGER
    ACCESS                      read-only
    STATUS                      optional
    DESCRIPTION                 "Enclosure id where the Alarm is attached"
    ::= { enclosureAlarmEntry 2 }
alarmStatus                OBJECT-TYPE
    SYNTAX                      INTEGER{
    							status-invalid(1),
                                status-ok(2),
                                status-critical(3),
                                status-nonCritical(4),
                                status-unrecoverable(5),
                                status-not-installed(6),
                                status-unknown(7),
                                status-not-available(8)
                                }
    ACCESS                      read-only
    STATUS                      optional
    DESCRIPTION                 "Status of the alarm"
    ::= { enclosureAlarmEntry 3 }
----------------------
enclosureSIMTable                    OBJECT-TYPE
    SYNTAX                      SEQUENCE OF EnclosureSIMEntry
    ACCESS                      not-accessible
    STATUS                      optional
    DESCRIPTION                 "A List of SIM Entries containing Information/Properties about enclosure SIMs"
    ::= { enclosureInfo 8 }


    enclosureSIMEntry                OBJECT-TYPE
    SYNTAX                      EnclosureSIMEntry
    ACCESS                      not-accessible
    STATUS                      mandatory
    DESCRIPTION                 "An Entry in the enclosureSIM table."
    INDEX                       { simID }
    ::= { enclosureSIMTable 1 }

    EnclosureSIMEntry ::=
        SEQUENCE {
            simID           INTEGER,
            enclosureId-ESIT     INTEGER,
            simStatus         INTEGER
    }

-- defines for each attribute in EnclosureEntry

simID                       OBJECT-TYPE
    SYNTAX                      INTEGER
    ACCESS                      read-only
    STATUS                      optional
    DESCRIPTION                 "ID for this SIM.(Unique)"
    ::= { enclosureSIMEntry 1 }

enclosureId-ESIT                OBJECT-TYPE
    SYNTAX                      INTEGER
    ACCESS                      read-only
    STATUS                      optional
    DESCRIPTION                 "Inclosure ID where the SIM is attached"
    ::= { enclosureSIMEntry 2 }
simStatus                OBJECT-TYPE
    SYNTAX                      INTEGER{
    							status-invalid(1),
                                status-ok(2),
                                status-critical(3),
                                status-nonCritical(4),
                                status-unrecoverable(5),
                                status-not-installed(6),
                                status-unknown(7),
                                status-not-available(8)
                                }
    ACCESS                      read-only
    STATUS                      optional
    DESCRIPTION                 "Status of the SIM"
    ::= { enclosureSIMEntry 3 }
-------------------------------Traps--------------------------------------------
adapterTraps                      OBJECT IDENTIFIER ::= {lsiRAIDServer 6}

-- Following are the Objects defined for Traps

atAdpNumber                 OBJECT-TYPE
    SYNTAX                      INTEGER
    ACCESS                      read-only
    STATUS                      optional
    DESCRIPTION                 "Adapter ID for which Trap is generated."
    ::= { adapterTraps 1001 }

atAlarmState            OBJECT-TYPE
    SYNTAX                      INTEGER
    ACCESS                      read-only
    STATUS                      optional
    DESCRIPTION                 "Alarm disabled/enabled. Values: disabled(0),enabled(1)"
    ::= { adapterTraps 1002 }

atRate            OBJECT-TYPE
    SYNTAX                      INTEGER
    ACCESS                      read-only
    STATUS                      optional
    DESCRIPTION                 "BGI/Check Consistency/Rebuild/Patrol Read/Reconstruction Rate"
    ::= { adapterTraps 1003 }
atFlashImageName            OBJECT-TYPE
    SYNTAX                      DisplayString
    ACCESS                      read-only
    STATUS                      optional
    DESCRIPTION                 "Flash Image Name"
    ::= { adapterTraps 1004 }
	
atID            OBJECT-TYPE
    SYNTAX                      DisplayString
    ACCESS                      read-only
    STATUS                      optional
    DESCRIPTION                 "ID"
    ::= { adapterTraps 1005 }

clustCtrlpropReset            OBJECT-TYPE
    SYNTAX                      DisplayString
    ACCESS                      read-only
    STATUS                      optional
    DESCRIPTION                 "Resetting controller property"
    ::= { adapterTraps 1006 }	

-- Following are the trap definitions, which use variables defined
-- within the object lsiRaidMib.

adpAlarmStateEnabled TRAP-TYPE
    ENTERPRISE adapterTraps
    VARIABLES 
    { 
    atAdpNumber
    }
    DESCRIPTION "Alarm has been enabled by user for Adapter $1"
	--#TYPE "LSI SAS Trap: Alarm Enabled"
	--#SUMMARY "Alarm has been enabled by user for Adapter %d"
	--#ARGUMENTS {0}
	--#SEVERITY INFORMATIONAL
	--#GENERIC 6
	--#CATEGORY "Error Events"
	--#STATE OPERATIONAL    
    ::= 8001

adpBGIRateChanged TRAP-TYPE
    ENTERPRISE adapterTraps
    VARIABLES
        {
        atRate,
        atAdpNumber
        }
    DESCRIPTION "Background initialization rate changed to $1 for Adapter $2" 
    --#TYPE "LSI SAS Trap: Background Initialization Rate Changed"
	--#SUMMARY "Background Initialization Rate changed to %d for Adapter %d"
	--#ARGUMENTS {0,1}
	--#SEVERITY INFORMATIONAL
	--#GENERIC 6
	--#CATEGORY "Error Events"
	--#STATE OPERATIONAL 
    ::= 8002
adpCacheDiscarded TRAP-TYPE
    ENTERPRISE adapterTraps
    VARIABLES
        {
        atAdpNumber
        }
    DESCRIPTION "Controller $1 cache discarded due to memory/battery problems"
    --#TYPE "LSI SAS Trap: Controller Cache Discarded"
	--#SUMMARY "Controller %d cache discarded due to memory/battery problems"
	--#ARGUMENTS {0}
	--#SEVERITY FATAL
	--#GENERIC 6
	--#CATEGORY "Error Events"
	--#STATE OPERATIONAL 
    ::= 8003
adpCacheRebootCantRecover TRAP-TYPE
    ENTERPRISE adapterTraps
    VARIABLES
        {
        atAdpNumber
        }
    DESCRIPTION "Unable to recover cache data due to configuration mismatch for Adapter $1"
    --#TYPE "LSI SAS Trap: Unable to Recover Cache data"
	--#SUMMARY "Unable to recover Cache Data due to configuration mismatch for Adapter %d"
	--#ARGUMENTS {0}
	--#SEVERITY FATAL
	--#GENERIC 6
	--#CATEGORY "Error Events"
	--#STATE OPERATIONAL 
    ::= 8004
adpCacheRebootRecover TRAP-TYPE
    ENTERPRISE adapterTraps
    VARIABLES
        {
        atAdpNumber
        }
    DESCRIPTION "Cache data recovered successfully for Adapter $1" 
    --#TYPE "LSI SAS Trap:Cache Recovered"
	--#SUMMARY "Cache Data Recovered for Adapter %d"
	--#ARGUMENTS {0}
	--#SEVERITY INFORMATIONAL
	--#GENERIC 6
	--#CATEGORY "Error Events"
	--#STATE OPERATIONAL 
    ::= 8005
adpCacheVersionMismatch TRAP-TYPE
    ENTERPRISE adapterTraps
    VARIABLES
        {
        atAdpNumber
        }
    DESCRIPTION "Controller cache discarded due to firmware version incompatibility for Adapter $1"
    --#TYPE "LSI SAS Trap: Controller Cache Discarded"
	--#SUMMARY "Controller Cache Discarded due to Firmware version incompatibility for Adapter %d"
	--#ARGUMENTS {0}
	--#SEVERITY FATAL
	--#GENERIC 6
	--#CATEGORY "Error Events"
	--#STATE OPERATIONAL 
    ::= 8006

adpCCRateChanged TRAP-TYPE
    ENTERPRISE adapterTraps
    VARIABLES
        {
        atRate,
        atAdpNumber
        }
    DESCRIPTION "Consistency Check rate changed to $1 for Adapter $2" 
    --#TYPE "LSI SAS Trap: Consistency Check Rate changed"
	--#SUMMARY "Consistency Check Rate changed to %d for Adapter %d"
	--#ARGUMENTS {0,1}
	--#SEVERITY INFORMATIONAL
	--#GENERIC 6
	--#CATEGORY "Error Events"
	--#STATE OPERATIONAL 
    ::= 8007
adpFlashBadImage TRAP-TYPE
    ENTERPRISE adapterTraps
    VARIABLES
        {
        atAdpNumber
        }
    DESCRIPTION "Flash downloaded image corrupted for Adapter $1" 
    --#TYPE "LSI SAS Trap: Flash Download Image corrupted"
	--#SUMMARY "Flash download image corrupted for Adapter %d"
	--#ARGUMENTS {0}
	--#SEVERITY WARNING
	--#GENERIC 6
	--#CATEGORY "Error Events"
	--#STATE OPERATIONAL 
    ::= 8008
adpFlashEraseError TRAP-TYPE
    ENTERPRISE adapterTraps
    VARIABLES
        {
        atAdpNumber
        }
    DESCRIPTION "Flash erase error for Adapter $1" 
    --#TYPE "LSI SAS Trap: Flash Erase Error"
	--#SUMMARY "Flash erase error for Adapter %d"
	--#ARGUMENTS {0}
	--#SEVERITY CRITICAL
	--#GENERIC 6
	--#CATEGORY "Error Events"
	--#STATE OPERATIONAL 
    ::= 8009
adpFlashEraseTimeout TRAP-TYPE
    ENTERPRISE adapterTraps
    VARIABLES
        {
        atAdpNumber
        }
    DESCRIPTION "Flash timeout during erase for Adapter $1"
    --#TYPE "LSI SAS Trap: Flash Timeout during Erase"
	--#SUMMARY "Flash Timeout during Erase for Adapter %d"
	--#ARGUMENTS {0}
	--#SEVERITY CRITICAL
	--#GENERIC 6
	--#CATEGORY "Error Events"
	--#STATE OPERATIONAL 
    ::= 8010
adpFlashGeneralError TRAP-TYPE
    ENTERPRISE adapterTraps
    VARIABLES
        {
        atAdpNumber
        }
    DESCRIPTION "Flash error for Adapter $1"
    --#TYPE "LSI SAS Trap: Flash Error"
	--#SUMMARY "General Flash Error occurred for Adapter %d"
	--#ARGUMENTS {0}
	--#SEVERITY CRITICAL
	--#GENERIC 6
	--#CATEGORY "Error Events"
	--#STATE OPERATIONAL 
    ::= 8011
adpFlashImage TRAP-TYPE
    ENTERPRISE adapterTraps
    VARIABLES
        {
        atFlashImageName,
        atAdpNumber
        }
    DESCRIPTION "Flashing image: $1 for Adapter $2"
    --#TYPE "LSI SAS Trap: Flashing Image"
	--#SUMMARY "Flashing Image %s for Adapter %d"
	--#ARGUMENTS {0,1}
	--#SEVERITY INFORMATIONAL
	--#GENERIC 6
	--#CATEGORY "Error Events"
	--#STATE OPERATIONAL 
    ::= 8012
adpFlashOK TRAP-TYPE
    ENTERPRISE adapterTraps
    VARIABLES
        {
        atAdpNumber
        }
    DESCRIPTION "Flash of new firmware image(s)complete for Adapter $1"
    --#TYPE "LSI SAS Trap: Flash of Firmware Image Complete"
	--#SUMMARY "Flash of Firmware Image complete for Adapter %d"
	--#ARGUMENTS {0}
	--#SEVERITY INFORMATIONAL
	--#GENERIC 6
	--#CATEGORY "Error Events"
	--#STATE OPERATIONAL 
    ::= 8013
adpFlashProgramError TRAP-TYPE
    ENTERPRISE adapterTraps
    VARIABLES
        {
        atAdpNumber
        }
    DESCRIPTION "Flash programming error for Adapter $1" 
    --#TYPE "LSI SAS Trap: Flash programming Error"
	--#SUMMARY "Flash programming error for Adapter %d"
	--#ARGUMENTS {0}
	--#SEVERITY CRITICAL
	--#GENERIC 6
	--#CATEGORY "Error Events"
	--#STATE OPERATIONAL 
    ::= 8014
adpFlashProgramTimeout TRAP-TYPE
    ENTERPRISE adapterTraps
    VARIABLES
        {
        atAdpNumber
        }
    DESCRIPTION "Flash timeout during programming for Adapter $1"
    --#TYPE "LSI SAS Trap: Flash timeout"
	--#SUMMARY "Flash timeout during programming for Adapter %d"
	--#ARGUMENTS {0}
	--#SEVERITY CRITICAL
	--#GENERIC 6
	--#CATEGORY "Error Events"
	--#STATE OPERATIONAL 
    ::= 8015
    
adpLogCleared TRAP-TYPE
    ENTERPRISE adapterTraps
    VARIABLES
        {
        atAdpNumber
        }
    DESCRIPTION "Event log cleared for Adapter $1"
    --#TYPE "LSI SAS Trap: Event Log cleared"
	--#SUMMARY "Event log cleared for Adapter %d"
	--#ARGUMENTS {0}
	--#SEVERITY INFORMATIONAL
	--#GENERIC 6
	--#CATEGORY "Error Events"
	--#STATE OPERATIONAL 
    ::= 8016
adpLogWrapped TRAP-TYPE
    ENTERPRISE adapterTraps
    VARIABLES
        {
        atAdpNumber
        }
    DESCRIPTION "Event log wrapped for Adapter $1"
    --#TYPE "LSI SAS Trap: Event log wrapped"
	--#SUMMARY "Event log wrapped for Adapter %d"
	--#ARGUMENTS {0}
	--#SEVERITY INFORMATIONAL
	--#GENERIC 6
	--#CATEGORY "Error Events"
	--#STATE OPERATIONAL 
    ::= 8017
    
adpPatrolReadComplete TRAP-TYPE
    ENTERPRISE adapterTraps
    VARIABLES
        {
        atAdpNumber
        }
    DESCRIPTION "Patrol Read complete for Adapter $1"
    --#TYPE "LSI SAS Trap: Patrol Read complete"
	--#SUMMARY "Patrol Read complete for Adapter %d"
	--#ARGUMENTS {0}
	--#SEVERITY INFORMATIONAL
	--#GENERIC 6
	--#CATEGORY "Error Events"
	--#STATE OPERATIONAL 
    ::= 8018
adpPatrolReadPaused TRAP-TYPE
    ENTERPRISE adapterTraps
    VARIABLES
        {
        atAdpNumber
        }
    DESCRIPTION "Patrol Read paused for Adapter $1"
    --#TYPE "LSI SAS Trap: Patrol Read paused"
	--#SUMMARY "Patrol Read paused for Adapter %d"
	--#ARGUMENTS {0}
	--#SEVERITY INFORMATIONAL
	--#GENERIC 6
	--#CATEGORY "Error Events"
	--#STATE OPERATIONAL 
    ::= 8019
adpPatrolReadResumed TRAP-TYPE
    ENTERPRISE adapterTraps
    VARIABLES
        {
        atAdpNumber
        }
    DESCRIPTION "Patrol Read resumed for Adapter $1"
    --#TYPE "LSI SAS Trap: Patrol Read resumed"
	--#SUMMARY "Patrol Read resumed for Adapter %d"
	--#ARGUMENTS {0}
	--#SEVERITY INFORMATIONAL
	--#GENERIC 6
	--#CATEGORY "Error Events"
	--#STATE OPERATIONAL 
    ::= 8020
adpPatrolReadStarted TRAP-TYPE
    ENTERPRISE adapterTraps
    VARIABLES
        {
        atAdpNumber
        }
    DESCRIPTION "Patrol Read started for Adapter $1" 
    --#TYPE "LSI SAS Trap: Patrol Read Started"
	--#SUMMARY "Patrol Read started for Adapter %d"
	--#ARGUMENTS {0}
	--#SEVERITY INFORMATIONAL
	--#GENERIC 6
	--#CATEGORY "Error Events"
	--#STATE OPERATIONAL 
    ::= 8021
adpShutdown TRAP-TYPE
    ENTERPRISE adapterTraps
    VARIABLES
        {
        atAdpNumber
        }
    DESCRIPTION "Shutdown command received for Adapter $1"
    --#TYPE "LSI SAS Trap: Shutdown command received"
	--#SUMMARY "Shutdown command received for Adapter %d"
	--#ARGUMENTS {0}
	--#SEVERITY INFORMATIONAL
	--#GENERIC 6
	--#CATEGORY "Error Events"
	--#STATE OPERATIONAL 
    ::= 8022
adpHibernate TRAP-TYPE
    ENTERPRISE adapterTraps
    VARIABLES
        {
        atAdpNumber
        }
    DESCRIPTION "Hibernate command received for Adapter $1"
    --#TYPE "LSI SAS Trap: Hibernate command received"
	--#SUMMARY "Hibernate command received for Adapter %d"
	--#ARGUMENTS {0}
	--#SEVERITY INFORMATIONAL
	--#GENERIC 6
	--#CATEGORY "Error Events"
	--#STATE OPERATIONAL 
    ::= 8023
adpCrash TRAP-TYPE
    ENTERPRISE adapterTraps
    VARIABLES
        {
        atAdpNumber
        }
    DESCRIPTION "Fatal error received for Adapter $1"
    --#TYPE "LSI SAS Trap: Fatal Error received"
	--#SUMMARY "Fatal error received for Adapter %d"
	--#ARGUMENTS {0}
	--#SEVERITY INFORMATIONAL
	--#GENERIC 6
	--#CATEGORY "Error Events"
	--#STATE OPERATIONAL 
    ::= 8024

adpRRChanged TRAP-TYPE
    ENTERPRISE adapterTraps
    VARIABLES
        {
        atRate,
        atAdpNumber
        }
    DESCRIPTION "Rebuild rate changed to $1 for Adapter $2"
    --#TYPE "LSI SAS Trap: Rebuild Rate changed"
	--#SUMMARY "Rebuild Rate changed to %d for Adapter %d"
	--#ARGUMENTS {0,1}
	--#SEVERITY INFORMATIONAL
	--#GENERIC 6
	--#CATEGORY "Error Events"
	--#STATE OPERATIONAL 
    ::= 8025
 adpPRRateChanged TRAP-TYPE
    ENTERPRISE adapterTraps
    VARIABLES
        {
        atRate,
        atAdpNumber
        }
    DESCRIPTION "Patrol Read rate changed to $1 for Adapter $2"
    --#TYPE "LSI SAS Trap: Patrol Read Rate changed"
	--#SUMMARY "Patrol Read Rate changed to %d for Adapter %d"
	--#ARGUMENTS {0,1}
	--#SEVERITY INFORMATIONAL
	--#GENERIC 6
	--#CATEGORY "Error Events"
	--#STATE OPERATIONAL 
     ::= 8026
adpAlarmStateDisabled TRAP-TYPE
    ENTERPRISE adapterTraps
    VARIABLES 
    { 
    atAdpNumber
    }
    DESCRIPTION "Alarm has been disabled by user for Adapter $1" 
    --#TYPE "LSI SAS Trap: Alarm disabled"
	--#SUMMARY "Alarm disabled by user for Adapter %d"
	--#ARGUMENTS {0}
	--#SEVERITY INFORMATIONAL
	--#GENERIC 6
	--#CATEGORY "Error Events"
	--#STATE OPERATIONAL 
    ::= 8027
adpConfigCleared TRAP-TYPE
    ENTERPRISE adapterTraps
    VARIABLES 
    { 
    atAdpNumber
    }
    DESCRIPTION "Configuration cleared for Adapter $1"
    --#TYPE "LSI SAS Trap: Configuration cleared"
	--#SUMMARY "Configuration cleared for Adapter %d"
	--#ARGUMENTS {0}
	--#SEVERITY INFORMATIONAL
	--#GENERIC 6
	--#CATEGORY "Error Events"
	--#STATE OPERATIONAL
    ::= 8028
adpReconRateChanged TRAP-TYPE
    ENTERPRISE adapterTraps
    VARIABLES
        {
        atRate,
        atAdpNumber
        }
    DESCRIPTION "Reconstruction rate changed to $1 for Adapter $2"
    --#TYPE "LSI SAS Trap: Reconstruction Rate changed"
	--#SUMMARY "Reconstruction Rate changed to %d for Adapter %d"
	--#ARGUMENTS {0,1}
	--#SEVERITY INFORMATIONAL
	--#GENERIC 6
	--#CATEGORY "Error Events"
	--#STATE OPERATIONAL 
    ::= 8029
adpDefault TRAP-TYPE
    ENTERPRISE adapterTraps
    VARIABLES 
    { 
    atAdpNumber
    }
    DESCRIPTION "Factory defaults restored for Adapter $1"
    --#TYPE "LSI SAS Trap: Factory defaults restored"
	--#SUMMARY "Factory defaults restored for Adapter %d"
	--#ARGUMENTS {0}
	--#SEVERITY INFORMATIONAL
	--#GENERIC 6
	--#CATEGORY "Error Events"
	--#STATE OPERATIONAL
    ::= 8030

-- bbu trap----------
bbuPresent TRAP-TYPE
    ENTERPRISE adapterTraps
    VARIABLES 
    { 
    atAdpNumber
    }
    DESCRIPTION "Battery Present for Adapter $1"
    --#TYPE "LSI SAS Trap: Battery present"
	--#SUMMARY "Battery Present for Adapter %d"
	--#ARGUMENTS {0}
	--#SEVERITY INFORMATIONAL
	--#GENERIC 6
	--#CATEGORY "Error Events"
	--#STATE OPERATIONAL
    ::= 8031
bbuNotPresent TRAP-TYPE
    ENTERPRISE adapterTraps
    VARIABLES 
    { 
    atAdpNumber
    }
    DESCRIPTION "Battery Not Present for Adapter $1"
    --#TYPE "LSI SAS Trap: Battery not present"
	--#SUMMARY "Battery not Present for Adapter %d"
	--#ARGUMENTS {0}
	--#SEVERITY WARNING
	--#GENERIC 6
	--#CATEGORY "Error Events"
	--#STATE OPERATIONAL
    ::= 8032   
bbuNewBattery TRAP-TYPE
    ENTERPRISE adapterTraps
    VARIABLES 
    { 
    atAdpNumber
    }
    DESCRIPTION "New Battery Detected for Adapter $1"
    --#TYPE "LSI SAS Trap: New Battery detected"
	--#SUMMARY "New Battery Detected for Adapter %d"
	--#ARGUMENTS {0}
	--#SEVERITY INFORMATIONAL
	--#GENERIC 6
	--#CATEGORY "Error Events"
	--#STATE OPERATIONAL
    ::= 8033   
bbuReplaced TRAP-TYPE
    ENTERPRISE adapterTraps
    VARIABLES 
    { 
    atAdpNumber
    }
    DESCRIPTION "Battery has been replaced for Adapter $1"
    --#TYPE "LSI SAS Trap: Battery replaced"
	--#SUMMARY "Battery has been replaced for Adapter %d"
	--#ARGUMENTS {0}
	--#SEVERITY INFORMATIONAL
	--#GENERIC 6
	--#CATEGORY "Error Events"
	--#STATE OPERATIONAL
    ::= 8034   
bbuTempHigh TRAP-TYPE
    ENTERPRISE adapterTraps
    VARIABLES 
    { 
    atAdpNumber
    }
    DESCRIPTION "Battery temperature is high for Adapter $1"
    --#TYPE "LSI SAS Trap: Battery temperature high"
	--#SUMMARY "Battery Temperature is high for Adapter %d"
	--#ARGUMENTS {0}
	--#SEVERITY WARNING
	--#GENERIC 6
	--#CATEGORY "Error Events"
	--#STATE OPERATIONAL
    ::= 8035   
bbuVoltageLow TRAP-TYPE
    ENTERPRISE adapterTraps
    VARIABLES 
    { 
    atAdpNumber
    }
    DESCRIPTION "Battery voltage low for Adapter $1"
    --#TYPE "LSI SAS Trap: Battery voltage low"
	--#SUMMARY "Battery voltage low for Adapter %d"
	--#ARGUMENTS {0}
	--#SEVERITY WARNING
	--#GENERIC 6
	--#CATEGORY "Error Events"
	--#STATE OPERATIONAL
    ::= 8036   
bbuCharging TRAP-TYPE
    ENTERPRISE adapterTraps
    VARIABLES 
    { 
    atAdpNumber
    }
    DESCRIPTION "Battery started charging for Adapter $1"
    --#TYPE "LSI SAS Trap: Battery started charging"
	--#SUMMARY "Battery started charging for Adapter %d"
	--#ARGUMENTS {0}
	--#SEVERITY INFORMATIONAL
	--#GENERIC 6
	--#CATEGORY "Error Events"
	--#STATE OPERATIONAL
    ::= 8037   
bbuDisCharging TRAP-TYPE
    ENTERPRISE adapterTraps
    VARIABLES 
    { 
    atAdpNumber
    }
    DESCRIPTION "Battery is discharging for Adapter $1"
    --#TYPE "LSI SAS Trap: Battery discharging"
	--#SUMMARY "Battery is discharging for Adapter %d"
	--#ARGUMENTS {0}
	--#SEVERITY INFORMATIONAL
	--#GENERIC 6
	--#CATEGORY "Error Events"
	--#STATE OPERATIONAL
    ::= 8038   
bbuTempNormal TRAP-TYPE
    ENTERPRISE adapterTraps
    VARIABLES 
    { 
    atAdpNumber
    }
    DESCRIPTION "Battery temperature is normal for Adapter $1"
    --#TYPE "LSI SAS Trap: Battery temperature normal"
	--#SUMMARY "Battery temperature is normal for Adapter %d"
	--#ARGUMENTS {0}
	--#SEVERITY INFORMATIONAL
	--#GENERIC 6
	--#CATEGORY "Error Events"
	--#STATE OPERATIONAL
    ::= 8039   
bbuReplace TRAP-TYPE
    ENTERPRISE adapterTraps
    VARIABLES 
    { 
    atAdpNumber
    }
    DESCRIPTION "Battery needs replacement, SOH Bad for Adapter $1"
    --#TYPE "LSI SAS Trap: Battery needs replacement"
	--#SUMMARY "Battery needs replacement for Adapter %d"
	--#ARGUMENTS {0}
	--#SEVERITY FATAL
	--#GENERIC 6
	--#CATEGORY "Error Events"
	--#STATE OPERATIONAL
    ::= 8040   
bbuRelearnStarted TRAP-TYPE
    ENTERPRISE adapterTraps
    VARIABLES 
    { 
    atAdpNumber
    }
    DESCRIPTION "Battery relearn started for Adapter $1"
    --#TYPE "LSI SAS Trap: Battery relearn started"
	--#SUMMARY "Battery Relearn started for Adapter %d"
	--#ARGUMENTS {0}
	--#SEVERITY INFORMATIONAL
	--#GENERIC 6
	--#CATEGORY "Error Events"
	--#STATE OPERATIONAL
    ::= 8041   
bbuRelearnProgress TRAP-TYPE
    ENTERPRISE adapterTraps
    VARIABLES 
    { 
    atAdpNumber
    }
    DESCRIPTION "Battery relearn in progress for Adapter $1"
    --#TYPE "LSI SAS Trap: Battery relearn in progress"
	--#SUMMARY "Battery Relearn in progress for Adapter %d"
	--#ARGUMENTS {0}
	--#SEVERITY INFORMATIONAL
	--#GENERIC 6
	--#CATEGORY "Error Events"
	--#STATE OPERATIONAL
    ::= 8042   
bbuRelearnComplete TRAP-TYPE
    ENTERPRISE adapterTraps
    VARIABLES 
    { 
    atAdpNumber
    }
    DESCRIPTION "Battery relearn completed for Adapter $1"
    --#TYPE "LSI SAS Trap: Battery relearn completed"
	--#SUMMARY "Battery Relearn completed for Adapter %d"
	--#ARGUMENTS {0}
	--#SEVERITY INFORMATIONAL
	--#GENERIC 6
	--#CATEGORY "Error Events"
	--#STATE OPERATIONAL
    ::= 8043   
bbuRelearnTimeout TRAP-TYPE
    ENTERPRISE adapterTraps
    VARIABLES 
    { 
    atAdpNumber
    }
    DESCRIPTION "Battery relearn timed out for Adapter $1"
    --#TYPE "LSI SAS Trap: Battery relearn timed out"
	--#SUMMARY "Battery Relearn timed out for Adapter %d"
	--#ARGUMENTS {0}
	--#SEVERITY WARNING
	--#GENERIC 6
	--#CATEGORY "Error Events"
	--#STATE OPERATIONAL
    ::= 8044   
bbuRelearnPending TRAP-TYPE
    ENTERPRISE adapterTraps
    VARIABLES 
    { 
    atAdpNumber
    }
    DESCRIPTION "Battery relearn pending: Battery is under charge for Adapter $1"
    --#TYPE "LSI SAS Trap: Battery relearn pending"
	--#SUMMARY "Battery Relearn pending: Battery is under charge for Adapter %d"
	--#ARGUMENTS {0}
	--#SEVERITY INFORMATIONAL
	--#GENERIC 6
	--#CATEGORY "Error Events"
	--#STATE OPERATIONAL
    ::= 8045  
bbuRelearnPostponed TRAP-TYPE
    ENTERPRISE adapterTraps
    VARIABLES 
    { 
    atAdpNumber
    }
    DESCRIPTION "Battery relearn postponed for Adapter $1"
    --#TYPE "LSI SAS Trap: Battery relearn postponed"
	--#SUMMARY "Battery Relearn postponed for Adapter %d"
	--#ARGUMENTS {0}
	--#SEVERITY INFORMATIONAL
	--#GENERIC 6
	--#CATEGORY "Error Events"
	--#STATE OPERATIONAL
    ::= 8046   
bbuRemoved TRAP-TYPE
    ENTERPRISE adapterTraps
    VARIABLES 
    { 
    atAdpNumber
    }
    DESCRIPTION "Battery removed for Adapter $1"
    --#TYPE "LSI SAS Trap: Battery removed"
	--#SUMMARY "Battery removed for Adapter %d"
	--#ARGUMENTS {0}
	--#SEVERITY WARNING
	--#GENERIC 6
	--#CATEGORY "Error Events"
	--#STATE OPERATIONAL
    ::= 8047   
bbuCapacityLow TRAP-TYPE
    ENTERPRISE adapterTraps
    VARIABLES 
    { 
    atAdpNumber
    }
    DESCRIPTION "Current capacity of the battery is below threshold for Adapter $1"
    --#TYPE "LSI SAS Trap: Current capacity below threshold"
	--#SUMMARY "Current capacity of the battery is below threshold for Adapter %d"
	--#ARGUMENTS {0}
	--#SEVERITY WARNING
	--#GENERIC 6
	--#CATEGORY "Error Events"
	--#STATE OPERATIONAL
    ::= 8048   
bbuCapacityAbove TRAP-TYPE
    ENTERPRISE adapterTraps
    VARIABLES 
    { 
    atAdpNumber
    }
    DESCRIPTION "Current capacity of the battery is above threshold for Adapter $1"
    --#TYPE "LSI SAS Trap: Current capacity above threshold"
	--#SUMMARY "Current capacity of the battery is above threshold for Adapter %d"
	--#ARGUMENTS {0}
	--#SEVERITY INFORMATIONAL
	--#GENERIC 6
	--#CATEGORY "Error Events"
	--#STATE OPERATIONAL
    ::= 8049   
   
bbuFRUChanged TRAP-TYPE
    ENTERPRISE adapterTraps
    VARIABLES 
    { 
    atAdpNumber
    }
    DESCRIPTION "Bbu FRU for Adapter $1 changed"
    --#TYPE "LSI SAS Trap: Bbu FRU Changed"
	--#SUMMARY "Bbu FRU changed for Adapter %d"
	--#ARGUMENTS {0}
	--#SEVERITY INFORMATIONAL
	--#GENERIC 6
	--#CATEGORY "Error Events"
	--#STATE OPERATIONAL
    ::= 8050 


revisionIdentifierChanged TRAP-TYPE
    ENTERPRISE adapterTraps
    VARIABLES 
    { 
    atAdpNumber
    }
    DESCRIPTION "Revision Identifier for Adapter $1 changed"
    --#TYPE "LSI SAS Trap: Revision Identifier Changed"
	--#SUMMARY "Revision Identifier changed for Adapter %d"
	--#ARGUMENTS {0}
	--#SEVERITY INFORMATIONAL
	--#GENERIC 6
	--#CATEGORY "Error Events"
	--#STATE OPERATIONAL
    ::= 8051

    
adpLockKeyCreated TRAP-TYPE
    ENTERPRISE adapterTraps
    VARIABLES 
    { 
    atAdpNumber
    }
    DESCRIPTION "Drive security key created for Adapter $1"
    --#TYPE "LSI SAS Trap: Drive security key created"
	--#SUMMARY "Drive security key created for Adapter %d"
	--#ARGUMENTS {0}
	--#SEVERITY INFORMATIONAL
	--#GENERIC 6
	--#CATEGORY "Error Events"
	--#STATE OPERATIONAL
    ::= 8052
    
adpLockKeyBackedup TRAP-TYPE
    ENTERPRISE adapterTraps
    VARIABLES 
    { 
    atAdpNumber
    }
    DESCRIPTION "Drive security key backed up for Adapter $1"
    --#TYPE "LSI SAS Trap: Drive security key backed up"
	--#SUMMARY "Drive security key backed up for Adapter %d"
	--#ARGUMENTS {0}
	--#SEVERITY INFORMATIONAL
	--#GENERIC 6
	--#CATEGORY "Error Events"
	--#STATE OPERATIONAL
    ::= 8053
    
adpLockKeyVerifiedEscrow TRAP-TYPE
    ENTERPRISE adapterTraps
    VARIABLES 
    { 
    atAdpNumber
    }
    DESCRIPTION "Drive security key from escrow, verified for Adapter $1"
    --#TYPE "LSI SAS Trap: Drive security key from escrow, verified"
	--#SUMMARY "Drive security key from escrow, verified for Adapter %d"
	--#ARGUMENTS {0}
	--#SEVERITY INFORMATIONAL
	--#GENERIC 6
	--#CATEGORY "Error Events"
	--#STATE OPERATIONAL
    ::= 8054

adpLockKeyRekeyed TRAP-TYPE
    ENTERPRISE adapterTraps
    VARIABLES 
    { 
    atAdpNumber
    }
    DESCRIPTION "Drive security key changed for Adapter $1"
    --#TYPE "LSI SAS Trap: Drive security key changed"
	--#SUMMARY "Drive security key changed for Adapter %d"
	--#ARGUMENTS {0}
	--#SEVERITY INFORMATIONAL
	--#GENERIC 6
	--#CATEGORY "Error Events"
	--#STATE OPERATIONAL
    ::= 8055

adpLockKeyRekeyFailed TRAP-TYPE
    ENTERPRISE adapterTraps
    VARIABLES 
    { 
    atAdpNumber
    }
    DESCRIPTION "Drive security key, re-key operation failed for Adapter $1"
    --#TYPE "LSI SAS Trap: Drive security key, re-key operation failed"
	--#SUMMARY "Drive security key, re-key operation failed for Adapter %d"
	--#ARGUMENTS {0}
	--#SEVERITY WARNING
	--#GENERIC 6
	--#CATEGORY "Error Events"
	--#STATE OPERATIONAL
    ::= 8056

adpLockKeyInvalid TRAP-TYPE
    ENTERPRISE adapterTraps
    VARIABLES 
    { 
    atAdpNumber
    }
    DESCRIPTION "Drive security key is invalid for Adapter $1"
    --#TYPE "LSI SAS Trap: Drive security key is invalid"
	--#SUMMARY "Drive security key is invalid for Adapter %d"
	--#ARGUMENTS {0}
	--#SEVERITY WARNING
	--#GENERIC 6
	--#CATEGORY "Error Events"
	--#STATE OPERATIONAL
    ::= 8057

adpLockKeyDestroyed TRAP-TYPE
    ENTERPRISE adapterTraps
    VARIABLES 
    { 
    atAdpNumber
    }
    DESCRIPTION "Drive security key destroyed for Adapter $1"
    --#TYPE "LSI SAS Trap: Drive security key destroyed"
	--#SUMMARY "Drive security key destroyed for Adapter %d"
	--#ARGUMENTS {0}
	--#SEVERITY INFORMATIONAL
	--#GENERIC 6
	--#CATEGORY "Error Events"
	--#STATE OPERATIONAL
    ::= 8058
    
adpEscrowKeyInvalid TRAP-TYPE
    ENTERPRISE adapterTraps
    VARIABLES 
    { 
    atAdpNumber
    }
    DESCRIPTION "Drive security key from escrow is invalid for Adapter $1"
    --#TYPE "LSI SAS Trap: Drive security key from escrow is invalid"
	--#SUMMARY "Drive security key from escrow is invalid for Adapter %d"
	--#ARGUMENTS {0}
	--#SEVERITY WARNING
	--#GENERIC 6
	--#CATEGORY "Error Events"
	--#STATE OPERATIONAL
    ::= 8059
    
adpLockKeyFailed TRAP-TYPE
    ENTERPRISE adapterTraps
    VARIABLES 
    { 
    atAdpNumber
    }
    DESCRIPTION "Drive security key failure, cannot access secured configuration for Adapter $1"
    --#TYPE "LSI SAS Trap: Drive security key failure, cannot access secured configuration"
	--#SUMMARY "Drive security key failure, cannot access secured configuration for Adapter %d"
	--#ARGUMENTS {0}
	--#SEVERITY WARNING
	--#GENERIC 6
	--#CATEGORY "Error Events"
	--#STATE OPERATIONAL
    ::= 8060

bbuChargeDisabled TRAP-TYPE
    ENTERPRISE adapterTraps
    VARIABLES 
    { 
    atAdpNumber
    }
    DESCRIPTION "Battery charging was suspended due to high battery temperature on Adapter $1"
    --#TYPE "LSI SAS Trap: Battery Charge Disabled"
	--#SUMMARY "Battery charging was suspended due to high battery temperature on Adapter %d"
	--#ARGUMENTS {0}
	--#SEVERITY WARNING
	--#GENERIC 6
	--#CATEGORY "Error Events"
	--#STATE OPERATIONAL
    ::= 8061

bbuMicrocodeUpdated TRAP-TYPE
    ENTERPRISE adapterTraps
    VARIABLES 
    { 
    atAdpNumber
    }
    DESCRIPTION "Battery NVCache firmware update was successful on Adapter $1"
    --#TYPE "LSI SAS Trap: Battery Microcode Updated"
	--#SUMMARY "Battery NVCache firmware update was successful on Adapter %d"
	--#ARGUMENTS {0}
	--#SEVERITY INFORMATIONAL
	--#GENERIC 6
	--#CATEGORY "Error Events"
	--#STATE OPERATIONAL
    ::= 8062

bbuMicrocodeUpdateFailed TRAP-TYPE
    ENTERPRISE adapterTraps
    VARIABLES 
    { 
    atAdpNumber
    }
    DESCRIPTION "Battery NVCache firmware update failed on Adapter $1"
    --#TYPE "LSI SAS Trap: Battery Microcode Update Failed"
	--#SUMMARY "Battery NVCache firmware update failed on Adapter %d"
	--#ARGUMENTS {0}
	--#SEVERITY INFORMATIONAL
	--#GENERIC 6
	--#CATEGORY "Error Events"
	--#STATE OPERATIONAL
    ::= 8063

haNodeJoin TRAP-TYPE
    ENTERPRISE adapterTraps
    VARIABLES
        {atAdpNumber}
    DESCRIPTION "Peer controller entered HA Domain at Adapter -$1"
    --#TYPE "LSI SAS Trap: Peer controller has joined HA domain"
	--#SUMMARY "Peer controller entered HA Domain at Adapter -%d"
	--#ARGUMENTS {0}
	--#SEVERITY INFORMATIONAL
	--#GENERIC 6
	--#CATEGORY "Error Events"
	--#STATE OPERATIONAL
    ::= 8064
	
haNodeBreak TRAP-TYPE
    ENTERPRISE adapterTraps
    VARIABLES
        {atAdpNumber}
    DESCRIPTION "Peer controller exited HA Domain at Adapter -$1"
    --#TYPE "LSI SAS Trap: Peer controller has left HA domain"
	--#SUMMARY "Peer controller exited HA Domain at Adapter -%d" 
	--#ARGUMENTS {0}
	--#SEVERITY CRITICAL
	--#GENERIC 6
	--#CATEGORY "Error Events"
	--#STATE OPERATIONAL
    ::= 8065	
	
haPeerIncompatible TRAP-TYPE
    ENTERPRISE adapterTraps
    DESCRIPTION "Peer controller settings are incompatible"
    --#TYPE "LSI SAS Trap: Peer controller is incompatible"
	--#SUMMARY "Peer controller settings are incompatible" 
	--#SEVERITY CRITICAL
	--#GENERIC 6
	--#CATEGORY "Error Events"
	--#STATE OPERATIONAL
    ::= 8066	

haCtrlpropIncompatible TRAP-TYPE
    ENTERPRISE adapterTraps
    DESCRIPTION "Controller property mismatch detected with Peer controller"
    --#TYPE "LSI SAS Trap: Controller properties are incompatible with peer's"
	--#SUMMARY "Controller property mismatch detected with Peer controller" 
	--#SEVERITY CRITICAL
	--#GENERIC 6
	--#CATEGORY "Error Events"
	--#STATE OPERATIONAL
    ::= 8067
	
haFWVersionMismatch TRAP-TYPE
    ENTERPRISE adapterTraps
   DESCRIPTION "FW version does not match Peer controller"
    --#TYPE "LSI SAS Trap: FW versions of the cluster nodes do not match"
	--#SUMMARY "FW version does not match Peer controller" 
	--#SEVERITY WARNING
	--#GENERIC 6
	--#CATEGORY "Error Events"
	--#STATE OPERATIONAL
    ::= 8068	
	
haCacheMirrorOnline TRAP-TYPE
    ENTERPRISE adapterTraps
    DESCRIPTION "Cache mirroring is online"
    --#TYPE "LSI SAS Trap: HA cache mirror is online"
	--#SUMMARY "Cache mirroring is online" 
	--#SEVERITY INFORMATIONAL
	--#GENERIC 6
	--#CATEGORY "Error Events"
	--#STATE OPERATIONAL
    ::= 8069

haCacheMirrorOffline TRAP-TYPE
    ENTERPRISE adapterTraps
    DESCRIPTION "Cache mirroring is offline"
    --#TYPE "LSI SAS Trap: HA cache mirror is offline"
	--#SUMMARY "Cache mirroring is offline" 
	--#SEVERITY CRITICAL
	--#GENERIC 6
	--#CATEGORY "Error Events"
	--#STATE OPERATIONAL
    ::= 8070  
	
adpPropChanged TRAP-TYPE
    ENTERPRISE adapterTraps
    VARIABLES 
    { 
    atAdpNumber
    }
    DESCRIPTION "Controller properties changed for Adapter $1"
    --#TYPE "LSI SAS Trap: Controller properties changed"
	--#SUMMARY "Controller properties changed for Adapter %d"
	--#ARGUMENTS {0}
	--#SEVERITY INFORMATIONAL
	--#GENERIC 6
	--#CATEGORY "Error Events"
	--#STATE OPERATIONAL
    ::= 8071

adpResetNowStart TRAP-TYPE
    ENTERPRISE adapterTraps
    VARIABLES 
    { 
    atAdpNumber
    }
    DESCRIPTION "Controller reset requested by host for Adapter $1"
    --#TYPE "LSI SAS Trap: Controller reset requested by host"
	--#SUMMARY "Controller reset requested by host for Adapter %d"
	--#ARGUMENTS {0}
	--#SEVERITY INFORMATIONAL
	--#GENERIC 6
	--#CATEGORY "Error Events"
	--#STATE OPERATIONAL
    ::= 8072

adpResetNowDone TRAP-TYPE
    ENTERPRISE adapterTraps
    VARIABLES 
    { 
    atAdpNumber
    }
    DESCRIPTION "Controller reset requested by host, completed for Adapter $1"
    --#TYPE "LSI SAS Trap: Controller reset requested by host, completed"
	--#SUMMARY "Controller reset requested by host, completed for Adapter %d"
	--#ARGUMENTS {0}
	--#SEVERITY INFORMATIONAL
	--#GENERIC 6
	--#CATEGORY "Error Events"
	--#STATE OPERATIONAL
    ::= 8073
	
peerControllerKeyMismatch TRAP-TYPE
    ENTERPRISE adapterTraps
    DESCRIPTION "Peer controller security key mismatch"
    --#TYPE "Peer controller security key mismatch"
	--#SUMMARY "Peer controller security key mismatch"
	--#SEVERITY CRITICAL
	--#GENERIC 6
	--#CATEGORY "Error Events"
	--#STATE OPERATIONAL
    ::= 8074

peerControllerKeyMatch TRAP-TYPE
    ENTERPRISE adapterTraps
    DESCRIPTION "Peer controller security key match"
    --#TYPE "LSI SAS Trap: Peer controller security key match"
	--#SUMMARY "Peer controller security key match"
	--#SEVERITY INFORMATIONAL
	--#GENERIC 6
	--#CATEGORY "Error Events"
	--#STATE OPERATIONAL
    ::= 8075

cfgAutoCreated TRAP-TYPE
    ENTERPRISE adapterTraps
    VARIABLES
    {
    atAdpNumber
    }
    DESCRIPTION "Configuration automatically created on Adapter $1"
    --#TYPE "LSI SAS Trap: Configuration automatically created on Adapter"
	--#SUMMARY "Configuration automatically created on Adapter %d" 
	--#ARGUMENTS {0}
	--#SEVERITY INFORMATIONAL
	--#GENERIC 6
	--#CATEGORY "Error Events"
	--#STATE OPERATIONAL
    ::= 8077

nvcacheBlockRecoverySkipped TRAP-TYPE
    ENTERPRISE adapterTraps
    VARIABLES
    {
    atAdpNumber
    }
    DESCRIPTION "Block recovery is skipped for Cache-vault. Reboot the system to recover the blocks $1"
    --#TYPE "LSI SAS Trap: Block recovery is skipped for Cache-vault. Reboot the system to recover the blocks"
	--#SUMMARY "Block recovery is skipped for Cache-vault. Reboot the system to recover the blocks %d" 
	--#ARGUMENTS {0}
	--#SEVERITY WARNING
	--#GENERIC 6
	--#CATEGORY "Error Events"
	--#STATE OPERATIONAL
    ::= 8078
	
---------------vd trap----------
vdTraps                      OBJECT IDENTIFIER ::= {lsiRAIDServer 7}
vdNumber                 OBJECT-TYPE
    SYNTAX                      INTEGER
    ACCESS                      read-only
    STATUS                      optional
    DESCRIPTION                 "vd Target ID for which Trap is generated."
    ::= { vdTraps 1101 }
vdSeq                 OBJECT-TYPE
    SYNTAX                      INTEGER
    ACCESS                      read-only
    STATUS                      optional
    DESCRIPTION                 "vd Sequence no for which Trap is generated."
    ::= { vdTraps 1102 }
vdProg                 OBJECT-TYPE
    SYNTAX                      INTEGER
    ACCESS                      read-only
    STATUS                      optional
    DESCRIPTION                 "progress %"
    ::= { vdTraps 1103 }

vdCachePolicyChangeReason            OBJECT-TYPE
    SYNTAX                      DisplayString
    ACCESS                      read-only
    STATUS                      optional
    DESCRIPTION                 "VD cache policy."
    ::= { vdTraps 1104 }

vdNewState            OBJECT-TYPE
    SYNTAX                      INTEGER
    ACCESS                      read-only
    STATUS                      optional
    DESCRIPTION                 "Virtual Drive state. Values are: offline(0),partially-degraded(1),degraded(2),optimal(3)"
    ::= { vdTraps 1105 }

vdOldState            OBJECT-TYPE
    SYNTAX                      INTEGER
    ACCESS                      read-only
    STATUS                      optional
    DESCRIPTION                 "Virtual Drive state. Values are: offline(0),partially-degraded(1),degraded(2),optimal(3)"
    ::= { vdTraps 1106 }
	
isRemote                 OBJECT-TYPE
    SYNTAX                      INTEGER
    ACCESS                      read-only
    STATUS                      optional
    DESCRIPTION                 "HA cluster locale: 0=local, 1=remote (at peer)"
    ::= { vdTraps 1107 }
	
vdOldAccessPolicy                 OBJECT-TYPE
    SYNTAX                      INTEGER
    ACCESS                      read-only
    STATUS                      optional
    DESCRIPTION                 "Virtual Drive access policy. Values are: read/write(0), read-only(2), blocked(3), transport-ready(14), hidden(15)"
    ::= { vdTraps 1108 }

vdNewAccessPolicy                 OBJECT-TYPE
    SYNTAX                      INTEGER
    ACCESS                      read-only
    STATUS                      optional
    DESCRIPTION                 "Virtual Drive access policy. Values are: read/write(0), read-only(2), blocked(3), transport-ready(14), hidden(15)"
    ::= { vdTraps 1109 }

vdOldAutoSnapshot                 OBJECT-TYPE
    SYNTAX                      INTEGER
    ACCESS                      read-only
    STATUS                      optional
    DESCRIPTION                 "Virtual Drive auto snapshot. Values are: enabled(1), disabled(0)"
    ::= { vdTraps 1110 }

vdNewAutoSnapshot                 OBJECT-TYPE
    SYNTAX                      INTEGER
    ACCESS                      read-only
    STATUS                      optional
    DESCRIPTION                 "Virtual Drive auto snapshot. Values are: enabled(1), disabled(0)"
    ::= { vdTraps 1111 }

vdOldcacheBypassIOSize                 OBJECT-TYPE
    SYNTAX                      INTEGER
    ACCESS                      read-only
    STATUS                      optional
    DESCRIPTION                 "Virtual Drive cache bypass IO size. Values are: 64k(0), 128k(1), 256k(2)"
    ::= { vdTraps 1112 }

vdNewcacheBypassIOSize                 OBJECT-TYPE
    SYNTAX                      INTEGER
    ACCESS                      read-only
    STATUS                      optional
    DESCRIPTION                 "Virtual Drive cache bypass IO size. Values are: 64k(0), 128k(1), 256k(2)"
    ::= { vdTraps 1113 }

vdOldcacheBypassMode                 OBJECT-TYPE
    SYNTAX                      INTEGER
    ACCESS                      read-only
    STATUS                      optional
    DESCRIPTION                 "Virtual Drive cache bypass mode. Values are: intelligent(0), standard(1), custom_mode_1(2), custom_mode_2(3), custom_mode_3(4), reserved_mode_1(5), reserved_mode_2(6), disable(7)"
    ::= { vdTraps 1114 }

vdNewcacheBypassMode                 OBJECT-TYPE
    SYNTAX                      INTEGER
    ACCESS                      read-only
    STATUS                      optional
    DESCRIPTION                 "Virtual Drive cache bypass mode. Values are: intelligent(0), standard(1), custom_mode_1(2), custom_mode_2(3), custom_mode_3(4), reserved_mode_1(5), reserved_mode_2(6), disable(7)"
    ::= { vdTraps 1115 }

vdOldcurrentCachePolicy                 OBJECT-TYPE
    SYNTAX                      INTEGER
    ACCESS                      read-only
    STATUS                      optional
    DESCRIPTION                 "Virtual Drive current cache policy. Values are: write-back(1), write-adaptive(2), read-ahead(4), read-adaptive(8), write-cache-bad-bbu(16), allow-write-cache(32), allow-read-cache(64)"
    ::= { vdTraps 1116 }

vdNewcurrentCachePolicy                 OBJECT-TYPE
    SYNTAX                      INTEGER
    ACCESS                      read-only
    STATUS                      optional
    DESCRIPTION                 "Virtual Drive current cache policy. Values are: write-back(1), write-adaptive(2), read-ahead(4), read-adaptive(8), write-cache-bad-bbu(16), allow-write-cache(32), allow-read-cache(64)"
    ::= { vdTraps 1117 }

vdOldcurrentPSPolicy                 OBJECT-TYPE
    SYNTAX                      INTEGER
    ACCESS                      read-only
    STATUS                      optional
    DESCRIPTION                 "Virtual Drive current powersave policy. Values are: ctrl-default(0), auto(1), max(2), no-cache(4), t10(8), none(254), reserved(255)"
    ::= { vdTraps 1118 }

vdNewcurrentPSPolicy                 OBJECT-TYPE
    SYNTAX                      INTEGER
    ACCESS                      read-only
    STATUS                      optional
    DESCRIPTION                 "Virtual Drive current powersave policy. Values are: ctrl-default(0), auto(1), max(2), no-cache(4), t10(8), none(254), reserved(255)"
    ::= { vdTraps 1119 }

vdOlddefaultCachePolicy                 OBJECT-TYPE
    SYNTAX                      INTEGER
    ACCESS                      read-only
    STATUS                      optional
    DESCRIPTION                 "Virtual Drive default cache policy. Values are: write-back(1), write-adaptive(2), read-ahead(4), read-adaptive(8), write-cache-bad-bbu(16), allow-write-cache(32), allow-read-cache(64)"
    ::= { vdTraps 1120 }

vdNewdefaultCachePolicy                 OBJECT-TYPE
    SYNTAX                      INTEGER
    ACCESS                      read-only
    STATUS                      optional
    DESCRIPTION                 "Virtual Drive default cache policy. Values are: write-back(1), write-adaptive(2), read-ahead(4), read-adaptive(8), write-cache-bad-bbu(16), allow-write-cache(32), allow-read-cache(64)"
    ::= { vdTraps 1121 }

vdOlddefaultPSPolicy                 OBJECT-TYPE
    SYNTAX                      INTEGER
    ACCESS                      read-only
    STATUS                      optional
    DESCRIPTION                 "Virtual Drive default powersave policy. Values are: ctrl-default(0), auto(1), max(2), no-cache(4), t10(8), none(254), reserved(255)"
    ::= { vdTraps 1122 }

vdNewdefaultPSPolicy                 OBJECT-TYPE
    SYNTAX                      INTEGER
    ACCESS                      read-only
    STATUS                      optional
    DESCRIPTION                 "Virtual Drive default powersave policy. Values are: ctrl-default(0), auto(1), max(2), no-cache(4), t10(8), none(254), reserved(255)"
    ::= { vdTraps 1123 }

vdOlddisableAutoDeleteOldestPIT                 OBJECT-TYPE
    SYNTAX                      INTEGER
    ACCESS                      read-only
    STATUS                      optional
    DESCRIPTION                 "Virtual drive disable auto delete oldest pit. Values are: enabled(1), disabled(0)"
    ::= { vdTraps 1124 }

vdNewdisableAutoDeleteOldestPIT                 OBJECT-TYPE
    SYNTAX                      INTEGER
    ACCESS                      read-only
    STATUS                      optional
    DESCRIPTION                 "Virtual Drive disable auto delete oldest pit. Values are: enabled(1), disabled(0)"
    ::= { vdTraps 1125 }

vdOlddiskCachePolicy                 OBJECT-TYPE
    SYNTAX                      INTEGER
    ACCESS                      read-only
    STATUS                      optional
    DESCRIPTION                 "Virtual Drive disk cache policy. Values are: unchanged(0), enabled(1), disabled(2)"
    ::= { vdTraps 1126 }

vdNewdiskCachePolicy                 OBJECT-TYPE
    SYNTAX                      INTEGER
    ACCESS                      read-only
    STATUS                      optional
    DESCRIPTION                 "Virtual Drive disk cache policy. Values are: unchanged(0), enabled(1), disabled(2)"
    ::= { vdTraps 1127 }

vdOldemulationType                 OBJECT-TYPE
    SYNTAX                      INTEGER
    ACCESS                      read-only
    STATUS                      optional
    DESCRIPTION                 "Virtual Drive emulation type. Values are: default(0), disabled(1)"
    ::= { vdTraps 1128 }

vdNewemulationType                 OBJECT-TYPE
    SYNTAX                      INTEGER
    ACCESS                      read-only
    STATUS                      optional
    DESCRIPTION                 "Virtual Drive emulation type. Values are: default(0), disabled(1)"
    ::= { vdTraps 1129 }

vdOldenabledAtomicityType                 OBJECT-TYPE
    SYNTAX                      INTEGER
    ACCESS                      read-only
    STATUS                      optional
    DESCRIPTION                 "Virtual Drive enabled automicity type. Values are: disabled(0), write-all(1), write-t10(2)"
    ::= { vdTraps 1130 }

vdNewenabledAtomicityType                 OBJECT-TYPE
    SYNTAX                      INTEGER
    ACCESS                      read-only
    STATUS                      optional
    DESCRIPTION                 "Virtual Drive enabled automicity type. Values are: disabled(0), write-all(1), write-t10(2)"
    ::= { vdTraps 1131 }

vdOldexclusiveAccess                 OBJECT-TYPE
    SYNTAX                      INTEGER
    ACCESS                      read-only
    STATUS                      optional
    DESCRIPTION                 "Virtual Drive exclusive access. Values are: true(1), false(0)"
    ::= { vdTraps 1132 }

vdNewexclusiveAccess                 OBJECT-TYPE
    SYNTAX                      INTEGER
    ACCESS                      read-only
    STATUS                      optional
    DESCRIPTION                 "Virtual Drive exclusive access. Values are: true(1), false(0)"
    ::= { vdTraps 1133 }

vdOldforceEmulation                 OBJECT-TYPE
    SYNTAX                      INTEGER
    ACCESS                      read-only
    STATUS                      optional
    DESCRIPTION                 "Virtual Drive force emulation. Values are: set(1), not-set(0)"
    ::= { vdTraps 1134 }


vdNewforceEmulation                 OBJECT-TYPE
    SYNTAX                      INTEGER
    ACCESS                      read-only
    STATUS                      optional
    DESCRIPTION                 "Virtual Drive force emulation. Values are: set(1), not-set(0)"
    ::= { vdTraps 1135 }


vdOldname                 OBJECT-TYPE
    SYNTAX                      STRING
    ACCESS                      read-only
    STATUS                      optional
    DESCRIPTION                 "Virtual Drive name"
    ::= { vdTraps 1136 }


vdNewname                 OBJECT-TYPE
    SYNTAX                      STRING
    ACCESS                      read-only
    STATUS                      optional
    DESCRIPTION                 "Virtual Drive name"
    ::= { vdTraps 1137 }


vdOldnoBGI                 OBJECT-TYPE
    SYNTAX                      INTEGER
    ACCESS                      read-only
    STATUS                      optional
    DESCRIPTION                 "Virtual Drive set no BGI. Values are: 1(disabled), 0 (enabled)"
    ::= { vdTraps 1138 }


vdNewnoBGI                 OBJECT-TYPE
    SYNTAX                      INTEGER
    ACCESS                      read-only
    STATUS                      optional
    DESCRIPTION                 "Virtual Drive set no BGI. Values are: 1(disabled), 0 (enabled)"
    ::= { vdTraps 1139 }


vdOldscsiUnmapEnabled                 OBJECT-TYPE
    SYNTAX                      INTEGER
    ACCESS                      read-only
    STATUS                      optional
    DESCRIPTION                 "Virtual Drive SCSI unmap enabled. Values are: 0(disabled), 1(enabled)"
    ::= { vdTraps 1140 }


vdNewscsiUnmapEnabled                 OBJECT-TYPE
    SYNTAX                      INTEGER
    ACCESS                      read-only
    STATUS                      optional
    DESCRIPTION                 "Virtual Drive SCSI unmap enabled. Values are: 0(disabled), 1(enabled)"
    ::= { vdTraps 1141 }


vdOldSSCWriteBuferMode                 OBJECT-TYPE
    SYNTAX                      INTEGER
    ACCESS                      read-only
    STATUS                      optional
    DESCRIPTION                 "Virtual Drive SSC write buffer mode. Values are: 0(disabled), 1(enabled)"
    ::= { vdTraps 1142 }


vdNewSSCWriteBuferMode                 OBJECT-TYPE
    SYNTAX                      INTEGER
    ACCESS                      read-only
    STATUS                      optional
    DESCRIPTION                 "Virtual Drive SSC write buffer mode. Values are: 0(disabled), 1(enabled)"
    ::= { vdTraps 1143 }


-- Following are the trap definitions, which use variables defined
-- within the object lsiRaidMib.

vdtBGIAborted TRAP-TYPE
    ENTERPRISE vdTraps
    VARIABLES { atAdpNumber,vdNumber,isRemote}
    DESCRIPTION "BGI aborted on Adapter -$1  VD Target -$2 Remote VD -$3"
    --#TYPE "LSI SAS Trap: BGI aborted"
	--#SUMMARY "BGI aborted on Adapter -%d  VD Target -%d Remote VD -%d"
	--#ARGUMENTS {0,1,2}
	--#SEVERITY INFORMATIONAL
	--#GENERIC 6
	--#CATEGORY "Error Events"
	--#STATE OPERATIONAL
    ::= 8101
vdtBGICompleted TRAP-TYPE
    ENTERPRISE vdTraps
    VARIABLES { atAdpNumber,vdNumber,isRemote}
    DESCRIPTION "BGI completed on Adapter -$1 VD Target -$2 Remote VD -$3"
    --#TYPE "LSI SAS Trap: BGI completed"
	--#SUMMARY "BGI completed on Adapter -%d  VD Target -%d Remote VD -%d"
	--#ARGUMENTS {0,1,2}
	--#SEVERITY INFORMATIONAL
	--#GENERIC 6
	--#CATEGORY "Error Events"
	--#STATE OPERATIONAL
    ::= 8102
vdtBGIDoneWR TRAP-TYPE
    ENTERPRISE vdTraps
    VARIABLES { atAdpNumber,vdNumber,isRemote}
    DESCRIPTION "BGI completed with uncorrectable errors on Adapter -$1  VD Target -$2 Remote VD -$3"
    --#TYPE "LSI SAS Trap: BGI completed with uncorrectble errors"
	--#SUMMARY "BGI completed with uncorrectable errors on Adapter -%d  VD Target -%d Remote VD -%d"
	--#ARGUMENTS {0,1,2}
	--#SEVERITY INFORMATIONAL
	--#GENERIC 6
	--#CATEGORY "Error Events"
	--#STATE OPERATIONAL
    ::= 8103
vdtBGIFailed TRAP-TYPE
    ENTERPRISE vdTraps
    VARIABLES { atAdpNumber,vdNumber,isRemote}
    DESCRIPTION "BGI failed on Adapter -$1  VD Target -$2 Remote VD -$3"
    --#TYPE "LSI SAS Trap: BGI failed"
	--#SUMMARY "BGI failed on Adapter -%d  VD Target -%d Remote VD -%d"
	--#ARGUMENTS {0,1,2}
	--#SEVERITY INFORMATIONAL
	--#GENERIC 6
	--#CATEGORY "Error Events"
	--#STATE OPERATIONAL
    ::= 8104
vdtBGIStarted TRAP-TYPE
    ENTERPRISE vdTraps
    VARIABLES { atAdpNumber,vdNumber,isRemote}
    DESCRIPTION "BGI started on Adapter -$1  VD Target -$2 Remote VD -$3"
    --#TYPE "LSI SAS Trap: BGI started"
	--#SUMMARY "BGI started on Adapter -%d  VD Target -%d Remote VD -%d"
	--#ARGUMENTS {0,1,2}
	--#SEVERITY INFORMATIONAL
	--#GENERIC 6
	--#CATEGORY "Error Events"
	--#STATE OPERATIONAL
    ::= 8105
vdtCCStarted TRAP-TYPE
    ENTERPRISE vdTraps
    VARIABLES
        {atAdpNumber,vdNumber,isRemote,isRemote}
    DESCRIPTION "CC started on Adapter -$1  VD Target -$2 Remote VD -$3"
    --#TYPE "LSI SAS Trap: CC started"
	--#SUMMARY "CC started on Adapter -%d  VD Target -%d Remote VD -%d"
	--#ARGUMENTS {0,1,2}
	--#SEVERITY INFORMATIONAL
	--#GENERIC 6
	--#CATEGORY "Error Events"
	--#STATE OPERATIONAL
    ::= 8107
vdtCCCompleted TRAP-TYPE
    ENTERPRISE vdTraps
    VARIABLES
        {atAdpNumber,vdNumber,isRemote}
    DESCRIPTION "CC completed on Adapter -$1  VD Target -$2 Remote VD -$3"
    --#TYPE "LSI SAS Trap: CC completed"
	--#SUMMARY "CC completed on Adapter -%d  VD Target -%d Remote VD -%d"
	--#ARGUMENTS {0,1,2}
	--#SEVERITY INFORMATIONAL
	--#GENERIC 6
	--#CATEGORY "Error Events"
	--#STATE OPERATIONAL
    ::= 8108
vdtCCFailed TRAP-TYPE
    ENTERPRISE vdTraps
    VARIABLES
        {atAdpNumber,vdNumber,isRemote}
    DESCRIPTION "CC failed on Adapter -$1  VD Target -$2 Remote VD -$3"
    --#TYPE "LSI SAS Trap: CC failed"
	--#SUMMARY "CC failed on Adapter -%d  VD Target-%d Remote VD -%d"
	--#ARGUMENTS {0,1,2}
	--#SEVERITY INFORMATIONAL
	--#GENERIC 6
	--#CATEGORY "Error Events"
	--#STATE OPERATIONAL
    ::= 8109
vdtCCAborted TRAP-TYPE
    ENTERPRISE vdTraps
    VARIABLES
        {atAdpNumber,vdNumber,isRemote}
    DESCRIPTION "CC aborted on Adapter -$1  VD Target -$2 Remote VD -$3"
    --#TYPE "LSI SAS Trap: CC aborted"
	--#SUMMARY "CC aborted on Adapter -%d  VD Target -%d Remote VD -%d"
	--#ARGUMENTS {0,1,2}
	--#SEVERITY INFORMATIONAL
	--#GENERIC 6
	--#CATEGORY "Error Events"
	--#STATE OPERATIONAL
    ::= 8110
vdtCCCompCor TRAP-TYPE
    ENTERPRISE vdTraps
    VARIABLES
        {atAdpNumber,vdNumber,isRemote}
    DESCRIPTION "CC completed with correction on Adapter -$1  VD Target -$2 Remote VD -$3"
    --#TYPE "LSI SAS Trap: CC completed with correction"
	--#SUMMARY "CC completed with correction on Adapter -%d  VD Target -%d Remote VD -%d"
	--#ARGUMENTS {0,1,2}
	--#SEVERITY INFORMATIONAL
	--#GENERIC 6
	--#CATEGORY "Error Events"
	--#STATE OPERATIONAL
    ::= 8111
vdtInitAborted TRAP-TYPE
    ENTERPRISE vdTraps
    VARIABLES
        {atAdpNumber,vdNumber,isRemote}
    DESCRIPTION "Initialization aborted on Adapter -$1  VD Target -$2 Remote VD -$3"
    --#TYPE "LSI SAS Trap: Initialization aborted"
	--#SUMMARY "Initialization aborted on Adapter -%d  VD Target -%d Remote VD -%d"
	--#ARGUMENTS {0,1,2}
	--#SEVERITY INFORMATIONAL
	--#GENERIC 6
	--#CATEGORY "Error Events"
	--#STATE OPERATIONAL
    ::= 8112
vdtInitFailed TRAP-TYPE
    ENTERPRISE vdTraps
    VARIABLES
        {atAdpNumber,vdNumber,isRemote}
    DESCRIPTION "Initialization failed on Adapter -$1  VD Target -$2 Remote VD -$3"
    --#TYPE "LSI SAS Trap: Initialization failed"
	--#SUMMARY "Initialization failed on Adapter -%d  VD Target-%d Remote VD -%d"
	--#ARGUMENTS {0,1,2}
	--#SEVERITY CRITICAL
	--#GENERIC 6
	--#CATEGORY "Error Events"
	--#STATE OPERATIONAL
    ::= 8113
vdtInitCompleted TRAP-TYPE
    ENTERPRISE vdTraps
    VARIABLES
        {atAdpNumber,vdNumber,isRemote}
    DESCRIPTION "Initialization completed on Adapter -$1  VD Target -$2 Remote VD -$3"
    --#TYPE "LSI SAS Trap: Initialization completed"
	--#SUMMARY "Initialization completed on Adapter -%d  VD Target -%d Remote VD -%d"
	--#ARGUMENTS {0,1,2}
	--#SEVERITY INFORMATIONAL
	--#GENERIC 6
	--#CATEGORY "Error Events"
	--#STATE OPERATIONAL
    ::= 8114
vdtInitFastStarted TRAP-TYPE
    ENTERPRISE vdTraps
    VARIABLES
        {atAdpNumber,vdNumber,isRemote}
    DESCRIPTION "Fast Initialization started on Adapter -$1  VD Target -$2 Remote VD -$3"
    --#TYPE "LSI SAS Trap: Fast Initialization started"
	--#SUMMARY "Fast Initialization started on Adapter -%d  VD Target -%d Remote VD -%d"
	--#ARGUMENTS {0,1,2}
	--#SEVERITY INFORMATIONAL
	--#GENERIC 6
	--#CATEGORY "Error Events"
	--#STATE OPERATIONAL
    ::= 8115
vdtInitFullStarted TRAP-TYPE
    ENTERPRISE vdTraps
    VARIABLES
        {atAdpNumber,vdNumber,isRemote}
    DESCRIPTION "Full Initialization started on Adapter-$1 VD Target-$2 Remote VD -$3"
    --#TYPE "LSI SAS Trap: Full Initialization started"
	--#SUMMARY "Full Initialization started on Adapter -%d  VD Target -%d Remote VD -%d"
	--#ARGUMENTS {0,1,2}
	--#SEVERITY INFORMATIONAL
	--#GENERIC 6
	--#CATEGORY "Error Events"
	--#STATE OPERATIONAL
    ::= 8116
vdtReconStarted TRAP-TYPE
    ENTERPRISE vdTraps
    VARIABLES
        {atAdpNumber,vdNumber,isRemote}
    DESCRIPTION "Reconstruction started on Adapter-$1 VD Target-$2 Remote VD -$3"
    --#TYPE "LSI SAS Trap: Reconstruction started"
	--#SUMMARY "Reconstruction started on Adapter -%d  VD Target -%d Remote VD -%d"
	--#ARGUMENTS {0,1,2}
	--#SEVERITY INFORMATIONAL
	--#GENERIC 6
	--#CATEGORY "Error Events"
	--#STATE OPERATIONAL
    ::= 8117
vdtReconCompleted TRAP-TYPE
    ENTERPRISE vdTraps
    VARIABLES
        {atAdpNumber,vdNumber,isRemote}
    DESCRIPTION "Reconstruction completed on Adapter -$1  VD Target -$2 Remote VD -$3"
    --#TYPE "LSI SAS Trap: Reconstruction completed"
	--#SUMMARY "Reconstruction completed on Adapter -%d  VD Target -%d Remote VD -%d"
	--#ARGUMENTS {0,1,2}
	--#SEVERITY INFORMATIONAL
	--#GENERIC 6
	--#CATEGORY "Error Events"
	--#STATE OPERATIONAL
    ::= 8118
vdtReconResumed TRAP-TYPE
    ENTERPRISE vdTraps
    VARIABLES
        {atAdpNumber,vdNumber,isRemote}
    DESCRIPTION "Reconstruction resumed on Adapter -$1  VD Target -$2 Remote VD -$3"
    --#TYPE "LSI SAS Trap: Reconstruction resumed"
	--#SUMMARY "Reconstruction resumed on Adapter -%d  VD Target -%d Remote VD -%d"
	--#ARGUMENTS {0,1,2}
	--#SEVERITY INFORMATIONAL
	--#GENERIC 6
	--#CATEGORY "Error Events"
	--#STATE OPERATIONAL
    ::= 8119
vdtReconStopped TRAP-TYPE
    ENTERPRISE vdTraps
    VARIABLES
        {atAdpNumber,vdNumber,isRemote}
    DESCRIPTION "Reconstruction stopped on Adapter-$1 VD Target-$2 Remote VD -$3"
    --#TYPE "LSI SAS Trap: Reconstruction stopped"
	--#SUMMARY "Reconstruction stopped on Adapter -%d  VD Target -%d Remote VD -%d"
	--#ARGUMENTS {0,1,2}
	--#SEVERITY FATAL
	--#GENERIC 6
	--#CATEGORY "Error Events"
	--#STATE OPERATIONAL
    ::= 8120

vdtStateChange TRAP-TYPE
    ENTERPRISE vdTraps
    VARIABLES
        {atAdpNumber,vdNumber, vdOldState, vdNewState}
    DESCRIPTION "VD state changed on Adapter -$1  VD Target -$2 from $3 to $4"
    --#TYPE "LSI SAS Trap: VD state changed"
	--#SUMMARY "VD state changed on Adapter -%d  VD Target -%d from %d to %d"
	--#ARGUMENTS {0,1,2,3}
	--#SEVERITY INFORMATIONAL
	--#GENERIC 6
	--#CATEGORY "Error Events"
	--#STATE OPERATIONAL
    ::= 8121
vdtCreated TRAP-TYPE
    ENTERPRISE vdTraps
    VARIABLES
        {atAdpNumber,vdNumber,isRemote}
    DESCRIPTION "A new VD created on Adapter -$1  VD Target -$2 Remote VD -$3"
    --#TYPE "LSI SAS Trap: New VD created"
	--#SUMMARY "A new VD created on Adapter -%d  VD Target -%d Remote VD -%d"
	--#ARGUMENTS {0,1,2}
	--#SEVERITY INFORMATIONAL
	--#GENERIC 6
	--#CATEGORY "Error Events"
	--#STATE OPERATIONAL
    ::= 8122
vdtDeleted TRAP-TYPE
    ENTERPRISE vdTraps
    VARIABLES
        {atAdpNumber,vdNumber,isRemote}
    DESCRIPTION "A VD deleted on Adapter -$1  VD Target -$2 Remote VD -$3" 
    --#TYPE "LSI SAS Trap: VD deleted"
	--#SUMMARY "A VD deleted on Adapter -%d  VD Target -%d Remote VD -%d"
	--#ARGUMENTS {0,1,2}
	--#SEVERITY INFORMATIONAL
	--#GENERIC 6
	--#CATEGORY "Error Events"
	--#STATE OPERATIONAL
    ::= 8123


vdtSecured TRAP-TYPE
    ENTERPRISE vdTraps
    VARIABLES
        {atAdpNumber,vdNumber,isRemote}
    DESCRIPTION "VD is now secured. Adapter -$1 VD Targt -$2 Remote VD -$3" 
    --#TYPE "LSI SAS Trap: VD is now secured"
	--#SUMMARY "VD is now secured. Adapter -%d VD Target -%d Remote VD -%d"
	--#ARGUMENTS {0,1,2}
	--#SEVERITY INFORMATIONAL
	--#GENERIC 6
	--#CATEGORY "Error Events"
	--#STATE OPERATIONAL
    ::= 8124
    
vdtPartiallySecured TRAP-TYPE
    ENTERPRISE vdTraps
    VARIABLES
        {atAdpNumber,vdNumber,isRemote}
    DESCRIPTION "VD is partially secured. Adapter -$1 VD Targt -$2 Remote VD -$3" 
    --#TYPE "LSI SAS Trap: VD is partially secured"
	--#SUMMARY "VD is partially secured. Adapter -%d VD Target -%d Remote VD -%d"
	--#ARGUMENTS {0,1,2}
	--#SEVERITY WARNING
	--#GENERIC 6
	--#CATEGORY "Error Events"
	--#STATE OPERATIONAL
    ::= 8125


vdtBbmLogCleared TRAP-TYPE
    ENTERPRISE vdTraps
    VARIABLES
        {atAdpNumber,vdNumber,isRemote}	
    DESCRIPTION "VD bad block table cleared on Adapter -$1 VD Targt -$2 Remote VD -$3" 
    --#TYPE "LSI SAS Trap: VD bad block table is cleared"
	--#SUMMARY "VD bad block table cleared on Adapter -%d VD Target -%d Remote VD -%d"
	--#ARGUMENTS {0,1,2}
	--#SEVERITY WARNING
	--#GENERIC 6
	--#CATEGORY "Error Events"
	--#STATE OPERATIONAL
    ::= 8126

vdtERASEAborted TRAP-TYPE
    ENTERPRISE vdTraps
    VARIABLES { atAdpNumber,vdNumber,isRemote}
    DESCRIPTION "LD Erase aborted on aborted on Adapter -$1  VD Target -$2 Remote VD -$3"
    --#TYPE "LSI SAS Trap: LD Erase aborted"
	--#SUMMARY "LD Erase aborted on Adapter -%d  VD Target -%d Remote VD -%d"
	--#ARGUMENTS {0,1,2}
	--#SEVERITY INFORMATIONAL
	--#GENERIC 6
	--#CATEGORY "Error Events"
	--#STATE OPERATIONAL
    ::= 8127

vdtERASECompleted TRAP-TYPE
    ENTERPRISE vdTraps
    VARIABLES { atAdpNumber,vdNumber,isRemote}
    DESCRIPTION "LD Erase completed on Adapter -$1 VD Target -$2 Remote VD -$3"
    --#TYPE "LSI SAS Trap: LD Erase completed"
	--#SUMMARY "LD Erase completed on Adapter -%d  VD Target -%d Remote VD -%d"
	--#ARGUMENTS {0,1,2}
	--#SEVERITY INFORMATIONAL
	--#GENERIC 6
	--#CATEGORY "Error Events"
	--#STATE OPERATIONAL
    ::= 8128

vdtERASEFailed TRAP-TYPE
    ENTERPRISE vdTraps
    VARIABLES { atAdpNumber,vdNumber,isRemote}
    DESCRIPTION "LD Erase failed on Adapter -$1  VD Target -$2 Remote VD -$3"
    --#TYPE "LSI SAS Trap: LD Erase failed"
	--#SUMMARY "LD Erase failed on Adapter -%d  VD Target -%d Remote VD -%d"
	--#ARGUMENTS {0,1,2}
	--#SEVERITY CRITICAL
	--#GENERIC 6
	--#CATEGORY "Error Events"
	--#STATE OPERATIONAL
    ::= 8129

vdtERASEStarted TRAP-TYPE
    ENTERPRISE vdTraps
    VARIABLES { atAdpNumber,vdNumber,isRemote}
    DESCRIPTION "LD Erase started on Adapter -$1  VD Target -$2 Remote VD -$3"
    --#TYPE "LSI SAS Trap: LD Erase started"
	--#SUMMARY "LD Erase started on Adapter -%d  VD Target -%d Remote VD -%d"
	--#ARGUMENTS {0,1,2}
	--#SEVERITY INFORMATIONAL
	--#GENERIC 6
	--#CATEGORY "Error Events"
	--#STATE OPERATIONAL
    ::= 8130

vdtSSCDISASSOCIATEStarted TRAP-TYPE
    ENTERPRISE vdTraps
    VARIABLES { atAdpNumber,vdNumber,isRemote}
    DESCRIPTION "CacheCade(TM) disassociate started on Adapter -$1  VD Target -$2 Remote VD -$3"
    --#TYPE "LSI SAS Trap: CacheCade(TM) disassociate started"
	--#SUMMARY "CacheCade(TM) disassociate started on Adapter -%d  VD Target -%d Remote VD -%d"
	--#ARGUMENTS {0,1,2}
	--#SEVERITY INFORMATIONAL
	--#GENERIC 6
	--#CATEGORY "Error Events"
	--#STATE OPERATIONAL
    ::= 8131

vdtSSCDISASSOCIATECompleted TRAP-TYPE
    ENTERPRISE vdTraps
    VARIABLES { atAdpNumber,vdNumber,isRemote}
    DESCRIPTION "CacheCade(TM) disassociate completed on Adapter -$1  VD Target -$2 Remote VD -$3"
    --#TYPE "LSI SAS Trap: CacheCade(TM) disassociate completed"
	--#SUMMARY "CacheCade(TM) disassociate completed on Adapter -%d  VD Target -%d Remote VD -%d"
	--#ARGUMENTS {0,1,2}
	--#SEVERITY INFORMATIONAL
	--#GENERIC 6
	--#CATEGORY "Error Events"
	--#STATE OPERATIONAL
    ::= 8132

vdtSSCDISASSOCIATEFailed TRAP-TYPE
    ENTERPRISE vdTraps
    VARIABLES { atAdpNumber,vdNumber,isRemote}
    DESCRIPTION "CacheCade(TM) disassociate failed on Adapter -$1  VD Target -$2 Remote VD -$3"
    --#TYPE "LSI SAS Trap: CacheCade(TM) disassociate failed"
	--#SUMMARY "CacheCade(TM) disassociate failed on Adapter -%d  VD Target -%d Remote VD -%d"
	--#ARGUMENTS {0,1,2}
	--#SEVERITY CRITICAL
	--#GENERIC 6
	--#CATEGORY "Error Events"
	--#STATE OPERATIONAL
    ::= 8133

vdtSSCDISASSOCIATEAborted TRAP-TYPE
    ENTERPRISE vdTraps
    VARIABLES { atAdpNumber,vdNumber,isRemote}
    DESCRIPTION "CacheCade(TM) disassociate aborted by user on Adapter -$1  VD Target -$2 Remote VD -$3"
    --#TYPE "LSI SAS Trap: CacheCade(TM) disassociate aborted"
	--#SUMMARY "CacheCade(TM) disassociate aborted by user on Adapter -%d  VD Target -%d Remote VD -%d"
	--#ARGUMENTS {0,1,2}
	--#SEVERITY INFORMATIONAL
	--#GENERIC 6
	--#CATEGORY "Error Events"
	--#STATE OPERATIONAL
    ::= 8134

vdtACCESSBLOCKEDSSCOFFLINE TRAP-TYPE
    ENTERPRISE vdTraps
    VARIABLES { atAdpNumber,vdNumber,isRemote}
    DESCRIPTION "Access blocked as cached data in CacheCade(TM) is unavailable on Adapter -$1  VD Target -$2 Remote VD -$3"
    --#TYPE "LSI SAS Trap: ACCESS BLOCKED SSC OFFLINE"
	--#SUMMARY "access blocked as cached data in CacheCade(TM) is unavailable on Adapter -%d  VD Target -%d Remote VD -%d"
	--#ARGUMENTS {0,1,2}
	--#SEVERITY FATAL
	--#GENERIC 6
	--#CATEGORY "Error Events"
	--#STATE OPERATIONAL
    ::= 8135
	
haLDIsRemote TRAP-TYPE
    ENTERPRISE vdTraps
    VARIABLES { atAdpNumber,vdNumber,isRemote}
    DESCRIPTION "Peer controller now manages LD on Adapter -$1  VD Target -$2 Remote VD -$3"
    --#TYPE "LSI SAS Trap: LD is managed by peer controller"
	--#SUMMARY "Peer controller now manages VD on Adapter -%d  VD Target -%d Remote VD -%d"
	--#ARGUMENTS {0,1,2}
	--#SEVERITY INFORMATIONAL
	--#GENERIC 6
	--#CATEGORY "Error Events"
	--#STATE OPERATIONAL
    ::= 8136
	
haLDIsLocal TRAP-TYPE
    ENTERPRISE vdTraps
    VARIABLES { atAdpNumber,vdNumber,isRemote}
    DESCRIPTION "Local controller now manages VD on Adapter -$1  VD Target -$2 Remote VD -$3"
    --#TYPE "LSI SAS Trap: LD is managed by local controller"
	--#SUMMARY "Local controller now manages VD on Adapter -%d  VD Target -%d Remote VD -%d"
	--#ARGUMENTS {0,1,2}
	--#SEVERITY INFORMATIONAL
	--#GENERIC 6
	--#CATEGORY "Error Events"
	--#STATE OPERATIONAL
    ::= 8137
	
haLDTargetIDConflict TRAP-TYPE
    ENTERPRISE vdTraps
    VARIABLES { atAdpNumber,vdNumber,isRemote}
    DESCRIPTION "Target ID conflict detected. VD on Adapter -$1  VD Target -$2 Remote VD -$3 access is restricted from Peer controller"
    --#TYPE "LSI SAS Trap: LD has a conflict in HA domain"
	--#SUMMARY "Target ID conflict detected. VD on Adapter -%d  VD Target -%d Remote VD -%d access is restricted from Peer controller"
	--#ARGUMENTS {0,1,2}
	--#SEVERITY WARNING
	--#GENERIC 6
	--#CATEGORY "Error Events"
	--#STATE OPERATIONAL
    ::= 8138
	
haLDAccessShared TRAP-TYPE
    ENTERPRISE vdTraps
    VARIABLES { atAdpNumber,vdNumber,isRemote}
    DESCRIPTION "Shared access set for VD on Adapter -$1  VD Target -$2 Remote VD -$3"
    --#TYPE "LSI SAS Trap: LD access is shared"
	--#SUMMARY "Shared access set for VD on Adapter -%d  VD Target -%d Remote VD -%d"
	--#ARGUMENTS {0,1,2}
	--#SEVERITY INFORMATIONAL
	--#GENERIC 6
	--#CATEGORY "Error Events"
	--#STATE OPERATIONAL
    ::= 8139
	
haLDAccessExclusive TRAP-TYPE
    ENTERPRISE vdTraps
    VARIABLES { atAdpNumber,vdNumber,isRemote}
    DESCRIPTION "Exclusive access set for VD on Adapter -$1  VD Target -$2 Remote VD -$3"
    --#TYPE "LSI SAS Trap: LD access is exclusive"
	--#SUMMARY "Exclusive access set for VD on Adapter -%d  VD Target -%d Remote VD -%d"
	--#ARGUMENTS {0,1,2}
	--#SEVERITY INFORMATIONAL
	--#GENERIC 6
	--#CATEGORY "Error Events"
	--#STATE OPERATIONAL
    ::= 8140

haLDIncompatible TRAP-TYPE
    ENTERPRISE vdTraps
    VARIABLES { atAdpNumber,vdNumber,isRemote}  
    DESCRIPTION "Adapter -$1 VD Target -$2 Remote VD -$3 is incompatible in the HA domain"
    --#TYPE "LSI SAS Trap: LD is incompatible in the HA domain"
	--#SUMMARY "Adapter -%d  VD Target -%d Remote VD -%d is incompatible in the HA domain"
	--#ARGUMENTS {0,1,2}
	--#SEVERITY WARNING
	--#GENERIC 6
	--#CATEGORY "Error Events"
	--#STATE OPERATIONAL
    ::= 8141
	
vdAccessBlockedPeerUnavailable TRAP-TYPE
    ENTERPRISE vdTraps
    VARIABLES { atAdpNumber,vdNumber,isRemote}  
    DESCRIPTION "Cached data from peer controller is unavailable. LD on Adapter -$1 VD Target -$2 Remote VD -$3 access policy is set to Blocked"
    --#TYPE "LSI SAS Trap: LD access blocked as cached data from peer controller is unavailable"
	--#SUMMARY "Cached data from peer controller is unavailable. LD on Adapter -%d  VD Target -%d Remote VD -%d access policy is set to Blocked"
	--#ARGUMENTS {0,1,2}
	--#SEVERITY FATAL
	--#GENERIC 6
	--#CATEGORY "Error Events"
	--#STATE OPERATIONAL
    ::= 8142	
	
haLDCompatible TRAP-TYPE
    ENTERPRISE vdTraps
    VARIABLES { atAdpNumber,vdNumber,isRemote}  
    DESCRIPTION "Adapter -$1 VD Target -$2 Remote VD -$3 is compatible in the HA domain"
    --#TYPE "LSI SAS Trap: LD is compatible in the HA domain"
	--#SUMMARY "Adapter -%d  VD Target -%d Remote VD -%d is compatible in the HA domain"
	--#ARGUMENTS {0,1,2}
	--#SEVERITY INFORMATIONAL
	--#GENERIC 6
	--#CATEGORY "Error Events"
	--#STATE OPERATIONAL
    ::= 8143

vdPropChanged TRAP-TYPE
    ENTERPRISE vdTraps
    VARIABLES { atAdpNumber,vdNumber,vdNewAccessPolicy,vdNewcurrentCachePolicy,vdNewcurrentPSPolicy,vdNewdefaultCachePolicy,vdNewdefaultPSPolicy,vdNewdiskCachePolicy,vdNewname}  
    DESCRIPTION "Adapter -$1 VD Target -$2 Properties changed. Access policy to $3, currentCachePolicy to $4, currentPSPolicy to $5, defaultCachePolicy to $6, defaultPSPolicy to $7, diskCachePolicy to $8, name to $9"
    --#TYPE "LSI SAS Trap: VD properties changed"
    --#SUMMARY "Adapter -$1 VD Target -$2 Properties changed. Access policy to $3, currentCachePolicy to $4, currentPSPolicy to $5, defaultCachePolicy to $6, defaultPSPolicy to $7, diskCachePolicy to $8, name to $9"
    --#ARGUMENTS {0,1,2,3,4,5,6,7,8}
    --#SEVERITY INFORMATIONAL
    --#GENERIC 6
    --#CATEGORY "Error Events"
    --#STATE OPERATIONAL
    ::= 8144
	
---------------vd trap----------
pdTraps                      OBJECT IDENTIFIER ::= {lsiRAIDServer 8}

pdID                 OBJECT-TYPE
    SYNTAX                      INTEGER
    ACCESS                      read-only
    STATUS                      optional
    DESCRIPTION                 "Device ID for which Trap is generated."
    ::= { pdTraps 1201 }
pdEncIndex                 OBJECT-TYPE
    SYNTAX                      INTEGER
    ACCESS                      read-only
    STATUS                      optional
    DESCRIPTION                 "Enclosure index(0 means not within an enclosure) for which Trap is generated."
    ::= { pdTraps 1202 }
pdSlotNo                 OBJECT-TYPE
    SYNTAX                      INTEGER
    ACCESS                      read-only
    STATUS                      optional
    DESCRIPTION                 "Slot no for the enclosure"
    ::= { pdTraps 1203 }
pdNewState            OBJECT-TYPE
    SYNTAX                      INTEGER
    ACCESS                      read-only
    STATUS                      optional
    DESCRIPTION                 "Physical Drive state. Values are: unconfigured-good(0),unconfigured-bad(1),hot-spare(2),offline(16),failed(17),rebuild(20),online(24),copyback(32),system(64)"
    ::= { pdTraps 1204 }
pdOldState            OBJECT-TYPE
    SYNTAX                      INTEGER
    ACCESS                      read-only
    STATUS                      optional
    DESCRIPTION                 "Physical Drive state. Values are: unconfigured-good(0),unconfigured-bad(1),hot-spare(2),offline(16),failed(17),rebuild(20),online(24),copyback(32),system(64)"
    ::= { pdTraps 1205 }
pdEnclDeviceId	       OBJECT-TYPE                  
    SYNTAX                      INTEGER
    ACCESS                      read-only
    STATUS                      optional
    DESCRIPTION                 "Enclosure Device ID for which Trap is generated."
    ::= { pdTraps 1206 }
pdSASAdd	               OBJECT-TYPE                 
    SYNTAX                      DisplayString
    ACCESS                      read-only
    STATUS                      optional
    DESCRIPTION                 "Device SAS addresses. Comma separeted for multiple address."
    ::= { pdTraps 1207 }

pdPath	               OBJECT-TYPE                     
    SYNTAX                      INTEGER
    ACCESS                      read-only
    STATUS                      optional
    DESCRIPTION                 "PD path."
    ::= { pdTraps 1208 }

pdFRU	               OBJECT-TYPE                 
    SYNTAX                      DisplayString
    ACCESS                      read-only
    STATUS                      optional
    DESCRIPTION                 "PD FRU for which trap is generated."
    ::= { pdTraps 1209 }

pdNewPowerState        		OBJECT-TYPE
    SYNTAX                      INTEGER
    ACCESS                      read-only
    STATUS                      optional
    DESCRIPTION                 "New Power Status Of the Device.Values are device is active(0),device is stopped(1),device is transitioning between power states(255)"
    ::= { pdTraps 1210 }

-- Following are the trap definitions, which use variables defined
-- within the object lsiRaidMib.

pdtClearAborted TRAP-TYPE
    ENTERPRISE pdTraps
    VARIABLES { atAdpNumber,pdID,pdEncIndex,pdSlotNo }
    DESCRIPTION "Physical Drive Clear aborted on Adapter -$1  Dev -$2  Enc -$3  Slot -$4"
    --#TYPE "LSI SAS Trap: Physical Drive Clear aborted"
	--#SUMMARY "Physical Drive Clear aborted on Adapter -%d  Dev -%d  Enc -%d  Slot-%d"
	--#ARGUMENTS {0,1,2,3}
	--#SEVERITY INFORMATIONAL
	--#GENERIC 6
	--#CATEGORY "Error Events"
	--#STATE OPERATIONAL
    ::= 8201
pdtClearFailed TRAP-TYPE
    ENTERPRISE pdTraps
    VARIABLES { atAdpNumber,pdID,pdEncIndex,pdSlotNo }
    DESCRIPTION " Physical Drive Clear failed on Adapter -$1  Dev -$2  Enc -$3  Slot -$4"
    --#TYPE "LSI SAS Trap: Physical Drive Clear failed"
	--#SUMMARY "Physical Drive Clear failed on Adapter -%d  Dev -%d  Enc -%d  Slot -%d"
	--#ARGUMENTS {0,1,2,3}
	--#SEVERITY CRITICAL
	--#GENERIC 6
	--#CATEGORY "Error Events"
	--#STATE OPERATIONAL
    ::= 8202
pdtClearStarted TRAP-TYPE
    ENTERPRISE pdTraps
    VARIABLES { atAdpNumber,pdID,pdEncIndex,pdSlotNo }
    DESCRIPTION " Physical Drive Clear started on Adapter -$1  Dev -$2  Enc -$3  Slot -$4"
    --#TYPE "LSI SAS Trap: Physical Drive Clear started"
	--#SUMMARY "Physical Drive Clear started on Adapter -%d  Dev -%d  Enc -%d  Slot -%d"
	--#ARGUMENTS {0,1,2,3}
	--#SEVERITY INFORMATIONAL
	--#GENERIC 6
	--#CATEGORY "Error Events"
	--#STATE OPERATIONAL
    ::= 8203
pdtClearCompleted TRAP-TYPE
    ENTERPRISE pdTraps
    VARIABLES { atAdpNumber,pdID,pdEncIndex,pdSlotNo }
    DESCRIPTION " Physical Drive Clear completed on Adapter -$1  Dev -$2  Enc -$3  Slot -$4"
    --#TYPE "LSI SAS Trap: Physical Drive Clear completed"
	--#SUMMARY "Physical Drive Clear completed on Adapter -%d  Dev -%d  Enc -%d  Slot -%d"
	--#ARGUMENTS {0,1,2,3}
	--#SEVERITY INFORMATIONAL
	--#GENERIC 6
	--#CATEGORY "Error Events"
	--#STATE OPERATIONAL
    ::= 8204
pdtError TRAP-TYPE
    ENTERPRISE pdTraps
    VARIABLES
        {atAdpNumber,pdID,pdEncIndex,pdSlotNo}
    DESCRIPTION "Error occurred on Adapter -$1  Dev -$2  Enc -$3  Slot -$4"
    --#TYPE "LSI SAS Trap: Error occurred"
	--#SUMMARY "Error occurred on Adapter -%d  Dev -%d  Enc -%d  Slot -%d"
	--#ARGUMENTS {0,1,2,3}
	--#SEVERITY WARNING
	--#GENERIC 6
	--#CATEGORY "Error Events"
	--#STATE OPERATIONAL
    ::= 8205
pdtFormatStart TRAP-TYPE
    ENTERPRISE pdTraps
    VARIABLES
        {atAdpNumber,pdID,pdEncIndex,pdSlotNo}
    DESCRIPTION " Physical Drive format started on Adapter -$1  Dev -$2  Enc -$3  Slot -$4"
    --#TYPE "LSI SAS Trap: Physical Drive Format started"
	--#SUMMARY "Physical Drive Format started on Adapter -%d  Dev -%d  Enc -%d  Slot -%d"
	--#ARGUMENTS {0,1,2,3}
	--#SEVERITY INFORMATIONAL
	--#GENERIC 6
	--#CATEGORY "Error Events"
	--#STATE OPERATIONAL
    ::= 8206
pdtFormatCompleted TRAP-TYPE
    ENTERPRISE pdTraps
    VARIABLES
        {atAdpNumber,pdID,pdEncIndex,pdSlotNo}
    DESCRIPTION " Physical Drive format completed on Adapter -$1  Dev -$2  Enc -$3  Slot -$4" 
    --#TYPE "LSI SAS Trap: Physical Drive Format completed"
	--#SUMMARY "Physical Drive Format completed on Adapter -%d  Dev -%d  Enc -%d  Slot -%d"
	--#ARGUMENTS {0,1,2,3}
	--#SEVERITY INFORMATIONAL
	--#GENERIC 6
	--#CATEGORY "Error Events"
	--#STATE OPERATIONAL
    ::= 8207
pdtInserted TRAP-TYPE
    ENTERPRISE pdTraps
    VARIABLES
        {atAdpNumber,pdID,pdEncIndex,pdSlotNo}
    DESCRIPTION "PD inserted on Adapter -$1  Dev -$2  Enc -$3  Slot -$4" 
    --#TYPE "LSI SAS Trap: Physical Drive inserted"
	--#SUMMARY "PD inserted on Adapter -%d  Dev -%d  Enc -%d  Slot -%d"
	--#ARGUMENTS {0,1,2,3}
	--#SEVERITY INFORMATIONAL
	--#GENERIC 6
	--#CATEGORY "Error Events"
	--#STATE OPERATIONAL
    ::= 8208
pdtRblAborted TRAP-TYPE
    ENTERPRISE pdTraps
    VARIABLES
        {atAdpNumber,pdID,pdEncIndex,pdSlotNo}
    DESCRIPTION "Rebuild aborted on Adapter -$1  Dev -$2  Enc -$3  Slot -$4"
    --#TYPE "LSI SAS Trap: Rebuild aborted"
	--#SUMMARY "Rebuild aborted on Adapter -%d  Dev -%d  Enc -%d  Slot -%d"
	--#ARGUMENTS {0,1,2,3}
	--#SEVERITY INFORMATIONAL
	--#GENERIC 6
	--#CATEGORY "Error Events"
	--#STATE OPERATIONAL
    ::= 8209
pdtRblCompleted TRAP-TYPE
    ENTERPRISE pdTraps
    VARIABLES
        {atAdpNumber,pdID,pdEncIndex,pdSlotNo}
    DESCRIPTION "Rebuild completed on Adapter -$1  Dev -$2  Enc -$3  Slot -$4"
    --#TYPE "LSI SAS Trap: Rebuild completed"
	--#SUMMARY "Rebuild completed on Adapter -%d  Dev -%d  Enc -%d  Slot -%d"
	--#ARGUMENTS {0,1,2,3}
	--#SEVERITY INFORMATIONAL
	--#GENERIC 6
	--#CATEGORY "Error Events"
	--#STATE OPERATIONAL
    ::= 8210
pdtRblFailedBS TRAP-TYPE
    ENTERPRISE pdTraps
    VARIABLES
        {atAdpNumber,pdID,pdEncIndex,pdSlotNo}
    DESCRIPTION "Rebuild failed(bad source) on Adapter -$1  Dev -$2  Enc -$3  Slot -$4"
    --#TYPE "LSI SAS Trap: Rebuild failed(bad source)"
	--#SUMMARY "Rebuild failed(bad source) on Adapter -%d  Dev -%d  Enc -%d  Slot -%d"
	--#ARGUMENTS {0,1,2,3}
	--#SEVERITY CRITICAL
	--#GENERIC 6
	--#CATEGORY "Error Events"
	--#STATE OPERATIONAL
    ::= 8211
pdtRblFailedBT TRAP-TYPE
    ENTERPRISE pdTraps
    VARIABLES
        {atAdpNumber,pdID,pdEncIndex,pdSlotNo}
    DESCRIPTION "Rebuild failed(bad target) on Adapter -$1  Dev -$2  Enc -$3  Slot -$4"
    --#TYPE "LSI SAS Trap: Rebuild failed(bad target)"
	--#SUMMARY "Rebuild failed(bad target) on Adapter -%d  Dev -%d  Enc -%d  Slot -%d"
	--#ARGUMENTS {0,1,2,3}
	--#SEVERITY CRITICAL
	--#GENERIC 6
	--#CATEGORY "Error Events"
	--#STATE OPERATIONAL
    ::= 8212
pdtRblStart TRAP-TYPE
    ENTERPRISE pdTraps
    VARIABLES
        {atAdpNumber,pdID,pdEncIndex,pdSlotNo}
    DESCRIPTION "Rebuild started on Adapter -$1  Dev -$2  Enc -$3  Slot -$4"
    --#TYPE "LSI SAS Trap: Rebuild started"
	--#SUMMARY "Rebuild started on Adapter -%d  Dev -%d  Enc -%d  Slot -%d"
	--#ARGUMENTS {0,1,2,3}
	--#SEVERITY INFORMATIONAL
	--#GENERIC 6
	--#CATEGORY "Error Events"
	--#STATE OPERATIONAL
    ::= 8213
pdtRblResumed TRAP-TYPE
    ENTERPRISE pdTraps
    VARIABLES
        {atAdpNumber,pdID,pdEncIndex,pdSlotNo}
    DESCRIPTION "Rebuild resumed on Adapter -$1  Dev -$2  Enc -$3  Slot -$4" 
    --#TYPE "LSI SAS Trap: Rebuild resumed"
	--#SUMMARY "Rebuild resumed on Adapter -%d  Dev -%d  Enc -%d  Slot -%d"
	--#ARGUMENTS {0,1,2,3}
	--#SEVERITY INFORMATIONAL
	--#GENERIC 6
	--#CATEGORY "Error Events"
	--#STATE OPERATIONAL
    ::= 8214
    
pdtRblStartA TRAP-TYPE
    ENTERPRISE pdTraps
    VARIABLES
        {atAdpNumber,pdID,pdEncIndex,pdSlotNo}
    DESCRIPTION "Rebuild started(auto) on Adapter -$1  Dev -$2  Enc -$3  Slot -$4"
    --#TYPE "LSI SAS Trap: Rebuild started(auto)"
	--#SUMMARY "Rebuild started(auto) on Adapter -%d  Dev -%d  Enc -%d  Slot -%d"
	--#ARGUMENTS {0,1,2,3}
	--#SEVERITY INFORMATIONAL
	--#GENERIC 6
	--#CATEGORY "Error Events"
	--#STATE OPERATIONAL
    ::= 8215
pdtRemoved TRAP-TYPE
    ENTERPRISE pdTraps
    VARIABLES
        {atAdpNumber,pdID,pdEncIndex,pdSlotNo}
    DESCRIPTION " Physical Drive removed on Adapter -$1  Dev -$2  Enc -$3  Slot -$4"
    --#TYPE "LSI SAS Trap: Physical Drive removed"
	--#SUMMARY "Physical Drive removed on Adapter -%d  Dev -%d  Enc -%d  Slot -%d"
	--#ARGUMENTS {0,1,2,3}
	--#SEVERITY WARNING
	--#GENERIC 6
	--#CATEGORY "Error Events"
	--#STATE OPERATIONAL
    ::= 8216
pdtStateChange TRAP-TYPE
    ENTERPRISE pdTraps
    VARIABLES
        {atAdpNumber,pdID,pdEncIndex,pdSlotNo, pdOldState, pdNewState}
    DESCRIPTION "PD state changed on Adapter -$1  Dev -$2  Enc -$3  Slot -$4  from $5 to $6"
    --#TYPE "LSI SAS Trap: PD state changed"
	--#SUMMARY "PD state changed on Adapter -%d  Dev -%d  Enc -%d  Slot -%d  from %d to %d"
	--#ARGUMENTS {0,1,2,3,4,5}
	--#SEVERITY INFORMATIONAL
	--#GENERIC 6
	--#CATEGORY "Error Events"
	--#STATE OPERATIONAL
    ::= 8217  
    
pdtRedundantPathBroken TRAP-TYPE    
    ENTERPRISE pdTraps
    VARIABLES
        {atAdpNumber,pdID,pdEncIndex,pdSlotNo,pdEnclDeviceId,pdSASAdd}
    DESCRIPTION " Redundant Path Broken For Physical Drive on Adapter -$1  Dev -$2  Enc -$3  Slot -$4 EncDevId -$5 pdSAS -$6"
    --#TYPE "LSI SAS Trap: Redundant Path Broken For Physical Drive "
	--#SUMMARY "Redundant Path For Physical Drive Broken on Adapter -%d  Dev -%d  Enc -%d  Slot -%d EncDevId -%d pdSAS -%s"
	--#ARGUMENTS {0,1,2,3,4,5}
	--#SEVERITY WARNING
	--#GENERIC 6
	--#CATEGORY "Error Events"
	--#STATE OPERATIONAL
    ::= 8218

pdtRedundantPathRestored TRAP-TYPE    
    ENTERPRISE pdTraps
    VARIABLES
        {atAdpNumber,pdID,pdEncIndex,pdSlotNo,pdEnclDeviceId,pdSASAdd}
    DESCRIPTION " Redundant Path Restored For Physical Drive on Adapter -$1  Dev -$2  Enc -$3  Slot -$4 EncDevId -$5 pdSAS -$6"
    --#TYPE "LSI SAS Trap: Redundant Path Restored For Physical Drive "
	--#SUMMARY "Redundant Path Restored For Physical Drive on Adapter -%d  Dev -%d  Enc -%d  Slot -%d EncDevId -%d pdSAS -%s"
	--#ARGUMENTS {0,1,2,3,4,5}
	--#SEVERITY INFORMATIONAL
	--#GENERIC 6
	--#CATEGORY "Error Events"
	--#STATE OPERATIONAL
    ::= 8219

pdtRedundantEnclModuleInserted TRAP-TYPE    
    ENTERPRISE pdTraps
    VARIABLES
        {atAdpNumber,pdID,pdEncIndex,pdSlotNo,pdEnclDeviceId,pdSASAdd,pdPath}
    DESCRIPTION " Redundant Encl Modul Inserted on Adapter -$1  Dev -$2  Enc -$3  Slot -$4 EncDevId -$5 pdSAS -$6 pdpath -$7 "
    --#TYPE "LSI SAS Trap: Redundant Encl Modul Inserted "
	--#SUMMARY "Redundant Encl Modul Inserted on Adapter -%d  Dev -%d  Enc -%d  Slot -%d EncDevId -%d pdSAS -%s pdpath -%d"
	--#ARGUMENTS {0,1,2,3,4,5,6}
	--#SEVERITY INFORMATIONAL
	--#GENERIC 6
	--#CATEGORY "Error Events"
	--#STATE OPERATIONAL
    ::= 8220 
pdtRedundantEnclModuleRemoved TRAP-TYPE    
    ENTERPRISE pdTraps
    VARIABLES
        {atAdpNumber,pdID,pdEncIndex,pdSlotNo,pdEnclDeviceId,pdSASAdd,pdPath}
    DESCRIPTION " Redundant Encl Modul Removed on Adapter -$1  Dev -$2  Enc -$3  Slot -$4 EncDevId -$5 pdSAS -$6 pdpath -$7"
    --#TYPE "LSI SAS Trap: Redundant Encl Modul Removed "
	--#SUMMARY "Redundant Encl Modul Removed on Adapter -%d  Dev -%d  Enc -%d  Slot -%d EncDevId -%d pdSAS -%s pdpath -%d"
	--#ARGUMENTS {0,1,2,3,4,5,6}
	--#SEVERITY INFORMATIONAL
	--#GENERIC 6
	--#CATEGORY "Error Events"
	--#STATE OPERATIONAL
    ::= 8221 

pdtFRU TRAP-TYPE    
    ENTERPRISE pdTraps
    VARIABLES
        {atAdpNumber,pdID,pdEncIndex,pdSlotNo,pdEnclDeviceId,pdFRU}
    DESCRIPTION " FRU changed on Adapter -$1  Dev -$2  Enc -$3  Slot -$4 EncDevId -$5 -FRU $6"
    --#TYPE "LSI SAS Trap: Redundant Encl Modul Removed "
	--#SUMMARY "FRU changed on Adapter -%d  Dev -%d  Enc -%d  Slot -%d EncDevId -%d pdFRU -%s"
	--#ARGUMENTS {0,1,2,3,4,5}
	--#SEVERITY INFORMATIONAL
	--#GENERIC 6
	--#CATEGORY "Error Events"
	--#STATE OPERATIONAL
    ::= 8222 


pdtSecured TRAP-TYPE
    ENTERPRISE pdTraps
    VARIABLES
        {atAdpNumber,pdID,pdEncIndex,pdSlotNo}
    DESCRIPTION "PD security activated on Adapter -$1  Dev -$2  Enc -$3  Slot -$4" 
    --#TYPE "LSI SAS Trap: PD security activated"
	--#SUMMARY "PD security activated on Adapter -%d  Dev -%d  Enc -%d  Slot -%d"
	--#ARGUMENTS {0,1,2,3}
	--#SEVERITY INFORMATIONAL
	--#GENERIC 6
	--#CATEGORY "Error Events"
	--#STATE OPERATIONAL
    ::= 8223

pdtUnsecured TRAP-TYPE
    ENTERPRISE pdTraps
    VARIABLES
        {atAdpNumber,pdID,pdEncIndex,pdSlotNo}
    DESCRIPTION "PD security disabled on Adapter -$1  Dev -$2  Enc -$3  Slot -$4" 
    --#TYPE "LSI SAS Trap: PD security disabled"
	--#SUMMARY "PD security disabled on Adapter -%d  Dev -%d  Enc -%d  Slot -%d"
	--#ARGUMENTS {0,1,2,3}
	--#SEVERITY INFORMATIONAL
	--#GENERIC 6
	--#CATEGORY "Error Events"
	--#STATE OPERATIONAL
    ::= 8224

pdtReprovisioned TRAP-TYPE
    ENTERPRISE pdTraps
    VARIABLES
        {atAdpNumber,pdID,pdEncIndex,pdSlotNo}
    DESCRIPTION "PD is reprovisioned on Adapter -$1  Dev -$2  Enc -$3  Slot -$4" 
    --#TYPE "LSI SAS Trap: PD is reprovisioned"
	--#SUMMARY "PD is reprovisioned on Adapter -%d  Dev -%d  Enc -%d  Slot -%d"
	--#ARGUMENTS {0,1,2,3}
	--#SEVERITY INFORMATIONAL
	--#GENERIC 6
	--#CATEGORY "Error Events"
	--#STATE OPERATIONAL
    ::= 8225

pdtLockKeyRekeyed TRAP-TYPE
    ENTERPRISE pdTraps
    VARIABLES
        {atAdpNumber,pdID,pdEncIndex,pdSlotNo}
    DESCRIPTION "PD security key changed on Adapter -$1  Dev -$2  Enc -$3  Slot -$4" 
    --#TYPE "LSI SAS Trap: PD security key changed"
	--#SUMMARY "PD security key changed on Adapter -%d  Dev -%d  Enc -%d  Slot -%d"
	--#ARGUMENTS {0,1,2,3}
	--#SEVERITY INFORMATIONAL
	--#GENERIC 6
	--#CATEGORY "Error Events"
	--#STATE OPERATIONAL
    ::= 8226

pdtSecurityFailure TRAP-TYPE
    ENTERPRISE pdTraps
    VARIABLES
        {atAdpNumber,pdID,pdEncIndex,pdSlotNo}
    DESCRIPTION "Security subsystem problems detected on Adapter -$1  Dev -$2  Enc -$3  Slot -$4" 
    --#TYPE "LSI SAS Trap: Security subsystem problems detected for the PD"
	--#SUMMARY "Security subsystem problems detected on Adapter -%d  Dev -%d  Enc -%d  Slot -%d"
	--#ARGUMENTS {0,1,2,3}
	--#SEVERITY FATAL
	--#GENERIC 6
	--#CATEGORY "Error Events"
	--#STATE OPERATIONAL
    ::= 8227
    

pdtPowerStateChange TRAP-TYPE
    ENTERPRISE pdTraps
    VARIABLES
        {atAdpNumber,pdID,pdEncIndex,pdSlotNo,pdNewPowerState}
    DESCRIPTION " Power State Change on Adapter -$1 Dev -$2  Enc -$3  Slot -$4 NewPowerState -$5"
    --#TYPE "LSI SAS Trap: Power State Change on the Device"
	--#SUMMARY "Power State Change on Adapter -%d  Dev -%d  Enc -%d  Slot -%d NewPowerState -%d"
	--#ARGUMENTS {0,1,2,3,4}
	--#SEVERITY INFORMATIONAL
	--#GENERIC 6
	--#CATEGORY "Error Events"
	--#STATE OPERATIONAL
    ::= 8228 
    

pdtNotSupported TRAP-TYPE
    ENTERPRISE pdTraps
    VARIABLES
        {atAdpNumber,pdID,pdEncIndex,pdSlotNo}
    DESCRIPTION "PD Not Supported on Adapter -$1 Dev -$2  Enc -$3  Slot -$4"
    --#TYPE "LSI SAS Trap: PD is not supported"
	--#SUMMARY "PD Not Supported on Adapter -%d  Dev -%d  Enc -%d  Slot -%d"
	--#ARGUMENTS {0,1,2,3}
	--#SEVERITY WARNING
	--#GENERIC 6
	--#CATEGORY "Error Events"
	--#STATE OPERATIONAL
    ::= 8229 

pdtNotCertified TRAP-TYPE
    ENTERPRISE pdTraps
    VARIABLES
        {atAdpNumber,pdID,pdEncIndex,pdSlotNo}
    DESCRIPTION "PD Not Certified on Adapter -$1 Dev -$2  Enc -$3  Slot -$4"
    --#TYPE "LSI SAS Trap: PD is not a certified drive"
	--#SUMMARY "PD Not Certified on Adapter -%d  Dev -%d  Enc -%d  Slot -%d"
	--#ARGUMENTS {0,1,2,3}
	--#SEVERITY WARNING
	--#GENERIC 6
	--#CATEGORY "Error Events"
	--#STATE OPERATIONAL
    ::= 8230 

pdtERASEAborted TRAP-TYPE
    ENTERPRISE pdTraps
    VARIABLES
        {atAdpNumber,pdID,pdEncIndex,pdSlotNo}
    DESCRIPTION "PD Erase aborted on Adapter -$1  Dev -$2  Enc -$3  Slot -$4"
    --#TYPE "LSI SAS Trap: PD Erase aborted"
	--#SUMMARY "PD Erase aborted on Adapter -%d  Dev -%d  Enc -%d  Slot -%d"
	--#ARGUMENTS {0,1,2,3}
	--#SEVERITY INFORMATIONAL
	--#GENERIC 6
	--#CATEGORY "Error Events"
	--#STATE OPERATIONAL
    ::= 8231

pdtERASECompleted TRAP-TYPE
    ENTERPRISE pdTraps
    VARIABLES
        {atAdpNumber,pdID,pdEncIndex,pdSlotNo}
    DESCRIPTION "PD Erase completed on Adapter -$1  Dev -$2  Enc -$3  Slot -$4"
    --#TYPE "LSI SAS Trap: PD Erase completed"
	--#SUMMARY "PD Erase completed on Adapter -%d  Dev -%d  Enc -%d  Slot -%d"
	--#ARGUMENTS {0,1,2,3}
	--#SEVERITY INFORMATIONAL
	--#GENERIC 6
	--#CATEGORY "Error Events"
	--#STATE OPERATIONAL
    ::= 8232

pdtERASEStarted TRAP-TYPE
    ENTERPRISE pdTraps
    VARIABLES
        {atAdpNumber,pdID,pdEncIndex,pdSlotNo}
    DESCRIPTION "PD Erase started on Adapter -$1  Dev -$2  Enc -$3  Slot -$4"
    --#TYPE "LSI SAS Trap: PD Erase started"
	--#SUMMARY "PD Erase started on Adapter -%d  Dev -%d  Enc -%d  Slot -%d"
	--#ARGUMENTS {0,1,2,3}
	--#SEVERITY INFORMATIONAL
	--#GENERIC 6
	--#CATEGORY "Error Events"
	--#STATE OPERATIONAL
    ::= 8233
    
pdtERASEFailed TRAP-TYPE
    ENTERPRISE pdTraps
    VARIABLES
        {atAdpNumber,pdID,pdEncIndex,pdSlotNo}
    DESCRIPTION "PD Erase Failed on Adapter -$1  Dev -$2  Enc -$3  Slot -$4"
    --#TYPE "LSI SAS Trap: PD Erase Failed"
	--#SUMMARY "PD Erase Failed on Adapter -%d  Dev -%d  Enc -%d  Slot -%d"
	--#ARGUMENTS {0,1,2,3}
	--#SEVERITY CRITICAL
	--#GENERIC 6
	--#CATEGORY "Error Events"
	--#STATE OPERATIONAL
    ::= 8234

haPDIsRemote TRAP-TYPE
    ENTERPRISE pdTraps
    VARIABLES
        {atAdpNumber,pdID,pdEncIndex,pdSlotNo}
    DESCRIPTION "Peer controller now manages PD on Adapter -$1  Dev -$2  Enc -$3  Slot -$4"
    --#TYPE "LSI SAS Trap: PD is managed by peer controller"
	--#SUMMARY "Peer controller now manages PD on Adapter -%d  Dev -%d  Enc -%d  Slot -%d"
	--#ARGUMENTS {0,1,2,3}
	--#SEVERITY INFORMATIONAL
	--#GENERIC 6
	--#CATEGORY "Error Events"
	--#STATE OPERATIONAL
    ::= 8235

haPDIsLocal TRAP-TYPE
    ENTERPRISE pdTraps
    VARIABLES
        {atAdpNumber,pdID,pdEncIndex,pdSlotNo}
    DESCRIPTION "Local controller now manages PD on Adapter -$1  Dev -$2  Enc -$3  Slot -$4"
    --#TYPE "LSI SAS Trap: PD is managed by local controller"
	--#SUMMARY "Local controller now manages PD on Adapter -%d  Dev -%d  Enc -%d  Slot -%d"
	--#ARGUMENTS {0,1,2,3}
	--#SEVERITY INFORMATIONAL
	--#GENERIC 6
	--#CATEGORY "Error Events"
	--#STATE OPERATIONAL
    ::= 8236	
	
pdtLOCATEStart TRAP-TYPE
    ENTERPRISE pdTraps
    VARIABLES
        {atAdpNumber,pdID}
    DESCRIPTION "Locate LED started on PD Adapter -$1 PD -$2"
    --#TYPE "LSI SAS Trap: Locate LED started on PD"
	--#SUMMARY "Local controller now manages PD on Adapter -%d  Dev -%d  Enc -%d  Slot -%d"
	--#ARGUMENTS {0,1}
	--#SEVERITY INFORMATIONAL
	--#GENERIC 6
	--#CATEGORY "Error Events"
	--#STATE OPERATIONAL
    ::= 8237	

pdtLOCATEStop TRAP-TYPE
    ENTERPRISE pdTraps
    VARIABLES
        {atAdpNumber,pdID}
    DESCRIPTION "Locate LED stopped on PD Adapter -$1 PD -$2"
    --#TYPE "LSI SAS Trap: Locate LED stopped on PD"
	--#SUMMARY "Locate LED stopped on PD Adapter -$1 PD -$2"
	--#ARGUMENTS {0,1}
	--#SEVERITY INFORMATIONAL
	--#GENERIC 6
	--#CATEGORY "Error Events"
	--#STATE OPERATIONAL
    ::= 8238	
	
	---------------Enclosure trap----------
enclTraps                      OBJECT IDENTIFIER ::= {lsiRAIDServer 9}
atPort                 OBJECT-TYPE
    SYNTAX                      INTEGER
    ACCESS                      read-only
    STATUS                      optional
    DESCRIPTION                 "Prot no."
    ::= { enclTraps 1301 }
onPHY                 OBJECT-TYPE
    SYNTAX                      INTEGER
    ACCESS                      read-only
    STATUS                      optional
    DESCRIPTION                 "PHY no"
    ::= { enclTraps 1302 }
	
widePortLinkLost TRAP-TYPE
    ENTERPRISE enclTraps
    VARIABLES
        {atAdpNumber,atPort,onPHY}
    DESCRIPTION "Link lost on SAS wide port on Adapter -$1  port -$2  PHY -$3"
    --#TYPE "LSI SAS Trap: Link lost on SAS wide port"
	--#SUMMARY "Link lost on SAS wide port on Adapter -%d  port -%d  PHY -%d"
	--#ARGUMENTS {0,1,2}
	--#SEVERITY WARNING
	--#GENERIC 6
	--#CATEGORY "Error Events"
	--#STATE OPERATIONAL
    ::= 8330
	
widePortLinkRestored TRAP-TYPE
    ENTERPRISE enclTraps
    VARIABLES
        {atAdpNumber,atPort,onPHY}
    DESCRIPTION "Link Restored on SAS wide port on Adapter -$1  port -$2  PHY -$3"
    --#TYPE "LSI SAS Trap: Link Restored on SAS wide port"
	--#SUMMARY "Link Restored on SAS wide port on Adapter -%d  port -%d  PHY -%d" 
	--#ARGUMENTS {0,1,2}
	--#SEVERITY INFORMATIONAL
	--#GENERIC 6
	--#CATEGORY "Error Events"
	--#STATE OPERATIONAL
    ::= 8331
	
	---------------PCI trap----------
pciTraps                      OBJECT IDENTIFIER ::= {lsiRAIDServer 10}
pciVendorId                     OBJECT-TYPE
    SYNTAX                      INTEGER
    ACCESS                      read-only
    STATUS                      optional
    DESCRIPTION                 "PCI VendorID"
    ::= { pciTraps 1501 }
pciDeviceId                 OBJECT-TYPE
    SYNTAX                      INTEGER
    ACCESS                      read-only
    STATUS                      optional
    DESCRIPTION                 "PCI Device ID"
    ::= { pciTraps 1502 }
pciSubVendorId                  OBJECT-TYPE
    SYNTAX                      INTEGER
    ACCESS                      read-only
    STATUS                      optional
    DESCRIPTION                 "PCI SubVendorID"
    ::= { pciTraps 1503 }
pciSubDeviceId                 OBJECT-TYPE
    SYNTAX                      INTEGER
    ACCESS                      read-only
    STATUS                      optional
    DESCRIPTION                 "PCI SubDeviceID"
    ::= { pciTraps 1504 }
	
haHwIncompatible TRAP-TYPE
    ENTERPRISE pciTraps
    DESCRIPTION "Peer Controller hardware is incompatible"
    --#TYPE "LSI SAS Trap: Controllers in the HA domain are incompatible"
	--#SUMMARY "Peer Controller hardware is incompatible"
	--#SEVERITY CRITICAL
	--#GENERIC 6
	--#CATEGORY "Error Events"
	--#STATE OPERATIONAL
    ::= 8501	
	
copyrightInfo                     OBJECT IDENTIFIER ::= {lsiRAIDServer 11}

copyright                     OBJECT-TYPE
   SYNTAX                     DisplayString (SIZE(0..63))
   ACCESS                     read-only
   STATUS                     mandatory
   DESCRIPTION                "LSI Corporation"
    ::= { copyrightInfo 1 }

END
