-- %DNP% $Id: ERICSSON-ROUTER-CPU-METER-CAP.my,v 1.1.2.4.388.5 2011/12/16 22:31:28 chiachun Exp $
-- %DNP% $Source: /cvsroot/pkt/sw/se/xc/bsd/config/snmp/mibs/Attic/ERICSSON-ROUTER-CPU-METER-CAP.my,v $
-- *****************************************************************
-- ERICSSON-ROUTER-CPU-METER-CAP    The ERICSSON-ROUTER CPU METER MIB Capabilities
--
-- Copyright (c) 1999, 2003, 2010-2011, 2015 Ericsson AB
-- All rights reserved.
-- 
-- *****************************************************************

ERICSSON-ROUTER-CPU-METER-CAP DEFINITIONS ::= BEGIN

IMPORTS
        MODULE-IDENTITY
                FROM SNMPv2-SMI
        AGENT-CAPABILITIES
                FROM SNMPv2-CONF
        eriRouterCapabilities
                FROM ERICSSON-ROUTER-SMI;

eriRouterCpuMeterCap MODULE-IDENTITY
        LAST-UPDATED    "201501141800Z" -- Jan 14, 2015
        ORGANIZATION    "Ericsson Inc."
        CONTACT-INFO
                "       Ericsson, Inc.

                Postal: 100 Headquarters Dr.
                        San Jose, CA  95134
                        USA

                 Phone: +1 408 750 5000
                   Fax: +1 408 750 5599
                "
        DESCRIPTION
                "The Agent Capabilities of the 
                CPU METER MIB (ERICSSON-ROUTER-CPU-METER-MIB).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                 to migrate RBN MIB to ERICSSON MIB."

        REVISION        "201112131800Z" -- Dec 13, 2011
        DESCRIPTION
                "Added eriRouterCpuMeterCap6."

        REVISION        "201106150000Z" -- Jun 15, 2011
        DESCRIPTION
                "Update DESCRIPTION clause of MODULE-IDENTITY
                and PRODUCT-RELEASE clause of AGENT-CAPABILITIES."

        REVISION        "201011010000Z" -- Nov 1, 2010
        DESCRIPTION
                "Modified PRODUCT-RELEASE clause for consistent naming.
                Updated CONTACT-INFO."

        REVISION        "200310140000Z" -- Oct 14, 2003
        DESCRIPTION
                "Added new OID: eriRouterCpuMeterCap5."

        REVISION        "200307070000Z" -- Jul 7, 2003
        DESCRIPTION
                "Added new OID: eriRouterCpuMeterCap4."

        REVISION        "200302110000Z" -- Feb 11, 2003
        DESCRIPTION
                "Added new OID: eriRouterCpuMeterCap3."

        REVISION        "200206260000Z" -- June 26, 2002
        DESCRIPTION
                "Updated CONTACT-INFO.  Added new OID: eriRouterCpuMeterCap2."

        REVISION        "9906162300Z" -- June 16, 1999
        DESCRIPTION
                "Initial version."
        ::= { eriRouterCapabilities 22 }

eriRouterCpuMeterCap1 AGENT-CAPABILITIES
        PRODUCT-RELEASE "AOS 3.0.X.X"
        STATUS          current
        DESCRIPTION     "ERICSSON-ROUTER-CPU-METER-MIB capabilities"
        SUPPORTS        ERICSSON-ROUTER-CPU-METER-MIB
        INCLUDES {
                    eriRouterCpuMeterStatsGroup
                 }
        ::= { eriRouterCpuMeterCap 1 }

eriRouterCpuMeterCap2 AGENT-CAPABILITIES
        PRODUCT-RELEASE "SEOS 2.3.3"
        STATUS          current
        DESCRIPTION     "ERICSSON-ROUTER-CPU-METER-MIB capabilities"
        SUPPORTS        ERICSSON-ROUTER-CPU-METER-MIB
        INCLUDES {
                    eriRouterCpuMeterStatsGroup
                 }
                 
        VARIATION       eriRouterCpuMeterFiveSecondAvg
        ACCESS          not-implemented
        DESCRIPTION
                "This object is not supported."

        VARIATION       eriRouterCpuMeterFiveMinuteAvg
        ACCESS          not-implemented
        DESCRIPTION
                "This object is not supported."
        ::= { eriRouterCpuMeterCap 2 }

eriRouterCpuMeterCap3 AGENT-CAPABILITIES
        PRODUCT-RELEASE "AOS 6.0.X.X"
        STATUS          current
        DESCRIPTION     "ERICSSON-ROUTER-CPU-METER-MIB capabilities"
        SUPPORTS        ERICSSON-ROUTER-CPU-METER-MIB
        INCLUDES {
                    eriRouterCpuMeterStatsGroup,
                    eriRouterCpuProcGroup
                 }
        ::= { eriRouterCpuMeterCap 3 }

eriRouterCpuMeterCap4 AGENT-CAPABILITIES
        PRODUCT-RELEASE "SEOS 2.5.4"
        STATUS          current
        DESCRIPTION     "ERICSSON-ROUTER-CPU-METER-MIB capabilities"
        SUPPORTS        ERICSSON-ROUTER-CPU-METER-MIB
        INCLUDES {
                    eriRouterCpuMeterStatsGroup
                 }
        ::= { eriRouterCpuMeterCap 4 }

eriRouterCpuMeterCap5 AGENT-CAPABILITIES
        PRODUCT-RELEASE "SEOS 2.6.3 [SE]; SEOS 6.3.X [SM]; SEOS 11.1.X [SSR]"
        STATUS          current
        DESCRIPTION     "ERICSSON-ROUTER-CPU-METER-MIB capabilities"
        SUPPORTS        ERICSSON-ROUTER-CPU-METER-MIB
        INCLUDES {
                    eriRouterCpuMeterStatsGroup,
                    eriRouterCpuProcGroup
                 }

        VARIATION       eriRouterCpuProcCalls
        ACCESS          not-implemented
        DESCRIPTION
                "This object is not supported."

        VARIATION       eriRouterCpuProcLongest
        ACCESS          not-implemented
        DESCRIPTION
                "This object is not supported."

        ::= { eriRouterCpuMeterCap 5 }

eriRouterCpuMeterCap6 AGENT-CAPABILITIES
        PRODUCT-RELEASE "IPOS 11.2.X"
        STATUS          current
        DESCRIPTION     "ERICSSON-ROUTER-CPU-METER-MIB capabilities"
        SUPPORTS        ERICSSON-ROUTER-CPU-METER-MIB
        INCLUDES {
                    eriRouterCpuMeterStatsGroup2,
                    eriRouterCpuProcGroup
                 }

        VARIATION       eriRouterCpuProcCalls
        ACCESS          not-implemented
        DESCRIPTION
                "This object is not supported."

        VARIATION       eriRouterCpuProcLongest
        ACCESS          not-implemented
        DESCRIPTION
                "This object is not supported."

        ::= { eriRouterCpuMeterCap 6 }
END
