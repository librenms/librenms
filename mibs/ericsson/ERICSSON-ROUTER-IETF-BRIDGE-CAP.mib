-- %DNP% $Id: ERICSSON-ROUTER-IETF-BRIDGE-CAP.my,v 1.1.2.2.6.5 2011/06/15 18:19:45 danielhe Exp $
-- %DNP% $Source: /cvsroot/pkt/sw/se/xc/bsd/config/snmp/mibs/Attic/ERICSSON-ROUTER-IETF-BRIDGE-CAP.my,v $
-- *****************************************************************
-- ERICSSON-ROUTER-IETF-BRIDGE-CAP.my:	BRIDGE-MIB Agent Capabilities
--
-- Copyright (c) 2007, 2008, 2010-2011, 2015 Ericsson AB
-- All rights reserved.
-- 
-- *****************************************************************

ERICSSON-ROUTER-IETF-BRIDGE-CAP DEFINITIONS ::= BEGIN

IMPORTS
	MODULE-IDENTITY
		FROM SNMPv2-SMI
	AGENT-CAPABILITIES
		FROM SNMPv2-CONF
	eriRouterCapabilities
		FROM ERICSSON-ROUTER-SMI;

eriRouterIetfBridgeCap MODULE-IDENTITY
	LAST-UPDATED    "201501141800Z" -- Jan 14, 2015
	ORGANIZATION	"Ericsson Inc."
	CONTACT-INFO
		"	Ericsson, Inc.

		Postal:	100 Headquarters Dr.
			San Jose, CA  95134
			USA

		 Phone:	+1 408 750 5000
		   Fax: +1 408 750 5599
		"
	DESCRIPTION
		"The Agent Capabilities of the 
		implementation of the BRIDGE-MIB (RFC 4188).

                If this MIB implementation is platform-dependent,
                the PRODUCT-RELEASE clause contains Ericsson SEOS version and
                at least one of the following Ericsson product families:
                    [SE]  SmartEdge Multi-service Edge Router (MSER) family
                    [SM]  SM family of Metro Ethernet Service Transport platforms
                    [SSR] Smart Service Router (SSR) family"

        REVISION        "201501141800Z" -- Jan 14, 2015
        DESCRIPTION
                "Updated RBN/rbn/Rbn as ERICSSON-ROUTER/eriRouter/EriRouter
                 to migrate RBN MIB to ERICSSON MIB."

        REVISION        "201106150000Z" -- Jun 15, 2011
        DESCRIPTION
                "Update DESCRIPTION clause of MODULE-IDENTITY
                 and PRODUCT-RELEASE clause of AGENT-CAPABILITIES."

	REVISION	"201011010000Z" -- Nov 1, 2010
	DESCRIPTION
		"Modified PRODUCT-RELEASE clause for consistent naming.
                 Updated CONTACT-INFO."
                
        REVISION        "200909091200Z" -- Sept 9, 2009
        DESCRIPTION
                "Updated CAP file, dot1dNotificationGroup 
                 is not supported."

        REVISION        "200806241200Z" -- June 24, 2008
        DESCRIPTION
                "Updated CAP file with objects not implemented."

	REVISION	"200711011200Z" -- Nov 1, 2007
	DESCRIPTION
		"Initial version"
	::= { eriRouterCapabilities 76 }

eriRouterIetfBridgeCap1 AGENT-CAPABILITIES
	PRODUCT-RELEASE	"SEOS 6.1.4 [SE]; SEOS 6.3.X [SM]"
	STATUS		current
	DESCRIPTION	"BRIDGE-MIB capabilities"
	SUPPORTS	BRIDGE-MIB
	INCLUDES {
                dot1dBaseBridgeGroup,
                dot1dBasePortGroup,
                dot1dStpBridgeGroup,
                dot1dStpPortGroup2,
                dot1dTpBridgeGroup,
                dot1dTpFdbGroup,
                dot1dTpGroup
		}

        VARIATION       dot1dBasePortDelayExceededDiscards 
        ACCESS          not-implemented
        DESCRIPTION
                "This information is not available."

        VARIATION       dot1dBasePortMtuExceededDiscards
        ACCESS          not-implemented
        DESCRIPTION
                "This information is not available."

        VARIATION       dot1dTpPortMaxInfo
        ACCESS          not-implemented
        DESCRIPTION
                "This information is not available."        

        VARIATION       dot1dTpPortInDiscards
        ACCESS          not-implemented
        DESCRIPTION
                "This information is not available."
	::= { eriRouterIetfBridgeCap 1 }

END
