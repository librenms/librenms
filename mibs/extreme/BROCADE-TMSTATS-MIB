-- MIB File: BROCADE-TMSTATS-MIB.mib

-- automatically generated by SNMP Research mibgp from BROCADE-TMSTATS-MIB.txt
-- Fri Nov  4 11:41:55 2016


BROCADE-TMSTATS-MIB DEFINITIONS ::= BEGIN

    IMPORTS
		DisplayString 
												FROM SNMPv2-TC
        Integer32,
        MODULE-IDENTITY,
        OBJECT-IDENTITY, OBJECT-TYPE,
        NOTIFICATION-TYPE
                                                FROM SNMPv2-SMI

        InterfaceIndex, InterfaceIndexOrZero
                                                FROM IF-MIB

        bcsiModules                             FROM Brocade-REG-MIB;

    bcsiTMStats MODULE-IDENTITY
        LAST-UPDATED "201805291200Z" -- May 29, 2018 12:00pm
        ORGANIZATION "Extreme Networks, Inc."
        CONTACT-INFO
             "Postal:  Extreme Networks, Inc.
                       6480 Via Del Oro
                       San Jose, CA 95119 USA
              Phone:   +1 408 579-2800
              E-mail:  support@extremenetworks.com
              WWW:     http://www.extremenetworks.com"

        DESCRIPTION     "The MIB module to describe Traffic Manager(TM)
                         related statistics information."

        REVISION	    "201805291200Z" -- May 29, 2018 12:00pm
        DESCRIPTION	    "Updated ORGANIZATION and CONTACT-INFO with Extreme Networks"
        REVISION        "201610211330Z" -- October 21, 2016 1:30pm
        DESCRIPTION     "Initial Version"
        ::=        { bcsiModules 15 }

--
-- high level object identifiers
--

bcsiTMStatsNotification    OBJECT IDENTIFIER ::=  { bcsiTMStats 0 }
bcsiTMStatsObjects         OBJECT IDENTIFIER ::=  { bcsiTMStats 1 }

bcsiTMStatsGlobals         OBJECT IDENTIFIER ::=  { bcsiTMStatsObjects 1 }

-- The TM Statistics Information Group

bcsiTMStatsInfoGroup       OBJECT IDENTIFIER ::=  { bcsiTMStatsObjects 2 }
bcsiTMStatsInfoGroupGlobals OBJECT IDENTIFIER ::=  { bcsiTMStatsInfoGroup 1 }

-- The TM Statistics Table

bcsiTMStatsTable   OBJECT-TYPE
    SYNTAX         SEQUENCE OF BcsiTMStatsEntry
    MAX-ACCESS     not-accessible
    STATUS         current
    DESCRIPTION    "Table contains information of Traffic Manager(TM) counters"
    ::= { bcsiTMStatsInfoGroup 2 }

bcsiTMStatsEntry   OBJECT-TYPE
    SYNTAX         BcsiTMStatsEntry
    MAX-ACCESS     not-accessible
    STATUS         current
    DESCRIPTION    "An entry containing TM counter information"
    INDEX {        bcsiTMStatsSlot,
                   bcsiTMStatsTower }
    ::= { bcsiTMStatsTable 1 }

BcsiTMStatsEntry ::=
    SEQUENCE {
        bcsiTMStatsSlot                        Unsigned32,
        bcsiTMStatsTower                       Unsigned32,
        bcsiTMStatsDescription                 DisplayString,
        bcsiTMStatsTotalIngressPkts            Counter64,
        bcsiTMStatsIngressCPUPkts              Counter64,
        bcsiTMStatsIngressEnquePkts            Counter64,
        bcsiTMStatsIngressDequePkts            Counter64,
        bcsiTMStatsIngressTotalDiscardPkts     Counter64,
        bcsiTMStatsIngressOldestDiscardPkts    Counter64,
        bcsiTMStatsIngressResolvedToBeDropped  Counter64,
        bcsiTMStatsIngressCRCErrorCount        Counter64,
        bcsiTMStatsEgressREDiscardPkts         Counter64,
        bcsiTMStatsEgressFilterDiscardPkts     Counter64,
        bcsiTMStatsEgressDiscardUCPkts         Counter64,
        bcsiTMStatsEgressDiscardMCPkts         Counter64,
        bcsiTMStatsEgressUnicastPkts           Counter64,
        bcsiTMStatsEgressMulticastPkts         Counter64,
        bcsiTMStatsEgressFQPPkts               Counter64
    }

bcsiTMStatsSlot OBJECT-TYPE
    SYNTAX     Unsigned32
    MAX-ACCESS not-accessible
    STATUS     current
    DESCRIPTION
           "Slot number which uniquely identifies a linecard.
           The line card must be physically present and operationally up."
    ::= { bcsiTMStatsEntry 1 }

bcsiTMStatsTower OBJECT-TYPE
    SYNTAX     Unsigned32
    MAX-ACCESS not-accessible
    STATUS     current
    DESCRIPTION
           "Tower number which uniquely identifies the network processor TM
           within a linecard in the system."
    ::= { bcsiTMStatsEntry 2 }

bcsiTMStatsDescription OBJECT-TYPE
    SYNTAX      DisplayString
    MAX-ACCESS  read-only
    STATUS      current
    DESCRIPTION
           "This object gives the description of this entry."
    ::= { bcsiTMStatsEntry 3 }

bcsiTMStatsTotalIngressPkts OBJECT-TYPE
    SYNTAX      Counter64
    MAX-ACCESS  read-only
    STATUS      current
    DESCRIPTION
           "A count of all packets entering into this TM."
    ::= { bcsiTMStatsEntry 4 }

bcsiTMStatsIngressCPUPkts OBJECT-TYPE
    SYNTAX      Counter64
    MAX-ACCESS  read-only
    STATUS      current
    DESCRIPTION
           "A count of all packets entering into this TM destined for the CPU."
    ::= { bcsiTMStatsEntry 5 }

bcsiTMStatsIngressEnquePkts OBJECT-TYPE
    SYNTAX      Counter64
    MAX-ACCESS  read-only
    STATUS      current
    DESCRIPTION
           "A count of all packets entering ingress queues on this TM."
    ::= { bcsiTMStatsEntry 6 }

bcsiTMStatsIngressDequePkts OBJECT-TYPE
    SYNTAX      Counter64
    MAX-ACCESS  read-only
    STATUS      current
    DESCRIPTION
           "A count of all packets dequeued from ingress queues and
           forwarded on this TM."
    ::= { bcsiTMStatsEntry 7 }

bcsiTMStatsIngressTotalDiscardPkts OBJECT-TYPE
    SYNTAX      Counter64
    MAX-ACCESS  read-only
    STATUS      current
    DESCRIPTION
           "A count of all packets failing to enter ingress queues on this
           TM."
    ::= { bcsiTMStatsEntry 8 }

bcsiTMStatsIngressOldestDiscardPkts OBJECT-TYPE
    SYNTAX      Counter64
    MAX-ACCESS  read-only
    STATUS      current
    DESCRIPTION
           "A count of all packets entering ingress queues on this TM, but
           deleted later due to buffer being full."
    ::= { bcsiTMStatsEntry 9 }

bcsiTMStatsIngressResolvedToBeDropped OBJECT-TYPE
    SYNTAX      Counter64
    MAX-ACCESS  read-only
    STATUS      current
    DESCRIPTION
           "A count of all packets entering ingress queues on this TM, but
           resolved to be dropped."
    ::= { bcsiTMStatsEntry 10 }

bcsiTMStatsIngressCRCErrorCount OBJECT-TYPE
    SYNTAX      Counter64
    MAX-ACCESS  read-only
    STATUS      current
    DESCRIPTION
           "A count of all packets entering ingress queues on this TM, but
           found to have bad CRC."
    ::= { bcsiTMStatsEntry 11 }

bcsiTMStatsEgressREDiscardPkts OBJECT-TYPE
    SYNTAX      Counter64
    MAX-ACCESS  read-only
    STATUS      current
    DESCRIPTION
           "A count of all packets entering egress queues on this TM and
           discarded due to Reassembly errors."
    ::= { bcsiTMStatsEntry 12 }

bcsiTMStatsEgressFilterDiscardPkts OBJECT-TYPE
    SYNTAX      Counter64
    MAX-ACCESS  read-only
    STATUS      current
    DESCRIPTION
           "A count of all packets entering egress queues on this TM and
           discarded due to filtering."
    ::= { bcsiTMStatsEntry 13 }

bcsiTMStatsEgressDiscardUCPkts OBJECT-TYPE
    SYNTAX      Counter64
    MAX-ACCESS  read-only
    STATUS      current
    DESCRIPTION
           "A count of all unicast packets failing to enter egress queues on
           this TM."
    ::= { bcsiTMStatsEntry 14 }

bcsiTMStatsEgressDiscardMCPkts OBJECT-TYPE
    SYNTAX      Counter64
    MAX-ACCESS  read-only
    STATUS      current
    DESCRIPTION
           "A count of all multicast packets failing to enter egress queues on
           this TM."
    ::= { bcsiTMStatsEntry 15 }

bcsiTMStatsEgressUnicastPkts OBJECT-TYPE
    SYNTAX      Counter64
    MAX-ACCESS  read-only
    STATUS      current
    DESCRIPTION
           "A count of all unicast packets entering egress queues and
           forwarded out on this TM."
    ::= { bcsiTMStatsEntry 16 }

bcsiTMStatsEgressMulticastPkts OBJECT-TYPE
    SYNTAX      Counter64
    MAX-ACCESS  read-only
    STATUS      current
    DESCRIPTION
           "A count of all multicast packets entering egress queues and
           forwarded out on this TM."
    ::= { bcsiTMStatsEntry 17 }

bcsiTMStatsEgressFQPPkts OBJECT-TYPE
    SYNTAX      Counter64
    MAX-ACCESS  read-only
    STATUS      current
    DESCRIPTION
           "A count of all FQP packets entering egress queues and
           forwarded out on this TM."
    ::= { bcsiTMStatsEntry 18 }

-- The TM VOQ Statistics Information Group

bcsiTMVOQStatsInfoGroup    OBJECT IDENTIFIER ::=  { bcsiTMStatsObjects 3 }
bcsiTMVOQStatsInfoGroupGlobals OBJECT IDENTIFIER
    ::=  { bcsiTMVOQStatsInfoGroup 1 }

-- The TM VOQ CPU Group Statistics Table

bcsiTMVOQCPUGroupStatsTable   OBJECT-TYPE
    SYNTAX         SEQUENCE OF BcsiTMVOQCPUGroupStatsEntry
    MAX-ACCESS     not-accessible
    STATUS         current
    DESCRIPTION    "Table contains information Traffic Manager(TM) VOQ
                   (Virtual Output Queue) counters for CPU groups"
    ::= { bcsiTMVOQStatsInfoGroup 2 }

bcsiTMVOQCPUGroupStatsEntry   OBJECT-TYPE
    SYNTAX         BcsiTMVOQCPUGroupStatsEntry
    MAX-ACCESS     not-accessible
    STATUS         current
    DESCRIPTION    "An entry containing TM VOQ counter information for
                   CPU groups"
    INDEX {        bcsiTMVOQCPUGroupStatsSlot,
                   bcsiTMVOQCPUGroupStatsGroup,
                   bcsiTMVOQCPUGroupStatsPriority  }
    ::= { bcsiTMVOQCPUGroupStatsTable 1 }

BcsiTMVOQCPUGroupStatsEntry ::=
    SEQUENCE {
        bcsiTMVOQCPUGroupStatsSlot             Unsigned32,
        bcsiTMVOQCPUGroupStatsGroup            Unsigned32,
        bcsiTMVOQCPUGroupStatsPriority         Unsigned32,
        bcsiTMVOQCPUGroupStatsDescription      DisplayString,
        bcsiTMVOQCPUGroupStatsEnQPkts          Counter64,
        bcsiTMVOQCPUGroupStatsEnQBytes         Counter64,
        bcsiTMVOQCPUGroupStatsTotalDiscardPkts Counter64,
        bcsiTMVOQCPUGroupStatsTotalDiscardBytes Counter64,
        bcsiTMVOQCPUGroupStatsCurrQDepth       Counter64,
        bcsiTMVOQCPUGroupStatsMaxQDepth        Counter64
    }

bcsiTMVOQCPUGroupStatsSlot OBJECT-TYPE
    SYNTAX     Unsigned32
    MAX-ACCESS not-accessible
    STATUS     current
    DESCRIPTION
           "Slot number which uniquely identifies a linecard.
           The line card must be physically present and operationally up."
    ::= { bcsiTMVOQCPUGroupStatsEntry 1 }

bcsiTMVOQCPUGroupStatsGroup OBJECT-TYPE
    SYNTAX     Unsigned32
    MAX-ACCESS not-accessible
    STATUS     current
    DESCRIPTION
           "The CPU Group(0-12) of the packets stored in this queue."
    ::= { bcsiTMVOQCPUGroupStatsEntry 2 }

bcsiTMVOQCPUGroupStatsPriority OBJECT-TYPE
    SYNTAX     Unsigned32
    MAX-ACCESS not-accessible
    STATUS     current
    DESCRIPTION
           "The priority(0-7) of the packets stored in this queue."
    ::= { bcsiTMVOQCPUGroupStatsEntry 3 }

bcsiTMVOQCPUGroupStatsDescription OBJECT-TYPE
    SYNTAX      DisplayString
    MAX-ACCESS  read-only
    STATUS      current
    DESCRIPTION
           "This object gives the description of this entry."
    ::= { bcsiTMVOQCPUGroupStatsEntry 4 }

bcsiTMVOQCPUGroupStatsEnQPkts OBJECT-TYPE
    SYNTAX      Counter64
    MAX-ACCESS  read-only
    STATUS      current
    DESCRIPTION
           "A count of all packets entering ingress queues for this priority
           in this CPU group"
    ::= { bcsiTMVOQCPUGroupStatsEntry 5 }

bcsiTMVOQCPUGroupStatsEnQBytes OBJECT-TYPE
    SYNTAX      Counter64
    MAX-ACCESS  read-only
    STATUS      current
    DESCRIPTION
           "A count of bytes entering ingress queues for this priority
           in this CPU group"
    ::= { bcsiTMVOQCPUGroupStatsEntry 6 }

bcsiTMVOQCPUGroupStatsTotalDiscardPkts OBJECT-TYPE
    SYNTAX      Counter64
    MAX-ACCESS  read-only
    STATUS      current
    DESCRIPTION
           "A count of all packets failing to enter ingress queues for this
           priority in this CPU group."
    ::= { bcsiTMVOQCPUGroupStatsEntry 7 }

bcsiTMVOQCPUGroupStatsTotalDiscardBytes OBJECT-TYPE
    SYNTAX      Counter64
    MAX-ACCESS  read-only
    STATUS      current
    DESCRIPTION
           "A count of bytes failing to enter ingress queues for this
           priority in this CPU group."
    ::= { bcsiTMVOQCPUGroupStatsEntry 8 }

bcsiTMVOQCPUGroupStatsCurrQDepth OBJECT-TYPE
    SYNTAX      Counter64
    MAX-ACCESS  read-only
    STATUS      current
    DESCRIPTION
           "The current queue depth for this priority in this CPU group."
    ::= { bcsiTMVOQCPUGroupStatsEntry 9 }

bcsiTMVOQCPUGroupStatsMaxQDepth OBJECT-TYPE
    SYNTAX      Counter64
    MAX-ACCESS  read-only
    STATUS      current
    DESCRIPTION
           "The maximum queue depth for this priority in this CPU group,
           since last read by any entity."
    ::= { bcsiTMVOQCPUGroupStatsEntry 10 }

-- The TM VOQ Ingress Tower Statistics Table

bcsiTMVOQIngressStatsTable   OBJECT-TYPE
    SYNTAX         SEQUENCE OF BcsiTMVOQIngressStatsEntry
    MAX-ACCESS     not-accessible
    STATUS         current
    DESCRIPTION    "Table contains information of Traffic Manager(TM) VOQ
                   (Virtual Output Queue) counters for ingress tower for
                   an egress port and priority"
    ::= { bcsiTMVOQStatsInfoGroup 3 }

bcsiTMVOQIngressStatsEntry   OBJECT-TYPE
    SYNTAX         BcsiTMVOQIngressStatsEntry
    MAX-ACCESS     not-accessible
    STATUS         current
    DESCRIPTION    "An entry containing TM VOQ counter information for
                   ingress tower for an egress port and priority"
    INDEX {
                   bcsiTMVOQIngressStatsSlot,
                   bcsiTMVOQIngressStatsTower,
                   bcsiTMVOQIngressStatsEgressPort,
                   bcsiTMVOQIngressStatsPriority }
    ::= { bcsiTMVOQIngressStatsTable 1 }

BcsiTMVOQIngressStatsEntry ::=
    SEQUENCE {
        bcsiTMVOQIngressStatsSlot              Unsigned32,
        bcsiTMVOQIngressStatsTower             Unsigned32,
        bcsiTMVOQIngressStatsEgressPort        InterfaceIndex,
        bcsiTMVOQIngressStatsPriority          Unsigned32,
        bcsiTMVOQIngressStatsDescription       DisplayString,
        bcsiTMVOQIngressStatsEnQPkts           Counter64,
        bcsiTMVOQIngressStatsEnQBytes          Counter64,
        bcsiTMVOQIngressStatsTotalDiscardPkts  Counter64,
        bcsiTMVOQIngressStatsTotalDiscardBytes Counter64,
        bcsiTMVOQIngressStatsCurrQDepth        Counter64,
        bcsiTMVOQIngressStatsMaxQDepth         Counter64
    }

bcsiTMVOQIngressStatsSlot OBJECT-TYPE
    SYNTAX     Unsigned32
    MAX-ACCESS not-accessible
    STATUS     current
    DESCRIPTION
           "Slot number which uniquely identifies a linecard.
           The line card must be physically present and operationally up."
    ::= { bcsiTMVOQIngressStatsEntry 1 }

bcsiTMVOQIngressStatsTower OBJECT-TYPE
    SYNTAX     Unsigned32
    MAX-ACCESS not-accessible
    STATUS     current
    DESCRIPTION
           "Tower number which uniquely identifies the network processor TM
           within a linecard in the system."
    ::= { bcsiTMVOQIngressStatsEntry 2 }

bcsiTMVOQIngressStatsEgressPort OBJECT-TYPE
    SYNTAX     InterfaceIndex
    MAX-ACCESS not-accessible
    STATUS     current
    DESCRIPTION
           "The value of ifIndex corresponding to the egress port."
    ::= { bcsiTMVOQIngressStatsEntry 3 }

bcsiTMVOQIngressStatsPriority OBJECT-TYPE
    SYNTAX     Unsigned32
    MAX-ACCESS not-accessible
    STATUS     current
    DESCRIPTION
           "The priority(0-7) of the packets stored in this queue."
    ::= { bcsiTMVOQIngressStatsEntry 4 }

bcsiTMVOQIngressStatsDescription OBJECT-TYPE
    SYNTAX      DisplayString
    MAX-ACCESS  read-only
    STATUS      current
    DESCRIPTION
           "This object gives the description of this entry."
    ::= { bcsiTMVOQIngressStatsEntry 5 }

bcsiTMVOQIngressStatsEnQPkts OBJECT-TYPE
    SYNTAX      Counter64
    MAX-ACCESS  read-only
    STATUS      current
    DESCRIPTION
           "A count of all packets entering ingress queues for this priority
           destined for the specified egress port"
    ::= { bcsiTMVOQIngressStatsEntry 6 }

bcsiTMVOQIngressStatsEnQBytes OBJECT-TYPE
    SYNTAX      Counter64
    MAX-ACCESS  read-only
    STATUS      current
    DESCRIPTION
           "A count of bytes entering ingress queues for this priority
           destined for the specified egress port"
    ::= { bcsiTMVOQIngressStatsEntry 7 }

bcsiTMVOQIngressStatsTotalDiscardPkts OBJECT-TYPE
    SYNTAX      Counter64
    MAX-ACCESS  read-only
    STATUS      current
    DESCRIPTION
           "A count of all packets failing to enter ingress queues for this
           priority destined for the specified egress port."
    ::= { bcsiTMVOQIngressStatsEntry 8 }

bcsiTMVOQIngressStatsTotalDiscardBytes OBJECT-TYPE
    SYNTAX      Counter64
    MAX-ACCESS  read-only
    STATUS      current
    DESCRIPTION
           "A count of bytes failing to enter ingress queues for this
           priority destined for the specified egress port."
    ::= { bcsiTMVOQIngressStatsEntry 9 }

bcsiTMVOQIngressStatsCurrQDepth OBJECT-TYPE
    SYNTAX      Counter64
    MAX-ACCESS  read-only
    STATUS      current
    DESCRIPTION
           "The current queue depth for this priority,
           destined for the specified egress port."
    ::= { bcsiTMVOQIngressStatsEntry 10 }

bcsiTMVOQIngressStatsMaxQDepth OBJECT-TYPE
    SYNTAX      Counter64
    MAX-ACCESS  read-only
    STATUS      current
    DESCRIPTION
           "The maximum queue depth for this priority,
           destined for the specified egress port,
           since last read by any entity."
    ::= { bcsiTMVOQIngressStatsEntry 11 }

END

-- ========================================================================================
