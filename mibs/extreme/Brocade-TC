-- MIB File: BRCD_TC.mib
--
-- Title: Extreme Registration MIB, Version v5.0
--
-- This is specified based on SMIv2, mainly to ensure that the specification
-- can be parsed easily by off-the-shelf network management product in
-- the market.
--
-- The goal of this mib is to access all the Extreme Enterprise products.
-- This mib file contains the generic textual conventions of Extreme's product.
--


Brocade-TC DEFINITIONS ::= BEGIN
  IMPORTS
	bcsiModules
      FROM Brocade-REG-MIB
	TEXTUAL-CONVENTION
      FROM SNMPv2-TC
	Integer32, MODULE-IDENTITY
      FROM SNMPv2-SMI;

  bcsiModuleTC MODULE-IDENTITY
    LAST-UPDATED "201805291200Z" -- May 29, 2018 12:00pm
    ORGANIZATION "Extreme Networks, Inc."
    CONTACT-INFO
         "Postal:  Extreme Networks, Inc.
                   6480 Via Del Oro
                   San Jose, CA 95119 USA
          Phone:   +1 408 579-2800
          E-mail:  support@extremenetworks.com
          WWW:     http://www.extremenetworks.com"
    DESCRIPTION	"The MIB module	contains all shared textual conventions
                 for Extreme specific MIBs.
                 Copyright (c) 2018 Extreme Networks, Inc.
  				 All rights reserved."
    REVISION	"201805291200Z" -- May 29, 2018 12:00pm
    DESCRIPTION	"Updated ORGANIZATION and CONTACT-INFO with Extreme Networks"
    REVISION	"0301131430Z" -- Jan 13, 2003 2:30pm
    DESCRIPTION	"The initial version of this module."
    ::=	{ bcsiModules 2 }

  -- additional textual conventions

  FcWwn 	::= TEXTUAL-CONVENTION		
     STATUS  current
     DESCRIPTION   "The World Wide Name (WWN) of Extreme's 
                    specific products and ports."
     SYNTAX  OCTET STRING (SIZE(8))

  SwDomainIndex		::= TEXTUAL-CONVENTION
     STATUS  current
     DESCRIPTION   "The Fibre Channel domain ID of the switch."
     SYNTAX  Integer32 (1..239)

  SwNbIndex         ::= TEXTUAL-CONVENTION
     STATUS  current
     DESCRIPTION   "Index of the neighbour ISL entry."
     SYNTAX  Integer32 (1..2048)

  SwSensorIndex		::= TEXTUAL-CONVENTION
     STATUS  current
     DESCRIPTION   "Index of the Sensor entry."
     SYNTAX  Integer32 (1..1024)

  SwPortIndex		::= TEXTUAL-CONVENTION
     STATUS  current
     DESCRIPTION   "Index of the Port start from 1 upto Maximum
                    number of ports of the Extreme Switch."
     SYNTAX  Integer32

  SwTrunkMaster		::= TEXTUAL-CONVENTION
     STATUS  current
     DESCRIPTION   "Index of the Trunk Master start from 1 upto Maximum
                    number of trunk groups of Extreme Switch."
     SYNTAX  Integer32

END


-- MIB File: BROCADE-PRODUCTS-MIB.mib
-- ****************************************************************
-- BROCADE-PRODUCTS-MIB.my: Extreme Products MIB.
--
-- Copyright (c) 2018 by Extreme Networks, Inc.
-- All rights reserved.
--
-- ****************************************************************
BROCADE-PRODUCTS-MIB DEFINITIONS ::= BEGIN
IMPORTS
   MODULE-IDENTITY
      	FROM SNMPv2-SMI
        bcsiReg  
        	FROM Brocade-REG-MIB;

      brocadeProductsMIB MODULE-IDENTITY
        LAST-UPDATED "201805291200Z" -- May 29, 2018 12:00pm
        ORGANIZATION "Extreme Networks, Inc."
        CONTACT-INFO
             "Postal:  Extreme Networks, Inc.
                       6480 Via Del Oro
                       San Jose, CA 95119 USA
              Phone:   +1 408 579-2800
              E-mail:  support@extremenetworks.com
              WWW:     http://www.extremenetworks.com"

        DESCRIPTION "This MIB module is for defining all the object 
		             identifiers to identify various hardware 
					 platforms. These identifiers are used as value
					 for 'sysObjectID'."

        REVISION "201805291200Z" -- May 29, 2018 12:00pm
        DESCRIPTION	"Updated ORGANIZATION and CONTACT-INFO with Extreme Networks"
		
        REVISION "201712070000Z"  -- 7 December, 2017
		DESCRIPTION "Updated the product name for RIGEL1U as vdx6940Q36.
				 then added RIGELMOR product name as vdx6940S144 and Removed RIGEL2U platform"

		REVISION "201701050000Z"  -- 5 January, 2017
	    DESCRIPTION "Added product types SLX9240 and SLX9140."

		REVISION "201612260000Z"  -- 26 December, 2016
	    DESCRIPTION "Added product type SLX9540."

		REVISION "201606280000Z"  -- 28 June, 2016
	    DESCRIPTION "Added product types SLX9850S4 and SLX9850S8."

		REVISION "201410071405Z" 
	    DESCRIPTION "Added product name for RIGEL1U as vdx7770P36
				and RIGEL2U as vdx7770P72."
		
		REVISION "201311210000Z"
		DESCRIPTION "Updated name for Blackbird as vdx2740"

		REVISION "201309251300Z" 
	    DESCRIPTION "Added new product name for Draco-T platform."

		REVISION "201202030000Z" 
	    DESCRIPTION "Initial version of this MIB module."

        ::= { bcsiReg 3 }

      brocadeProducts   OBJECT IDENTIFIER ::= { brocadeProductsMIB 1 }

      vdx6740		OBJECT IDENTIFIER ::= { brocadeProducts 131 }

      vdx6740T		OBJECT IDENTIFIER ::= { brocadeProducts 137 }

	  vdx2740        OBJECT IDENTIFIER ::= { brocadeProducts 138 }

      vdx6740T1G  	OBJECT IDENTIFIER ::= { brocadeProducts 151 }

	  vdx6940Q36 	OBJECT IDENTIFIER ::= { brocadeProducts 153 }

	  vdx6940S144 	OBJECT IDENTIFIER ::= { brocadeProducts 164 }

      vdx8770S4		OBJECT IDENTIFIER ::= { brocadeProducts 1000 }

      vdx8770S8   	OBJECT IDENTIFIER ::= { brocadeProducts 1001 }

      vdx8770S16  	OBJECT IDENTIFIER ::= { brocadeProducts 1002 }

      slx9850S4  	OBJECT IDENTIFIER ::= { brocadeProducts 2000 }
      slx9850S8  	OBJECT IDENTIFIER ::= { brocadeProducts 2001 }

      slx9240       OBJECT IDENTIFIER ::= { brocadeProducts 3000 }
      slx9140       OBJECT IDENTIFIER ::= { brocadeProducts 3001 }

      slx9540       OBJECT IDENTIFIER ::= { brocadeProducts 4000 }

END
