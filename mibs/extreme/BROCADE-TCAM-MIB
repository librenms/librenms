-- MIB File: BROCADE-TCAM-MIB.mib

-- automatically generated by SNMP Research mibgp from BROCADE-TCAM-MIB.txt
-- Mon Oct 24 20:23:01 2016


BROCADE-TCAM-MIB DEFINITIONS ::= BEGIN

    IMPORTS
        Gauge32, Unsigned32,
        MODULE-IDENTITY,
        OBJECT-IDENTITY, OBJECT-TYPE,
        NOTIFICATION-TYPE
                                                FROM SNMPv2-SMI -- [RFC2578]

        TEXTUAL-CONVENTION
                                                FROM SNMPv2-TC  -- [RFC2579]

        bcsiModules                             FROM Brocade-REG-MIB;

    bcsiTCAM MODULE-IDENTITY
        LAST-UPDATED "201805291200Z" -- May 29, 2018 12:00pm
        ORGANIZATION "Extreme Networks, Inc."
        CONTACT-INFO
             "Postal:  Extreme Networks, Inc.
                       6480 Via Del Oro
                       San Jose, CA 95119 USA
              Phone:   +1 408 579-2800
              E-mail:  support@extremenetworks.com
              WWW:     http://www.extremenetworks.com"

        DESCRIPTION     "The MIB module to describe generic objects for the
                         usage of Ternary Content-Addressable Memory (TCAM)."

        REVISION        "201805291200Z" -- May 29, 2018 12:00pm
        DESCRIPTION	    "Updated ORGANIZATION and CONTACT-INFO with Extreme Networks"
        REVISION        "201610241330Z" -- October 24, 2016 1:30pm
        DESCRIPTION     "Initial Version"
        ::=        { bcsiModules 14 }

--
-- high level object identifiers
--

bcsiTCAMNotification    OBJECT IDENTIFIER ::=  { bcsiTCAM 0 }
bcsiTCAMObjects         OBJECT IDENTIFIER ::=  { bcsiTCAM 1 }

bcsiTCAMGlobals         OBJECT IDENTIFIER ::=  { bcsiTCAMObjects 1 }

-- bcsiTCAMProfile

bcsiTCAMProfile OBJECT-TYPE
    SYNTAX  INTEGER {
                default(0),
                vxlanExt(1),
                l2l3l4Openflow1(2),
                l2l3l4Openflow2(3),
                v6Openflow1(4),
                npbProfile1(5)
            }
    MAX-ACCESS  read-only
    STATUS      current
    DESCRIPTION
            "This object identifies TCAM partition profile. Each profile
            adjusts the partitions to optimize the device for corresponding
            applications."
    ::= { bcsiTCAMGlobals 1 }

-- TCAM usage objects

bcsiTCAMUsageGroup        OBJECT IDENTIFIER ::=  { bcsiTCAMObjects 2 }

-- the bcsiTCAMUsage table

-- The bcsiTCAMUsage table contains information of the entity's
-- TCAM usage.

bcsiTCAMUsageTable OBJECT-TYPE
    SYNTAX      SEQUENCE OF BcsiTCAMUsageEntry
    MAX-ACCESS  not-accessible
    STATUS      current
    DESCRIPTION
            "A list of bcsiTCAMUsage entries. This table contains
            information of the entity's TCAM usage."
    ::= { bcsiTCAMUsageGroup 1 }

bcsiTCAMUsageEntry OBJECT-TYPE
    SYNTAX      BcsiTCAMUsageEntry
    MAX-ACCESS  not-accessible
    STATUS      current
    DESCRIPTION
            "An entry containing management information applicable to
            TCAM usage"
    INDEX   {   bcsiTCAMUsageSlot,
                bcsiTCAMUsageProcessor,
                bcsiTCAMUsageFeature }
    ::= { bcsiTCAMUsageTable 1 }

BcsiTCAMUsageEntry ::=
    SEQUENCE {
        bcsiTCAMUsageSlot                  Unsigned32,
        bcsiTCAMUsageProcessor             Unsigned32,
        bcsiTCAMUsageFeature               INTEGER,
        bcsiTCAMUsageContainerId           Unsigned32,
        bcsiTCAMUsageDBId                  Unsigned32,
        bcsiTCAMUsageSize                  INTEGER,
        bcsiTCAMUsageMaxLimit              Gauge32,
        bcsiTCAMUsageCurrentUsage          Gauge32,
        bcsiTCAMUsageFreeCountContainer    Gauge32,
        bcsiTCAMUsageFreeCountDB           Gauge32,
        bcsiTCAMUsageFreeCountFeature      Gauge32
    }

bcsiTCAMUsageSlot OBJECT-TYPE
    SYNTAX  Unsigned32
    MAX-ACCESS  not-accessible
    STATUS      current
    DESCRIPTION
            "A number which uniquely identifies a linecard  in the device"
    ::= { bcsiTCAMUsageEntry 1 }

bcsiTCAMUsageProcessor OBJECT-TYPE
    SYNTAX  Unsigned32
    MAX-ACCESS  not-accessible
    STATUS      current
    DESCRIPTION
            "A number which uniquely identifies the network processor within a
            linecard in the device"
    ::= { bcsiTCAMUsageEntry 2 }

bcsiTCAMUsageFeature OBJECT-TYPE
    SYNTAX  INTEGER {
                l2Ctrl(0),
                l3V4Ctrl(1),
                l3V6Ctrl(2),
                l2UserIngress(3),
                l2UserEgress(4),
                portRL(5),
                bumRL(6),
                l3IPV4UserIngress(7),
                l3IPV4UserEgress(8),
                l3IPV4VxlanVisibility(9),
                l3IPV4UserWithRL(10),
                l3IPV4RACL(11),
                l3IPV4PBR(12),
                l3IPV6UserIngress(13),
                l3IPV6UserEgress(14),
                l3IPV6UserWithRL(15),
                l3IPV6RACL(16),
                l3IPV6PBR(17),
                oflowL2(18),
                oflowL3V4(19),
                oflowL3V6(20),
                oflowL2L3V4(21),
                oflowL2L3V6(22),
                mct(23),
                mplsXC(24),
                profileAGT(25)
            }
    MAX-ACCESS  not-accessible
    STATUS      current
    DESCRIPTION
            "This object identifies the feature within the linecard
            and network processor."
    ::= { bcsiTCAMUsageEntry 3 }

bcsiTCAMUsageContainerId OBJECT-TYPE
    SYNTAX  Unsigned32
    MAX-ACCESS  read-only
    STATUS      current
    DESCRIPTION
            "This object identifies the bank container which can refer
            to a single bank or multiple TCAM banks."
    ::= { bcsiTCAMUsageEntry 4 }

bcsiTCAMUsageDBId OBJECT-TYPE
    SYNTAX  Unsigned32
    MAX-ACCESS  read-only
    STATUS      current
    DESCRIPTION
            "This object identifies the logical database."
    ::= { bcsiTCAMUsageEntry 5 }

bcsiTCAMUsageSize OBJECT-TYPE
    SYNTAX  INTEGER {
                fixed(0),
                dynamic(1)
            }
    MAX-ACCESS  read-only
    STATUS      current
    DESCRIPTION
            "This object indicates if the size for this feature in 
             the current profile is fixed or dynamic."
    ::= { bcsiTCAMUsageEntry 6 }

bcsiTCAMUsageCurrentUsage	OBJECT-TYPE
    SYNTAX  Gauge32
    UNITS  "Entries"
    MAX-ACCESS  read-only
    STATUS      current
    DESCRIPTION
            "This object indicates the current usage of TCAM entries
            by this feature."
    ::= { bcsiTCAMUsageEntry 7 }

bcsiTCAMUsageMaxLimit	OBJECT-TYPE
    SYNTAX  Gauge32
    UNITS  "Entries"
    MAX-ACCESS  read-only
    STATUS      current
    DESCRIPTION
            "This object indicates the Maximum Limit of TCAM entries
            available for this feature."
    ::= { bcsiTCAMUsageEntry 8 }

bcsiTCAMUsageFreeCountContainer	OBJECT-TYPE
    SYNTAX  Gauge32
    UNITS  "Entries"
    MAX-ACCESS  read-only
    STATUS      current
    DESCRIPTION
            "This object indicates the number of free entries in the
             Container that is associated with the TCAM logical database
             used by this feature. Used for debugging purpose."
    ::= { bcsiTCAMUsageEntry 9 }

bcsiTCAMUsageFreeCountDB	OBJECT-TYPE
    SYNTAX  Gauge32
    UNITS  "Entries"
    MAX-ACCESS  read-only
    STATUS      current
    DESCRIPTION
            "This object indicates the number of free entries in the
             TCAM logical database used by this feature. Used for
             debugging purpose."
    ::= { bcsiTCAMUsageEntry 10 }

bcsiTCAMUsageFreeCountFeature	OBJECT-TYPE
    SYNTAX  Gauge32
    UNITS  "Entries"
    MAX-ACCESS  read-only
    STATUS      current
    DESCRIPTION
            "This object indicates the number of free entries available
             for this feature. Used for debugging purpose."
    ::= { bcsiTCAMUsageEntry 11 }

END

-- ========================================================================================
