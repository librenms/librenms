-- MIB File: BRCD_TC.mib
--
-- Title: Extreme Registration MIB, Version v5.0
--
-- This is specified based on SMIv2, mainly to ensure that the specification
-- can be parsed easily by off-the-shelf network management product in
-- the market.
--
-- The goal of this mib is to access all the Extreme Enterprise products.
-- This mib file contains the generic textual conventions of Extreme's product.
--


Brocade-TC DEFINITIONS ::= BEGIN
  IMPORTS
	bcsiModules
      FROM Brocade-REG-MIB
	TEXTUAL-CONVENTION
      FROM SNMPv2-TC
	Integer32, MODULE-IDENTITY
      FROM SNMPv2-SMI;

  bcsiModuleTC MODULE-IDENTITY
    LAST-UPDATED "201805291200Z" -- May 29, 2018 12:00pm
    ORGANIZATION "Extreme Networks, Inc."
    CONTACT-INFO
         "Postal:  Extreme Networks, Inc.
                   6480 Via Del Oro
                   San Jose, CA 95119 USA
          Phone:   +1 408 579-2800
          E-mail:  support@extremenetworks.com
          WWW:     http://www.extremenetworks.com"
    DESCRIPTION	"The MIB module	contains all shared textual conventions
                 for Extreme specific MIBs.
                 Copyright (c) 2018 Extreme Networks, Inc.
  				 All rights reserved."
    REVISION	"201805291200Z" -- May 29, 2018 12:00pm
    DESCRIPTION	"Updated ORGANIZATION and CONTACT-INFO with Extreme Networks"
    REVISION	"0301131430Z" -- Jan 13, 2003 2:30pm
    DESCRIPTION	"The initial version of this module."
    ::=	{ bcsiModules 2 }

  -- additional textual conventions

  FcWwn 	::= TEXTUAL-CONVENTION		
     STATUS  current
     DESCRIPTION   "The World Wide Name (WWN) of Extreme's 
                    specific products and ports."
     SYNTAX  OCTET STRING (SIZE(8))

  SwDomainIndex		::= TEXTUAL-CONVENTION
     STATUS  current
     DESCRIPTION   "The Fibre Channel domain ID of the switch."
     SYNTAX  Integer32 (1..239)

  SwNbIndex         ::= TEXTUAL-CONVENTION
     STATUS  current
     DESCRIPTION   "Index of the neighbour ISL entry."
     SYNTAX  Integer32 (1..2048)

  SwSensorIndex		::= TEXTUAL-CONVENTION
     STATUS  current
     DESCRIPTION   "Index of the Sensor entry."
     SYNTAX  Integer32 (1..1024)

  SwPortIndex		::= TEXTUAL-CONVENTION
     STATUS  current
     DESCRIPTION   "Index of the Port start from 1 upto Maximum
                    number of ports of the Extreme Switch."
     SYNTAX  Integer32

  SwTrunkMaster		::= TEXTUAL-CONVENTION
     STATUS  current
     DESCRIPTION   "Index of the Trunk Master start from 1 upto Maximum
                    number of trunk groups of Extreme Switch."
     SYNTAX  Integer32

END
