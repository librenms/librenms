-- *****************************************************************
-- UBIQUOSS-SMI.mib:  Ubiquoss Enterprise Structure of Management Information
-- Obsoletes: LNS-SMI.mib
--
-- July 2006, Song Sang-Jun
-- 
-- LNS-SMI.mib:  LocusNetworks Enterprise Structure of Management Information
-- Obsoletes: LNS-BASE-MIB.mib
--
-- April 2004, Jisoo Kim
--
-- Copyright (c) 2006 by Ubiquoss, Corp.
-- All rights reserved.
-- 
-- *****************************************************************
--

UBIQUOSS-SMI DEFINITIONS ::= BEGIN

IMPORTS
	MODULE-IDENTITY,
	OBJECT-IDENTITY,
	enterprises
		FROM SNMPv2-SMI;

ubiquoss MODULE-IDENTITY
	LAST-UPDATED "0607130000Z"
	ORGANIZATION "Ubiquoss Corp."
	CONTACT-INFO
		"	Ubiquoss
			Customer Service

		Postal: 24F Milennium B/D,
		 	467-12, Dogok-Dong,
			GangNam-Gu, Seoul 135-270
			Korea

		   Tel: 82-2-2190-3100"

--		E-mail: khpark@locusnet.com  
		
	DESCRIPTION
		"The Structure of Management Information for the
		LocusNetworks enterprise."
    
    REVISION      "0607130000Z"
	DESCRIPTION
		"New oid assignments for Ubiquoss MIB."

	REVISION      "0404220000Z"
	DESCRIPTION
		"New oid assignments for LocusNetworks switchAgent MIB."

	REVISION      "0110090000Z"
	DESCRIPTION
		"Initial version of this MIB module."
		      
	REVISION	  "200806221308Z" 	-- Jun 22, 2008 at 13:08 GMT
	DESCRIPTION	
		"Epon Group MIB"
	::= { enterprises 7800 }	-- assigned by IANA

-------------------------------------------------------------------------------
lnsProducts OBJECT-IDENTITY
	STATUS	current
	DESCRIPTION
		"lnsProduct is the root OBJECT IDENTIFIER from
		which sysObjectID values are assigned.  Actual
		values are defined in LNS-PRODUCTS-MIB."
	::= { ubiquoss 1 }

ubiMgmt OBJECT-IDENTITY
	STATUS	current
	DESCRIPTION
		"subtree reserved for use by the Workgroup Business Unit"
	::= { ubiquoss 2 }   

--------------------------------------------------------------------------------	
lnsKtEmsAgnt	OBJECT-IDENTITY   
	STATUS	current
	DESCRIPTION
		"subtree reserved for LNS-KT Ems Agent"
		::=  {  ubiMgmt  1  }
	
switchAgent		OBJECT-IDENTITY
	STATUS	current
	DESCRIPTION
		"subtree reserved for switch agent"
		::=  {  ubiMgmt  2  }
		                               
-- added by Hyungeun Park (2008-06-22) for Epon Group MIB 		                               
ubiEponGroupMIB		OBJECT-IDENTITY
	STATUS	current
	DESCRIPTION
		"subtree reserved for Epon Group MIB"
		::=	{ ubiMgmt 500 }		
	
	
END
