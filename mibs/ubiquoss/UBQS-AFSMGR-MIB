--
-- UBQS-AFSMGR-MIB.my
-- MIB generated by MG-SOFT Visual MIB Builder Version 3.0 Build 271
-- Monday, April 12, 2010
--

	UBQS-AFSMGR-MIB DEFINITIONS ::= BEGIN
 
		IMPORTS
			sysObjectID, sysContact, sysName, sysLocation, ifIndex			
				FROM RFC1213-MIB						
			IpAddress, Integer32, OBJECT-TYPE, MODULE-IDENTITY, NOTIFICATION-TYPE			
				FROM SNMPv2-SMI			
			DisplayString, RowStatus			
				FROM SNMPv2-TC
			ubiMgmtv2
				FROM UBQS-SMI;
	
	
		ubiAFSMGREventMIB MODULE-IDENTITY 
			LAST-UPDATED "201004120000Z"
			ORGANIZATION 	"Ubiquoss Corp."
			CONTACT-INFO
				"	Ubiquoss
					Customer Service

		 		Postal: 24F Milennium B/D,
		 			467-12, Dogok-Dong,
					GangNam-Gu, Seoul 135-270
					Korea

		   			Tel: 82-2-2190-3100" 			
		   	DESCRIPTION
				"AFSMGR Event Group"
			::= { ubiMgmtv2 7 }
		
	
	
--
-- Node definitions
--
	
		-- 1.3.6.1.4.1.236.4.1.7.2.1
		currentAlarmTable OBJECT-TYPE
			SYNTAX SEQUENCE OF CurrentAlarmEntry
			MAX-ACCESS not-accessible
			STATUS current
			DESCRIPTION
				"Description."
			::= { ubiAFSMGREventMIB 1 }
		
		-- 1.3.6.1.4.1.236.4.1.7.2.1.1
		currentAlarmEntry OBJECT-TYPE
			SYNTAX CurrentAlarmEntry
			MAX-ACCESS not-accessible
			STATUS current
			DESCRIPTION
				"Description."
			INDEX { AlarmIndex }
			::= { currentAlarmTable 1 }
		
		CurrentAlarmEntry ::=
			SEQUENCE { 
				alarmIndex
					Integer32,
				alarmId
					DisplayString,
				alarmType
					INTEGER,
				alarmSeverity
					INTEGER,
				alarmPhysicalLoc
					DisplayString,
				alarmLogicalLoc
					DisplayString,
				alarmCurStatus
					Integer32,
				alarmAuxinfo
					DisplayString,
				alarmDateTime
					DisplayString,
				alarmStatus
					Integer32
			 }

		alarmIndex OBJECT-TYPE
			SYNTAX Integer32
			MAX-ACCESS read-only
			STATUS current
			DESCRIPTION
				"current Alarm index."
			::= { currentAlarmEntry 1 }
		
		alarmId OBJECT-TYPE
			SYNTAX DisplayString
			MAX-ACCESS read-only
			STATUS current
			DESCRIPTION
				"Description"
			::= { currentAlarmEntry 2 }

		alarmType OBJECT-TYPE
			SYNTAX INTEGER
			{
				equipment(1),
				communications(2),
				qos(3),
				processing(4),
				environment(5)
			}
			MAX-ACCESS read-only
			STATUS current
			DESCRIPTION
				"Description
				   1 : equipment
				   2 : communications
				   3 : QoS
				   4 : processing
				   5 : environment
				"
			::= { currentAlarmEntry 3 }
		
		alarmSeverity OBJECT-TYPE
			SYNTAX INTEGER
			{
			   critical(1),
			   major(2),
			   minor(3),
			   warning(4),
			   indeterminate(5)
			}
			MAX-ACCESS read-only
			STATUS current
			DESCRIPTION
				"Description
				   1 : critical
				   2 : major
				   3 : minor
				   4 : warning
				   5 : indeterminate
				"
			::= { currentAlarmEntry 4 }
		
		alarmPhysicalLoc OBJECT-TYPE
			SYNTAX DisplayString
			MAX-ACCESS read-only
			STATUS current
			DESCRIPTION
				"Description"
			::= { currentAlarmEntry 5 }
		
		alarmLogicalLoc OBJECT-TYPE
			SYNTAX DisplayString
			MAX-ACCESS read-only
			STATUS current
			DESCRIPTION
				"Description"
			::= { currentAlarmEntry 6 }

		alarmCurStatus OBJECT-TYPE
			SYNTAX Integer32
			MAX-ACCESS read-only
			STATUS current
			DESCRIPTION
				"Description"
			::= { currentAlarmEntry 7 }
		    
		alarmAuxinfo OBJECT-TYPE
			SYNTAX DisplayString
			MAX-ACCESS read-only
			STATUS current
			DESCRIPTION
				"Description"
			::= { currentAlarmEntry 8 }
			
		alarmDateTime OBJECT-TYPE
			SYNTAX DisplayString
			MAX-ACCESS read-only
			STATUS current
			DESCRIPTION
				"Description"
			::= { currentAlarmEntry 9 }
			
		alarmStatus OBJECT-TYPE
			SYNTAX Integer32
			MAX-ACCESS read-only
			STATUS current
			DESCRIPTION
				"Description"
			::= { currentAlarmEntry 10 }

--		
-- eventLogTable
--
		eventLogTable OBJECT-TYPE
			SYNTAX SEQUENCE OF EventLogEntry
			MAX-ACCESS not-accessible
			STATUS current
			DESCRIPTION
				"Description."
			::= { ubiAFSMGREventMIB 2 }
		
		eventLogEntry OBJECT-TYPE
			SYNTAX EventLogEntry
			MAX-ACCESS not-accessible
			STATUS current
			DESCRIPTION
				"Description."
			INDEX { EventIndex }
			::= { eventLogTable 1 }
		
		EventLogEntry ::=
			SEQUENCE { 
				eventIndex
					Integer32,
				eventId
					DisplayString,
				eventType
					INTEGER,
				eventSeverity
					INTEGER,
				eventValue
					DisplayString,
				eventDateTime
					DisplayString,
				eventStatus
					Integer32
			 }

		eventIndex OBJECT-TYPE
			SYNTAX Integer32
			MAX-ACCESS read-only
			STATUS current
			DESCRIPTION
				"Description"
			::= { eventLogEntry 1 }
		
		eventId OBJECT-TYPE
			SYNTAX DisplayString
			MAX-ACCESS read-only
			STATUS current
			DESCRIPTION
				"Description"
			::= { eventLogEntry 2 }
		
		eventType OBJECT-TYPE
			SYNTAX INTEGER
			{
				equipment(1),
				communications(2),
				qos(3),
				processing(4),
				environment(5)
			}
			MAX-ACCESS read-only
			STATUS current
			DESCRIPTION
				"Description
				   1 : equipment
				   2 : communications
				   3 : QoS
				   4 : processing
				   5 : environment
				"
			::= { eventLogEntry 3 }
		
		eventSeverity OBJECT-TYPE
			SYNTAX INTEGER    
			{
				critical(1),
				major(2),
				minor(3),
				warning(4),
				indeterminate(5)
			}
			MAX-ACCESS read-only
			STATUS current
			DESCRIPTION
				"Description
				   1 : critical
				   2 : major
				   3 : minor
				   4 : warning
				   5 : indeterminate
				"
			::= { eventLogEntry 4 }
		
		eventValue OBJECT-TYPE
			SYNTAX DisplayString
			MAX-ACCESS read-only
			STATUS current
			DESCRIPTION
				"Description"
			::= { eventLogEntry 5 }
		
		eventDateTime OBJECT-TYPE
			SYNTAX DisplayString
			MAX-ACCESS read-only
			STATUS current
			DESCRIPTION
				"Description"
			::= { eventLogEntry 6 }
		
		eventStatus OBJECT-TYPE
			SYNTAX Integer32
			MAX-ACCESS read-only
			STATUS current
			DESCRIPTION
				"Description"
			::= { eventLogEntry 7 }
		
		
--
-- afsmgrEventManagerTrap
--	
		afsmgrEventManagerTrap OBJECT IDENTIFIER ::= { ubiAFSMGREventMIB 3 }
		
		sysWarmStartNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"System Warm-Start Notification."
			::= { afsmgrEventManagerTrap 1 }
		
		sysColdStartNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"System Cold-Start Notification."
			::= { afsmgrEventManagerTrap 2 }
		
		linkUpNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Link Up Notification."
			::= { afsmgrEventManagerTrap 3 }
		
		linkDownNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Link Down Notification."
			::= { afsmgrEventManagerTrap 4 }
				                                          
		cpuOverloadFallingNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"CPU Overload Falling Notification."
			::= { afsmgrEventManagerTrap 5 }
		
		cpuOverloadRisingNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"CPU Overload Rising Notification."
			::= { afsmgrEventManagerTrap 6 }

		gbicOperNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Gbic Equip/Unequip Operation Notification."
			::= { afsmgrEventManagerTrap 7 }

		memoryOverloadNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Memory Overload Notification."
			::= { afsmgrEventManagerTrap 8 }
		
		slotOperNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Slot Equip/Unequip Operation Notification."
			::= { afsmgrEventManagerTrap 9 }
		
		tempLowNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Temperature Low Alarm Notification."
			::= { afsmgrEventManagerTrap 10 }
		
		tempHighNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Temperature High Alarm Notification."
			::= { afsmgrEventManagerTrap 11 }
		
		fanAlarmNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Fan Alarm Notification."
			::= { afsmgrEventManagerTrap 12 }
		
		fmuEquipStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Fan Module Unit Equip/Unequip Status Notification."
			::= { afsmgrEventManagerTrap 13 }

		psuAlarmNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Power Alarm Notification."
			::= { afsmgrEventManagerTrap 14 }

		psuEquipStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Power Supply Unit Equip/Unequip Status Notification."
			::= { afsmgrEventManagerTrap 15 }
		
		portAdminNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Port Administration Status Notification."
			::= { afsmgrEventManagerTrap 16 }
		
		fanOperStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Fan Operational Status Notification."
			::= { afsmgrEventManagerTrap 17 }

		rmonRisingNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Rmon Rising Notification."
			::= { afsmgrEventManagerTrap 18 }
											
		rmonFallingNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Rmon Falling Notification."
			::= { afsmgrEventManagerTrap 19 }
											
		portSLDNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Port Self-Loop Detection Notification."
			::= { afsmgrEventManagerTrap 20 }

											
		remoteConnection NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Remote connection Notification."
			::= { afsmgrEventManagerTrap 30 }

   		ponDriftWindowNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Onu Drift Window Notification."
			::= { afsmgrEventManagerTrap 41 }
		                                     	                                     
   		ponGemChannelLossNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Loss of GEM channel delineation Notification."
			::= { afsmgrEventManagerTrap 42 }
				                                     
   		ponAckLossNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Loss of acknowledge with ONUi Notification."
			::= { afsmgrEventManagerTrap 43 }
				                                     
   		ponSigDegradeNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Signal Degraded of ONUi Notification."
			::= { afsmgrEventManagerTrap 44 }
				                                     
   		ponSigFailNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Signal Fail of ONUi Notification."
			::= { afsmgrEventManagerTrap 45 }
				                                     
   		ponPhysEquipErrNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Physical Equipment Error of ONUi Notification."
			::= { afsmgrEventManagerTrap 46 }
                                             				                                     
   		ponKeySyncLossNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Loss of Key sync with ONUi Notification."
			::= { afsmgrEventManagerTrap 47 }
				                                     
   		ponTransIfWarmNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Transmission Interference Warning Notification."
			::= { afsmgrEventManagerTrap 48 }
				                                     
   		ponTransIfAlarmNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Transmission Interference Alarm Notification."
			::= { afsmgrEventManagerTrap 49 }
				                                     
   		ponRemoDefectIndNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Remote Defect Indication of ONUi Notification."
			::= { afsmgrEventManagerTrap 50 }
			
		onuOperStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Onu Operation Status Notification."
			::= { afsmgrEventManagerTrap 51 }
		
		oltAlarmNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Olt Alarm Notification."
			::= { afsmgrEventManagerTrap 52 }
			
		oltLinkFaultNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Olt Link Fault Notification."
			::= { afsmgrEventManagerTrap 53 }		

		ontDyingGaspNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Ont Dying Gasp Notification."
			::= { afsmgrEventManagerTrap 54 }              

		ponLinkStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Link Status Notification."
			::= { afsmgrEventManagerTrap 55 }  
						
		linkLoopbackTestNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Link Loopback Test Notification."
			::= { afsmgrEventManagerTrap 57 }   
       
         ponOltOperStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Olt Oper Status Notification."
			::= { afsmgrEventManagerTrap 68 }                                         
       
        ponOltAdminStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Olt Administrator Status Notification."
			::= { afsmgrEventManagerTrap 69 }                                         
                                                    
		ponOnuAdminStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Onu Admin Status Notification."
			::= { afsmgrEventManagerTrap 70 }  
		
		ponOnuRegisterSubMacNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Onu Subscriber Mac Registration Notification."
			::= { afsmgrEventManagerTrap 71 }

		linkLoopbackTestFailNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Link Loopback Test Fail Notification."
			::= { afsmgrEventManagerTrap 73 }               
		
	    ponOnuRegOverloadNoti NOTIFICATION-TYPE
			OBJECTS { alarmIndex, alarmId, alarmType, alarmSeverity, alarmPhysicalLoc, alarmLogicalLoc, alarmCurStatus, alarmAuxinfo, alarmDateTime, alarmStatus }
			STATUS current                          
			DESCRIPTION 
				"Pon Onu Register Overload Notification. (onu too many registration)"
			::= { afsmgrEventManagerTrap 93 }
	
		ponLinkRegNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Link Register Notification."
			::= { afsmgrEventManagerTrap 96 } 
		
		ponOnuLoopDetectNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Onu Loop Detect Notification."
			::= { afsmgrEventManagerTrap 97 }		
		
			
		ponOltImageUpgrageNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Olt Image Upgrade Notification."
			::= { afsmgrEventManagerTrap 98 }
			
		ponOltImageUpgrageFailNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Olt Image Upgrade Fail Notification."
			::= { afsmgrEventManagerTrap 99 }
     
        onuImageUpgradeNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"ONU Image Upgrade Notification."
			::= { afsmgrEventManagerTrap 100 }
		
		onuImageUpgradeFailNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"ONU Image Upgrade Fail Notification."
			::= { afsmgrEventManagerTrap 101 }                           

		onuLdShutdownNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"ONU LD shutdown Notification."
			::= { afsmgrEventManagerTrap 102 }       
			
		ponUnadminMacRegNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Unadmin Mac-address Register Notification."
			::= { afsmgrEventManagerTrap 103 }
                                                
		ponDupMacRegNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Duplicated Mac-address Register Notification."
			::= { afsmgrEventManagerTrap 104 }

		ponOnuTypeMismatchNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Onu Type Mismatch Notification."
			::= { afsmgrEventManagerTrap 105 }
                  
		ponOltDyingGaspNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Olt DyingGasp Notification."
			::= { afsmgrEventManagerTrap 106 }                
                                                                                          
		ponOltCableDownNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Olt Cable Down Notification."
			::= { afsmgrEventManagerTrap 107 }

		ponPMCcrc32MonitorNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"PMC CRC32 Monitor Notification."
			::= { afsmgrEventManagerTrap 108 }
			
		imageUpDownloadStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Image Up/Download Status Notification."
			::= { afsmgrEventManagerTrap 109 }  
			
		imageUpDownloadFailNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Image Up/Download Fail Notification."
			::= { afsmgrEventManagerTrap 110 }      

		configUpDownloadStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Config Up/Download Status Notification."
			::= { afsmgrEventManagerTrap 111 }
			
		sysRebootMaxTempNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"System Reboot by Max Temperature Notification."
			::= { afsmgrEventManagerTrap 112 }
					
 		ponRogueOnuLdShutdown NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Rogue Onu Ld Shutdown Notification."
			::= { afsmgrEventManagerTrap 113 }

		scuOperStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"SCU Operation Status Notification."
			::= { afsmgrEventManagerTrap 114 }
		
		configUpDownloadFailNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Config Up/Download Fail Notification."
			::= { afsmgrEventManagerTrap 115 }           
			
		ponOntRxPowerStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Ont Rx-optical-alarm Notification."
			::= { afsmgrEventManagerTrap 116 }

		ponOltRxPowerStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Olt Rx-optical-alarm Notification."
			::= { afsmgrEventManagerTrap 117 }   	     
			
		ponOntTxPowerStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Ont Tx-optical-alarm Notification."
			::= { afsmgrEventManagerTrap 118 }

		ponOntTemperatureStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Ont Temperature-alarm Notification."
			::= { afsmgrEventManagerTrap 119 }


		ponOntVoltageStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Ont Voltage-alarm Notification."
			::= { afsmgrEventManagerTrap 120 }
                                            
        ponOntBiasStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Ont Bias-alarm Notification."
			::= { afsmgrEventManagerTrap 121 }         
			
        ponOltRedSlaveFaultNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Olt Redundancy Slave Link Fault Notification."
			::= { afsmgrEventManagerTrap 122 }  
			             
        ponOltRedSwitchoverNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Olt Redundancy Switchover Notification."
			::= { afsmgrEventManagerTrap 123 }  

        ponOnuOpticRxPowerOnusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Onus Low Optic Rx Power Notification."
			::= { afsmgrEventManagerTrap 124 }  

        ponOnuDownThresholdNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Onu Down Threshold Notification."
			::= { afsmgrEventManagerTrap 127 }
		             
		ponOnuFanStatusNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Onu Fan Status Notification."
			::= { afsmgrEventManagerTrap 128 }
		             
		ExternalACAlarm  NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"External AC alarm"
			::= { afsmgrEventManagerTrap 129 }

		ExternalUnitAlarm NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"External unit alarm."
			::= { afsmgrEventManagerTrap 130 }
                                                                  
        ponLoopCntThresholdNoti NOTIFICATION-TYPE
             OBJECTS { alarmIndex, alarmId, alarmType, alarmSeverity, alarmPhysicalLoc, alarmLogicalLoc, alarmCurStatus, alarmAuxinfo, alarmDateTime, alarmStatus }
             STATUS current
             DESCRIPTION 
             "Loop-Count-Threshold-alarm Notification."
             ::= { afsmgrEventManagerTrap 131 }
             
        scuUnequipNoti  NOTIFICATION-TYPE
             OBJECTS { alarmIndex, alarmId, alarmType, alarmSeverity, alarmPhysicalLoc, alarmLogicalLoc, alarmCurStatus, alarmAuxinfo, alarmDateTime, alarmStatus }
             STATUS current
             DESCRIPTION 
             "scu unequip alarm"
             ::= { afsmgrEventManagerTrap 132 }
        
        liuUnequipNoti    NOTIFICATION-TYPE
             OBJECTS { alarmIndex, alarmId, alarmType, alarmSeverity, alarmPhysicalLoc, alarmLogicalLoc, alarmCurStatus, alarmAuxinfo, alarmDateTime, alarmStatus }
             STATUS current
             DESCRIPTION 
             "liu unequip alarm"
             ::= { afsmgrEventManagerTrap 133 }

        fmuUnequipNoti  NOTIFICATION-TYPE
             OBJECTS { alarmIndex, alarmId, alarmType, alarmSeverity, alarmPhysicalLoc, alarmLogicalLoc, alarmCurStatus, alarmAuxinfo, alarmDateTime, alarmStatus }
             STATUS current
             DESCRIPTION 
             "fmu unequip alarm" 
             ::= { afsmgrEventManagerTrap 134 }
			
   		ponOltLineCodeErrorMonitorNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"OLT line code errors monitor Notification"
			::= { afsmgrEventManagerTrap 135 }
			
   		ponOltAlignmentErrorMonitorNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"OLT alignment errors monitor Notification"
			::= { afsmgrEventManagerTrap 136 }

		scuEjectorAlarmNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"SCU ejector alarm Notification"
			::= { afsmgrEventManagerTrap 137 }
		
		systemCheckAlarm NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"EMS System Check Monitor Notification"
			::= { afsmgrEventManagerTrap 138 }

		ponOnuRegThreshOverNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Pon Onu Registration Threshold Over Notification"
			::= { afsmgrEventManagerTrap 139 }                                        

		dcTempHighNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Dc Board Temperature High Threshold Notification"
			::= { afsmgrEventManagerTrap 140 } 

		dcTempLowNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Dc Board Temperature Low Threshold Notification"
			::= { afsmgrEventManagerTrap 141 } 			

		humidityHighNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Mainboard Humidity High Threshold Notification"
			::= { afsmgrEventManagerTrap 142 } 

		humidityLowNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Mainboard Humidity Low Threshold Notification"
			::= { afsmgrEventManagerTrap 143 }

		dcHumidityHighNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Dc Board Humidity High Threshold Notification"
			::= { afsmgrEventManagerTrap 144 } 

		dcHumidityLowNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Dc Board Humidity Low Threshold Notification"
			::= { afsmgrEventManagerTrap 145 }

		sysRebootMaxDcTempNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"System Reboot by Max Dc Board Temperature Notification."
			::= { afsmgrEventManagerTrap 146 }

		sysRebootMaxHumidNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"System Reboot by Max Humidity Notification."
			::= { afsmgrEventManagerTrap 147 }

		sysRebootMaxDcHumidNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"System Reboot by Max Dc Board Humidity Notification."
			::= { afsmgrEventManagerTrap 148 }

		fanSpeedHighNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Fan Speed High Notification."
			::= { afsmgrEventManagerTrap 149 }

		psuUnequipNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Psu Unequip Notification."
			::= { afsmgrEventManagerTrap 150 }   
		
		doorOpenAlarmNoti NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"Door Open Monitor Notification"
			::= { afsmgrEventManagerTrap 151 }	
			
		ExternalMajorAlarm NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"External Power Major Alarm."
			::= { afsmgrEventManagerTrap 152 }      
			
			
		Piu10gFanFailAlarm NOTIFICATION-TYPE
			OBJECTS { alarmIndex, alarmId, alarmType, alarmSeverity, alarmPhysicalLoc, alarmLogicalLoc, alarmCurStatus, alarmAuxinfo, alarmDateTime, alarmStatus }
			STATUS current
			DESCRIPTION 
				"10G PIU Fan Fail Alarm."
			::= { afsmgrEventManagerTrap 157 }


			
-- TODO
					
	END

--
-- UBQS-AFSMGR-EVENT-MANAGEMENT-MIB.my
--
