DEVTRAPS-MIB DEFINITIONS ::= BEGIN

	IMPORTS
		MODULE-IDENTITY, OBJECT-TYPE, NOTIFICATION-TYPE
			FROM SNMPv2-SMI
		device
			FROM ANIROOT-MIB;

-- Device Trap Mib (Common to BSU/SU)

aniDevTrap  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	   "The trap group.
	   "
	  ::= { device 10 }

aniDevTrapControl       OBJECT IDENTIFIER ::= { aniDevTrap 1 }
aniDevTraps             OBJECT IDENTIFIER ::= { aniDevTrap 0 }

aniDevControlTrapGeneration  OBJECT-TYPE 	  
	SYNTAX	INTEGER {
		enable(1),
		disable(2)
	}           
	MAX-ACCESS  read-write
	STATUS      current
	DESCRIPTION
	"Enable or disable SNMP Trap Generation."
	--DEFAULT next-function-async     std_next_async
	::= { aniDevTrapControl 1 }


aniDevTrapSuSyncAcquired NOTIFICATION-TYPE 
	STATUS      current
	DESCRIPTION
	   "This trap is generated by LKAD when SYNC is acquired.
	   "
        ::= { aniDevTraps 1 }

aniDevTrapBsuSuUp NOTIFICATION-TYPE 
	STATUS      current
	DESCRIPTION
	   "This trap is sent out by BSU to report that SU is 
	    operational.
	   "
        ::= { aniDevTraps 2 }

aniDevTrapBsuSuDown NOTIFICATION-TYPE 
	STATUS      current
	DESCRIPTION
	   "This trap is sent out by BSU to report that SU is down.
	   "
        ::= { aniDevTraps 3 }

aniDevTrapSuBsuUp NOTIFICATION-TYPE 
	STATUS      current
	DESCRIPTION
	   "This trap is sent out by SU to report that BSU is 
	    operational.
	   "
        ::= { aniDevTraps 4 }

aniDevTrapSuBsuDown NOTIFICATION-TYPE 
	STATUS      current
	DESCRIPTION
	   "This trap is sent out by SU to report that BSU is down.
	   "
        ::= { aniDevTraps 5 }

aniDevTrapDhcpFailure NOTIFICATION-TYPE 
	STATUS      current
	DESCRIPTION
	   "This trap is generated when DHCP fails.
	   "
        ::= { aniDevTraps 6 }

aniDevTrapConfigDownloadFailure NOTIFICATION-TYPE 
	STATUS      current
	DESCRIPTION
	   "This trap is generated when Config file download fails.
	   "
        ::= { aniDevTraps 7 }

aniDevTrapRamTooLow NOTIFICATION-TYPE 
	STATUS      current
	DESCRIPTION
	   "This trap is sent out to indicate that the RAM is 
	    too low.
	   "
        ::= { aniDevTraps 8 }

aniDevTrapRamNormal NOTIFICATION-TYPE 
	STATUS      current
	DESCRIPTION
	   "This trap is sent out to indicate that the RAM 
	    available is normal.
	    This trap is sent out to indicate that the 
	    aniDevTrapRamTooLow alarm is cleared. 
	   "
        ::= { aniDevTraps 9 }

aniDevTrapModemPllNotLocked NOTIFICATION-TYPE 
	STATUS      current
	DESCRIPTION
	   "The Modem PLL (Phase Locked Loop) not locked trap. 
	   "
        ::= { aniDevTraps 10 }

aniDevTrapModemPllNotLockedClear NOTIFICATION-TYPE 
	STATUS      current
	DESCRIPTION
	   "The Modem PLL (Phase Locked Loop) not locked trap cleared. 
	    This trap is sent out to indicate that the 
	    aniDevTrapModemPllNotLocked alarm is cleared. 
	   "
        ::= { aniDevTraps 11 }

aniDevTrapRadioVoltReg NOTIFICATION-TYPE 
	STATUS      current
	DESCRIPTION
	   "This trap indicates a Radio Voltage Failure. 
	    It is sent out by both BSU and SU.
	   "
        ::= { aniDevTraps 12 }

aniDevTrapRadioVoltRegClear NOTIFICATION-TYPE 
	STATUS      current
	DESCRIPTION
	   "This trap is sent out when aniDevTrapRadioVoltReg
	    (Radio Voltage Failure) alarm is cleared. 
	    It is sent out by both BSU and SU.
	   "
        ::= { aniDevTraps 13 }

aniDevTrapRadioSynthNotLocked NOTIFICATION-TYPE 
	STATUS      current
	DESCRIPTION
	   "This trap is generated when the Radio Synthesizer 
	    is not locked.
	    It is sent out by BSU and SU.
	   "
        ::= { aniDevTraps 14 }

aniDevTrapRadioSynthNotLockedClear NOTIFICATION-TYPE 
	STATUS      current
	DESCRIPTION
	   "This trap is sent out by BSU and SU to indicate that 
	    aniDevTrapRadioSynthNotLocked is cleared.
	   "
        ::= { aniDevTraps 15 }

aniDevTrapBsuFanStatus NOTIFICATION-TYPE 
	STATUS      current
	DESCRIPTION
	   "This trap is sent out when a fan on BSU is not 
	    operational.
	   "
        ::= { aniDevTraps 16 }

aniDevTrapBsuFanStatusClear NOTIFICATION-TYPE 
	STATUS      current
	DESCRIPTION
	   "This trap is sent to indicate that aniDevTrapBsuFanStatus
	    is cleared, that is, the fan on BSU is operational again.
	   "
        ::= { aniDevTraps 17 }

aniDevTrapBsuDc12vStatus NOTIFICATION-TYPE 
	STATUS      current
	DESCRIPTION
	   "This trap is generated when a 12V DC power failure occurs
	    on the BSU.
	   "
        ::= { aniDevTraps 18 }

aniDevTrapBsuDc12vStatusClear NOTIFICATION-TYPE 
	STATUS      current
	DESCRIPTION
	   "This trap indicates that aniDevTrapBsuDc12vStatus alarm
	    on the BSU has been cleared.
	   "
        ::= { aniDevTraps 19 }

aniDevTrapMssPllNotLocked NOTIFICATION-TYPE 
	STATUS      current
	DESCRIPTION
	   "The MSS PLL (Phase Locked Loop) not locked trap
	    which is sent out by BSU.
	   "
        ::= { aniDevTraps 20 }

aniDevTrapMssPllNotLockedClear NOTIFICATION-TYPE 
	STATUS      current
	DESCRIPTION
	   "This trap indicates that aniDevTrapMssPllNotLocked alarm
	    on the BSU has been cleared.
	   "
        ::= { aniDevTraps 21 }

aniDevTrapBsuTempTooLow NOTIFICATION-TYPE 
	STATUS      current
	DESCRIPTION
	   "This indicates that the temperature on the BSU is below
	    the operating limits. A temperature sensor on the BSU 
	    checks the operating temperature of the system board.
	   "
        ::= { aniDevTraps 22 }

aniDevTrapBsuTempTooHigh NOTIFICATION-TYPE 
	STATUS      current
	DESCRIPTION
	   "This indicates that the temperature on the BSU is above
	    the operating limits. A temperature sensor on the BSU 
	    checks the operating temperature of the system board.
	   "
        ::= { aniDevTraps 23 }

aniDevTrapBsuTempNormal NOTIFICATION-TYPE 
	STATUS      current
	DESCRIPTION
	   "This indicates that the temperature on the BSU is within
	    the operating limits. 
	    It shows that either the aniDevTrapBsuTempTooLow or 
	    aniDevTrapBsuTempTooHigh alarm on the BSU has been cleared.
	   "
        ::= { aniDevTraps 24 }

aniDevTrapFlashSpaceTooLow NOTIFICATION-TYPE 
	STATUS      current
	DESCRIPTION
	   "This trap is sent out when the disk space on file system 
	    is too low.
	    It can be sent out by either BSU or SU.
	   "
        ::= { aniDevTraps 25 }

aniDevTrapFlashSpaceNormal NOTIFICATION-TYPE 
	STATUS      current
	DESCRIPTION
	   "This trap is sent out when the disk space on file system 
	    is again normal.
	    It can be sent out by either BSU or SU to clear the
	    aniDevTrapFlashSpaceTooLow alarm.
	   "
        ::= { aniDevTraps 26 }

aniDevTrapNvramCorrupted NOTIFICATION-TYPE 
	STATUS      current
	DESCRIPTION
	   "This trap is sent out when the NVRAM is corrupted.
	    64 kB of NVRAM is allocated from the first block
	    of flash on both BSU and SU. A checksum is maintained
	    whenever some value if stored in it.
	   "
        ::= { aniDevTraps 27 }

aniDevTrapNvramCorruptionClear NOTIFICATION-TYPE 
	STATUS      current
	DESCRIPTION
	   "This trap indicates that aniDevTrapNvramCorrupted 
	    alarm has been cleared.
	   "
        ::= { aniDevTraps 28 }

aniDevTrapFileSysCorrupted NOTIFICATION-TYPE 
	STATUS      current
	DESCRIPTION
	   "This trap indicates that the file system
	    has been corrupted.
	    It can be sent out by either BSU or SU.
	   "
        ::= { aniDevTraps 29 }

aniDevTrapFileSysCorruptionClear NOTIFICATION-TYPE 
	STATUS      current
	DESCRIPTION
	   "This trap indicates that aniDevTrapFileSysCorrupted 
	    alarm has been cleared.
	    It can be sent out by either BSU or SU.
	   "
        ::= { aniDevTraps 30 }

aniDevTrapSmtpConnectFailure NOTIFICATION-TYPE 
	STATUS      current
	DESCRIPTION
	   "This trap is sent out when the connection to the
	    SMTP server fails.
	    It can be sent out by either BSU or SU.
	   "
        ::= { aniDevTraps 31 }

aniDevTrapSmtpDisabled NOTIFICATION-TYPE 
	STATUS      current
	DESCRIPTION
	   "This trap is sent out when SMTP is disabled on the
	    system (either BSU or SU).
	   "
        ::= { aniDevTraps 32 }

aniDevTrapSwWatchdogReset NOTIFICATION-TYPE 
	STATUS      current
	DESCRIPTION
	   "This trap is sent out when SU is reset by the Software 
	    Watchdog. The Software Watchdog feature detects low memory 
	    and task suspended cases, sends out the trap and reboots 
	    the device.
	   "
        ::= { aniDevTraps 33 }
	
aniDevTrapNatFailure NOTIFICATION-TYPE 
	STATUS      current
	DESCRIPTION
	   "This trap is sent out when NAT failure occurs.
	    It is sent out by SU.
	   "
        ::= { aniDevTraps 34 }

aniDevTrapCurrentImageCorrupted NOTIFICATION-TYPE 
	STATUS      current
	DESCRIPTION
	   "This trap is sent out to indicate that the current image 
	    is corrupted.
	    It can be sent out by both BSU or SU.
	   "
        ::= { aniDevTraps 35 }

aniDevTrapBsuSuFailedReg NOTIFICATION-TYPE 
	STATUS      current
	DESCRIPTION
	   "This trap is sent out when the BSU-SU registration fails.
	   "
        ::= { aniDevTraps 36 }

aniDevTrapDefaultConfigFileNotFound NOTIFICATION-TYPE 
	STATUS      current
	DESCRIPTION
	   "This trap is sent out when the default configuration
	    file is not found.
	    It can be sent out by both BSU or SU.
	   "
        ::= { aniDevTraps 37 }

aniDevTrapCurrentBsuState NOTIFICATION-TYPE 
	STATUS      current
	DESCRIPTION
	   "This trap shows the current BSU State.
	   "
        ::= { aniDevTraps 38 }

aniDevTrapCurrentSuState NOTIFICATION-TYPE 
	STATUS      current
	DESCRIPTION
	   "This trap shows the current SU State.
	   "
        ::= { aniDevTraps 39 }

aniDevTrapMemBufferTooLow NOTIFICATION-TYPE 
	STATUS      current
	DESCRIPTION
	   "This trap is sent out when the memory buffer is too low.
	    It can be sent out by either BSU or SU.
	   "
        ::= { aniDevTraps 40 }

aniDevTrapMemBufferNormal NOTIFICATION-TYPE 
	STATUS      current
	DESCRIPTION
	   "This trap is sent out when the memory buffer is again 
	    normal.
	    It can be sent out by either BSU or SU to clear the
	    aniDevMemBufferTooLow alarm.
	   "
        ::= { aniDevTraps 41 }

aniDevTrapConfigFileVersionCheckFailure NOTIFICATION-TYPE 
	STATUS      current
	DESCRIPTION
	   "This trap is sent out when there is a problem in the version
	    of the config file. It is sent out when either the version
	    information is missing or if there is a mismatch in the 
	    version.
	   "
        ::= { aniDevTraps 42 }

aniDevTrapDefaultFileVersionCheckFailure NOTIFICATION-TYPE 
	STATUS      current
	DESCRIPTION
	   "This trap is sent out when there is a problem in the version
	    of the default file. It is sent out when either the version
	    information is missing or if there is a mismatch in the 
	    version.
	   "
        ::= { aniDevTraps 43 }

aniDevTrapConfigFileUploadFailure NOTIFICATION-TYPE 
	STATUS      current
	DESCRIPTION
	   "This trap is sent out when the upload of the config file 
	    fails.
	   "
        ::= { aniDevTraps 44 }

aniDevTrapConfigFileUploadChecksumFailure NOTIFICATION-TYPE 
	STATUS      current
	DESCRIPTION
	   "This trap is sent out when there is a checksum error
	    on the config file after the upload. 
	   "
        ::= { aniDevTraps 45 }

aniDevTrapRunningBaselineImage NOTIFICATION-TYPE 
	STATUS      current
	DESCRIPTION
	   "This trap is sent out when a baseline image is
	    running.
	   "
        ::= { aniDevTraps 46 }



aniDevTrapPowerSupplyFailure NOTIFICATION-TYPE 
	STATUS      current
	DESCRIPTION
	   "This trap is sent out by the BSU when there is a power 
	    supply failure.
	   "
        ::= { aniDevTraps 48 }

aniDevTrapPowerSupplyNormal NOTIFICATION-TYPE 
	STATUS      current
	DESCRIPTION
	   "This trap is sent out by the BSU when the power supply is 
	    normal again. It is sent out to indicate that the 
	    aniDevTrapPowerSupplyFailure alarm is cleared. 
	   "
        ::= { aniDevTraps 49 }

aniDevTrapRealtimeClockFailure NOTIFICATION-TYPE 
	STATUS      current
	DESCRIPTION
	   "This trap is sent out by the BSU when there is a real time
	    clock failure.
	   "
        ::= { aniDevTraps 50 }

aniDevTrapRealtimeClockNormal NOTIFICATION-TYPE 
	STATUS      current
	DESCRIPTION
	   "This trap is sent out by the BSU when the real time clock 
	    is normal again. It is sent out to indicate that the 
	    aniDevTrapRealtimeClockFailure alarm is cleared. 
	   "
        ::= { aniDevTraps 51 }

aniDevTrapModelNumFailure NOTIFICATION-TYPE 
	STATUS      current
	DESCRIPTION
	   "This trap is sent out when there is an error
	    related to the model number. 
	   "
        ::= { aniDevTraps 53 }

aniDevTrapConfigParseFailure NOTIFICATION-TYPE 
	STATUS      current
	DESCRIPTION
	   "This trap is sent out when there is an error in
	    the parsing of the configuration file.
	   "
        ::= { aniDevTraps 55 }

aniDevUpdateInventory NOTIFICATION-TYPE 
	STATUS      current
	DESCRIPTION
	   "This trap is sent out to notify configuration change in
	    SU customer name. 
	   "
        ::= { aniDevTraps 56 }

aniDevTrapPppFailure NOTIFICATION-TYPE 
	STATUS      current
	DESCRIPTION
	   "This trap is sent out whenever PPP fails to establish a session.
	   "
        ::= { aniDevTraps 57 }

aniDevTrapPppStatus NOTIFICATION-TYPE 
	STATUS      current
	DESCRIPTION
	   "This trap is sent whenever a PPP link goes up or down.
	   "
        ::= { aniDevTraps 58 }

aniDevTrapFrequencyChange NOTIFICATION-TYPE 
	STATUS      current
	DESCRIPTION
	   "This trap is sent out whenever the channel frequency
	    is changed on the BSU and SU while they are in the 
	    operational state.
	   "
        ::= { aniDevTraps 59 }

aniDevTrapPPPoeSessionUp NOTIFICATION-TYPE 
	STATUS      current
	DESCRIPTION
	   "This trap is sent out whenever the when a PPPoE Session comes up.
	   "
        ::= { aniDevTraps 62 }

aniDevTrapPPPoeOfferError NOTIFICATION-TYPE 
	STATUS      current
	DESCRIPTION
       "This trap is sent out whenever the when no valid PPPoE Active Discovery Offer (PADO)
        is received in response to a PPPoE Active Discovery Initiation (PADI) packet 
        or if no valid PPPoE Active Discovery Session-confirmation (PADS) is received 
        in response to a PPPoE Active Discovery Request (PADR) packet.
	   "
        ::= { aniDevTraps 63 }

aniDevTrapPPPoeSessionTerminate NOTIFICATION-TYPE 
	STATUS      current
	DESCRIPTION
	   "This trap is sent out when a PPPoE Session is terminated.
	   "
        ::= { aniDevTraps 64 }

aniDevTrapEtherAutoNegotiate NOTIFICATION-TYPE 
	STATUS      current
	DESCRIPTION
	   "This trap is sent out when device go back to auto-negotiate mode.
	   "
        ::= { aniDevTraps 65 }

aniDevTrapRadioInitError NOTIFICATION-TYPE 
	STATUS      current
	DESCRIPTION
       "This trap is sent out when the radio can't be initialized.
        Under an error condition this event will be generated prior to 
        SU becoming operational.
	   "
        ::= { aniDevTraps 66 }

aniDevTrapMaxPowerError NOTIFICATION-TYPE 
	STATUS      current
	DESCRIPTION
       "This trap is sent out when when the radio board can't reach maximum
        configured power. This can be caused by a combination of faulty 
        (or very long) coaxial cable connecting IDU and ODU and/or extremely 
        hot weather or just bad calibration data on the radio board.
	   "
        ::= { aniDevTraps 67 }

aniDevTrapMaxPowerErrorClear NOTIFICATION-TYPE 
	STATUS      current
	DESCRIPTION
	   "This trap is sent out when the event aniDevTrapMaxPowerError has been cleared.
	   "
        ::= { aniDevTraps 68 }

aniDevTrapAgcTableNotCalibrated NOTIFICATION-TYPE 
	STATUS      current
	DESCRIPTION
       "This trap is sent out when the AGC Table is not calibrated.
        SODU platform relies on accurate calibration of the receive gain
        throughout the entire receive chain. If the table is not correctly calibrated
        or gets corrupted in the field, the SODU will have to fall back on default receive
        power adjustment algorithm, which may be far from optimal. This problem doesn't stop 
        an SODU from getting operational but the downstream link quality can suffer.
	   "
        ::= { aniDevTraps 69 }

aniDevTrapFreqTableInvalidEntry NOTIFICATION-TYPE 
	STATUS      current
	DESCRIPTION
	   "This trap is sent out whenever the frequency table contains an invalid entry.
	   "
        ::= { aniDevTraps 70 }

aniDevTrapHtmlUnzippedError NOTIFICATION-TYPE 
	STATUS      current
	DESCRIPTION
	   "This trap is sent out when html compressed zip files are either missing or 
	    corrupted.
	   "
        ::= { aniDevTraps 71 }

aniDevTrapBootLineBackupUpdated NOTIFICATION-TYPE 
	STATUS      current
	DESCRIPTION
	   "This trap is sent out whenever the backup bootline parameters are updated to bring 
	   them in sync with the actual boot parameters.
	   "
        ::= { aniDevTraps 72 }

aniDevTrapBootLineRestoredFromBackup NOTIFICATION-TYPE 
	STATUS      current
	DESCRIPTION
	   "This trap is sent out when the main bootline parameters are corrupted 
	   and the system has to fall back on backup boot parameters.
	   "
        ::= { aniDevTraps 73 }

aniDevTrapNvramBackupUpdated NOTIFICATION-TYPE 
	STATUS      current
	DESCRIPTION
	   "This trap is sent out whenever the backup copy of NVRAM configuration 
	   parameters is updated to bring them in sync with the actual NVRAM configuration.
	   "
        ::= { aniDevTraps 74 }

aniDevTrapNvramRestoredFromBackup NOTIFICATION-TYPE 
	STATUS      current
	DESCRIPTION
	   "This trap is sent out when the main NVRAM configuration data is corrupted 
	   and the system has to fall back on backup NVRAM configuration.
	   "
        ::= { aniDevTraps 75 }


END
