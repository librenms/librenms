SAMSUNG-PRINTER-EXT-TC DEFINITIONS ::= BEGIN

-- Module:  Printer MIB TC
-- File: SamsungPrinttc.mib
-- Editors: wono.song@samsung.com
-- Date:    July 17, 2004
-- Version: 1.00

IMPORTS
    MODULE-IDENTITY, OBJECT-TYPE
        FROM SNMPv2-SMI                    -- RFC 1442/1902/2578
    TEXTUAL-CONVENTION
        FROM SNMPv2-TC                     -- RFC 1443/1903/2579
    samsungCommonMIB
        FROM SAMSUNG-COMMON-MIB;

scmPrintTC MODULE-IDENTITY
    LAST-UPDATED "0407170000Z" -- 17 Jul 2004
    ORGANIZATION "Samsung Common Management Interface Working Group"
    CONTACT-INFO "
                      SCMI Editors
        E-Mail:       wono.song@samsung.com

        --
        --
    "
    DESCRIPTION "
        Version:    1.00

        SCMI Extensions to Printer MIB Textual Conventions.
        This Module provides Samsung extensions of the IETF Printer MIB.

        Copyright (C) 2003-2004 Samsung Corporation. All Rights Reserved."
    ::= { samsungCommonMIB 54 }

--
--  SCMI Extensions to Printer MIB Textual Convention Definitions:
--
--      ScmPrtAuxSheetContent
--      ScmPrtAuxSheetType
--      ScmPrtChannelType
--      ScmPrtGroupSupport
--      ScmPrtIETFPrintMIBGroupSupport
--      ScmPrtInterpreterLangFamily


--      ScmPrtMediaTypeErrorPolicy
--      ScmPrtMediumClassType
--      ScmPrtMediumSize
--      ScmPrtOutputOffsetStackingType
--      ScmPrtOutputStaplePosition
--      ScmPrtPageSizeErrorPolicy
--      ScmPrtPCLFontSource
--      ScmPrtPlex
--      ScmPrtPrintQuality
--      ScmPrtPrintScreen
--      ScmPrtTraySwitch
--      ScmPrtGeneralMonoPrintOpt 
--

ScmPrtAuxSheetContent ::= TEXTUAL-CONVENTION
    STATUS      current
    DESCRIPTION "
        Auxiliary sheets are added by the printing system and
        are not part of the actual print job. Examples include
        error pages and banner pages.

        This textual convention is used to specify the information
        content of auxiliary sheets."
    SYNTAX INTEGER {
                other(1),
                unknown(2),
                notSpecified(3),
                concise(5),              -- content of page is concise
                verbose(6)               -- content of page is verbose
                }

ScmPrtAuxSheetType ::= TEXTUAL-CONVENTION
    STATUS      current
    DESCRIPTION "
        Auxiliary sheets are added by the printing system and
        are not part of the actual print job.
        This attribute uniquely identifies an auxiliary-sheet,
        which includes the types jobErrorSheet and printerStartupSheet.

        'printerStartupSheet' is a sheet printed shortly after power-up
        when the device is ready.  Typical startup pages include test
        patterns and/or printer configuration information.

        'jobErrorSheet' is a sheet printed with error messages
        generated during the printing of a job-result-set that is to be
        printed with the hardcopy output of that job-result-set, and
        should be printed on an ending sheet of the job-result-set, or
        some similar sheet.  These sheets are not
        a part of any job-copy.  If no error messages have been
        generated, the device need not print an extra page.
        The default for this page type should be 'On'.

        The following Auxiliary-sheet-package types can be specified 
        either for a job component (job result set or job copy) or


        document (document result set or document copy).
        For now, only the jobSetStart package has been enumerated.   

        'jobSetStart' - Auxiliary-sheet starts each result-set
                        Sometimes referred to as a jobBanner sheet
        'jobSetEnd'   - Auxiliary-sheet at the end of a result set "

    REFERENCE   "
        ISO/IEC 10175-1:1996(E)
        Section 9.10.2.2: Delivery-methods for hardcopy output logs
        Section 9.11.1:   Auxiliary-sheet-package identifier"
    SYNTAX INTEGER {
                other(-1),
                unknown(-2),
                notSpecified(-3),

                jobSetStart(1),
                jobSetEnd(2),

                printerStartupSheet(101),
                jobErrorSheet(102)
                }

ScmPrtChannelType ::= TEXTUAL-CONVENTION
    STATUS      current
    DESCRIPTION "
        This enumeration indicates the type of channel that is
        receiving jobs.

        This enumeration is being added to the IETF Printer MIB.

        This is an IETF type 2 enum."
    SYNTAX INTEGER {
                       other(1),
                       chSerialPort(3),
                       chParallelPort(4),
                       chIEEE1284Port(5),
                       chSCSIPort(6),
                       chAppleTalkPAP(7),
                           -- AppleTalk Printer
                           -- Access Protocol (PAP)
                           --
                           -- prtChannelInformation entry:
                           --
                           -- Printer Name
                           --   Keyword:      Name
                           --   Status:       Optional
                           --   Multiplicity: Single
                           --   Description:  The name of the
                           --     printer within the AppleTalk
                           --     naming scope
                       chLPDServer(8),
                           -- prtChannelInformation entry:
                           --


                           -- Printer queue name
                           --   Keyword:      Queue
                           --   Syntax:       Name
                           --   Status:       Mandatory
                           --   Multiplicity: Single
                           --   Description: queue name as
                           --     defined in RFC 1179.
                       chNetwareRPrinter(9),
                           -- Novell, Inc.
                           -- For each entry of this type, the
                           -- prtChannelInformation must have a pair
                           -- of keywords. For Netware 3.x channels
                           -- this must be a (PServer, Printer) pair.
                           -- For Netware 4.x channels and for
                           -- IntranetWare channels this must be a
                           -- (NDSTree, NDSPrinter) pair.
                           --
                           -- prtChannelInformation entries:

                           -- Print Server Name
                           --   Keyword:       PServer
                           --   Syntax:        Name
                           --   Status:        Mandatory
                           --   Multiplicity: Single
                           --   Description:  The Pserver's SAP name
                           --
                           -- Printer Number
                           --   Keyword:       Printer
                           --   Syntax:        Integer
                           --   Status:        Mandatory
                           --   Multiplicity: Single
                           --   Description:  The printer number
                           --
                           -- NDSTree
                           --   Keyword:      NDSTree
                           --   Syntax:       Name
                           --   Multiplicity: Single
                           --   Description:  The tree's SAP name
                           --
                           -- NDS Printer object
                           --   Keyword:      NDSPrinter
                           --   Syntax:       Text (Unicode)
                           --   Status:       Mandatory
                           --   Multiplicity: Single
                           --   Description:  The fully qualified
                           --     name of the Printer
                           --
                           -- In the Netware 3.x environment, the
                           -- client checks the Bindery object
                           -- representing the named PServer. The
                           -- client then checks for queues which
                           -- are associated with the numbered
                           -- printer. In the 4.x and IntraNetware
                           -- environment, the client looks up the


                           -- queues which are associated with the
                           -- NDS Printer Object in the named Tree.
                           -- Depending on client access rights to
                           -- those queues, the client submits jobs
                           -- to the appropriate queue.
                        chNetwarePServer(10),
                           -- Novell,Inc.
                           -- For each entry of this type, the
                           -- prtChannelInformation must have a pair
                           -- of keywords. For Netware 3.x channels
                           -- this must be a (Server, PServer) pair.
                           -- For Netware 4.x and IntranetWare
                           -- channels, this must be a
                           -- (NDSTree, NDSPServer) pair.
                           --
                           -- prtChannelInformation entries:
                           --
                           -- Server Name
                           --   Keyword:      Server
                           --   Syntax:       Name
                           --   Status:       Mandatory
                           --   Multiplicity: Single
                           --   Description:  The SAP name of the
                           --     server for which the PServer is
                           --     defined.
                           --
                           -- PServer
                           --   Keyword:      PServer
                           --   Syntax:       Name
                           --   Status:       Mandatory
                           --   Multiplicity: Single
                           --   Description:  The bindery name of
                           --     the PServer
                           --
                           -- NDS Tree
                           --   Keyword:      NDSTree
                           --   Syntax:       Name
                           --   Status:       Mandatory
                           --   Multiplicity: Single
                           --   Description:  The NDS Tree name
                           --
                           -- PServer
                           --   Keyword:      NDSPServer
                           --   Syntax:       Text (Unicode)
                           --   Status:       Mandatory
                           --   Multiplicity: Single
                           --   Description:  The fully qualified
                           --     name of the PServer object in the
                           --     tree.
                           --
                           -- In the 3.x environment, the client
                           -- checks the bindery object
                           -- representing the named PServer on the
                           -- named Server. In the 4.x and


                           -- IntranetWare environment,
                           -- the client checks the NDS object
                           -- representing the named PServer in the
                           -- named Tree. In either case, the
                           -- client then checks for all queues
                           -- associated with the Pserver object.
                           -- Depending on client access rights
                           -- to those queues, the client submits
                           -- jobs to the appropriate queue.
                       chPort9100(11),
                           -- DEPRECATED
                       chAppSocket(12),
                           -- A bi-directional, LPD-like,
                           -- protocol using 9101 for
                           -- control and 9100 for data.
                           -- Adobe Systems, Inc.
                       chFTP(13),         -- RFC 959
                       chTFTP(14),        -- RFC 1350
                       chDLCLLCPort(15),
                       chIBM3270(16),     -- IBM Coax
                       chIBM5250(17),     -- IBM Twinax
                       chFax(18),
                       chIEEE1394(19),
                       chTransport1(20),
                           -- TCP port 35, see reserved TCP port list
                           -- in RFC 1700 or current "Assigned
                           -- Numbers" RFC. This RFC should also be
                           -- referenced for other channel
                           -- enumerations utilizing TCP port
                           -- numbers 0 through 1024.
                       chCPAP(21),      -- TCP port 170, Digital
                                        -- Equipment Corp.
                       chPCPrint(26),   -- Banyan
                       chServerMessageBlock(27),
                           -- File/Print sharing protocol used by
                           -- various network operating systems
                           -- from IBM 3Com, Microsoft and others
                           --
                           -- prtChannelInformation entry:
                           --
                           -- Service Name
                           --   Keyword:      Name
                           --   Syntax:       Name
                           --   Status:       Optional
                           --   Multiplicity: Single
                           --   Description:  The service name of
                           --     the printer
                       chPSM(28),       -- Printing Systems
                                        -- Manager, IBM
                       chSystemObjectManager(31), -- IBM
                       chDECLAT(32),
                           -- Digital Equipment Corp.
                           --
                           -- prtChannelInformation entries:


                           --
                           -- Port Name
                           --   Keyword:      Port
                           --   Syntax:       Name
                           --   Status:       Conditionally
                           --                 Mandatory
                           --                 (see note below)
                           --   Multiplicity: Single
                           --   Description:  LAT port name
                           --
                           -- Service Name
                           --    Keyword:      Service
                           --    Syntax:       Name
                           --    Status:       Conditionally
                           --                  Mandatory
                           --    Multiplicity: Single
                           --    Description:  LAT service
                           --      name
                           --
                           -- The LAT channel may be
                           -- identified by either a port or
                           -- service, so either a
                           -- Port or Service entry must be
                           -- specified, but not both.
                       chNPAP(33),
                       chUSB(34),    -- Universal Serial Bus
                       chIRDA(35),   -- Infrared Data Assoc. Prot.
                       chPrintXChange(36), -- PrintXChange Protocol
                       chPortTCP(37),
                           -- A unidirectional "raw" TCP
                           -- channel that uses an administratively
                           -- assigned TCP port address.
                           --
                           -- prtChannelInformation entry:
                           --
                           -- Port Number
                           --    Keyword:      Port
                           --    Syntax:       decimal number
                           --    Status:       Mandatory
                           --    Multiplicity: Single
                           --    Description:  TCP port number
                       chBidirPortTCP(38),
                           -- A bidirectional version of chPortTCP
                           --
                           -- prtChannelInformation entries:
                           -- (See chPortTCP)
                       chUNPP(39),
                           -- Universal Network Printing
                           -- Protocol(UNPP). A bi-directional,
                           -- multiport network printing
                           -- application protocol available on
                           -- multiple transport protocols.
                           -- Underscore, Inc.
                           -- Contact: info@underscore.com


                       chAppleTalkADSP(40),
                           -- AppleTalk Data Stream Protocol.
                           -- ADSP is part of the AppleTalk
                           -- suite of protocols.
                           -- It is a symmetric, connection-
                           -- oriented protocol that makes
                           -- possible the establishment
                           -- and maintenance of full-duplex
                           -- streams of data bytes between
                           -- two sockets in an AppleTalk
                           -- internet.
                           -- See Inside AppleTalk, second
                           -- Edition, by Sidhu, Andrews and
                           -- Oppenheimer.
                       chPortSPX(41),
                           -- Sequenced Packet Exchange (SPX)
                           -- socket.
                           -- Novell, Inc. Similar to TCP, a
                           -- bi-directional data pipe using
                           -- Novell SPX as a transport.
                           --
                           -- prtChannelInformation entries:
                           --
                           -- Network Number
                           --   Keyword:      Net
                           --   Syntax:       HexString
                           --   Status:       Mandatory
                           --   Multiplicity: Single
                           --   Description:  The network number
                           --
                           -- Node Number
                           --   Keyword:      Node
                           --   Syntax:       HexString
                           --   Status:       Mandatory
                           --   Multiplicity: Single
                           --   Description:  The node number
                           --
                           -- Socket Number
                           --   Keyword:      Socket
                           --   Syntax:       HexString
                           --   Status:       Mandatory
                           --   Multiplicity: Single
                           --   Description:  The SPX socket number
                           --
                           -- There must be exactly one "Net" and
                           -- one "Node" and one "Socket" entry. A
                           -- HexString is a binary value
                           -- represented as a string of
                           -- ASCII characters using hexadecimal
                           -- notation.
                       chPortHTTP(42),
                           -- Hypertext Transfer Protocol. See IETF
                           -- documents relating to HTTP 1.0/1.1
                           -- (RFCs 1945 and 2068,etc.)


                       chNDPS(43)
                           -- Novell, Inc.
                           --
                           -- prtChannelInformation entry:
                           --
                           -- Printer Agent Name
                           --   Keyword:      PA
                           --   Syntax:       Name
                           --   Status:       Mandatory
                           --   Multiplicity: Single
                           --   Description:  The NDPS Printer
                           --      Agent Name
                }

ScmPrtGroupSupport ::= TEXTUAL-CONVENTION
    STATUS      current
    DESCRIPTION "
        The terse conformance statement of ALL mandatory, conditionally
        mandatory, and optional Printer MIB Extension object groups,
        specified in a bit-mask.

        The current set of values (which may be extended in the future)
        is given below:
              1 : scmPrtBaseGroup                    -- 2**0
              2 : scmPrtGeneralGroup                 -- 2**1
              4 : scmPrtInputGroup                   -- 2**2
              8 : scmPrtOutputGroup                  -- 2**3
             16 : scmPrtChannelGroup                 -- 2**4
             32 : scmPrtInterpreterGroup             -- 2**5
             64 : scmPrtInputAliasGroup              -- 2**6
            128 : scmPrtGeneralAuxSheetGroup         -- 2**7
            256 : scmPrtGeneralProdSpecificGroup     -- 2**8
            512 : scmPrtAuxPackageGroup              -- 2**9
           1024 : scmPrtChannelProdSpecificGroup     -- 2**10
           2048 : scmPrtInterpProdSpecificGroup      -- 2**11
           4096 : scmPrtInterpPCLGroup               -- 2**12
           8192 : scmPrtInterpPCLProdSpecificGroup   -- 2**13
          16384 : scmPrtMediumTypeSupportedGroup     -- 2**14

        Usage:  Conforming management agents shall ALWAYS accurately
        report their support for SCMI Printer MIB Extensions
        object groups."
    SYNTAX      INTEGER (0..2147483647)  -- biggest int = 2**31-1

ScmPrtIETFPrintMIBGroupSupport ::= TEXTUAL-CONVENTION
    STATUS      current
    DESCRIPTION "
        The terse conformance statement of ALL mandatory, conditionally
        mandatory, and optional IETF Printer MIB object groups,
        specified in a bit-mask.

        The current set of values (which may be extended in the future)
        is given below:
              1 : prtGeneralGroup               -- 2**0   (mandatory)


              2 : prtResponsiblePartyGroup      -- 2**1  
              4 : prtInputGroup                 -- 2**2   (mandatory)
              8 : prtExtendedInputGroup         -- 2**3
             16 : prtInputMediaGroup            -- 2**4
             32 : prtOutputGroup                -- 2**5   (mandatory)
             64 : prtExtendedOutputGroup        -- 2**6
            128 : prtOutputDimensionsGroup      -- 2**7
            256 : prtOutputFeaturesGroup        -- 2**8
            512 : prtMarkerGroup                -- 2**9   (mandatory)
           1024 : prtMarkerSuppliesGroup        -- 2**10
           2048 : prtMarkerColorantGroup        -- 2**11
           4096 : prtMediaPathGroup             -- 2**12  (mandatory)
           8192 : prtChannelGroup               -- 2**13  (mandatory)
          16384 : prtInterpreterGroup           -- 2**14  (mandatory)
          32768 : prtConsoleGroup               -- 2**15  (mandatory)
          65536 : prtAlertTableGroup            -- 2**16  (mandatory)
         131072 : prtAuxiliarySheetGroup        -- 2**17
         262144 : prtInputSwitchingGroup        -- 2**18

        Usage:  Conforming management agents shall ALWAYS accurately
        report their support for IETF Printer MIB object groups."
    REFERENCE   "See: IETF Printer MIB"
    SYNTAX      INTEGER (0..2147483647)  -- biggest int = 2**31-1

ScmPrtInterpreterLangFamily ::= TEXTUAL-CONVENTION
    STATUS      current
    DESCRIPTION "
        This enumeration indicates the type of interpreter that is
        receiving jobs.

        This enumeration is being added to the IETF Printer MIB.

        This value is an IETF type 2 enumeration."
    SYNTAX INTEGER {
              other(1),
              unknown(2),
              langPCL(3),      -- PCL.  Starting with PCL version 5,
                               -- HP-GL/2 is included as part of the
                               -- PCL language.
                               -- PCL and HP-GL/2 are registered
                               -- trademarks of Hewlett-Packard
                               -- Company.
              langHPGL(4),     -- Hewlett-Packard Graphics Language.
                               -- HP-GL is a registered trademark of
                               -- Hewlett-Packard Company.
              langPJL(5),      -- Peripheral Job Language. Appears in
                               -- the data stream between data intended
                               -- for a page description language.
                               -- Hewlett-Packard Co.
              langPS(6),       -- PostScript (tm) Language
                               -- Postscript - a trademark of Adobe
                               -- Systems Incorporated which may be
                               -- registered in certain jurisdictions
              langIPDS(7),     -- Intelligent Printer Data Stream


                               -- Bi-directional print data stream for
                               -- documents consisting of data objects
                               -- (text, image, graphics, bar codes),
                               -- resources (fonts, overlays) and page,
                               -- form and finishing instructions.
                               -- Facilitates system level device
                               -- control, document tracking and error
                               -- recovery throughout the print
                               -- process.
                               -- Pennant Systems, IBM
              langPPDS(8),     -- IBM Personal Printer Data Stream.
                               -- Originally called IBM ASCII, the name
                               -- was changed to PPDS when the Laser
                               -- Printer was introduced in 1989.
                               -- Lexmark International, Inc.
              langEscapeP(9),  -- Epson Corp.
              langEpson(10),
              langDDIF(11),    -- Digital Document Interchange Format
                               -- Digital Equipment Corp., Maynard MA
              langInterpress(12),
                               -- Samsung Corp.
              langISO6429(13), -- ISO 6429.  Control functions for
                               -- Coded Character Sets (has ASCII
                               -- control characters, plus additional
                               -- controls for
                               -- character imaging devices.)
                               -- ISO Standard, Geneva, Switzerland
              langLineData(14),-- line-data:  Lines of data as
                               -- separate ASCII or EBCDIC records
                               -- and containing no control functions
                               -- (no CR, LF, HT, FF, etc.)
                               -- For use with traditional line
                               -- printers.  May use CR and/or LF to
                               -- delimit lines, instead of records.
                               -- See ISO 10175 Document Printing
                               -- Application(DPA)
                               -- ISO standard, Geneva, Switzerland
              langMODCA(15),   -- Mixed Object Document Content
                               -- Architecture
                               -- Definitions that allow the
                               -- composition, interchange, and
                               -- presentation of final form
                               -- documents as a collection of data
                               -- objects (text, image, graphics, bar
                               -- codes), resources (fonts, overlays)
                               -- and page, form and finishing
                               -- instructions.
                               -- Pennant Systems, IBM
              langREGIS(16),   -- Remote Graphics Instruction Set,
                               -- Digital Equipment Corp., Maynard MA
              langSCS(17),     -- SNA Character String
                               -- Bi-directional print data stream for
                               -- SNA LU-1 mode of communication.
                               -- IBM


              langSPDL(18),    -- ISO 10180 Standard Page Description
                               -- Language
                               -- ISO Standard
              langTEK4014(19), -- Tektronix Corp.
              langPDS(20),
              langIGP(21),     -- Printronix Corp.
              langCodeV(22),   -- Magnum Code-V, Image and printer
                               -- control language used to control
                               -- impact/dot-matrix printers.
                               -- QMS, Inc., Mobile AL
              langDSCDSE(23),  -- DSC-DSE:  Data Stream Compatible and
                               -- Emulation Bi-directional print data
                               -- stream for non-SNA (DSC) and SNA LU-3
                               -- 3270 controller (DSE) communications
                               -- IBM
              langWPS(24),     -- Windows Printing System, Resource
                               -- based command/data stream used by
                               -- Microsoft At Work Peripherals.
                               -- Developed by the Microsoft
                               -- Corporation.
              langLN03(25),    -- Early DEC-PPL3, Digital Equipment
                               -- Corp.
              langCCITT(26),
              langQUIC(27),    -- QUIC (Quality Information Code), Page
                               -- Description Language for laser
                               -- printers. Included graphics, printer
                               -- control capability and emulation of
                               -- other well-known printer .
                               -- QMS, Inc.
              langCPAP(28),    -- Common Printer Access Protocol
                               -- Digital Equipment Corp.
              langDecPPL(29),  -- Digital ANSI-Compliant Printing
                               -- Protocol
                               -- (DEC-PPL)
                               -- Digital Equipment Corp.
              langSimpleText(30),
                               -- simple-text:  character coded data,
                               -- including NUL, CR , LF, HT, and FF
                               -- control characters.  See ISO 10175
                               -- Document Printing Application (DPA)
                               -- ISO standard, Geneva, Switzerland
              langNPAP(31),    -- Network Printer Alliance Protocol
                               -- (NPAP). This protocol has been
                               -- superseded by the IEEE 1284.1 TIPSI
                               -- Std (ref. LangTIPSI(49)).
              langDOC(32),     -- Document Option Commands, Appears in
                               -- the data stream between data
                               -- intended for a page description .
                               -- QMS, Inc.
              langimPress(33), -- imPRESS, Page description language
                               -- originally developed for the
                               -- ImageServer product line. A binary
                               -- language providing representations
                               -- of text, simple graphics, and some


                               -- large forms (simple
                               -- bit-map and CCITT group /
                               -- encoded).The
                               -- language was intended to be sent over
                               -- an 8-bit channel and supported early
                               -- document preparation languages (e.g.
                               -- TeX and TROFF).
                               -- QMS, Inc.
              langPinwriter(34),
                               -- 24 wire dot matrix printer  for
                               -- USA, Europe, and Asia except
                               -- Japan.
                               -- More widely used in Germany, and
                               -- some Asian countries than in US.
                               -- NEC
              langNPDL(35),    -- Page printer  for Japanese market.
                               -- NEC
              langNEC201PL(36),-- Serial printer language used in
                               -- the Japanese market.
                               -- NEC
              langAutomatic(37),
                               -- Automatic PDL sensing.  Automatic
                               -- sensing of the interpreter
                               -- language family by the printer
                               -- examining the document content.
                               -- Which actual interpreter language
                               -- families are sensed depends on
                               -- the printer implementation.
              langPages(38),   -- Page printer Advanced Graphic
                               -- Escape Set
                               -- IBM Japan
              langLIPS(39),    -- LBP Image Processing System
              langTIFF(40),    -- Tagged Image File Format (Aldus)
              langDiagnostic(41),
                               -- A hex dump of the input to the
                               -- interpreter
              langPSPrinter(42),
                               -- The PostScript Language used for
                               -- control (with any PDLs)
                               -- Adobe Systems Incorporated
              langCaPSL(43),   -- Canon Print Systems Language
              langEXCL(44),    -- Extended Command Language
                               -- Talaris Systems Inc.
              langLCDS(45),    -- Line Conditioned Data Stream
                               -- Samsung Corporation
              langXES(46),     -- Samsung Escape Sequences
                               -- Samsung Corporation
              langPCLXL(47),   -- Printer Control Language. Extended
                               -- language features for printing, and
                               -- printer control.
                               -- Hewlett-Packard Co.
              langART(48),     -- Advanced Rendering Tools (ART).
                               -- Page Description language
                               -- originally developed for the Laser


                               -- Press printers.
                               -- Technical reference manual: "ART IV
                               -- Reference Manual", No F33M.
                               -- Fuji Samsung Co., Ltd.
              langTIPSI(49),   -- Transport Independent Printer
                               -- System Interface (ref. IEEE Std.
                               -- 1284.1)
              langPrescribe(50),
                               -- Page description and printer
                               -- control language. It can be
                               -- described with ordinary ASCII
                               -- Technical reference manual:
                               -- "PRESCRIBE II Programming Manual"
              langLinePrinter(51),
                               -- A simple-text character stream which
                               -- supports the control codes LF, VT,
                               -- FF, and plus Centronics or
                               -- Dataproducts Vertical Format Unit
                               -- (VFU) language is commonly used on
                               -- many older model line and matrix
                               -- printers.
              langIDP(52),     -- Imaging Device Protocol
                               -- Apple Computer.
              langXJCL(53),    -- Samsung Job Control Language (JCL).
                               -- A Job Control language originally
                               -- developed for the LaserPress printers
                               -- and is capable of switching PDLs.
                               -- Technical reference manual:
                               -- "ART IV Reference Manual", No F33M.
                               -- Fuji Samsung Co., Ltd.
              langPDF(54),     -- Adobe Portable Document Format
                               -- Adobe Systems, Inc.
              langRPDL(55),    -- Ricoh Page Description Language for
                               -- printers.
                               -- Technical manual "RPDL command
                               -- reference" No.307029
                               -- RICOH, Co. LTD
              langIntermecIPL(56),
                               -- Intermec Printer Language for label
                               -- printers.
                               -- Technical Manual: "IPL Programmers
                               -- Reference Manual"
                               -- Intermec Corporation
              langUBIFingerprint(57),
                               -- An intelligent basic-like programming
                               -- language for label printers.
                               -- Reference Manual: "UBI Fingerprint
                               -- 7.1", No. 1-960434-00
                               -- United Barcode Industries
              langUBIDirectProtocol(58)
                               -- An intelligent control language for
                               -- label printers.
                               -- Programmers guide: " UBI Direct
                               -- Protocol", No. 1-960419-00


                               -- United Barcode Industries
          }

ScmPrtMediaTypeErrorPolicy ::= TEXTUAL-CONVENTION
    STATUS      current
    DESCRIPTION "
        Controls interpreter behavior when the requested Media Type
        is not currently available.

        * The values 'other' and 'unknown' are deprecated for
          conforming implementations.
        * 'abortJob' will cause the interpreter to abort the job
          with an appropriate error condition.
        * 'ignore' will cause the job to be printed on the default
          media as specified by scmPrtInterpInputIndexDefault OR
          scmPrtInterpPaperSizeDefault OR any available media
          deemed appropriate by the implementation.
          No adjustment will be made to the image size.
          Exact semantics of this setting are product specific.
        * 'interactWithOperator' will cause the printer to interact
          with the operator to determine what to do. For example,
          display a message at the operator console requesting the
          desired media. The semantics of this policy vary among
          different products and environments.
        * 'ignoreAfterTimeout' will cause the job to be ignored
          same as 'ignore' above, but not till after
          scmPrtInterpErrorPolicyTimeout expires."
    REFERENCE "
        See: ScmPrtPageSizeErrorPolicy"
    SYNTAX INTEGER {
                other(1),
                unknown(2),
                notSpecified(3),
                abortJob(4),
                ignore(5),
                interactWithOperator(6),
                ignoreAfterTimeout(11)
                }

ScmPrtMediumClassType ::= TEXTUAL-CONVENTION
    STATUS      current
    DESCRIPTION "
        Paper size classes for a printer."
    SYNTAX INTEGER {
                other (1),
                unknown(2),
                notSpecified(3),
                northAmerica(4),
                iso(5),
                jis(6)
                }

ScmPrtMediumSize ::= TEXTUAL-CONVENTION
    STATUS      current


    DESCRIPTION "
        This attribute specifies the size of this medium by means of a
        pre-defined value.  The medium size specified in this manner may
        be one of the standard sizes to which object identifiers have
        been assigned in ISO/IEC 10175 (DPA), or another applicable
        standard, or for which a value has been created.

        Enumerations for DPA defined medium sizes are derived by adding
        1000 to the ISO/IEC 10175 enumerations.
        SCMI defined enumerations start at 10."
    REFERENCE   "ISO/IEC 10175-1:1996(E), Section 9.6.5: Medium-size"
    SYNTAX INTEGER {
                other(1),
                unknown(2),
                notSpecified(3),

                -- SCMI defined medium sizes
                mediumSize13x18(10),       -- 13   by 18 inches

                -- DPA defined medium sizes
                naLetter(1000),            --  8.5 by 11 inches
                naLegal(1001),             --  8.5 by 14 inches

                na10x13Envelope(1002),     -- 10   by 13 inches
                na9x12Envelope(1003),      --  9   by 12 inches
                naNumber10Envelope(1004),  --  4.125 by 9.5 inches
                na7x9Envelope(1005),       --  7   by  9 inches
                na9x11Envelope(1006),      --  9   by 11 inches
                na10x14Envelope(1007),     -- 10   by 14 inches
                naNumber9Envelope(1008),   --
                na6x9Envelope(1009),       --  6   by  9 inches
                na10x15Envelope(1010),     -- 10   by 15 inches

                a(1011),                   --  8.5 by 11 inches
                b(1012),                   -- 11   by 17 inches
                c(1013),                   -- 17   by 22 inches
                d(1014),                   -- 22   by 34 inches
                e(1015),                   -- 34   by 44 inches

                monarchEnvelope(1016),     -- 3.87 by 7.5 inches

                isoA0(1020),               -- 841 by 1189 mm
                isoA1(1021),               -- 594 by 841 mm
                isoA2(1022),               -- 420 by 594 mm
                isoA3(1023),               -- 297 by 420 mm
                isoA4(1024),               -- 210 by 297 mm
                isoA5(1025),               -- 148 by 210 mm
                isoA6(1026),               -- 105 by 148 mm
                isoA7(1027),               --  74 by 105 mm
                isoA8(1028),               --  52 by  74 mm
                isoA9(1029),               --  37 by  52 mm
                isoA10(1030),              --  26 by  37 mm

                isoB0(1040),               -- 1000 by 1414 mm


                isoB1(1041),               -- 707 by 1000 mm
                isoB2(1042),               -- 500 by 707 mm
                isoB3(1043),               -- 353 by 500 mm
                isoB4(1044),               -- 250 by 353 mm
                isoB5(1045),               -- 176 by 250 mm
                isoB6(1046),               -- 125 by 176 mm
                isoB7(1047),               --  88 by 125 mm
                isoB8(1048),               --  62 by  88 mm
                isoB9(1049),               --  44 by  62 mm
                isoB10(1050),              --  31 by  44 mm

                isoC3(1063),               -- 324 by 458 mm
                isoC4(1064),               -- 229 by 324 mm
                isoC5(1065),               -- 162 by 229 mm
                isoC6(1066),               -- 114 by 162 mm
                isoDesignatedLong(1067),   -- 110 by 220 mm

                jisB0(1080),               -- 1030 by 1456 mm
                jisB1(1081),               -- 728 by 1030 mm
                jisB2(1082),               -- 515 by 728 mm
                jisB3(1083),               -- 364 by 515 mm
                jisB4(1084),               -- 257 by 364 mm
                jisB5(1085),               -- 182 by 257 mm
                jisB6(1086),               -- 128 by 182 mm
                jisB7(1087),               --  91 by 128 mm
                jisB8(1088),               --  64 by  91 mm
                jisB9(1089),               --  45 by  64 mm
                jisB10(1090),              --  32 by  45 mm

                executive(1100),            -- 7.25 by 10.5  inches
                folio(1101),                -- 8.5  by 13    inches
                invoice(1102),              -- 5.5  by 8.5   inches
                ledger(1103),  -- aka statement, 11 by 17    inches
                quarto(1104)                -- 8.5  by 10.83 inches
                }

ScmPrtOutputOffsetStackingType ::= TEXTUAL-CONVENTION
    STATUS      current
    DESCRIPTION "
        Offset stacking types further refining that specified by
        the object prtOutputOffsetStacking in the Printer MIB.

        - offsetOnJob means that each job is offset but copies within
          the job are not offset.
        - offsetOnJobAndCopy means that there is an offset on job and
          copy boundaries."
    REFERENCE "Printer MIB prtOutputOffsetStacking object"
    SYNTAX INTEGER {
                other(1),
                unknown(2),
                notSpecified(3),
                noOffset(4),
                offsetOnJob(5),
                offsetOnJobandCopy(6)


                }

ScmPrtOutputStaplePosition ::= TEXTUAL-CONVENTION
    STATUS      current
    DESCRIPTION "
        This Textual Convention enumerates possible staple positions.

        The staple positions enumerated are relative to the
        physical layout of the finishing device.  
        The observer is on the front side of the finisher which
        is defined as for sheets passing through the finisher.
        The 'front' side is the side from which staples are pushed.

        The physical corners of the finishing device are specified
        by designating the corner of the finisher where a portrait
        long-edge fed sheet with english/left-to-right text is stapled
        as staplePosCorner1, and then the other corners are numbered
        in a counter-clockwise direction with the observer on the
        front side of the finisher.  

        'staplePosCorner1', 'staplePosCorner2', 'staplePosCorner3', and
        'staplePosCorner4' indicate a single staple in the specified
        corner.  This object does not specify the angle of the staple,
        e.g. 90, 45 or zero degrees.

        'stapleEdge...' indicates multiple staples on the edge
        specified.  'stapleEdge12' is the edge which include Corner1
        and Corner2.

        The current set of values (which may be extended in the future)
        is given below:
              1 : staplePosCorner1                -- 2**0
              2 : staplePosCorner2                -- 2**1
              4 : staplePosCorner3                -- 2**2
              8 : staplePosCorner4                -- 2**3
             16 : stapleEdge12                    -- 2**4
             32 : stapleEdge23                    -- 2**5
             64 : stapleEdge34                    -- 2**6
            128 : stapleEdge14                    -- 2**7"
    REFERENCE "
        See: 'scmPrtOutputStaplePosDefault'
        See: 'scmPrtOutputStaplePosSupported'"
    SYNTAX  INTEGER(0..255)

ScmPrtPageSizeErrorPolicy ::= TEXTUAL-CONVENTION
    STATUS      current
    DESCRIPTION "
        Controls interpreter behavior when the requested Page Size
        is not currently available.

        * The values 'other' and 'unknown' are deprecated for
          conforming implementations.
        * 'abortJob' will cause the interpreter to abort the job
          with an appropriate error condition.


        * 'ignore' will cause the job to be printed on the default
          media as specified by scmPrtInterpInputIndexDefault OR
          scmPrtInterpPaperSizeDefault OR any available media
          deemed appropriate by the implementation.
          No adjustment will be made to the image size.
          Exact semantics of this setting are product specific.
        * 'interactWithOperator' will cause the printer to interact
          with the operator to determine what to do. For example,
          display a message at the operator console requesting the
          desired media. The semantics of this policy vary among
          different products and environments.
        * 'useNearestAndAdjust' will cause the job to be printed on
          the nearest available media (as described below). The
          interpreter will adjust the image size (by scaling and
          centering) to fit.
        * 'useNextLargerAndAdjust' will cause the job to be printed
          on the next larger available media (as described below). 
          The interpreter will adjust the image size (by scaling and 
          centering) to fit.
        * 'useNearest' will cause the job to be printed on
          the nearest available media (as described below).
          No adjustment will be made to the image size.
        * 'useNextLarger' will cause the job to be printed on
          the next larger available media (as described below). 
          No adjustment will be made to the image size.
        * 'ignoreAfterTimeout' will cause the job to be ignored
          same as ignore' above, but not till after
          scmPrtInterpErrorPolicyTimeout expires.

        In the above descriptions, nearest size is defined as the
        one closest in area to the requested size. The next larger
        size is the one that is at least as large as the requested
        size in both width and height and is smallest in area.

        To adjust the page means to scale the page image (if 
        necessary) to fit the medium, then center the image on
        the medium."
    REFERENCE "
        PostScript Language Reference Manual, second edition,
        Adobe Systems Incorporated, pp 239-249.
        See: ScmPrtMediaTypeErrorPolicy"
    SYNTAX INTEGER {
                other(1),
                unknown(2),
                notSpecified(3),
                abortJob(4),
                ignore(5),
                interactWithOperator(6),
                useNearestAndAdjust(7),
                useNextLargerAndAdjust(8),
                useNearest(9),
                useNextLarger(10),
                ignoreAfterTimeout(11)


                }

ScmPrtPCLFontSource ::= TEXTUAL-CONVENTION
    STATUS      current
    DESCRIPTION "
        "
    REFERENCE "
        See: PJL Technical Reference Manual- FONTSOURCE"
    SYNTAX INTEGER {
               other(1),
               unknown(2),
               notSpecified(3),

               internal(20),     -- PJL value 'I'

               romSimm1(41),     -- PJL value 'M1'
               romSimm2(42),     -- PJL value 'M2'
               romSimm3(43),     -- PJL value 'M3'
               romSimm4(44),     -- PJL value 'M4'
               romSimm5(45),     -- PJL value 'M5'
               romSimm6(46),     -- PJL value 'M6'
               romSimm7(47),     -- PJL value 'M7'
               romSimm8(48),     -- PJL value 'M8'
               romSimm9(49),     -- PJL value 'M9'

               cartridge1(61),   -- PJL value 'C1'
               cartridge2(62),   -- PJL value 'C2'
               cartridge3(63),   -- PJL value 'C3'
               cartridge4(64),   -- PJL value 'C4'
               cartridge5(65),   -- PJL value 'C5'
               cartridge6(66),   -- PJL value 'C6'
               cartridge7(67),   -- PJL value 'C7'
               cartridge8(68),   -- PJL value 'C8'
               cartridge9(69),   -- PJL value 'C9'

               permanentSoft(80) -- PJL value 'S'
               }

ScmPrtPlex ::= TEXTUAL-CONVENTION
    STATUS      current
    DESCRIPTION "
        This Textual Convention enumerates plex modes which may
        be supported by a printer or interpreter.  A plex mode
        specifies whether pages are to be printed one-sided or
        two-sided, as well as the content orientation between
        consecutive pages.

        For the ScmPrtPlex TC, the following definitions apply:

          'one-sided' - Print on only one side of each sheet.
          'two-sided' - Print on both sides of each sheet.

          'simplex' - The document pages are to be oriented so as to
               condition them for one-sided printing.


          'long-edge-bind'  - The document pages are to be oriented so
               as to condition them for two-sided printing, bound along
               the length (the longer edge) of the physical page.
          'short-edge-bind' - The document pages are to be oriented so
               as to condition them for two-sided printing, bound along
               the width (the shorter edge) of the physical page. 

        ScmPrtPlex's representation is bit-encoded, so that a device
        may show multiple plex modes supported.  The value zero shall
        mean notSpecified.

        The following ScmPrtPlex values and meanings are defined:
        0x001 simplex, one-sided
        0X002 simplex, two-sided

        0x010 long-edge-bind,  one-sided
        0x020 long-edge-bind,  two-sided
        0x040 short-edge-bind, one-sided
        0x080 short-edge-bind, two-sided

        The following describes the relationship of the scmPrtPlex
        modes to DPA, PostScript and PCL.

        DPA:
        In DPA, Plex specifies whether the page images of the
        output document are to be conditioned for (eventual) one-sided
        or two-sided printing, and also specifies whether the
        relative orientation between consecutive page-images is to
        be altered.

        In DPA, the Plex modes specified are named 'Simplex', 'Duplex'
        and 'Tumble'.  However, 'Duplex' would more accurately be named
        bindLongEdge, and 'Tumble' would more accurately be named
        bindShortEdge.

        As written in DPA, 'Whether the images are portrait or
        landscape, the binding edge is parallel to: the y axis for
        'duplex', and the x axis for 'tumble'.  This last observation
        is important for understanding when to use 'tumble'.  If the
        binding edge of the document is along the y-axis, the plex is
        'duplex', whether the orientation is portrait or landscape, and
        if the binding-edge is along the x-axis, the plex is 'tumble',
        whether the orientation is portrait or landscape.
        In DPA, a separate attribute, 'Sides', specifies 1-sided or
        2-sided printing.

        In DPA, the value of this attribute may also be used by the
        presentation processes of some document formats to determine
        whether or not to print certain designated pages 
        (e.g. the extra blank pages needed in two-sided printing to
        cause sections to begin on the righthand side of a book, or
        recto page).


        The following enumerations are relevant to DPA:
        simplexOneSided,       simplexTwoSided,
        bindLongEdgeOneSided,  bindLongEdgeTwoSided,
        bindShortEdgeOneSided, bindShortEdgeTwoSided.

        PostScript:
        In PostScript, the keys 'duplex' and 'tumble' are booleans
        which specify relative orientation between consecutive pages,
        and to the number of sides printed.   

        If 'Duplex' is False, pages are printed 1-sided, i.e. 'simplex'.
        If 'Duplex' is True,  pages are printed 2-sided.

        (For most PostScript interpreters, only when 'Duplex' is set to
        True) 'Tumble' specifies how the page images on opposite
        sides of a sheet are oriented with respect to each other.  

        If 'Tumble' is False, the default user spaces of the two pages
        are oriented such that the highest value of y in the two spaces
        lie along the same edge of the media.  Informally, a Tumble
        value of False produces output suitable for binding on the left
        or right.  When the default user space is set to a portrait
        'pagesize', setting Tumble to false is the same as using the
        ScmPrtPlex attribute longEdgeBind.  When the default user space
        is set to a landscape 'pagesize', setting Tumble to false is the
        same as using the ScmPrtPlex attribute shortEdgeBind.

        If 'Tumble' is True,  the default user spaces of the two pages
        are oriented such that the highest value of y in the two spaces
        lie along opposite edges of the media. Informally, a Tumble
        value of True produces output suitable for binding on the top
        or bottom.  When the default user space is set to a landscape
        'pagesize', setting Tumble to true is the same as using the
        ScmPrtPlex attribute shortEdgeBind.  When the default user space
        is set to a landscape 'pagesize', setting Tumble to true is the
        same as using the ScmPrtPlex attribute longEdgeBind.

        The following ScmPrtPlex enumerations are
        relevant to PostScript:
            bindLongEdgeOneSided,  bindLongEdgeTwoSided,
            bindShortEdgeOneSided, bindShortEdgeTwoSided.
        Typically (ie, for a Portrait default user space):
        OneSided      maps to the duplex boolean set to false
        TwoSided      maps to the duplex boolean set to true
        bindEdgeLong  maps to the tumble boolean set to false
        bindEdgeShort maps to the tumble boolean set to true

        PCL:
        In PCL, the attributes simplex, duplex long-edge-binding, and
        duplex short-edge-binding, along with content orientation,
        landscape or portrait, detail the number of sides to be printed,


        content orientation, and relative orientation between
        consecutive pages.  The PCL model matches that of DPA.

        The following ScmPrtPlex enumerations are relevant to PCL:
        simplexOneSided, bindLongEdgeTwoSided, bindShortEdgeTwoSided."

    REFERENCE "
        See: ISO/IEC 10175-1:1996(E)
             Section 9.3.2.16.2: Plex
             Section 9.3.2.19:   Sides
        See: PostScript Language Reference Manual (2nd Edition)
             - PageSize, Duplex, Tumble
        See: PCL 5 Printer Language Technical Reference Manual
             Simplex/Duplex Print Command"
    SYNTAX INTEGER (0..255)

ScmPrtPrintQuality ::= TEXTUAL-CONVENTION
    STATUS      current
    DESCRIPTION "
        These attributes specify the output quality of the printed
        document.  Some printers have programmatically controlled output
        quality.  This attribute allows the user to specify the level of
        output quality desired from printers.

        The following standard values are defined:
        - 'draft'  means lowest quality available on the printer.
          Uses include increasing the printer's speed and saving
          toner.
        - 'normal' means normal or intermediate quality on the printer. 
        - 'high'   means highest quality available on the printer."
    REFERENCE "
        ISO/IEC 10175-1:1996(E)
        Section 9.3.2.17:  Print-quality"
    SYNTAX INTEGER {
                other(1),
                unknown(2),
                notSpecified(3),
                draft(4),
                normal(5),
                high(6)
                }
ScmPrtPrintScreen ::= TEXTUAL-CONVENTION
    STATUS      current
    DESCRIPTION "
        This Textual-Convention enumerates special modes for 80
        character screen dumps onto A4 size paper, which is usually
        77 characters wide.  This function is useful when printing the
        80 characters per line width of computer displays.

        The PrintScreen mode enables characters to be printed as shown 
        on the display when PrintScreen is executed from the host.

        When mode850 or mode852 is set, the following is done:
            - Symbol set value changed to PC-850 or PC-852.


              with the current Symbol set value being stored.
            - A4 size horizontal printable area expanded to being 80
              characters wide.

        When the special mode is returned to Off, the following is done:
            - Symbol set value returned to the stored SymbolSet Value.
            - A4 size horizontal printable area returned to being 77
              characters."
    SYNTAX INTEGER {
                other(1),
                unknown(2),
                notSpecified(3),
                off(4),
                mode850(5),
                mode852(6)
                }

ScmPrtTraySwitch ::= TEXTUAL-CONVENTION
    STATUS      current
    DESCRIPTION "
        This Textual-Convention enumerates which tray switching
        declaration mechanism is used."
    REFERENCE "
        See:  scmPrtInterpTraySwitch
        See:  scmPrtInputNextPrtInputIndex
        See:  scmPrtInputAliasTable"
    SYNTAX INTEGER {
                other(1),
                unknown(2),
                notSpecified(3),
                off(4),
                useScmPrtInputNextPrtInputIndex(5),
                useScmPrtInputAliasTable(6)
                }

--
-- Added per Chuck Adam request 6/13/03
--

ScmPrtGeneralMonoPrintOpt ::= TEXTUAL-CONVENTION
    STATUS      current
    DESCRIPTION "
        These attributes specify the printing performance /
        economy mode setting."
    REFERENCE "
        See: Phaser 7750 User Guide... for more information "
    SYNTAX INTEGER {
                other(1),
                optimizeForSpeed(3),
                optimizeForEconomy(4),
                notPresent(5)
                }

--


--          The Printer MIB Extensions TC Dumma Group (DO NOT USE)
--
--          DO NOT USE - Present to suppress compiler warnings ONLY!
--
--          Note:  The following objects have 'odd' use of case in their
--          names (ie, 'sCm...'), in order to make obvious their related
--          textual conventions

sCmPrintTCDummy     OBJECT IDENTIFIER ::= { scmPrintTC 999 }

sCmPrtTCAuxSheetContent OBJECT-TYPE
    SYNTAX      ScmPrtAuxSheetContent
    MAX-ACCESS  not-accessible
    STATUS      current
    DESCRIPTION "Dummy - DO NOT USE"
    ::= { sCmPrintTCDummy 1 }

sCmPrtTCScmPrtAuxSheetType OBJECT-TYPE
    SYNTAX      ScmPrtAuxSheetType
    MAX-ACCESS  not-accessible
    STATUS      current
    DESCRIPTION "Dummy - DO NOT USE"
    ::= { sCmPrintTCDummy 2 }

sCmPrtTCTCChannelType OBJECT-TYPE
    SYNTAX      ScmPrtChannelType
    MAX-ACCESS  not-accessible
    STATUS      current
    DESCRIPTION "Dummy - DO NOT USE"
    ::= { sCmPrintTCDummy 3 }

sCmPrtTCGroupSupport OBJECT-TYPE
    SYNTAX      ScmPrtGroupSupport
    MAX-ACCESS  not-accessible
    STATUS      current
    DESCRIPTION "Dummy - DO NOT USE"
    ::= { sCmPrintTCDummy 4 }

sCmPrtTCIETFPrintMIBGroupSupport OBJECT-TYPE
    SYNTAX      ScmPrtIETFPrintMIBGroupSupport
    MAX-ACCESS  not-accessible
    STATUS      current
    DESCRIPTION "Dummy - DO NOT USE"
    ::= { sCmPrintTCDummy 5 }

sCmPrtTCInterpreterLangFamily OBJECT-TYPE
    SYNTAX      ScmPrtInterpreterLangFamily
    MAX-ACCESS  not-accessible
    STATUS      current
    DESCRIPTION "Dummy - DO NOT USE"
    ::= { sCmPrintTCDummy 6 }

sCmPrtTCMediaTypeErrorPolicy OBJECT-TYPE
    SYNTAX      ScmPrtMediaTypeErrorPolicy


    MAX-ACCESS  not-accessible
    STATUS      current
    DESCRIPTION "Dummy - DO NOT USE"
    ::= { sCmPrintTCDummy 7 }

sCmPrtTCMediumClassType OBJECT-TYPE
    SYNTAX      ScmPrtMediumClassType
    MAX-ACCESS  not-accessible
    STATUS      current
    DESCRIPTION "Dummy - DO NOT USE"
    ::= { sCmPrintTCDummy 8 }

sCmPrtTCMediumSize OBJECT-TYPE
    SYNTAX      ScmPrtMediumSize
    MAX-ACCESS  not-accessible
    STATUS      current
    DESCRIPTION "Dummy - DO NOT USE"
    ::= { sCmPrintTCDummy 9 }

sCmPrtTCOutputOffsetStackingType OBJECT-TYPE
    SYNTAX      ScmPrtOutputOffsetStackingType
    MAX-ACCESS  not-accessible
    STATUS      current
    DESCRIPTION "Dummy - DO NOT USE"
    ::= { sCmPrintTCDummy 10 }

sCmPrtOutputStaplePosition OBJECT-TYPE
    SYNTAX      ScmPrtOutputStaplePosition
    MAX-ACCESS  not-accessible
    STATUS      current
    DESCRIPTION "Dummy - DO NOT USE"
    ::= { sCmPrintTCDummy 11 }

sCmPrtTCPageSizeErrorPolicy OBJECT-TYPE
    SYNTAX      ScmPrtPageSizeErrorPolicy
    MAX-ACCESS  not-accessible
    STATUS      current
    DESCRIPTION "Dummy - DO NOT USE"
    ::= { sCmPrintTCDummy 12 }

sCmPrtTCPCLFontSource OBJECT-TYPE
    SYNTAX      ScmPrtPCLFontSource
    MAX-ACCESS  not-accessible
    STATUS      current
    DESCRIPTION "Dummy - DO NOT USE"
    ::= { sCmPrintTCDummy 13 }

sCmPrtTCPlex OBJECT-TYPE
    SYNTAX      ScmPrtPlex
    MAX-ACCESS  not-accessible
    STATUS      current
    DESCRIPTION "Dummy - DO NOT USE"
    ::= { sCmPrintTCDummy 14 }


sCmPrtTCPrintQuality OBJECT-TYPE
    SYNTAX      ScmPrtPrintQuality
    MAX-ACCESS  not-accessible
    STATUS      current
    DESCRIPTION "Dummy - DO NOT USE"
    ::= { sCmPrintTCDummy 15 }

sCmPrtTCPrintScreen OBJECT-TYPE
    SYNTAX      ScmPrtPrintScreen
    MAX-ACCESS  not-accessible
    STATUS      current
    DESCRIPTION "Dummy - DO NOT USE"
    ::= { sCmPrintTCDummy 16 }

sCmPrtTCTraySwitch OBJECT-TYPE
    SYNTAX      ScmPrtTraySwitch
    MAX-ACCESS  not-accessible
    STATUS      current
    DESCRIPTION "Dummy - DO NOT USE"
    ::= { sCmPrintTCDummy 17 }

sCmPrtTCGeneralMonoPrintOpt OBJECT-TYPE
    SYNTAX      ScmPrtGeneralMonoPrintOpt
    MAX-ACCESS  not-accessible
    STATUS      current
    DESCRIPTION "Dummy - DO NOT USE"
    ::= { sCmPrintTCDummy 18 }

END
