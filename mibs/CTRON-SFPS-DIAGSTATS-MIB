CTRON-SFPS-DIAGSTATS-MIB DEFINITIONS ::= BEGIN

--  sfps-diagstats-mib.txt
--  Revision: 0.0.03
--              
--  Cabletron Systems, Inc.
--  35 Industrial Way, P.O. Box 5005
--  Rochester, NH 03867-0505
--  (603) 332-9400
--  support@ctron.com
--
--  This module provides authoritative definitions for Cabletron's
--  enterprise specific Fast Packet Switching Services API MIB.
--
--  This module will be extended, as required.
--
--
--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.
--  Copyright October 93 Cabletron Systems
--

IMPORTS
      OBJECT-TYPE
                FROM RFC-1212
--      DisplayString
--                FROM RFC1213-MIB
--  tcl    enterprises
--         IpAddress,
--       Counter, Gauge
         TimeTicks
                FROM RFC1155-SMI
 
--  These Objects are defined in the file sfps-inc.mib.txt.0.0.2
        sfpsFloodCounters, sfpsFloodCountersReset, sfpsIsolatedSwitch, sfpsResetNVRAM
                FROM CTRON-SFPS-INCLUDE-MIB;

--  Textual Conventions

--SfpsSwitchInstance ::= OCTET STRING (SIZE(4))
--  this will map to chassis.module index value
 
--SfpsSwitchPort ::= INTEGER
--  this will map to chassis.module.portgroup.portsubgroup.port index value
 
SfpsAddress ::= OCTET STRING (SIZE (6))
--  this will map to a MAC address
  
--HexInteger ::= INTEGER
--  display this integer in hex format



--  SFPS Diagnostic Statistics Group

sfpsFloodCountersTable     OBJECT-TYPE
        SYNTAX  SEQUENCE OF SfpsFloodCountersEntry
        ACCESS  not-accessible
        STATUS  mandatory
        DESCRIPTION
                "A table of flood count information."
        ::= { sfpsFloodCounters 1 }

sfpsFloodCountersEntry    OBJECT-TYPE
        SYNTAX  SfpsFloodCountersEntry
        ACCESS  not-accessible
        STATUS  mandatory
        DESCRIPTION
                "Each entry is instanced by the Source MAC address."
        INDEX   { sfpsFloodCountersSource }
                ::= { sfpsFloodCountersTable 1 }

SfpsFloodCountersEntry ::=
        SEQUENCE {
                sfpsFloodCountersSource               SfpsAddress,  
                sfpsFloodCountersNumFloods            INTEGER,  
                sfpsFloodCountersLastSeqNum           INTEGER,  
                sfpsFloodCountersNumDrops             INTEGER,  
                sfpsFloodCountersLastDropTime         TimeTicks,  
                sfpsFloodCountersMaxDrops             INTEGER,  
                sfpsFloodCountersMaxDropsTime         TimeTicks
        }  

sfpsFloodCountersSource   OBJECT-TYPE
        SYNTAX  SfpsAddress
        ACCESS  read-only
        STATUS  mandatory
        DESCRIPTION
                "Source Mac Address."
        ::= { sfpsFloodCountersEntry 1 }

sfpsFloodCountersNumFloods   OBJECT-TYPE
        SYNTAX  INTEGER
        ACCESS  read-only
        STATUS  mandatory
        DESCRIPTION
                "Number of floods caused by this Source MAC."
        ::= { sfpsFloodCountersEntry 2 }


sfpsFloodCountersLastSeqNum   OBJECT-TYPE
        SYNTAX  INTEGER
        ACCESS  read-only
        STATUS  mandatory
        DESCRIPTION
                "Last Sequence number."
        ::= { sfpsFloodCountersEntry 3 }


sfpsFloodCountersNumDrops   OBJECT-TYPE
        SYNTAX  INTEGER
        ACCESS  read-only
        STATUS  mandatory
        DESCRIPTION
                "Number of drops for that Source MAC.."
        ::= { sfpsFloodCountersEntry 4 }


sfpsFloodCountersLastDropTime   OBJECT-TYPE
        SYNTAX  TimeTicks
        ACCESS  read-only
        STATUS  mandatory
        DESCRIPTION
                "The time tick on when the last drop occurred for that 
                Source MAC.."
        ::= { sfpsFloodCountersEntry 5 }


sfpsFloodCountersMaxDrops   OBJECT-TYPE
        SYNTAX  INTEGER
        ACCESS  read-only
        STATUS  mandatory
        DESCRIPTION
                "Maximum drops for that Source MAC."
        ::= { sfpsFloodCountersEntry 6 }

sfpsFloodCountersMaxDropsTime   OBJECT-TYPE
        SYNTAX  TimeTicks
        ACCESS  read-only
        STATUS  mandatory
        DESCRIPTION
                "The time tick on when the maximum drops occurred
                for that Source MAC."
        ::= { sfpsFloodCountersEntry 7 }


-- Flood Counters Reset

sfpsFloodCountersResetReset             OBJECT-TYPE
    SYNTAX      INTEGER
    ACCESS      read-write
    STATUS      mandatory
    DESCRIPTION
        "Reset the Flood counters (1 to reset)."
    ::= { sfpsFloodCountersReset 1 }

sfpsFloodCountersTotalDropped           OBJECT-TYPE
    SYNTAX      INTEGER
    ACCESS      read-only
    STATUS      mandatory
    DESCRIPTION
        "Total number of drops based on sequence numbers for the switch."
    ::= { sfpsFloodCountersReset 2 }

sfpsFloodCountersTotalRunts             OBJECT-TYPE
    SYNTAX      INTEGER
    ACCESS      read-only
    STATUS      mandatory
    DESCRIPTION
        "Total number of runt packets originated from the Flooder."
    ::= { sfpsFloodCountersReset 3 }

sfpsFloodCountersTotalSelfOrig          OBJECT-TYPE
    SYNTAX      INTEGER
    ACCESS      read-only
    STATUS      mandatory
    DESCRIPTION
        "Total number of floods that the switch sees that were generated
        from itself."
    ::= { sfpsFloodCountersReset 4 }

sfpsFloodCountersNonNetPort             OBJECT-TYPE
    SYNTAX      INTEGER
    ACCESS      read-only
    STATUS      mandatory
    DESCRIPTION
        "Total number of floods received on non-Network ports."
    ::= { sfpsFloodCountersReset 5 }


-- Isoloated Switch

sfpsIsolatedSwitchIsolatedSwitch                OBJECT-TYPE
    SYNTAX      INTEGER {
--              no(0),
                yes(1)
        }
    ACCESS      read-only
    STATUS      mandatory
    DESCRIPTION
        "Designates whether this switch has determined that it is an
        Isolated switch."
    ::= { sfpsIsolatedSwitch 1 }

sfpsIsolatedSwitchResetCounters         OBJECT-TYPE
    SYNTAX      INTEGER
    ACCESS      read-write
    STATUS      mandatory
    DESCRIPTION
        "Clears the INBDropped and INBNotSent counters."
    ::= { sfpsIsolatedSwitch 2 }

sfpsIsolatedSwitchINBDropped            OBJECT-TYPE
    SYNTAX      INTEGER
    ACCESS      read-only
    STATUS      mandatory
    DESCRIPTION
        "During the time that switch has not converged, this number should
        increment. It should not increment once things are stable."
    ::= { sfpsIsolatedSwitch 3 }

sfpsIsolatedSwitchINBNotSent            OBJECT-TYPE
    SYNTAX      INTEGER
    ACCESS      read-only
    STATUS      mandatory
    DESCRIPTION
        "Number of times the packet not sent out the INB. Used for debugging    
        purposes."
    ::= { sfpsIsolatedSwitch 4 }

-- Reset NVRAM

sfpsResetNVRAMPercentNvramAvailable      OBJECT-TYPE
    SYNTAX      INTEGER
    ACCESS      read-only
    STATUS      mandatory
    DESCRIPTION
        "Percent of Nvram available."
    ::= { sfpsResetNVRAM 1 }

sfpsResetNVRAMTotalNVRAM      OBJECT-TYPE
    SYNTAX      INTEGER
    ACCESS      read-only
    STATUS      mandatory
    DESCRIPTION
        "Total amount of Nvram."
    ::= { sfpsResetNVRAM 2 }

sfpsResetNVRAMOnetoResetNvramAndRestoreIP      OBJECT-TYPE
    SYNTAX      INTEGER
    ACCESS      read-write
    STATUS      mandatory
    DESCRIPTION
        ""
    ::= { sfpsResetNVRAM 3 }

sfpsResetNVRAMDelayTimer      OBJECT-TYPE
    SYNTAX      INTEGER
    ACCESS      read-write
    STATUS      mandatory
    DESCRIPTION
        ""
    ::= { sfpsResetNVRAM 4 }

END
