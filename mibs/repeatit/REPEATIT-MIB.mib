-- Radio Bridge MIB


REPEATIT-MIB DEFINITIONS ::= BEGIN

IMPORTS
	enterprises
		FROM RFC1155-SMI
	TruthValue, DisplayString, RowStatus, PhysAddress
		FROM SNMPv2-TC
	MODULE-IDENTITY, OBJECT-TYPE, Integer32, Gauge32, Counter64, IpAddress, TimeTicks
		FROM SNMPv2-SMI
	ifIndex
        FROM IF-MIB

	OBJECT-GROUP
		FROM SNMPv2-CONF;

radioBridgeRegMib MODULE-IDENTITY
    LAST-UPDATED 	"201406241200Z"
    ORGANIZATION 	"Repeatit AB"
    CONTACT-INFO 	"info@repeatit.se"
    DESCRIPTION  	"Provides SNMP to get parameters of Trinity units"
    REVISION 	"201406241200Z"
    DESCRIPTION  	"Initial version 1.0"
::= { enterprises 16068 1 1}

-- Repeatit Root
radioBridgeRoot  	OBJECT IDENTIFIER ::= { enterprises 16068 }
radioBridgeReg	OBJECT IDENTIFIER ::= { radioBridgeRoot 1 }
radioBridgeSystem  	OBJECT IDENTIFIER ::= { radioBridgeRoot 2 }
radioBridgeTrinity	OBJECT IDENTIFIER ::= { radioBridgeRoot 3 }
	--radioBridgeIp	OBJECT IDENTIFIER ::= { radioBridgeTrinity 1 }
	radioBridgeRf       OBJECT IDENTIFIER ::= { radioBridgeTrinity 2 }
	radioBridgeEthernet OBJECT IDENTIFIER ::= { radioBridgeTrinity 3 }
	--radioBridgeSync	OBJECT IDENTIFIER ::= { radioBridgeTrinity 5 }
--radioBridgeLegacy	OBJECT IDENTIFIER ::= { radioBridgeRoot 4 }

-- ===========================================================
-- Radio Bridge system extension
-- ===========================================================

rbSystemUpAbsoluteTime OBJECT-TYPE
       SYNTAX      Counter64
       MAX-ACCESS  read-only
       STATUS      current
       DESCRIPTION
               "since the Epoch (00:00:00 UTC, January 1, 1970), measured in seconds."
       ::= { radioBridgeSystem 1 }

rbSystemLocation OBJECT-TYPE
	SYNTAX      DisplayString
	MAX-ACCESS  read-only
	STATUS      current
	DESCRIPTION
	"String describing the loaction of the unit, set in webinterface or other mgmt system"
	::= {  radioBridgeSystem 2 }

rbSystemName OBJECT-TYPE
	SYNTAX      DisplayString
	MAX-ACCESS  read-only
	STATUS      current
	DESCRIPTION
	"String with name of unit given in web interface or other mgmt-system"
	::= {  radioBridgeSystem 3 }

rbSystemType OBJECT-TYPE
	SYNTAX      DisplayString
	MAX-ACCESS  read-only
	STATUS      current
	DESCRIPTION
	"String describing the type of unit, example Trinity323TDD"
	::= {  radioBridgeSystem 4 }

rbSystemFWVersion OBJECT-TYPE
	SYNTAX      DisplayString
	MAX-ACCESS  read-only
	STATUS      current
	DESCRIPTION
	"Current Firmware number"
	::= {  radioBridgeSystem 5 }

rbSystemSerialNumber OBJECT-TYPE
	SYNTAX      DisplayString
	MAX-ACCESS  read-only
	STATUS      current
	DESCRIPTION
	"Unit Serial number"
	::= {  radioBridgeSystem 6 }

-- ===========================================================
-- Radio Bridge RF table
-- ===========================================================

rbRadioNumber OBJECT-TYPE
	SYNTAX      Integer32 (0..10)
	MAX-ACCESS  read-only
	STATUS      current
	DESCRIPTION
	"Number of Radio interfaces in table"
	::= {  radioBridgeRf 1 }
	
rbRadioTable OBJECT-TYPE
	SYNTAX      SEQUENCE OF RbRadioEntry
	MAX-ACCESS  not-accessible
	STATUS      current
	DESCRIPTION
	"Table with parameters for each radio"
	::= { radioBridgeRf  2 }


rbRadioEntry OBJECT-TYPE
	SYNTAX      RbRadioEntry
	MAX-ACCESS  not-accessible
	STATUS      current
	DESCRIPTION
	""
	INDEX { rfIndex }
	::= { rbRadioTable 1 }

RbRadioEntry ::= SEQUENCE {		
	rfIndex			INTEGER,
	rfPhysAddress		PhysAddress,
	rfRadioType		DisplayString,
	rfLinkId			DisplayString,
	rfChannelWidth		INTEGER,
	rfOperationalFrequency	Counter64,
	rfRate			INTEGER,
	rfRateHighest		INTEGER,
	rfRateLowest		INTEGER,
	rfOperationalState		INTEGER,
	rfSignCh1Ctrl		Integer32,
	rfSignCh2Ctrl		Integer32,
	rfSignCh1Ext		Integer32,
	rfSignCh2Ext		Integer32,
	rfTxPower			Integer32,
	rfPhyErr			Counter64,
	rfCRCErr			Counter64,
	rfPhyRadar		Counter64,
	rfNumOfTotTS		Integer32,
	rfNumOfAlocTS		Integer32,
	rfNumOfFreeTS		Integer32,
	rfLinkNumber		Integer32
}


rfIndex OBJECT-TYPE
	SYNTAX      Integer32 (0..1)
	MAX-ACCESS  not-accessible
	STATUS      current
	DESCRIPTION
	"Index in this table"
	::= {  rbRadioEntry 1 }

rfPhysAddress OBJECT-TYPE
	SYNTAX      PhysAddress (SIZE (6))
	MAX-ACCESS  read-only
	STATUS      current
	DESCRIPTION
	"MAC address of the radio"
	::= {  rbRadioEntry 2 }

rfRadioType OBJECT-TYPE
	SYNTAX      DisplayString
	MAX-ACCESS  read-only
	STATUS      current
	DESCRIPTION
	"String describing the type of radio"
	::= {  rbRadioEntry 3 }

rfLinkId OBJECT-TYPE
	SYNTAX      DisplayString
	MAX-ACCESS  read-only
	STATUS      current
	DESCRIPTION
	"The LinkId that this radio is either transmitting or looking for depending on the mode of the link"
	::= {  rbRadioEntry 4 }

rfChannelWidth OBJECT-TYPE
	SYNTAX      INTEGER
	{
		rfWidth40(40),
		rfWidth20(20),
		rfWidth10(10),
		rfWidth5(5)
	}
	MAX-ACCESS  read-only
	STATUS      current
	DESCRIPTION
	"Current Channel Bandwidth in MHz, 5, 10 ,20 or 40MHz "
	::= {  rbRadioEntry 5 }

rfOperationalFrequency OBJECT-TYPE
	SYNTAX      Counter64
	MAX-ACCESS  read-only
	STATUS      current
	DESCRIPTION
	"The current channel frequency in Hz"
	::= {  rbRadioEntry 6 }

rfRate OBJECT-TYPE
	SYNTAX      INTEGER
	MAX-ACCESS  read-only
	STATUS      current
	DESCRIPTION
	"Displays the current bitrate used by the radio, in Mbit/s"
	::= {  rbRadioEntry 7 }

rfRateHighest OBJECT-TYPE
	SYNTAX      INTEGER
	MAX-ACCESS  read-only
	STATUS      current
	DESCRIPTION
	"Displays the max bitrate allowed to be used by the radio, in Mbit/s (Dispalys only whole Mbit/s, depending on other settings actual rate could be with decimals)"
	::= {  rbRadioEntry 8 }

rfRateLowest OBJECT-TYPE
	SYNTAX      INTEGER
	MAX-ACCESS  read-only
	STATUS      current
	DESCRIPTION
	"Displays the min bitrate allowed to be used by the radio, in Mbit/s (Dispalys only whole Mbit/s, depending on other settings actual rate could be with decimals)"
	::= {  rbRadioEntry 9 }

rfOperationalState OBJECT-TYPE
	SYNTAX      INTEGER
	{
		unknown(0),
		master(1),
		client(2)
	}	
	MAX-ACCESS  read-only
	STATUS      current
	DESCRIPTION
	"The current operational mode this radio is working in master or slave"
	::= {  rbRadioEntry 10 }

rfSignCh1Ctrl OBJECT-TYPE
	SYNTAX      Integer32 (-128..127)
	MAX-ACCESS  read-only
	STATUS      current
	DESCRIPTION
	"Signal level "
	::= {  rbRadioEntry 11 }

rfSignCh2Ctrl OBJECT-TYPE
	SYNTAX      Integer32 (-128..127)
	MAX-ACCESS  read-only
	STATUS      current
	DESCRIPTION
	""
	::= {  rbRadioEntry 12 }

rfSignCh1Ext OBJECT-TYPE
	SYNTAX      Integer32 (-128..127)
	MAX-ACCESS  read-only
	STATUS      current
	DESCRIPTION
	""
	::= {  rbRadioEntry 13 }

rfSignCh2Ext OBJECT-TYPE
	SYNTAX      Integer32 (-128..127)
	MAX-ACCESS  read-only
	STATUS      current
	DESCRIPTION
	""
	::= {  rbRadioEntry 14 }

rfTxPower OBJECT-TYPE
	SYNTAX      Integer32 (0 ..30)
	MAX-ACCESS  read-only
	STATUS      current
	DESCRIPTION
	"Current txpower used by the Radio"
	::= {  rbRadioEntry 15 }

rfPhyErr OBJECT-TYPE
	SYNTAX      Counter64
	MAX-ACCESS  read-only
	STATUS      current
	DESCRIPTION
	"Total number of phy-errors received by this radio"
	::= {  rbRadioEntry 16 }

rfCRCErr OBJECT-TYPE
	SYNTAX      Counter64
	MAX-ACCESS  read-only
	STATUS      current
	DESCRIPTION
	"Total number of CRC errors recieved by this radio"
	::= {  rbRadioEntry 17 }

rfPhyRadar OBJECT-TYPE
	SYNTAX      Counter64
	MAX-ACCESS  read-only
	STATUS      current
	DESCRIPTION
	"Total number of phy-radar errors receivedby this radio"
	::= {  rbRadioEntry 18 }

rfNumOfTotTS OBJECT-TYPE
	SYNTAX      Integer32 (0 ..64)
	MAX-ACCESS  read-only
	STATUS      current
	DESCRIPTION
	"Total number of timeslots this radio is configured with"
	::= {  rbRadioEntry 19 }

rfNumOfAlocTS OBJECT-TYPE
	SYNTAX      Integer32 (0 ..64)
	MAX-ACCESS  read-only
	STATUS      current
	DESCRIPTION
	"Number of timeslots alloctated on this radio"
	::= {  rbRadioEntry 20 }

rfNumOfFreeTS OBJECT-TYPE
	SYNTAX      Integer32 (0 ..64)
	MAX-ACCESS  read-only
	STATUS      current
	DESCRIPTION
	"Number of unallocated timeslots on this radio"
	::= { rbRadioEntry 21 }

rfLinkNumber OBJECT-TYPE
	SYNTAX      Integer32
	MAX-ACCESS  read-only
	STATUS      current
	DESCRIPTION
	"Number of Links in table"
	::= {  rbRadioEntry 22 }

-- ===========================================================
-- Radio Bridge Link table within radioBridgeRf
-- ===========================================================


	
rbLinkTable OBJECT-TYPE
	SYNTAX      SEQUENCE OF RbLinkEntry
	MAX-ACCESS  not-accessible
	STATUS      current
	DESCRIPTION
	""
	::= { radioBridgeRf  3 }


rbLinkEntry OBJECT-TYPE
	SYNTAX      RbLinkEntry
	MAX-ACCESS  not-accessible
	STATUS      current
	DESCRIPTION
	""
	INDEX { linkIndex }
	::= { rbLinkTable 1 }

RbLinkEntry ::= SEQUENCE {
	linkIndex			Integer32,
	linkRfIndex		Integer32,
	linkPhysAddress		PhysAddress,
	linkUptime		Counter64,
	linkOperationalState	INTEGER,
	linkInOctets		Counter64,
	linkOutOctets		Counter64,
	linkInPackets		Counter64,
	linkOutPackets		Counter64,
	linkRetries		Counter64,
	linkXRetries		Counter64,
	linkTxRate		INTEGER,
	linkRxRate		INTEGER,
	linkSignCh1Ctrl		Integer32,
	linkSignCh2Ctrl		Integer32,
	linkSignCh1Ext		Integer32,
	linkSignCh2Ext		Integer32,
	linkNumOfTS		Integer32
}
linkIndex OBJECT-TYPE
	SYNTAX      Integer32 (0 .. 32)
	MAX-ACCESS  not-accessible
	STATUS      current
	DESCRIPTION
	"Index in this table"
	::= {  rbLinkEntry 1 }

linkRfIndex OBJECT-TYPE
	SYNTAX      Integer32 (0 .. 32)
	MAX-ACCESS  read-only
	STATUS      current
	DESCRIPTION
	"Unicly indetifies which radioBridgeRf instance this link is part of."
	::= {  rbLinkEntry 2 }

linkPhysAddress OBJECT-TYPE
	SYNTAX      PhysAddress(SIZE (6))
	MAX-ACCESS  read-only
	STATUS      current
	DESCRIPTION
	"MAC address of the Remote unit using this Link"
	::= {  rbLinkEntry 3 }

linkUptime OBJECT-TYPE
	SYNTAX      Counter64
	MAX-ACCESS  read-only
	STATUS      current
	DESCRIPTION
	"Uptime of this Link in seconds"
	::= {  rbLinkEntry 4 }

linkOperationalState OBJECT-TYPE
	SYNTAX      INTEGER
	{
		notAssigned(0),
		scheduleddeassign(1),
		radarblock(2),
		assigned(3),
		syncstate1(4),
		syncstate2(5),
		syncstate3(6),
		connected(7)
	}
	MAX-ACCESS  read-only
	STATUS      current
	DESCRIPTION
	"Displays the current state of the radio."
	::= {  rbLinkEntry 5 }

linkInOctets OBJECT-TYPE
	SYNTAX      Counter64
	MAX-ACCESS  read-only
	STATUS      current
	DESCRIPTION
	"Total number of bytes received on this link"
	::= {  rbLinkEntry 6 }

linkOutOctets OBJECT-TYPE
	SYNTAX      Counter64
	MAX-ACCESS  read-only
	STATUS      current
	DESCRIPTION
	"Total number of bytes sent on this link"
	::= {  rbLinkEntry 7 }

linkInPackets OBJECT-TYPE
	SYNTAX      Counter64
	MAX-ACCESS  read-only
	STATUS      current
	DESCRIPTION
	"Total number of packets received on this link"
	::= {  rbLinkEntry 8 }

linkOutPackets OBJECT-TYPE
	SYNTAX      Counter64
	MAX-ACCESS  read-only
	STATUS      current
	DESCRIPTION
	"Total number of packets sent on this link"
	::= {  rbLinkEntry 9 }

linkRetries OBJECT-TYPE
	SYNTAX      Counter64
	MAX-ACCESS  read-only
	STATUS      current
	DESCRIPTION
	"Total number of retried packets on this link"
	::= {  rbLinkEntry 10 }

linkXRetries OBJECT-TYPE
	SYNTAX      Counter64
	MAX-ACCESS  read-only
	STATUS      current
	DESCRIPTION
	"Total number of droped frames on this link"
	::= {  rbLinkEntry 11 }

linkTxRate OBJECT-TYPE
	SYNTAX      INTEGER
	MAX-ACCESS  read-only
	STATUS      current
	DESCRIPTION
	"Displays the current bitrate used by the radio, in Mbit/s (Dispalys only whole Mbit/s, depending on other settings actual rate could be with decimals)"
	::= {  rbLinkEntry 12 }

linkRxRate OBJECT-TYPE
	SYNTAX      INTEGER
	MAX-ACCESS  read-only
	STATUS      current
	DESCRIPTION
	"Displays the current bitrate the packets are recived with on this link, in Mbit/s (Dispalys only whole Mbit/s, depending on other settings actual rate could be with decimals)"
	::= {  rbLinkEntry 13 }

linkSignCh1Ctrl OBJECT-TYPE
	SYNTAX      Integer32 (-128..127)
	MAX-ACCESS  read-only
	STATUS      current
	DESCRIPTION
	"Displays the current receive signal level for MIMO chain 1 on the control channel in dBm"
	::= {  rbLinkEntry 14 }

linkSignCh2Ctrl OBJECT-TYPE
	SYNTAX      Integer32 (-128..127)
	MAX-ACCESS  read-only
	STATUS      current
	DESCRIPTION
	"Displays the current receive signal level for MIMO chain 2 on the control channel in dBm"
	::= {  rbLinkEntry 15 }

linkSignCh1Ext OBJECT-TYPE
	SYNTAX      Integer32 (-128..127)
	MAX-ACCESS  read-only
	STATUS      current
	DESCRIPTION
	"Displays the current receive signal level for MIMO chain 1 on the extension channel in dBm"
	::= {  rbLinkEntry 16 }

linkSignCh2Ext OBJECT-TYPE
	SYNTAX      Integer32 (-128..127)
	MAX-ACCESS  read-only
	STATUS      current
	DESCRIPTION
	"Displays the current receive signal level for MIMO chain 2 on the extension channel in dBm"
	::= {  rbLinkEntry 17 }

linkNumOfTS OBJECT-TYPE
	SYNTAX      Integer32 (0 ..64)
	MAX-ACCESS  read-only
	STATUS      current
	DESCRIPTION
	"Displays the number of Timeslots this radio is configured with"
	::= {  rbLinkEntry 18 }

-- ===========================================================
-- Radio Bridge ethernet table
-- ===========================================================
rbEthernetNumber OBJECT-TYPE
	SYNTAX      Integer32 (0..10)
	MAX-ACCESS  read-only
	STATUS      current
	DESCRIPTION
	"Number of Ethernet interfaces in table"
	::= {  radioBridgeEthernet 1 }
	
rbEthernetTable OBJECT-TYPE
	SYNTAX      SEQUENCE OF RbEthernetEntry
	MAX-ACCESS  not-accessible
	STATUS      current
	DESCRIPTION
	""
	::= { radioBridgeEthernet  2 }


rbEthernetEntry OBJECT-TYPE
	SYNTAX      RbEthernetEntry
	MAX-ACCESS  not-accessible
	STATUS      current
	DESCRIPTION
	""
	INDEX { ethernetIndex }
	::= { rbEthernetTable 1 }

RbEthernetEntry ::= SEQUENCE {
	ethernetIndex		INTEGER,
	ethernetName		DisplayString,
	ethernetPhysAddress		PhysAddress,
	ethernetSpeed		INTEGER,
	ethernetMode		INTEGER,
	ethernetOperationalState	TruthValue,
	ethernetInOctets		Counter64,
	ethernetOutOctets		Counter64,
	ethernetInPackets		Counter64,
	ethernetOutPackets		Counter64
}


ethernetIndex OBJECT-TYPE
	SYNTAX      Integer32 (0..1)
	MAX-ACCESS  not-accessible
	STATUS      current
	DESCRIPTION
	"Index in this table"
	::= {  rbEthernetEntry 1 }

ethernetName OBJECT-TYPE
	SYNTAX      DisplayString
	MAX-ACCESS  read-only
	STATUS      current
	DESCRIPTION
	"Name of interface."
	::= {  rbEthernetEntry 2 }

ethernetPhysAddress OBJECT-TYPE
	SYNTAX      PhysAddress
	MAX-ACCESS  read-only
	STATUS      current
	DESCRIPTION
	"MAC address of this interface"
	::= {  rbEthernetEntry 3 }

ethernetSpeed OBJECT-TYPE
	SYNTAX      INTEGER
	{
		speed10(10),
		speed100(100),
		speed1000(1000)
	}
	MAX-ACCESS  read-only
	STATUS      current
	DESCRIPTION
	"Current ethernetspeed on this interface"
	::= {  rbEthernetEntry 4 }

ethernetMode OBJECT-TYPE
	SYNTAX      INTEGER
	{
		hd(0),
		fd(1)
	}
	MAX-ACCESS  read-only
	STATUS      current
	DESCRIPTION
	"Current mode of this interface halfduplex or fullduplex"
	::= {  rbEthernetEntry 5 }

ethernetOperationalState OBJECT-TYPE
	SYNTAX      TruthValue
	{
		true(1),
		false(2)
	}
	MAX-ACCESS  read-only
	STATUS      current
	DESCRIPTION
	"Specifies if this interface is up or down"
	::= {  rbEthernetEntry 6 }

ethernetInOctets OBJECT-TYPE
	SYNTAX      Counter64
	MAX-ACCESS  read-only
	STATUS      current
	DESCRIPTION
	""
	::= {  rbEthernetEntry 7 }

ethernetOutOctets OBJECT-TYPE
	SYNTAX      Counter64
	MAX-ACCESS  read-only
	STATUS      current
	DESCRIPTION
	""
	::= {  rbEthernetEntry 8 }

ethernetInPackets OBJECT-TYPE
	SYNTAX      Counter64
	MAX-ACCESS  read-only
	STATUS      current
	DESCRIPTION
	""
	::= {  rbEthernetEntry 9 }

ethernetOutPackets OBJECT-TYPE
	SYNTAX      Counter64
	MAX-ACCESS  read-only
	STATUS      current
	DESCRIPTION
	""
	::= {  rbEthernetEntry 10 }

END
