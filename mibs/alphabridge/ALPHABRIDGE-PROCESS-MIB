-- *****************************************************************
-- ALPHABRIDGE-PROCESS-MIB.my: MIB for CPU and process statistics
--
-- October 2023
--
-- Copyright (c) 2023 by ALPHABRIDGE, Inc.
-- All rights reserved.
-- *****************************************************************
--

ALPHABRIDGE-PROCESS-MIB DEFINITIONS ::= BEGIN

IMPORTS
	MODULE-IDENTITY,
	OBJECT-TYPE,
	Counter32,
	Gauge32
		FROM SNMPv2-SMI
	TimeStamp,
	DisplayString
		FROM SNMPv2-TC
	MODULE-COMPLIANCE,
	OBJECT-GROUP
		FROM SNMPv2-CONF
	abMgmt
		FROM ALPHABRIDGE-SMI
	Unsigned32 FROM SNMPv2-SMI
	EntPhysicalIndexOrZero
		FROM ALPHABRIDGE-TC;


alphabridgeProcessMIB MODULE-IDENTITY
	LAST-UPDATED "200311060000Z"
	ORGANIZATION "ALPHABRIDGE, Inc."
	CONTACT-INFO
		" Tel:   +86-21-50800666  
		 Postal: No.123,Juli RD,Zhangjiang Hitech Park,
			 Shanghai Baud Data Communication Corporation Inc,
			 Shanghai City 201203,
		 	P.R.C "
	DESCRIPTION
		"The MIB module to describe active system processes."
	REVISION        "200310160000Z"
	DESCRIPTION
		"Initial version of this MIB."		
	::= { abMgmt 109 }

-- This MIB displays memory and CPU utilization on cisco devices. CPU 
-- utilization will give a general idea of how busy the processor is. 
-- The numbers are a ratio of the current idle time over the longest 
-- idle time. Please note that this information should be used as an 
-- estimate only. 

alphabridgeProcessMIBObjects	OBJECT IDENTIFIER ::= { alphabridgeProcessMIB 1 }
abpmCPU		OBJECT IDENTIFIER ::= { alphabridgeProcessMIBObjects 1 }
abpmProcess		OBJECT IDENTIFIER ::= { alphabridgeProcessMIBObjects 2 }


--ALPHABRIDGE CPU Total Table

abpmCPUTotalTable OBJECT-TYPE
	SYNTAX		SEQUENCE OF BdpmCPUTotalEntry
	MAX-ACCESS      not-accessible
        STATUS          current
        DESCRIPTION
		"A table of overall CPU statistics. "
	::= { abpmCPU 1 }

abpmCPUTotalEntry OBJECT-TYPE
	SYNTAX		BdpmCPUTotalEntry
	MAX-ACCESS      not-accessible
        STATUS          current
        DESCRIPTION
		"Overall information about the CPU load. Entries in this
		table come and go as CPUs are added and removed from the
		system."
	INDEX	{ abpmCPUTotalIndex }
	::= { abpmCPUTotalTable 1 }

BdpmCPUTotalEntry ::=
	SEQUENCE {
		abpmCPUTotalIndex		Unsigned32,
		abpmCPUTotalPhysicalIndex	EntPhysicalIndexOrZero,
		abpmCPUTotal5sec		Gauge32,
		abpmCPUTotal1min		Gauge32,
		abpmCPUTotal5min		Gauge32
	}

abpmCPUTotalIndex OBJECT-TYPE
	SYNTAX          Unsigned32 (1.. 4294967295)
	MAX-ACCESS      not-accessible
	STATUS          current
	DESCRIPTION
		"An index that uniquely represents a CPU (or group of CPUs)
		whose CPU load information is reported by a row in this table.
		This index is assigned arbitrarily by the engine
		and is not saved over reboots."
	::= { abpmCPUTotalEntry 1 }

abpmCPUTotalPhysicalIndex OBJECT-TYPE
	SYNTAX	        EntPhysicalIndexOrZero
        MAX-ACCESS      read-only
        STATUS          current
        DESCRIPTION
		"The entPhysicalIndex of the physical entity for which
		 the CPU statistics in this entry are maintained.
		 The physical entity can be a CPU chip, a group of CPUs,
		 a CPU card etc. The exact type of this entity is described by
		 its entPhysicalVendorType value. If the CPU statistics
		 in this entry correspond to more than one physical entity
		 (or to no physical entity), or if the entPhysicalTable is
		 not supported on the SNMP agent, the value of this object
		 must be zero."
	::= { abpmCPUTotalEntry 2 }

abpmCPUTotal5sec OBJECT-TYPE
        SYNTAX          Gauge32 (1..100)
	UNITS		"percent"
        MAX-ACCESS      read-only
        STATUS          current
        DESCRIPTION
		"The overall CPU busy percentage in the last 5 second 
		period. This object obsoletes the busyPer object from 
		the OLD-CISCO-SYSTEM-MIB. This object is deprecated
		by abpmCPUTotal5secRev which has the changed range of
		value (0..100)."
	::= { abpmCPUTotalEntry 3 }

abpmCPUTotal1min OBJECT-TYPE
        SYNTAX          Gauge32  (1..100)
	UNITS		"percent"
        MAX-ACCESS      read-only
        STATUS          current
        DESCRIPTION
		"The overall CPU busy percentage in the last 1 minute
		period. This object obsoletes the avgBusy1 object from 
		the OLD-CISCO-SYSTEM-MIB. This object is deprecated
		by abpmCPUTotal1minRev which has the changed range
		of value (0..100)."
	::= { abpmCPUTotalEntry 4 }

abpmCPUTotal5min OBJECT-TYPE
        SYNTAX          Gauge32 (1..100)
	UNITS		"percent"
        MAX-ACCESS      read-only
        STATUS          current
        DESCRIPTION
		"The overall CPU busy percentage in the last 5 minute
		period. This object deprecates the avgBusy5 object from 
		the OLD-CISCO-SYSTEM-MIB. This object is deprecated
		by abpmCPUTotal5minRev which has the changed range 
		of value (0..100)."
	::= { abpmCPUTotalEntry 5 }


-- ALPHABRIDGE Processes Common Table

abpmProcessTable OBJECT-TYPE
	SYNTAX		SEQUENCE OF BdpmProcessEntry
        MAX-ACCESS      not-accessible
        STATUS          current
        DESCRIPTION
		"A table of generic information on all active 
		processes on this device."
	::= { abpmProcess 1 }

abpmProcessEntry OBJECT-TYPE
	SYNTAX    	BdpmProcessEntry
        MAX-ACCESS      not-accessible
        STATUS          current
        DESCRIPTION
		"Generic information about an active process on this 
		device. Entries in this table come and go as processes are 
		created and destroyed by the device."
	INDEX	{ abpmCPUTotalIndex, abpmProcessPID }
	::= { abpmProcessTable 1 }

BdpmProcessEntry ::=
	SEQUENCE {
		abpmProcessPID
			Unsigned32,
		abpmProcessName 
			DisplayString,
		abpmProcessPriority
			INTEGER,
		abpmProcessTimeCreated
			TimeStamp
	}

abpmProcessPID OBJECT-TYPE
	SYNTAX    	Unsigned32
        MAX-ACCESS      read-only
        STATUS          current
        DESCRIPTION
		"This object contains the process ID. abpmProcessTimeCreated
		should be checked against the last time it was polled,
		and if it has changed the PID has been reused and the
		 entire entry should be polled again. The process IDs
		are discrete."
	::= { abpmProcessEntry 1 }

abpmProcessName OBJECT-TYPE
	SYNTAX    	DisplayString(SIZE(1..32))
        MAX-ACCESS      read-only
        STATUS          current
        DESCRIPTION
		"The name associated with this process. If the name is
		longer than 32 characters, it will be truncated to the first
		31 characters, and a `*' will be appended as the last
		character to imply this is a truncated process name."
	::= { abpmProcessEntry 2 }

abpmProcessPriority OBJECT-TYPE
	SYNTAX		INTEGER {
				critical(0),
				veryhigh(55),
				high(60),
				normal(128),
				low(180),
				verylow(255)
			}
	MAX-ACCESS      read-write
        STATUS          current
        DESCRIPTION
		"The priority level at which the process is 
		running. This object is deprecated by
		abpmProcExtPriorityRev."
	::= { abpmProcessEntry 3 }

abpmProcessTimeCreated OBJECT-TYPE
	SYNTAX		TimeStamp
	MAX-ACCESS      read-only
        STATUS          current
        DESCRIPTION
		"The time when the process was created. The process ID 
		and the time when the process was created, uniquely 
		identifies a process."
	::= { abpmProcessEntry 4 }

-- notifications

alphabridgeProcessMIBNotifPrefix OBJECT IDENTIFIER ::= { alphabridgeProcessMIB 2 }
alphabridgeProcessMIBNotifs OBJECT IDENTIFIER ::=
	{ alphabridgeProcessMIBNotifPrefix 0 }

-- (no notifications are currently defined)


-- conformance information
--
--alphabridgeProcessMIBConformance OBJECT IDENTIFIER ::= { alphabridgeProcessMIB 3 }
--abpmCompliances OBJECT IDENTIFIER ::= { alphabridgeProcessMIBConformance 1 }
--abpmGroups OBJECT IDENTIFIER ::=      { alphabridgeProcessMIBConformance 2 }
--
--abProcessMIBCompliance  MODULE-COMPLIANCE
--	STATUS	deprecated
--	DESCRIPTION
--		"The compliance statement for entities which implement
--		the ALPHABRIDGE Process MIB. This is deprecated and new 
--		compliance abProcessMIBComplianceRev is added."
-- this module
--	MODULE	
--		MANDATORY-GROUPS { abpmCPUTotalGroup, abpmProcessGroup }
--
--
--	GROUP abpmProcessExtGroup
--	DESCRIPTION
--		"The abpmProcessExtGroup is optional for all entities."
--
--	OBJECT		abpmProcExtPriority
--	MIN-ACCESS	read-only
--	DESCRIPTION     "Write access is not required."
--
--	::= { abpmCompliances 1 }
--
--abProcessMIBComplianceRev  MODULE-COMPLIANCE
--	STATUS	current
--	DESCRIPTION
--		"The compliance statement for entities which implement
--		the ALPHABRIDGE Process MIB. This compliance module
--		deprecates abProcessMIBCompliance."
-- this module
--	MODULE	
--		MANDATORY-GROUPS { abpmCPUTotalGroupRev, abpmProcessGroupRev}	
--
--	GROUP abpmProcessExtGroupRev
--	DESCRIPTION
--		"The abpmProcessExtGroupRev is optional for all
--		entities. This object is defined after deprecating
--		abpmProcessExtGroup."
--	
--	::= { abpmCompliances 2 }
--
-- units of conformance
--
--abpmCPUTotalGroup OBJECT-GROUP
--	OBJECTS {
--		abpmCPUTotalPhysicalIndex,
--		abpmCPUTotal5sec,
--		abpmCPUTotal1min,
--		abpmCPUTotal5min
--	}
--	STATUS  deprecated
--	DESCRIPTION
--		"A collection of objects providing CPU load monitoring
--		information. This group is mandatory for all cisco devices.
--		This group is deprecated since the objects abpmCPUTotal5sec,
--		abpmCPUTotal1min and abpmCPUTotal5min are
--		deprecated. A new object abpmCPUTotalGroupRev is
--		added in place of it."
--	::= { abpmGroups 1 }
--
--abpmProcessGroup OBJECT-GROUP
--	OBJECTS {
--		abpmProcessPID,
--		abpmProcessName,
--		abpmProcessuSecs,
--		abpmProcessTimeCreated
--	}
--	STATUS	deprecated
--	DESCRIPTION
--		"A collection of objects providing common process 
--		monitoring information. This group is mandatory for 
--		all cisco devices. This object is deprecated
--		by abpmProcessGroupRev."
--	::= { abpmGroups 2 }
--
--abpmProcessExtGroup OBJECT-GROUP
--	OBJECTS {
--		abpmProcExtMemAllocated,
--		abpmProcExtMemFreed,
--		abpmProcExtInvoked,
--		abpmProcExtRuntime,
--		abpmProcExtUtil5Sec,
--		abpmProcExtUtil1Min,
--		abpmProcExtUtil5Min,
--		abpmProcExtPriority
--	}
--	STATUS	deprecated
--	DESCRIPTION
--		"A collection of objects providing additional and 
--		more detailed process monitoring information. This 
--		group is mandatory for all cisco devices that have 
--		the internal capability to keep this information. 
--		This group is deprecated and new group
--		abpmProcessExtGroupRev is added."
--	::= { abpmGroups 3 }
--
--abpmCPUTotalGroupRev OBJECT-GROUP
--	OBJECTS {
--		abpmCPUTotalPhysicalIndex,
--		abpmCPUTotal5secRev,
--		abpmCPUTotal1minRev,
--		abpmCPUTotal5minRev
--	}
--	STATUS  current
--	DESCRIPTION
--		"A collection of objects providing CPU load monitoring
--		information. This group is mandatory for all cisco
--		devices. This group deprecates abpmCPUTotalGroup."
--	::= { abpmGroups 4 }
--
--abpmProcessExtGroupRev OBJECT-GROUP
--	OBJECTS {
--		abpmProcExtMemAllocatedRev,
--		abpmProcExtMemFreedRev,
--		abpmProcExtInvokedRev,
--		abpmProcExtRuntimeRev,
--		abpmProcExtUtil5SecRev,
--		abpmProcExtUtil1MinRev,
--		abpmProcExtUtil5MinRev,
--		abpmProcExtPriorityRev
--	}
--	STATUS	current
--	DESCRIPTION
--		"A collection of objects providing additional and 
--		more detailed process monitoring information. This 
--		group is mandatory for all cisco devices that have 
--		the internal capability to keep this information.
--		This group is formed after deprecating abpmProcessExtGroup.
--		abpmProcExtMemAllocatedRev, abpmProcExtMemFreedRev,
--		abpmProcExtInvokedRev, abpmProcExtRuntimeRev,
--		abpmProcExtUtil5SecRev, abpmProcExtUtil1MinRev and 
--		abpmProcExtUtil5MinRev are the new objects added."
--	::= { abpmGroups 5 }
--
--abpmProcessGroupRev OBJECT-GROUP
--	OBJECTS {
--		abpmProcessPID,
--		abpmProcessName,
--		abpmProcessAverageUSecs,
--		abpmProcessTimeCreated
--	}
--	STATUS	current
--	DESCRIPTION
--		"A collection of objects providing common process 
--		monitoring information. This group is mandatory for 
--		all cisco devices. This object deprecates
--		abpmProcessGroup."
--	::= { abpmGroups 6 }

END
