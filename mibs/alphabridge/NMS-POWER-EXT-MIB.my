-- *****************************************************************
-- NMS-POWER-EXT-MIB: NMS POWER EXT MIB
--
-- JUL 2011
-- Edit by LIUQIANG
-- Copyright (c) 2011 by NMS, Inc.
-- All rights reserved.
-- *****************************************************************

NMS-POWER-EXT-MIB DEFINITIONS ::= BEGIN

IMPORTS
    MODULE-IDENTITY, OBJECT-TYPE, NOTIFICATION-TYPE,
    Integer32, Unsigned32                   FROM SNMPv2-SMI
    MODULE-COMPLIANCE, OBJECT-GROUP,
    NOTIFICATION-GROUP                      FROM SNMPv2-CONF
    DisplayString                           FROM RFC1213-MIB
    nmsMgmt                                 FROM NMS-SMI;
    


    powerExt         OBJECT IDENTIFIER ::= { nmsMgmt 251 }
               
              
-- Notifications
    power1Status OBJECT-TYPE
      SYNTAX  INTEGER {
                  down(0), 
                  up(1),
                  absent(2),
                  abnormal(3)
                  }
      ACCESS  read-only
      STATUS  mandatory
      DESCRIPTION
              "Power status: down(0), up(1) ."
      ::= { powerExt 1 }
          
    power2Status OBJECT-TYPE
      SYNTAX  INTEGER {
                  down(0), 
                  up(1),
                  absent(2),
                  abnormal(3)
                  }
      ACCESS  not-accessible
      STATUS  mandatory
      DESCRIPTION
              "Power status , down(0), up(1) ."
      ::= { powerExt 2 }

        
          

    powerExtNotifications OBJECT IDENTIFIER
                                ::= { powerExt 3 }


    powerExtNotification NOTIFICATION-TYPE
            OBJECTS {
                       power1Status,
                       power2Status
                        }
            STATUS      current
            DESCRIPTION
            "The agent generates this notification when power status changes."
            ::= { powerExtNotifications 1 }
                
    powerDeviceTable OBJECT-TYPE
        SYNTAX  SEQUENCE OF  PowerDeviceEntry
        ACCESS  not-accessible
        STATUS  mandatory
        DESCRIPTION
                "A list of  Power-Device entries."
        ::= { powerExt 4 }

           powerDeviceEntry OBJECT-TYPE
               SYNTAX  PowerDeviceEntry
               ACCESS  not-accessible
               STATUS  mandatory
               DESCRIPTION
                        "A collection of Power-Device ."
               INDEX { PowerDeviceIndex }
           ::= { powerDeviceTable 1 }

           PowerDeviceEntry ::=
               SEQUENCE {
                   powerDeviceIndex
                       INTEGER,
                   powerDeviceType
                       INTEGER,
                   powerDeviceDescr
                       DisplayString,
                   powerDeviceStatus
                       INTEGER,
                   powerShelfNum
                       INTEGER

              }
              powerDeviceIndex OBJECT-TYPE
                   SYNTAX  INTEGER
                   ACCESS  read-only
                   STATUS  mandatory
                   DESCRIPTION
                           "Index of Power-Device"
                   ::= { powerDeviceEntry 1 }


               powerDeviceType OBJECT-TYPE
                   SYNTAX  INTEGER  { 
                                    empty-shelf(0)
                                   }

                   ACCESS  read-only
                   STATUS  mandatory
                   DESCRIPTION
                           "Type of Power-Device ."
                   ::= { powerDeviceEntry 2 }



               powerDeviceDescr OBJECT-TYPE
                   SYNTAX  DisplayString
                   ACCESS  read-only
                   STATUS  mandatory
                   DESCRIPTION
                           "Text description of this Power-Device."
                   ::= { powerDeviceEntry 3 }

               powerDeviceStatus OBJECT-TYPE
                   SYNTAX  INTEGER{ 
                                    on(1),
                                    off(2)
                                   }
                   ACCESS  read-write
                   STATUS  mandatory
                   DESCRIPTION
                           "When value is ON(1), that means Power-Device is working; when value is OFF(2) means Power-Device is out of working."
                   ::= { powerDeviceEntry 4 }
                   
                powerShelfNum   OBJECT-TYPE
                   SYNTAX  INTEGER{ 
                                    a(1),
                                    b(2)
                                   }
                   ACCESS  read-write
                   STATUS  mandatory
                   DESCRIPTION
                           "Powerdevice belong to which shelf."
                   ::= { powerDeviceEntry 5 }

          
                
                
              
END
