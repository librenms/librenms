NMS-TELNET-MIB  DEFINITIONS ::= BEGIN

    IMPORTS
        MODULE-IDENTITY,
        OBJECT-TYPE,BITS, Counter64
            FROM SNMPv2-SMI
        
        DisplayString,ifIndex,ifDescr,PhysAddress
            FROM RFC1213-MIB
        nms
            FROM NMS-SMI 
        PhysAddress, RowStatus, DateAndTime, TruthValue, MacAddress
            FROM SNMPv2-TC
        InetAddressIPv6
            FROM INET-ADDRESS-MIB;
            
            

                        
nmsTelnetMIB  MODULE-IDENTITY
        LAST-UPDATED    "201804040000Z"
        ORGANIZATION    ""
        CONTACT-INFO
                    ""
            
        DESCRIPTION
                "nmsTelnet management group."
        ::= { nms 9 256 }
        
      telnetEnable OBJECT-TYPE
          SYNTAX  INTEGER{
                    enable(1),
                    disable(2)
                         }
          ACCESS  read-write
          STATUS  mandatory
          DESCRIPTION
                  "Enable telnet server"
          ::= { nmsTelnetMIB 1 }

END
