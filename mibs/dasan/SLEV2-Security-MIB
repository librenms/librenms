--
-- slev2-security-mib.mib
-- MIB generated by MG-SOFT Visual MIB Builder Version 6.0  Build 88
-- Tuesday, July 28, 2015 at 14:14:00
--

	SLEV2-Security-MIB DEFINITIONS ::= BEGIN
 
		IMPORTS
			sleV2Mgmt			
				FROM DASAN-SMI			
			InetAddressType, InetAddress, InetAddressPrefixLength			
				FROM INET-ADDRESS-MIB			
			SleControlStatusType, SleControlRequestResultType			
				FROM SLE-TC-MIB			
			OBJECT-GROUP, NOTIFICATION-GROUP			
				FROM SNMPv2-CONF			
			TimeTicks, IpAddress, Integer32, Gauge32, Counter32, 
			Counter64, BITS, OBJECT-TYPE, MODULE-IDENTITY, NOTIFICATION-TYPE			
				FROM SNMPv2-SMI			
			TimeStamp, TEXTUAL-CONVENTION			
				FROM SNMPv2-TC;
	
	
		-- 1.3.6.1.4.1.6296.102.7
		sleV2Security MODULE-IDENTITY 
			LAST-UPDATED "200605051406Z"		-- May 05, 2006 at 14:06 GMT
			ORGANIZATION 
				"Organization."
			CONTACT-INFO 
				"Contact-info."
			DESCRIPTION 
				"slev2 security"
			::= { sleV2Mgmt 7 }

		
	
--
-- Type definitions
--
	
		IntFlowIndex ::= INTEGER (1..1024)

		IntClassIndex ::= INTEGER (1..1024)

		IntPolicyIndex ::= INTEGER (1..1024)

		OctetName ::= OCTET STRING (SIZE (1..64))

		IntIpAddrMask ::= INTEGER (0..32)

		IntProtocolType ::= INTEGER (-1 | 0..255)

		IntL4Port ::= INTEGER (-1 | 0..65535)

		IntIcmpType ::= INTEGER (-1 | 0..255)

		IntIcmpCode ::= INTEGER (-1 | 0..255)

		IntInternetProtocolFlag ::= INTEGER
			{
			nothing(-1),
			tcp(1),
			ucp(2),
			icmp(3)
			}

		IntRulePriority ::= INTEGER
			{
			nothing(-1),
			low(1),
			medium(2),
			high(3),
			highest(4)
			}

		IntFlowClass ::= INTEGER
			{
			nothing(-1),
			flow(1),
			class(2),
			both(4)
			}

		IntInterfaceIndex ::= INTEGER (-1 | 1..512)

		IntFlowOrClass ::= INTEGER
			{
			flow(1),
			class(2)
			}

		IntPermit ::= INTEGER
			{
			deny(1),
			permit(2),
			none(3)
			}

	
--
-- Textual conventions
--
	
		MacAddressMask ::= TEXTUAL-CONVENTION
			STATUS current
			DESCRIPTION 
				"Represents Mac address Mask.
				"
			SYNTAX OCTET STRING (SIZE (6))

	
--
-- Node definitions
--
	
		-- 1.3.6.1.4.1.6296.102.7.1
		sleV2SecurityBase OBJECT IDENTIFIER ::= { sleV2Security 1 }

		
		-- 1.3.6.1.4.1.6296.102.7.2
		sleVSecurity4 OBJECT IDENTIFIER ::= { sleV2Security 2 }

		
		-- 1.3.6.1.4.1.6296.102.7.2.5
		sleV2SecurityACL OBJECT IDENTIFIER ::= { sleVSecurity4 5 }

		
		-- 1.3.6.1.4.1.6296.102.7.2.5.1
		sleV2Security4ACLBase OBJECT IDENTIFIER ::= { sleV2SecurityACL 1 }

		
		-- 1.3.6.1.4.1.6296.102.7.2.5.2
		sleV2Security4ACLFlow OBJECT IDENTIFIER ::= { sleV2SecurityACL 2 }

		
		-- 1.3.6.1.4.1.6296.102.7.2.5.2.1
		sleV2Security4ACLFlowInfo OBJECT IDENTIFIER ::= { sleV2Security4ACLFlow 1 }

		
		-- 1.3.6.1.4.1.6296.102.7.2.5.2.1.1
		sleV2Security4ACLFlowTable OBJECT-TYPE
			SYNTAX SEQUENCE OF SleV2Security4ACLFlowEntry
			MAX-ACCESS not-accessible
			STATUS current
			DESCRIPTION
				"ACL flow table."
			::= { sleV2Security4ACLFlowInfo 1 }

		
		-- 1.3.6.1.4.1.6296.102.7.2.5.2.1.1.1
		sleV2Security4ACLFlowEntry OBJECT-TYPE
			SYNTAX SleV2Security4ACLFlowEntry
			MAX-ACCESS not-accessible
			STATUS current
			DESCRIPTION
				"key: sleV2Security4ACLFlowIndex"
			INDEX { sleV2Security4ACLFlowIndex }
			::= { sleV2Security4ACLFlowTable 1 }

		
		SleV2Security4ACLFlowEntry ::=
			SEQUENCE { 
				sleV2Security4ACLFlowIndex
					INTEGER,
				sleV2Security4ACLFlowName
					OctetName,
				sleV2Security4ACLFlowSrcIpAddr
					IpAddress,
				sleV2Security4ACLFlowSrcIpAddrMask
					IntIpAddrMask,
				sleV2Security4ACLFlowDstIpAddr
					IpAddress,
				sleV2Security4ACLFlowDstIpAddrMask
					IntIpAddrMask,
				sleV2Security4ACLFlowProtocolType
					IntProtocolType,
				sleV2Security4ACLFlowTcpSrcStartPort
					IntL4Port,
				sleV2Security4ACLFlowTcpSrcEndPort
					IntL4Port,
				sleV2Security4ACLFlowTcpDstStartPort
					IntL4Port,
				sleV2Security4ACLFlowTcpDstEndPort
					IntL4Port,
				sleV2Security4ACLFlowTcpFlag
					BITS,
				sleV2Security4ACLFlowUdpSrcStartPort
					IntL4Port,
				sleV2Security4ACLFlowUdpSrcEndPort
					IntL4Port,
				sleV2Security4ACLFlowUdpDstStartPort
					IntL4Port,
				sleV2Security4ACLFlowUdpDstEndPort
					IntL4Port,
				sleV2Security4ACLFlowIcmpType
					IntIcmpType,
				sleV2Security4ACLFlowIcmpCode
					IntIcmpCode,
				sleV2Security4ACLFlowHdrlen
					INTEGER,
				sleV2Security4ACLFlowIpFlag
					INTEGER,
				sleV2SecurityACLFlowInetAddrType
					InetAddressType,
				sleV2SecurityACLFlowSrcInetAddr
					InetAddress,
				sleV2SecurityACLFlowDstInetAddr
					InetAddress,
				sleV2SecurityACLFlowSrcInetAddrLen
					InetAddressPrefixLength,
				sleV2SecurityACLFlowDstInetAddrLen
					InetAddressPrefixLength
			 }

		-- 1.3.6.1.4.1.6296.102.7.2.5.2.1.1.1.1
		sleV2Security4ACLFlowIndex OBJECT-TYPE
			SYNTAX INTEGER (1..1024)
			MAX-ACCESS read-only
			STATUS current
			DESCRIPTION
				"The index of flow"
			::= { sleV2Security4ACLFlowEntry 1 }

		
		-- 1.3.6.1.4.1.6296.102.7.2.5.2.1.1.1.2
		sleV2Security4ACLFlowName OBJECT-TYPE
			SYNTAX OctetName
			MAX-ACCESS read-only
			STATUS current
			DESCRIPTION
				"The name of flow"
			::= { sleV2Security4ACLFlowEntry 2 }

		
		-- 1.3.6.1.4.1.6296.102.7.2.5.2.1.1.1.3
		sleV2Security4ACLFlowSrcIpAddr OBJECT-TYPE
			SYNTAX IpAddress
			MAX-ACCESS read-only
			STATUS current
			DESCRIPTION
				"The IP address to match against the packet's source IP address.
				The value of 0.0.0.0 means any(not set)
				"
			::= { sleV2Security4ACLFlowEntry 3 }

		
		-- 1.3.6.1.4.1.6296.102.7.2.5.2.1.1.1.4
		sleV2Security4ACLFlowSrcIpAddrMask OBJECT-TYPE
			SYNTAX IntIpAddrMask
			MAX-ACCESS read-only
			STATUS current
			DESCRIPTION
				"The mask of source IP address
				The value of -1 means any(not set)
				"
			::= { sleV2Security4ACLFlowEntry 4 }

		
		-- 1.3.6.1.4.1.6296.102.7.2.5.2.1.1.1.5
		sleV2Security4ACLFlowDstIpAddr OBJECT-TYPE
			SYNTAX IpAddress
			MAX-ACCESS read-only
			STATUS current
			DESCRIPTION
				"The IP address to match against the packet's destination IP address.
				The value of 0.0.0.0 means any(not set)
				"
			::= { sleV2Security4ACLFlowEntry 5 }

		
		-- 1.3.6.1.4.1.6296.102.7.2.5.2.1.1.1.6
		sleV2Security4ACLFlowDstIpAddrMask OBJECT-TYPE
			SYNTAX IntIpAddrMask
			MAX-ACCESS read-only
			STATUS current
			DESCRIPTION
				"The mask of destination IP address
				The value of -1 means any(not set)
				"
			::= { sleV2Security4ACLFlowEntry 6 }

		
		-- 1.3.6.1.4.1.6296.102.7.2.5.2.1.1.1.7
		sleV2Security4ACLFlowProtocolType OBJECT-TYPE
			SYNTAX IntProtocolType
			MAX-ACCESS read-only
			STATUS current
			DESCRIPTION
				"The type of IP protocol
				The flat internet protocol is from sleV2QoS4FlowTcpSrcStartPort to sleV2QoS4FlowIcmpCode
				If the value is tcp(6),
				From sleV2QoS4FlowTcpSrcStartPort to sleV2QoS4FlowTcpFlag value is available
				If the value is u¿¡(17),
				From sleV2QoS4FlowUdpSrcStartPort to sleV2QoS4FlowUdpDstEndPort value is available
				If the value is icmp(1),
				The value of sleV2QoS4FlowIcmpType and sleV2QoS4FlowIcmpCode is available
				The value of -1 means any(not set)
				Otherwise, from sleV2QoS4FlowTcpSrcStartPort to sleV2QoS4FlowIcmpCode value is not available
				The value of -1 means any(not set)
				"
			::= { sleV2Security4ACLFlowEntry 7 }

		
		-- 1.3.6.1.4.1.6296.102.7.2.5.2.1.1.1.8
		sleV2Security4ACLFlowTcpSrcStartPort OBJECT-TYPE
			SYNTAX IntL4Port
			MAX-ACCESS read-only
			STATUS current
			DESCRIPTION
				"The start source port in range of source port in TCP packet
				The value of -1 means any(not set)
				"
			::= { sleV2Security4ACLFlowEntry 8 }

		
		-- 1.3.6.1.4.1.6296.102.7.2.5.2.1.1.1.9
		sleV2Security4ACLFlowTcpSrcEndPort OBJECT-TYPE
			SYNTAX IntL4Port
			MAX-ACCESS read-only
			STATUS current
			DESCRIPTION
				"The end source port in range of source port in TCP packet
				The value of -1 means any(not set)
				"
			::= { sleV2Security4ACLFlowEntry 9 }

		
		-- 1.3.6.1.4.1.6296.102.7.2.5.2.1.1.1.10
		sleV2Security4ACLFlowTcpDstStartPort OBJECT-TYPE
			SYNTAX IntL4Port
			MAX-ACCESS read-only
			STATUS current
			DESCRIPTION
				"The start destination port in range of source port in TCP packet. The value of -1 means any(not set)"
			::= { sleV2Security4ACLFlowEntry 10 }

		
		-- 1.3.6.1.4.1.6296.102.7.2.5.2.1.1.1.11
		sleV2Security4ACLFlowTcpDstEndPort OBJECT-TYPE
			SYNTAX IntL4Port
			MAX-ACCESS read-only
			STATUS current
			DESCRIPTION
				"The end destination port in range of destination port in TCP packet. The value of -1 means any(not set)"
			::= { sleV2Security4ACLFlowEntry 11 }

		
		-- 1.3.6.1.4.1.6296.102.7.2.5.2.1.1.1.12
		sleV2Security4ACLFlowTcpFlag OBJECT-TYPE
			SYNTAX BITS
				{
				reserv0(0),
				reserv1(1),
				urg(2),
				ack(3),
				psh(4),
				rst(5),
				syn(6),
				fin(7)
				}
			MAX-ACCESS read-only
			STATUS current
			DESCRIPTION
				"The flag in TCP packet"
			::= { sleV2Security4ACLFlowEntry 12 }

		
		-- 1.3.6.1.4.1.6296.102.7.2.5.2.1.1.1.13
		sleV2Security4ACLFlowUdpSrcStartPort OBJECT-TYPE
			SYNTAX IntL4Port
			MAX-ACCESS read-only
			STATUS current
			DESCRIPTION
				"The start source port in range of source port in UDP packet
				The value of -1 means any(not set)
				"
			::= { sleV2Security4ACLFlowEntry 13 }

		
		-- 1.3.6.1.4.1.6296.102.7.2.5.2.1.1.1.14
		sleV2Security4ACLFlowUdpSrcEndPort OBJECT-TYPE
			SYNTAX IntL4Port
			MAX-ACCESS read-only
			STATUS current
			DESCRIPTION
				"The end source port in range of source port in UDP packet
				The value of -1 means any(not set)
				"
			::= { sleV2Security4ACLFlowEntry 14 }

		
		-- 1.3.6.1.4.1.6296.102.7.2.5.2.1.1.1.15
		sleV2Security4ACLFlowUdpDstStartPort OBJECT-TYPE
			SYNTAX IntL4Port
			MAX-ACCESS read-only
			STATUS current
			DESCRIPTION
				"The start destination port in range of destination port in UDP packet. The value of -1 means any(not set)"
			::= { sleV2Security4ACLFlowEntry 15 }

		
		-- 1.3.6.1.4.1.6296.102.7.2.5.2.1.1.1.16
		sleV2Security4ACLFlowUdpDstEndPort OBJECT-TYPE
			SYNTAX IntL4Port
			MAX-ACCESS read-only
			STATUS current
			DESCRIPTION
				"The end destination port in range of destination port in UDP packet. The value of -1 means any(not set)"
			::= { sleV2Security4ACLFlowEntry 16 }

		
		-- 1.3.6.1.4.1.6296.102.7.2.5.2.1.1.1.17
		sleV2Security4ACLFlowIcmpType OBJECT-TYPE
			SYNTAX IntIcmpType
			MAX-ACCESS read-only
			STATUS current
			DESCRIPTION
				"The type of ICMP message
				The value of -1 means any(not set)
				"
			::= { sleV2Security4ACLFlowEntry 17 }

		
		-- 1.3.6.1.4.1.6296.102.7.2.5.2.1.1.1.18
		sleV2Security4ACLFlowIcmpCode OBJECT-TYPE
			SYNTAX IntIcmpCode
			MAX-ACCESS read-only
			STATUS current
			DESCRIPTION
				"The code of ICMP message
				The value of -1 means any(not set)
				"
			::= { sleV2Security4ACLFlowEntry 18 }

		
		-- 1.3.6.1.4.1.6296.102.7.2.5.2.1.1.1.19
		sleV2Security4ACLFlowHdrlen OBJECT-TYPE
			SYNTAX INTEGER (0 | 1..15)
			MAX-ACCESS read-only
			STATUS current
			DESCRIPTION
				"The IP header length.
				The value of 0 means any(not set)"
			::= { sleV2Security4ACLFlowEntry 19 }

		
		-- 1.3.6.1.4.1.6296.102.7.2.5.2.1.1.1.20
		sleV2Security4ACLFlowIpFlag OBJECT-TYPE
			SYNTAX INTEGER
				{
				none(0),
				srcAny(1),
				dstAny(2),
				srcDstAny(3)
				}
			MAX-ACCESS read-only
			STATUS current
			DESCRIPTION
				"The any flag of IP address."
			::= { sleV2Security4ACLFlowEntry 20 }

		
		-- 1.3.6.1.4.1.6296.102.7.2.5.2.1.1.1.21
		sleV2SecurityACLFlowInetAddrType OBJECT-TYPE
			SYNTAX InetAddressType
			MAX-ACCESS read-only
			STATUS current
			DESCRIPTION
				"IP address type"
			::= { sleV2Security4ACLFlowEntry 21 }

		
		-- 1.3.6.1.4.1.6296.102.7.2.5.2.1.1.1.22
		sleV2SecurityACLFlowSrcInetAddr OBJECT-TYPE
			SYNTAX InetAddress
			MAX-ACCESS read-only
			STATUS current
			DESCRIPTION
				"The IP address to match against the packet¡¯s source IP address."
			::= { sleV2Security4ACLFlowEntry 22 }

		
		-- 1.3.6.1.4.1.6296.102.7.2.5.2.1.1.1.23
		sleV2SecurityACLFlowDstInetAddr OBJECT-TYPE
			SYNTAX InetAddress
			MAX-ACCESS read-only
			STATUS current
			DESCRIPTION
				"The IP address to match against the packet¡¯s destination IP address."
			::= { sleV2Security4ACLFlowEntry 23 }

		
		-- 1.3.6.1.4.1.6296.102.7.2.5.2.1.1.1.24
		sleV2SecurityACLFlowSrcInetAddrLen OBJECT-TYPE
			SYNTAX InetAddressPrefixLength
			MAX-ACCESS read-only
			STATUS current
			DESCRIPTION
				"The prefix length of source IP address
				"
			::= { sleV2Security4ACLFlowEntry 24 }

		
		-- 1.3.6.1.4.1.6296.102.7.2.5.2.1.1.1.25
		sleV2SecurityACLFlowDstInetAddrLen OBJECT-TYPE
			SYNTAX InetAddressPrefixLength
			MAX-ACCESS read-only
			STATUS current
			DESCRIPTION
				"The prefix length of destination IP address"
			::= { sleV2Security4ACLFlowEntry 25 }

		
		-- 1.3.6.1.4.1.6296.102.7.2.5.2.1.2
		sleV2Security4ACLFlowControl OBJECT IDENTIFIER ::= { sleV2Security4ACLFlowInfo 2 }

		
		-- 1.3.6.1.4.1.6296.102.7.2.5.2.1.2.1
		sleV2Security4ACLFlowControlRequest OBJECT-TYPE
			SYNTAX INTEGER
				{
				createFlow(1),
				modifyFlow(2),
				destroyFlow(3),
				destroyAllFlow(4),
				createFlowEx(5),
				setFlowEx(6)
				}
			MAX-ACCESS read-write
			STATUS current
			DESCRIPTION
				"The request of a user command"
			::= { sleV2Security4ACLFlowControl 1 }

		
		-- 1.3.6.1.4.1.6296.102.7.2.5.2.1.2.2
		sleV2Security4ACLFlowControlStatus OBJECT-TYPE
			SYNTAX SleControlStatusType
			MAX-ACCESS read-only
			STATUS current
			DESCRIPTION
				"The status of user command"
			::= { sleV2Security4ACLFlowControl 2 }

		
		-- 1.3.6.1.4.1.6296.102.7.2.5.2.1.2.3
		sleV2Security4ACLFlowControlTimer OBJECT-TYPE
			SYNTAX Gauge32
			MAX-ACCESS read-write
			STATUS current
			DESCRIPTION
				"The maximum time for the manager for a long running user command"
			::= { sleV2Security4ACLFlowControl 3 }

		
		-- 1.3.6.1.4.1.6296.102.7.2.5.2.1.2.4
		sleV2Security4ACLFlowControlTimeStamp OBJECT-TYPE
			SYNTAX TimeTicks
			MAX-ACCESS read-only
			STATUS current
			DESCRIPTION
				"The time stamp of the last command(end of command)"
			::= { sleV2Security4ACLFlowControl 4 }

		
		-- 1.3.6.1.4.1.6296.102.7.2.5.2.1.2.5
		sleV2Security4ACLFlowControlReqResult OBJECT-TYPE
			SYNTAX SleControlRequestResultType
			MAX-ACCESS read-only
			STATUS current
			DESCRIPTION
				"The result of the last user command"
			::= { sleV2Security4ACLFlowControl 5 }

		
		-- 1.3.6.1.4.1.6296.102.7.2.5.2.1.2.6
		sleV2Security4ACLFlowControlIndex OBJECT-TYPE
			SYNTAX IntFlowIndex
			MAX-ACCESS read-write
			STATUS current
			DESCRIPTION
				"The index of flow"
			::= { sleV2Security4ACLFlowControl 6 }

		
		-- 1.3.6.1.4.1.6296.102.7.2.5.2.1.2.7
		sleV2Security4ACLFlowControlName OBJECT-TYPE
			SYNTAX OctetName
			MAX-ACCESS read-write
			STATUS current
			DESCRIPTION
				"The name of flow"
			::= { sleV2Security4ACLFlowControl 7 }

		
		-- 1.3.6.1.4.1.6296.102.7.2.5.2.1.2.8
		sleV2Security4ACLFlowControlSrcIpAddr OBJECT-TYPE
			SYNTAX IpAddress
			MAX-ACCESS read-write
			STATUS current
			DESCRIPTION
				"The IP address to match against the packet's source IP address.
				The value of 0.0.0.0 means any(not set)
				"
			::= { sleV2Security4ACLFlowControl 8 }

		
		-- 1.3.6.1.4.1.6296.102.7.2.5.2.1.2.9
		sleV2Security4ACLFlowControlSrcIpAddrMask OBJECT-TYPE
			SYNTAX IntIpAddrMask
			MAX-ACCESS read-write
			STATUS current
			DESCRIPTION
				"The mask of source IP address
				The value of -1 means any(not set)
				"
			::= { sleV2Security4ACLFlowControl 9 }

		
		-- 1.3.6.1.4.1.6296.102.7.2.5.2.1.2.10
		sleV2Security4ACLFlowControlDstIpAddr OBJECT-TYPE
			SYNTAX IpAddress
			MAX-ACCESS read-write
			STATUS current
			DESCRIPTION
				"The IP address to match against the packet's destination IP address.
				The value of 0.0.0.0 means any(not set)
				"
			::= { sleV2Security4ACLFlowControl 10 }

		
		-- 1.3.6.1.4.1.6296.102.7.2.5.2.1.2.11
		sleV2Security4ACLFlowControlDstIpAddrMask OBJECT-TYPE
			SYNTAX IntIpAddrMask
			MAX-ACCESS read-write
			STATUS current
			DESCRIPTION
				"The mask of destination IP address
				The value of -1 means any(not set)
				"
			::= { sleV2Security4ACLFlowControl 11 }

		
		-- 1.3.6.1.4.1.6296.102.7.2.5.2.1.2.12
		sleV2Security4ACLFlowControlProtocolType OBJECT-TYPE
			SYNTAX IntProtocolType
			MAX-ACCESS read-write
			STATUS current
			DESCRIPTION
				"The type of IP protocol
				The flat internet protocol is from sleV2QoS4FlowTcpSrcStartPort to sleV2QoS4FlowIcmpCode
				If the value is tcp(6),
				From sleV2QoS4FlowControlTcpSrcStartPort to sleV2QoS4FlowControlTcpFlag value is available
				If the value is u¿¡(17),
				From sleV2QoS4FlowControlUdpSrcStartPort to sleV2QoS4FlowControlUdpDstEndPort value is available
				If the value is icmp(1),
				The value of sleV2QoS4FlowControlIcmpType and sleV2QoS4FlowControlIcmpCode is available
				The value of -1 means any(not set)
				Otherwise, from sleV2QoS4FlowControlTcpSrcStartPort to sleV2QoS4FlowControlIcmpCode value is not available
				The value of -1 means any(not set)
				"
			::= { sleV2Security4ACLFlowControl 12 }

		
		-- 1.3.6.1.4.1.6296.102.7.2.5.2.1.2.13
		sleV2Security4ACLFlowControlTcpSrcStartPort OBJECT-TYPE
			SYNTAX IntL4Port
			MAX-ACCESS read-write
			STATUS current
			DESCRIPTION
				"The start source port in range of source port in TCP packet
				The value of -1 means any(not set)
				"
			::= { sleV2Security4ACLFlowControl 13 }

		
		-- 1.3.6.1.4.1.6296.102.7.2.5.2.1.2.14
		sleV2Security4ACLFlowControlTcpSrcEndPort OBJECT-TYPE
			SYNTAX IntL4Port
			MAX-ACCESS read-write
			STATUS current
			DESCRIPTION
				"The end source port in range of source port in TCP packet
				The value of -1 means any(not set)
				"
			::= { sleV2Security4ACLFlowControl 14 }

		
		-- 1.3.6.1.4.1.6296.102.7.2.5.2.1.2.15
		sleV2Security4ACLFlowControlTcpDstStartPort OBJECT-TYPE
			SYNTAX IntL4Port
			MAX-ACCESS read-write
			STATUS current
			DESCRIPTION
				"The start destination port in range of source port in TCP packet. The value of -1 means any(not set)"
			::= { sleV2Security4ACLFlowControl 15 }

		
		-- 1.3.6.1.4.1.6296.102.7.2.5.2.1.2.16
		sleV2Security4ACLFlowControlTcpDstEndPort OBJECT-TYPE
			SYNTAX IntL4Port
			MAX-ACCESS read-write
			STATUS current
			DESCRIPTION
				"The end destination port in range of destination port in TCP packet. The value of -1 means any(not set)"
			::= { sleV2Security4ACLFlowControl 16 }

		
		-- 1.3.6.1.4.1.6296.102.7.2.5.2.1.2.17
		sleV2Security4ACLFlowControlTcpFlag OBJECT-TYPE
			SYNTAX BITS
				{
				reserv0(0),
				reserv1(1),
				urg(2),
				ack(3),
				psh(4),
				rst(5),
				syn(6),
				fin(7)
				}
			MAX-ACCESS read-write
			STATUS current
			DESCRIPTION
				"The flag in TCP packet"
			::= { sleV2Security4ACLFlowControl 17 }

		
		-- 1.3.6.1.4.1.6296.102.7.2.5.2.1.2.18
		sleV2Security4ACLFlowControlUdpSrcStartPort OBJECT-TYPE
			SYNTAX IntL4Port
			MAX-ACCESS read-write
			STATUS current
			DESCRIPTION
				"The start source port in range of source port in UDP packet
				The value of -1 means any(not set)
				"
			::= { sleV2Security4ACLFlowControl 18 }

		
		-- 1.3.6.1.4.1.6296.102.7.2.5.2.1.2.19
		sleV2Security4ACLFlowControlUdpSrcEndPort OBJECT-TYPE
			SYNTAX IntL4Port
			MAX-ACCESS read-write
			STATUS current
			DESCRIPTION
				"The end source port in range of source port in UDP packet
				The value of -1 means any(not set)
				"
			::= { sleV2Security4ACLFlowControl 19 }

		
		-- 1.3.6.1.4.1.6296.102.7.2.5.2.1.2.20
		sleV2Security4ACLFlowControlUdpDstStartPort OBJECT-TYPE
			SYNTAX IntL4Port
			MAX-ACCESS read-write
			STATUS current
			DESCRIPTION
				"The start destination port in range of destination port in UDP packet. The value of -1 means any(not set)"
			::= { sleV2Security4ACLFlowControl 20 }

		
		-- 1.3.6.1.4.1.6296.102.7.2.5.2.1.2.21
		sleV2Security4ACLFlowControlUdpDstEndPort OBJECT-TYPE
			SYNTAX IntL4Port
			MAX-ACCESS read-write
			STATUS current
			DESCRIPTION
				"The end destination port in range of destination port in UDP packet. The value of -1 means any(not set)"
			::= { sleV2Security4ACLFlowControl 21 }

		
		-- 1.3.6.1.4.1.6296.102.7.2.5.2.1.2.22
		sleV2Security4ACLFlowControlIcmpType OBJECT-TYPE
			SYNTAX IntIcmpType
			MAX-ACCESS read-write
			STATUS current
			DESCRIPTION
				"The type of ICMP message
				The value of -1 means any(not set)
				"
			::= { sleV2Security4ACLFlowControl 22 }

		
		-- 1.3.6.1.4.1.6296.102.7.2.5.2.1.2.23
		sleV2Security4ACLFlowControlIcmpCode OBJECT-TYPE
			SYNTAX IntIcmpCode
			MAX-ACCESS read-write
			STATUS current
			DESCRIPTION
				"The code of ICMP message
				The value of -1 means any(not set)
				"
			::= { sleV2Security4ACLFlowControl 23 }

		
		-- 1.3.6.1.4.1.6296.102.7.2.5.2.1.2.24
		sleV2Security4ACLFlowControlHdrlen OBJECT-TYPE
			SYNTAX INTEGER (0 | 1..15)
			MAX-ACCESS read-write
			STATUS current
			DESCRIPTION
				"The IP header length
				The value of 0 means any(not set)"
			::= { sleV2Security4ACLFlowControl 24 }

		
		-- 1.3.6.1.4.1.6296.102.7.2.5.2.1.2.25
		sleV2Security4ACLFlowControlIpFlag OBJECT-TYPE
			SYNTAX INTEGER
				{
				none(0),
				srcAny(1),
				dstAny(2),
				srcDstAny(3)
				}
			MAX-ACCESS read-write
			STATUS current
			DESCRIPTION
				"The any flag of IP address."
			::= { sleV2Security4ACLFlowControl 25 }

		
		-- 1.3.6.1.4.1.6296.102.7.2.5.2.1.2.26
		sleV2SecurityACLFlowControlInetAddrType OBJECT-TYPE
			SYNTAX InetAddressType
			MAX-ACCESS read-write
			STATUS current
			DESCRIPTION
				"IP address type"
			::= { sleV2Security4ACLFlowControl 26 }

		
		-- 1.3.6.1.4.1.6296.102.7.2.5.2.1.2.27
		sleV2SecurityACLFlowControlSrcInetAddr OBJECT-TYPE
			SYNTAX InetAddress
			MAX-ACCESS read-write
			STATUS current
			DESCRIPTION
				"The IP address to match against the packet¡¯s source IP address."
			::= { sleV2Security4ACLFlowControl 27 }

		
		-- 1.3.6.1.4.1.6296.102.7.2.5.2.1.2.28
		sleV2SecurityACLFlowControlDstInetAddr OBJECT-TYPE
			SYNTAX InetAddress
			MAX-ACCESS read-write
			STATUS current
			DESCRIPTION
				"The IP address to match against the packet¡¯s destination IP address."
			::= { sleV2Security4ACLFlowControl 28 }

		
		-- 1.3.6.1.4.1.6296.102.7.2.5.2.1.2.29
		sleV2SecurityACLFlowControlSrcInetAddrLen OBJECT-TYPE
			SYNTAX InetAddressPrefixLength
			MAX-ACCESS read-write
			STATUS current
			DESCRIPTION
				"The prefix length of source IP address"
			::= { sleV2Security4ACLFlowControl 29 }

		
		-- 1.3.6.1.4.1.6296.102.7.2.5.2.1.2.30
		sleV2SecurityACLFlowControlDstInetAddrLen OBJECT-TYPE
			SYNTAX InetAddressPrefixLength
			MAX-ACCESS read-write
			STATUS current
			DESCRIPTION
				"The prefix length of destination IP address"
			::= { sleV2Security4ACLFlowControl 30 }

		
		-- 1.3.6.1.4.1.6296.102.7.2.5.2.1.3
		sleV2Security4ACLFlowNotification OBJECT IDENTIFIER ::= { sleV2Security4ACLFlowInfo 3 }

		
		-- 1.3.6.1.4.1.6296.102.7.2.5.2.1.3.1
		sleACLFlowCreated NOTIFICATION-TYPE
			OBJECTS { sleV2Security4ACLFlowControlRequest, sleV2Security4ACLFlowControlTimeStamp, sleV2Security4ACLFlowIpFlag, sleV2Security4ACLFlowControlIpFlag, sleV2Security4ACLFlowControlReqResult, 
				sleV2Security4ACLFlowName, sleV2Security4ACLFlowSrcIpAddr, sleV2Security4ACLFlowSrcIpAddrMask, sleV2Security4ACLFlowDstIpAddr, sleV2Security4ACLFlowDstIpAddrMask, 
				sleV2Security4ACLFlowProtocolType, sleV2Security4ACLFlowTcpSrcStartPort, sleV2Security4ACLFlowTcpSrcEndPort, sleV2Security4ACLFlowTcpDstStartPort, sleV2Security4ACLFlowTcpDstEndPort, 
				sleV2Security4ACLFlowTcpFlag, sleV2Security4ACLFlowUdpSrcStartPort, sleV2Security4ACLFlowUdpSrcEndPort, sleV2Security4ACLFlowUdpDstStartPort, sleV2Security4ACLFlowUdpDstEndPort, 
				sleV2Security4ACLFlowIcmpType, sleV2Security4ACLFlowIcmpCode, sleV2Security4ACLFlowHdrlen }
			STATUS current
			DESCRIPTION 
				"Description."
			::= { sleV2Security4ACLFlowNotification 1 }

		
		-- 1.3.6.1.4.1.6296.102.7.2.5.2.1.3.2
		sleACLFlowChanged NOTIFICATION-TYPE
			OBJECTS { sleV2Security4ACLFlowControlRequest, sleV2Security4ACLFlowControlTimeStamp, sleV2Security4ACLFlowControlReqResult, sleV2Security4ACLFlowIpFlag, sleV2Security4ACLFlowControlIpFlag, 
				sleV2Security4ACLFlowControlIndex, sleV2Security4ACLFlowSrcIpAddr, sleV2Security4ACLFlowSrcIpAddrMask, sleV2Security4ACLFlowDstIpAddr, sleV2Security4ACLFlowDstIpAddrMask, 
				sleV2Security4ACLFlowProtocolType, sleV2Security4ACLFlowTcpSrcStartPort, sleV2Security4ACLFlowTcpSrcEndPort, sleV2Security4ACLFlowTcpDstStartPort, sleV2Security4ACLFlowTcpDstEndPort, 
				sleV2Security4ACLFlowTcpFlag, sleV2Security4ACLFlowUdpSrcStartPort, sleV2Security4ACLFlowUdpSrcEndPort, sleV2Security4ACLFlowUdpDstStartPort, sleV2Security4ACLFlowUdpDstEndPort, 
				sleV2Security4ACLFlowIcmpType, sleV2Security4ACLFlowIcmpCode, sleV2Security4ACLFlowHdrlen }
			STATUS current
			DESCRIPTION 
				"Description."
			::= { sleV2Security4ACLFlowNotification 2 }

		
		-- 1.3.6.1.4.1.6296.102.7.2.5.2.1.3.3
		sleACLFlowDestroyed NOTIFICATION-TYPE
			OBJECTS { sleV2Security4ACLFlowControlRequest, sleV2Security4ACLFlowControlTimeStamp, sleV2Security4ACLFlowControlReqResult, sleV2Security4ACLFlowControlIndex }
			STATUS current
			DESCRIPTION 
				"Description."
			::= { sleV2Security4ACLFlowNotification 3 }

		
		-- 1.3.6.1.4.1.6296.102.7.2.5.2.1.3.4
		sleACLFlowAllDestroyed NOTIFICATION-TYPE
			OBJECTS { sleV2Security4ACLFlowControlRequest, sleV2Security4ACLFlowControlTimeStamp, sleV2Security4ACLFlowControlReqResult }
			STATUS current
			DESCRIPTION 
				"Description."
			::= { sleV2Security4ACLFlowNotification 4 }

		
		-- 1.3.6.1.4.1.6296.102.7.2.5.2.1.3.5
		sleACLFlowExCreated NOTIFICATION-TYPE
			OBJECTS { sleV2Security4ACLFlowControlRequest, sleV2Security4ACLFlowControlTimeStamp, sleV2Security4ACLFlowControlReqResult, sleV2Security4ACLFlowName, sleV2SecurityACLFlowInetAddrType, 
				sleV2SecurityACLFlowSrcInetAddr, sleV2SecurityACLFlowDstInetAddr, sleV2SecurityACLFlowSrcInetAddrLen, sleV2SecurityACLFlowDstInetAddrLen, sleV2Security4ACLFlowProtocolType, 
				sleV2Security4ACLFlowTcpSrcStartPort, sleV2Security4ACLFlowTcpSrcEndPort, sleV2Security4ACLFlowTcpDstStartPort, sleV2Security4ACLFlowTcpDstEndPort, sleV2Security4ACLFlowTcpFlag, 
				sleV2Security4ACLFlowUdpSrcStartPort, sleV2Security4ACLFlowUdpSrcEndPort, sleV2Security4ACLFlowUdpDstStartPort, sleV2Security4ACLFlowUdpDstEndPort, sleV2Security4ACLFlowIcmpType, 
				sleV2Security4ACLFlowIcmpCode, sleV2Security4ACLFlowHdrlen, sleV2Security4ACLFlowIpFlag }
			STATUS current
			DESCRIPTION 
				"createACLFlowEx"
			::= { sleV2Security4ACLFlowNotification 5 }

		
		-- 1.3.6.1.4.1.6296.102.7.2.5.2.1.3.6
		sleACLFlowExChanged NOTIFICATION-TYPE
			OBJECTS { sleV2Security4ACLFlowControlRequest, sleV2Security4ACLFlowControlTimeStamp, sleV2Security4ACLFlowControlReqResult, sleV2Security4ACLFlowIndex, sleV2SecurityACLFlowInetAddrType, 
				sleV2SecurityACLFlowSrcInetAddr, sleV2SecurityACLFlowDstInetAddr, sleV2SecurityACLFlowSrcInetAddrLen, sleV2SecurityACLFlowDstInetAddrLen, sleV2Security4ACLFlowProtocolType, 
				sleV2Security4ACLFlowTcpSrcStartPort, sleV2Security4ACLFlowTcpSrcEndPort, sleV2Security4ACLFlowTcpDstStartPort, sleV2Security4ACLFlowTcpDstEndPort, sleV2Security4ACLFlowTcpFlag, 
				sleV2Security4ACLFlowUdpSrcStartPort, sleV2Security4ACLFlowUdpSrcEndPort, sleV2Security4ACLFlowUdpDstStartPort, sleV2Security4ACLFlowUdpDstEndPort, sleV2Security4ACLFlowIcmpType, 
				sleV2Security4ACLFlowIcmpCode, sleV2Security4ACLFlowHdrlen, sleV2Security4ACLFlowIpFlag }
			STATUS current
			DESCRIPTION 
				"setACLFlowEx"
			::= { sleV2Security4ACLFlowNotification 6 }

		
		-- 1.3.6.1.4.1.6296.102.7.2.5.2.2
		sleV2Security4ACLFlowClass OBJECT IDENTIFIER ::= { sleV2Security4ACLFlow 2 }

		
		-- 1.3.6.1.4.1.6296.102.7.2.5.2.2.1
		sleV2Security4ACLFlowClassTable OBJECT-TYPE
			SYNTAX SEQUENCE OF SleV2Security4ACLFlowClassEntry
			MAX-ACCESS not-accessible
			STATUS current
			DESCRIPTION
				"ACL flow class table."
			::= { sleV2Security4ACLFlowClass 1 }

		
		-- 1.3.6.1.4.1.6296.102.7.2.5.2.2.1.1
		sleV2Security4ACLFlowClassEntry OBJECT-TYPE
			SYNTAX SleV2Security4ACLFlowClassEntry
			MAX-ACCESS not-accessible
			STATUS current
			DESCRIPTION
				"key: sleV2Security4ACLFlowIndex, sleV2Security4ACLFlowClassIndex"
			INDEX { sleV2Security4ACLFlowIndex, sleV2Security4ACLFlowClassIndex }
			::= { sleV2Security4ACLFlowClassTable 1 }

		
		SleV2Security4ACLFlowClassEntry ::=
			SEQUENCE { 
				sleV2Security4ACLFlowClassIndex
					IntClassIndex,
				sleV2Security4ACLFlowClassID
					IntClassIndex,
				sleV2Security4ACLFlowClassName
					OctetName
			 }

		-- 1.3.6.1.4.1.6296.102.7.2.5.2.2.1.1.1
		sleV2Security4ACLFlowClassIndex OBJECT-TYPE
			SYNTAX IntClassIndex
			MAX-ACCESS read-only
			STATUS current
			DESCRIPTION
				"The index of the class for the flow"
			::= { sleV2Security4ACLFlowClassEntry 1 }

		
		-- 1.3.6.1.4.1.6296.102.7.2.5.2.2.1.1.2
		sleV2Security4ACLFlowClassID OBJECT-TYPE
			SYNTAX IntClassIndex
			MAX-ACCESS read-only
			STATUS current
			DESCRIPTION
				"The identifier of the class"
			::= { sleV2Security4ACLFlowClassEntry 2 }

		
		-- 1.3.6.1.4.1.6296.102.7.2.5.2.2.1.1.3
		sleV2Security4ACLFlowClassName OBJECT-TYPE
			SYNTAX OctetName
			MAX-ACCESS read-only
			STATUS current
			DESCRIPTION
				"The name of the class"
			::= { sleV2Security4ACLFlowClassEntry 3 }

		
		-- 1.3.6.1.4.1.6296.102.7.2.5.2.3
		sleV2Security4ACLFlowPolicy OBJECT IDENTIFIER ::= { sleV2Security4ACLFlow 3 }

		
		-- 1.3.6.1.4.1.6296.102.7.2.5.2.3.1
		sleV2QoS4ACLFlowPolicyTable OBJECT-TYPE
			SYNTAX SEQUENCE OF SleV2QoS4ACLFlowPolicyEntry
			MAX-ACCESS not-accessible
			STATUS current
			DESCRIPTION
				"ACL flow policy table."
			::= { sleV2Security4ACLFlowPolicy 1 }

		
		-- 1.3.6.1.4.1.6296.102.7.2.5.2.3.1.1
		sleV2QoS4ACLFlowPolicyEntry OBJECT-TYPE
			SYNTAX SleV2QoS4ACLFlowPolicyEntry
			MAX-ACCESS not-accessible
			STATUS current
			DESCRIPTION
				"key: sleV2Security4ACLFlowIndex, sleV2Security4ACLFlowPolicyIndex"
			INDEX { sleV2Security4ACLFlowIndex, sleV2Security4ACLFlowPolicyIndex }
			::= { sleV2QoS4ACLFlowPolicyTable 1 }

		
		SleV2QoS4ACLFlowPolicyEntry ::=
			SEQUENCE { 
				sleV2Security4ACLFlowPolicyIndex
					IntPolicyIndex,
				sleV2Security4ACLFlowPolicyID
					IntPolicyIndex,
				sleV2Security4ACLFlowPolicyName
					OctetName
			 }

		-- 1.3.6.1.4.1.6296.102.7.2.5.2.3.1.1.1
		sleV2Security4ACLFlowPolicyIndex OBJECT-TYPE
			SYNTAX IntPolicyIndex
			MAX-ACCESS read-only
			STATUS current
			DESCRIPTION
				"The index of the policy for the flow"
			::= { sleV2QoS4ACLFlowPolicyEntry 1 }

		
		-- 1.3.6.1.4.1.6296.102.7.2.5.2.3.1.1.2
		sleV2Security4ACLFlowPolicyID OBJECT-TYPE
			SYNTAX IntPolicyIndex
			MAX-ACCESS read-only
			STATUS current
			DESCRIPTION
				"The identifier of the policy"
			::= { sleV2QoS4ACLFlowPolicyEntry 2 }

		
		-- 1.3.6.1.4.1.6296.102.7.2.5.2.3.1.1.3
		sleV2Security4ACLFlowPolicyName OBJECT-TYPE
			SYNTAX OctetName
			MAX-ACCESS read-only
			STATUS current
			DESCRIPTION
				"The name of the policy"
			::= { sleV2QoS4ACLFlowPolicyEntry 3 }

		
		-- 1.3.6.1.4.1.6296.102.7.2.5.3
		sleV2Security4ACLClass OBJECT IDENTIFIER ::= { sleV2SecurityACL 3 }

		
		-- 1.3.6.1.4.1.6296.102.7.2.5.3.1
		sleV2Security4ACLClassInfo OBJECT IDENTIFIER ::= { sleV2Security4ACLClass 1 }

		
		-- 1.3.6.1.4.1.6296.102.7.2.5.3.1.1
		sleV2Security4ACLClassTable OBJECT-TYPE
			SYNTAX SEQUENCE OF SleV2Security4ACLClassEntry
			MAX-ACCESS not-accessible
			STATUS current
			DESCRIPTION
				"ACL class table."
			::= { sleV2Security4ACLClassInfo 1 }

		
		-- 1.3.6.1.4.1.6296.102.7.2.5.3.1.1.1
		sleV2Security4ACLClassEntry OBJECT-TYPE
			SYNTAX SleV2Security4ACLClassEntry
			MAX-ACCESS not-accessible
			STATUS current
			DESCRIPTION
				"key: sleV2Security4ACLClassIndex"
			INDEX { sleV2Security4ACLClassIndex }
			::= { sleV2Security4ACLClassTable 1 }

		
		SleV2Security4ACLClassEntry ::=
			SEQUENCE { 
				sleV2Security4ACLClassIndex
					IntClassIndex,
				sleV2Security4ACLClassName
					OctetName,
				sleV2Security4ACLClassFlowCnt
					Counter32
			 }

		-- 1.3.6.1.4.1.6296.102.7.2.5.3.1.1.1.1
		sleV2Security4ACLClassIndex OBJECT-TYPE
			SYNTAX IntClassIndex
			MAX-ACCESS read-only
			STATUS current
			DESCRIPTION
				"The index of class"
			::= { sleV2Security4ACLClassEntry 1 }

		
		-- 1.3.6.1.4.1.6296.102.7.2.5.3.1.1.1.2
		sleV2Security4ACLClassName OBJECT-TYPE
			SYNTAX OctetName
			MAX-ACCESS read-only
			STATUS current
			DESCRIPTION
				"The name of class"
			::= { sleV2Security4ACLClassEntry 2 }

		
		-- 1.3.6.1.4.1.6296.102.7.2.5.3.1.1.1.3
		sleV2Security4ACLClassFlowCnt OBJECT-TYPE
			SYNTAX Counter32
			MAX-ACCESS read-only
			STATUS current
			DESCRIPTION
				"The counter of flow in class"
			::= { sleV2Security4ACLClassEntry 3 }

		
		-- 1.3.6.1.4.1.6296.102.7.2.5.3.1.2
		sleV2Security4ACLClassControl OBJECT IDENTIFIER ::= { sleV2Security4ACLClassInfo 2 }

		
		-- 1.3.6.1.4.1.6296.102.7.2.5.3.1.2.1
		sleV2Security4ACLClassControlRequest OBJECT-TYPE
			SYNTAX INTEGER
				{
				createClass(1),
				destroyClass(2),
				destroyAllClass(3)
				}
			MAX-ACCESS read-write
			STATUS current
			DESCRIPTION
				"The request of a user command"
			::= { sleV2Security4ACLClassControl 1 }

		
		-- 1.3.6.1.4.1.6296.102.7.2.5.3.1.2.2
		sleV2Security4ACLClassControlStatus OBJECT-TYPE
			SYNTAX SleControlStatusType
			MAX-ACCESS read-only
			STATUS current
			DESCRIPTION
				"The status of user command"
			::= { sleV2Security4ACLClassControl 2 }

		
		-- 1.3.6.1.4.1.6296.102.7.2.5.3.1.2.3
		sleV2Security4ACLClassControlTimer OBJECT-TYPE
			SYNTAX Gauge32
			MAX-ACCESS read-write
			STATUS current
			DESCRIPTION
				"The maximum time for the manager for a long running user command"
			::= { sleV2Security4ACLClassControl 3 }

		
		-- 1.3.6.1.4.1.6296.102.7.2.5.3.1.2.4
		sleV2Security4ACLClassControlTimeStamp OBJECT-TYPE
			SYNTAX TimeTicks
			MAX-ACCESS read-only
			STATUS current
			DESCRIPTION
				"The time stamp of the last command(end of command)"
			::= { sleV2Security4ACLClassControl 4 }

		
		-- 1.3.6.1.4.1.6296.102.7.2.5.3.1.2.5
		sleV2Security4ACLClassControlReqResult OBJECT-TYPE
			SYNTAX SleControlRequestResultType
			MAX-ACCESS read-only
			STATUS current
			DESCRIPTION
				"The result of the last user command"
			::= { sleV2Security4ACLClassControl 5 }

		
		-- 1.3.6.1.4.1.6296.102.7.2.5.3.1.2.6
		sleV2Security4ACLClassControlIndex OBJECT-TYPE
			SYNTAX IntClassIndex
			MAX-ACCESS read-write
			STATUS current
			DESCRIPTION
				"The index of class"
			::= { sleV2Security4ACLClassControl 6 }

		
		-- 1.3.6.1.4.1.6296.102.7.2.5.3.1.2.7
		sleV2Security4ACLClassControlName OBJECT-TYPE
			SYNTAX OctetName
			MAX-ACCESS read-write
			STATUS current
			DESCRIPTION
				"The name of class"
			::= { sleV2Security4ACLClassControl 7 }

		
		-- 1.3.6.1.4.1.6296.102.7.2.5.3.1.3
		sleV2Security4ACLClassNotification OBJECT IDENTIFIER ::= { sleV2Security4ACLClassInfo 3 }

		
		-- 1.3.6.1.4.1.6296.102.7.2.5.3.1.3.1
		sleACLClassCreated NOTIFICATION-TYPE
			OBJECTS { sleV2Security4ACLClassControlRequest, sleV2Security4ACLClassControlTimeStamp, sleV2Security4ACLClassControlReqResult, sleV2Security4ACLFlowClassName }
			STATUS current
			DESCRIPTION 
				"Description."
			::= { sleV2Security4ACLClassNotification 1 }

		
		-- 1.3.6.1.4.1.6296.102.7.2.5.3.1.3.2
		sleACLClassDestroyed NOTIFICATION-TYPE
			OBJECTS { sleV2Security4ACLClassControlRequest, sleV2Security4ACLClassControlTimeStamp, sleV2Security4ACLClassControlReqResult, sleV2Security4ACLClassControlIndex }
			STATUS current
			DESCRIPTION 
				"Description."
			::= { sleV2Security4ACLClassNotification 2 }

		
		-- 1.3.6.1.4.1.6296.102.7.2.5.3.1.3.3
		sleACLClassAllDestroyed NOTIFICATION-TYPE
			OBJECTS { sleV2Security4ACLClassControlRequest, sleV2Security4ACLClassControlTimeStamp, sleV2Security4ACLClassControlReqResult }
			STATUS current
			DESCRIPTION 
				"Description."
			::= { sleV2Security4ACLClassNotification 3 }

		
		-- 1.3.6.1.4.1.6296.102.7.2.5.3.2
		sleV2Security4ACLClassFlow OBJECT IDENTIFIER ::= { sleV2Security4ACLClass 2 }

		
		-- 1.3.6.1.4.1.6296.102.7.2.5.3.2.1
		sleV2Security4ACLClassFlowTable OBJECT-TYPE
			SYNTAX SEQUENCE OF SleV2Security4ACLClassFlowEntry
			MAX-ACCESS not-accessible
			STATUS current
			DESCRIPTION
				"Description."
			::= { sleV2Security4ACLClassFlow 1 }

		
		-- 1.3.6.1.4.1.6296.102.7.2.5.3.2.1.1
		sleV2Security4ACLClassFlowEntry OBJECT-TYPE
			SYNTAX SleV2Security4ACLClassFlowEntry
			MAX-ACCESS not-accessible
			STATUS current
			DESCRIPTION
				"Description."
			INDEX { sleV2Security4ACLClassIndex, sleV2Security4ACLClassFlowIndex }
			::= { sleV2Security4ACLClassFlowTable 1 }

		
		SleV2Security4ACLClassFlowEntry ::=
			SEQUENCE { 
				sleV2Security4ACLClassFlowIndex
					IntFlowIndex,
				sleV2Security4ACLClassFlowID
					IntFlowIndex,
				sleV2Security4ACLClassFlowName
					OctetName,
				sleV2Security4ACLClassFlowClassName
					OctetName
			 }

		-- 1.3.6.1.4.1.6296.102.7.2.5.3.2.1.1.1
		sleV2Security4ACLClassFlowIndex OBJECT-TYPE
			SYNTAX IntFlowIndex
			MAX-ACCESS read-only
			STATUS current
			DESCRIPTION
				"The index of flow in class"
			::= { sleV2Security4ACLClassFlowEntry 1 }

		
		-- 1.3.6.1.4.1.6296.102.7.2.5.3.2.1.1.2
		sleV2Security4ACLClassFlowID OBJECT-TYPE
			SYNTAX IntFlowIndex
			MAX-ACCESS read-only
			STATUS current
			DESCRIPTION
				"The identifier of flow"
			::= { sleV2Security4ACLClassFlowEntry 2 }

		
		-- 1.3.6.1.4.1.6296.102.7.2.5.3.2.1.1.3
		sleV2Security4ACLClassFlowName OBJECT-TYPE
			SYNTAX OctetName
			MAX-ACCESS read-only
			STATUS current
			DESCRIPTION
				"The name of the flow"
			::= { sleV2Security4ACLClassFlowEntry 3 }

		
		-- 1.3.6.1.4.1.6296.102.7.2.5.3.2.1.1.4
		sleV2Security4ACLClassFlowClassName OBJECT-TYPE
			SYNTAX OctetName
			MAX-ACCESS read-only
			STATUS current
			DESCRIPTION
				"The class name of the Classflow"
			::= { sleV2Security4ACLClassFlowEntry 4 }

		
		-- 1.3.6.1.4.1.6296.102.7.2.5.3.2.2
		sleV2Security4ACLClassFlowControl OBJECT IDENTIFIER ::= { sleV2Security4ACLClassFlow 2 }

		
		-- 1.3.6.1.4.1.6296.102.7.2.5.3.2.2.1
		sleV2Security4ACLClassFlowControlRequest OBJECT-TYPE
			SYNTAX INTEGER
				{
				addFlow(1),
				deleteFlow(2),
				deleteAllFlow(3)
				}
			MAX-ACCESS read-write
			STATUS current
			DESCRIPTION
				"The request of a user command"
			::= { sleV2Security4ACLClassFlowControl 1 }

		
		-- 1.3.6.1.4.1.6296.102.7.2.5.3.2.2.2
		sleV2Security4ACLClassFlowControlStatus OBJECT-TYPE
			SYNTAX SleControlStatusType
			MAX-ACCESS read-only
			STATUS current
			DESCRIPTION
				"The status of user command"
			::= { sleV2Security4ACLClassFlowControl 2 }

		
		-- 1.3.6.1.4.1.6296.102.7.2.5.3.2.2.3
		sleV2Security4ACLClassFlowControlTimer OBJECT-TYPE
			SYNTAX Gauge32
			MAX-ACCESS read-write
			STATUS current
			DESCRIPTION
				"The maximum time for the manager for a long running user command"
			::= { sleV2Security4ACLClassFlowControl 3 }

		
		-- 1.3.6.1.4.1.6296.102.7.2.5.3.2.2.4
		sleV2Security4ACLClassFlowControlTimeStamp OBJECT-TYPE
			SYNTAX TimeTicks
			MAX-ACCESS read-only
			STATUS current
			DESCRIPTION
				"The time stamp of the last command(end of command)"
			::= { sleV2Security4ACLClassFlowControl 4 }

		
		-- 1.3.6.1.4.1.6296.102.7.2.5.3.2.2.5
		sleV2Security4ACLClassFlowControlReqResult OBJECT-TYPE
			SYNTAX SleControlRequestResultType
			MAX-ACCESS read-only
			STATUS current
			DESCRIPTION
				"The result of the last user command"
			::= { sleV2Security4ACLClassFlowControl 5 }

		
		-- 1.3.6.1.4.1.6296.102.7.2.5.3.2.2.6
		sleV2Security4ACLClassFlowControlClassIndex OBJECT-TYPE
			SYNTAX IntClassIndex
			MAX-ACCESS read-write
			STATUS current
			DESCRIPTION
				"The index of class"
			::= { sleV2Security4ACLClassFlowControl 6 }

		
		-- 1.3.6.1.4.1.6296.102.7.2.5.3.2.2.7
		sleV2Security4ACLClassFlowControlFlowIndex OBJECT-TYPE
			SYNTAX IntFlowIndex
			MAX-ACCESS read-write
			STATUS current
			DESCRIPTION
				"The index of flow in this class"
			::= { sleV2Security4ACLClassFlowControl 7 }

		
		-- 1.3.6.1.4.1.6296.102.7.2.5.3.2.2.8
		sleV2Security4ACLClassFlowControlFlowID OBJECT-TYPE
			SYNTAX IntFlowIndex
			MAX-ACCESS read-write
			STATUS current
			DESCRIPTION
				"The index of flow
				Refer to sleV2QoS4FlowIndex
				"
			::= { sleV2Security4ACLClassFlowControl 8 }

		
		-- 1.3.6.1.4.1.6296.102.7.2.5.3.2.2.9
		sleV2Security4ACLClassFlowControlClassName OBJECT-TYPE
			SYNTAX OCTET STRING
			MAX-ACCESS read-write
			STATUS current
			DESCRIPTION
				"The class name of classFlow"
			::= { sleV2Security4ACLClassFlowControl 9 }

		
		-- 1.3.6.1.4.1.6296.102.7.2.5.3.2.3
		sleV2Security4ACLClassFlowNotification OBJECT IDENTIFIER ::= { sleV2Security4ACLClassFlow 3 }

		
		-- 1.3.6.1.4.1.6296.102.7.2.5.3.2.3.1
		sleACLClassFlowAdded NOTIFICATION-TYPE
			OBJECTS { sleV2Security4ACLClassFlowControlRequest, sleV2Security4ACLClassFlowControlTimeStamp, sleV2Security4ACLClassFlowControlReqResult, sleV2Security4ACLClassFlowControlClassName, sleV2Security4ACLClassFlowControlClassIndex, 
				sleV2Security4ACLClassFlowID }
			STATUS current
			DESCRIPTION 
				"Description."
			::= { sleV2Security4ACLClassFlowNotification 1 }

		
		-- 1.3.6.1.4.1.6296.102.7.2.5.3.2.3.2
		sleACLClassFlowDeleted NOTIFICATION-TYPE
			OBJECTS { sleV2Security4ACLClassFlowControlRequest, sleV2Security4ACLClassFlowControlTimeStamp, sleV2Security4ACLClassFlowControlReqResult, sleV2Security4ACLClassFlowControlClassIndex, sleV2Security4ACLClassFlowControlFlowIndex, 
				sleV2Security4ACLClassFlowControlClassName }
			STATUS current
			DESCRIPTION 
				"Description."
			::= { sleV2Security4ACLClassFlowNotification 2 }

		
		-- 1.3.6.1.4.1.6296.102.7.2.5.3.2.3.3
		sleACLClassFlowAllDeleted NOTIFICATION-TYPE
			OBJECTS { sleV2Security4ACLClassFlowControlRequest, sleV2Security4ACLClassFlowControlTimeStamp, sleV2Security4ACLClassFlowControlReqResult, sleV2Security4ACLClassFlowControlClassIndex }
			STATUS current
			DESCRIPTION 
				"Description."
			::= { sleV2Security4ACLClassFlowNotification 3 }

		
		-- 1.3.6.1.4.1.6296.102.7.2.5.3.3
		sleV2Security4ACLClassPolicy OBJECT IDENTIFIER ::= { sleV2Security4ACLClass 3 }

		
		-- 1.3.6.1.4.1.6296.102.7.2.5.3.3.1
		sleV2Security4ACLClassPolicyTable OBJECT-TYPE
			SYNTAX SEQUENCE OF SleV2Security4ACLClassPolicyEntry
			MAX-ACCESS not-accessible
			STATUS current
			DESCRIPTION
				"Description."
			::= { sleV2Security4ACLClassPolicy 1 }

		
		-- 1.3.6.1.4.1.6296.102.7.2.5.3.3.1.1
		sleV2Security4ACLClassPolicyEntry OBJECT-TYPE
			SYNTAX SleV2Security4ACLClassPolicyEntry
			MAX-ACCESS not-accessible
			STATUS current
			DESCRIPTION
				"Description."
			INDEX { sleV2Security4ACLClassIndex, sleV2Security4ACLClassPolicyIndex }
			::= { sleV2Security4ACLClassPolicyTable 1 }

		
		SleV2Security4ACLClassPolicyEntry ::=
			SEQUENCE { 
				sleV2Security4ACLClassPolicyIndex
					IntPolicyIndex,
				sleV2Security4ACLClassPolicyID
					IntPolicyIndex,
				sleV2Security4ACLClassPolicyName
					OctetName
			 }

		-- 1.3.6.1.4.1.6296.102.7.2.5.3.3.1.1.1
		sleV2Security4ACLClassPolicyIndex OBJECT-TYPE
			SYNTAX IntPolicyIndex
			MAX-ACCESS read-only
			STATUS current
			DESCRIPTION
				"The index of the policy for the class"
			::= { sleV2Security4ACLClassPolicyEntry 1 }

		
		-- 1.3.6.1.4.1.6296.102.7.2.5.3.3.1.1.2
		sleV2Security4ACLClassPolicyID OBJECT-TYPE
			SYNTAX IntPolicyIndex
			MAX-ACCESS read-only
			STATUS current
			DESCRIPTION
				"The identifier of the policy"
			::= { sleV2Security4ACLClassPolicyEntry 2 }

		
		-- 1.3.6.1.4.1.6296.102.7.2.5.3.3.1.1.3
		sleV2Security4ACLClassPolicyName OBJECT-TYPE
			SYNTAX OctetName
			MAX-ACCESS read-only
			STATUS current
			DESCRIPTION
				"The name of the policy"
			::= { sleV2Security4ACLClassPolicyEntry 3 }

		
		-- 1.3.6.1.4.1.6296.102.7.2.5.4
		sleV2Security4ACLPolicy OBJECT IDENTIFIER ::= { sleV2SecurityACL 4 }

		
		-- 1.3.6.1.4.1.6296.102.7.2.5.4.1
		sleV2Security4ACLPolicyInfo OBJECT IDENTIFIER ::= { sleV2Security4ACLPolicy 1 }

		
		-- 1.3.6.1.4.1.6296.102.7.2.5.4.1.1
		sleV2Security4ACLPolicyTable OBJECT-TYPE
			SYNTAX SEQUENCE OF SleV2Security4ACLPolicyEntry
			MAX-ACCESS not-accessible
			STATUS current
			DESCRIPTION
				"ACL policy table."
			::= { sleV2Security4ACLPolicyInfo 1 }

		
		-- 1.3.6.1.4.1.6296.102.7.2.5.4.1.1.1
		sleV2Security4ACLPolicyEntry OBJECT-TYPE
			SYNTAX SleV2Security4ACLPolicyEntry
			MAX-ACCESS not-accessible
			STATUS current
			DESCRIPTION
				"key: sleV2Security4ACLPolicyIndex"
			INDEX { sleV2Security4ACLPolicyIndex }
			::= { sleV2Security4ACLPolicyTable 1 }

		
		SleV2Security4ACLPolicyEntry ::=
			SEQUENCE { 
				sleV2Security4ACLPolicyIndex
					IntPolicyIndex,
				sleV2Security4ACLPolicyName
					OctetName,
				sleV2Security4ACLPolicyFlowCnt
					Integer32,
				sleV2Security4ACLPolicyClassCnt
					Integer32,
				sleV2Security4ACLPolicyPriority
					INTEGER,
				sleV2Security4ACLPolicyMatchFlag
					IntPermit,
				sleV2Security4ACLPolicyNomatchFlag
					IntPermit
			 }

		-- 1.3.6.1.4.1.6296.102.7.2.5.4.1.1.1.1
		sleV2Security4ACLPolicyIndex OBJECT-TYPE
			SYNTAX IntPolicyIndex
			MAX-ACCESS read-only
			STATUS current
			DESCRIPTION
				"The index of policy"
			::= { sleV2Security4ACLPolicyEntry 1 }

		
		-- 1.3.6.1.4.1.6296.102.7.2.5.4.1.1.1.2
		sleV2Security4ACLPolicyName OBJECT-TYPE
			SYNTAX OctetName
			MAX-ACCESS read-only
			STATUS current
			DESCRIPTION
				"The name of policy"
			::= { sleV2Security4ACLPolicyEntry 2 }

		
		-- 1.3.6.1.4.1.6296.102.7.2.5.4.1.1.1.3
		sleV2Security4ACLPolicyFlowCnt OBJECT-TYPE
			SYNTAX Integer32
			MAX-ACCESS read-only
			STATUS current
			DESCRIPTION
				"The counter of flow that was included to policy"
			::= { sleV2Security4ACLPolicyEntry 3 }

		
		-- 1.3.6.1.4.1.6296.102.7.2.5.4.1.1.1.4
		sleV2Security4ACLPolicyClassCnt OBJECT-TYPE
			SYNTAX Integer32
			MAX-ACCESS read-only
			STATUS current
			DESCRIPTION
				"The counter of class that was included to policy"
			::= { sleV2Security4ACLPolicyEntry 4 }

		
		-- 1.3.6.1.4.1.6296.102.7.2.5.4.1.1.1.5
		sleV2Security4ACLPolicyPriority OBJECT-TYPE
			SYNTAX INTEGER
				{
				low(1),
				medium(2),
				high(3),
				highest(4)
				}
			MAX-ACCESS read-only
			STATUS current
			DESCRIPTION
				"The priority of the policy
				
				low : default value
				"
			::= { sleV2Security4ACLPolicyEntry 5 }

		
		-- 1.3.6.1.4.1.6296.102.7.2.5.4.1.1.1.6
		sleV2Security4ACLPolicyMatchFlag OBJECT-TYPE
			SYNTAX IntPermit
			MAX-ACCESS read-only
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				"
			::= { sleV2Security4ACLPolicyEntry 6 }

		
		-- 1.3.6.1.4.1.6296.102.7.2.5.4.1.1.1.7
		sleV2Security4ACLPolicyNomatchFlag OBJECT-TYPE
			SYNTAX IntPermit
			MAX-ACCESS read-only
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { sleV2Security4ACLPolicyEntry 7 }

		
		-- 1.3.6.1.4.1.6296.102.7.2.5.4.1.2
		sleV2Security4ACLPolicyControl OBJECT IDENTIFIER ::= { sleV2Security4ACLPolicyInfo 2 }

		
		-- 1.3.6.1.4.1.6296.102.7.2.5.4.1.2.1
		sleV2Security4ACLPolicyControlRequest OBJECT-TYPE
			SYNTAX INTEGER
				{
				createPolicy(1),
				setPolicyInfo(2),
				setMatchAction(3),
				setNomatchAction(4),
				destroyPolicy(5)
				}
			MAX-ACCESS read-write
			STATUS current
			DESCRIPTION
				"The request of a user command"
			::= { sleV2Security4ACLPolicyControl 1 }

		
		-- 1.3.6.1.4.1.6296.102.7.2.5.4.1.2.2
		sleV2Security4ACLPolicyControlStatus OBJECT-TYPE
			SYNTAX SleControlStatusType
			MAX-ACCESS read-only
			STATUS current
			DESCRIPTION
				"The status of user command"
			::= { sleV2Security4ACLPolicyControl 2 }

		
		-- 1.3.6.1.4.1.6296.102.7.2.5.4.1.2.3
		sleV2Security4ACLPolicyControlTimer OBJECT-TYPE
			SYNTAX Gauge32
			MAX-ACCESS read-write
			STATUS current
			DESCRIPTION
				"The maximum time for the manager for a long running user command"
			::= { sleV2Security4ACLPolicyControl 3 }

		
		-- 1.3.6.1.4.1.6296.102.7.2.5.4.1.2.4
		sleV2Security4ACLPolicyControlTimeStamp OBJECT-TYPE
			SYNTAX TimeTicks
			MAX-ACCESS read-only
			STATUS current
			DESCRIPTION
				"The time stamp of the last command(end of command)"
			::= { sleV2Security4ACLPolicyControl 4 }

		
		-- 1.3.6.1.4.1.6296.102.7.2.5.4.1.2.5
		sleV2Security4ACLPolicyControlReqResult OBJECT-TYPE
			SYNTAX SleControlRequestResultType
			MAX-ACCESS read-only
			STATUS current
			DESCRIPTION
				"The result of the last user command"
			::= { sleV2Security4ACLPolicyControl 5 }

		
		-- 1.3.6.1.4.1.6296.102.7.2.5.4.1.2.6
		sleV2Security4ACLPolicyControlIndex OBJECT-TYPE
			SYNTAX IntPolicyIndex
			MAX-ACCESS read-write
			STATUS current
			DESCRIPTION
				"The index of policy"
			::= { sleV2Security4ACLPolicyControl 6 }

		
		-- 1.3.6.1.4.1.6296.102.7.2.5.4.1.2.7
		sleV2Security4ACLPolicyControlName OBJECT-TYPE
			SYNTAX OctetName
			MAX-ACCESS read-write
			STATUS current
			DESCRIPTION
				"The name of policy"
			::= { sleV2Security4ACLPolicyControl 7 }

		
		-- 1.3.6.1.4.1.6296.102.7.2.5.4.1.2.8
		sleV2Security4ACLPolicyControlPriority OBJECT-TYPE
			SYNTAX IntRulePriority
			MAX-ACCESS read-write
			STATUS current
			DESCRIPTION
				"The priority of the policy
				
				low : default
				"
			::= { sleV2Security4ACLPolicyControl 8 }

		
		-- 1.3.6.1.4.1.6296.102.7.2.5.4.1.2.9
		sleV2Security4ACLPolicyControlMatchFlag OBJECT-TYPE
			SYNTAX IntPermit
			MAX-ACCESS read-write
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				"
			::= { sleV2Security4ACLPolicyControl 9 }

		
		-- 1.3.6.1.4.1.6296.102.7.2.5.4.1.2.10
		sleV2Security4ACLPolicyControlNomatchFlag OBJECT-TYPE
			SYNTAX IntPermit
			MAX-ACCESS read-write
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { sleV2Security4ACLPolicyControl 10 }

		
		-- 1.3.6.1.4.1.6296.102.7.2.5.4.1.2.11
		sleV2Security4ACLPolicyControlFlowID OBJECT-TYPE
			SYNTAX Integer32
			MAX-ACCESS read-write
			STATUS current
			DESCRIPTION
				"The index of flow"
			::= { sleV2Security4ACLPolicyControl 11 }

		
		-- 1.3.6.1.4.1.6296.102.7.2.5.4.1.2.12
		sleV2Security4ACLPolicyControlClassID OBJECT-TYPE
			SYNTAX Integer32
			MAX-ACCESS read-write
			STATUS current
			DESCRIPTION
				"The index of class"
			::= { sleV2Security4ACLPolicyControl 12 }

		
		-- 1.3.6.1.4.1.6296.102.7.2.5.4.1.3
		sleV2Security4ACLPolicyNotification OBJECT IDENTIFIER ::= { sleV2Security4ACLPolicyInfo 3 }

		
		-- 1.3.6.1.4.1.6296.102.7.2.5.4.1.3.1
		sleACLPolicyCreated NOTIFICATION-TYPE
			OBJECTS { sleV2Security4ACLPolicyControlRequest, sleV2Security4ACLPolicyControlTimeStamp, sleV2Security4ACLPolicyControlReqResult, sleV2Security4ACLClassPolicyName, sleV2Security4ACLPolicyPriority, 
				sleV2Security4ACLPolicyMatchFlag, sleV2Security4ACLPolicyNomatchFlag }
			STATUS current
			DESCRIPTION 
				"Description."
			::= { sleV2Security4ACLPolicyNotification 1 }

		
		-- 1.3.6.1.4.1.6296.102.7.2.5.4.1.3.2
		sleACLPolicyInfoChanged NOTIFICATION-TYPE
			OBJECTS { sleV2Security4ACLPolicyControlRequest, sleV2Security4ACLPolicyControlTimeStamp, sleV2Security4ACLPolicyControlReqResult, sleV2Security4ACLPolicyPriority }
			STATUS current
			DESCRIPTION 
				"Description."
			::= { sleV2Security4ACLPolicyNotification 2 }

		
		-- 1.3.6.1.4.1.6296.102.7.2.5.4.1.3.3
		sleACLPolicyMatchActionChanged NOTIFICATION-TYPE
			OBJECTS { sleV2Security4ACLPolicyControlRequest, sleV2Security4ACLPolicyControlTimeStamp, sleV2Security4ACLPolicyControlReqResult, sleV2Security4ACLPolicyMatchFlag }
			STATUS current
			DESCRIPTION 
				"Description."
			::= { sleV2Security4ACLPolicyNotification 3 }

		
		-- 1.3.6.1.4.1.6296.102.7.2.5.4.1.3.4
		sleACLPolicyNomatchActionChanged NOTIFICATION-TYPE
			OBJECTS { sleV2Security4ACLPolicyControlRequest, sleV2Security4ACLPolicyControlTimeStamp, sleV2Security4ACLPolicyControlReqResult, sleV2Security4ACLPolicyNomatchFlag }
			STATUS current
			DESCRIPTION 
				"Description."
			::= { sleV2Security4ACLPolicyNotification 4 }

		
		-- 1.3.6.1.4.1.6296.102.7.2.5.4.1.3.5
		sleACLPolicyDestroyed NOTIFICATION-TYPE
			OBJECTS { sleV2Security4ACLPolicyControlRequest, sleV2Security4ACLPolicyControlTimeStamp, sleV2Security4ACLPolicyControlReqResult, sleV2Security4ACLPolicyControlIndex }
			STATUS current
			DESCRIPTION 
				"Description."
			::= { sleV2Security4ACLPolicyNotification 5 }

		
		-- 1.3.6.1.4.1.6296.102.7.2.5.4.2
		sleV2Security4ACLPolicyFlowClass OBJECT IDENTIFIER ::= { sleV2Security4ACLPolicy 2 }

		
		-- 1.3.6.1.4.1.6296.102.7.2.5.4.2.1
		sleV2Security4ACLPolicyFlowClassTable OBJECT-TYPE
			SYNTAX SEQUENCE OF SleV2Security4ACLPolicyFlowClassEntry
			MAX-ACCESS not-accessible
			STATUS current
			DESCRIPTION
				"ACL policy flow class table."
			::= { sleV2Security4ACLPolicyFlowClass 1 }

		
		-- 1.3.6.1.4.1.6296.102.7.2.5.4.2.1.1
		sleV2Security4ACLPolicyFlowClassEntry OBJECT-TYPE
			SYNTAX SleV2Security4ACLPolicyFlowClassEntry
			MAX-ACCESS not-accessible
			STATUS current
			DESCRIPTION
				"key: sleV2Security4ACLPolicyIndex, sleV2Security4ACLPolicyFlowClassIndex"
			INDEX { sleV2Security4ACLPolicyIndex, sleV2Security4ACLPolicyFlowClassIndex }
			::= { sleV2Security4ACLPolicyFlowClassTable 1 }

		
		SleV2Security4ACLPolicyFlowClassEntry ::=
			SEQUENCE { 
				sleV2Security4ACLPolicyFlowClassIndex
					IntFlowIndex,
				sleV2Security4ACLPolicyFlowClassType
					IntFlowOrClass,
				sleV2Security4ACLPolicyFlowClassID
					IntFlowIndex,
				sleV2Security4ACLPolicyFlowClassName
					OctetName
			 }

		-- 1.3.6.1.4.1.6296.102.7.2.5.4.2.1.1.1
		sleV2Security4ACLPolicyFlowClassIndex OBJECT-TYPE
			SYNTAX IntFlowIndex
			MAX-ACCESS read-only
			STATUS current
			DESCRIPTION
				"The index of flow or class in policy"
			::= { sleV2Security4ACLPolicyFlowClassEntry 1 }

		
		-- 1.3.6.1.4.1.6296.102.7.2.5.4.2.1.1.2
		sleV2Security4ACLPolicyFlowClassType OBJECT-TYPE
			SYNTAX IntFlowOrClass
			MAX-ACCESS read-only
			STATUS current
			DESCRIPTION
				"The flag about flow or class"
			::= { sleV2Security4ACLPolicyFlowClassEntry 2 }

		
		-- 1.3.6.1.4.1.6296.102.7.2.5.4.2.1.1.3
		sleV2Security4ACLPolicyFlowClassID OBJECT-TYPE
			SYNTAX IntFlowIndex
			MAX-ACCESS read-only
			STATUS current
			DESCRIPTION
				"The identifier of class or flow"
			::= { sleV2Security4ACLPolicyFlowClassEntry 3 }

		
		-- 1.3.6.1.4.1.6296.102.7.2.5.4.2.1.1.4
		sleV2Security4ACLPolicyFlowClassName OBJECT-TYPE
			SYNTAX OctetName
			MAX-ACCESS read-only
			STATUS current
			DESCRIPTION
				"The name of class or flow"
			::= { sleV2Security4ACLPolicyFlowClassEntry 4 }

		
		-- 1.3.6.1.4.1.6296.102.7.2.5.4.2.2
		sleV2Security4ACLPolicyFlowClassControl OBJECT IDENTIFIER ::= { sleV2Security4ACLPolicyFlowClass 2 }

		
		-- 1.3.6.1.4.1.6296.102.7.2.5.4.2.2.1
		sleV2Security4ACLPolicyFlowClassControlRequest OBJECT-TYPE
			SYNTAX INTEGER
				{
				addFlowClass(1),
				deleteFlowClass(2),
				deleteAllFlow(3),
				deleteAllClass(4),
				deleteAllFlowClass(5)
				}
			MAX-ACCESS read-write
			STATUS current
			DESCRIPTION
				"The request of a user command"
			::= { sleV2Security4ACLPolicyFlowClassControl 1 }

		
		-- 1.3.6.1.4.1.6296.102.7.2.5.4.2.2.2
		sleV2Security4ACLPolicyFlowClassControlStatus OBJECT-TYPE
			SYNTAX SleControlStatusType
			MAX-ACCESS read-write
			STATUS current
			DESCRIPTION
				"The status of user command"
			::= { sleV2Security4ACLPolicyFlowClassControl 2 }

		
		-- 1.3.6.1.4.1.6296.102.7.2.5.4.2.2.3
		sleV2Security4ACLPolicyFlowClassControlTimer OBJECT-TYPE
			SYNTAX Gauge32
			MAX-ACCESS read-write
			STATUS current
			DESCRIPTION
				"The maximum time for the manager for a long running user command"
			::= { sleV2Security4ACLPolicyFlowClassControl 3 }

		
		-- 1.3.6.1.4.1.6296.102.7.2.5.4.2.2.4
		sleV2Security4ACLPolicyFlowClassControlTimeStamp OBJECT-TYPE
			SYNTAX TimeTicks
			MAX-ACCESS read-write
			STATUS current
			DESCRIPTION
				"The time stamp of the last command(end of command)"
			::= { sleV2Security4ACLPolicyFlowClassControl 4 }

		
		-- 1.3.6.1.4.1.6296.102.7.2.5.4.2.2.5
		sleV2Security4ACLPolicyFlowClassControlReqResult OBJECT-TYPE
			SYNTAX SleControlRequestResultType
			MAX-ACCESS read-write
			STATUS current
			DESCRIPTION
				"The result of the last user command"
			::= { sleV2Security4ACLPolicyFlowClassControl 5 }

		
		-- 1.3.6.1.4.1.6296.102.7.2.5.4.2.2.6
		sleV2Security4ACLPolicyFlowClassControlPolicyIndex OBJECT-TYPE
			SYNTAX IntPolicyIndex
			MAX-ACCESS read-write
			STATUS current
			DESCRIPTION
				"The index of Policy"
			::= { sleV2Security4ACLPolicyFlowClassControl 6 }

		
		-- 1.3.6.1.4.1.6296.102.7.2.5.4.2.2.7
		sleV2Security4ACLPolicyFlowClassControlIndex OBJECT-TYPE
			SYNTAX IntFlowIndex
			MAX-ACCESS read-write
			STATUS current
			DESCRIPTION
				"The index of flow or class in this policy"
			::= { sleV2Security4ACLPolicyFlowClassControl 7 }

		
		-- 1.3.6.1.4.1.6296.102.7.2.5.4.2.2.8
		sleV2Security4ACLPolicyFlowClassControlType OBJECT-TYPE
			SYNTAX IntFlowOrClass
			MAX-ACCESS read-write
			STATUS current
			DESCRIPTION
				"The type of flow or class"
			::= { sleV2Security4ACLPolicyFlowClassControl 8 }

		
		-- 1.3.6.1.4.1.6296.102.7.2.5.4.2.2.9
		sleV2Security4ACLPolicyFlowClassControlFlowID OBJECT-TYPE
			SYNTAX IntFlowIndex
			MAX-ACCESS read-write
			STATUS current
			DESCRIPTION
				"The index of flow
				Available according to sleV2QoS4PolicyFlowClassControlType.
				"
			::= { sleV2Security4ACLPolicyFlowClassControl 9 }

		
		-- 1.3.6.1.4.1.6296.102.7.2.5.4.2.2.10
		sleV2Security4ACLPolicyFlowClassControlClassID OBJECT-TYPE
			SYNTAX IntClassIndex
			MAX-ACCESS read-write
			STATUS current
			DESCRIPTION
				"The index of class
				Available according to sleV2QoS4PolicyFlowClassControlType.
				"
			::= { sleV2Security4ACLPolicyFlowClassControl 10 }

		
		-- 1.3.6.1.4.1.6296.102.7.2.5.4.2.3
		sleV2Security4ACLPolicyFlowClassNotification OBJECT IDENTIFIER ::= { sleV2Security4ACLPolicyFlowClass 3 }

		
		-- 1.3.6.1.4.1.6296.102.7.2.5.4.2.3.1
		sleACLPolicyFlowAdded NOTIFICATION-TYPE
			OBJECTS { sleV2Security4ACLPolicyFlowClassControlRequest, sleV2Security4ACLPolicyFlowClassControlTimeStamp, sleV2Security4ACLPolicyFlowClassControlReqResult, sleV2Security4ACLPolicyFlowClassType, sleV2Security4ACLPolicyFlowClassID
				 }
			STATUS current
			DESCRIPTION 
				"Description."
			::= { sleV2Security4ACLPolicyFlowClassNotification 1 }

		
		-- 1.3.6.1.4.1.6296.102.7.2.5.4.2.3.2
		sleACLPolicyFlowDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex, sleV2Security4ACLPolicyFlowClassControlIndex
				 }
			STATUS current
			DESCRIPTION 
				"Description."
			::= { sleV2Security4ACLPolicyFlowClassNotification 2 }

		
		-- 1.3.6.1.4.1.6296.102.7.2.5.4.2.3.3
		sleACLPolicyAllFlowDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex }
			STATUS current
			DESCRIPTION 
				"Description."
			::= { sleV2Security4ACLPolicyFlowClassNotification 3 }

		
		-- 1.3.6.1.4.1.6296.102.7.2.5.4.2.3.4
		sleACLPolicyAllClassDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex }
			STATUS current
			DESCRIPTION 
				"Description."
			::= { sleV2Security4ACLPolicyFlowClassNotification 4 }

		
		-- 1.3.6.1.4.1.6296.102.7.2.5.4.2.3.5
		sleACLPolicyAllFlowClassDeleted NOTIFICATION-TYPE
			OBJECTS { sleV2Security4ACLPolicyFlowClassControlRequest, sleV2Security4ACLPolicyFlowClassControlTimeStamp, sleV2Security4ACLPolicyFlowClassControlReqResult, sleV2Security4ACLPolicyFlowClassControlPolicyIndex }
			STATUS current
			DESCRIPTION 
				"Description."
			::= { sleV2Security4ACLPolicyFlowClassNotification 5 }

		
		-- 1.3.6.1.4.1.6296.102.7.2.5.5
		sleV2Security4ACLGroup OBJECT IDENTIFIER ::= { sleV2SecurityACL 5 }

		
		-- 1.3.6.1.4.1.6296.102.7.2.5.5.1
		sleV2Security4ACLGroupIf OBJECT IDENTIFIER ::= { sleV2Security4ACLGroup 1 }

		
		-- 1.3.6.1.4.1.6296.102.7.2.5.5.1.1
		sleV2Security4ACLGroupIfTable OBJECT-TYPE
			SYNTAX SEQUENCE OF SleV2Security4ACLGroupIfEntry
			MAX-ACCESS not-accessible
			STATUS current
			DESCRIPTION
				"Description."
			::= { sleV2Security4ACLGroupIf 1 }

		
		-- 1.3.6.1.4.1.6296.102.7.2.5.5.1.1.1
		sleV2Security4ACLGroupIfEntry OBJECT-TYPE
			SYNTAX SleV2Security4ACLGroupIfEntry
			MAX-ACCESS not-accessible
			STATUS current
			DESCRIPTION
				"Description."
			INDEX { sleV2Security4ACLGroupIfindex, sleV2Security4ACLGroupIfType }
			::= { sleV2Security4ACLGroupIfTable 1 }

		
		SleV2Security4ACLGroupIfEntry ::=
			SEQUENCE { 
				sleV2Security4ACLGroupIfindex
					Integer32,
				sleV2Security4ACLGroupIfType
					INTEGER,
				sleV2Security4ACLGroupIfName
					OCTET STRING,
				sleV2Security4ACLGroupIfPriority
					INTEGER
			 }

		-- 1.3.6.1.4.1.6296.102.7.2.5.5.1.1.1.1
		sleV2Security4ACLGroupIfindex OBJECT-TYPE
			SYNTAX Integer32 (1..65535)
			MAX-ACCESS read-only
			STATUS current
			DESCRIPTION
				"interface index"
			::= { sleV2Security4ACLGroupIfEntry 1 }

		
		-- 1.3.6.1.4.1.6296.102.7.2.5.5.1.1.1.2
		sleV2Security4ACLGroupIfType OBJECT-TYPE
			SYNTAX INTEGER
				{
				ip(3),
				mac(4)
				}
			MAX-ACCESS read-only
			STATUS current
			DESCRIPTION
				"The access-list type"
			::= { sleV2Security4ACLGroupIfEntry 2 }

		
		-- 1.3.6.1.4.1.6296.102.7.2.5.5.1.1.1.3
		sleV2Security4ACLGroupIfName OBJECT-TYPE
			SYNTAX OCTET STRING
			MAX-ACCESS read-only
			STATUS current
			DESCRIPTION
				"The access-list name"
			::= { sleV2Security4ACLGroupIfEntry 3 }

		
		-- 1.3.6.1.4.1.6296.102.7.2.5.5.1.1.1.4
		sleV2Security4ACLGroupIfPriority OBJECT-TYPE
			SYNTAX INTEGER
				{
				low(1),
				medium(2),
				high(3),
				highest(4)
				}
			MAX-ACCESS read-only
			STATUS current
			DESCRIPTION
				"The policy priority"
			::= { sleV2Security4ACLGroupIfEntry 4 }

		
		-- 1.3.6.1.4.1.6296.102.7.2.5.5.1.2
		sleV2Security4ACLGroupIfControl OBJECT IDENTIFIER ::= { sleV2Security4ACLGroupIf 2 }

		
		-- 1.3.6.1.4.1.6296.102.7.2.5.5.1.2.1
		sleV2Security4ACLGroupIfControlRequest OBJECT-TYPE
			SYNTAX INTEGER
				{
				setSecurityAclGroupIfProfile(1),
				delSecurityAclGroupIfProfile(2)
				}
			MAX-ACCESS read-write
			STATUS current
			DESCRIPTION
				"The request of a user command"
			::= { sleV2Security4ACLGroupIfControl 1 }

		
		-- 1.3.6.1.4.1.6296.102.7.2.5.5.1.2.2
		sleV2Security4ACLGroupIfControlStatus OBJECT-TYPE
			SYNTAX SleControlStatusType
			MAX-ACCESS read-write
			STATUS current
			DESCRIPTION
				"The status of user command"
			::= { sleV2Security4ACLGroupIfControl 2 }

		
		-- 1.3.6.1.4.1.6296.102.7.2.5.5.1.2.3
		sleV2Security4ACLGroupIfControlTimer OBJECT-TYPE
			SYNTAX Gauge32
			MAX-ACCESS read-write
			STATUS current
			DESCRIPTION
				"The maximum time for the manager for a long running user command"
			::= { sleV2Security4ACLGroupIfControl 3 }

		
		-- 1.3.6.1.4.1.6296.102.7.2.5.5.1.2.4
		sleV2Security4ACLGroupIfControlReqResult OBJECT-TYPE
			SYNTAX TimeTicks
			MAX-ACCESS read-write
			STATUS current
			DESCRIPTION
				"The time stamp of the last command(end of command)"
			::= { sleV2Security4ACLGroupIfControl 4 }

		
		-- 1.3.6.1.4.1.6296.102.7.2.5.5.1.2.5
		sleV2Security4ACLGroupIfControlTimeStamp OBJECT-TYPE
			SYNTAX SleControlRequestResultType
			MAX-ACCESS read-write
			STATUS current
			DESCRIPTION
				"The result of the last user command"
			::= { sleV2Security4ACLGroupIfControl 5 }

		
		-- 1.3.6.1.4.1.6296.102.7.2.5.5.1.2.6
		sleV2Security4ACLGroupIfConrolIndex OBJECT-TYPE
			SYNTAX Integer32
			MAX-ACCESS read-write
			STATUS current
			DESCRIPTION
				"interface index"
			::= { sleV2Security4ACLGroupIfControl 6 }

		
		-- 1.3.6.1.4.1.6296.102.7.2.5.5.1.2.7
		sleV2Security4ACLGroupIfControlType OBJECT-TYPE
			SYNTAX INTEGER
				{
				ip(3),
				mac(4)
				}
			MAX-ACCESS read-write
			STATUS current
			DESCRIPTION
				"The access-list type"
			::= { sleV2Security4ACLGroupIfControl 7 }

		
		-- 1.3.6.1.4.1.6296.102.7.2.5.5.1.2.8
		sleV2Security4ACLGroupIfControlName OBJECT-TYPE
			SYNTAX OCTET STRING
			MAX-ACCESS read-write
			STATUS current
			DESCRIPTION
				"The access-list name"
			::= { sleV2Security4ACLGroupIfControl 8 }

		
		-- 1.3.6.1.4.1.6296.102.7.2.5.5.1.2.9
		sleV2Security4ACLGroupIfControlPriority OBJECT-TYPE
			SYNTAX INTEGER
				{
				low(1),
				medium(2),
				high(3),
				highest(4)
				}
			MAX-ACCESS read-write
			STATUS current
			DESCRIPTION
				"Integer
				1: low(1)
				2: medium(2)
				3: high(3)
				4: highest(4)	The policy priority
				"
			::= { sleV2Security4ACLGroupIfControl 9 }

		
		-- 1.3.6.1.4.1.6296.102.7.2.5.5.1.3
		sleV2SecurityACLGroupIfNotification OBJECT IDENTIFIER ::= { sleV2Security4ACLGroupIf 3 }

		
		-- 1.3.6.1.4.1.6296.102.7.2.5.5.1.3.1
		sleV2Security4ACLGroupIfProfileAdd NOTIFICATION-TYPE
			OBJECTS { sleV2Security4ACLGroupIfControlRequest, sleV2Security4ACLGroupIfControlReqResult, sleV2Security4ACLGroupIfControlTimeStamp, sleV2Security4ACLGroupIfControlName }
			STATUS current
			DESCRIPTION 
				"setSecurityACLGroupIfProfile"
			::= { sleV2SecurityACLGroupIfNotification 1 }

		
		-- 1.3.6.1.4.1.6296.102.7.2.5.5.1.3.2
		sleV2Security4ACLGroupIfProfileDelete NOTIFICATION-TYPE
			OBJECTS { sleV2Security4ACLGroupIfControlRequest, sleV2Security4ACLGroupIfControlReqResult, sleV2Security4ACLGroupIfControlTimeStamp, sleV2Security4ACLGroupIfConrolIndex, sleV2Security4ACLGroupIfControlType
				 }
			STATUS current
			DESCRIPTION 
				"delSecurityACLGroupIfProfile"
			::= { sleV2SecurityACLGroupIfNotification 2 }

		
		-- 1.3.6.1.4.1.6296.102.7.2.6
		sleV2SecuritySACL OBJECT IDENTIFIER ::= { sleVSecurity4 6 }

		
		-- 1.3.6.1.4.1.6296.102.7.2.6.1
		sleV2SecuritySACLTable OBJECT-TYPE
			SYNTAX SEQUENCE OF SleV2SecuritySACLEntry
			MAX-ACCESS not-accessible
			STATUS current
			DESCRIPTION
				"ACL table."
			::= { sleV2SecuritySACL 1 }

		
		-- 1.3.6.1.4.1.6296.102.7.2.6.1.1
		sleV2SecuritySACLEntry OBJECT-TYPE
			SYNTAX SleV2SecuritySACLEntry
			MAX-ACCESS not-accessible
			STATUS current
			DESCRIPTION
				"key: sleV2SecuritySACLName"
			INDEX { sleV2SecuritySACLName }
			::= { sleV2SecuritySACLTable 1 }

		
		SleV2SecuritySACLEntry ::=
			SEQUENCE { 
				sleV2SecuritySACLName
					OctetName,
				sleV2SecuritySACLSrcIpaddr
					IpAddress,
				sleV2SecuritySACLSrcPrefixLength
					Integer32,
				sleV2SecuritySACLDstIpAddr
					IpAddress,
				sleV2SecuritySACLDstPrefixLength
					Integer32,
				sleV2SecuritySACLProtocolType
					IntProtocolType,
				sleV2SecuritySACLTcpflag
					BITS,
				sleV2SecuritySACLSrcL4Port
					IntL4Port,
				sleV2SecuritySACLDstL4Port
					IntL4Port,
				sleV2SecuritySACLIcmpType
					IntProtocolType,
				sleV2SecuritySACLIcmpCode
					IntProtocolType,
				sleV2SecuritySACLPriority
					INTEGER,
				sleV2SecuritySACLMatchAction
					INTEGER,
				sleV2SecuritySACLNomatchAction
					INTEGER
			 }

		-- 1.3.6.1.4.1.6296.102.7.2.6.1.1.1
		sleV2SecuritySACLName OBJECT-TYPE
			SYNTAX OctetName
			MAX-ACCESS read-only
			STATUS current
			DESCRIPTION
				"Name of this ACL rule"
			::= { sleV2SecuritySACLEntry 1 }

		
		-- 1.3.6.1.4.1.6296.102.7.2.6.1.1.2
		sleV2SecuritySACLSrcIpaddr OBJECT-TYPE
			SYNTAX IpAddress
			MAX-ACCESS read-only
			STATUS current
			DESCRIPTION
				"The IP address to match against the packet¡¯s source IP address"
			::= { sleV2SecuritySACLEntry 2 }

		
		-- 1.3.6.1.4.1.6296.102.7.2.6.1.1.3
		sleV2SecuritySACLSrcPrefixLength OBJECT-TYPE
			SYNTAX Integer32 (0..32)
			MAX-ACCESS read-only
			STATUS current
			DESCRIPTION
				"Subnet mask."
			::= { sleV2SecuritySACLEntry 3 }

		
		-- 1.3.6.1.4.1.6296.102.7.2.6.1.1.4
		sleV2SecuritySACLDstIpAddr OBJECT-TYPE
			SYNTAX IpAddress
			MAX-ACCESS read-only
			STATUS current
			DESCRIPTION
				"The IP address to match against the packet¡¯s destination IP address"
			::= { sleV2SecuritySACLEntry 4 }

		
		-- 1.3.6.1.4.1.6296.102.7.2.6.1.1.5
		sleV2SecuritySACLDstPrefixLength OBJECT-TYPE
			SYNTAX Integer32 (0..32)
			MAX-ACCESS read-only
			STATUS current
			DESCRIPTION
				"Subnet mask."
			::= { sleV2SecuritySACLEntry 5 }

		
		-- 1.3.6.1.4.1.6296.102.7.2.6.1.1.6
		sleV2SecuritySACLProtocolType OBJECT-TYPE
			SYNTAX IntProtocolType
			MAX-ACCESS read-only
			STATUS current
			DESCRIPTION
				"The type of IP protocol
				 	The flat internet protocol is from sleV2SecuritySACLTcpflag to sleV2SecuritySACLIcmpCode
				 	If the value is tcp(6) or udp(17),
				 	From sleV2SecuritySACLTcpflag to sleV2SecuritySACLDstL4Port value is available
				 	If the value is icmp(1),
				 	The value of sleV2SecuritySACLIcmpType and sleV2SecuritySACLIcmpCode is available
				 	The value of -1 means any(not set)
				"
			::= { sleV2SecuritySACLEntry 6 }

		
		-- 1.3.6.1.4.1.6296.102.7.2.6.1.1.7
		sleV2SecuritySACLTcpflag OBJECT-TYPE
			SYNTAX BITS
				{
				reserv(0),
				reserv1(1),
				urg(2),
				ack(3),
				psh(4),
				rst(5),
				syn(6),
				fin(7)
				}
			MAX-ACCESS read-only
			STATUS current
			DESCRIPTION
				"TCP flag"
			::= { sleV2SecuritySACLEntry 7 }

		
		-- 1.3.6.1.4.1.6296.102.7.2.6.1.1.8
		sleV2SecuritySACLSrcL4Port OBJECT-TYPE
			SYNTAX IntL4Port
			MAX-ACCESS read-only
			STATUS current
			DESCRIPTION
				"The source service port number (only valid for TCP or UDP packet).."
			::= { sleV2SecuritySACLEntry 8 }

		
		-- 1.3.6.1.4.1.6296.102.7.2.6.1.1.9
		sleV2SecuritySACLDstL4Port OBJECT-TYPE
			SYNTAX IntL4Port
			MAX-ACCESS read-only
			STATUS current
			DESCRIPTION
				"The destination service port number (only valid for TCP or UDP packet). "
			::= { sleV2SecuritySACLEntry 9 }

		
		-- 1.3.6.1.4.1.6296.102.7.2.6.1.1.10
		sleV2SecuritySACLIcmpType OBJECT-TYPE
			SYNTAX IntProtocolType
			MAX-ACCESS read-only
			STATUS current
			DESCRIPTION
				"The Type of ICMP message
				The value of -1 means any(not set)"
			::= { sleV2SecuritySACLEntry 10 }

		
		-- 1.3.6.1.4.1.6296.102.7.2.6.1.1.11
		sleV2SecuritySACLIcmpCode OBJECT-TYPE
			SYNTAX IntProtocolType
			MAX-ACCESS read-only
			STATUS current
			DESCRIPTION
				"The code of ICMP message
				The value of -1 means any(not set)"
			::= { sleV2SecuritySACLEntry 11 }

		
		-- 1.3.6.1.4.1.6296.102.7.2.6.1.1.12
		sleV2SecuritySACLPriority OBJECT-TYPE
			SYNTAX INTEGER
				{
				low(1),
				medium(2),
				high(3),
				highest(4)
				}
			MAX-ACCESS read-only
			STATUS current
			DESCRIPTION
				"The type of ICMP message
				The value of -1 means any(not set)
				"
			::= { sleV2SecuritySACLEntry 12 }

		
		-- 1.3.6.1.4.1.6296.102.7.2.6.1.1.13
		sleV2SecuritySACLMatchAction OBJECT-TYPE
			SYNTAX INTEGER
				{
				none(0),
				permit(1),
				deny(2)
				}
			MAX-ACCESS read-only
			STATUS current
			DESCRIPTION
				"Action for packets that match against this ACL rule."
			::= { sleV2SecuritySACLEntry 13 }

		
		-- 1.3.6.1.4.1.6296.102.7.2.6.1.1.14
		sleV2SecuritySACLNomatchAction OBJECT-TYPE
			SYNTAX INTEGER
				{
				none(0),
				permit(1),
				deny(2)
				}
			MAX-ACCESS read-only
			STATUS current
			DESCRIPTION
				"Action for packets that don¡¯t match against this ACL rule."
			::= { sleV2SecuritySACLEntry 14 }

		
		-- 1.3.6.1.4.1.6296.102.7.2.6.2
		sleV2SecuritySACLControl OBJECT IDENTIFIER ::= { sleV2SecuritySACL 2 }

		
		-- 1.3.6.1.4.1.6296.102.7.2.6.2.1
		sleV2SecuritySACLControlRequest OBJECT-TYPE
			SYNTAX INTEGER
				{
				createSAclRule(1),
				destroySAclRule(2),
				destroyAllSAclRule(3)
				}
			MAX-ACCESS read-write
			STATUS current
			DESCRIPTION
				"The request of a user command"
			::= { sleV2SecuritySACLControl 1 }

		
		-- 1.3.6.1.4.1.6296.102.7.2.6.2.2
		sleV2SecuritySACLControlStatus OBJECT-TYPE
			SYNTAX SleControlStatusType
			MAX-ACCESS read-only
			STATUS current
			DESCRIPTION
				"The status of user command"
			::= { sleV2SecuritySACLControl 2 }

		
		-- 1.3.6.1.4.1.6296.102.7.2.6.2.3
		sleV2SecuritySACLControlTimer OBJECT-TYPE
			SYNTAX Gauge32
			MAX-ACCESS read-write
			STATUS current
			DESCRIPTION
				"The maximum time for the manager for a long running user command"
			::= { sleV2SecuritySACLControl 3 }

		
		-- 1.3.6.1.4.1.6296.102.7.2.6.2.4
		sleV2SecuritySACLControlTimeStamp OBJECT-TYPE
			SYNTAX TimeStamp
			MAX-ACCESS read-only
			STATUS current
			DESCRIPTION
				"The time stamp of the last command(end of command)"
			::= { sleV2SecuritySACLControl 4 }

		
		-- 1.3.6.1.4.1.6296.102.7.2.6.2.5
		sleV2SecuritySACLControlReqResult OBJECT-TYPE
			SYNTAX SleControlRequestResultType
			MAX-ACCESS read-only
			STATUS current
			DESCRIPTION
				"The result of the last user command"
			::= { sleV2SecuritySACLControl 5 }

		
		-- 1.3.6.1.4.1.6296.102.7.2.6.2.6
		sleV2SecuritySACLControlName OBJECT-TYPE
			SYNTAX OctetName
			MAX-ACCESS read-write
			STATUS current
			DESCRIPTION
				"Name of this ACL rule"
			::= { sleV2SecuritySACLControl 6 }

		
		-- 1.3.6.1.4.1.6296.102.7.2.6.2.7
		sleV2SecuritySACLControlSrcIpaddr OBJECT-TYPE
			SYNTAX IpAddress
			MAX-ACCESS read-write
			STATUS current
			DESCRIPTION
				"The IP address to match against the packet¡¯s source IP address"
			::= { sleV2SecuritySACLControl 7 }

		
		-- 1.3.6.1.4.1.6296.102.7.2.6.2.8
		sleV2SecuritySACLControlSrcPrefixLength OBJECT-TYPE
			SYNTAX IntIpAddrMask
			MAX-ACCESS read-write
			STATUS current
			DESCRIPTION
				"Subnet mask."
			::= { sleV2SecuritySACLControl 8 }

		
		-- 1.3.6.1.4.1.6296.102.7.2.6.2.9
		sleV2SecuritySACLControlDstIpaddr OBJECT-TYPE
			SYNTAX IpAddress
			MAX-ACCESS read-write
			STATUS current
			DESCRIPTION
				"The IP address to match against the packet¡¯s destination IP address"
			::= { sleV2SecuritySACLControl 9 }

		
		-- 1.3.6.1.4.1.6296.102.7.2.6.2.10
		sleV2SecuritySACLControlDstPrefixLength OBJECT-TYPE
			SYNTAX IntIpAddrMask
			MAX-ACCESS read-write
			STATUS current
			DESCRIPTION
				"Subnet mask."
			::= { sleV2SecuritySACLControl 10 }

		
		-- 1.3.6.1.4.1.6296.102.7.2.6.2.11
		sleV2SecuritySACLControlProtocolType OBJECT-TYPE
			SYNTAX IntProtocolType
			MAX-ACCESS read-write
			STATUS current
			DESCRIPTION
				"The IP protocol type value"
			::= { sleV2SecuritySACLControl 11 }

		
		-- 1.3.6.1.4.1.6296.102.7.2.6.2.12
		sleV2SecuritySACLControlTcpflag OBJECT-TYPE
			SYNTAX BITS
				{
				reserv(0),
				reserv1(1),
				urg(2),
				ack(3),
				psh(4),
				rst(5),
				syn(6),
				fin(7)
				}
			MAX-ACCESS read-write
			STATUS current
			DESCRIPTION
				"TCP flag"
			::= { sleV2SecuritySACLControl 12 }

		
		-- 1.3.6.1.4.1.6296.102.7.2.6.2.13
		sleV2SecuritySACLControlSrcL4Port OBJECT-TYPE
			SYNTAX IntL4Port
			MAX-ACCESS read-write
			STATUS current
			DESCRIPTION
				"The source service port number (only valid for TCP or UDP packet).."
			::= { sleV2SecuritySACLControl 13 }

		
		-- 1.3.6.1.4.1.6296.102.7.2.6.2.14
		sleV2SecuritySACLControlDstL4Port OBJECT-TYPE
			SYNTAX IntL4Port
			MAX-ACCESS read-write
			STATUS current
			DESCRIPTION
				"The destination service port number (only valid for TCP or UDP packet). "
			::= { sleV2SecuritySACLControl 14 }

		
		-- 1.3.6.1.4.1.6296.102.7.2.6.2.15
		sleV2SecuritySACLControlIcmpType OBJECT-TYPE
			SYNTAX IntProtocolType
			MAX-ACCESS read-write
			STATUS current
			DESCRIPTION
				"The type of ICMP message
				The value of -1 means any(not set)
				"
			::= { sleV2SecuritySACLControl 15 }

		
		-- 1.3.6.1.4.1.6296.102.7.2.6.2.16
		sleV2SecuritySACLControlIcmpCode OBJECT-TYPE
			SYNTAX IntProtocolType
			MAX-ACCESS read-write
			STATUS current
			DESCRIPTION
				"The code of ICMP message
				The value of -1 means any(not set)
				"
			::= { sleV2SecuritySACLControl 16 }

		
		-- 1.3.6.1.4.1.6296.102.7.2.6.2.17
		sleV2SecuritySACLControlPriority OBJECT-TYPE
			SYNTAX INTEGER
				{
				low(1),
				medium(2),
				high(3),
				highest(4)
				}
			MAX-ACCESS read-write
			STATUS current
			DESCRIPTION
				"The Priority of this ACL rule)"
			::= { sleV2SecuritySACLControl 17 }

		
		-- 1.3.6.1.4.1.6296.102.7.2.6.2.18
		sleV2SecuritySACLControlMatchAction OBJECT-TYPE
			SYNTAX INTEGER
				{
				none(0),
				permit(1),
				deny(2)
				}
			MAX-ACCESS read-write
			STATUS current
			DESCRIPTION
				"Action for packets that match against this ACL rule."
			::= { sleV2SecuritySACLControl 18 }

		
		-- 1.3.6.1.4.1.6296.102.7.2.6.2.19
		sleV2SecuritySACLControlNomatchAction OBJECT-TYPE
			SYNTAX INTEGER
				{
				none(0),
				permit(1),
				deny(2)
				}
			MAX-ACCESS read-write
			STATUS current
			DESCRIPTION
				"Action for packets that don¡¯t match against this ACL rule."
			::= { sleV2SecuritySACLControl 19 }

		
		-- 1.3.6.1.4.1.6296.102.7.2.6.3
		sleV2SecuritySACLNotification OBJECT IDENTIFIER ::= { sleV2SecuritySACL 3 }

		
		-- 1.3.6.1.4.1.6296.102.7.2.6.3.1
		sleSACLCreated NOTIFICATION-TYPE
			OBJECTS { sleV2SecuritySACLControlRequest, sleV2SecuritySACLControlTimeStamp, sleV2SecuritySACLControlReqResult, sleV2SecuritySACLSrcIpaddr, sleV2SecuritySACLSrcPrefixLength, 
				sleV2SecuritySACLDstIpAddr, sleV2SecuritySACLDstPrefixLength, sleV2SecuritySACLProtocolType, sleV2SecuritySACLTcpflag, sleV2SecuritySACLIcmpType, 
				sleV2SecuritySACLIcmpCode, sleV2SecuritySACLPriority, sleV2SecuritySACLMatchAction, sleV2SecuritySACLNomatchAction, sleV2SecuritySACLSrcL4Port, 
				sleV2SecuritySACLDstL4Port }
			STATUS current
			DESCRIPTION 
				"Description."
			::= { sleV2SecuritySACLNotification 1 }

		
		-- 1.3.6.1.4.1.6296.102.7.2.6.3.2
		sleSACLDestroyed NOTIFICATION-TYPE
			OBJECTS { sleV2SecuritySACLControlRequest, sleV2SecuritySACLControlTimeStamp, sleV2SecuritySACLControlName, sleV2SecuritySACLControlReqResult }
			STATUS current
			DESCRIPTION 
				"Description."
			::= { sleV2SecuritySACLNotification 2 }

		
		-- 1.3.6.1.4.1.6296.102.7.2.6.3.3
		sleSACLAllDestroyed NOTIFICATION-TYPE
			OBJECTS { sleV2SecuritySACLControlRequest, sleV2SecuritySACLControlTimeStamp, sleV2SecuritySACLControlReqResult }
			STATUS current
			DESCRIPTION 
				"Description."
			::= { sleV2SecuritySACLNotification 3 }

		
		-- 1.3.6.1.4.1.6296.102.7.2.7
		sleV2SecurityACLStatistics OBJECT IDENTIFIER ::= { sleVSecurity4 7 }

		
		-- 1.3.6.1.4.1.6296.102.7.2.7.1
		sleV2SecurityACLStatisticsBase OBJECT IDENTIFIER ::= { sleV2SecurityACLStatistics 1 }

		
		-- 1.3.6.1.4.1.6296.102.7.2.7.1.1
		sleV2SecurityACLStatisticsBaseInfo OBJECT IDENTIFIER ::= { sleV2SecurityACLStatisticsBase 1 }

		
		-- 1.3.6.1.4.1.6296.102.7.2.7.1.1.1
		sleV2SecurityACLStatisticsSyslogStatus OBJECT-TYPE
			SYNTAX INTEGER
				{
				enable(1),
				disable(2)
				}
			MAX-ACCESS read-only
			STATUS current
			DESCRIPTION
				"ACL statistics syslog status"
			::= { sleV2SecurityACLStatisticsBaseInfo 1 }

		
		-- 1.3.6.1.4.1.6296.102.7.2.7.1.2
		sleV2SecurityACLStatisticsBaseControl OBJECT IDENTIFIER ::= { sleV2SecurityACLStatisticsBase 2 }

		
		-- 1.3.6.1.4.1.6296.102.7.2.7.1.2.1
		sleV2SecurityACLStatisticsBaseControlRequest OBJECT-TYPE
			SYNTAX INTEGER { aclSyslogModeChange(1) }
			MAX-ACCESS read-write
			STATUS current
			DESCRIPTION
				"The request of a user command"
			::= { sleV2SecurityACLStatisticsBaseControl 1 }

		
		-- 1.3.6.1.4.1.6296.102.7.2.7.1.2.2
		sleV2SecurityACLStatisticsBaseControlStatus OBJECT-TYPE
			SYNTAX SleControlStatusType
			MAX-ACCESS read-only
			STATUS current
			DESCRIPTION
				"The status of user command"
			::= { sleV2SecurityACLStatisticsBaseControl 2 }

		
		-- 1.3.6.1.4.1.6296.102.7.2.7.1.2.3
		sleV2SecurityACLStatisticsBaseControlTimer OBJECT-TYPE
			SYNTAX Gauge32
			MAX-ACCESS read-write
			STATUS current
			DESCRIPTION
				"The maximum time for the manager for a long running user command"
			::= { sleV2SecurityACLStatisticsBaseControl 3 }

		
		-- 1.3.6.1.4.1.6296.102.7.2.7.1.2.4
		sleV2SecurityACLStatisticsBaseControlTimeStamp OBJECT-TYPE
			SYNTAX TimeStamp
			MAX-ACCESS read-only
			STATUS current
			DESCRIPTION
				"The time stamp of the last command(end of command)"
			::= { sleV2SecurityACLStatisticsBaseControl 4 }

		
		-- 1.3.6.1.4.1.6296.102.7.2.7.1.2.5
		sleV2SecurityACLStatisticsBaseControlReqResult OBJECT-TYPE
			SYNTAX SleControlRequestResultType
			MAX-ACCESS read-only
			STATUS current
			DESCRIPTION
				"The result of the last user command"
			::= { sleV2SecurityACLStatisticsBaseControl 5 }

		
		-- 1.3.6.1.4.1.6296.102.7.2.7.1.2.6
		sleV2SecurityACLStatisticsBaseControlSyslogMode OBJECT-TYPE
			SYNTAX INTEGER
				{
				enable(1),
				disable(2)
				}
			MAX-ACCESS read-write
			STATUS current
			DESCRIPTION
				"The ACL statistics syslog mode"
			::= { sleV2SecurityACLStatisticsBaseControl 6 }

		
		-- 1.3.6.1.4.1.6296.102.7.2.7.1.3
		sleV2SecurityACLStatisticsBaseNotification OBJECT IDENTIFIER ::= { sleV2SecurityACLStatisticsBase 3 }

		
		-- 1.3.6.1.4.1.6296.102.7.2.7.1.3.1
		sleV2SecurityACLStatisticsSyslogModeChanged NOTIFICATION-TYPE
			OBJECTS { sleV2SecurityACLStatisticsBaseControlRequest, sleV2SecurityACLStatisticsBaseControlTimeStamp, sleV2SecurityACLStatisticsBaseControlReqResult, sleV2SecurityACLStatisticsBaseControlSyslogMode }
			STATUS current
			DESCRIPTION 
				"Description."
			::= { sleV2SecurityACLStatisticsBaseNotification 1 }

		
		-- 1.3.6.1.4.1.6296.102.7.2.7.2
		sleV2SecurityACLStatisticsPacketHistory OBJECT IDENTIFIER ::= { sleV2SecurityACLStatistics 2 }

		
		-- 1.3.6.1.4.1.6296.102.7.2.7.2.1
		sleV2SecurityACLPacketCountTable OBJECT-TYPE
			SYNTAX SEQUENCE OF SleV2SecurityACLPacketCountEntry
			MAX-ACCESS not-accessible
			STATUS current
			DESCRIPTION
				"ACL packet count table."
			::= { sleV2SecurityACLStatisticsPacketHistory 1 }

		
		-- 1.3.6.1.4.1.6296.102.7.2.7.2.1.1
		sleV2SecurityACLPacketCountEntry OBJECT-TYPE
			SYNTAX SleV2SecurityACLPacketCountEntry
			MAX-ACCESS not-accessible
			STATUS current
			DESCRIPTION
				"key: sleV2SecuritySACLName"
			INDEX { sleV2SecuritySACLName }
			::= { sleV2SecurityACLPacketCountTable 1 }

		
		SleV2SecurityACLPacketCountEntry ::=
			SEQUENCE { 
				sleV2SecurityACLTotalPacket
					Counter64
			 }

		-- 1.3.6.1.4.1.6296.102.7.2.7.2.1.1.1
		sleV2SecurityACLTotalPacket OBJECT-TYPE
			SYNTAX Counter64
			MAX-ACCESS read-only
			STATUS current
			DESCRIPTION
				"ACL total packet"
			::= { sleV2SecurityACLPacketCountEntry 1 }

		
		-- 1.3.6.1.4.1.6296.102.7.2.7.2.2
		sleV2SecurityACLSrcHistoryTable OBJECT-TYPE
			SYNTAX SEQUENCE OF SleV2SecurityACLSrcHistoryEntry
			MAX-ACCESS not-accessible
			STATUS current
			DESCRIPTION
				"ACL source history table."
			::= { sleV2SecurityACLStatisticsPacketHistory 2 }

		
		-- 1.3.6.1.4.1.6296.102.7.2.7.2.2.1
		sleV2SecurityACLSrcHistoryEntry OBJECT-TYPE
			SYNTAX SleV2SecurityACLSrcHistoryEntry
			MAX-ACCESS not-accessible
			STATUS current
			DESCRIPTION
				"key: sleV2SecuritySACLName, sleV2SecurityACLSrcHistoryIndex"
			INDEX { sleV2SecuritySACLName, sleV2SecurityACLSrcHistoryIndex }
			::= { sleV2SecurityACLSrcHistoryTable 1 }

		
		SleV2SecurityACLSrcHistoryEntry ::=
			SEQUENCE { 
				sleV2SecurityACLSrcHistoryIndex
					Integer32,
				sleV2SecurityACLSrcHistoryIpAddr
					IpAddress
			 }

		-- 1.3.6.1.4.1.6296.102.7.2.7.2.2.1.1
		sleV2SecurityACLSrcHistoryIndex OBJECT-TYPE
			SYNTAX Integer32 (1..1024)
			MAX-ACCESS read-only
			STATUS current
			DESCRIPTION
				"The ACL index."
			::= { sleV2SecurityACLSrcHistoryEntry 1 }

		
		-- 1.3.6.1.4.1.6296.102.7.2.7.2.2.1.2
		sleV2SecurityACLSrcHistoryIpAddr OBJECT-TYPE
			SYNTAX IpAddress
			MAX-ACCESS read-only
			STATUS current
			DESCRIPTION
				"The ACl IP address"
			::= { sleV2SecurityACLSrcHistoryEntry 2 }

		
		-- 1.3.6.1.4.1.6296.102.7.2.7.2.3
		sleV2SecurityACLStatisticsControl OBJECT IDENTIFIER ::= { sleV2SecurityACLStatisticsPacketHistory 3 }

		
		-- 1.3.6.1.4.1.6296.102.7.2.7.2.3.1
		sleV2SecurityACLStatisticsControlRequest OBJECT-TYPE
			SYNTAX INTEGER { clearAruleStatus(1) }
			MAX-ACCESS read-write
			STATUS current
			DESCRIPTION
				"The request of a user command"
			::= { sleV2SecurityACLStatisticsControl 1 }

		
		-- 1.3.6.1.4.1.6296.102.7.2.7.2.3.2
		sleV2SecurityACLStatisticsControlStatus OBJECT-TYPE
			SYNTAX SleControlStatusType
			MAX-ACCESS read-only
			STATUS current
			DESCRIPTION
				"The status of user command"
			::= { sleV2SecurityACLStatisticsControl 2 }

		
		-- 1.3.6.1.4.1.6296.102.7.2.7.2.3.3
		sleV2SecurityACLStatisticsControlTimer OBJECT-TYPE
			SYNTAX Gauge32
			MAX-ACCESS read-write
			STATUS current
			DESCRIPTION
				"The maximum time for the manager for a long running user command"
			::= { sleV2SecurityACLStatisticsControl 3 }

		
		-- 1.3.6.1.4.1.6296.102.7.2.7.2.3.4
		sleV2SecurityACLStatisticsControlTimeStamp OBJECT-TYPE
			SYNTAX TimeStamp
			MAX-ACCESS read-only
			STATUS current
			DESCRIPTION
				"The time stamp of the last command(end of command)"
			::= { sleV2SecurityACLStatisticsControl 4 }

		
		-- 1.3.6.1.4.1.6296.102.7.2.7.2.3.5
		sleV2SecurityACLStatisticsControlReqResult OBJECT-TYPE
			SYNTAX SleControlRequestResultType
			MAX-ACCESS read-only
			STATUS current
			DESCRIPTION
				"The result of the last user command"
			::= { sleV2SecurityACLStatisticsControl 5 }

		
		-- 1.3.6.1.4.1.6296.102.7.2.7.2.3.6
		sleV2SecurityACLStatisticsControlName OBJECT-TYPE
			SYNTAX OctetName
			MAX-ACCESS read-write
			STATUS current
			DESCRIPTION
				"The ACL statistics name"
			::= { sleV2SecurityACLStatisticsControl 6 }

		
		-- 1.3.6.1.4.1.6296.102.7.2.7.2.4
		sleV2SecurityACLStatisticsNotification OBJECT IDENTIFIER ::= { sleV2SecurityACLStatisticsPacketHistory 4 }

		
		-- 1.3.6.1.4.1.6296.102.7.2.7.2.4.1
		sleV2SecurityACLStatisticsCleared NOTIFICATION-TYPE
			OBJECTS { sleV2SecurityACLStatisticsControlRequest, sleV2SecurityACLStatisticsControlTimeStamp, sleV2SecurityACLStatisticsControlReqResult, sleV2SecurityACLStatisticsControlName }
			STATUS current
			DESCRIPTION 
				"Description."
			::= { sleV2SecurityACLStatisticsNotification 1 }

		
		-- 1.3.6.1.4.1.6296.102.7.2.8
		sleV2CpuPacketFilter OBJECT IDENTIFIER ::= { sleVSecurity4 8 }

		
		-- 1.3.6.1.4.1.6296.102.7.2.8.1
		sleV2CpuPacketFilterTable OBJECT-TYPE
			SYNTAX SEQUENCE OF SleV2CpuPacketFilterEntry
			MAX-ACCESS not-accessible
			STATUS current
			DESCRIPTION
				"cpu packet filter table."
			::= { sleV2CpuPacketFilter 1 }

		
		-- 1.3.6.1.4.1.6296.102.7.2.8.1.1
		sleV2CpuPacketFilterEntry OBJECT-TYPE
			SYNTAX SleV2CpuPacketFilterEntry
			MAX-ACCESS not-accessible
			STATUS current
			DESCRIPTION
				"key: sleV2CpuPacketFilterIndex"
			INDEX { sleV2CpuPacketFilterIndex }
			::= { sleV2CpuPacketFilterTable 1 }

		
		SleV2CpuPacketFilterEntry ::=
			SEQUENCE { 
				sleV2CpuPacketFilterIndex
					Integer32,
				sleV2CpuPacketFilterName
					OCTET STRING,
				sleV2CpuPacketFilterCreationTime
					Counter32,
				sleV2CpuPacketFilterElapsedtimeAfterClear
					Counter32,
				sleV2CpuPacketFilterStage
					INTEGER,
				sleV2CpuPacketFilterPriority
					Integer32,
				sleV2CpuPacketFilterAction
					INTEGER,
				sleV2CpuPacketFilterActionRateLimit
					Integer32,
				sleV2CpuPacketFilterActionBurstSize
					Integer32,
				sleV2CpuPacketFilterActionTpid
					Integer32,
				sleV2CpuPacketFilterActionPcp
					Integer32,
				sleV2CpuPacketFilterActionVid
					Integer32,
				sleV2CpuPacketFilterActionTagPosition
					Integer32
			 }

		-- 1.3.6.1.4.1.6296.102.7.2.8.1.1.1
		sleV2CpuPacketFilterIndex OBJECT-TYPE
			SYNTAX Integer32 (1..2147483647)
			MAX-ACCESS read-only
			STATUS current
			DESCRIPTION
				"The index of cpu packet filter"
			::= { sleV2CpuPacketFilterEntry 1 }

		
		-- 1.3.6.1.4.1.6296.102.7.2.8.1.1.2
		sleV2CpuPacketFilterName OBJECT-TYPE
			SYNTAX OCTET STRING
			MAX-ACCESS read-only
			STATUS current
			DESCRIPTION
				"The name of cpu packet filter"
			::= { sleV2CpuPacketFilterEntry 2 }

		
		-- 1.3.6.1.4.1.6296.102.7.2.8.1.1.3
		sleV2CpuPacketFilterCreationTime OBJECT-TYPE
			SYNTAX Counter32
			MAX-ACCESS read-only
			STATUS current
			DESCRIPTION
				"The creation time.  (unit : sec)"
			::= { sleV2CpuPacketFilterEntry 3 }

		
		-- 1.3.6.1.4.1.6296.102.7.2.8.1.1.4
		sleV2CpuPacketFilterElapsedtimeAfterClear OBJECT-TYPE
			SYNTAX Counter32
			MAX-ACCESS read-only
			STATUS current
			DESCRIPTION
				"The elapsed time after clear   (unit : sec)"
			::= { sleV2CpuPacketFilterEntry 4 }

		
		-- 1.3.6.1.4.1.6296.102.7.2.8.1.1.5
		sleV2CpuPacketFilterStage OBJECT-TYPE
			SYNTAX INTEGER
				{
				cpuingress(1),
				cpuegress(2),
				portrx(3),
				porttx(4),
				vlanAssigned(5),
				unknown(255)
				}
			MAX-ACCESS read-only
			STATUS current
			DESCRIPTION
				"The stage of cpu packet filter."
			::= { sleV2CpuPacketFilterEntry 5 }

		
		-- 1.3.6.1.4.1.6296.102.7.2.8.1.1.6
		sleV2CpuPacketFilterPriority OBJECT-TYPE
			SYNTAX Integer32 (1..65535)
			MAX-ACCESS read-only
			STATUS current
			DESCRIPTION
				"The priority of cpu packet filter."
			::= { sleV2CpuPacketFilterEntry 6 }

		
		-- 1.3.6.1.4.1.6296.102.7.2.8.1.1.7
		sleV2CpuPacketFilterAction OBJECT-TYPE
			SYNTAX INTEGER
				{
				drop(1),
				permit(2),
				rateLimit(3),
				pass(4),
				dot1q(5),
				dot1qAttach(6),
				dot1qDetach(7),
				unknown(255)
				}
			MAX-ACCESS read-only
			STATUS current
			DESCRIPTION
				"The action to matched packet.
				Dot1q -> replace
				dot1qAttach -> add
				dot1qDettach -> remove"
			::= { sleV2CpuPacketFilterEntry 7 }

		
		-- 1.3.6.1.4.1.6296.102.7.2.8.1.1.8
		sleV2CpuPacketFilterActionRateLimit OBJECT-TYPE
			SYNTAX Integer32 (1..100)
			MAX-ACCESS read-only
			STATUS current
			DESCRIPTION
				"The allowed-packet count per second."
			::= { sleV2CpuPacketFilterEntry 8 }

		
		-- 1.3.6.1.4.1.6296.102.7.2.8.1.1.9
		sleV2CpuPacketFilterActionBurstSize OBJECT-TYPE
			SYNTAX Integer32 (1..100)
			MAX-ACCESS read-only
			STATUS current
			DESCRIPTION
				"The burst-allowed-packet count."
			::= { sleV2CpuPacketFilterEntry 9 }

		
		-- 1.3.6.1.4.1.6296.102.7.2.8.1.1.10
		sleV2CpuPacketFilterActionTpid OBJECT-TYPE
			SYNTAX Integer32 (0..65535)
			MAX-ACCESS read-only
			STATUS current
			DESCRIPTION
				"The Action TPID
				The value 65535(0xffff) means any."
			::= { sleV2CpuPacketFilterEntry 10 }

		
		-- 1.3.6.1.4.1.6296.102.7.2.8.1.1.11
		sleV2CpuPacketFilterActionPcp OBJECT-TYPE
			SYNTAX Integer32 (0..7 | 255)
			MAX-ACCESS read-only
			STATUS current
			DESCRIPTION
				"The Action PCP.
				The value 255(0xff) means any."
			::= { sleV2CpuPacketFilterEntry 11 }

		
		-- 1.3.6.1.4.1.6296.102.7.2.8.1.1.12
		sleV2CpuPacketFilterActionVid OBJECT-TYPE
			SYNTAX Integer32 (0 | 1..4094 | 65535)
			MAX-ACCESS read-only
			STATUS current
			DESCRIPTION
				"The Action VID
				The value 65535(0xffff) means any."
			::= { sleV2CpuPacketFilterEntry 12 }

		
		-- 1.3.6.1.4.1.6296.102.7.2.8.1.1.13
		sleV2CpuPacketFilterActionTagPosition OBJECT-TYPE
			SYNTAX Integer32 (0 | 1..8)
			MAX-ACCESS read-only
			STATUS current
			DESCRIPTION
				"The Action tag position.
				1 s-vlan
				2 c-vlan"
			::= { sleV2CpuPacketFilterEntry 13 }

		
		-- 1.3.6.1.4.1.6296.102.7.2.8.2
		sleV2CpuPacketFilterMatchTable OBJECT-TYPE
			SYNTAX SEQUENCE OF SleV2CpuPacketFilterMatchEntry
			MAX-ACCESS not-accessible
			STATUS current
			DESCRIPTION
				"cpu packet filter match table."
			::= { sleV2CpuPacketFilter 2 }

		
		-- 1.3.6.1.4.1.6296.102.7.2.8.2.1
		sleV2CpuPacketFilterMatchEntry OBJECT-TYPE
			SYNTAX SleV2CpuPacketFilterMatchEntry
			MAX-ACCESS not-accessible
			STATUS current
			DESCRIPTION
				"key: sleV2CpuPacketFilterIndex, sleV2CpuPacketFilterMatchIndex"
			INDEX { sleV2CpuPacketFilterIndex, sleV2CpuPacketFilterMatchIndex }
			::= { sleV2CpuPacketFilterMatchTable 1 }

		
		SleV2CpuPacketFilterMatchEntry ::=
			SEQUENCE { 
				sleV2CpuPacketFilterMatchIndex
					Integer32,
				sleV2CpuPacketFilterMatchType
					BITS,
				sleV2CpuPacketFilterMatchCos
					OCTET STRING,
				sleV2CpuPacketFilterMatchPort
					OCTET STRING,
				sleV2CpuPacketFilterMatchVidmap
					OCTET STRING,
				sleV2CpuPacketFilterMatchTagPosition
					Integer32,
				sleV2CpuPacketFilterMatchTpid
					Integer32,
				sleV2CpuPacketFilterMatchPcp
					Integer32,
				sleV2CpuPacketFilterMatchVid
					Integer32,
				sleV2CpuPacketFilterMatchOffset
					Integer32,
				sleV2CpuPacketFilterMatchLength
					Integer32,
				sleV2CpuPacketFilterMatchData
					OCTET STRING,
				sleV2CpuPacketFilterMatchMask
					OCTET STRING,
				sleV2CpuPacketFilterMatchDesc
					OCTET STRING
			 }

		-- 1.3.6.1.4.1.6296.102.7.2.8.2.1.1
		sleV2CpuPacketFilterMatchIndex OBJECT-TYPE
			SYNTAX Integer32 (1..65535)
			MAX-ACCESS read-only
			STATUS current
			DESCRIPTION
				"The match entry Index"
			::= { sleV2CpuPacketFilterMatchEntry 1 }

		
		-- 1.3.6.1.4.1.6296.102.7.2.8.2.1.2
		sleV2CpuPacketFilterMatchType OBJECT-TYPE
			SYNTAX BITS
				{
				vid(0),
				cos(1),
				port(2),
				offset(3),
				dot1q(4)
				}
			MAX-ACCESS read-only
			STATUS current
			DESCRIPTION
				"The  match classifiter type."
			::= { sleV2CpuPacketFilterMatchEntry 2 }

		
		-- 1.3.6.1.4.1.6296.102.7.2.8.2.1.3
		sleV2CpuPacketFilterMatchCos OBJECT-TYPE
			SYNTAX OCTET STRING
			MAX-ACCESS read-only
			STATUS current
			DESCRIPTION
				"The matched CoS Queue."
			::= { sleV2CpuPacketFilterMatchEntry 3 }

		
		-- 1.3.6.1.4.1.6296.102.7.2.8.2.1.4
		sleV2CpuPacketFilterMatchPort OBJECT-TYPE
			SYNTAX OCTET STRING
			MAX-ACCESS read-only
			STATUS current
			DESCRIPTION
				"The matched port index."
			::= { sleV2CpuPacketFilterMatchEntry 4 }

		
		-- 1.3.6.1.4.1.6296.102.7.2.8.2.1.5
		sleV2CpuPacketFilterMatchVidmap OBJECT-TYPE
			SYNTAX OCTET STRING
			MAX-ACCESS read-only
			STATUS current
			DESCRIPTION
				"The matched VID."
			::= { sleV2CpuPacketFilterMatchEntry 5 }

		
		-- 1.3.6.1.4.1.6296.102.7.2.8.2.1.6
		sleV2CpuPacketFilterMatchTagPosition OBJECT-TYPE
			SYNTAX Integer32 (0 | 1..8)
			MAX-ACCESS read-only
			STATUS current
			DESCRIPTION
				"The matched tag position."
			::= { sleV2CpuPacketFilterMatchEntry 6 }

		
		-- 1.3.6.1.4.1.6296.102.7.2.8.2.1.7
		sleV2CpuPacketFilterMatchTpid OBJECT-TYPE
			SYNTAX Integer32 (0..65535)
			MAX-ACCESS read-only
			STATUS current
			DESCRIPTION
				"The matched TPID."
			::= { sleV2CpuPacketFilterMatchEntry 7 }

		
		-- 1.3.6.1.4.1.6296.102.7.2.8.2.1.8
		sleV2CpuPacketFilterMatchPcp OBJECT-TYPE
			SYNTAX Integer32 (0..7 | 255)
			MAX-ACCESS read-only
			STATUS current
			DESCRIPTION
				"The matched PCP"
			::= { sleV2CpuPacketFilterMatchEntry 8 }

		
		-- 1.3.6.1.4.1.6296.102.7.2.8.2.1.9
		sleV2CpuPacketFilterMatchVid OBJECT-TYPE
			SYNTAX Integer32 (0 | 1..4094 | 65535)
			MAX-ACCESS read-only
			STATUS current
			DESCRIPTION
				"The matched VID"
			::= { sleV2CpuPacketFilterMatchEntry 9 }

		
		-- 1.3.6.1.4.1.6296.102.7.2.8.2.1.10
		sleV2CpuPacketFilterMatchOffset OBJECT-TYPE
			SYNTAX Integer32 (0..127)
			MAX-ACCESS read-only
			STATUS current
			DESCRIPTION
				"The matched offset"
			::= { sleV2CpuPacketFilterMatchEntry 10 }

		
		-- 1.3.6.1.4.1.6296.102.7.2.8.2.1.11
		sleV2CpuPacketFilterMatchLength OBJECT-TYPE
			SYNTAX Integer32 (1..16)
			MAX-ACCESS read-only
			STATUS current
			DESCRIPTION
				"The matched Length"
			::= { sleV2CpuPacketFilterMatchEntry 11 }

		
		-- 1.3.6.1.4.1.6296.102.7.2.8.2.1.12
		sleV2CpuPacketFilterMatchData OBJECT-TYPE
			SYNTAX OCTET STRING
			MAX-ACCESS read-only
			STATUS current
			DESCRIPTION
				"The matched data. (HEX string)"
			::= { sleV2CpuPacketFilterMatchEntry 12 }

		
		-- 1.3.6.1.4.1.6296.102.7.2.8.2.1.13
		sleV2CpuPacketFilterMatchMask OBJECT-TYPE
			SYNTAX OCTET STRING
			MAX-ACCESS read-only
			STATUS current
			DESCRIPTION
				"The matched mask. (HEX string)"
			::= { sleV2CpuPacketFilterMatchEntry 13 }

		
		-- 1.3.6.1.4.1.6296.102.7.2.8.2.1.14
		sleV2CpuPacketFilterMatchDesc OBJECT-TYPE
			SYNTAX OCTET STRING
			MAX-ACCESS read-only
			STATUS current
			DESCRIPTION
				"The matched Description"
			::= { sleV2CpuPacketFilterMatchEntry 14 }

		
		-- 1.3.6.1.4.1.6296.102.7.2.8.3
		sleV2CpuPacketFilterControl OBJECT IDENTIFIER ::= { sleV2CpuPacketFilter 3 }

		
		-- 1.3.6.1.4.1.6296.102.7.2.8.3.1
		sleV2CpuPacketFilterControlRequest OBJECT-TYPE
			SYNTAX INTEGER
				{
				addCpuPktFilter(1),
				delCpuPktfilter(2),
				setAction(3),
				addMatch(4),
				delMatch(5)
				}
			MAX-ACCESS read-write
			STATUS current
			DESCRIPTION
				"The request of a user command"
			::= { sleV2CpuPacketFilterControl 1 }

		
		-- 1.3.6.1.4.1.6296.102.7.2.8.3.2
		sleV2CpuPacketFilterControlStatus OBJECT-TYPE
			SYNTAX SleControlStatusType
			MAX-ACCESS read-only
			STATUS current
			DESCRIPTION
				"The status of user command"
			::= { sleV2CpuPacketFilterControl 2 }

		
		-- 1.3.6.1.4.1.6296.102.7.2.8.3.3
		sleV2CpuPacketFilterControlTimer OBJECT-TYPE
			SYNTAX Gauge32
			MAX-ACCESS read-write
			STATUS current
			DESCRIPTION
				"The maximum time for the manager for a long running user command"
			::= { sleV2CpuPacketFilterControl 3 }

		
		-- 1.3.6.1.4.1.6296.102.7.2.8.3.4
		sleV2CpuPacketFilterControlTimeStamp OBJECT-TYPE
			SYNTAX TimeStamp
			MAX-ACCESS read-only
			STATUS current
			DESCRIPTION
				"The time stamp of the last command(end of command)"
			::= { sleV2CpuPacketFilterControl 4 }

		
		-- 1.3.6.1.4.1.6296.102.7.2.8.3.5
		sleV2CpuPacketFilterControlReqResult OBJECT-TYPE
			SYNTAX SleControlRequestResultType
			MAX-ACCESS read-only
			STATUS current
			DESCRIPTION
				"The result of the last user command"
			::= { sleV2CpuPacketFilterControl 5 }

		
		-- 1.3.6.1.4.1.6296.102.7.2.8.3.6
		sleV2CpuPacketFilterControlIndex OBJECT-TYPE
			SYNTAX Integer32 (1..2147483647)
			MAX-ACCESS read-write
			STATUS current
			DESCRIPTION
				"The match entry Index"
			::= { sleV2CpuPacketFilterControl 6 }

		
		-- 1.3.6.1.4.1.6296.102.7.2.8.3.7
		sleV2CpuPacketFilterControlName OBJECT-TYPE
			SYNTAX OCTET STRING
			MAX-ACCESS read-write
			STATUS current
			DESCRIPTION
				"Cpu packet filter name."
			::= { sleV2CpuPacketFilterControl 7 }

		
		-- 1.3.6.1.4.1.6296.102.7.2.8.3.8
		sleV2CpuPacketFilterControlStage OBJECT-TYPE
			SYNTAX INTEGER
				{
				cpuingress(1),
				cpuegress(2),
				portrx(3),
				porttx(4),
				vlanAssigned(5),
				unknown(255)
				}
			MAX-ACCESS read-write
			STATUS current
			DESCRIPTION
				"The stage of cpu packet filter."
			::= { sleV2CpuPacketFilterControl 8 }

		
		-- 1.3.6.1.4.1.6296.102.7.2.8.3.9
		sleV2CpuPacketFilterControlPriority OBJECT-TYPE
			SYNTAX Integer32 (1..65535)
			MAX-ACCESS read-write
			STATUS current
			DESCRIPTION
				"The priority of cpu packet filter."
			::= { sleV2CpuPacketFilterControl 9 }

		
		-- 1.3.6.1.4.1.6296.102.7.2.8.3.10
		sleV2CpuPacketFilterControlAction OBJECT-TYPE
			SYNTAX INTEGER
				{
				drop(1),
				permit(2),
				rateLimit(3),
				pass(4),
				dot1q(5),
				dot1qAttach(6),
				dot1qDetach(7),
				unknown(255)
				}
			MAX-ACCESS read-write
			STATUS current
			DESCRIPTION
				"The action to matched packet.
				Dot1q -> replace
				dot1qAttach -> add
				dot1qDettach -> remove"
			::= { sleV2CpuPacketFilterControl 10 }

		
		-- 1.3.6.1.4.1.6296.102.7.2.8.3.11
		sleV2CpuPacketFilterControlActionRateLimit OBJECT-TYPE
			SYNTAX Integer32 (1..100)
			MAX-ACCESS read-write
			STATUS current
			DESCRIPTION
				"The allowed-packet count per second."
			::= { sleV2CpuPacketFilterControl 11 }

		
		-- 1.3.6.1.4.1.6296.102.7.2.8.3.12
		sleV2CpuPacketFilterControlActionBurstSize OBJECT-TYPE
			SYNTAX Integer32 (1..100)
			MAX-ACCESS read-write
			STATUS current
			DESCRIPTION
				"The burst-allowed-packet count."
			::= { sleV2CpuPacketFilterControl 12 }

		
		-- 1.3.6.1.4.1.6296.102.7.2.8.3.13
		sleV2CpuPacketFilterControlActionTpid OBJECT-TYPE
			SYNTAX Integer32 (0..65535)
			MAX-ACCESS read-write
			STATUS current
			DESCRIPTION
				"The Action TPID
				The value 65535(0xffff) means any.
				"
			::= { sleV2CpuPacketFilterControl 13 }

		
		-- 1.3.6.1.4.1.6296.102.7.2.8.3.14
		sleV2CpuPacketFilterControlActionPcp OBJECT-TYPE
			SYNTAX Integer32 (0..7 | 255)
			MAX-ACCESS read-write
			STATUS current
			DESCRIPTION
				"The Action PCP.
				The value 255(0xff) means any.
				"
			::= { sleV2CpuPacketFilterControl 14 }

		
		-- 1.3.6.1.4.1.6296.102.7.2.8.3.15
		sleV2CpuPacketFilterControlActionVid OBJECT-TYPE
			SYNTAX Integer32 (0 | 1..4094 | 65535)
			MAX-ACCESS read-write
			STATUS current
			DESCRIPTION
				"The Action VID
				The value 65535(0xffff) means any.
				"
			::= { sleV2CpuPacketFilterControl 15 }

		
		-- 1.3.6.1.4.1.6296.102.7.2.8.3.16
		sleV2CpuPacketFilterControlActionTagPosition OBJECT-TYPE
			SYNTAX Integer32 (0 | 1..8)
			MAX-ACCESS read-write
			STATUS current
			DESCRIPTION
				"The Action tag position.
				1: S-vlan
				2: C-vlan
				M2200 uses only 1 and 2.
				"
			::= { sleV2CpuPacketFilterControl 16 }

		
		-- 1.3.6.1.4.1.6296.102.7.2.8.3.17
		sleV2CpuPacketFilterControlMatchType OBJECT-TYPE
			SYNTAX BITS
				{
				vid(0),
				cos(1),
				port(2),
				offset(3),
				dot1q(4)
				}
			MAX-ACCESS read-write
			STATUS current
			DESCRIPTION
				"The  match classifiter type."
			::= { sleV2CpuPacketFilterControl 17 }

		
		-- 1.3.6.1.4.1.6296.102.7.2.8.3.18
		sleV2CpuPacketFilterControlMatchCos OBJECT-TYPE
			SYNTAX OCTET STRING
			MAX-ACCESS read-write
			STATUS current
			DESCRIPTION
				"The matched CoS Queue.   
				M2200 doesn't  use
				"
			::= { sleV2CpuPacketFilterControl 18 }

		
		-- 1.3.6.1.4.1.6296.102.7.2.8.3.19
		sleV2CpuPacketFilterControlMatchPort OBJECT-TYPE
			SYNTAX OCTET STRING
			MAX-ACCESS read-write
			STATUS current
			DESCRIPTION
				"The matched port index."
			::= { sleV2CpuPacketFilterControl 19 }

		
		-- 1.3.6.1.4.1.6296.102.7.2.8.3.20
		sleV2CpuPacketFilterControlMatchVidmap OBJECT-TYPE
			SYNTAX OCTET STRING
			MAX-ACCESS read-write
			STATUS current
			DESCRIPTION
				"The matched VID
				M2200 doesn't  use
				"
			::= { sleV2CpuPacketFilterControl 20 }

		
		-- 1.3.6.1.4.1.6296.102.7.2.8.3.21
		sleV2CpuPacketFilterControlMatchTagPosition OBJECT-TYPE
			SYNTAX Integer32 (0 | 1..8)
			MAX-ACCESS read-write
			STATUS current
			DESCRIPTION
				"The matched tag position
				M2200 doesn't use
				"
			::= { sleV2CpuPacketFilterControl 21 }

		
		-- 1.3.6.1.4.1.6296.102.7.2.8.3.22
		sleV2CpuPacketFilterControlMatchTpid OBJECT-TYPE
			SYNTAX Integer32 (0..65535)
			MAX-ACCESS read-write
			STATUS current
			DESCRIPTION
				"The matched TPID."
			::= { sleV2CpuPacketFilterControl 22 }

		
		-- 1.3.6.1.4.1.6296.102.7.2.8.3.23
		sleV2CpuPacketFilterControlMatchPcp OBJECT-TYPE
			SYNTAX Integer32 (0..7 | 255)
			MAX-ACCESS read-write
			STATUS current
			DESCRIPTION
				"The matched PCP"
			::= { sleV2CpuPacketFilterControl 23 }

		
		-- 1.3.6.1.4.1.6296.102.7.2.8.3.24
		sleV2CpuPacketFilterControlMatchVid OBJECT-TYPE
			SYNTAX Integer32 (0 | 1..4094 | 65535)
			MAX-ACCESS read-write
			STATUS current
			DESCRIPTION
				"The matched VID"
			::= { sleV2CpuPacketFilterControl 24 }

		
		-- 1.3.6.1.4.1.6296.102.7.2.8.3.25
		sleV2CpuPacketFilterControlMatchOffset OBJECT-TYPE
			SYNTAX Integer32 (0..127)
			MAX-ACCESS read-write
			STATUS current
			DESCRIPTION
				"The matched offset"
			::= { sleV2CpuPacketFilterControl 25 }

		
		-- 1.3.6.1.4.1.6296.102.7.2.8.3.26
		sleV2CpuPacketFilterControlMatchLength OBJECT-TYPE
			SYNTAX Integer32 (1..16)
			MAX-ACCESS read-write
			STATUS current
			DESCRIPTION
				"The matched Length"
			::= { sleV2CpuPacketFilterControl 26 }

		
		-- 1.3.6.1.4.1.6296.102.7.2.8.3.27
		sleV2CpuPacketFilterControlMatchData OBJECT-TYPE
			SYNTAX OCTET STRING
			MAX-ACCESS read-write
			STATUS current
			DESCRIPTION
				"he matched data. (HEX string)"
			::= { sleV2CpuPacketFilterControl 27 }

		
		-- 1.3.6.1.4.1.6296.102.7.2.8.3.28
		sleV2CpuPacketFilterControlMatchMask OBJECT-TYPE
			SYNTAX OCTET STRING
			MAX-ACCESS read-write
			STATUS current
			DESCRIPTION
				"The matched mask. (HEX string)"
			::= { sleV2CpuPacketFilterControl 28 }

		
		-- 1.3.6.1.4.1.6296.102.7.2.8.3.29
		sleV2CpuPacketFilterControlMatchDesc OBJECT-TYPE
			SYNTAX OCTET STRING
			MAX-ACCESS read-write
			STATUS current
			DESCRIPTION
				"The matched Description"
			::= { sleV2CpuPacketFilterControl 29 }

		
		-- 1.3.6.1.4.1.6296.102.7.2.8.4
		sleV2CpuPacketFilterNotification OBJECT IDENTIFIER ::= { sleV2CpuPacketFilter 4 }

		
		-- 1.3.6.1.4.1.6296.102.7.2.8.4.1
		sleV2CpuPacketFilterAdded NOTIFICATION-TYPE
			OBJECTS { sleV2CpuPacketFilterControlRequest, sleV2CpuPacketFilterControlName, sleV2CpuPacketFilterControlStage, sleV2CpuPacketFilterControlPriority, sleV2CpuPacketFilterControlAction, 
				sleV2CpuPacketFilterControlActionRateLimit, sleV2CpuPacketFilterControlActionBurstSize, sleV2CpuPacketFilterControlActionTpid, sleV2CpuPacketFilterControlActionPcp, sleV2CpuPacketFilterControlActionVid, 
				sleV2CpuPacketFilterControlActionTagPosition, sleV2CpuPacketFilterControlMatchType, sleV2CpuPacketFilterControlMatchCos, sleV2CpuPacketFilterControlMatchPort, sleV2CpuPacketFilterControlMatchVid, 
				sleV2CpuPacketFilterControlMatchTagPosition, sleV2CpuPacketFilterControlMatchOffset, sleV2CpuPacketFilterControlMatchLength, sleV2CpuPacketFilterControlMatchData, sleV2CpuPacketFilterControlMatchMask, 
				sleV2CpuPacketFilterControlStatus, sleV2CpuPacketFilterControlTimer, sleV2CpuPacketFilterControlMatchVidmap, sleV2CpuPacketFilterControlMatchTpid, sleV2CpuPacketFilterControlMatchPcp, 
				sleV2CpuPacketFilterControlMatchDesc, sleV2CpuPacketFilterControlTimeStamp, sleV2CpuPacketFilterControlReqResult }
			STATUS current
			DESCRIPTION 
				"Description."
			::= { sleV2CpuPacketFilterNotification 1 }

		
		-- 1.3.6.1.4.1.6296.102.7.2.8.4.2
		sleV2CpuPacketFilterDeleted NOTIFICATION-TYPE
			OBJECTS { sleV2CpuPacketFilterControlRequest, sleV2CpuPacketFilterControlTimeStamp, sleV2CpuPacketFilterControlReqResult, sleV2CpuPacketFilterControlIndex }
			STATUS current
			DESCRIPTION 
				"Description."
			::= { sleV2CpuPacketFilterNotification 2 }

		
		-- 1.3.6.1.4.1.6296.102.7.2.8.4.3
		sleV2CpuPacketFilterActionChanged NOTIFICATION-TYPE
			OBJECTS { sleV2CpuPacketFilterControlRequest, sleV2CpuPacketFilterControlTimeStamp, sleV2CpuPacketFilterControlReqResult, sleV2CpuPacketFilterControlIndex, sleV2CpuPacketFilterControlAction, 
				sleV2CpuPacketFilterControlActionRateLimit, sleV2CpuPacketFilterControlActionBurstSize, sleV2CpuPacketFilterControlActionTpid, sleV2CpuPacketFilterControlActionPcp, sleV2CpuPacketFilterControlActionVid, 
				sleV2CpuPacketFilterControlActionTagPosition, sleV2CpuPacketFilterControlMatchType }
			STATUS current
			DESCRIPTION 
				"Description."
			::= { sleV2CpuPacketFilterNotification 3 }

		
		-- 1.3.6.1.4.1.6296.102.7.2.8.4.4
		sleV2CpuPacketFilterMatchChanged NOTIFICATION-TYPE
			OBJECTS { sleV2CpuPacketFilterControlRequest, sleV2CpuPacketFilterControlTimeStamp, sleV2CpuPacketFilterControlReqResult, sleV2CpuPacketFilterControlIndex, sleV2CpuPacketFilterControlMatchType, 
				sleV2CpuPacketFilterControlMatchCos, sleV2CpuPacketFilterControlMatchPort, sleV2CpuPacketFilterControlMatchVidmap, sleV2CpuPacketFilterControlMatchTagPosition, sleV2CpuPacketFilterControlMatchTpid, 
				sleV2CpuPacketFilterControlMatchPcp, sleV2CpuPacketFilterControlMatchVid, sleV2CpuPacketFilterControlMatchOffset, sleV2CpuPacketFilterControlMatchLength, sleV2CpuPacketFilterControlMatchData, 
				sleV2CpuPacketFilterControlMatchMask, sleV2CpuPacketFilterControlMatchDesc }
			STATUS current
			DESCRIPTION 
				"Description."
			::= { sleV2CpuPacketFilterNotification 4 }

		
		-- 1.3.6.1.4.1.6296.102.7.2.9
		sleV2VlanOperation OBJECT IDENTIFIER ::= { sleVSecurity4 9 }

		
		-- 1.3.6.1.4.1.6296.102.7.2.9.1
		sleV2VlanOperationTable OBJECT-TYPE
			SYNTAX SEQUENCE OF SleV2VlanOperationEntry
			MAX-ACCESS not-accessible
			STATUS current
			DESCRIPTION
				"Description."
			::= { sleV2VlanOperation 1 }

		
		-- 1.3.6.1.4.1.6296.102.7.2.9.1.1
		sleV2VlanOperationEntry OBJECT-TYPE
			SYNTAX SleV2VlanOperationEntry
			MAX-ACCESS not-accessible
			STATUS current
			DESCRIPTION
				"Description."
			INDEX { sleV2VlanOperationIndex, sleV2VlanOperationName }
			::= { sleV2VlanOperationTable 1 }

		
		SleV2VlanOperationEntry ::=
			SEQUENCE { 
				sleV2VlanOperationIndex
					Integer32,
				sleV2VlanOperationName
					OCTET STRING,
				sleV2VlanOperationStage
					INTEGER,
				sleV2VlanOperationProiroty
					Integer32,
				sleV2VlanOperationPort
					OCTET STRING,
				sleV2VlanOperationOuterVlan
					OCTET STRING,
				sleV2VlanOperationInnerVlan
					OCTET STRING,
				sleV2VlanOperationEtherType
					Integer32,
				sleV2VlanOperationIpProtocol
					Integer32,
				sleV2VlanOperationArpSip
					OCTET STRING,
				sleV2VlanOperationArpSipPfxLen
					Integer32,
				sleV2VlanOperationSip
					OCTET STRING,
				sleV2VlanOperationSipPfxLen
					Integer32,
				sleV2VlanOperationDip
					OCTET STRING,
				sleV2VlanOperationDipPfxLen
					Integer32,
				sleV2VlanOperationAction
					INTEGER,
				sleV2VlanOperationActionVid
					Integer32
			 }

		-- 1.3.6.1.4.1.6296.102.7.2.9.1.1.1
		sleV2VlanOperationIndex OBJECT-TYPE
			SYNTAX Integer32 (1..65565)
			MAX-ACCESS read-only
			STATUS current
			DESCRIPTION
				"The vlan operation index."
			::= { sleV2VlanOperationEntry 1 }

		
		-- 1.3.6.1.4.1.6296.102.7.2.9.1.1.2
		sleV2VlanOperationName OBJECT-TYPE
			SYNTAX OCTET STRING
			MAX-ACCESS read-only
			STATUS current
			DESCRIPTION
				"The vlan operation name"
			::= { sleV2VlanOperationEntry 2 }

		
		-- 1.3.6.1.4.1.6296.102.7.2.9.1.1.3
		sleV2VlanOperationStage OBJECT-TYPE
			SYNTAX INTEGER
				{
				ingressSlowPath(1),
				egressSlowPath(2)
				}
			MAX-ACCESS read-only
			STATUS current
			DESCRIPTION
				"The vlan operation stage."
			::= { sleV2VlanOperationEntry 3 }

		
		-- 1.3.6.1.4.1.6296.102.7.2.9.1.1.4
		sleV2VlanOperationProiroty OBJECT-TYPE
			SYNTAX Integer32 (1..65535)
			MAX-ACCESS read-only
			STATUS current
			DESCRIPTION
				"The vlan operation priority."
			::= { sleV2VlanOperationEntry 4 }

		
		-- 1.3.6.1.4.1.6296.102.7.2.9.1.1.5
		sleV2VlanOperationPort OBJECT-TYPE
			SYNTAX OCTET STRING
			MAX-ACCESS read-only
			STATUS current
			DESCRIPTION
				"The vlan operation ports"
			::= { sleV2VlanOperationEntry 5 }

		
		-- 1.3.6.1.4.1.6296.102.7.2.9.1.1.6
		sleV2VlanOperationOuterVlan OBJECT-TYPE
			SYNTAX OCTET STRING
			MAX-ACCESS read-only
			STATUS current
			DESCRIPTION
				"The Outer vlan."
			::= { sleV2VlanOperationEntry 6 }

		
		-- 1.3.6.1.4.1.6296.102.7.2.9.1.1.7
		sleV2VlanOperationInnerVlan OBJECT-TYPE
			SYNTAX OCTET STRING
			MAX-ACCESS read-only
			STATUS current
			DESCRIPTION
				"The inner Vlan."
			::= { sleV2VlanOperationEntry 7 }

		
		-- 1.3.6.1.4.1.6296.102.7.2.9.1.1.8
		sleV2VlanOperationEtherType OBJECT-TYPE
			SYNTAX Integer32
			MAX-ACCESS read-only
			STATUS current
			DESCRIPTION
				"The vlan operation ether-type."
			::= { sleV2VlanOperationEntry 8 }

		
		-- 1.3.6.1.4.1.6296.102.7.2.9.1.1.9
		sleV2VlanOperationIpProtocol OBJECT-TYPE
			SYNTAX Integer32
			MAX-ACCESS read-only
			STATUS current
			DESCRIPTION
				"The vlan operation IP Protocol"
			::= { sleV2VlanOperationEntry 9 }

		
		-- 1.3.6.1.4.1.6296.102.7.2.9.1.1.10
		sleV2VlanOperationArpSip OBJECT-TYPE
			SYNTAX OCTET STRING
			MAX-ACCESS read-only
			STATUS current
			DESCRIPTION
				"The vlan operation source-IPaddress."
			::= { sleV2VlanOperationEntry 10 }

		
		-- 1.3.6.1.4.1.6296.102.7.2.9.1.1.11
		sleV2VlanOperationArpSipPfxLen OBJECT-TYPE
			SYNTAX Integer32
			MAX-ACCESS read-only
			STATUS current
			DESCRIPTION
				"The vlan operation source-IPAddress prefix-length."
			::= { sleV2VlanOperationEntry 11 }

		
		-- 1.3.6.1.4.1.6296.102.7.2.9.1.1.12
		sleV2VlanOperationSip OBJECT-TYPE
			SYNTAX OCTET STRING
			MAX-ACCESS read-only
			STATUS current
			DESCRIPTION
				"The vlan operation Source-IPaddress."
			::= { sleV2VlanOperationEntry 12 }

		
		-- 1.3.6.1.4.1.6296.102.7.2.9.1.1.13
		sleV2VlanOperationSipPfxLen OBJECT-TYPE
			SYNTAX Integer32
			MAX-ACCESS read-only
			STATUS current
			DESCRIPTION
				"The vlan operation Source-IPAddress prefix-length."
			::= { sleV2VlanOperationEntry 13 }

		
		-- 1.3.6.1.4.1.6296.102.7.2.9.1.1.14
		sleV2VlanOperationDip OBJECT-TYPE
			SYNTAX OCTET STRING
			MAX-ACCESS read-only
			STATUS current
			DESCRIPTION
				"The vlan operation Destination-IPaddress."
			::= { sleV2VlanOperationEntry 14 }

		
		-- 1.3.6.1.4.1.6296.102.7.2.9.1.1.15
		sleV2VlanOperationDipPfxLen OBJECT-TYPE
			SYNTAX Integer32
			MAX-ACCESS read-only
			STATUS current
			DESCRIPTION
				"The vlan operation Destination-IPAddress prefix-length."
			::= { sleV2VlanOperationEntry 15 }

		
		-- 1.3.6.1.4.1.6296.102.7.2.9.1.1.16
		sleV2VlanOperationAction OBJECT-TYPE
			SYNTAX INTEGER
				{
				addServiceVlanTag(1),
				replaceServiceVlanID(2),
				removeServiceVlanTag(3),
				addCustomerVlanTag(4),
				replaceCustomerVlanID(5),
				removeCustomerVlanTag(6)
				}
			MAX-ACCESS read-only
			STATUS current
			DESCRIPTION
				"The vlan-operation action types."
			::= { sleV2VlanOperationEntry 16 }

		
		-- 1.3.6.1.4.1.6296.102.7.2.9.1.1.17
		sleV2VlanOperationActionVid OBJECT-TYPE
			SYNTAX Integer32 (1..4095)
			MAX-ACCESS read-only
			STATUS current
			DESCRIPTION
				"The vlan operation action-vid."
			::= { sleV2VlanOperationEntry 17 }

		
		-- 1.3.6.1.4.1.6296.102.7.2.9.2
		sleV2VlanOperationControl OBJECT IDENTIFIER ::= { sleV2VlanOperation 2 }

		
		-- 1.3.6.1.4.1.6296.102.7.2.9.2.1
		sleV2VlanOperationControlRequest OBJECT-TYPE
			SYNTAX INTEGER
				{
				addVlanOperation(1),
				delVlanOperation(2)
				}
			MAX-ACCESS read-write
			STATUS current
			DESCRIPTION
				"The request of a user command"
			::= { sleV2VlanOperationControl 1 }

		
		-- 1.3.6.1.4.1.6296.102.7.2.9.2.2
		sleV2VlanOperationControlStatus OBJECT-TYPE
			SYNTAX SleControlStatusType
			MAX-ACCESS read-only
			STATUS current
			DESCRIPTION
				"The status of user command"
			::= { sleV2VlanOperationControl 2 }

		
		-- 1.3.6.1.4.1.6296.102.7.2.9.2.3
		sleV2VlanOperationControlTimer OBJECT-TYPE
			SYNTAX Gauge32
			MAX-ACCESS read-write
			STATUS current
			DESCRIPTION
				"The maximum time for the manager for a long running user command"
			::= { sleV2VlanOperationControl 3 }

		
		-- 1.3.6.1.4.1.6296.102.7.2.9.2.4
		sleV2VlanOperationControlTimeStamp OBJECT-TYPE
			SYNTAX TimeTicks
			MAX-ACCESS read-only
			STATUS current
			DESCRIPTION
				"The time stamp of the last command(end of command)"
			::= { sleV2VlanOperationControl 4 }

		
		-- 1.3.6.1.4.1.6296.102.7.2.9.2.5
		sleV2VlanOperationControlReqResult OBJECT-TYPE
			SYNTAX SleControlRequestResultType
			MAX-ACCESS read-only
			STATUS current
			DESCRIPTION
				"The result of the last user command"
			::= { sleV2VlanOperationControl 5 }

		
		-- 1.3.6.1.4.1.6296.102.7.2.9.2.6
		sleV2VlanOperationControlIndex OBJECT-TYPE
			SYNTAX Integer32 (1..65535)
			MAX-ACCESS read-write
			STATUS current
			DESCRIPTION
				"The vlan operation index."
			::= { sleV2VlanOperationControl 6 }

		
		-- 1.3.6.1.4.1.6296.102.7.2.9.2.7
		sleV2VlanOperationControlName OBJECT-TYPE
			SYNTAX OCTET STRING
			MAX-ACCESS read-write
			STATUS current
			DESCRIPTION
				"The vlan operation name"
			::= { sleV2VlanOperationControl 7 }

		
		-- 1.3.6.1.4.1.6296.102.7.2.9.2.8
		sleV2VlanOperationControlStage OBJECT-TYPE
			SYNTAX INTEGER
				{
				ingressSlowPath(1),
				egressSlowPath(2)
				}
			MAX-ACCESS read-write
			STATUS current
			DESCRIPTION
				"The vlan operation stage."
			::= { sleV2VlanOperationControl 8 }

		
		-- 1.3.6.1.4.1.6296.102.7.2.9.2.9
		sleV2VlanOperationControlProiroty OBJECT-TYPE
			SYNTAX Integer32 (1..65535)
			MAX-ACCESS read-write
			STATUS current
			DESCRIPTION
				"The vlan operation priority."
			::= { sleV2VlanOperationControl 9 }

		
		-- 1.3.6.1.4.1.6296.102.7.2.9.2.10
		sleV2VlanOperationControlPort OBJECT-TYPE
			SYNTAX OCTET STRING
			MAX-ACCESS read-write
			STATUS current
			DESCRIPTION
				"The vlan operation ports"
			::= { sleV2VlanOperationControl 10 }

		
		-- 1.3.6.1.4.1.6296.102.7.2.9.2.11
		sleV2VlanOperationControlOuterVlan OBJECT-TYPE
			SYNTAX OCTET STRING
			MAX-ACCESS read-write
			STATUS current
			DESCRIPTION
				"The Outer vlan."
			::= { sleV2VlanOperationControl 11 }

		
		-- 1.3.6.1.4.1.6296.102.7.2.9.2.12
		sleV2VlanOperationControlInnerVlan OBJECT-TYPE
			SYNTAX OCTET STRING
			MAX-ACCESS read-write
			STATUS current
			DESCRIPTION
				"The Inner vlan."
			::= { sleV2VlanOperationControl 12 }

		
		-- 1.3.6.1.4.1.6296.102.7.2.9.2.13
		sleV2VlanOperationControlEtherType OBJECT-TYPE
			SYNTAX Integer32
			MAX-ACCESS read-write
			STATUS current
			DESCRIPTION
				"The vlan operation ether-type."
			::= { sleV2VlanOperationControl 13 }

		
		-- 1.3.6.1.4.1.6296.102.7.2.9.2.14
		sleV2VlanOperationControlIpProtocol OBJECT-TYPE
			SYNTAX Integer32
			MAX-ACCESS read-write
			STATUS current
			DESCRIPTION
				"The vlan operation IP Protocol"
			::= { sleV2VlanOperationControl 14 }

		
		-- 1.3.6.1.4.1.6296.102.7.2.9.2.15
		sleV2VlanOperationControlArpSip OBJECT-TYPE
			SYNTAX OCTET STRING
			MAX-ACCESS read-write
			STATUS current
			DESCRIPTION
				"The vlan operation source-IPaddress."
			::= { sleV2VlanOperationControl 15 }

		
		-- 1.3.6.1.4.1.6296.102.7.2.9.2.16
		sleV2VlanOperationControlArpSipPfxLen OBJECT-TYPE
			SYNTAX Integer32
			MAX-ACCESS read-write
			STATUS current
			DESCRIPTION
				"The vlan operation source-IPAddress prefix-length."
			::= { sleV2VlanOperationControl 16 }

		
		-- 1.3.6.1.4.1.6296.102.7.2.9.2.17
		sleV2VlanOperationControlSip OBJECT-TYPE
			SYNTAX OCTET STRING
			MAX-ACCESS read-write
			STATUS current
			DESCRIPTION
				"The vlan operation Source-IPaddress."
			::= { sleV2VlanOperationControl 17 }

		
		-- 1.3.6.1.4.1.6296.102.7.2.9.2.18
		sleV2VlanOperationControlSipPfxLen OBJECT-TYPE
			SYNTAX Integer32
			MAX-ACCESS read-write
			STATUS current
			DESCRIPTION
				"The vlan operation Source-IPAddress prefix-length."
			::= { sleV2VlanOperationControl 18 }

		
		-- 1.3.6.1.4.1.6296.102.7.2.9.2.19
		sleV2VlanOperationControlDip OBJECT-TYPE
			SYNTAX OCTET STRING
			MAX-ACCESS read-write
			STATUS current
			DESCRIPTION
				"The vlan operation Destination-IPaddress."
			::= { sleV2VlanOperationControl 19 }

		
		-- 1.3.6.1.4.1.6296.102.7.2.9.2.20
		sleV2VlanOperationControlDipPfxLen OBJECT-TYPE
			SYNTAX Integer32
			MAX-ACCESS read-write
			STATUS current
			DESCRIPTION
				"The vlan operation Destination-IPAddress prefix-length."
			::= { sleV2VlanOperationControl 20 }

		
		-- 1.3.6.1.4.1.6296.102.7.2.9.2.21
		sleV2VlanOperationControlAction OBJECT-TYPE
			SYNTAX INTEGER
				{
				addServiceVlanTag(1),
				replaceServiceVlanID(2),
				removeServiceVlanTag(3),
				addCustomerVlanTag(4),
				replaceCustomerVlanID(5),
				removeCustomerVlanTag(6)
				}
			MAX-ACCESS read-write
			STATUS current
			DESCRIPTION
				"The vlan-operation action types."
			::= { sleV2VlanOperationControl 21 }

		
		-- 1.3.6.1.4.1.6296.102.7.2.9.2.22
		sleV2VlanOperationControlActionVid OBJECT-TYPE
			SYNTAX Integer32 (1..4095)
			MAX-ACCESS read-write
			STATUS current
			DESCRIPTION
				"The vlan operation action-vid."
			::= { sleV2VlanOperationControl 22 }

		
		-- 1.3.6.1.4.1.6296.102.7.2.9.3
		sleV2VlanOperationNotification OBJECT IDENTIFIER ::= { sleV2VlanOperation 3 }

		
		-- 1.3.6.1.4.1.6296.102.7.2.9.3.1
		sleV2VlanOperationCreated NOTIFICATION-TYPE
			OBJECTS { sleV2VlanOperationControlRequest, sleV2VlanOperationControlTimeStamp, sleV2VlanOperationControlReqResult, sleV2VlanOperationControlName, sleV2VlanOperationControlStage, 
				sleV2VlanOperationControlProiroty, sleV2VlanOperationControlPort, sleV2VlanOperationControlOuterVlan, sleV2VlanOperationControlInnerVlan, sleV2VlanOperationControlEtherType, 
				sleV2VlanOperationControlIpProtocol, sleV2VlanOperationControlArpSip, sleV2VlanOperationControlArpSipPfxLen, sleV2VlanOperationControlSip, sleV2VlanOperationControlSipPfxLen, 
				sleV2VlanOperationControlDip, sleV2VlanOperationControlDipPfxLen, sleV2VlanOperationControlAction, sleV2VlanOperationControlActionVid }
			STATUS current
			DESCRIPTION 
				"addVlanOperation"
			::= { sleV2VlanOperationNotification 1 }

		
		-- 1.3.6.1.4.1.6296.102.7.2.9.3.2
		sleV2VlanOperationDeleted NOTIFICATION-TYPE
			OBJECTS { sleV2VlanOperationControlRequest, sleV2VlanOperationControlTimeStamp, sleV2VlanOperationControlReqResult, sleV2VlanOperationControlName }
			STATUS current
			DESCRIPTION 
				"delVlanOperation"
			::= { sleV2VlanOperationNotification 2 }

		
		-- 1.3.6.1.4.1.6296.102.7.2.10
		sleV2EthernetService OBJECT IDENTIFIER ::= { sleVSecurity4 10 }

		
		-- 1.3.6.1.4.1.6296.102.7.2.10.1
		sleV2EthernetServiceBase OBJECT IDENTIFIER ::= { sleV2EthernetService 1 }

		
		-- 1.3.6.1.4.1.6296.102.7.2.10.1.1
		sleV2EthernetServiceEnableStatus OBJECT-TYPE
			SYNTAX INTEGER
				{
				none(0),
				rt(1),
				cot(2)
				}
			MAX-ACCESS read-only
			STATUS current
			DESCRIPTION
				"The ethernet service mode status."
			::= { sleV2EthernetServiceBase 1 }

		
		-- 1.3.6.1.4.1.6296.102.7.2.10.1.2
		sleV2EthernetServiceEnableManagement OBJECT-TYPE
			SYNTAX INTEGER
				{
				enable(1),
				disable(2)
				}
			MAX-ACCESS read-only
			STATUS current
			DESCRIPTION
				"The global management access status ( only in RT mode )"
			::= { sleV2EthernetServiceBase 2 }

		
		-- 1.3.6.1.4.1.6296.102.7.2.10.1.3
		sleV2EthernetServiceHealthCheckPort OBJECT-TYPE
			SYNTAX OCTET STRING
			MAX-ACCESS read-only
			STATUS current
			DESCRIPTION
				"The health check port of uplink. ( only in COT mode )"
			::= { sleV2EthernetServiceBase 3 }

		
		-- 1.3.6.1.4.1.6296.102.7.2.10.1.4
		sleV2EthernetServiceHealthCheckVid OBJECT-TYPE
			SYNTAX OCTET STRING
			MAX-ACCESS read-only
			STATUS current
			DESCRIPTION
				"The health check vid of uplink. ( only in COT mode )"
			::= { sleV2EthernetServiceBase 4 }

		
		-- 1.3.6.1.4.1.6296.102.7.2.10.2
		sleV2EthernetServiceTable OBJECT-TYPE
			SYNTAX SEQUENCE OF SleV2EthernetServiceEntry
			MAX-ACCESS not-accessible
			STATUS current
			DESCRIPTION
				"Description."
			::= { sleV2EthernetService 2 }

		
		-- 1.3.6.1.4.1.6296.102.7.2.10.2.1
		sleV2EthernetServiceEntry OBJECT-TYPE
			SYNTAX SleV2EthernetServiceEntry
			MAX-ACCESS not-accessible
			STATUS current
			DESCRIPTION
				"Description."
			INDEX { sleV2EthernetServiceSid }
			::= { sleV2EthernetServiceTable 1 }

		
		SleV2EthernetServiceEntry ::=
			SEQUENCE { 
				sleV2EthernetServiceSid
					INTEGER,
				sleV2EthernetServiceType
					INTEGER,
				sleV2EthernetServiceRtCustomerPort
					OCTET STRING,
				sleV2EthernetServiceRtCustomerVid
					OCTET STRING,
				sleV2EthernetServiceRtNetworkPort
					OCTET STRING,
				sleV2EthernetServiceRtNetworkVid
					OCTET STRING,
				sleV2EthernetServiceRtEnableManagement
					INTEGER,
				sleV2EthernetServiceCotExternalPort
					OCTET STRING,
				sleV2EthernetServiceCotExternalVid
					OCTET STRING,
				sleV2EthernetServiceCotInternalPort
					OCTET STRING,
				sleV2EthernetServiceCotInternalVid
					OCTET STRING
			 }

		-- 1.3.6.1.4.1.6296.102.7.2.10.2.1.1
		sleV2EthernetServiceSid OBJECT-TYPE
			SYNTAX INTEGER (1..65535)
			MAX-ACCESS read-only
			STATUS current
			DESCRIPTION
				"The unique number is given by service identifier."
			::= { sleV2EthernetServiceEntry 1 }

		
		-- 1.3.6.1.4.1.6296.102.7.2.10.2.1.2
		sleV2EthernetServiceType OBJECT-TYPE
			SYNTAX INTEGER
				{
				unicast(1),
				multicast(2)
				}
			MAX-ACCESS read-only
			STATUS current
			DESCRIPTION
				"The ethernet service type
				1: unicast
				2: multicast"
			::= { sleV2EthernetServiceEntry 2 }

		
		-- 1.3.6.1.4.1.6296.102.7.2.10.2.1.3
		sleV2EthernetServiceRtCustomerPort OBJECT-TYPE
			SYNTAX OCTET STRING
			MAX-ACCESS read-only
			STATUS current
			DESCRIPTION
				"The Configuring service's customer port for RT mode."
			::= { sleV2EthernetServiceEntry 3 }

		
		-- 1.3.6.1.4.1.6296.102.7.2.10.2.1.4
		sleV2EthernetServiceRtCustomerVid OBJECT-TYPE
			SYNTAX OCTET STRING
			MAX-ACCESS read-only
			STATUS current
			DESCRIPTION
				"The Configuring service's customer vid for RT mode."
			::= { sleV2EthernetServiceEntry 4 }

		
		-- 1.3.6.1.4.1.6296.102.7.2.10.2.1.5
		sleV2EthernetServiceRtNetworkPort OBJECT-TYPE
			SYNTAX OCTET STRING
			MAX-ACCESS read-only
			STATUS current
			DESCRIPTION
				"The Configuring service's network port for RT mode."
			::= { sleV2EthernetServiceEntry 5 }

		
		-- 1.3.6.1.4.1.6296.102.7.2.10.2.1.6
		sleV2EthernetServiceRtNetworkVid OBJECT-TYPE
			SYNTAX OCTET STRING
			MAX-ACCESS read-only
			STATUS current
			DESCRIPTION
				"The Configuring service's network vid for RT mode."
			::= { sleV2EthernetServiceEntry 6 }

		
		-- 1.3.6.1.4.1.6296.102.7.2.10.2.1.7
		sleV2EthernetServiceRtEnableManagement OBJECT-TYPE
			SYNTAX INTEGER
				{
				enable(1),
				disable(2)
				}
			MAX-ACCESS read-only
			STATUS current
			DESCRIPTION
				"Description."
			::= { sleV2EthernetServiceEntry 7 }

		
		-- 1.3.6.1.4.1.6296.102.7.2.10.2.1.8
		sleV2EthernetServiceCotExternalPort OBJECT-TYPE
			SYNTAX OCTET STRING
			MAX-ACCESS read-only
			STATUS current
			DESCRIPTION
				"The Configuring service's external port for COT mode."
			::= { sleV2EthernetServiceEntry 8 }

		
		-- 1.3.6.1.4.1.6296.102.7.2.10.2.1.9
		sleV2EthernetServiceCotExternalVid OBJECT-TYPE
			SYNTAX OCTET STRING
			MAX-ACCESS read-only
			STATUS current
			DESCRIPTION
				"The Configuring service's external vid for COT mode."
			::= { sleV2EthernetServiceEntry 9 }

		
		-- 1.3.6.1.4.1.6296.102.7.2.10.2.1.10
		sleV2EthernetServiceCotInternalPort OBJECT-TYPE
			SYNTAX OCTET STRING
			MAX-ACCESS read-only
			STATUS current
			DESCRIPTION
				"The Configuring service's internal port for COT mode."
			::= { sleV2EthernetServiceEntry 10 }

		
		-- 1.3.6.1.4.1.6296.102.7.2.10.2.1.11
		sleV2EthernetServiceCotInternalVid OBJECT-TYPE
			SYNTAX OCTET STRING
			MAX-ACCESS read-only
			STATUS current
			DESCRIPTION
				"The Configuring service's internal vid for COT mode."
			::= { sleV2EthernetServiceEntry 11 }

		
		-- 1.3.6.1.4.1.6296.102.7.2.10.3
		sleV2EthernetServiceControl OBJECT IDENTIFIER ::= { sleV2EthernetService 3 }

		
		-- 1.3.6.1.4.1.6296.102.7.2.10.3.1
		sleV2EthernetServiceControlRequest OBJECT-TYPE
			SYNTAX INTEGER
				{
				setEnableStatus(1),
				setEnableManagement(2),
				setHealthCheck(3),
				delHealthCheck(4),
				setSidForRT(5),
				setSidForCOT(6),
				delService(7)
				}
			MAX-ACCESS read-write
			STATUS current
			DESCRIPTION
				"The request of a user command"
			::= { sleV2EthernetServiceControl 1 }

		
		-- 1.3.6.1.4.1.6296.102.7.2.10.3.2
		sleV2EthernetServiceControlStatus OBJECT-TYPE
			SYNTAX SleControlStatusType
			MAX-ACCESS read-only
			STATUS current
			DESCRIPTION
				"The status of user command"
			::= { sleV2EthernetServiceControl 2 }

		
		-- 1.3.6.1.4.1.6296.102.7.2.10.3.3
		sleV2EthernetServiceControlTimer OBJECT-TYPE
			SYNTAX Gauge32
			MAX-ACCESS read-write
			STATUS current
			DESCRIPTION
				"The maximum time for the manager for a long running user command"
			::= { sleV2EthernetServiceControl 3 }

		
		-- 1.3.6.1.4.1.6296.102.7.2.10.3.4
		sleV2EthernetServiceControlTimeStamp OBJECT-TYPE
			SYNTAX TimeTicks
			MAX-ACCESS read-only
			STATUS current
			DESCRIPTION
				"The time stamp of the last command(end of command)"
			::= { sleV2EthernetServiceControl 4 }

		
		-- 1.3.6.1.4.1.6296.102.7.2.10.3.5
		sleV2EthernetServiceControlReqResult OBJECT-TYPE
			SYNTAX SleControlRequestResultType
			MAX-ACCESS read-only
			STATUS current
			DESCRIPTION
				"The result of the last user command"
			::= { sleV2EthernetServiceControl 5 }

		
		-- 1.3.6.1.4.1.6296.102.7.2.10.3.6
		sleV2EthernetServiceControlEnableStatus OBJECT-TYPE
			SYNTAX INTEGER
				{
				none(0),
				rt(1),
				cot(2)
				}
			MAX-ACCESS read-write
			STATUS current
			DESCRIPTION
				"The ethernet service mode status."
			::= { sleV2EthernetServiceControl 6 }

		
		-- 1.3.6.1.4.1.6296.102.7.2.10.3.7
		sleV2EthernetServiceControlEnableManagement OBJECT-TYPE
			SYNTAX INTEGER
				{
				enable(1),
				disable(2)
				}
			MAX-ACCESS read-write
			STATUS current
			DESCRIPTION
				"The local management access status ( only in RT mode )"
			::= { sleV2EthernetServiceControl 7 }

		
		-- 1.3.6.1.4.1.6296.102.7.2.10.3.8
		sleV2EthernetServiceControlHealthCheckPort OBJECT-TYPE
			SYNTAX OCTET STRING
			MAX-ACCESS read-write
			STATUS current
			DESCRIPTION
				"The health check port of uplink. ( only in COT mode )"
			::= { sleV2EthernetServiceControl 8 }

		
		-- 1.3.6.1.4.1.6296.102.7.2.10.3.9
		sleV2EthernetServiceControlHealthCheckVid OBJECT-TYPE
			SYNTAX OCTET STRING
			MAX-ACCESS read-write
			STATUS current
			DESCRIPTION
				"The health check vid of uplink. ( only in COT mode )"
			::= { sleV2EthernetServiceControl 9 }

		
		-- 1.3.6.1.4.1.6296.102.7.2.10.3.10
		sleV2EthernetServiceControlSid OBJECT-TYPE
			SYNTAX INTEGER (1..65535)
			MAX-ACCESS read-write
			STATUS current
			DESCRIPTION
				"The unique number is given by service identifier."
			::= { sleV2EthernetServiceControl 10 }

		
		-- 1.3.6.1.4.1.6296.102.7.2.10.3.11
		sleV2EthernetServiceControlType OBJECT-TYPE
			SYNTAX INTEGER
				{
				unicast(1),
				multicast(2)
				}
			MAX-ACCESS read-write
			STATUS current
			DESCRIPTION
				"The ethernet service type
				1: unicast
				2: multicast"
			::= { sleV2EthernetServiceControl 11 }

		
		-- 1.3.6.1.4.1.6296.102.7.2.10.3.12
		sleV2EthernetServiceControlRtCustomerPort OBJECT-TYPE
			SYNTAX OCTET STRING
			MAX-ACCESS read-write
			STATUS current
			DESCRIPTION
				"The Configuring service's customer port for RT mode."
			::= { sleV2EthernetServiceControl 12 }

		
		-- 1.3.6.1.4.1.6296.102.7.2.10.3.13
		sleV2EthernetServiceControlRtCustomerVid OBJECT-TYPE
			SYNTAX OCTET STRING
			MAX-ACCESS read-write
			STATUS current
			DESCRIPTION
				"The Configuring service's customer vid for RT mode."
			::= { sleV2EthernetServiceControl 13 }

		
		-- 1.3.6.1.4.1.6296.102.7.2.10.3.14
		sleV2EthernetServiceControlRtNetworkPort OBJECT-TYPE
			SYNTAX OCTET STRING
			MAX-ACCESS read-write
			STATUS current
			DESCRIPTION
				"The Configuring service's network port for RT mode."
			::= { sleV2EthernetServiceControl 14 }

		
		-- 1.3.6.1.4.1.6296.102.7.2.10.3.15
		sleV2EthernetServiceControlRtNetworkVid OBJECT-TYPE
			SYNTAX OCTET STRING
			MAX-ACCESS read-write
			STATUS current
			DESCRIPTION
				"The Configuring service's network vid for RT mode."
			::= { sleV2EthernetServiceControl 15 }

		
		-- 1.3.6.1.4.1.6296.102.7.2.10.3.16
		sleV2EthernetServiceControlRtEnableManagement OBJECT-TYPE
			SYNTAX INTEGER
				{
				enable(1),
				disable(2)
				}
			MAX-ACCESS read-write
			STATUS current
			DESCRIPTION
				"Description."
			::= { sleV2EthernetServiceControl 16 }

		
		-- 1.3.6.1.4.1.6296.102.7.2.10.3.17
		sleV2EthernetServiceControlCotExternalPort OBJECT-TYPE
			SYNTAX OCTET STRING
			MAX-ACCESS read-write
			STATUS current
			DESCRIPTION
				"The Configuring service's external port for COT mode."
			::= { sleV2EthernetServiceControl 17 }

		
		-- 1.3.6.1.4.1.6296.102.7.2.10.3.18
		sleV2EthernetServiceControlCotExternalVid OBJECT-TYPE
			SYNTAX OCTET STRING
			MAX-ACCESS read-write
			STATUS current
			DESCRIPTION
				"The Configuring service's external vid for COT mode."
			::= { sleV2EthernetServiceControl 18 }

		
		-- 1.3.6.1.4.1.6296.102.7.2.10.3.19
		sleV2EthernetServiceControlCotInternalPort OBJECT-TYPE
			SYNTAX OCTET STRING
			MAX-ACCESS read-write
			STATUS current
			DESCRIPTION
				"The Configuring service's internal port for COT mode."
			::= { sleV2EthernetServiceControl 19 }

		
		-- 1.3.6.1.4.1.6296.102.7.2.10.3.20
		sleV2EthernetServiceControlCotInternalVid OBJECT-TYPE
			SYNTAX OCTET STRING
			MAX-ACCESS read-write
			STATUS current
			DESCRIPTION
				"The Configuring service's internal vid for COT mode."
			::= { sleV2EthernetServiceControl 20 }

		
		-- 1.3.6.1.4.1.6296.102.7.2.10.4
		sleV2EthernetServiceNotification OBJECT IDENTIFIER ::= { sleV2EthernetService 4 }

		
		-- 1.3.6.1.4.1.6296.102.7.2.10.4.1
		sleV2EthernetServiceEnableStatusChanged NOTIFICATION-TYPE
			OBJECTS { sleV2EthernetServiceControlRequest, sleV2EthernetServiceControlTimeStamp, sleV2EthernetServiceControlReqResult, sleV2EthernetServiceControlEnableStatus }
			STATUS current
			DESCRIPTION 
				"setEnableStatus"
			::= { sleV2EthernetServiceNotification 1 }

		
		-- 1.3.6.1.4.1.6296.102.7.2.10.4.2
		sleV2EthernetServiceEnableManagementChanged NOTIFICATION-TYPE
			OBJECTS { sleV2EthernetServiceControlRequest, sleV2EthernetServiceControlTimeStamp, sleV2EthernetServiceControlReqResult, sleV2EthernetServiceControlEnableManagement }
			STATUS current
			DESCRIPTION 
				"setEnableManagement"
			::= { sleV2EthernetServiceNotification 2 }

		
		-- 1.3.6.1.4.1.6296.102.7.2.10.4.3
		sleV2EthernetServiceHealthCheckChanged NOTIFICATION-TYPE
			OBJECTS { sleV2EthernetServiceControlRequest, sleV2EthernetServiceControlTimeStamp, sleV2EthernetServiceControlReqResult, sleV2EthernetServiceControlHealthCheckPort, sleV2EthernetServiceControlHealthCheckVid
				 }
			STATUS current
			DESCRIPTION 
				"setHealthCheck"
			::= { sleV2EthernetServiceNotification 3 }

		
		-- 1.3.6.1.4.1.6296.102.7.2.10.4.4
		sleV2EthernetServiceHealthCheckDeleted NOTIFICATION-TYPE
			OBJECTS { sleV2EthernetServiceControlRequest, sleV2EthernetServiceControlTimeStamp, sleV2EthernetServiceControlReqResult }
			STATUS current
			DESCRIPTION 
				"delHealthCheck"
			::= { sleV2EthernetServiceNotification 4 }

		
		-- 1.3.6.1.4.1.6296.102.7.2.10.4.5
		sleV2EthernetServiceSidForRtModeCreated NOTIFICATION-TYPE
			OBJECTS { sleV2EthernetServiceControlRequest, sleV2EthernetServiceControlTimeStamp, sleV2EthernetServiceControlReqResult, sleV2EthernetServiceControlSid, sleV2EthernetServiceControlType, 
				sleV2EthernetServiceControlRtCustomerPort, sleV2EthernetServiceControlRtCustomerVid, sleV2EthernetServiceControlRtNetworkPort, sleV2EthernetServiceControlRtNetworkVid, sleV2EthernetServiceControlRtEnableManagement
				 }
			STATUS current
			DESCRIPTION 
				"setSidForRT"
			::= { sleV2EthernetServiceNotification 5 }

		
		-- 1.3.6.1.4.1.6296.102.7.2.10.4.6
		sleV2EthernetServiceSidForCotModeCreated NOTIFICATION-TYPE
			OBJECTS { sleV2EthernetServiceControlRequest, sleV2EthernetServiceControlTimeStamp, sleV2EthernetServiceControlReqResult, sleV2EthernetServiceControlSid, sleV2EthernetServiceControlType, 
				sleV2EthernetServiceControlCotExternalPort, sleV2EthernetServiceControlCotExternalVid, sleV2EthernetServiceControlCotInternalPort, sleV2EthernetServiceControlCotInternalVid }
			STATUS current
			DESCRIPTION 
				"setSidForCOT"
			::= { sleV2EthernetServiceNotification 6 }

		
		-- 1.3.6.1.4.1.6296.102.7.2.10.4.7
		sleV2EthernetServiceSidDeleted NOTIFICATION-TYPE
			OBJECTS { sleV2EthernetServiceControlRequest, sleV2EthernetServiceControlTimeStamp, sleV2EthernetServiceControlReqResult, sleV2EthernetServiceControlSid }
			STATUS current
			DESCRIPTION 
				"delService"
			::= { sleV2EthernetServiceNotification 7 }

		
		-- 1.3.6.1.4.1.6296.102.7.3
		sleV2Security6 OBJECT IDENTIFIER ::= { sleV2Security 3 }

		
		-- 1.3.6.1.4.1.6296.102.7.4
		sleV2SecurityGroup OBJECT-GROUP
			OBJECTS { sleV2Security4ACLFlowIndex, sleV2Security4ACLFlowName, sleV2Security4ACLFlowSrcIpAddr, sleV2Security4ACLFlowSrcIpAddrMask, sleV2Security4ACLFlowDstIpAddr, 
				sleV2Security4ACLFlowDstIpAddrMask, sleV2Security4ACLFlowProtocolType, sleV2Security4ACLFlowTcpSrcStartPort, sleV2Security4ACLFlowTcpSrcEndPort, sleV2Security4ACLFlowTcpDstStartPort, 
				sleV2Security4ACLFlowTcpDstEndPort, sleV2Security4ACLFlowTcpFlag, sleV2Security4ACLFlowUdpSrcStartPort, sleV2Security4ACLFlowUdpSrcEndPort, sleV2Security4ACLFlowUdpDstStartPort, 
				sleV2Security4ACLFlowUdpDstEndPort, sleV2Security4ACLFlowIcmpType, sleV2Security4ACLFlowIcmpCode, sleV2Security4ACLFlowControlTcpFlag, sleV2Security4ACLFlowClassIndex, 
				sleV2Security4ACLFlowClassID, sleV2Security4ACLFlowClassName, sleV2Security4ACLFlowPolicyIndex, sleV2Security4ACLFlowPolicyID, sleV2Security4ACLFlowPolicyName, 
				sleV2Security4ACLClassIndex, sleV2Security4ACLClassName, sleV2Security4ACLClassFlowCnt, sleV2Security4ACLClassFlowIndex, sleV2Security4ACLClassFlowID, 
				sleV2Security4ACLClassFlowName, sleV2Security4ACLClassPolicyIndex, sleV2Security4ACLClassPolicyID, sleV2Security4ACLClassPolicyName, sleV2Security4ACLPolicyIndex, 
				sleV2Security4ACLPolicyName, sleV2Security4ACLPolicyFlowCnt, sleV2Security4ACLPolicyClassCnt, sleV2Security4ACLPolicyPriority, sleV2Security4ACLPolicyMatchFlag, 
				sleV2Security4ACLPolicyNomatchFlag, sleV2Security4ACLPolicyFlowClassIndex, sleV2Security4ACLPolicyFlowClassType, sleV2Security4ACLPolicyFlowClassID, sleV2Security4ACLFlowControlRequest, 
				sleV2Security4ACLFlowControlStatus, sleV2Security4ACLFlowControlTimer, sleV2Security4ACLFlowControlTimeStamp, sleV2Security4ACLFlowControlReqResult, sleV2Security4ACLFlowControlIndex, 
				sleV2Security4ACLFlowControlName, sleV2Security4ACLFlowControlSrcIpAddr, sleV2Security4ACLFlowControlSrcIpAddrMask, sleV2Security4ACLFlowControlDstIpAddr, sleV2Security4ACLFlowControlDstIpAddrMask, 
				sleV2Security4ACLFlowControlProtocolType, sleV2Security4ACLFlowControlTcpSrcStartPort, sleV2Security4ACLFlowControlTcpSrcEndPort, sleV2Security4ACLFlowControlTcpDstStartPort, sleV2Security4ACLFlowControlTcpDstEndPort, 
				sleV2Security4ACLFlowControlUdpSrcStartPort, sleV2Security4ACLFlowControlUdpSrcEndPort, sleV2Security4ACLFlowControlUdpDstStartPort, sleV2Security4ACLFlowControlUdpDstEndPort, sleV2Security4ACLFlowControlIcmpType, 
				sleV2Security4ACLFlowControlIcmpCode, sleV2Security4ACLFlowControlHdrlen, sleV2Security4ACLClassControlRequest, sleV2Security4ACLClassControlStatus, sleV2Security4ACLClassControlTimer, 
				sleV2Security4ACLClassControlTimeStamp, sleV2Security4ACLClassControlReqResult, sleV2Security4ACLClassControlIndex, sleV2Security4ACLClassControlName, sleV2Security4ACLClassFlowControlRequest, 
				sleV2Security4ACLClassFlowControlStatus, sleV2Security4ACLClassFlowControlTimer, sleV2Security4ACLClassFlowControlTimeStamp, sleV2Security4ACLClassFlowControlReqResult, sleV2Security4ACLClassFlowControlClassIndex, 
				sleV2Security4ACLClassFlowControlFlowIndex, sleV2Security4ACLClassFlowControlFlowID, sleV2Security4ACLPolicyControlRequest, sleV2Security4ACLPolicyControlStatus, sleV2Security4ACLPolicyControlTimer, 
				sleV2Security4ACLPolicyControlTimeStamp, sleV2Security4ACLPolicyControlReqResult, sleV2Security4ACLPolicyControlIndex, sleV2Security4ACLPolicyControlName, sleV2Security4ACLPolicyControlPriority, 
				sleV2Security4ACLPolicyControlMatchFlag, sleV2Security4ACLPolicyControlNomatchFlag, sleV2Security4ACLPolicyFlowClassControlRequest, sleV2Security4ACLPolicyFlowClassControlStatus, sleV2Security4ACLPolicyFlowClassControlTimer, 
				sleV2Security4ACLPolicyFlowClassControlTimeStamp, sleV2Security4ACLPolicyFlowClassControlReqResult, sleV2Security4ACLPolicyFlowClassControlPolicyIndex, sleV2Security4ACLPolicyFlowClassControlIndex, sleV2Security4ACLPolicyFlowClassControlType, 
				sleV2Security4ACLPolicyFlowClassControlFlowID, sleV2Security4ACLPolicyFlowClassControlClassID, sleV2SecuritySACLName, sleV2SecuritySACLSrcIpaddr, sleV2SecuritySACLSrcPrefixLength, 
				sleV2SecuritySACLDstIpAddr, sleV2SecuritySACLDstPrefixLength, sleV2SecuritySACLProtocolType, sleV2SecuritySACLTcpflag, sleV2SecuritySACLIcmpType, 
				sleV2SecuritySACLIcmpCode, sleV2SecuritySACLPriority, sleV2SecuritySACLMatchAction, sleV2SecuritySACLNomatchAction, sleV2SecuritySACLControlRequest, 
				sleV2SecuritySACLControlStatus, sleV2SecuritySACLControlTimer, sleV2SecuritySACLControlTimeStamp, sleV2SecuritySACLControlReqResult, sleV2SecuritySACLControlName, 
				sleV2SecuritySACLControlSrcIpaddr, sleV2SecuritySACLControlSrcPrefixLength, sleV2SecuritySACLControlDstIpaddr, sleV2SecuritySACLControlDstPrefixLength, sleV2SecuritySACLControlProtocolType, 
				sleV2SecuritySACLControlTcpflag, sleV2SecuritySACLControlIcmpType, sleV2SecuritySACLControlIcmpCode, sleV2SecuritySACLControlPriority, sleV2SecuritySACLControlMatchAction, 
				sleV2SecuritySACLControlNomatchAction, sleV2Security4ACLPolicyFlowClassName, sleV2Security4ACLFlowHdrlen, sleV2SecuritySACLDstL4Port, sleV2SecuritySACLSrcL4Port, 
				sleV2SecuritySACLControlSrcL4Port, sleV2SecuritySACLControlDstL4Port, sleV2SecurityACLTotalPacket, sleV2SecurityACLSrcHistoryIpAddr, sleV2SecurityACLStatisticsControlRequest, 
				sleV2SecurityACLStatisticsControlStatus, sleV2SecurityACLStatisticsControlTimer, sleV2SecurityACLStatisticsControlTimeStamp, sleV2SecurityACLStatisticsControlReqResult, sleV2SecurityACLStatisticsBaseControlTimer, 
				sleV2SecurityACLStatisticsBaseControlStatus, sleV2SecurityACLStatisticsBaseControlRequest, sleV2SecurityACLStatisticsControlName, sleV2SecurityACLSrcHistoryIndex, sleV2SecurityACLStatisticsBaseControlTimeStamp, 
				sleV2SecurityACLStatisticsBaseControlReqResult, sleV2CpuPacketFilterIndex, sleV2CpuPacketFilterName, sleV2CpuPacketFilterCreationTime, sleV2CpuPacketFilterElapsedtimeAfterClear, 
				sleV2CpuPacketFilterStage, sleV2CpuPacketFilterPriority, sleV2CpuPacketFilterAction, sleV2CpuPacketFilterActionRateLimit, sleV2CpuPacketFilterActionBurstSize, 
				sleV2CpuPacketFilterActionTpid, sleV2CpuPacketFilterActionPcp, sleV2CpuPacketFilterActionVid, sleV2CpuPacketFilterActionTagPosition, sleV2CpuPacketFilterMatchType, 
				sleV2CpuPacketFilterMatchCos, sleV2CpuPacketFilterMatchPort, sleV2CpuPacketFilterMatchVid, sleV2CpuPacketFilterMatchTagPosition, sleV2CpuPacketFilterMatchOffset, 
				sleV2CpuPacketFilterMatchLength, sleV2CpuPacketFilterMatchData, sleV2CpuPacketFilterMatchMask, sleV2CpuPacketFilterMatchDesc, sleV2CpuPacketFilterControlRequest, 
				sleV2CpuPacketFilterControlStatus, sleV2CpuPacketFilterControlTimer, sleV2CpuPacketFilterControlTimeStamp, sleV2CpuPacketFilterControlReqResult, sleV2CpuPacketFilterControlIndex, 
				sleV2CpuPacketFilterControlName, sleV2CpuPacketFilterControlStage, sleV2CpuPacketFilterControlPriority, sleV2CpuPacketFilterControlAction, sleV2CpuPacketFilterControlActionRateLimit, 
				sleV2CpuPacketFilterControlActionBurstSize, sleV2CpuPacketFilterControlActionTpid, sleV2CpuPacketFilterControlActionPcp, sleV2CpuPacketFilterControlActionVid, sleV2CpuPacketFilterControlActionTagPosition, 
				sleV2CpuPacketFilterControlMatchType, sleV2CpuPacketFilterControlMatchCos, sleV2CpuPacketFilterControlMatchPort, sleV2CpuPacketFilterControlMatchVid, sleV2CpuPacketFilterControlMatchTagPosition, 
				sleV2CpuPacketFilterControlMatchOffset, sleV2CpuPacketFilterControlMatchLength, sleV2CpuPacketFilterControlMatchData, sleV2CpuPacketFilterControlMatchMask, sleV2CpuPacketFilterControlMatchDesc, 
				sleV2CpuPacketFilterMatchIndex, sleV2CpuPacketFilterMatchVidmap, sleV2CpuPacketFilterMatchTpid, sleV2CpuPacketFilterMatchPcp, sleV2CpuPacketFilterControlMatchVidmap, 
				sleV2CpuPacketFilterControlMatchTpid, sleV2CpuPacketFilterControlMatchPcp, sleV2Security4ACLFlowIpFlag, sleV2Security4ACLFlowControlIpFlag, sleV2VlanOperationIndex, 
				sleV2VlanOperationName, sleV2VlanOperationStage, sleV2VlanOperationPort, sleV2VlanOperationEtherType, sleV2VlanOperationIpProtocol, 
				sleV2VlanOperationArpSip, sleV2VlanOperationArpSipPfxLen, sleV2VlanOperationDip, sleV2VlanOperationDipPfxLen, sleV2VlanOperationAction, 
				sleV2VlanOperationActionVid, sleV2VlanOperationProiroty, sleV2VlanOperationControlIndex, sleV2VlanOperationControlName, sleV2VlanOperationControlStage, 
				sleV2VlanOperationControlProiroty, sleV2VlanOperationControlPort, sleV2VlanOperationControlEtherType, sleV2VlanOperationControlIpProtocol, sleV2VlanOperationControlArpSip, 
				sleV2VlanOperationControlArpSipPfxLen, sleV2VlanOperationControlDip, sleV2VlanOperationControlDipPfxLen, sleV2VlanOperationControlAction, sleV2VlanOperationControlActionVid, 
				sleV2VlanOperationSip, sleV2VlanOperationSipPfxLen, sleV2VlanOperationControlSip, sleV2VlanOperationControlSipPfxLen, sleV2VlanOperationOuterVlan, 
				sleV2VlanOperationInnerVlan, sleV2VlanOperationControlOuterVlan, sleV2VlanOperationControlInnerVlan, sleV2EthernetServiceEnableStatus, sleV2EthernetServiceEnableManagement, 
				sleV2EthernetServiceHealthCheckPort, sleV2EthernetServiceHealthCheckVid, sleV2EthernetServiceSid, sleV2EthernetServiceType, sleV2EthernetServiceRtCustomerPort, 
				sleV2EthernetServiceRtCustomerVid, sleV2EthernetServiceRtNetworkPort, sleV2EthernetServiceRtNetworkVid, sleV2EthernetServiceRtEnableManagement, sleV2EthernetServiceCotExternalPort, 
				sleV2EthernetServiceCotExternalVid, sleV2EthernetServiceCotInternalPort, sleV2EthernetServiceCotInternalVid, sleV2EthernetServiceControlRequest, sleV2EthernetServiceControlStatus, 
				sleV2EthernetServiceControlTimer, sleV2EthernetServiceControlTimeStamp, sleV2EthernetServiceControlReqResult, sleV2EthernetServiceControlEnableStatus, sleV2EthernetServiceControlEnableManagement, 
				sleV2EthernetServiceControlHealthCheckPort, sleV2EthernetServiceControlHealthCheckVid, sleV2EthernetServiceControlSid, sleV2EthernetServiceControlType, sleV2EthernetServiceControlRtCustomerPort, 
				sleV2EthernetServiceControlRtCustomerVid, sleV2EthernetServiceControlRtNetworkPort, sleV2EthernetServiceControlRtNetworkVid, sleV2EthernetServiceControlRtEnableManagement, sleV2EthernetServiceControlCotExternalPort, 
				sleV2EthernetServiceControlCotExternalVid, sleV2EthernetServiceControlCotInternalPort, sleV2EthernetServiceControlCotInternalVid, sleV2Security4ACLClassFlowClassName, sleV2Security4ACLClassFlowControlClassName, 
				sleV2Security4ACLPolicyControlFlowID, sleV2Security4ACLPolicyControlClassID, sleV2SecurityACLFlowInetAddrType, sleV2SecurityACLFlowSrcInetAddr, sleV2SecurityACLFlowDstInetAddr, 
				sleV2SecurityACLFlowSrcInetAddrLen, sleV2SecurityACLFlowDstInetAddrLen, sleV2SecurityACLFlowControlInetAddrType, sleV2SecurityACLFlowControlSrcInetAddr, sleV2SecurityACLFlowControlDstInetAddr, 
				sleV2SecurityACLFlowControlSrcInetAddrLen, sleV2SecurityACLFlowControlDstInetAddrLen, sleV2Security4ACLGroupIfindex, sleV2Security4ACLGroupIfType, sleV2Security4ACLGroupIfName, 
				sleV2Security4ACLGroupIfPriority, sleV2Security4ACLGroupIfControlRequest, sleV2Security4ACLGroupIfControlStatus, sleV2Security4ACLGroupIfControlTimer, sleV2Security4ACLGroupIfControlReqResult, 
				sleV2Security4ACLGroupIfControlTimeStamp, sleV2Security4ACLGroupIfConrolIndex, sleV2Security4ACLGroupIfControlType, sleV2Security4ACLGroupIfControlName, sleV2Security4ACLGroupIfControlPriority, 
				sleV2SecurityACLStatisticsBaseControlSyslogMode, sleV2SecurityACLStatisticsSyslogStatus, sleV2VlanOperationControlRequest, sleV2VlanOperationControlStatus, sleV2VlanOperationControlTimer, 
				sleV2VlanOperationControlTimeStamp, sleV2VlanOperationControlReqResult }
			STATUS current
			DESCRIPTION 
				"Description."
			::= { sleV2Security 4 }

		
		-- 1.3.6.1.4.1.6296.102.7.5
		sleV2SecurityNotificationGroup NOTIFICATION-GROUP
			NOTIFICATIONS { sleACLFlowCreated, sleACLFlowChanged, sleACLFlowDestroyed, sleACLFlowAllDestroyed, sleACLClassCreated, 
				sleACLClassDestroyed, sleACLClassAllDestroyed, sleACLClassFlowAdded, sleACLClassFlowDeleted, sleACLClassFlowAllDeleted, 
				sleACLPolicyCreated, sleACLPolicyInfoChanged, sleACLPolicyMatchActionChanged, sleACLPolicyNomatchActionChanged, sleACLPolicyDestroyed, 
				sleACLPolicyFlowAdded, sleACLPolicyFlowDeleted, sleACLPolicyAllFlowDeleted, sleACLPolicyAllClassDeleted, sleACLPolicyAllFlowClassDeleted, 
				sleSACLCreated, sleSACLDestroyed, sleSACLAllDestroyed, sleV2SecurityACLStatisticsSyslogModeChanged, sleV2SecurityACLStatisticsCleared, 
				sleV2CpuPacketFilterAdded, sleV2CpuPacketFilterDeleted, sleV2CpuPacketFilterActionChanged, sleV2CpuPacketFilterMatchChanged, sleV2VlanOperationCreated, 
				sleV2VlanOperationDeleted, sleV2EthernetServiceEnableStatusChanged, sleV2EthernetServiceEnableManagementChanged, sleV2EthernetServiceHealthCheckChanged, sleV2EthernetServiceHealthCheckDeleted, 
				sleV2EthernetServiceSidForRtModeCreated, sleV2EthernetServiceSidForCotModeCreated, sleV2EthernetServiceSidDeleted, sleACLFlowExCreated, sleACLFlowExChanged, 
				sleV2Security4ACLGroupIfProfileAdd, sleV2Security4ACLGroupIfProfileDelete }
			STATUS current
			DESCRIPTION 
				"Description."
			::= { sleV2Security 5 }

		
	
	END

--
-- slev2-security-mib.mib
--
