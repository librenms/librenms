CISCOSB-TUNNEL-MIB DEFINITIONS ::= BEGIN

IMPORTS
    switch001                FROM CISCOSB-MIB
    OBJECT-TYPE,Unsigned32, IpAddress,
    MODULE-IDENTITY     FROM SNMPv2-SMI
--    TruthValue          FROM SNMPv2-TC
    IANAtunnelType      FROM IANAifType-MIB
    DnsName             FROM DNS-SERVER-MIB;


rlTunnel MODULE-IDENTITY
         LAST-UPDATED "200703280000Z"
		 ORGANIZATION "Cisco Small Business"

		 CONTACT-INFO
		 "Postal: 170 West Tasman Drive
		 San Jose , CA 95134-1706
		 USA

		 Website: Cisco Small Business Home http://www.cisco.com/smb>;,
		 Cisco Small Business Support Community <http://www.cisco.com/go/smallbizsupport>"

         DESCRIPTION
                "The private MIB module definition for Tunneling."
         REVISION "200703280000Z"
         DESCRIPTION
                "Initial revision."
        ::= { switch001 122 }

rlTunnelIsatapStatus  OBJECT-TYPE
    SYNTAX INTEGER {
       enable(1),
       disable(2)
       }
    MAX-ACCESS  read-write
    STATUS      current
    DESCRIPTION
        "The ISATAP status."
    DEFVAL  { disable }
    ::= { rlTunnel 1 }


rlTunnelIsatapRobustness  OBJECT-TYPE
    SYNTAX  Unsigned32 (1 .. 20)
--  UNITS   "seconds"
    MAX-ACCESS  read-write
    STATUS      current
    DESCRIPTION
        "specifies how many DNS Querys and Router Solicitations
         should be sent to get the corresponding reply."
    DEFVAL  { 3 }
    ::= { rlTunnel 2 }


rlTunnelIsatapDnsHostName OBJECT-TYPE
    SYNTAX      DnsName
    MAX-ACCESS  read-write
    STATUS      current
    DESCRIPTION
        "The domain name for ISATAP."
    ::= { rlTunnel 3 }

rlTunnelIsatapQueryInterval OBJECT-TYPE
    SYNTAX  Unsigned32 (10 .. 3600)
--  UNITS   "seconds"
    MAX-ACCESS  read-write
    STATUS      current
    DESCRIPTION
        "specifies the time interval between sending of
         DNS Queries before receiving the first reply from the DNS Server."
    DEFVAL  { 10 }
    ::= { rlTunnel 4 }

rlTunnelIsatapRSInterval OBJECT-TYPE
    SYNTAX  Unsigned32 (10 .. 3600)
--  UNITS   "seconds"
    MAX-ACCESS  read-write
    STATUS      current
    DESCRIPTION
        "specifies the time interval between sending of Router
         Solicitations before receiving the first reply from the ISATAP Router."
    DEFVAL  { 10 }
    ::= { rlTunnel 5 }

rlTunnelIsatapMinQueryInterval OBJECT-TYPE
    SYNTAX  Unsigned32 (0 .. 3600)
--  UNITS   "seconds"
    MAX-ACCESS  read-only
    STATUS      current
    DESCRIPTION
        "specifies the minimum time interval between between successive queries
         of same advertising ISATAP interface."
    DEFVAL  { 0 }
    ::= { rlTunnel 6 }

rlTunnelIsatapMinRSInterval OBJECT-TYPE
    SYNTAX  Unsigned32 (0 .. 3600)
--  UNITS   "seconds"
    MAX-ACCESS  read-only
    STATUS      current
    DESCRIPTION
        "specifies the minimum time between successive solicitations of the
         same advertising ISATAP interface."
    DEFVAL  { 0 }
    ::= { rlTunnel 7 }

rlTunnelIsatapRouterAddress OBJECT-TYPE
    SYNTAX  IpAddress
    MAX-ACCESS  read-only
    STATUS      current
    DESCRIPTION
        "specifies the IPv4 address of ISATAP Router."
    DEFVAL  { 0 }
    ::= { rlTunnel 8 }

rlTunnelIsatapLocalIPv4Address OBJECT-TYPE
    SYNTAX  IpAddress
    MAX-ACCESS  read-only
    STATUS      current
    DESCRIPTION
        "specifies the IPv4 address currently used as IPv4 source address
         for ISATAP Tunnel."
    DEFVAL  { 0 }
    ::= { rlTunnel 9 }


    END
