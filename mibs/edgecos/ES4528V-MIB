--------------------------------------------------
--Version Number: 20060410001
--------------------------------------------------

ES4528V-MIB DEFINITIONS ::= BEGIN

IMPORTS
       
        MODULE-IDENTITY, OBJECT-TYPE, Unsigned32, Integer32, Counter32,IpAddress,
        NOTIFICATION-TYPE, enterprises
                FROM SNMPv2-SMI
        DisplayString, RowStatus, TruthValue
                FROM SNMPv2-TC
        MacAddress
                FROM TOKEN-RING-RMON-MIB                
        PortList, VlanIndex
                FROM Q-BRIDGE-MIB
        InetAddressType, InetAddress
                FROM INET-ADDRESS-MIB        
        InterfaceIndex, ifIndex
               FROM IF-MIB
        EnabledStatus 
                FROM P-BRIDGE-MIB
		BridgeId, Timeout, dot1dStpPort,dot1dStpPortEntry, MacAddress
		FROM BRIDGE-MIB
--        dot1xAuthConfigEntry
--                FROM IEEE8021-PAE-MIB
	Timeout
		FROM BRIDGE-MIB;

accton              OBJECT IDENTIFIER ::= { enterprises 259 }
--snmpMgt             OBJECT IDENTIFIER ::= { accton 6 }
--cheetahSwitchMgt    OBJECT IDENTIFIER ::= { snmpMgt 10 }
edgecore             OBJECT IDENTIFIER ::= { accton 8 }
cheetahSwitchMgt    OBJECT IDENTIFIER ::= { edgecore 1 }

ES4528VMIB MODULE-IDENTITY
        LAST-UPDATED "200109060000Z"
        ORGANIZATION "Accton Technology Corp."
        CONTACT-INFO
                "Accton Technology Corp.
                 Customer Service

                 Postal: No. 1 Creation Rd. III,
                         Science-based Industrial Park,Hsinchu 300-77, 
                         Taiwan, R.O.C.
                         
                 Tel: +886-3-5770270
                
                 E-mail: support@accton.com.tw"
        DESCRIPTION
                "The MIB module for ES3526XA/ES3510."
        REVISION "200109060000Z"
        DESCRIPTION
                "Initial version of this MIB."
        ::= { cheetahSwitchMgt 10 }


ES4528VMIBObjects       OBJECT IDENTIFIER ::= { ES4528VMIB 1 }
ES4528VNotifications    OBJECT IDENTIFIER ::= { ES4528VMIB 2 }
ES4528VConformance      OBJECT IDENTIFIER ::= { ES4528VMIB 3 }

--supported groups
switchMgt           OBJECT IDENTIFIER ::= { ES4528VMIBObjects 1 }
portMgt             OBJECT IDENTIFIER ::= { ES4528VMIBObjects 2 }
trunkMgt            OBJECT IDENTIFIER ::= { ES4528VMIBObjects 3 }
lacpMgt             OBJECT IDENTIFIER ::= { ES4528VMIBObjects 4 }
staMgt              OBJECT IDENTIFIER ::= { ES4528VMIBObjects 5 }
--tftpMgt             OBJECT IDENTIFIER ::= { ES4528VMIBObjects 6 }
restartMgt          OBJECT IDENTIFIER ::= { ES4528VMIBObjects 7 }
--mirrorMgt           OBJECT IDENTIFIER ::= { ES4528VMIBObjects 8 }
--igmpSnoopMgt        OBJECT IDENTIFIER ::= { ES4528VMIBObjects 9 }
--ipMgt               OBJECT IDENTIFIER ::= { ES4528VMIBObjects 10 }
--bcastStormMgt       OBJECT IDENTIFIER ::= { ES4528VMIBObjects 11 }
vlanMgt             OBJECT IDENTIFIER ::= { ES4528VMIBObjects 12 }
--priorityMgt         OBJECT IDENTIFIER ::= { ES4528VMIBObjects 13 }
--trapDestMgt         OBJECT IDENTIFIER ::= { ES4528VMIBObjects 14 }
--qosMgt              OBJECT IDENTIFIER ::= { ES4528VMIBObjects 16 }
--securityMgt         OBJECT IDENTIFIER ::= { ES4528VMIBObjects 17 }
--sysLogMgt           OBJECT IDENTIFIER ::= { ES4528VMIBObjects 19 }
--lineMgt             OBJECT IDENTIFIER ::= { ES4528VMIBObjects 20 }
sysTimeMgt          OBJECT IDENTIFIER ::= { ES4528VMIBObjects 23 }
fileMgt             OBJECT IDENTIFIER ::= { ES4528VMIBObjects 24 }
--dnsMgt              OBJECT IDENTIFIER ::= { ES4528VMIBObjects 26 }
--mvrMgt              OBJECT IDENTIFIER ::= { ES4528VMIBObjects 44 }
--dhcpSnoopMgt        OBJECT IDENTIFIER ::= { ES4528VMIBObjects 46 }
--clusterMgt          OBJECT IDENTIFIER ::= { ES4528VMIBObjects 47 }
--ipSrcGuardMgt       OBJECT IDENTIFIER ::= { ES4528VMIBObjects 48 }

-- -------------------------------------------------------------
-- Textual Conventions 
-- -------------------------------------------------------------
KeySegment ::= TEXTUAL-CONVENTION
    STATUS      current
    DESCRIPTION
        "The total length of the key is 1024 characters,
         it is divided into 8 parts and stored in 8 separated mib
         variables as below:
                    
             Key1: part 1 of the key (1-128)
             Key2: part 2 of the key (129-256)
             Key3: part 3 of the key (257-384)
             Key4: part 4 of the key (385-512)
             Key5: part 5 of the key (513-640)
             Key6: part 6 of the key (641-768)
             Key7: part 7 of the key (769-896)
             Key8: part 8 of the key (897-1024)
                    
         Please note that if the key string is less then 1024 characters,
         the remaining part of the string will be filled by a zero-length string.
         For example, if the length of the key is 129,
         we will get a string of length 128 in Key1, and 
         a string of length 1 in Key2, 
         moreover, Key3 to Key8 will all be zero-length strings."
    SYNTAX      DisplayString(SIZE(0..128))   

ValidStatus ::= TEXTUAL-CONVENTION
    STATUS      current
    DESCRIPTION
        "A simple status value for the object to create and destroy
         a table entry. This is a simplified variant of RowStatus as it
         supports only two values. Setting it to valid(1) creates an entry.
         Setting it to invalid(2) destroys an entry."
    SYNTAX      INTEGER { valid(1), invalid(2) }

StaPathCostMode ::= TEXTUAL-CONVENTION
     STATUS  current
     DESCRIPTION 
         "The path cost mode of a spanning tree algorithm, short(1) indicates 
          that we retrieve/configure the spanning tree path cost as a 16 bit 
          value and long(2) indicates that we retrieve/configure the spanning 
          tree path cost as a 32 bit value."
     SYNTAX      INTEGER { short(1), long(2) }
    
--
-- switchMgt
--

switchManagementVlan OBJECT-TYPE
        SYNTAX      INTEGER (1..4092)
        MAX-ACCESS  read-write
        STATUS      current
        DESCRIPTION "The VLAN on which management is done."
        ::= { switchMgt 1 }

switchNumber OBJECT-TYPE
        SYNTAX      Integer32
        MAX-ACCESS  read-only
        STATUS      current
        DESCRIPTION "The total number of switches present on this system."
        ::= { switchMgt 2 }

switchInfoTable OBJECT-TYPE
        SYNTAX      SEQUENCE OF SwitchInfoEntry
        MAX-ACCESS  not-accessible
        STATUS      current
        DESCRIPTION "Table of descriptive and status information about
                     switches in this system."
        ::= { switchMgt 3 }

switchInfoEntry OBJECT-TYPE
        SYNTAX      SwitchInfoEntry
        MAX-ACCESS  not-accessible
        STATUS      current
        DESCRIPTION "An entry in the table, containing information
                     about a single switch in this system. The value
                     is always equal 1 in ES4528V product."
        INDEX       { swUnitIndex }
        ::= { switchInfoTable 1 }

SwitchInfoEntry ::= SEQUENCE
{
    swUnitIndex             Integer32,
    swHardwareVer           DisplayString,
    swMicrocodeVer          DisplayString,
    swLoaderVer             DisplayString,
    swBootRomVer            DisplayString,
    swOpCodeVer             DisplayString,
    swPortNumber            Integer32,
    swPowerStatus           INTEGER,
    swRoleInSystem          INTEGER,
    swSerialNumber          DisplayString,
--    swExpansionSlot1        INTEGER,
--    swExpansionSlot2        INTEGER,
    swServiceTag            DisplayString
}

swUnitIndex OBJECT-TYPE
        SYNTAX      Integer32
        MAX-ACCESS  not-accessible
        STATUS      current
        DESCRIPTION "This object identifies the switch within the system
                     for which this entry contains information. This
                     value can never be greater than switchNumber."
        ::= { switchInfoEntry 1 }

swHardwareVer OBJECT-TYPE
        SYNTAX      DisplayString (SIZE(0..20))
        MAX-ACCESS  read-only
        STATUS      current
        DESCRIPTION "Hardware version of the main board."
        ::= { switchInfoEntry 2 }

swMicrocodeVer OBJECT-TYPE
        SYNTAX      DisplayString (SIZE(0..20))
        MAX-ACCESS  read-only
        STATUS      current
        DESCRIPTION "Microcode version of the main board."
        ::= { switchInfoEntry 3 }

swLoaderVer OBJECT-TYPE
        SYNTAX      DisplayString (SIZE(0..20))
        MAX-ACCESS  read-only
        STATUS      current
        DESCRIPTION "Loader version of the main board."
        ::= { switchInfoEntry 4 }

swBootRomVer OBJECT-TYPE
        SYNTAX      DisplayString (SIZE(0..20))
        MAX-ACCESS  read-only
        STATUS      current
        DESCRIPTION "Boot ROM code version of the main board."
        ::= { switchInfoEntry 5 }

swOpCodeVer OBJECT-TYPE
        SYNTAX      DisplayString (SIZE(0..20))
        MAX-ACCESS  read-only
        STATUS      current
        DESCRIPTION "Operation code version of the main board."
        ::= { switchInfoEntry 6 }

swPortNumber OBJECT-TYPE
        SYNTAX      Integer32
        MAX-ACCESS  read-only
        STATUS      current
        DESCRIPTION "The total port number of this switch
                     (including expansion slot)."
        ::= { switchInfoEntry 7 }

swPowerStatus OBJECT-TYPE
        SYNTAX      INTEGER
                    {
                        internalPower(1),
                        redundantPower(2),
                        internalAndRedundantPower(3)
                    }
        MAX-ACCESS  read-only
        STATUS      current
        DESCRIPTION "Indicates the switch using internalPower(1),
                     redundantPower(2) or both(3)"
        ::= { switchInfoEntry 8 }

swRoleInSystem OBJECT-TYPE
        SYNTAX      INTEGER
                    {
                        master(1),
                        backupMaster(2),
                        slave(3)
                    }
        MAX-ACCESS  read-only
        STATUS      current
        DESCRIPTION "Indicates the switch is master(1), backupMaster(2)
                     or slave(3) in this system."
        ::= { switchInfoEntry 9 }

swSerialNumber OBJECT-TYPE
        SYNTAX      DisplayString (SIZE(0..80))
        MAX-ACCESS  read-only
        STATUS      current
        DESCRIPTION "Serial number of the switch."
        ::= { switchInfoEntry 10 }

-- swExpansionSlot1 OBJECT-TYPE
--        SYNTAX      INTEGER
--                    {
--                        notPresent(1),
--                        other(2),
--                        hundredBaseFxScMmf(3),
--                        hundredBaseFxScSmf(4),
--                        hundredBaseFxMtrjMmf(5),
--                        thousandBaseSxScMmf(6),
--                        thousandBaseSxMtrjMmf(7),
--                        thousandBaseXGbic(8),
--                        thousandBaseLxScSmf(9),
--                        thousandBaseT(10),
--                        stackingModule(11),
--                        thousandBaseSfp(12),
--                        tenHundredBaseT4port(13),
--                        tenHundredBaseFxMtrj4port(14),
--                        comboStackingSfp(15),
--                       tenHundredBaseT(16)
--                    }
--        MAX-ACCESS  read-only
--        STATUS      current
--        DESCRIPTION "Type of expansion module in this switch slot 1."
--        ::= { switchInfoEntry 11 }

--swExpansionSlot2 OBJECT-TYPE
--        SYNTAX      INTEGER
--                    {
--                        notPresent(1),
--                        other(2),
--                        hundredBaseFxScMmf(3),
--                        hundredBaseFxScSmf(4),
--                        hundredBaseFxMtrjMmf(5),
--                        thousandBaseSxScMmf(6),
--                        thousandBaseSxMtrjMmf(7),
--                        thousandBaseXGbic(8),
--                        thousandBaseLxScSmf(9),
--                        thousandBaseT(10),
--                        stackingModule(11),
--                        thousandBaseSfp(12),
--                        tenHundredBaseT4port(13),
--                        tenHundredBaseFxMtrj4port(14),
--                        comboStackingSfp(15),
--                        tenHundredBaseT(16)
--                    }
--        MAX-ACCESS  read-only
--        STATUS      current
--        DESCRIPTION "Type of expansion module in this switch slot 2."
--        ::= { switchInfoEntry 12 }

swServiceTag OBJECT-TYPE
        SYNTAX      DisplayString (SIZE(0..80))
        MAX-ACCESS  read-only
        STATUS      current
        DESCRIPTION "Service tag serial-number of the switch."
        ::= { switchInfoEntry 13 }

switchOperState OBJECT-TYPE
        SYNTAX      INTEGER
                    {
                        other(1),
                        unknown(2),
                        ok(3),
                        noncritical(4),
                        critical(5),
                        nonrecoverable(6)
                    }
        MAX-ACCESS  read-only
        STATUS      current
        DESCRIPTION "Global operation state of the switch."
        ::= { switchMgt 4 }

switchProductId     OBJECT IDENTIFIER ::= { switchMgt 5 }

swProdName OBJECT-TYPE
        SYNTAX      DisplayString (SIZE(0..127))
        MAX-ACCESS  read-only
        STATUS      current
        DESCRIPTION ""
        ::= { switchProductId 1 }

swProdManufacturer OBJECT-TYPE
        SYNTAX      DisplayString (SIZE(0..127))
        MAX-ACCESS  read-only
        STATUS      current
        DESCRIPTION ""
        ::= { switchProductId 2 }

swProdDescription OBJECT-TYPE
        SYNTAX      DisplayString (SIZE(0..127))
        MAX-ACCESS  read-only
        STATUS      current
        DESCRIPTION ""
        ::= { switchProductId 3 }

swProdVersion OBJECT-TYPE
        SYNTAX      DisplayString (SIZE(0..127))
        MAX-ACCESS  read-only
        STATUS      current
        DESCRIPTION ""
        ::= { switchProductId 4 }

swProdUrl OBJECT-TYPE
        SYNTAX      DisplayString (SIZE(0..127))
        MAX-ACCESS  read-only
        STATUS      current
        DESCRIPTION ""
        ::= { switchProductId 5 }

swIdentifier OBJECT-TYPE
        SYNTAX      INTEGER
        MAX-ACCESS  read-only
        STATUS      current
        DESCRIPTION "A unique identifier of which switch in the chassis is currently 
                     being looked at."
        ::= { switchProductId 6 }
        
swChassisServiceTag OBJECT-TYPE
        SYNTAX      DisplayString (SIZE(0..80))
        MAX-ACCESS  read-only
        STATUS      current
        DESCRIPTION "The service tag of the chassis this switch resides in."
        ::= { switchProductId 7 }

--switchIndivPowerTable OBJECT-TYPE
--        SYNTAX      SEQUENCE OF SwitchIndivPowerEntry
--        MAX-ACCESS  not-accessible
--        STATUS      current
--        DESCRIPTION "Table about statuses of individual powers."
--        ::= { switchMgt 6 }
--
--switchIndivPowerEntry OBJECT-TYPE
--        SYNTAX      SwitchIndivPowerEntry
--        MAX-ACCESS  not-accessible
--        STATUS      current
--        DESCRIPTION "Table about statuses of individual powers."
--        INDEX       { swIndivPowerUnitIndex, swIndivPowerIndex }
--        ::= { switchIndivPowerTable 1 }
--
--SwitchIndivPowerEntry ::= SEQUENCE
--{
--    swIndivPowerUnitIndex   Integer32,
--    swIndivPowerIndex       INTEGER,
--    swIndivPowerStatus      INTEGER
--}
--
--swIndivPowerUnitIndex OBJECT-TYPE
--        SYNTAX      Integer32
--        MAX-ACCESS  read-only
--        STATUS      current
--        DESCRIPTION "This is defined as swUnitIndex."
--        ::= { switchIndivPowerEntry 1 }
--
--swIndivPowerIndex OBJECT-TYPE
--        SYNTAX      INTEGER (1..2)
--        MAX-ACCESS  read-only
--        STATUS      current
--        DESCRIPTION "1 means internal power. 2 means external power."
--        ::= { switchIndivPowerEntry 2 }
--
--swIndivPowerStatus OBJECT-TYPE
--        SYNTAX      INTEGER
--                    {
--                        notPresent(1),
--                        green(2),
--                        red(3)
--                    }
--        MAX-ACCESS  read-only
--        STATUS      current
--        DESCRIPTION "notPresent(1) means not present. green(2) means
--                     up. red(3) means down."
--        ::= { switchIndivPowerEntry 3 }

amtrMgt      OBJECT IDENTIFIER   ::= { switchMgt 8 }
-- Address Management
amtrMacAddrAgingStatus OBJECT-TYPE
         SYNTAX     EnabledStatus
         MAX-ACCESS read-only
         STATUS     current
         DESCRIPTION "If this is enabled(1), the MAC address table will age out according to
                      its timer. If this is disabled(2), the MAC address table will not
                      age out."
         ::= { amtrMgt 3 } 
         
--
-- portMgt
--

portTable OBJECT-TYPE
        SYNTAX      SEQUENCE OF PortEntry
        MAX-ACCESS  not-accessible
        STATUS      current
        DESCRIPTION "Table of descriptive and status information about
                     configuration of each switch port (including expansion slot)
                     in this system. This table also contains information
                     about each trunk (similar to Cisco's EtherChannel)."
        ::= { portMgt 1 }

portEntry OBJECT-TYPE
        SYNTAX      PortEntry
        MAX-ACCESS  not-accessible
        STATUS      current
        DESCRIPTION "An entry in the table, containing information
                     about configuration in one switch port of the switch."
        INDEX       { portIndex }
        ::= { portTable 1 }

PortEntry ::= SEQUENCE
{
    portIndex                Integer32,
    portName                 DisplayString,
    portType                 INTEGER,
    portSpeedDpxCfg          INTEGER,
    portFlowCtrlCfg          INTEGER,
    portCapabilities         BITS,
    portAutonegotiation      INTEGER,
    portSpeedDpxStatus       INTEGER,
    portFlowCtrlStatus       INTEGER,
    portTrunkIndex           Integer32
}

portIndex OBJECT-TYPE
        SYNTAX      Integer32
        MAX-ACCESS  not-accessible
        STATUS      current
        DESCRIPTION "This is defined as ifIndex in the IF-MIB."
        ::= { portEntry 1 }

portName OBJECT-TYPE
        SYNTAX      DisplayString (SIZE(0..64))
        MAX-ACCESS  read-only
        STATUS      current
        DESCRIPTION "Indicates the port name. This is same as 
                     ifAlias in the IF-MIB (RFC2863 or later)."
        ::= { portEntry 2 }

portType OBJECT-TYPE
        SYNTAX      INTEGER
                    {
                        other(1),
                        hundredBaseTX(2),
                        hundredBaseFX(3),
                        thousandBaseSX(4),
                        thousandBaseLX(5),
                        thousandBaseT(6),
                        thousandBaseGBIC(7),
                        thousandBaseSfp(8),
                        hundredBaseFxScSingleMode(9),
                        hundredBaseFxScMultiMode(10)
                    }
        MAX-ACCESS  read-only
        STATUS      current
        DESCRIPTION "Indicates the port type."
        ::= { portEntry 3 }

portSpeedDpxCfg OBJECT-TYPE
        SYNTAX      INTEGER
                    {
                        reserved(1),
                        halfDuplex10(2),
                        fullDuplex10(3),
                        halfDuplex100(4),
                        fullDuplex100(5),
                        halfDuplex1000(6),
                        fullDuplex1000(7)
                    }
        MAX-ACCESS  read-write
        STATUS      current
        DESCRIPTION "Set the port speed and duplex mode as follows:
                         halfDuplex10(2)    - 10Mbps and half duplex mode
                         fullDuplex10(3)    - 10Mbps and full duplex mode
                         halfDuplex100(4)   - 100Mbps and half duplex mode
                         fullDuplex100(5)   - 100Mbps and full duplex mode
                         halfDuplex1000(6)  - 1000Mbps and half duplex mode
                         fullDuplex1000(7)  - 1000Mbps and full duplex mode
                     hundredBaseTX port can be set as
                         halfDuplex10(2)
                         fullDuplex10(3)
                         halfDuplex100(4)
                         fullDuplex100(5)
                     hundredBaseFX port can be set as
                         halfDuplex100(4)
                         fullDuplex100(5)
                     thousandBaseSX port can be set as
                         halfDuplex1000(6)
                         fullDuplex1000(7)
                     The actual operating speed and duplex of the port
                     is given by portSpeedDpxStatus."
        DEFVAL      { halfDuplex10 }
        ::= { portEntry 4 }

portFlowCtrlCfg OBJECT-TYPE
        SYNTAX      INTEGER
                    {
                        enabled(1),
                        disabled(2),
--                        backPressure(3),
--                        dot3xFlowControl(4)
                    }
        MAX-ACCESS  read-write
        STATUS      current
        DESCRIPTION "(1) Flow control mechanism is enabled.
                         If the port type is hundredBaseTX or thousandBaseSX:
                         When the port is operating in halfDuplex mode, the
                         port uses backPressure flow control mechanism. When
                         the port is operating in fullDuplex mode, the port
                         uses IEEE 802.3x flow control mechanism.
                         If the port type is hundredBaseFX:
                         When the port is operating in halfDuplex mode, the
                         port uses backPressure flow control mechanism. When
                         the port is operating in fullDuplex mode, Flow
                         control mechanism will not function.
                     (2) Flow control mechanism is disabled."
--                     (3) Flow control mechanism is backPressure.
--                         when the port is in fullDuplex mode.This flow control
--                         mechanism will not function.
--                     (4) Flow control mechanism is IEEE 802.3x flow control.
--                         when the port is in halfDuplex mode.This flow control
--                         mechanism will not function.
--                     hundredBaseTX and thousandBaseSX port can be set as:
--                         enabled(1),
--                         disabled(2),
--                         backPressure(3),
--                         dot3xFlowControl(4).
--                     hundredBaseFX port can be set as:
--                         enabled(1),
--                         disabled(2),
--                         backPressure(3).
--                     The actual flow control mechanism is used given by
--                     portFlowCtrlStatus."
        DEFVAL      { enabled }
        ::= { portEntry 5 }

portCapabilities OBJECT-TYPE
        SYNTAX      BITS
                    {
                        portCap10half(0),
                        portCap10full(1),
                        portCap100half(2),
                        portCap100full(3),
                        portCap1000half(4),
                        portCap1000full(5),
                        reserved6(6),
                        reserved7(7),
                        reserved8(8),
                        reserved9(9),
                        reserved10(10),
                        reserved11(11),
                        reserved12(12),
                        reserved13(13),
                        portCapSym(14),
                        portCapFlowCtrl(15)
                    }
        MAX-ACCESS  read-only
        STATUS      current
        DESCRIPTION "Port capabilities."
        ::= { portEntry 6 }

portAutonegotiation OBJECT-TYPE
        SYNTAX      INTEGER
                    {
                        enabled(1),
                        disabled(2)
                    }
        MAX-ACCESS  read-write
        STATUS      current
        DESCRIPTION "Whether autonegotiation is enabled."
        ::= { portEntry 7 }
                        
portSpeedDpxStatus OBJECT-TYPE
        SYNTAX      INTEGER
                    {
                        error(1),
                        halfDuplex10(2),
                        fullDuplex10(3),
                        halfDuplex100(4),
                        fullDuplex100(5),
                        halfDuplex1000(6),
                        fullDuplex1000(7)
                    }
        MAX-ACCESS  read-only
        STATUS      current
        DESCRIPTION "The operating speed and duplex mode of the
                     switched port. If this index is a trunk,
                     the speed is the speed of its individual members.
                     If this index is a trunk and the result
                     is inconsistent among its member ports, this value is
                     error(1)."
        ::= { portEntry 8 }

portFlowCtrlStatus OBJECT-TYPE
        SYNTAX      INTEGER
                    {
                        error(1),
                        backPressure(2),
                        dot3xFlowControl(3),
                        none(4)
                    }
        MAX-ACCESS  read-only
        STATUS      current
        DESCRIPTION "(2) BackPressure flow control machanism is used.
                     (3) IEEE 802.3 flow control machanism is used.
                     (4) Flow control mechanism is disabled.
                     If this index is a trunk and the result
                     is inconsistent among its member ports, this value is
                     error(1)."
        ::= { portEntry 9 }

portTrunkIndex OBJECT-TYPE
        SYNTAX      Integer32
        MAX-ACCESS  read-only
        STATUS      current
        DESCRIPTION "The trunk to which this port belongs. A value of 0
                    means that this port does not belong to any trunk.
                    A value greater than zero means that this port
                    belongs to trunk at trunkIndex, defined by the
                    corresponding trunkPorts."
        ::= { portEntry 10 }

--
-- trunkMgt
--

trunkMaxId OBJECT-TYPE
    SYNTAX      INTEGER
    MAX-ACCESS  read-only
    STATUS      current
    DESCRIPTION
        "The maximum number for a trunk identifier."
    ::= { trunkMgt 1 }

trunkValidNumber OBJECT-TYPE
    SYNTAX      INTEGER
    MAX-ACCESS  read-only
    STATUS      current
    DESCRIPTION
        "The number of valid trunks."
    ::= { trunkMgt 2 }

trunkTable OBJECT-TYPE
        SYNTAX      SEQUENCE OF TrunkEntry
        MAX-ACCESS  not-accessible
        STATUS      current
        DESCRIPTION "Table of descriptive and status information about
                     configuration of each trunk,
                     similar to Cisco EtherChannel."
        ::= { trunkMgt 3 }

trunkEntry OBJECT-TYPE
        SYNTAX      TrunkEntry
        MAX-ACCESS  not-accessible
        STATUS      current
        DESCRIPTION "An entry in the table, containing information
                     about configuration in one trunk of the switch."
        INDEX       { trunkIndex }
        ::= { trunkTable 1 }

TrunkEntry ::= SEQUENCE
{
    trunkIndex                Integer32,
    trunkPorts                PortList,
    trunkCreation             INTEGER,
    trunkStatus               ValidStatus
}

trunkIndex OBJECT-TYPE
        SYNTAX      Integer32
        MAX-ACCESS  not-accessible
        STATUS      current
        DESCRIPTION "This object identifies the trunk within the switch
                     for which this entry contains information."
        ::= { trunkEntry 1 }

trunkPorts OBJECT-TYPE
    SYNTAX      PortList
    MAX-ACCESS  read-write
    STATUS      current
    DESCRIPTION
        "The complete set of ports currently associated with
        this trunk."
    ::= { trunkEntry 2 }

trunkCreation OBJECT-TYPE
    SYNTAX      INTEGER
                {
                    static(1),
                    lacp(2)
                }
    MAX-ACCESS  read-only
    STATUS      current
    DESCRIPTION
        "A value of static(1) means a statically configured trunk.
         A value of lacp(2) means an LACP-configured trunk."
    ::= { trunkEntry 3 }

--trunkStatus OBJECT-TYPE
--    SYNTAX      ValidStatus
--    MAX-ACCESS  read-create
--    STATUS      current
--    DESCRIPTION
--        "Writing this to valid(1) creates an entry.
--         Writing this to invalid(2) destroys an entry.
--         A trunk created by LACP cannot be manually destroyed
--         or (re)configured."
--    ::= { trunkEntry 4 }

---
--- lacpMgt
---

lacpPortTable OBJECT-TYPE
        SYNTAX      SEQUENCE OF LacpPortEntry
        MAX-ACCESS  not-accessible
        STATUS      current
        DESCRIPTION "Table for LACP port configuration."
        ::= { lacpMgt 1 }

lacpPortEntry OBJECT-TYPE
        SYNTAX      LacpPortEntry
        MAX-ACCESS  not-accessible
        STATUS      current
        DESCRIPTION "Entry for LACP port configuration."
        INDEX       { lacpPortIndex }
        ::= { lacpPortTable 1 }

LacpPortEntry ::= SEQUENCE
{
    lacpPortIndex            Integer32,
    lacpPortStatus           INTEGER
}

lacpPortIndex OBJECT-TYPE
        SYNTAX      Integer32
        MAX-ACCESS  not-accessible
        STATUS      current
        DESCRIPTION "This is defined as ifIndex in the IF-MIB."
        ::= { lacpPortEntry 1 }

lacpPortStatus OBJECT-TYPE
        SYNTAX      INTEGER
                    {
                        enabled(1),
                        disabled(2)
                    }
        MAX-ACCESS  read-write
        STATUS      current
        DESCRIPTION "Whether 802.3ad LACP is enabled."
        ::= { lacpPortEntry 2 }

--
-- staMgt
--

-- Management for Spanning Tree Algorithm (STA).
-- This has variables not already defined in the implemented
-- standard MIB(s).
      
-- for 1d(STP) start     
staSystemStatus OBJECT-TYPE
        SYNTAX      EnabledStatus
        MAX-ACCESS  read-write
        STATUS      current
        DESCRIPTION "Global spanning tree status.
                     (1) Spanning tree protocol is enabled.
                     (2) Spanning tree protocol is disabled."
        DEFVAL      { enabled }
        ::= { staMgt 1 }
-- for 1d(STP) end

staPortTable OBJECT-TYPE
        SYNTAX      SEQUENCE OF StaPortEntry
        MAX-ACCESS  not-accessible
        STATUS      current
        DESCRIPTION "The table manages port settings for Spanning Tree 
                     Protocol 802.1d, 802.1w or 802.1s depending on the 
                     value specified by staProtocolType."
        REFERENCE "IEEE 802.1d, IEEE 802.1w, IEEE 802.1s."
        ::= { staMgt 2 }

staPortEntry OBJECT-TYPE
        SYNTAX      StaPortEntry
        MAX-ACCESS  not-accessible
        STATUS      current
        DESCRIPTION "The conceptual entry of staPortTable."
        INDEX       { staPortIndex }
        ::= { staPortTable 1 }

StaPortEntry ::= SEQUENCE
{
    staPortIndex                  Integer32,
-- for 1d(STP) start     
    staPortFastForward        EnabledStatus,
-- for 1d(STP) end
-- for 1w(RSTP) start          
    staPortProtocolMigration  TruthValue,
    staPortAdminEdgePort      TruthValue,
    staPortOperEdgePort       TruthValue,
    staPortAdminPointToPoint  INTEGER,
    staPortOperPointToPoint   TruthValue,
    staPortLongPathCost       Integer32,
    staPortSystemStatus       EnabledStatus
-- for 1w(RSTP) end  
}

staPortIndex OBJECT-TYPE
        SYNTAX      Integer32
        MAX-ACCESS  not-accessible
        STATUS      current
        DESCRIPTION "The port and the trunk (excluding trunk member ports) 
                     interface of the staPortTable. The interface identified
                     by a particular value of this index is the same interface 
                     as identified by the same value of dot1dStpPort in the
                     BRIDGE-MIB."
        ::= { staPortEntry 1 }

-- for 1d(STP) start
staPortFastForward OBJECT-TYPE
        SYNTAX      EnabledStatus
        MAX-ACCESS  read-write
        STATUS      current
        DESCRIPTION "Whether fast forwarding is enabled."
        ::= { staPortEntry 2 }
-- for 1d(STP) end

-- for 1w(RSTP) start          
staPortProtocolMigration OBJECT-TYPE
    SYNTAX      TruthValue
    MAX-ACCESS  read-write
    STATUS      current
    DESCRIPTION
        "When operating in RSTP (version 2) mode, writing true(1)
         to this object forces this port to transmit RSTP BPDUs.
         Any other operation on this object has no effect and
         it always returns false(2) when read."
    REFERENCE
        "IEEE 802.1w clause 14.8.2.4, 17.18.10, 17.26"
    ::= { staPortEntry 3 }

staPortAdminEdgePort OBJECT-TYPE
    SYNTAX      TruthValue
    MAX-ACCESS  read-write
    STATUS      current
    DESCRIPTION
        "The administrative value of the edge port parameter.  A
         value of true(1) indicates that this port should be
         assumed as an edge-port and a value of false(2) indicates
         that this port should be assumed as a non-edge-port."
    REFERENCE
        "IEEE 802.1t clause 14.8.2, 18.3.3"
    ::= { staPortEntry 4 }

staPortOperEdgePort OBJECT-TYPE
    SYNTAX      TruthValue
    MAX-ACCESS  read-only
    STATUS      current
    DESCRIPTION
        "The operational value of the edge port parameter. The object is
         initialized to the value of staPortAdminEdgePort and is set false
         when a BPDU is received."
    REFERENCE
        "IEEE 802.1t clause 14.8.2, 18.3.4"
    ::= { staPortEntry 5 }

staPortAdminPointToPoint OBJECT-TYPE
    SYNTAX      INTEGER
                {
                    forceTrue(0),
                    forceFalse(1),
                    auto(2)
                }
    MAX-ACCESS  read-write
    STATUS      current
     DESCRIPTION
        "The administrative point-to-point status of the LAN segment
         attached to this port. A value of forceTrue(0) indicates that
         this port should always be treated as if it is connected to
         a point-to-point link. A value of forceFalse(1) indicates
         that this port should be treated as having a shared media
         connection. A value of auto(2) indicates that this port is
         considered to have a point-to-point link if it is an Aggregator
         and all of its members are aggregatable, or if the MAC entity
         is configured for full duplex operation, either through
         auto-negotiation or by management means."
   REFERENCE
       "IEEE 802.1w clause 6.4.3, 6.5, 14.8.2"
   ::= { staPortEntry 6 }

staPortOperPointToPoint OBJECT-TYPE
    SYNTAX      TruthValue
    MAX-ACCESS  read-only
    STATUS      current
    DESCRIPTION
        "The operational point-to-point status of the LAN segment
         attached to this port. This indicates whether a port is
         considered to have a point-to-point connection or not.
         The value is determined by management or by auto-detection,
         as described in the staPortAdminPointToPoint object."
    REFERENCE
        "IEEE 802.1w clause 6.4.3, 6.5, 14.8.2"
    ::= { staPortEntry 7 }

staPortLongPathCost OBJECT-TYPE
    SYNTAX      Integer32(1..200000000)
    MAX-ACCESS  read-write
    STATUS      current
    DESCRIPTION 
          "The contribution of this port to the path cost (in 32
          bits value) of paths towards the spanning tree root which
          include this port.

          This object is used to configure the spanning tree port
          path cost in the 32-bit value range when the
          staPathCostMethod is long(2).

          If the staPathCostMethod is short(1), this mib object is not 
          instantiated."
    ::= { staPortEntry 8 }

staPortSystemStatus OBJECT-TYPE
        SYNTAX      EnabledStatus
        MAX-ACCESS  read-write
        STATUS      current
        DESCRIPTION "Per-port spanning tree status.
                     (1) Spanning tree protocol is enabled.
                     (2) Spanning tree protocol is disabled."
        DEFVAL      { enabled }
        ::= { staPortEntry 9 }

staProtocolType OBJECT-TYPE
    SYNTAX      INTEGER {
                    stp(1),
                    rstp(2),
                    mstp(3)
                }
    MAX-ACCESS  read-write
    STATUS      current
    DESCRIPTION "The version of Spanning Tree Protocol the bridge is currently
                 running. The value 'stp(1)' indicates the Spanning Tree 
                 Protocol is as specified in IEEE 802.1D,'rstp(2)' indicates that
                 the Rapid Spanning Tree Protocol is as specified in IEEE 
                 802.1w, and the value 'mstp(3)' indicates that the Multiple Spanning
                 Tree Protocol is as specified in IEEE 802.1s. Here LEO doesn't support 'mstp(3)'
                 New values may be defined in the future as new or updated versions of the 
                 protocol become available."
    REFERENCE
        "IEEE 802.1w clause 14.8.1, 17.12, 17.16.1"
    ::= { staMgt 3 }


staTxHoldCount OBJECT-TYPE
    SYNTAX      Integer32 (1..10)
    MAX-ACCESS  read-write
    STATUS      current
    DESCRIPTION
        "The value used by the Port Transmit state machine to limit
         the maximum transmission rate."
    REFERENCE
        "IEEE 802.1w clause 17.16.6"
    DEFVAL      { 3 }
    ::= { staMgt 4 }

staPathCostMethod    OBJECT-TYPE
    SYNTAX       StaPathCostMode
    MAX-ACCESS   read-write
    STATUS       current
    DESCRIPTION "Indicates the type of spanning tree path cost mode configured
                 on the switch. This mode applies to all instances of the 
                 spanning tree protocol running on the switch.

                 When the value of this MIB object is changed, the path cost of
                 all ports will be reassigned to the default path cost values 
                 based on the new spanning tree path cost mode and the 
                 ports' speed.

                 When the value of this MIB object is set to long(2), the 
                 staPortLongPathCost MIB object must be used to retrieve/configure 
                 the spanning tree port path cost as a 32-bit value. 
                 The set operation on dot1dStpPortPathCost in BRIDGE-MIB will be rejected. 
                 While retrieving the value of dot1dStpPortPathCost, the maximum 
                 value of 65535 will be returned if the value of staPortLongPathCost 
                 for the same instance exceeds 65535.

                 When the value of this MIB object is set to short(1), the 
                 dot1dStpPortPathCost in BRIDGE-MIB must be used."
   DEFVAL  { short }
   ::= { staMgt 5} 
-- for 1w(RSTP) end   

-- for 1s(MSTP) start
--
-- xstMgt
--

xstMgt OBJECT IDENTIFIER ::= { staMgt 6}

mstName OBJECT-TYPE
    SYNTAX      DisplayString(SIZE(0..32))
    MAX-ACCESS  read-write
    STATUS      current
    DESCRIPTION "The name of the Multiple Spanning Tree region."
    ::= { xstMgt 1 }

mstRevision OBJECT-TYPE
    SYNTAX      Integer32
    MAX-ACCESS  read-write
    STATUS      current
    DESCRIPTION "The Revision number of the Multiple Spanning Tree region."
    ::= { xstMgt 2 }

mstMaxHops OBJECT-TYPE
    SYNTAX      Integer32(1..40)
    MAX-ACCESS  read-write
    STATUS      current
    DESCRIPTION "The max hop number counts of the Multiple Spanning Tree region."
    ::= { xstMgt 3 }

xstInstanceCfgTable OBJECT-TYPE
    SYNTAX      SEQUENCE OF XstInstanceCfgEntry
    MAX-ACCESS  not-accessible
    STATUS      current
    DESCRIPTION "This table is used to configure the property of a specific
                 instance in Multiple Spanning Tree or Rapid Spanning Tree.
                 If Rapid Spanning Tree protocol is in use, the
                 mstInstanceEditIndex is always 0."
    ::= { xstMgt 4 }

xstInstanceCfgEntry OBJECT-TYPE
    SYNTAX      XstInstanceCfgEntry
    MAX-ACCESS  not-accessible
    STATUS      current
    DESCRIPTION "A conceptual row containing the property of the RST or MST instance."
    INDEX       { xstInstanceCfgIndex }
    ::= { xstInstanceCfgTable 1 }

XstInstanceCfgEntry ::= SEQUENCE
{
      xstInstanceCfgIndex                    Integer32,
      xstInstanceCfgPriority                 Integer32,
      xstInstanceCfgTimeSinceTopologyChange  TimeTicks,
      xstInstanceCfgTopChanges               Integer32,
      xstInstanceCfgDesignatedRoot           BridgeId,
      xstInstanceCfgRootCost                 Integer32,
      xstInstanceCfgRootPort                 Integer32,
      xstInstanceCfgMaxAge                   Timeout,
      xstInstanceCfgHelloTime                Timeout,
      xstInstanceCfgHoldTime                 Timeout,
      xstInstanceCfgForwardDelay             Timeout,
      xstInstanceCfgBridgeMaxAge             Timeout,
      xstInstanceCfgBridgeHelloTime          Timeout,
      xstInstanceCfgBridgeForwardDelay       Timeout,
      xstInstanceCfgTxHoldCount              Integer32,
      xstInstanceCfgPathCostMethod           StaPathCostMode
}

xstInstanceCfgIndex OBJECT-TYPE
      SYNTAX      Integer32 (0..4094)
      MAX-ACCESS  not-accessible
      STATUS      current
      DESCRIPTION
          "An arbitrary integer within the range from 1 to the value of
          the maximum instance that uniquely identifies a spanning
          tree instance."
      ::= {xstInstanceCfgEntry 1 }

xstInstanceCfgPriority OBJECT-TYPE
     SYNTAX      Integer32 (0..61440)
     MAX-ACCESS  read-write
     STATUS      current
     DESCRIPTION "The priority of a specific spanning tree instance.
                  The value assigned should be in the range 0-61440
                  in steps of 4096."
     ::= { xstInstanceCfgEntry 2 }


xstInstanceCfgTimeSinceTopologyChange OBJECT-TYPE
     SYNTAX      TimeTicks
     MAX-ACCESS  read-only
     STATUS      current
     DESCRIPTION "The time (in hundredths of a second) since the last topology
                 change detected by the bridge entity in RST or MST."
     ::= { xstInstanceCfgEntry 3 }

xstInstanceCfgTopChanges OBJECT-TYPE
     SYNTAX      Integer32
     MAX-ACCESS  read-only
     STATUS      current
     DESCRIPTION "The total number of topology changes detected by
                 this bridge in RST or MST since the management entity
                 was last reset or initialized."
     ::= { xstInstanceCfgEntry 4 }


xstInstanceCfgDesignatedRoot OBJECT-TYPE
     SYNTAX      BridgeId
     MAX-ACCESS  read-only
     STATUS      current
     DESCRIPTION "The bridge identifier of the root of the spanning
                 tree as determined by the Multiple Spanning Tree Protocol. (802.1s)
                 or Rapid Spanning Tree Protocol (802.1w) executed by this node.
                 This value is used as the root identifier parameter in
                 all configuration bridge PDUs originated by this node."
     REFERENCE   "IEEE 802.1w."
     ::= { xstInstanceCfgEntry 5 }

xstInstanceCfgRootCost OBJECT-TYPE
     SYNTAX      Integer32
     MAX-ACCESS  read-only
     STATUS      current
     DESCRIPTION "The cost of the path to the root as seen from
                 this bridge of the RST or MST."
     ::= { xstInstanceCfgEntry 6 }


xstInstanceCfgRootPort OBJECT-TYPE
     SYNTAX      Integer32
     MAX-ACCESS  read-only
     STATUS      current
     DESCRIPTION "The number of the port which offers the
                 lowest cost path from this bridge to the root
                 bridge of the RST or MST."
     ::= { xstInstanceCfgEntry 7 }

xstInstanceCfgMaxAge OBJECT-TYPE
     SYNTAX      Timeout
     MAX-ACCESS  read-only
     STATUS      current
     DESCRIPTION "The maximum age of Multiple Spanning Tree Protocol (802.1s)
                 or Rapid Spanning Tree Protocol (802.1w) information learned
                 from the network on any port before it is discarded,
                 in units of hundredths of a second. This is the actual
                 value that this bridge is currently using."
     ::= { xstInstanceCfgEntry 8 }


xstInstanceCfgHelloTime OBJECT-TYPE
     SYNTAX      Timeout
     MAX-ACCESS  read-only
     STATUS      current
     DESCRIPTION  "The amount of time between the transmission of
                  configuration bridge PDUs by this node on any port
                  when it is the root of the specific spanning tree or trying
                  to become so, in units of hundredths of a second.
                  This is the actual value that this bridge is
                  currently using in RST or MST."
     ::= { xstInstanceCfgEntry 9 }

xstInstanceCfgHoldTime OBJECT-TYPE
     SYNTAX      Timeout
     MAX-ACCESS  read-only
     STATUS      current
     DESCRIPTION  "This time value determines the interval length
                  during which no more than two configuration bridge
                  PDUs shall be transmitted by this node, in units
                  of hundredths of a second."
     ::= { xstInstanceCfgEntry 10 }

xstInstanceCfgForwardDelay OBJECT-TYPE
     SYNTAX      Timeout
     MAX-ACCESS  read-only
     STATUS      current
     DESCRIPTION  "For RST or MST protocol, this time value, measured in units of
                  hundredths of a second, controls how fast a port changes
                  its spanning state when moving towards the forwarding
                  state.  The value determines how long the port
                  stays in each of the listening and learning
                  states, which precede the forwarding state.  This
                  value is also used, when a topology change has
                  been detected and is underway, to age all dynamic
                  entries in the forwarding database. This value is the
                  current value being used by the bridge.
                  xstInstanceCfgBridgeForwardDelay defines the value that
                  this bridge and all others would start using
                  if/when this bridge were to become the root."
     ::= { xstInstanceCfgEntry 11 }

xstInstanceCfgBridgeMaxAge OBJECT-TYPE
     SYNTAX      Timeout
     MAX-ACCESS  read-only
     STATUS      current
     DESCRIPTION   "For RST or MST protocol, the time (in hundredths of second)
                   that all bridges use for MaxAge when this bridge is acting
                   as the root. Note that 802.1D-1990 specifies that the range
                   for this parameter is related to the value of
                   xstInstanceCfgBridgeHelloTime. The granularity of this
                   timer is specified by 802.1D-1990 to be 1 second."
     REFERENCE   "802.1D-1990."
     ::= { xstInstanceCfgEntry 12 }

xstInstanceCfgBridgeHelloTime OBJECT-TYPE
     SYNTAX      Timeout
     MAX-ACCESS  read-only
     STATUS      current
     DESCRIPTION   "For RST or MST protocol,the time (in hundredths of a second) that
                   all bridges use for HelloTime when this bridge is acting
                   as the root. The granularity of this timer is specified
                   by 802.1D-1990 to be 1 second."
     REFERENCE   "802.1D-1990."
     ::= { xstInstanceCfgEntry 13 }


xstInstanceCfgBridgeForwardDelay OBJECT-TYPE
     SYNTAX      Timeout
     MAX-ACCESS  read-only
     STATUS      current
     DESCRIPTION  "For RST or MST protocol, the time (in hundredths of a second)
                  that all bridges use for ForwardDelay when this bridge
                  is acting as the root.
                  Note that 802.1D-1990 specifies that the range for this
                  parameter is related to the value of
                  xstInstanceCfgBridgeMaxAge. The granularity of this
                  timer is specified by 802.1D-1990 to be 1 second."
     REFERENCE   "802.1D-1990."
     ::= { xstInstanceCfgEntry 14 }

xstInstanceCfgTxHoldCount OBJECT-TYPE
     SYNTAX      Integer32
     MAX-ACCESS  read-only
     STATUS      current
     DESCRIPTION  "For RST or MST protocol, the value used by the port transmit
                  state machine to limit the maximum transmission rate."
     ::= { xstInstanceCfgEntry 15 }

xstInstanceCfgPathCostMethod OBJECT-TYPE
     SYNTAX      StaPathCostMode
     MAX-ACCESS  read-only
     STATUS      current
     DESCRIPTION
       "For RST or MST protocol, this indicates the type of spanning tree path
       cost mode used by the switch. The mode applies to all instances of the
       Spanning Tree protocol running on the switch.

       When the value of this MIB object is changed, the path cost
       of all ports will be reassigned to the default path cost
       values based on the new spanning tree path cost mode and the
       ports' speed.

       When the value of this MIB object is set to long(2),
       the xstInstancePortPathCost MIB object must be used in order
       to retrieve/configure the spanning tree port path cost as a
       32-bit value. The set operation on dot1dStpPortPathCost in
       BRIDGE-MIB will be rejected. While retrieving the value of
       dot1dStpPortPathCost, the maximum value of 65535 will be
       returned if the value of xstInstancePortPathCost for the same
       instance exceeds 65535.

       When the value of this MIB object is set to short(1),
       the dot1dStpPortPathCost in BRIDGE-MIB must be used."
     ::= { xstInstanceCfgEntry 16 }

xstInstancePortTable OBJECT-TYPE
     SYNTAX      SEQUENCE OF XstInstancePortEntry
     MAX-ACCESS  not-accessible
     STATUS      current
     DESCRIPTION "The extension table for dot1dStpPortEntry to provide
                 additional Spanning Tree information and configuration."
     ::= { xstMgt 5 }

xstInstancePortEntry OBJECT-TYPE
     SYNTAX      XstInstancePortEntry
     MAX-ACCESS  not-accessible
     STATUS      current
     DESCRIPTION "The conceptual row for xstInstancePortTable."
     INDEX       { xstInstancePortInstance, xstInstancePortPort }
     ::= { xstInstancePortTable 1 }

XstInstancePortEntry ::= SEQUENCE
{
  xstInstancePortInstance           Integer32,
  xstInstancePortPort               Integer32,
  xstInstancePortPriority           Integer32,
  xstInstancePortState              INTEGER,
  xstInstancePortEnable             EnabledStatus,
  xstInstancePortPathCost           Integer32,
  xstInstancePortDesignatedRoot     BridgeId,
  xstInstancePortDesignatedCost     Integer32,
  xstInstancePortDesignatedBridge   BridgeId,
  xstInstancePortDesignatedPort     OCTET STRING,
  xstInstancePortForwardTransitions Counter32,
  xstInstancePortPortRole           INTEGER
}

xstInstancePortInstance OBJECT-TYPE
     SYNTAX      Integer32
     MAX-ACCESS  not-accessible
     STATUS      current
     DESCRIPTION "The instance of the MSTP."
     ::= { xstInstancePortEntry 1 }

xstInstancePortPort OBJECT-TYPE
     SYNTAX      Integer32
     MAX-ACCESS  not-accessible
     STATUS      current
     DESCRIPTION "The port and the trunk (excluding trunk member ports)
                  interface of the mstInstancePortTable. The interface identified
                  by a particular value of this index is the same interface
                  as identified by the same value of dot1dStpPort in the BRIDGE-MIB."
     ::= { xstInstancePortEntry 2 }

xstInstancePortPriority OBJECT-TYPE
     SYNTAX      Integer32(0..240)
     MAX-ACCESS  read-write
     STATUS      current
     DESCRIPTION "Defines the priority used for this port in the Spanning
                 Tree Algorithm. If the path cost for all ports on a
                 switch is the same, the port with the highest priority
                 (i.e., lowest value) will be configured as an active link
                 in the Spanning Tree. This makes a port with higher
                 priority less likely to be blocked if the Spanning Tree
                 Algorithm is detecting network loops. Where more than one
                 port is assigned the highest priority, the port with
                 lowest numeric identifier will be enabled."
     ::= { xstInstancePortEntry 3 }

xstInstancePortState OBJECT-TYPE
     SYNTAX      INTEGER {
                          discarding(1),
                          learning(2),
                          forwarding(3)
                         }
     MAX-ACCESS  read-only
     STATUS  current
     DESCRIPTION  "The port's current state as defined by application of
                  the Spanning Tree Protocol.  This state controls what
                  action a port takes on reception of a frame:
                  discarding(1): Port receives configuration messages,
                                 but does not forward packets.
                  learning(2):   Port has transmitted configuration messages
                                 for an interval set by the Forward Delay
                                 parameter without receiving contradictory
                                 information. Port address table is cleared,
                                 and the port begins learning addresses.
                  forwarding(3): Port forwards packets, and continues learning
                                 addresses.

                  For ports which are disabled (see xstInstancePortEnable),
                  this object will have a value of discarding(1)."
              ::= { xstInstancePortEntry 4}

xstInstancePortEnable OBJECT-TYPE
     SYNTAX     EnabledStatus
     MAX-ACCESS  read-only
     STATUS      current
     DESCRIPTION    "The enabled/disabled status of the port."
     ::= { xstInstancePortEntry 5 }

xstInstancePortPathCost OBJECT-TYPE
     SYNTAX      Integer32(1..200000000)
     MAX-ACCESS  read-write
     STATUS      current
     DESCRIPTION "The pathcost of the RST or MST in the range 1 to 200000000.
                  This parameter is used to determine the best path between
                  devices. Therefore, lower values should be assigned to
                  ports attached to faster media, and higher values assigned
                  to ports with slower media. (Path cost takes precedence
                  over port priority)."
     ::= { xstInstancePortEntry 6 }

xstInstancePortDesignatedRoot OBJECT-TYPE
     SYNTAX      BridgeId
     MAX-ACCESS  read-only
     STATUS      current
     DESCRIPTION
                 "The unique bridge identifier of the bridge
                 recorded as the root in the configuration BPDUs
                 transmitted by the designated bridge for the
                 segment to which the port is attached."
     ::= { xstInstancePortEntry 7 }

xstInstancePortDesignatedCost OBJECT-TYPE
     SYNTAX      Integer32
     MAX-ACCESS  read-only
     STATUS      current
     DESCRIPTION
                 "The path cost of the designated port of the
                  segment connected to this port.  This value is
                  compared to the root path cost field in received
                  bridge PDUs."
     ::= { xstInstancePortEntry 8 }

xstInstancePortDesignatedBridge OBJECT-TYPE
     SYNTAX      BridgeId
     MAX-ACCESS  read-only
     STATUS      current
     DESCRIPTION
                 "The bridge identifier of the bridge which this
                 port considers to be the designated bridge for
                 this port's segment."
     ::= { xstInstancePortEntry 9 }

xstInstancePortDesignatedPort OBJECT-TYPE
     SYNTAX      OCTET STRING (SIZE (2))
     MAX-ACCESS  read-only
     STATUS      current
     DESCRIPTION
            "The port identifier of the port on the designated
            bridge for this port's segment."
     ::= { xstInstancePortEntry 10 }

xstInstancePortForwardTransitions OBJECT-TYPE
     SYNTAX  Counter32
     MAX-ACCESS  read-only
     STATUS  current
     DESCRIPTION
             "The number of times this port has transitioned
             from the learning state to the forwarding state."
     ::= { xstInstancePortEntry 11 }

xstInstancePortPortRole OBJECT-TYPE
     SYNTAX  INTEGER
             {
               disabled(1),
               root(2),
               designated(3),
               alternate(4),
               backup(5),
               master(6)
             }
     MAX-ACCESS read-only
     STATUS current
     DESCRIPTION "The role of the port in the RST or MST protocol:
                  (1) The port has no role within the spanning tree
                  (2) The port is part of the active topology connecting
                      the bridge to the root bridge (i.e., root port)
                  (3) The port is connecting a LAN through the bridge to the
                      root bridge (i.e., designated port)
                  (4) The port may provide connectivity if other
                      bridges, bridge ports, or LANs fail or are removed.
                  (5) The port provides backup if other
                      bridges, bridge ports, or LANs fail or are removed.
                  (6) For MST protocol only, indicates whether this instance
                      is in a master role."
     ::= { xstInstancePortEntry 12 }

mstInstanceEditTable OBJECT-TYPE
     SYNTAX      SEQUENCE OF MstInstanceEditEntry
     MAX-ACCESS  not-accessible
     STATUS      current
     DESCRIPTION "The Multiple Spanning Tree region instance vlan configuration table.
                  Please read the actual instance vlan mapped in the mstInstanceOperTable."
     ::= { xstMgt 6 }

mstInstanceEditEntry OBJECT-TYPE
     SYNTAX      MstInstanceEditEntry
     MAX-ACCESS  not-accessible
     STATUS      current
     DESCRIPTION  "A conceptual row containing the status of the MSTP instance."
     INDEX       { mstInstanceEditIndex }
     ::= { mstInstanceEditTable 1 }

MstInstanceEditEntry ::= SEQUENCE
{
    mstInstanceEditIndex      Integer32,
    mstInstanceEditVlansMap   OCTET STRING,
    mstInstanceEditVlansMap2k OCTET STRING,
    mstInstanceEditVlansMap3k OCTET STRING,
    mstInstanceEditVlansMap4k OCTET STRING,
    mstInstanceEditRemainingHops Integer32
}

mstInstanceEditIndex OBJECT-TYPE
      SYNTAX      Integer32 (0..4094)
      MAX-ACCESS  not-accessible
      STATUS      current
      DESCRIPTION
          "An arbitrary integer within the range from 1 to the value of
          the maximum instance that uniquely identifies a spanning
          tree instance."
      ::= {mstInstanceEditEntry 1 }

mstInstanceEditVlansMap OBJECT-TYPE
    SYNTAX     OCTET STRING (SIZE (0..128))
    MAX-ACCESS read-create
    STATUS     current
    DESCRIPTION
            "A string of octets containing one bit per VLAN. The
            first octet corresponds to VLANs with vlanIndex values
            of 0 through 7; the second octet to VLANs 8 through
            15; etc., The most significant bit of each octet
            corresponds to the lowest value vlanIndex in that octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 2 }

mstInstanceEditVlansMap2k OBJECT-TYPE
    SYNTAX     OCTET STRING (SIZE (0..128))
    MAX-ACCESS read-create
    STATUS     current
    DESCRIPTION
            "A string of octets containing one bit per VLAN for
            VLANS with vlanIndex values of 1024 through 2047. The
            first octet corresponds to VLANs with vlanIndex values
            of 1024 through 1031; the second octet to VLANs 1032
            through 1039; etc. The most significant bit of each
            octet corresponds to the lowest value vlanIndex in that
            octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 3 }

mstInstanceEditVlansMap3k OBJECT-TYPE
    SYNTAX     OCTET STRING (SIZE (0..128))
    MAX-ACCESS read-create
    STATUS     current
    DESCRIPTION
            "A string of octets containing one bit per VLAN for
            VLANS with vlanIndex values of 2048 through 3071. The
            first octet corresponds to VLANs with vlanIndex values
            of 2048 through 2055; the second octet to VLANs 2056
            through 2063; etc. The most significant bit of each
            octet corresponds to the lowest value vlanIndex in that
            octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 4 }

mstInstanceEditVlansMap4k OBJECT-TYPE
    SYNTAX     OCTET STRING (SIZE (0..128))
    MAX-ACCESS read-create
    STATUS     current
    DESCRIPTION
            "A string of octets containing one bit per VLAN for
            VLANS with vlanIndex values of 3072 through 4095. The
            first octet corresponds to VLANs with vlanIndex values
            of 3072 through 3079; the second octet to VLANs 3080
            through 3087; etc. The most significant bit of each
            octet corresponds to the lowest value vlanIndex in that
            octet.

            For each VLAN, if it is mapped to this MSTP instance,
            then the bit corresponding to that VLAN is set to '1'.

            To create a row, write any of mstInstanceEditVlansMap,
            mstInstanceEditVlansMap2k, mstInstanceEditVlansMap3k or
            mstInstanceEditVlansMap4k, to a non-empty list.
            To destroy a row, write all of these four variables
            to an empty list."
    ::= {mstInstanceEditEntry 5 }

mstInstanceEditRemainingHops OBJECT-TYPE
     SYNTAX      Integer32
     MAX-ACCESS  read-only
     STATUS      current
     DESCRIPTION "The remaining hop count for this MST instance."
     ::= { mstInstanceEditEntry 6 }

--mstInstanceOperTable
mstInstanceOperTable OBJECT-TYPE
     SYNTAX      SEQUENCE OF MstInstanceOperEntry
     MAX-ACCESS  not-accessible
     STATUS      current
     DESCRIPTION "The Multiple Spanning Tree region instance vlan mapped table."
     ::= { xstMgt 7 }

mstInstanceOperEntry OBJECT-TYPE
     SYNTAX      MstInstanceOperEntry
     MAX-ACCESS  not-accessible
     STATUS      current
     DESCRIPTION  "A conceptual row containing the status of the MSTP instance."
     INDEX       { mstInstanceOperIndex }
     ::= { mstInstanceOperTable 1 }

MstInstanceOperEntry ::= SEQUENCE
{
    mstInstanceOperIndex      Integer32,
    mstInstanceOperVlansMap   OCTET STRING,
    mstInstanceOperVlansMap2k OCTET STRING,
    mstInstanceOperVlansMap3k OCTET STRING,
    mstInstanceOperVlansMap4k OCTET STRING
}

mstInstanceOperIndex OBJECT-TYPE
      SYNTAX      Integer32 (0..4094)
      MAX-ACCESS  not-accessible
      STATUS      current
      DESCRIPTION
          "An arbitrary integer within the range from 1 to the value of
          the maximum instance that uniquely identifies a spanning
          tree instance."
      ::= {mstInstanceOperEntry 1 }

mstInstanceOperVlansMap OBJECT-TYPE
    SYNTAX     OCTET STRING (SIZE (0..128))
    MAX-ACCESS read-only
    STATUS     current
    DESCRIPTION
            "A string of octets containing one bit per VLAN. The
            first octet corresponds to VLANs with vlanIndex values
            of 0 through 7; the second octet to VLANs 8 through
            15; etc., The most significant bit of each octet
            corresponds to the lowest value vlanIndex in that octet.

            For each VLAN, if it is mapped to this MSTP instance,
            then the bit corresponding to that VLAN is set to '1'."
    ::= {mstInstanceOperEntry 2 }

mstInstanceOperVlansMap2k OBJECT-TYPE
    SYNTAX     OCTET STRING (SIZE (0..128))
    MAX-ACCESS read-only
    STATUS     current
    DESCRIPTION
            "A string of octets containing one bit per VLAN for
            VLANS with vlanIndex values of 1024 through 2047. The
            first octet corresponds to VLANs with vlanIndex values
            of 1024 through 1031; the second octet to VLANs 1032
            through 1039; etc. The most significant bit of each
            octet corresponds to the lowest value vlanIndex in that
            octet.

            For each VLAN, if it is mapped to this MSTP instance,
            then the bit corresponding to that VLAN is set to '1'."
    ::= {mstInstanceOperEntry 3 }

mstInstanceOperVlansMap3k OBJECT-TYPE
    SYNTAX     OCTET STRING (SIZE (0..128))
    MAX-ACCESS read-only
    STATUS     current
    DESCRIPTION
            "A string of octets containing one bit per VLAN for
            VLANS with vlanIndex values of 2048 through 3071. The
            first octet corresponds to VLANs with vlanIndex values
            of 2048 through 2055; the second octet to VLANs 2056
            through 2063; etc. The most significant bit of each
            octet corresponds to the lowest value vlanIndex in that
            octet.

            For each VLAN, if it is mapped to this MSTP instance,
            then the bit corresponding to that VLAN is set to '1'."
    ::= {mstInstanceOperEntry 4 }

mstInstanceOperVlansMap4k OBJECT-TYPE
    SYNTAX     OCTET STRING (SIZE (0..128))
    MAX-ACCESS read-only
    STATUS     current
    DESCRIPTION
            "A string of octets containing one bit per VLAN for
            VLANS with vlanIndex values of 3072 through 4095. The
            first octet corresponds to VLANs with vlanIndex values
            of 3072 through 3079; the second octet to VLANs 3080
            through 3087; etc. The most significant bit of each
            octet corresponds to the lowest value vlanIndex in that
            octet.

            For each VLAN, if it is mapped to this MSTP instance,
            then the bit corresponding to that VLAN is set to '1'."
    ::= {mstInstanceOperEntry 5 }

-- for 1s(MSTP) end
--
-- tftpMgt
--

--tftpFileType  OBJECT-TYPE
--    SYNTAX     INTEGER {
--                  opcode(1),
--                  config(2)
--               }
--    MAX-ACCESS read-write
--    STATUS     current
--    DESCRIPTION
--        "Type of file to transfer."
--    ::= { tftpMgt 1 }
--
--tftpSrcFile  OBJECT-TYPE
--    SYNTAX     DisplayString (SIZE(0..32))
--    MAX-ACCESS read-write
--    STATUS     current
--    DESCRIPTION
--        "The source file name for TFTP transfer when a
--        transfer is next requested via this MIB.  This value is set to
--        the zero length string when no file name has been specified."
--    ::= { tftpMgt 2 }
--
--tftpDestFile  OBJECT-TYPE
--    SYNTAX     DisplayString (SIZE(0..32))
--    MAX-ACCESS read-write
--    STATUS     current
--    DESCRIPTION
--        "The destination file name for TFTP transfer when a
--        transfer is next requested via this MIB.  This value is set to
--        the zero length string when no file name has been specified."
--    ::= { tftpMgt 3 }
--
--tftpServer  OBJECT-TYPE
--    SYNTAX     IpAddress
--    MAX-ACCESS read-write
--    STATUS     current
--    DESCRIPTION
--        "The IP address of the TFTP server for transfer
--        when a download is next requested via this MIB.
--        This value is set to `0.0.0.0' when no IP address has been
--        specified."
--    ::= { tftpMgt 4 }
--
--tftpAction  OBJECT-TYPE
--    SYNTAX     INTEGER {
--                  notDownloading(1),
--                  downloadToPROM(2),
--                  downloadToRAM(3),
--                  upload(4)
--               }
--    MAX-ACCESS read-write
--    STATUS     current
--    DESCRIPTION
--        "When this object is set to downloadToRAM(3) or
--        downloadToPROM(2), the device will discontinue its
--        normal operation and begin download of the file specified
--        by tftpSrcFile from the server specified by
--        tftpServer to tftpDestFile in the device
--        using the TFTP protocol.  If
--        downloadToRAM(3) is specified, the new image is copied
--        to RAM only (the old image remains unaltered in the flash
--        EPROM).  If downloadToPROM(2) is specified
--        the new image is written to the flash EPROM
--        memory after its checksum has been verified to be correct.
--        When the download process is completed, the device will
--        warm boot to restart the newly loaded application.
--        When the device is not downloading, this object will have
--        a value of notDownloading(1).
--        downloadToRAM(3) applies only to configuration download.
--        Otherwise 'invalid value' is replied.
--        When this object is set to upload(4), the device will begin
--        upload of the file specified by tftpScrFile in the device
--        to tftpDestFile in the server specified by tftpServer."
--    ::= { tftpMgt 5 }
--
-- tftpStatus  OBJECT-TYPE
--    SYNTAX     INTEGER {
--                    tftpSuccess(1),
--                    tftpStatusUnknown(2),
--                    tftpGeneralError(3),
--                    tftpNoResponseFromServer(4),
--                    tftpDownloadChecksumError(5),--download only
--                    tftpDownloadIncompatibleImage(6),--download only
--                    tftpTftpFileNotFound(7),
--                    tftpTftpAccessViolation(8)
--               }
--    MAX-ACCESS read-only
--    STATUS     current
--    DESCRIPTION
--        "The status of the last transfer procedure, if any.  This
--        object will have a value of downloadStatusUnknown(2) if no
--        transfer process has been performed."
--    ::= { tftpMgt 6 }


--
-- restartMgt
--

-- restartOpCodeFile OBJECT-TYPE
--        SYNTAX      DisplayString (SIZE(0..32))
--        MAX-ACCESS  read-write
--        STATUS      current
--        DESCRIPTION "Name of op-code file for start-up."
--        ::= { restartMgt 1 }

-- restartConfigFile OBJECT-TYPE
--        SYNTAX      DisplayString (SIZE(0..32))
--        MAX-ACCESS  read-write
--        STATUS      current
--        DESCRIPTION "Name of configuration file for start-up."
--        ::= { restartMgt 2 }

restartControl  OBJECT-TYPE
    SYNTAX     INTEGER {
                    running(1),
                    warmBoot(2),
                    coldBoot(3)
              }
    MAX-ACCESS read-write
    STATUS     current
    DESCRIPTION
        "Setting this object to warmBoot(2) causes the device to
        restart the application software with current configuration
        parameters saved in non-volatile memory.  Setting this
        object to coldBoot(3) causes the device to reinitialize
        configuration parameters in non-volatile memory to default
        values and restart the application software.  When the device
        is running normally, this variable has a value of
        running(1)."
    ::= { restartMgt 3 }

--
-- mirrorMgt
--

-- mirrorTable OBJECT-TYPE
--        SYNTAX      SEQUENCE OF MirrorEntry
--        MAX-ACCESS  not-accessible
--        STATUS      current
--        DESCRIPTION "Table of descriptive and status information about
--                     switches in this system."
--        ::= { mirrorMgt 1 }
--
-- mirrorEntry OBJECT-TYPE
--        SYNTAX      MirrorEntry
--        MAX-ACCESS  not-accessible
--        STATUS      current
--        DESCRIPTION "An entry in the table, containing information
--                     about a single switch in this system. "
--        INDEX       { mirrorDestinationPort, mirrorSourcePort }
--        ::= { mirrorTable 1 }
--
-- MirrorEntry ::= SEQUENCE
-- {
--    mirrorDestinationPort  Integer32,
--    mirrorSourcePort       Integer32,
--    mirrorType             INTEGER,
--    mirrorStatus           ValidStatus
-- }
--
-- mirrorDestinationPort OBJECT-TYPE
--        SYNTAX      Integer32
--        MAX-ACCESS  not-accessible
--        STATUS      current
--        DESCRIPTION "Destination port for mirrored packets. This is defined
--                    as ifIndex in the IF-MIB."
--        ::= { mirrorEntry 1 }
--
-- mirrorSourcePort OBJECT-TYPE
--        SYNTAX      Integer32
--        MAX-ACCESS  not-accessible
--        STATUS      current
--        DESCRIPTION "Source port for mirrored packets. This is defined as
--                    ifIndex in the IF-MIB."
--        ::= { mirrorEntry 2 }
--
-- mirrorType OBJECT-TYPE
--        SYNTAX      INTEGER
--                    {
--                        rx(1),
--                        tx(2),
--                        both(3)
--
--                    }
--        MAX-ACCESS  read-create
--        STATUS      current
--        DESCRIPTION "If this value is rx(1), receive packets will
--                    be mirrored. If this value is tx(2), transmit
--                    packets will be mirrored. If this value is both(3),
--                    receive and transmit packets will be mirrored."
--        ::= { mirrorEntry 3 }
--
-- mirrorStatus OBJECT-TYPE
--        SYNTAX      ValidStatus
--        MAX-ACCESS  read-create
--        STATUS      current
--        DESCRIPTION "Setting this to valid(1) creates an entry.
--                     Setting this to invalid(2) destroys an entry."
--        ::= { mirrorEntry 4 }
--
-- --
-- -- igmpSnoopMgt
-- --
--
-- igmpSnoopStatus OBJECT-TYPE
--        SYNTAX      INTEGER
--                    {
--                        enabled(1),
--                        disabled(2)
--                    }
--        MAX-ACCESS  read-write
--        STATUS      current
--        DESCRIPTION "Parameter to enable or disable IGMP snooping on the device.
--                     When enabled, the device will examine IGMP packets and set
--                     up filters for IGMP ports. "
--        DEFVAL      { enabled }
--        ::= { igmpSnoopMgt 1 }
--
-- igmpSnoopQuerier OBJECT-TYPE
--        SYNTAX      INTEGER
--                    {
--                        enabled(1),
--                        disabled(2)
--                    }
--        MAX-ACCESS  read-write
--        STATUS      current
--        DESCRIPTION "Whether to act as querier."
--        DEFVAL      { enabled }
--        ::= { igmpSnoopMgt 2 }
--
-- igmpSnoopQueryCount OBJECT-TYPE
--        SYNTAX      INTEGER (2..10)
--        MAX-ACCESS  read-write
--        STATUS      current
--        DESCRIPTION "Maximum number of queries that have not been heard on the
--                     system before the system starts taking action to solicit
--                     reports."
--        DEFVAL      { 2 }
--        ::= { igmpSnoopMgt 3 }
--
--
-- igmpSnoopQueryInterval OBJECT-TYPE
--        SYNTAX      INTEGER (60..125)
--        MAX-ACCESS  read-write
--        STATUS      current
--        DESCRIPTION "Query interval."
--        DEFVAL      { 125 }
--        ::= { igmpSnoopMgt 4 }
--
-- igmpSnoopQueryMaxResponseTime OBJECT-TYPE
--        SYNTAX      INTEGER (5..25)
--        MAX-ACCESS  read-write
--        STATUS      current
--        DESCRIPTION "Timeout value (seconds) between IGMP reports received on a port
--                     for an IP Multicast Address that can pass before the system
--                     sends an IGMP Query out the port and removes it from the
--                     list."
--        DEFVAL      { 10 }
--        ::= { igmpSnoopMgt 5 }
--
-- igmpSnoopQueryTimeout OBJECT-TYPE
--        SYNTAX      INTEGER (300..500)
--        MAX-ACCESS  read-write
--        STATUS      current
--        DESCRIPTION "Query time-out."
--        DEFVAL      { 300 }
--        ::= { igmpSnoopMgt 6 }
--
-- igmpSnoopVersion OBJECT-TYPE
--        SYNTAX      INTEGER (1..2)
--        MAX-ACCESS  read-write
--        STATUS      current
--        DESCRIPTION "Version."
--        DEFVAL      { 2 }
--        ::= { igmpSnoopMgt 7 }
--
-- igmpSnoopRouterCurrentTable OBJECT-TYPE
--    SYNTAX      SEQUENCE OF IgmpSnoopRouterCurrentEntry
--    MAX-ACCESS  not-accessible
--    STATUS      current
--    DESCRIPTION
--        "Table for current router ports."
--    ::= { igmpSnoopMgt 8 }
--
-- igmpSnoopRouterCurrentEntry OBJECT-TYPE
--    SYNTAX      IgmpSnoopRouterCurrentEntry
--    MAX-ACCESS  not-accessible
--    STATUS      current
--    DESCRIPTION
--        "Entry for current router ports."
--    INDEX   { igmpSnoopRouterCurrentVlanIndex }
--    ::= { 
-- igmpSnoopRouterCurrentTable 1 }
--
-- IgmpSnoopRouterCurrentEntry ::=
--    SEQUENCE {
--        igmpSnoopRouterCurrentVlanIndex
--            Unsigned32,
--        igmpSnoopRouterCurrentPorts
--            PortList,
--        igmpSnoopRouterCurrentStatus
--            PortList
--    }
--
-- igmpSnoopRouterCurrentVlanIndex OBJECT-TYPE
--    SYNTAX      Unsigned32
--    MAX-ACCESS  not-accessible
--    STATUS      current
--    DESCRIPTION
--        "This is defined as dot1qVlanIndex in the Q-BRIDGE-MIB."
--    ::= { igmpSnoopRouterCurrentEntry 1 }
--
-- igmpSnoopRouterCurrentPorts OBJECT-TYPE
--    SYNTAX      PortList
--    MAX-ACCESS  read-only
--    STATUS      current
--    DESCRIPTION
--        "The set of ports which are current router ports.
--         Within this list, some router ports are static router ports.
--         Please refer to igmpSnoopRouterStaticTable."
--    ::= { igmpSnoopRouterCurrentEntry 2 }
--
-- igmpSnoopRouterCurrentStatus OBJECT-TYPE
--    SYNTAX      PortList
--    MAX-ACCESS  read-only
--    STATUS      current
--    DESCRIPTION
--        "The set of ports which are static router ports."
--    ::= { igmpSnoopRouterCurrentEntry 3 }
--
-- igmpSnoopRouterStaticTable OBJECT-TYPE
--    SYNTAX      SEQUENCE OF IgmpSnoopRouterStaticEntry
--    MAX-ACCESS  not-accessible
--    STATUS      current
--    DESCRIPTION
--        "Table for static router ports."
--    ::= { igmpSnoopMgt 9 }
--
-- igmpSnoopRouterStaticEntry OBJECT-TYPE
--    SYNTAX      IgmpSnoopRouterStaticEntry
--    MAX-ACCESS  not-accessible
--    STATUS      current
--    DESCRIPTION
--        "Entry for static router ports."
--    INDEX   { igmpSnoopRouterStaticVlanIndex }
--    ::= { 
-- igmpSnoopRouterStaticTable 1 }
--
-- IgmpSnoopRouterStaticEntry ::=
--    SEQUENCE {
--        igmpSnoopRouterStaticVlanIndex
--            Unsigned32,
--        igmpSnoopRouterStaticPorts
--            PortList,
--        igmpSnoopRouterStaticStatus
--            ValidStatus
--    }
--
-- igmpSnoopRouterStaticVlanIndex OBJECT-TYPE
--    SYNTAX      Unsigned32
--    MAX-ACCESS  not-accessible
--    STATUS      current
--    DESCRIPTION
--        "This is defined as dot1qVlanIndex in the Q-BRIDGE-MIB."
--    ::= { igmpSnoopRouterStaticEntry 1 }
--
-- igmpSnoopRouterStaticPorts OBJECT-TYPE
--    SYNTAX      PortList
--    MAX-ACCESS  read-create
--    STATUS      current
--    DESCRIPTION
--        "The set of ports which are static router ports."
--    ::= { igmpSnoopRouterStaticEntry 2 }
--
-- igmpSnoopRouterStaticStatus OBJECT-TYPE
--    SYNTAX      ValidStatus
--    MAX-ACCESS  read-create
--    STATUS      current
--    DESCRIPTION
--        "Setting this to valid(1) creates an entry.
--         Setting this to invalid(2) destroys an entry."
--    ::= { igmpSnoopRouterStaticEntry 3 }
--
-- igmpSnoopMulticastCurrentTable OBJECT-TYPE
--    SYNTAX      SEQUENCE OF IgmpSnoopMulticastCurrentEntry
--    MAX-ACCESS  not-accessible
--    STATUS      current
--    DESCRIPTION
--        "Table for current multicast addresses."
--    ::= { igmpSnoopMgt 10 }
--
-- igmpSnoopMulticastCurrentEntry OBJECT-TYPE
--    SYNTAX      IgmpSnoopMulticastCurrentEntry
--    MAX-ACCESS  not-accessible
--    STATUS      current
--    DESCRIPTION
--        "Entry for current multicast addresses."
--    INDEX   { igmpSnoopMulticastCurrentVlanIndex,
--              igmpSnoopMulticastCurrentIpAddress }
--    ::= { 
-- igmpSnoopMulticastCurrentTable 1 }
--
-- IgmpSnoopMulticastCurrentEntry ::=
--    SEQUENCE {
--        igmpSnoopMulticastCurrentVlanIndex
--            Unsigned32,
--        igmpSnoopMulticastCurrentIpAddress
--            IpAddress,
--        igmpSnoopMulticastCurrentPorts
--            PortList,
--        igmpSnoopMulticastCurrentStatus
--            PortList
--    }
--
-- igmpSnoopMulticastCurrentVlanIndex OBJECT-TYPE
--    SYNTAX      Unsigned32
--    MAX-ACCESS  not-accessible
--    STATUS      current
--    DESCRIPTION
--        "This is defined as dot1qVlanIndex in the Q-BRIDGE-MIB."
--    ::= { igmpSnoopMulticastCurrentEntry 1 }
--
-- igmpSnoopMulticastCurrentIpAddress OBJECT-TYPE
--    SYNTAX      IpAddress
--    MAX-ACCESS  not-accessible
--    STATUS      current
--    DESCRIPTION
--        "IP address of multicast group."
--    ::= { igmpSnoopMulticastCurrentEntry 2 }
--
-- igmpSnoopMulticastCurrentPorts OBJECT-TYPE
--    SYNTAX      PortList
--    MAX-ACCESS  read-only
--    STATUS      current
--    DESCRIPTION
--        "The set of ports which are members."
--    ::= { igmpSnoopMulticastCurrentEntry 3 }
--
-- igmpSnoopMulticastCurrentStatus OBJECT-TYPE
--    SYNTAX      PortList
--    MAX-ACCESS  read-only
--    STATUS      current
--    DESCRIPTION
--        "The set of ports which are static members."
--    ::= { igmpSnoopMulticastCurrentEntry 4 }
--
-- igmpSnoopMulticastStaticTable OBJECT-TYPE
--    SYNTAX      SEQUENCE OF IgmpSnoopMulticastStaticEntry
--    MAX-ACCESS  not-accessible
--    STATUS      current
--    DESCRIPTION
--        "Table for static multicast addresses."
--    ::= { igmpSnoopMgt 11 }
--
--igmpSnoopMulticastStaticEntry OBJECT-TYPE
--    SYNTAX      IgmpSnoopMulticastStaticEntry
--    MAX-ACCESS  not-accessible
--    STATUS      current
--    DESCRIPTION
--        "Entry for static multicast addresses."
--    INDEX   { igmpSnoopMulticastStaticVlanIndex,
--              igmpSnoopMulticastStaticIpAddress }
--    ::= { 
--igmpSnoopMulticastStaticTable 1 }
--
--IgmpSnoopMulticastStaticEntry ::=
--    SEQUENCE {
--        igmpSnoopMulticastStaticVlanIndex
--            Unsigned32,
--        igmpSnoopMulticastStaticIpAddress
--            IpAddress,
--        igmpSnoopMulticastStaticPorts
--            PortList,
--        igmpSnoopMulticastStaticStatus
--            ValidStatus
--    }
--
--igmpSnoopMulticastStaticVlanIndex OBJECT-TYPE
--    SYNTAX      Unsigned32
--    MAX-ACCESS  not-accessible
--    STATUS      current
--    DESCRIPTION
--        "The interface identified by a particular value of
--         this index is the same interface as identified by
--         the same value of dot1qVlanIndex in the Q-BRIDGE-MIB.
--         The entry will only appear here after a configure to
--         igmpSnoopMulticastStaticTable."
--    ::= { igmpSnoopMulticastStaticEntry 1 }
--
--igmpSnoopMulticastStaticIpAddress OBJECT-TYPE
--    SYNTAX      IpAddress
--    MAX-ACCESS  not-accessible
--    STATUS      current
--    DESCRIPTION
--        "IP address of multicast group."
--    ::= { igmpSnoopMulticastStaticEntry 2 }
--
--igmpSnoopMulticastStaticPorts OBJECT-TYPE
--    SYNTAX      PortList
--    MAX-ACCESS  read-create
--    STATUS      current
--    DESCRIPTION
--        "The set of ports which are members."
--    ::= { igmpSnoopMulticastStaticEntry 3 }
--
--igmpSnoopMulticastStaticStatus OBJECT-TYPE
--    SYNTAX      ValidStatus
--    MAX-ACCESS  read-create
--    STATUS      current
--    DESCRIPTION
--        "Setting this to valid(1) creates an entry.
--         Setting this to invalid(2) destroys an entry."
--    ::= { igmpSnoopMulticastStaticEntry 4 }
--
--igmpSnoopCurrentVlanTable OBJECT-TYPE
--        SYNTAX      SEQUENCE OF IgmpSnoopCurrentVlanEntry
--        MAX-ACCESS  not-accessible
--        STATUS      current
--        DESCRIPTION "Table for enabling or disabling IGMP snooping per VLAN."
--        ::= { igmpSnoopMgt 14 }
--
--igmpSnoopCurrentVlanEntry OBJECT-TYPE
--        SYNTAX      IgmpSnoopCurrentVlanEntry
--        MAX-ACCESS  not-accessible
--        STATUS      current
--        DESCRIPTION "Entry for enabling or disabling IGMP snooping."
--        INDEX       { igmpSnoopCurrentVlanIndex }
--        ::= { igmpSnoopCurrentVlanTable 1 }
--
--IgmpSnoopCurrentVlanEntry ::= SEQUENCE
--{
--    igmpSnoopCurrentVlanIndex     Unsigned32,
--    igmpSnoopCurrentVlanImmediateLeave    EnabledStatus
--}
--
--igmpSnoopCurrentVlanIndex OBJECT-TYPE
--        SYNTAX      Unsigned32
--        MAX-ACCESS  not-accessible
--        STATUS      current
--        DESCRIPTION "Same is dot1qVlanIndex in the Q-BRIDGE-MIB.
--            This table has only one entry - the entry for
--            the VLAN of the management interface."
--        ::= { igmpSnoopCurrentVlanEntry 1 }
--
--igmpSnoopCurrentVlanImmediateLeave OBJECT-TYPE
--        SYNTAX      EnabledStatus
--        MAX-ACCESS  read-write
--        STATUS      current
--        DESCRIPTION "The parameter to enable or disable the Immediate-Leave feature on this VLAN."
--        ::= { igmpSnoopCurrentVlanEntry 3 }
--
--igmpSnoopLeaveProxy OBJECT-TYPE
--        SYNTAX      EnabledStatus
--        MAX-ACCESS  read-write
--        STATUS      current
--        DESCRIPTION "This enables or disables Leave Proxy for IGMP Snooping."
--        ::= { igmpSnoopMgt 15 }
--
--igmpSnoopFilterStatus OBJECT-TYPE
--    SYNTAX      EnabledStatus
--    MAX-ACCESS  read-write
--    STATUS      current
--    DESCRIPTION
--        "Parameter to enable or disable IGMP filtering on the device."      
--    ::= { igmpSnoopMgt 17 }
--    
--igmpSnoopProfileTable OBJECT-TYPE
--        SYNTAX      SEQUENCE OF IgmpSnoopProfileEntry
--        MAX-ACCESS  not-accessible
--        STATUS      current        
--        DESCRIPTION "The table for configuring the IGMP snooping profile."
--        ::= { igmpSnoopMgt 18 }
--
--igmpSnoopProfileEntry OBJECT-TYPE
--        SYNTAX      IgmpSnoopProfileEntry
--        MAX-ACCESS  not-accessible
--        STATUS      current
--        DESCRIPTION "The entry for configuring the IGMP snooping profile."
--        INDEX       { igmpSnoopProfileId }
--        ::= { igmpSnoopProfileTable 1 }
--
--IgmpSnoopProfileEntry ::= SEQUENCE
--{
--    igmpSnoopProfileId               Unsigned32,    
--    igmpSnoopProfileAction           INTEGER,
--    igmpSnoopProfileStatus           ValidStatus
--}
--
--igmpSnoopProfileId OBJECT-TYPE
--        SYNTAX      Unsigned32
--        MAX-ACCESS  not-accessible
--        STATUS      current
--        DESCRIPTION "The ID of the IGMP snooping profile."
--        ::= { igmpSnoopProfileEntry 1 }      
--        
--igmpSnoopProfileAction OBJECT-TYPE
--    SYNTAX      INTEGER
--                {
--                    permit(1),
--                    deny(2)
--                }
--    MAX-ACCESS  read-write
--    STATUS      current
--    DESCRIPTION "The access mode of the IGMP snooping profile."
--    DEFVAL      { deny }
--    ::= { igmpSnoopProfileEntry 2 }
--
--igmpSnoopProfileStatus OBJECT-TYPE
--        SYNTAX      ValidStatus
--        MAX-ACCESS  read-write
--        STATUS      current
--        DESCRIPTION "Setting this to valid(1) creates an entry.
--                     Setting this to invalid(2) destroys an entry."
--        ::= { igmpSnoopProfileEntry 3 }
--    
--igmpSnoopProfileCtl      OBJECT IDENTIFIER   ::= { igmpSnoopMgt 19 }
--
--igmpSnoopProfileCtlId   OBJECT-TYPE
--        SYNTAX      Unsigned32
--        MAX-ACCESS  read-write
--        STATUS      current
--        DESCRIPTION "The ID of the IGMP snooping profile."
--        ::= { igmpSnoopProfileCtl 1 }
--
--igmpSnoopProfileCtlInetAddressType OBJECT-TYPE
--    SYNTAX      InetAddressType
--    MAX-ACCESS  read-write
--    STATUS      current
--    DESCRIPTION
--      "The address type is associated with this agent.
--       Only ipv4(1) type is supported."
--    ::= { igmpSnoopProfileCtl 2 }
--    
--igmpSnoopProfileCtlStartInetAddress OBJECT-TYPE
--        SYNTAX      InetAddress
--        MAX-ACCESS  read-write
--        STATUS      current
--        DESCRIPTION "The specified addresses in the start of the controlled IP multicast addresses."
--        ::= { igmpSnoopProfileCtl 3 }
--
--igmpSnoopProfileCtlEndInetAddress OBJECT-TYPE
--        SYNTAX      InetAddress
--        MAX-ACCESS  read-write
--        STATUS      current
--        DESCRIPTION "The specified addresses in the end of the controlled IP multicast addresses."
--        ::= { igmpSnoopProfileCtl 4 }
--        
--igmpSnoopProfileCtlAction   OBJECT-TYPE
--        SYNTAX      INTEGER
--        {
--            noAction(1),
--            create(2),
--            destroy(3)
--        }
--        MAX-ACCESS  read-write
--        STATUS      current
--        DESCRIPTION "Setting it to create(2) creates the range of the controlled IP multicast addresses.
--                     Setting it to destroy(3) destroys the range of the controlled IP multicast addresses.
--                     When the action is completed, this object becomes noAction(1)."
--        ::= { igmpSnoopProfileCtl 5 }
--
--igmpSnoopProfileRangeTable OBJECT-TYPE
--        SYNTAX      SEQUENCE OF IgmpSnoopProfileRangeEntry
--        MAX-ACCESS  not-accessible
--        STATUS      current        
--        DESCRIPTION "The table for configuring the range of the IGMP snooping profile."
--        ::= { igmpSnoopMgt 20 }
--
--igmpSnoopProfileRangeEntry OBJECT-TYPE
--        SYNTAX      IgmpSnoopProfileRangeEntry
--        MAX-ACCESS  not-accessible
--        STATUS      current
--        DESCRIPTION "The entry for configuring the range of the IGMP snooping profile."
--        INDEX       { igmpSnoopProfileRangeProfileId ,igmpSnoopProfileRangeInetAddressType,igmpSnoopProfileRangeStartInetAddress }
--        ::= { igmpSnoopProfileRangeTable 1 }
--
--IgmpSnoopProfileRangeEntry ::= SEQUENCE
--{
--    igmpSnoopProfileRangeProfileId           Unsigned32,
--    igmpSnoopProfileRangeInetAddressType     InetAddressType,      
--    igmpSnoopProfileRangeStartInetAddress    InetAddress,
--    igmpSnoopProfileRangeEndInetAddress      InetAddress,
--    igmpSnoopProfileRangeAction              INTEGER
--}
--
--igmpSnoopProfileRangeProfileId  OBJECT-TYPE
--        SYNTAX      Unsigned32
--        MAX-ACCESS  not-accessible
--        STATUS      current
--        DESCRIPTION "This is defined as igmpSnoopProfileId."
--        ::= { igmpSnoopProfileRangeEntry 1 }
--        
--igmpSnoopProfileRangeInetAddressType OBJECT-TYPE
--    SYNTAX      InetAddressType
--    MAX-ACCESS  not-accessible
--    STATUS      current
--    DESCRIPTION
--      "The address type is associated with this agent.
--        Only ipv4(1) type is supported."
--    ::= { igmpSnoopProfileRangeEntry 2 }
--    
--igmpSnoopProfileRangeStartInetAddress OBJECT-TYPE
--        SYNTAX      InetAddress
--        MAX-ACCESS  not-accessible
--        STATUS      current
--        DESCRIPTION "The specified addresses in the start of the controlled IP multicast addresses."
--        ::= { igmpSnoopProfileRangeEntry 3 }
--
--igmpSnoopProfileRangeEndInetAddress OBJECT-TYPE
--        SYNTAX      InetAddress
--        MAX-ACCESS  read-only
--        STATUS      current
--        DESCRIPTION "The specified addresses in the end of the controlled IP multicast addresses."
--        ::= { igmpSnoopProfileRangeEntry 4 }
--        
--igmpSnoopProfileRangeAction OBJECT-TYPE
--    SYNTAX      INTEGER
--                {
--                    permit(1),
--                    deny(2)
--                }
--    MAX-ACCESS  read-only
--    STATUS      current
--    DESCRIPTION "The access mode of the IGMP snooping profile."
--    DEFVAL      { deny }
--    ::= { igmpSnoopProfileRangeEntry 5 }  
-- 
--igmpSnoopFilterPortTable OBJECT-TYPE
--        SYNTAX      SEQUENCE OF IgmpSnoopFilterPortEntry
--        MAX-ACCESS  not-accessible
--        STATUS      current        
--        DESCRIPTION "Table for port configuration in IGMP filtering."
--        ::= { igmpSnoopMgt 21 }
--
--igmpSnoopFilterPortEntry OBJECT-TYPE
--        SYNTAX      IgmpSnoopFilterPortEntry
--        MAX-ACCESS  not-accessible
--        STATUS      current
--        DESCRIPTION "Entry for port configuration in IGMP filtering."
--        INDEX       { igmpSnoopFilterPortIndex }
--        ::= { igmpSnoopFilterPortTable 1 }
--
--IgmpSnoopFilterPortEntry ::= SEQUENCE
--{
--    igmpSnoopFilterPortIndex              Unsigned32,    
--    igmpSnoopFilterPortProfileId          Integer32   
--}
--
--igmpSnoopFilterPortIndex OBJECT-TYPE
--        SYNTAX      Unsigned32
--        MAX-ACCESS  not-accessible
--        STATUS      current
--        DESCRIPTION "The port and trunk (including trunk members) interface of
--                     the portTable. The interface identified by a particular value
--                     of this index is the same interface identified by the same
--                     value of ifIndex in the IF-MIB."
--        ::= { igmpSnoopFilterPortEntry 1 }
--        
--igmpSnoopFilterPortProfileId OBJECT-TYPE
--        SYNTAX     Integer32
--        MAX-ACCESS read-write
--        STATUS     current
--        DESCRIPTION
--            "The igmpSnoopProfileEntry identified by a particular value of this index
--             is the same interface identified by the same value of the igmpSnoopProfileId
--             object. If there is no corresponding entry in the igmpSnoopProfileTable,
--             then no association exists. In particular, if this value is zero, no 
--             associated profile will be generated, as zero is not a valid profile index."
--        ::= { igmpSnoopFilterPortEntry 2 }
--    
--igmpSnoopThrottlePortTable OBJECT-TYPE
--        SYNTAX      SEQUENCE OF IgmpSnoopThrottlePortEntry
--        MAX-ACCESS  not-accessible
--        STATUS      current
--        DESCRIPTION "Table for port configuration in IGMP throttling."
--        ::= { igmpSnoopMgt 22 }
--
--igmpSnoopThrottlePortEntry OBJECT-TYPE
--        SYNTAX      IgmpSnoopThrottlePortEntry
--        MAX-ACCESS  not-accessible
--        STATUS      current
--        DESCRIPTION "Entry for port configuration in IGMP throttling."
--        INDEX       { igmpSnoopThrottlePortIndex }
--        ::= { igmpSnoopThrottlePortTable 1 }
--
--IgmpSnoopThrottlePortEntry ::= SEQUENCE
--{
--    igmpSnoopThrottlePortIndex            Unsigned32,
--    igmpSnoopThrottlePortRunningStatus    INTEGER,
--    igmpSnoopThrottlePortAction           INTEGER,
--    igmpSnoopThrottlePortMaxGroups        Integer32,
--    igmpSnoopThrottlePortCurrentGroups    Integer32
--}
--
--igmpSnoopThrottlePortIndex OBJECT-TYPE
--        SYNTAX      Unsigned32
--        MAX-ACCESS  not-accessible
--        STATUS      current
--        DESCRIPTION "The port and trunk (including trunk members) interface of
--                     the portTable. The interface identified by a particular value
--                     of this index is the same interface identified by the same
--                     value of ifIndex in the IF-MIB."
--        ::= { igmpSnoopThrottlePortEntry 1 }
--
--igmpSnoopThrottlePortRunningStatus OBJECT-TYPE
--        SYNTAX  TruthValue
--        MAX-ACCESS  read-only
--        STATUS      current
--        DESCRIPTION "Describes the running status of the IGMP throttling to the switch. 
--                     A value of true(1) indicates the IGMP throttling mechanism is active.
--                     A value of false(2) indicates the IGMP throttling mechanism is inactive."
--        ::= { igmpSnoopThrottlePortEntry 2 }
--
--igmpSnoopThrottlePortAction OBJECT-TYPE
--    SYNTAX      INTEGER
--                {
--                    replace(1),
--                    deny(2)
--                }
--    MAX-ACCESS  read-write
--    STATUS      current
--    DESCRIPTION "The action mode of the IGMP throttling. A value of replace(1)
--                 means to replace a joined multicast group randomly when an interface 
--                 receives an IGMP report and the number of current joined multicast groups
--                 is equal to the maximum number of IGMP groups that the interface can join.
--                 A value of deny(2) means to deny the IGMP report request when an interface
--                 receives an IGMP report and the number of current joined multicast groups
--                 is equal to the maximum number of IGMP groups that the interface can join."
--    DEFVAL      { deny }
--    ::= { igmpSnoopThrottlePortEntry 3 }
--        
--igmpSnoopThrottlePortMaxGroups  OBJECT-TYPE
--        SYNTAX      Integer32(0..64)
--        MAX-ACCESS  read-write
--        STATUS      current
--        DESCRIPTION "The maximum number of IGMP groups that the interface can join."
--        ::= { igmpSnoopThrottlePortEntry 4 }
--
--igmpSnoopThrottlePortCurrentGroups   OBJECT-TYPE
--        SYNTAX      Integer32
--        MAX-ACCESS  read-only
--        STATUS      current
--        DESCRIPTION "The current number of IGMP groups that the interface has joined."
--        ::= { igmpSnoopThrottlePortEntry 5}
--
----
---- The Probe Configuration Group
----
---- This group controls the configuration of various operating
---- parameters of the probe.
--
--netConfigTable  OBJECT-TYPE
--    SYNTAX     SEQUENCE OF NetConfigEntry
--    MAX-ACCESS not-accessible
--    STATUS     current
--    DESCRIPTION
--        "A table of netConfigEntries."
--    ::= { ipMgt 1 }
--
--netConfigEntry  OBJECT-TYPE
--    SYNTAX     NetConfigEntry
--    MAX-ACCESS not-accessible
--    STATUS     current
--    DESCRIPTION
--        "A set of configuration parameters for a particular
--        network interface on this device. If the device has no network
--        interface, this table is empty.
--
--        The index is composed of the ifIndex assigned to the
--        corresponding interface."
--    INDEX  { netConfigIfIndex, netConfigIPAddress, netConfigSubnetMask }
--    ::= { netConfigTable 1 }
--
--NetConfigEntry ::= SEQUENCE {
--    netConfigIfIndex           Integer32,
--    netConfigIPAddress         IpAddress,
--    netConfigSubnetMask        IpAddress,
--    netConfigPrimaryInterface  INTEGER,
--    netConfigUnnumbered        INTEGER,
--    netConfigStatus            RowStatus
--}
--
--
--
--
--netConfigIfIndex  OBJECT-TYPE
--    SYNTAX     Integer32
--    MAX-ACCESS not-accessible
--    STATUS     current
--    DESCRIPTION
--        "VLAN interface on which this entry is defined.
--        This is defined as ifIndex in the IF-MIB."
--    ::= { netConfigEntry 1 }
--
--netConfigIPAddress  OBJECT-TYPE
--    SYNTAX     IpAddress
--    MAX-ACCESS not-accessible
--    STATUS     current
--    DESCRIPTION
--        "The IP address of this Net interface.  The default value
--        for this object is 0.0.0.0.  If either the netConfigIPAddress
--        or netConfigSubnetMask are 0.0.0.0, then when the device
--        boots, it may use BOOTP to try to figure out what these
--        values should be. If BOOTP fails, before the device
--        can talk on the network, this value must be configured
--        (e.g., through a terminal attached to the device). If BOOTP is
--        used, care should be taken to not send BOOTP broadcasts too
--        frequently and to eventually send very infrequently if no
--        replies are received."
--    ::= { netConfigEntry 2 }
--
--netConfigSubnetMask  OBJECT-TYPE
--    SYNTAX     IpAddress
--    MAX-ACCESS not-accessible
--    STATUS     current
--    DESCRIPTION
--        "The subnet mask of this Net interface.  The default value
--        for this object is 0.0.0.0.  If either the netConfigIPAddress
--        or netConfigSubnetMask are 0.0.0.0, then when the device
--        boots, it may use BOOTP to try to figure out what these
--        values should be. If BOOTP fails, before the device
--        can talk on the network, this value must be configured
--        (e.g., through a terminal attached to the device). If BOOTP is
--        used, care should be taken to not send BOOTP broadcasts too
--        frequently and to eventually send very infrequently if no
--        replies are received."
--    ::= { netConfigEntry 3 }
--
--netConfigPrimaryInterface OBJECT-TYPE
--    SYNTAX     INTEGER
--               {
--                   primary(1),
--                   secondary(2)
--               }
--    MAX-ACCESS read-create
--    STATUS     current
--    DESCRIPTION
--        "Whether this is a primary interface."
--    ::= { netConfigEntry 4 }
--
--netConfigUnnumbered OBJECT-TYPE
--    SYNTAX     INTEGER
--               {
--                   unnumbered(1),
--                   notUnnumbered(2)
--               }
--    MAX-ACCESS read-create
--    STATUS     current
--    DESCRIPTION
--        "Whether this is an unnumbered interface."
--    ::= { netConfigEntry 5 }
--
--netConfigStatus  OBJECT-TYPE
--    SYNTAX     RowStatus
--    MAX-ACCESS read-create
--    STATUS     current
--    DESCRIPTION
--        "The status of this netConfigEntry.
--
--        An entry may not exist in the active state unless all
--        objects in the entry have an appropriate value."
--    ::= { netConfigEntry 6 }
--
--netDefaultGateway  OBJECT-TYPE
--    SYNTAX     IpAddress
--    MAX-ACCESS read-write
--    STATUS     current
--    DESCRIPTION
--        "The IP Address of the default gateway.  If this value is
--        undefined or unknown, it shall have the value 0.0.0.0."
--    ::= { ipMgt 2 }
--
--ipHttpState OBJECT-TYPE
--    SYNTAX     INTEGER
--               {
--                   enabled(1),
--                   disabled(2)
--               }
--    MAX-ACCESS read-write
--    STATUS     current
--    DESCRIPTION
--        "Whether HTTP is enabled."
--    ::= { ipMgt 3 }
--
--ipHttpPort OBJECT-TYPE
--   SYNTAX     INTEGER (1..65535)
--    MAX-ACCESS read-write
--    STATUS     current
--    DESCRIPTION
--        "The port number for HTTP."
--    ::= { ipMgt 4 }
--
--ipDhcpRestart OBJECT-TYPE
--    SYNTAX     INTEGER
--               {
--                   restart(1),
--                   noRestart(2)
--               }
--    MAX-ACCESS read-write
--    STATUS     current
--    DESCRIPTION
--        "Write it to restart(1) to restart DHCP.
--        When read, this value always returns noRestart(2)."
--    ::= { ipMgt 5 }
--    
--ipHttpsState OBJECT-TYPE
--    SYNTAX     INTEGER
--               {
--                   enabled(1),
--                   disabled(2)
--               }
--    MAX-ACCESS read-write
--    STATUS     current
--    DESCRIPTION
--        "Whether HTTPS is enabled."
--    ::= { ipMgt 6 }
--
--ipHttpsPort OBJECT-TYPE
--    SYNTAX     INTEGER (1..65535)
--    MAX-ACCESS read-write
--    STATUS     current
--    DESCRIPTION
--        "The port number for HTTPS."
--    ::= { ipMgt 7 }
--
----dhcpMgt              OBJECT IDENTIFIER ::= { ipMgt 11 }
----dhcpOption82		 OBJECT IDENTIFIER ::= { dhcpMgt 4 }
----
----dhcpOption82Status OBJECT-TYPE
----SYNTAX     INTEGER {
----                   enabled(1),
----                   disabled(2)
----                 }
----	MAX-ACCESS read-write
----	STATUS     current
----	DESCRIPTION
----		"Set enabled(1) to enable DHCP Relay Option 82,
----			set disabled(2) to disable it."
----	::= { dhcpOption82 1 }
----	
----dhcpOption82Policy OBJECT-TYPE
----SYNTAX     INTEGER {
----                   drop(1),
----                   replace(2),
----                   keep(3)
----                 }
----	MAX-ACCESS read-write
----	STATUS     current
----	DESCRIPTION
----		"Provide three policies to handle packet"
----	::= { dhcpOption82 2 }
--
--pingMgt              OBJECT IDENTIFIER ::= { ipMgt 15 }
--
--pingIpAddress OBJECT-TYPE
--	SYNTAX     IpAddress
--	MAX-ACCESS read-write
--	STATUS     current
--	DESCRIPTION
--		"The address of the device to be pinged."
--	::= { pingMgt 1 }
--
--pingPacketSize OBJECT-TYPE
--	SYNTAX     Integer32 (32..512)
--	MAX-ACCESS read-write
--	STATUS     current
--	DESCRIPTION
--		"Specifies the size of ping packets to send to the target in this ping
--	     operation. The lower and upper boundaries of this object are 
--	     protocol-dependent."
--	DEFVAL { 32 }
--	::= { pingMgt 2 }
--	
--pingRoundTripTime OBJECT-TYPE
--    SYNTAX     Integer32
--    UNITS	   "milliseconds"
--	MAX-ACCESS read-only
--	STATUS     current
--	DESCRIPTION
--		"The last round trip time of a single ping operation. When the ping 
--		 opertion is time out, a value of -1 will be returned."
--	::= { pingMgt 3 }
--
--pingCompleted OBJECT-TYPE
--	SYNTAX     TruthValue
--	MAX-ACCESS read-only
--	STATUS     current
--	DESCRIPTION
--		"A value of true(1) will be read when this ping operation  
--		have been either responded to or timed out. A value of false(2) will be
--		read when there is a ping operation is currently running and all 
--		associate objects in pingMgt cannot be modified during this period."
--	::= { pingMgt 4 }
--
--pingAction OBJECT-TYPE
--	SYNTAX     INTEGER {
--                   noAction(1),
--                   pingStart(2)
--                 }
--	MAX-ACCESS read-write
--	STATUS     current
--	DESCRIPTION
--		"The action of the pingMgt. Set this objects to pingStart(2) to begin
--		 the ping operation. Once the action is set to pingStart(2), the
--		 associate pingMgt objects cannot be modified until this ping operation is
--		 completed (pingCompleted is true). When the ping has ended or no ping 
--		 operation is performing, this object will get a value of noAction(1)."
--	::= { pingMgt 5 }
--
----
---- bcastStormMgt
----
--
--bcastStormTable OBJECT-TYPE
--        SYNTAX      SEQUENCE OF BcastStormEntry
--        MAX-ACCESS  not-accessible
--        STATUS      current
--        DESCRIPTION "Table of descriptive and status information about
--                     configuration of each switch ports(including expansion slot)
--                     in this system."
--        ::= { bcastStormMgt 1 }
--
--bcastStormEntry OBJECT-TYPE
--        SYNTAX      BcastStormEntry
--        MAX-ACCESS  not-accessible
--        STATUS      current
--        DESCRIPTION "An entry in the table, containing information
--                     about configuration in one switch port of the switch."
--        INDEX       { bcastStormIfIndex }
--        ::= { bcastStormTable 1 }
--
--BcastStormEntry ::= SEQUENCE
--{
--    bcastStormIfIndex      Integer32,
--    bcastStormStatus       INTEGER,
--    bcastStormOctetRateScale   INTEGER,    
--    bcastStormOctetRateLevel    INTEGER    
--}
--
--bcastStormIfIndex OBJECT-TYPE
--        SYNTAX      Integer32
--        MAX-ACCESS  not-accessible
--        STATUS      current
--        DESCRIPTION "This is defined as ifIndex in the IF-MIB."
--        ::= { bcastStormEntry 1 }
--
--bcastStormStatus OBJECT-TYPE
--        SYNTAX      INTEGER
--                    {
--                        enabled(1),
--                        disabled(2)
--                    }
--        MAX-ACCESS  read-write
--        STATUS      current
--        DESCRIPTION "Whether broadcast storm protection is enabled."
--        ::= { bcastStormEntry 2 }
--
------------------------------
--bcastStormOctetRateScale OBJECT-TYPE
--        SYNTAX      INTEGER
--                    {
--                        scale-1m(0),
--                        scale-100k(1),
--                        scale-10k(2),
--                        scale-1k(3)
--                    }        
--        MAX-ACCESS  read-write
--        STATUS      current
--        DESCRIPTION "Broadcast storm scale as octets per second.
--                     If this is scale-1m(0), then Broadcast storm scale as 1M bytes per second,
--                     If this is scale-100k(1), then Broadcast storm scale as 100K bytes per second,
--                     If this is scale-10k(2), then Broadcast storm scale as 10K bytes per second,
--                     If this is scale-1k(3), then Broadcast storm scale as 1K bytes per second,"
--        ::= { bcastStormEntry 3 }
--        
--bcastStormOctetRateLevel OBJECT-TYPE
--        SYNTAX      INTEGER (1..127)
--        MAX-ACCESS  read-write
--        STATUS      current
--        DESCRIPTION "Broadcast storm level."
--        ::= { bcastStormEntry 5 }
----------------------------------        

-------------------------------------------------------------------------------
--bcastStormSampleType OBJECT-TYPE
--        SYNTAX      INTEGER
--                    {
--                        octet-rate(2)
--                    }
--        MAX-ACCESS  read-write
--        STATUS      current
--        DESCRIPTION "Sample type. If this is pkt-rate(1), then
--                     bcastStormPktRate is valid. If this is octet-rate(2),
--                     then bcastStormOctetRate is valid. If this is percent(3),
--                     then bcastStormPercent is valid."
--        ::= { bcastStormEntry 3 }
--
--bcastStormOctetRate OBJECT-TYPE
--        SYNTAX      INTEGER (64..95232000)
--        MAX-ACCESS  read-write
--        STATUS      current
--        DESCRIPTION "Broadcast storm threshold as octets per second."
--        ::= { bcastStormEntry 5 }
--------------------------------------------------------------------------------

--
-- vlanMgt
--

vlanTable OBJECT-TYPE
        SYNTAX      SEQUENCE OF VlanEntry
        MAX-ACCESS  not-accessible
        STATUS      current
        DESCRIPTION "Table for VLAN configuration."
        ::= { vlanMgt 1 }

vlanEntry OBJECT-TYPE
        SYNTAX      VlanEntry
        MAX-ACCESS  not-accessible
        STATUS      current
        DESCRIPTION "Entry for VLAN configuration."
        INDEX       { vlanIndex }
        ::= { vlanTable 1 }

VlanEntry ::= SEQUENCE
{
    vlanIndex               Unsigned32,
    vlanAddressMethod       INTEGER
}

vlanIndex OBJECT-TYPE
        SYNTAX      Unsigned32
        MAX-ACCESS  not-accessible
        STATUS      current
        DESCRIPTION "Same is dot1qVlanIndex in the Q-BRIDGE-MIB.
            This table has only one entry - the entry for
            the VLAN of the management interface."
        ::= { vlanEntry 1 }

vlanAddressMethod OBJECT-TYPE
        SYNTAX      INTEGER
                    {
                        user(1),
                        dhcp(2)
                    }
        MAX-ACCESS  read-write
        STATUS      current
        DESCRIPTION "Method to get the IP address."
        ::= { vlanEntry 2 }

vlanPortTable OBJECT-TYPE
        SYNTAX      SEQUENCE OF VlanPortEntry
        MAX-ACCESS  not-accessible
        STATUS      current
        DESCRIPTION "Table for port configuration in VLAN."
        ::= { vlanMgt 2 }

vlanPortEntry OBJECT-TYPE
        SYNTAX      VlanPortEntry
        MAX-ACCESS  not-accessible
        STATUS      current
        DESCRIPTION "Entry for port configuration in VLAN."
        INDEX       { vlanPortIndex }
        ::= { vlanPortTable 1 }

VlanPortEntry ::= SEQUENCE
{
    vlanPortIndex            Integer32,
    vlanPortMode             INTEGER,
    vlanPortPrivateVlanType  INTEGER
}

vlanPortIndex OBJECT-TYPE
        SYNTAX      Integer32
        MAX-ACCESS  not-accessible
        STATUS      current
        DESCRIPTION "This is defined as ifIndex in the IF-MIB."
        ::= { vlanPortEntry 1 }

vlanPortMode OBJECT-TYPE
        SYNTAX      INTEGER
                    {
                        hybrid(1),
                        dot1qTrunk(2),
                        access(3),
                        vlanUnaware(4)
                    }
        MAX-ACCESS  read-write
        STATUS      current
        DESCRIPTION "This variable sets the 802.1Q VLAN mode.
                    Setting it to hybrid(1) sets a hybrid link.
                    Setting it to dot1qTrunk(2) sets a trunk link.
                    Setting it to access(3) sets an access link, but
                    it is not supported in ES4528V product."
        ::= { vlanPortEntry 2 }

vlanPortPrivateVlanType OBJECT-TYPE
        SYNTAX     INTEGER
                   {
                       non-isolated(1),
                       isolated(2)
                   }
        MAX-ACCESS  read-write
        STATUS      current
        DESCRIPTION "The port type defined for Private vlan. In a private VLAN,
                     communication between isolated ports in that private VLAN is not permitted."
       ::= { vlanPortEntry 3 }        

--
-- priorityMgt
--

--prioIpPrecDscpStatus OBJECT-TYPE
--        SYNTAX      INTEGER
--                    {
--                        disabled(1),
--                        precedence(2),
--                        dscp(3),
--                        tos(4)
--                    }
--        MAX-ACCESS  read-write
--        STATUS      current
--        DESCRIPTION "Whether IP precedence or DSCP look-up is enabled."
--        ::= { priorityMgt 1 }
--
--prioIpPrecTable OBJECT-TYPE
--        SYNTAX      SEQUENCE OF PrioIpPrecEntry
--        MAX-ACCESS  not-accessible
--        STATUS      current
--        DESCRIPTION "Table for IP precedence priority mapping."
--        ::= { priorityMgt 2 }
--
--prioIpPrecEntry OBJECT-TYPE
--        SYNTAX      PrioIpPrecEntry
--        MAX-ACCESS  not-accessible
--        STATUS      current
--        DESCRIPTION "Entry for IP precendence priority mapping."
--        INDEX       { prioIpPrecPort, prioIpPrecValue }
--        ::= { prioIpPrecTable 1 }
--
--PrioIpPrecEntry ::= SEQUENCE
--{
--    prioIpPrecPort           Integer32,
--    prioIpPrecValue          Integer32,
--    prioIpPrecCos            INTEGER
--}
--
--prioIpPrecPort OBJECT-TYPE
--        SYNTAX      Integer32
--        MAX-ACCESS  not-accessible
--        STATUS      current
--        DESCRIPTION "This is defined as ifIndex in the IF-MIB."
--        ::= { prioIpPrecEntry 2 }
--
--prioIpPrecValue OBJECT-TYPE
--        SYNTAX      Integer32 (0..7)
--        MAX-ACCESS  not-accessible
--        STATUS      current
--        DESCRIPTION "Precedence value for this entry."
--        ::= { prioIpPrecEntry 3 }
--
--prioIpPrecCos OBJECT-TYPE
--        SYNTAX      INTEGER (0..7)
--        MAX-ACCESS  read-write
--        STATUS      current
--        DESCRIPTION "Class of service for this entry."
--        ::= { prioIpPrecEntry 4 }
--
--prioIpPrecRestoreDefault OBJECT-TYPE
--        SYNTAX      Integer32
--        MAX-ACCESS  read-write
--        STATUS      current
--        DESCRIPTION "This object is to restore IP Precedence
--                    settings of a port to default.
--                    To do this, write it to the value of ifIndex
--                    defined by the ifIndex in the IF-MIB.
--                    The range is 1-28 when port number is 26. 
--                    When read, this object always returns 0."
--        ::= { priorityMgt 3 }
--
--prioIpDscpTable OBJECT-TYPE
--        SYNTAX      SEQUENCE OF PrioIpDscpEntry
--        MAX-ACCESS  not-accessible
--        STATUS      current
--        DESCRIPTION "Table for IP DSCP priority mapping."
--        ::= { priorityMgt 4 }
--
--prioIpDscpEntry OBJECT-TYPE
--        SYNTAX      PrioIpDscpEntry
--        MAX-ACCESS  not-accessible
--        STATUS      current
--        DESCRIPTION "Entry for IP DSCP priority mapping."
--        INDEX       { prioIpDscpPort, prioIpDscpValue }
--        ::= { prioIpDscpTable 1 }
--
--PrioIpDscpEntry ::= SEQUENCE
--{
--    prioIpDscpPort           Integer32,
--    prioIpDscpValue          Integer32,
--    prioIpDscpCos            INTEGER
--}
--
--prioIpDscpPort OBJECT-TYPE
--        SYNTAX      Integer32
--        MAX-ACCESS  not-accessible
--        STATUS      current
--        DESCRIPTION "This is defined as ifIndex in the IF-MIB."
--        ::= { prioIpDscpEntry 1 }
--
--prioIpDscpValue OBJECT-TYPE
--        SYNTAX      Integer32 (0..63)
--        MAX-ACCESS  not-accessible
--        STATUS      current
--        DESCRIPTION "DSCP value for this entry."
--        ::= { prioIpDscpEntry 2 }
--
--prioIpDscpCos OBJECT-TYPE
--        SYNTAX      INTEGER (0..7)
--        MAX-ACCESS  read-write
--        STATUS      current
--        DESCRIPTION "Class of service for this entry."
--        ::= { prioIpDscpEntry 3 }
--
--prioIpDscpRestoreDefault OBJECT-TYPE
--        SYNTAX      Integer32
--        MAX-ACCESS  read-write
--        STATUS      current
--        DESCRIPTION "This object is to restore IP DSCP
--                    settings of a port to default.
--                    To do this, write it to the value of ifIndex
--                    defined by the ifIndex in the IF-MIB.
--                    The range is 1-28 when port number is 26.
--                    When read, this object always returns 0."
--        ::= { priorityMgt 5 }
--
--prioIpPortEnableStatus OBJECT-TYPE
--        SYNTAX      INTEGER
--                    {
--                        enabled(1),
--                        disabled(2)
--                    }
--        MAX-ACCESS  read-write
--        STATUS      current
--        DESCRIPTION "Whether IP Port priority look-up is enabled."
--        ::= { priorityMgt 6 }
--
--prioIpPortTable OBJECT-TYPE
--        SYNTAX      SEQUENCE OF PrioIpPortEntry
--        MAX-ACCESS  not-accessible
--        STATUS      current
--        DESCRIPTION "Table for IP port priority mapping."
--        ::= { priorityMgt 7 }
--
--prioIpPortEntry OBJECT-TYPE
--        SYNTAX      PrioIpPortEntry
--        MAX-ACCESS  not-accessible
--        STATUS      current
--        DESCRIPTION "Entry for IP port priority mapping."
--        INDEX       { prioIpPortPhysPort,prioIpPortValue }
--        ::= { prioIpPortTable 1 }
--
--PrioIpPortEntry ::= SEQUENCE
--{
--    prioIpPortPhysPort       Integer32,
--    prioIpPortValue          Integer32,
--    prioIpPortCos            INTEGER,
--    prioIpPortStatus         INTEGER
--}
--
--prioIpPortPhysPort OBJECT-TYPE
--        SYNTAX      Integer32
--        MAX-ACCESS  not-accessible
--        STATUS      current
--        DESCRIPTION "This is defined as ifIndex in the IF-MIB."
--        ::= { prioIpPortEntry 1 }
--
--prioIpPortValue OBJECT-TYPE
--        SYNTAX      Integer32 (1..65535)
--        MAX-ACCESS  not-accessible
--        STATUS      current
--        DESCRIPTION "IP port for this value."
--        ::= { prioIpPortEntry 2 }
--
--prioIpPortCos OBJECT-TYPE
--        SYNTAX      INTEGER (0..7)
--        MAX-ACCESS  read-create
--        STATUS      current
--        DESCRIPTION "Class of service for this entry."
--        ::= { prioIpPortEntry 3 }
--
--prioIpPortStatus OBJECT-TYPE
--        SYNTAX      INTEGER
--                    {
--                        valid(1),
--                        invalid(2)
--                    }
--        MAX-ACCESS  read-create
--        STATUS      current
--        DESCRIPTION "Writing this to valid(1) creates an entry.
--                     Writing this to invalid(2) destroys an entry."
--        ::= { prioIpPortEntry 4 }
--
--prioCopy            OBJECT IDENTIFIER ::= { priorityMgt 8 }
--
--prioCopyIpPrec OBJECT-TYPE
--        SYNTAX      OCTET STRING
--        MAX-ACCESS  read-write
--        STATUS      current
--        DESCRIPTION "Action to copy IP Precedence settings from
--                    a source port to many destination ports.
--                    The first four octets represent an integer for
--                    the source port, in high-to-low (big-endian) order.
--                    Starting from the 5th octet is destination port list
--                    in a form described by PortList in the Q-BRIDGE-MIB.
--                    Writing this object will perform copy.
--                    Reading this object will always get a zero-length
--                    octet string."
--        ::= { prioCopy 1 }
--
--prioCopyIpDscp OBJECT-TYPE
--        SYNTAX      OCTET STRING
--        MAX-ACCESS  read-write
--        STATUS      current
--        DESCRIPTION "Action to copy IP DSCP settings from
--                    a source port to many destination ports.
--                    The first four octets represent an integer for
--                    the source port, in high-to-low (big-endian) order.
--                    Starting from the 5th octet is destination port list
--                    in a form described by PortList in the Q-BRIDGE-MIB.
--                    Writing this object will perform copy.
--                    Reading this object will always get a zero-length
--                    octet string."
--        ::= { prioCopy 2 }
--
--prioCopyIpPort OBJECT-TYPE
--        SYNTAX      OCTET STRING
--        MAX-ACCESS  read-write
--        STATUS      current
--        DESCRIPTION "Action to copy IP Port settings from
--                    a source port to many destination ports.
--                    The first four octets represent an integer for
--                    the source port, in high-to-low (big-endian) order.
--                    Starting from the 5th octet is destination port list
--                    in a form described by PortList in the Q-BRIDGE-MIB.
--                    Writing this object will perform copy.
--                    Reading this object will always get a zero-length
--                    octet string."
--        ::= { prioCopy 3 }
--
--prioWrrTable OBJECT-TYPE
--        SYNTAX      SEQUENCE OF PrioWrrEntry
--        MAX-ACCESS  not-accessible
--        STATUS      current
--        DESCRIPTION "Table for weighted round robin (WRR)."
--        ::= { priorityMgt 9 }
--
--prioWrrEntry OBJECT-TYPE
--        SYNTAX      PrioWrrEntry
--        MAX-ACCESS  not-accessible
--        STATUS      current
--        DESCRIPTION "Entry for weighted round robin (WRR)."
--        INDEX       { prioWrrTrafficClass }
--        ::= { prioWrrTable 1 }
--
--PrioWrrEntry ::= SEQUENCE
--{
--    prioWrrTrafficClass    INTEGER,
--    prioWrrWeight          INTEGER
--}
--
--prioWrrTrafficClass OBJECT-TYPE
--        SYNTAX      INTEGER (0..7)
--        MAX-ACCESS  not-accessible
--        STATUS      current
--        DESCRIPTION "Traffic class for this entry, as defined in
--                    dot1dTrafficClass in the Q-BRIDGE-MIB. The actual
--                    maximum depends on the hardware, and is
--                    equal to dot1dPortNumTrafficClasses-1."
--        ::= { prioWrrEntry 1 }
--
--prioWrrWeight OBJECT-TYPE
--        SYNTAX      INTEGER (1..31)
--        MAX-ACCESS  read-write
--        STATUS      current
--        DESCRIPTION "Weight for this entry."
--        ::= { prioWrrEntry 2 }
--
--prioQueueMode OBJECT-TYPE
--        SYNTAX  INTEGER {
--                    wrr(1),
--                    strict(2),
--                    hybrid(4)
--                                     
--                }
--        MAX-ACCESS  read-write
--        STATUS      current
--        DESCRIPTION "The global status for the prioQueue.
--                    wrr(1),strict(2),hybrid(4)"
--        ::= { priorityMgt 10 }      
--
--
--
--prioIpTosTable OBJECT-TYPE
--        SYNTAX      SEQUENCE OF PrioIpTosEntry
--        MAX-ACCESS  not-accessible
--        STATUS      current
--        DESCRIPTION "Table for IP tos priority mapping."
--        ::= { priorityMgt 11 }
--
--prioIpTosEntry OBJECT-TYPE
--        SYNTAX      PrioIpTosEntry
--        MAX-ACCESS  not-accessible
--        STATUS      current
--        DESCRIPTION "Entry for IP tos priority mapping."
--        INDEX       { prioIpTosPort, prioIpTosValue }
--        ::= { prioIpTosTable 1 }
--
--PrioIpTosEntry ::= SEQUENCE
--{
--    prioIpTosPort           Integer32,
--    prioIpTosValue          Integer32,
--    prioIpTosCos            INTEGER
--}
--
--prioIpTosPort OBJECT-TYPE
--        SYNTAX      Integer32
--        MAX-ACCESS  not-accessible
--        STATUS      current
--        DESCRIPTION "This is defined as ifIndex in the IF-MIB."
--        ::= { prioIpTosEntry 2 }
--
--prioIpTosValue OBJECT-TYPE
--        SYNTAX      Integer32 (0..7)
--        MAX-ACCESS  not-accessible
--        STATUS      current
--        DESCRIPTION "Tos value for this entry."
--        ::= { prioIpTosEntry 3 }
--
--prioIpTosCos OBJECT-TYPE
--        SYNTAX      INTEGER (0..7)
--        MAX-ACCESS  read-write
--        STATUS      current
--        DESCRIPTION "Class of service for this entry."
--        ::= { prioIpTosEntry 4 }
--
--prioIpTosRestoreDefault OBJECT-TYPE
--        SYNTAX      Integer32
--        MAX-ACCESS  read-write
--        STATUS      current
--        DESCRIPTION "This object is to restore IP Tos
--                    settings of a port to default.
--                    To do this, write it to the value of ifIndex
--                    defined by the ifIndex in the IF-MIB.
--                    The range is 1-28 when port number is 26. 
--                    When read, this object always returns 0."
--        ::= { priorityMgt 12 }
--        
--                
----
---- trapDestMgt
----
--
----trapDestTable  OBJECT-TYPE
----    SYNTAX     SEQUENCE OF TrapDestEntry
----    MAX-ACCESS not-accessible
----    STATUS     current
----    DESCRIPTION
----        "A list of trap destination entries."
----    ::= { trapDestMgt 1 }
----
----trapDestEntry  OBJECT-TYPE
----    SYNTAX     TrapDestEntry
----    MAX-ACCESS not-accessible
----    STATUS     current
----    DESCRIPTION
----        "This entry includes a destination IP address to which to send
----        traps for this community."
----    INDEX { trapDestAddress }
----    ::= { trapDestTable 1 }
----
----TrapDestEntry ::= SEQUENCE {
----    trapDestAddress             IpAddress,
----    trapDestCommunity           OCTET STRING,
----    trapDestStatus              INTEGER,
----    trapDestVersion             INTEGER
----}
----
----trapDestAddress  OBJECT-TYPE
----    SYNTAX     IpAddress
----    MAX-ACCESS not-accessible
----    STATUS     current
----    DESCRIPTION
----        "The address to send traps."
----    ::= { trapDestEntry 1 }
----
----trapDestCommunity  OBJECT-TYPE
----    SYNTAX     OCTET STRING (SIZE(0..32))
----    MAX-ACCESS read-create
----    STATUS     current
----    DESCRIPTION
----        "A community to which this destination address belongs."
----    ::= { trapDestEntry 2 }
----
----trapDestStatus  OBJECT-TYPE
----    SYNTAX     INTEGER
----               {
----                   valid(1),
----                   invalid(2)
----               }
----    MAX-ACCESS read-create
----    STATUS     current
----    DESCRIPTION
----        "Writing this to valid(1) creates an entry.
----         Writing this to invalid(2) destroys an entry."
----    ::= { trapDestEntry 3 }
----
----trapDestVersion OBJECT-TYPE
----    SYNTAX     INTEGER
----               {
----                   version1(1),
----                   version2(2)
----               }
----    MAX-ACCESS read-create
----    STATUS     current
----    DESCRIPTION
----        "This variables represent the version of the Trap we wish to send to trap Receiver,
----         if the value is 1, mean we wish to send Version 1 trap, if the value is 2,
----         mean we wish to send version 2 trap."
----    ::= { trapDestEntry 4}
--
---- trapVar is for binding variables for traps, there is no value when
---- no trap is sent.
----trapVar OBJECT IDENTIFIER ::= { trapDestMgt 2 }   
----
----trapIpFilterRejectMode OBJECT-TYPE
----     SYNTAX      INTEGER
----                 {
----                     web(1),
----                     snmp(2),
----                     telnet(3)
----                 }
----     MAX-ACCESS  accessible-for-notify
----     STATUS      current
----     DESCRIPTION "This variable is for trap var binding, 
----                  indicated the ipfilter reject mode.
----                  web(1),
----                  snmp(2),
----                  telnet(3)."
----     ::= { trapVar 6 }
----
----trapIpFilterRejectIp OBJECT-TYPE
----     SYNTAX      Integer32
----     MAX-ACCESS  accessible-for-notify
----     STATUS      current
----     DESCRIPTION "This variable is for trap var binding, 
----                 indicating the IP address that rejected by the ipfilter."
----     ::= { trapVar 7 }    
--    
----
---- rateLimitMgt
----
--
--rateLimitMgt        OBJECT IDENTIFIER ::= { qosMgt 1 }
--
--rateLimitPortTable OBJECT-TYPE
--        SYNTAX      SEQUENCE OF RateLimitPortEntry
--        MAX-ACCESS  not-accessible
--        STATUS      current
--        DESCRIPTION "Table for rate limit of each port."
--        ::= { rateLimitMgt 2 }
--
--rateLimitPortEntry OBJECT-TYPE
--        SYNTAX      RateLimitPortEntry
--        MAX-ACCESS  not-accessible
--        STATUS      current
--        DESCRIPTION "Entry for rate limit of each port."
--        INDEX       { rlPortIndex }
--        ::= { rateLimitPortTable 1 }
-- 
--                  
--RateLimitPortEntry ::= SEQUENCE
--{
--    rlPortIndex              Integer32,    
--    rlPortInputStatus        EnabledStatus,
--    rlPortOutputStatus       EnabledStatus,
--    rlPortInputLevel         Integer32,
--    rlPortInputScale         INTEGER,
--    rlPortOutputLevel        Integer32,
--    rlPortOutputScale        INTEGER
--}
--
--rlPortIndex OBJECT-TYPE
--        SYNTAX      Integer32
--        MAX-ACCESS  not-accessible
--        STATUS      current
--        DESCRIPTION "The port and the trunk (including trunk member) interface of
--                     the portTable. The interface identified by a particular value
--                     of this index is the same interface as identified by the same 
--                     value of ifIndex in the IF-MIB."
--        ::= { rateLimitPortEntry 1 }
--
--rlPortInputStatus OBJECT-TYPE
--        SYNTAX      EnabledStatus                      
--        MAX-ACCESS  read-write
--        STATUS      current
--        DESCRIPTION "Whether input rate limit is enabled for this port."
--        ::= { rateLimitPortEntry 6 }
--
--rlPortOutputStatus OBJECT-TYPE
--        SYNTAX      EnabledStatus
--        MAX-ACCESS  read-write
--        STATUS      current
--        DESCRIPTION "Whether output rate limit is enabled for this port."
--        ::= { rateLimitPortEntry 7 }
--
--rlPortInputLevel OBJECT-TYPE
--        SYNTAX      Integer32(1..127)
--        MAX-ACCESS  read-write
--        STATUS      current
--        DESCRIPTION "The Level of the input rate limit.all ports range is 1..127"
--        ::= { rateLimitPortEntry 8 }
--
--rlPortInputScale OBJECT-TYPE
--        SYNTAX      INTEGER
--                    {
--                        scale-10m(0),
--                        scale-1m(1),
--                        scale-100k(2),
--                        scale-10k(3),
--                        scale-1k(4)
--                    }  
--        MAX-ACCESS  read-write
--        STATUS      current
--        DESCRIPTION "Rate Limit scale as octets per second.
--                     If this is scale-10m(0), then Rate Limit scale as 10M bytes per second,
--                     If this is scale-1m(1), then Rate Limit scale as 1M bytes per second,
--                     If this is scale-100k(2), then Rate Limit scale as 100K bytes per second,
--                     If this is scale-10k(3), then Rate Limit scale as 10K bytes per second,
--                     If this is scale-1k(4), then Rate Limit scale as 1K bytes per second,"
--        ::= { rateLimitPortEntry 9 }
--
--rlPortOutputLevel OBJECT-TYPE  
--        SYNTAX      Integer32(1..127)
--        MAX-ACCESS  read-write
--        STATUS      current
--        DESCRIPTION "The Level of the output rate limit.all ports range is 1..127"
--        ::= { rateLimitPortEntry 10 }
--
--rlPortOutputScale OBJECT-TYPE
--        SYNTAX      INTEGER
--                    {
--                        scale-10m(0),
--                        scale-1m(1),
--                        scale-100k(2),
--                        scale-10k(3),
--                        scale-1k(4)
--                    }                
--        MAX-ACCESS  read-write
--        STATUS      current
--        DESCRIPTION "Rate Limit scale as octets per second.
--                     If this is scale-10m(0), then Rate Limit scale as 10M bytes per second,
--                     If this is scale-1m(1), then Rate Limit scale as 1M bytes per second,
--                     If this is scale-100k(2), then Rate Limit scale as 100K bytes per second,
--                     If this is scale-10k(3), then Rate Limit scale as 10K bytes per second,
--                     If this is scale-1k(4), then Rate Limit scale as 1K bytes per second,"    
--        ::= { rateLimitPortEntry 11 }
--
--cosMgt        OBJECT IDENTIFIER ::= { qosMgt 3 }
-- 
----prioAclToCosMappingTable
--prioAclToCosMappingTable OBJECT-TYPE
--        SYNTAX      SEQUENCE OF PrioAclToCosMappingEntry
--        MAX-ACCESS  not-accessible
--        STATUS      current
--        DESCRIPTION "Table for ACL to CoS Mapping."
--        ::= { cosMgt 1 }
--
--prioAclToCosMappingEntry OBJECT-TYPE
--        SYNTAX      PrioAclToCosMappingEntry
--        MAX-ACCESS  not-accessible
--        STATUS      current
--        DESCRIPTION "Entry for ACL to CoS Mapping."
--        INDEX       { prioAclToCosMappingIfIndex, prioAclToCosMappingAclName }
--        ::= { prioAclToCosMappingTable 1 }
--
--PrioAclToCosMappingEntry ::= SEQUENCE
--{
--    prioAclToCosMappingIfIndex    Integer32,
--    prioAclToCosMappingAclName  DisplayString,    
--    prioAclToCosMappingCosValue      Integer32,
--    prioAclToCosMappingStatus      RowStatus
--}
--
--prioAclToCosMappingIfIndex OBJECT-TYPE
--        SYNTAX      Integer32 
--        MAX-ACCESS  not-accessible
--        STATUS      current
--        DESCRIPTION "The port interface of the prioAclToCosMappingEntry. The interface 
--                     identified by a particular value of this index is the 
--                     same interface as identified by the same value of 
--                     ifIndex in the IF-MIB."        
--        ::= { prioAclToCosMappingEntry 1 }
--        
--prioAclToCosMappingAclName OBJECT-TYPE
--        SYNTAX      DisplayString (SIZE(1..15))
--        MAX-ACCESS  not-accessible
--        STATUS      current
--        DESCRIPTION "The name of an IP ACL. Within a feature a unique name is
--                     used to identify the list to which the entry belongs 
--                     in the device."        
--        ::= { prioAclToCosMappingEntry 2 }
--     
--prioAclToCosMappingCosValue OBJECT-TYPE
--        SYNTAX      Integer32 (0..7)
--        MAX-ACCESS  read-create
--        STATUS      current
--        DESCRIPTION "CoS value of the prioAclToCosMappingTable."
--        ::= { prioAclToCosMappingEntry 3 } 
--
--prioAclToCosMappingStatus OBJECT-TYPE
--        SYNTAX      RowStatus
--        MAX-ACCESS  read-create
--        STATUS      current
--	    DESCRIPTION
--			"The status of this conceptual row entry. This object isused to manage the
--			creation and deletion of conceptual rows.
--			
--			The status column has six defined values:
--			
--			     - 'active', which indicates that the conceptual row is
--			     available for use by the managed device;
--			
--			     - 'notInService', which indicates that the conceptual
--			     row exists in the agent, but is unavailable for use by
--			     the managed device (see NOTE below);
--			
--			     - 'notReady', which indicates that the conceptual row
--			     exists in the agent, but is missing information
--			     necessary in order to be available for use by the
--			     managed device;
--			
--			     - 'createAndGo', which is supplied by a management
--			     station wishing to create a new instance of a
--			     conceptual row and to have its status automatically set
--			     to active, making it available for use by the managed
--			     device;
--			
--			     - 'createAndWait', which is supplied by a management
--			     station wishing to create a new instance of a
--			     conceptual row (but not make it available for use by
--			     the managed device); and,
--			
--			     - 'destroy', which is supplied by a management station
--			     wishing to delete all of the instances associated with
--			     an existing conceptual row.
--			
--			Whereas five of the six values (all except 'notReady') may
--			be specified in a management protocol set operation, only
--			three values will be returned in response to a management
--			protocol retrieval operation:  'notReady', 'notInService' or
--			'active'.  That is, when queried, an existing conceptual row
--			has only three states:  it is either available for use by
--			the managed device (the status column has value 'active');
--			it is not available for use by the managed device, though
--			the agent has sufficient information to make it so (the
--			status column has value 'notInService'); or, it is not
--			available for use by the managed device, and an attempt to
--			make it so would fail because the agent has insufficient
--			information (the state column has value 'notReady').
--
--            For a detailed description of this object, please refer to 
--            SNMPv2-TC MIB." 
--        ::= { prioAclToCosMappingEntry 4 } 
--
----
---- privateVlanMgt
----
--
--portSecurityMgt     OBJECT IDENTIFIER ::= { securityMgt 2 }
--radiusMgt           OBJECT IDENTIFIER ::= { securityMgt 4 }
--tacacsMgt           OBJECT IDENTIFIER ::= { securityMgt 5 }
--sshMgt              OBJECT IDENTIFIER ::= { securityMgt 6 }
--aclMgt              OBJECT IDENTIFIER ::= { securityMgt 7 }
--ipFilterMgt         OBJECT IDENTIFIER ::= { securityMgt 9 }
----macAuthMgt          OBJECT IDENTIFIER ::= { securityMgt 13}
----netAccessMgt        OBJECT IDENTIFIER ::= { securityMgt 14}
--
--
--    
---- PortSecurityMgt
--
---- Management for Port Security. A secure port only allowes
---- secure MAC addresses to come in.
--
--
--
--portSecPortTable OBJECT-TYPE 
--        SYNTAX      SEQUENCE OF PortSecPortEntry
--        MAX-ACCESS  not-accessible
--        STATUS      current
--        DESCRIPTION "The Port Security(MAC bindind) Table"
--        ::= { portSecurityMgt 1 }
--        
--portSecPortEntry OBJECT-TYPE  
--        SYNTAX      PortSecPortEntry
--        MAX-ACCESS  not-accessible
--        STATUS      current
--        DESCRIPTION "The entry of portSecPortTable"
--        INDEX       { portSecPortIndex }
--        ::= { portSecPortTable 1 }
--
--PortSecPortEntry ::= SEQUENCE
--{
--      portSecPortIndex      Integer32,
--      portSecPortStatus     EnabledStatus,
--      portSecAction         INTEGER,
--      portSecMaxMacCount       Integer32
--}
--
--portSecPortIndex OBJECT-TYPE
--        SYNTAX      Integer32
--        MAX-ACCESS  not-accessible
--        STATUS      current
--        DESCRIPTION "The port and the trunk (excluding trunk members) interface of
--                     the portTable. The interface identified by a particular value
--                     of this index is the same interface as identified by the same 
--                     value of ifIndex in the IF-MIB."
--        ::= { portSecPortEntry 1 }
--
--portSecPortStatus OBJECT-TYPE
--        SYNTAX      EnabledStatus
--        MAX-ACCESS  read-write
--        STATUS      current
--        DESCRIPTION "Set enabled(1) to enable port security and set disabled(2) to 
--                     disable port security."
--        ::= { portSecPortEntry 2  }
--
--portSecAction OBJECT-TYPE
--        SYNTAX        INTEGER
--                      {
--                        none(1),
--                        trap(2),
--                        shutdown(3),
--                        trapAndShutdown(4)
--                      }
--        MAX-ACCESS    read-write
--        STATUS        current
--        DESCRIPTION  "The corresponding actions that will take place when a
--                      port is under intrusion, when this variable is set to
--                      none(1), no action will be performed, when this variable is
--                      set to trap(2), a swPortSecurityTrap trap will be sent,
--                      when this variable is set to shutdown(3), the port will
--                      shutdown, when this variable is set to
--                      trapAndShutdown(4), a swPortSecurityTrap will be sent
--                      and the port will shutdown."
--        ::= { portSecPortEntry 3  }
--
--portSecMaxMacCount OBJECT-TYPE
--        SYNTAX       Integer32(0..1024)
--        MAX-ACCESS   read-write
--        STATUS       current
--        DESCRIPTION  "The maximun number of MAC addresses that will be learned and locked.
--                      When we change the value of this variable, if the 
--                      portSecPortStatus is enabled, we will discard all secure MAC 
--                      and begin to learn again, until the number of MAC has reached
--                      this value, and only the secure MAC addresses can enter
--                      this port. If the portSecPortStatus is disabled, we will begin
--                      to learn the MAC, and auto enabled the portSecPortStatus when 
--                      the MAC has reached this value."
--        ::= { portSecPortEntry 4 }
--        
----
---- radiusMgt
----
--
---- Management for Remote Authentication Dial-In User Service (RADIUS).
----SYS_ADPT_MAX_NBR_OF_RADIUS_SERVERS=1: single server
----SYS_ADPT_MAX_NBR_OF_RADIUS_SERVERS>1: multiple server
--
--radiusServerGlobalAuthPort OBJECT-TYPE
--        SYNTAX      Integer32 (1..65535)
--        MAX-ACCESS  read-write
--        STATUS      current
--        DESCRIPTION "Aauthentication port number for RADIUS server.
--                     When specified radius server do not set
--                     aauthentication port number, this value is used."
--        ::= { radiusMgt 1 }
--                
--radiusServerGlobalAcctPort OBJECT-TYPE
--        SYNTAX      Integer32 (1..65535)
--        MAX-ACCESS  read-write
--        STATUS      current
--        DESCRIPTION "Accounting port number of RADIUS server.
--                    When specified radius server do not set
--                    accounting port number, this value is used."
--        ::= { radiusMgt 2 }
--
--radiusServerGlobalKey OBJECT-TYPE
--        SYNTAX      DisplayString(SIZE(0..48))
--        MAX-ACCESS  read-write
--        STATUS      current
--        DESCRIPTION "Key for RADIUS.  This variable can only be written.
--                     When this variable is read, it always returns a
--                     zero-length string.
--                     When specified radius server do not set
--                     key, this this value is used."
--        ::= { radiusMgt 3 }
--
--radiusServerGlobalRetransmit OBJECT-TYPE
--        SYNTAX      INTEGER (1..30)
--        MAX-ACCESS  read-write
--        STATUS      current
--        DESCRIPTION "Maximum number of retransmissions for RADIUS.
--                     When specified radius server do not set
--                     maximum number of retransmissions, this value is used."
--        ::= { radiusMgt 4 }
--
--radiusServerGlobalTimeout OBJECT-TYPE
--        SYNTAX      INTEGER (1..65535)
--        MAX-ACCESS  read-write
--        STATUS      current
--        DESCRIPTION "Timeout for RADIUS.
--                     When specified radius server do not set
--                     timeout, this value is used."
--        ::= { radiusMgt 5 }
--
----radiusServerTable
--
--radiusServerTable OBJECT-TYPE
--        SYNTAX      SEQUENCE OF RadiusServerEntry
--        MAX-ACCESS  not-accessible
--        STATUS      current
--        DESCRIPTION "The table for RADIUS server."
--        ::= { radiusMgt 7 }
--
--radiusServerEntry OBJECT-TYPE
--        SYNTAX      RadiusServerEntry
--        MAX-ACCESS  not-accessible
--        STATUS      current
--        DESCRIPTION "The conceptual row for radiusServerTable."
--        INDEX       { radiusServerIndex }
--        ::= { radiusServerTable 1 }
--
--RadiusServerEntry ::= SEQUENCE
--{
--   radiusServerIndex                  Integer32,
--   radiusServerAddress                IpAddress,
--   radiusServerAuthPortNumber         Integer32,
--   radiusServerAcctPortNumber         Integer32,
--   radiusServerKey                    DisplayString,
--   radiusServerRetransmit             Integer32,
--   radiusServerTimeout                Integer32,
--   radiusServerStatus                 ValidStatus
--}
--
--radiusServerIndex OBJECT-TYPE
--        SYNTAX      Integer32
--        MAX-ACCESS  not-accessible
--        STATUS      current
--        DESCRIPTION "The RADIUS server index in the table."
--        ::= { radiusServerEntry 1 }
--        
--radiusServerAddress OBJECT-TYPE
--        SYNTAX      IpAddress
--        MAX-ACCESS  read-create
--        STATUS      current
--        DESCRIPTION "IP address of a RADIUS server."
--        ::= { radiusServerEntry 2 }
--
--radiusServerAuthPortNumber OBJECT-TYPE
--        SYNTAX      Integer32 (1..65535)
--        MAX-ACCESS  read-create
--        STATUS      current
--        DESCRIPTION "Authentication port number of RADIUS server."
--        ::= { radiusServerEntry 3 }
--
--radiusServerAcctPortNumber OBJECT-TYPE
--        SYNTAX      Integer32 (1..65535)
--        MAX-ACCESS  read-create
--        STATUS      current
--        DESCRIPTION "Accounting port number of RADIUS server."
--        ::= { radiusServerEntry 4 }
--
--radiusServerKey OBJECT-TYPE
--        SYNTAX      DisplayString(SIZE(0..48))
--        MAX-ACCESS  read-write
--        STATUS      current
--        DESCRIPTION "Key for RADIUS.  This variable can only be written.
--                     When this variable is read, it always returns a
--                     zero-length string."
--        ::= { radiusServerEntry 5 }
--
--radiusServerRetransmit OBJECT-TYPE
--        SYNTAX      Integer32 (1..30)
--        MAX-ACCESS  read-write
--        STATUS      current
--        DESCRIPTION "Timeout for RADIUS."
--        ::= { radiusServerEntry 6 }
--
--radiusServerTimeout OBJECT-TYPE
--        SYNTAX      Integer32 (1..65535)
--        MAX-ACCESS  read-write
--        STATUS      current
--        DESCRIPTION "Timeout for RADIUS."
--        ::= { radiusServerEntry 7 }
--        
--radiusServerStatus OBJECT-TYPE
--        SYNTAX      ValidStatus
--        MAX-ACCESS  read-create
--        STATUS      current
--        DESCRIPTION "Setting this to valid(1) creates an entry.
--                     Setting this to invalid(2) destroys an entry."        
--        ::= { radiusServerEntry 8 }
--
----
---- tacacsMgt
----
--
---- Management for Terminal Access Controller Access Control System plus (TACACS+).
--
---- Global server setting
--tacacsPlusServerGlobalPortNumber OBJECT-TYPE
--        SYNTAX      Integer32 (1..65535)
--        MAX-ACCESS  read-write
--        STATUS      current
--        DESCRIPTION "TCP port number of TACACS+ server.
--                     When specified TACACS+ server do not set
--                     TCP port number, this this value is used."
--        ::= { tacacsMgt 2 }
--
--tacacsPlusServerGlobalKey OBJECT-TYPE
--        SYNTAX      DisplayString(SIZE(0..48))
--        MAX-ACCESS  read-write
--        STATUS      current
--        DESCRIPTION  "The encryption key used to encrpt the traffic between client and
--                  TACACS+ server. Do not use blank spaces in the string. This variable
--                  can only be set. When this variable is read, it always returns a
--                  zero-length string.When specified TACACS+ server do not set
--                  the encryption key , this this value is used."
--        ::= { tacacsMgt 3 }
--
--tacacsPlusServerTable OBJECT-TYPE
--        SYNTAX      SEQUENCE OF TacacsPlusServerEntry
--        MAX-ACCESS  not-accessible
--        STATUS      current
--        DESCRIPTION "The table for TACACS+ server."
--        ::= { tacacsMgt 4 }
--
--tacacsPlusServerEntry OBJECT-TYPE
--        SYNTAX      TacacsPlusServerEntry
--        MAX-ACCESS  not-accessible
--        STATUS      current
--        DESCRIPTION "The conceptual row for tacacsPlusServerTable."
--        INDEX       { tacacsPlusServerIndex }
--        ::= { tacacsPlusServerTable 1 }
--
--TacacsPlusServerEntry ::= SEQUENCE
--{
--   tacacsPlusServerIndex            Integer32,
--   tacacsPlusServerAddress          IpAddress,
--   tacacsPlusServerPortNumber       Integer32,
--   tacacsPlusServerKey	            DisplayString,
--   tacacsPlusServerStatus           ValidStatus,
--   tacacsPlusServerRetransmit       Integer32,
--   tacacsPlusServerTimeout          Integer32
--}
--
--tacacsPlusServerIndex OBJECT-TYPE
--        SYNTAX      Integer32
--        MAX-ACCESS  not-accessible
--        STATUS      current
--        DESCRIPTION "TACACS+ server index."
--        ::= { tacacsPlusServerEntry 1 }
--
--tacacsPlusServerAddress OBJECT-TYPE
--        SYNTAX      IpAddress
--        MAX-ACCESS  read-create
--        STATUS      current
--        DESCRIPTION "IP address of a TACACS+ server."
--        ::= { tacacsPlusServerEntry 2 }
--
--tacacsPlusServerPortNumber OBJECT-TYPE
--        SYNTAX      Integer32 (1..65535)
--        MAX-ACCESS  read-create
--        STATUS      current
--        DESCRIPTION "TCP port number of a TACACS+ server."
--        ::= { tacacsPlusServerEntry 3 }
--
--tacacsPlusServerKey OBJECT-TYPE
--        SYNTAX      DisplayString(SIZE(0..48))
--        MAX-ACCESS  read-create
--        STATUS      current
--        DESCRIPTION "The encryption key used to encrpt the traffic between client and
--                     TACACS+ server. Do not use blank spaces in the string. This
--                     variable can only be set. When this variable is read, it always
--                     returns a zero-length string."
--        ::= { tacacsPlusServerEntry 4 }
--
--tacacsPlusServerStatus OBJECT-TYPE
--        SYNTAX      ValidStatus
--        MAX-ACCESS  read-create
--        STATUS      current
--        DESCRIPTION "Setting this to valid(1) creates an entry.
--                     Setting this to invalid(2) destroys an entry."
--        ::= { tacacsPlusServerEntry 8 }
--
--tacacsPlusServerRetransmit OBJECT-TYPE
--        SYNTAX      Integer32 (1..30)
--        MAX-ACCESS  read-create
--        STATUS      current
--        DESCRIPTION "The maximum number of retransmissions for TACACS+."
--        ::= { tacacsPlusServerEntry 9 }
--
--tacacsPlusServerTimeout OBJECT-TYPE
--        SYNTAX      Integer32 (1..540)
--        UNITS       "seconds"
--        MAX-ACCESS  read-create
--        STATUS      current
--        DESCRIPTION "Timeout for TACACS+."
--        ::= { tacacsPlusServerEntry 10 }
--
--tacacsPlusServerGlobalRetransmit OBJECT-TYPE
--        SYNTAX      Integer32 (1..30)
--        MAX-ACCESS  read-write
--        STATUS      current
--        DESCRIPTION "The maximum number of retransmissions for TACACS+ global server."
--        ::= { tacacsMgt 5 }
--
--tacacsPlusServerGlobalTimeout OBJECT-TYPE
--        SYNTAX      Integer32 (1..540)
--        UNITS       "seconds"
--        MAX-ACCESS  read-write
--        STATUS      current
--        DESCRIPTION " Timeout for TACACS+ global server."
--        ::= { tacacsMgt 6 }
--
----
---- sshMgt
----
--
---- Management for Secure Shell Configuration
--
--sshServerStatus OBJECT-TYPE
--        SYNTAX      EnabledStatus
--        MAX-ACCESS  read-write
--        STATUS      current
--        DESCRIPTION "The status of Secure Shell Server. Set this value to 
--                     enabled(1) to enable SSH server, set this value to 
--                     disabled(2) to disable the SSH server."
--        ::= { sshMgt 1 }
--
--sshServerMajorVersion  OBJECT-TYPE
--        SYNTAX      Integer32
--        MAX-ACCESS  read-only
--        STATUS      current
--        DESCRIPTION "The major version of the SSH Server."
--        ::= { sshMgt 2 }
--
--sshServerMinorVersion  OBJECT-TYPE
--        SYNTAX      Integer32
--        MAX-ACCESS  read-only
--        STATUS      current
--        DESCRIPTION "The minor version of the SSH Server."
--        ::= { sshMgt 3 }
-- 
--sshTimeout OBJECT-TYPE
--        SYNTAX      INTEGER(1..120)
--        UNITS       "seconds"
--        MAX-ACCESS  read-write
--        STATUS      current
--        DESCRIPTION "The time interval that the router waits for the SSH 
--                     client to respond. The range is 1-120."
--        ::= { sshMgt 4 }
--
--sshAuthRetries OBJECT-TYPE
--        SYNTAX      INTEGER(1..5)
--        MAX-ACCESS  read-write
--        STATUS      current
--        DESCRIPTION "The number of attempts after which the interface is reset.
--                     The range is 1-5."
--        ::= { sshMgt 5 }
--
--sshConnInfoTable OBJECT-TYPE
--        SYNTAX      SEQUENCE OF SshConnInfoEntry
--        MAX-ACCESS  not-accessible
--        STATUS      current
--        DESCRIPTION "The table for Secure Shell Connection."
--        ::= { sshMgt 6 }
--
--sshConnInfoEntry OBJECT-TYPE
--        SYNTAX      SshConnInfoEntry
--        MAX-ACCESS  not-accessible
--        STATUS      current
--        DESCRIPTION "The conceptual row for sshConnInfoTable."
--        INDEX       { sshConnID }
--        ::= { sshConnInfoTable 1 }
--
--SshConnInfoEntry ::= SEQUENCE
--{
----both sshv1 & sshv2 start
--   sshConnID             Integer32,
--   sshConnMajorVersion   Integer32,
--   sshConnMinorVersion   Integer32,
--   sshConnStatus         INTEGER, 
----both sshv1 & sshv2 end 
----both sshv1 & sshv2 start    
--   sshConnUserName       DisplayString,
--   sshDisconnect         INTEGER,   
----both sshv1 & sshv2 end    
----sshv2 only start   
--   sshConnEncryptionTypeStr DisplayString
----sshv2 only end      
--}
--
----both sshv1 & sshv2 start
--sshConnID OBJECT-TYPE
--        SYNTAX      Integer32
--        MAX-ACCESS  not-accessible
--        STATUS      current
--        DESCRIPTION "The connection ID of the Secure Shell Connection."
--        ::= { sshConnInfoEntry 1 }
--
--sshConnMajorVersion OBJECT-TYPE
--        SYNTAX      Integer32
--        MAX-ACCESS  read-only
--        STATUS      current
--        DESCRIPTION "The SSH major version."
--        ::= { sshConnInfoEntry 2 }
--
--sshConnMinorVersion OBJECT-TYPE
--        SYNTAX      Integer32
--        MAX-ACCESS  read-only
--        STATUS      current
--        DESCRIPTION "The SSH minor version."
--        ::= { sshConnInfoEntry 3 }
--
--sshConnStatus OBJECT-TYPE
--        SYNTAX      INTEGER
--                    {
--                      negotiationStart(1),
--                      authenticationStart(2),
--                      sessionStart(3)
--                    }      
--        MAX-ACCESS  read-only
--        STATUS      current
--        DESCRIPTION "The SSH connection State. negotiationStart(1) means the
--                     SSH is in its negotiation start state, authenticationStart(2)
--                     means the SSH is in authentication start state, sessionStart(3)
--                     means the SSH is in session start State."
--        ::= { sshConnInfoEntry 5 }
--
----both sshv1 & sshv2 end    
--
--
----both sshv1 & sshv2 start  
--         
--sshConnUserName OBJECT-TYPE
--        SYNTAX      DisplayString(SIZE(1..8))
--        MAX-ACCESS  read-only
--        STATUS      current
--        DESCRIPTION "The user name of the connection."
--        ::= { sshConnInfoEntry 6 }
--
--sshDisconnect OBJECT-TYPE
--        SYNTAX      INTEGER
--                    {
--                      noDisconnect(1),
--                      disconnect(2)
--                    }
--        MAX-ACCESS  read-write
--        STATUS      current
--        DESCRIPTION "Set the variable to disconnect the connection,
--                     noDisconnect(1) will always be obtained when reading this variable."
--        ::= { sshConnInfoEntry 7 }
--        
----both sshv1 & sshv2 end 
--
----sshv2 only start
--sshConnEncryptionTypeStr  OBJECT-TYPE    
--SYNTAX      DisplayString(SIZE(0..64))
--        MAX-ACCESS  read-only
--        STATUS      current
--        DESCRIPTION "The encryption type of the SSH."
--        ::= { sshConnInfoEntry 8 }
--        
--
--sshKeySize OBJECT-TYPE
--        SYNTAX      INTEGER(512..896)
--        MAX-ACCESS  read-write
--        STATUS      current
--        DESCRIPTION "The SSH server key size."
--        ::= { sshMgt 7 }
--         
--
--sshRsaHostKey1 OBJECT-TYPE
--        SYNTAX      KeySegment
--        MAX-ACCESS  read-only
--        STATUS      current
--        DESCRIPTION "The RSA host key segment 1."
--        ::= { sshMgt 8 }
--
--sshRsaHostKey2 OBJECT-TYPE
--        SYNTAX      KeySegment
--        MAX-ACCESS  read-only
--        STATUS      current
--        DESCRIPTION "The RSA host key segment 2."
--        ::= { sshMgt 9 }
--        
--sshRsaHostKey3 OBJECT-TYPE
--        SYNTAX      KeySegment
--        MAX-ACCESS  read-only
--        STATUS      current
--        DESCRIPTION "The RSA host key segment 3."
--        ::= { sshMgt 10 }
--        
--sshRsaHostKey4 OBJECT-TYPE
--        SYNTAX      KeySegment
--        MAX-ACCESS  read-only
--        STATUS      current
--        DESCRIPTION "The RSA host key segment 4."
--        ::= { sshMgt 11 }
--
--sshRsaHostKey5 OBJECT-TYPE
--        SYNTAX      KeySegment
--        MAX-ACCESS  read-only
--        STATUS      current
--        DESCRIPTION "The RSA host key segment 5."
--        ::= { sshMgt 12 } 
--
--sshRsaHostKey6 OBJECT-TYPE
--        SYNTAX      KeySegment
--        MAX-ACCESS  read-only
--        STATUS      current
--        DESCRIPTION "The RSA host key segment 6."
--        ::= { sshMgt 13 } 
--
--sshRsaHostKey7 OBJECT-TYPE
--        SYNTAX      KeySegment
--        MAX-ACCESS  read-only
--        STATUS      current
--        DESCRIPTION "The RSA host key segment 7."
--        ::= { sshMgt 14 } 
--
--sshRsaHostKey8 OBJECT-TYPE
--        SYNTAX      KeySegment
--        MAX-ACCESS  read-only
--        STATUS      current
--        DESCRIPTION "The RSA host key segment 8."
--        ::= { sshMgt 15 }                         
--
--sshDsaHostKey1 OBJECT-TYPE
--        SYNTAX      KeySegment
--        MAX-ACCESS  read-only
--        STATUS      current
--        DESCRIPTION "The DSA host key segment 1."
--        ::= { sshMgt 16 }
--
--sshDsaHostKey2 OBJECT-TYPE
--        SYNTAX      KeySegment
--        MAX-ACCESS  read-only
--        STATUS      current
--        DESCRIPTION "The DSA host key segment 2."
--        ::= { sshMgt 17 }
--        
--sshDsaHostKey3 OBJECT-TYPE
--        SYNTAX      KeySegment
--        MAX-ACCESS  read-only
--        STATUS      current
--        DESCRIPTION "The DSA host key segment 3."
--        ::= { sshMgt 18 }
--        
--sshDsaHostKey4 OBJECT-TYPE
--        SYNTAX      KeySegment
--        MAX-ACCESS  read-only
--        STATUS      current
--        DESCRIPTION "The DSA host key segment 4."
--        ::= { sshMgt 19 }
--
--sshDsaHostKey5 OBJECT-TYPE
--        SYNTAX      KeySegment
--        MAX-ACCESS  read-only
--        STATUS      current
--        DESCRIPTION "The DSA host key segment 5."
--        ::= { sshMgt 20 } 
--
--sshDsaHostKey6 OBJECT-TYPE
--        SYNTAX      KeySegment
--        MAX-ACCESS  read-only
--        STATUS      current
--        DESCRIPTION "The DSA host key segment 6."
--        ::= { sshMgt 21 }
--
--sshDsaHostKey7 OBJECT-TYPE
--        SYNTAX      KeySegment
--        MAX-ACCESS  read-only
--        STATUS      current
--        DESCRIPTION "The DSA host key segment 7."
--        ::= { sshMgt 22 }
--
--sshDsaHostKey8 OBJECT-TYPE
--        SYNTAX      KeySegment
--        MAX-ACCESS  read-only
--        STATUS      current
--        DESCRIPTION "The DSA host key segment 8."
--        ::= { sshMgt 23 }                
--        
--sshHostKeyGenAction OBJECT-TYPE
--        SYNTAX      INTEGER
--                    {
--                        noGen(1),
--                        genRsaKey(2),
--                        genDsaKey(3),
--                        genBothKeys(4)
--                    } 
--        MAX-ACCESS  read-write
--        STATUS      current
--        DESCRIPTION "This variable is for host key generating.
--        
--                    For the set behavior:
--                    Set it to genRsaKey(2) to generate the RSA host key,
--                    and to genDsaKey(3) to generate the DSA host key, 
--                    if genBothKeys(4) is set, both RSA and DSA host key are 
--                    generated. 
--                    
--                    For the get behavior:
--                    You will get genRsaKey(2), genDsaKey(3) or
--                    genBothKeys(4) when the key gen action is in progress.
--                    otherwise, you will get noGen(1)."
--        ::= { sshMgt 24 }
--
--sshHostKeyGenStatus OBJECT-TYPE
--        SYNTAX      INTEGER
--                    {
--                        unknown(1), 
--                        success(2), 
--                        failure(3)
--                    }
--        MAX-ACCESS  read-only
--        STATUS      current
--        DESCRIPTION "The result of the last KeyGen status.
--                     if no key gen action has been performed.
--                     you will get unknown(1) status."
--        ::= { sshMgt 25 }        
--
--sshHostKeySaveAction OBJECT-TYPE
--        SYNTAX      INTEGER
--                    {
--                        noSave(1),
--                        save(2)
--                    }     
--        MAX-ACCESS  read-write
--        STATUS      current
--        DESCRIPTION "To save host key from memory to flash.
--        
--                     For the set behavior:                     
--                     Set it to save(2) to perform the save operation.
--                     
--                     For the get behavior:
--                     You will get save(1) when the save action is in progress.
--                     Otherwise, you will get noSave(1)."
--        ::= { sshMgt 26 }
--
--sshHostKeySaveStatus OBJECT-TYPE
--        SYNTAX      INTEGER
--                    {
--                        unknown(1), 
--                        success(2), 
--                        failure(3)
--                    }
--        MAX-ACCESS  read-only
--        STATUS      current
--        DESCRIPTION "The result of the last savekey status.
--                     If no save action has been performed,
--                     you will get unknown(1) status."
--        ::= { sshMgt 27 }
--
--sshHostKeyDelAction  OBJECT-TYPE
--        SYNTAX      INTEGER
--                    {
--                        noDel(1),
--                        delRsaKey(2),
--                        delDsaKey(3), 
--                        delBothKeys(4)
--                    }    
--        MAX-ACCESS  read-write
--        STATUS      current
--        DESCRIPTION "To delete the host key.
--        
--                     For the set behavior:                     
--                     Set it to delRsaKey(2) to delete the RSA host key,
--                     to delDsaKey(3) to delete the DSA host key,
--                     or to delBothKeys(4) to delete both RSA and DSA host key.
--                     
--                     For the get behavior:
--                     You will get delRsaKey(2), delDsaKey(3) or  delBothKeys(4)
--                     when the delete operation is in progress.
--                     Otherwise, you will get noDel(1)."
--        ::= { sshMgt 28 } 
--
----sshUserTable OBJECT-TYPE
----        SYNTAX      SEQUENCE OF SshUserEntry
----        MAX-ACCESS  not-accessible
----        STATUS      current
----        DESCRIPTION "The conceptual table of all of sshUserEntry."
----        ::= { sshMgt 29 }              
----
----sshUserEntry OBJECT-TYPE
----        SYNTAX      SshUserEntry
----        MAX-ACCESS  not-accessible
----        STATUS      current
----        DESCRIPTION "The conceptual row for sshUserTable."
----        INDEX       { IMPLIED sshUserName}
----        ::= { sshUserTable 1 }          
---- 
----SshUserEntry ::= SEQUENCE
----{
----    sshUserName             DisplayString,
----    sshUserRsaKey1          KeySegment,    
----    sshUserRsaKey2          KeySegment,
----    sshUserRsaKey3          KeySegment,
----    sshUserRsaKey4          KeySegment,
----    sshUserRsaKey5          KeySegment,
----    sshUserRsaKey6          KeySegment,
----    sshUserRsaKey7          KeySegment,
----    sshUserRsaKey8          KeySegment,
----    sshUserDsaKey1          KeySegment,
----    sshUserDsaKey2          KeySegment,
----    sshUserDsaKey3    	    KeySegment,
----    sshUserDsaKey4    	    KeySegment,
----    sshUserDsaKey5    	    KeySegment,
----    sshUserDsaKey6    	    KeySegment,
----    sshUserDsaKey7    	    KeySegment,
----    sshUserDsaKey8    	    KeySegment,
----    sshUserKeyDelAction     INTEGER
----}  
----
----sshUserName OBJECT-TYPE
----        SYNTAX      DisplayString(SIZE(1..8))
----        MAX-ACCESS  not-accessible
----        STATUS      current
----        DESCRIPTION "User Name."
----        ::= { sshUserEntry 1 }
----
----sshUserRsaKey1 OBJECT-TYPE
----        SYNTAX      KeySegment
----        MAX-ACCESS  read-only
----        STATUS      current
----        DESCRIPTION "The RSA user key segment 1."
----        ::= { sshUserEntry 2 }   
----
----sshUserRsaKey2 OBJECT-TYPE
----        SYNTAX      KeySegment
----        MAX-ACCESS  read-only
----        STATUS      current
----        DESCRIPTION "The RSA user key segment 2."
----        ::= { sshUserEntry 3 }  
----
----sshUserRsaKey3 OBJECT-TYPE
----        SYNTAX      KeySegment
----        MAX-ACCESS  read-only
----        STATUS      current
----        DESCRIPTION "The RSA user key segment 3."
----        ::= { sshUserEntry 4 }    
----
----sshUserRsaKey4 OBJECT-TYPE
----        SYNTAX      KeySegment
----        MAX-ACCESS  read-only
----        STATUS      current
----        DESCRIPTION "The RSA user key segment 4."
----        ::= { sshUserEntry 5 } 
----
----sshUserRsaKey5 OBJECT-TYPE
----        SYNTAX      KeySegment
----        MAX-ACCESS  read-only
----        STATUS      current
----        DESCRIPTION "The RSA user key segment 5."
----        ::= { sshUserEntry 6 } 
----
----sshUserRsaKey6 OBJECT-TYPE
----        SYNTAX      KeySegment
----        MAX-ACCESS  read-only
----        STATUS      current
----        DESCRIPTION "The RSA user key segment 6."
----        ::= { sshUserEntry 7 }
----
----sshUserRsaKey7 OBJECT-TYPE
----        SYNTAX      KeySegment
----        MAX-ACCESS  read-only
----        STATUS      current
----        DESCRIPTION "The RSA user key segment 7."
----        ::= { sshUserEntry 8 }
----
----sshUserRsaKey8 OBJECT-TYPE
----        SYNTAX      KeySegment
----        MAX-ACCESS  read-only
----        STATUS      current
----        DESCRIPTION "The RSA user key segment 8."
----        ::= { sshUserEntry 9 }                        
----
----sshUserDsaKey1 OBJECT-TYPE
----        SYNTAX      KeySegment
----        MAX-ACCESS  read-only
----        STATUS      current
----        DESCRIPTION "The DSA user key segment 1."
----        ::= { sshUserEntry 10 }   
----
----sshUserDsaKey2 OBJECT-TYPE
----        SYNTAX      KeySegment
----        MAX-ACCESS  read-only
----        STATUS      current
----        DESCRIPTION "The DSA user key segment 2."
----        ::= { sshUserEntry 11 } 
----
----sshUserDsaKey3 OBJECT-TYPE
----        SYNTAX      KeySegment
----        MAX-ACCESS  read-only
----        STATUS      current
----        DESCRIPTION "The DSA user key segment 3."
----        ::= { sshUserEntry 12 } 
----        
----sshUserDsaKey4 OBJECT-TYPE
----        SYNTAX      KeySegment
----        MAX-ACCESS  read-only
----        STATUS      current
----        DESCRIPTION "The DSA user key segment 4."
----        ::= { sshUserEntry 13 }       
----
----sshUserDsaKey5 OBJECT-TYPE
----        SYNTAX      KeySegment
----        MAX-ACCESS  read-only
----        STATUS      current
----        DESCRIPTION "The DSA user key segment 5."
----        ::= { sshUserEntry 14 } 
----
----sshUserDsaKey6 OBJECT-TYPE
----        SYNTAX      KeySegment
----        MAX-ACCESS  read-only
----        STATUS      current
----        DESCRIPTION "The DSA user key segment 6."
----        ::= { sshUserEntry 15 }
----
----sshUserDsaKey7 OBJECT-TYPE
----        SYNTAX      KeySegment
----        MAX-ACCESS  read-only
----        STATUS      current
----        DESCRIPTION "The DSA user key segment 7."
----        ::= { sshUserEntry 16 }
----
----sshUserDsaKey8 OBJECT-TYPE
----        SYNTAX      KeySegment
----        MAX-ACCESS  read-only
----        STATUS      current
----        DESCRIPTION "The DSA user key segment 8."
----        ::= { sshUserEntry 17 }                        
----
----sshUserKeyDelAction  OBJECT-TYPE
----        SYNTAX      INTEGER
----                    {
----                        noDel(1),
----                        delRsaKey(2),
----                        delDsaKey(3), 
----                        delBothKeys(4)
----                    }   
----        MAX-ACCESS  read-write
----        STATUS      current
----        DESCRIPTION "To delete the user key.
----        
----                     For the set behavior:                     
----                     Set it to delRsaKey(2) to delete the RSA user key,
----                     to delDsaKey(3) to delete the DSA user key,
----                     or to delBothKeys(4) to delete both RSA and DSA user key.
----                     
----                     For the get behavior:
----                     You will get delRsaKey(2), delDsaKey(3) or  delBothKeys(4)
----                     when the delete operation is in progress.
----                     Otherwise, you will get noDel(1)."
----        ::= { sshUserEntry 18 }     
----
----
---- aclMgt
----
--
----aclIpAceTable
--aclIpAceTable       OBJECT-TYPE
--        SYNTAX      SEQUENCE OF AclIpAceEntry
--        MAX-ACCESS  not-accessible
--        STATUS      current
--        DESCRIPTION "The conceptual table of all of aclIpAceEntry."
--        ::= { aclMgt 1 }       
--
--aclIpAceEntry OBJECT-TYPE
--        SYNTAX      AclIpAceEntry
--        MAX-ACCESS  not-accessible
--        STATUS      current
--        DESCRIPTION "The conceptual row for aclIpAceTable."
--        INDEX       { aclIpAceName, aclIpAceIndex }
--        ::= { aclIpAceTable 1 }  
--
--AclIpAceEntry ::= SEQUENCE
--{
--    aclIpAceName                    DisplayString,
--    aclIpAceIndex                   Integer32,
--    aclIpAcePrecedence              Integer32,
--    aclIpAceAction                  INTEGER,
--    aclIpAceSourceIpAddr            IpAddress,
--    aclIpAceSourceIpAddrBitmask     IpAddress,
--    aclIpAceDestIpAddr              IpAddress,
--    aclIpAceDestIpAddrBitmask       IpAddress,
--    aclIpAceProtocol                Integer32,
--    aclIpAcePrec                    Integer32,
--    aclIpAceTos                     Integer32,
--    aclIpAceDscp                    Integer32,
--    aclIpAceSourcePortOp            INTEGER,
--    aclIpAceMinSourcePort           Integer32,
--    aclIpAceMaxSourcePort           Integer32,    
--    aclIpAceDestPortOp              INTEGER,
--    aclIpAceMinDestPort             Integer32,
--    aclIpAceMaxDestPort             Integer32,    
--    aclIpAceControlCode             Integer32,
--    aclIpAceControlCodeBitmask      Integer32,
--    aclIpAceStatus                  RowStatus
--} 
--
--aclIpAceName OBJECT-TYPE
--        SYNTAX      DisplayString (SIZE(1..15))
--        MAX-ACCESS  not-accessible
--        STATUS      current
--        DESCRIPTION "The name of an ACL. Within a feature a unique 
--                     name is used to identify
--                     the list to which the entry belongs in the device."
--        ::= { aclIpAceEntry 1 }  
--        
--aclIpAceIndex OBJECT-TYPE
--        SYNTAX      Integer32 (1..32)
--        MAX-ACCESS  not-accessible
--        STATUS      current
--        DESCRIPTION "The unique index of an ACE within an ACL."
--        ::= { aclIpAceEntry 2 }    
--        
--aclIpAcePrecedence OBJECT-TYPE
--        SYNTAX      Integer32 (0..32)
--        MAX-ACCESS  read-only
--        STATUS      current
--        DESCRIPTION "Specifies the IP precedence value to be matched against.
--                     This object cannot not be configured when the status of the
--                     entry, aclIpAceStatus, is active(1)." 
--        ::= { aclIpAceEntry 3 } 
--
--aclIpAceAction OBJECT-TYPE
--        SYNTAX      INTEGER
--                    {
--                        permit(1),
--                        deny(2)
--                    }
--        MAX-ACCESS  read-create
--        STATUS      current
--        DESCRIPTION "Indicates the action to be taken if a packet matches this ACE.
--                     This object cannot not be configured when the status of the
--                     entry, aclIpAceStatus, is active(1)." 
--        ::= { aclIpAceEntry 4 }
--        
--aclIpAceSourceIpAddr OBJECT-TYPE
--        SYNTAX      IpAddress
--        MAX-ACCESS  read-create
--        STATUS      current
--        DESCRIPTION "The specified source IP address. The packet's source address is
--        AND-ed with the value of aclIpAceSourceIpAddrBitmask and then compared
--                    against the value of this object.
--                    This object cannot be configured when the status of the
--                    entry, aclIpAceStatus, is active(1)."
--        ::= { aclIpAceEntry 5 }       
--        
--aclIpAceSourceIpAddrBitmask OBJECT-TYPE
--        SYNTAX      IpAddress
--        MAX-ACCESS  read-create
--        STATUS      current
--        DESCRIPTION "The specified source IP address mask. The packet's destination
--                     address is AND-ed with the value of aclIpAceSourceIpAddr and then
--                     compared against the value of this object."
--        ::= { aclIpAceEntry 6 } 
--        
--aclIpAceDestIpAddr OBJECT-TYPE
--        SYNTAX      IpAddress
--        MAX-ACCESS  read-create
--        STATUS      current
--        DESCRIPTION "The specified destination IP address. 
--                     The packet's destination address is
--        AND-ed with the value of aclIpAceDestIpAddrBitmask and then compared
--                     against the value of this object."
--        ::= { aclIpAceEntry 7 } 
--        
--aclIpAceDestIpAddrBitmask OBJECT-TYPE
--        SYNTAX      IpAddress
--        MAX-ACCESS  read-create
--        STATUS      current
--        DESCRIPTION "The specified destination IP address mask."
--        ::= { aclIpAceEntry 8 }  
--        
--aclIpAceProtocol OBJECT-TYPE
--        SYNTAX      Integer32 (0..256)
--        MAX-ACCESS  read-create
--        STATUS      current
--        DESCRIPTION "The protocol number field in the IP header used to indicate
--        the higher layer protocol as specified in RFC 1700. A value 
--                    value of 0 matches every IP packet. The object=256, means 'any'
--
--        For example :
--        0 is IP, 1 is ICMP, 2 is IGMP, 4 is IP in IP encapsulation,
--        6 is TCP, 9 is IGRP, 17 is UDP, 47 is GRE, 50 is ESP, 51 is AH,
--        88 is IGRP, 89 is OSPF, 94 is KA9Q/NOS compatible IP over IP,
--        103 is PIMv2, 108 is PCP. "
--        ::= { aclIpAceEntry 9 }  
--
--aclIpAcePrec OBJECT-TYPE
--        SYNTAX      Integer32 (0..8)
--        MAX-ACCESS  read-create
--        STATUS      current
--        DESCRIPTION "Specifies the IP precedence value to be matched against.
--                     This object cannot be configured when the status of the
--                     entry, aclIpAceStatus, is active(1). 
--                     The value of this object is ignored whenever the value of 
--                     aclIpAcePrec object is 8."
--        ::= { aclIpAceEntry 10 }  
--
--aclIpAceTos OBJECT-TYPE
--        SYNTAX      Integer32 (0..16)
--        MAX-ACCESS  read-create
--        STATUS      current
--        DESCRIPTION "Specifies the IP ToS facility value to be matched against.
--                     This object cannot be configured when the status of the
--                     entry, aclIpAceStatus, is active(1). 
--                     The value of this object is ignored whenever the value of 
--                     aclIpAcePrec object is 9."
--        ::= { aclIpAceEntry 11 } 
--        
--aclIpAceDscp OBJECT-TYPE
--        SYNTAX      Integer32 (0..64)
--        MAX-ACCESS  read-create
--        STATUS      current
--        DESCRIPTION "Specifies the DSCP value to be matched against. 
--                     This object cannot be configured when the status of the
--                     entry, aclIpAceStatus, is active(1). 
--                     The value of this object is ignored whenever the value of 
--                     aclIpAcePrec object is 64."
--        ::= { aclIpAceEntry 12 }
--
--aclIpAceSourcePortOp OBJECT-TYPE
--        SYNTAX      INTEGER
--                    {
--                        noOperator(1),
--                        equal(2),
--                        range(3)
--                    }
--        MAX-ACCESS  read-create
--        STATUS      current
--        DESCRIPTION "Indicates how a packet's source TCP/UDP port number is
--                     to be compared. noOperator(1), which is the default value, means no
--                     comparison is to be made with the source TCP/UDP port
--                     number."
--        ::= { aclIpAceEntry 13 }  
--
--aclIpAceMinSourcePort OBJECT-TYPE
--        SYNTAX      Integer32 (0..'FFFF'h)
--        MAX-ACCESS  read-create
--        STATUS      current
--        DESCRIPTION "If the aclIpAceSourcePortOp is range(3), 
--                     this indicates the lower bound of the TCP/UDP port number value range."
--        ::= { aclIpAceEntry 14 }   
--
--aclIpAceMaxSourcePort OBJECT-TYPE
--        SYNTAX      Integer32 (0..'FFFF'h)
--        MAX-ACCESS  read-create
--        STATUS      current
--        DESCRIPTION "If the aclIpAceSourcePortOp is range(3), 
--                     this indicates the upper bound of the TCP/UDP port number value range."
--        ::= { aclIpAceEntry 15 } 
--
--aclIpAceDestPortOp OBJECT-TYPE
--        SYNTAX      INTEGER
--                    {
--                        noOperator(1),
--                        equal(2),
--                        range(3)
--                    }
--        MAX-ACCESS  read-create
--        STATUS      current
--        DESCRIPTION "Indicates how a packet's destination TCP/UDP port number is
--                     to be compared. noOperator(1), which is the default value, means that no
--                     comparison is to be made with the destination TCP/UDP port
--                     number."
--        ::= { aclIpAceEntry 17 } 
--
--aclIpAceMinDestPort OBJECT-TYPE
--        SYNTAX      Integer32 (0..'FFFF'h)
--        MAX-ACCESS  read-create
--        STATUS      current
--        DESCRIPTION "If the aclIpAceDestPortOp is range(3), 
--                     this indicates the lower bound of the TCP/UDP port number value range."
--        ::= { aclIpAceEntry 18 } 
--        
--aclIpAceMaxDestPort OBJECT-TYPE
--        SYNTAX      Integer32 (0..'FFFF'h)
--        MAX-ACCESS  read-create
--        STATUS      current
--        DESCRIPTION "If the aclIpAceDestPortOp is range(3), 
--                     this indicates the upper bound of the TCP/UDP port number value range."
--        ::= { aclIpAceEntry 19 }    
--
--aclIpAceControlCode OBJECT-TYPE
--        SYNTAX      Integer32 (0..63)
--        MAX-ACCESS  read-create
--        STATUS      current
--        DESCRIPTION "Indicates how the control flags of TCP packets are to be compared. 
--                     aceIpControlCode is AND-ed with aceIpControlCodeBitmask." 
--        ::= { aclIpAceEntry 21 }            
--
--aclIpAceControlCodeBitmask OBJECT-TYPE
--        SYNTAX      Integer32 (0..63)
--        MAX-ACCESS  read-create
--        STATUS      current
--        DESCRIPTION "Indicates how the control flags of TCP packets are to be compared.
--                     It can be used to check multiple flags of the 
--                     FIN, SYN, RST, PSH, ACK, URG by the sum of 
--                     FIN=1, SYN=2, RST=4, PSH=8, ACK=16, URG=32."
--        ::= { aclIpAceEntry 22 } 
--
--aclIpAceStatus OBJECT-TYPE
--        SYNTAX      RowStatus
--        MAX-ACCESS  read-create
--        STATUS      current
--	    DESCRIPTION
--			"The status of this conceptual row entry. This object isused to manage the
--			creation and deletion of conceptual rows.
--       
--			The status column has six defined values:
--			
--			     - 'active', which indicates that the conceptual row is
--			     available for use by the managed device;
--        
--			     - 'notInService', which indicates that the conceptual
--			     row exists in the agent, but is unavailable for use by
--			     the managed device (see NOTE below);
--			
--			     - 'notReady', which indicates that the conceptual row
--			     exists in the agent, but is missing information
--			     necessary in order to be available for use by the
--			     managed device;
--        
--			     - 'createAndGo', which is supplied by a management
--			     station wishing to create a new instance of a
--			     conceptual row and to have its status automatically set
--			     to active, making it available for use by the managed
--			     device;
--			
--			     - 'createAndWait', which is supplied by a management
--			     station wishing to create a new instance of a
--			     conceptual row (but not make it available for use by
--			     the managed device); and,
--        
--			     - 'destroy', which is supplied by a management station
--			     wishing to delete all of the instances associated with
--			     an existing conceptual row.
--			
--			Whereas five of the six values (all except 'notReady') may
--			be specified in a management protocol set operation, only
--			three values will be returned in response to a management
--			protocol retrieval operation:  'notReady', 'notInService' or
--			'active'.  That is, when queried, an existing conceptual row
--			has only three states:  it is either available for use by
--			the managed device (the status column has value 'active');
--			it is not available for use by the managed device, though
--			the agent has sufficient information to make it so (the
--			status column has value 'notInService'); or, it is not
--			available for use by the managed device, and an attempt to
--			make it so would fail because the agent has insufficient
--			information (the state column has value 'notReady').
--
--            For a detailed description of this object, please refer to 
--            SNMPv2-TC MIB."     
--        ::= { aclIpAceEntry 23 } 
--
---- aclMacAceTable
--aclMacAceTable OBJECT-TYPE
--        SYNTAX      SEQUENCE OF AclMacAceEntry
--        MAX-ACCESS  not-accessible
--        STATUS      current
--        DESCRIPTION "The conceptual table of all of aclMacAceEntry."
--        ::= { aclMgt 2 }  
--
--aclMacAceEntry OBJECT-TYPE
--        SYNTAX      AclMacAceEntry
--        MAX-ACCESS  not-accessible
--        STATUS      current
--        DESCRIPTION "The conceptual row for aclMacAceTable. "
--        INDEX       { aclMacAceName, aclMacAceIndex }
--        ::= { aclMacAceTable 1 }
--
--AclMacAceEntry ::= SEQUENCE
--{
--    aclMacAceName                   DisplayString,
--    aclMacAceIndex                  Integer32,
--    aclMacAcePrecedence             Integer32,
--    aclMacAceAction                 INTEGER,
--    aclMacAcePktformat              INTEGER,
--    aclMacAceSourceMacAddr          OCTET STRING,
--    aclMacAceSourceMacAddrBitmask   OCTET STRING,
--    aclMacAceDestMacAddr            OCTET STRING,
--    aclMacAceDestMacAddrBitmask     OCTET STRING,
--    aclMacAceVidOp                  INTEGER,
--    aclMacAceMinVid                 Integer32,    
--    aclMacAceMaxVid                 Integer32,
--    aclMacAceEtherTypeOp            INTEGER,    
--    aclMacAceMinEtherType           Integer32,
--    aclMacAceMaxEtherType           Integer32,
--    aclMacAceStatus                 RowStatus
--}        
--
--aclMacAceName OBJECT-TYPE
--        SYNTAX      DisplayString (SIZE(1..15))
--        MAX-ACCESS  not-accessible
--        STATUS      current
--        DESCRIPTION "The name of an ACL. Within a feature, a unique
--                    name is used to identify
--                    the list to which the entry belongs in the device."
--        ::= { aclMacAceEntry 1 } 
--
--aclMacAceIndex OBJECT-TYPE
--        SYNTAX      Integer32 (1..32)
--        MAX-ACCESS  not-accessible
--        STATUS      current
--        DESCRIPTION "The unique index of an ACE within an ACL."
--        ::= { aclMacAceEntry 2 }  
--
--aclMacAcePrecedence OBJECT-TYPE
--        SYNTAX      Integer32 (0..32)
--        MAX-ACCESS  read-only
--        STATUS      current
--        DESCRIPTION "Specifies the entry's precedence."
--        ::= { aclMacAceEntry 3 }  
--
--aclMacAceAction OBJECT-TYPE
--        SYNTAX      INTEGER
--                    {
--                        permit(1),
--                        deny(2)
--                    }
--        MAX-ACCESS  read-create
--        STATUS      current
--        DESCRIPTION "Indicates the action to be taken if a packet matches this ACE.
--                     This object cannot be configured when the status of the
--                     entry, aclMacAceStatus, is active(1)." 
--        ::= { aclMacAceEntry 4 }
--
--aclMacAcePktformat OBJECT-TYPE
--        SYNTAX      INTEGER
--                    {
--                        any(1),
--                        untagged-Eth2(2),
--                        untagged802Dot3(3),
--                        tagggedEth2(4),
--                        tagged802Dot3(5)
--                    }
--        MAX-ACCESS  read-create
--        STATUS      current
--        DESCRIPTION "Used to check the packet format of the packets.
--                     This object cannot be configured when the status of the
--                     entry, aclMacAceStatus, is active(1)."
--        ::= { aclMacAceEntry 5 }
--
--aclMacAceSourceMacAddr OBJECT-TYPE
--        SYNTAX      OCTET STRING (SIZE (6))
--        MAX-ACCESS  read-create
--        STATUS      current
--        DESCRIPTION "Indicates the 48-bit destination MAC address. 
--                    The specified source MAC of the packet The packet's source MAC 
--                    address is AND-ed with the value of aceMacSourceMacAddrBitmask 
--                    and then compared against the value of this object. This object 
--                    cannot be configured when the status of the entry, 
--                    aclMacAceStatus, is active(1)."
--        ::= { aclMacAceEntry 6 }          
--        
--aclMacAceSourceMacAddrBitmask OBJECT-TYPE
--        SYNTAX      OCTET STRING (SIZE (6))
--        MAX-ACCESS  read-create
--        STATUS      current
--        DESCRIPTION "The specified source MAC address mask.
--                    This object cannot be configured when the status of the
--                    entry, aclMacAceStatus, is active(1)."
--        ::= { aclMacAceEntry 7 }  
--
--aclMacAceDestMacAddr OBJECT-TYPE
--        SYNTAX      OCTET STRING (SIZE (6))
--        MAX-ACCESS  read-create
--        STATUS      current
--        DESCRIPTION "Indicates the 48-bit destination MAC address. 
--                     The specified destination MAC of the packet. 
--                     The packet's destination MAC address is
--                     AND-ed with the value of aceMacDestMacAddrBitmask and then compared
--                     against the value of this object.
--                     This object cannot be configured when the status of the
--                     entry, aclMacAceStatus, is active(1)."
--        ::= { aclMacAceEntry 8 }
--
--aclMacAceDestMacAddrBitmask OBJECT-TYPE
--        SYNTAX      OCTET STRING (SIZE (6))
--        MAX-ACCESS  read-create
--        STATUS      current
--        DESCRIPTION "The specified destination MAC address mask.
--                     This object cannot be configured when the status of the
--                     entry, aclMacAceStatus, is active(1)."
--        ::= { aclMacAceEntry 9 }                            
--        
--aclMacAceVidOp OBJECT-TYPE
--        SYNTAX      INTEGER
--                    {
--                        noOperator(1),
--                        range(3)
--                    }
--        MAX-ACCESS  read-create
--        STATUS      current
--        DESCRIPTION "Indicates how a packet's vid is
--                     to be compared.
--                     This object cannot be configured when the status of the
--                     entry, aclMacAceStatus, is active(1)."       
--        ::= { aclMacAceEntry 10 }     
--
--aclMacAceMinVid OBJECT-TYPE
--        SYNTAX      Integer32 (1..4094)
--        MAX-ACCESS  read-create
--        STATUS      current
--        DESCRIPTION "Indicates the lower bound of the vid value range if the aclMacAceVidOp is range(3).  
--                     This object cannot be configured when the status of the
--                     entry, aclMacAceStatus, is active(1)."
--        ::= { aclMacAceEntry 11 }        
--
--aclMacAceMaxVid OBJECT-TYPE
--        SYNTAX      Integer32 (1..4094)
--        MAX-ACCESS  read-create
--        STATUS      current
--        DESCRIPTION "Indicates the upper bound of the vid value range if the aclMacAceVidOp is range(3).  
--                     This object cannot be configured when the status of the
--                     entry, aclMacAceStatus, is active(1)."
--        ::= { aclMacAceEntry 13 } 
--
--aclMacAceEtherTypeOp OBJECT-TYPE
--        SYNTAX      INTEGER
--                    {
--                        noOperator(1),
--                        range(3)
--                    }
--        MAX-ACCESS  read-create
--        STATUS      current
--        DESCRIPTION "Indicates how a packet's ethertype is
--                     to be compared.
--                     This object cannot be configured when the status of the
--                     entry, aclMacAceStatus, is active(1)." 
--        ::= { aclMacAceEntry 14 }   
--
--aclMacAceMinEtherType OBJECT-TYPE
--        SYNTAX      Integer32 (0..'FFFF'h)
--        MAX-ACCESS  read-create
--        STATUS      current
--        DESCRIPTION "Indicates the lower bound of the vid value range if the aclMacAceEtherTypeOp is range(3).  
--                     This object cannot be configured when the status of the
--                     entry, aclMacAceStatus, is active(1)."
--        ::= { aclMacAceEntry 16 }  
--
--aclMacAceMaxEtherType OBJECT-TYPE
--        SYNTAX      Integer32 (0..'FFFF'h)
--        MAX-ACCESS  read-create
--        STATUS      current
--        DESCRIPTION "Indicates the upper bound of the vid value range if the aclMacAceEtherTypeOp is range(3).
--                     This object cannot be configured when the status of the
--                     entry, aclMacAceStatus, is active(1)."
--        ::= { aclMacAceEntry 17 }  
--
--aclMacAceStatus OBJECT-TYPE
--        SYNTAX      RowStatus
--        MAX-ACCESS  read-create
--        STATUS      current
--	    DESCRIPTION
--			"The status of this conceptual row entry. This object isused to manage the
--			creation and deletion of conceptual rows.
--			
--			The status column has six defined values:
--			
--			     - 'active', which indicates that the conceptual row is
--			     available for use by the managed device;
--			
--			     - 'notInService', which indicates that the conceptual
--			     row exists in the agent, but is unavailable for use by
--			     the managed device (see NOTE below);
--			
--			     - 'notReady', which indicates that the conceptual row
--			     exists in the agent, but is missing information
--			     necessary in order to be available for use by the
--			     managed device;
--			
--			     - 'createAndGo', which is supplied by a management
--			     station wishing to create a new instance of a
--			     conceptual row and to have its status automatically set
--			     to active, making it available for use by the managed
--			     device;
--			
--			     - 'createAndWait', which is supplied by a management
--			     station wishing to create a new instance of a
--			     conceptual row (but not make it available for use by
--			     the managed device); and,
--			
--			     - 'destroy', which is supplied by a management station
--			     wishing to delete all of the instances associated with
--			     an existing conceptual row.
--			
--			Whereas five of the six values (all except 'notReady') may
--			be specified in a management protocol set operation, only
--			three values will be returned in response to a management
--			protocol retrieval operation:  'notReady', 'notInService' or
--			'active'.  That is, when queried, an existing conceptual row
--			has only three states:  it is either available for use by
--			the managed device (the status column has value 'active');
--			it is not available for use by the managed device, though
--			the agent has sufficient information to make it so (the
--			status column has value 'notInService'); or, it is not
--			available for use by the managed device, and an attempt to
--			make it so would fail because the agent has insufficient
--			information (the state column has value 'notReady').
--
--            For a detailed description of this object, please refer to 
--            SNMPv2-TC MIB." 
--        ::= { aclMacAceEntry 18 }  
--
----aclAclGroupTable
--aclAclGroupTable OBJECT-TYPE
--        SYNTAX      SEQUENCE OF AclAclGroupEntry
--        MAX-ACCESS  not-accessible
--        STATUS      current
--        DESCRIPTION "The conceptual table of aclAclGroupEntry."
--        ::= { aclMgt 3 }    
--
--aclAclGroupEntry OBJECT-TYPE
--        SYNTAX      AclAclGroupEntry
--        MAX-ACCESS  not-accessible
--        STATUS      current
--        DESCRIPTION "The conceptual row for aclAclGroupTable."
--        INDEX       { aclAclGroupIfIndex }
--        ::= { aclAclGroupTable 1 } 
--
--AclAclGroupEntry ::= SEQUENCE
--{
--    aclAclGroupIfIndex Integer32,
--    aclAclGroupIngressIpAcl DisplayString,
--    aclAclGroupEgressIpAcl DisplayString,
--    aclAclGroupIngressMacAcl DisplayString,
--    aclAclGroupEgressMacAcl DisplayString
--}                                                                                           
--   
--aclAclGroupIfIndex OBJECT-TYPE
--        SYNTAX      Integer32
--        MAX-ACCESS  not-accessible
--        STATUS      current
--        DESCRIPTION "The interface number specifying the ACL binding to."
--        ::= { aclAclGroupEntry 1 }   
--
--aclAclGroupIngressIpAcl OBJECT-TYPE
--        SYNTAX      DisplayString (SIZE(0..15))
--        MAX-ACCESS  read-write
--        STATUS      current
--        DESCRIPTION "Specifies the ingress IP ACL(standard or extended) binding to the interface."
--        ::= { aclAclGroupEntry 2 }        
--        
--aclAclGroupEgressIpAcl OBJECT-TYPE
--        SYNTAX      DisplayString (SIZE(0..15))
--        MAX-ACCESS  read-write
--        STATUS      current
--        DESCRIPTION "Specifies the egress IP ACL(standard or extended) binding to the interface.But it
--                     is not supported in LEO product."
--        ::= { aclAclGroupEntry 3 } 
--
--aclAclGroupIngressMacAcl OBJECT-TYPE
--        SYNTAX      DisplayString (SIZE(0..15))
--        MAX-ACCESS  read-write
--        STATUS      current
--        DESCRIPTION "Specifies the ingress MAC ACL binding to the interface."
--        ::= { aclAclGroupEntry 4 }       
--
--aclAclGroupEgressMacAcl OBJECT-TYPE
--        SYNTAX      DisplayString (SIZE(0..15))
--        MAX-ACCESS  read-write
--        STATUS      current
--        DESCRIPTION "Specifies the egress MAC ACL binding to the interface.But it is not supported 
--                     in LEO product."
--        ::= { aclAclGroupEntry 5 }   
--
----
---- ipFilterMgt
----
--
----ipFilterSnmpTable
--ipFilterSnmpTable  OBJECT-TYPE
--    SYNTAX     SEQUENCE OF IpFilterSnmpEntry
--    MAX-ACCESS not-accessible
--    STATUS     current
--    DESCRIPTION
--        "A list of IP address entries."
--    ::= { ipFilterMgt 1 }
--
--ipFilterSnmpEntry  OBJECT-TYPE
--    SYNTAX     IpFilterSnmpEntry
--    MAX-ACCESS not-accessible
--    STATUS     current
--    DESCRIPTION
--        "This entry includes an IP address range which the system
--         will allow to connect to this device through SNMP."
--    INDEX { ipFilterSnmpStartAddress }
--    ::= { ipFilterSnmpTable 1 }
--    
--IpFilterSnmpEntry ::= SEQUENCE {
--    ipFilterSnmpStartAddress        IpAddress,
--    ipFilterSnmpEndAddress          IpAddress,
--    ipFilterSnmpStatus              ValidStatus
--    }
--
--ipFilterSnmpStartAddress OBJECT-TYPE
--        SYNTAX      IpAddress
--        MAX-ACCESS  not-accessible
--        STATUS      current
--        DESCRIPTION "The start IP address."        
--        ::= { ipFilterSnmpEntry 1 }
--        
--ipFilterSnmpEndAddress OBJECT-TYPE
--        SYNTAX      IpAddress
--        MAX-ACCESS  read-create
--        STATUS      current
--        DESCRIPTION "The end IP address."        
--        ::= { ipFilterSnmpEntry 2 }     
--
--ipFilterSnmpStatus OBJECT-TYPE
--        SYNTAX      ValidStatus
--        MAX-ACCESS  read-create
--        STATUS      current
--        DESCRIPTION "Setting this to valid(1) creates an entry.
--                     Setting this to invalid(2) destroys an entry."        
--        ::= { ipFilterSnmpEntry 3 }               
--            
----ipFilterHTTPTable
--ipFilterHTTPTable  OBJECT-TYPE
--    SYNTAX     SEQUENCE OF IpFilterHTTPEntry
--    MAX-ACCESS not-accessible
--    STATUS     current
--    DESCRIPTION
--        "A list of IP address entries."
--    ::= { ipFilterMgt 2 }
--
--ipFilterHTTPEntry  OBJECT-TYPE
--    SYNTAX     IpFilterHTTPEntry
--    MAX-ACCESS not-accessible
--    STATUS     current
--    DESCRIPTION
--        "This entry includes an IP address range which the system 
--         will allow to connect to this device through SNMP."
--    INDEX { ipFilterHTTPStartAddress }
--    ::= { ipFilterHTTPTable 1 }
--    
--IpFilterHTTPEntry ::= SEQUENCE {
--    ipFilterHTTPStartAddress        IpAddress,
--    ipFilterHTTPEndAddress          IpAddress,
--    ipFilterHTTPStatus              ValidStatus
--}
--
--ipFilterHTTPStartAddress OBJECT-TYPE
--        SYNTAX      IpAddress
--        MAX-ACCESS  not-accessible
--        STATUS      current
--        DESCRIPTION "The start IP address."        
--        ::= { ipFilterHTTPEntry 1 }
--        
--ipFilterHTTPEndAddress OBJECT-TYPE
--        SYNTAX      IpAddress
--        MAX-ACCESS  read-create
--        STATUS      current
--        DESCRIPTION "The end IP address."        
--        ::= { ipFilterHTTPEntry 2 }     
--
--ipFilterHTTPStatus OBJECT-TYPE
--        SYNTAX      ValidStatus
--        MAX-ACCESS  read-create
--        STATUS      current
--        DESCRIPTION "Setting this to valid(1) creates an entry.
--                     Setting this to invalid(2) destroys an entry."        
--        ::= { ipFilterHTTPEntry 3 } 
--        
----ipFilterTelnetTable
--ipFilterTelnetTable  OBJECT-TYPE
--    SYNTAX     SEQUENCE OF IpFilterTelnetEntry
--    MAX-ACCESS not-accessible
--    STATUS     current
--    DESCRIPTION
--        "A list of IP address entries."
--    ::= { ipFilterMgt 3 }
--
--ipFilterTelnetEntry  OBJECT-TYPE
--    SYNTAX     IpFilterTelnetEntry
--    MAX-ACCESS not-accessible
--    STATUS     current
--    DESCRIPTION
--        "This entry includes an IP address range which the system 
--         will allow them to connect to this device through SNMP."
--    INDEX { ipFilterTelnetStartAddress }
--    ::= { ipFilterTelnetTable 1 }
--    
--IpFilterTelnetEntry ::= SEQUENCE {
--    ipFilterTelnetStartAddress        IpAddress,
--    ipFilterTelnetEndAddress          IpAddress,
--    ipFilterTelnetStatus              ValidStatus
--}
--
--ipFilterTelnetStartAddress OBJECT-TYPE
--        SYNTAX      IpAddress
--        MAX-ACCESS  not-accessible
--        STATUS      current
--        DESCRIPTION "The start IP address."        
--        ::= { ipFilterTelnetEntry 1 }
--        
--ipFilterTelnetEndAddress OBJECT-TYPE
--        SYNTAX      IpAddress
--        MAX-ACCESS  read-create
--        STATUS      current
--        DESCRIPTION "The end IP address."        
--        ::= { ipFilterTelnetEntry 2 }     
--
--ipFilterTelnetStatus OBJECT-TYPE
--        SYNTAX      ValidStatus
--        MAX-ACCESS  read-create
--        STATUS      current
--        DESCRIPTION "Setting this to valid(1) creates an entry.
--                     Setting this to invalid(2) destroys an entry."        
--        ::= { ipFilterTelnetEntry 3 } 
--                  
----        
----macAuthMgt
----
--
----macAuthReauthTime OBJECT-TYPE
----        SYNTAX       Unsigned32(120..1000000)
----        MAX-ACCESS   read-write
----        STATUS       current
----        DESCRIPTION
----                "The time, in seconds, after which an authenticated MAC address
----                 is reauthenticated."
----        ::= { macAuthMgt 1 }
--
----
----netAccessMgt
----
--
----netAccessPortTable OBJECT-TYPE
----        SYNTAX      SEQUENCE OF NetAccessPortEntry
----        MAX-ACCESS  not-accessible
----        STATUS      current
----        DESCRIPTION
----                "Specifies the attributes and functions of secure ports."
----        ::= { netAccessMgt 1 }
----
----netAccessPortEntry OBJECT-TYPE
----        SYNTAX      NetAccessPortEntry
----        MAX-ACCESS  not-accessible
----        STATUS      current
----        DESCRIPTION
----                "A conceptual row of the netAccessPortTable."
----        INDEX      { netAccessPortIfIndex }
----        ::= { netAccessPortTable 1 }
----
----NetAccessPortEntry ::= SEQUENCE
----{
----        netAccessPortIfIndex                  InterfaceIndex,
----        netAccessPortMode                     INTEGER,
----        netAccessPortMaxMacCount              Unsigned32(1..32),
----        netAccessPortFilterId                 Unsigned32(0..64),
----        netAccessPortDynamicVlanEnable        EnabledStatus
----}
----
----netAccessPortIfIndex OBJECT-TYPE
----        SYNTAX       InterfaceIndex
----        MAX-ACCESS   not-accessible
----        STATUS       current
----        DESCRIPTION
----                "Specifies the index for the netAccessPortTable entry.
----                 This is defined as ifIndex in the IF-MIB."
----        ::= { netAccessPortEntry 1 }
----
----netAccessPortMode OBJECT-TYPE
----        SYNTAX       INTEGER
----                     {
----                         noRestrictions(1),
----                         macAuthentication(6)
----                     }
----        MAX-ACCESS   read-write
----        STATUS       current
----        DESCRIPTION
----                "This variable determines the secure mode of a port.
----                 In non-secure port mode, this variable has a value of
----                 noRestrictions(1) and MAC authentication is disabled for the 
----                 port. In secure port mode, this variable has a value of
----                 macAuthentication(6), and MAC authentication is enabled for
----                 the port."
----        ::= { netAccessPortEntry 2 }
----
----netAccessPortMaxMacCount OBJECT-TYPE
----        SYNTAX       Unsigned32(1..1024)
----        MAX-ACCESS   read-write
----        STATUS       current
----        DESCRIPTION
----                "The maximum number of MAC addresses that can be learned by
----                 the secure port. This value can be set by user after setting
----                 netAccessPortMode macAuthentication(6). The value range
----                 is between 1 and 1024. The value 1024 indicates no limit to
----                 the number of MAC addresses that can be learned."
----        ::= { netAccessPortEntry 3 }
----
----netAccessPortFilterId OBJECT-TYPE
----        SYNTAX       Unsigned32(0..64)
----        MAX-ACCESS   read-write
----        STATUS       current
----        DESCRIPTION
----                "Creates a MAC address filter that can be applied to one
----                 port. The filter cannot be applied to multiple ports. The 
----                 filter ID range is between 0 and 64. Using filter ID 0
----                 removes the filter from the port."
----        ::= { netAccessPortEntry 4 }
----
----netAccessPortDynamicVlanEnable	OBJECT-TYPE
----        SYNTAX       EnabledStatus
----        MAX-ACCESS   read-write
----        STATUS       current
----        DESCRIPTION
----                "Enables secure dynamic VLAN assignment. VLAN IDs are assigned
----                 from a configured RADIUS server."
----        ::= { netAccessPortEntry 5 }
----
----netAccessMacFilterTable	OBJECT-TYPE
----        SYNTAX      SEQUENCE OF NetAccessMacFilterEntry
----        MAX-ACCESS  not-accessible
----        STATUS      current
----        DESCRIPTION
----                "Specifies the relationship between filters and MAC addresses."
----        ::= { netAccessMgt 2 }
----
----netAccessMacFilterEntry OBJECT-TYPE
----        SYNTAX      NetAccessMacFilterEntry
----        MAX-ACCESS  not-accessible
----        STATUS      current
----        DESCRIPTION
----                "A conceptual row of the netAccessMacFilterTable."
----        INDEX      { netAccessMacFilterId, netAccessMacFilterMacAddr }
----        ::= { netAccessMacFilterTable 1 }
----
----NetAccessMacFilterEntry ::= SEQUENCE
----{
----        netAccessMacFilterId            Unsigned32,
----        netAccessMacFilterMacAddr       MacAddress,
----        netAccessMacFilterStatus        ValidStatus
----}
----
----netAccessMacFilterId OBJECT-TYPE
----        SYNTAX       Unsigned32(1..64)
----        MAX-ACCESS   not-accessible
----        STATUS       current
----        DESCRIPTION
----                "Specifies the filter ID for the netAccessMacFilterTable entry."
----        ::= { netAccessMacFilterEntry 1 }
----
----netAccessMacFilterMacAddr OBJECT-TYPE
----        SYNTAX       MacAddress
----        MAX-ACCESS   not-accessible
----        STATUS       current
----        DESCRIPTION
----                "Specifies the MAC address for the netAccessMacFilterTable
----                 entry."
----        ::= { netAccessMacFilterEntry 2 }
----
----netAccessMacFilterStatus OBJECT-TYPE
----        SYNTAX       ValidStatus
----        MAX-ACCESS   read-create
----        STATUS       current
----        DESCRIPTION
----                "Set this to valid(1) creates an entry.
----                 Set this to invalid(2) destroys an entry."
----        ::= { netAccessMacFilterEntry 3 }
----
----netAccessMacAddrTable	OBJECT-TYPE
----        SYNTAX      SEQUENCE OF NetAccessMacAddrEntry
----        MAX-ACCESS  not-accessible
----        STATUS      current
----        DESCRIPTION
----                "The table of authenticated MAC addresses for this switch's
----                 port and MAC address."
----        ::= { netAccessMgt 3 }
----
----netAccessMacAddrEntry OBJECT-TYPE
----        SYNTAX      NetAccessMacAddrEntry
----        MAX-ACCESS  not-accessible
----        STATUS      current
----        DESCRIPTION
----                "A conceptual row of the netAccessMacAddrTable."
----        INDEX      { netAccessMacAddrPortIfIndex, netAccessMacAddr }
----        ::= { netAccessMacAddrTable 1 }
----
----NetAccessMacAddrEntry ::= SEQUENCE
----{
----        netAccessMacAddrPortIfIndex        InterfaceIndex,
----        netAccessMacAddr                   MacAddress,
----        netAccessMacAddrRadiusServer       IpAddress,
----        netAccessMacAddrTime               TimeTicks,
----        netAccessMacAddrAttribute          INTEGER
----}
----
----netAccessMacAddrPortIfIndex OBJECT-TYPE
----        SYNTAX       InterfaceIndex
----        MAX-ACCESS   not-accessible
----        STATUS       current
----        DESCRIPTION
----                "Specifies the filter ID for the netAccessMacAddrTable entry.
----                 This is defined as ifIndex in the IF-MIB."
----        ::= { netAccessMacAddrEntry 1 }
----
----netAccessMacAddr OBJECT-TYPE
----        SYNTAX       MacAddress
----        MAX-ACCESS   not-accessible
----        STATUS       current
----        DESCRIPTION
----                "Specifies the MAC address for the netAccessMacAddrTable entry."
----        ::= { netAccessMacAddrEntry 2 }
----
----netAccessMacAddrRadiusServer OBJECT-TYPE
----        SYNTAX       IpAddress
----        MAX-ACCESS   read-only
----        STATUS       current
----        DESCRIPTION
----                "This represents the relationship of the RADIUS server and MAC
----                 addresses. The value is the IP address of the RADIUS server."
----        ::= { netAccessMacAddrEntry 3 }
----
----netAccessMacAddrTime OBJECT-TYPE
----        SYNTAX       TimeTicks
----        MAX-ACCESS   read-only
----        STATUS       current
----        DESCRIPTION
----                "The value is the time in seconds since the MAC address was 
----                 authenticated. The MAC address is authenticated by the 
----                 RADIUS server."
----        ::= { netAccessMacAddrEntry 4 }
----
----netAccessMacAddrAttribute OBJECT-TYPE
----        SYNTAX       INTEGER
----                     { 
----                         static(1),
----                         dynamic(2)
----                     }
----        MAX-ACCESS   read-only
----        STATUS       current
----        DESCRIPTION
----                "Indicates how the MAC address was obtained by the system.
----                 static(1):  Added by a user.
----                 dynamic(2): Learned by the switch."
----        ::= { netAccessMacAddrEntry 5 }
--
--
----
---- sysLogMgt
----
--
--sysLogStatus OBJECT-TYPE
--        SYNTAX      INTEGER
--                    {
--                        enabled(1),
--                        disabled(2)
--                    }
--        MAX-ACCESS  read-write
--        STATUS      current
--        DESCRIPTION "Whether system log is enabled."
--        ::= { sysLogMgt 1 }
--
--sysLogHistoryFlashLevel OBJECT-TYPE
--        SYNTAX      INTEGER (0..7)
--        MAX-ACCESS  read-write
--        STATUS      current
--        DESCRIPTION "Severity level for logging to flash."
--        ::= { sysLogMgt 2 }
--
--sysLogHistoryRamLevel OBJECT-TYPE
--        SYNTAX      INTEGER (0..7)
--        MAX-ACCESS  read-write
--        STATUS      current
--        DESCRIPTION "Severity level for logging to RAM."
--        ::= { sysLogMgt 3 }
--
--remoteLogMgt OBJECT IDENTIFIER ::= { sysLogMgt 6 }
--
--remoteLogStatus OBJECT-TYPE
--       SYNTAX      EnabledStatus
--       MAX-ACCESS  read-write
--       STATUS      current
--       DESCRIPTION "Whether the remote log system is enabled."
--       ::= { remoteLogMgt 1 }
--
--remoteLogLevel OBJECT-TYPE
--        SYNTAX      Integer32 (0..7)
--        MAX-ACCESS  read-write
--        STATUS      current
--        DESCRIPTION "Severity level for remote log."
--        ::= { remoteLogMgt 2 }
--
--remoteLogFacilityType OBJECT-TYPE
--        SYNTAX      INTEGER
--                    {
--                      localUse0(16),
--                      localUse1(17),
--                      localUse2(18),
--                      localUse3(19),
--                      localUse4(20),
--                      localUse5(21),
--                      localUse6(22),
--                      localUse7(23)
--                     }
--        MAX-ACCESS   read-write
--        STATUS       current
--        DESCRIPTION " The FacilityType for remote log."
--        ::= { remoteLogMgt 3 }
--
--remoteLogServerTable OBJECT-TYPE
--        SYNTAX      SEQUENCE OF RemoteLogServerEntry
--        MAX-ACCESS  not-accessible
--        STATUS      current
--        DESCRIPTION "A Table for storing the remote log Server list."
--        ::= { remoteLogMgt 4 }
--
--remoteLogServerEntry OBJECT-TYPE
--        SYNTAX      RemoteLogServerEntry
--        MAX-ACCESS  not-accessible
--        STATUS      current
--        DESCRIPTION "A conceptually row for remoteLogServerTable."
--        INDEX { remoteLogServerIp }
--        ::= { remoteLogServerTable 1 }
--
--RemoteLogServerEntry ::= SEQUENCE
--{
--    remoteLogServerIp     IpAddress,
--    remoteLogServerStatus ValidStatus
--}
--
--remoteLogServerIp OBJECT-TYPE
--         SYNTAX      IpAddress
--         MAX-ACCESS  read-create
--         STATUS      current
--         DESCRIPTION "The IP address of the remote log Server."
--         ::= { remoteLogServerEntry 1 }
--
--remoteLogServerStatus OBJECT-TYPE
--         SYNTAX      ValidStatus
--         MAX-ACCESS  read-create
--         STATUS      current
--         DESCRIPTION  "Setting this to valid(1) creates an entry.
--                       Setting this to invalid(2) destroys an entry."
--         ::= { remoteLogServerEntry 2 }
--         
----
----smtpMgt
----
--smtpMgt   OBJECT IDENTIFIER ::= { sysLogMgt 7 }
--
--smtpStatus OBJECT-TYPE
--    SYNTAX       EnabledStatus
--    MAX-ACCESS   read-write
--    STATUS       current
--    DESCRIPTION "Set enabled(1) to enable the SMTP, set disabled(2) to disable 
--                 the SMTP."
--    ::= { smtpMgt 1 }
--    
--smtpSeverityLevel OBJECT-TYPE
--    SYNTAX       Integer32 (0..7)
--    MAX-ACCESS   read-write
--    STATUS       current
--    DESCRIPTION "Specify the SMTP minimum severity level to send the event message."
--    ::= { smtpMgt 2 } 
--
--smtpSourceEMail OBJECT-TYPE
--    SYNTAX       DisplayString (SIZE(0..41)) 
--    MAX-ACCESS   read-write
--    STATUS       current
--    DESCRIPTION "SMTP source email address, 
--                the sender's mail address that appears 
--                in the 'From' field of the mail."
--    ::= { smtpMgt 3 }
--
----smtpServerIpTable  
--
--smtpServerIpTable OBJECT-TYPE
--       SYNTAX      SEQUENCE OF SmtpServerIpEntry
--       MAX-ACCESS  not-accessible
--       STATUS      current
--       DESCRIPTION "The SMTP server IP table. 
--                    The maximum servers to be added is 3."
--       ::= { smtpMgt 4 }
--
--smtpServerIpEntry OBJECT-TYPE
--       SYNTAX      SmtpServerIpEntry
--       MAX-ACCESS  not-accessible
--       STATUS      current
--       DESCRIPTION "A conceptual row of the smtpServerIpTable."
--       INDEX  { smtpServerIp }
--       ::= { smtpServerIpTable 1 }
--
--SmtpServerIpEntry ::= SEQUENCE
--{
--    smtpServerIp     IpAddress,
--    smtpServerIpStatus ValidStatus
--}
--
--smtpServerIp OBJECT-TYPE
--       SYNTAX      IpAddress
--       MAX-ACCESS  accessible-for-notify
--       STATUS      current
--       DESCRIPTION "SMTP mail server's IP address."
--       ::= { smtpServerIpEntry 1 }  
--
--smtpServerIpStatus OBJECT-TYPE
--       SYNTAX      ValidStatus
--       MAX-ACCESS  read-create
--       STATUS      current
--       DESCRIPTION "Setting this to valid(1) creates an entry.
--                    Setting this to invalid(2) destroys an entry."
--       ::= { smtpServerIpEntry 2 }           
--       
----smtpDestEMailTable
--
--smtpDestEMailTable OBJECT-TYPE
--       SYNTAX      SEQUENCE OF SmtpDestEMailEntry
--       MAX-ACCESS  not-accessible
--       STATUS      current
--       DESCRIPTION "The table of the destination e-mail address.
--                    The maximum numbers of destination email address to be added is 5."
--       ::= { smtpMgt 5}
--
--smtpDestEMailEntry OBJECT-TYPE
--       SYNTAX      SmtpDestEMailEntry
--       MAX-ACCESS  not-accessible
--       STATUS      current
--       DESCRIPTION "A conceptual row of the smtpDestEMailTable."
--       INDEX  { smtpDestEMail }
--       ::= { smtpDestEMailTable 1 }
--
--SmtpDestEMailEntry ::= SEQUENCE
--{
--    smtpDestEMail     DisplayString,
--    smtpDestEMailStatus ValidStatus
--}
--
--smtpDestEMail OBJECT-TYPE
--       SYNTAX      DisplayString (SIZE(0..41)) 
--       MAX-ACCESS  not-accessible
--       STATUS      current
--       DESCRIPTION "SMTP destination e-mail address."
--       ::= { smtpDestEMailEntry 1 }  
--
--smtpDestEMailStatus OBJECT-TYPE
--       SYNTAX      ValidStatus
--       MAX-ACCESS  read-create
--       STATUS      current
--       DESCRIPTION "Setting this to valid(1) creates an entry.
--                    Setting this to invalid(2) destroys an entry."
--       ::= { smtpDestEMailEntry 2 }                   
--
----smtpServerHostTable  
----
----smtpServerHostTable OBJECT-TYPE
----       SYNTAX      SEQUENCE OF SmtpServerHostEntry
----       MAX-ACCESS  not-accessible
----       STATUS      current
----       DESCRIPTION "The SMTP server table. 
----                    The maximum servers to be added is 3."
----       ::= { smtpMgt 6 }
----
----smtpServerHostEntry OBJECT-TYPE
----       SYNTAX      SmtpServerHostEntry
----       MAX-ACCESS  not-accessible
----       STATUS      current
----       DESCRIPTION "A conceptual row of the smtpServerHostTable."
----       INDEX  { smtpServerHostName }
----       ::= { smtpServerHostTable 1 }
----
----SmtpServerHostEntry ::= SEQUENCE
----{
----    smtpServerHostName     DisplayString,
----    smtpServerHostStatus ValidStatus
----}
----
----smtpServerHostName OBJECT-TYPE
----       SYNTAX      DisplayString(SIZE(0..255))
----       MAX-ACCESS  not-accessible
----       STATUS      current
----       DESCRIPTION "IP address or DNS of SMTP mail servers."
----       ::= { smtpServerHostEntry 1 }  
----
----smtpServerHostStatus OBJECT-TYPE
----       SYNTAX      ValidStatus
----       MAX-ACCESS  read-create
----       STATUS      current
----       DESCRIPTION "Setting this to valid(1) creates an entry.
----                    Setting this to invalid(2) destroys an entry."
----       ::= { smtpServerHostEntry 2 } 
----
---- lineMgt
----
--
---- Management for line. This includes management for
---- serial line (RS232 port) and Telnet.
--
--consoleMgt           OBJECT IDENTIFIER ::= { lineMgt 1 }
--telnetMgt            OBJECT IDENTIFIER ::= { lineMgt 2 }
--
--
----consoleMgt
--
--consoleDataBits OBJECT-TYPE
--        SYNTAX      INTEGER
--                    {
--                      databits7(1),
--                      databits8(2)
--                    }
--        MAX-ACCESS  read-write
--        STATUS      current
--        DESCRIPTION "Number of data bits."
--        ::= { consoleMgt 1 }
--
--consoleParity OBJECT-TYPE
--        SYNTAX      INTEGER
--                    {
--                     partyNone(1),
--                     partyEven(2),
--                     partyOdd(3)
--                    }
--        MAX-ACCESS  read-write
--        STATUS      current
--        DESCRIPTION "Defines the generation of a parity bit."
--        ::= { consoleMgt 2 }
--
--consoleStopBits OBJECT-TYPE
--        SYNTAX     INTEGER
--                   {
--                    stopbits1(1),
--                    stopbits2(2)
--                   }
--        MAX-ACCESS read-write
--        STATUS     current
--        DESCRIPTION "The console stop bits, valid values are stopbits1(1) or stopbits2(2)"
--        ::= { consoleMgt 4 }
--
--consoleExecTimeout OBJECT-TYPE
--        SYNTAX      Integer32 (0..65535)
--        MAX-ACCESS  read-write
--        STATUS      current
--        DESCRIPTION "In a serial console, use the consoleExecTimeout
--                     variable to set the interval that the EXEC command
--                     interpreter waits until user input is detected;
--                     set the value to 0 to disable it."
--        ::= { consoleMgt 5 }
--
--consolePasswordThreshold OBJECT-TYPE
--        SYNTAX      Integer32 (0..120)
--        MAX-ACCESS  read-write
--        STATUS      current
--        DESCRIPTION "The number of failed console logon attempts that may be
--                     made before the system will not accept a further attempt
--                     in the time specified by consoleSilentTime. A value of 0
--                     disables the functionality."
--        ::= { consoleMgt 6 }
--
--consoleSilentTime OBJECT-TYPE
--        SYNTAX      Integer32 (0..65535)
--        MAX-ACCESS  read-write
--        STATUS      current
--        DESCRIPTION "The length of time that the management console is
--                     inaccessible after the number of failed logon
--                     attempts has reached consolePasswordThreshold. A value
--                     of 0 disables the functionality."
--                     
--        ::= { consoleMgt 7 }
--        
--consoleAdminBaudRate OBJECT-TYPE
--        SYNTAX      Integer32
--        MAX-ACCESS  read-write
--        STATUS      current
--        DESCRIPTION "Baud rate. Valid values are 2400, 4800, 9600,
--                    19200, 38400, 57600, 115200.
--                    
--                    Setting this variable to 0 means autobaud.
--                    Please read the actual baud rate in the consoleOperBaudRate variable."                                                          
--        ::= { consoleMgt 8 }
--        
--consoleOperBaudRate OBJECT-TYPE
--        SYNTAX      Integer32
--        MAX-ACCESS  read-only
--        STATUS      current
--        DESCRIPTION "The baud rate currently in use."
--        ::= { consoleMgt 9 } 
--
----to set login timeout seconds
--consoleLoginResponseTimeout OBJECT-TYPE
--        SYNTAX      Integer32(0..300)
--        MAX-ACCESS  read-write
--        STATUS      current
--        DESCRIPTION  "Console login response timeout setting.
--                     Valid range is 0 to 300. Setting to 0 means disabled."
--        ::= { consoleMgt 10 }        
--
---- telnetMgt
--
--telnetExecTimeout OBJECT-TYPE
--        SYNTAX      INTEGER (1..65535)
--        MAX-ACCESS  read-write
--        STATUS      current
--        DESCRIPTION  "In a telnet session, to set the interval that the EXEC command interpreter
--                     waits until user input is detected, use the telnetExecTimeout
--                     variables. "
--        ::= { telnetMgt 1 }
--
--telnetPasswordThreshold OBJECT-TYPE
--        SYNTAX      INTEGER (0..120)
--        MAX-ACCESS  read-write
--        STATUS      current
--        DESCRIPTION "In a telnet session, use the consolePasswordThreshold variabes to
--                     set the password intrusion threshold, which limits the number of 
--                     failed logon attempts allowed. Set it value to 0 to disable it."
--        ::= { telnetMgt 2 }
--        
----to set login timeout seconds
--telnetLoginResponseTimeout OBJECT-TYPE
--        SYNTAX      Integer32(1..300)
--        MAX-ACCESS  read-write
--        STATUS      current
--        DESCRIPTION  "Telnet login response timeout setting.
--                     Valid range is 1 to 300.
--                     This timout setting cannot be disbled."
--        ::= { telnetMgt 3 }        

--
-- sysTimeMgt
--

sntpMgt OBJECT IDENTIFIER ::= { sysTimeMgt 1 }

sntpStatus OBJECT-TYPE
    SYNTAX      EnabledStatus
    MAX-ACCESS  read-write
    STATUS      current
    DESCRIPTION "Set enabled(1) to enable the SNTP, set disabled(2) to disable 
                 the SNTP."
    ::= { sntpMgt 1 }

sntpServiceMode OBJECT-TYPE
    SYNTAX      INTEGER
                {
                    unicast(1)
                }
    MAX-ACCESS  read-write
    STATUS      current
    DESCRIPTION "Service mode."
    ::= { sntpMgt 2 }

sntpPollInterval OBJECT-TYPE
    SYNTAX      Integer32(16..16384)
    MAX-ACCESS  read-only
    STATUS      current
    DESCRIPTION "Polling interval."
    ::= { sntpMgt 3 }

sntpServerTable OBJECT-TYPE
        SYNTAX      SEQUENCE OF SntpServerEntry
        MAX-ACCESS  not-accessible
        STATUS      current
        DESCRIPTION "Table for SNTP servers"
        ::= { sntpMgt 4 }

sntpServerEntry OBJECT-TYPE
        SYNTAX      SntpServerEntry
        MAX-ACCESS  not-accessible
        STATUS      current
        DESCRIPTION "Entry for SNTP servers."
        INDEX       { sntpServerIndex }
        ::= { sntpServerTable 1 }

SntpServerEntry ::= SEQUENCE
{
    sntpServerIndex Integer32,
    sntpServerIpAddress IpAddress
}


sntpServerIndex OBJECT-TYPE
    SYNTAX      Integer32 (1..3)
    MAX-ACCESS  not-accessible
    STATUS      current
    DESCRIPTION "The index of a server. This table has fixed size."
    ::= { sntpServerEntry 1 }

sntpServerIpAddress OBJECT-TYPE
    SYNTAX      IpAddress
    MAX-ACCESS  read-write
    STATUS      current
    DESCRIPTION "The IP address of a server. Valid IP addresses
                 must occupy contiguous indexes.
                 All IP addresses after the last valid index is 0."
    ::= { sntpServerEntry 2 }

sysCurrentTime OBJECT-TYPE
     SYNTAX      DisplayString(SIZE(20))
     MAX-ACCESS  read-only
     STATUS      current
     DESCRIPTION "It is a text string in the following form, based on Unix:
                  'Mmm _d hh:mm:ss yyyy'. 'Mmm' is the first three letters 
                  of the English name of the month. '_d' is the day of month. 
                  A single-digit day is preceded by the space. 'hh:mm:ss' is
                  a 24-hour representations of hours, minutes, and seconds. 
                  A single-digit hour is preceded by a zero. 'yyyy' is the 
                  four-digit year. An example is: 'Jan  1 02:03:04 2002'."
     ::= { sysTimeMgt 2 }

sysTimeZone OBJECT-TYPE
     SYNTAX      DisplayString(SIZE(6))
     MAX-ACCESS  read-write
     STATUS      current
     DESCRIPTION "It is a text string in the following form: '[s]hh:mm'.
                  '[s]' is a plus-or-minus sign. For UTC, this is omitted. 
                  For a positive offset, this is '+'. For a negative offset,
                  this is '-'. 'hh:mm' in the hour and minute offset from UTC. 
                  A single-digit hour is preceded by a zero."
     ::= { sysTimeMgt 3 }

--sysTimeZoneName OBJECT-TYPE
--     SYNTAX      DisplayString(SIZE(0..30))
--     MAX-ACCESS  read-write
--     STATUS      current
--     DESCRIPTION "The name of the time zone."
--     ::= { sysTimeMgt 4 }

ntpMgt OBJECT IDENTIFIER ::= { sysTimeMgt 5}
ntpStatus OBJECT-TYPE
            SYNTAX      EnabledStatus
            MAX-ACCESS  read-write
            STATUS      current
            DESCRIPTION "Set enabled(1) to enable the NTP, set disabled(2) to disable 
                     the NTP."
	::= { ntpMgt 1 }
ntpServiceMode OBJECT-TYPE
    	SYNTAX      INTEGER
                {
                    unicast(1)
                }
    	MAX-ACCESS  read-write
    	STATUS      current
    	DESCRIPTION "Service mode."
	::= { ntpMgt 2 }
ntpPollInterval OBJECT-TYPE
    	SYNTAX      Integer32(16..16384)
    	MAX-ACCESS  read-write
    	STATUS      current
    	DESCRIPTION "Polling interval."
    	::= { ntpMgt 3 }
ntpAuthenticateStatus OBJECT-TYPE
            SYNTAX      EnabledStatus
            MAX-ACCESS  read-write
            STATUS      current
            DESCRIPTION "Set enabled(1) to enable the NTP Authenticate, set disabled(2) to 
                     disable  the NTP."
	::= { ntpMgt 4 }
ntpServerTable OBJECT-TYPE
        	SYNTAX      SEQUENCE OF NtpServerEntry
        	MAX-ACCESS  not-accessible
        	STATUS      current
        	DESCRIPTION "Table for NTP servers"
        	::= { ntpMgt 5 }
ntpServerEntry OBJECT-TYPE
        	SYNTAX      NtpServerEntry
        	MAX-ACCESS  not-accessible
        	STATUS      current
        	DESCRIPTION "Entry for NTP servers."
        	INDEX       { ntpServerIpAddress }
        	::= { ntpServerTable 1 }
NtpServerEntry ::= SEQUENCE
	{
	ntpServerIpAddress IpAddress,
	ntpServerVersion Integer32,
	ntpServerKeyId       Integer32,
	ntpServerStatus INTEGER
	}
ntpServerIpAddress OBJECT-TYPE
    	SYNTAX      IpAddress
    	MAX-ACCESS  not-accessible
    	STATUS      current
    	DESCRIPTION "The IP address of a server. Valid IP addresses
                 must occupy contiguous indexes.
                 All IP addresses after the last valid index is 0."
    	::= { ntpServerEntry 1 }
ntpServerVersion OBJECT-TYPE
        	SYNTAX      Integer32 (1..3)
        	MAX-ACCESS  read-create
        	STATUS      current
        	DESCRIPTION "NTP version."
        	::= { ntpServerEntry 2 }
ntpServerKeyId       OBJECT-TYPE
            SYNTAX      Integer32 (1..65535)
            MAX-ACCESS  read-write
            STATUS      current
            DESCRIPTION "Key for a NTP server.  This variable can only be written.
                     "
           ::= { ntpServerEntry 3 }
           
ntpServerStatus OBJECT-TYPE
        SYNTAX     INTEGER
               {
                   create(1),
                   active(2),
                   destroy(3)
               }
        MAX-ACCESS  read-create
        STATUS      current
	DESCRIPTION
			"The status of this conceptual row entry. This object isused to manage the
			creation and deletion of conceptual rows.

			The status column has six defined values:

			     - 'active', which indicates that the conceptual row is
			     available for use by the managed device;
			     
			     - 'create', which is supplied by a management
			     station wishing to create a new instance of a
			     conceptual row and to have its status automatically set
			     to active, making it available for use by the managed
			     device;  
			     
			     - 'destroy', which is supplied by a management station
			     wishing to delete all of the instances associated with
			     an existing conceptual row."
        ::= { ntpServerEntry 4 }
        
ntpAuthKeyTable OBJECT-TYPE
        	SYNTAX      SEQUENCE OF NtpAuthKeyEntry
        	MAX-ACCESS  not-accessible
        	STATUS      current
        	DESCRIPTION "Table for NTP Authentication keys"
        	::= { ntpMgt 6 }
ntpAuthKeyEntry OBJECT-TYPE
        	SYNTAX      NtpAuthKeyEntry
        	MAX-ACCESS  not-accessible
        	STATUS      current
        	DESCRIPTION "Entry for NTP Authentication keys."
        	INDEX       { ntpAuthKeyId }
        	::= { ntpAuthKeyTable 1 }
NtpAuthKeyEntry::= SEQUENCE
	{
	ntpAuthKeyId Integer32,
	ntpAuthKeyWord OCTET STRING,
	ntpAuthKeyStatus INTEGER
	}
ntpAuthKeyId OBJECT-TYPE
    	SYNTAX      Integer32 (1..65536)
    	MAX-ACCESS  not-accessible
    	STATUS      current
    	DESCRIPTION "The index of a Authentication key. This table has fixed size."
    	::= { ntpAuthKeyEntry 1 }
ntpAuthKeyWord OBJECT-TYPE
    	SYNTAX      OCTET STRING (SIZE (1..32))
    	MAX-ACCESS  read-create
    	STATUS      current
    	DESCRIPTION "The Authentication key word is used to created a key  by the MD5
	And the max length is 32."
    	::= { ntpAuthKeyEntry 2 }
ntpAuthKeyStatus OBJECT-TYPE
        SYNTAX          INTEGER
               {
                   create(1),
                   active(2),
                   destroy(3)
               }
        MAX-ACCESS  read-create
        STATUS      current
	    DESCRIPTION
			"The status of this conceptual row entry. This object isused to manage the
			creation and deletion of conceptual rows.

			The status column has six defined values:

			     - 'active', which indicates that the conceptual row is
			     available for use by the managed device;
			     
			     - 'create', which is supplied by a management
			     station wishing to create a new instance of a
			     conceptual row and to have its status automatically set
			     to active, making it available for use by the managed
			     device;  
			     
			     - 'destroy', which is supplied by a management station
			     wishing to delete all of the instances associated with
			     an existing conceptual row."
        ::= { ntpAuthKeyEntry 3 }


-- 
-- fileMgt
--

-- Management for File System Manipulate, including files copy, display and delete.


fileCopyMgt OBJECT IDENTIFIER ::= { fileMgt 1 }
--
-- This performs the copy operation.
--

fileCopySrcOperType OBJECT-TYPE
    SYNTAX     INTEGER 
               {
                 switchDevice(1),
                 tftp(2)
                }
    MAX-ACCESS read-write
    STATUS     current
    DESCRIPTION "The Copy Operation that we want to perform on the
                 fileCopyDestOperType.
                 switchDevice(1) means we want save configuration to TFTP server, tftp(2) means 
                 we want to load firmware or configuration from TFTP server.
                 Note: The value of fileCopySrcOperType and fileCopyDestOperType should not equal."
    ::= { fileCopyMgt 1}
    
fileCopySrcFileName OBJECT-TYPE
    SYNTAX     DisplayString (SIZE(0..32))
    MAX-ACCESS read-write
    STATUS     current
    DESCRIPTION
        "The source file name for fileCopyMgt when a copy
        operation is next requested via this MIB. This value is set to
        a zero length string when no file name has been specified.
        Note: If the fileCopySrcOperType is switchDevice(1),
        this variable can be ignored."
    ::= { fileCopyMgt 2 }
    
fileCopyDestOperType OBJECT-TYPE
    SYNTAX     INTEGER 
               {
                 switchDevice(1),
                 tftp(2)
                }
    MAX-ACCESS read-write
    STATUS     current
    DESCRIPTION "The Copy Operation that we want to perform on
                 fileCopySrcOperType.
                 switchDevice(1) means we want load firmware or configuration from TFTP server, tftp(2) means 
                 we want to save configuration to TFTP server.
                 Note: The value of fileCopySrcOperType and fileCopyDestOperType should not equal."
    ::= { fileCopyMgt 3 }

fileCopyDestFileName  OBJECT-TYPE
    SYNTAX     DisplayString (SIZE(0..32))
    MAX-ACCESS read-write
    STATUS     current
    DESCRIPTION
        "The destination file name for fileCopyMgt when a
        copy operation is next requested via this MIB. This value is set to
        a zero length string when no file name has been specified.
        Note: If the fileCopyDestOperType is switchDevice(1),
        this variable can be ignored."
    ::= { fileCopyMgt 4 }

fileCopyFileType  OBJECT-TYPE
    SYNTAX     INTEGER {
                  opcode(1),
                  config(2)
               }
    MAX-ACCESS read-write
    STATUS     current
    DESCRIPTION
        "Type of file to copy in fileCopyMgt."
    ::= { fileCopyMgt 5 }

fileCopyTftpServer  OBJECT-TYPE
    SYNTAX     IpAddress
    MAX-ACCESS read-write
    STATUS     current
    DESCRIPTION
        "The IP address of the TFTP server for transfer
        when a download is next requested via this MIB.
        This value is set to '0.0.0.0' when no IP address has been
        specified." 
--      If neither fileCopySrcOperType nor fileCopyDestOperType
--      is tftp(4), this variable can be ignored."
    ::= { fileCopyMgt 6 }   

--fileCopyUnitId OBJECT-TYPE
--    SYNTAX      Integer32
--    MAX-ACCESS  read-write
--    STATUS      current
--    DESCRIPTION "Specifies the switch unit for stackable devices. 
--                When performing the 'copy unit file' or 'copy file unit' action,
--                if neither fileCopySrcOperType nor fileCopyDestOperType
--                is unit(5), this variable can be ignored."
--    ::= { fileCopyMgt 7 }

fileCopyAction OBJECT-TYPE
    SYNTAX      INTEGER
                {
                  notCopying(1),
                  copy(2)
                }
    MAX-ACCESS read-write
    STATUS     current
    DESCRIPTION
          "Setting this object to copy(2) to begin the copy Operation.
           In ES4528V product, if copy opcode action is successful, the system
           will reboot immediately. In others condittion, we can get the current
           status whatever successful or error message from OID fileCopyTftpErrMsg."
    ::= { fileCopyMgt 8 }
                  
    
--fileCopyStatus  OBJECT-TYPE
--    SYNTAX     INTEGER {                    
--                    fileCopyTftpUndefError(1),
--                    fileCopyTftpFileNotFound(2),
--                    fileCopyTftpAccessViolation(3),
--                    fileCopyTftpDiskFull(4),
--                    fileCopyTftpIllegalOperation(5),
--                    fileCopyTftpUnkownTransferId(6),
--                    fileCopyTftpFileExisted(7),
--                    fileCopyTftpNoSuchUser(8),
--                    fileCopyTftpTimeout(9),
--                    fileCopyTftpSendError(10),
--                    fileCopyTftpReceiverError(11),
--                    fileCopyTftpSocketOpenError(12),
--                    fileCopyTftpSocketBindError(13),
--                    fileCopyTftpUserCancel(14),
--                    fileCopyTftpCompleted(15),
--                    fileCopyParaError(16),
--                    fileCopyBusy(17),
--                    fileCopyUnknown(18),
--                    fileCopyReadFileError(19),
--                    fileCopySetStartupError(20),
--                    fileCopyFileSizeExceed(21),
--                    fileCopyMagicWordError(22),
--                    fileCopyImageTypeError(23),
--                    fileCopyHeaderChecksumError(24),
--                    fileCopyImageChecksumError(25),                 
--                    fileCopyWriteFlashFinish(26),
--                    fileCopyWriteFlashError(27),
--                    fileCopyWriteFlashProgramming(28),
--                    fileCopyError(29),
--                    fileCopySuccess(30),
--                    fileCopyCompleted(31)                                                                          
--               }
--    MAX-ACCESS read-only
--    STATUS     current
--    DESCRIPTION
--        "The status of the last copy procedure, if any. This
--        object will have a value of downloadStatusUnknown(2) if no
--        copy operation has been performed."
--    ::= { fileCopyMgt 9 }

fileCopyTftpErrMsg OBJECT-TYPE
    SYNTAX      DisplayString(SIZE(0..255))
    MAX-ACCESS read-only
    STATUS     current
    DESCRIPTION
          "TFTP error message"
    ::= { fileCopyMgt 10 }
  
--fileInfoMgt OBJECT IDENTIFIER ::= { fileMgt 2 }

-- This mangement performs the display and delete operation.



--fileInfoTable OBJECT-TYPE
--    SYNTAX       SEQUENCE OF FileInfoEntry
--    MAX-ACCESS   not-accessible
--    STATUS       current
--    DESCRIPTION "This table contain the information of the file system;
--                 we can also perform the delete, set startup file operation."
--                
--    ::= { fileInfoMgt 1 }
--
--fileInfoEntry OBJECT-TYPE
--    SYNTAX       FileInfoEntry
--    MAX-ACCESS   not-accessible
--    STATUS       current
--    DESCRIPTION "A conceptually row for fileInfoTable."
--    INDEX       {fileInfoUnitID, IMPLIED fileInfoFileName}
--    ::= { fileInfoTable 1 }
--
--FileInfoEntry ::= SEQUENCE
--    {   
--        fileInfoUnitID                  Integer32,
--        fileInfoFileName                DisplayString,
--        fileInfoFileType                INTEGER,
--        fileInfoIsStartUp               TruthValue,
--        fileInfoFileSize                Integer32,
--        fileInfoCreationTime            DisplayString,
--        fileInfoDelete                  INTEGER        
--    }
--
--fileInfoUnitID OBJECT-TYPE
--    SYNTAX       Integer32
--    MAX-ACCESS   not-accessible
--    STATUS       current
--    DESCRIPTION "The switch unit in a stacking system, in a 
--                 non-stacking system, this value is always 1."
--    ::= { fileInfoEntry 1 }
--
--fileInfoFileName OBJECT-TYPE
--    SYNTAX       DisplayString (SIZE (1..32))
--    MAX-ACCESS   not-accessible
--    STATUS       current
--    DESCRIPTION "The file Name of the file System in the device."
--    ::= { fileInfoEntry 2 }
--    
--fileInfoFileType OBJECT-TYPE
--    SYNTAX       INTEGER
--                 {
--                    diag(1),
--                    runtime(2),
--                    syslog(3),
--                    cmdlog(4),
--                    config(5),
--                    postlog(6),
--                    private(7),
--                    certificate(8),
--                    webarchive(9)                                                        
--                 } 
--    MAX-ACCESS   read-only
--    STATUS       current
--    DESCRIPTION "The file type of the file System in the device."
--    ::= { fileInfoEntry 3 }
--
--fileInfoIsStartUp OBJECT-TYPE
--    SYNTAX       TruthValue
--    MAX-ACCESS   read-write
--    STATUS       current
--    DESCRIPTION "This flag indicate whether this file is a startup file. Set this
--                 object to true(1) to indicate that this is a startup file. Setting this 
--                 object to false(2) is a invalid operation."
--    ::= { fileInfoEntry 4 }
--
--fileInfoFileSize OBJECT-TYPE
--    SYNTAX       Integer32
--    UNITS        "bytes"
--    MAX-ACCESS   read-only
--    STATUS       current
--    DESCRIPTION "The sizes (in bytes) of the file."
--    ::= { fileInfoEntry 5 }
--
--fileInfoCreationTime OBJECT-TYPE
--    SYNTAX       DisplayString(SIZE(20))
--    MAX-ACCESS   read-only
--    STATUS       current
--    DESCRIPTION "The creation time of the file, This is a text string in the 
--                 following form, based on Unix: 'Mmm _d hh:mm:ss yyyy'. 'Mmm' 
--                 are the first three letters of the English name of the month. 
--                 '_d' is the day of month. A single-digit day is preceded by 
--                 a space. 'hh:mm:ss' is a 24-hour representations of hours,
--                 minutes, and seconds. A single-digit hour is preceded by a 
--                 zero. 'yyyy' is the four-digit year. An example is: 
--                 'Jan  1 02:03:04 2002'."
--    ::= { fileInfoEntry 6 }
--
--fileInfoDelete OBJECT-TYPE
--    SYNTAX       INTEGER
--                 {
--                  noDelete(1),
--                  delete(2)
--                 }
--    MAX-ACCESS   read-write
--    STATUS       current
--    DESCRIPTION "Write this object to delete(2) to delete a file, when
--                 read, this always return noDelete(1)."
--    ::= { fileInfoEntry 7 }

--
--dnsMgt
--

--dnsHostTable
--dnsDomainLookup OBJECT-TYPE
--    SYNTAX       EnabledStatus
--    MAX-ACCESS   read-write
--    STATUS       current
--    DESCRIPTION "To enable the IP Domain Naming System (DNS)-based host name-to-address translation."
--    ::= { dnsMgt 1 }
--    
--dnsDomainName OBJECT-TYPE
--    SYNTAX       DisplayString(SIZE(0..255))
--    MAX-ACCESS   read-write
--    STATUS       current
--    DESCRIPTION "To define a default domain name to complete 
--                unqualified host names (names without a dotted-decimal domain name)."
--    ::= { dnsMgt 2 }
--            
--dnsHostTable OBJECT-TYPE
--    SYNTAX       SEQUENCE OF DnsHostEntry
--    MAX-ACCESS   not-accessible
--    STATUS       current
--    DESCRIPTION "This table is used to define static host name-to-address mapping."               
--    ::= { dnsMgt 3 }
--    
--dnsHostEntry OBJECT-TYPE
--    SYNTAX       DnsHostEntry
--    MAX-ACCESS   not-accessible
--    STATUS       current
--    DESCRIPTION "A conceptual row for the dnsHostTable."
--    INDEX       { dnsHostName, dnsHostIndex }
--    ::= { dnsHostTable 1 }
--
--DnsHostEntry ::= SEQUENCE
--    {   
--        dnsHostName           DisplayString,
--        dnsHostIndex          Integer32,
--        dnsHostIp             IpAddress
--    }
--
--dnsHostName OBJECT-TYPE
--    SYNTAX       DisplayString(SIZE(1..255))
--    MAX-ACCESS   not-accessible
--    STATUS       current
--    DESCRIPTION "The DNS Host name."
--    ::= { dnsHostEntry 1 }
--
--dnsHostIndex OBJECT-TYPE
--    SYNTAX       Integer32(1..8)
--    MAX-ACCESS   not-accessible
--    STATUS       current
--    DESCRIPTION "The secondary index of this dnsHostTable, representing the 
--                 sequence of the dnsHostIp."
--    ::= { dnsHostEntry 2 }
--    
--dnsHostIp OBJECT-TYPE
--    SYNTAX       IpAddress
--    MAX-ACCESS   read-create
--    STATUS       current
--    DESCRIPTION "The DNS Host IP."
--    ::= { dnsHostEntry 3 }
--    
----dnsAliasTable
--dnsAliasTable OBJECT-TYPE
--    SYNTAX       SEQUENCE OF DnsAliasEntry
--    MAX-ACCESS   not-accessible
--    STATUS       current
--    DESCRIPTION "This table displays the alias of the host name."               
--    ::= { dnsMgt 4 }
--    
--dnsAliasEntry OBJECT-TYPE
--    SYNTAX       DnsAliasEntry
--    MAX-ACCESS   not-accessible
--    STATUS       current
--    DESCRIPTION "A conceptual row for the dnsAliasTable."
--    INDEX       { dnsAliasName, dnsAliasAlias }
--    ::= { dnsAliasTable 1 }
--
--DnsAliasEntry ::= SEQUENCE
--    {   
--        dnsAliasName           DisplayString,
--        dnsAliasAlias          DisplayString                
--    }
--
--dnsAliasName OBJECT-TYPE
--    SYNTAX       DisplayString(SIZE(1..255))
--    MAX-ACCESS   read-only
--    STATUS       current
--    DESCRIPTION "Host name."
--    ::= { dnsAliasEntry 1 }
--    
--dnsAliasAlias OBJECT-TYPE
--    SYNTAX       DisplayString(SIZE(1..255))
--    MAX-ACCESS   read-only
--    STATUS       current
--    DESCRIPTION "Alias."
--    ::= { dnsAliasEntry 2 }
--
----dnsDomainListEntry
--dnsDomainListTable OBJECT-TYPE
--    SYNTAX       SEQUENCE OF DnsDomainListEntry
--    MAX-ACCESS   not-accessible
--    STATUS       current
--    DESCRIPTION "This table defines a list of default domain names to complete unqualified host names."               
--    ::= { dnsMgt 5 }
--    
--dnsDomainListEntry OBJECT-TYPE
--    SYNTAX       DnsDomainListEntry
--    MAX-ACCESS   not-accessible
--    STATUS       current
--    DESCRIPTION "A conceptual row for the dnsDomainListTable."
--    INDEX       { dnsDomainListName }
--    ::= { dnsDomainListTable 1 }
--
--DnsDomainListEntry ::= SEQUENCE
--    {   
--        dnsDomainListName           DisplayString,
--        dnsDomainListStatus             ValidStatus        
--    }
--
--dnsDomainListName OBJECT-TYPE
--    SYNTAX       DisplayString(SIZE(1..255))
--    MAX-ACCESS   not-accessible
--    STATUS       current
--    DESCRIPTION "Domain name."
--    ::= { dnsDomainListEntry 1 }   
--
--dnsDomainListStatus OBJECT-TYPE
--    SYNTAX       ValidStatus
--    MAX-ACCESS   read-create
--    STATUS       current
--    DESCRIPTION "Setting this to valid(1) creates an entry.
--                 Setting this to invalid(2) destroys an entry."
--    ::= { dnsDomainListEntry 2 }
--
----dnsNameServerEntry
--dnsNameServerTable OBJECT-TYPE
--    SYNTAX       SEQUENCE OF DnsNameServerEntry
--    MAX-ACCESS   not-accessible
--    STATUS       current
--    DESCRIPTION "To specify the address of one or more 
--                 name servers to use for name and address resolution.
--                 This table has fixed size, will get 0.0.0.0 dnsNameServerIp 
--                 if this entry is not existed."               
--    ::= { dnsMgt 6 }
--    
--dnsNameServerEntry OBJECT-TYPE
--    SYNTAX       DnsNameServerEntry
--    MAX-ACCESS   not-accessible
--    STATUS       current
--    DESCRIPTION "A conceptual row for dnsNameServerTable."
--    INDEX       { dnsNameServerIndex }
--    ::= { dnsNameServerTable 1 }
--
--DnsNameServerEntry ::= SEQUENCE
--{ 
--    dnsNameServerIndex        Integer32,         
--    dnsNameServerIp           IpAddress    
--}
--
--dnsNameServerIndex  OBJECT-TYPE
--    SYNTAX       Integer32(1..6)
--    MAX-ACCESS   not-accessible
--    STATUS       current
--    DESCRIPTION "Index of this dnsNameServerTable,
--                 representing the sequence of the dnsNameServerIp."
--    ::= { dnsNameServerEntry 1 } 
--
--
--dnsNameServerIp OBJECT-TYPE
--    SYNTAX       IpAddress
--    MAX-ACCESS   read-write
--    STATUS       current
--    DESCRIPTION "IP address of name server."
--    ::= { dnsNameServerEntry 2 } 
--
----dnsCacheEntry
--dnsCacheTable OBJECT-TYPE
--    SYNTAX       SEQUENCE OF DnsCacheEntry
--    MAX-ACCESS   not-accessible
--    STATUS       current
--    DESCRIPTION "To display the RRs in DNS cache."               
--    ::= { dnsMgt 7 }
--    
--dnsCacheEntry OBJECT-TYPE
--    SYNTAX       DnsCacheEntry
--    MAX-ACCESS   not-accessible
--    STATUS       current
--    DESCRIPTION "A conceptual row for the dnsCacheTable."
--    INDEX       { dnsCacheIndex }
--    ::= { dnsCacheTable 1 }
--
--DnsCacheEntry ::= SEQUENCE
--    {   
--        dnsCacheIndex           Integer32,
--        dnsCacheFlag            Integer32,
--        dnsCacheType            INTEGER,
--        dnsCacheIp              IpAddress,
--        dnsCacheTtl             Integer32,      
--        dnsCacheDomain          DisplayString
--    }
--
--dnsCacheIndex OBJECT-TYPE
--    SYNTAX       Integer32
--    MAX-ACCESS   not-accessible
--    STATUS       current
--    DESCRIPTION "The entry sequence number."
--    ::= { dnsCacheEntry 1 }   
--
--dnsCacheFlag OBJECT-TYPE
--    SYNTAX       Integer32
--    MAX-ACCESS   read-only
--    STATUS       current
--    DESCRIPTION "Always get 4, means this record is unreliable."
--    ::= { dnsCacheEntry 2 }  
--    
--dnsCacheType OBJECT-TYPE
--    SYNTAX       INTEGER
--                 {
--                    address(1),
--                    cname(2)
--                 }
--    MAX-ACCESS   read-only
--    STATUS       current
--    DESCRIPTION "Cache Type: address(1); cname(2)."
--    ::= { dnsCacheEntry 3 }     
--
--dnsCacheIp OBJECT-TYPE
--    SYNTAX       IpAddress
--    MAX-ACCESS   read-only
--    STATUS       current
--    DESCRIPTION "The DNS cache IP."
--    ::= { dnsCacheEntry 4 }   
--
--dnsCacheTtl OBJECT-TYPE
--    SYNTAX       Integer32(0..876000)
--    MAX-ACCESS   read-only
--    STATUS       current
--    DESCRIPTION "The DNS cache TTL."
--    ::= { dnsCacheEntry 5 }   
--
--dnsCacheDomain OBJECT-TYPE
--    SYNTAX       DisplayString(SIZE(1..255))
--    MAX-ACCESS   read-only
--    STATUS       current
--    DESCRIPTION "The DNS cache domain."
--    ::= { dnsCacheEntry 6 }
--
----
----mvrMgt
----
--    
--mvrStatus OBJECT-TYPE
--        SYNTAX      EnabledStatus
--        MAX-ACCESS  read-write
--        STATUS      current
--        DESCRIPTION "Parameter to enable or disable MVR(Multicast VLAN
--                     Registration) on the device. NOTE: IGMP Snooping 
--                     must be enabled first before enabling MVR and MVR 
--                     will be disabled when IGMP Snooping is disabled."
--        ::= { mvrMgt 1 }
--
--mvrVlanId OBJECT-TYPE
--        SYNTAX      Integer32
--        MAX-ACCESS  read-write
--        STATUS      current
--        DESCRIPTION "To set VLAN for MVR.The VLAN identified by a particular
--                     value of this index is the same VLAN as identified by the
--                     same value of dot1qVlanIndex in the Q-BRIDGE-MIB."
--        ::= { mvrMgt 2 }
--
--mvrMaxGroups  OBJECT-TYPE
--        SYNTAX      Integer32
--        MAX-ACCESS  read-only
--        STATUS      current
--        DESCRIPTION "The maximum number of MVR groups."
--        ::= { mvrMgt 3 }
--
--mvrCurrentGroups   OBJECT-TYPE
--        SYNTAX      Integer32
--        MAX-ACCESS  read-only
--        STATUS      current
--        DESCRIPTION "The current number of MVR groups."
--        ::= { mvrMgt 4}
--        
--mvrGroupsCtl      OBJECT IDENTIFIER   ::= { mvrMgt 5 }
--
--mvrGroupsCtlId   OBJECT-TYPE
--        SYNTAX      IpAddress
--        MAX-ACCESS  read-write
--        STATUS      current
--        DESCRIPTION "The start of a contiguous range of MVR group
--                     addresses."
--        ::= { mvrGroupsCtl 1 }
--
--mvrGroupsCtlCount   OBJECT-TYPE
--        SYNTAX      Integer32
--        MAX-ACCESS  read-write
--        STATUS      current
--        DESCRIPTION "The range count for configuring MVR group addresses."
--        ::= { mvrGroupsCtl 2 }
--
--mvrGroupsCtlAction   OBJECT-TYPE
--        SYNTAX      INTEGER
--        {
--            noAction(0),
--            create(1),
--            destory(2)
--        }
--        MAX-ACCESS  read-write
--        STATUS      current
--        DESCRIPTION "Sets the configure action for a contiguous range of MVR group 
--                     addresses. The start addresses is the current value of 
--                     mvrGroupsCtlId and the range count is the current value of 
--                     mvrGroupsCtlCount. Set this object to create(2) to 
--                     create MVR group addresses. Set this object 
--                     to destory(3) to delete MVR group addresses. When 
--                     the action is complete, this object becomes noAction(1)."
--        ::= { mvrGroupsCtl 3 }
--
--mvrGroupTable OBJECT-TYPE
--       SYNTAX      SEQUENCE OF MvrGroupEntry
--       MAX-ACCESS  not-accessible
--       STATUS      current
--       DESCRIPTION "The table for configuring the MVR group."
--       ::= { mvrMgt 6 }
--
--mvrGroupEntry OBJECT-TYPE
--       SYNTAX      MvrGroupEntry
--       MAX-ACCESS  not-accessible
--       STATUS      current
--       DESCRIPTION "The entry for configuring the MVR group."
--       INDEX  {mvrGroupId}
--       ::= { mvrGroupTable 1 }
--
--MvrGroupEntry ::= SEQUENCE
--{
--    mvrGroupId IpAddress,
--    mvrGroutActive INTEGER,
--    mvrGroupStatus INTEGER
--}
--
--mvrGroupId OBJECT-TYPE
--        SYNTAX      IpAddress
--        MAX-ACCESS  not-accessible
--        STATUS      current
--        DESCRIPTION "The multicast address of the MVR group."
--        ::= { mvrGroupEntry 1 }
--
--mvrGroutActive   OBJECT-TYPE
--        SYNTAX      INTEGER
--        {
--            active(1),
--            inactive(2)
--        }
--        MAX-ACCESS  read-only
--        STATUS      current
--        DESCRIPTION "To indicate if the group has a member or not. If there are no
--                     members, the status is inactive(2); otherwise the status
--                     is active(1)."
--        ::= { mvrGroupEntry 2 }
--
--mvrGroupStatus   OBJECT-TYPE
--        SYNTAX      INTEGER
--        {
--            valid(1),
--            invalid(2)
--        }
--        MAX-ACCESS  read-write
--        STATUS      current
--        DESCRIPTION "Setting this to valid(1) creates an entry. Setting this
--                     to invalid(2) destroys an entry."
--        ::= { mvrGroupEntry 3 }
--
--mvrGroupStaticTable   OBJECT-TYPE
--        SYNTAX      SEQUENCE OF MvrGroupStaticEntry
--        MAX-ACCESS  not-accessible
--        STATUS      current
--        DESCRIPTION "The table for configuring the static members of the
--                     MVR group."
--        ::= { mvrMgt 7 }
--
--mvrGroupStaticEntry OBJECT-TYPE
--       SYNTAX      MvrGroupStaticEntry
--       MAX-ACCESS  not-accessible
--       STATUS      current
--       DESCRIPTION "The entry for configuring the static members of the
--                    MVR group."
--       INDEX  {mvrGroupStaticAddress}
--       ::= { mvrGroupStaticTable 1 }
--
--MvrGroupStaticEntry ::= SEQUENCE
--{
--    mvrGroupStaticAddress   IpAddress,
--    mvrGroupStaticPorts     PortList,
--    mvrGroupStaticStatus    INTEGER
--
--}
--
--mvrGroupStaticAddress  OBJECT-TYPE
--        SYNTAX      IpAddress
--        MAX-ACCESS  not-accessible
--        STATUS      current
--        DESCRIPTION "The multicast address of the MVR group."
--        ::= { mvrGroupStaticEntry 1 }
--
--mvrGroupStaticPorts  OBJECT-TYPE
--        SYNTAX      PortList
--        MAX-ACCESS  read-write
--        STATUS      current
--        DESCRIPTION "The set of ports configured by management in this entry.
--                     Ports entered in this list will be the static members
--                     of this MVR group."
--        ::= { mvrGroupStaticEntry 2 }
--
--mvrGroupStaticStatus  OBJECT-TYPE
--        SYNTAX      INTEGER
--        {
--            valid(1),
--            invalid(2)
--        }
--        MAX-ACCESS  read-write
--        STATUS      current
--        DESCRIPTION "Setting this to valid(1) creates an entry. Setting this
--                     to invalid(2) destroys an entry."
--        ::= { mvrGroupStaticEntry 3 }
--
--mvrGroupCurrentTable   OBJECT-TYPE
--        SYNTAX      SEQUENCE OF MvrGroupCurrentEntry
--        MAX-ACCESS  not-accessible
--        STATUS      current
--        DESCRIPTION "The table for the current members of the MVR group."
--        ::= { mvrMgt 8 }
--
--mvrGroupCurrentEntry OBJECT-TYPE
--       SYNTAX      MvrGroupCurrentEntry
--       MAX-ACCESS  not-accessible
--       STATUS      current
--       DESCRIPTION "The entry for the current members of the MVR group."
--       INDEX  {mvrGroupCurrentAddress}
--       ::= { mvrGroupCurrentTable 1 }
--
--MvrGroupCurrentEntry ::= SEQUENCE
--{
--    mvrGroupCurrentAddress  IpAddress,
--    mvrGroupCurrentPorts    PortList
--}
--
--mvrGroupCurrentAddress   OBJECT-TYPE
--        SYNTAX      IpAddress
--        MAX-ACCESS  not-accessible
--        STATUS      current
--        DESCRIPTION "The multicast address of the MVR group."
--        ::= { mvrGroupCurrentEntry 1 }
--
--mvrGroupCurrentPorts   OBJECT-TYPE
--        SYNTAX      PortList
--        MAX-ACCESS  read-only
--        STATUS      current
--        DESCRIPTION "The complete set of ports currently associated with this
--                     MVR group."
--        ::= { mvrGroupCurrentEntry 2 }
--
--mvrPortTable   OBJECT-TYPE
--        SYNTAX      SEQUENCE OF MvrPortEntry
--        MAX-ACCESS  not-accessible
--        STATUS      current
--        DESCRIPTION "The table for configuring the MVR port."
--        ::= { mvrMgt 9 }
--
--mvrPortEntry OBJECT-TYPE
--       SYNTAX      MvrPortEntry
--       MAX-ACCESS  not-accessible
--       STATUS      current
--       DESCRIPTION "The entry for configuring the MVR port."
--       INDEX  {mvrIfIndex}
--       ::= { mvrPortTable 1 }
--
--MvrPortEntry ::= SEQUENCE
--{
--    mvrIfIndex  InterfaceIndex,
--    mvrPortType INTEGER,
--    mvrPortImmediateLeave   EnabledStatus,
--    mvrPortActive   INTEGER
--
--}
--
--mvrIfIndex   OBJECT-TYPE
--        SYNTAX      InterfaceIndex
--        MAX-ACCESS  not-accessible
--        STATUS      current
--        DESCRIPTION "The port interface of the portTable. The interface
--                     identified by a particular value of this index is the
--                     same interface as identified by the same value of ifIndex
--                     in the IF-MIB."
--        ::= { mvrPortEntry 1 }
--
--mvrPortType   OBJECT-TYPE
--        SYNTAX      INTEGER
--        {
--            none(0),
--            source(1),
--            receiver(2)
--        }
--        MAX-ACCESS  read-write
--        STATUS      current
--        DESCRIPTION "For configuring the MVR port type. To disable the MVR
--                     port type, use the none(0)."
--        ::= { mvrPortEntry 2 }
--
--mvrPortImmediateLeave   OBJECT-TYPE
--        SYNTAX      EnabledStatus
--        MAX-ACCESS  read-write
--        STATUS      current
--        DESCRIPTION "To enable immediate leave on MVR port."
--        ::= { mvrPortEntry 3 }
--
--mvrPortActive   OBJECT-TYPE
--        SYNTAX      INTEGER
--        {
--            active(1),
--            inactive(2)
--        }
--        MAX-ACCESS  read-only
--        STATUS      current
--        DESCRIPTION "To indicate if the port is associated with the MVR group.
--                     If the port is the MVR receiver port or the MVR source 
--                     port in MVR vlan, the status is active(1); otherwise 
--                     the status is inactive(2)."
--        ::= { mvrPortEntry 4 }
--        
--mvrRunningStatus OBJECT-TYPE
--        SYNTAX  TruthValue
--        MAX-ACCESS  read-only
--        STATUS      current
--        DESCRIPTION "Describes the running status of MVR (Multicast VLAN Registration)
--                     to the switch. A value of true(1) indicates that all necessary 
--                     conditions in the MVR environment are satisfied. A value of false(2)
--                     indicates that some necessary conditions in the MVR environment are
--                     not satisfied."
--        ::= { mvrMgt 10 }
--        
--	                               
----
---- dhcpSnoopMgt
----
--
---- Management of DHCP snooping and IP souce guard.
--
--dhcpSnoopGlobal         OBJECT IDENTIFIER ::= { dhcpSnoopMgt 1 }
--dhcpSnoopVlan           OBJECT IDENTIFIER ::= { dhcpSnoopMgt 2 }
--dhcpSnoopInterface      OBJECT IDENTIFIER ::= { dhcpSnoopMgt 3 }
--dhcpSnoopBindings       OBJECT IDENTIFIER ::= { dhcpSnoopMgt 4 }
--dhcpSnoopStatistics     OBJECT IDENTIFIER ::= { dhcpSnoopMgt 5 }
--
--dhcpSnoopEnable  OBJECT-TYPE
--        SYNTAX     EnabledStatus
--        MAX-ACCESS  read-write
--        STATUS      current
--        DESCRIPTION "This object indicates whether the DHCP Snooping feature is
--                     enabled."
--        ::= { dhcpSnoopGlobal 1 }
--
--dhcpSnoopVerifyMacAddressEnable     OBJECT-TYPE
--        SYNTAX     EnabledStatus
--        MAX-ACCESS  read-write
--        STATUS      current
--        DESCRIPTION "This object indicates whether DHCP Snooping Mac address
--                     verification is enabled."
--        ::= { dhcpSnoopGlobal 2 }
--
--dhcpSnoopInformationOptionEnable  OBJECT-TYPE
--
--        SYNTAX     EnabledStatus
--        MAX-ACCESS  read-write
--        STATUS      current
--        DESCRIPTION "This object indicates whether the DHCP snooping information option(option 82) feature is
--                     enabled."
--        ::= { dhcpSnoopGlobal 3 }
--
--dhcpSnoopInformationOptionPolicy     OBJECT-TYPE
--        SYNTAX     INTEGER
--                    {
--                        drop(1),
--                        keep(2),
--                        replace(3)
--                    }
--        MAX-ACCESS  read-write
--        STATUS      current
--        DESCRIPTION "This object indicates which reforwarding policy shall be used for DHCP
--                     snooping information option(option 82). A value of drop(1) means to drop
--                     the DHCP request packet which has the information option(option 82). 
--                     A value of keep(2) means to keep the existing information option(option 82)
--                     of the DHCP request packet. A value of replace(3), which is the default value,
--                     means to replace the existing information option(option 82) of the DHCP 
--                     request packet."
--        ::= { dhcpSnoopGlobal 4 }        
--
----
--dhcpSnoopVlanConfigTable    OBJECT-TYPE
--        SYNTAX      SEQUENCE OF DhcpSnoopVlanConfigEntry
--        MAX-ACCESS  not-accessible
--        STATUS      current
--        DESCRIPTION "A table contains DHCP Snooping configurations of existing VLANs."
--        ::= { dhcpSnoopVlan 1 }
--
--dhcpSnoopVlanConfigEntry    OBJECT-TYPE
--        SYNTAX      DhcpSnoopVlanConfigEntry
--        MAX-ACCESS  not-accessible
--        STATUS      current
--        DESCRIPTION "An instance contains the configuration to enable
--                     or disable DHCP Snooping at each existing VLAN."
--        INDEX       { dhcpSnoopVlanIndex }
--        ::= { dhcpSnoopVlanConfigTable 1 }
--
--DhcpSnoopVlanConfigEntry  ::= SEQUENCE
--{
--        dhcpSnoopVlanIndex      VlanIndex,
--        dhcpSnoopVlanEnable     EnabledStatus
--}
--
--dhcpSnoopVlanIndex      OBJECT-TYPE
--        SYNTAX      VlanIndex
--        MAX-ACCESS  not-accessible
--        STATUS      current
--        DESCRIPTION "This object indicates the VLAN ID on which DHCP Snooping
--                     feature is configured."
--        ::= { dhcpSnoopVlanConfigEntry 1 }
--
--dhcpSnoopVlanEnable     OBJECT-TYPE
--        SYNTAX     EnabledStatus
--        MAX-ACCESS  read-write
--        STATUS      current
--        DESCRIPTION "This object indicates whether DHCP Snooping is enabled in
--                     this VLAN."
--        ::= { dhcpSnoopVlanConfigEntry 2 }
--
----
--dhcpSnoopPortConfigTable    OBJECT-TYPE
--        SYNTAX      SEQUENCE OF DhcpSnoopPortConfigEntry
--        MAX-ACCESS  not-accessible
--        STATUS      current
--        DESCRIPTION "A table provides the mechanism to configure the trust
--                     state of each port or trunk for DHCP Snooping purpose."
--        ::= { dhcpSnoopInterface 1 }
--
--dhcpSnoopPortConfigEntry    OBJECT-TYPE
--        SYNTAX      DhcpSnoopPortConfigEntry
--        MAX-ACCESS  not-accessible
--        STATUS      current
--        DESCRIPTION "An instance contains the configuration to enable or disable
--                     trust state of each port or trunk for DHCP Snooping purpose."
--        INDEX       { dhcpSnoopPortIfIndex }
--        ::= { dhcpSnoopPortConfigTable 1 }
--
--DhcpSnoopPortConfigEntry    ::= SEQUENCE
--{
--        dhcpSnoopPortIfIndex        InterfaceIndex,
--        dhcpSnoopPortTrustEnable    EnabledStatus
--}
--
--dhcpSnoopPortIfIndex        OBJECT-TYPE
--        SYNTAX      InterfaceIndex
--        MAX-ACCESS  not-accessible
--        STATUS      current
--        DESCRIPTION "The ifIndex value of the port or trunk."
--        ::= { dhcpSnoopPortConfigEntry 1 }
--
--dhcpSnoopPortTrustEnable    OBJECT-TYPE
--        SYNTAX     EnabledStatus
--        MAX-ACCESS  read-write
--        STATUS      current
--        DESCRIPTION "This object indicates whether the port or trunk is trusted
--                     for DHCP Snooping purpose."
--        ::= { dhcpSnoopPortConfigEntry 2 }
----
--dhcpSnoopBindingsTable      OBJECT-TYPE
--        SYNTAX      SEQUENCE OF DhcpSnoopBindingsEntry
--        MAX-ACCESS  not-accessible
--        STATUS      current
--        DESCRIPTION "A table contains the DHCP bindings information learnt by
--                     the device."
--        ::= { dhcpSnoopBindings 1 }
--
--dhcpSnoopBindingsEntry      OBJECT-TYPE
--        SYNTAX      DhcpSnoopBindingsEntry
--        MAX-ACCESS  not-accessible
--        STATUS      current
--        DESCRIPTION "An instance contains the Mac address, IP address type,
--                     IP address, VLAN number, interface number, leased time and
--                     status."
--        INDEX       { dhcpSnoopBindingsVlanIndex, dhcpSnoopBindingsMacAddress }
--        ::= { dhcpSnoopBindingsTable 1 }
--
--DhcpSnoopBindingsEntry      ::= SEQUENCE
--{
--        dhcpSnoopBindingsVlanIndex      VlanIndex,
--        dhcpSnoopBindingsMacAddress     MacAddress,
--        dhcpSnoopBindingsAddrType       InetAddressType,
--        dhcpSnoopBindingsEntryType      INTEGER,
--        dhcpSnoopBindingsIpAddress      IpAddress,
--        dhcpSnoopBindingsPortIfIndex    InterfaceIndex,
--        dhcpSnoopBindingsLeaseTime      Unsigned32
--}
--
--dhcpSnoopBindingsVlanIndex      OBJECT-TYPE
--        SYNTAX      VlanIndex
--        MAX-ACCESS  not-accessible
--        STATUS      current
--        DESCRIPTION "This object indicates the VLAN which a DHCP client host
--                     belongs to."
--        ::= { dhcpSnoopBindingsEntry 1 }
--
--dhcpSnoopBindingsMacAddress     OBJECT-TYPE
--        SYNTAX      MacAddress
--        MAX-ACCESS  not-accessible
--        STATUS      current
--        DESCRIPTION "This object indicates the MAC address of a DHCP client
--                     host."
--        ::= { dhcpSnoopBindingsEntry 2 }
--
--dhcpSnoopBindingsAddrType       OBJECT-TYPE
--        SYNTAX      InetAddressType
--        MAX-ACCESS  read-only
--        STATUS      current
--        DESCRIPTION "This object indicates the type of IP address denoted in
--                     dhcpSnoopBindingsIpAddress type."
--        ::= { dhcpSnoopBindingsEntry 3 }
--
--dhcpSnoopBindingsEntryType      OBJECT-TYPE
--        SYNTAX      INTEGER { dynamic(1), static(2) }
--        MAX-ACCESS  read-only
--        STATUS      current
--        DESCRIPTION "This object indicates that this binding is obtained from
--                     dynamically learning or is a static configuraion."
--        ::= { dhcpSnoopBindingsEntry 4 }
--
--dhcpSnoopBindingsIpAddress      OBJECT-TYPE
--        SYNTAX      IpAddress
--        MAX-ACCESS  read-only
--        STATUS      current
--        DESCRIPTION "This object indicates the allocated IP address of
--                     a DHCP client host."
--        ::= { dhcpSnoopBindingsEntry 5 }
--
--dhcpSnoopBindingsPortIfIndex    OBJECT-TYPE
--        SYNTAX      InterfaceIndex
--        MAX-ACCESS  read-only
--        STATUS      current
--        DESCRIPTION "This object indicates the port or trunk where a DHCP client
--                     host connects to."
--        ::= { dhcpSnoopBindingsEntry 6 }
--
--dhcpSnoopBindingsLeaseTime      OBJECT-TYPE
--        SYNTAX      Unsigned32
--        MAX-ACCESS  read-only
--        STATUS      current
--        DESCRIPTION "This object indicates the leased time of this DHCP
--                     bindings."
--        ::= { dhcpSnoopBindingsEntry 7 }
--
----
--
--dhcpSnoopTotalForwardedPkts     OBJECT-TYPE
--        SYNTAX      Counter32
--        MAX-ACCESS  read-only
--        STATUS      current
--        DESCRIPTION "Indicates the total number of packets subjected to
--                     DHCP Snooping is forwarded."
--        ::= { dhcpSnoopStatistics 1 }
--
--dhcpSnoopUntrustedPortDroppedPkts   OBJECT-TYPE
--        SYNTAX      Counter32
--        MAX-ACCESS  read-only
--        STATUS      current
--        DESCRIPTION "Indicates the number of packets subjected to DHCP Snooping
--                     is dropped because they come from untrusted interface."
--        ::= { dhcpSnoopStatistics 3 }
--
--
----
---- clusterMgt
----
--
--clusterEnable  OBJECT-TYPE
--    SYNTAX     EnabledStatus
--    MAX-ACCESS read-write
--    STATUS     current
--    DESCRIPTION
--        "Enables or disables clustering on the device."
--    ::= { clusterMgt 1 }
--
--clusterCommanderEnable  OBJECT-TYPE
--    SYNTAX     EnabledStatus
--    MAX-ACCESS read-write
--    STATUS     current
--    DESCRIPTION
--        "Enables or disables the device as commander in a cluster."
--    ::= { clusterMgt 2 }
--
--clusterIpPool  OBJECT-TYPE
--    SYNTAX     IpAddress
--    MAX-ACCESS read-write
--    STATUS     current
--    DESCRIPTION
--        "The start internal IP address of a cluster pool."
--    ::= { clusterMgt 4 }
--
--clusterClearCandidateTable  OBJECT-TYPE
--    SYNTAX     INTEGER
--    					 {
--    					     noClear(1),
--    					     clear(2)
--    					 }
--    MAX-ACCESS read-write
--    STATUS     current
--    DESCRIPTION
--        "Setting this object to clear(2) starts to clear the candidate table."
--    ::= { clusterMgt 5 }
--
--clusterRole  OBJECT-TYPE
--    SYNTAX     INTEGER
--               {
--                   commander(1),
--                   candidate(2),
--                   activeMember(3),
--                   disabled(5)
--               }
--    MAX-ACCESS read-only
--    STATUS     current
--    DESCRIPTION
--        "The current role of the device in a cluster.
--             commander(1)   : The switch is the controlling device in a
--                              cluster.
--             candidate(2)   : The switch has been discovered by the commander,
--                              but it has not been manually configured
--                              for access from the commander.
--             activeMember(3): The switch has been manually configured for access
--                              from the commander and it is active
--                              in the cluster.
--             disabled(5)     : The switch has clustering disabled."
--    ::= { clusterMgt 6 }
--
--clusterMemberCount  OBJECT-TYPE
--    SYNTAX     Counter32
--    MAX-ACCESS read-only
--    STATUS     current
--    DESCRIPTION
--        "The total number of members in a cluster."
--    ::= { clusterMgt 7 }
--
--clusterCandidateCount  OBJECT-TYPE
--    SYNTAX     Counter32
--    MAX-ACCESS read-only
--    STATUS     current
--    DESCRIPTION
--        "The total number of candidates in a cluster."
--    ::= { clusterMgt 8 }
--
--clusterCandidateTable OBJECT-TYPE
--    SYNTAX     SEQUENCE OF ClusterCandidateEntry
--    MAX-ACCESS not-accessible
--    STATUS     current
--    DESCRIPTION
--        "A table listing cluster candidates."
--    ::= { clusterMgt 9 }
--
--clusterCandidateEntry OBJECT-TYPE
--    SYNTAX     ClusterCandidateEntry
--    MAX-ACCESS not-accessible
--    STATUS     current
--    DESCRIPTION
--        "A conceptual row containing the information of the candidate."
--    INDEX { clusterCandidateMacAddr}
--    ::= { clusterCandidateTable 1 }
--
--ClusterCandidateEntry ::=
--    SEQUENCE {
--                clusterCandidateMacAddr  MacAddress,
--                clusterCandidateDesc     DisplayString,
--                clusterCandidateRole     INTEGER
--    }
--
--clusterCandidateMacAddr OBJECT-TYPE
--       SYNTAX     MacAddress
--       MAX-ACCESS not-accessible
--       STATUS     current
--       DESCRIPTION
--           "The MAC address of the candidate."
--       ::= {clusterCandidateEntry  1 }
--
--clusterCandidateDesc OBJECT-TYPE
--       SYNTAX     DisplayString (SIZE (0..42))
--       MAX-ACCESS read-only
--       STATUS     current
--       DESCRIPTION
--           "The description of the candidate."
--       ::= {clusterCandidateEntry  3 }
--
--clusterCandidateRole OBJECT-TYPE
--       SYNTAX     INTEGER
--                  {
--                      candidate(2),
--                      activeMember(3),
--                      inactiveMember(4)
--                  }
--       MAX-ACCESS read-only
--       STATUS     current
--       DESCRIPTION
--           "The role of the candidate.
--                candidate(2)     : The switch is discovered by the commander,
--                                   but it has not been manually configured for
--                                   access from the commander.
--                activeMember(3)  : The switch is manually configured for access
--                                   from the commander and it is active in the
--                                   cluster.
--                inactiveMember(4): The switch is manually configured for access
--                                   from the commander, but it is inactive in
--                                   the cluster."
--       ::= {clusterCandidateEntry  4 }
--
--clusterMemberTable OBJECT-TYPE
--    SYNTAX     SEQUENCE OF ClusterMemberEntry
--    MAX-ACCESS not-accessible
--    STATUS     current
--    DESCRIPTION
--        "A table listing clustering members."
--    ::= { clusterMgt 10 }
--
--clusterMemberEntry OBJECT-TYPE
--    SYNTAX     ClusterMemberEntry
--    MAX-ACCESS not-accessible
--    STATUS     current
--    DESCRIPTION
--          "A conceptual row containing the information of the member."
--    INDEX { clusterMemberId}
--    ::= { clusterMemberTable 1 }
--
--ClusterMemberEntry ::=
--    SEQUENCE {
--                clusterMemberId       Unsigned32,
--                clusterMemberMacAddr  MacAddress,
--                clusterMemberDesc     DisplayString,
--                clusterMemberActive   INTEGER
--             }
--
--clusterMemberId OBJECT-TYPE
--       SYNTAX     Unsigned32
--       MAX-ACCESS not-accessible
--       STATUS     current
--       DESCRIPTION
--           "The ID of the member."
--       ::= {clusterMemberEntry  1 }
--
--clusterMemberMacAddr OBJECT-TYPE
--       SYNTAX     MacAddress
--       MAX-ACCESS read-only
--       STATUS     current
--       DESCRIPTION
--           "The MAC address of the member."
--       ::= {clusterMemberEntry  2 }
--
--clusterMemberDesc OBJECT-TYPE
--       SYNTAX     DisplayString(SIZE (0..42))
--       MAX-ACCESS read-only
--       STATUS     current
--       DESCRIPTION
--           "The description of the member."
--       ::= {clusterMemberEntry  3 }
--
--clusterMemberActive OBJECT-TYPE
--       SYNTAX     INTEGER
--                  {
--                      activeMember(3),
--                      inactiveMember(4)
--                  }
--       MAX-ACCESS read-only
--       STATUS     current
--       DESCRIPTION
--           "The active status of the member.
--                activeMember(3)  : The switch is manually configured for access
--                                   from the commander and it is active in the
--                                   cluster.
--                inactiveMember(4): The switch is manually configured for access
--                                   from the commander, but it is inactive in
--                                   the cluster."
--       ::= {clusterMemberEntry  4 }
--
--clusterMemberAddCtl  OBJECT IDENTIFIER ::= { clusterMgt 11 }
--
--clusterMemberAddCtlMacAddr  OBJECT-TYPE
--    SYNTAX     MacAddress
--    MAX-ACCESS read-write
--    STATUS     current
--    DESCRIPTION
--        "The MAC address of the device associated with clusterMemberAddCtlAction."
--    ::= { clusterMemberAddCtl 1 }
--
--clusterMemberAddCtlId  OBJECT-TYPE
--    SYNTAX     Unsigned32
--    MAX-ACCESS read-write
--    STATUS     current
--    DESCRIPTION
--        "The member id associated with clusterMemberAddCtlAction."
--    ::= { clusterMemberAddCtl 2 }
--
--clusterMemberAddCtlAction  OBJECT-TYPE
--    SYNTAX     INTEGER
--               {
--                   noAdd(1),
--                   add(2)
--               }
--    MAX-ACCESS read-write
--    STATUS     current
--    DESCRIPTION
--        "Adds the device to members that can be accessed from the commander.
--         The MAC of the device is the current value of
--         clusterMemberAddCtlMacAddr and the assigned member ID is the current
--         value of clusterMemberAddCtlId. Set this object to add(2) to begin
--         adding the member."
--    ::= { clusterMemberAddCtl 5 }
--
--clusterMemberRemoveCtl  OBJECT IDENTIFIER ::= { clusterMgt 12 }
--
--clusterMemberRemoveCtlId  OBJECT-TYPE
--    SYNTAX     Unsigned32
--    MAX-ACCESS read-write
--    STATUS     current
--    DESCRIPTION
--        "The member ID associated with clusterMemberRemoveCtlAction."
--    ::= { clusterMemberRemoveCtl 1 }
--
--clusterMemberRemoveCtlAction  OBJECT-TYPE
--    SYNTAX     INTEGER
--               {
--                   noRemove(1),
--                   remove(2)
--               }
--    MAX-ACCESS read-write
--    STATUS     current
--    DESCRIPTION
--        "Removes the device from members that can be accessed from the commander.
--         The member ID is the current value of clusterMemberRemoveCtlId.
--         Set this object to remove(2) to begin removing the member."
--    ::= { clusterMemberRemoveCtl 2 }
--    
--    
----
---- ipSrcGuardMgt
----
--
--ipSrcGuardConfigTable       OBJECT-TYPE
--        SYNTAX      SEQUENCE OF IpSrcGuardConfigEntry
--        MAX-ACCESS  not-accessible
--        STATUS      current
--        DESCRIPTION "A table contains the configurations to enable or disable
--                     IP Source Guard at each port or trunk."
--        ::= { ipSrcGuardMgt 1 }
--
--ipSrcGuardConfigEntry       OBJECT-TYPE
--        SYNTAX      IpSrcGuardConfigEntry
--        MAX-ACCESS  not-accessible
--        STATUS      current
--        DESCRIPTION "An instance contains the configuration to enable
--                     or disable IP Source Guard at each port or trunk."
--        INDEX       { ipSrcGuardPortIfIndex }
--        ::= { ipSrcGuardConfigTable 1 }
--
--IpSrcGuardConfigEntry       ::= SEQUENCE
--{
--        ipSrcGuardPortIfIndex       InterfaceIndex,
--        ipSrcGuardMode              INTEGER
--}
--
--ipSrcGuardPortIfIndex       OBJECT-TYPE
--        SYNTAX      InterfaceIndex
--        MAX-ACCESS  not-accessible
--        STATUS      current
--        DESCRIPTION "This object idents the port or trunk which is capable of
--                     IP Source Guard feature."
--        ::= { ipSrcGuardConfigEntry 1 }
--
--ipSrcGuardMode      OBJECT-TYPE
--        SYNTAX      INTEGER { diabled(0), srcIp(1), srcIpMac(2) }
--        MAX-ACCESS  read-write
--        STATUS      current
--        DESCRIPTION "This object indicates whether Ip Source Guard is enabled
--                     at this interface. If the value equals 0, it means Ip Source
--                     Guard  is disabled. If the value equals 1, it means Ip Source
--                     Guard is enabled, and packets are filtered by checking source ip.
--                     If the value equals 2, it means Ip Source Guard is enabled
--                     and packets are filtered by checking source ip and source mac."
--        ::= { ipSrcGuardConfigEntry 2 }
----
--ipSrcGuardAddrTable     OBJECT-TYPE
--        SYNTAX      SEQUENCE OF IpSrcGuardAddrEntry
--        MAX-ACCESS  not-accessible
--        STATUS      current
--        DESCRIPTION "A table contains the IP Source Guard bindings information
--                     learnt by the device."
--        ::= { ipSrcGuardMgt 2 }
--
--ipSrcGuardAddrEntry     OBJECT-TYPE
--        SYNTAX      IpSrcGuardAddrEntry
--        MAX-ACCESS  not-accessible
--        STATUS      current
--        DESCRIPTION "An instance contains the Mac address, IP address type,
--                     IP address, VLAN number, interface number, leased time and
--                     status."
--        INDEX   { ipSrcGuardBindingsVlanIndex, ipSrcGuardBindingsMacAddress }
--        ::= { ipSrcGuardAddrTable 1 }
--
--IpSrcGuardAddrEntry     ::= SEQUENCE
--{
--        ipSrcGuardBindingsVlanIndex         VlanIndex,
--        ipSrcGuardBindingsMacAddress        MacAddress,
--        ipSrcGuardBindingsAddrType          InetAddressType,
--        ipSrcGuardBindingsEntryType         INTEGER,
--        ipSrcGuardBindingsIpAddress         IpAddress,
--        ipSrcGuardBindingsPortIfIndex       InterfaceIndex,
--        ipSrcGuardBindingsLeaseTime         Unsigned32,
--        ipSrcGuardBindingsStatus         RowStatus
--}
--ipSrcGuardBindingsVlanIndex      OBJECT-TYPE
--        SYNTAX      VlanIndex
--        MAX-ACCESS  not-accessible
--        STATUS      current
--        DESCRIPTION "This object indicates the VLAN which a DHCP client host
--                     belongs to."
--        ::= { ipSrcGuardAddrEntry 1 }
--
--ipSrcGuardBindingsMacAddress     OBJECT-TYPE
--        SYNTAX      MacAddress
--        MAX-ACCESS  not-accessible
--        STATUS      current
--        DESCRIPTION "This object indicates the MAC address of a DHCP client
--                     host."
--        ::= { ipSrcGuardAddrEntry 2 }
--        
--ipSrcGuardBindingsAddrType       OBJECT-TYPE
--        SYNTAX      InetAddressType
--        MAX-ACCESS  read-create
--        STATUS      current
--        DESCRIPTION "This object indicates the type of IP address denoted in 
--                     ipSrcGuardBindingsIpAddress type."
--        ::= { ipSrcGuardAddrEntry 3 }
--        
--ipSrcGuardBindingsEntryType     OBJECT-TYPE
--        SYNTAX      INTEGER { dynamic(1), static(3) }
--        MAX-ACCESS  read-only
--        STATUS      current
--        DESCRIPTION "This object indicates that this binding is obtained from 
--                     dynamically learning or is a static configuraion."
--        ::= { ipSrcGuardAddrEntry 4 }
--
--ipSrcGuardBindingsIpAddress     OBJECT-TYPE
--        SYNTAX      IpAddress
--        MAX-ACCESS  read-create
--        STATUS      current
--        DESCRIPTION "This object indicates the allocated IP address of
--                     a DHCP client host."
--        ::= { ipSrcGuardAddrEntry 5 }
--        
--ipSrcGuardBindingsPortIfIndex   OBJECT-TYPE
--        SYNTAX      InterfaceIndex
--        MAX-ACCESS  read-create
--        STATUS      current
--        DESCRIPTION "This object indicates the port or trunk where a DHCP client
--                     host connects to."
--        ::= { ipSrcGuardAddrEntry 6 }
--        
--ipSrcGuardBindingsLeaseTime     OBJECT-TYPE
--        SYNTAX      Unsigned32
--        MAX-ACCESS  read-only
--        STATUS      current
--        DESCRIPTION "This object indicates the leased time of this DHCP
--                     bindings."
--        ::= { ipSrcGuardAddrEntry 7 }
--        
--ipSrcGuardBindingsStatus     OBJECT-TYPE
--        SYNTAX      RowStatus
--        MAX-ACCESS  read-create
--        STATUS      current
--        DESCRIPTION "The status of this conceptual row entry. This object issued to 
--                     manage the creation and deletion of conceptual rows.  
--                     The status column has six defined values:  - 'active', which 
--                     indicates that the conceptual row is available for use by the 
--                     managed device;  - 'notInService', which indicates that the 
--                     conceptual row exists in the agent, but is unavailable for use 
--                     by the managed device."
--        ::= { ipSrcGuardAddrEntry 8 }
    
    
--
-- trap definitions
--

    ES4528VTraps  OBJECT IDENTIFIER ::= { ES4528VNotifications 1 }
    ES4528VTrapsPrefix OBJECT IDENTIFIER ::= { ES4528VTraps 0 }

--      swPowerStatusChangeTrap NOTIFICATION-TYPE
--          OBJECTS     { swIndivPowerUnitIndex, swIndivPowerIndex, swIndivPowerStatus }
--          STATUS      current
--          DESCRIPTION "This trap is sent when the power status of
--                       an individual power changes."
--          ::= { ES4528VTrapsPrefix 1 }

    swPortSecurityTrap NOTIFICATION-TYPE
          OBJECTS     { ifIndex }
          STATUS      current
          DESCRIPTION "This trap is sent when the port is being intruded. This trap
                       will only be sent when the portSecActionTrap is enabled."
          ::= { ES4528VTrapsPrefix 36 }

    swIpFilterRejectTrap NOTIFICATION-TYPE
          OBJECTS     { trapIpFilterRejectMode, trapIpFilterRejectIp }
          STATUS      current
          DESCRIPTION "This trap is sent when an incorrect IP address is rejected by 
                       the ipfilter."
          ::= { ES4528VTrapsPrefix 40 }  
        
--    swSmtpConnFailureTrap NOTIFICATION-TYPE 
--          OBJECTS     { smtpServerIp }        
--          STATUS      current
--          DESCRIPTION "This trap is triggered if the SMTP system 
--                       cannot open a connection to the mail server successfully."            
--          ::= { ES4528VTrapsPrefix 41 }

--    swMainBoardVerMismatchNotificaiton NOTIFICATION-TYPE
--          OBJECTS     { swOpCodeVer, swOpCodeVer}
--          STATUS      current
--          DESCRIPTION "This trap is sent when the slave version is mismatch with the
--                       master version. This trap will binds two object, the first object
--                       indicate the master version, whereas the second represent the
--                       slave version."
--          ::= { ES4528VTrapsPrefix 56 }
      

--
--diffServMgt
--
--diffServMgt    OBJECT IDENTIFIER ::= { qosMgt 4 }
--
--diffServPortTable OBJECT-TYPE
--        SYNTAX      SEQUENCE OF DiffServPortEntry
--        MAX-ACCESS  not-accessible
--        STATUS      current
--        DESCRIPTION "Table for differentiated services on each port."
--        ::= { diffServMgt 9 }
--
--diffServPortEntry OBJECT-TYPE
--        SYNTAX      DiffServPortEntry
--        MAX-ACCESS  not-accessible
--        STATUS      current
--        DESCRIPTION "Entry for differentiated services on each port."
--        INDEX       { diffServPortIfIndex }
--        ::= { diffServPortTable 1 }
--
--DiffServPortEntry ::= SEQUENCE
--{
--    diffServPortIfIndex             Integer32,
--    diffServPortPolicyMapIndex      Integer32,
--    diffServPortIngressIpAclIndex   Integer32,
--    diffServPortIngressMacAclIndex  Integer32
--}
--
--diffServPortIfIndex OBJECT-TYPE
--        SYNTAX      Integer32
--        MAX-ACCESS  not-accessible
--        STATUS      current
--        DESCRIPTION "This object is the interface index of diffServPortEntry.
--                     The interface identified by a particular value of this
--                     index is the same interface as identified by the same
--                     value of ifIndex in the IF-MIB."
--        ::= { diffServPortEntry 1 }
--
--diffServPortPolicyMapIndex OBJECT-TYPE
--    SYNTAX      Integer32
--    MAX-ACCESS  read-write
--    STATUS      current
--    DESCRIPTION "Specifies the policy map binding to the interface. The policy
--                 map identified by a particular value of this index is
--                 associated with the same DiffServPolicyMapEntry as identified
--                 by the same value of diffServPolicyMapIndex."
--    ::= { diffServPortEntry 2 }
--
--diffServPortIngressIpAclIndex OBJECT-TYPE
--    SYNTAX      Integer32
--    MAX-ACCESS  read-write
--    STATUS      current
--    DESCRIPTION "Specifies the ingress IP ACL binding to the interface. The
--                 ingress IP ACL identified by a particular value of this index
--                 is associated with the same diffServAclEntry as identified by
--                 the same value of diffServAclIndex."
--    ::= { diffServPortEntry 3 }
--
--diffServPortIngressMacAclIndex OBJECT-TYPE
--    SYNTAX      Integer32
--    MAX-ACCESS  read-write
--    STATUS      current
--    DESCRIPTION "Specifies the ingress MAC ACL binding to the interface. The
--                 ingress MAC ACL identified by a particular value of this
--                 index is associated with the same diffServAclEntry as
--                 identified by the same value of diffServAclIndex."
--    ::= { diffServPortEntry 4 }
--
--diffServPolicyMapTable OBJECT-TYPE
--        SYNTAX      SEQUENCE OF DiffServPolicyMapEntry
--        MAX-ACCESS  not-accessible
--        STATUS      current
--        DESCRIPTION "Table for policy map."
--        ::= { diffServMgt 10 }
--
--diffServPolicyMapEntry OBJECT-TYPE
--        SYNTAX      DiffServPolicyMapEntry
--        MAX-ACCESS  not-accessible
--        STATUS      current
--        DESCRIPTION "Entry for policy map."
--        INDEX       { diffServPolicyMapIndex }
--        ::= { diffServPolicyMapTable 1 }
--
--DiffServPolicyMapEntry ::= SEQUENCE
--{
--    diffServPolicyMapIndex              Integer32,
--    diffServPolicyMapName               DisplayString,
--    diffServPolicyMapDescription        DisplayString,
--    diffServPolicyMapElementIndexList   OCTET STRING,
--    diffServPolicyMapStatus             RowStatus
--}
--
--diffServPolicyMapIndex OBJECT-TYPE
--        SYNTAX      Integer32
--        MAX-ACCESS  not-accessible
--        STATUS      current
--        DESCRIPTION "An index that uniquely identifies an entry in this table."
--        ::= { diffServPolicyMapEntry 1 }
--
--diffServPolicyMapName OBJECT-TYPE
--    SYNTAX      DisplayString (SIZE (1..16))
--    MAX-ACCESS  read-create
--    STATUS      current
--    DESCRIPTION "The name of this entry."
--    ::= { diffServPolicyMapEntry 2 }
--
--diffServPolicyMapDescription OBJECT-TYPE
--    SYNTAX      DisplayString (SIZE (0..64))
--    MAX-ACCESS  read-create
--    STATUS      current
--    DESCRIPTION "The description of this entry."
--    ::= { diffServPolicyMapEntry 3 }
--
--diffServPolicyMapElementIndexList OBJECT-TYPE
--    SYNTAX      OCTET STRING (SIZE (0..32))
--    MAX-ACCESS  read-only
--    STATUS      current
--    DESCRIPTION "The octet string containes the diffServPolicyMapElementEntry
--                 indexes. Two octets express one index and it is represented
--                 in network order. This index list indicates the
--                 diffServPolicyMapEntrys which belong to this entry."
--    ::= { diffServPolicyMapEntry 4 }
--
--diffServPolicyMapStatus OBJECT-TYPE
--    SYNTAX      RowStatus
--    MAX-ACCESS  read-create
--    STATUS      current
--    DESCRIPTION "This object is used to create a new row, or modify or delete
--                 an existing row, in this table. The status column has six
--                 defined values:
--                 The status column has six defined values:
--
--                      - 'active', which indicates that the conceptual row is
--                      available for use by the managed device;
--
--                      - 'notInService', which indicates that the conceptual
--                      row exists in the agent, but is unavailable for use by
--                      the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically set
--                      to active, making it available for use by the managed
--                      device;
--
--                      - 'createAndWait', which is supplied by a management
--                      station wishing to create a new instance of a
--                      conceptual row (but not make it available for use by
--                      the managed device); and,
--
--                      - 'destroy', which is supplied by a management station
--                      wishing to delete all of the instances associated with
--                      an existing conceptual row.
--
--                 Whereas five of the six values (all except 'notReady') may
--                 be specified in a management protocol set operation, only
--                 three values will be returned in response to a management
--                 protocol retrieval operation:  'notReady', 'notInService' or
--                 'active'.  That is, when queried, an existing conceptual row
--                 has only three states:  it is either available for use by
--                 the managed device (the status column has the value
--                 'active');it is not available for use by the managed device,
--                 though the agent has sufficient information to make it so
--                 (the status column has the value 'notInService'); or, it is
--                 not available for use by the managed device, and an attempt
--                 to make it so would fail because the agent has insufficient
--                 information (the state column has the value 'notReady').
--
--                 For a detailed description of this object, please refer to
--                 SNMPv2-TC MIB."
--    ::= { diffServPolicyMapEntry 5 }
--
--diffServPolicyMapAttachCtl  OBJECT IDENTIFIER   ::= { diffServMgt 11 }
--
--diffServPolicyMapAttachCtlIndex OBJECT-TYPE
--        SYNTAX      Integer32
--        MAX-ACCESS  read-write
--        STATUS      current
--        DESCRIPTION "Index for attachment control.
--                     Specifies the policy map as the target to relate with
--                     the policy map element. The policy map identified by
--                     a particular value of this index is associated with
--                     the same diffServPolicyMapEntry as identified by the
--                     same value of diffServPolicyMapIndex."
--        ::= { diffServPolicyMapAttachCtl 1 }
--
--diffServPolicyMapAttachCtlElementIndex OBJECT-TYPE
--    SYNTAX      Integer32
--    MAX-ACCESS  read-write
--    STATUS      current
--    DESCRIPTION "Element Index for attachment control.Specifies the policy map
--                 element to relate with the policy map. The policy map element
--                 identified by a particular value of this index is associated
--                 with the same diffServPolicyMapElementEntry as identified by
--                 the same value of diffServPolicyMapElementIndex."
--    ::= { diffServPolicyMapAttachCtl 2 }
--
--diffServPolicyMapAttachCtlAction OBJECT-TYPE
--    SYNTAX      INTEGER
--                    {
--                        noAction(1),
--                        attach(2),
--                        detach(3)
--                    }
--    MAX-ACCESS  read-write
--    STATUS      current
--    DESCRIPTION "Action for attachment control. When setting this object to
--                 attach(2) to begin the attaching operation, a particular
--                 policy map element is attached to a particular policy map.
--                 When setting this object to detach(3) to begin the not
--                 attached operation, a particular policy map element is not
--                 attached to a particular policy map. When the action is
--                 finshed or no action is taken, the value of this object is
--                 noAction(1). A particular policy map is specified in the
--                 diffServPolicyMapAttachCtlIndex. A particularpolicy map
--                 element is specified in the
--                 diffServPolicyMapAttachCtlElementIndex."
--    ::= { diffServPolicyMapAttachCtl 3 }
--
--diffServPolicyMapElementTable OBJECT-TYPE
--        SYNTAX      SEQUENCE OF DiffServPolicyMapElementEntry
--        MAX-ACCESS  not-accessible
--        STATUS      current
--        DESCRIPTION "Table for policy map element."
--        ::= { diffServMgt 12 }
--
--diffServPolicyMapElementEntry OBJECT-TYPE
--        SYNTAX      DiffServPolicyMapElementEntry
--        MAX-ACCESS  not-accessible
--        STATUS      current
--        DESCRIPTION "Entry for policy map element."
--        INDEX       { diffServPolicyMapElementIndex }
--        ::= { diffServPolicyMapElementTable 1 }
--
--DiffServPolicyMapElementEntry ::= SEQUENCE
--{
--    diffServPolicyMapElementIndex           Integer32,
--    diffServPolicyMapElementClassMapIndex   Integer32,
--    diffServPolicyMapElementMeterIndex      Integer32,
--    diffServPolicyMapElementActionIndex     Integer32,
--    diffServPolicyMapElementStatus          RowStatus
--}
--
--diffServPolicyMapElementIndex OBJECT-TYPE
--        SYNTAX      Integer32
--        MAX-ACCESS  not-accessible
--        STATUS      current
--        DESCRIPTION "An index that uniquely identifies an entry in this table."
--        ::= { diffServPolicyMapElementEntry 1 }
--
--diffServPolicyMapElementClassMapIndex OBJECT-TYPE
--    SYNTAX      Integer32(1..65535)
--    MAX-ACCESS  read-create
--    STATUS      current
--    DESCRIPTION "Specifies the class map binding to this entry. The class map
--                 identified by a particular value of this index is associated
--                 with the same diffServClassMapEntry as identified by the same
--                 value of diffServClassMapIndex."
--    ::= { diffServPolicyMapElementEntry 2 }
--
--diffServPolicyMapElementMeterIndex OBJECT-TYPE
--    SYNTAX      Integer32
--    MAX-ACCESS  read-create
--    STATUS      current
--    DESCRIPTION "Specifies the meter binding to this entry. The meter
--                 identified by a particular value of this index is associated
--                 with the same diffServMeterEntry as identified by the same
--                 value of diffServMeterIndex. If this value is 
--                 zero, no associated meter will be associated, as zero is not a 
--                 valid meter index."
--    ::= { diffServPolicyMapElementEntry 3 }
--
--diffServPolicyMapElementActionIndex OBJECT-TYPE
--    SYNTAX      Integer32(1..65535)
--    MAX-ACCESS  read-create
--    STATUS      current
--    DESCRIPTION "Specifies the action binding to this entry. The action
--                 identified by a particular value of this index is associated
--                 with the same diffServActionEntry as identified by the same
--                 value of diffServActionIndex."
--    ::= { diffServPolicyMapElementEntry 4 }
--
--diffServPolicyMapElementStatus OBJECT-TYPE
--    SYNTAX      RowStatus
--    MAX-ACCESS  read-create
--    STATUS      current
--    DESCRIPTION "This object is used to create a new row, or modify or delete
--                 an existing row, in this table. The status column has six
--                 defined values:
--
--                 The status column has six defined values:
--
--                      - 'active', which indicates that the conceptual row is
--                      available for use by the managed device;
--
--                      - 'notInService', which indicates that the conceptual
--                      row exists in the agent, but is unavailable for use by
--                      the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically set
--                      to active, making it available for use by the managed
--                      device;
--
--                      - 'createAndWait', which is supplied by a management
--                      station wishing to create a new instance of a
--                      conceptual row (but not make it available for use by
--                      the managed device); and,
--
--                      - 'destroy', which is supplied by a management station
--                      wishing to delete all of the instances associated with
--                      an existing conceptual row.
--
--                 Whereas five of the six values (all except 'notReady') may
--                 be specified in a management protocol set operation, only
--                 three values will be returned in response to a management
--                 protocol retrieval operation:  'notReady', 'notInService' or
--                 'active'.  That is, when queried, an existing conceptual row
--                 has only three states:  it is either available for use by
--                 the managed device (the status column has the value
--                 'active'); it is not available for use by the managed device,
--                 though the agent has sufficient information to make it so
--                 (the status column has the value 'notInService'); or, it is
--                 not available for use by the managed device, and an attempt
--                 to make it so would fail because the agent has insufficient
--                 information (the state column has the value 'notReady').
--
--                 For a detailed description of this object, please refer to
--                 SNMPv2-TC MIB."
--    ::= { diffServPolicyMapElementEntry 5 }
--
--diffServClassMapTable OBJECT-TYPE
--        SYNTAX      SEQUENCE OF DiffServClassMapEntry
--        MAX-ACCESS  not-accessible
--        STATUS      current
--        DESCRIPTION "Table for class map."
--        ::= { diffServMgt 13 }
--
--diffServClassMapEntry OBJECT-TYPE
--        SYNTAX      DiffServClassMapEntry
--        MAX-ACCESS  not-accessible
--        STATUS      current
--        DESCRIPTION "Entry for class map."
--        INDEX       { diffServClassMapIndex }
--        ::= { diffServClassMapTable 1 }
--
--DiffServClassMapEntry ::= SEQUENCE
--{
--    diffServClassMapIndex                Integer32,
--    diffServClassMapName                 DisplayString,
--    diffServClassMapDescription          DisplayString,
--    diffServClassMapMatchType            INTEGER,
--    diffServClassMapElementIndexTypeList OCTET STRING,
--    diffServClassMapElementIndexList     OCTET STRING,
--    diffServClassMapStatus               RowStatus
--}
--
--diffServClassMapIndex OBJECT-TYPE
--        SYNTAX      Integer32
--        MAX-ACCESS  not-accessible
--        STATUS      current
--        DESCRIPTION "An index that uniquely identifies an entry in this table."
--        ::= { diffServClassMapEntry 1 }
--
--diffServClassMapName OBJECT-TYPE
--    SYNTAX      DisplayString (SIZE (1..16))
--    MAX-ACCESS  read-create
--    STATUS      current
--    DESCRIPTION "The name of this entry."
--    ::= { diffServClassMapEntry 2 }
--
--diffServClassMapDescription OBJECT-TYPE
--    SYNTAX      DisplayString (SIZE (0..64))
--    MAX-ACCESS  read-create
--    STATUS      current
--    DESCRIPTION "The description of this entry."
--    ::= { diffServClassMapEntry 3 }
--
--diffServClassMapMatchType OBJECT-TYPE
--    SYNTAX       INTEGER {
--                     matchAny(1),
--                     matchAll(2)
--                }
--    MAX-ACCESS  read-create
--    STATUS      current
--    DESCRIPTION "The map match type of this entry."
--    ::= { diffServClassMapEntry 4 }
--
--diffServClassMapElementIndexTypeList OBJECT-TYPE
--    SYNTAX      OCTET STRING (SIZE (0..255))
--    MAX-ACCESS  read-only
--    STATUS      current
--    DESCRIPTION "The octet string containes the type of class map element
--                 indexes. Two octets which are represented in network order
--                 express one type of the class map element index in network
--                 order and it maps the index of
--                 differServClasssMapElementIndexList in order. When the type is
--                 macAce(1), the maping index of
--                 differServClasssMapElementIndexList is the
--                 diffServMacAceEntry. When the type is ipAce(2), the maping
--                 index of differServClasssMapElementIndexList is the
--                 diffServIpAceEntry. When the type is acl(3), the maping index
--                 of differServClasssMapElementIndexList is the
--                 diffServAclEntry. When the type is ipv6Ace(4), the maping
--                 index of differServClasssMapElementIndexList is the
--                 diffServIpv6AceEntry."
--    ::= { diffServClassMapEntry 5 }
--
--diffServClassMapElementIndexList OBJECT-TYPE
--    SYNTAX      OCTET STRING (SIZE (0..255))
--    MAX-ACCESS  read-only
--    STATUS      current
--    DESCRIPTION "The octet string containes the class map element indexes. Two
--                 octets express one index and it is represented in
--                 network order. This index list indicates the particular
--                 class map elements which belong to this table. The class map
--                 element uses type to indicate diffServAclEntry, the
--                 diffServIpAceEntry, the diffServMacAceEntry or
--                 diffServIpv6AceEntry. The type is two octet specified in
--                 differServClasssMapElementIndexTypeList in order. When the
--                 type is macAce(1), the maping index of
--                 differServClasssMapElementIndexList is the
--                 diffServMacAceEntry. When the type is ipAce(2), the maping
--                 index of differServClasssMapElementIndexList is the
--                 diffServIpAceEntry. When the type is acl(3), the maping index
--                 of differServClasssMapElementIndexList is the
--                 diffServAclEntry. When the type is ipv6Ace(4), the maping
--                 index of differServClasssMapElementIndexList is the
--                 diffServIpv6AceEntry."
--    ::= { diffServClassMapEntry 6 }
--
--diffServClassMapStatus OBJECT-TYPE
--    SYNTAX      RowStatus
--    MAX-ACCESS  read-create
--    STATUS      current
--    DESCRIPTION "This object is used to create a new row or modify or delete
--                 an existing row in this table.The status column has six
--                 defined values:
--
--                 The status column has six defined values:
--
--                      - 'active', which indicates that the conceptual row is
--                      available for use by the managed device;
--
--                      - 'notInService', which indicates that the conceptual
--                      row exists in the agent, but is unavailable for use by
--                      the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically set
--                      to active, making it available for use by the managed
--                      device;
--
--                      - 'createAndWait', which is supplied by a management
--                      station wishing to create a new instance of a
--                      conceptual row (but not make it available for use by
--                      the managed device); and,
--
--                      - 'destroy', which is supplied by a management station
--                      wishing to delete all of the instances associated with
--                      an existing conceptual row.
--
--                 Whereas five of the six values (all except 'notReady') may
--                 be specified in a management protocol set operation, only
--                 three values will be returned in response to a management
--                 protocol retrieval operation:  'notReady', 'notInService' or
--                 'active'.  That is, when queried, an existing conceptual row
--                 has only three states:  it is either available for use by
--                 the managed device (the status column has the value
--                 'active'); it is not available for use by the managed device,
--                 though the agent has sufficient information to make it so
--                 (the status column has the value 'notInService'); or, it is
--                 not available for use by the managed device, and an attempt
--                 to make it so would fail because the agent has insufficient
--                 information (the state column has the value 'notReady').
--
--                 For a detailed description of this object, please refer to
--                 SNMPv2-TC MIB."
--    ::= { diffServClassMapEntry 7 }
--
--diffServClassMapAttachCtl  OBJECT IDENTIFIER   ::= { diffServMgt 14 }
--
--diffServClassMapAttachCtlIndex OBJECT-TYPE
--        SYNTAX      Integer32
--        MAX-ACCESS  read-write
--        STATUS      current
--        DESCRIPTION "Index for attachment control. Specifies the class map as
--                     the target to relate with class map elements. The class
--                     map identified by a particular value of this index is
--                     associated with the same diffServClassMapEntry as
--                     identified by the same value of diffServClassMapIndex."
--        ::= { diffServClassMapAttachCtl 1 }
--
--diffServClassMapAttachCtlElementIndexType OBJECT-TYPE
--    SYNTAX    INTEGER {
--                     macAce(1),
--                     ipAce(2),
--                     acl(3),
--                     ipv6Ace(4)
--                }
--    MAX-ACCESS  read-write
--    STATUS      current
--    DESCRIPTION "Element Index for attachment control. Specifies the type of
--                 class map element to relate with the class map. When type is
--                 macAce(1), the index of diffServClassMapAttachCtlElementIndex
--                 is the index of diffServMacAceEntry. When the type is
--                 ipAce(2), the index of diffServClassMapAttachCtlElementIndex
--                 is the index of diffServIpAceEntry. When the type is acl(3),
--                 the index of diffServClassMapAttachCtlElementIndex is the
--                 index of diffServAclEntry. When the type is ipv6Ace(4), the
--                 index of diffServClassMapAttachCtlElementIndex is the index of
--                 diffServIpv6AceEntry."
--    ::= { diffServClassMapAttachCtl 2 }
--
--diffServClassMapAttachCtlElementIndex OBJECT-TYPE
--    SYNTAX      Integer32
--    MAX-ACCESS  read-write
--    STATUS      current
--    DESCRIPTION "Element Index for attachment control. Specifies the class map
--                 element related with the class map. The class map element uses
--                 type to indicate diffServAclEntry, the diffServIpAceEntry, the
--                 diffServMacAceEntry or the diffServIpv6AceEntry. The type is
--                 specified in diffServClassMapAttachCtlElementIndexType. When
--                 the type is macAce(1), the maping index of
--                 differServClasssMapElementIndexList is the
--                 diffServMacAceEntry. When the type is ipAce(2), the maping
--                 index of differServClasssMapElementIndexList is the
--                 diffServIpAceEntry. When the type is acl(3), the maping index
--                 of differServClasssMapElementIndexList is the
--                 diffServAclEntry. When the type is ipv6Ace(4), the maping
--                 index of differServClasssMapElementIndexList is the
--                 diffServIpv6AceEntry."
--    ::= { diffServClassMapAttachCtl 3 }
--
--diffServClassMapAttachCtlAction OBJECT-TYPE
--    SYNTAX      INTEGER
--                    {
--                        noAction(1),
--                        attach(2),
--                        detach(3)
--                    }
--    MAX-ACCESS  read-write
--    STATUS      current
--    DESCRIPTION "Action for attachment control. When setting this object to
--                 attach(2) to begin the attaching operation, a particular class
--                 map element is attached to a particular class map. When
--                 setting this object to detach(3) to begin the not attached
--                 operation, then a particular class map element is not attached
--                 to a particular class map. When the action is finshed or no
--                 action is taken, the value of this object is noAction(1). The
--                 value of a particular class map is specified in the
--                 AclAttachCtlTargetIndex. The class map element is specified
--                 by diffServClassMapAttachCtlElementIndexType and
--                 diffServClassMapAttachCtlElementIndex."
--    ::= { diffServClassMapAttachCtl 4 }
--
--diffServAclTable OBJECT-TYPE
--        SYNTAX      SEQUENCE OF DiffServAclEntry
--        MAX-ACCESS  not-accessible
--        STATUS      current
--        DESCRIPTION "Table for ACL."
--        ::= { diffServMgt 15 }
--
--diffServAclEntry OBJECT-TYPE
--        SYNTAX      DiffServAclEntry
--        MAX-ACCESS  not-accessible
--        STATUS      current
--        DESCRIPTION "Entry for ACL."
--        INDEX       { diffServAclIndex }
--        ::= { diffServAclTable 1 }
--
--DiffServAclEntry ::= SEQUENCE
--{
--    diffServAclIndex        Integer32,
--    diffServAclName         DisplayString,
--    diffServAclType         INTEGER,
--    diffServAclAceIndexList OCTET STRING,
--    diffServAclStatus       RowStatus
--}
--
--diffServAclIndex OBJECT-TYPE
--        SYNTAX      Integer32
--        MAX-ACCESS  not-accessible
--        STATUS      current
--        DESCRIPTION "An index that uniquely identifies an entry in the ACL
--                     table."
--        ::= { diffServAclEntry 1 }
--
--diffServAclName OBJECT-TYPE
--    SYNTAX      DisplayString (SIZE (1..16))
--    MAX-ACCESS  read-create
--    STATUS      current
--    DESCRIPTION "The name of this entry."
--    ::= { diffServAclEntry 2 }
--
--diffServAclType OBJECT-TYPE
--    SYNTAX      INTEGER {
--                    mac(1),
--                    ipstandard(2),
--                    ipextended(3)
--                }
--    MAX-ACCESS  read-create
--    STATUS      current
--    DESCRIPTION "The type of this entry. When the value of ACL type is
--                 modified, then the ACEs in the diffServAclAceIndexList of
--                 this entry will be auto-removed, and this entry will be aoto-
--                 unbound from the diffServPortTable and the
--                 diffServClassMapTable."
--    ::= { diffServAclEntry 3 }
--
--diffServAclAceIndexList OBJECT-TYPE
--    SYNTAX      OCTET STRING (SIZE (0..255))
--    MAX-ACCESS  read-only
--    STATUS      current
--    DESCRIPTION "The octet string containes the ACE indexes. Two octets
--                 express one index and it is represented in network
--                 order. This index list indicates the particular ACEs which
--                 belong to this table. The ACE uses type to indicate the
--                 diffServIpAceEntry, the diffServMacAceEntry or the
--                 diffServIpv6AceEntry. The type is specified in
--                 diffServAclType. When the type is macAce(1), the index of
--                 diffServAclAceIndexList is the diffServMacAceEntry. When the
--                 type is ipAce(2), the index of diffServAclAceIndexList is
--                 the diffServIpAceEntry. When the type is ipv6Ace(3), the
--                 index of diffServAclAceIndexListis the
--                 diffServIpv6AceEntry."
--    ::= { diffServAclEntry 4 }
--
--diffServAclStatus OBJECT-TYPE
--    SYNTAX      RowStatus
--    MAX-ACCESS  read-create
--    STATUS      current
--    DESCRIPTION "This object is used to create a new row or modify or delete
--                 an existing row in this table. The status column has six
--                 defined values:
--
--                      - 'active', which indicates that the conceptual row is
--                      available for use by the managed device;
--
--                      - 'notInService', which indicates that the conceptual
--                      row exists in the agent, but is unavailable for use by
--                      the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically set
--                      to active, making it available for use by the managed
--                      device;
--
--                      - 'createAndWait', which is supplied by a management
--                      station wishing to create a new instance of a
--                      conceptual row (but not make it available for use by
--                      the managed device); and,
--
--                      - 'destroy', which is supplied by a management station
--                      wishing to delete all of the instances associated with
--                      an existing conceptual row.
--
--                 Whereas five of the six values (all except 'notReady') may
--                 be specified in a management protocol set operation, only
--                 three values will be returned in response to a management
--                 protocol retrieval operation:  'notReady', 'notInService' or
--                 'active'.  That is, when queried, an existing conceptual row
--                 has only three states:  it is either available for use by
--                 the managed device (the status column has the value
--                 'active'); it is not available for use by the managed device,
--                 though the agent has sufficient information to make it so
--                 (the status column has the value 'notInService'); or, it is
--                 not available for use by the managed device, and an attempt
--                 to make it so would fail because the agent has insufficient
--                 information (the state column has the value 'notReady').
--
--                 For a detailed description of this object, please refer to
--                 SNMPv2-TC MIB."
--    ::= { diffServAclEntry 5 }
--
--diffServAclAttachCtl  OBJECT IDENTIFIER   ::= { diffServMgt 16 }
--
--diffServAclAttachCtlIndex OBJECT-TYPE
--        SYNTAX      Integer32
--        MAX-ACCESS  read-write
--        STATUS      current
--        DESCRIPTION "Index for attachment control. Specifies the ACL as the
--                     target to relate with the IP ACE, the MAC ACE or IPv6 ACE.
--                     The ACL identified by a particular value of this index  is
--                     associated with the same diffServAclEntry as identified by
--                     the same value of diffServAclIndex."
--        ::= { diffServAclAttachCtl 1 }
--
--diffServAclAttachCtlAceType OBJECT-TYPE
--    SYNTAX    INTEGER {
--        macAce(1),
--        ipAce(2)
--    }
--    MAX-ACCESS  read-write
--    STATUS      current
--    DESCRIPTION "Type for attachment control. Specifies the type of
--                 diffServAclAttachCtlAceIndex to relate with the
--                 diffServAclAttachCtlIndex. When the type is macAce(1), the
--                 index of diffServAclAceIndexList is the diffServMacAceEntry.
--                 When the type is ipAce(2), the index of
--                 diffServAclAceIndexList is the diffServIpAceEntry."
--    ::= { diffServAclAttachCtl 2 }
--
--diffServAclAttachCtlAceIndex OBJECT-TYPE
--    SYNTAX      Integer32
--    MAX-ACCESS  read-write
--    STATUS      current
--    DESCRIPTION "Index for attachment control. Specifies the ACE to relate with
--                 the diffServAclAttachCtlIndex. When
--                 diffServAclAttachCtlAceType is macAce(1), the value of
--                 diffServAclAttachCtlIndex is the diffServMacAceEntry. When
--                 diffServAclAttachCtlAceType is ipAce(2), the value of
--                 diffServAclAttachCtlIndex is the diffServIpAceEntry. When
--                 diffServAclAttachCtlAceType is ipv6Ace(3), the value of
--                 diffServAclAttachCtlIndex is the diffServIpv6AceEntry."
--    ::= { diffServAclAttachCtl 3 }
--
--diffServAclAttachCtlAction OBJECT-TYPE
--    SYNTAX      INTEGER
--                    {
--                        noAction(1),
--                        attach(2),
--                        detach(3)
--                    }
--    MAX-ACCESS  read-write
--    STATUS      current
--    DESCRIPTION "Action for attachment control. When setting this object to
--                 attach(2) to begin the attaching operation, a particular ACE
--                 is attached to a particular ACL. When setting this object to
--                 detach(3) to begin the not attached operation, then a
--                 particular ACE is not attached to a particular ACL. When the
--                 action is finshed or no action is taken, the value of this
--                 object is noAction(1), The value of a particular ACL is
--                 specified in the diffServAclAttachCtlAceType and
--                 diffServAclAttachCtlAceIndex."
--    ::= { diffServAclAttachCtl 4 }
--
--diffServIpAceTable OBJECT-TYPE
--        SYNTAX      SEQUENCE OF DiffServIpAceEntry
--        MAX-ACCESS  not-accessible
--        STATUS      current
--        DESCRIPTION "Table for IP ACE."
--        ::= { diffServMgt 17 }
--
--diffServIpAceEntry OBJECT-TYPE
--        SYNTAX      DiffServIpAceEntry
--        MAX-ACCESS  not-accessible
--        STATUS      current
--        DESCRIPTION "Entry for IP ACE."
--        INDEX       { diffServIpAceIndex }
--        ::= { diffServIpAceTable 1 }
--
--DiffServIpAceEntry ::= SEQUENCE
--{
--    diffServIpAceIndex                  Integer32,
--    diffServIpAceType                   INTEGER,
--    diffServIpAceAccess                 INTEGER,
--    diffServIpAceSourceIpAddr           Integer32,
--    diffServIpAceSourceIpAddrBitmask    Integer32,
--    diffServIpAceDestIpAddr             Integer32,
--    diffServIpAceDestIpAddrBitmask      Integer32,
--    diffServIpAceProtocol               Integer32,
--    diffServIpAcePrec                   Integer32,
--    diffServIpAceTos                    Integer32,
--    diffServIpAceDscp                   Integer32,
--    diffServIpAceSourcePortOp           INTEGER,
--    diffServIpAceMinSourcePort          Integer32,
--    diffServIpAceMaxSourcePort          Integer32,
--    diffServIpAceSourcePortBitmask      Integer32,
--    diffServIpAceDestPortOp             INTEGER,
--    diffServIpAceMinDestPort            Integer32,
--    diffServIpAceMaxDestPort            Integer32,
--    diffServIpAceDestPortBitmask        Integer32,
--    diffServIpAceControlCode            Integer32,
--    diffServIpAceControlCodeBitmask     Integer32,
--    diffServIpAceStatus                 RowStatus
--}
--
--diffServIpAceIndex OBJECT-TYPE
--        SYNTAX      Integer32
--        MAX-ACCESS  not-accessible
--        STATUS      current
--        DESCRIPTION "An index that uniquely identifies an entry in the IP ACE
--                     table."
--        ::= { diffServIpAceEntry 1 }
--
--diffServIpAceType OBJECT-TYPE
--    SYNTAX  INTEGER {
--      standard(1),
--      extended(2)
--    }
--    MAX-ACCESS  read-create
--    STATUS      current
--    DESCRIPTION "The specified IP ACE type. When the type of this entry is
--                 modified, then this entry will be auto-unbound from the
--                 diffServAclEntry and the not supporting field of this entry
--                 will be set 0."
--    ::= { diffServIpAceEntry 2 }
--
--diffServIpAceAccess OBJECT-TYPE
--    SYNTAX  INTEGER {
--        permit(1),
--        deny(2)
--    }
--    MAX-ACCESS  read-create
--    STATUS      current
--    DESCRIPTION "Indicates the action to be taken if a packet matches this
--                 ACE."
--    ::= { diffServIpAceEntry 3 }
--
--diffServIpAceSourceIpAddr OBJECT-TYPE
--    SYNTAX      Integer32
--    MAX-ACCESS  read-create
--    STATUS      current
--    DESCRIPTION "The specified source IP address. The packet's source address
--                 is AND-ed with the value of IpAceSourceIpAddrBitmask and then
--                 compared against the value of this object."
--    ::= { diffServIpAceEntry 4 }
--
--diffServIpAceSourceIpAddrBitmask OBJECT-TYPE
--    SYNTAX      Integer32
--    MAX-ACCESS  read-create
--    STATUS      current
--    DESCRIPTION "The specified source IP address mask. The packet's source
--                 address is AND-ed with the value of IpAceSourceIpAddr and
--                 then compared against the value of this object."
--    ::= { diffServIpAceEntry 5 }
--
--diffServIpAceDestIpAddr OBJECT-TYPE
--    SYNTAX      Integer32
--    MAX-ACCESS  read-create
--    STATUS      current
--    DESCRIPTION "The specified destination IP address. The packet's
--                 destination address is AND-ed with the value of
--                 diffServIpAceDestIpAddrBitmask and then compared against the
--                 value of this object. This object may not be modified if the
--                 associated diffServIpAceType object is equal to standard(1)."
--    ::= { diffServIpAceEntry 6 }
--
--diffServIpAceDestIpAddrBitmask OBJECT-TYPE
--        SYNTAX      Integer32
--        MAX-ACCESS  read-create
--        STATUS      current
--        DESCRIPTION "The specified destination IP address mask. This object may
--                     not be modified if the associated diffServIpAceType object
--                     is equal to standard(1)."
--        ::= { diffServIpAceEntry 7 }
--
--diffServIpAceProtocol OBJECT-TYPE
--    SYNTAX      Integer32 (0..256)
--    MAX-ACCESS  read-create
--    STATUS      current
--    DESCRIPTION "The protocol number field in the IP header used to indicate
--                 the higher layer protocol as specified in RFC 1700. A value
--                 of 0 matches every IP packet. The object=256 means 'any'. For
--                 example: 0 is IP, 1 is ICMP, 2 is IGMP, 4 is IP in IP
--                 encapsulation, 6 is TCP, 9 is IGRP, 17 is UDP, 47 is GRE, 50
--                 is ESP, 51 is AH, 88 is IGRP, 89 is OSPF, 94 is KA9Q/NOS
--                 compatible IP over IP, 103 is PIMv2, 108 is PCP. This object
--                 may not be modified if the associated diffServIpAceType object
--                 is equal to standard(1)."
--    ::= { diffServIpAceEntry 8 }
--
--diffServIpAcePrec OBJECT-TYPE
--    SYNTAX      Integer32 (0..8)
--    MAX-ACCESS  read-create
--    STATUS      current
--    DESCRIPTION "Specifies the IP precedence value to match against. The value
--                 of this object is ignored whenever the value of
--                 diffServIpAcePrec object is 8. This object may not be modified
--                 if the associated diffServIpAceType object is equal to
--                 standard(1)."
--    ::= { diffServIpAceEntry 9 }
--
--diffServIpAceTos OBJECT-TYPE
--    SYNTAX      Integer32 (0..16)
--    MAX-ACCESS  read-create
--    STATUS      current
--    DESCRIPTION "Specifies the IP ToS facility value to match against. The
--                 value of this object is ignored whenever the value of
--                 diffServIpAcePrec object is 9. This object may not be modified
--                 if the associated diffServIpAceType object is equal to
--                 standard(1)."
--    ::= { diffServIpAceEntry 10 }
--
--diffServIpAceDscp OBJECT-TYPE
--    SYNTAX      Integer32 (0..64)
--    MAX-ACCESS  read-create
--    STATUS      current
--    DESCRIPTION "Specifies the DSCP value to match against. The value of this
--                 object is ignored whenever the value of diffServIpAcePrec
--                 object is 64. This object may not be modified if the
--                 associated diffServIpAceType object is equal to standard(1)."
--    ::= { diffServIpAceEntry 11 }
--
--diffServIpAceSourcePortOp OBJECT-TYPE
--    SYNTAX  INTEGER {
--                noOperator(1),
--                equal(2),
--                range(3)
--    }
--    MAX-ACCESS  read-create
--    STATUS      current
--    DESCRIPTION "Indicates how a packet's source TCP/UDP port number is to be
--                 compared. noOperator(1), which is the default value, means no
--                 comparison is to be made with the source TCP/UDP port
--                 number. equal(2), which is used the
--                 diffServIpAceSourcePortBitmask and the
--                 diffServIpAceMinSourcePort to match against. range(3),which is
--                 used the diffServIpAceMinSourcePort and the
--                 diffServIpAceMaxSourcePort to match against. This object may
--                 not be modified if the associated diffServIpAceType object is
--                 equal to standard(1)."
--    ::= { diffServIpAceEntry 12 }
--
--diffServIpAceMinSourcePort OBJECT-TYPE
--        SYNTAX      Integer32 (0..'FFFF'h)
--        MAX-ACCESS  read-create
--        STATUS      current
--        DESCRIPTION "If the diffServIpAceSourcePortOp is range(3), this
--                     indicates the lower bound of the TCP/UDP port number
--                     value range. This object may not be modified if the
--                     associated diffServIpAceType object is equal to
--                     standard(1)."
--        ::= { diffServIpAceEntry 13 }
--
--diffServIpAceMaxSourcePort OBJECT-TYPE
--    SYNTAX      Integer32 (0..'FFFF'h)
--    MAX-ACCESS  read-create
--    STATUS      current
--    DESCRIPTION "If the diffServIpAceSourcePortOp is range(3), this indicates
--                 the upper bound of the TCP/UDP port number value range. This
--                 object may not be modified if the associated
--                 diffServIpAceType object is equal to standard(1)."
--    ::= { diffServIpAceEntry 14 }
--
--diffServIpAceSourcePortBitmask OBJECT-TYPE
--    SYNTAX      Integer32 (0..'FFFF'h)
--    MAX-ACCESS  read-create
--    STATUS      current
--    DESCRIPTION "If the diffServIpAceSourcePortOp is equal(2), this indicates
--                 the bitmask of the diffServIpAceMinSourcePort. This object may
--                 not be modified if the associated diffServIpAceType object is
--                 equal to standard(1)."
--    ::= { diffServIpAceEntry 15 }
--
--diffServIpAceDestPortOp OBJECT-TYPE
--    SYNTAX      INTEGER{
--                noOperator(1),
--                equal(2),
--                range(3)
--    }
--    MAX-ACCESS  read-create
--    STATUS      current
--    DESCRIPTION "Indicates how a packet's destination TCP/UDP port number is
--                 to be compared. noOperator(1), which is the default value,
--                 means that no comparison is to be made with the destination
--                 TCP/UDP port number. equal(2), which is used the
--                 diffServIpAceSourcePortBitmask and the
--                 diffServIpAceMinDestPort to match against. range(3),which is
--                 used the diffServIpAceMinDestPort and the
--                 diffServIpAceMaxDestPort to match against. This object may not
--                 be modified if the associated diffServIpAceType object is
--                 equal to standard(1)."
--    ::= { diffServIpAceEntry 16 }
--
--diffServIpAceMinDestPort OBJECT-TYPE
--    SYNTAX      Integer32 (0..'FFFF'h)
--    MAX-ACCESS  read-create
--    STATUS      current
--    DESCRIPTION "If the diffServIpAceDestPortOp is range(3), this indicates
--                 the lower bound of the TCP/UDP port number value range. This
--                 object may not be modified if the associated
--                 diffServIpAceType object is equal to standard(1)."
--    ::= { diffServIpAceEntry 17 }
--
--diffServIpAceMaxDestPort OBJECT-TYPE
--    SYNTAX      Integer32 (0..'FFFF'h)
--    MAX-ACCESS  read-create
--    STATUS      current
--    DESCRIPTION "If the diffServIpAceDestPortOp is range(3), this indicates
--                 the upper bound of the TCP/UDP port number value range. This
--                 object may not be modified if the associated
--                 diffServIpAceType object is equal to standard(1)."
--    ::= { diffServIpAceEntry 18 }
--
--diffServIpAceDestPortBitmask OBJECT-TYPE
--    SYNTAX      Integer32 (0..'FFFF'h)
--    MAX-ACCESS  read-create
--    STATUS      current
--    DESCRIPTION "If the diffServIpAceDestPortOp is equal(2), this indicates
--                 the bitmask of the diffServIpAceMinDestPort. This object may
--                 not be modified if the associated diffServIpAceType object
--                 is equal to standard(1)."
--    ::= { diffServIpAceEntry 19 }
--
--diffServIpAceControlCode OBJECT-TYPE
--    SYNTAX      Integer32 (0..63)
--    MAX-ACCESS  read-create
--    STATUS      current
--    DESCRIPTION "Indicates how the control flags of TCP packets are to be
--                 compared. diffServIpAceControlCode is AND-ed with
--                 diffServIpAceControlCodeBitmask. This object may not be
--                 modified if the associated diffServIpAceType object is
--                 equal to standard(1)."
--    ::= { diffServIpAceEntry 20 }
--
--diffServIpAceControlCodeBitmask OBJECT-TYPE
--    SYNTAX      Integer32 (0..63)
--    MAX-ACCESS  read-create
--    STATUS      current
--    DESCRIPTION "Indicates how the control flags of TCP packets are to be
--                 compared. It can be used to check multiple flags of the FIN,
--                 SYN, RST, PSH, ACK, URG by the sum of FIN=1, SYN=2, RST=4,
--                 PSH=8, ACK=16, URG=32. This object may not be modified if the
--                 associated diffServIpAceType object is equal to standard(1)."
--    ::= { diffServIpAceEntry 21 }
--
--diffServIpAceStatus OBJECT-TYPE
--    SYNTAX      RowStatus
--    MAX-ACCESS  read-create
--    STATUS      current
--    DESCRIPTION "This object is used to create a new row or modify or delete
--                 an existing row in this table. The status column has six
--                 defined values:
--
--                 The status column has six defined values:
--
--                      - 'active', which indicates that the conceptual row is
--                      available for use by the managed device;
--
--                      - 'notInService', which indicates that the conceptual
--                      row exists in the agent, but is unavailable for use by
--                      the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically set
--                      to active, making it available for use by the managed
--                      device;
--
--                      - 'createAndWait', which is supplied by a management
--                      station wishing to create a new instance of a
--                      conceptual row (but not make it available for use by
--                      the managed device); and,
--
--                      - 'destroy', which is supplied by a management station
--                      wishing to delete all of the instances associated with
--                      an existing conceptual row.
--
--                 Whereas five of the six values (all except 'notReady') may
--                 be specified in a management protocol set operation, only
--                 three values will be returned in response to a management
--                 protocol retrieval operation:  'notReady', 'notInService' or
--                 'active'.  That is, when queried, an existing conceptual row
--                 has only three states:  it is either available for use by
--                 the managed device (the status column has the value
--                 'active'); it is not available for use by the managed device,
--                 though the agent has sufficient information to make it so
--                 (the status column has the value 'notInService'); or, it is
--                 not available for use by the managed device, and an attempt
--                 to make it so would fail because the agent has insufficient
--                 information (the state column has the value 'notReady').
--
--                 For a detailed description of this object, please refer to
--                 SNMPv2-TC MIB."
--    ::= { diffServIpAceEntry 22 }
--
--diffServMacAceTable OBJECT-TYPE
--        SYNTAX      SEQUENCE OF DiffServMacAceEntry
--        MAX-ACCESS  not-accessible
--        STATUS      current
--        DESCRIPTION "Table for MAC ACE."
--        ::= { diffServMgt 18 }
--
--diffServMacAceEntry OBJECT-TYPE
--        SYNTAX      DiffServMacAceEntry
--        MAX-ACCESS  not-accessible
--        STATUS      current
--        DESCRIPTION "Entry for MAC ACE."
--        INDEX       { diffServMacAceIndex }
--        ::= { diffServMacAceTable 1 }
--
--DiffServMacAceEntry ::= SEQUENCE
--{
--    diffServMacAceIndex                 Integer32,
--    diffServMacAceAccess                INTEGER,
--    diffServMacAcePktformat             INTEGER,
--    diffServMacAceSourceMacAddr         MacAddress,
--    diffServMacAceSourceMacAddrBitmask  MacAddress,
--    diffServMacAceDestMacAddr           MacAddress,
--    diffServMacAceDestMacAddrBitmask    MacAddress,
--    diffServMacAceVidOp                 INTEGER,
--    diffServMacAceMinVid                Integer32,
--    diffServMacAceVidBitmask            Integer32,
--    diffServMacAceMaxVid                Integer32,
--    diffServMacAceEtherTypeOp           INTEGER,
--    diffServMacAceEtherTypeBitmask      Integer32,
--    diffServMacAceMinEtherType          Integer32,
--    diffServMacAceMaxEtherType          Integer32,
--    diffServMacAceStatus                RowStatus
--}
--
--diffServMacAceIndex OBJECT-TYPE
--        SYNTAX      Integer32
--        MAX-ACCESS  not-accessible
--        STATUS      current
--        DESCRIPTION "An index that uniquely identifies an entry in the MAC ACE
--                     table."
--        ::= { diffServMacAceEntry 1 }
--
--diffServMacAceAccess OBJECT-TYPE
--        SYNTAX    INTEGER {
--            permit(1),
--            deny(2)
--        }
--        MAX-ACCESS  read-create
--        STATUS      current
--        DESCRIPTION "Indicates the action to be taken if a packet matches this
--                     ACE."
--        ::= { diffServMacAceEntry 2 }
--
--diffServMacAcePktformat OBJECT-TYPE
--    SYNTAX    INTEGER {
--        any(1),
--        untagged-Eth2(2),
--        untagged802Dot3(3),
--        tagggedEth2(4),
--        tagged802Dot3(5)
--    }
--    MAX-ACCESS  read-create
--    STATUS      current
--    DESCRIPTION "Used to check the packet format of the packets. This object
--                 cannot be configured when the status of the entry,
--                 diffServMacAceStatus, is active(1)."
--    ::= { diffServMacAceEntry 3 }
--
--diffServMacAceSourceMacAddr OBJECT-TYPE
--    SYNTAX      MacAddress
--    MAX-ACCESS  read-create
--    STATUS      current
--    DESCRIPTION "Indicates the 48-bit source MAC address. The specified source
--                 MAC of the packet. The packet's source MAC address is AND-ed
--                 with the value of diffServMacAceSourceMacAddrBitmask
--                 and then compared against the value of this object."
--    ::= { diffServMacAceEntry 4 }
--
--diffServMacAceSourceMacAddrBitmask OBJECT-TYPE
--    SYNTAX      MacAddress
--    MAX-ACCESS  read-create
--    STATUS      current
--    DESCRIPTION "The specified source MAC address mask."
--    ::= { diffServMacAceEntry 5 }
--
--diffServMacAceDestMacAddr OBJECT-TYPE
--    SYNTAX      MacAddress
--    MAX-ACCESS  read-create
--    STATUS      current
--    DESCRIPTION "Indicates the 48-bit destination MAC address. The specified
--                 destination MAC of the packet. The packet's destination MAC
--                 address is AND-ed with the value of
--                 diffServMacAceDestMacAddrBitmask and then compared against
--                 the value of this object."
--    ::= { diffServMacAceEntry 6 }
--
--diffServMacAceDestMacAddrBitmask OBJECT-TYPE
--    SYNTAX      MacAddress
--    MAX-ACCESS  read-create
--    STATUS      current
--    DESCRIPTION "The specified destination MAC address mask."
--    ::= { diffServMacAceEntry 7 }
--
--diffServMacAceVidOp OBJECT-TYPE
--    SYNTAX    INTEGER {
--            noOperator(1),
--            equal(2),
--            range(3)
--        }
--        MAX-ACCESS  read-create
--        STATUS      current
--        DESCRIPTION "Indicates how a packet's VID is to be compared. This
--                     object cannot be configured when the status of the entry,
--                     diffServMacAceStatus, is active(1)."
--        ::= { diffServMacAceEntry 8 }
--
--diffServMacAceMinVid OBJECT-TYPE
--    SYNTAX      Integer32 (1..4094)
--    MAX-ACCESS  read-create
--    STATUS      current
--    DESCRIPTION "Indicates the lower bound of the VID value range if the
--                 diffServMacAceVidOp is range(3)."
--    ::= { diffServMacAceEntry 9 }
--
--diffServMacAceVidBitmask OBJECT-TYPE
--    SYNTAX      Integer32 (0..'0FFF'h)
--    MAX-ACCESS  read-create
--    STATUS      current
--    DESCRIPTION "The bitmask of the VID if the diffServMacAceVidOp is
--                 equal(2). Default value is 0xfff."
--    ::= { diffServMacAceEntry 10 }
--
--diffServMacAceMaxVid OBJECT-TYPE
--    SYNTAX      Integer32 (1..4094)
--    MAX-ACCESS  read-create
--    STATUS      current
--    DESCRIPTION "Indicates the upper bound of the VID value range if the
--                 diffServMacAceVidOp is range(3). This object cannot be
--                 configured when the status of the entry,
--                 diffServMacAceStatus, is active(1)."
--    ::= { diffServMacAceEntry 11 }
--
--diffServMacAceEtherTypeOp OBJECT-TYPE
--    SYNTAX    INTEGER {
--        noOperator(1),
--        equal(2),
--        range(3)
--    }
--    MAX-ACCESS  read-create
--    STATUS      current
--    DESCRIPTION "Indicates how a packet's ether type is to be compared."
--    ::= { diffServMacAceEntry 12 }
--
--diffServMacAceEtherTypeBitmask OBJECT-TYPE
--    SYNTAX      Integer32 (0..'FFFF'h)
--    MAX-ACCESS  read-create
--    STATUS      current
--    DESCRIPTION "The bitmask of ether type if the diffServMacAceEtherTypeOp is
--                 equal(2). The default value is 'FFFF'h."
--    ::= { diffServMacAceEntry 13 }
--
--diffServMacAceMinEtherType OBJECT-TYPE
--        SYNTAX      Integer32 ('0600'h..'FFFF'h)
--        MAX-ACCESS  read-create
--        STATUS      current
--        DESCRIPTION "Indicates the lower bound of the ether type value range
--                     if the diffServMacAceEtherTypeOp is range(3)."
--        ::= { diffServMacAceEntry 14 }
--
--diffServMacAceMaxEtherType OBJECT-TYPE
--    SYNTAX      Integer32 ('0600'h..'FFFF'h)
--    MAX-ACCESS  read-create
--    STATUS      current
--    DESCRIPTION "Indicates the upper bound of the ether type value range if
--                 the diffServMacAceEtherTypeOp is range(3)."
--    ::= { diffServMacAceEntry 15 }
--
--diffServMacAceStatus OBJECT-TYPE
--    SYNTAX      RowStatus
--    MAX-ACCESS  read-create
--    STATUS      current
--    DESCRIPTION "This object is used to create a new row or modify or delete
--                 an existing row in this table. The status column has six
--                 defined values:
--
--                 The status column has six defined values:
--
--                      - 'active', which indicates that the conceptual row is
--                      available for use by the managed device;
--
--                      - 'notInService', which indicates that the conceptual
--                      row exists in the agent, but is unavailable for use by
--                      the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically set
--                      to active, making it available for use by the managed
--                      device;
--
--                      - 'createAndWait', which is supplied by a management
--                      station wishing to create a new instance of a
--                      conceptual row (but not make it available for use by
--                      the managed device); and,
--
--                      - 'destroy', which is supplied by a management station
--                      wishing to delete all of the instances associated with
--                      an existing conceptual row.
--
--                 Whereas five of the six values (all except 'notReady') may
--                 be specified in a management protocol set operation, only
--                 three values will be returned in response to a management
--                 protocol retrieval operation:  'notReady', 'notInService' or
--                 'active'.  That is, when queried, an existing conceptual row
--                 has only three states:  it is either available for use by
--                 the managed device (the status column has the value
--                 'active'); it is not available for use by the managed device,
--                 though the agent has sufficient information to make it so
--                 (the status column has the value 'notInService'); or, it is
--                 not available for use by the managed device, and an attempt
--                 to make it so would fail because the agent has insufficient
--                 information (the state column has the value 'notReady').
--
--                 For a detailed description of this object, please refer to
--                 SNMPv2-TC MIB."
--    ::= { diffServMacAceEntry 16 }
--
--diffServActionTable OBJECT-TYPE
--        SYNTAX      SEQUENCE OF DiffServActionEntry
--        MAX-ACCESS  not-accessible
--        STATUS      current
--        DESCRIPTION "Table for action."
--        ::= { diffServMgt 19 }
--
--diffServActionEntry OBJECT-TYPE
--        SYNTAX      DiffServActionEntry
--        MAX-ACCESS  not-accessible
--        STATUS      current
--        DESCRIPTION "Entry for action."
--        INDEX       { diffServActionIndex }
--        ::= { diffServActionTable 1 }
--
--DiffServActionEntry ::= SEQUENCE
--{
--    diffServActionIndex                 Integer32,
--    diffServActionList                  BITS,
--    diffServActionPktNewPri             Integer32,
--    diffServActionPktNewIpPrec          Integer32,
--    diffServActionPktNewDscp            Integer32,
--    diffServActionRedPktNewDscp         Integer32,
--    diffServActionRedDrop               EnabledStatus,
--    diffServActionStatus                RowStatus
--}
--
--diffServActionIndex OBJECT-TYPE
--        SYNTAX      Integer32
--        MAX-ACCESS  not-accessible
--        STATUS      current
--        DESCRIPTION "An index that uniquely identifies an entry in the
--                     action table."
--        ::= { diffServActionEntry 1 }
--
--diffServActionList OBJECT-TYPE
--        SYNTAX      BITS 
--                    {
--                        actionPktNewPri(0),
--                        actionPktNewIpPrec(1),
--                        actionPktNewDscp(2),
--                        actionRedPktNewDscp(3),
--                        actionRedDrop(4)
--                    }
--        MAX-ACCESS  read-create
--        STATUS      current
--        DESCRIPTION "The bitmap value used to identify which action
--                     capabilities are enabled on the entry. The
--                     actionPktNewPri, actionPktNewIpPrec and
--                     actionPktNewDscp can not be enabled at the 
--                     same time on the entry. The actionRedPktNewDscp and
--                     actionRedDrop can not be enabled at the same 
--                     time on the entry."
--        ::= { diffServActionEntry 2 }
--
--diffServActionPktNewPri OBJECT-TYPE
--        SYNTAX      Integer32 (0..7)
--        MAX-ACCESS  read-create
--        STATUS      current
--        DESCRIPTION "Specifies the new priority value for the packet when 
--                     the action is satisfied. If the actionPktNewPri bit of 
--                     the diffServActionList is not enabled, this object can 
--                     not be set."
--        ::= { diffServActionEntry 3 }
--
--diffServActionPktNewIpPrec  OBJECT-TYPE
--        SYNTAX      Integer32 (0..7)
--        MAX-ACCESS  read-create
--        STATUS      current
--        DESCRIPTION "Specifies the new IP precedence facility value for 
--                     the packet when the action is satisfied. If the 
--                     actionPktNewIpPrec bit of the diffServActionList is not 
--                     enabled, this object can not be set."
--        ::= { diffServActionEntry 4 }
--
--diffServActionPktNewDscp OBJECT-TYPE
--        SYNTAX      Integer32 (0..63)
--        MAX-ACCESS  read-create
--        STATUS      current
--        DESCRIPTION "Specifies the new DSCP value for the packet when 
--                     the action is satisfied. If the actionPktNewDscp bit of 
--                     the diffServActionList is not enabled, this object 
--                     can not be set."
--        ::= { diffServActionEntry 5 }
--
--diffServActionRedPktNewDscp OBJECT-TYPE
--        SYNTAX      Integer32 (0..63)
--        MAX-ACCESS  read-create
--        STATUS      current
--        DESCRIPTION "Specifies the new DSCP value for the red
--                     marking packet when the action is satisfied. If the
--                     actionRedPktNewDscp bit of the diffServActionList is 
--                     not enabled, this object can not be set."
--        ::= { diffServActionEntry 6 }
--
--diffServActionRedDrop OBJECT-TYPE
--        SYNTAX      EnabledStatus
--        MAX-ACCESS  read-only
--        STATUS      current
--        DESCRIPTION "The actionRedDrop bit of the            
--                     diffServActionList is for configuring this 
--                     object. If the value of this object is enabled, the 
--                     red marking packet will be dropped."
--        ::= { diffServActionEntry 7 }
--
--diffServActionStatus OBJECT-TYPE
--        SYNTAX      RowStatus
--        MAX-ACCESS  read-create
--        STATUS      current
--        DESCRIPTION "This object is used to create a new row, modify or
--                     delete an existing row in this table.
--                 The status column has six defined values:
--
--                 The status column has six defined values:
--
--                      - 'active', which indicates that the conceptual row 
--                         is available for use by the managed device;
--
--                      - 'notInService', which indicates that the conceptual
--                      row exists in the agent, but is unavailable for use 
--                      by the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically 
--                      set to active, making it available for use by the 
--                      managed device;
--
--                      - 'createAndWait', which is supplied by a management
--                      station wishing to create a new instance of a
--                      conceptual row (but not make it available for use by
--                      the managed device); and,
--
--                      - 'destroy', which is supplied by a management 
--                      station wishing to delete all of the instances 
--                      associated with an existing conceptual row.
--
--                 Whereas five of the six values (all except 'notReady') may
--                 be specified in a management protocol set operation, only
--                 three values will be returned in response to a management
--                 protocol retrieval operation:  'notReady', 'notInService' 
--                 or 'active'.  That is, when queried, an existing 
--                 conceptual row has only three states:  it is either 
--                 available for use by the managed device (the status column 
--                 has the value 'active'); it is not available for use by 
--                 the managed device, though the agent has sufficient 
--                 information to make it so (the status column has the value 
--                 'notInService'); or, it is not available for use by the 
--                 managed device, and an attempt to make it so would fail 
--                 because the agent has insufficient information (the state 
--                 column has the value 'notReady').
--
--                 For a detailed description of this object, please refer to
--                 SNMPv2-TC MIB."
--        ::= { diffServActionEntry 8 }
--
--diffServMeterTable OBJECT-TYPE
--        SYNTAX      SEQUENCE OF DiffServMeterEntry
--        MAX-ACCESS  not-accessible
--        STATUS      current
--        DESCRIPTION "Table for meter."
--        ::= { diffServMgt 20 }
--
--diffServMeterEntry OBJECT-TYPE
--        SYNTAX      DiffServMeterEntry
--        MAX-ACCESS  not-accessible
--        STATUS      current
--        DESCRIPTION "Entry for meter."
--        INDEX       { diffServActionIndex }
--        ::= { diffServMeterTable 1 }
--
--DiffServMeterEntry ::= SEQUENCE
--{
--    diffServMeterIndex       Integer32,
--    diffServMeterModel       INTEGER,
--    diffServMeterRate        Integer32,
--    diffServMeterBurstSize   Integer32,
--    diffServMeterInterval    Integer32,
--    diffServMeterStatus      RowStatus
--}
--
--diffServMeterIndex OBJECT-TYPE
--        SYNTAX      Integer32
--        MAX-ACCESS  not-accessible
--        STATUS      current
--        DESCRIPTION "An entry that describes a single set of token bucket
--                     parameters."
--        ::= { diffServMeterEntry 1 }
--
--diffServMeterModel OBJECT-TYPE
--    SYNTAX    INTEGER {
--            default(1),
--            flow(2),
--            trTcmColorBlind(3),
--            trTcmColorAware(4),
--            srTcmColorBlind(5),
--            srTcmColorAware(6)
--        }
--    MAX-ACCESS  read-create
--    STATUS      current
--    DESCRIPTION "The Metering algorithm associated with the Token Bucket
--                 parameters. The zeroDotZero indicates this is unknown."
--    ::= { diffServMeterEntry 2 }
--
--diffServMeterRate OBJECT-TYPE
--    SYNTAX      Integer32 (1..100000)
--    MAX-ACCESS  read-create
--    STATUS      current
--    DESCRIPTION "The token-bucket rate, in kilobits per second (kbps)."
--    ::= { diffServMeterEntry 3 }
--
--diffServMeterBurstSize OBJECT-TYPE
--    SYNTAX      Integer32 (64..1522)
--    MAX-ACCESS  read-create
--    STATUS      current
--    DESCRIPTION "The maximum number of bytes in a single transmission burst."
--    ::= { diffServMeterEntry 4 }
--
--diffServMeterInterval OBJECT-TYPE
--    SYNTAX      Integer32
--    MAX-ACCESS  read-create
--    STATUS      current
--    DESCRIPTION "The time interval used with the token bucket. "
--    ::= { diffServMeterEntry 5 }
--
--diffServMeterStatus OBJECT-TYPE
--    SYNTAX      RowStatus
--    MAX-ACCESS  read-create
--    STATUS      current
--    DESCRIPTION "This object is used to create a new row or modify or delete
--                 an existing row in this table. The status column has six
--                 defined values:
--
--                 The status column has six defined values:
--
--                      - 'active', which indicates that the conceptual row is
--                      available for use by the managed device;
--
--                      - 'notInService', which indicates that the conceptual
--                      row exists in the agent, but is unavailable for use by
--                      the managed device (see NOTE below);
--
--                      - 'notReady', which indicates that the conceptual row
--                      exists in the agent, but is missing information
--                      necessary in order to be available for use by the
--                      managed device;
--
--                      - 'createAndGo', which is supplied by a management
--                      station wishing to create a new instance of a
--                      conceptual row and to have its status automatically set
--                      to active, making it available for use by the managed
--                      device;
--
--                      - 'createAndWait', which is supplied by a management
--                      station wishing to create a new instance of a
--                      conceptual row (but not make it available for use by
--                      the managed device); and,
--
--                      - 'destroy', which is supplied by a management station
--                      wishing to delete all of the instances associated with
--                      an existing conceptual row.
--
--                 Whereas five of the six values (all except 'notReady') may
--                 be specified in a management protocol set operation, only
--                 three values will be returned in response to a management
--                 protocol retrieval operation:  'notReady', 'notInService' or
--                 'active'.  That is, when queried, an existing conceptual row
--                 has only three states:  it is either available for use by
--                 the managed device (the status column has the value
--                 'active'); it is not available for use by the managed device,
--                 though the agent has sufficient information to make it so
--                 (the status column has the value 'notInService'); or, it is
--                 not available for use by the managed device, and an attempt
--                 to make it so would fail because the agent has insufficient
--                 information (the state column has the value 'notReady').
--
--                 For a detailed description of this object, please refer to
--                 SNMPv2-TC MIB."
--    ::= { diffServMeterEntry 6 }

END
