EDGECORE-QCN-MIB DEFINITIONS ::= BEGIN

-- Version:    7.50
-- Date:       21 Mar 2010
-- 21 Mar 2010 Initial release
IMPORTS
    MODULE-IDENTITY, OBJECT-TYPE,Counter32,
    Gauge32, Unsigned32, IpAddress, TimeTicks   FROM SNMPv2-SMI
    InterfaceIndexOrZero, InterfaceIndex        FROM IF-MIB
    TruthValue, RowStatus, RowPointer,
    TEXTUAL-CONVENTION,DisplayString            FROM SNMPv2-TC
    Counter64, OBJECT-TYPE                      FROM SNMPv2-SMI
    PortList                                    FROM Q-BRIDGE-MIB
    Percents,rnd                                FROM EDGECORE-MIB;


rlQcnMib MODULE-IDENTITY
        LAST-UPDATED "201003210000Z"
        ORGANIZATION "Marvell Computer Communications Ltd."
        CONTACT-INFO
                "marvell.com"
        DESCRIPTION
                "Added:
                    rlQcnFeatureStatus
                    rlQcnPriorityStateTable
                    rlQcnIfStateTable
                    rlQcnCmnPriority
                    rlQcnCpPfcSetPoint
                    rlQcnCpNonPfcSetPoint
                    rlQcnCpFeedbackWeight
                    rlQcnCpMinSampleBase."

        ::= { rnd 202 }


-- QCN global enable status

rlQcnFeatureStatus OBJECT-TYPE
    SYNTAX     TruthValue
    MAX-ACCESS read-write
    STATUS     current
    DESCRIPTION
        "This scalar indicates QCN enable status."
    DEFVAL { false }
    ::= { rlQcnMib 1 }



-- QCN Priority state table

rlQcnPriorityStateTable OBJECT-TYPE
    SYNTAX SEQUENCE OF RlQcnPriorityStateEntry
    MAX-ACCESS not-accessible
    STATUS current
    DESCRIPTION
        "This table describes Quantized Congestion Notification per Priority state."
    ::= { rlQcnMib 2 }

rlQcnPriorityStateEntry OBJECT-TYPE
    SYNTAX RlQcnPriorityStateEntry
    MAX-ACCESS not-accessible
    STATUS current
    DESCRIPTION
        "Each entry in this table describes priority state.
         The index is represented by rlQcnPriorityStatePriority."
    INDEX { rlQcnPriorityStatePriority }
    ::= { rlQcnPriorityStateTable 1 }

RlQcnPriorityStateEntry ::= SEQUENCE {
        rlQcnPriorityStatePriority      INTEGER,
        rlQcnPriorityAdminStateEnable   TruthValue,
        rlQcnPriorityOperStateEnable    TruthValue,
        rlQcnPriorityAdminStateReason   INTEGER,
        rlQcnPriorityStateStatus        RowStatus
    }

rlQcnPriorityStatePriority OBJECT-TYPE
    SYNTAX INTEGER (0..7)
    MAX-ACCESS not-accessible
    STATUS current
    DESCRIPTION
        "802.1Q Priority."
    ::= { rlQcnPriorityStateEntry 1 }

rlQcnPriorityAdminStateEnable OBJECT-TYPE
    SYNTAX TruthValue
    MAX-ACCESS read-write
    STATUS current
    DESCRIPTION
        "Admin status of this priority."
    DEFVAL   { false }
    ::= { rlQcnPriorityStateEntry 2 }

rlQcnPriorityOperStateEnable OBJECT-TYPE
    SYNTAX TruthValue
    MAX-ACCESS read-only
    STATUS current
    DESCRIPTION
        "Operational status of this priority."
    DEFVAL   { false }
    ::= { rlQcnPriorityStateEntry 3 }

rlQcnPriorityAdminStateReason OBJECT-TYPE
    SYNTAX INTEGER {
                    ok(1),
                    queue0(2),
                    sharedQueue(3)
                   }
    MAX-ACCESS read-only
    STATUS current
    DESCRIPTION
        "Reason for admin status (if admin status not equal to oper)."
    DEFVAL   { ok }
    ::= { rlQcnPriorityStateEntry 4 }

rlQcnPriorityStateStatus OBJECT-TYPE
    SYNTAX  RowStatus
    MAX-ACCESS  read-write
    STATUS  current
    DESCRIPTION
       "The status of a table entry.
        It is used to delete/Add an entry from/to this table."
    ::= { rlQcnPriorityStateEntry 5 }



-- QCN Interface state table

rlQcnIfStateTable OBJECT-TYPE
    SYNTAX SEQUENCE OF RlQcnIfStateEntry
    MAX-ACCESS not-accessible
    STATUS current
    DESCRIPTION
        "This table describes Quantized Congestion Notification per interface state."
    ::= { rlQcnMib 3 }

rlQcnIfStateEntry OBJECT-TYPE
    SYNTAX RlQcnIfStateEntry
    MAX-ACCESS not-accessible
    STATUS current
    DESCRIPTION
        "Each entry in this table describes state of the interface.
         The index is represented by rlQcnIfStateIfIndex."
    INDEX { rlQcnIfStateIfIndex }
    ::= { rlQcnIfStateTable 1 }

RlQcnIfStateEntry ::= SEQUENCE {
        rlQcnIfStateIfIndex         INTEGER,
        rlQcnIfStateCpCreationEn    TruthValue,
        rlQcnIfStateStatus          RowStatus
    }

rlQcnIfStateIfIndex OBJECT-TYPE
    SYNTAX INTEGER
    MAX-ACCESS not-accessible
    STATUS current
    DESCRIPTION
        "IfIndex."
    ::= { rlQcnIfStateEntry 1 }

rlQcnIfStateCpCreationEn OBJECT-TYPE
    SYNTAX TruthValue
    MAX-ACCESS read-write
    STATUS current
    DESCRIPTION
        "Congestion point creation enable status.
        If CP creation is enabled for an interface,
        the system automatically creates a
        Congestion Point (CP) for a queue of that
        interface if at least one QCN priority
        (Oper state) is mapped to that queue."
    DEFVAL   { false }
    ::= { rlQcnIfStateEntry 2 }

rlQcnIfStateStatus OBJECT-TYPE
    SYNTAX  RowStatus
    MAX-ACCESS  read-write
    STATUS  current
    DESCRIPTION
       "The status of a table entry.
        It is used to delete/Add an entry from/to this table."
    ::= { rlQcnIfStateEntry 3 }


-- QCN Congestion notification message priority

rlQcnCmnPriority OBJECT-TYPE
    SYNTAX     INTEGER (0..7)
    MAX-ACCESS read-write
    STATUS     current
    DESCRIPTION
        "This scalar indicates priority which is used for all
        Congestion Notification Messages (CNMs) transmitted by the device."
    DEFVAL { 0 }
    ::= { rlQcnMib 4 }


-- QCN Congestion Point set point for PFC interface

rlQcnCpPfcSetPoint OBJECT-TYPE
    SYNTAX     INTEGER
    MAX-ACCESS read-write
    STATUS     obsolete
    DESCRIPTION
        "This scalar indicates QCN set-point of an
        egress queue on PFC enabled interface.
        Value of set-point is in bytes and in multiples of 512."
    DEFVAL { 26112 }
    ::= { rlQcnMib 5 }


-- QCN Congestion Point set point for non-PFC interface

rlQcnCpNonPfcSetPoint OBJECT-TYPE
    SYNTAX     INTEGER
    MAX-ACCESS read-write
    STATUS     obsolete
    DESCRIPTION
        "This scalar indicates QCN set-point of an
        egress queue on PFC disabled interface.
        Value of set-point is in bytes and in multiples of 512."
    DEFVAL { 26112 }
    ::= { rlQcnMib 6 }


-- QCN Congestion Point feedback-weight

rlQcnCpFeedbackWeight OBJECT-TYPE
    SYNTAX     INTEGER ( -10..10 )
    MAX-ACCESS read-write
    STATUS     current
    DESCRIPTION
        "This scalar indicates Feedback Weight of a QCN egress queue.
         The weight is equal to two to the power of this object.
         Thus, if this number contains a -1, weight = 1/2."
    DEFVAL { 1 }
    ::= { rlQcnMib 7 }


-- QCN Congestion Point min-sample-base

rlQcnCpMinSampleBase OBJECT-TYPE
    SYNTAX     INTEGER
    MAX-ACCESS read-write
    STATUS     current
    DESCRIPTION
        "This scalar indicates minimum number of bytes to
         enqueue in a QCN egress queue between transmissions
         of Congestion Notification Messages.
         Value of min-sample-base is in bytes and in multiples of 16."
    DEFVAL { 150000 }
    ::= { rlQcnMib 8 }

-- QCN Congestion Point set point for an interface

rlQcnCpSetPoint OBJECT-TYPE
    SYNTAX     INTEGER
    MAX-ACCESS read-write
    STATUS     current
    DESCRIPTION
        "This scalar indicates QCN set-point of an egress queue.
        Value of set-point is in bytes and in multiples of 512."
    DEFVAL { 26112 }
    ::= { rlQcnMib 9 }

END
