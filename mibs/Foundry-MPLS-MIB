Foundry-MPLS-MIB DEFINITIONS ::= BEGIN

-- SECTION 1: Top Level Definitions

-- Imports

IMPORTS
    MODULE-IDENTITY, OBJECT-TYPE, NOTIFICATION-TYPE,
    Unsigned32, Counter32, Counter64, IpAddress, Integer32
        FROM SNMPv2-SMI
    DisplayString, TimeStamp, RowStatus
        FROM SNMPv2-TC
    snMpls, snTraps
        FROM FOUNDRY-SN-ROOT-MIB
    TruthValue,TEXTUAL-CONVENTION
	 FROM SNMPv2-TC
    ClassOfService
        FROM FDRY-MPLS-L2VPN-MIB
    MplsTunnelAffinity
        FROM MPLS-TC-STD-MIB
    AreaID
        FROM FOUNDRY-SN-OSPF-GROUP-MIB;


mpls MODULE-IDENTITY
    LAST-UPDATED "201006020000Z"  -- 04 June 2010
    ORGANIZATION "Brocade Communications Systems, Inc."
    CONTACT-INFO
             "Technical Support Center
              130 Holger Way,
              San Jose, CA  95134
              Email:  ipsupport@brocade.com
              Phone: 1-800-752-8061
              URL:  www.brocade.com"
    DESCRIPTION
        "This is Brocade's proprietary MIB module for Multi-Protocol Label Switched Paths.

        Copyright 1996-2010 Brocade Communications Systems, Inc.
               All rights reserved.
               This Brocade Communications Systems SNMP Management Information Base Specification
               embodies Brocade Communications Systems' confidential and proprietary
               intellectual property. Brocade Communications Systems retains all
               title and ownership in the Specification, including any revisions.

               This Specification is supplied AS IS, and Brocade Communications Systems makes
               no warranty, either express or implied, as to the use,
               operation, condition, or performance of the specification, and any unintended
               consequence it may on the user environment."

    REVISION        "201006020000Z"  -- 04 June 2010
    DESCRIPTION
        "Changed the ORGANIZATION, CONTACT-INFO and DESCRIPTION fields."

    REVISION      "200802060000Z"		-- Feb 6, 2008
    DESCRIPTION
        "Add support for proprietary extensions to the VLL and VPLS mib."
    ::= { snMpls 1 }

mplsLspNotifications     OBJECT IDENTIFIER ::= { mpls 0 }
mplsInfo      OBJECT IDENTIFIER ::= { mpls 1 }
mplsLspInfo   OBJECT IDENTIFIER ::= { mpls 2 }
mplsVllInfo   OBJECT IDENTIFIER ::= { mpls 3 }
mplsVplsInfo   OBJECT IDENTIFIER ::= { mpls 4 }

mplsVersion OBJECT-TYPE
    SYNTAX     Unsigned32
    MAX-ACCESS read-only
    STATUS     current
    DESCRIPTION "MPLS version number."
    ::= { mplsInfo 1 }

--
-- Administrative groups, also known as resource classes or link colors,
-- allows MPLS-enabled interfaces to be assigned to various classes.
-- For ease of use to a user, a groupname can be associated to a single or
-- multiple administrative group.
-- Up to 32 administrative groups can be configured on the device.
--

brcdMplsAdminGroupTable OBJECT-TYPE
    SYNTAX     SEQUENCE OF BrcdMplsAdminGroupEntry
    MAX-ACCESS not-accessible
    STATUS     current
    DESCRIPTION
        "List of administrative groups (by ID) that have a configured group name."
    ::= { mplsInfo 2 }

brcdMplsAdminGroupEntry OBJECT-TYPE
    SYNTAX     BrcdMplsAdminGroupEntry
    MAX-ACCESS not-accessible
    STATUS     current
    DESCRIPTION
        "Information about an administrative group entry."
    INDEX { brcdMplsAdminGroupId }
    ::= { brcdMplsAdminGroupTable 1 }

BrcdMplsAdminGroupEntry ::=
    SEQUENCE {
        brcdMplsAdminGroupId    		Unsigned32,
        brcdMplsAdminGroupName  		DisplayString,
        brcdMplsAdminGroupRowStatus  	RowStatus
}

brcdMplsAdminGroupId OBJECT-TYPE
    SYNTAX     Unsigned32 (1..32)
    MAX-ACCESS not-accessible
    STATUS     current
    DESCRIPTION
        "Identifies the administrative group ID in 1-based.
         The end user of this object must convert this to 0-based since this
         maps to the bit position in the constraint-based link selection."
    ::= { brcdMplsAdminGroupEntry 1 }

brcdMplsAdminGroupName OBJECT-TYPE
    SYNTAX     DisplayString (SIZE (1..32))
    MAX-ACCESS read-create
    STATUS     current
    DESCRIPTION
        "The group name that this administrative group is associated with."
    ::= { brcdMplsAdminGroupEntry 2 }

brcdMplsAdminGroupRowStatus OBJECT-TYPE
    SYNTAX     RowStatus
    MAX-ACCESS read-create
    STATUS     current
    DESCRIPTION
        "The row status of an entry.
         Note: Set request to this table is not supported in this release.
         Always returns 'active' for the existing entries."
    ::= { brcdMplsAdminGroupEntry 3 }


--
-- MPLS-enabled Interface Table
--

brcdMplsInterfaceTable OBJECT-TYPE
    SYNTAX     SEQUENCE OF BrcdMplsInterfaceEntry
    MAX-ACCESS not-accessible
    STATUS     current
    DESCRIPTION
        "List of MPLS-enabled Interfaces."
    ::= { mplsInfo 3 }

brcdMplsInterfaceEntry OBJECT-TYPE
    SYNTAX     BrcdMplsInterfaceEntry
    MAX-ACCESS not-accessible
    STATUS     current
    DESCRIPTION
        "Information about an MPLS interface entry."
    INDEX { brcdMplsInterfaceIndex }
    ::= { brcdMplsInterfaceTable 1 }

BrcdMplsInterfaceEntry::=
    SEQUENCE {
        brcdMplsInterfaceIndex        	Unsigned32,
        brcdMplsInterfaceAdminGroup   	MplsTunnelAffinity,
        brcdMplsInterfaceRowStatus     	RowStatus
}

brcdMplsInterfaceIndex OBJECT-TYPE
    SYNTAX     Unsigned32
    MAX-ACCESS not-accessible
    STATUS     current
    DESCRIPTION
        "The ifIndex of the MPLS-enabled port or VE interface."
    ::= { brcdMplsInterfaceEntry 1 }

brcdMplsInterfaceAdminGroup OBJECT-TYPE
    SYNTAX     MplsTunnelAffinity
    MAX-ACCESS read-create
    STATUS     current
    DESCRIPTION
        "Specifies which administrative groups this MPLS-enabled
         interface belongs to."
    ::= { brcdMplsInterfaceEntry 2 }

brcdMplsInterfaceRowStatus     OBJECT-TYPE
    SYNTAX     RowStatus
    MAX-ACCESS read-create
    STATUS     current
    DESCRIPTION
        "The row status of an entry.
         Note: Set request to this table is not supported in this release.
         Always returns 'active' for the existing entries."
    ::= { brcdMplsInterfaceEntry 3 }


mplsConfiguredLsps OBJECT-TYPE
    SYNTAX     Unsigned32
    MAX-ACCESS read-only
    STATUS     deprecated
    DESCRIPTION "Number of configured LSPs. Sum of RSVP and static configured LSPs.
                    DEPRECATED BY mplsTunnelConfigured IN rfc3812-MPLS-TE-STD-MIB."
    ::= { mplsLspInfo 1 }

mplsActiveLsps OBJECT-TYPE
    SYNTAX     Unsigned32
    MAX-ACCESS read-only
    STATUS     deprecated
    DESCRIPTION "Number of active LSPs. Sum of RSVP, LDP and static LSPs.
                    DEPRECATED BY mplsTunnelActive IN rfc3812-MPLS-TE-STD-MIB."
    ::= { mplsLspInfo 2 }


--
-- MPLS LSP Table
--

mplsLspTable OBJECT-TYPE
    SYNTAX     SEQUENCE OF MplsLspEntry
    MAX-ACCESS not-accessible
    STATUS     current
    DESCRIPTION "List of Configured Label Switched Paths."
    ::= { mplsLspInfo 3 }

mplsLspEntry OBJECT-TYPE
    SYNTAX     MplsLspEntry
    MAX-ACCESS not-accessible
    STATUS     current
    DESCRIPTION
        "Entry containing information about a particular
         Label Switched Path."
    INDEX { mplsLspSignalingProto, mplsLspIndex }
    ::= { mplsLspTable 1 }

MplsLspEntry ::=
    SEQUENCE {
        mplsLspSignalingProto      	INTEGER,
        mplsLspIndex            		Unsigned32,
        mplsLspName             		DisplayString,
        mplsLspState            		INTEGER,
        mplsLspPackets          		Counter64,
        mplsLspAge              		TimeStamp,
        mplsLspTimeUp           		TimeStamp,
        mplsLspPrimaryTimeUp    	TimeStamp,
        mplsLspTransitions      		Counter32,
        mplsLspLastTransition   	TimeStamp,
        mplsLspFrom             		IpAddress,
        mplsLspTo               		IpAddress,
        mplsLspPathName               DisplayString,
        mplsLspPathType                INTEGER,
        mplsLspAdaptive             	TruthValue,
        mplsLspBfdSessionId      	Unsigned32,
        mplsLspReoptimizeTimer  	Unsigned32,
        mplsLspCoS			   	ClassOfService,
        mplsLspHopLimit			Unsigned32,
        mplsLspCspf   			INTEGER,
        mplsLspCspfTieBreaker		INTEGER,
        mplsLspFrrMode			INTEGER,
        mplsLspFrrSetupPriority	Unsigned32,
        mplsLspFrrHoldingPriority	Unsigned32,
        mplsLspFrrHopLimit		Unsigned32,
        mplsLspFrrBandwidth		Unsigned32,
        mplsLspFrrAdmGrpIncludeAny		MplsTunnelAffinity,
        mplsLspFrrAdmGrpIncludeAll		MplsTunnelAffinity,
        mplsLspFrrAdmGrpExcludeAny		MplsTunnelAffinity,
        mplsLspPathSelectMode			INTEGER,
        mplsLspPathSelectPathname              DisplayString,
        mplsLspPathSelectRevertTimer		Unsigned32,
        mplsLspShortcutOspfAllowed		TruthValue,
        mplsLspShortcutIsisAllowed			TruthValue,
        mplsLspShortcutIsisLevel			INTEGER,
        mplsLspShortcutIsisAnnounce		TruthValue,
        mplsLspShortcutIsisAnnounceMetric	Integer32,
        mplsLspShortcutIsisRelativeMetric	Integer32
}

mplsLspSignalingProto OBJECT-TYPE
    SYNTAX     INTEGER {
        ldp(1),
        rsvp(2)
    }
    MAX-ACCESS not-accessible
    STATUS     current
    DESCRIPTION "MPLS signaling protocol used by this LSP."
    ::= { mplsLspEntry 1 }

mplsLspIndex OBJECT-TYPE
    SYNTAX     Unsigned32
    MAX-ACCESS not-accessible
    STATUS     current
    DESCRIPTION "The unique index of the LSP in the system for a given signaling protocol."
    ::= { mplsLspEntry 2 }

mplsLspName OBJECT-TYPE
    SYNTAX     DisplayString (SIZE (0..32))
    MAX-ACCESS read-only
    STATUS     current
    DESCRIPTION "Name of the Label Switched Path."
    ::= { mplsLspEntry 3 }

mplsLspState OBJECT-TYPE
    SYNTAX     INTEGER {
               unknown(1),
               up(2),
               down(3)
    }
    MAX-ACCESS read-only
    STATUS     current
    DESCRIPTION "The operational state of the LSP."
    ::= { mplsLspEntry 4 }

mplsLspPackets OBJECT-TYPE
    SYNTAX     Counter64
    MAX-ACCESS read-only
    STATUS     current
    DESCRIPTION
        "The number of egress Layer-3 VPN and IPoMPLS packets
        meeting the in-label and tunnel criteria."
    ::= { mplsLspEntry 5 }

mplsLspAge OBJECT-TYPE
    SYNTAX     TimeStamp
    MAX-ACCESS read-only
    STATUS     current
    DESCRIPTION
        "The age, since creation of this LSP in 10-millisecond periods."
    ::= { mplsLspEntry 6 }

mplsLspTimeUp OBJECT-TYPE
    SYNTAX     TimeStamp
    MAX-ACCESS read-only
    STATUS     current
    DESCRIPTION
        "The total time in 10-millisecond units that this
         LSP has been operational. The percentage up time
         can be determined by computing
         (mplsLspTimeUp/mplsLspAge * 100 %)."
    ::= { mplsLspEntry 7 }

mplsLspPrimaryTimeUp OBJECT-TYPE
    SYNTAX     TimeStamp
    MAX-ACCESS read-only
    STATUS     current
    DESCRIPTION
        "The total time in 10-millisecond units that this
         LSP's primary path has been operational. The
         percentage contribution of the primary
         path to the operational time is given by
         (mplsLspPrimaryTimeUp/mplsLspTimeUp * 100) %."
    ::= { mplsLspEntry 8 }

mplsLspTransitions OBJECT-TYPE
    SYNTAX     Counter32
    MAX-ACCESS read-only
    STATUS     current
    DESCRIPTION
        "The number of state transitions (up -> down and
         down -> up) this LSP has undergone."
    ::= { mplsLspEntry 9 }

mplsLspLastTransition OBJECT-TYPE
    SYNTAX     TimeStamp
    MAX-ACCESS read-only
    STATUS     current
    DESCRIPTION
        "The time in 10-millisecond units since the last
         transition occurred on this LSP."
    ::= { mplsLspEntry 10 }

mplsLspFrom OBJECT-TYPE
    SYNTAX     IpAddress
    MAX-ACCESS read-only
    STATUS     current
    DESCRIPTION
        "Source IP address of this LSP."
    ::= { mplsLspEntry 11 }

mplsLspTo OBJECT-TYPE
    SYNTAX     IpAddress
    MAX-ACCESS read-only
    STATUS     current
    DESCRIPTION
        "Destination IP address of this LSP."
    ::= { mplsLspEntry 12 }

mplsLspPathName OBJECT-TYPE
    SYNTAX     DisplayString (SIZE(0..16))
    MAX-ACCESS read-only
    STATUS     current
    DESCRIPTION
        "The name of the active path for this LSP, if
         any.  If there is none, the name should be
         empty; in that case, the rest of the fields
         in mplsLspEntry are meaningless."
    ::= { mplsLspEntry 13 }

mplsLspPathType OBJECT-TYPE
    SYNTAX     INTEGER {
        other(1),
        primary(2),
        standby(3),
        secondary(4)
    }
    MAX-ACCESS read-only
    STATUS     current
    DESCRIPTION
        "The type of path that is active, i.e., a
         primary path, a standby path, or a generic
         secondary path. This field is meaningless
         unless mplsLspPathName is not empty"
    ::= { mplsLspEntry 14 }

mplsLspAdaptive OBJECT-TYPE
    SYNTAX          TruthValue
    MAX-ACCESS read-only
    STATUS          current
    DESCRIPTION
        "Indicates if the LSP supports adaptive mechanism or not."
    ::= { mplsLspEntry 15 }

mplsLspBfdSessionId OBJECT-TYPE
    SYNTAX          Unsigned32
    MAX-ACCESS read-only
    STATUS          current
    DESCRIPTION
        "The BFD session ID associated to this LSP. Zero indicates
         there is no BFD session for this LSP. Non-zero value is an
         index to an entry in the bfdSessTable"
    ::= { mplsLspEntry 16 }

 mplsLspReoptimizeTimer OBJECT-TYPE
    SYNTAX          Unsigned32 ( 0 | 300..65535 )
    MAX-ACCESS read-only
    STATUS          current
    DESCRIPTION
        "The number of seconds from the beginning of one reoptimization
         attempt to the beginning of the next attempt."
    ::= { mplsLspEntry 17 }

mplsLspCoS OBJECT-TYPE
    SYNTAX          ClassOfService
    MAX-ACCESS read-only
    STATUS          current
    DESCRIPTION
        "The Class of Service for this LSP."
    ::= { mplsLspEntry 18 }

mplsLspHopLimit OBJECT-TYPE
    SYNTAX          Unsigned32 ( 0..255 )
    MAX-ACCESS read-only
    STATUS          current
    DESCRIPTION
        "The number of hops this LSP can traverse."
    ::= { mplsLspEntry 19 }

mplsLspCspf OBJECT-TYPE
    SYNTAX          INTEGER {
               enabled(1),
               disabled(2)
    }
    MAX-ACCESS read-only
    STATUS          current
    DESCRIPTION
        "Indicates if CSPF path calculation is enabled
         on this LSP."
    ::= { mplsLspEntry 20 }

mplsLspCspfTieBreaker OBJECT-TYPE
    SYNTAX          INTEGER {
               random(1),
               leastFill(2),
               mostFill(3)
    }
    MAX-ACCESS read-only
    STATUS          current
    DESCRIPTION
        "The tie-breaker to use for selecting CSPF
         equal-cost paths. The value of this variable is
         meaningless if the mplsLspCspf is 'disabled'."
    ::= { mplsLspEntry 21 }

mplsLspFrrMode OBJECT-TYPE
    SYNTAX          INTEGER {
               none(1),
               detour(2),
               facility(3)
    }
    MAX-ACCESS read-only
    STATUS          current
    DESCRIPTION
        "Indicates which protection method is to be used
         for Fast Reroute. 'detour' means one-to-one backup
         and 'facility' for facility backup."
    ::= { mplsLspEntry 22 }

mplsLspFrrSetupPriority OBJECT-TYPE
    SYNTAX          Unsigned32 (0..7)
    MAX-ACCESS read-only
    STATUS          current
    DESCRIPTION
        "The setup priority for MPLS Fast Reroute.
         The value of this variable is meaningless if the
         mplsLspFrrMode is 'none'."
    ::= { mplsLspEntry 23 }

mplsLspFrrHoldingPriority OBJECT-TYPE
    SYNTAX          Unsigned32 (0..7)
    MAX-ACCESS read-only
    STATUS          current
    DESCRIPTION
        "The hold priority for MPLS Fast Reroute.
         The value of this variable is meaningless if the
         mplsLspFrrMode is 'none'."
    ::= { mplsLspEntry 24 }

mplsLspFrrHopLimit OBJECT-TYPE
    SYNTAX          Unsigned32 ( 0..255 )
    MAX-ACCESS read-only
    STATUS          current
    DESCRIPTION
        "The hop limit for MPLS Fast Reroute.
         The value of this variable is meaningless if the
         mplsLspFrrMode is 'none'."
    ::= { mplsLspEntry 25 }

mplsLspFrrBandwidth OBJECT-TYPE
    SYNTAX          Unsigned32 (0..2147483647)
    MAX-ACCESS read-only
    STATUS          current
    DESCRIPTION
        "The bandwidth constraint for MPLS Fast Reroute.
         The value 0 means that the detour route uses a
         best-effort value for bandwidth.
         The value of this variable is meaningless if the
         mplsLspFrrMode is 'none'."
    ::= { mplsLspEntry 26 }

mplsLspFrrAdmGrpIncludeAny OBJECT-TYPE
    SYNTAX          MplsTunnelAffinity
    MAX-ACCESS read-only
    STATUS          current
    DESCRIPTION
        "The administrative group setting that the device
         includes any of the interfaces that are members of
         the group when calculating detour routes for this LSP.
         The value of this variable is meaningless if the
         mplsLspFrrMode is 'none'."
    ::= { mplsLspEntry 27 }

mplsLspFrrAdmGrpIncludeAll OBJECT-TYPE
    SYNTAX          MplsTunnelAffinity
    MAX-ACCESS read-only
    STATUS          current
    DESCRIPTION
        "The administrative group setting that an interface
         must be a member of to be considered in a detour
         route for the LSP. Any interface that is not a member
         of all the groups is eliminated from consideration.
         The value of this variable is meaningless if the
         mplsLspFrrMode is 'none'."
    ::= { mplsLspEntry 28 }

mplsLspFrrAdmGrpExcludeAny OBJECT-TYPE
    SYNTAX          MplsTunnelAffinity
    MAX-ACCESS read-only
    STATUS          current
    DESCRIPTION
        "The administrative group setting that the device
         excludes any of the interfaces that are members of
         the group when calculating detour routes for this LSP.
         The value of this variable is meaningless if the
         mplsLspFrrMode is 'none'."
    ::= { mplsLspEntry 29 }

mplsLspPathSelectMode OBJECT-TYPE
    SYNTAX          INTEGER {
               auto(1),
               manual(2),
               unconditional(3)
    }
    MAX-ACCESS read-only
    STATUS          current
    DESCRIPTION
        "Indicates the path selection mode to use.
         Auto-select is the default mode. I this mode, the
         primary path is always selected to carry traffic when
         the primary path has stayed operating in the working
         state for at least the amount of time specified in
         mplsLspPathSelectRevertTimer.
         For manual-select, traffic is switched to a user-
         selected path specified in mplsLspPathSelectPathname
         after the selected path has stayed operating in the
         working state for at least the amount of time specified
         in mplsLspPathSelectRevertTimer.
         For unconditional-select, traffic is switched to and
         stays on the selected path regardless of the path's
         condition even if it is in a failure state."
    ::= { mplsLspEntry 30 }

mplsLspPathSelectPathname OBJECT-TYPE
    SYNTAX     DisplayString (SIZE (0..64))
    MAX-ACCESS read-only
    STATUS     current
    DESCRIPTION
        "The user-selected pathname when the mplsLspPathSelectMode
         is either 'manual' or 'unconditional'."
    ::= { mplsLspEntry 31 }

mplsLspPathSelectRevertTimer OBJECT-TYPE
    SYNTAX          Unsigned32 (0..65535)
    MAX-ACCESS read-only
    STATUS          current
    DESCRIPTION
        "The number of seconds to wait after the primary or selected
         path comes up before traffic reverts to that path.
         A value of 0 indicates that it will switch immediately
         after the current working path goes down."
    ::= { mplsLspEntry 32 }

mplsLspShortcutOspfAllowed OBJECT-TYPE
    SYNTAX          TruthValue
    MAX-ACCESS read-only
    STATUS          current
    DESCRIPTION
        "Indicates that this LSP allows shortcut between nodes in an AS.
         OSPF includes the LSP in its SPF calculation."
    ::= { mplsLspEntry 33 }

mplsLspShortcutIsisAllowed OBJECT-TYPE
    SYNTAX          TruthValue
    MAX-ACCESS read-only
    STATUS          current
    DESCRIPTION
        "Indicates that this LSP allows shortcut through the
         network to a destination based on the path's cost (metric).
         Traffic is forwarded through this LSP to destinations
         within the IS-IS routing domain. IS-IS includes the LSP
         in its SPF calculation."
    ::= { mplsLspEntry 34 }

mplsLspShortcutIsisLevel OBJECT-TYPE
    SYNTAX          INTEGER {
               level1(1),
               level2(2),
               level1and2(3)
    }
    MAX-ACCESS read-only
    STATUS          current
    DESCRIPTION
        "Indicates the level of IS-IS routing enabled on the device.
         The value of this variable is meaningless if the
         mplsLspShortcutIsisAllowed is 'false'."
    ::= { mplsLspEntry 35 }

mplsLspShortcutIsisAnnounce OBJECT-TYPE
    SYNTAX          TruthValue
    MAX-ACCESS read-only
    STATUS          current
    DESCRIPTION
        "Indicates that this IS-IS shortcut will be announced or
         advertised. The metric to announce is specified by
         mplsLspShortcutIsisAnnounceMetric.
         The value of this variable is meaningless if the
         mplsLspShortcutIsisAllowed is 'false'."
    ::= { mplsLspEntry 36 }

mplsLspShortcutIsisAnnounceMetric OBJECT-TYPE
    SYNTAX          Integer32 (1..16777215)
    MAX-ACCESS read-only
    STATUS          current
    DESCRIPTION
        "Indicates the metric value to announce for this shortcut.
         The value of this variable is meaningless if the
         mplsLspShortcutIsisAnnounce is 'false'. Default value is 10."
    ::= { mplsLspEntry 37 }

mplsLspShortcutIsisRelativeMetric OBJECT-TYPE
    SYNTAX          Integer32 (-16777215..16777215)
    MAX-ACCESS read-only
    STATUS          current
    DESCRIPTION
        "Indicates the relative metric used to compute the LSP cost
         when announce is not enabled.
         The value of this variable is meaningless if the
         mplsLspShortcutIsisAllowed is 'false'."
    ::= { mplsLspEntry 38 }


-- definition of MPLS traps
--
snMplsLspUp NOTIFICATION-TYPE
OBJECTS { mplsLspName,
          mplsLspPathName } -- LspPath
STATUS current
DESCRIPTION
     "An mplsLspUp trap signifies that the
     specified LSP is up. The current active
     path for the LSP is mplsLspPathName."
--#TYPE "Foundry Trap: MPLS LSP Up"
--#SUMMARY "LSP %s using path %s is up."
--#ARGUMENTS { 0, 1 }
--#SEVERITY INFORMATIONAL
--#STATE OPERATIONAL
::= { snTraps 1010 }


snMplsLspDown NOTIFICATION-TYPE
OBJECTS { mplsLspName,
          mplsLspPathName } -- LspPath
STATUS current
DESCRIPTION
     "An mplsLspDown trap signifies that the
     specified LSP is down, because the current
     active path mplsLspPathName went down."
--#TYPE "Foundry Trap: MPLS LSP Down"
--#SUMMARY "LSP %s using path %s is down."
--#ARGUMENTS { 0, 1 }
--#SEVERITY INFORMATIONAL
--#STATE OPERATIONAL
::= { snTraps 1011 }


snMplsLspChange NOTIFICATION-TYPE
OBJECTS { mplsLspName,
          mplsLspPathName } -- LspPath
STATUS current
DESCRIPTION
     "An mplsLspChange trap signifies that the
     the specified LSP has switched traffic to
     the new active path 'toLspPath'. The LSP maintains
     up state before and after the switch over"
--#TYPE "Foundry Trap: MPLS LSP Change"
--#SUMMARY "LSP %s switches to new active path %s."
--#ARGUMENTS { 0, 1 }
--#SEVERITY INFORMATIONAL
--#STATE OPERATIONAL
::= { snTraps 1012 }

END
