--
-- NMS ERPS MIB
--    2010.04.20 Lysh
--    Last Updated: 2010.5.10
--

NMS-ERPS-MIB DEFINITIONS ::= BEGIN

	IMPORTS
		OBJECT-TYPE
			FROM RFC-1212
		DisplayString
			FROM RFC1213-MIB
		nmslocal
			FROM NMS-SMI;
			
-- 1.3.6.1.4.1.3320.2.X
nmsERPS OBJECT IDENTIFIER ::={ nmslocal 231 }

	-- 1.3.6.1.4.1.3320.2.X.1
	nmsERPSRings OBJECT-TYPE
		SYNTAX INTEGER
		ACCESS read-only
		STATUS mandatory
		DESCRIPTION
			"The number of ethernet ring instances."
		::={ nmsERPS 1 }
		
	-- 1.3.6.1.4.1.3320.2.X.2
	nmsERPSInconsistenceCheck OBJECT-TYPE
		SYNTAX INTEGER {
			disabled(0),
			enabled(1)
		}
		ACCESS read-write
		STATUS mandatory
		DESCRIPTION
			"A value indicates that the ring-port inconsistence check is enabled or disabled."
		::={ nmsERPS 2 }
		
	-- 1.3.6.1.4.1.3320.2.X.3
	nmsERPSPduRx OBJECT-TYPE
		SYNTAX INTEGER
		ACCESS read-only
		STATUS mandatory
		DESCRIPTION
			"The total number of input PDUs."
		::={ nmsERPS 3 }
		
	-- 1.3.6.1.4.1.3320.2.X.4
	nmsERPSPduRxDropped OBJECT-TYPE
		SYNTAX INTEGER
		ACCESS read-only
		STATUS mandatory
		DESCRIPTION
			"The number of input discarded PDUs."
		::={ nmsERPS 4 }
		
	-- 1.3.6.1.4.1.3320.2.X.5
	nmsERPSPduTx OBJECT-TYPE
		SYNTAX INTEGER
		ACCESS read-only
		STATUS mandatory
		DESCRIPTION
			"The total number of output PDUs."
		::={ nmsERPS 5 }
		
	-- 1.3.6.1.4.1.3320.2.X.6
	nmsERPSRingTable OBJECT-TYPE
		SYNTAX  SEQUENCE OF NMSERPSRingTableEntry
		ACCESS  not-accessible
		STATUS  mandatory
		DESCRIPTION
			"A table that contains information of rings."
		::= { nmsERPS 6 }
		
		-- 1.3.6.1.4.1.3320.2.X.6.1
		nmsERPSRingTableEntry OBJECT-TYPE
			SYNTAX NMSERPSRingTableEntry
			ACCESS  not-accessible
			STATUS  mandatory
			DESCRIPTION
				"A table that contains information of rings."
			INDEX { nmsERPSRingID }
			::= { nmsERPSRingTable 1 }
			
		NMSERPSRingTableEntry ::=
			SEQUENCE {
				nmsERPSRingID
					INTEGER,
				nmsERPSRingNodeID
					DisplayString,
				nmsERPSRingPorts
					INTEGER,
				nmsERPSRingRole
					INTEGER,
				nmsERPSRingState
					INTEGER,
				nmsERPSRingWTR
					INTEGER,
				nmsERPSRingWtrWhile
					INTEGER,
				nmsERPSRingSignalFail
					INTEGER,
				nmsERPSRingSending
					DisplayString,
				nmsERPSRingRplOwnerID
					DisplayString,
				nmsERPSRingRplOwnerMAC
					DisplayString,
				nmsERPSRingDiscovering
					INTEGER,
				nmsERPSRingDiscoverWhile
					INTEGER,
				nmsERPSRingPriorityValue
					INTEGER,
				nmsERPSRingWtrTime
					INTEGER,
				nmsERPSRingGuardTime
					INTEGER,
				nmsERPSRingSendTime
					INTEGER,
				nmsERPSRingDiscoveryTime
					INTEGER,
				nmsERPSRingDpduInterval
					INTEGER,
				nmsERPSRingDiscoveryCount
					INTEGER,
				nmsERPSRingDiscoveryLastDuration
					INTEGER,
				nmsERPSRingDiscoveryLastElapsed
					INTEGER,
				nmsERPSRingAdminStatus
					INTEGER,
				nmsERPSRingPort1
					INTEGER,
				nmsERPSRingPort1AdminType
					INTEGER,
				nmsERPSRingPort1OperType
					INTEGER,
				nmsERPSRingPort1State
					INTEGER,
				nmsERPSRingPort1Status
					INTEGER,
				nmsERPSRingPort2
					INTEGER,
				nmsERPSRingPort2AdminType
					INTEGER,
				nmsERPSRingPort2OperType
					INTEGER,
				nmsERPSRingPort2State
					INTEGER,
				nmsERPSRingPort2Status
					INTEGER
			}
		
			-- 1.3.6.1.4.1.3320.2.X.6.1.1
			nmsERPSRingID OBJECT-TYPE
				SYNTAX INTEGER
				ACCESS read-only
				STATUS mandatory
				DESCRIPTION
					"The index of ring instances."
				::={ nmsERPSRingTableEntry 1 }
				
			-- 1.3.6.1.4.1.3320.2.X.6.1.2
			nmsERPSRingNodeID OBJECT-TYPE
				SYNTAX  DisplayString (SIZE (0..32))
              	ACCESS  read-only
              	STATUS  mandatory
              	DESCRIPTION
              		"The ring node identifier composed of a priority value
              		and the bridge MAC address."
				::={ nmsERPSRingTableEntry 2 }
				
			-- 1.3.6.1.4.1.3320.2.X.6.1.3
			nmsERPSRingPorts OBJECT-TYPE
				SYNTAX INTEGER
				ACCESS read-only
				STATUS mandatory
				DESCRIPTION
					"The number of interfaces which are configured in a ring."
				::={ nmsERPSRingTableEntry 3 }
				
			-- 1.3.6.1.4.1.3320.2.X.6.1.4
			nmsERPSRingRole OBJECT-TYPE
				SYNTAX INTEGER {
					notRplOwner(0),
					rplOwner(1)
				}
				ACCESS read-only
				STATUS mandatory
				DESCRIPTION
					"A value indicates whether one port of the ring node
					is the Ring protection link(RPL)."
				::={ nmsERPSRingTableEntry 4 }
				
			-- 1.3.6.1.4.1.3320.2.X.6.1.5
			nmsERPSRingState OBJECT-TYPE
				SYNTAX INTEGER {
					idle(0),
					protection(1)
				}
				ACCESS read-only
				STATUS mandatory
				DESCRIPTION
					"The ring protection state machine value."
				::={ nmsERPSRingTableEntry 5 }
				
			-- 1.3.6.1.4.1.3320.2.X.6.1.6
			nmsERPSRingWTR OBJECT-TYPE
				SYNTAX INTEGER {
					notWaitToRestore(0),
					waitToRestore(1)
				}
				ACCESS read-only
				STATUS mandatory
				DESCRIPTION
					"This value from the RPL-Owner indicates whether it is Waiting to restore."
				::={ nmsERPSRingTableEntry 6 }
				
			-- 1.3.6.1.4.1.3320.2.X.6.1.7
			nmsERPSRingWtrWhile OBJECT-TYPE
				SYNTAX INTEGER
				ACCESS read-only
				STATUS mandatory
				DESCRIPTION
					"The Wait-to-restore timer value, in seconds,
					which is the time left before the RPL-Owner restores from Protection state."
				::={ nmsERPSRingTableEntry 7 }
				
			-- 1.3.6.1.4.1.3320.2.X.6.1.8
			nmsERPSRingSignalFail OBJECT-TYPE
				SYNTAX INTEGER {
					noSignalFail(0),
					signalFail(1)
				}
				ACCESS read-only
				STATUS mandatory
				DESCRIPTION
					"A value indicates if a ring port is failed."
				::={ nmsERPSRingTableEntry 8 }
				
			-- 1.3.6.1.4.1.3320.2.X.6.1.9
			nmsERPSRingSending OBJECT-TYPE
				SYNTAX DisplayString (SIZE (0..32))
				ACCESS read-only
				STATUS mandatory
				DESCRIPTION
					"The type of PDUs being sent."
				::={ nmsERPSRingTableEntry 9 }
				
			-- 1.3.6.1.4.1.3320.2.X.6.1.10
			nmsERPSRingRplOwnerID OBJECT-TYPE
				SYNTAX  DisplayString (SIZE (0..32))
              	ACCESS  read-only
              	STATUS  mandatory
              	DESCRIPTION
              		"The RPL-Owner's identifier,
              		recorded from a superior discovery PDU."
				::={ nmsERPSRingTableEntry 10 }
				
			-- 1.3.6.1.4.1.3320.2.X.6.1.11
			nmsERPSRingRplOwnerMAC OBJECT-TYPE
				SYNTAX  DisplayString (SIZE (0..32))
              	ACCESS  read-only
              	STATUS  mandatory
              	DESCRIPTION
              		"The RPL-Owner's bridge MAC address,
              		recorded from a NR-RB PDU."
				::={ nmsERPSRingTableEntry 11 }
				
			-- 1.3.6.1.4.1.3320.2.X.6.1.12
			nmsERPSRingDiscovering OBJECT-TYPE
				SYNTAX INTEGER {
					notDiscovering(0),
					discovering(1),
					disabled(2),
					enabled(3)
				}
				ACCESS read-write
				STATUS mandatory
				DESCRIPTION
					"A value indicates if the ring discovery process is running."
				::={ nmsERPSRingTableEntry 12 }
				
			-- 1.3.6.1.4.1.3320.2.X.6.1.13
			nmsERPSRingDiscoverWhile OBJECT-TYPE
				SYNTAX INTEGER
				ACCESS read-only
				STATUS mandatory
				DESCRIPTION
					"The discovery timer value, in seconds.
					Remaining time of the discovery process."
				::={ nmsERPSRingTableEntry 13 }
				
			-- 1.3.6.1.4.1.3320.2.X.6.1.14
			nmsERPSRingPriorityValue OBJECT-TYPE
				SYNTAX INTEGER
				ACCESS read-write
				STATUS mandatory
				DESCRIPTION
					"The configured ring node priority value.
					The lowest priority makes a node RPL-Owner in the ring.
					Available range is from 0 to 61440, in steps of 4096."
				::={ nmsERPSRingTableEntry 14 }
				
			-- 1.3.6.1.4.1.3320.2.X.6.1.15
			nmsERPSRingWtrTime OBJECT-TYPE
				SYNTAX INTEGER
				ACCESS read-write
				STATUS mandatory
				DESCRIPTION
					"The configured Wait-to-restore time, in seconds."
				::={ nmsERPSRingTableEntry 15 }
				
			-- 1.3.6.1.4.1.3320.2.X.6.1.16
			nmsERPSRingGuardTime OBJECT-TYPE
				SYNTAX INTEGER
				ACCESS read-write
				STATUS mandatory
				DESCRIPTION
					"The configured Guard-time, in 10ms."
				::={ nmsERPSRingTableEntry 16 }
				
			-- 1.3.6.1.4.1.3320.2.X.6.1.17
			nmsERPSRingSendTime OBJECT-TYPE
				SYNTAX INTEGER
				ACCESS read-write
				STATUS mandatory
				DESCRIPTION
					"The configured interval of ring protection PDUs, in seconds."
				::={ nmsERPSRingTableEntry 17 }
			
			-- 1.3.6.1.4.1.3320.2.X.6.1.18
			nmsERPSRingDiscoveryTime OBJECT-TYPE
				SYNTAX INTEGER
				ACCESS read-write
				STATUS mandatory
				DESCRIPTION
					"The duration configured for discovery process, in seconds."
				::={ nmsERPSRingTableEntry 18 }
				
			-- 1.3.6.1.4.1.3320.2.X.6.1.19
			nmsERPSRingDpduInterval OBJECT-TYPE
				SYNTAX INTEGER
				ACCESS read-write
				STATUS mandatory
				DESCRIPTION
					"The configured interval of ring discovery PDUs, in seconds."
				::={ nmsERPSRingTableEntry 19 }
				
			-- 1.3.6.1.4.1.3320.2.X.6.1.20
			nmsERPSRingDiscoveryCount OBJECT-TYPE
				SYNTAX INTEGER
				ACCESS read-only
				STATUS mandatory
				DESCRIPTION
					"The total number of discovery process ever started."
				::={ nmsERPSRingTableEntry 20 }
			
			-- 1.3.6.1.4.1.3320.2.X.6.1.21
			nmsERPSRingDiscoveryLastDuration OBJECT-TYPE
				SYNTAX INTEGER
				ACCESS read-only
				STATUS mandatory
				DESCRIPTION
					"Runtime of the last discovery process, in 10 ms."
				::={ nmsERPSRingTableEntry 21 }
			
			-- 1.3.6.1.4.1.3320.2.X.6.1.22
			nmsERPSRingDiscoveryLastElapsed OBJECT-TYPE
				SYNTAX INTEGER
				ACCESS read-only
				STATUS mandatory
				DESCRIPTION
					"Elapsed time since last discovery started, in seconds."
				::={ nmsERPSRingTableEntry 22 }
			
			-- 1.3.6.1.4.1.3320.2.X.6.1.23
			nmsERPSRingAdminStatus OBJECT-TYPE
				SYNTAX INTEGER {
					disabled(0),
					enabled(1)
				}
				ACCESS read-create
				STATUS mandatory
				DESCRIPTION
					"A read-create value that indicates the configuration status 
					of the ring instance. Set this value to 'enabled' to start 
					the ring or 'disabled' to stop it."
				::={ nmsERPSRingTableEntry 23 }
			
			-- 1.3.6.1.4.1.3320.2.X.6.1.24	
			nmsERPSRingPort1 OBJECT-TYPE
				SYNTAX INTEGER
				ACCESS read-create
				STATUS mandatory
				DESCRIPTION
					"The interface index of the first ring port. Value 0 indicates that
					the first port is not configured. This value is read-write."
				::={ nmsERPSRingTableEntry 24 }
			
			-- 1.3.6.1.4.1.3320.2.X.6.1.25
			nmsERPSRingPort1AdminType OBJECT-TYPE
				SYNTAX INTEGER {
					ring-port(0),
					rpl(1)
				}
				ACCESS read-write
				STATUS mandatory
				DESCRIPTION
					"The configured type of the first ring port. Set this value to
					'rpl' to configure the Ring-Protection-Link."
				::={ nmsERPSRingTableEntry 25 }
				
			-- 1.3.6.1.4.1.3320.2.X.6.1.26
			nmsERPSRingPort1OperType OBJECT-TYPE
				SYNTAX INTEGER {
					ring-port(0),
					rpl(1)
				}
				ACCESS read-only
				STATUS mandatory
				DESCRIPTION
					"The running type of the first ring port."
				::={ nmsERPSRingTableEntry 26 }
			
			-- 1.3.6.1.4.1.3320.2.X.6.1.27
			nmsERPSRingPort1State OBJECT-TYPE
				SYNTAX INTEGER {
					blocking(0),
					forwarding(1)
				}
				ACCESS read-only
				STATUS mandatory
				DESCRIPTION
					"Forwarding state of the first ring port."
				::={ nmsERPSRingTableEntry 27 }
			
			-- 1.3.6.1.4.1.3320.2.X.6.1.28
			nmsERPSRingPort1Status OBJECT-TYPE
				SYNTAX INTEGER {
					link-down(0),
					link-up(1)
				}
				ACCESS read-only
				STATUS mandatory
				DESCRIPTION
					"Link status of the first ring port."
				::={ nmsERPSRingTableEntry 28 }
				
			-- 1.3.6.1.4.1.3320.2.X.6.1.29
			nmsERPSRingPort2 OBJECT-TYPE
				SYNTAX INTEGER
				ACCESS read-create
				STATUS mandatory
				DESCRIPTION
					"The interface index of the second ring port. Value 0 indicates that
					the second port is not configured. This value is read-write.."
				::={ nmsERPSRingTableEntry 29 }
			
			-- 1.3.6.1.4.1.3320.2.X.6.1.30
			nmsERPSRingPort2AdminType OBJECT-TYPE
				SYNTAX INTEGER {
					ring-port(0),
					rpl(1)
				}
				ACCESS read-write
				STATUS mandatory
				DESCRIPTION
					"The configured type of the second ring port. Set this value to
					'rpl' to configure the Ring-Protection-Link."
				::={ nmsERPSRingTableEntry 30 }
				
			-- 1.3.6.1.4.1.3320.2.X.6.1.31
			nmsERPSRingPort2OperType OBJECT-TYPE
				SYNTAX INTEGER {
					ring-port(0),
					rpl(1)
				}
				ACCESS read-only
				STATUS mandatory
				DESCRIPTION
					"The running type of the second ring port."
				::={ nmsERPSRingTableEntry 31 }
			
			-- 1.3.6.1.4.1.3320.2.X.6.1.32
			nmsERPSRingPort2State OBJECT-TYPE
				SYNTAX INTEGER {
					blocking(0),
					forwarding(1)
				}
				ACCESS read-only
				STATUS mandatory
				DESCRIPTION
					"Forwarding state of the second ring port."
				::={ nmsERPSRingTableEntry 32 }
			
			-- 1.3.6.1.4.1.3320.2.X.6.1.33
			nmsERPSRingPort2Status OBJECT-TYPE
				SYNTAX INTEGER {
					link-down(0),
					link-up(1)
				}
				ACCESS read-only
				STATUS mandatory
				DESCRIPTION
					"Link status of the second ring port."
				::={ nmsERPSRingTableEntry 33 }
				
	-- 1.3.6.1.4.1.3320.2.X.7
	nmsERPSRingPortTable OBJECT-TYPE
		SYNTAX  SEQUENCE OF NMSERPSRingPortTableEntry
		ACCESS  not-accessible
		STATUS  mandatory
		DESCRIPTION
			"A table that contains informations of ring ports."
		::= { nmsERPS 7 }
		
		-- 1.3.6.1.4.1.3320.2.X.7.1
		nmsERPSRingPortTableEntry OBJECT-TYPE
			SYNTAX NMSERPSRingPortTableEntry
			ACCESS  not-accessible
			STATUS  mandatory
			DESCRIPTION
				"A table that contains informations of ring ports."
			INDEX { nmsERPSRingPortRingID, nmsERPSRingPort }
			::= { nmsERPSRingPortTable 1 }
			
		NMSERPSRingPortTableEntry ::=
			SEQUENCE {
				nmsERPSRingPortRingID
					INTEGER,
				nmsERPSRingPort
					INTEGER,
				nmsERPSRingPortNum
					INTEGER,
				nmsERPSRingPortAdminType
					INTEGER,
				nmsERPSRingPortOperType
					INTEGER,
				nmsERPSRingPortState
					INTEGER,
				nmsERPSRingPortStatus
					INTEGER,
				nmsERPSRingPortForwards
					INTEGER,
				nmsERPSRingPortForwardLastElapsed
					INTEGER,
				nmsERPSRingPortRx
					INTEGER,
				nmsERPSRingPortTx
					INTEGER
			}
			
			-- 1.3.6.1.4.1.3320.2.X.7.1.1
			nmsERPSRingPortRingID OBJECT-TYPE
				SYNTAX INTEGER
				ACCESS read-only
				STATUS mandatory
				DESCRIPTION
					"The index of ring instance, in which this port is configured."
				::={ nmsERPSRingPortTableEntry 1 }
			
			-- 1.3.6.1.4.1.3320.2.X.7.1.2
			nmsERPSRingPort OBJECT-TYPE
				SYNTAX INTEGER
				ACCESS read-only
				STATUS mandatory
				DESCRIPTION
					"Interface index of the ring port."
				::={ nmsERPSRingPortTableEntry 2 }
				
			-- 1.3.6.1.4.1.3320.2.X.7.1.3
			nmsERPSRingPortAdminType OBJECT-TYPE
				SYNTAX INTEGER {
					ring-port(0),
					rpl(1)
				}
				ACCESS read-only
				STATUS mandatory
				DESCRIPTION
					"A value indicates that if the port is configured as
					the Ring Protection Link(RPL)."
				::={ nmsERPSRingPortTableEntry 3 }
				
			-- 1.3.6.1.4.1.3320.2.X.7.1.4
			nmsERPSRingPortOperType OBJECT-TYPE
				SYNTAX INTEGER {
					ring-port(0),
					rpl(1)
				}
				ACCESS read-only
				STATUS mandatory
				DESCRIPTION
					"A value indicates that if the port is running as
					the Ring Protection Link(RPL). This value may be 
					different with the value of 'nmsERPSRingPortAdminType'"
				::={ nmsERPSRingPortTableEntry 4 }
				
			-- 1.3.6.1.4.1.3320.2.X.7.1.5
			nmsERPSRingPortState OBJECT-TYPE
				SYNTAX INTEGER {
					blocking(0),
					forwarding(1)
				}
				ACCESS read-only
				STATUS mandatory
				DESCRIPTION
					"State of a ring port, forwarding or blocking."
				::={ nmsERPSRingPortTableEntry 5 }
				
			-- 1.3.6.1.4.1.3320.2.X.7.1.6
			nmsERPSRingPortStatus OBJECT-TYPE
				SYNTAX INTEGER {
					link-down(0),
					link-up(1)
				}
				ACCESS read-only
				STATUS mandatory
				DESCRIPTION
					"Link status of a ring port."
				::={ nmsERPSRingPortTableEntry 6 }
				
			-- 1.3.6.1.4.1.3320.2.X.7.1.7
			nmsERPSRingPortForwards OBJECT-TYPE
				SYNTAX INTEGER
				ACCESS read-only
				STATUS mandatory
				DESCRIPTION
					"The number of times this port transitioned to forwarding state."
				::={ nmsERPSRingPortTableEntry 7 }
				
			-- 1.3.6.1.4.1.3320.2.X.7.1.8
			nmsERPSRingPortForwardLastElapsed OBJECT-TYPE
				SYNTAX INTEGER
				ACCESS read-only
				STATUS mandatory
				DESCRIPTION
					"Elapsed time since the port became forwarding, in seconds."
				::={ nmsERPSRingPortTableEntry 8 }
				
			-- 1.3.6.1.4.1.3320.2.X.7.1.9
			nmsERPSRingPortRx OBJECT-TYPE
				SYNTAX INTEGER
				ACCESS read-only
				STATUS mandatory
				DESCRIPTION
					"The number of received PDUs on this port."
				::={ nmsERPSRingPortTableEntry 9 }
				
			-- 1.3.6.1.4.1.3320.2.X.7.1.10
			nmsERPSRingPortTx OBJECT-TYPE
				SYNTAX INTEGER
				ACCESS read-only
				STATUS mandatory
				DESCRIPTION
					"The number of transmitted PDUs on this port."
				::={ nmsERPSRingPortTableEntry 10 }
				
		-- Notifications
		
		-- 1.3.6.1.4.1.3320.2.X.8
		nmsERPSRingNotifications OBJECT IDENTIFIER ::= { nmsERPS 8 }
		
		-- 1.3.6.1.4.1.3320.2.X.8.1
		nmsERPSRingRoleChange NOTIFICATION-TYPE
			OBJECTS {
				nmsERPSRingID,
				nmsERPSRingNodeID,
				nmsERPSRingRole
			}
			STATUS current
			DESCRIPTION
				"The notification is generated when ring node role changes."
			::= { nmsERPSRingNotifications 1 }
		
		-- 1.3.6.1.4.1.3320.2.X.8.2
		nmsERPSRingStateChange NOTIFICATION-TYPE
			OBJECTS {
				nmsERPSRingID,
				nmsERPSRingNodeID,
				nmsERPSRingRole,
				nmsERPSRingState
			}
			STATUS current
			DESCRIPTION
				"The notification is generated when a RPL-Owner detects that
				the state of ring changed."
			::= { nmsERPSRingNotifications 2 }
			
END
