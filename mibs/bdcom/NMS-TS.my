--------------------------------------------------------------------
-- NMS-TS.my:  NMS Terminal Service MIB file
--
-- June 2000, 
-- 
--------------------------------------------------------------------

   NMS-TS DEFINITIONS ::= BEGIN

               IMPORTS
			IpAddress
				FROM RFC1155-SMI
			OBJECT-TYPE
				FROM RFC-1212
			DisplayString
				FROM RFC1213-MIB
			nmslocal
				FROM NMS-SMI;
          
               nmslts             OBJECT IDENTIFIER ::= { nmslocal 9 }


          -- This group is present in all products which contain
          -- asynchronous terminal lines.

               nmstsLines OBJECT-TYPE
                   SYNTAX  INTEGER
                   ACCESS  read-only
                   STATUS  mandatory
                   DESCRIPTION
                           "Number of terminal lines on this device.
                           Includes virtual lines."
                   ::= { nmslts 1 }


               -- Local Terminal Service Line Table

          -- This group contains terminal service specific
          -- information on a per line basis.

               nmsltsLineTable OBJECT-TYPE
                   SYNTAX  SEQUENCE OF NMSLtsLineEntry
                   ACCESS  not-accessible
                   STATUS  mandatory
                   DESCRIPTION
                            "A list of terminal server line entries."
                   ::= { nmslts 2 }

               nmsltsLineEntry OBJECT-TYPE
                   SYNTAX NMSLtsLineEntry
                   ACCESS  not-accessible
                   STATUS  mandatory
                   DESCRIPTION
                            "A collection of per TTY objects in the
                            NMS Terminal Server implementation."
                   INDEX { tsLineNumber }
               ::= { nmsltsLineTable 1 }

               NMSLtsLineEntry ::=
                   SEQUENCE {
                       nmstsLineActive
                           INTEGER,
                       nmstsLineType
                           INTEGER,
                       nmstsLineAutobaud
                           INTEGER,
                       nmstsLineSpeedin
                           INTEGER,
                       nmstsLineSpeedout
                           INTEGER,
                       nmstsLineFlow
                           INTEGER,
                       nmstsLineModem
                           INTEGER,
                       nmstsLineLoc
                           DisplayString,
                       nmstsLineTerm
                           DisplayString,
                       nmstsLineScrlen
                           INTEGER,
                       nmstsLineScrwid
                           INTEGER,
                       nmstsLineEsc
                           DisplayString,
                       nmstsLineTmo
                           INTEGER,
                       nmstsLineSestmo
                           INTEGER,
                       nmstsLineRotary
                           INTEGER,
                       nmstsLineUses
                           INTEGER,
                       nmstsLineNses
                           INTEGER,
                       nmstsLineUser
                           DisplayString,
                       nmstsLineNoise
                           INTEGER,
                       nmstsLineNumber
                           INTEGER,
                       nmstsLineTimeActive
                           INTEGER
                   }


          -- The following section describes the components of the
          -- table.

               nmstsLineActive OBJECT-TYPE
                   SYNTAX  INTEGER
                   ACCESS  read-only
                   STATUS  mandatory
                   DESCRIPTION
                           "Boolean whether this line is active or not."
                   ::= { nmsltsLineEntry 1 }

               nmstsLineType OBJECT-TYPE
                   SYNTAX  INTEGER {
                        unknown(1),
                        console(2),
                        terminal(3),
                        line-printer(4),
                        virtual-terminal(5),
                        auxiliary(6)
                   }
                   ACCESS  read-only
                   STATUS  mandatory
                   DESCRIPTION
                           "Type of line."
                   ::= { nmsltsLineEntry 2 }

               nmstsLineAutobaud OBJECT-TYPE
                   SYNTAX  INTEGER
                   ACCESS  read-only
                   STATUS  mandatory
                   DESCRIPTION
                           "Boolean whether line will autobaud or not."
                   ::= { nmsltsLineEntry 3 }

               nmstsLineSpeedin OBJECT-TYPE
                   SYNTAX  INTEGER
                   ACCESS  read-only
                   STATUS  mandatory
                   DESCRIPTION
                           "What input speed the line is running at."
                   ::= { nmsltsLineEntry 4 }

               nmstsLineSpeedout OBJECT-TYPE
                   SYNTAX  INTEGER
                   ACCESS  read-only
                   STATUS  mandatory
                   DESCRIPTION
                           "What output speed the line is running at."
                   ::= { nmsltsLineEntry 5 }

               nmstsLineFlow OBJECT-TYPE
                   SYNTAX  INTEGER {
                        unknown(1),
                        none(2),
                        software-input(3),
                        software-output(4),
                        software-both(5),
                        hardware-input(6),
                        hardware-output(7),
                        hardware-both(8)
                   }
                   ACCESS  read-only
                   STATUS  mandatory
                   DESCRIPTION
                           "What kind of flow control the line is
                           using."
                   ::= { nmsltsLineEntry 6 }

               nmstsLineModem OBJECT-TYPE
                   SYNTAX  INTEGER {
                        unknown(1),
                        none(2),
                        call-in(3),
                        call-out(4),
                        cts-required(5),
                        ri-is-cd(6),
                        inout(7)
                   }
                   ACCESS  read-only
                   STATUS  mandatory
                   DESCRIPTION
                           "What kind of modem control the line is
                           using."
                   ::= { nmsltsLineEntry 7 }

               nmstsLineLoc OBJECT-TYPE
                   SYNTAX  DisplayString
                   ACCESS  read-only
                   STATUS  mandatory
                   DESCRIPTION
                           "Describes the line's physical location."
                   ::= { nmsltsLineEntry 8 }

               nmstsLineTerm OBJECT-TYPE
                   SYNTAX  DisplayString
                   ACCESS  read-only
                   STATUS  mandatory
                   DESCRIPTION
                           "Describes the line's terminal type."
                   ::= { nmsltsLineEntry 9 }

               nmstsLineScrlen OBJECT-TYPE
                   SYNTAX  INTEGER
                   ACCESS  read-only
                   STATUS  mandatory
                   DESCRIPTION
                           "Length in lines of the screen of terminal
                           attached to this line."
                   ::= { nmsltsLineEntry 10 }

               nmstsLineScrwid OBJECT-TYPE
                   SYNTAX  INTEGER
                   ACCESS  read-only
                   STATUS  mandatory
                   DESCRIPTION
                           "Width in characters of the screen of
                           terminal attached to this line."
                   ::= { nmsltsLineEntry 11 }

               nmstsLineEsc OBJECT-TYPE
                   SYNTAX  DisplayString
                   ACCESS  read-only
                   STATUS  mandatory
                   DESCRIPTION
                           "Escape character used to break out of active
                           sessions."
                   ::= { nmsltsLineEntry 12 }

               nmstsLineTmo OBJECT-TYPE
                   SYNTAX  INTEGER
                   ACCESS  read-only
                   STATUS  mandatory
                   DESCRIPTION
                           "Line idleness timeout in seconds."
                   ::= { nmsltsLineEntry 13 }

               nmstsLineSestmo OBJECT-TYPE
                   SYNTAX  INTEGER
                   ACCESS  read-only
                   STATUS  mandatory
                   DESCRIPTION
                           "Session idleness timeout in seconds."
                   ::= { nmsltsLineEntry 14 }

               nmstsLineRotary OBJECT-TYPE
                   SYNTAX  INTEGER
                   ACCESS  read-only
                   STATUS  mandatory
                   DESCRIPTION
                           "Rotary group number the line belongs in."
                   ::= { nmsltsLineEntry 15 }

               nmstsLineUses OBJECT-TYPE
                   SYNTAX  INTEGER
                   ACCESS  read-only
                   STATUS  mandatory
                   DESCRIPTION
                           "Number of times a connection has been made
                           to or from this line."
                   ::= { nmsltsLineEntry 16 }

               nmstsLineNses OBJECT-TYPE
                   SYNTAX  INTEGER
                   ACCESS  read-only
                   STATUS  mandatory
                   DESCRIPTION
                           "Current number of sessions in use on this
                           line."
                   ::= { nmsltsLineEntry 17 }

               nmstsLineUser OBJECT-TYPE
                   SYNTAX  DisplayString
                   ACCESS  read-only
                   STATUS  mandatory
                   DESCRIPTION
                           "TACACS user name, if TACACS enabled, of user
                           on this line."
                   ::= { nmsltsLineEntry 18 }

               nmstsLineNoise OBJECT-TYPE
                   SYNTAX  INTEGER
                   ACCESS  read-only
                   STATUS  mandatory
                   DESCRIPTION
                           "Count of garbage characters received when
                           line inactive."
                   ::= { nmsltsLineEntry 19 }

               nmstsLineNumber OBJECT-TYPE
                   SYNTAX  INTEGER
                   ACCESS  read-only
                   STATUS  mandatory
                   DESCRIPTION
                           "The line i've been talking about."
                   ::= { nmsltsLineEntry 20 }

               nmstsLineTimeActive OBJECT-TYPE
                   SYNTAX  INTEGER
                   ACCESS  read-only
                   STATUS  mandatory
                   DESCRIPTION
                           "The time in seconds since line was activated."
                   ::= { nmsltsLineEntry 21 }
               -- End of table

               -- Local Terminal Service Line Session Table

          -- This group contains terminal server specific
          -- information on a per line and per session basis.

               nmsltsLineSessionTable OBJECT-TYPE
                   SYNTAX  SEQUENCE OF NMSLtsLineSessionEntry
                   ACCESS  not-accessible
                   STATUS  mandatory
                   DESCRIPTION
                            "A list of terminal server line and session
                            entries."
                   ::= { nmslts 3 }

               nmsltsLineSessionEntry OBJECT-TYPE
                   SYNTAX NMSLtsLineSessionEntry
                   ACCESS  not-accessible
                   STATUS  mandatory
                   DESCRIPTION
                            "A collection of per session and per TTY
                            objects in the NMS Terminal Server
                            implementation."
                   INDEX { nmstslineSesLine, nmstslineSesSession }
               ::= { nmsltsLineSessionTable 1 }

               NMSLtsLineSessionEntry ::=
                   SEQUENCE {
                       nmstslineSesType
                           INTEGER,
                       nmstslineSesDir
                           INTEGER,
                       nmstslineSesAddr
                           IpAddress,
                       nmstslineSesName
                           DisplayString,
                       nmstslineSesCur
                           INTEGER,
                       nmstslineSesIdle
                           INTEGER,
                       nmstslineSesLine
                           INTEGER,
                       nmstslineSesSession 
                           INTEGER
                   }


          -- The following section describes the components of the
          -- table.

               nmstslineSesType OBJECT-TYPE
                   SYNTAX  INTEGER {
                        unknown(1),
                        pad(2),
                        stream(3),
                        rlogin(4),
                        telnet(5),
                        tcp(6),
                        lat(7),
                        mop(8),
                        slip(9),
                        xremote(10),
			rshell(11)
                   }
                   ACCESS  read-only
                   STATUS  mandatory
                   DESCRIPTION
                           "Type of session."
                   ::= { nmsltsLineSessionEntry 1 }

               nmstslineSesDir OBJECT-TYPE
                   SYNTAX  INTEGER {
                        unknown(1),
                        incoming(2),
                        outgoing(3)
                   }
                   ACCESS  read-only
                   STATUS  mandatory
                   DESCRIPTION
                           "Direction of session."
                   ::= { nmsltsLineSessionEntry 2 }

               nmstslineSesAddr OBJECT-TYPE
                   SYNTAX  IpAddress
                   ACCESS  read-only
                   STATUS  mandatory
                   DESCRIPTION
                           "Remote host address of session. [What about
                           PAD connections?]"
                   ::= { nmsltsLineSessionEntry 3 }

               nmstslineSesName OBJECT-TYPE
                   SYNTAX  DisplayString
                   ACCESS  read-only
                   STATUS  mandatory
                   DESCRIPTION
                           "Remote host name of session."
                   ::= { nmsltsLineSessionEntry 4 }

               nmstslineSesCur OBJECT-TYPE
                   SYNTAX  INTEGER
                   ACCESS  read-only
                   STATUS  mandatory
                   DESCRIPTION
                           "Boolean whether session is the currently
                           active one."
                   ::= { nmsltsLineSessionEntry 5 }

               nmstslineSesIdle OBJECT-TYPE
                   SYNTAX  INTEGER
                   ACCESS  read-only
                   STATUS  mandatory
                   DESCRIPTION
                           "Time in seconds session has been idle."
                   ::= { nmsltsLineSessionEntry 6 }

               nmstslineSesLine OBJECT-TYPE
                   SYNTAX  INTEGER
                   ACCESS  read-only
                   STATUS  mandatory
                   DESCRIPTION
                           "Table index 1."
                   ::= { nmsltsLineSessionEntry 7 }

               nmstslineSesSession OBJECT-TYPE
                   SYNTAX  INTEGER
                   ACCESS  read-only
                   STATUS  mandatory
                   DESCRIPTION
                           "Table index 2."
                   ::= { nmsltsLineSessionEntry 8 }

               -- End of table


               nmstsMsgTtyLine OBJECT-TYPE
                   SYNTAX  INTEGER
                   ACCESS  read-write
                   STATUS  mandatory
                   DESCRIPTION
                           "tty line to send the message to. -1 will
                           send it to all tty lines"
                   ::= { nmslts 4 }

               nmstsMsgIntervaltim OBJECT-TYPE
                   SYNTAX  INTEGER
                   ACCESS  read-write
                   STATUS  mandatory
                   DESCRIPTION
                           "Interval between reissuing message in
                           milliseconds. Minimum non-zero setting is
                           10000. 0 will cause the routine to choose its
                           own intervals becoming more frequent as
                           MessageDuration gets close to expiring. 2hr,
                           1hr, 30min, 5min, 1min"
                   ::= { nmslts 5 }

               nmstsMsgDuration OBJECT-TYPE
                   SYNTAX  INTEGER
                   ACCESS  read-write
                   STATUS  mandatory
                   DESCRIPTION
                           "Length of time to reissue message in
                           milliseconds. Minimum non-zero setting is
                           10000. A setting of 0 will not repeat the
                           message."
                   ::= { nmslts 6 }

               nmstsMsgText OBJECT-TYPE
                   SYNTAX  DisplayString
                   ACCESS  read-write
                   STATUS  mandatory
                   DESCRIPTION
                           "Up to 256 characters that will make up the
                           message"
                   ::= { nmslts 7 }

               nmstsMsgTmpBanner OBJECT-TYPE
                   SYNTAX  INTEGER {
                        no(1),
                        additive(2)
                   }
                   ACCESS  read-write
                   STATUS  mandatory
                   DESCRIPTION
                           "Should the message be used as a temporary
                           banner. 1 - No. 2 - In addition to the normal
                           banner"
                   ::= { nmslts 8 }

               nmstsMsgSend OBJECT-TYPE
                   SYNTAX  INTEGER {
                        nothing(1),
                        reload(2),
                        messagedone(3),
                        abort(4)
                   }
                   ACCESS  read-write
                   STATUS  mandatory
                   DESCRIPTION
                           "Sends the message. The value determines what
                           to do after the message has completed."
                   ::= { nmslts 9 }

               nmstsClrTtyLine OBJECT-TYPE
                   SYNTAX  INTEGER
                   ACCESS  read-write
                   STATUS  mandatory
                   DESCRIPTION
                           "tty line to clear.  Read returns the last line
                           cleared.  A value of -1 indicates no lines have 
                           been cleared."
                   ::= { nmslts 10 }

END
