-- *****************************************************************
-- DIFFSERV-MIB-CAPABILITY.my: 
-- DIFFSERV MIB AGENT-CAPABILITIES
--
-- October 2003, H.K.Vivek
--
-- Copyright (c) 2003 by cisco Systems, Inc.
-- All rights reserved.
--
-- *****************************************************************

DIFFSERV-MIB-CAPABILITY DEFINITIONS ::= BEGIN

IMPORTS
        MODULE-IDENTITY
                FROM SNMPv2-SMI
        AGENT-CAPABILITIES
                FROM SNMPv2-CONF
        ciscoAgentCapability
                FROM CISCO-SMI
        IndexInteger, IfDirection
                FROM DIFFSERV-MIB;

diffServMibCapability MODULE-IDENTITY
                        LAST-UPDATED    "200310130000Z"
                        ORGANIZATION    "Cisco Systems, Inc."
                        CONTACT-INFO  
                                "       Cisco Systems
                                        Customer Service

                                Postal: 170 West Tasman Drive
                                        San Jose, CA  95134
                                        USA

                                Tel: +1 800 553-NETS

                                E-mail: cs-san@cisco.com"
                        DESCRIPTION
                                "Agent capabilities for 
                                 DIFFSERV-MIB"
                        REVISION        "200310130000Z"
                        DESCRIPTION
                                "The capabilities description of 
                                 DIFFSERV-MIB (RFC 3289) for
                                 MDS 1.3(1)."
        ::= { ciscoAgentCapability 377 }

diffServMibCapabilityMDS13R1 AGENT-CAPABILITIES

PRODUCT-RELEASE "Cisco MDS 1.3(1)"
      STATUS          current
      DESCRIPTION     "DIFFSERV MIB capabilities"

      SUPPORTS        DIFFSERV-MIB
      INCLUDES        { 
                          diffServMIBDataPathGroup,
                          diffServMIBClfrGroup,
                          diffServMIBClfrElementGroup,
                          diffServMIBMeterGroup,
                          diffServMIBActionGroup,
                          diffServMIBDscpMarkActGroup  
                      }

      VARIATION           diffServDataPathIfDirection
      SYNTAX              IfDirection
      DESCRIPTION         "Only 'inbound(1)' is supported."

      VARIATION           diffServDataPathStart
      ACCESS              read-only
      DESCRIPTION         "create is not supported."

      VARIATION           diffServDataPathStorage
      ACCESS              read-only
      DESCRIPTION         "create is not supported."

      VARIATION           diffServDataPathStatus
      ACCESS              read-only
      DESCRIPTION         "create is not supported."

      VARIATION           diffServClfrNextFree
      ACCESS              not-implemented
      DESCRIPTION         "Not supported."

      VARIATION           diffServClfrId
      SYNTAX              IndexInteger (1..1023)
      DESCRIPTION         "Only the range 1-1023 is supported."

      VARIATION           diffServClfrStorage
      ACCESS              read-only
      DESCRIPTION         "create is not supported."

      VARIATION           diffServClfrElementNextFree
      ACCESS              not-implemented
      DESCRIPTION         "Not supported."

      VARIATION           diffServClfrElementId
      SYNTAX              IndexInteger (1..256)
      DESCRIPTION         "Only the range 1-256 is supported."

      VARIATION           diffServClfrElementPrecedence
      ACCESS              read-only
      DESCRIPTION         "create is not supported."

      VARIATION           diffServClfrElementStorage
      ACCESS              read-only
      DESCRIPTION         "create is not supported."

      VARIATION            diffServClfrElementEntry
      CREATION-REQUIRES    { diffServClfrElementSpecific }
      DESCRIPTION          "The diffServClfrElementSpecific
                            object must be specified during
                            creation and this object cannot
                            be modified later."

      VARIATION            diffServClfrElementNext
      DESCRIPTION          "This object can only be set to
                            diffServActionEntry."

      VARIATION            diffServClfrElementSpecific
      DESCRIPTION          "This object can only be set to
                            cdsmFCMultiFieldClfrEntry, which
                            is defined in 
                            CISCO-DIFFSERV-EXT-MIB."

      VARIATION            diffServMeterNextFree
      ACCESS               not-implemented
      DESCRIPTION          "Not supported."

      VARIATION            diffServMeterSucceedNext
      ACCESS               read-only
      DESCRIPTION          "create is not supported."

      VARIATION            diffServMeterFailNext
      ACCESS               read-only
      DESCRIPTION          "create is not supported."

      VARIATION            diffServMeterSpecific
      ACCESS               read-only
      DESCRIPTION          "create is not supported."

      VARIATION            diffServMeterStorage
      ACCESS               read-only
      DESCRIPTION          "create is not supported."

      VARIATION            diffServMeterStatus
      ACCESS               read-only
      DESCRIPTION          "create is not supported."

      VARIATION            diffServActionNextFree
      ACCESS               not-implemented
      DESCRIPTION          "Not supported."

      VARIATION            diffServActionNext
      ACCESS               read-only
      DESCRIPTION          "create is not supported."

      VARIATION            diffServActionSpecific
      ACCESS               read-only
      DESCRIPTION          "create is not supported."

      VARIATION            diffServActionStorage
      ACCESS               read-only
      DESCRIPTION          "create is not supported."
 
      VARIATION            diffServActionInterface
      ACCESS               read-only
      DESCRIPTION          "create is not supported."

      VARIATION            diffServActionStatus
      ACCESS               read-only
      DESCRIPTION          "create is not supported."

    ::= { diffServMibCapability 1 } 

END
