-- *****************************************************************
-- RUIJIE-SYSTEM-MIB.mib:  Ruijie System MIB file
--
-- March 2002, Wuzg
--
-- Copyright (c) 2002 by Ruijie Networks Co.,Ltd.
-- All rights reserved.
-- 
-- *****************************************************************
--

RUIJIE-SYSTEM-MIB DEFINITIONS ::= BEGIN

IMPORTS
        MODULE-IDENTITY,
        OBJECT-TYPE,
        NOTIFICATION-TYPE,
        Integer32,
        TimeTicks,
        Unsigned32
                FROM SNMPv2-SMI
        DisplayString,
        MacAddress
                FROM SNMPv2-TC
        Gauge
                FROM RFC1155-SMI
        MODULE-COMPLIANCE,
        OBJECT-GROUP
                FROM SNMPv2-CONF
        ruijieApMacAddr   
                FROM RUIJIE-AC-MGMT-MIB
        ruijieMemoryPoolCurrentUtilization,
        ruijieNodeMemoryPoolName,
        ruijieNodeMemoryPoolCurrentUtilization
                FROM RUIJIE-MEMORY-MIB
        ruijieCPUUtilization1Min,
        Percent,
        ruijieNodeCPUTotalName,
        ruijieNodeCPUTotal1min
                FROM RUIJIE-PROCESS-MIB
        entPhysicalName 
                FROM ENTITY-MIB
        ruijieMgmt
                FROM RUIJIE-SMI;

ruijieSystemMIB MODULE-IDENTITY
        LAST-UPDATED "200203200000Z"
        ORGANIZATION "Ruijie Networks Co.,Ltd."
        CONTACT-INFO
                " 
                Tel: 4008-111-000 

                E-mail: service@ruijie.com.cn"
        DESCRIPTION
                "This module defines ruijie system mibs."
        REVISION      "200203200000Z"
        DESCRIPTION
                "Initial version of this MIB module."
        ::= { ruijieMgmt 1}

ruijieSystemMIBObjects OBJECT IDENTIFIER ::= { ruijieSystemMIB 1 }

ruijieSystemHwVersion OBJECT-TYPE
        SYNTAX DisplayString(SIZE (1..32))
        MAX-ACCESS read-only
        STATUS current
        DESCRIPTION
          "Return the string of the Revision number of hardware resides
          on the FastSwitch."
        ::= { ruijieSystemMIBObjects 1 }

ruijieSystemSwVersion OBJECT-TYPE
        SYNTAX DisplayString(SIZE (1..32))
        MAX-ACCESS read-only
        STATUS current
        DESCRIPTION
          "Return the string of the Revision number of software resides
          on the FastSwitch."
        ::= { ruijieSystemMIBObjects 2 }
        
ruijieSystemBootVersion OBJECT-TYPE
        SYNTAX DisplayString(SIZE (1..32))
        MAX-ACCESS read-only
        STATUS current
        DESCRIPTION
          "Return the string of the Revision number of BOOT software resides
          on the FastSwitch."
        ::= { ruijieSystemMIBObjects 3 }
        
ruijieSystemSysCtrlVersion OBJECT-TYPE
        SYNTAX DisplayString(SIZE (1..32))
        MAX-ACCESS read-only
        STATUS current
        DESCRIPTION
          "Return the string of the Revision number of CTRL software resides
          on the FastSwitch."
        ::= { ruijieSystemMIBObjects 4 }       

ruijieSystemParametersSave OBJECT-TYPE
        SYNTAX Integer32
        MAX-ACCESS read-write
        STATUS current
        DESCRIPTION
            "Save all parameters changed in configuration by setting 
            this object to any value but 0, set its value to 0 will
            cause no action of agent, otherwise all changes of 
            prarameters will be saved for retrive when system is 
            reset, if parameter is changed but not saved all changes
            will come to their original value when system down and up
            again, when query always return value 0."
        ::= { ruijieSystemMIBObjects 5 }

ruijieSystemOutBandRate OBJECT-TYPE
   	  SYNTAX  INTEGER {
                baud9600  (1),
                baud19200 (2),
                baud38400 (3),
                baud57600 (4),
                baud115200 (5)
             }
        MAX-ACCESS read-write
        STATUS current
        DESCRIPTION
   	    "Determine the console(OutBand) baud rate :
             9600 - 1,19200 - 2, 38300 - 3, 57600 - 4, 115200 - 5, 
             when the console baud rate is other value will return value 0."
   	::=  { ruijieSystemMIBObjects 6 }
        
ruijieSystemReset OBJECT-TYPE
        SYNTAX INTEGER {
            normal(0),
            restart(1)
        } 
        MAX-ACCESS read-write
        STATUS current
        DESCRIPTION
            "This Object allow perform soft reset of system by setting its
            value to none zero. if a soft resetis performed, after this 
            having completed a warm start trap will send to declare the state
            and when queried will always return 0."
        ::= { ruijieSystemMIBObjects 7 }

ruijieSwitchLayer OBJECT-TYPE
   	  SYNTAX  INTEGER {
                layer2 (1), -- Layer 2 Switch
                layer3 (2), -- Layer 3 Switch
                router(3)  -- Router
             }
        MAX-ACCESS read-only
        STATUS current
        DESCRIPTION
   		"Which layer's device the switch in system "
   	     ::=  { ruijieSystemMIBObjects 8 }

ruijieSystemHwPower OBJECT-TYPE
        SYNTAX INTEGER{
        	rpsNoLink(1),
        	rpsLinkAndNoPower(2),
        	rpsLinkAndReadyForPower(3),
        	rpsLinkAndPower(4)
        }
        MAX-ACCESS read-only
        STATUS current
        DESCRIPTION
          "The state of power."
        ::= { ruijieSystemMIBObjects 9 }

ruijieSystemHwFan OBJECT-TYPE
        SYNTAX INTEGER{
        	work(1),
        	stop(2)
        }
        MAX-ACCESS read-only
        STATUS current
        DESCRIPTION
          "The state of fan."
        ::= { ruijieSystemMIBObjects 10 }

--The ruijieSystemOutBandTimeout is obsoleted after 2007.9
ruijieSystemOutBandTimeout OBJECT-TYPE
        SYNTAX     Integer32(0..3600)
        UNITS      "seconds"
        MAX-ACCESS read-write
        STATUS obsolete
        DESCRIPTION
          "The timeout of console.0 indicate that timeout function is disabled."
        ::= { ruijieSystemMIBObjects 11 }

--The ruijieSystemTelnetTimeout is obsoleted after 2007.9
ruijieSystemTelnetTimeout OBJECT-TYPE
        SYNTAX     Integer32(0..3600)
        UNITS      "seconds"
        MAX-ACCESS read-write
        STATUS obsolete
        DESCRIPTION
          "The timeout of telnet.0 indicate that timeout function is disabled."
        ::= { ruijieSystemMIBObjects 12 }
      
ruijieSystemMainFile OBJECT-TYPE
        SYNTAX DisplayString(SIZE (1..255))
        MAX-ACCESS read-only
        STATUS current
        DESCRIPTION
          "Return the string of the name of main file on the FastSwitch."
        ::= { ruijieSystemMIBObjects 13 }
        
ruijieSystemCurrentPower OBJECT-TYPE
        SYNTAX Integer32
        MAX-ACCESS read-only
        STATUS current
        DESCRIPTION
          "Return the current power of the FastSwitch."
        ::= { ruijieSystemMIBObjects 14 }

ruijieSystemRemainPower OBJECT-TYPE
        SYNTAX Integer32
        MAX-ACCESS read-only
        STATUS current
        DESCRIPTION
          "Return the remain power of the FastSwitch."
        ::= { ruijieSystemMIBObjects 15 }

ruijieSystemTemperature OBJECT-TYPE
        SYNTAX Integer32
        MAX-ACCESS read-only
        STATUS current
        DESCRIPTION
          "Return the temperature of the FastSwitch."
        ::= { ruijieSystemMIBObjects 16 }

ruijieSystemElectricalSourceNum OBJECT-TYPE
        SYNTAX Integer32
        MAX-ACCESS read-only
        STATUS current
        DESCRIPTION
          "Return the electrical source number of the FastSwitch."
        ::= { ruijieSystemMIBObjects 17 }

ruijieSystemElectricalSourceIsNormalTable OBJECT-TYPE
  SYNTAX      SEQUENCE OF RuijieSystemElectricalSourceIsNormalEntry
  MAX-ACCESS  not-accessible
  STATUS      current
  DESCRIPTION
    "A table of electrical source entries. Each object displays 
     whether different electrical sources are normal or not."
  ::= { ruijieSystemMIBObjects 18 }

ruijieSystemElectricalSourceIsNormalEntry OBJECT-TYPE
  SYNTAX      RuijieSystemElectricalSourceIsNormalEntry
  MAX-ACCESS  not-accessible
  STATUS      current
  DESCRIPTION
    "An entry displays whether different electrical sources are normal or not."
  INDEX { ruijieSystemElectricalSourceIsNormalIndex }
  ::= { ruijieSystemElectricalSourceIsNormalTable 1 }

RuijieSystemElectricalSourceIsNormalEntry ::=
  SEQUENCE {
    ruijieSystemElectricalSourceIsNormalIndex  Integer32,
    ruijieSystemElectricalSourceIsNormal  INTEGER,
    ruijieSystemElectricalSourceName   DisplayString
  }
    
ruijieSystemElectricalSourceIsNormalIndex OBJECT-TYPE
    SYNTAX        Integer32(0..255)
    MAX-ACCESS    read-only
    STATUS        current
    DESCRIPTION
        "An index that uniquely represents a electrical source."
    ::= { ruijieSystemElectricalSourceIsNormalEntry 1 }

ruijieSystemElectricalSourceIsNormal OBJECT-TYPE
   	SYNTAX  INTEGER {
                noexist (1),          --no exist
                existnopower (2),     --exist no power
                existreadypower (3),  --exist ready power
                normal (4),           --normal
                powerbutabnormal (5), --power but abnormal
                unknow (6),           --unknow
                linefail (7)          --line fail
             }
    MAX-ACCESS    read-only
    STATUS        current
    DESCRIPTION
        "This object displays whether an electrical source is normal or not."
    ::= { ruijieSystemElectricalSourceIsNormalEntry 2 }
    
ruijieSystemElectricalSourceName OBJECT-TYPE
    SYNTAX        DisplayString
    MAX-ACCESS    read-only
    STATUS        current
    DESCRIPTION
        "The name of electrical source"
    ::= { ruijieSystemElectricalSourceIsNormalEntry 3 }  
    
ruijieSystemCurrentVoltage OBJECT-TYPE
        SYNTAX Integer32
        MAX-ACCESS read-only
        STATUS current
        DESCRIPTION
          "Return the current voltage of the FastSwitch."
        ::= { ruijieSystemMIBObjects 19 }
        
ruijieSystemFanNUM OBJECT-TYPE
        SYNTAX Integer32
        MAX-ACCESS read-only
        STATUS current
        DESCRIPTION
          "Return the number of fan on the FastSwitch."
        ::= { ruijieSystemMIBObjects 20 }  
        
ruijieSystemFanIsNormalTable OBJECT-TYPE
  SYNTAX      SEQUENCE OF RuijieSystemFanIsNormalEntry
  MAX-ACCESS  not-accessible
  STATUS      current
  DESCRIPTION
    "A table of fan entries. Each object displays 
     whether different fans are normal or not."
  ::= { ruijieSystemMIBObjects 21 }

ruijieSystemFanIsNormalEntry OBJECT-TYPE
  SYNTAX      RuijieSystemFanIsNormalEntry
  MAX-ACCESS  not-accessible
  STATUS      current
  DESCRIPTION
    "An entry displays whether different fans are normal or not."
  INDEX { ruijieSystemFanIsNormalIndex }
  ::= { ruijieSystemFanIsNormalTable 1 }

RuijieSystemFanIsNormalEntry ::=
  SEQUENCE {
    ruijieSystemFanIsNormalIndex  Integer32,
    ruijieSystemFanIsNormal  INTEGER,
    ruijieSystemFanName   DisplayString,
    ruijieSystemFanSpeed  Integer32
  }
    
ruijieSystemFanIsNormalIndex OBJECT-TYPE
    SYNTAX        Integer32(0..255)
    MAX-ACCESS    read-only
    STATUS        current
    DESCRIPTION
        "An index that uniquely represents a fan."
    ::= { ruijieSystemFanIsNormalEntry 1 }

ruijieSystemFanIsNormal OBJECT-TYPE
   	SYNTAX  INTEGER {
                noexist (1),          --no exist
                existnopower (2),     --exist no power
                existreadypower (3),  --exist ready power
                normal (4),           --normal
                powerbutabnormal (5), --power but abnormal
                unknow (6),           --unknow
                linefail (7)          --line fail
             }
    MAX-ACCESS    read-only
    STATUS        current
    DESCRIPTION
        "This object displays whether an fan is normal or not."
    ::= { ruijieSystemFanIsNormalEntry 2 }   
        
ruijieSystemFanName OBJECT-TYPE
    SYNTAX        DisplayString
    MAX-ACCESS    read-only
    STATUS        current
    DESCRIPTION
        "The name of fan"
    ::= { ruijieSystemFanIsNormalEntry 3 }     

ruijieSystemFanSpeed OBJECT-TYPE
    SYNTAX        Integer32
    MAX-ACCESS    read-only
    STATUS        current
    DESCRIPTION
        "This object displays the fan's speed."
    ::= { ruijieSystemFanIsNormalEntry 4 }   

ruijieSystemReloadTimeRemain OBJECT-TYPE
        SYNTAX Integer32
        MAX-ACCESS read-only
        STATUS current
        DESCRIPTION
          "Return the remain time of reloading on the FastSwitch."
        ::= { ruijieSystemMIBObjects 22 }      
        
ruijieSystemTemperatureTable OBJECT-TYPE
  SYNTAX      SEQUENCE OF RuijieSystemTemperatureEntry
  MAX-ACCESS  not-accessible
  STATUS      current
  DESCRIPTION
    "A table of temperature entries. Each object displays 
     the temperature information."
  ::= { ruijieSystemMIBObjects 23 }

ruijieSystemTemperatureEntry OBJECT-TYPE
  SYNTAX      RuijieSystemTemperatureEntry
  MAX-ACCESS  not-accessible
  STATUS      current
  DESCRIPTION
    "An entry displays the temperature information."
  INDEX { ruijieSystemTemperatureIndex }
  ::= { ruijieSystemTemperatureTable 1 }

RuijieSystemTemperatureEntry ::=
  SEQUENCE {
    ruijieSystemTemperatureIndex    Integer32,
    ruijieSystemTemperatureName     DisplayString,
    ruijieSystemTemperatureCurrent  Integer32,
    ruijieSystemTemperatureWarningVaule Integer32,
    ruijieSystemTemperatureCritialVaule Integer32
  }
    
ruijieSystemTemperatureIndex OBJECT-TYPE
    SYNTAX        Integer32(0..255)
    MAX-ACCESS    read-only
    STATUS        current
    DESCRIPTION
        "An index that uniquely represents a device's temperature information."
    ::= { ruijieSystemTemperatureEntry 1 }

ruijieSystemTemperatureName OBJECT-TYPE
    SYNTAX        DisplayString
    MAX-ACCESS    read-only
    STATUS        current
    DESCRIPTION
        "A textual name assigned to a temperature chip"
    ::= { ruijieSystemTemperatureEntry 2 }          
                    
ruijieSystemTemperatureCurrent OBJECT-TYPE
    SYNTAX        Integer32
    MAX-ACCESS    read-only
    STATUS        current
    DESCRIPTION
        "Return the current temperature of the FastSwitch.The temperature display
         is not supported for the current temperature returns to 0."
    ::= { ruijieSystemTemperatureEntry 3 }        
        
ruijieSystemTemperatureWarningVaule OBJECT-TYPE
    SYNTAX        Integer32
    MAX-ACCESS    read-write
    STATUS        current
    DESCRIPTION
        "The first warning of temperature of the device CPU."
    ::= { ruijieSystemTemperatureEntry 4 }       
        
ruijieSystemTemperatureCritialVaule OBJECT-TYPE
    SYNTAX        Integer32
    MAX-ACCESS    read-write
    STATUS        current
    DESCRIPTION
        "The second warning of temperature of the device CPU."
    ::= { ruijieSystemTemperatureEntry 5 }           
        
ruijieSystemSerialno OBJECT-TYPE
        SYNTAX DisplayString 
        MAX-ACCESS read-only
        STATUS current
        DESCRIPTION
          "Return the string of the serial number resides on the FastSwitch. 
          Or return the serial number resides on the current master engine of a chassis device."
        ::= { ruijieSystemMIBObjects 24 }    
    
ruijieSystemVersionTable OBJECT-TYPE
  SYNTAX      SEQUENCE OF RuijieSystemVersionEntry
  MAX-ACCESS  not-accessible
  STATUS      current
  DESCRIPTION
    "A table of system version entries. Each object displays 
     the system version information."
  ::= { ruijieSystemMIBObjects 25 }

ruijieSystemVersionEntry OBJECT-TYPE
  SYNTAX      RuijieSystemVersionEntry
  MAX-ACCESS  not-accessible
  STATUS      current
  DESCRIPTION
    "An entry displays the system version information."
  INDEX { ruijieSystemVersionIndex }
  ::= { ruijieSystemVersionTable 1 }

RuijieSystemVersionEntry ::=
  SEQUENCE {
    ruijieSystemVersionIndex    Unsigned32,
    ruijieSystemVersionName     DisplayString,
    ruijieSystemVersionSwBoot   DisplayString,
    ruijieSystemVersionSwCtrl   DisplayString,
    ruijieSystemVersionSwMain   DisplayString,
    ruijieSystemVersionHw       DisplayString,
    ruijieSystemVersionSerialno DisplayString
  }
    
ruijieSystemVersionIndex OBJECT-TYPE
    SYNTAX        Unsigned32
    MAX-ACCESS    read-only
    STATUS        current
    DESCRIPTION
        "An index that uniquely represents a device's system version information."
    ::= { ruijieSystemVersionEntry 1 }

ruijieSystemVersionName OBJECT-TYPE
    SYNTAX        DisplayString
    MAX-ACCESS    read-only
    STATUS        current
    DESCRIPTION
        "A textual name assigned to a system version chip"
    ::= { ruijieSystemVersionEntry 2 }          
                    
ruijieSystemVersionSwBoot OBJECT-TYPE
    SYNTAX        DisplayString
    MAX-ACCESS    read-only
    STATUS        current
    DESCRIPTION
        "Return the software boot system version of the FastSwitch."
    ::= { ruijieSystemVersionEntry 3 }        
        
ruijieSystemVersionSwCtrl OBJECT-TYPE
    SYNTAX        DisplayString
    MAX-ACCESS    read-only
    STATUS        current
    DESCRIPTION
        "Return the software ctrl system version of the FastSwitch."
    ::= { ruijieSystemVersionEntry 4 }       
        
ruijieSystemVersionSwMain OBJECT-TYPE
    SYNTAX        DisplayString
    MAX-ACCESS    read-only
    STATUS        current
    DESCRIPTION
        "Return the software main system version of the FastSwitch."
    ::= { ruijieSystemVersionEntry 5 }      
        
ruijieSystemVersionHw OBJECT-TYPE
    SYNTAX        DisplayString
    MAX-ACCESS    read-only
    STATUS        current
    DESCRIPTION
        "Return the hardware system version of the FastSwitch."
    ::= { ruijieSystemVersionEntry 6 }      
                
ruijieSystemVersionSerialno OBJECT-TYPE
    SYNTAX        DisplayString
    MAX-ACCESS    read-only
    STATUS        current
    DESCRIPTION
        "Return the serial number of the FastSwitch."
    ::= { ruijieSystemVersionEntry 7 }               

--System models added 2010-05
ruijieSystemSysModel OBJECT-TYPE
    SYNTAX        DisplayString
    MAX-ACCESS    read-only
    STATUS        current
    DESCRIPTION
        "Return the SysModel of equipment."
    ::={ ruijieSystemMIBObjects 26 }
    
ruijieSystemUptime OBJECT-TYPE
    SYNTAX        INTEGER
    MAX-ACCESS    read-only
    STATUS        current
    DESCRIPTION
        "Return the SysUptime of equipment,unit is seconds."
    ::={ ruijieSystemMIBObjects 27 }
    
--System Sample Time 2010-05
ruijieSystemSampleTime OBJECT-TYPE
    SYNTAX        Integer32
    MAX-ACCESS    read-write
    STATUS        current
    DESCRIPTION
        "Sampling duration."
    ::={ ruijieSystemMIBObjects 28 }
    
ruijieSystemStatWindowTime OBJECT-TYPE
    SYNTAX        Integer32
    MAX-ACCESS    read-write
    STATUS        current
    DESCRIPTION
        "Stating duration."
    ::={ ruijieSystemMIBObjects 29 }
    
ruijieSystemManufacturer OBJECT-TYPE
    SYNTAX DisplayString 
    MAX-ACCESS read-only
    STATUS current
    DESCRIPTION
      "Return the string of the manufacturer."
    ::= { ruijieSystemMIBObjects 30 }    
    
ruijieSystemCurrentTime OBJECT-TYPE
    SYNTAX DisplayString 
    MAX-ACCESS read-write
    STATUS current
    DESCRIPTION
      "Return the current time of the system."
    ::= { ruijieSystemMIBObjects 31 }    
    
ruijieSystemWarnResendTime OBJECT-TYPE
    SYNTAX Integer32
    MAX-ACCESS read-write
    STATUS current
    DESCRIPTION
      "Return the resending time of warn trap of the system."
    ::= { ruijieSystemMIBObjects 32 }    
    
ruijieSystemSoftwareName OBJECT-TYPE
    SYNTAX DisplayString
    MAX-ACCESS read-only
    STATUS current
    DESCRIPTION
      "Return the software name of the system."
    ::= { ruijieSystemMIBObjects 33 }    
    
ruijieSystemSoftwareManufacturer OBJECT-TYPE
    SYNTAX DisplayString
    MAX-ACCESS read-only
    STATUS current
    DESCRIPTION
      "Return the software manufacturer of the system."
    ::= { ruijieSystemMIBObjects 34 }    
    
ruijieSystemCpuType OBJECT-TYPE
    SYNTAX DisplayString
    MAX-ACCESS read-only
    STATUS current
    DESCRIPTION
      "Return the cpu type infomation of the system."
    ::= { ruijieSystemMIBObjects 35 }    
    
ruijieSystemMemoryType OBJECT-TYPE
    SYNTAX DisplayString
    MAX-ACCESS read-only
    STATUS current
    DESCRIPTION
      "Return the memory type of the system."
    ::= { ruijieSystemMIBObjects 36 }    
    
ruijieSystemMemorySize OBJECT-TYPE
    SYNTAX Gauge
    MAX-ACCESS read-only
    STATUS current
    DESCRIPTION
      "Return the memory card storage of the system."
    ::= { ruijieSystemMIBObjects 37 }    
    
ruijieSystemFlashSize OBJECT-TYPE
    SYNTAX Gauge
    MAX-ACCESS read-only
    STATUS current
    DESCRIPTION
      "Return the flash size of the system."
    ::= { ruijieSystemMIBObjects 38 }    
    
 --lank ap 2010-7    
ruijieSystemLankApTable OBJECT-TYPE
  SYNTAX      SEQUENCE OF RuijieSystemLankApEntry
  MAX-ACCESS  not-accessible
  STATUS      current
  DESCRIPTION
    "A table of lank ap system entries. Each object displays 
     the lank ap system information."
  ::= { ruijieSystemMIBObjects 39 }

ruijieSystemLankApEntry OBJECT-TYPE
  SYNTAX      RuijieSystemLankApEntry
  MAX-ACCESS  not-accessible
  STATUS      current
  DESCRIPTION
    "An entry displays the lank ap system information."
  INDEX { ruijieSystemLankApMacAddr }
  ::= { ruijieSystemLankApTable 1 }

RuijieSystemLankApEntry ::=
  SEQUENCE {
    ruijieSystemLankApMacAddr              MacAddress,
    ruijieSystemLankApStatWindowTime       Integer32,
    ruijieSystemLankApSampleTime           Integer32,
    ruijieSystemLankApReset                INTEGER,
    ruijieSystemLankApSoftwareName         DisplayString,
    ruijieSystemLankApSwVersion            DisplayString,
    ruijieSystemLankApSoftwareManufacturer DisplayString,
    ruijieSystemLankApCpuType              DisplayString,
    ruijieSystemLankApMemoryType           DisplayString,
    ruijieSystemLankApMemorySize           Gauge,
    ruijieSystemLankAPFlashSize            Gauge,
    ruijieSystemLankApManufacturer         DisplayString,
    ruijieSystemLankApSerialno             DisplayString,
    ruijieSystemLankApSysModel             DisplayString,
    ruijieSystemLankApUptime               INTEGER,
    ruijieSystemLankApAccurateUptime       TimeTicks,
    ruijieSystemLankApHwVersion            DisplayString
  }
    
ruijieSystemLankApMacAddr OBJECT-TYPE
    SYNTAX        MacAddress
    MAX-ACCESS    read-only
    STATUS        current
    DESCRIPTION
        "An index that uniquely represents lank ap system information."
    ::= { ruijieSystemLankApEntry 1 }    
    
ruijieSystemLankApStatWindowTime OBJECT-TYPE
    SYNTAX        Integer32
    MAX-ACCESS    read-write
    STATUS        current
    DESCRIPTION
        "Stating duration of lank ap."
    ::={ ruijieSystemLankApEntry 2 }   

ruijieSystemLankApSampleTime OBJECT-TYPE
    SYNTAX        Integer32
    MAX-ACCESS    read-write
    STATUS        current
    DESCRIPTION
        "Sampling duration of lank ap."
    ::={ ruijieSystemLankApEntry 3 }    
    
ruijieSystemLankApReset OBJECT-TYPE
    SYNTAX INTEGER {
        normal(0),
        restart(1)
    }
    MAX-ACCESS read-write
    STATUS current
    DESCRIPTION
        "This Object allow perform soft reset of lank ap system by setting 
         its value to none zero. if a soft resetis performed, after this 
         having completed a warm start trap will send to declare the state
         and when queried will always return 0."
    ::= { ruijieSystemLankApEntry 4 }
        
ruijieSystemLankApSoftwareName OBJECT-TYPE
    SYNTAX DisplayString
    MAX-ACCESS read-only
    STATUS current
    DESCRIPTION
      "Return the software name of the lank ap system."
    ::= { ruijieSystemLankApEntry 5 }    

ruijieSystemLankApSwVersion OBJECT-TYPE
    SYNTAX DisplayString(SIZE (1..32))
    MAX-ACCESS read-only
    STATUS current
    DESCRIPTION
        "Return the string of the Revision number of software resides
         on the lank ap FastSwitch."
    ::= { ruijieSystemLankApEntry 6 }   
    
ruijieSystemLankApSoftwareManufacturer OBJECT-TYPE
    SYNTAX DisplayString
    MAX-ACCESS read-only
    STATUS current
    DESCRIPTION
      "Return the software manufacturer of the lank ap system."
    ::= { ruijieSystemLankApEntry 7 } 
  
ruijieSystemLankApCpuType OBJECT-TYPE
    SYNTAX DisplayString
    MAX-ACCESS read-only
    STATUS current
    DESCRIPTION
      "Return the cpu type infomation of the lank ap system."
    ::= { ruijieSystemLankApEntry 8 }  
   
ruijieSystemLankApMemoryType OBJECT-TYPE
    SYNTAX DisplayString
    MAX-ACCESS read-only
    STATUS current
    DESCRIPTION
      "Return the memory type of the lank ap system."
    ::= { ruijieSystemLankApEntry 9 }    
 
ruijieSystemLankApMemorySize OBJECT-TYPE
    SYNTAX Gauge
    MAX-ACCESS read-only
    STATUS current
    DESCRIPTION
      "Return the memory card storage of the lank ap system."
    ::= { ruijieSystemLankApEntry 10 }    

ruijieSystemLankAPFlashSize OBJECT-TYPE
    SYNTAX Gauge
    MAX-ACCESS read-only
    STATUS current
    DESCRIPTION
      "Return the flash size of the lank ap system."
    ::= { ruijieSystemLankApEntry 11 }   
    
ruijieSystemLankApManufacturer OBJECT-TYPE
    SYNTAX DisplayString 
    MAX-ACCESS read-only
    STATUS current
    DESCRIPTION
      "Return the string of the manufacturer of lank ap."
    ::= { ruijieSystemLankApEntry 12} 
    
ruijieSystemLankApSerialno OBJECT-TYPE
        SYNTAX DisplayString 
        MAX-ACCESS read-only
        STATUS current
        DESCRIPTION
          "Return the string of the serial number resides
          on the lank ap FastSwitch."
        ::= { ruijieSystemLankApEntry 13 }    
        
ruijieSystemLankApSysModel OBJECT-TYPE
    SYNTAX        DisplayString
    MAX-ACCESS    read-only
    STATUS        current
    DESCRIPTION
        "Return the SysModel of lank ap equipment."
    ::={ ruijieSystemLankApEntry 14 }
      
ruijieSystemLankApUptime OBJECT-TYPE
    SYNTAX        INTEGER
    MAX-ACCESS    read-only
    STATUS        current
    DESCRIPTION
        "Return the SysUptime of lank ap equipment."
    ::={ ruijieSystemLankApEntry 15 }
    
ruijieSystemLankApAccurateUptime OBJECT-TYPE
    SYNTAX        TimeTicks
    MAX-ACCESS    read-only
    STATUS        current
    DESCRIPTION
        "Return the accurate system Uptime of ap equipment,unit is ticks"
    ::={ ruijieSystemLankApEntry 16 }

ruijieSystemLankApHwVersion OBJECT-TYPE
    SYNTAX DisplayString(SIZE (1..32))
    MAX-ACCESS read-only
    STATUS current
    DESCRIPTION
        "Return the string of the Revision number of hardware resides
         on the lank ap FastSwitch."
    ::= { ruijieSystemLankApEntry 17 }   
    

ruijieSystemBoardTemperatureTable OBJECT-TYPE
  SYNTAX      SEQUENCE OF RuijieSystemBoardTemperatureEntry
  MAX-ACCESS  not-accessible
  STATUS      current
  DESCRIPTION
    "A table of board temperature entries. Each object displays 
     the board temperature information."
  ::= { ruijieSystemMIBObjects 40 }

ruijieSystemBoardTemperatureEntry OBJECT-TYPE
  SYNTAX      RuijieSystemBoardTemperatureEntry
  MAX-ACCESS  not-accessible
  STATUS      current
  DESCRIPTION
    "An entry displays the board temperature information."
  INDEX { ruijieSystemBoardTemperatureIndex }
  ::= { ruijieSystemBoardTemperatureTable 1 }

RuijieSystemBoardTemperatureEntry ::=
  SEQUENCE {
    ruijieSystemBoardTemperatureIndex    Integer32,
    ruijieSystemBoardTemperatureName     DisplayString,
    ruijieSystemBoardTemperatureCurrent  Integer32
  }
    
ruijieSystemBoardTemperatureIndex OBJECT-TYPE
    SYNTAX        Integer32(0..255)
    MAX-ACCESS    read-only
    STATUS        current
    DESCRIPTION
        "An index that uniquely represents a device's board temperature information."
    ::= { ruijieSystemBoardTemperatureEntry 1 }

ruijieSystemBoardTemperatureName OBJECT-TYPE
    SYNTAX        DisplayString
    MAX-ACCESS    read-only
    STATUS        current
    DESCRIPTION
        "A textual name assigned to a board temperature chip"
    ::= { ruijieSystemBoardTemperatureEntry 2 }          
                    
ruijieSystemBoardTemperatureCurrent OBJECT-TYPE
    SYNTAX        Integer32
    MAX-ACCESS    read-only
    STATUS        current
    DESCRIPTION
        "Return the current board temperature of the FastSwitch.The temperature display
         is not supported for the current temperature returns to 0."
    ::= { ruijieSystemBoardTemperatureEntry 3 }    

ruijieSystemElectricalInformationTable OBJECT-TYPE
  SYNTAX      SEQUENCE OF RuijieSystemElectricalInformationEntry
  MAX-ACCESS  not-accessible
  STATUS      current
  DESCRIPTION
    "A table of electrical entries. Each object displays the electrical information."
  ::= { ruijieSystemMIBObjects 41 }

ruijieSystemElectricalInformationEntry OBJECT-TYPE
  SYNTAX      RuijieSystemElectricalInformationEntry
  MAX-ACCESS  not-accessible
  STATUS      current
  DESCRIPTION
    "An entry displays the electrical information."
  INDEX {ruijieSystemElectricalInformationDeviceIndex, ruijieSystemElectricalInformationIndex }
  ::= { ruijieSystemElectricalInformationTable 1 }

RuijieSystemElectricalInformationEntry ::=
  SEQUENCE {
    ruijieSystemElectricalInformationDeviceIndex      Integer32,
    ruijieSystemElectricalInformationIndex            Integer32,
    ruijieSystemElectricalInformationStatus           INTEGER,
    ruijieSystemElectricalInformationType             DisplayString,
    ruijieSystemElectricalInformationAttribute        DisplayString,
    ruijieSystemElectricalInformationSofeVersion      DisplayString,
    ruijieSystemElectricalInformationHardwareVersion  DisplayString,
    ruijieSystemElectricalInformationSerial           DisplayString,
    ruijieSystemElectricalInformationProductionDate   DisplayString,
    ruijieSystemElectricalInformationRatedPower       Integer32,
    ruijieSystemElectricalInformationInVoltage        Integer32,
    ruijieSystemElectricalInformationInCurrent        Integer32,
    ruijieSystemElectricalInformationOutVoltage       Integer32,
    ruijieSystemElectricalInformationOutCurrent       Integer32,
    ruijieSystemElectricalInformationOutPower         Integer32,
    ruijieSystemElectricalInformationTemperature      Integer32,
    ruijieSystemElectricalInformationAirflowCoexist   DisplayString,
    ruijieSystemElectricalInformationWarningStatus    DisplayString,
    ruijieSystemElectricalInformationMode             DisplayString
  }

ruijieSystemElectricalInformationDeviceIndex OBJECT-TYPE
    SYNTAX        Integer32(0..255)
    MAX-ACCESS    read-only
    STATUS        current
    DESCRIPTION
        "An index that uniquely represents a device."
    ::= { ruijieSystemElectricalInformationEntry 1 }

ruijieSystemElectricalInformationIndex OBJECT-TYPE
    SYNTAX        Integer32(0..255)
    MAX-ACCESS    read-only
    STATUS        current
    DESCRIPTION
        "An index that uniquely represents a electriacl."
    ::= { ruijieSystemElectricalInformationEntry 2 }

ruijieSystemElectricalInformationStatus OBJECT-TYPE
   	SYNTAX  INTEGER {
                noexist (1),          --no exist
                existnopower (2),     -- exist no power
                existreadypower (3),  --exist ready power
                normal (4),           --normal
                powerbutabnormal (5), --power but abnormal
                unknow (6)            --unknow
             }
    MAX-ACCESS    read-only
    STATUS        current
    DESCRIPTION
        "This object displays whether an electrical source is normal or not.
         If the electrical is no exist, the other of electrical information maybe 
         return nothing information and 0."
    ::= { ruijieSystemElectricalInformationEntry 3 }

ruijieSystemElectricalInformationType OBJECT-TYPE
    SYNTAX        DisplayString
    MAX-ACCESS    read-only
    STATUS        current
    DESCRIPTION
        "This object displays the type of the electrical. If the device is no support this information,
         This object will return nothing information."
    ::= { ruijieSystemElectricalInformationEntry 4 }

ruijieSystemElectricalInformationAttribute OBJECT-TYPE
    SYNTAX        DisplayString
    MAX-ACCESS    read-only
    STATUS        current
    DESCRIPTION
        "This object displays attribute of the electrical. If the device is no support
         this information, This object will return nothing information."
    ::= { ruijieSystemElectricalInformationEntry 5 }

ruijieSystemElectricalInformationSofeVersion OBJECT-TYPE
    SYNTAX        DisplayString
    MAX-ACCESS    read-only
    STATUS        current
    DESCRIPTION
        "This object displays the sofe version of the electrical. If the device is no support
         this information, This object will return nothing information."
    ::= { ruijieSystemElectricalInformationEntry 6}

ruijieSystemElectricalInformationHardwareVersion OBJECT-TYPE
    SYNTAX        DisplayString
    MAX-ACCESS    read-only
    STATUS        current
    DESCRIPTION
        "This object displays the hardware version of the electrical. If the device is no support
         this information, This object will return nothing information."
    ::= { ruijieSystemElectricalInformationEntry 7 }

ruijieSystemElectricalInformationSerial OBJECT-TYPE
    SYNTAX        DisplayString
    MAX-ACCESS    read-only
    STATUS        current
    DESCRIPTION
        "This object displays the serial of the electrical. If the device is no support
         this information, This object will return nothing information."
    ::= { ruijieSystemElectricalInformationEntry 8 }

ruijieSystemElectricalInformationProductionDate OBJECT-TYPE
    SYNTAX        DisplayString
    MAX-ACCESS    read-only
    STATUS        current
    DESCRIPTION
        "This object displays the productiron date of the electrical. If the device is no support
         this information, This object will return nothing information."
    ::= { ruijieSystemElectricalInformationEntry 9 }

ruijieSystemElectricalInformationRatedPower OBJECT-TYPE
    SYNTAX        Integer32
    MAX-ACCESS    read-only
    STATUS        current
    DESCRIPTION
        "This object displays the rated power(Unit: W) of the electrical. If the device is no support
         this information, This object will return 0."
    ::= { ruijieSystemElectricalInformationEntry 10 }

ruijieSystemElectricalInformationInVoltage OBJECT-TYPE
    SYNTAX        Integer32
    MAX-ACCESS    read-only
    STATUS        current
    DESCRIPTION
        "This object displays the input voltage(Unit: V) of the electrical. If the device is no support
         this information, This object will return 0."
    ::= { ruijieSystemElectricalInformationEntry 11 }

ruijieSystemElectricalInformationInCurrent OBJECT-TYPE
    SYNTAX        Integer32
    MAX-ACCESS    read-only
    STATUS        current
    DESCRIPTION
        "This object displays the input current(Unit: mA) of the electrical. If the device is no support
         this information, This object will return 0."
    ::= { ruijieSystemElectricalInformationEntry 12 }

ruijieSystemElectricalInformationOutVoltage OBJECT-TYPE
    SYNTAX        Integer32
    MAX-ACCESS    read-only
    STATUS        current
    DESCRIPTION
        "This object displays the output voltage(Unit: mV) of the electrical. If the device is no support
         this information, This object will return 0."
    ::= { ruijieSystemElectricalInformationEntry 13 }

ruijieSystemElectricalInformationOutCurrent OBJECT-TYPE
    SYNTAX        Integer32
    MAX-ACCESS    read-only
    STATUS        current
    DESCRIPTION
        "This object displays the output current(Unit: mA) of the electrical. If the device is no support
         this information, This object will return 0."
    ::= { ruijieSystemElectricalInformationEntry 14 }

ruijieSystemElectricalInformationOutPower OBJECT-TYPE
    SYNTAX        Integer32
    MAX-ACCESS    read-only
    STATUS        current
    DESCRIPTION
        "This object displays the output power(Unit: mW) of the electrical. If the device is no support
         this information, This object will return 0."
    ::= { ruijieSystemElectricalInformationEntry 15 }

ruijieSystemElectricalInformationTemperature OBJECT-TYPE
    SYNTAX        Integer32
    MAX-ACCESS    read-only
    STATUS        current
    DESCRIPTION
        "This object displays the temperature(Unit: C) of the electrical. If the device is no support
         this information, This object will return -255."
    ::= { ruijieSystemElectricalInformationEntry 16 }

ruijieSystemElectricalInformationAirflowCoexist OBJECT-TYPE
    SYNTAX        DisplayString
    MAX-ACCESS    read-only
    STATUS        current
    DESCRIPTION
        "This object displays the airflow coexist of the electrical. If the device is no support
         this information, This object will return nothing information."
    ::= { ruijieSystemElectricalInformationEntry 17 }

ruijieSystemElectricalInformationWarningStatus OBJECT-TYPE
    SYNTAX        DisplayString
    MAX-ACCESS    read-only
    STATUS        current
    DESCRIPTION
        "This object displays the warning status of the electrical. If the device is no support
         this information, This object will return nothing information."
    ::= { ruijieSystemElectricalInformationEntry 18 }	

ruijieSystemElectricalInformationMode OBJECT-TYPE
    SYNTAX        DisplayString
    MAX-ACCESS    read-only
    STATUS        current
    DESCRIPTION
        "This object displays the mode of the electrical. If the device is no support
         this information, This object will return nothing information."
    ::= { ruijieSystemElectricalInformationEntry 19 }

ruijieSystemFanInformationTable OBJECT-TYPE
  SYNTAX      SEQUENCE OF RuijieSystemFanInformationEntry
  MAX-ACCESS  not-accessible
  STATUS      current
  DESCRIPTION
    "A table of fan entries. Each object displays the fan information."
  ::= { ruijieSystemMIBObjects 42 }

ruijieSystemFanInformationEntry OBJECT-TYPE
  SYNTAX      RuijieSystemFanInformationEntry
  MAX-ACCESS  not-accessible
  STATUS      current
  DESCRIPTION
    "An entry displays the fan information."
  INDEX { ruijieSystemFanInformationDeviceIndex ,  ruijieSystemFanInformationFanIndex}
  ::= {ruijieSystemFanInformationTable 1 }

RuijieSystemFanInformationEntry ::=
  SEQUENCE {
    ruijieSystemFanInformationDeviceIndex      Integer32,
    ruijieSystemFanInformationFanIndex         Integer32,
    ruijieSystemFanInformationStatus           INTEGER,
    ruijieSystemFanInformationType             DisplayString,
    ruijieSystemFanInformationAttribute        DisplayString,
    ruijieSystemFanInformationSofeVersion      DisplayString,
    ruijieSystemFanInformationFirmwareVersion  DisplayString,
    ruijieSystemFanInformationHardwareVersion  DisplayString,
    ruijieSystemFanInformationSerial           DisplayString,
    ruijieSystemFanInformationProductionDate   DisplayString,
    ruijieSystemFanInformationTemperature      Integer32,
    ruijieSystemFanInformationNumber           Integer32,
    ruijieSystemFanInformationAirflowCoexist   DisplayString,
    ruijieSystemFanInformationWarningStatus    DisplayString
  }

ruijieSystemFanInformationDeviceIndex  OBJECT-TYPE
    SYNTAX        Integer32(0..255)
    MAX-ACCESS    read-only
    STATUS        current
    DESCRIPTION
        "An index that uniquely represents a device."
    ::= { ruijieSystemFanInformationEntry 1 }

ruijieSystemFanInformationFanIndex OBJECT-TYPE
    SYNTAX        Integer32(0..255)
    MAX-ACCESS    read-only
    STATUS        current
    DESCRIPTION
        "An index that uniquely represents a fan device."
    ::= { ruijieSystemFanInformationEntry 2 }

ruijieSystemFanInformationStatus OBJECT-TYPE
   	SYNTAX  INTEGER {
                noexist (1),          --no exist
                existnopower (2),     --exist no power
                existreadypower (3),  --exist ready power
                normal (4),           --normal
                powerbutabnormal (5), --power but abnormal
                unknow (6),           --unknow
                linefail (7)          --line fail
             }
    MAX-ACCESS    read-only
    STATUS        current
    DESCRIPTION
        "This object displays whether an fan device source is exist or not.
         If the fan device is no exist, the other of fan information maybe 
         return nothing information and 0."
    ::= { ruijieSystemFanInformationEntry 3 }

ruijieSystemFanInformationType OBJECT-TYPE
    SYNTAX        DisplayString
    MAX-ACCESS    read-only
    STATUS        current
    DESCRIPTION
        "This object displays the type of the fan. If the device is no support this information,
         This object will return nothing information."
    ::= { ruijieSystemFanInformationEntry 4 }

ruijieSystemFanInformationAttribute OBJECT-TYPE
    SYNTAX        DisplayString
    MAX-ACCESS    read-only
    STATUS        current
    DESCRIPTION
        "This object displays attribute of the fan. If the device is no support
         this information, This object will return nothing information."
    ::= { ruijieSystemFanInformationEntry 5 }

ruijieSystemFanInformationSofeVersion OBJECT-TYPE
    SYNTAX        DisplayString
    MAX-ACCESS    read-only
    STATUS        current
    DESCRIPTION
        "This object displays the sofe version of the fan. If the device is no support
         this information, This object will return nothing information."
    ::= { ruijieSystemFanInformationEntry 6}

ruijieSystemFanInformationFirmwareVersion OBJECT-TYPE
    SYNTAX        DisplayString
    MAX-ACCESS    read-only
    STATUS        current
    DESCRIPTION
        "This object displays the firmware version of the fan. If the device is no support
         this information, This object will return nothing information."
    ::= { ruijieSystemFanInformationEntry 7 }

ruijieSystemFanInformationHardwareVersion OBJECT-TYPE
    SYNTAX        DisplayString
    MAX-ACCESS    read-only
    STATUS        current
    DESCRIPTION
        "This object displays the hardware version of the fan. If the device is no support
         this information, This object will return nothing information."
    ::= { ruijieSystemFanInformationEntry 8 }

ruijieSystemFanInformationSerial OBJECT-TYPE
    SYNTAX        DisplayString
    MAX-ACCESS    read-only
    STATUS        current
    DESCRIPTION
        "This object displays the serial of the fan. If the device is no support
         this information, This object will return nothing information."
    ::= { ruijieSystemFanInformationEntry 9 }

ruijieSystemFanInformationProductionDate OBJECT-TYPE
    SYNTAX        DisplayString
    MAX-ACCESS    read-only
    STATUS        current
    DESCRIPTION
        "This object displays the productiron date of the fan. If the device is no support
         this information, This object will return nothing information."
    ::= { ruijieSystemFanInformationEntry 10 }

ruijieSystemFanInformationTemperature OBJECT-TYPE
    SYNTAX        Integer32
    MAX-ACCESS    read-only
    STATUS        current
    DESCRIPTION
        "This object displays the temperature of the fan device. If the device is no support
         this information, This object will return -255."
    ::= { ruijieSystemFanInformationEntry 11 }

ruijieSystemFanInformationNumber OBJECT-TYPE
    SYNTAX        Integer32
    MAX-ACCESS    read-only
    STATUS        current
    DESCRIPTION
        "This object displays the number of the fan device. If the device is no support
         this information, This object will return 0."
    ::= { ruijieSystemFanInformationEntry 12 }

ruijieSystemFanInformationAirflowCoexist OBJECT-TYPE
    SYNTAX        DisplayString
    MAX-ACCESS    read-only
    STATUS        current
    DESCRIPTION
        "This object displays the airflow coexist of the fan device. If the device is no support
         this information, This object will return nothing information."
    ::= { ruijieSystemFanInformationEntry 13 }

ruijieSystemFanInformationWarningStatus OBJECT-TYPE
    SYNTAX        DisplayString
    MAX-ACCESS    read-only
    STATUS        current
    DESCRIPTION
        "This object displays the warning status of the fan device. If the device is no support
         this information, This object will return nothing information."
    ::= { ruijieSystemFanInformationEntry 14 }

ruijieSystemFanStatusTable OBJECT-TYPE
  SYNTAX      SEQUENCE OF RuijieSystemFanStatusEntry
  MAX-ACCESS  not-accessible
  STATUS      current
  DESCRIPTION
    "A table of fan status entries. Each object displays the fan status information."
  ::= { ruijieSystemMIBObjects 43 }

ruijieSystemFanStatusEntry OBJECT-TYPE
  SYNTAX      RuijieSystemFanStatusEntry
  MAX-ACCESS  not-accessible
  STATUS      current
  DESCRIPTION
    "An entry displays the fan status information."
  INDEX { ruijieSystemFanStatusDeviceIndex,
          ruijieSystemFanStatusFanIndex,
          ruijieSystemFanStatusIndex }
  ::= {ruijieSystemFanStatusTable 1 }

RuijieSystemFanStatusEntry ::=
  SEQUENCE {
    ruijieSystemFanStatusDeviceIndex      Integer32,
    ruijieSystemFanStatusFanIndex         Integer32,
    ruijieSystemFanStatusIndex            Integer32,
    ruijieSystemFanStatus                 INTEGER,
    ruijieSystemFanStatusLevel            Integer32,
    ruijieSystemFanStatusSpeed            Integer32
  }

ruijieSystemFanStatusDeviceIndex  OBJECT-TYPE
    SYNTAX        Integer32(0..255)
    MAX-ACCESS    read-only
    STATUS        current
    DESCRIPTION
        "An index that uniquely represents a device."
    ::= { ruijieSystemFanStatusEntry 1 }

ruijieSystemFanStatusFanIndex OBJECT-TYPE
    SYNTAX        Integer32(0..255)
    MAX-ACCESS    read-only
    STATUS        current
    DESCRIPTION
        "An index that uniquely represents a fan device."
    ::= { ruijieSystemFanStatusEntry 2 }

ruijieSystemFanStatusIndex OBJECT-TYPE
    SYNTAX        Integer32(0..255)
    MAX-ACCESS    read-only
    STATUS        current
    DESCRIPTION
        "An index that uniquely represents a fan."
    ::= { ruijieSystemFanStatusEntry 3 }

ruijieSystemFanStatus OBJECT-TYPE
   	SYNTAX  INTEGER {
                noexist (1),          --no exist
                existnopower (2),     --exist no power
                existreadypower (3),  --exist ready power
                normal (4),           --normal
                powerbutabnormal (5), --power but abnormal
                unknow (6)            --unknow
             }
    MAX-ACCESS    read-only
    STATUS        current
    DESCRIPTION
        "This object displays whether an fan is normal or not."
    ::= { ruijieSystemFanStatusEntry 4 }

ruijieSystemFanStatusLevel OBJECT-TYPE
    SYNTAX        Integer32
    MAX-ACCESS    read-only
    STATUS        current
    DESCRIPTION
        "This object displays the level of the fan speed. If the device is no support this information,
         This object will return 0."
    ::= { ruijieSystemFanStatusEntry 5 }

ruijieSystemFanStatusSpeed OBJECT-TYPE
    SYNTAX        Integer32
    MAX-ACCESS    read-only
    STATUS        current
    DESCRIPTION
        "This object displays fan speed(rpm). If the device is no support
         this information, This object will return nothing information."
    ::= { ruijieSystemFanStatusEntry 6 }

ruijieSystemMultipleTemperatureTable OBJECT-TYPE
  SYNTAX      SEQUENCE OF RuijieSystemMultipleTemperatureEntry
  MAX-ACCESS  not-accessible
  STATUS      current
  DESCRIPTION
    "A table of multiple temperature entries. Each object displays 
     the multiple temperature information."
  ::= { ruijieSystemMIBObjects 44 }

ruijieSystemMultipleTemperatureEntry OBJECT-TYPE
  SYNTAX      RuijieSystemMultipleTemperatureEntry
  MAX-ACCESS  not-accessible
  STATUS      current
  DESCRIPTION
    "An entry displays the multiple temperature information."
  INDEX { ruijieSystemMultipleTemperatureDeviceIndex,
          ruijieSystemMultipleTemperatureSlotIndex, 
          ruijieSystemMultipleTemperatureIndex }
  ::= { ruijieSystemMultipleTemperatureTable 1 }

RuijieSystemMultipleTemperatureEntry ::=
  SEQUENCE {
    ruijieSystemMultipleTemperatureDeviceIndex  Integer32,
    ruijieSystemMultipleTemperatureSlotIndex    Integer32,
    ruijieSystemMultipleTemperatureIndex        Integer32,
    ruijieSystemMultipleTemperatureName         DisplayString,
    ruijieSystemMultipleTemperatureCurrent      Integer32,
    ruijieSystemMultipleTemperatureWarning      Integer32,
    ruijieSystemMultipleTemperatureCritical     Integer32,
    ruijieSystemMultipleTemperatureStatus       INTEGER
  }

ruijieSystemMultipleTemperatureDeviceIndex OBJECT-TYPE
    SYNTAX        Integer32(0..255)
    MAX-ACCESS    read-only
    STATUS        current
    DESCRIPTION
        "An index that uniquely represents a device."
    ::= { ruijieSystemMultipleTemperatureEntry 1 }

ruijieSystemMultipleTemperatureSlotIndex OBJECT-TYPE
    SYNTAX        Integer32(0..255)
    MAX-ACCESS    read-only
    STATUS        current
    DESCRIPTION
        "An index that uniquely represents a slot device."
    ::= { ruijieSystemMultipleTemperatureEntry 2 }

ruijieSystemMultipleTemperatureIndex OBJECT-TYPE
    SYNTAX        Integer32(0..255)
    MAX-ACCESS    read-only
    STATUS        current
    DESCRIPTION
        "An index that uniquely represents a device's multiple temperature information."
    ::= { ruijieSystemMultipleTemperatureEntry 3 }

ruijieSystemMultipleTemperatureName OBJECT-TYPE
    SYNTAX        DisplayString
    MAX-ACCESS    read-only
    STATUS        current
    DESCRIPTION
        "A textual name assigned to a multiple temperature chip"
    ::= { ruijieSystemMultipleTemperatureEntry 4 }          
                    
ruijieSystemMultipleTemperatureCurrent OBJECT-TYPE
    SYNTAX        Integer32
    MAX-ACCESS    read-only
    STATUS        current
    DESCRIPTION
        "Return the current multiple temperature of the FastSwitch.The temperature display
         is not supported for the current temperature returns to -255."
::= { ruijieSystemMultipleTemperatureEntry 5 }

ruijieSystemMultipleTemperatureWarning OBJECT-TYPE
    SYNTAX        Integer32
    MAX-ACCESS    read-write
    STATUS        current
    DESCRIPTION
        "Return the warning multiple temperature of the FastSwitch.The temperature display
         is not supported for the warning temperature returns to -255."
::= { ruijieSystemMultipleTemperatureEntry 6 }

ruijieSystemMultipleTemperatureCritical OBJECT-TYPE
    SYNTAX        Integer32
    MAX-ACCESS    read-write
    STATUS        current
    DESCRIPTION
        "Return the critical multiple temperature of the FastSwitch.The temperature display
         is not supported for the critical temperature returns to -255."
::= { ruijieSystemMultipleTemperatureEntry 7 }

ruijieSystemMultipleTemperatureStatus OBJECT-TYPE
   	SYNTAX  INTEGER {
                ok (1),          --status ok
                warning (2),     --status warning
                critical (3),    --status critical
                fail (4)         --status fail
             }
    MAX-ACCESS    read-only
    STATUS        current
    DESCRIPTION
        "This object displays whether the temperature is normal or not."
    ::= { ruijieSystemMultipleTemperatureEntry 8 }
        
ruijieSystemAccurateUptime OBJECT-TYPE
    SYNTAX        TimeTicks
    MAX-ACCESS    read-only
    STATUS        current
    DESCRIPTION
        "Return the accurate system Uptime of equipment,unit is ticks."
    ::={ ruijieSystemMIBObjects 45 }     

ruijieSystemPowerIndex OBJECT-TYPE
    SYNTAX Integer32
    MAX-ACCESS read-only
    STATUS current
    DESCRIPTION
        "Index of power"
    ::= { ruijieSystemMIBObjects 46 }

ruijieSystemSwitchID OBJECT-TYPE
    SYNTAX Integer32
    MAX-ACCESS read-only
    STATUS current
    DESCRIPTION
        "Switch id in VSU"
    ::= { ruijieSystemMIBObjects 47 }

ruijieSystemApDeviceDescriptionTable OBJECT-TYPE
  SYNTAX      SEQUENCE OF RuijieSystemApDeviceDescriptionEntry
  MAX-ACCESS  not-accessible
  STATUS      current
  DESCRIPTION
    "A table of lank ap system entries. Each object displays 
     the lank ap system information."
  ::= { ruijieSystemMIBObjects 48 }

ruijieSystemApDeviceDescriptionEntry OBJECT-TYPE
  SYNTAX      RuijieSystemApDeviceDescriptionEntry
  MAX-ACCESS  not-accessible
  STATUS      current
  DESCRIPTION
    "An entry displays the ap Device Description."
  INDEX { ruijieSystemApDescMacAddr }
  ::= { ruijieSystemApDeviceDescriptionTable 1 }

RuijieSystemApDeviceDescriptionEntry ::=
  SEQUENCE {
    ruijieSystemApDescMacAddr          MacAddress,
    ruijieSystemApMemoryType           INTEGER,
    ruijieSystemApMemorySize           Gauge,
    ruijieSystemAPFlashType            INTEGER,
    ruijieSystemAPFlashSize            Gauge,
    ruijieSystemApNVRAMSize            Gauge,
    ruijieSystemApCFSize               Gauge,
    ruijieSystemApCPUType              DisplayString        
  }
    
ruijieSystemApDescMacAddr OBJECT-TYPE
    SYNTAX        MacAddress
    MAX-ACCESS    read-only
    STATUS        current
    DESCRIPTION
        "An index that uniquely represents ap system information."
    ::= { ruijieSystemApDeviceDescriptionEntry 1 } 

ruijieSystemApMemoryType OBJECT-TYPE
    SYNTAX INTEGER {
        reserved(0),
        sdram(1),
        ddram(2)
    }
    MAX-ACCESS    read-only
    STATUS        current
    DESCRIPTION
        "Return the memory type of the lank ap system."
    ::= { ruijieSystemApDeviceDescriptionEntry 2 } 

ruijieSystemApMemorySize OBJECT-TYPE
    SYNTAX        Gauge
    MAX-ACCESS    read-only
    STATUS        current
    DESCRIPTION
        "Return the memory card storage of the lank ap system, unit is MB."
    ::= { ruijieSystemApDeviceDescriptionEntry 3 } 

ruijieSystemAPFlashType OBJECT-TYPE
    SYNTAX INTEGER {
        reserved(0),
        nor(1),
        non-nor(2)
    }
    MAX-ACCESS    read-only
    STATUS        current
    DESCRIPTION
        "An index that uniquely represents ap system information."
    ::= { ruijieSystemApDeviceDescriptionEntry 4 } 

ruijieSystemAPFlashSize OBJECT-TYPE
    SYNTAX        Gauge
    MAX-ACCESS    read-only
    STATUS        current
    DESCRIPTION
        "Return the flash size of the lank ap system, unit is MB."
    ::= { ruijieSystemApDeviceDescriptionEntry 5 } 

ruijieSystemApNVRAMSize OBJECT-TYPE
    SYNTAX        Gauge
    MAX-ACCESS    read-only
    STATUS        current
    DESCRIPTION
        "Return the NVRAM size of the lank ap system, unit is MB."
    ::= { ruijieSystemApDeviceDescriptionEntry 6 } 

ruijieSystemApCFSize OBJECT-TYPE
    SYNTAX        Gauge
    MAX-ACCESS    read-only
    STATUS        current
    DESCRIPTION
        "Return the CF size of the lank ap system, unit is MB."
    ::= { ruijieSystemApDeviceDescriptionEntry 7 } 

ruijieSystemApCPUType OBJECT-TYPE
    SYNTAX        DisplayString
    MAX-ACCESS    read-only
    STATUS        current
    DESCRIPTION
        "Return the cpu type of the lank ap system."
    ::= { ruijieSystemApDeviceDescriptionEntry 8 } 

ruijieSystemApDeviceStatisticsTable OBJECT-TYPE
  SYNTAX      SEQUENCE OF RuijieSystemApDeviceStatisticsEntry
  MAX-ACCESS  not-accessible
  STATUS      current
  DESCRIPTION
    "A table of lank ap system entries. Each object displays 
     the lank ap system information."
  ::= { ruijieSystemMIBObjects 49 }
  
ruijieSystemApDeviceStatisticsEntry OBJECT-TYPE
  SYNTAX      RuijieSystemApDeviceStatisticsEntry
  MAX-ACCESS  not-accessible
  STATUS      current
  DESCRIPTION
    "An entry displays the ap Device Statistics."
  INDEX { ruijieSystemApStatMacAddr }
  ::= { ruijieSystemApDeviceStatisticsTable 1 }

RuijieSystemApDeviceStatisticsEntry ::=
  SEQUENCE {
    ruijieSystemApStatMacAddr                   MacAddress,
    ruijieSystemApInterfaceNum                  Integer32,
    ruijieSystemApUptime                        TimeTicks,
    ruijieSystemApCPUUtilizationCurrent         Percent,
    ruijieSystemApCPUUtilizationAverage         Percent, 
    ruijieSystemApMemoryPoolCurrentUtilization  Percent,
    ruijieSystemApMemoryPoolAverageUtilization  Percent,
    ruijieSystemApFlashFreeSize                 Unsigned32,
    ruijieSystemAPDeviceTemperature             Integer32
  }
    
ruijieSystemApStatMacAddr OBJECT-TYPE
    SYNTAX        MacAddress
    MAX-ACCESS    read-only
    STATUS        current
    DESCRIPTION
        "An index that uniquely represents ap system information."
    ::= { ruijieSystemApDeviceStatisticsEntry 1 }    

ruijieSystemApInterfaceNum OBJECT-TYPE
    SYNTAX        Integer32
    MAX-ACCESS    read-only
    STATUS        current
    DESCRIPTION
        "Return the interface number of the lank ap system."
    ::= { ruijieSystemApDeviceStatisticsEntry 2 }  

ruijieSystemApUptime OBJECT-TYPE
    SYNTAX        TimeTicks
    MAX-ACCESS    read-only
    STATUS        current
    DESCRIPTION
        "Return the SysUptime of lank ap equipment, unit is ticks."
    ::= { ruijieSystemApDeviceStatisticsEntry 3 } 

ruijieSystemApCPUUtilizationCurrent OBJECT-TYPE
    SYNTAX        Percent
    MAX-ACCESS    read-only
    STATUS        current
    DESCRIPTION
        "This is the collection of current lank ap cpu using rate."
    ::= { ruijieSystemApDeviceStatisticsEntry 4 }

ruijieSystemApCPUUtilizationAverage OBJECT-TYPE
    SYNTAX        Percent
    MAX-ACCESS    read-only
    STATUS        current
    DESCRIPTION
        "This is the average cpu using rate currently."
    ::= { ruijieSystemApDeviceStatisticsEntry 5 }

ruijieSystemApMemoryPoolCurrentUtilization OBJECT-TYPE
    SYNTAX        Percent
    MAX-ACCESS    read-only
    STATUS        current
    DESCRIPTION
        "This is the memory pool utilization currently."
    ::= { ruijieSystemApDeviceStatisticsEntry 6 }

ruijieSystemApMemoryPoolAverageUtilization OBJECT-TYPE
    SYNTAX        Percent
    MAX-ACCESS    read-only
    STATUS        current
    DESCRIPTION
        "This is the average memory pool utilization currently."
    ::= { ruijieSystemApDeviceStatisticsEntry 7 } 

ruijieSystemApFlashFreeSize OBJECT-TYPE
    SYNTAX        Unsigned32
    MAX-ACCESS    read-only
    STATUS        current
    DESCRIPTION
        "This is the free size of the flash device, unit is MB."
    ::= { ruijieSystemApDeviceStatisticsEntry 8 }

ruijieSystemAPDeviceTemperature OBJECT-TYPE
    SYNTAX        Integer32
    MAX-ACCESS    read-only
    STATUS        current
    DESCRIPTION
        "This is the temperature of the ap.But the ap is no support
         this information, so it will return 35 in perpetuity"
    ::= { ruijieSystemApDeviceStatisticsEntry 9 }   
    
ruijieSystemUptimeMsLow OBJECT-TYPE
  SYNTAX        Unsigned32
  MAX-ACCESS    read-only
  STATUS        current
  DESCRIPTION
    "Return the equipment SysUptime Low 32-bit,unit is tick."
  ::={ ruijieSystemMIBObjects 50 }
  
ruijieSystemUptimeMsHigh OBJECT-TYPE
  SYNTAX        Unsigned32
  MAX-ACCESS    read-only
  STATUS        current
  DESCRIPTION
    "Return the equipment SysUptime High 32-bit,unit is tick."
  ::={ ruijieSystemMIBObjects 51 }      
 
ruijieSystemFanSNTable OBJECT-TYPE
  SYNTAX      SEQUENCE OF RuijieSystemFanSNEntry
  MAX-ACCESS  not-accessible
  STATUS      current
  DESCRIPTION
    "A table of fan's serial number"
  ::= { ruijieSystemMIBObjects 52 }

ruijieSystemFanSNEntry OBJECT-TYPE
  SYNTAX      RuijieSystemFanSNEntry
  MAX-ACCESS  not-accessible
  STATUS      current
  DESCRIPTION
    "An entry displays fan SN."
  INDEX { ruijieSystemFanPadIndex }
  ::= { ruijieSystemFanSNTable 1 }

RuijieSystemFanSNEntry ::=
  SEQUENCE {
    ruijieSystemFanPadIndex          Integer32,
    ruijieSystemFanPadName           DisplayString,
    ruijieSystemFanPadSN             DisplayString
  }

ruijieSystemFanPadIndex OBJECT-TYPE
    SYNTAX        Integer32(0..255)
    MAX-ACCESS    read-only
    STATUS        current
    DESCRIPTION
        "Return the index of the fan pad."
    ::= { ruijieSystemFanSNEntry 1 }  

ruijieSystemFanPadName OBJECT-TYPE
    SYNTAX        DisplayString
    MAX-ACCESS    read-only
    STATUS        current
    DESCRIPTION
        "Return the name of the fan pad."
    ::= { ruijieSystemFanSNEntry 2 } 

ruijieSystemFanPadSN OBJECT-TYPE
    SYNTAX        DisplayString
    MAX-ACCESS    read-only
    STATUS        current
    DESCRIPTION
        "Return the SN of the fan pad."
    ::= { ruijieSystemFanSNEntry 3 } 

ruijieSystemDsfSNTable OBJECT-TYPE
  SYNTAX      SEQUENCE OF RuijieSystemDsfSNEntry
  MAX-ACCESS  not-accessible
  STATUS      current
  DESCRIPTION
    "A table of dsf's serial number"
  ::= { ruijieSystemMIBObjects 53 }

ruijieSystemDsfSNEntry OBJECT-TYPE
  SYNTAX      RuijieSystemDsfSNEntry
  MAX-ACCESS  not-accessible
  STATUS      current
  DESCRIPTION
    "An entry displays dsf SN."
  INDEX { ruijieSystemDsfIndex }
  ::= { ruijieSystemDsfSNTable 1 }

RuijieSystemDsfSNEntry ::=
  SEQUENCE {
    ruijieSystemDsfIndex          Integer32,  
    ruijieSystemDsfName           DisplayString,
    ruijieSystemDsfSN             DisplayString
  }

ruijieSystemDsfIndex OBJECT-TYPE
    SYNTAX        Integer32(0..255)
    MAX-ACCESS    read-only
    STATUS        current
    DESCRIPTION
        "Return the index of the dsf."
    ::= { ruijieSystemDsfSNEntry 1 }  

ruijieSystemDsfName OBJECT-TYPE
    SYNTAX        DisplayString
    MAX-ACCESS    read-only
    STATUS        current
    DESCRIPTION
        "Return the name of the dsf."
    ::= { ruijieSystemDsfSNEntry 2 } 

ruijieSystemDsfSN OBJECT-TYPE
    SYNTAX        DisplayString
    MAX-ACCESS    read-only
    STATUS        current
    DESCRIPTION
        "Return the SN of the dsf."
    ::= { ruijieSystemDsfSNEntry 3 } 

ruijieSystemPowerSNTable OBJECT-TYPE
  SYNTAX      SEQUENCE OF RuijieSystemPowerSNEntry
  MAX-ACCESS  not-accessible
  STATUS      current
  DESCRIPTION
    "A table of power's serial number"
  ::= { ruijieSystemMIBObjects 54 }

ruijieSystemPowerSNEntry OBJECT-TYPE
  SYNTAX      RuijieSystemPowerSNEntry
  MAX-ACCESS  not-accessible
  STATUS      current
  DESCRIPTION
    "An entry displays power SN."
  INDEX { ruijieSystemPowerSNIndex }
  ::= { ruijieSystemPowerSNTable 1 }

RuijieSystemPowerSNEntry ::=
  SEQUENCE {
    ruijieSystemPowerSNIndex          Integer32,
    ruijieSystemPowerSNName           DisplayString,  
    ruijieSystemPowerSN               DisplayString
  }

ruijieSystemPowerSNIndex OBJECT-TYPE
    SYNTAX        Integer32(0..255)
    MAX-ACCESS    read-only
    STATUS        current
    DESCRIPTION
        "Return the index of the power."
    ::= { ruijieSystemPowerSNEntry 1 }  

ruijieSystemPowerSNName OBJECT-TYPE
    SYNTAX        DisplayString
    MAX-ACCESS    read-only
    STATUS        current
    DESCRIPTION
        "Return the name of the power."
    ::= { ruijieSystemPowerSNEntry 2 } 

ruijieSystemPowerSN OBJECT-TYPE
    SYNTAX        DisplayString
    MAX-ACCESS    read-only
    STATUS        current
    DESCRIPTION
        "Return the SN of the power."
    ::= { ruijieSystemPowerSNEntry 3 } 
 
 ruijieSystemFanPad1SpeedTable OBJECT-TYPE
  SYNTAX      SEQUENCE OF RuijieSystemFanPad1SpeedEntry
  MAX-ACCESS  not-accessible
  STATUS      current
  DESCRIPTION
    "A table of fan's speed on fan pad1."
  ::= { ruijieSystemMIBObjects 55 }

ruijieSystemFanPad1SpeedEntry OBJECT-TYPE
  SYNTAX      RuijieSystemFanPad1SpeedEntry
  MAX-ACCESS  not-accessible
  STATUS      current
  DESCRIPTION
    "An entry displays fan's speed on same fan pad"
  INDEX { ruijieSystemOamFanPad1Index }
  ::= { ruijieSystemFanPad1SpeedTable 1 }

RuijieSystemFanPad1SpeedEntry ::=
  SEQUENCE {
    ruijieSystemOamFanPad1Index    Integer32,
    ruijieSystemOamFanPad1Name	  DisplayString,
    ruijieSystemFanPad1Speed1         Integer32,
    ruijieSystemFanPad1Speed2         Integer32,
    ruijieSystemFanPad1Speed3         Integer32,
    ruijieSystemFanPad1Speed4         Integer32,
    ruijieSystemFanPad1Speed5         Integer32,
    ruijieSystemFanPad1Speed6         Integer32,
    ruijieSystemFanPad1Speed7         Integer32,
    ruijieSystemFanPad1Speed8         Integer32,    
    ruijieSystemFanPad1Speed9         Integer32
  }

ruijieSystemOamFanPad1Index OBJECT-TYPE
    SYNTAX        Integer32(0..255)
    MAX-ACCESS    read-only
    STATUS        current
    DESCRIPTION
        "Return the index of the fan pad."
    ::= { ruijieSystemFanPad1SpeedEntry 1 }

ruijieSystemOamFanPad1Name OBJECT-TYPE
    SYNTAX        DisplayString
    MAX-ACCESS    read-only
    STATUS        current
    DESCRIPTION
        "Return the name of the fan pad."
    ::= { ruijieSystemFanPad1SpeedEntry 2 }

ruijieSystemFanPad1Speed1 OBJECT-TYPE
    SYNTAX        Integer32
    MAX-ACCESS    read-only
    STATUS        current
    DESCRIPTION
        "Return the speed of the fan1."
    ::= { ruijieSystemFanPad1SpeedEntry 3 }

ruijieSystemFanPad1Speed2 OBJECT-TYPE
    SYNTAX        Integer32
    MAX-ACCESS    read-only
    STATUS        current
    DESCRIPTION
        "Return the speed of the fan2."
    ::= { ruijieSystemFanPad1SpeedEntry 4 }

ruijieSystemFanPad1Speed3 OBJECT-TYPE
    SYNTAX        Integer32
    MAX-ACCESS    read-only
    STATUS        current
    DESCRIPTION
        "Return the speed of the fan3."
    ::= { ruijieSystemFanPad1SpeedEntry 5 }

ruijieSystemFanPad1Speed4 OBJECT-TYPE
    SYNTAX        Integer32
    MAX-ACCESS    read-only
    STATUS        current
    DESCRIPTION
        "Return the speed of the fan4."
    ::= { ruijieSystemFanPad1SpeedEntry 6 }

ruijieSystemFanPad1Speed5 OBJECT-TYPE
    SYNTAX        Integer32
    MAX-ACCESS    read-only
    STATUS        current
    DESCRIPTION
        "Return the speed of the fan5."
    ::= { ruijieSystemFanPad1SpeedEntry 7 }

ruijieSystemFanPad1Speed6 OBJECT-TYPE
    SYNTAX        Integer32
    MAX-ACCESS    read-only
    STATUS        current
    DESCRIPTION
        "Return the speed of the fan6."
    ::= { ruijieSystemFanPad1SpeedEntry 8 }

ruijieSystemFanPad1Speed7 OBJECT-TYPE
    SYNTAX        Integer32
    MAX-ACCESS    read-only
    STATUS        current
    DESCRIPTION
        "Return the speed of the fan7."
    ::= { ruijieSystemFanPad1SpeedEntry 9 }

ruijieSystemFanPad1Speed8 OBJECT-TYPE
    SYNTAX        Integer32
    MAX-ACCESS    read-only
    STATUS        current
    DESCRIPTION
        "Return the speed of the fan8."
    ::= { ruijieSystemFanPad1SpeedEntry 10 }
   
ruijieSystemFanPad1Speed9 OBJECT-TYPE
    SYNTAX        Integer32
    MAX-ACCESS    read-only
    STATUS        current
    DESCRIPTION
        "Return the speed of the fan9."
    ::= { ruijieSystemFanPad1SpeedEntry 11 }

ruijieSystemFanPad2SpeedTable OBJECT-TYPE
  SYNTAX      SEQUENCE OF RuijieSystemFanPad2SpeedEntry
  MAX-ACCESS  not-accessible
  STATUS      current
  DESCRIPTION
    "A table of fan's speed on fan pad2."
  ::= { ruijieSystemMIBObjects 56 }

ruijieSystemFanPad2SpeedEntry OBJECT-TYPE
  SYNTAX      RuijieSystemFanPad2SpeedEntry
  MAX-ACCESS  not-accessible
  STATUS      current
  DESCRIPTION
    "An entry displays fan's speed on same fan pad2"
  INDEX { ruijieSystemOamFanPad2Index }
  ::= { ruijieSystemFanPad2SpeedTable 1 }

RuijieSystemFanPad2SpeedEntry ::=
  SEQUENCE {
    ruijieSystemOamFanPad2Index    Integer32,
    ruijieSystemOamFanPad2Name	  DisplayString,
    ruijieSystemFanPad2Speed1         Integer32,
    ruijieSystemFanPad2Speed2         Integer32,
    ruijieSystemFanPad2Speed3         Integer32
  }

ruijieSystemOamFanPad2Index OBJECT-TYPE
    SYNTAX        Integer32(0..255)
    MAX-ACCESS    read-only
    STATUS        current
    DESCRIPTION
        "Return the index of the fan pad2."
    ::= { ruijieSystemFanPad2SpeedEntry 1 }

ruijieSystemOamFanPad2Name OBJECT-TYPE
    SYNTAX        DisplayString
    MAX-ACCESS    read-only
    STATUS        current
    DESCRIPTION
        "Return the name of the fan pad."
    ::= { ruijieSystemFanPad2SpeedEntry 2 }

ruijieSystemFanPad2Speed1 OBJECT-TYPE
    SYNTAX        Integer32
    MAX-ACCESS    read-only
    STATUS        current
    DESCRIPTION
        "Return the speed of the fan1."
    ::= { ruijieSystemFanPad2SpeedEntry 3 }

ruijieSystemFanPad2Speed2 OBJECT-TYPE
    SYNTAX        Integer32
    MAX-ACCESS    read-only
    STATUS        current
    DESCRIPTION
        "Return the speed of the fan2."
    ::= { ruijieSystemFanPad2SpeedEntry 4 }

ruijieSystemFanPad2Speed3 OBJECT-TYPE
    SYNTAX        Integer32
    MAX-ACCESS    read-only
    STATUS        current
    DESCRIPTION
        "Return the speed of the fan3."
    ::= { ruijieSystemFanPad2SpeedEntry 5 }

ruijieSystemFanPad3SpeedTable OBJECT-TYPE
  SYNTAX      SEQUENCE OF RuijieSystemFanPad3SpeedEntry
  MAX-ACCESS  not-accessible
  STATUS      current
  DESCRIPTION
    "A table of fan's speed on fan pad3."
  ::= { ruijieSystemMIBObjects 57 }

ruijieSystemFanPad3SpeedEntry OBJECT-TYPE
  SYNTAX      RuijieSystemFanPad3SpeedEntry
  MAX-ACCESS  not-accessible
  STATUS      current
  DESCRIPTION
    "An entry displays fan's speed on same fan pad3"
  INDEX { ruijieSystemOamFanPad3Index }
  ::= { ruijieSystemFanPad3SpeedTable 1 }

RuijieSystemFanPad3SpeedEntry ::=
  SEQUENCE {
    ruijieSystemOamFanPad3Index    Integer32,
    ruijieSystemOamFanPad3Name	  DisplayString,
    ruijieSystemFanPad3Speed1         Integer32,
    ruijieSystemFanPad3Speed2         Integer32,
    ruijieSystemFanPad3Speed3         Integer32,
    ruijieSystemFanPad3Speed4         Integer32,
    ruijieSystemFanPad3Speed5         Integer32
  }

ruijieSystemOamFanPad3Index OBJECT-TYPE
    SYNTAX        Integer32(0..255)
    MAX-ACCESS    read-only
    STATUS        current
    DESCRIPTION
        "Return the index of the fan pad3."
    ::= { ruijieSystemFanPad3SpeedEntry 1 }

ruijieSystemOamFanPad3Name OBJECT-TYPE
    SYNTAX        DisplayString
    MAX-ACCESS    read-only
    STATUS        current
    DESCRIPTION
        "Return the name of the fan pad."
    ::= { ruijieSystemFanPad3SpeedEntry 2 }

ruijieSystemFanPad3Speed1 OBJECT-TYPE
    SYNTAX        Integer32
    MAX-ACCESS    read-only
    STATUS        current
    DESCRIPTION
        "Return the speed of the fan1."
    ::= { ruijieSystemFanPad3SpeedEntry 3 }

ruijieSystemFanPad3Speed2 OBJECT-TYPE
    SYNTAX        Integer32
    MAX-ACCESS    read-only
    STATUS        current
    DESCRIPTION
        "Return the speed of the fan2."
    ::= { ruijieSystemFanPad3SpeedEntry 4 }

ruijieSystemFanPad3Speed3 OBJECT-TYPE
    SYNTAX        Integer32
    MAX-ACCESS    read-only
    STATUS        current
    DESCRIPTION
        "Return the speed of the fan3."
    ::= { ruijieSystemFanPad3SpeedEntry 5 }

ruijieSystemFanPad3Speed4 OBJECT-TYPE
    SYNTAX        Integer32
    MAX-ACCESS    read-only
    STATUS        current
    DESCRIPTION
        "Return the speed of the fan4."
    ::= { ruijieSystemFanPad3SpeedEntry 6 }

ruijieSystemFanPad3Speed5 OBJECT-TYPE
    SYNTAX        Integer32
    MAX-ACCESS    read-only
    STATUS        current
    DESCRIPTION
        "Return the speed of the fan5."
    ::= { ruijieSystemFanPad3SpeedEntry 7 }

ruijieSystemParamSaveErrIdx  OBJECT-TYPE
    SYNTAX  Integer32
    MAX-ACCESS  read-only
    STATUS  current
    DESCRIPTION
            "Param Save Err Idx."
    ::= { ruijieSystemMIBObjects 58 }

ruijieSystemParamSaveErrMsg  OBJECT-TYPE
    SYNTAX  DisplayString (SIZE (1..64))
    MAX-ACCESS  read-only
    STATUS  current
    DESCRIPTION
            "Param Save Err Msg."
    ::= { ruijieSystemMIBObjects 59 }

ruijieSystemDeviceLevel  OBJECT-TYPE
        SYNTAX  INTEGER {
                unknown (0), -- Unknown Layer
                core (1), -- Core Layer
                collect (2), -- Collect Layer
                access (3)  -- Access Layer
             }
        MAX-ACCESS read-write
        STATUS current
        DESCRIPTION
        "This object can display or set which device application level the device belongs to."
    ::= { ruijieSystemMIBObjects 60 }

ruijieSystemSysmac OBJECT-TYPE
        SYNTAX MacAddress
        MAX-ACCESS read-only
        STATUS current
        DESCRIPTION
            "Sysmac of the system."
    ::= { ruijieSystemMIBObjects 61 }

ruijieSystemDeviceMode OBJECT-TYPE
    SYNTAX Integer32
    MAX-ACCESS read-only
    STATUS current
    DESCRIPTION
        "Device mode of the system. Only support in all-in-one device."
    ::= { ruijieSystemMIBObjects 62 }

--add card power consume info
ruijieSystemCardPowerConsumeTable OBJECT-TYPE
  SYNTAX      SEQUENCE OF RuijieSystemCardPowerConsumeEntry
  MAX-ACCESS  not-accessible
  STATUS      current
  DESCRIPTION
    "A table of card power consume entries. Each object displays the card power consume information."
  ::= { ruijieSystemMIBObjects 63 }

ruijieSystemCardPowerConsumeEntry OBJECT-TYPE
  SYNTAX      RuijieSystemCardPowerConsumeEntry
  MAX-ACCESS  not-accessible
  STATUS      current
  DESCRIPTION
    "An entry displays the card power consume information."
  INDEX { ruijieSystemCardPowerConsumeDeviceIndex,
          ruijieSystemCardPowerConsumeSlotIndex}
  ::= {ruijieSystemCardPowerConsumeTable 1 }

RuijieSystemCardPowerConsumeEntry ::=
  SEQUENCE {
    ruijieSystemCardPowerConsumeDeviceIndex    Integer32,
    ruijieSystemCardPowerConsumeSlotIndex      Integer32,
    ruijieSystemCardPowerVoltage               Integer32,
    ruijieSystemCardPowerCurrent               Integer32,
    ruijieSystemCardPowerConsume               Integer32
  }

ruijieSystemCardPowerConsumeDeviceIndex  OBJECT-TYPE
    SYNTAX        Integer32(0..255)
    MAX-ACCESS    read-only
    STATUS        current
    DESCRIPTION
        "An index that uniquely represents a device."
    ::= { ruijieSystemCardPowerConsumeEntry 1 }

ruijieSystemCardPowerConsumeSlotIndex OBJECT-TYPE
    SYNTAX        Integer32(0..255)
    MAX-ACCESS    read-only
    STATUS        current
    DESCRIPTION
        "An index that uniquely represents a slot device."
    ::= { ruijieSystemCardPowerConsumeEntry 2 }

ruijieSystemCardPowerVoltage OBJECT-TYPE
    SYNTAX        Integer32
    MAX-ACCESS    read-only
    STATUS        current
    DESCRIPTION
        "This object displays the power voltage(Unit: mV) of the slot device. If the device is no support
         this information, This object will return -255."
    ::= { ruijieSystemCardPowerConsumeEntry 3 }

ruijieSystemCardPowerCurrent OBJECT-TYPE
    SYNTAX        Integer32
    MAX-ACCESS    read-only
    STATUS        current
    DESCRIPTION
        "This object displays the power current(Unit: mA) of the slot device. If the device is no support
         this information, This object will return -255."
    ::= { ruijieSystemCardPowerConsumeEntry 4 }

ruijieSystemCardPowerConsume OBJECT-TYPE
    SYNTAX        Integer32
    MAX-ACCESS    read-only
    STATUS        current
    DESCRIPTION
        "This object displays the power consume(Unit: W) of the slot device. If the device is no support
         this information, This object will return -255."
    ::= { ruijieSystemCardPowerConsumeEntry 5 }

ruijieSystemPowerInsertNum OBJECT-TYPE
        SYNTAX Integer32
        MAX-ACCESS read-only
        STATUS current
        DESCRIPTION
          "Return the number of inserted power on the FastSwitch."
        ::= { ruijieSystemMIBObjects 64 }

ruijieSystemPowerOnlineNum OBJECT-TYPE
        SYNTAX Integer32
        MAX-ACCESS read-only
        STATUS current
        DESCRIPTION
          "Return the number of online power that state is normal on the FastSwitch."
        ::= { ruijieSystemMIBObjects 65 }

ruijieSystemPowerOfflineNum OBJECT-TYPE
        SYNTAX Integer32
        MAX-ACCESS read-only
        STATUS current
        DESCRIPTION
          "Return the number of offline power that state is abnormal on the FastSwitch."
        ::= { ruijieSystemMIBObjects 66 }

ruijieSystemPowerRedun OBJECT-TYPE
        SYNTAX DisplayString
        MAX-ACCESS read-only
        STATUS current
        DESCRIPTION
          "Return the redundancy of power on the FastSwitch."
        ::= { ruijieSystemMIBObjects 67 }

ruijieSystemTotalPower OBJECT-TYPE
        SYNTAX Integer32
        MAX-ACCESS read-only
        STATUS current
        DESCRIPTION
          "Return the total power of the FastSwitch."
        ::= { ruijieSystemMIBObjects 68 }

ruijieSystemAvailablePower OBJECT-TYPE
        SYNTAX Integer32
        MAX-ACCESS read-only
        STATUS current
        DESCRIPTION
          "Return the available power of the FastSwitch."
        ::= { ruijieSystemMIBObjects 69 }

ruijieSystemCardAllocatedPower OBJECT-TYPE
        SYNTAX Integer32
        MAX-ACCESS read-only
        STATUS current
        DESCRIPTION
          "Return the card allocated power of the FastSwitch."
    ::= { ruijieSystemMIBObjects 70 }

ruijieSystemFanAllocatedPower OBJECT-TYPE
        SYNTAX Integer32
        MAX-ACCESS read-only
        STATUS current
        DESCRIPTION
          "Return the fan allocated power of the FastSwitch."
    ::= { ruijieSystemMIBObjects 71 }

ruijieSystemCardPowerUsed OBJECT-TYPE
        SYNTAX Integer32
        MAX-ACCESS read-only
        STATUS current
        DESCRIPTION
          "Return the card power used of the FastSwitch."
        ::= { ruijieSystemMIBObjects 72 }

ruijieSystemFanPowerUsed OBJECT-TYPE
        SYNTAX Integer32
        MAX-ACCESS read-only
        STATUS current
        DESCRIPTION
          "Return the fan power used of the FastSwitch."
        ::= { ruijieSystemMIBObjects 73 }

ruijieSystemFanMode OBJECT-TYPE
        SYNTAX DisplayString
        MAX-ACCESS read-only
        STATUS current
        DESCRIPTION
          "Return the mode of fan on the FastSwitch."
        ::= { ruijieSystemMIBObjects 74 }

ruijieSystemStartupGmChssSerialno OBJECT-TYPE
        SYNTAX DisplayString 
        MAX-ACCESS read-only
        STATUS current
        DESCRIPTION
          "Return the string of the serial number of the startup master's chassis."
        ::= { ruijieSystemMIBObjects 75 }

ruijieSystemDeviceTemperatureTable OBJECT-TYPE
  SYNTAX      SEQUENCE OF RuijieSystemDeviceTemperatureEntry
  MAX-ACCESS  not-accessible
  STATUS      current
  DESCRIPTION
    "A table of temperature entries. Each object displays 
     the temperature information."
  ::= { ruijieSystemMIBObjects 76 }

ruijieSystemDeviceTemperatureEntry OBJECT-TYPE
  SYNTAX      RuijieSystemDeviceTemperatureEntry
  MAX-ACCESS  not-accessible
  STATUS      current
  DESCRIPTION
    "An entry displays the multiple temperature information."
  INDEX { ruijieSystemDeviceTemperatureDeviceIndex,
          ruijieSystemDeviceTemperatureSlotIndex, 
          ruijieSystemDeviceTemperatureSubSlotIndex }
  ::= { ruijieSystemDeviceTemperatureTable 1 }

RuijieSystemDeviceTemperatureEntry ::=
  SEQUENCE {
    ruijieSystemDeviceTemperatureDeviceIndex  Integer32,
    ruijieSystemDeviceTemperatureSlotIndex    Integer32,
    ruijieSystemDeviceTemperatureSubSlotIndex Integer32,
    ruijieSystemDeviceTemperatureIndex        Integer32,
    ruijieSystemDeviceTemperatureName         DisplayString,
    ruijieSystemDeviceTemperatureCurrent      Integer32,
    ruijieSystemDeviceTemperatureWarning      Integer32,
    ruijieSystemDeviceTemperatureCritical     Integer32,
    ruijieSystemDeviceTemperatureShutdown     Integer32,
    ruijieSystemDeviceTemperaturePoweroff     Integer32
  }

ruijieSystemDeviceTemperatureDeviceIndex OBJECT-TYPE
    SYNTAX        Integer32(0..255)
    MAX-ACCESS    read-only
    STATUS        current
    DESCRIPTION
        "An index that uniquely represents a device."
    ::= { ruijieSystemDeviceTemperatureEntry 1 }

ruijieSystemDeviceTemperatureSlotIndex OBJECT-TYPE
    SYNTAX        Integer32(0..255)
    MAX-ACCESS    read-only
    STATUS        current
    DESCRIPTION
        "An index that uniquely represents a slot device."
    ::= { ruijieSystemDeviceTemperatureEntry 2 }

ruijieSystemDeviceTemperatureSubSlotIndex OBJECT-TYPE
    SYNTAX        Integer32(0..255)
    MAX-ACCESS    read-only
    STATUS        current
    DESCRIPTION
        "An index that uniquely represents a sub slot device."
    ::= { ruijieSystemDeviceTemperatureEntry 3 }

ruijieSystemDeviceTemperatureIndex OBJECT-TYPE
    SYNTAX        Integer32
    MAX-ACCESS    read-only
    STATUS        current
    DESCRIPTION
        "An index that uniquely represents a device's temperature information."
    ::= { ruijieSystemDeviceTemperatureEntry 4 }

ruijieSystemDeviceTemperatureName OBJECT-TYPE
    SYNTAX        DisplayString
    MAX-ACCESS    read-only
    STATUS        current
    DESCRIPTION
        "A textual name assigned to a temperature chip"
    ::= { ruijieSystemDeviceTemperatureEntry 5 }          
                    
ruijieSystemDeviceTemperatureCurrent OBJECT-TYPE
    SYNTAX        Integer32
    MAX-ACCESS    read-only
    STATUS        current
    DESCRIPTION
        "Return the current device temperature of the FastSwitch.The temperature display
         is not supported for the current temperature returns to -255."
    ::= { ruijieSystemDeviceTemperatureEntry 6 }

ruijieSystemDeviceTemperatureWarning OBJECT-TYPE
    SYNTAX        Integer32
    MAX-ACCESS    read-write
    STATUS        current
    DESCRIPTION
        "Return the warning device temperature of the FastSwitch.The temperature display
         is not supported for the warning temperature returns to -255."
    ::= { ruijieSystemDeviceTemperatureEntry 7 }

ruijieSystemDeviceTemperatureCritical OBJECT-TYPE
    SYNTAX        Integer32
    MAX-ACCESS    read-write
    STATUS        current
    DESCRIPTION
        "Return the critical device temperature of the FastSwitch.The temperature display
         is not supported for the critical temperature returns to -255."
    ::= { ruijieSystemDeviceTemperatureEntry 8 }

ruijieSystemDeviceTemperatureShutdown OBJECT-TYPE
    SYNTAX        Integer32
    MAX-ACCESS    read-write
    STATUS        current
    DESCRIPTION
        "Return the shutdown device temperature of the FastSwitch.The temperature display
         is not supported for the shutdown temperature returns to -255."
    ::= { ruijieSystemDeviceTemperatureEntry 9 }

ruijieSystemDeviceTemperaturePoweroff OBJECT-TYPE
    SYNTAX        Integer32
    MAX-ACCESS    read-write
    STATUS        current
    DESCRIPTION
        "Return the poweroff device temperature of the FastSwitch.The temperature display
         is not supported for the poweroff temperature returns to -255."
    ::= { ruijieSystemDeviceTemperatureEntry 10 }

ruijieSystemDeviceModelInformationTable OBJECT-TYPE
  SYNTAX      SEQUENCE OF RuijieSystemDeviceModelInformationEntry
  MAX-ACCESS  not-accessible
  STATUS      current
  DESCRIPTION
    "A table of device model entries. Each object displays 
     the model information."
  ::= { ruijieSystemMIBObjects 77 }

ruijieSystemVacConfigDiffMsg  OBJECT-TYPE
    SYNTAX  DisplayString (SIZE (1..255))
    MAX-ACCESS accessible-for-notify
    STATUS  current
    DESCRIPTION
            "Vac Config Diff Msg."
    ::= { ruijieSystemMIBObjects 78 }

ruijieSystemDeviceModelInformationEntry OBJECT-TYPE
  SYNTAX      RuijieSystemDeviceModelInformationEntry
  MAX-ACCESS  not-accessible
  STATUS      current
  DESCRIPTION
    "An entry displays the multiple model information."
  INDEX { ruijieSystemDeviceModelInformationDeviceIndex,
          ruijieSystemDeviceModelInformationSlotIndex, 
          ruijieSystemDeviceModelInformationSubSlotIndex }
  ::= { ruijieSystemDeviceModelInformationTable 1 }

RuijieSystemDeviceModelInformationEntry ::=
  SEQUENCE {
    ruijieSystemDeviceModelInformationDeviceIndex  				Integer32,
    ruijieSystemDeviceModelInformationSlotIndex    				Integer32,
    ruijieSystemDeviceModelInformationSubSlotIndex 				Integer32,
    ruijieSystemDeviceModelInformationCPUName				    DisplayString,
    ruijieSystemDeviceModelInformationMACName           	    DisplayString,
    ruijieSystemDeviceModelInformationFabricName	            DisplayString,
    ruijieSystemDeviceModelInformationSDRAMName       		    DisplayString,
    ruijieSystemDeviceModelInformationFlashName		      	    DisplayString,
    ruijieSystemDeviceModelInformationPHYName       			DisplayString,
    ruijieSystemDeviceModelInformationClockName	        	    DisplayString,
    ruijieSystemDeviceModelInformationDCDCName          	    DisplayString
  }

ruijieSystemDeviceModelInformationDeviceIndex OBJECT-TYPE
    SYNTAX        Integer32(0..255)
    MAX-ACCESS    read-only
    STATUS        current
    DESCRIPTION
        "An index that uniquely represents a device."
    ::= { ruijieSystemDeviceModelInformationEntry 1 }

ruijieSystemDeviceModelInformationSlotIndex OBJECT-TYPE
    SYNTAX        Integer32(0..255)
    MAX-ACCESS    read-only
    STATUS        current
    DESCRIPTION
        "An index that uniquely represents a slot device."
    ::= { ruijieSystemDeviceModelInformationEntry 2 }

ruijieSystemDeviceModelInformationSubSlotIndex OBJECT-TYPE
    SYNTAX        Integer32(0..255)
    MAX-ACCESS    read-only
    STATUS        current
    DESCRIPTION
        "An index that uniquely represents a sub slot device."
    ::= { ruijieSystemDeviceModelInformationEntry 3 }

ruijieSystemDeviceModelInformationCPUName OBJECT-TYPE
    SYNTAX        DisplayString
    MAX-ACCESS    read-only
    STATUS        current
    DESCRIPTION
        "Returns the model name of the CPU."
    ::= { ruijieSystemDeviceModelInformationEntry 4 }

ruijieSystemDeviceModelInformationMACName OBJECT-TYPE
    SYNTAX        DisplayString
    MAX-ACCESS    read-only
    STATUS        current
    DESCRIPTION
        "Returns the model name of the MAC."
    ::= { ruijieSystemDeviceModelInformationEntry 5 }

ruijieSystemDeviceModelInformationFabricName OBJECT-TYPE
    SYNTAX        DisplayString
    MAX-ACCESS    read-only
    STATUS        current
    DESCRIPTION
        "Returns the model name of the fabric."
    ::= { ruijieSystemDeviceModelInformationEntry 6 }          

ruijieSystemDeviceModelInformationSDRAMName OBJECT-TYPE
    SYNTAX        DisplayString
    MAX-ACCESS    read-only
    STATUS        current
    DESCRIPTION
        "Returns the model name of the SDRAM."
    ::= { ruijieSystemDeviceModelInformationEntry 7 }

ruijieSystemDeviceModelInformationFlashName OBJECT-TYPE
    SYNTAX        DisplayString
    MAX-ACCESS    read-only
    STATUS        current
    DESCRIPTION
        "Returns the model name of the Flash."
    ::= { ruijieSystemDeviceModelInformationEntry 8 }

ruijieSystemDeviceModelInformationPHYName OBJECT-TYPE
    SYNTAX        DisplayString
    MAX-ACCESS    read-only
    STATUS        current
    DESCRIPTION
        "Returns the model name of the PHY."
    ::= { ruijieSystemDeviceModelInformationEntry 9 }



ruijieSystemDeviceModelInformationClockName OBJECT-TYPE
    SYNTAX        DisplayString
    MAX-ACCESS    read-only
    STATUS        current
    DESCRIPTION
        "Returns the model name of the clock."
    ::= { ruijieSystemDeviceModelInformationEntry 10 }

ruijieSystemDeviceModelInformationDCDCName OBJECT-TYPE
    SYNTAX        DisplayString
    MAX-ACCESS    read-only
    STATUS        current
    DESCRIPTION
        "Returns the model name of the DC-DC."
    ::= { ruijieSystemDeviceModelInformationEntry 11 }

ruijieSystemAllTotalPower OBJECT-TYPE
    SYNTAX Integer32
    MAX-ACCESS read-only
    STATUS current
    DESCRIPTION
        "The output power of the all devices. (Unit W)"
    ::= { ruijieSystemMIBObjects 79 }

ruijieSystemDeviceInformationTable OBJECT-TYPE
    SYNTAX      SEQUENCE OF RuijieSystemDeviceInformationEntry
    MAX-ACCESS  not-accessible
    STATUS      current
    DESCRIPTION
        "A table of device information entries. Each object displays
         the devcie's information."
    ::= { ruijieSystemMIBObjects 80 }

ruijieSystemDeviceInformationEntry OBJECT-TYPE
    SYNTAX      RuijieSystemDeviceInformationEntry
    MAX-ACCESS  not-accessible
    STATUS      current
    DESCRIPTION
        "An entry displays the device's information."
    INDEX { ruijieSystemDeviceInformationIndex }
    ::= { ruijieSystemDeviceInformationTable 1 }

RuijieSystemDeviceInformationEntry ::=
    SEQUENCE {
        ruijieSystemDeviceInformationIndex    Integer32,
        ruijieSystemDeviceInformationName     DisplayString,
        ruijieSystemDeviceInformationOutPower Integer32
    }

ruijieSystemDeviceInformationIndex OBJECT-TYPE
    SYNTAX        Integer32(0..255)
    MAX-ACCESS    read-only
    STATUS        current
    DESCRIPTION
        "An index that uniquely represents a device's information."
    ::= { ruijieSystemDeviceInformationEntry 1 }

ruijieSystemDeviceInformationName OBJECT-TYPE
    SYNTAX        DisplayString
    MAX-ACCESS    read-only
    STATUS        current
    DESCRIPTION
        "A textual name assigned to a device"
    ::= { ruijieSystemDeviceInformationEntry 2 }

ruijieSystemDeviceInformationOutPower OBJECT-TYPE
    SYNTAX        Integer32
    MAX-ACCESS    read-only
    STATUS        current
    DESCRIPTION
        "Return the current device's outpower of the FastSwitch.The device display
         is not supported for the current outpower returns to 0."
    ::= { ruijieSystemDeviceInformationEntry 3 }

ruijieSystemMIBTraps OBJECT IDENTIFIER ::= { ruijieSystemMIB 2 }

ruijieSystemHardChangeDesc OBJECT-TYPE
        SYNTAX DisplayString
        MAX-ACCESS accessible-for-notify
        STATUS current
        DESCRIPTION
          "The description of hard change"
        ::= { ruijieSystemMIBTraps 1 }       
        
ruijieSystemHardChangeDetected NOTIFICATION-TYPE
        OBJECTS   {ruijieSystemHardChangeDesc}
        STATUS     current
        DESCRIPTION
                "System hardware has changed include number of devices or number of modules 
                 or the place or type of the module is change."
        ::= { ruijieSystemMIBTraps 2 }
        
ruijieSystemPowerStateChange NOTIFICATION-TYPE
        OBJECTS   {ruijieSystemHwPower}
        STATUS     current
        DESCRIPTION
                "while the state of power changed, then this trap will be sent."
        ::= { ruijieSystemMIBTraps 3 }
        
ruijieSystemFanStateChange NOTIFICATION-TYPE
        OBJECTS   {ruijieSystemHwFan}
        STATUS     current
        DESCRIPTION
                "while the state of fan changed, then this trap will be sent."
        ::= { ruijieSystemMIBTraps 4 }                

--2010-05    
ruijieSystemCPUusageTooHighTrap NOTIFICATION-TYPE
        OBJECTS   {ruijieCPUUtilization1Min}
        STATUS     current
        DESCRIPTION
                "CPU usage Too High warning."
        ::= { ruijieSystemMIBTraps 5 }
                      
--2010-05 
ruijieSystemCPUusageTooHighRecovTrap NOTIFICATION-TYPE
        OBJECTS   {ruijieCPUUtilization1Min}
        STATUS     current
        DESCRIPTION
                "clear the warning of CPU usage too high and report the current CPU usage."
        ::= { ruijieSystemMIBTraps 6 }
        
--2010-05 
ruijieSystemTmpTooHighTrap NOTIFICATION-TYPE
        OBJECTS   {ruijieSystemTemperatureCurrent}
        STATUS     current
        DESCRIPTION
                "Temperature Too High warning."
        ::= { ruijieSystemMIBTraps 7 }   
           
--Temperature Too High Recover Trap 2010-05 
ruijieSystemTmpTooHighRecovTrap NOTIFICATION-TYPE
        OBJECTS   {ruijieSystemTemperatureCurrent}
        STATUS     current
        DESCRIPTION
                "clear the warning of temperature too high and report the current temperature."
        ::= { ruijieSystemMIBTraps 8 }
                
--Memory usage too high trap 2010-05 
ruijieSystemMemusageTooHighTrap NOTIFICATION-TYPE
        OBJECTS   {ruijieMemoryPoolCurrentUtilization}
        STATUS     current
        DESCRIPTION
                "Memory usage too high warning."
        ::= { ruijieSystemMIBTraps 9 }   
        
--Memory usage too high recover trap 2010-05 
ruijieSystemMemusageTooHighRecovTrap NOTIFICATION-TYPE
        OBJECTS   {ruijieMemoryPoolCurrentUtilization}
        STATUS     current
        DESCRIPTION
                "clear the warning of Memory usage too high and report the current Memory usage."
        ::= { ruijieSystemMIBTraps 10 }  
        
--lank ap 2010-7     
ruijieSystemLankApCPUusageTooHighTrap NOTIFICATION-TYPE
        OBJECTS   {
           ruijieApMacAddr,
           ruijieCPUUtilization1Min
        }
        STATUS     current
        DESCRIPTION
                "lank ap CPU usage Too High warning."
        ::= { ruijieSystemMIBTraps 11 }
                      
--lank ap 2010-7 
ruijieSystemLankApCPUusageTooHighRecovTrap NOTIFICATION-TYPE
        OBJECTS   {
           ruijieApMacAddr,
           ruijieCPUUtilization1Min
        }
        STATUS     current
        DESCRIPTION
                "clear the warning of lank ap CPU usage too high and report the current CPU usage."
        ::= { ruijieSystemMIBTraps 12 }
        
--lank ap 2010-7
ruijieSystemLankApMemusageTooHighTrap NOTIFICATION-TYPE
        OBJECTS   {
           ruijieApMacAddr,
           ruijieMemoryPoolCurrentUtilization
        }
        STATUS     current
        DESCRIPTION
                "lank ap Memory usage too high warning."
        ::= { ruijieSystemMIBTraps 13 }   
        
--lank ap 2010-7
ruijieSystemLankApMemusageTooHighRecovTrap NOTIFICATION-TYPE
        OBJECTS   {
           ruijieApMacAddr,
           ruijieMemoryPoolCurrentUtilization
        }
        STATUS     current
        DESCRIPTION
                "clear the warning of lank ap Memory usage too high and report the current Memory usage."
        ::= { ruijieSystemMIBTraps 14 }    

--System reset trap 2010-7
ruijieSystemResetTrap NOTIFICATION-TYPE
        STATUS     current
        DESCRIPTION
                "send a trap while system reset"
        ::= { ruijieSystemMIBTraps 15 }
        
--lank ap reset trap 2010-8
ruijieSystemLankApResetTrap NOTIFICATION-TYPE
        OBJECTS   {ruijieApMacAddr}
        STATUS     current
        DESCRIPTION
                "send a trap while lank ap system reset"
        ::= { ruijieSystemMIBTraps 16 }
   
ruijieSystemPowerOnTrap NOTIFICATION-TYPE
        OBJECTS   {ruijieSystemPowerIndex}
        STATUS     current
        DESCRIPTION
                "send a trap while power on."
        ::= { ruijieSystemMIBTraps 17 }
                      
ruijieSystemPowerOffTrap NOTIFICATION-TYPE
        OBJECTS   {ruijieSystemPowerIndex}
        STATUS     current
        DESCRIPTION
                "send a trap while power off."
        ::= { ruijieSystemMIBTraps 18 }

ruijieSystemPowerOnTrapInVSU NOTIFICATION-TYPE
        OBJECTS   { 
            ruijieSystemSwitchID,
            ruijieSystemPowerIndex
        }
        STATUS     current
        DESCRIPTION
                "send a trap while power on in VSU."
        ::= { ruijieSystemMIBTraps 19 }
                      
ruijieSystemPowerOffTrapInVSU NOTIFICATION-TYPE
        OBJECTS   {
            ruijieSystemSwitchID,
            ruijieSystemPowerIndex
        }
        STATUS     current
        DESCRIPTION
                "send a trap while power off in VSU."
        ::= { ruijieSystemMIBTraps 20 }

ruijieSystemTmpTableTooHighTrap NOTIFICATION-TYPE
        OBJECTS   {
            ruijieSystemMultipleTemperatureSlotIndex
        }
        STATUS     current
        DESCRIPTION
                "Temperature Too High warning with the slot index."
        ::= { ruijieSystemMIBTraps 21 }

ruijieSystemTmpTableTooHighRecovTrap NOTIFICATION-TYPE
        OBJECTS   {
            ruijieSystemMultipleTemperatureSlotIndex
        }
        STATUS     current
        DESCRIPTION
                "clear the warning of Temperature too high with the slot index."
        ::= { ruijieSystemMIBTraps 22 }

ruijieSystemTmpTableTooHighTrapVSU NOTIFICATION-TYPE
        OBJECTS   {
            ruijieSystemMultipleTemperatureDeviceIndex,
            ruijieSystemMultipleTemperatureSlotIndex
        }
        STATUS     current
        DESCRIPTION
                "Temperature Too High warning with the slot index in VSU."
        ::= { ruijieSystemMIBTraps 23 }
 
ruijieSystemTmpTableTooHighRecovTrapVSU NOTIFICATION-TYPE
        OBJECTS   {            
            ruijieSystemMultipleTemperatureDeviceIndex,
            ruijieSystemMultipleTemperatureSlotIndex
        }
        STATUS     current
        DESCRIPTION
                "clear the warning of Temperature too high with the slot index."
        ::= { ruijieSystemMIBTraps 24 }

ruijieSystemFanTableStateChange  NOTIFICATION-TYPE
        OBJECTS   {
            ruijieSystemFanStatusFanIndex,
            ruijieSystemFanStatusIndex,
            ruijieSystemFanStatus
        }
        STATUS     current
        DESCRIPTION
                "while the state of fan changed, then this trap will be sent."
        ::= { ruijieSystemMIBTraps 25 }                

ruijieSystemFanTableStateChangeVSU NOTIFICATION-TYPE
        OBJECTS   {
            ruijieSystemFanStatusDeviceIndex,  
            ruijieSystemFanStatusFanIndex,
            ruijieSystemFanStatusIndex,
            ruijieSystemFanStatus
        }
        STATUS     current
        DESCRIPTION
                "In VSU, while the state of fan changed, then this trap will be sent."
        ::= { ruijieSystemMIBTraps 26 }                

ruijieSystemParamSaveErr NOTIFICATION-TYPE
        OBJECTS   {
        ruijieSystemParamSaveErrIdx,
        ruijieSystemParamSaveErrMsg
        }
        STATUS     current
        DESCRIPTION
                "while call exec write, then this trap will be sent."
        ::= { ruijieSystemMIBTraps 27 }                
        
ruijieSystemFanTableOn  NOTIFICATION-TYPE
        OBJECTS   {
            ruijieSystemFanStatusFanIndex,
            ruijieSystemFanStatusIndex,
            ruijieSystemFanStatus
        }
        STATUS     current
        DESCRIPTION
                "while fan is turned on, then this trap will be sent."
        ::= { ruijieSystemMIBTraps 28 }                

ruijieSystemFanTableOff  NOTIFICATION-TYPE
        OBJECTS   {
            ruijieSystemFanStatusFanIndex,
            ruijieSystemFanStatusIndex,
            ruijieSystemFanStatus
        }
        STATUS     current
        DESCRIPTION
                "while fan is turned off, then this trap will be sent."
        ::= { ruijieSystemMIBTraps 29 }   

ruijieSystemFanTableOnVSU NOTIFICATION-TYPE
        OBJECTS   {
            ruijieSystemFanStatusDeviceIndex,  
            ruijieSystemFanStatusFanIndex,
            ruijieSystemFanStatusIndex,
            ruijieSystemFanStatus
        }
        STATUS     current
        DESCRIPTION
                "In VSU, while fan is turned on, then this trap will be sent."
        ::= { ruijieSystemMIBTraps 30 }   

ruijieSystemFanTableOffVSU NOTIFICATION-TYPE
        OBJECTS   {
            ruijieSystemFanStatusDeviceIndex,  
            ruijieSystemFanStatusFanIndex,
            ruijieSystemFanStatusIndex,
            ruijieSystemFanStatus
        }
        STATUS     current
        DESCRIPTION
                "In VSU, while fan is turned off, then this trap will be sent."
        ::= { ruijieSystemMIBTraps 31 }

ruijieSwitchOverNotify NOTIFICATION-TYPE
        OBJECTS   {
            ruijieSystemSwitchID
        }
        STATUS     current
        DESCRIPTION
                " while redundancy forceswitch, then this trap will be sent."
        ::= { ruijieSystemMIBTraps 32 }

ruijieResetNotify NOTIFICATION-TYPE
        OBJECTS   {
            ruijieSystemSwitchID,
            entPhysicalName
        }
        STATUS     current
        DESCRIPTION
                " while reset slot, then this trap will be sent."
        ::= { ruijieSystemMIBTraps 33 }

ruijieOfflineNotify NOTIFICATION-TYPE
        OBJECTS   {
            ruijieSystemSwitchID,
            entPhysicalName
        }
        STATUS     current
        DESCRIPTION
                " while offline slot, then this trap will be sent."
        ::= { ruijieSystemMIBTraps 34 }

ruijieSystemPowerOnNotify NOTIFICATION-TYPE
        OBJECTS   {
            ruijieSystemSwitchID,
            entPhysicalName
        }
        STATUS     current
        DESCRIPTION
                " while user enter power on command, then this trap will be sent."
        ::= { ruijieSystemMIBTraps 35 }
        
ruijieSystemPowerOffNotify NOTIFICATION-TYPE
        OBJECTS   {
            ruijieSystemSwitchID,
            entPhysicalName
        }
        STATUS     current
        DESCRIPTION
                " while user enter power off command, then this trap will be sent."
        ::= { ruijieSystemMIBTraps 36 }  

--Memory usage too high trap 2019-03
ruijieSystemMemusageTooHighAlarm NOTIFICATION-TYPE
        OBJECTS   {
                ruijieNodeMemoryPoolName,
                ruijieNodeMemoryPoolCurrentUtilization
        }
        STATUS     current
        DESCRIPTION
                "Memory usage too high warning."
        ::= { ruijieSystemMIBTraps 37 }   
        
--Memory usage too high recover trap 2019-03 
ruijieSystemMemusageTooHighRecovAlarm NOTIFICATION-TYPE
        OBJECTS   {
                ruijieNodeMemoryPoolName,
                ruijieNodeMemoryPoolCurrentUtilization
        }
        STATUS     current
        DESCRIPTION
                "Clear the warning of memory usage too high and report the current memory usage."
        ::= { ruijieSystemMIBTraps 38 }  

--CPUsage too high trap 2019-03    
ruijieSystemCPUusageTooHighAlarm NOTIFICATION-TYPE
        OBJECTS   {
                ruijieNodeCPUTotalName,
                ruijieNodeCPUTotal1min
        }
        STATUS     current
        DESCRIPTION
                "CPU usage too high warning."
        ::= { ruijieSystemMIBTraps 39 }
                      
--CPUsage too high recover trap 2019-03 
ruijieSystemCPUusageTooHighRecovAlarm NOTIFICATION-TYPE
        OBJECTS   {
                ruijieNodeCPUTotalName,
                ruijieNodeCPUTotal1min
        }
        STATUS     current
        DESCRIPTION
                "Clear the warning of CPU usage too high and report the current CPU usage."
        ::= { ruijieSystemMIBTraps 40 }

ruijieSystemDeviceModeChange NOTIFICATION-TYPE
    OBJECTS {
        ruijieSystemDeviceMode
    }
    STATUS current
    DESCRIPTION
        "Notification of device running mode changing. Only support in all-in-one device."
    ::= { ruijieSystemMIBTraps 41 }

ruijieSystemDeviceTemperatureWarningAlarm NOTIFICATION-TYPE
        OBJECTS   {
            ruijieSystemDeviceTemperatureDeviceIndex,
            ruijieSystemDeviceTemperatureSlotIndex,
            ruijieSystemDeviceTemperatureSubSlotIndex
        }
        STATUS     current
        DESCRIPTION
                "Notification of device temperature reaches warning level."
        ::= { ruijieSystemMIBTraps 42 }
 
ruijieSystemDeviceTemperatureWarningRecovAlarm NOTIFICATION-TYPE
        OBJECTS   {            
            ruijieSystemDeviceTemperatureDeviceIndex,
            ruijieSystemDeviceTemperatureSlotIndex,
            ruijieSystemDeviceTemperatureSubSlotIndex
        }
        STATUS     current
        DESCRIPTION
                "Clear the notification of device temperature reaches warning level."
        ::= { ruijieSystemMIBTraps 43 }

ruijieSystemDeviceTemperatureCriticalAlarm NOTIFICATION-TYPE
        OBJECTS   {
            ruijieSystemDeviceTemperatureDeviceIndex,
            ruijieSystemDeviceTemperatureSlotIndex,
            ruijieSystemDeviceTemperatureSubSlotIndex
        }
        STATUS     current
        DESCRIPTION
                "Notification of device temperature reaches critical level."
        ::= { ruijieSystemMIBTraps 44 }
 
ruijieSystemDeviceTemperatureCriticalRecovAlarm NOTIFICATION-TYPE
        OBJECTS   {            
            ruijieSystemDeviceTemperatureDeviceIndex,
            ruijieSystemDeviceTemperatureSlotIndex,
            ruijieSystemDeviceTemperatureSubSlotIndex
        }
        STATUS     current
        DESCRIPTION
                "Clear the notification of device temperature reaches critical level."
        ::= { ruijieSystemMIBTraps 45 }

ruijieSystemDeviceTemperatureShutdownAlarm NOTIFICATION-TYPE
        OBJECTS   {
            ruijieSystemDeviceTemperatureDeviceIndex,
            ruijieSystemDeviceTemperatureSlotIndex,
            ruijieSystemDeviceTemperatureSubSlotIndex
        }
        STATUS     current
        DESCRIPTION
                "Notification of device temperature reaches shutdown level."
        ::= { ruijieSystemMIBTraps 46 }
 
ruijieSystemDeviceTemperatureShutdownRecovAlarm NOTIFICATION-TYPE
        OBJECTS   {            
            ruijieSystemDeviceTemperatureDeviceIndex,
            ruijieSystemDeviceTemperatureSlotIndex,
            ruijieSystemDeviceTemperatureSubSlotIndex
        }
        STATUS     current
        DESCRIPTION
                "Clear the notification of device temperature reaches shutdown level."
        ::= { ruijieSystemMIBTraps 47 }

ruijieSwitchOverFailNotify NOTIFICATION-TYPE
        OBJECTS   {
            ruijieSystemSwitchID
        }
        STATUS     current
        DESCRIPTION
                "When redundancy forceswitch failed, this trap will be sent."
        ::= { ruijieSystemMIBTraps 48 }

ruijieMasterSwitchoverPreviousMaster OBJECT-TYPE
        SYNTAX DisplayString
        MAX-ACCESS accessible-for-notify
        STATUS current
        DESCRIPTION
                "Previous master for ruijieMasterSwitchoverNotify."
        ::= { ruijieSystemMIBTraps 49 }

ruijieMasterSwitchoverCurrentMaster OBJECT-TYPE
        SYNTAX DisplayString
        MAX-ACCESS accessible-for-notify
        STATUS current
        DESCRIPTION
                "Current master for ruijieMasterSwitchoverNotify."
        ::= { ruijieSystemMIBTraps 50 }

ruijieMasterSwitchoverNotify NOTIFICATION-TYPE
        OBJECTS   {
            ruijieMasterSwitchoverPreviousMaster,
            ruijieMasterSwitchoverCurrentMaster
        }
        STATUS     current
        DESCRIPTION
                " When master changed, this trap will be sent."
        ::= { ruijieSystemMIBTraps 51 }

ruijieSystemFanRemovedTimeoutNotify NOTIFICATION-TYPE
        OBJECTS   {
            ruijieSystemSwitchID
        }
        STATUS     current
        DESCRIPTION
                "When a fan is absent for 2 minutes, this trap will be sent."
        ::= { ruijieSystemMIBTraps 52 }

ruijieSystemFanRemovedResumeNotify NOTIFICATION-TYPE
        OBJECTS   {
            ruijieSystemSwitchID
        }
        STATUS     current
        DESCRIPTION
                "When no fan is absent for 2 minutes, this trap will be sent."
        ::= { ruijieSystemMIBTraps 53 }

ruijieCardPowerOnNotify NOTIFICATION-TYPE
        OBJECTS   {
            entPhysicalName
        }
        STATUS     current
        DESCRIPTION
                "When user enter power on command, this trap will be sent."
        ::= { ruijieSystemMIBTraps 54 }
        
ruijieCardPowerOffNotify NOTIFICATION-TYPE
        OBJECTS   {
            entPhysicalName
        }
        STATUS     current
        DESCRIPTION
                "When user enter power off command, this trap will be sent."
        ::= { ruijieSystemMIBTraps 55 }

ruijieSystemVacConfigDiff NOTIFICATION-TYPE
        OBJECTS   {
            ruijieSystemVacConfigDiffMsg
        }
        STATUS     current
        DESCRIPTION
                "while the running config of slave vac is different to master vac, then this trap will be sent."
        ::= { ruijieSystemMIBTraps 56 }   

ruijieSystemMIBConformance OBJECT IDENTIFIER ::= { ruijieSystemMIB 3 }
ruijieSystemMIBCompliances OBJECT IDENTIFIER ::= { ruijieSystemMIBConformance 1 }
ruijieSystemMIBGroups      OBJECT IDENTIFIER ::= { ruijieSystemMIBConformance 2 }


-- compliance statements

ruijieSystemMIBCompliance MODULE-COMPLIANCE
        STATUS  current
        DESCRIPTION
                "The compliance statement for entities which implement
                the Ruijie System MIB"
        MODULE  -- this module
                MANDATORY-GROUPS { ruijieSystemMIBGroup
                 }
        ::= { ruijieSystemMIBCompliances 1 }
                
-- units of conformance

ruijieSystemMIBGroup OBJECT-GROUP
        OBJECTS {
               ruijieSystemHwVersion, 
               ruijieSystemSwVersion,
               ruijieSystemBootVersion,
               ruijieSystemSysCtrlVersion,
               ruijieSystemParametersSave,
               ruijieSystemReset,
               ruijieSystemOutBandRate,
               ruijieSwitchLayer 
        }
        STATUS  current
        DESCRIPTION
                "A collection of objects providing system information and
                opertion to a Ruijie agent."
        ::= { ruijieSystemMIBGroups 1 } 
  
END
