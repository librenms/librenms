-- Copyright 2002-2014 by Allied Telesis, Inc.
--
-- Name: AtiEdgeSwitch-MIB
--
-- Version: 7.00 MIB 2.4.1.5 
--
-- Products using this MIB:
-- AT-9000/28
-- AT-9000/28SP
-- AT-9000/28POE
-- AT-9000/52
-- AT-9000/12POE
-- AT-8100S/24
-- AT-8100S/24C
-- AT-8100S/24POE
-- AT-8100S/48
-- AT-8100S/48POE
-- AT-8100S/16F8-SC
-- AT-8100S/24F-LC
-- AT-8100S/16F8-LC
-- AT-8100L/8
-- AT-8100L/8POE
-- AT-8100S/24F-SC
-- AT-8100S/24DC
-- AT-FS970M/24C
-- AT-FS970M/8
-- AT-FS970M/8PS
-- AT-FS970M/24PS
-- AT-FS970M/48
-- AT-FS970M/48PS
-- AT-FS970M/16F8-LC
-- AT-FS970M/24LPS
-- AT-FS970M/24F
-- AT-FS970M/16F8-SC
--
-- History:
-- Nelson Ho                        08/28/2009  : Ported from ATS63
--
-- Nelson Ho             v 4.00     08/28/2009  : Add new product branch 14 for 9924T
--
-- Youn-Mor Steven Chen             05/11/2010  : Add SFLOW and LLDP tables
--
-- Shirley Shi           v 5.00     04/03/2012  : Fix syntax errors detected by snmpB and MG-Soft
--
-- Shirley Shi           v 6.00     02/10/2013  : Design traps for 9000 and 8100 products
--
-- Masahiko Iwamoto      v 6.01     09/03/2013  : Add new product for AT-FS970M/24C
--
-- Masahiko Iwamoto      v 7.00     04/23/2014  : Add new product for AT-FS970M/24LPS
--
-- Shirley Shi                      04/30/2014  : Add DHCP Server tables
--
-- Ethan Yen                        05/02/2014  : Add Loop Protection tables
--
-- Masahiko Iwamoto                 05/13/2014  : Add new product for AT-FS970M/24F
--
-- Masahiko Iwamoto                 06/24/2014  : Add new product for AT-FS970M/16F8-SC

AtiEdgeSwitch-MIB       DEFINITIONS ::= BEGIN
        IMPORTS
                IpAddress, MODULE-IDENTITY,OBJECT-TYPE, NOTIFICATION-TYPE,
                Integer32, Counter64, Counter32, TimeTicks, Gauge32
                        FROM SNMPv2-SMI
                TEXTUAL-CONVENTION, DisplayString, RowStatus, TruthValue, MacAddress
                        FROM SNMPv2-TC
                enterprises
                        FROM RFC1155-SMI;


alliedTelesis   MODULE-IDENTITY

        LAST-UPDATED
                "201108180000Z"
        ORGANIZATION
                "Allied Telesis International"
        CONTACT-INFO
                "Allied Telesis International"
        DESCRIPTION
                "Private MIB for ATI layer 2 stackable switches. This MIB
                can be used in Windows and UNIX environments."
        REVISION
                "201108180000Z"
        DESCRIPTION
                "Fixed Semantic Errors"
        REVISION
                "200407220000Z"
        DESCRIPTION
                "Private MIB for ATI layer 2 stackable switches. This MIB
                can be used in Windows and UNIX environments."
        ::= { enterprises 207 }

-- OID tree for Allied Telesis MIBs

        mibObject       OBJECT IDENTIFIER ::= { alliedTelesis 8 }
        atiStkSwMib     OBJECT IDENTIFIER ::= { mibObject 17 }


-- MODULE IDENTITY for the private mib

-- LLDP-MED textual conventions

AtiStkSwLldpMedDeviceClass  ::= TEXTUAL-CONVENTION
        STATUS          current
        DESCRIPTION
                "Device Class to which the device is a member.

                A value of notDefined(0) indicates that the device
                has capabilities not covered by any of the LLDP-MED classes.

                A value of endpointClass1(1) indicates that the device
                has endpoint class 1 capabilities.

                A value of endpointClass2(2) indicates that the device
                has endpoint class 2 capabilities.

                A value of endpointClass3(3) indicates that the device
                has endpoint class 3 capabilities.

                A value of networkConnectivity(4) indicates that the device
                has network connectivity device capabilities."
        SYNTAX          INTEGER {
                                notDefined (0),
                                endpointClass1 (1),
                                endpointClass2 (2),
                                endpointClass3 (3),
                                networkConnectivity (4)
                                }

-- LLDP-MED Capabilities TC

AtiStkSwLldpMedCapabilities  ::= TEXTUAL-CONVENTION
        STATUS          current
        DESCRIPTION
                "Bitmap that includes the MED organizationally defined set of LLDP
                TLVs the device is capable of and whose transmission is allowed on
                the local LLDP agent by network management.

                Each bit in the bitmap corresponds to an LLDP-MED subtype associated
                with a specific TIA TR41.4 MED TLV.

                Having the bit 'capabilities(0)' set indicates that the LLDP
                agent refers to the Capabilities TLVs.

                Having the bit 'networkPolicy(1)' set indicates that the LLDP
                agent refers to the Network Policy TLVs.

                Having the bit 'location(2)' set indicates that
                the LLDP agent refers to the Emergency Communications
                System Location TLVs.

                Having the bit 'extendedPSE(3)' set indicates that
                the LLDP agent refers to the Extended PoE TLVs with PSE
                capabilities.

                Having the bit 'extendedPD(4)' set indicates that
                the LLDP agent refers to the Extended PoE TLVs with PD
                capabilities.

                Having the bit 'inventory(5)' set indicates that
                the LLDP agent refers to the Hardware Revision, Firmware
                Revision, Software Revision, Serial Number, Manufacturer Name,
                Model Name, and Asset ID TLVs."

        SYNTAX          BITS    {
                                capabilities (0),
                                networkPolicy (1),
                                location (2),
                                extendedPSE (3),
                                extendedPD (4),
                                inventory (5)
                                }


--  Location Subtype Textual Convention

LocationSubtype ::= TEXTUAL-CONVENTION
        STATUS          current
        DESCRIPTION
                "The location subtype advertised by the remote endpoint.

                A value coordinateBased(2) indicates that the location subtype
                advertised by the endpoint is defined to use the relevant sub-
                fields of the DHCP option for Coordinate LCI as specified in
                ANSI/TIA-1057, Section 10.2.4.3.1.

                A value civicAddress(3) indicates that the location subtype
                advertised by the endpoint is defined to use the relevant sub-
                fields of the DHCP option for Civic Address as specified in
                ANSI/TIA-1057, Section 10.2.4.3.2.

                A value elin(4) indicates that the location subtype
                advertised by the endpoint is defined to use the Emergency
                Location Information Number (ELIN) as specified in
                ANSI/TIA-1057, Section 10.2.4.3.3."
        SYNTAX          INTEGER {
                                unknown (1),
                                coordinateBased (2),
                                civicAddress (3),
                                elin (4)
                                }

-- Policy Application Type Textual Convention

PolicyAppType ::= TEXTUAL-CONVENTION
        STATUS          current
        DESCRIPTION
                "The media type that defines the primary function of the
                application for the policy advertised by an endpoint.

                Having the bit voice(1) set indicates that the media type defining
                a primary function of the application for the policy advertised on
                the local port is voice.

                Having the bit voiceSignaling(3) set indicates that the media type
                defining a primary function of the application for the policy
                advertised on the local port is voice signaling.

                Having the bit guestVoice(4) set indicates that the media type
                Defining a primary function of the application for the policy
                advertised on the local port is guest voice.

                Having the bit guestVoiceSignaling(5) set indicates that the media
                type defining a primary function of the application for the policy
                advertised on the local port is guest voice signaling.

                Having the bit softPhoneVoice(6) set indicates that the media type
                Defining a primary function of the application for the policy
                advertised on the local port is softphone voice.

                Having the bit videoConferencing(7) set indicates that the media
                type defining a primary function of the application for the policy
                advertised on the local port is voice.

                Having the bit streamingVideo(8) set indicates that the media type
                defining a primary function of the application for the policy
                advertised on  the local port is streaming video.

                Having the bit videoSignaling(2) set indicates that the media type
                defining a primary function of the application for the policy
                advertised on the local port is video signaling."
        SYNTAX          BITS    {
                                unknown(0),
                                voice(1),
                                voiceSignaling(2),
                                guestVoice(3),
                                guestVoiceSignaling(4),
                                softPhoneVoice(5),
                                videoconferencing(6),
                                streamingVideo(7),
                                videoSignaling(8)
                                }


-- OID tree for Allied Telesis Layer-2 switches

        atiProduct              OBJECT IDENTIFIER ::= { alliedTelesis 1 }
        swhub                   OBJECT IDENTIFIER ::= { atiProduct 4 }
        at-9000-28              OBJECT IDENTIFIER ::= { swhub 148 }
        at-9000-28SP            OBJECT IDENTIFIER ::= { swhub 149 }
        at-9000-28POE           OBJECT IDENTIFIER ::= { swhub 150 }
        at-9000-52              OBJECT IDENTIFIER ::= { swhub 151 }
        at-9000-12POE           OBJECT IDENTIFIER ::= { swhub 207 }
        at-8100S-24             OBJECT IDENTIFIER ::= { swhub 169 }
        at-8100S-24C            OBJECT IDENTIFIER ::= { swhub 170 }
        at-8100S-24POE          OBJECT IDENTIFIER ::= { swhub 171 }
        at-8100S-48             OBJECT IDENTIFIER ::= { swhub 172 }
        at-8100S-48POE          OBJECT IDENTIFIER ::= { swhub 173 }
        at-8100S-16F8-SC        OBJECT IDENTIFIER ::= { swhub 174 }
        at-8100S-24F-LC         OBJECT IDENTIFIER ::= { swhub 175 }
        at-8100S-16F8-LC        OBJECT IDENTIFIER ::= { swhub 176 }
        at-8100-8               OBJECT IDENTIFIER ::= { swhub 177 }
        at-8100-8POE            OBJECT IDENTIFIER ::= { swhub 178 }
        at-8100S-24F-SC         OBJECT IDENTIFIER ::= { swhub 206 }
        at-8100S-24DC           OBJECT IDENTIFIER ::= { swhub 208 }
        at-FS970M-24C           OBJECT IDENTIFIER ::= { swhub 233 }
        at-FS970M-8             OBJECT IDENTIFIER ::= { swhub 234 }
        at-FS970M-8PS           OBJECT IDENTIFIER ::= { swhub 235 }
        at-FS970M-24PS          OBJECT IDENTIFIER ::= { swhub 236 }
        at-FS970M-48            OBJECT IDENTIFIER ::= { swhub 237 }
        at-FS970M-48PS          OBJECT IDENTIFIER ::= { swhub 238 }
        at-FS970M-16F8-LC       OBJECT IDENTIFIER ::= { swhub 239 }
        at-FS970M-24LPS         OBJECT IDENTIFIER ::= { swhub 240 }
        at-FS970M-24F           OBJECT IDENTIFIER ::= { swhub 241 }
        at-FS970M-16F8-SC       OBJECT IDENTIFIER ::= { swhub 242 }

-- OID tree for Allied Telesis 9924 family

        routerSwitch            OBJECT IDENTIFIER ::= { atiProduct 14 }
        at-9924T-EMC            OBJECT IDENTIFIER ::= { routerSwitch 53 }

-- Groups supported in this MIB

atiStkSwSysGroup                OBJECT IDENTIFIER ::= { atiStkSwMib 1 }
atiStkSwPortGroup               OBJECT IDENTIFIER ::= { atiStkSwMib 2 }
atiStkSwVlanGroup               OBJECT IDENTIFIER ::= { atiStkSwMib 3 }
atiStkSwMacAddrGroup            OBJECT IDENTIFIER ::= { atiStkSwMib 4 }
atiStkSwEthStatsGroup           OBJECT IDENTIFIER ::= { atiStkSwMib 5 }
atiStkSwTrapsGroup              OBJECT IDENTIFIER ::= { atiStkSwMib 6 }
atiStkSwQoSGroup                OBJECT IDENTIFIER ::= { atiStkSwMib 7 }
atiStkSwTrunkGroup              OBJECT IDENTIFIER ::= { atiStkSwMib 8 }
atiStkSwACLGroup                OBJECT IDENTIFIER ::= { atiStkSwMib 9 }
atiStkSwLldpGroup               OBJECT IDENTIFIER ::= { atiStkSwMib 10 }
atiSflowRcvrGroup               OBJECT IDENTIFIER ::= { atiStkSwMib 11 }
atiSflowFsGroup                 OBJECT IDENTIFIER ::= { atiStkSwMib 12 }
atiSflowCpGroup                 OBJECT IDENTIFIER ::= { atiStkSwMib 13 }
atiSflowSetGroup                OBJECT IDENTIFIER ::= { atiStkSwMib 14 }
atiSflowEnableGroup             OBJECT IDENTIFIER ::= { atiStkSwMib 15 }
atiStkSwAQoSGroup               OBJECT IDENTIFIER ::= { atiStkSwMib 17 }
atiStkSwAACLGroup               OBJECT IDENTIFIER ::= { atiStkSwMib 18 }
atiStkSwMSTPGroup               OBJECT IDENTIFIER ::= { atiStkSwMib 19 }
atiStkSwMVRGroup                OBJECT IDENTIFIER ::= { atiStkSwMib 20 }
atiStkSwPSTACKGroup             OBJECT IDENTIFIER ::= { atiStkSwMib 21 }
atiStkSwDhcpSvrGroup            OBJECT IDENTIFIER ::= { atiStkSwMib 22 }


-- The atiStkSwSysGroup

atiStkSwSysConfig               OBJECT IDENTIFIER ::= { atiStkSwSysGroup 1 }
atiStkSwSysNwMgmt               OBJECT IDENTIFIER ::= { atiStkSwSysGroup 2 }
atiStkSwSysSystemTimeConfig     OBJECT IDENTIFIER ::= { atiStkSwSysGroup 5 }
atiStkSwSysInfoGroup            OBJECT IDENTIFIER ::= { atiStkSwSysGroup 6 }
atiStkSwSysMgmtACLGroup         OBJECT IDENTIFIER ::= { atiStkSwSysGroup 7 }


-- atiStkSwSysConfig

atiStkSwSysReset        OBJECT-TYPE
        SYNTAX          INTEGER {
                                no-reset (1),
                                reset (2)
                                }
        MAX-ACCESS      read-write
        STATUS          current
        DESCRIPTION
                "Setting this object to 'reset' will cause the switch to
                perform a soft reboot. Setting this object to 'no-reset' will
                have no effect."
        ::= { atiStkSwSysConfig 1 }

atiStkSwSysIpAddress    OBJECT-TYPE
        SYNTAX          IpAddress
        MAX-ACCESS      read-only
        STATUS          current
        DESCRIPTION
                "The IP address of the switch."
        ::= { atiStkSwSysConfig 2 }

atiStkSwSysSubnetMask   OBJECT-TYPE
        SYNTAX          IpAddress
        MAX-ACCESS      read-only
        STATUS          current
        DESCRIPTION
                "The subnet mask of the switch."
        ::= { atiStkSwSysConfig 3 }

atiStkSwSysGateway      OBJECT-TYPE
        SYNTAX          IpAddress
        MAX-ACCESS      read-write
        STATUS          current
        DESCRIPTION
                "The IP address of the gateway for the switch."
        ::= { atiStkSwSysConfig 4 }

atiStkSwSysIpAddressStatus  OBJECT-TYPE
        SYNTAX          INTEGER {
                                fromDhcp (1),
                                fromBootp (2),
                                static (3)
                                }
        MAX-ACCESS      read-only
        STATUS          current
        DESCRIPTION
                "This object specifies how the IP address, subnet mask and the
                gateway address currently in use on the switch was
                obtained/configured."
        ::= { atiStkSwSysConfig 5 }

atiStkSwSysDnsServer    OBJECT-TYPE
        SYNTAX          IpAddress
        MAX-ACCESS      read-only
        STATUS          current
        DESCRIPTION
                "This object specifies the IP address of the DNS server for
                the switch.
                This MIB is not applicable to the 85xx and 94xx family of ATI
                switches."
        ::= { atiStkSwSysConfig 6 }

atiStkSwSysDefaultDomainName  OBJECT-TYPE
        SYNTAX          DisplayString
        MAX-ACCESS      read-only
        STATUS          current
        DESCRIPTION
                "This object specifies the default domain name for the switch.

                This MIB is not applicable to the 85xx and 94xx family of ATI
                switches."
        ::= { atiStkSwSysConfig 7 }

atiStkSwSysNumberOfModules  OBJECT-TYPE
        SYNTAX          Integer32
        MAX-ACCESS      read-only
        STATUS          current
        DESCRIPTION
                "This object gives a count of the number of modules present
                in the stackable switch."
        ::= { atiStkSwSysConfig 8 }

atiStkSwSysSpanningTreeStatus  OBJECT-TYPE
        SYNTAX          INTEGER {
                                disable (1),
                                enable (2)
                                }
        MAX-ACCESS      read-write
        STATUS          current
        DESCRIPTION
                "Setting this object to 'enable' will enable spanning tree
                protocol on the switch. Setting this object to 'disable'
                will disable spanning tree protocol on the switch.

                Select the spanning tree protocol version using the object
                'atiStkSwSysSpanningTreeVersion'."
        ::= { atiStkSwSysConfig 9 }

atiStkSwSysSpanningTreeVersion  OBJECT-TYPE
        SYNTAX          INTEGER {
                                rstp (1),
                                stp (2),
                                mstp (3)
                                }
        MAX-ACCESS      read-write
        STATUS          current
        DESCRIPTION
                "The object can be used to select the version of spanning tree
                protocol running on the switch."
        ::= { atiStkSwSysConfig 10 }

atiStkSwSysAction       OBJECT-TYPE
        SYNTAX          INTEGER {
                                saveConfig (1),
                                reset (2),
                                defaultConfig (3)
                                }
        MAX-ACCESS      read-only
        STATUS          current
        DESCRIPTION
                        "This  object specifies the  following actions  that apply to the switch:
                         saveConfig - Save the current switch configuration.
                         reset - Reboot the switch.
                         defaultConfig - Restore default switch configuration.
                         The switch is automatically rebooted after this operation.
                         Note that this  object returns a zero value when doing a Get operation."
        ::= { atiStkSwSysConfig 11 }

atiStkSwSysNumOfModuleInStack  OBJECT-TYPE
        SYNTAX          Integer32 (1..8)
        MAX-ACCESS      read-only
        STATUS          current
        DESCRIPTION
                "This  object specifies the  number of stacking modules in the stack."
        ::= { atiStkSwSysConfig 12 }


-- atiStkSwSysNwMgmt

atiStkSwSysTrapRecv1    OBJECT-TYPE
        SYNTAX          IpAddress
        MAX-ACCESS      read-write
        STATUS          obsolete
        DESCRIPTION
                "This object specifies the IP address of the management
                station #1 to which traps are sent by the switch.

                This MIB is not applicable to the 85xx and 94xx family of ATI
                switches."
        ::= { atiStkSwSysNwMgmt 1 }

atiStkSwSysTrapRecv2    OBJECT-TYPE
        SYNTAX          IpAddress
        MAX-ACCESS      read-write
        STATUS          obsolete
        DESCRIPTION
                "This object specifies the IP address of the management
                station #2 to which traps are sent by the switch.

                This MIB is not applicable to the 85xx and 94xx family of ATI
                switches."
        ::= { atiStkSwSysNwMgmt 2 }

atiStkSwSysTrapRecv3    OBJECT-TYPE
        SYNTAX          IpAddress
        MAX-ACCESS      read-write
        STATUS          obsolete
        DESCRIPTION
                "This object specifies the IP address of the management
                station #3 to which traps are sent by the switch.

                This MIB is not applicable to the 85xx and 94xx family of ATI
                switches."
        ::= { atiStkSwSysNwMgmt 3 }

atiStkSwSysTrapRecv4    OBJECT-TYPE
        SYNTAX          IpAddress
        MAX-ACCESS      read-write
        STATUS          obsolete
        DESCRIPTION
                "This object specifies the IP address of the management
                station #4 to which traps are sent by the switch.

                This MIB is not applicable to the 85xx and 94xx family of ATI
                switches."
        ::= { atiStkSwSysNwMgmt 4 }

-- The system time group

atiStkSwSysCurrentTime  OBJECT-TYPE
        SYNTAX          DisplayString (SIZE(0..32))
        MAX-ACCESS      read-write
        STATUS          current
        DESCRIPTION     "This object specify the current time of the system. The user
                         can change the time by providing the string format as an input,
                         e.g. HH:MM:SS."
        ::= { atiStkSwSysSystemTimeConfig 1 }

atiStkSwSysCurrentDate  OBJECT-TYPE
        SYNTAX          DisplayString (SIZE(0..32))
        MAX-ACCESS      read-write
        STATUS          current
        DESCRIPTION     "This object specify the current time of the system. The user
                         can change the date by providing the string format as an input,
                         e.g. DD-MM-YYYY."
        ::= { atiStkSwSysSystemTimeConfig 2 }


atiStkSwSysSNTPStatus   OBJECT-TYPE
        SYNTAX          INTEGER {
                                disabled (1),
                                enabled (2)
                        }
        MAX-ACCESS      read-write
        STATUS          current
        DESCRIPTION     "Enable/disable the SNTP status."
        ::= { atiStkSwSysSystemTimeConfig 3 }

atiStkSwSysSNTPServerIPAddress  OBJECT-TYPE
        SYNTAX          IpAddress
        MAX-ACCESS      read-write
        STATUS          current
        DESCRIPTION     "The ipaddress of the SNTP Server."
        ::= { atiStkSwSysSystemTimeConfig 4 }

atiStkSwSysSNTPUTCOffset  OBJECT-TYPE
        SYNTAX          Integer32 (-12..12)
        MAX-ACCESS      read-write
        STATUS          current
        DESCRIPTION     "Set the UTC Offset value within the range from -12 to 12 in hours."
        ::= { atiStkSwSysSystemTimeConfig 5 }

atiStkSwSysSNTPDSTStatus  OBJECT-TYPE
        SYNTAX          INTEGER {
                                disabled (1),
                                enabled (2)
                        }
        MAX-ACCESS      read-write
        STATUS          current
        DESCRIPTION     "Enable/disble the Daylight Saving Time."
        ::= { atiStkSwSysSystemTimeConfig 6 }

atiStkSwSysSNTPPollingInterval  OBJECT-TYPE
        SYNTAX          Integer32 (60..1200)
        MAX-ACCESS      read-only
        STATUS          current
        DESCRIPTION     "Setting the interval for polling the SNTP Server. The polling
                         time range is between 60 and 1200 in seconds."
        ::= { atiStkSwSysSystemTimeConfig 7 }


atiStkSwSysSNTPLastDelta  OBJECT-TYPE
        SYNTAX          Integer32
        MAX-ACCESS      read-only
        STATUS          current
        DESCRIPTION     "Display the last adjustment to system done in seconds."
        ::= { atiStkSwSysSystemTimeConfig 8 }


-- The atiStkSwSysInfoGroup

-- System Temperature Information Table

atiStkSwTemperatureInfoTable  OBJECT-TYPE
        SYNTAX          SEQUENCE OF AtiStkSwTemperatureInfoEntry
        MAX-ACCESS      not-accessible
        STATUS          current
        DESCRIPTION
                "This table contains a list of system temperature information present in the switch
                stack including voltage and temperature."
        ::= { atiStkSwSysInfoGroup 1 }

atiStkSwTemperatureInfoEntry  OBJECT-TYPE
        SYNTAX          AtiStkSwTemperatureInfoEntry
        MAX-ACCESS      not-accessible
        STATUS          current
        DESCRIPTION
                "This object specifies an entry in 'atiStkSwTemperatureInfoTable'
                that describes the hardware informaton for a module present in
                the switch stack."
        INDEX           { atiStkSwTemperatureInfoModuleId }
        ::= { atiStkSwTemperatureInfoTable 1 }

AtiStkSwTemperatureInfoEntry ::=
        SEQUENCE {
                atiStkSwTemperatureInfoModuleId         Integer32,
                atiStkSwTemperatureInfoTemperature      Integer32,
                atiStkSwTemperatureInfoState            DisplayString
                }

atiStkSwTemperatureInfoModuleId  OBJECT-TYPE
        SYNTAX          Integer32 (1..8)
        MAX-ACCESS      read-only
        STATUS          current
        DESCRIPTION     "The module Id of a switch, it also used as an index of the table."
        ::= { atiStkSwTemperatureInfoEntry 1 }


atiStkSwTemperatureInfoTemperature  OBJECT-TYPE
        SYNTAX          Integer32 (1..200)
        MAX-ACCESS      read-only
        STATUS          current
        DESCRIPTION     "The temperature of the device in Celcius."
        ::= { atiStkSwTemperatureInfoEntry 2 }

atiStkSwTemperatureInfoState  OBJECT-TYPE
        SYNTAX          DisplayString (SIZE(1..12))
        MAX-ACCESS      read-only
        STATUS          current
        DESCRIPTION     "The state of the temperature state, either normal or off."
        ::= { atiStkSwTemperatureInfoEntry 3 }


-- The System Fan Information Table

atiStkSwFanInfoTable    OBJECT-TYPE
        SYNTAX          SEQUENCE OF AtiStkSwFanInfoEntry
        MAX-ACCESS      not-accessible
        STATUS          current
        DESCRIPTION
                "This table contains information for all the fans present
                in the switch."
        ::= { atiStkSwSysInfoGroup 2 }

atiStkSwFanInfoEntry    OBJECT-TYPE
        SYNTAX          AtiStkSwFanInfoEntry
        MAX-ACCESS      not-accessible
        STATUS          current
        DESCRIPTION
                "This object specifies an entry in 'atiStkSwFanInfoTable'
                that describes the informaton for a specific fan in
                the switch."
        INDEX           { atiStkSwFanInfoModuleId }
        ::= { atiStkSwFanInfoTable 1 }

AtiStkSwFanInfoEntry ::=
        SEQUENCE {
                atiStkSwFanInfoModuleId                 Integer32,
                atiStkSwFanInfoFan1Id                   Integer32,
                atiStkSwFan1InfoState                   DisplayString,
                atiStkSwFan1InfoSpeed                   Integer32,
                atiStkSwFanInfoFan2Id                   Integer32,
                atiStkSwFan2InfoState                   DisplayString,
                atiStkSwFan2InfoSpeed                   Integer32
                }


atiStkSwFanInfoModuleId OBJECT-TYPE
        SYNTAX          Integer32 (1..8)
        MAX-ACCESS      read-only
        STATUS          current
        DESCRIPTION     "The module Id of the switch."
        ::= { atiStkSwFanInfoEntry 1 }

atiStkSwFanInfoFan1Id   OBJECT-TYPE
        SYNTAX          Integer32 (1..8)
        MAX-ACCESS      read-only
        STATUS          current
        DESCRIPTION     "The fan Id1 of the switch."
        ::= { atiStkSwFanInfoEntry 2 }

atiStkSwFan1InfoState   OBJECT-TYPE
        SYNTAX          DisplayString (SIZE(1..12))
        MAX-ACCESS      read-only
        STATUS          current
        DESCRIPTION     "The state of the fan1 running, either normal or off."
        ::= { atiStkSwFanInfoEntry 3 }

atiStkSwFan1InfoSpeed   OBJECT-TYPE
        SYNTAX          Integer32 (1..10000)
        MAX-ACCESS      read-only
        STATUS          current
        DESCRIPTION     "The current speed of fan1."
        ::= { atiStkSwFanInfoEntry 4 }

atiStkSwFanInfoFan2Id   OBJECT-TYPE
        SYNTAX          Integer32 (1..8)
        MAX-ACCESS      read-only
        STATUS          current
        DESCRIPTION     "The fan2 Id of the switch."
        ::= { atiStkSwFanInfoEntry 5 }

atiStkSwFan2InfoState   OBJECT-TYPE
        SYNTAX          DisplayString (SIZE(1..12))
        MAX-ACCESS      read-only
        STATUS          current
        DESCRIPTION     "The state of the fan2 running, either normal or off."
        ::= { atiStkSwFanInfoEntry 6 }

atiStkSwFan2InfoSpeed   OBJECT-TYPE
        SYNTAX          Integer32 (1..10000)
        MAX-ACCESS      read-only
        STATUS          current
        DESCRIPTION     "The current speed of fan2."
        ::= { atiStkSwFanInfoEntry 7 }


-- The System Voltage Information Table

-- atiStkSwVoltageInfoTable  OBJECT-TYPE
--      SYNTAX          SEQUENCE OF AtiStkSwVoltageInfoEntry
--      MAX-ACCESS      not-accessible
--      STATUS          current
--      DESCRIPTION
--              "This table contains a list of system Voltage information."
--      ::= { atiStkSwSysInfoGroup 3 }

-- atiStkSwVoltageInfoEntry  OBJECT-TYPE
--      SYNTAX          AtiStkSwVoltageInfoEntry
--      MAX-ACCESS      not-accessible
--      STATUS          current
--      DESCRIPTION
--              "This object specifies an entry in 'atiStkSwVoltageInfoTable'
--              that describes the Voltage informaton for the switch."
--      INDEX           { atiStkSwVoltageInfoModuleId, atiStkSwVoltageInfoIndex }
--      ::= { atiStkSwVoltageInfoTable 1 }

-- AtiStkSwVoltageInfoEntry ::=
--      SEQUENCE {
--              atiStkSwVoltageInfoModuleId             Integer32,
--              atiStkSwVoltageInfoIndex                Integer32,
--              atiStkSwVoltageInfoLevel                DisplayString,
--              atiStkSwVoltageInfoMeasured             DisplayString
--              }


-- atiStkSwVoltageInfoModuleId  OBJECT-TYPE
--      SYNTAX          Integer32 (1..8)
--      MAX-ACCESS      read-only
--      STATUS          current
--      DESCRIPTION     "The module Id of the switch."
--      ::= { atiStkSwVoltageInfoEntry 1 }

-- atiStkSwVoltageInfoIndex  OBJECT-TYPE
--      SYNTAX          Integer32 (1..10)
--      MAX-ACCESS      read-only
--      STATUS          current
--      DESCRIPTION     "The index of the voltage table."
--      ::= { atiStkSwVoltageInfoEntry 2 }

-- atiStkSwVoltageInfoLevel  OBJECT-TYPE
--      SYNTAX          DisplayString (SIZE(1..16))
--      MAX-ACCESS      read-only
--      STATUS          current
--      DESCRIPTION     "The voltage input level."
--      ::= { atiStkSwVoltageInfoEntry 3 }

-- atiStkSwVoltageInfoMeasured  OBJECT-TYPE
--      SYNTAX          DisplayString (SIZE(0..16))
--      MAX-ACCESS      read-only
--      STATUS          current
--      DESCRIPTION     "The current voltage."
--      ::= { atiStkSwVoltageInfoEntry 4 }

-- The System PSU Information Table

atiStkSwPSUInfoTable    OBJECT-TYPE
        SYNTAX          SEQUENCE OF AtiStkSwPSUInfoEntry
        MAX-ACCESS      not-accessible
        STATUS          current
        DESCRIPTION
                "This table contains information for all the power supply units present
                in the switch."
        ::= { atiStkSwSysInfoGroup 4 }

atiStkSwPSUInfoEntry    OBJECT-TYPE
        SYNTAX          AtiStkSwPSUInfoEntry
        MAX-ACCESS      not-accessible
        STATUS          current
        DESCRIPTION
                "This object specifies an entry in 'atiStkSwPSUInfoTable'
                that describes the informaton for a specific PSU in
                the switch."
        INDEX           { atiStkSwPSUInfoModuleId }
        ::= { atiStkSwPSUInfoTable 1 }

AtiStkSwPSUInfoEntry ::=
        SEQUENCE {
                atiStkSwPSUInfoModuleId                 Integer32,
                atiStkSwPSUInfoPSU1Id                   Integer32,
                atiStkSwPSU1InfoState                   DisplayString,
                atiStkSwPSU1InfoStatus                  DisplayString,
                atiStkSwPSUInfoPSU2Id                   Integer32,
                atiStkSwPSU2InfoState                   DisplayString,
                atiStkSwPSU2InfoStatus                  DisplayString
                }


atiStkSwPSUInfoModuleId OBJECT-TYPE
        SYNTAX          Integer32 (1..8)
        MAX-ACCESS      read-only
        STATUS          current
        DESCRIPTION     "The module Id of the switch."
        ::= { atiStkSwPSUInfoEntry 1 }

atiStkSwPSUInfoPSU1Id   OBJECT-TYPE
        SYNTAX          Integer32 (1..8)
        MAX-ACCESS      read-only
        STATUS          current
        DESCRIPTION     "The PSU1 Id of the switch."
        ::= { atiStkSwPSUInfoEntry 2 }

atiStkSwPSU1InfoState   OBJECT-TYPE
        SYNTAX          DisplayString (SIZE(1..12))
        MAX-ACCESS      read-only
        STATUS          current
        DESCRIPTION     "The state of the PSU1, either normal or off."
        ::= { atiStkSwPSUInfoEntry 3 }

atiStkSwPSU1InfoStatus  OBJECT-TYPE
        SYNTAX          DisplayString (SIZE(1..12))
        MAX-ACCESS      read-only
        STATUS          current
        DESCRIPTION     "The status of the PSU1, either on or off."
        ::= { atiStkSwPSUInfoEntry 4 }

atiStkSwPSUInfoPSU2Id   OBJECT-TYPE
        SYNTAX          Integer32 (1..8)
        MAX-ACCESS      read-only
        STATUS          current
        DESCRIPTION     "The PSU2 Id of the switch."
        ::= { atiStkSwPSUInfoEntry 5 }

atiStkSwPSU2InfoState   OBJECT-TYPE
        SYNTAX          DisplayString (SIZE(1..12))
        MAX-ACCESS      read-only
        STATUS          current
        DESCRIPTION     "The state of the PSU2, either normal or off."
        ::= { atiStkSwPSUInfoEntry 6 }

atiStkSwPSU2InfoStatus  OBJECT-TYPE
        SYNTAX          DisplayString (SIZE(1..12))
        MAX-ACCESS      read-only
        STATUS          current
        DESCRIPTION     "The status of the PSU2, either on or off."
        ::= { atiStkSwPSUInfoEntry 7 }


-- atiStkSwSysMgmtACL Group

atiStkSwSysMgmtACLStatus  OBJECT-TYPE
        SYNTAX          INTEGER {
                                enabled (1),
                                disabled (2)
                                }
        MAX-ACCESS      read-write
        STATUS          current
        DESCRIPTION     "Enable/Disable management ACL feature."
        ::= { atiStkSwSysMgmtACLGroup 1 }

atiStkSwSysMgmtACLConfigTable  OBJECT-TYPE
        SYNTAX          SEQUENCE OF AtiStkSwSysMgmtACLConfigEntry
        MAX-ACCESS      not-accessible
        STATUS          current
        DESCRIPTION
                "This table contains a list of MgmtACLs present in the switch
                stack and their associated hardware information."
        ::= { atiStkSwSysMgmtACLGroup 2 }

atiStkSwSysMgmtACLConfigEntry  OBJECT-TYPE
        SYNTAX          AtiStkSwSysMgmtACLConfigEntry
        MAX-ACCESS      not-accessible
        STATUS          current
        DESCRIPTION
                "This object specifies an entry in 'atiStkSwSysMgmtACLConfigTable'
                that allow the user controls which management stations can remotely
                manage the device using the Telnet application protocol or a web
                browser."
        INDEX           { atiStkSwSysMgmtACLConfigModuleId, atiStkSwSysMgmtACLConfigId }
        ::= { atiStkSwSysMgmtACLConfigTable 1 }

AtiStkSwSysMgmtACLConfigEntry ::=
        SEQUENCE {
                atiStkSwSysMgmtACLConfigModuleId        Integer32,
                atiStkSwSysMgmtACLConfigId              Integer32,
                atiStkSwSysMgmtACLConfigIpAddr          IpAddress,
                atiStkSwSysMgmtACLConfigMask            IpAddress,
                atiStkSwSysMgmtACLConfigApplication     BITS,
                atiStkSwSysMgmtACLConfigRowStatus       RowStatus
                }

atiStkSwSysMgmtACLConfigModuleId  OBJECT-TYPE
        SYNTAX          Integer32 (1..8)
        MAX-ACCESS      read-only
        STATUS          current
        DESCRIPTION
                "The ID of this module."
        ::= { atiStkSwSysMgmtACLConfigEntry 1 }

atiStkSwSysMgmtACLConfigId  OBJECT-TYPE
        SYNTAX          Integer32 (1..256)
        MAX-ACCESS      read-only
        STATUS          current
        DESCRIPTION
                "The ID of the Management ACL Table for this module."
        ::= { atiStkSwSysMgmtACLConfigEntry 2 }


atiStkSwSysMgmtACLConfigIpAddr  OBJECT-TYPE
        SYNTAX          IpAddress
        MAX-ACCESS      read-write
        STATUS          current
        DESCRIPTION
                "The IP Address of the specific management station."
        ::= { atiStkSwSysMgmtACLConfigEntry 3 }

atiStkSwSysMgmtACLConfigMask  OBJECT-TYPE
        SYNTAX          IpAddress
        MAX-ACCESS      read-write
        STATUS          current
        DESCRIPTION
                "The subnet mask of the IP Address."
        ::= { atiStkSwSysMgmtACLConfigEntry 4 }

atiStkSwSysMgmtACLConfigApplication  OBJECT-TYPE
        SYNTAX          BITS    {
                                telnet (0),
                                web (1),
                                ping (2)
                                }
        MAX-ACCESS      read-write
        STATUS          current
        DESCRIPTION
                "This object specify which interface the user want the management
                station to be able to use when managing the switch. The options are :
                telnet, web, ping, all. Note that the enum value correspond to the
                bit position of the mask."
        ::= { atiStkSwSysMgmtACLConfigEntry 5 }

atiStkSwSysMgmtACLConfigRowStatus  OBJECT-TYPE
        SYNTAX          RowStatus
        MAX-ACCESS      read-write
        STATUS          current
        DESCRIPTION
                "The Row Status of the Mgmt ACL table. "
        ::= { atiStkSwSysMgmtACLConfigEntry 6 }


-- The atiStkSwPortGroup

-- Defined Below atiStkSwPortConfigTable  OBJECT IDENTIFIER ::= { atiStkSwPortGroup 1 }
atiStkSwPortMirroringConfig     OBJECT IDENTIFIER ::= { atiStkSwPortGroup 2 }
-- atiStkSwPortSecurityConfig   OBJECT IDENTIFIER ::= { atiStkSwPortGroup 3 }
-- Define Below atiStkSwPortIntrusionDetectionTable  OBJECT IDENTIFIER ::= { atiStkSwPortGroup 4 }
-- Defined Below atiStkPortSecurityConfigTable  OBJECT IDENTIFIER ::= { atiStkSwPortGroup 5 }

-- atiStkDOSConfig              OBJECT IDENTIFIER ::= { atiStkSwPortGroup 6 }
-- atiStkSwIntrusionAttackTable OBJECT IDENTIFIER ::= { atiStkSwPortGroup 7 }


-- atiStkSwPortConfigTable

atiStkSwPortConfigTable OBJECT-TYPE
        SYNTAX          SEQUENCE OF AtiStkSwPortConfigEntry
        MAX-ACCESS      not-accessible
        STATUS          current
        DESCRIPTION
                "This table contains a list of physical ports present in the
                switch and their associated attributes."
        ::= { atiStkSwPortGroup 1 }

atiStkSwPortConfigEntry OBJECT-TYPE
        SYNTAX          AtiStkSwPortConfigEntry
        MAX-ACCESS      not-accessible
        STATUS          current
        DESCRIPTION
                "This object specifies an entry in 'atiStkSwPortConfigTable'
                that describes the attributes associated with a physical port
                present in the switch."
        INDEX           { atiStkSwModuleId, atiStkSwPortId }
        ::= { atiStkSwPortConfigTable 1 }

AtiStkSwPortConfigEntry ::=
        SEQUENCE {
                atiStkSwModuleId                        Integer32,
                atiStkSwPortId                          Integer32,
                atiStkSwPortName                        DisplayString,
                atiStkSwPortState                       INTEGER,
                atiStkSwPortLinkState                   INTEGER,
                atiStkSwPortNegotiation                 INTEGER,
                atiStkSwPortSpeed                       INTEGER,
                atiStkSwPortDuplexStatus                INTEGER,
                atiStkSwPortFlowControl                 INTEGER,
                atiStkSwPortBackPressure                INTEGER,
                atiStkSwPortPriority                    INTEGER,
                atiStkSwPortBroadcastProcessing         INTEGER,
                atiStkSwPortMDIO                        INTEGER,
                atiStkSwPortHOLLimit                    Integer32,
                atiStkSwPortBackPressureLimit           Integer32,
                atiStkSwPortSTPState                    INTEGER
                }

atiStkSwModuleId        OBJECT-TYPE
        SYNTAX          Integer32 (1..8)
        MAX-ACCESS      read-only
        STATUS          current
        DESCRIPTION
                "This object specifies the ID of a module present in the switch
                stack."
        ::= { atiStkSwPortConfigEntry 1 }

atiStkSwPortId          OBJECT-TYPE
        SYNTAX          Integer32 (1..50)
        MAX-ACCESS      read-only
        STATUS          current
        DESCRIPTION
                "This object specifies the ID of a port present on a given
                module."
        ::= { atiStkSwPortConfigEntry 2 }

atiStkSwPortName        OBJECT-TYPE
        SYNTAX          DisplayString (SIZE(0..19))
        MAX-ACCESS      read-write
        STATUS          current
        DESCRIPTION
                "The user-defined ASCII name of the port."
        ::= { atiStkSwPortConfigEntry 3 }

atiStkSwPortState       OBJECT-TYPE
        SYNTAX          INTEGER {
                                enabled (1),
                                disabled (2)
                                }
        MAX-ACCESS      read-write
        STATUS          current
        DESCRIPTION
                "This object allows the user to either enabled or disabled.
                This object can be read to obtain the current state of the port."
        ::= { atiStkSwPortConfigEntry 4 }

atiStkSwPortLinkState   OBJECT-TYPE
        SYNTAX          INTEGER {
                                online (1),
                                offline (2)
                                }
        MAX-ACCESS      read-only
        STATUS          current
        DESCRIPTION
                "This object specifies the link state on this port."
        ::= { atiStkSwPortConfigEntry 5 }

atiStkSwPortNegotiation OBJECT-TYPE
        SYNTAX          INTEGER {
                                autosense (1),
                                forceHalfDuplex-10M (2),
                                forceHalfDuplex-100M (3),
                                forceHalfDuplex-1G (4),
                                forceFullDuplex-10M (5),
                                forceFullDuplex-100M (6),
                                forceFullDuplex-1G (7)
                                }
        MAX-ACCESS      read-write
        STATUS          current
        DESCRIPTION
                "This object allows an admin request to configure the port
                to either autosense or one of the different speed-duplex
                combinations."
        ::= { atiStkSwPortConfigEntry 6 }

atiStkSwPortSpeed       OBJECT-TYPE
        SYNTAX          INTEGER {
                                unknown (1),
                                speed-10M (2),
                                speed-100M (3),
                                speed-1G (4)
                                }
        MAX-ACCESS      read-only
        STATUS          current
        DESCRIPTION
                "This object specifies the current speed of the port."
        ::= { atiStkSwPortConfigEntry 7 }

atiStkSwPortDuplexStatus  OBJECT-TYPE
        SYNTAX          INTEGER {
                                unknown (1),
                                halfDuplex (2),
                                fullDuplex (3)
                                }
        MAX-ACCESS      read-only
        STATUS          current
        DESCRIPTION
                "This object specifies the current duplex type used by the
                port."
        ::= { atiStkSwPortConfigEntry 8 }

atiStkSwPortFlowControl OBJECT-TYPE
        SYNTAX          INTEGER {
                                disable (1),
                                enable (2)
                                }
        MAX-ACCESS      read-write
        STATUS          current
        DESCRIPTION
                "This object is used to enable/disable flow control on the
                port. When enabled, flow control will be full duplex.

                Flow control is disabled by default."
        ::= { atiStkSwPortConfigEntry 9 }

atiStkSwPortBackPressure  OBJECT-TYPE
        SYNTAX          INTEGER {
                                disable (1),
                                enable (2)
                                }
        MAX-ACCESS      read-write
        STATUS          current
        DESCRIPTION
                "This object is used to enable/disable Back Pressure on the
                port.

                Back Pressure is disabled by default."
        ::= { atiStkSwPortConfigEntry 10 }

atiStkSwPortPriority    OBJECT-TYPE
        SYNTAX          INTEGER {
                                use-vlan-priority (1),
                                override-and-use-low-priority (2),
                                override-and-use-high-priority (3)
                                }
        MAX-ACCESS      read-write
        STATUS          current
        DESCRIPTION
                "This object specifies whether packets flowing through this
                port use the associated VLAN priority or override the
                associated VLAN priority with either a high or a low priority.


                This MIB is not applicable to the 85xx and 94xx family of ATI
                switches. Note: These switch families support CoS/QoS."
        ::= { atiStkSwPortConfigEntry 11 }

atiStkSwPortBroadcastProcessing  OBJECT-TYPE
        SYNTAX          INTEGER {
                                discard-broadcasts (1),
                                do-not-discard-broadcasts (2)
                                }
        MAX-ACCESS      read-only
        STATUS          current
        DESCRIPTION
                "This object specifies whether the received broadcast packets
                should be processed or discarded.

                Broadcast packets are processed by default."
        ::= { atiStkSwPortConfigEntry 12 }

atiStkSwPortMDIO        OBJECT-TYPE
        SYNTAX          INTEGER {
                                mdi (1),
                                mdix (2),
                                auto-mdix (3)
                                }
        MAX-ACCESS      read-write
        STATUS          current
        DESCRIPTION
                "This object is used to set the MDIO of this port for required
                cable connection type. For straight-through cable set to mdi
                and for cross-over cable set to mdix."
        ::= { atiStkSwPortConfigEntry 13 }

atiStkSwPortHOLLimit    OBJECT-TYPE
        SYNTAX          Integer32 (1..8191)
        MAX-ACCESS      read-write
        STATUS          current
        DESCRIPTION
                "This object allows user to set the head of line blocking limit.

                Note (94xx): Range upto 8191 is supported for Gigabit Ports."
        ::= { atiStkSwPortConfigEntry 14 }

atiStkSwPortBackPressureLimit  OBJECT-TYPE
        SYNTAX          Integer32 (1..7935)
        MAX-ACCESS      read-write
        STATUS          current
        DESCRIPTION
                "This object is used to set the MDIO of this port for required
                cable connection type. For straight-through cable set to mdi
                and for cross-over cable set to mdix. This limit can be used
                for both BackPressure and FlowControl Limits.

                Note: The range of 1 to 7935 is supported on the 94xx family."
        ::= { atiStkSwPortConfigEntry 15 }

atiStkSwPortSTPState    OBJECT-TYPE
        SYNTAX          INTEGER {
                                unknown (1),
                                disabled (2),
                                blocking (3),
                                listening (4),
                                learning (5),
                                forwarding (6)
                                }
        MAX-ACCESS      read-only
        STATUS          current
        DESCRIPTION
                "This object specifies the spanning tree state on this port.

                This object is not applicable to 8300 series products. This
                object is not valid on the 9400 series of boxes."
        ::= { atiStkSwPortConfigEntry 16 }


-- atiStkSwPortMirroringConfig

atiStkSwPortMirroringState  OBJECT-TYPE
        SYNTAX          INTEGER {
                                disabled (1),
                                enabled (2)
                                }
        MAX-ACCESS      read-write
        STATUS          current
        DESCRIPTION
                "This object specifies whether port mirroring is l2-enabled,
                or disabled on the switch.

                Note that, when enabled, both transmit and receive packets will
                be mirrored."
        ::= { atiStkSwPortMirroringConfig 1 }

-- atiStkSwPortMirroringSourceModuleId  OBJECT-TYPE
--      SYNTAX          Integer32 (1..8)
--      MAX-ACCESS      read-write
--      STATUS          obsolete
--      DESCRIPTION
--              "This object specifies the module ID of the source port that is
--              mirrored.  All packets transmitted and received on the source
--              port will be mirrored onto the destination port (specified by
--              'atiStkSwPortMirroringDestinationModuleId' and
--              'atiStkSwPortMirroringDestinationPortId').
--
--              This object will be set to 0 when port mirroring is disabled.
--              This object will have a default value of 1 (the master module
--              ID) when mirroring is enabled. This is not available on the 85xx
--              and 94xx series of switches."
--      ::= { atiStkSwPortMirroringConfig 2 }

-- atiStkSwPortMirroringSourcePortId  OBJECT-TYPE
--      SYNTAX          Integer32
--      MAX-ACCESS      read-write
--      STATUS          obsolete
--      DESCRIPTION
--              "This object specifies the port ID (on the module specified
--              by 'atiStkSwPortMirroringSourceModuleId') of the source
--              port that is mirrored.  All packets transmitted and received
--              on the source port will be mirrored onto the destination port
--              (specified by 'atiStkSwPortMirroringDestinationModuleId' and
--              'atiStkSwPortMirroringDestinationPortId').
--
--              This object will be set to 0 when port mirroring is
--              disabled. When mirroring is enabled, set this object to a
--              non-zero value to activate mirroring.
--
--              This is not available on the 85xx and 94xx series of switches."
--      ::= { atiStkSwPortMirroringConfig 3 }

atiStkSwPortMirroringDestinationModuleId  OBJECT-TYPE
        SYNTAX          Integer32 (1..8)
        MAX-ACCESS      read-write
        STATUS          current
        DESCRIPTION
                "This object specifies the module ID of the destination port
                that mirrors the source port (specified by
                'atiStkSwPortMirroringSourceModuleId' and
                'atiStkSwPortMirroringSourcePortId'). All packets
                transmitted and received on the source port will be mirrored
                onto the destination port.

                This object will have a value of 0 when port mirroring is
                disabled. This object will have a default value of 1 (the
                master module ID) when mirroring is enabled.

                This is not available on the 85xx and 94xx series of switches"
        ::= { atiStkSwPortMirroringConfig 4 }

atiStkSwPortMirroringDestinationPortId  OBJECT-TYPE
        SYNTAX          Integer32
        MAX-ACCESS      read-write
        STATUS          current
        DESCRIPTION
                "This object specifies the port ID (on the module
                specified by 'atiStkSwPortMirroringDestinationModuleId') of
                the destination port that mirrors the source port (specified
                by 'atiStkSwPortMirroringSourceModuleId' and
                'atiStkSwPortMirroringSourcePortId'). All packets transmitted
                and received on the source port will be mirrored onto the
                destination port.

                This object will have a value of 0 when port mirroring is
                disabled. When mirroring is enabled, set this object to a
                non-zero value to activate mirroring."
        ::= { atiStkSwPortMirroringConfig 5 }

atiStkSwPortMirroringSourceRxList  OBJECT-TYPE
        SYNTAX          DisplayString
        MAX-ACCESS      read-write
        STATUS          current
        DESCRIPTION
                "This object specifies a list of ports that are mirrored for ingress traffic.
                All packets received on these ports will be mirrored onto the
                mirror port (atiStkSwPortMirroringDestinationPortId).

                It is in the format of a list of <PortNumber>
                separated by comma. For example, '1, 4-7' represents the
                port number 1 ports
                from number 4 to 7.

                This object is not applicable to 8300 series products."
        ::= { atiStkSwPortMirroringConfig 6 }

atiStkSwPortMirroringSourceTxList  OBJECT-TYPE
        SYNTAX          DisplayString
        MAX-ACCESS      read-write
        STATUS          current
        DESCRIPTION
                "This object specifies a list of ports that are mirrored for egress traffic.
                All packets transmitted from these ports will be mirrored onto the
                mirror port (atiStkSwPortMirroringDestinationPortId).

                It is in the format of a list of <PortNumber>
                separated by comma. For example, '1, 4-7' represents the
                port number 1 ports
                from number 4 to 7.
                This object is not applicable to 8300 series products."
        ::= { atiStkSwPortMirroringConfig 7 }


-- atiStkSwPortSecurityConfig

-- atiStkSwPortSecurityMode  OBJECT-TYPE
--      SYNTAX          INTEGER {
--                              automatic (1),
--                              limited (2),
--                              secured (3),
--                              locked (4)
--                              }
--      MAX-ACCESS      read-write
--      STATUS          obsolete
--      DESCRIPTION
--              "This object specifies the type of port security configured
--              on the switch.

--              Setting this object to 'automatic(1)' allows the ports to learn
--              new MAC addresses normally. In 'limited(2)' mode, only a
--              limited number of addresses are learned per port. In
--              'secured(3)' mode, the administrator is responsible for
--              configuring the MAC addresses manually per port. In 'locked(4)'
--              mode, the ports stop learning new addresses and those
--              addresses already learnt are locked.

--              By default, port security is set to 'automatic(1)' mode."
--      ::= { atiStkSwPortSecurityConfig 1 }


-- atiStkSwPortIntrusionDetectionTable


-- atiStkSwPortIntrusionDetectionTable  OBJECT-TYPE
--      SYNTAX          SEQUENCE OF AtiStkSwPortIntrusionDetectionEntry
--      MAX-ACCESS      not-accessible
--      STATUS          obsolete
--      DESCRIPTION
--              "This table contains a list of modules and their associated
--              port security -related intrusion detection options. This table
--              is valid only when 'atiStkSwPortSecurityMode' is set to a
--              value other than 'automatic(1)'.

--              This table object is not applicable to 8500 and 9400 series products."
--      ::= { atiStkSwPortGroup 4 }

-- atiStkSwPortIntrusionDetectionEntry  OBJECT-TYPE
--      SYNTAX          AtiStkSwPortIntrusionDetectionEntry
--      MAX-ACCESS      not-accessible
--      STATUS          obsolete
--      DESCRIPTION
--              "This object specifies an entry in
--              'atiStkSwPortIntrusionDetectionTable' that describes port
--              security -related intruder detection configuration associated
--              with a module."
--      INDEX           { atiStkSwModuleId }
--      ::= { atiStkSwPortIntrusionDetectionTable 1 }

-- AtiStkSwPortIntrusionDetectionEntry ::=
--      SEQUENCE {
--              atiStkSwPortIntrusionDetectionAction    INTEGER,
--              atiStkSwPortIntrusionDetectionPortList  DisplayString
--              }

-- atiStkSwPortIntrusionDetectionAction  OBJECT-TYPE
--      SYNTAX          INTEGER {
--                              do-nothing (1),
--                              send-trap-only (2),
--                              disable-port-and-send-trap (3)
--                              }
--      MAX-ACCESS      read-write
--      STATUS          obsolete
--      DESCRIPTION
--              "This object specifies the security action that should be
--              taken when an intrusion is detected."
--      ::= { atiStkSwPortIntrusionDetectionEntry 1 }

-- atiStkSwPortIntrusionDetectionPortList  OBJECT-TYPE
--      SYNTAX          DisplayString
--      MAX-ACCESS      read-write
--      STATUS          obsolete
--      DESCRIPTION
--              "This object specifies a list of ports on this module that
--              participate in intrusion detection."
--      ::= { atiStkSwPortIntrusionDetectionEntry 2 }


-- atiStkPortSecurityConfigTable

atiStkPortSecurityConfigTable  OBJECT-TYPE
        SYNTAX          SEQUENCE OF AtiStkPortSecurityConfigEntry
        MAX-ACCESS      not-accessible
        STATUS          current
        DESCRIPTION
                "This table contains the port security attributes of a list of
                physical ports present in the switch.

                This table object is not applicable to 8300 series products."
        ::= { atiStkSwPortGroup 5 }

atiStkPortSecurityConfigEntry  OBJECT-TYPE
        SYNTAX          AtiStkPortSecurityConfigEntry
        MAX-ACCESS      not-accessible
        STATUS          current
        DESCRIPTION
                "This object specifies an entry in
                'atiStkPortSecurityConfigTable' that describes the port
                security attributes associated with a physical port present in
                the switch."
        INDEX           { atiStkSwModuleId, atiStkSwPortId }
        ::= { atiStkPortSecurityConfigTable 1 }

AtiStkPortSecurityConfigEntry ::=
        SEQUENCE {
--              atiStkPortSecurityMode                  INTEGER,
                atiStkPortSecurityThreshold             Integer32,
                atiStkPortIntrusionAction               INTEGER,
                atiStkPortSecurityAging                 INTEGER,
                atiStkPortIntrusionActionStatus         INTEGER
                }

-- atiStkPortSecurityMode  OBJECT-TYPE
--      SYNTAX          INTEGER {
--                              automatic (1),
--                              limited (2),
--                              secured (3),
--                              locked (4)
--                              }
--      MAX-ACCESS      read-write
--      STATUS          current
--      DESCRIPTION
--              "This object specifies the type of port security configured
--              on the switch.
--
--              Setting this object to 'automatic(1)' allows the ports to learn
--              new MAC addresses normally. In 'limited(2)' mode, only a
--              limited number of addresses are learned per port. In
--              'secured(3)' mode, the administrator is responsible for
--              configuring the MAC addresses manually per port. In 'locked(4)'
--              mode, the ports stop learning new addresses and those
--              addresses already learnt are locked.
--
--              By default, port security is set to 'automatic(1)' mode."
--      ::= { atiStkPortSecurityConfigEntry 1 }

atiStkPortSecurityThreshold  OBJECT-TYPE
        SYNTAX          Integer32 (1..256)
        MAX-ACCESS      read-write
        STATUS          current
        DESCRIPTION
                "This object specifies the security threshold on this port. It
                is applicable only if the port security mode (specified by
                'portSecurityMode') is set to 'limited(2)' mode."
        ::= { atiStkPortSecurityConfigEntry 2 }

atiStkPortIntrusionAction  OBJECT-TYPE
        SYNTAX          INTEGER {
                                protect  (1),
                                restrict (2),
                                shutdown (3)
                                }
        MAX-ACCESS      read-write
        STATUS          current
        DESCRIPTION
                "This object specifies the security action that should be
                taken when an intrusion is detected.

                By default, port intrusion action is set to 'discard' mode."
        ::= { atiStkPortSecurityConfigEntry 3 }

atiStkPortSecurityAging OBJECT-TYPE
        SYNTAX          INTEGER {
                                yes (1),
                                no (2)
                                }
        MAX-ACCESS      read-write
        STATUS          current
        DESCRIPTION
                "This object enables or disables the security aging
                by the 'portSecurityAging'.

                By default, port intrusion action is disabled."
        ::= { atiStkPortSecurityConfigEntry 4 }

atiStkPortIntrusionActionStatus  OBJECT-TYPE
        SYNTAX          INTEGER {
                                enabled (1),
                                disabled (2)
                                }
        MAX-ACCESS      read-write
        STATUS          current
        DESCRIPTION
                "This object enables or disables the security action specified
                by the 'portIntrusionAction'.

                By default, port intrusion action is disabled."
        ::= { atiStkPortSecurityConfigEntry 5 }


-- atiStkPortDhcpIpConfigTable

atiStkPortDhcpIpConfigTable  OBJECT-TYPE
        SYNTAX          SEQUENCE OF AtiStkPortDhcpIpConfigEntry
        MAX-ACCESS      not-accessible
        STATUS          current
        DESCRIPTION
                "This table contains the port DHCP IP assignments list of
                physical ports present in the switch."
        ::= { atiStkSwPortGroup 6 }

atiStkPortDhcpIpConfigEntry  OBJECT-TYPE
        SYNTAX          AtiStkPortDhcpIpConfigEntry
        MAX-ACCESS      not-accessible
        STATUS          current
        DESCRIPTION
                "This object specifies an entry in
                'atiStkPortDhcpIpConfigTable' that describes the port
                DHCP IP assignments  associated with a physical port present in
                the switch."
        INDEX           { atiStkSwModuleId, atiStkSwPortId }
        ::= { atiStkPortDhcpIpConfigTable 1 }

AtiStkPortDhcpIpConfigEntry ::=
        SEQUENCE {
                atiStkPortDhcpIpOffer                      DisplayString,
                atiStkPortDhcpIpAdd                        IpAddress,
                atiStkPortDhcpIpDelete                     IpAddress
                }

atiStkPortDhcpIpOffer   OBJECT-TYPE
        SYNTAX          DisplayString (SIZE(0..32))
        MAX-ACCESS      read-only
        STATUS          current
        DESCRIPTION
                "This object specifies the DHCP IP Offer on this port."
        ::= { atiStkPortDhcpIpConfigEntry 1 }

atiStkPortDhcpIpAdd     OBJECT-TYPE
        SYNTAX          IpAddress
        MAX-ACCESS      read-write
        STATUS          current
        DESCRIPTION
                "This object specifies the DHCP IP added on this port."
        ::= { atiStkPortDhcpIpConfigEntry 2 }

atiStkPortDhcpIpDelete  OBJECT-TYPE
        SYNTAX          IpAddress
        MAX-ACCESS      read-write
        STATUS          current
        DESCRIPTION
                "This object specifies the DHCP IP deleted on this port."
        ::= { atiStkPortDhcpIpConfigEntry 3 }

-- atiStkDOSConfig
-- DOS (Denial Of Service) is not applicable to 8300 series products.

-- atiStkDOSConfigLANIpAddress  OBJECT-TYPE
--      SYNTAX          IpAddress
--      MAX-ACCESS      read-write
--      STATUS          current
--      DESCRIPTION
--              "The IP address of LAN.
--
--              This object is not applicable to 8300 series products."
--      ::= { atiStkDOSConfig 1 }

-- atiStkDOSConfigLANSubnetMask  OBJECT-TYPE
--      SYNTAX          IpAddress
--      MAX-ACCESS      read-write
--      STATUS          current
--      DESCRIPTION
--            "The subnet mask of LAN.
--
--            This object is not applicable to 8300 series products."
--      ::= { atiStkDOSConfig 2 }

-- atiStkPortDOSAttackConfigTable  OBJECT-TYPE
--      SYNTAX          SEQUENCE OF AtiStkPortDOSAttackConfigEntry
--      MAX-ACCESS      not-accessible
--      STATUS          current
--      DESCRIPTION
--              "This table contains the port DOS (denial of service) attack configuration attributes of a list of
--              physical ports present in the switch.
--
--              This table object is not applicable to 8300 series products."
--      ::= { atiStkDOSConfig 3 }

-- atiStkPortDOSAttackConfigEntry  OBJECT-TYPE
--      SYNTAX          AtiStkPortDOSAttackConfigEntry
--      MAX-ACCESS      not-accessible
--      STATUS          current
--      DESCRIPTION
--              "This object specifies an entry in
--              'atiStkPortDOSAttackConfigTable' that describes the port
--              DOS attack configuration attributes associated with a physical port present in
--              the switch."
--      INDEX   { atiStkSwModuleId, atiStkSwPortId }
--      ::= { atiStkPortDOSAttackConfigTable 1 }

-- AtiStkPortDOSAttackConfigEntry ::=
--      SEQUENCE {
--              atiStkSwPortDOSAttackType               INTEGER,
--              atiStkSwPortDOSAttackActionStatus       INTEGER,
--              atiStkSwPortDOSAttackMirrorPort         Integer32,
--              atiStkSwPortDOSAttackMirrorPortStatus   INTEGER
--              }

-- atiStkSwPortDOSAttackType  OBJECT-TYPE
--      SYNTAX          INTEGER {
--                              syn-flood (1),
--                              smurf (2),
--                              land (3),
--                              ip-option (4),
--                              teardrop (5),
--                              ping-of-death (6)
--                              }
--      MAX-ACCESS      read-write
--      STATUS          current
--      DESCRIPTION
--              "This object specifies the type of Port DOS attack configured
--              on the switch."
--      ::= { atiStkPortDOSAttackConfigEntry 1 }

-- atiStkSwPortDOSAttackActionStatus  OBJECT-TYPE
--      SYNTAX          INTEGER {
--                              enabled (1),
--                              disabled (2)
--                              }
--      MAX-ACCESS      read-write
--      STATUS          current
--      DESCRIPTION
--              "This object enables or disables the port DOS action specified
--              by the 'atiStkSwPortDOSAttackType'.
--
--              By default, port DOS attack action is disabled.
--              "
--      ::= { atiStkPortDOSAttackConfigEntry 2 }

-- atiStkSwPortDOSAttackMirrorPort  OBJECT-TYPE
--      SYNTAX          Integer32
--      MAX-ACCESS      read-only
--      STATUS          obsolete
--      DESCRIPTION
--              "This object specifies the mirror port number to which the packet are to be mirrored for the
--              DOS attack as specified by atiStkSwPortDOSAttackType.
--              "
--      ::= { atiStkPortDOSAttackConfigEntry 3 }

-- atiStkSwPortDOSAttackMirrorPortStatus OBJECT-TYPE
--      SYNTAX          INTEGER {
--                              enabled (1),
--                              disabled (2)
--                              }
--      MAX-ACCESS      read-write
--      STATUS          current
--      DESCRIPTION
--              "This object enables or disables mirroring of attack packets. If enabled, all potential
--               attack packets are mirrored to the port specified by atiStkSwPortMirroringDestinationModuleId
--               and atiStkSwPortMirroringDestinationPortId. The object atiStkSwPortMirroringState should also
--               be set to l2-enabled for mirroring to work."
--      ::= { atiStkPortDOSAttackConfigEntry 4 }


-- The atiStkSwIntrusionAttackTable

atiStkSwIntrusionAttackTable  OBJECT-TYPE
        SYNTAX          SEQUENCE OF AtiStkSwIntrusionAttackEntry
        MAX-ACCESS      not-accessible
        STATUS          current
        DESCRIPTION
                "This object specifies an entry in 'atiStkSwIntrusionAttackTable'
                that describes the intruder attack associated with a physical port
                present in the switch."
        ::= { atiStkSwPortGroup 7 }

atiStkSwIntrusionAttackEntry  OBJECT-TYPE
        SYNTAX          AtiStkSwIntrusionAttackEntry
        MAX-ACCESS      not-accessible
        STATUS          current
        DESCRIPTION
                "This object specifies an entry in 'atiStkSwIntrusionAttackTable'
                that describes the intruder attack associated with a physical port
                present in the switch."
        INDEX           { atiStkSwModuleId, atiStkSwPortId }
        ::= { atiStkSwIntrusionAttackTable 1 }

AtiStkSwIntrusionAttackEntry   ::=
        SEQUENCE {
                atiStkSwIntruderAttackVlanId            Integer32,
                atiStkSwIntruderAttackMacAddr           MacAddress
                }

atiStkSwIntruderAttackVlanId  OBJECT-TYPE
        SYNTAX          Integer32
        MAX-ACCESS      read-only
        STATUS          current
        DESCRIPTION
                "This object identifies the intruding VlanId  on the port for
                this module."
        ::= { atiStkSwIntrusionAttackEntry 1 }

atiStkSwIntruderAttackMacAddr   OBJECT-TYPE
        SYNTAX          MacAddress
        MAX-ACCESS      read-only
        STATUS          current
        DESCRIPTION
                "This object identifies the intruding MAC address on the port for
                this module."
        ::= { atiStkSwIntrusionAttackEntry 2 }


-- atiStkSwPortLoopProtectConfigTable

atiStkSwPortLoopProtectConfigTable  OBJECT-TYPE
        SYNTAX          SEQUENCE OF AtiStkSwPortLoopProtectConfigEntry
        MAX-ACCESS      not-accessible
        STATUS          current
        DESCRIPTION
                "This table contains the current loop detection information of a list
                 of physical ports present in the switch."
        ::= { atiStkSwPortGroup 8 }

atiStkSwPortLoopProtectConfigEntry  OBJECT-TYPE
        SYNTAX          AtiStkSwPortLoopProtectConfigEntry
        MAX-ACCESS      not-accessible
        STATUS          current
        DESCRIPTION
                "This object specifies an entry in
                'atiStkSwPortLoopProtectConfigTable' that describe the current
                Loop Detection information with a physical port present in the
                switch."
        INDEX           { atiStkSwModuleId, atiStkSwPortId }
        ::= { atiStkSwPortLoopProtectConfigTable 1 }

AtiStkSwPortLoopProtectConfigEntry ::=
        SEQUENCE {
                atiStkSwPortLoopProtectConfigStatus     INTEGER,
                atiStkSwPortLoopProtectConfigAction     INTEGER,
                atiStkSwPortLoopProtectConfigExpiry     Integer32,
                atiStkSwRxLDFModuleId                   Integer32,
                atiStkSwRxLDFPortId                     Integer32,
                atiStkSwRxLDFVlanId                     Integer32
                }

atiStkSwPortLoopProtectConfigStatus  OBJECT-TYPE
        SYNTAX          INTEGER {
                                inactive (1),
                                normal (2),
                                detected (3),
                                blocking (4)
                                }
        MAX-ACCESS      read-only
        STATUS          current
        DESCRIPTION
                "This object specifies the current loop status of Loop Protection."
        ::= { atiStkSwPortLoopProtectConfigEntry 1 }

atiStkSwPortLoopProtectConfigAction  OBJECT-TYPE
        SYNTAX          INTEGER {
                                unknown (1),
                                learn-disable (2),
                                link-down (3),
                                log-only (4),
                                port-disabled (5),
                                vlan-disable (6),
                                none (7)
                                }
        MAX-ACCESS      read-only
        STATUS          current
        DESCRIPTION
                "This object specifies the current loop action by Loop Detected."
        ::= { atiStkSwPortLoopProtectConfigEntry 2 }

atiStkSwPortLoopProtectConfigExpiry  OBJECT-TYPE
        SYNTAX          Integer32
        MAX-ACCESS      read-only
        STATUS          current
        DESCRIPTION
                "This object specifies the remaining time(sec) to back to normal status
                from blocking status. A value of -1 indicates that Blocktimeout has
                been set 'None' or Loop Protection is 'Normal' status."
        ::= { atiStkSwPortLoopProtectConfigEntry 3 }

atiStkSwRxLDFModuleId   OBJECT-TYPE
        SYNTAX          Integer32
        MAX-ACCESS      read-only
        STATUS          current
        DESCRIPTION
                "The Module ID where the loop detection frame is received on."
        ::= { atiStkSwPortLoopProtectConfigEntry 4 }

atiStkSwRxLDFPortId     OBJECT-TYPE
        SYNTAX          Integer32
        MAX-ACCESS      read-only
        STATUS          current
        DESCRIPTION
                "The Port ID where the loop detection frame is received on."
        ::= { atiStkSwPortLoopProtectConfigEntry 5 }

atiStkSwRxLDFVlanId     OBJECT-TYPE
        SYNTAX          Integer32
        MAX-ACCESS      read-only
        STATUS          current
        DESCRIPTION
                "The Vlan ID where the loop detection frame is received on."
        ::= { atiStkSwPortLoopProtectConfigEntry 6 }


-- The atiStkSwVlanGroup
-- Defined below atiStkSwVlanSettingsTable      OBJECT IDENTIFIER ::= { atiStkSwVlanGroup 4 }
-- Defined below atiStkSwVlanConfigTable        OBJECT IDENTIFIER ::= { atiStkSwVlanGroup 1 }
-- Defined Below atiStkSwPort2VlanTable         OBJECT IDENTIFIER ::= { atiStkSwVlanGroup 2 }
-- Defined Below atiStkSwMacAddr2VlanTable      OBJECT IDENTIFIER ::= { atiStkSwVlanGroup 3 }
-- Defined below atiStkSwVlanSettingsTable      OBJECT IDENTIFIER ::= { atiStkSwVlanGroup 4 }
-- Defined Below atiStkSwGVRPConfig             OBJECT IDENTIFIER ::= { atiStkSwVlanGroup 6 }
-- Defined Below atiStkSwGVRPPortConfigTable    OBJECT IDENTIFIER ::= { atiStkSwVlanGroup 7 }
-- Defined Below atiStkSwGVRPCounters           OBJECT IDENTIFIER ::= { atiStkSwVlanGroup 8 }



-- atiStkSwVlanConfigTable


atiStkSwVlanConfigTable OBJECT-TYPE
        SYNTAX          SEQUENCE OF AtiStkSwVlanConfigEntry
        MAX-ACCESS      not-accessible
        STATUS          current
        DESCRIPTION
                "This table contains a list of VLANs configured on the switch."
        ::= { atiStkSwVlanGroup 1 }

atiStkSwVlanConfigEntry OBJECT-TYPE
        SYNTAX          AtiStkSwVlanConfigEntry
        MAX-ACCESS      not-accessible
        STATUS          current
        DESCRIPTION
                "This object specifies an entry in 'atiStkSwVlanConfigTable'
                that describes a VLAN configured on the switch."
          INDEX         { atiStkSwVlanId }
        ::= { atiStkSwVlanConfigTable 1 }

AtiStkSwVlanConfigEntry ::=
        SEQUENCE {
---             atiStkSwEntry                           Integer32,
                atiStkSwVlanId                          Integer32,
                atiStkSwVlanName                        DisplayString,
                ipAddress                               DisplayString,
--              atiStkSwVlanTaggedPortListModule1       DisplayString,
--              atiStkSwVlanUntaggedPortListModule1     DisplayString,
--              atiStkSwVlanActualUntaggedPortListModule1  DisplayString,
--              atiStkSwVlanTaggedPortListModule2       DisplayString,
--              atiStkSwVlanUntaggedPortListModule2     DisplayString,
--              atiStkSwVlanTaggedPortListModule3       DisplayString,
--              atiStkSwVlanUntaggedPortListModule3     DisplayString,
--              atiStkSwVlanTaggedPortListModule4       DisplayString,
--              atiStkSwVlanUntaggedPortListModule4     DisplayString,
--              atiStkSwVlanTaggedPortListModule5       DisplayString,
--              atiStkSwVlanUntaggedPortListModule5     DisplayString,
--              atiStkSwVlanTaggedPortListModule6       DisplayString,
--              atiStkSwVlanUntaggedPortListModule6     DisplayString,
--              atiStkSwVlanTaggedPortListModule7       DisplayString,
--              atiStkSwVlanUntaggedPortListModule7     DisplayString,
--              atiStkSwVlanTaggedPortListModule8       DisplayString,
--              atiStkSwVlanUntaggedPortListModule8     DisplayString,
--              atiStkSwVlanConfigEntryStatus           RowStatus,
--              atiStkSwVlanActualUntaggedPortList      DisplayString,
                atiStkSwVlanVlanType                    INTEGER,
                atiStkSwVlanTaggedPortList              DisplayString,
                atiStkSwVlanUntaggedPortList            DisplayString,
                atiStkSwVlanConfigEntryStatus           INTEGER
---             atiStkSwVlanPortStatus                  INTEGER
                }

---atiStkSwEntry                OBJECT-TYPE
---        SYNTAX          Integer32
---        MAX-ACCESS      read-only
---        STATUS          current
---        DESCRIPTION
---             "Number of entries in the table of this VLAN. This includes all the tagged and untagged entries"
---        ::= { atiStkSwVlanConfigEntry 1 }


atiStkSwVlanId          OBJECT-TYPE
        SYNTAX          Integer32 (1..4094)
        MAX-ACCESS      read-only
        STATUS          current
        DESCRIPTION
                "The VLAN ID of this VLAN as stored in the tag information
                header in accordance with the 802.1q specifications."
        ::= { atiStkSwVlanConfigEntry 1 }

atiStkSwVlanName        OBJECT-TYPE
        SYNTAX          DisplayString (SIZE(0..32))
        MAX-ACCESS      read-write
        STATUS          current
        DESCRIPTION
                "The name of the VLAN."
        ::= { atiStkSwVlanConfigEntry 2 }

ipAddress               OBJECT-TYPE
        SYNTAX          DisplayString (SIZE(0..32))
        MAX-ACCESS      read-write
        STATUS          current
        DESCRIPTION
                "The ip address of the VLAN."
        ::= { atiStkSwVlanConfigEntry 3 }

-- atiStkSwVlanTaggedPortListModule1   OBJECT-TYPE
--      SYNTAX          DisplayString
--      MAX-ACCESS      read-write
--      STATUS          obsolete
--      DESCRIPTION
--              "This object specifies a list of tagged ports (on module #1)
--              that participate in this VLAN."
--      ::= { atiStkSwVlanConfigEntry 3 }

-- atiStkSwVlanUntaggedPortListModule1  OBJECT-TYPE
--      SYNTAX          DisplayString
--      MAX-ACCESS      read-write
--      STATUS          obsolete
--      DESCRIPTION
--              "This object specifies a list of untagged ports (on module #1)
--              that participate in this VLAN."
--      ::= { atiStkSwVlanConfigEntry 4 }

-- atiStkSwVlanTaggedPortListModule2  OBJECT-TYPE
--      SYNTAX          DisplayString
--      MAX-ACCESS      read-write
--      STATUS          obsolete
--      DESCRIPTION
--              "This object specifies a list of tagged ports (on module #2)
--              that participate in this VLAN."
--      ::= { atiStkSwVlanConfigEntry 5 }

-- atiStkSwVlanUntaggedPortListModule2  OBJECT-TYPE
--      SYNTAX          DisplayString
--      MAX-ACCESS      read-write
--      STATUS          obsolete
--      DESCRIPTION
--              "This object specifies a list of untagged ports (on module #2)
--              that participate in this VLAN."
--      ::= { atiStkSwVlanConfigEntry 6 }

-- atiStkSwVlanTaggedPortListModule3  OBJECT-TYPE
--      SYNTAX          DisplayString
--      MAX-ACCESS      read-write
--      STATUS          obsolete
--      DESCRIPTION
--              "This object specifies a list of tagged ports (on module #3)
--              that participate in this VLAN."
--      ::= { atiStkSwVlanConfigEntry 7 }

-- atiStkSwVlanUntaggedPortListModule3  OBJECT-TYPE
--      SYNTAX          DisplayString
--      MAX-ACCESS      read-write
--      STATUS          obsolete
--      DESCRIPTION
--              "This object specifies a list of untagged ports (on module #3)
--              that participate in this VLAN."
--      ::= { atiStkSwVlanConfigEntry 8 }

-- atiStkSwVlanTaggedPortListModule4  OBJECT-TYPE
--      SYNTAX          DisplayString
--      MAX-ACCESS      read-write
--      STATUS          obsolete
--      DESCRIPTION
--              "This object specifies a list of tagged ports (on module #4)
--              that participate in this VLAN."
--      ::= { atiStkSwVlanConfigEntry 9 }

-- atiStkSwVlanUntaggedPortListModule4  OBJECT-TYPE
--      SYNTAX          DisplayString
--      MAX-ACCESS      read-write
--      STATUS          obsolete
--      DESCRIPTION
--              "This object specifies a list of untagged ports (on module #4)
--              that participate in this VLAN."
--      ::= { atiStkSwVlanConfigEntry 10 }

-- atiStkSwVlanTaggedPortListModule5  OBJECT-TYPE
--      SYNTAX          DisplayString
--      MAX-ACCESS      read-write
--      STATUS          obsolete
--      DESCRIPTION
--              "This object specifies a list of tagged ports (on module #5)
--              that participate in this VLAN."
--      ::= { atiStkSwVlanConfigEntry 11 }

-- atiStkSwVlanUntaggedPortListModule5  OBJECT-TYPE
--      SYNTAX          DisplayString
--      MAX-ACCESS      read-write
--      STATUS          obsolete
--      DESCRIPTION
--              "This object specifies a list of untagged ports (on module #5)
--              that participate in this VLAN."
--      ::= { atiStkSwVlanConfigEntry 12 }

-- atiStkSwVlanTaggedPortListModule6  OBJECT-TYPE
--      SYNTAX          DisplayString
--      MAX-ACCESS      read-write
--      STATUS          obsolete
--      DESCRIPTION
--              "This object specifies a list of tagged ports (on module #6)
--              that participate in this VLAN."
--      ::= { atiStkSwVlanConfigEntry 13 }

-- atiStkSwVlanUntaggedPortListModule6  OBJECT-TYPE
--      SYNTAX          DisplayString
--      MAX-ACCESS      read-write
--      STATUS          obsolete
--      DESCRIPTION
--              "This object specifies a list of untagged ports (on module #6)
--              that participate in this VLAN."
--      ::= { atiStkSwVlanConfigEntry 14 }

-- atiStkSwVlanTaggedPortListModule7  OBJECT-TYPE
--      SYNTAX          DisplayString
--      MAX-ACCESS      read-write
--      STATUS          obsolete
--      DESCRIPTION
--              "This object specifies a list of tagged ports (on module #7)
--              that participate in this VLAN."
--      ::= { atiStkSwVlanConfigEntry 15 }

-- atiStkSwVlanUntaggedPortListModule7  OBJECT-TYPE
--      SYNTAX          DisplayString
--      MAX-ACCESS      read-write
--      STATUS          obsolete
--      DESCRIPTION
--              "This object specifies a list of untagged ports (on module #7)
--              that participate in this VLAN."
--      ::= { atiStkSwVlanConfigEntry 16 }

-- atiStkSwVlanTaggedPortListModule8  OBJECT-TYPE
--      SYNTAX          DisplayString
--      MAX-ACCESS      read-write
--      STATUS          obsolete
--      DESCRIPTION
--              "This object specifies a list of tagged ports (on module #8)
--              that participate in this VLAN."
--      ::= { atiStkSwVlanConfigEntry 17 }

-- atiStkSwVlanUntaggedPortListModule8  OBJECT-TYPE
--      SYNTAX          DisplayString
--      MAX-ACCESS      read-write
--      STATUS          obsolete
--      DESCRIPTION
--              "This object specifies a list of untagged ports (on module #8)
--              that participate in this VLAN."
--      ::= { atiStkSwVlanConfigEntry 18 }

-- atiStkSwVlanConfigEntryStatus  OBJECT-TYPE
--      SYNTAX          RowStatus
--      MAX-ACCESS      read-create
--      STATUS          current
--      DESCRIPTION
--              "The current status of this VLAN entry.
--              Please note the RowStatus implementation details.
--
--              VLANs can be created with a CreateandWait or CreateAndGo RowStatus.
--              When using CreateAndGo all fields must be valid.
--
--              VLANs created without a named defined have a NotReady Status.
--              NotReady accepts transitions to NotInService or Active.
--
--              A NotInService VLAN is not commited to hardware.
--              NotInService accepts transitions to Active or the Destroy action.
--              VLANs in any state other than active is considered non-persistent
--              and is not available after a reset.
--
--              VLANs in the active state are persistent.
--              An active VLAN cannot accept a transition to NotInService., i.e.
--              from persistent to non-persistent. It may be destroyed."
--      ::= { atiStkSwVlanConfigEntry 19 }

-- atiStkSwVlanActualUntaggedPortListModule1  OBJECT-TYPE
--      SYNTAX          DisplayString
--      MAX-ACCESS      read-only
--      STATUS          obsolete
--      DESCRIPTION
--              "This object specifies the list of actual untagged ports that are
--               participating in this VLAN.  The untagged port membership can be
--               temporarily changed by 802.1x Dynamic VLAN or Guest VLAN features.
--               The currently effective port membership information can be retrieved
--               from this object. "
--      ::= { atiStkSwVlanConfigEntry 20 }

atiStkSwVlanVlanType    OBJECT-TYPE
        SYNTAX          INTEGER {
                                static(0),
                                port-based (1),
                                mac-based (2),
                                dynamic (3),
                                protected (4)
                                }
        MAX-ACCESS      read-only
        STATUS          current
        DESCRIPTION
                "This object specifies the type of the Vlan."
        ::= { atiStkSwVlanConfigEntry 4 }

atiStkSwVlanTaggedPortList  OBJECT-TYPE
        SYNTAX          DisplayString
        MAX-ACCESS      read-write
        STATUS          current
        DESCRIPTION
                "This object specifies a list of tagged ports (on module #1)
                that participate in this VLAN."
        ::= { atiStkSwVlanConfigEntry 5 }

atiStkSwVlanUntaggedPortList  OBJECT-TYPE
        SYNTAX          DisplayString
        MAX-ACCESS      read-write
        STATUS          current
        DESCRIPTION
                "This object specifies a list of untagged ports (on module #1)
                that participate in this VLAN."
        ::= { atiStkSwVlanConfigEntry 6 }

atiStkSwVlanConfigEntryStatus   OBJECT-TYPE
        SYNTAX          INTEGER {
                                nonexistent (0),
                                active (1),
                                inactive (2),
                                destroy (3),
                                createAndGo (4),
                                createAndWait (5)
                                }
        MAX-ACCESS      read-write
        STATUS          current
        DESCRIPTION
                "The current status of this VLAN entry."
        ::= { atiStkSwVlanConfigEntry 7 }

--- atiStkSwVlanPortStatus  OBJECT-TYPE
---     SYNTAX          INTEGER {
---                             tagged (0),
---                             untagged (1)
---                             }
---     MAX-ACCESS      read-only
---     STATUS          current
---     DESCRIPTION
---             "This object specifies a whether the port, is tagged or untagged,
---             that participate in this VLAN."
---     ::= { atiStkSwVlanConfigEntry 6 }

-- atiStkSwVlanActualUntaggedPortList  OBJECT-TYPE
--      SYNTAX          DisplayString
--      MAX-ACCESS      read-only
--      STATUS          current
--      DESCRIPTION
--               "This object specifies the list of actual untagged ports that are
--               participating in this VLAN.  The untagged port membership can be
--               temporarily changed by 802.1x Dynamic VLAN or Guest VLAN features.
--               The currently effective port membership information can be retrieved
--               from this object. "
--      ::= { atiStkSwVlanConfigEntry 23 }


-- atiStkSwPort2VlanTable

atiStkSwPort2VlanTable  OBJECT-TYPE
        SYNTAX          SEQUENCE OF AtiStkSwPort2VlanEntry
        MAX-ACCESS      not-accessible
        STATUS          current
        DESCRIPTION
                "This tables contains a list of ports in the switch and their
                associated VLAN configuration information."
        ::= { atiStkSwVlanGroup 2 }

atiStkSwPort2VlanEntry  OBJECT-TYPE
        SYNTAX          AtiStkSwPort2VlanEntry
        MAX-ACCESS      not-accessible
        STATUS          current
        DESCRIPTION
                "This object specifies an entry in 'atiStkSwPort2VlanTable'
                that describes the VLAN information associated with a given
                module/port."
        INDEX           { atiStkSwPortIndex }
        ::= { atiStkSwPort2VlanTable 1 }

AtiStkSwPort2VlanEntry ::=
        SEQUENCE {
                atiStkSwPortIndex                       Integer32,
                atiStkSwPortPortId                      DisplayString,
                atiStkSwPortVlanId                      Integer32,
                atiStkSwPortVlanName                    DisplayString
                }

atiStkSwPortIndex       OBJECT-TYPE
        SYNTAX          Integer32 (0..255)
        MAX-ACCESS      read-only
        STATUS          current
        DESCRIPTION
                "The Index of the VLAN to which this port belongs."
        ::= { atiStkSwPort2VlanEntry 1 }

atiStkSwPortPortId      OBJECT-TYPE
        SYNTAX          DisplayString
        MAX-ACCESS      read-only
        STATUS          current
        DESCRIPTION
                "The ID of the VLAN to which this port belongs."
        ::= { atiStkSwPort2VlanEntry 2 }

atiStkSwPortVlanId      OBJECT-TYPE
        SYNTAX          Integer32
        MAX-ACCESS      read-only
        STATUS          current
        DESCRIPTION
                "The ID of the VLAN to which this port belongs."
        ::= { atiStkSwPort2VlanEntry 3 }

atiStkSwPortVlanName    OBJECT-TYPE
        SYNTAX          DisplayString (SIZE(0..19))
        MAX-ACCESS      read-only
        STATUS          current
        DESCRIPTION
                "The name of the VLAN to which this port belongs."
        ::= { atiStkSwPort2VlanEntry 4 }


-- atiStkSwMacAddr2VlanTable

atiStkSwMacAddr2VlanTable  OBJECT-TYPE
        SYNTAX          SEQUENCE OF AtiStkSwMacAddr2VlanEntry
        MAX-ACCESS      not-accessible
        STATUS          current
        DESCRIPTION
                "This table contains a list of MAC addresses (in the
                forwarding table of the switch) and the associated VLAN to
                which each MAC address belongs."
        ::= { atiStkSwVlanGroup 3 }

atiStkSwMacAddr2VlanEntry  OBJECT-TYPE
        SYNTAX          AtiStkSwMacAddr2VlanEntry
        MAX-ACCESS      not-accessible
        STATUS          current
        DESCRIPTION
                "This object specifies an entry in 'atiStkSwMacAddr2VlanTable'
                that associates a MAC address (in the forwarding table of the
                switch) with the VLAN to which the address belongs."
--      INDEX           { atiStkSwMacAddress, atiStkSwMacAddrVlanId }
        INDEX           { atiStkSwMacEntry }
        ::= { atiStkSwMacAddr2VlanTable 1 }

AtiStkSwMacAddr2VlanEntry ::=
        SEQUENCE {
                atiStkSwMacEntry                        Integer32,
                atiStkSwMacAddress                      MacAddress,
                atiStkSwMacAddrVlanId                   Integer32,
                atiStkSwMacAddrVlanName                 DisplayString,
--              atiStkSwMacAddrModuleId                 Integer32,
--              atiStkSwMacAddrPortId                   Integer32,
                atiStkSwMacAddrPortList                 DisplayString
                }

atiStkSwMacEntry        OBJECT-TYPE
        SYNTAX          Integer32  (0..255)
        MAX-ACCESS      read-only
        STATUS          current
        DESCRIPTION
                "All entries present in the table."
        ::= { atiStkSwMacAddr2VlanEntry 1 }

atiStkSwMacAddress      OBJECT-TYPE
        SYNTAX          MacAddress
        MAX-ACCESS      read-only
        STATUS          current
        DESCRIPTION
                "A MAC address from the forwarding table of the switch."
        ::= { atiStkSwMacAddr2VlanEntry 2 }

atiStkSwMacAddrVlanId   OBJECT-TYPE
        SYNTAX          Integer32 (1..4094)
        MAX-ACCESS      read-only
        STATUS          current
        DESCRIPTION
                "The ID of the VLAN to which this MAC address belongs."
        ::= { atiStkSwMacAddr2VlanEntry 3 }

atiStkSwMacAddrVlanName OBJECT-TYPE
        SYNTAX          DisplayString (SIZE(0..19))
        MAX-ACCESS      read-only
        STATUS          current
        DESCRIPTION
                "The name of the VLAN to which this MAC address belongs."
        ::= { atiStkSwMacAddr2VlanEntry 4 }

-- atiStkSwMacAddrModuleId  OBJECT-TYPE
--      SYNTAX          Integer32(1..8)
--      MAX-ACCESS      read-only
--      STATUS          current
--      DESCRIPTION
--              "The module ID on which this MAC address entry exists."
--      ::= { atiStkSwMacAddr2VlanEntry 5 }

-- atiStkSwMacAddrPortId OBJECT-TYPE
--      SYNTAX          Integer32
--      MAX-ACCESS      read-only
--      STATUS          current
--      DESCRIPTION
--              "The port ID (on the module specified by
--              'atiStkSwMacAddrModuleId') on which this MAC address entry
--              exists. This will display 0 for a multicast mac address.
--              Please check the PortList for the Multicast details.
--              Note: This will be eventually deprected approximately Dec'2004."
--      ::= { atiStkSwMacAddr2VlanEntry 6 }

atiStkSwMacAddrPortList OBJECT-TYPE
        SYNTAX          DisplayString (SIZE(0..255))
        MAX-ACCESS      read-only
        STATUS          current
        DESCRIPTION
                "The port List (on the module specified by
                'atiStkSwMacAddrModuleId') on which this MAC address entry
                exists. This is shown as U: Untagged Ports T: Tagged Ports."
        ::= { atiStkSwMacAddr2VlanEntry 7 }


-- Objects to control VLAN mode (user-configured vs pre-configured)

-- atiStkSwVlanMode  OBJECT-TYPE
--      SYNTAX          INTEGER {
--                              user-configured (1),
--                              multiple (2),
--                              multiple-802-1Q (3)
--                              }
--      MAX-ACCESS      read-write
--      STATUS          current
--      DESCRIPTION
--              "This object specifies the current VLAN mode. Setting
--              this object to 'user-configured (1)' allows the
--              manager to create, delete and modify VLANs using
--              'atiStkSwVlanConfigTable'.
--
--              Setting this object to 'multiple (2)' or
--              'multiple-802-1Q (3)'will result in the creation of
--              predefined VLANs. Setting these values requires that
--              the object 'atiStkSwVlanUplinkVlanPort' also be set
--              in the same SET request. Note that SET operations on
--              any object under 'atiStkSwVlanConfigTable' are not
--              allowed in these two modes."
--      ::=     { atiStkSwVlanGroup 4 }

-- atiStkSwVlanUplinkVlanPort  OBJECT-TYPE
--      SYNTAX          Integer32
--      MAX-ACCESS      read-write
--      STATUS          current
--      DESCRIPTION
--              "This object specifies the Uplink VLAN Port ID used
--              while creating pre-configured VLANs. This object can
--              be set to any valid Port ID present on the switch.
--
--              Note that a SET operation on the object
--              'atiStkSwVlanMode' to the value 'multiple (2)' or
--              'multiple-802-1Q (3)' should always be accompanied
--              by a SET operation on this object in the same SET
--              request.
--
--              By default this object is set to 0 when
--              'atiStkSwVlanMode' is set to 'user-configured (1)'."
--      ::=     { atiStkSwVlanGroup 5 }


atiStkSwGVRPConfig      OBJECT IDENTIFIER ::= { atiStkSwVlanGroup 6 }

-- The atiStkSwGVRPConfig

atiStkSwGVRPStatus      OBJECT-TYPE
        SYNTAX          INTEGER {
                                enabled (1),
                                disabled (0)
                                }
        MAX-ACCESS      read-write
        STATUS          current
        DESCRIPTION
                "Enabled/Disabled GVRP on a switch basis."
        ::= { atiStkSwGVRPConfig 1 }

atiStkSwGVRPGIPStatus   OBJECT-TYPE
        SYNTAX          INTEGER {
                                enabled (1),
                                disabled (0)
                                }
        MAX-ACCESS      read-write
        STATUS          current
        DESCRIPTION
                "Enabled/Disabled GARP Information Propagation (GIP) on a switch basis."
        ::= { atiStkSwGVRPConfig 2 }

atiStkSwGVRPJoinTimer   OBJECT-TYPE
        SYNTAX          Integer32 (10..60)
        MAX-ACCESS      read-write
        STATUS          current
        DESCRIPTION
                "Specifies the Join Timer in centi seconds, (1/100th of seconds), The default
                is 20 centi seconds."
        ::= { atiStkSwGVRPConfig 3 }

atiStkSwGVRPLeaveTimer  OBJECT-TYPE
        SYNTAX          Integer32 (30..180)
        MAX-ACCESS      read-write
        STATUS          current
        DESCRIPTION
                "Specifies the Leave Timer in centi seconds, (1/100th of seconds), The default
                is 60 centi seconds."
        ::= { atiStkSwGVRPConfig 4 }

atiStkSwGVRPLeaveAllTimer  OBJECT-TYPE
        SYNTAX          Integer32 (500..3000)
        MAX-ACCESS      read-write
        STATUS          current
        DESCRIPTION
                "Specifies the Leave All Timer in centi seconds, (1/100th of seconds), The
                default is 1000 centi seconds."
        ::= { atiStkSwGVRPConfig 5 }


-- The atiStkSwGVRPPortConfigTable

atiStkSwGVRPPortConfigTable  OBJECT-TYPE
        SYNTAX          SEQUENCE OF AtiStkSwGVRPPortConfigEntry
        MAX-ACCESS      not-accessible
        STATUS          current
        DESCRIPTION
                "This table is configuring the GVRP Vlan base on each port."
        ::= { atiStkSwVlanGroup 7 }

atiStkSwGVRPPortConfigEntry  OBJECT-TYPE
        SYNTAX          AtiStkSwGVRPPortConfigEntry
        MAX-ACCESS      not-accessible
        STATUS          current
        DESCRIPTION
                "This object specifies an entry in 'atiStkSwGVRPPortConfigTable'."
        INDEX           { atiStkSwGVRPPortConfigModuleId, atiStkSwGVRPPortConfigPortId }
        ::= { atiStkSwGVRPPortConfigTable 1 }

AtiStkSwGVRPPortConfigEntry::=
        SEQUENCE {
                atiStkSwGVRPPortConfigModuleId          Integer32,
                atiStkSwGVRPPortConfigPortId            Integer32,
                atiStkSwGVRPPortConfigStatus            INTEGER
                }

atiStkSwGVRPPortConfigModuleId  OBJECT-TYPE
        SYNTAX          Integer32 (1..8)
        MAX-ACCESS      read-only
        STATUS          current
        DESCRIPTION
                "An ID that indicate which module it refer to for stacking."
        ::= { atiStkSwGVRPPortConfigEntry 1 }

atiStkSwGVRPPortConfigPortId  OBJECT-TYPE
        SYNTAX          Integer32 (1..50)
        MAX-ACCESS      read-only
        STATUS          current
        DESCRIPTION
                "Port Index."
        ::= { atiStkSwGVRPPortConfigEntry 2 }

atiStkSwGVRPPortConfigStatus  OBJECT-TYPE
        SYNTAX          INTEGER {
                                none (1),
                                normal (0)
                                }
        MAX-ACCESS      read-write
        STATUS          current
        DESCRIPTION
                "Port Status for GVRP Vlan either Normal or Mode can be set."
        ::= { atiStkSwGVRPPortConfigEntry 3 }


-------------- atiStkSwGVRPCountersTable ----------------------------

atiStkSwGVRPCountersTable  OBJECT-TYPE
        SYNTAX          SEQUENCE OF AtiStkSwGVRPCountersEntry
        MAX-ACCESS      not-accessible
        STATUS          current
        DESCRIPTION
                "This table is configuring the GVRP Vlan base on each port."
        ::= { atiStkSwVlanGroup 8 }

atiStkSwGVRPCountersEntry  OBJECT-TYPE
        SYNTAX          AtiStkSwGVRPCountersEntry
        MAX-ACCESS      not-accessible
        STATUS          current
        DESCRIPTION
                "This object specifies an entry in 'atiStkSwGVRPCountersTable'."
        INDEX           { atiStkSwGVRPCountersModuleId }
        ::= { atiStkSwGVRPCountersTable 1 }

AtiStkSwGVRPCountersEntry::=
        SEQUENCE {
                atiStkSwGVRPCountersModuleId            Integer32,
                atiStkSwGVRPCountersGARPRxPkt           Counter32,
                atiStkSwGVRPCountersInvalidGARPRxPkt    Counter32,
                atiStkSwGVRPCountersGARPTxPkt           Counter32,
                atiStkSwGVRPCountersGARPTxDisabled      Counter32,
                atiStkSwGVRPCountersPortNotSending      Counter32,
                atiStkSwGVRPCountersGARPDisabled        Counter32,
                atiStkSwGVRPCountersPortNotListening    Counter32,
                atiStkSwGVRPCountersInvalidPort         Counter32,
                atiStkSwGVRPCountersInvalidProtocol     Counter32,
                atiStkSwGVRPCountersInvalidFormat       Counter32,
                atiStkSwGVRPCountersDatabaseFull        Counter32,
                atiStkSwGVRPCountersRxMsgLeaveAll       Counter32,
                atiStkSwGVRPCountersRxMsgJoinEmpty      Counter32,
                atiStkSwGVRPCountersRxMsgJoinIn         Counter32,
                atiStkSwGVRPCountersRxMsgLeaveEmpty     Counter32,
                atiStkSwGVRPCountersRxMsgLeaveIn        Counter32,
                atiStkSwGVRPCountersRxMsgEmpty          Counter32,
                atiStkSwGVRPCountersRxMsgBadMsg         Counter32,
                atiStkSwGVRPCountersRxMsgBadAttribute   Counter32,
                atiStkSwGVRPCountersTxMsgLeaveAll       Counter32,
                atiStkSwGVRPCountersTxMsgJoinEmpty      Counter32,
                atiStkSwGVRPCountersTxMsgJoinIn         Counter32,
                atiStkSwGVRPCountersTxMsgLeaveEmpty     Counter32,
                atiStkSwGVRPCountersTxMsgLeaveIn        Counter32,
                atiStkSwGVRPCountersTxMsgEmpty          Counter32
                }

atiStkSwGVRPCountersModuleId  OBJECT-TYPE
        SYNTAX          Integer32 (1..8)
        MAX-ACCESS      read-only
        STATUS          current
        DESCRIPTION
                "An ID that indicate which module it refer to for stacking."
        ::= { atiStkSwGVRPCountersEntry 1 }

atiStkSwGVRPCountersGARPRxPkt  OBJECT-TYPE
        SYNTAX          Counter32
        MAX-ACCESS      read-only
        STATUS          current
        DESCRIPTION
                ""
        ::= { atiStkSwGVRPCountersEntry 2 }

atiStkSwGVRPCountersInvalidGARPRxPkt  OBJECT-TYPE
        SYNTAX          Counter32
        MAX-ACCESS      read-only
        STATUS          current
        DESCRIPTION
                ""
        ::= { atiStkSwGVRPCountersEntry 3 }

atiStkSwGVRPCountersGARPTxPkt  OBJECT-TYPE
        SYNTAX          Counter32
        MAX-ACCESS      read-only
        STATUS          current
        DESCRIPTION
                ""
        ::= { atiStkSwGVRPCountersEntry 4 }

atiStkSwGVRPCountersGARPTxDisabled  OBJECT-TYPE
        SYNTAX          Counter32
        MAX-ACCESS      read-only
        STATUS          current
        DESCRIPTION
                ""
        ::= { atiStkSwGVRPCountersEntry 5 }

atiStkSwGVRPCountersPortNotSending  OBJECT-TYPE
        SYNTAX          Counter32
        MAX-ACCESS      read-only
        STATUS          current
        DESCRIPTION
                ""
        ::= { atiStkSwGVRPCountersEntry 6 }

atiStkSwGVRPCountersGARPDisabled  OBJECT-TYPE
        SYNTAX          Counter32
        MAX-ACCESS      read-only
        STATUS          current
        DESCRIPTION
                ""
        ::= { atiStkSwGVRPCountersEntry 7 }

atiStkSwGVRPCountersPortNotListening  OBJECT-TYPE
        SYNTAX          Counter32
        MAX-ACCESS      read-only
        STATUS          current
        DESCRIPTION
                ""
        ::= { atiStkSwGVRPCountersEntry 8 }

atiStkSwGVRPCountersInvalidPort  OBJECT-TYPE
        SYNTAX          Counter32
        MAX-ACCESS      read-only
        STATUS          current
        DESCRIPTION
                ""
        ::= { atiStkSwGVRPCountersEntry 9 }

atiStkSwGVRPCountersInvalidProtocol  OBJECT-TYPE
        SYNTAX          Counter32
        MAX-ACCESS      read-only
        STATUS          current
        DESCRIPTION
                ""
        ::= { atiStkSwGVRPCountersEntry 10 }

atiStkSwGVRPCountersInvalidFormat  OBJECT-TYPE
        SYNTAX          Counter32
        MAX-ACCESS      read-only
        STATUS          current
        DESCRIPTION
                ""
        ::= { atiStkSwGVRPCountersEntry 11 }

atiStkSwGVRPCountersDatabaseFull  OBJECT-TYPE
        SYNTAX          Counter32
        MAX-ACCESS      read-only
        STATUS          current
        DESCRIPTION
                ""
        ::= { atiStkSwGVRPCountersEntry 12 }

atiStkSwGVRPCountersRxMsgLeaveAll  OBJECT-TYPE
        SYNTAX          Counter32
        MAX-ACCESS      read-only
        STATUS          current
        DESCRIPTION
                ""
        ::= { atiStkSwGVRPCountersEntry 13 }

atiStkSwGVRPCountersRxMsgJoinEmpty  OBJECT-TYPE
        SYNTAX          Counter32
        MAX-ACCESS      read-only
        STATUS          current
        DESCRIPTION
                ""
        ::= { atiStkSwGVRPCountersEntry 14 }

atiStkSwGVRPCountersRxMsgJoinIn  OBJECT-TYPE
        SYNTAX          Counter32
        MAX-ACCESS      read-only
        STATUS          current
        DESCRIPTION
                ""
        ::= { atiStkSwGVRPCountersEntry 15 }

atiStkSwGVRPCountersRxMsgLeaveEmpty  OBJECT-TYPE
        SYNTAX          Counter32
        MAX-ACCESS      read-only
        STATUS          current
        DESCRIPTION
                ""
        ::= { atiStkSwGVRPCountersEntry 16 }

atiStkSwGVRPCountersRxMsgLeaveIn  OBJECT-TYPE
        SYNTAX          Counter32
        MAX-ACCESS      read-only
        STATUS          current
        DESCRIPTION
                ""
        ::= { atiStkSwGVRPCountersEntry 17 }

atiStkSwGVRPCountersRxMsgEmpty  OBJECT-TYPE
        SYNTAX          Counter32
        MAX-ACCESS      read-only
        STATUS          current
        DESCRIPTION
                ""
        ::= { atiStkSwGVRPCountersEntry 18 }

atiStkSwGVRPCountersRxMsgBadMsg  OBJECT-TYPE
        SYNTAX          Counter32
        MAX-ACCESS      read-only
        STATUS          current
        DESCRIPTION
                ""
        ::= { atiStkSwGVRPCountersEntry 19 }

atiStkSwGVRPCountersRxMsgBadAttribute  OBJECT-TYPE
        SYNTAX          Counter32
        MAX-ACCESS      read-only
        STATUS          current
        DESCRIPTION
                ""
        ::= { atiStkSwGVRPCountersEntry 20 }

atiStkSwGVRPCountersTxMsgLeaveAll  OBJECT-TYPE
        SYNTAX          Counter32
        MAX-ACCESS      read-only
        STATUS          current
        DESCRIPTION
                ""
        ::= { atiStkSwGVRPCountersEntry 21 }

atiStkSwGVRPCountersTxMsgJoinEmpty  OBJECT-TYPE
        SYNTAX          Counter32
        MAX-ACCESS      read-only
        STATUS          current
        DESCRIPTION
                ""
        ::= { atiStkSwGVRPCountersEntry 22 }

atiStkSwGVRPCountersTxMsgJoinIn  OBJECT-TYPE
        SYNTAX          Counter32
        MAX-ACCESS      read-only
        STATUS          current
        DESCRIPTION
                ""
        ::= { atiStkSwGVRPCountersEntry 23 }

atiStkSwGVRPCountersTxMsgLeaveEmpty  OBJECT-TYPE
        SYNTAX          Counter32
        MAX-ACCESS      read-only
        STATUS          current
        DESCRIPTION
                ""
        ::= { atiStkSwGVRPCountersEntry 24 }

atiStkSwGVRPCountersTxMsgLeaveIn  OBJECT-TYPE
        SYNTAX          Counter32
        MAX-ACCESS      read-only
        STATUS          current
        DESCRIPTION
                ""
        ::= { atiStkSwGVRPCountersEntry 25 }

atiStkSwGVRPCountersTxMsgEmpty  OBJECT-TYPE
        SYNTAX          Counter32
        MAX-ACCESS      read-only
        STATUS          current
        DESCRIPTION
                ""
        ::= { atiStkSwGVRPCountersEntry 26 }


-- The atiStkSwMacAddrGroup

-- Defined below atiStkSwStaticMacAddrTable     OBJECT IDENTIFIER ::= { atiStkSwMacAddrGroup 1 }


-- atiStkSwStaticMacAddrTable

atiStkSwStaticMacAddrTable  OBJECT-TYPE
        SYNTAX          SEQUENCE OF AtiStkSwStaticMacAddrEntry
        MAX-ACCESS      not-accessible
        STATUS          current
        DESCRIPTION
                "This table contains a list of static MAC address configured
                on the switch."
        ::= { atiStkSwMacAddrGroup 1 }

atiStkSwStaticMacAddrEntry  OBJECT-TYPE
        SYNTAX          AtiStkSwStaticMacAddrEntry
        MAX-ACCESS      not-accessible
        STATUS          current
        DESCRIPTION
                "This object is an entry in 'atiStkSwStaticMacAddrTable' that
                describes a static MAC address configured on a given module
                and port."
        INDEX   { atiStkSwStaticEntry }
        ::= { atiStkSwStaticMacAddrTable 1 }

AtiStkSwStaticMacAddrEntry ::=
        SEQUENCE {
                atiStkSwStaticEntry                     Integer32,
                atiStkSwStaticMacAddress                MacAddress,
                atiStkSwStaticMacAddrVlanId             Integer32,
                atiStkSwStaticMacAddrModuleId           Integer32,
                atiStkSwStaticMacAddrPortId             DisplayString,
                atiStkSwStaticMacAddrDstMacState        INTEGER,
                atiStkSwStaticMacAddrEntryStatus        INTEGER
                }

atiStkSwStaticEntry     OBJECT-TYPE
        SYNTAX          Integer32 (0..255)
        MAX-ACCESS      read-only
        STATUS          current
        DESCRIPTION
                "The Table Entry number in static MAC address entry table."
        ::= { atiStkSwStaticMacAddrEntry 1 }

atiStkSwStaticMacAddress  OBJECT-TYPE
        SYNTAX          MacAddress
        MAX-ACCESS      read-only
        STATUS          current
        DESCRIPTION
                "This object identifies the static MAC address of this entry."
        ::= { atiStkSwStaticMacAddrEntry 2 }

atiStkSwStaticMacAddrVlanId  OBJECT-TYPE
        SYNTAX          Integer32(1..4094)
        MAX-ACCESS      read-only
        STATUS          current
        DESCRIPTION
                "The ID of the VLAN on which this static MAC address entry is
                configured."
        ::= { atiStkSwStaticMacAddrEntry 3 }

atiStkSwStaticMacAddrModuleId  OBJECT-TYPE
        SYNTAX          Integer32(1..8)
        MAX-ACCESS      read-only
        STATUS          current
        DESCRIPTION
                "The module ID on which this static MAC address entry is
                configured."
        ::= { atiStkSwStaticMacAddrEntry 4 }

atiStkSwStaticMacAddrPortId  OBJECT-TYPE
        SYNTAX          DisplayString (SIZE(0..255))
        MAX-ACCESS      read-only
        STATUS          current
        DESCRIPTION
                "The port ID (on the module specified by
                'atiStkSwStaticMacAddrModuleId') on which this static MAC
                address entry is configured.
                Note: a) When defining a list this value must be 0.
                      b) This is on track to be deprecated approx. Dec'2004."
        ::= { atiStkSwStaticMacAddrEntry 5 }

atiStkSwStaticMacAddrDstMacState  OBJECT-TYPE
        SYNTAX          INTEGER {
                                discard (0),
                                forward (1)
                                }
        MAX-ACCESS      read-only
        STATUS          current
        DESCRIPTION
                "The current status of this static MAC address entry."
        ::= { atiStkSwStaticMacAddrEntry 6 }

atiStkSwStaticMacAddrEntryStatus  OBJECT-TYPE
        SYNTAX          INTEGER {
                                static (0),
                                dynamic (1)
                                }
        MAX-ACCESS      read-only
        STATUS          current
        DESCRIPTION
                "The current status of this static MAC address entry."
        ::= { atiStkSwStaticMacAddrEntry 7 }


-- The atiStkSwEthStatsGroup

-- atiStkSwEthModuleMonTable  OBJECT IDENTIFIER ::= { atiStkSwEthStatsGroup 1 }
-- atiStkSwEthModuleErrTable  OBJECT IDENTIFIER ::= { atiStkSwEthStatsGroup 2 }
-- atiStkSwEthPortMonTable    OBJECT IDENTIFIER ::= { atiStkSwEthStatsGroup 3 }
-- atiStkSwEthPortErrTable    OBJECT IDENTIFIER ::= { atiStkSwEthStatsGroup 4 }

-- atiStkSwEthModuleMonTable

atiStkSwEthModuleMonTable  OBJECT-TYPE
        SYNTAX          SEQUENCE OF AtiStkSwEthModuleMonEntry
        MAX-ACCESS      not-accessible
        STATUS          current
        DESCRIPTION
                "This table contains a list of modules and their associated
                ethernet statistics (measured on the module as a whole)."
        ::= { atiStkSwEthStatsGroup 1 }

atiStkSwEthModuleMonEntry  OBJECT-TYPE
        SYNTAX          AtiStkSwEthModuleMonEntry
        MAX-ACCESS      not-accessible
        STATUS          current
        DESCRIPTION
                "This object specifies an entry in 'atiStkSwEthModuleMonTable'
                that describes the ethernet statistics measured on a given
                module as a whole."
        INDEX           { atiStkSwEthModuleMonId }
        ::= { atiStkSwEthModuleMonTable 1 }

AtiStkSwEthModuleMonEntry ::=
        SEQUENCE {
                atiStkSwEthModuleMonId                  Integer32,
                atiStkSwEthModuleMonTxGoodFrames        Counter64,
                atiStkSwEthModuleMonRxGoodFrames        Counter64,
                atiStkSwEthModuleMonTxTotalBytes        Counter64,
                atiStkSwEthModuleMonTxBroadcastFrames   Counter64,
                atiStkSwEthModuleMonTxMulticastFrames   Counter64,
                atiStkSwEthModuleMonRxOverrunFrames     Counter64
                }

atiStkSwEthModuleMonId  OBJECT-TYPE
        SYNTAX          Integer32  (0..255)
        MAX-ACCESS      read-only
        STATUS          current
        DESCRIPTION
                "Index into atiStkSwEthModuleMonTable."
        ::= { atiStkSwEthModuleMonEntry 1 }

atiStkSwEthModuleMonTxGoodFrames  OBJECT-TYPE
        SYNTAX          Counter64
        MAX-ACCESS      read-only
        STATUS          current
        DESCRIPTION
                "The total number of good frames transmitted by this module."
        ::= { atiStkSwEthModuleMonEntry 2 }

atiStkSwEthModuleMonRxGoodFrames  OBJECT-TYPE
        SYNTAX          Counter64
        MAX-ACCESS      read-only
        STATUS          current
        DESCRIPTION
                "The total number of good frames received by this module."
        ::= { atiStkSwEthModuleMonEntry 3 }

atiStkSwEthModuleMonTxTotalBytes  OBJECT-TYPE
        SYNTAX          Counter64
        MAX-ACCESS      read-only
        STATUS          current
        DESCRIPTION
                "The total number of bytes transmitted by this module."
        ::= { atiStkSwEthModuleMonEntry 4 }

atiStkSwEthModuleMonTxBroadcastFrames  OBJECT-TYPE
        SYNTAX          Counter64
        MAX-ACCESS      read-only
        STATUS          current
        DESCRIPTION
                "The total number of broadcast frames transmitted from this
                module."
        ::= { atiStkSwEthModuleMonEntry 5 }

atiStkSwEthModuleMonTxMulticastFrames  OBJECT-TYPE
        SYNTAX          Counter64
        MAX-ACCESS      read-only
        STATUS          current
        DESCRIPTION
                "The total number of multicast frames transmitted from this
                module."
        ::= { atiStkSwEthModuleMonEntry 6 }

atiStkSwEthModuleMonRxOverrunFrames  OBJECT-TYPE
        SYNTAX          Counter64
        MAX-ACCESS      read-only
        STATUS          current
        DESCRIPTION
                "The total number of oversized frames received on this module."
        ::= { atiStkSwEthModuleMonEntry 7 }


-- atiStkSwEthModuleErrTable

atiStkSwEthModuleErrTable  OBJECT-TYPE
        SYNTAX          SEQUENCE OF AtiStkSwEthModuleErrEntry
        MAX-ACCESS      not-accessible
        STATUS          current
        DESCRIPTION
                "This table contains a list of modules and their associated
                ethernet error statistics (measured on the module as a whole)."
        ::= { atiStkSwEthStatsGroup 2 }

atiStkSwEthModuleErrEntry  OBJECT-TYPE
        SYNTAX          AtiStkSwEthModuleErrEntry
        MAX-ACCESS      not-accessible
        STATUS          current
        DESCRIPTION
                "This object specifies an entry in 'atiStkSwEthModuleErrTable'
                that describes the ethernet error statistics measured on a
                given module as a whole."
        INDEX           { atiStkSwEthModuleErrId }
        ::= { atiStkSwEthModuleErrTable 1 }

AtiStkSwEthModuleErrEntry ::=
        SEQUENCE {
                atiStkSwEthModuleErrId                  Integer32,
                atiStkSwEthModuleErrRxCRC               Counter64,
                atiStkSwEthModuleErrRxBadFrames         Counter64,
                atiStkSwEthModuleErrCollisions          Counter64
                }

atiStkSwEthModuleErrId  OBJECT-TYPE
        SYNTAX          Integer32  (0..255)
        MAX-ACCESS      read-only
        STATUS          current
        DESCRIPTION
                "Index into atiStkSwEthModuleErrTable."
        ::= { atiStkSwEthModuleErrEntry 1 }

atiStkSwEthModuleErrRxCRC  OBJECT-TYPE
        SYNTAX          Counter64
        MAX-ACCESS      read-only
        STATUS          current
        DESCRIPTION
                "The total number of CRC errors on packets received on this
                module."
        ::= { atiStkSwEthModuleErrEntry 2 }

atiStkSwEthModuleErrRxBadFrames  OBJECT-TYPE
        SYNTAX          Counter64
        MAX-ACCESS      read-only
        STATUS          current
        DESCRIPTION
                "The total number of bad frames received on this module."
        ::= { atiStkSwEthModuleErrEntry 3 }

atiStkSwEthModuleErrCollisions  OBJECT-TYPE
        SYNTAX          Counter64
        MAX-ACCESS      read-only
        STATUS          current
        DESCRIPTION
                "The number of times a collision was detected on this module."
        ::= { atiStkSwEthModuleErrEntry 4 }


-- atiStkSwEthPortMonTable

atiStkSwEthPortMonTable OBJECT-TYPE
        SYNTAX          SEQUENCE OF AtiStkSwEthPortMonEntry
        MAX-ACCESS      not-accessible
        STATUS          current
        DESCRIPTION
                "This table contains a list of ports and their associated
                ethernet statistics."
        ::= { atiStkSwEthStatsGroup 3 }

atiStkSwEthPortMonEntry OBJECT-TYPE
        SYNTAX          AtiStkSwEthPortMonEntry
        MAX-ACCESS      not-accessible
        STATUS          current
        DESCRIPTION
                "This object specifies an entry in 'atiStkSwEthPortMonTable'
                that describes the ethernet statistics measured on a given
                module/port."
        INDEX           { atiStkSwEthPortMonId }
        ::= { atiStkSwEthPortMonTable 1 }

AtiStkSwEthPortMonEntry ::=
        SEQUENCE {
                atiStkSwEthPortMonId                    Integer32,
                atiStkSwEthPortMonTxGoodFrames          Counter64,
                atiStkSwEthPortMonRxGoodFrames          Counter64,
                atiStkSwEthPortMonTxTotalBytes          Counter64,
                atiStkSwEthPortMonTxBroadcastFrames     Counter64,
                atiStkSwEthPortMonTxMulticastFrames     Counter64,
                atiStkSwEthPortMonRxOverrunFrames       Counter64
                }

atiStkSwEthPortMonId    OBJECT-TYPE
        SYNTAX          Integer32 (0..255)
        MAX-ACCESS      read-only
        STATUS          current
        DESCRIPTION
                "Index into atiStkSwEthPortMonTable."
        ::= { atiStkSwEthPortMonEntry 1 }

atiStkSwEthPortMonTxGoodFrames  OBJECT-TYPE
        SYNTAX          Counter64
        MAX-ACCESS      read-only
        STATUS          current
        DESCRIPTION
                "The total number of good frames transmitted by this port."
        ::= { atiStkSwEthPortMonEntry 2 }

atiStkSwEthPortMonRxGoodFrames  OBJECT-TYPE
        SYNTAX          Counter64
        MAX-ACCESS      read-only
        STATUS          current
        DESCRIPTION
                "The total number of good frames received by this port."
        ::= { atiStkSwEthPortMonEntry 3 }

atiStkSwEthPortMonTxTotalBytes  OBJECT-TYPE
        SYNTAX          Counter64
        MAX-ACCESS      read-only
        STATUS          current
        DESCRIPTION
                "The total number of bytes transmitted by this port."
        ::= { atiStkSwEthPortMonEntry 4 }

atiStkSwEthPortMonTxBroadcastFrames  OBJECT-TYPE
        SYNTAX          Counter64
        MAX-ACCESS      read-only
        STATUS          current
        DESCRIPTION
                "The total number of broadcast frames transmitted from this
                port."
        ::= { atiStkSwEthPortMonEntry 5 }

atiStkSwEthPortMonTxMulticastFrames  OBJECT-TYPE
        SYNTAX          Counter64
        MAX-ACCESS      read-only
        STATUS          current
        DESCRIPTION
                "The total number of broadcast frames transmitted from this
                port."
        ::= { atiStkSwEthPortMonEntry 6 }

atiStkSwEthPortMonRxOverrunFrames  OBJECT-TYPE
        SYNTAX          Counter64
        MAX-ACCESS      read-only
        STATUS          current
        DESCRIPTION
                "The total number of oversized frames received on this port."
        ::= { atiStkSwEthPortMonEntry 7 }


-- atiStkSwEthPortErrTable

atiStkSwEthPortErrTable OBJECT-TYPE
        SYNTAX          SEQUENCE OF AtiStkSwEthPortErrEntry
        MAX-ACCESS      not-accessible
        STATUS          current
        DESCRIPTION
                "This table contains a list of ports and their associated
                ethernet error statistics."
        ::= { atiStkSwEthStatsGroup 4 }

atiStkSwEthPortErrEntry OBJECT-TYPE
        SYNTAX          AtiStkSwEthPortErrEntry
        MAX-ACCESS      not-accessible
        STATUS          current
        DESCRIPTION
                "This object specifies an entry in atiStkSwEthPortErrTable
                that describes the ethernet error statistics measured on a
                given module/port."
        INDEX           { atiStkSwEthPortErrId }
        ::= { atiStkSwEthPortErrTable 1 }

AtiStkSwEthPortErrEntry ::=
        SEQUENCE {
                atiStkSwEthPortErrId                    Integer32,
                atiStkSwEthPortErrRxBadFrames           Counter64,
                atiStkSwEthPortErrCollisions            Counter64
                }

atiStkSwEthPortErrId    OBJECT-TYPE
        SYNTAX          Integer32 (0..255)
        MAX-ACCESS      read-only
        STATUS          current
        DESCRIPTION
                "Index into atiStkSwEthPortMonTable."
        ::= { atiStkSwEthPortErrEntry 1 }

atiStkSwEthPortErrRxBadFrames  OBJECT-TYPE
        SYNTAX          Counter64
        MAX-ACCESS      read-only
        STATUS          current
        DESCRIPTION
                "The total number of bad frames received on this port."
        ::= { atiStkSwEthPortErrEntry 2 }

atiStkSwEthPortErrCollisions  OBJECT-TYPE
        SYNTAX          Counter64
        MAX-ACCESS      read-only
        STATUS          current
        DESCRIPTION
                "The number of times a collision was detected on this port."
        ::= { atiStkSwEthPortErrEntry 3 }


-- The atiStkSwTrapsGroup

atiStkSwTrapsInfo       OBJECT IDENTIFIER ::= { atiStkSwTrapsGroup 0 }


--atiStkSwTrapsInfo

atiStkSwIntrusionDetectionTrap  NOTIFICATION-TYPE
        OBJECTS         { atiStkSwModuleId, atiStkSwPortId, atiStkSwIntruderAttackVlanId, atiStkSwIntruderAttackMacAddr }
        STATUS          current
        DESCRIPTION
                "This trap is sent out when an intrusion is detected on a port
                in the switch and the port security has been configured to
                send traps. It includes the mac address and vlan."
        ::= { atiStkSwTrapsInfo 1 }

atiStkSwSTPPortStateChangeTrap  NOTIFICATION-TYPE
        OBJECTS         { atiStkSwModuleId, atiStkSwPortId }
        STATUS          current
        DESCRIPTION
                "This trap is sent out when STP port state changes due to RSTP/MSTP topology changes
                in the switch.

                This trap is not applicable to 8300 series products."
        ::= { atiStkSwTrapsInfo 2 }

atiStkSwBPDUGuardIsTriggeredTrap  NOTIFICATION-TYPE
        OBJECTS         { atiStkSwModuleId, atiStkSwPortId }
        STATUS          current
        DESCRIPTION
                "This trap is sent out when a BPDU guard detects a spoofed BPDU
                entering the STP system thru the edge port. The BPDU guard will
                disable the port and notify the system administrator."
        ::= { atiStkSwTrapsInfo 3 }

atiStkSwPOEPowerExceedThresholdTrap  NOTIFICATION-TYPE
        OBJECTS         { atiStkSwModuleId }
        STATUS          current
        DESCRIPTION
                "This trap is sent out when there is a port power exceeding the threshold."
        ::= { atiStkSwTrapsInfo 4 }

atiStkSwPOEPowerNormalTrap  NOTIFICATION-TYPE
        OBJECTS         { atiStkSwModuleId }
        STATUS          current
        DESCRIPTION
                "This trap is sent out when there is a port power under threshold."
        ::= { atiStkSwTrapsInfo 5 }

atiStkSwFanStopSpinTrap NOTIFICATION-TYPE
        OBJECTS         { atiStkSwModuleId }
        STATUS          current
        DESCRIPTION
                "This trap is sent out when an error in the fan operation is
                detected in a module."
        ::= { atiStkSwTrapsInfo 6 }

atiStkSwFanStopSpinRecoveryTrap  NOTIFICATION-TYPE
        OBJECTS         { atiStkSwModuleId }
        STATUS          current
        DESCRIPTION
                "This trap is sent out when a fan become running Ok."
        ::= { atiStkSwTrapsInfo 7 }

atiStkSwTemperatureHighTrap  NOTIFICATION-TYPE
        OBJECTS         { atiStkSwModuleId }
        STATUS          obsolete
        DESCRIPTION
                "This trap is sent out when the temperature of a module
                becomes too high."
        ::= { atiStkSwTrapsInfo 8 }

atiStkSwTemperatureLowTrap  NOTIFICATION-TYPE
        OBJECTS         { atiStkSwModuleId }
        STATUS          obsolete
        DESCRIPTION
                "This trap is sent out when the temperature of a module
                becomes too low."
        ::= { atiStkSwTrapsInfo 9 }

atiStkSwTemperatureLimitClearTrap  NOTIFICATION-TYPE
        OBJECTS         { atiStkSwModuleId }
        STATUS          current
        DESCRIPTION
                "This trap is sent out when it is generated when system temperature
                 become normal."
        ::= { atiStkSwTrapsInfo 10 }

atiStkSwVolt5VLimitTrap NOTIFICATION-TYPE
        OBJECTS         { atiStkSwModuleId }
        STATUS          current
        DESCRIPTION
                "This trap is sent out when there is a port 5v power exceeds limit."
        ::= { atiStkSwTrapsInfo 11 }

atiStkSwVolt5VLimitClearTrap  NOTIFICATION-TYPE
        OBJECTS         { atiStkSwModuleId }
        STATUS          current
        DESCRIPTION
                "This trap is sent out when there is a port 5v power returns normal."
        ::= { atiStkSwTrapsInfo 12 }

atiStkSwVoltVCCLimitTrap  NOTIFICATION-TYPE
        OBJECTS         { atiStkSwModuleId }
        STATUS          current
        DESCRIPTION
                "This trap is sent out when there is a port VCC power exceeds limit."
        ::= { atiStkSwTrapsInfo 13 }

atiStkSwVoltVCCLimitClearTrap  NOTIFICATION-TYPE
        OBJECTS         { atiStkSwModuleId }
        STATUS          current
        DESCRIPTION
                "This trap is sent out when there is a port VCC power returns normal."
        ::= { atiStkSwTrapsInfo 14 }

atiStkSwVoltVCCPLimitTrap  NOTIFICATION-TYPE
        OBJECTS         { atiStkSwModuleId }
        STATUS          current
        DESCRIPTION
                "This trap is sent out when there is a port VCCP power exceeds limit."
        ::= { atiStkSwTrapsInfo 15 }

atiStkSwVoltVCCPLimitClearTrap  NOTIFICATION-TYPE
        OBJECTS         { atiStkSwModuleId }
        STATUS          current
        DESCRIPTION
                "This trap is sent out when there is a port VCCP power returns normal."
        ::= { atiStkSwTrapsInfo 16 }

atiStkSwVolt2HalfVLimitTrap  NOTIFICATION-TYPE
        OBJECTS         { atiStkSwModuleId }
        STATUS          current
        DESCRIPTION
                "This trap is sent out when there is a port 2.5v power exceeds limit."
        ::= { atiStkSwTrapsInfo 17 }

atiStkSwVolt2HalfVLimitClearTrap  NOTIFICATION-TYPE
        OBJECTS         { atiStkSwModuleId }
        STATUS          current
        DESCRIPTION
                "This trap is sent out when there is a port 2.5v power returns normal."
        ::= { atiStkSwTrapsInfo 18 }

atiStkSwVolt12VLimitTrap  NOTIFICATION-TYPE
        OBJECTS         { atiStkSwModuleId }
        STATUS          current
        DESCRIPTION
                "This trap is sent out when there is a port 12v power exceeds limit."
        ::= { atiStkSwTrapsInfo 19 }

atiStkSwVolt12VLimitClearTrap  NOTIFICATION-TYPE
        OBJECTS         { atiStkSwModuleId }
        STATUS          current
        DESCRIPTION
                "This trap is sent out when there is a port 12v power returns normal."
        ::= { atiStkSwTrapsInfo 20 }

atiStkSwPOEErrorStateTrap  NOTIFICATION-TYPE
        OBJECTS         { atiStkSwModuleId }
        STATUS          current
        DESCRIPTION
                "This trap is sent out when there is a POE port abnormal."
        ::= { atiStkSwTrapsInfo 21 }

atiStkSwPOEPortResetTrap  NOTIFICATION-TYPE
        OBJECTS         { atiStkSwModuleId }
        STATUS          current
        DESCRIPTION
                "This trap is sent out when there is a POE port reset."
        ::= { atiStkSwTrapsInfo 22 }

atiStkSwSysRPSStateChangedTrap  NOTIFICATION-TYPE
        OBJECTS         { atiStkSwModuleId }
        STATUS          current
        DESCRIPTION
                "This trap is sent out when the RPS(redundant Power Supply)
                changes state in the switch.

                This trap is not applicable to 8300 series products."
        ::= { atiStkSwTrapsInfo 23 }

atiStkSwBPDUGuardFilterTriggeredTrap  NOTIFICATION-TYPE
        OBJECTS         { atiStkSwModuleId, atiStkSwPortId }
        STATUS          current
        DESCRIPTION
                "This trap is sent out when a BPDU filter detects a spoofed BPDU
                entering the STP system thru the edge port. The BPDU filter will
                block the port and notify the system administrator."
        ::= { atiStkSwTrapsInfo 24 }

atiStkSwLoopProtectDetectedLoopBlockedTrap  NOTIFICATION-TYPE
        OBJECTS         { atiStkSwModuleId, atiStkSwPortId, atiStkSwVlanId, atiStkSwPortLoopProtectConfigAction }
        STATUS          current
        DESCRIPTION
                "Generated when Loop Protection feature blocks a interface with a loop."
        ::= { atiStkSwTrapsInfo 25 }

atiStkSwLoopProtectRecoverLoopBlockedTrap  NOTIFICATION-TYPE
        OBJECTS         { atiStkSwModuleId, atiStkSwPortId, atiStkSwVlanId, atiStkSwPortLoopProtectConfigAction }
        STATUS          current
        DESCRIPTION
                "Generated when Loop Protection feature restores a blocked interface back to normal operation."
        ::= { atiStkSwTrapsInfo 26 }

atiStkSwLoopProtectDetectedByLDFTrap  NOTIFICATION-TYPE
        OBJECTS         { atiStkSwModuleId, atiStkSwPortId, atiStkSwVlanId, atiStkSwRxLDFModuleId, atiStkSwRxLDFPortId, atiStkSwRxLDFVlanId }
        STATUS          current
        DESCRIPTION
                "Generated when Loop Protection feature detects a loop by Loop Detection method."
        ::= { atiStkSwTrapsInfo 27 }


-- The atiStkSwQoSGroup
-- This group is not applicable to 8300 series products.

-- atiStkSwQoSGroupNumberOfQueues  OBJECT-TYPE
--      SYNTAX          Integer32
--      MAX-ACCESS      read-only
--      STATUS          current
--      DESCRIPTION
--              "This object gives a count of the CoS Queues supported by the chipset.
--
--              This object is not applicable to 8300 series products."
--      ::= { atiStkSwQoSGroup 1 }

-- atiStkSwQoSGroupSchedulingMode  OBJECT-TYPE
--      SYNTAX          INTEGER {
--                              strict-priority (1),
--                              weighted-round-robin (2)
--                              }
--      MAX-ACCESS      read-write
--      STATUS          current
--      DESCRIPTION
--              "This object allows to configure QOS scheduling mode.
--
--              This object is not applicable to 8300 series products."
--      ::= { atiStkSwQoSGroup 2 }

-- The atiStkSwQoSGroupCoSToQueueTable

-- atiStkSwQoSGroupCoSToQueueTable  OBJECT-TYPE
--      SYNTAX          SEQUENCE OF AtiStkSwQoSGroupCoSToQueueEntry
--      MAX-ACCESS      not-accessible
--      STATUS          current
--      DESCRIPTION
--              "This table object allows to configure queue for each CoS (Class fo Service) priority.
--
--              This table object is not applicable to 8300 series products."
--      ::= { atiStkSwQoSGroup 3 }

-- atiStkSwQoSGroupCoSToQueueEntry  OBJECT-TYPE
--      SYNTAX          AtiStkSwQoSGroupCoSToQueueEntry
--      MAX-ACCESS      not-accessible
--      STATUS          current
--      DESCRIPTION
--              "This object specifies an entry in 'atiStkSwQoSGroupCoSToQueueTable'
--              that describes the mapping of CoS priorities to corresponding Cos Queues."
--      INDEX           { atiStkSwQoSGroupCoSPriority }
--      ::= { atiStkSwQoSGroupCoSToQueueTable 1 }

-- AtiStkSwQoSGroupCoSToQueueEntry ::=
--      SEQUENCE {
--              atiStkSwQoSGroupCoSPriority             INTEGER,
--              atiStkSwQoSGroupCoSQueue                INTEGER
--              }

-- atiStkSwQoSGroupCoSPriority  OBJECT-TYPE
--      SYNTAX          INTEGER {
--                              cos-priority-0 (1),
--                              cos-priority-1 (2),
--                              cos-priority-2 (3),
--                              cos-priority-3 (4),
--                              cos-priority-4 (5),
--                              cos-priority-5 (6),
--                              cos-priority-6 (7),
--                              cos-priority-7 (8)
--                              }
--      MAX-ACCESS      read-only
--      STATUS          current
--      DESCRIPTION
--              "This object specifies the CoS priority."
--      ::= { atiStkSwQoSGroupCoSToQueueEntry 1 }

-- atiStkSwQoSGroupCoSQueue  OBJECT-TYPE
--      SYNTAX          INTEGER {
--                              egress-queue-0 (1),
--                              egress-queue-1 (2),
--                              egress-queue-2 (3),
--                              egress-queue-3 (4),
--                              egress-queue-4 (5),
--                              egress-queue-5 (6),
--                              egress-queue-6 (7),
--                              egress-queue-7 (8)
--                              }
--      MAX-ACCESS      read-write
--      STATUS          current
--      DESCRIPTION
--              "This object specifies the queue for each CoS priority. Please
--              note that the 94xx supports 8 levels, however, the 85xx
--              supports 4 levels."
--      ::= { atiStkSwQoSGroupCoSToQueueEntry 2 }

-- The atiStkSwQoSGroupQueueToWeightTable

-- atiStkSwQoSGroupQueueToWeightTable  OBJECT-TYPE
--      SYNTAX          SEQUENCE OF AtiStkSwQoSGroupQueueToWeightEntry
--      MAX-ACCESS      not-accessible
--      STATUS          current
--      DESCRIPTION
--              "This object allows to configure weight for each CoS (Class fo Service) queue .
--
--              This object table is not applicable to 8300 series products."
--      ::= { atiStkSwQoSGroup 4 }

-- atiStkSwQoSGroupQueueToWeightEntry  OBJECT-TYPE
--      SYNTAX          AtiStkSwQoSGroupQueueToWeightEntry
--      MAX-ACCESS      not-accessible
--      STATUS          current
--      DESCRIPTION
--              "This object specifies an entry in 'atiStkSwQoSGroupQueueToWeightTable'
--              that describes the mapping of CoS queues to corresponding weights."
--      INDEX           { atiStkSwQoSGroupQueue }
--      ::= { atiStkSwQoSGroupQueueToWeightTable 1 }

-- AtiStkSwQoSGroupQueueToWeightEntry ::=
--      SEQUENCE {
--              atiStkSwQoSGroupQueue                   INTEGER,
--              atiStkSwQoSGroupQueueWeight             INTEGER
--              }

-- atiStkSwQoSGroupQueue  OBJECT-TYPE
--      SYNTAX          INTEGER {
--                              egress-queue-0 (1),
--                              egress-queue-1 (2),
--                              egress-queue-2 (3),
--                              egress-queue-3 (4),
--                              egress-queue-4 (5),
--                              egress-queue-5 (6),
--                              egress-queue-6 (7),
--                              egress-queue-7 (8)
--                              }
--      MAX-ACCESS      read-only
--      STATUS          current
--      DESCRIPTION
--              "This object specifies the queue. Please note that the 94xx
--              supports 8 levels, however, the 85xx supports 4 levels."
--      ::= { atiStkSwQoSGroupQueueToWeightEntry 1 }

-- atiStkSwQoSGroupQueueWeight  OBJECT-TYPE
--      SYNTAX          INTEGER (0..256)
--      MAX-ACCESS      read-write
--      STATUS          current
--      DESCRIPTION
--              "This object specifies the queue weight for each queue."
--      ::= { atiStkSwQoSGroupQueueToWeightEntry 2 }

-- atiStkSwQosFlowGrpTable --

-- atiStkSwQosFlowGrpTable  OBJECT-TYPE
--      SYNTAX          SEQUENCE OF AtiStkSwQosFlowGrpEntry
--      MAX-ACCESS      not-accessible
--      STATUS          current
--      DESCRIPTION
--              "This table contains a list of modules present in the switch
--              stack and their associated hardware information."
--      ::= { atiStkSwQoSGroup 5 }

-- atiStkSwQosFlowGrpEntry  OBJECT-TYPE
--      SYNTAX          AtiStkSwQosFlowGrpEntry
--      MAX-ACCESS      not-accessible
--      STATUS          current
--      DESCRIPTION
--              "This object specifies an entry in 'atiStkSwQosFlowGrpTable'
--              that describes the hardware informaton for a module present in
--              the switch stack."
--      INDEX           { atiStkSwQosFlowGrpModuleId, atiStkSwQosFlowGrpId }
--      ::= { atiStkSwQosFlowGrpTable 1 }

-- AtiStkSwQosFlowGrpEntry ::=
--      SEQUENCE {
--              atiStkSwQosFlowGrpModuleId              Integer32,
--              atiStkSwQosFlowGrpId                    Integer32,
--              atiStkSwQosFlowGrpDescription           DisplayString,
--              atiStkSwQosFlowGrpDSCPValue             DisplayString,
--              atiStkSwQosFlowGrpPriority              DisplayString,
--              atiStkSwQosFlowGrpRemarkPriority        INTEGER,
--              atiStkSwQosFlowGrpTos                   DisplayString,
--              atiStkSwQosFlowGrpTosToPriority         INTEGER,
--              atiStkSwQosFlowGrpPriorityToTos         INTEGER,
--              atiStkSwQosFlowGrpClassifierList        DisplayString,
--              atiStkSwQosFlowGrpRowStatus             RowStatus
--              }

-- atiStkSwQosFlowGrpModuleId  OBJECT-TYPE
--      SYNTAX          Integer32 (1..8)
--      MAX-ACCESS      read-only
--      STATUS          current
--      DESCRIPTION
--              "An index that corresponds to which module the data is retrieved
--              with stacking capability."
--      ::= { atiStkSwQosFlowGrpEntry 1 }

-- atiStkSwQosFlowGrpId   OBJECT-TYPE
--      SYNTAX          Integer32 (0..1023)
--      MAX-ACCESS      read-only
--      STATUS          current
--      DESCRIPTION
--              "An index that corresponds to specific Flow Group base on Id within
--              Flow Group list."
--      ::= { atiStkSwQosFlowGrpEntry 2 }

-- atiStkSwQosFlowGrpDescription  OBJECT-TYPE
--      SYNTAX          DisplayString (SIZE(1..255))
--      MAX-ACCESS      read-write
--      STATUS          current
--      DESCRIPTION
--              "The description of a specific Flow Group."
--      ::= { atiStkSwQosFlowGrpEntry 3 }

-- atiStkSwQosFlowGrpDSCPValue  OBJECT-TYPE
--      SYNTAX          DisplayString (SIZE(0..4))
--      MAX-ACCESS      read-write
--      STATUS          current
--      DESCRIPTION
--              ""
--      ::= { atiStkSwQosFlowGrpEntry 4 }

-- atiStkSwQosFlowGrpPriority  OBJECT-TYPE
--      SYNTAX          DisplayString (SIZE(0..2))
--      MAX-ACCESS      read-write
--      STATUS          current
--      DESCRIPTION
--              ""
--      ::= { atiStkSwQosFlowGrpEntry 5 }

-- atiStkSwQosFlowGrpRemarkPriority  OBJECT-TYPE
--      SYNTAX          INTEGER {
--                              yes (1),
--                              no (2)
--                              }
--      MAX-ACCESS      read-write
--      STATUS          current
--      DESCRIPTION
--              ""
--      ::= { atiStkSwQosFlowGrpEntry 6 }

-- atiStkSwQosFlowGrpTos  OBJECT-TYPE
--      SYNTAX          DisplayString (SIZE(0..2))
--      MAX-ACCESS      read-write
--      STATUS          current
--      DESCRIPTION
--              ""
--      ::= { atiStkSwQosFlowGrpEntry 7 }

-- atiStkSwQosFlowGrpTosToPriority  OBJECT-TYPE
--      SYNTAX          INTEGER {
--                              yes (1),
--                              no (2)
--                              }
--      MAX-ACCESS      read-write
--      STATUS          current
--      DESCRIPTION
--              ""
--      ::= { atiStkSwQosFlowGrpEntry 8 }

-- atiStkSwQosFlowGrpPriorityToTos  OBJECT-TYPE
--      SYNTAX          INTEGER {
--                              yes (1),
--                              no (2)
--                              }
--      MAX-ACCESS      read-write
--      STATUS          current
--      DESCRIPTION
--              ""
--      ::= { atiStkSwQosFlowGrpEntry 9 }

-- atiStkSwQosFlowGrpClassifierList  OBJECT-TYPE
--      SYNTAX          DisplayString
--      MAX-ACCESS      read-write
--      STATUS          current
--      DESCRIPTION
--              ""
--      ::= { atiStkSwQosFlowGrpEntry 10 }

-- atiStkSwQosFlowGrpRowStatus  OBJECT-TYPE
--      SYNTAX          RowStatus
--      MAX-ACCESS      read-create
--      STATUS          current
--      DESCRIPTION
--              ""
--      ::= { atiStkSwQosFlowGrpEntry 11 }

-- atiStkSwQosTrafficClassTable

-- atiStkSwQosTrafficClassTable  OBJECT-TYPE
--      SYNTAX          SEQUENCE OF AtiStkSwQosTrafficClassEntry
--      MAX-ACCESS      not-accessible
--      STATUS          current
--      DESCRIPTION
--              "This table contains a list of modules present in the switch
--              stack and their associated hardware information."
--      ::= { atiStkSwQoSGroup 6 }

-- atiStkSwQosTrafficClassEntry  OBJECT-TYPE
--      SYNTAX          AtiStkSwQosTrafficClassEntry
--      MAX-ACCESS      not-accessible
--      STATUS          current
--      DESCRIPTION
--              "This object specifies an entry in 'atiStkSwQosTrafficClassTable'
--              that describes the hardware informaton for a module present in
--              the switch stack."
--      INDEX           { atiStkSwQosTrafficClassModuleId, atiStkSwQosTrafficClassId }
--      ::= { atiStkSwQosTrafficClassTable 1 }

-- AtiStkSwQosTrafficClassEntry ::=
--      SEQUENCE {
--              atiStkSwQosTrafficClassModuleId                 Integer32,
--              atiStkSwQosTrafficClassId                       Integer32,
--              atiStkSwQosTrafficClassDescription              DisplayString,
--              atiStkSwQosTrafficClassExceedAction             INTEGER,
--              atiStkSwQosTrafficClassExceedRemarkValue        Integer32,
--              atiStkSwQosTrafficClassDSCPValue                DisplayString,
--              atiStkSwQosTrafficClassMaxBandwidth             DisplayString,
--              atiStkSwQosTrafficClassBurstSize                DisplayString,
--              atiStkSwQosTrafficClassPriority                 DisplayString,
--              atiStkSwQosTrafficClassRemarkPriority           INTEGER,
--              atiStkSwQosTrafficClassToS                      DisplayString,
--              atiStkSwQosTrafficClassMoveToSToPriority        INTEGER,
--              atiStkSwQosTrafficClassMovePriorityToToS        INTEGER,
--              atiStkSwQosTrafficClassFlowGroupList            DisplayString,
--              atiStkSwQosTrafficClassRowStatus                RowStatus
--              }

-- atiStkSwQosTrafficClassModuleId  OBJECT-TYPE
--      SYNTAX          Integer32 (1..8)
--      MAX-ACCESS      read-only
--      STATUS          current
--      DESCRIPTION
--              ""
--      ::= { atiStkSwQosTrafficClassEntry 1 }

-- atiStkSwQosTrafficClassId  OBJECT-TYPE
--      SYNTAX          Integer32 (0..511)
--      MAX-ACCESS      read-only
--     STATUS          current
--      DESCRIPTION
--              ""
--      ::= { atiStkSwQosTrafficClassEntry 2 }

-- atiStkSwQosTrafficClassDescription  OBJECT-TYPE
--      SYNTAX          DisplayString (SIZE(1..255))
--      MAX-ACCESS      read-write
--      STATUS          current
--      DESCRIPTION
--              ""
--      ::= { atiStkSwQosTrafficClassEntry 3 }

-- atiStkSwQosTrafficClassExceedAction  OBJECT-TYPE
--      SYNTAX          INTEGER {
--                              drop (1),
--                              remark (2)
--                              }
--      MAX-ACCESS      read-write
--      STATUS          current
--      DESCRIPTION
--              ""
--      ::= { atiStkSwQosTrafficClassEntry 4 }

-- atiStkSwQosTrafficClassExceedRemarkValue  OBJECT-TYPE
--      SYNTAX          Integer32 (0..63)
--      MAX-ACCESS      read-write
--      STATUS          current
--      DESCRIPTION
--              ""
--      ::= { atiStkSwQosTrafficClassEntry 5 }

-- atiStkSwQosTrafficClassDSCPValue  OBJECT-TYPE
--      SYNTAX          DisplayString (SIZE(0..4))
--      MAX-ACCESS      read-write
--      STATUS          current
--      DESCRIPTION     ""
--      ::= { atiStkSwQosTrafficClassEntry 6 }

-- atiStkSwQosTrafficClassMaxBandwidth  OBJECT-TYPE
--      SYNTAX          DisplayString (SIZE(0..8))
--      MAX-ACCESS      read-write
--      STATUS          current
--      DESCRIPTION
--              ""
--      ::= { atiStkSwQosTrafficClassEntry 7 }

-- atiStkSwQosTrafficClassBurstSize  OBJECT-TYPE
--      SYNTAX          DisplayString (SIZE(0..8))
--      MAX-ACCESS      read-write
--      STATUS          current
--      DESCRIPTION
--              ""
--      ::= { atiStkSwQosTrafficClassEntry 8 }

-- atiStkSwQosTrafficClassPriority  OBJECT-TYPE
--      SYNTAX          DisplayString (SIZE(0..4))
--      MAX-ACCESS      read-write
--      STATUS          current
--      DESCRIPTION
--              ""
--      ::= { atiStkSwQosTrafficClassEntry 9 }

-- atiStkSwQosTrafficClassRemarkPriority  OBJECT-TYPE
--      SYNTAX          INTEGER {
--                              yes (1),
--                              no (2)
--                              }
--      MAX-ACCESS      read-write
--      STATUS          current
--      DESCRIPTION
--              ""
--      ::= { atiStkSwQosTrafficClassEntry 10 }

-- atiStkSwQosTrafficClassToS  OBJECT-TYPE
--      SYNTAX          DisplayString (SIZE(0..4))
--      MAX-ACCESS      read-write
--      STATUS          current
--      DESCRIPTION     ""
--      ::= { atiStkSwQosTrafficClassEntry 11 }

-- atiStkSwQosTrafficClassMoveToSToPriority   OBJECT-TYPE
--      SYNTAX          INTEGER {
--                              yes (1),
--                              no (2)
--                              }
--      MAX-ACCESS      read-write
--      STATUS          current
--      DESCRIPTION     ""
--      ::= { atiStkSwQosTrafficClassEntry 12 }

-- atiStkSwQosTrafficClassMovePriorityToToS  OBJECT-TYPE
--      SYNTAX          INTEGER {
--                              yes (1),
--                              no (2)
--                              }
--      MAX-ACCESS      read-write
--      STATUS          current
--      DESCRIPTION     ""
--      ::= { atiStkSwQosTrafficClassEntry 13 }

-- atiStkSwQosTrafficClassFlowGroupList OBJECT-TYPE
--      SYNTAX          DisplayString
--      MAX-ACCESS      read-write
--      STATUS          current
--      DESCRIPTION     ""
--      ::= { atiStkSwQosTrafficClassEntry 14 }

-- atiStkSwQosTrafficClassRowStatus  OBJECT-TYPE
--      SYNTAX          RowStatus
--      MAX-ACCESS      read-create
--      STATUS          current
--      DESCRIPTION     ""
--      ::= { atiStkSwQosTrafficClassEntry 15 }

-- atiStkSwQosPolicyTable

-- atiStkSwQosPolicyTable OBJECT-TYPE
--      SYNTAX          SEQUENCE OF AtiStkSwQosPolicyEntry
--      MAX-ACCESS      not-accessible
--      STATUS          current
--      DESCRIPTION
--              "This table contains a list of modules present in the switch
--              stack and their associated hardware information."
--      ::= { atiStkSwQoSGroup 7 }

-- atiStkSwQosPolicyEntry OBJECT-TYPE
--      SYNTAX          AtiStkSwQosPolicyEntry
--      MAX-ACCESS      not-accessible
--      STATUS          current
--      DESCRIPTION
--              "This object specifies an entry in 'atiStkSwQosPolicyTable'
--              that describes the hardware informaton for a module present in
--              the switch stack."
--      INDEX           { atiStkSwQosPolicyModuleId, atiStkSwQosPolicyId }
--      ::= { atiStkSwQosPolicyTable 1 }

-- AtiStkSwQosPolicyEntry ::=
--      SEQUENCE {
--              atiStkSwQosPolicyModuleId               Integer32,
--              atiStkSwQosPolicyId                     Integer32,
--              atiStkSwQosPolicyDescription            DisplayString,
--              atiStkSwQosPolicyRemarkDSCP             INTEGER,
--              atiStkSwQosPolicyDSCPValue              DisplayString,
--              atiStkSwQosPolicyToS                    DisplayString,
--              atiStkSwQosPolicyMoveToSToPriority      INTEGER,
--              atiStkSwQosPolicyMovePriorityToToS      INTEGER,
--              atiStkSwQosPolicySendToMirrorPort       INTEGER,
--              atiStkSwQosPolicyTrafficClassList       DisplayString,
--              atiStkSwQosPolicyRedirectPort           DisplayString,
--              atiStkSwQosPolicyIngressPortList        DisplayString,
--              atiStkSwQosPolicyEgressPortList         DisplayString,
--              atiStkSwQosPolicyRowStatus              RowStatus
--              }

-- atiStkSwQosPolicyModuleId  OBJECT-TYPE
--      SYNTAX          Integer32 (1..8)
--      MAX-ACCESS      read-only
--      STATUS          current
--      DESCRIPTION
--              ""
--      ::= { atiStkSwQosPolicyEntry 1 }

-- atiStkSwQosPolicyId  OBJECT-TYPE
--      SYNTAX          Integer32 (0..511)
--      MAX-ACCESS      read-only
--      STATUS          current
--      DESCRIPTION
--              ""
--      ::= { atiStkSwQosPolicyEntry 2 }

-- atiStkSwQosPolicyDescription  OBJECT-TYPE
--      SYNTAX          DisplayString (SIZE(1..255))
--      MAX-ACCESS      read-write
--      STATUS          current
--      DESCRIPTION
--              ""
--      ::= { atiStkSwQosPolicyEntry 3 }

-- atiStkSwQosPolicyRemarkDSCP  OBJECT-TYPE
--      SYNTAX          INTEGER {
--                              all (1),
--                              none (2)
--                              }
--      MAX-ACCESS      read-write
--      STATUS          current
--      DESCRIPTION
--              ""
--      ::= { atiStkSwQosPolicyEntry 4 }

-- atiStkSwQosPolicyDSCPValue  OBJECT-TYPE
--      SYNTAX          DisplayString (SIZE(0..4))
--      MAX-ACCESS      read-write
--      STATUS          current
--      DESCRIPTION     ""
--      ::= { atiStkSwQosPolicyEntry 5 }

-- atiStkSwQosPolicyToS   OBJECT-TYPE
--      SYNTAX          DisplayString (SIZE(0..4))
--      MAX-ACCESS      read-write
--      STATUS          current
--      DESCRIPTION     ""
--      ::= { atiStkSwQosPolicyEntry 6 }

-- atiStkSwQosPolicyMoveToSToPriority  OBJECT-TYPE
--      SYNTAX          INTEGER {
--                              yes (1),
--                              no (2)
--                              }
--      MAX-ACCESS      read-write
--      STATUS          current
--      DESCRIPTION     ""
--      ::= { atiStkSwQosPolicyEntry 7 }

-- atiStkSwQosPolicyMovePriorityToToS   OBJECT-TYPE
--      SYNTAX          INTEGER {
--                              yes (1),
--                              no (2)
--                              }
--      MAX-ACCESS      read-write
--      STATUS          current
--      DESCRIPTION     ""
--      ::= { atiStkSwQosPolicyEntry 8 }

-- atiStkSwQosPolicySendToMirrorPort  OBJECT-TYPE
--      SYNTAX          INTEGER {
--                              yes (1),
--                              no (2)
--                              }
--      MAX-ACCESS      read-write
--      STATUS          current
--      DESCRIPTION     ""
--      ::= { atiStkSwQosPolicyEntry 9 }

-- atiStkSwQosPolicyTrafficClassList  OBJECT-TYPE
--      SYNTAX          DisplayString
--      MAX-ACCESS      read-write
--      STATUS          current
--      DESCRIPTION     ""
--      ::= { atiStkSwQosPolicyEntry 10 }

-- atiStkSwQosPolicyRedirectPort  OBJECT-TYPE
--      SYNTAX          DisplayString
--      MAX-ACCESS      read-write
--      STATUS          current
--      DESCRIPTION     ""
--      ::= { atiStkSwQosPolicyEntry 11 }

-- atiStkSwQosPolicyIngressPortList  OBJECT-TYPE
--      SYNTAX          DisplayString
--      MAX-ACCESS      read-write
--      STATUS          current
--      DESCRIPTION     ""
--      ::= { atiStkSwQosPolicyEntry 12 }

-- atiStkSwQosPolicyEgressPortList  OBJECT-TYPE
--      SYNTAX          DisplayString
--      MAX-ACCESS      read-write
--      STATUS          current
--      DESCRIPTION     ""
--      ::= { atiStkSwQosPolicyEntry 13 }

-- atiStkSwQosPolicyRowStatus  OBJECT-TYPE
--      SYNTAX          RowStatus
--      MAX-ACCESS      read-create
--      STATUS          current
--      DESCRIPTION     ""
--      ::= { atiStkSwQosPolicyEntry 14 }

-- atiStkSwQosGroupPortCosPriorityTable

-- atiStkSwQoSGroupPortCoSPriorityTable OBJECT-TYPE
--      SYNTAX          SEQUENCE OF AtiStkSwQoSGroupPortCoSPriorityEntry
--      MAX-ACCESS      not-accessible
--      STATUS          current
--      DESCRIPTION
--              "This table object allows to configure port priority for each CoS (Class of Service)
--              priority. This table object is not applicable to 8300 series products."
--      ::= { atiStkSwQoSGroup 8 }

-- atiStkSwQoSGroupPortCoSPriorityEntry OBJECT-TYPE
--      SYNTAX          AtiStkSwQoSGroupPortCoSPriorityEntry
--      MAX-ACCESS      not-accessible
--      STATUS          current
--      DESCRIPTION
--              "This object specifies an entry in 'atiStkSwQoSGroupPortCoSPriorityTable'
--              it defines the CoS priority for each port, and the priority defined for a
--              port should override priority already in the priority tagged packet
--              received by the switch."
--      INDEX           { atiStkSwQoSGroupPortCoSPriorityModuleId,
--                      atiStkSwQoSGroupPortCoSPriorityPortId }
--      ::= { atiStkSwQoSGroupPortCoSPriorityTable 1 }

-- AtiStkSwQoSGroupPortCoSPriorityEntry ::=
--      SEQUENCE {
--              atiStkSwQoSGroupPortCoSPriorityModuleId         Integer32,
--              atiStkSwQoSGroupPortCoSPriorityPortId           Integer32,
--              atiStkSwQoSGroupPortCoSPriorityPriority         Integer32,
--              atiStkSwQoSGroupPortCoSPriorityOverridePriority INTEGER
--              }

-- atiStkSwQoSGroupPortCoSPriorityModuleId  OBJECT-TYPE
--      SYNTAX          Integer32 (1..8)
--      MAX-ACCESS      read-only
--      STATUS          current
--      DESCRIPTION
--              "This object specifies the Module Id of the table."
--      ::= { atiStkSwQoSGroupPortCoSPriorityEntry 1 }

-- atiStkSwQoSGroupPortCoSPriorityPortId  OBJECT-TYPE
--      SYNTAX          Integer32
--      MAX-ACCESS      read-only
--      STATUS          current
--      DESCRIPTION
--              "This object specifies the IfIndex of the table."
--      ::= { atiStkSwQoSGroupPortCoSPriorityEntry 2 }

-- atiStkSwQoSGroupPortCoSPriorityPriority  OBJECT-TYPE
--      SYNTAX          Integer32 (0..7)
--      MAX-ACCESS      read-write
--      STATUS          current
--      DESCRIPTION
--              "This object specifies the priority for each port CoS priority."
--      ::= { atiStkSwQoSGroupPortCoSPriorityEntry 3 }

-- atiStkSwQoSGroupPortCoSPriorityOverridePriority  OBJECT-TYPE
--      SYNTAX          INTEGER {
--                              yes (1),
--                              no (2)
--                              }
--      MAX-ACCESS      read-write
--      STATUS          current
--      DESCRIPTION
--              "This object specifies the override priority for each port CoS priority."
--      ::= { atiStkSwQoSGroupPortCoSPriorityEntry 4 }

--
-- atiStkSwQoSGroup Tables
--

atiStkSwQosStatusTable OBJECT-TYPE
        SYNTAX      SEQUENCE OF AtiStkSwQosStatusEntry
        MAX-ACCESS  not-accessible
        STATUS      current
        DESCRIPTION
                "atiStkSwQosStatusTable"
        ::= { atiStkSwQoSGroup 1 }

atiStkSwQosStatusEntry OBJECT-TYPE
        SYNTAX      AtiStkSwQosStatusEntry
        MAX-ACCESS  not-accessible
        STATUS      current
        DESCRIPTION
                " "
        INDEX { atiStkSwQosStatusPortId }
        ::= { atiStkSwQosStatusTable 1 }

AtiStkSwQosStatusEntry ::=
        SEQUENCE {
                atiStkSwQosStatusPortId          Integer32,
                atiStkSwQosStatusStatus          INTEGER
        }

atiStkSwQosStatusPortId OBJECT-TYPE
        SYNTAX      Integer32 (0..255)
        MAX-ACCESS  read-only
        STATUS      current
        DESCRIPTION
                "Index into atiStkSwQosStatusTable"
        ::= { atiStkSwQosStatusEntry 1 }

atiStkSwQosStatusStatus OBJECT-TYPE
        SYNTAX      INTEGER {
                                        disable (0),
                                        enable  (1)
                                }
        MAX-ACCESS  read-write
        STATUS      current
        DESCRIPTION
                " "
        ::= { atiStkSwQosStatusEntry 2 }

atiStkSwQosInterfaceDetailsTable OBJECT-TYPE
        SYNTAX      SEQUENCE OF AtiStkSwQosInterfaceDetailsEntry
        MAX-ACCESS  not-accessible
        STATUS      current
        DESCRIPTION
                "atiStkSwQosInterfaceDetailsTable"
        ::= { atiStkSwQoSGroup 2 }

atiStkSwQosInterfaceDetailsEntry OBJECT-TYPE
        SYNTAX      AtiStkSwQosInterfaceDetailsEntry
        MAX-ACCESS  not-accessible
        STATUS      current
        DESCRIPTION
                "atiStkSwQosInterfaceDetailsEntry"
        INDEX { atiStkSwQosInterfaceDetailsPortId }
        ::= { atiStkSwQosInterfaceDetailsTable 1 }

AtiStkSwQosInterfaceDetailsEntry ::=
        SEQUENCE {
                atiStkSwQosInterfaceDetailsPortId                       Integer32,
                atiStkSwQosInterfaceDetailsDefaultQueue                 Integer32,
                atiStkSwQosInterfaceDetailsTrust                        INTEGER,
                atiStkSwQosInterfaceDetailsSetCOS                       DisplayString,
                atiStkSwQosInterfaceDetailsSetDSCP                      DisplayString,
                atiStkSwQosInterfaceDetailsSchedularAndQueueWeightList  DisplayString
                }

atiStkSwQosInterfaceDetailsPortId  OBJECT-TYPE
        SYNTAX          Integer32 (0..255)
        MAX-ACCESS      read-only
        STATUS          current
        DESCRIPTION
                "Index into atiStkSwQosInterfaceDetailsPortId"
        ::= { atiStkSwQosInterfaceDetailsEntry 1 }

atiStkSwQosInterfaceDetailsDefaultQueue  OBJECT-TYPE
        SYNTAX          Integer32
        MAX-ACCESS      read-write
        STATUS          current
        DESCRIPTION
                "atiStkSwQosInterfaceDetailsDefaultQueue"
        ::= { atiStkSwQosInterfaceDetailsEntry 2 }

atiStkSwQosInterfaceDetailsTrust  OBJECT-TYPE
        SYNTAX          INTEGER {
                                none (0),
                                cos (1),
                                dscp (2)
                                }
        MAX-ACCESS      read-write
        STATUS          current
        DESCRIPTION
                "atiStkSwQosInterfaceDetailsDefaultQueue"
        ::= { atiStkSwQosInterfaceDetailsEntry 3 }

atiStkSwQosInterfaceDetailsSetCOS  OBJECT-TYPE
        SYNTAX          DisplayString (SIZE(1..255))
        MAX-ACCESS      read-write
        STATUS          current
        DESCRIPTION
                "atiStkSwQosInterfaceDetailsMarkOrRemark"
        ::= { atiStkSwQosInterfaceDetailsEntry 4 }

atiStkSwQosInterfaceDetailsSetDSCP  OBJECT-TYPE
        SYNTAX          DisplayString (SIZE(1..255))
        MAX-ACCESS      read-write
        STATUS          current
        DESCRIPTION
                "atiStkSwQosInterfaceDetailsMarkOrRemark"
        ::= { atiStkSwQosInterfaceDetailsEntry 5 }

atiStkSwQosInterfaceDetailsSchedularAndQueueWeightList  OBJECT-TYPE
        SYNTAX          DisplayString (SIZE(1..255))
        MAX-ACCESS      read-write
        STATUS          current
        DESCRIPTION
                "atiStkSwQosInterfaceDetailsSchedularAndQueueWeightList"
        ::= { atiStkSwQosInterfaceDetailsEntry 6 }


atiStkSwQosCosQueueMapTable  OBJECT-TYPE
        SYNTAX          SEQUENCE OF AtiStkSwQosCosQueueMapEntry
        MAX-ACCESS      not-accessible
        STATUS          current
        DESCRIPTION
                "atiStkSwQosCosQueueMapTable"
        ::= { atiStkSwQoSGroup 3 }

atiStkSwQosCosQueueMapEntry  OBJECT-TYPE
        SYNTAX          AtiStkSwQosCosQueueMapEntry
        MAX-ACCESS      not-accessible
        STATUS          current
        DESCRIPTION
                "atiStkSwQosCosQueueMapEntry"
        INDEX           { atiStkSwQosCosQueueMapPortId }
        ::= { atiStkSwQosCosQueueMapTable 1 }

AtiStkSwQosCosQueueMapEntry ::=
        SEQUENCE {
                atiStkSwQosCosQueueMapPortId            Integer32,
                atiStkSwQosCosQueueMapCos0Queue         Integer32,
                atiStkSwQosCosQueueMapCos1Queue         Integer32,
                atiStkSwQosCosQueueMapCos2Queue         Integer32,
                atiStkSwQosCosQueueMapCos3Queue         Integer32,
                atiStkSwQosCosQueueMapCos4Queue         Integer32,
                atiStkSwQosCosQueueMapCos5Queue         Integer32,
                atiStkSwQosCosQueueMapCos6Queue         Integer32,
                atiStkSwQosCosQueueMapCos7Queue         Integer32,
                atiStkSwQosCosQueueMapDefaultMap        INTEGER
                }

atiStkSwQosCosQueueMapPortId  OBJECT-TYPE
        SYNTAX          Integer32 (0..255)
        MAX-ACCESS      read-only
        STATUS          current
        DESCRIPTION
                "Index into atiStkSwQosCosQueueMapTable"
        ::= { atiStkSwQosCosQueueMapEntry 1 }

atiStkSwQosCosQueueMapCos0Queue  OBJECT-TYPE
        SYNTAX          Integer32 (0..7)
        MAX-ACCESS      read-write
        STATUS          current
        DESCRIPTION
                "atiStkSwQosCosQueueMapCos0Queue"
        ::= { atiStkSwQosCosQueueMapEntry 2 }

atiStkSwQosCosQueueMapCos1Queue  OBJECT-TYPE
        SYNTAX          Integer32 (0..7)
        MAX-ACCESS      read-write
        STATUS          current
        DESCRIPTION
                "atiStkSwQosCosQueueMapCos1Queue"
        ::= { atiStkSwQosCosQueueMapEntry 3 }

atiStkSwQosCosQueueMapCos2Queue  OBJECT-TYPE
        SYNTAX          Integer32 (0..7)
        MAX-ACCESS      read-write
        STATUS          current
        DESCRIPTION
                "atiStkSwQosCosQueueMapCos2Queue"
        ::= { atiStkSwQosCosQueueMapEntry 4 }

atiStkSwQosCosQueueMapCos3Queue  OBJECT-TYPE
        SYNTAX          Integer32 (0..7)
        MAX-ACCESS      read-write
        STATUS          current
        DESCRIPTION
                "atiStkSwQosCosQueueMapCos3Queue"
        ::= { atiStkSwQosCosQueueMapEntry 5 }

atiStkSwQosCosQueueMapCos4Queue  OBJECT-TYPE
        SYNTAX          Integer32 (0..7)
        MAX-ACCESS      read-write
        STATUS          current
        DESCRIPTION
                "atiStkSwQosCosQueueMapCos4Queue"
        ::= { atiStkSwQosCosQueueMapEntry 6 }

atiStkSwQosCosQueueMapCos5Queue  OBJECT-TYPE
        SYNTAX          Integer32 (0..7)
        MAX-ACCESS      read-write
        STATUS          current
        DESCRIPTION
                "atiStkSwQosCosQueueMapCos5Queue"
        ::= { atiStkSwQosCosQueueMapEntry 7 }

atiStkSwQosCosQueueMapCos6Queue  OBJECT-TYPE
        SYNTAX          Integer32 (0..7)
        MAX-ACCESS      read-write
        STATUS          current
        DESCRIPTION
                "atiStkSwQosCosQueueMapCos6Queue"
        ::= { atiStkSwQosCosQueueMapEntry 8 }

atiStkSwQosCosQueueMapCos7Queue  OBJECT-TYPE
        SYNTAX          Integer32 (0..7)
        MAX-ACCESS      read-write
        STATUS          current
        DESCRIPTION
                "atiStkSwQosCosQueueMapCos7Queue"
        ::= { atiStkSwQosCosQueueMapEntry 9 }

atiStkSwQosCosQueueMapDefaultMap  OBJECT-TYPE
        SYNTAX          INTEGER {
                                no (0),
                                yes (1)
                                }
        MAX-ACCESS      read-write
        STATUS          current
        DESCRIPTION
                "atiStkSwQosCosQueueMapDefaultQueue"
        ::= { atiStkSwQosCosQueueMapEntry 10 }

atiStkSwQosDscpQueueMapTable  OBJECT-TYPE
        SYNTAX          SEQUENCE OF AtiStkSwQosDscpQueueMapEntry
        MAX-ACCESS      not-accessible
        STATUS          current
        DESCRIPTION
                "atiStkSwQosDscpQueueMapTable"
        ::= { atiStkSwQoSGroup 4 }

atiStkSwQosDscpQueueMapEntry  OBJECT-TYPE
        SYNTAX          AtiStkSwQosDscpQueueMapEntry
        MAX-ACCESS      not-accessible
        STATUS          current
        DESCRIPTION
                "atiStkSwQosDscpQueueMapEntry"
        INDEX           { atiStkSwQosDscpQueueMapPortId }
        ::= { atiStkSwQosDscpQueueMapTable 1 }

AtiStkSwQosDscpQueueMapEntry ::=
        SEQUENCE {
                atiStkSwQosDscpQueueMapPortId           Integer32,
                atiStkSwQosDscpQueueMapQueue0           DisplayString,
                atiStkSwQosDscpQueueMapQueue1           DisplayString,
                atiStkSwQosDscpQueueMapQueue2           DisplayString,
                atiStkSwQosDscpQueueMapQueue3           DisplayString,
                atiStkSwQosDscpQueueMapQueue4           DisplayString,
                atiStkSwQosDscpQueueMapQueue5           DisplayString,
                atiStkSwQosDscpQueueMapQueue6           DisplayString,
                atiStkSwQosDscpQueueMapQueue7           DisplayString,
                atiStkSwQosDscpQueueMapDefaultMap       INTEGER
                }

atiStkSwQosDscpQueueMapPortId  OBJECT-TYPE
        SYNTAX          Integer32 (0..255)
        MAX-ACCESS      read-only
        STATUS          current
        DESCRIPTION
                "Index into atiStkSwQosDscpQueueMapTable"
        ::= { atiStkSwQosDscpQueueMapEntry 1 }

atiStkSwQosDscpQueueMapQueue0  OBJECT-TYPE
        SYNTAX          DisplayString (SIZE(1..255))
        MAX-ACCESS      read-write
        STATUS          current
        DESCRIPTION
                "atiStkSwQosDscpQueueMapQueue0"
        ::= { atiStkSwQosDscpQueueMapEntry 2 }

atiStkSwQosDscpQueueMapQueue1  OBJECT-TYPE
        SYNTAX          DisplayString (SIZE(1..255))
        MAX-ACCESS      read-write
        STATUS          current
        DESCRIPTION
                "atiStkSwQosDscpQueueMapQueue1"
        ::= { atiStkSwQosDscpQueueMapEntry 3 }

atiStkSwQosDscpQueueMapQueue2  OBJECT-TYPE
        SYNTAX          DisplayString (SIZE(1..255))
        MAX-ACCESS      read-write
        STATUS          current
        DESCRIPTION
                "atiStkSwQosDscpQueueMapQueue2"
        ::= { atiStkSwQosDscpQueueMapEntry 4 }

atiStkSwQosDscpQueueMapQueue3  OBJECT-TYPE
        SYNTAX          DisplayString (SIZE(1..255))
        MAX-ACCESS      read-write
        STATUS          current
        DESCRIPTION
                "atiStkSwQosDscpQueueMapQueue3"
        ::= { atiStkSwQosDscpQueueMapEntry 5 }

atiStkSwQosDscpQueueMapQueue4  OBJECT-TYPE
        SYNTAX          DisplayString (SIZE(1..255))
        MAX-ACCESS      read-write
        STATUS          current
        DESCRIPTION
                "atiStkSwQosDscpQueueMapQueue4"
        ::= { atiStkSwQosDscpQueueMapEntry 6 }

atiStkSwQosDscpQueueMapQueue5  OBJECT-TYPE
        SYNTAX          DisplayString (SIZE(1..255))
        MAX-ACCESS      read-write
        STATUS          current
        DESCRIPTION
                "atiStkSwQosDscpQueueMapQueue5"
        ::= { atiStkSwQosDscpQueueMapEntry 7 }

atiStkSwQosDscpQueueMapQueue6  OBJECT-TYPE
        SYNTAX          DisplayString (SIZE(1..255))
        MAX-ACCESS      read-write
        STATUS          current
        DESCRIPTION
                "atiStkSwQosDscpQueueMapQueue6"
        ::= { atiStkSwQosDscpQueueMapEntry 8 }

atiStkSwQosDscpQueueMapQueue7  OBJECT-TYPE
        SYNTAX          DisplayString (SIZE(1..255))
        MAX-ACCESS      read-write
        STATUS          current
        DESCRIPTION
                "atiStkSwQosDscpQueueMapQueue7"
        ::= { atiStkSwQosDscpQueueMapEntry 9 }

atiStkSwQosDscpQueueMapDefaultMap  OBJECT-TYPE
        SYNTAX          INTEGER {
                                no (0),
                                yes (1)
                                }
        MAX-ACCESS      read-write
        STATUS          current
        DESCRIPTION
                "atiStkSwQosDscpQueueMapDefaultQueue"
        ::= { atiStkSwQosDscpQueueMapEntry 10 }


-- atiStkSwStaticTrunkTable

atiStkSwStaticTrunkTable  OBJECT-TYPE
        SYNTAX          SEQUENCE OF AtiStkSwStaticTrunkEntry
        MAX-ACCESS      not-accessible
        STATUS          current
        DESCRIPTION
                "This table contains a list of static trunk configuration present
                 in the switch stack."
        ::= { atiStkSwTrunkGroup 1 }

atiStkSwStaticTrunkEntry  OBJECT-TYPE
        SYNTAX          AtiStkSwStaticTrunkEntry
        MAX-ACCESS      not-accessible
        STATUS          current
        DESCRIPTION
                "This object specifies an entry in 'atiStkSwStaticTrunkTable'
                that describes the static trunk informaton for a module present in
                the switch stack."
        INDEX           { atiStkSwStaticTrunkId }
        ::= { atiStkSwStaticTrunkTable 1 }

AtiStkSwStaticTrunkEntry ::=
        SEQUENCE {
                atiStkSwStaticTrunkId                   Integer32,
                atiStkSwStaticTrunkName                 DisplayString,
                atiStkSwStaticTrunkMethod               INTEGER,
                atiStkSwStaticTrunkPortList             DisplayString,
                atiStkSwStaticTrunkStatus               INTEGER
                }

atiStkSwStaticTrunkId   OBJECT-TYPE
        SYNTAX          Integer32 (0..255)
        MAX-ACCESS      read-only
        STATUS          current
        DESCRIPTION     "An identifier for a trunk."
        ::= { atiStkSwStaticTrunkEntry 1 }

atiStkSwStaticTrunkName OBJECT-TYPE
        SYNTAX          DisplayString (SIZE(1..16))
        MAX-ACCESS      read-only
        STATUS          current
        DESCRIPTION     "Name of a trunk, once the entry has created, it
                         cannot be changed."
        ::= { atiStkSwStaticTrunkEntry 2 }

atiStkSwStaticTrunkMethod  OBJECT-TYPE
        SYNTAX          INTEGER {
                                srcMac (1),
                                dstMac (2),
                                src-dstMac (3),
                                srcIp (4),
                                dstIp (5),
                                src-dstIp (6)
                                }
        MAX-ACCESS      read-write
        STATUS          current
        DESCRIPTION     "Trunk distribution mode."
        ::= { atiStkSwStaticTrunkEntry 3 }

atiStkSwStaticTrunkPortList  OBJECT-TYPE
        SYNTAX          DisplayString
        MAX-ACCESS      read-only
        STATUS          current
        DESCRIPTION     "A list of ports that used as a trunk port."
        ::= { atiStkSwStaticTrunkEntry 4 }

atiStkSwStaticTrunkStatus  OBJECT-TYPE
        SYNTAX          INTEGER {
                                up (1),
                                down (2)
                                }
        MAX-ACCESS      read-only
        STATUS          current
        DESCRIPTION     "The status of the trunk, either up or down."
        ::= { atiStkSwStaticTrunkEntry 5 }

-- atiStkSwACLConfigTable

 atiStkSwACLConfigTable OBJECT-TYPE
        SYNTAX          SEQUENCE OF AtiStkSwACLConfigEntry
        MAX-ACCESS      not-accessible
        STATUS          current
        DESCRIPTION
                "This table contains a Access Control List (ACL) in the
                switch and their associated attributes."
        ::= { atiStkSwACLGroup 1 }

 atiStkSwACLConfigEntry OBJECT-TYPE
        SYNTAX          AtiStkSwACLConfigEntry
        MAX-ACCESS      not-accessible
        STATUS          current
        DESCRIPTION
                "This object specifies an entry in 'atiStkSwACLConfigTable'
                that describes the ACL in the switch."
        INDEX           { atiStkSwACLId }
        ::= { atiStkSwACLConfigTable 1 }

AtiStkSwACLConfigEntry ::=
        SEQUENCE {
                atiStkSwACLId                           Integer32,
                atiStkSwACLShowId                       Integer32,
                atiStkSwACLStatus                       INTEGER,
                atiStkSwACLAction                       INTEGER,
                atiStkSwACLTrafficType                  INTEGER,
                atiStkSwACLSrcType                      INTEGER,
                atiStkSwACLSrcAddr                      IpAddress,
                atiStkSwACLSrcMask                      IpAddress,
                atiStkSwACLDestType                     INTEGER,
                atiStkSwACLDestAddr                     IpAddress,
                atiStkSwACLDestMask                     IpAddress,
                atiStkSwACLVlanId                       Integer32,
                atiStkSwACLProtocol                     Integer32,
                atiStkSwACLICMPType                     Integer32,
                atiStkSwACLUDPTCPSrcPort                INTEGER,
                atiStkSwACLSrcPort1                     Integer32,
                atiStkSwACLSrcPort2                     Integer32,
                atiStkSwACLUDPTCPDestPort               INTEGER,
                atiStkSwACLDestPort1                    Integer32,
                atiStkSwACLDestPort2                    Integer32
                }

atiStkSwACLId           OBJECT-TYPE
        SYNTAX          Integer32 (1..700)
        MAX-ACCESS      read-only
        STATUS          current
        DESCRIPTION
                "This object specifies the ID of the ACL table."
        ::= { atiStkSwACLConfigEntry 1 }

atiStkSwACLShowId       OBJECT-TYPE
        SYNTAX          Integer32 (3000..3699)
        MAX-ACCESS      read-only
        STATUS          current
        DESCRIPTION
                "This object specifies the ID of the ACL table."
        ::= { atiStkSwACLConfigEntry 2 }

atiStkSwACLStatus       OBJECT-TYPE
        SYNTAX          INTEGER {
                                create (1),
                                delete (2)
                                }
        MAX-ACCESS      read-write
        STATUS          current
        DESCRIPTION
                "This object specifies the status of the ACL ID."
        ::= { atiStkSwACLConfigEntry 3 }

atiStkSwACLAction       OBJECT-TYPE
        SYNTAX          INTEGER {
                                deny (1),
                                permit (2),
                                copytomirror (3)
                                }
        MAX-ACCESS      read-write
        STATUS          current
        DESCRIPTION
                "The action of the ACL entry either deny or permit or copy to mirror."
        ::= { atiStkSwACLConfigEntry 4 }

atiStkSwACLTrafficType  OBJECT-TYPE
        SYNTAX          INTEGER {
                                icmp (1),
                                ip (2),
                                proto (3),
                                tcp (4),
                                udp (5)
                                }
        MAX-ACCESS      read-write
        STATUS          current
        DESCRIPTION
                "The Object specifies the traffic type of the ACL."
        ::= { atiStkSwACLConfigEntry 5 }

atiStkSwACLSrcType      OBJECT-TYPE
        SYNTAX          INTEGER {
                                any (1),
                                host (2),
                                ip (3)
                                }
        MAX-ACCESS      read-write
        STATUS          current
        DESCRIPTION
                "The Object specifies the source type of the ACL."
        ::= { atiStkSwACLConfigEntry 6 }

atiStkSwACLSrcAddr      OBJECT-TYPE
        SYNTAX          IpAddress
        MAX-ACCESS      read-write
        STATUS          current
        DESCRIPTION
                "This object displays the IPv4 address of the source of an ACL."
        ::= { atiStkSwACLConfigEntry 7 }

atiStkSwACLSrcMask      OBJECT-TYPE
        SYNTAX          IpAddress
        MAX-ACCESS      read-write
        STATUS          current
        DESCRIPTION
                "This object displays the IPv4 mask of the source of an ACL."
        ::= { atiStkSwACLConfigEntry 8 }

atiStkSwACLDestType     OBJECT-TYPE
        SYNTAX          INTEGER {
                                any (1),
                                host (2),
                                ip (3)
                                }
        MAX-ACCESS      read-write
        STATUS          current
        DESCRIPTION
                "The Object specifies the destination type of the ACL."
        ::= { atiStkSwACLConfigEntry 9 }

atiStkSwACLDestAddr     OBJECT-TYPE
        SYNTAX          IpAddress
        MAX-ACCESS      read-write
        STATUS          current
        DESCRIPTION
                "This object displays the IPv4 address of the destination of an ACL."
        ::= { atiStkSwACLConfigEntry 10 }

atiStkSwACLDestMask     OBJECT-TYPE
        SYNTAX          IpAddress
        MAX-ACCESS      read-write
        STATUS          current
        DESCRIPTION
                "This object displays the IPv4 mask of the destination of an ACL."
        ::= { atiStkSwACLConfigEntry 11 }

atiStkSwACLVlanId       OBJECT-TYPE
        SYNTAX          Integer32 (1..4094)
        MAX-ACCESS      read-write
        STATUS          current
        DESCRIPTION
                "This object specifies the Vlan ID of the ACL table."
        ::= { atiStkSwACLConfigEntry 12 }

atiStkSwACLProtocol     OBJECT-TYPE
        SYNTAX          Integer32 (1..255)
        MAX-ACCESS      read-write
        STATUS          current
        DESCRIPTION
                "This object specifies the Protocol ID of the ACL table."
        ::= { atiStkSwACLConfigEntry 13 }

atiStkSwACLICMPType     OBJECT-TYPE
        SYNTAX          Integer32
        MAX-ACCESS      read-write
        STATUS          current
        DESCRIPTION
                "This object specifies the ICMP Type of the ACL table."
        ::= { atiStkSwACLConfigEntry 14 }

atiStkSwACLUDPTCPSrcPort  OBJECT-TYPE
        SYNTAX          INTEGER {
                                eq (1),
                                lt (2),
                                gt (3),
                                ne (4),
                                range (5),
                                noCompare (6)
                                }
        MAX-ACCESS      read-write
        STATUS          current
        DESCRIPTION
                "The Object specifies the comparision of the port."
        ::= { atiStkSwACLConfigEntry 15 }

atiStkSwACLSrcPort1     OBJECT-TYPE
        SYNTAX          Integer32 (0..65535)
        MAX-ACCESS      read-write
        STATUS          current
        DESCRIPTION
                "This object specifies the port."
        ::= { atiStkSwACLConfigEntry 16 }

atiStkSwACLSrcPort2     OBJECT-TYPE
        SYNTAX          Integer32 (0..65535)
        MAX-ACCESS      read-write
        STATUS          current
        DESCRIPTION
                "This object specifies the port."
        ::= { atiStkSwACLConfigEntry 17 }

atiStkSwACLUDPTCPDestPort  OBJECT-TYPE
        SYNTAX          INTEGER {
                                eq (1),
                                lt (2),
                                gt (3),
                                ne (4),
                                range (5),
                                noCompare (6)
                                }
        MAX-ACCESS      read-write
        STATUS          current
        DESCRIPTION
                "The Object specifies the comparision of the port."
        ::= { atiStkSwACLConfigEntry 18 }

atiStkSwACLDestPort1    OBJECT-TYPE
        SYNTAX          Integer32 (0..65535)
        MAX-ACCESS      read-write
        STATUS          current
        DESCRIPTION
                "This object specifies the port."
        ::= { atiStkSwACLConfigEntry 19 }

atiStkSwACLDestPort2    OBJECT-TYPE
        SYNTAX          Integer32 (0..65535)
        MAX-ACCESS      read-write
        STATUS          current
        DESCRIPTION
                "This object specifies the port."
        ::= { atiStkSwACLConfigEntry 20 }


atiStkSwACLMACConfigTable  OBJECT-TYPE
        SYNTAX          SEQUENCE OF AtiStkSwACLMACConfigEntry
        MAX-ACCESS      not-accessible
        STATUS          current
        DESCRIPTION
                "This table contains a Access Control List (ACL) in the
                switch and their associated attributes."
        ::= { atiStkSwACLGroup 2 }

atiStkSwACLMACConfigEntry  OBJECT-TYPE
        SYNTAX          AtiStkSwACLMACConfigEntry
        MAX-ACCESS      not-accessible
        STATUS          current
        DESCRIPTION
                "This object specifies an entry in 'atiStkSwACLMACConfigTable'
                that describes the ACL in the switch."
        INDEX           { atiStkSwACLMACId }
        ::= { atiStkSwACLMACConfigTable 1 }

AtiStkSwACLMACConfigEntry ::=
        SEQUENCE {
                atiStkSwACLMACId                        Integer32,
                atiStkSwACLMACShowId                    Integer32,
                atiStkSwACLMACStatus                    INTEGER,
                atiStkSwACLMACAction                    INTEGER,
                atiStkSwACLMACSrc                       INTEGER,
                atiStkSwACLMACDest                      INTEGER,
                atiStkSwACLMACSrcMac                    DisplayString,
                atiStkSwACLMACSrcMacMask                DisplayString,
                atiStkSwACLMACDestMac                   DisplayString,
                atiStkSwACLMACDestMacMask               DisplayString
                }

atiStkSwACLMACId        OBJECT-TYPE
        SYNTAX          Integer32 (1..700)
        MAX-ACCESS      read-only
        STATUS          current
        DESCRIPTION
                "This object specifies the ID of the ACL table."
        ::= { atiStkSwACLMACConfigEntry 1 }

atiStkSwACLMACShowId    OBJECT-TYPE
        SYNTAX          Integer32 (4000..4699)
        MAX-ACCESS      read-only
        STATUS          current
        DESCRIPTION
                "This object specifies the ID of the ACL table."
        ::= { atiStkSwACLMACConfigEntry 2 }

atiStkSwACLMACStatus    OBJECT-TYPE
        SYNTAX          INTEGER {
                                create (1),
                                delete (2)
                                }
        MAX-ACCESS      read-write
        STATUS          current
        DESCRIPTION
                "This object specifies the status of the ACL ID."
        ::= { atiStkSwACLMACConfigEntry 3 }

atiStkSwACLMACAction    OBJECT-TYPE
        SYNTAX          INTEGER {
                                deny (1),
                                permit (2),
                                copytomirror (3)
                                }
        MAX-ACCESS      read-write
        STATUS          current
        DESCRIPTION
                "The action of the ACL entry either deny or permit or copy to mirror."
        ::= { atiStkSwACLMACConfigEntry 4 }

atiStkSwACLMACSrc       OBJECT-TYPE
        SYNTAX          INTEGER {
                                any (1),
                                mac (2)
                                }
        MAX-ACCESS  read-write
        STATUS      current
        DESCRIPTION
                "This object specifies the source type."
        ::= { atiStkSwACLMACConfigEntry 5 }

atiStkSwACLMACDest       OBJECT-TYPE
        SYNTAX          INTEGER {
                                any (1),
                                mac (2)
                                }
        MAX-ACCESS      read-write
        STATUS          current
        DESCRIPTION
                "This object specifies destination type."
        ::= { atiStkSwACLMACConfigEntry 6 }

atiStkSwACLMACSrcMac    OBJECT-TYPE
        SYNTAX          DisplayString (SIZE(1..18))
        MAX-ACCESS      read-write
        STATUS          current
        DESCRIPTION
                "The MAC address Mask used by this source."
        ::= { atiStkSwACLMACConfigEntry 7 }

atiStkSwACLMACSrcMacMask  OBJECT-TYPE
        SYNTAX          DisplayString (SIZE(1..18))
        MAX-ACCESS      read-write
        STATUS          current
        DESCRIPTION
                "The MAC address Mask used by this source ."
        ::= { atiStkSwACLMACConfigEntry 8 }

atiStkSwACLMACDestMac   OBJECT-TYPE
        SYNTAX          DisplayString (SIZE(1..18))
        MAX-ACCESS      read-write
        STATUS          current
        DESCRIPTION
                "The MAC address used by this destination."
        ::= { atiStkSwACLMACConfigEntry 9 }

atiStkSwACLMACDestMacMask  OBJECT-TYPE
        SYNTAX          DisplayString (SIZE(1..18))
        MAX-ACCESS      read-write
        STATUS          current
        DESCRIPTION
                "The MAC address Mask used by this destination."
        ::= { atiStkSwACLMACConfigEntry 10 }


atiStkSwACLInterfaceConfigTable  OBJECT-TYPE
        SYNTAX          SEQUENCE OF AtiStkSwACLInterfaceConfigEntry
        MAX-ACCESS      not-accessible
        STATUS          current
        DESCRIPTION
                "This table contains a Access Control List (ACL) in the
                switch and their associated attributes."
        ::= { atiStkSwACLGroup 3 }

atiStkSwACLInterfaceConfigEntry  OBJECT-TYPE
        SYNTAX          AtiStkSwACLInterfaceConfigEntry
        MAX-ACCESS      not-accessible
        STATUS          current
        DESCRIPTION
                "This object specifies an entry in 'atiStkSwACLMACConfigTable'
                that describes the ACL in the switch."
        INDEX           { atiStkSwACLInterfaceModuleId, atiStkSwACLInterfacePortId }
        ::= { atiStkSwACLInterfaceConfigTable 1 }

AtiStkSwACLInterfaceConfigEntry ::=
        SEQUENCE {
                atiStkSwACLInterfaceModuleId            Integer32,
                atiStkSwACLInterfacePortId              Integer32,
                atiStkSwACLInterfacaeACLId              DisplayString,
                atiStkSwACLInterfacaeAddACLId           Integer32,
                atiStkSwACLInterfacaeRemoveACLId        Integer32
                }

atiStkSwACLInterfaceModuleId  OBJECT-TYPE
        SYNTAX          Integer32 (1..8)
        MAX-ACCESS      read-only
        STATUS          current
        DESCRIPTION
                "This object specifies the Module ID of the system."
        ::= { atiStkSwACLInterfaceConfigEntry 1 }

atiStkSwACLInterfacePortId  OBJECT-TYPE
        SYNTAX          Integer32 (1..28)
        MAX-ACCESS      read-only
        STATUS          current
        DESCRIPTION
                "This object specifies the Port ID of the system."
        ::= { atiStkSwACLInterfaceConfigEntry 2 }

atiStkSwACLInterfacaeACLId  OBJECT-TYPE
        SYNTAX          DisplayString
        MAX-ACCESS      read-only
        STATUS          current
        DESCRIPTION
                "This object specifies the created ACL ID."
        ::= { atiStkSwACLInterfaceConfigEntry 3 }

atiStkSwACLInterfacaeAddACLId  OBJECT-TYPE
        SYNTAX          Integer32
        MAX-ACCESS      read-write
        STATUS          current
        DESCRIPTION
                "This object specifies the ACL ID to Add."
        ::= { atiStkSwACLInterfaceConfigEntry 4 }

atiStkSwACLInterfacaeRemoveACLId  OBJECT-TYPE
        SYNTAX          Integer32
        MAX-ACCESS      read-write
        STATUS          current
        DESCRIPTION
                "This object specifies the ACL ID to Remove."
        ::= { atiStkSwACLInterfaceConfigEntry 5 }


-- atiStkSwAACLIpv4ConfigTable

atiStkSwAACLIpv4ConfigTable  OBJECT-TYPE
        SYNTAX          SEQUENCE OF AtiStkSwAACLIpv4ConfigEntry
        MAX-ACCESS      not-accessible
        STATUS          current
        DESCRIPTION
                "This table contains a Access Control List (ACL) for Ipv4
                addresses in the switch and their associated attributes."
        ::= { atiStkSwAACLGroup 1 }

atiStkSwAACLIpv4ConfigEntry  OBJECT-TYPE
        SYNTAX          AtiStkSwAACLIpv4ConfigEntry
        MAX-ACCESS      not-accessible
        STATUS          current
        DESCRIPTION
                "This object specifies an entry in 'atiStkSwACLConfigTable'
                that describes the ACL in the switch."
        INDEX           { atiStkSwAACLId }
        ::= { atiStkSwAACLIpv4ConfigTable 1 }

AtiStkSwAACLIpv4ConfigEntry ::=
        SEQUENCE {
                atiStkSwAACLId                          Integer32,
                atiStkSwAACLStatus                      INTEGER,
                atiStkSwAACLName                        DisplayString,
                atiStkSwAACLAction                      INTEGER,
                atiStkSwAACLTrafficType                 INTEGER,
                atiStkSwAACLSrcType                     INTEGER,
                atiStkSwAACLSrcAddr                     IpAddress,
                atiStkSwAACLSrcMask                     IpAddress,
                atiStkSwAACLDestType                    INTEGER,
                atiStkSwAACLDestAddr                    IpAddress,
                atiStkSwAACLDestMask                    IpAddress,
                atiStkSwAACLVlanId                      Integer32,
                atiStkSwAACLProtocol                    Integer32,
                atiStkSwAACLICMPType                    Integer32,
                atiStkSwAACLUDPTCPSrcPort               INTEGER,
                atiStkSwAACLSrcPort1                    Integer32,
                atiStkSwAACLSrcPort2                    Integer32,
                atiStkSwAACLUDPTCPDestPort              INTEGER,
                atiStkSwAACLDestPort1                   Integer32,
                atiStkSwAACLDestPort2                   Integer32,
                atiStkSwAACLTimeRange                   DisplayString
                }

atiStkSwAACLId          OBJECT-TYPE
        SYNTAX          Integer32(1..255)
        MAX-ACCESS      read-only
        STATUS          current
        DESCRIPTION
                "This object specifies the ID of the ACL table."
        ::= { atiStkSwAACLIpv4ConfigEntry 1 }
atiStkSwAACLStatus      OBJECT-TYPE
        SYNTAX          INTEGER {
                                create (1),
                                delete (2)
                                }
        MAX-ACCESS      read-write
        STATUS          current
        DESCRIPTION
                "This object specifies the status of the ACL ID."
        ::= { atiStkSwAACLIpv4ConfigEntry 2 }

atiStkSwAACLName        OBJECT-TYPE
        SYNTAX          DisplayString
        MAX-ACCESS      read-write
        STATUS      current
        DESCRIPTION
                "This object specifies the name of the ACL."
        ::= { atiStkSwAACLIpv4ConfigEntry 3 }

atiStkSwAACLAction      OBJECT-TYPE
        SYNTAX          INTEGER {
                                deny (1),
                                permit (2),
                                copytomirror (3)
                                }
        MAX-ACCESS      read-write
        STATUS          current
        DESCRIPTION
                "The action of the ACL entry either deny or permit or copy to mirror."
        ::= { atiStkSwAACLIpv4ConfigEntry 4 }

atiStkSwAACLTrafficType OBJECT-TYPE
        SYNTAX          INTEGER {
                                icmp (1),
                                ip (2),
                                proto (3),
                                tcp (4),
                                udp (5)
                                }
        MAX-ACCESS      read-write
        STATUS          current
        DESCRIPTION
                "The Object specifies the traffic type of the ACL."
        ::= { atiStkSwAACLIpv4ConfigEntry 5 }

atiStkSwAACLSrcType     OBJECT-TYPE
        SYNTAX          INTEGER {
                                any (1),
                                host (2),
                                ip (3)
                                }
        MAX-ACCESS      read-write
        STATUS          current
        DESCRIPTION
                "The Object specifies the source type of the ACL."
        ::= { atiStkSwAACLIpv4ConfigEntry 6 }

atiStkSwAACLSrcAddr     OBJECT-TYPE
        SYNTAX          IpAddress
        MAX-ACCESS      read-write
        STATUS          current
        DESCRIPTION
                "This object displays the IPv4 address of the source of an ACL."
        ::= { atiStkSwAACLIpv4ConfigEntry 7 }

atiStkSwAACLSrcMask     OBJECT-TYPE
        SYNTAX          IpAddress
        MAX-ACCESS      read-write
        STATUS          current
        DESCRIPTION
                "This object displays the IPv4 mask of the source of an ACL."
        ::= { atiStkSwAACLIpv4ConfigEntry 8 }

atiStkSwAACLDestType    OBJECT-TYPE
        SYNTAX          INTEGER {
                                any (1),
                                host (2),
                                ip (3)
                                }
        MAX-ACCESS      read-write
        STATUS          current
        DESCRIPTION
                "The Object specifies the destination type of the ACL."
        ::= { atiStkSwAACLIpv4ConfigEntry 9 }

atiStkSwAACLDestAddr    OBJECT-TYPE
        SYNTAX          IpAddress
        MAX-ACCESS      read-write
        STATUS          current
        DESCRIPTION
                "This object displays the IPv4 address of the destination of an ACL."
        ::= { atiStkSwAACLIpv4ConfigEntry 10 }

atiStkSwAACLDestMask    OBJECT-TYPE
        SYNTAX          IpAddress
        MAX-ACCESS      read-write
        STATUS          current
        DESCRIPTION
                "This object displays the IPv4 mask of the destination of an ACL."
        ::= { atiStkSwAACLIpv4ConfigEntry 11 }

atiStkSwAACLVlanId      OBJECT-TYPE
        SYNTAX          Integer32 (1..4094)
        MAX-ACCESS      read-write
        STATUS          current
        DESCRIPTION
                "This object specifies the Vlan ID of the ACL table."
        ::= { atiStkSwAACLIpv4ConfigEntry 12 }

atiStkSwAACLProtocol    OBJECT-TYPE
        SYNTAX          Integer32 (1..255)
        MAX-ACCESS      read-write
        STATUS          current
        DESCRIPTION
                "This object specifies the Protocol ID of the ACL table."
        ::= { atiStkSwAACLIpv4ConfigEntry 13 }

atiStkSwAACLICMPType    OBJECT-TYPE
        SYNTAX          Integer32
        MAX-ACCESS      read-write
        STATUS          current
        DESCRIPTION
                "This object specifies the ICMP Type of the ACL table."
        ::= { atiStkSwAACLIpv4ConfigEntry 14 }

atiStkSwAACLUDPTCPSrcPort  OBJECT-TYPE
        SYNTAX          INTEGER {
                                eq (1),
                                lt (2),
                                gt (3),
                                ne (4),
                                range (5),
                                noCompare (6)
                                }
        MAX-ACCESS      read-write
        STATUS          current
        DESCRIPTION
                "The Object specifies the comparision of the port."
        ::= { atiStkSwAACLIpv4ConfigEntry 15 }

atiStkSwAACLSrcPort1    OBJECT-TYPE
        SYNTAX          Integer32 (0..65535)
        MAX-ACCESS      read-write
        STATUS          current
        DESCRIPTION
                "This object specifies the port."
        ::= { atiStkSwAACLIpv4ConfigEntry 16 }

atiStkSwAACLSrcPort2    OBJECT-TYPE
        SYNTAX          Integer32 (0..65535)
        MAX-ACCESS      read-write
        STATUS          current
        DESCRIPTION
                "This object specifies the port."
        ::= { atiStkSwAACLIpv4ConfigEntry 17 }

atiStkSwAACLUDPTCPDestPort        OBJECT-TYPE
        SYNTAX          INTEGER {
                                eq (1),
                                lt (2),
                                gt (3),
                                ne (4),
                                range (5),
                                noCompare (6)
                                }
        MAX-ACCESS      read-write
        STATUS          current
        DESCRIPTION
                "The Object specifies the comparision of the port."
        ::= { atiStkSwAACLIpv4ConfigEntry 18 }

atiStkSwAACLDestPort1   OBJECT-TYPE
        SYNTAX          Integer32 (0..65535)
        MAX-ACCESS      read-write
        STATUS          current
        DESCRIPTION
                "This object specifies the port."
        ::= { atiStkSwAACLIpv4ConfigEntry 19 }

atiStkSwAACLDestPort2   OBJECT-TYPE
        SYNTAX          Integer32 (0..65535)
        MAX-ACCESS      read-write
        STATUS          current
        DESCRIPTION
                "This object specifies the port."
        ::= { atiStkSwAACLIpv4ConfigEntry 20 }

atiStkSwAACLTimeRange   OBJECT-TYPE
        SYNTAX          DisplayString
        MAX-ACCESS      read-write
        STATUS          current
        DESCRIPTION
                "This object specifies the time range ACL."
        ::= { atiStkSwAACLIpv4ConfigEntry 21 }


-- atiStkSwAACLIpv6ConfigTable

atiStkSwAACLIpv6ConfigTable  OBJECT-TYPE
        SYNTAX          SEQUENCE OF AtiStkSwAACLIpv6ConfigEntry
        MAX-ACCESS      not-accessible
        STATUS          current
        DESCRIPTION
                "This table contains a Access Control List (ACL) for Ipv4
                addresses in the switch and their associated attributes."
        ::= { atiStkSwAACLGroup 2 }

atiStkSwAACLIpv6ConfigEntry  OBJECT-TYPE
        SYNTAX          AtiStkSwAACLIpv6ConfigEntry
        MAX-ACCESS      not-accessible
        STATUS          current
        DESCRIPTION
                "This object specifies an entry in 'atiStkSwACLConfigTable'
                that describes the ACL in the switch."
        INDEX           { atiStkSwAACLv6Id }
        ::= { atiStkSwAACLIpv6ConfigTable 1 }

AtiStkSwAACLIpv6ConfigEntry ::=
        SEQUENCE {
                atiStkSwAACLv6Id                        Integer32,
                atiStkSwAACLv6Status                    INTEGER,
                atiStkSwAACLv6Name                      DisplayString,
                atiStkSwAACLv6Action                    INTEGER,
                atiStkSwAACLv6TrafficType               INTEGER,
                atiStkSwAACLv6SrcType                   INTEGER,
                atiStkSwAACLv6SrcAddr                   DisplayString,
                atiStkSwAACLv6SrcMask                   DisplayString,
                atiStkSwAACLv6DestType                  INTEGER,
                atiStkSwAACLv6DestAddr                  DisplayString,
                atiStkSwAACLv6DestMask                  DisplayString,
                atiStkSwAACLv6VlanId                    Integer32,
                atiStkSwAACLv6Protocol                  Integer32,
                atiStkSwAACLv6ICMPType                  Integer32,
                atiStkSwAACLv6UDPTCPSrcPort             INTEGER,
                atiStkSwAACLv6SrcPort1                  Integer32,
                atiStkSwAACLv6SrcPort2                  Integer32,
                atiStkSwAACLv6UDPTCPDestPort            INTEGER,
                atiStkSwAACLv6DestPort1                 Integer32,
                atiStkSwAACLv6DestPort2                 Integer32,
                atiStkSwAACLv6TimeRange                 DisplayString
                }

atiStkSwAACLv6Id        OBJECT-TYPE
        SYNTAX          Integer32 (0..255)
        MAX-ACCESS      read-only
        STATUS          current
        DESCRIPTION
                "This object specifies the ID of the ACL table."
        ::= { atiStkSwAACLIpv6ConfigEntry 1 }

atiStkSwAACLv6Status    OBJECT-TYPE
        SYNTAX          INTEGER {
                                create (1),
                                delete (2)
                                }
        MAX-ACCESS      read-write
        STATUS          current
        DESCRIPTION
                "This object specifies the status of the ACL ID."
        ::= { atiStkSwAACLIpv6ConfigEntry 2 }

atiStkSwAACLv6Name      OBJECT-TYPE
        SYNTAX          DisplayString
        MAX-ACCESS      read-write
        STATUS          current
        DESCRIPTION
                "This object specifies the name of the ACL."
        ::= { atiStkSwAACLIpv6ConfigEntry 3 }

atiStkSwAACLv6Action    OBJECT-TYPE
        SYNTAX          INTEGER {
                                deny (1),
                                permit (2),
                                copytomirror (3)
                                }
        MAX-ACCESS      read-write
        STATUS          current
        DESCRIPTION
                "The action of the ACL entry either deny or permit or copy to mirror."
        ::= { atiStkSwAACLIpv6ConfigEntry 4 }

atiStkSwAACLv6TrafficType  OBJECT-TYPE
        SYNTAX          INTEGER {
                                icmp (1),
                                ip (2),
                                proto (3),
                                tcp (4),
                                udp (5)
                                }
        MAX-ACCESS      read-write
        STATUS          current
        DESCRIPTION
                "The Object specifies the traffic type of the ACL."
        ::= { atiStkSwAACLIpv6ConfigEntry 5 }

atiStkSwAACLv6SrcType   OBJECT-TYPE
        SYNTAX          INTEGER {
                                any (1),
                                host (2),
                                ip (3)
                                }
        MAX-ACCESS      read-write
        STATUS          current
        DESCRIPTION
                "The Object specifies the source type of the ACL."
        ::= { atiStkSwAACLIpv6ConfigEntry 6 }

atiStkSwAACLv6SrcAddr   OBJECT-TYPE
        SYNTAX          DisplayString
        MAX-ACCESS      read-write
        STATUS          current
        DESCRIPTION
                "This object displays the IPv6 address of the source of an ACL."
        ::= { atiStkSwAACLIpv6ConfigEntry 7 }

atiStkSwAACLv6SrcMask   OBJECT-TYPE
        SYNTAX          DisplayString
        MAX-ACCESS      read-write
        STATUS          current
        DESCRIPTION
                "This object displays the IPv6 mask of the source of an ACL."
        ::= { atiStkSwAACLIpv6ConfigEntry 8 }

atiStkSwAACLv6DestType  OBJECT-TYPE
        SYNTAX          INTEGER {
                                any (1),
                                host (2),
                                ip (3)
                                }
        MAX-ACCESS      read-write
        STATUS          current
        DESCRIPTION
                "The Object specifies the destination type of the ACL."
        ::= { atiStkSwAACLIpv6ConfigEntry 9 }

atiStkSwAACLv6DestAddr  OBJECT-TYPE
        SYNTAX          DisplayString
        MAX-ACCESS      read-write
        STATUS          current
        DESCRIPTION
                "This object displays the IPv6 address of the destination of an ACL."
        ::= { atiStkSwAACLIpv6ConfigEntry 10 }

atiStkSwAACLv6DestMask  OBJECT-TYPE
        SYNTAX          DisplayString
        MAX-ACCESS      read-write
        STATUS          current
        DESCRIPTION
                "This object displays the IPv6 mask of the destination of an ACL."
        ::= { atiStkSwAACLIpv6ConfigEntry 11 }

atiStkSwAACLv6VlanId    OBJECT-TYPE
        SYNTAX          Integer32 (1..4094)
        MAX-ACCESS      read-write
        STATUS          current
        DESCRIPTION
                "This object specifies the Vlan ID of the ACL table."
        ::= { atiStkSwAACLIpv6ConfigEntry 12 }

atiStkSwAACLv6Protocol  OBJECT-TYPE
        SYNTAX          Integer32 (1..255)
        MAX-ACCESS      read-write
        STATUS          current
        DESCRIPTION
                "This object specifies the Protocol ID of the ACL table."
        ::= { atiStkSwAACLIpv6ConfigEntry 13 }

atiStkSwAACLv6ICMPType  OBJECT-TYPE
        SYNTAX          Integer32
        MAX-ACCESS      read-write
        STATUS          current
        DESCRIPTION
                "This object specifies the ICMP Type of the ACL table."
        ::= { atiStkSwAACLIpv6ConfigEntry 14 }

atiStkSwAACLv6UDPTCPSrcPort  OBJECT-TYPE
        SYNTAX          INTEGER {
                                eq (1),
                                lt (2),
                                gt (3),
                                ne (4),
                                range (5),
                                noCompare (6)
                                }
        MAX-ACCESS      read-write
        STATUS          current
        DESCRIPTION
                "The Object specifies the comparision of the port."
        ::= { atiStkSwAACLIpv6ConfigEntry 15 }

atiStkSwAACLv6SrcPort1  OBJECT-TYPE
        SYNTAX          Integer32 (0..65535)
        MAX-ACCESS      read-write
        STATUS          current
        DESCRIPTION
                "This object specifies the port."
        ::= { atiStkSwAACLIpv6ConfigEntry 16 }

atiStkSwAACLv6SrcPort2  OBJECT-TYPE
        SYNTAX          Integer32 (0..65535)
        MAX-ACCESS      read-write
        STATUS          current
        DESCRIPTION
                "This object specifies the port."
        ::= { atiStkSwAACLIpv6ConfigEntry 17 }

atiStkSwAACLv6UDPTCPDestPort  OBJECT-TYPE
        SYNTAX          INTEGER {
                                eq (1),
                                lt (2),
                                gt (3),
                                ne (4),
                                range (5),
                                noCompare (6)
                                }
        MAX-ACCESS      read-write
        STATUS          current
        DESCRIPTION
                "The Object specifies the comparision of the port."
        ::= { atiStkSwAACLIpv6ConfigEntry 18 }

atiStkSwAACLv6DestPort1 OBJECT-TYPE
        SYNTAX          Integer32 (0..65535)
        MAX-ACCESS      read-write
        STATUS          current
        DESCRIPTION
                "This object specifies the port."
        ::= { atiStkSwAACLIpv6ConfigEntry 19 }

atiStkSwAACLv6DestPort2 OBJECT-TYPE
        SYNTAX          Integer32 (0..65535)
        MAX-ACCESS      read-write
        STATUS          current
        DESCRIPTION
                "This object specifies the port."
        ::= { atiStkSwAACLIpv6ConfigEntry 20 }

atiStkSwAACLv6TimeRange OBJECT-TYPE
        SYNTAX          DisplayString
        MAX-ACCESS      read-write
        STATUS          current
        DESCRIPTION
                "This object specifies the time range ACL."
        ::= { atiStkSwAACLIpv6ConfigEntry 21 }


atiStkSwAACLInterfaceConfigTable  OBJECT-TYPE
        SYNTAX          SEQUENCE OF AtiStkSwAACLInterfaceConfigEntry
        MAX-ACCESS      not-accessible
        STATUS          current
        DESCRIPTION
                "This table contains a Access Control List (ACL) in the
                switch and their associated attributes."
        ::= { atiStkSwAACLGroup 3 }

atiStkSwAACLInterfaceConfigEntry  OBJECT-TYPE
        SYNTAX          AtiStkSwAACLInterfaceConfigEntry
        MAX-ACCESS      not-accessible
        STATUS          current
        DESCRIPTION
                "This object specifies an entry in 'atiStkSwACLMACConfigTable'
                that describes the ACL in the switch."
        INDEX           { atiStkSwAACLInterfaceModuleId, atiStkSwAACLInterfacePortId }
        ::= { atiStkSwAACLInterfaceConfigTable 1 }

AtiStkSwAACLInterfaceConfigEntry ::=
        SEQUENCE {
                atiStkSwAACLInterfaceModuleId           Integer32,
                atiStkSwAACLInterfacePortId             Integer32,
                atiStkSwAACLInterfacaeACLName           DisplayString,
                atiStkSwAACLInterfacaeAddACLName        DisplayString,
                atiStkSwAACLInterfacaeRemoveACLName     DisplayString
                }

atiStkSwAACLInterfaceModuleId  OBJECT-TYPE
        SYNTAX          Integer32 (1..8)
        MAX-ACCESS      read-only
        STATUS          current
        DESCRIPTION
                "This object specifies the Module ID of the system."
        ::= { atiStkSwAACLInterfaceConfigEntry 1 }

atiStkSwAACLInterfacePortId  OBJECT-TYPE
        SYNTAX          Integer32 (1..28)
        MAX-ACCESS      read-only
        STATUS          current
        DESCRIPTION
                "This object specifies the Port ID of the system."
        ::= { atiStkSwAACLInterfaceConfigEntry 2 }

atiStkSwAACLInterfacaeACLName  OBJECT-TYPE
        SYNTAX          DisplayString
        MAX-ACCESS      read-only
        STATUS          current
        DESCRIPTION
                "This object specifies the created ACL ID."
        ::= { atiStkSwAACLInterfaceConfigEntry 3 }

atiStkSwAACLInterfacaeAddACLName  OBJECT-TYPE
        SYNTAX          DisplayString
        MAX-ACCESS      read-write
        STATUS          current
        DESCRIPTION
                "This object specifies the ACL ID to Add."
        ::= { atiStkSwAACLInterfaceConfigEntry 4 }

atiStkSwAACLInterfacaeRemoveACLName  OBJECT-TYPE
        SYNTAX          DisplayString
        MAX-ACCESS      read-write
        STATUS          current
        DESCRIPTION
                "This object specifies the ACL ID to Remove."
        ::= { atiStkSwAACLInterfaceConfigEntry 5 }


--acl time range
atiStkSwAACLTimeRangeConfigTable  OBJECT-TYPE
        SYNTAX          SEQUENCE OF AtiStkSwAACLTimeRangeConfigEntry
        MAX-ACCESS      not-accessible
        STATUS          current
        DESCRIPTION
                "This table contains a time range Access Control List (ACL) in the
                switch and their associated attributes."
        ::= { atiStkSwAACLGroup 4 }

atiStkSwAACLTimeRangeConfigEntry  OBJECT-TYPE
        SYNTAX          AtiStkSwAACLTimeRangeConfigEntry
        MAX-ACCESS      not-accessible
        STATUS          current
        DESCRIPTION
                "This object specifies an entry in 'atiStkSwAACLTimeRangeAbsoluteConfigTable'
                that describes the ACL in the switch."
        INDEX           { atiStkSwAACLTimeRangeEntry }
        ::= { atiStkSwAACLTimeRangeConfigTable 1 }

AtiStkSwAACLTimeRangeConfigEntry ::=
        SEQUENCE {
                atiStkSwAACLTimeRangeEntry              Integer32,
                atiStkSwAACLTimeRangeName               DisplayString,
                atiStkSwAACLTimeRangeType               INTEGER,
                atiStkSwAACLTimeRangeAbsoluteStartTime  DisplayString,
                atiStkSwAACLTimeRangeAbsoluteEndTime    DisplayString,
                atiStkSwAACLTimeRangePeriodicFrequency  INTEGER,
                atiStkSwAACLTimeRangePeriodicStartDay   INTEGER,
                atiStkSwAACLTimeRangePeriodicEndDay     INTEGER,
                atiStkSwAACLTimeRangePeriodicStartTime  DisplayString,
                atiStkSwAACLTimeRangePeriodicEndTime    DisplayString,
                atiStkSwAACLTimeRangeStatus             INTEGER
                }

atiStkSwAACLTimeRangeEntry  OBJECT-TYPE
        SYNTAX          Integer32 (1..100)
        MAX-ACCESS      read-only
        STATUS          current
        DESCRIPTION
                "This object specifies the entry of the time range ACL."
        ::= { atiStkSwAACLTimeRangeConfigEntry 1 }

atiStkSwAACLTimeRangeName  OBJECT-TYPE
        SYNTAX          DisplayString
        MAX-ACCESS      read-write
        STATUS          current
        DESCRIPTION
                "This object specifies the Name of the time range ACL."
        ::= { atiStkSwAACLTimeRangeConfigEntry 2 }

atiStkSwAACLTimeRangeType  OBJECT-TYPE
        SYNTAX          INTEGER {
                                absolute(1),
                                periodic(2),
                                none(3)
                                }
        MAX-ACCESS      read-write
        STATUS          current
        DESCRIPTION
                "This object specifies the type of the time range ACL."
        ::= { atiStkSwAACLTimeRangeConfigEntry 3 }

atiStkSwAACLTimeRangeAbsoluteStartTime  OBJECT-TYPE
        SYNTAX          DisplayString
        MAX-ACCESS      read-write
        STATUS          current
        DESCRIPTION
                "This object specifies the start time of the time range ACL."
        ::= { atiStkSwAACLTimeRangeConfigEntry 4 }

atiStkSwAACLTimeRangeAbsoluteEndTime  OBJECT-TYPE
        SYNTAX          DisplayString
        MAX-ACCESS      read-write
        STATUS          current
        DESCRIPTION
                "This object specifies the end time of the time range ACL."
        ::= { atiStkSwAACLTimeRangeConfigEntry 5 }

atiStkSwAACLTimeRangePeriodicFrequency  OBJECT-TYPE
        SYNTAX          INTEGER {
                                day (1),
                                daily (2),
                                weekdays (3),
                                weekends (4),
                                notvalid (5),
                                select (6)
                                }
        MAX-ACCESS      read-write
        STATUS          current
        DESCRIPTION
                "This object specifies the Frequency of days for periodic  time range ACL."
        ::= { atiStkSwAACLTimeRangeConfigEntry 6 }

atiStkSwAACLTimeRangePeriodicStartDay  OBJECT-TYPE
        SYNTAX          INTEGER {
                                monday (1),
                                tuesday (2),
                                wednesday (3),
                                thursday (4),
                                friday (5),
                                saturday (6),
                                sunday (7)
                                }
        MAX-ACCESS      read-write
        STATUS          current
        DESCRIPTION
                "This object specifies the start day for periodic  time range ACL."
        ::= { atiStkSwAACLTimeRangeConfigEntry 7 }

atiStkSwAACLTimeRangePeriodicEndDay  OBJECT-TYPE
        SYNTAX          INTEGER {
                                monday (1),
                                tuesday (2),
                                wednesday (3),
                                thursday (4),
                                friday (5),
                                saturday (6),
                                sunday (7)
                                }
        MAX-ACCESS      read-write
        STATUS          current
        DESCRIPTION
                "This object specifies the end day for periodic  time range ACL."
        ::= { atiStkSwAACLTimeRangeConfigEntry 8 }

atiStkSwAACLTimeRangePeriodicStartTime  OBJECT-TYPE
        SYNTAX          DisplayString
        MAX-ACCESS      read-write
        STATUS          current
        DESCRIPTION
                "This object specifies the start time of the periodic time range ACL."
        ::= { atiStkSwAACLTimeRangeConfigEntry 9 }

atiStkSwAACLTimeRangePeriodicEndTime  OBJECT-TYPE
        SYNTAX          DisplayString
        MAX-ACCESS      read-write
        STATUS          current
        DESCRIPTION
                "This object specifies the end time of the periodic time range ACL."
        ::= { atiStkSwAACLTimeRangeConfigEntry 10 }

atiStkSwAACLTimeRangeStatus  OBJECT-TYPE
        SYNTAX          INTEGER {
                                create (1),
                                delete (2)
                                }
        MAX-ACCESS      read-write
        STATUS          current
        DESCRIPTION
                "This object specifies the status of the time range ACL."
        ::= { atiStkSwAACLTimeRangeConfigEntry 11 }


--IPv4 MAC
atiStkSwAACLIPV4MACConfigTable  OBJECT-TYPE
        SYNTAX          SEQUENCE OF AtiStkSwAACLIPV4MACConfigEntry
        MAX-ACCESS      not-accessible
        STATUS          current
        DESCRIPTION
                "This table contains a Access Control List (ACL) in the
                switch and their associated attributes."
        ::= { atiStkSwAACLGroup 5 }

atiStkSwAACLIPV4MACConfigEntry  OBJECT-TYPE
        SYNTAX          AtiStkSwAACLIPV4MACConfigEntry
        MAX-ACCESS      not-accessible
        STATUS          current
        DESCRIPTION
                "This object specifies an entry in 'atiStkSwACLMACConfigTable'
                that describes the ACL in the switch."
        INDEX       { atiStkSwAACLIPV4MACId }
        ::= { atiStkSwAACLIPV4MACConfigTable 1 }

AtiStkSwAACLIPV4MACConfigEntry ::=
        SEQUENCE {
                atiStkSwAACLIPV4MACId                   Integer32,
--              atiStkSwAACLIPV4MACShowId               Integer32,
                atiStkSwAACLIPV4MACName                 DisplayString,
                atiStkSwAACLIPV4MACStatus               INTEGER,
                atiStkSwAACLIPV4MACAction               INTEGER,
                atiStkSwAACLIPV4MACSrc                  INTEGER,
                atiStkSwAACLIPV4MACDest                 INTEGER,
                atiStkSwAACLIPV4MACSrcMac               DisplayString,
                atiStkSwAACLIPV4MACSrcMacMask           DisplayString,
                atiStkSwAACLIPV4MACDestMac              DisplayString,
                atiStkSwAACLIPV4MACDestMacMask          DisplayString,
                atiStkSwAACLIPV4MACVlanId               Integer32,
                atiStkSwAACLIPV4MACTimeRange            DisplayString
                }

atiStkSwAACLIPV4MACId   OBJECT-TYPE
        SYNTAX          Integer32 (1..700)
        MAX-ACCESS      read-only
        STATUS          current
        DESCRIPTION
                "This object specifies the ID of the ACL table."
        ::= { atiStkSwAACLIPV4MACConfigEntry 1 }

atiStkSwAACLIPV4MACName OBJECT-TYPE
        SYNTAX          DisplayString
        MAX-ACCESS      read-write
        STATUS          current
        DESCRIPTION
                "This object specifies the name of the ACL."
        ::= { atiStkSwAACLIPV4MACConfigEntry 2 }

atiStkSwAACLIPV4MACStatus  OBJECT-TYPE
        SYNTAX          INTEGER {
                                create (1),
                                delete (2)
                                }
        MAX-ACCESS      read-write
        STATUS          current
        DESCRIPTION
                "This object specifies the status of the ACL ID."
        ::= { atiStkSwAACLIPV4MACConfigEntry 3 }

atiStkSwAACLIPV4MACAction  OBJECT-TYPE
        SYNTAX          INTEGER {
                                deny (1),
                                permit (2),
                                copytomirror (3)
                                }
        MAX-ACCESS      read-write
        STATUS          current
        DESCRIPTION
                "The action of the ACL entry either deny or permit or copy to mirror."
        ::= { atiStkSwAACLIPV4MACConfigEntry 4 }

atiStkSwAACLIPV4MACSrc  OBJECT-TYPE
        SYNTAX          INTEGER {
                                any (1),
                                mac (2)
                                }
        MAX-ACCESS      read-write
        STATUS          current
        DESCRIPTION
                "This object specifies the source type."
        ::= { atiStkSwAACLIPV4MACConfigEntry 5 }

atiStkSwAACLIPV4MACDest OBJECT-TYPE
        SYNTAX          INTEGER {
                                any (1),
                                mac (2)
                                }
        MAX-ACCESS      read-write
        STATUS          current
        DESCRIPTION
                "This object specifies destination type."
        ::= { atiStkSwAACLIPV4MACConfigEntry 6 }

atiStkSwAACLIPV4MACSrcMac  OBJECT-TYPE
        SYNTAX          DisplayString (SIZE(1..18))
        MAX-ACCESS      read-write
        STATUS          current
        DESCRIPTION
                "The MAC address Mask used by this source."
        ::= { atiStkSwAACLIPV4MACConfigEntry 7 }

atiStkSwAACLIPV4MACSrcMacMask  OBJECT-TYPE
        SYNTAX          DisplayString (SIZE(1..18))
        MAX-ACCESS      read-write
        STATUS          current
        DESCRIPTION
                "The MAC address Mask used by this source ."
        ::= { atiStkSwAACLIPV4MACConfigEntry 8 }

atiStkSwAACLIPV4MACDestMac  OBJECT-TYPE
        SYNTAX          DisplayString (SIZE(1..18))
        MAX-ACCESS      read-write
        STATUS          current
        DESCRIPTION
                "The MAC address used by this destination."
        ::= { atiStkSwAACLIPV4MACConfigEntry 9 }

atiStkSwAACLIPV4MACDestMacMask  OBJECT-TYPE
        SYNTAX          DisplayString (SIZE(1..18))
        MAX-ACCESS      read-write
        STATUS          current
        DESCRIPTION
                "The MAC address Mask used by this destination."
        ::= { atiStkSwAACLIPV4MACConfigEntry 10 }

atiStkSwAACLIPV4MACVlanId  OBJECT-TYPE
        SYNTAX          Integer32 (1..4094)
        MAX-ACCESS      read-write
        STATUS          current
        DESCRIPTION
                "This object specifies the Vlan ID of the ACL table."
        ::= { atiStkSwAACLIPV4MACConfigEntry 11 }

atiStkSwAACLIPV4MACTimeRange  OBJECT-TYPE
        SYNTAX          DisplayString
        MAX-ACCESS      read-write
        STATUS          current
        DESCRIPTION
                "This object specifies the time range ACL."
        ::= { atiStkSwAACLIPV4MACConfigEntry 12 }


--SS IPV4

-- atiStkSwAACLTimeRangePeriodicConfigTable  OBJECT-TYPE
--      SYNTAX          SEQUENCE OF AtiStkSwAACLTimeRangePeriodicConfigEntry
--      MAX-ACCESS      not-accessible
--      STATUS          current
--      DESCRIPTION
--              "This table contains a periodic time range Access Control List (ACL) in the
--              switch and their associated attributes."
--      ::= { atiStkSwAACLGroup 5 }

-- atiStkSwAACLTimeRangePeriodicConfigEntry  OBJECT-TYPE
--      SYNTAX          AtiStkSwAACLTimeRangePeriodicConfigEntry
--      MAX-ACCESS      not-accessible
--      STATUS          current
--      DESCRIPTION
--              "This object specifies an entry in 'atiStkSwAACLTimeRangePeriodicConfigTable'
--              that describes the ACL in the switch."
--      INDEX           { atiStkSwAACLTimeRangePeriodicEntry }
--      ::= { atiStkSwAACLTimeRangePeriodicConfigTable 1 }

-- AtiStkSwAACLTimeRangePeriodicConfigEntry ::=
--      SEQUENCE {
--              atiStkSwAACLTimeRangePeriodicEntry      Integer32,
--              atiStkSwAACLTimeRangePeriodicName       DisplayString,
--              atiStkSwAACLTimeRangePeriodicType       INTEGER,
--              atiStkSwAACLTimeRangePeriodicStartTime  DisplayString,
--              atiStkSwAACLTimeRangePeriodicEndTime    DisplayString,
--              atiStkSwAACLTimeRangePeriodicStatus     INTEGER
--              }

-- atiStkSwAACLTimeRangePeriodicEntry  OBJECT-TYPE
--      SYNTAX          Integer32 (1..255)
--      MAX-ACCESS      read-only
--      STATUS          current
--      DESCRIPTION
--              "This object specifies the entry of the time range ACL."
--      ::= { atiStkSwAACLTimeRangePeriodicConfigEntry 1 }

-- atiStkSwAACLTimeRangePeriodicName  OBJECT-TYPE
--      SYNTAX          DisplayString
--      MAX-ACCESS      read-write
--      STATUS          current
--      DESCRIPTION
--              "This object specifies the Name of the time range ACL."
--      ::= { atiStkSwAACLTimeRangePeriodicConfigEntry 2 }

-- atiStkSwAACLTimeRangePeriodicType  OBJECT-TYPE
--      SYNTAX          INTEGER {
--                              day (1),
--                              daily (2),
--                              weekdays (3),
--                              weekends (4)
--                              }
--      MAX-ACCESS  read-write
--      STATUS      current
--      DESCRIPTION
--              "This object specifies the type of the time range ACL."
--      ::= { atiStkSwAACLTimeRangePeriodicConfigEntry 3 }

-- atiStkSwAACLTimeRangePeriodicStartTime  OBJECT-TYPE
--      SYNTAX          DisplayString
--      MAX-ACCESS      read-write
--      STATUS          current
--      DESCRIPTION
--              "This object specifies the start time of the time range ACL."
--      ::= { atiStkSwAACLTimeRangePeriodicConfigEntry 4 }

-- atiStkSwAACLTimeRangePeriodicEndTime  OBJECT-TYPE
--      SYNTAX          DisplayString
--      MAX-ACCESS      read-write
--      STATUS          current
--      DESCRIPTION
--              "This object specifies the end time of the time range ACL."
--      ::= { atiStkSwAACLTimeRangePeriodicConfigEntry 5 }

-- atiStkSwAACLTimeRangePeriodicStatus  OBJECT-TYPE
--      SYNTAX          INTEGER {
--                              create (1),
--                              delete (2)
--                              }
--      MAX-ACCESS      read-write
--      STATUS          current
--      DESCRIPTION
--              "This object specifies the status of the time range ACL."
--      ::= { atiStkSwAACLTimeRangePeriodicConfigEntry 6 }


-- ***********************************************************
--
--                  M S T P    C O N F I G
--
-- ***********************************************************

--Mst config table
atiStkSwMSTPMstConfigTable  OBJECT IDENTIFIER ::= { atiStkSwMSTPGroup 1 }

atiStkSwMSTPMstRegion   OBJECT-TYPE
        SYNTAX          DisplayString
        MAX-ACCESS      read-write
        STATUS          current
        DESCRIPTION
                "Set the Region name for MSTP."
        ::= { atiStkSwMSTPMstConfigTable 1 }

atiStkSwMSTPMstRevision OBJECT-TYPE
        SYNTAX          Integer32 (0..255)
        MAX-ACCESS      read-write
        STATUS          current
        DESCRIPTION
                "Set the revision number for MSTP."
        ::= { atiStkSwMSTPMstConfigTable 2 }

--Instance table
atiStkSwMSTPMstInstanceConfigTable  OBJECT-TYPE
        SYNTAX          SEQUENCE OF AtiStkSwMSTPMstInstanceConfigEntry
        MAX-ACCESS      not-accessible
        STATUS          current
        DESCRIPTION
                "This table contains a mst-config Instance associated attributes."
        ::= { atiStkSwMSTPGroup 2 }

atiStkSwMSTPMstInstanceConfigEntry  OBJECT-TYPE
        SYNTAX          AtiStkSwMSTPMstInstanceConfigEntry
        MAX-ACCESS      not-accessible
        STATUS          current
        DESCRIPTION
                "This object specifies an entry in 'atiStkSwMSTPMstInstanceConfigTable'
                that describes the mst config in the switch."
        INDEX           { atiStkSwMSTPMstInstanceId }
        ::= { atiStkSwMSTPMstInstanceConfigTable 1 }

AtiStkSwMSTPMstInstanceConfigEntry ::=
        SEQUENCE {
                atiStkSwMSTPMstInstanceId               Integer32,
                atiStkSwMSTPMstInstanceVlan             Integer32,
                atiStkSwMSTPMstInstancePriority         Integer32
                }

atiStkSwMSTPMstInstanceId  OBJECT-TYPE
        SYNTAX          Integer32 (1..15)
        MAX-ACCESS      read-only
        STATUS          current
        DESCRIPTION
                "This object specifies the Instance ID for MSTP."
        ::= { atiStkSwMSTPMstInstanceConfigEntry 1 }

atiStkSwMSTPMstInstanceVlan  OBJECT-TYPE
        SYNTAX          Integer32 (1..4094)
        MAX-ACCESS      read-write
        STATUS          current
        DESCRIPTION
                "This object associates the Instance ID with vlanId for MSTP."
        ::= { atiStkSwMSTPMstInstanceConfigEntry 2 }

atiStkSwMSTPMstInstancePriority  OBJECT-TYPE
        SYNTAX          Integer32 (0..61440)
        MAX-ACCESS      read-write
        STATUS          current
        DESCRIPTION
                "This object associates the Instance ID with priority for MSTP."
        ::= { atiStkSwMSTPMstInstanceConfigEntry 3 }

--Interface level config for MSTP
atiStkSwMSTPMstInterfaceConfigTable  OBJECT-TYPE
        SYNTAX          SEQUENCE OF AtiStkSwMSTPMstInterfaceConfigEntry
        MAX-ACCESS      not-accessible
        STATUS          current
        DESCRIPTION
                "This table contains a mstp interface level config."
        ::= { atiStkSwMSTPGroup 3 }

atiStkSwMSTPMstInterfaceConfigEntry  OBJECT-TYPE
        SYNTAX          AtiStkSwMSTPMstInterfaceConfigEntry
        MAX-ACCESS      not-accessible
        STATUS          current
        DESCRIPTION
                "This object specifies an entry in 'atiStkSwMSTPMstInterfaceConfigTable'
                that describes the mstp interface levl config in the switch."
            INDEX       { atiStkSwMSTPMstInterfaceModuleId, atiStkSwMSTPMstInterfacePortId }
        ::= { atiStkSwMSTPMstInterfaceConfigTable 1 }

AtiStkSwMSTPMstInterfaceConfigEntry ::=
        SEQUENCE {
                atiStkSwMSTPMstInterfaceModuleId        Integer32,
                atiStkSwMSTPMstInterfacePortId          Integer32,
                atiStkSwMSTPMstInterfaceInstanceId      Integer32,
                atiStkSwMSTPMstInterfacePathCost        Integer32,
                atiStkSwMSTPMstInterfacePriority        Integer32
                }

atiStkSwMSTPMstInterfaceModuleId  OBJECT-TYPE
        SYNTAX          Integer32 (0..255)
        MAX-ACCESS      read-only
        STATUS          current
        DESCRIPTION
                "This object specifies the module ID for MSTP."
        ::= { atiStkSwMSTPMstInterfaceConfigEntry 1 }

atiStkSwMSTPMstInterfacePortId  OBJECT-TYPE
        SYNTAX          Integer32 (0..255)
        MAX-ACCESS      read-only
        STATUS          current
        DESCRIPTION
                "This object specifies the port ID for MSTP."
        ::= { atiStkSwMSTPMstInterfaceConfigEntry 2 }

atiStkSwMSTPMstInterfaceInstanceId  OBJECT-TYPE
        SYNTAX          Integer32(0..15)
        MAX-ACCESS      read-write
        STATUS          current
        DESCRIPTION
                "This object associates the port ID with instance id for MSTP."
        ::= { atiStkSwMSTPMstInterfaceConfigEntry 3 }

atiStkSwMSTPMstInterfacePathCost  OBJECT-TYPE
        SYNTAX          Integer32 (1..200000000)
        MAX-ACCESS      read-write
        STATUS          current
        DESCRIPTION
                "This object associates the path cost with instance id for MSTP."
        ::= { atiStkSwMSTPMstInterfaceConfigEntry 4 }

atiStkSwMSTPMstInterfacePriority  OBJECT-TYPE
        SYNTAX          Integer32 (0..61440)
        MAX-ACCESS      read-write
        STATUS          current
        DESCRIPTION
                "This object associates the priority with instance id for MSTP."
        ::= { atiStkSwMSTPMstInterfaceConfigEntry 5 }


-- ***********************************************************
--
--                  M V R    C O N F I G
--
-- ***********************************************************

--MVR config table
atiStkSwMVRConfigTable  OBJECT IDENTIFIER ::= { atiStkSwMVRGroup 1 }

atiStkSwMVRStatus       OBJECT-TYPE
        SYNTAX          INTEGER {
                                enable (1),
                                disable (2)
                                }
        MAX-ACCESS      read-write
        STATUS          current
        DESCRIPTION
                "Set the status for MVR."
        ::= { atiStkSwMVRConfigTable 1 }

atiStkSwMVRGroupIp      OBJECT-TYPE
        SYNTAX          IpAddress
        MAX-ACCESS      read-write
        STATUS          current
        DESCRIPTION
                "Set the group IP address for MVR."
        ::= { atiStkSwMVRConfigTable 2 }

atiStkSwMVRVlan         OBJECT-TYPE
        SYNTAX          Integer32 (1..4094)
        MAX-ACCESS      read-write
        STATUS          current
        DESCRIPTION
                "Set the group IP address for MVR."
        ::= { atiStkSwMVRConfigTable 3 }

--Interface level MVR table
atiStkSwMVRInterfaceConfigTable  OBJECT-TYPE
        SYNTAX          SEQUENCE OF AtiStkSwMVRInterfaceConfigEntry
        MAX-ACCESS      not-accessible
        STATUS          current
        DESCRIPTION
                "This table contains a MVR interface level attributes."
        ::= { atiStkSwMVRGroup 2 }

atiStkSwMVRInterfaceConfigEntry  OBJECT-TYPE
        SYNTAX          AtiStkSwMVRInterfaceConfigEntry
        MAX-ACCESS      not-accessible
        STATUS          current
        DESCRIPTION
                "This object specifies an entry in 'atiStkSwMVRInterfaceConfigTable'
                that describes the MVR config in switch."
        INDEX           { atiStkSwMVRInterfaceIndex }
        ::= { atiStkSwMVRInterfaceConfigTable 1 }

AtiStkSwMVRInterfaceConfigEntry ::=
        SEQUENCE {
                atiStkSwMVRInterfaceIndex               Integer32,
                atiStkSwMVRInterfacePortId              DisplayString,
                atiStkSwMVRInterfaceType                INTEGER
                }

atiStkSwMVRInterfaceIndex  OBJECT-TYPE
        SYNTAX          Integer32 (0..255)
        MAX-ACCESS      read-only
        STATUS          current
        DESCRIPTION
                "This object specifies the index for MVR."
        ::= { atiStkSwMVRInterfaceConfigEntry 1 }

atiStkSwMVRInterfacePortId  OBJECT-TYPE
        SYNTAX          DisplayString
        MAX-ACCESS      read-only
        STATUS          current
        DESCRIPTION
                "This object specifies the port ID for MVR."
        ::= { atiStkSwMVRInterfaceConfigEntry 2 }

atiStkSwMVRInterfaceType  OBJECT-TYPE
        SYNTAX          INTEGER {
                                source (1),
                                receiver (2),
                                none (3)
                                }
        MAX-ACCESS      read-write
        STATUS          current
        DESCRIPTION
                "This object associates the type with port Id for MSTP."
        ::= { atiStkSwMVRInterfaceConfigEntry 3 }

-- MVR Cofig Group Ip table
atiStkSwMVRConfigGroupIpTable  OBJECT-TYPE
        SYNTAX          SEQUENCE OF AtiStkSwMVRConfigGroupIpEntry
        MAX-ACCESS      not-accessible
        STATUS          current
        DESCRIPTION
                "This table contains a MVR Group ip attributes."
        ::= { atiStkSwMVRGroup 3 }

atiStkSwMVRConfigGroupIpEntry  OBJECT-TYPE
        SYNTAX          AtiStkSwMVRConfigGroupIpEntry
        MAX-ACCESS      not-accessible
        STATUS          current
        DESCRIPTION
                "This object specifies an entry in 'atiStkSwMVRConfigGroupIpTable'
                that describes the MVR config Group ip in switch."
        INDEX           { atiStkSwMVRGroupIpIndex }
        ::= { atiStkSwMVRConfigGroupIpTable 1 }

AtiStkSwMVRConfigGroupIpEntry ::=
        SEQUENCE {
                atiStkSwMVRGroupIpIndex                 Integer32,
                atiStkSwMVRGroupIp                      DisplayString
                }

atiStkSwMVRGroupIpIndex OBJECT-TYPE
        SYNTAX          Integer32 (0..255)
        MAX-ACCESS      read-only
        STATUS          current
        DESCRIPTION
                "This object specifies the index for MVR Group ip."
        ::= { atiStkSwMVRConfigGroupIpEntry 1 }

atiStkSwMVRGroupIp      OBJECT-TYPE
        SYNTAX          DisplayString
        MAX-ACCESS      read-write
        STATUS          current
        DESCRIPTION
                "This object specifies the group ip for MVR."
        ::= { atiStkSwMVRConfigGroupIpEntry 2 }


-- ***********************************************************
--
--                  P S T A C K    C O N F I G
--
-- ***********************************************************

--PSTACK config table
atiStkSwPSTACKConfigTable  OBJECT IDENTIFIER ::= { atiStkSwPSTACKGroup 1 }

atiStkSwPSTACKNoofModules  OBJECT-TYPE
        SYNTAX          Integer32
        MAX-ACCESS      read-only
        STATUS          current
        DESCRIPTION     "Set the Number of modules for PStack."
        ::= { atiStkSwPSTACKConfigTable 1 }

atiStkSwPSTACKTopology  OBJECT-TYPE
        SYNTAX          INTEGER {
                                none (0),
                                chain (1),
                                ring (2),
                                standalone (3)
                                }
        MAX-ACCESS      read-only
        STATUS          current
        DESCRIPTION
                "Set the Topology for PStack."
        ::= { atiStkSwPSTACKConfigTable 2 }

atiStkSwPSTACKLclModID  OBJECT-TYPE
        SYNTAX          Integer32 (1..4094)
        MAX-ACCESS      read-only
        STATUS          current
        DESCRIPTION
                "Set the Local Module ID for PStack."
        ::= { atiStkSwPSTACKConfigTable 3 }

atiStkSwPSTACKLclMacAdd OBJECT-TYPE
        SYNTAX          MacAddress
        MAX-ACCESS      read-only
        STATUS          current
        DESCRIPTION
                "Set the Mac Address for PStack."
        ::= { atiStkSwPSTACKConfigTable 4 }

atiStkSwPSTACKMasterModId  OBJECT-TYPE
        SYNTAX          Integer32 (1..4094)
        MAX-ACCESS      read-only
        STATUS          current
        DESCRIPTION
                "Set the Master Module ID for PStack."
        ::= { atiStkSwPSTACKConfigTable 5 }

atiStkSwPSTACKMasterMacAdd  OBJECT-TYPE
        SYNTAX          MacAddress
        MAX-ACCESS      read-only
        STATUS          current
        DESCRIPTION
                "Set the Master Mac Address for PStack."
        ::= { atiStkSwPSTACKConfigTable 6 }

atiStkSwPSTACKSlaveMacAdd1  OBJECT-TYPE
        SYNTAX          MacAddress
        MAX-ACCESS      read-only
        STATUS          current
        DESCRIPTION
                "Set the Slave Mac Address 1 for PStack."
        ::= { atiStkSwPSTACKConfigTable 7 }

atiStkSwPSTACKSlaveMacAdd2  OBJECT-TYPE
        SYNTAX          MacAddress
        MAX-ACCESS      read-only
        STATUS          current
        DESCRIPTION
                "Set the Slave Mac Address 2 for PStack."
        ::= { atiStkSwPSTACKConfigTable 8 }

atiStkSwPSTACKSlaveMacAdd3  OBJECT-TYPE
        SYNTAX          MacAddress
        MAX-ACCESS      read-only
        STATUS          current
        DESCRIPTION
                "Set the Slave Mac Address 3 for PStack."
        ::= { atiStkSwPSTACKConfigTable 9 }

atiStkSwPSTACKSlaveMacAdd4  OBJECT-TYPE
        SYNTAX          MacAddress
        MAX-ACCESS      read-only
        STATUS          current
        DESCRIPTION
                "Set the Slave Mac Address 4 for PStack."
        ::= { atiStkSwPSTACKConfigTable 10 }

atiStkSwPSTACKSlaveMacAdd5  OBJECT-TYPE
        SYNTAX          MacAddress
        MAX-ACCESS      read-only
        STATUS          current
        DESCRIPTION
                "Set the Slave Mac Address 5 for PStack."
        ::= { atiStkSwPSTACKConfigTable 11 }

atiStkSwPSTACKSlaveMacAdd6  OBJECT-TYPE
        SYNTAX          MacAddress
        MAX-ACCESS      read-only
        STATUS          current
        DESCRIPTION
                "Set the Slave Mac Address 6 for PStack."
        ::= { atiStkSwPSTACKConfigTable 12 }

atiStkSwPSTACKSlaveMacAdd7  OBJECT-TYPE
        SYNTAX          MacAddress
        MAX-ACCESS      read-only
        STATUS          current
        DESCRIPTION
                "Set the Slave Mac Address 7 for PStack."
        ::= { atiStkSwPSTACKConfigTable 13 }

--Interface level PStack table
atiStkSwPSTACKInterfaceConfigTable  OBJECT-TYPE
        SYNTAX          SEQUENCE OF AtiStkSwPSTACKInterfaceConfigEntry
        MAX-ACCESS      not-accessible
        STATUS          current
        DESCRIPTION
                "This table contains a PStack interface level attributes."
        ::= { atiStkSwPSTACKGroup 2 }

atiStkSwPSTACKInterfaceConfigEntry  OBJECT-TYPE
        SYNTAX          AtiStkSwPSTACKInterfaceConfigEntry
        MAX-ACCESS      not-accessible
        STATUS          current
        DESCRIPTION
                "This object specifies an entry in 'atiStkSwPStackInterfaceConfigTable'
                that describes the PStack config in switch."
        INDEX           { atiStkSwPSTACKInterfaceDeviceId }
        ::= { atiStkSwPSTACKInterfaceConfigTable 1 }

AtiStkSwPSTACKInterfaceConfigEntry ::=
        SEQUENCE {
                atiStkSwPSTACKInterfaceDeviceId         Integer32,
                atiStkSwPSTACKInterfaceMacAddress       MacAddress,
                atiStkSwPSTACKInterfaceSwVersion        DisplayString,
                atiStkSwPSTACKInterfaceModel            DisplayString
                }

atiStkSwPSTACKInterfaceDeviceId  OBJECT-TYPE
        SYNTAX          Integer32  (0..255)
        MAX-ACCESS      read-only
        STATUS          current
        DESCRIPTION
                "This object specifies the Device ID for PStack."
        ::= { atiStkSwPSTACKInterfaceConfigEntry 1 }

atiStkSwPSTACKInterfaceMacAddress  OBJECT-TYPE
        SYNTAX          MacAddress
        MAX-ACCESS      read-only
        STATUS          current
        DESCRIPTION
                "This object associates the Mac Address with Device Id for PStack."
        ::= { atiStkSwPSTACKInterfaceConfigEntry 2 }

atiStkSwPSTACKInterfaceSwVersion  OBJECT-TYPE
        SYNTAX          DisplayString
        MAX-ACCESS      read-only
        STATUS          current
        DESCRIPTION
                "This object associates the Software Version with Device Id for PStack."
        ::= { atiStkSwPSTACKInterfaceConfigEntry 3 }

atiStkSwPSTACKInterfaceModel  OBJECT-TYPE
        SYNTAX          DisplayString
        MAX-ACCESS      read-only
        STATUS          current
        DESCRIPTION
                "This object associates the Model type with Device Id for PStack."
        ::= { atiStkSwPSTACKInterfaceConfigEntry 4 }

--PSTACK config device ID table
atiStkSwPSTACKDeviceIDConfigTable              OBJECT IDENTIFIER ::= { atiStkSwPSTACKGroup 3 }
atiStkSwPSTACKDeviceID  OBJECT-TYPE
        SYNTAX          Integer32
        MAX-ACCESS      read-write
        STATUS          current
        DESCRIPTION
                "Set the Device ID for PSTACK."
        ::= { atiStkSwPSTACKDeviceIDConfigTable 1 }

--PSTACK config reboot table
atiStkSwPSTACKRebootConfigTable                OBJECT IDENTIFIER ::= { atiStkSwPSTACKGroup 4 }
atiStkSwPSTACKRebootDeviceID  OBJECT-TYPE
        SYNTAX          INTEGER {
                                device1 (1),
                                device2 (2),
                                device3 (3),
                                device4 (4),
                                device5 (5),
                                device6 (6),
                                device7 (7),
                                device8 (8),
                                all (9)
                                }
        MAX-ACCESS      read-write
        STATUS          current
        DESCRIPTION
                "Set Reboot for PSTACK."
        ::= { atiStkSwPSTACKRebootConfigTable 1 }


-- ***********************************************************
--
--                  L L D P    C O N F I G
--
-- ***********************************************************

-- atiStkSwLldpConfig

atiStkSwLldpConfig      OBJECT IDENTIFIER ::= { atiStkSwLldpGroup 1 }

atiStkSwLldpRun         OBJECT-TYPE
        SYNTAX          INTEGER {
                                enabled (1),
                                disabled (2)
                                }
        MAX-ACCESS      read-write
        STATUS          current
        DESCRIPTION
                "The operational mode, whether enabled or disabled, of LLDP on the device."
        DEFVAL          { 2 }
        ::= { atiStkSwLldpConfig 1 }

atiStkSwLldpTimer       OBJECT-TYPE
        SYNTAX          Integer32 (5..32768)
        UNITS           "seconds"
        MAX-ACCESS      read-write
        STATUS          current
        DESCRIPTION
                "The interval at which LLDP frames are transmitted on
                behalf of this LLDP agent."
        REFERENCE
                "IEEE 802.1AB-2005 10.5.3.3"
        DEFVAL          { 30 }
        ::= { atiStkSwLldpConfig 2 }

atiStkSwLldpHoldMultiplier  OBJECT-TYPE
        SYNTAX          Integer32 (2..10)
        MAX-ACCESS      read-write
        STATUS          current
        DESCRIPTION
                "The time-to-live value expressed as a multiple of the
                atiStkSwLldpTimer object."
        REFERENCE
                "IEEE 802.1AB-2005 10.5.3.3"
        DEFVAL          { 4 }
        ::= { atiStkSwLldpConfig 3 }

atiStkSwLldpReinit      OBJECT-TYPE
        SYNTAX          Integer32 (1..10)
        UNITS           "seconds"
        MAX-ACCESS      read-write
        STATUS          current
        DESCRIPTION
                "The atiStkSwLldpReinit indicates the delay (in units of
                seconds) from when lldp feature of a particular port becomes
                'disabled' until re-initialization will be attempted."
        REFERENCE
                "IEEE 802.1AB-2005 10.5.3.3"
        DEFVAL          { 2 }
        ::= { atiStkSwLldpConfig 4 }

atiStkSwLldpTxDelay     OBJECT-TYPE
        SYNTAX          Integer32 (1..8192)
        UNITS           "seconds"
        MAX-ACCESS      read-write
        STATUS          current
        DESCRIPTION
                "The atiStkSwLldpTxDelay indicates the delay (in units
                of seconds) between successive LLDP frame transmissions
                initiated by value/status changes in the LLDP local systems
                MIB."
        REFERENCE
                "IEEE 802.1AB-2005 10.5.3.3"
        DEFVAL          { 2 }
        ::= { atiStkSwLldpConfig 5 }

atiStkSwLldpNotificationInterval  OBJECT-TYPE
        SYNTAX          Integer32 (5..3600)
        UNITS           "seconds"
        MAX-ACCESS      read-write
        STATUS          current
        DESCRIPTION
                "This object controls the transmission of LLDP notifications.
                The agent must not generate more than one lldpRemTablesChange
                notification-event in the indicated period."
        DEFVAL          { 5 }
        ::= { atiStkSwLldpConfig 6 }

atiStkSwLldpFaststartCount  OBJECT-TYPE
        SYNTAX          Integer32 (1..10)
        UNITS           "seconds"
        MAX-ACCESS      read-write
        STATUS          current
        DESCRIPTION
                "The atiStkSwLldpFaststartCoun"
        REFERENCE
                "IEEE"
        DEFVAL          { 3 }
        ::= { atiStkSwLldpConfig 7 }

atiStkSwLldpNonStrictMedTlvOrderCheck  OBJECT-TYPE
        SYNTAX          INTEGER {
                                enabled (1),
                                disabled (2)
                                }
        MAX-ACCESS      read-write
        STATUS          current
        DESCRIPTION
                "The atiStkSwLldpNonStrictMedTlvOrderCheck"
        DEFVAL          { 2 }
        ::= { atiStkSwLldpConfig 8 }

atiStkSwLldpConfigPortTable  OBJECT-TYPE
        SYNTAX          SEQUENCE OF AtiStkSwLldpConfigPortEntry
        MAX-ACCESS      not-accessible
        STATUS          current
        DESCRIPTION
                "The table that controls LLDP frame transmission on individual
                ports."
        ::= { atiStkSwLldpConfig 9 }

atiStkSwLldpConfigPortEntry  OBJECT-TYPE
        SYNTAX          AtiStkSwLldpConfigPortEntry
        MAX-ACCESS      not-accessible
        STATUS          current
        DESCRIPTION
                "LLDP configuration information for a particular port.
                This configuration parameter controls the transmission and
                the reception of LLDP frames on those ports whose rows are
                created in this table."
        INDEX           { atiStkSwLldpConfigModuleId, atiStkSwLldpConfigPortId }
        ::= { atiStkSwLldpConfigPortTable 1 }

AtiStkSwLldpConfigPortEntry ::=
        SEQUENCE {
                atiStkSwLldpConfigModuleId              Integer32,
                atiStkSwLldpConfigPortId                Integer32,
                atiStkSwLldpConfigDirection             INTEGER,
                atiStkSwLldpConfigNotif                 INTEGER,
                atiStkSwLldpConfigMgmtAddr              IpAddress,
                atiStkSwLldpConfigTlvSelect             BITS,
                atiStkSwLldpConfigTlvDeselect           BITS,
                atiStkSwLldpConfigMedNotif              INTEGER,
                atiStkSwLldpConfigMedTlvSelect          BITS,
                atiStkSwLldpConfigMedTlvDeselect        BITS,
                atiStkSwLldpConfigLocCoord              Integer32,
                atiStkSwLldpConfigLocCivic              Integer32,
                atiStkSwLldpConfigLocElin               Integer32
        }

atiStkSwLldpConfigModuleId  OBJECT-TYPE
        SYNTAX          Integer32 (1..8)
        MAX-ACCESS      read-only
        STATUS          current
        DESCRIPTION
                "This object specifies the ID of a module present in the switch
                stack."
        ::= { atiStkSwLldpConfigPortEntry 1 }

atiStkSwLldpConfigPortId  OBJECT-TYPE
        SYNTAX          Integer32 (1..50)
        MAX-ACCESS      read-only
        STATUS          current
        DESCRIPTION
                "The index value used to identify the port component
                (contained in the local chassis with the LLDP agent)
                associated with this entry.

                The value of this object is used as a port index to the
                atiStkSwLldpConfigPortTable."
        ::= { atiStkSwLldpConfigPortEntry 2 }

atiStkSwLldpConfigDirection  OBJECT-TYPE
        SYNTAX          INTEGER {
                                transmit (1),
                                receive (2),
                                both (3),
                                none (4)
                                }
        MAX-ACCESS      read-write
        STATUS          current
        DESCRIPTION
                "This object specifies the operation mode of the LLDP
                for the indicated port - whether to transmit and/or receive
                LLDP package, or do nothing."
        DEFVAL          { both }
        ::= { atiStkSwLldpConfigPortEntry 3 }

atiStkSwLldpConfigNotif OBJECT-TYPE
        SYNTAX          INTEGER {
                                enabled (1),
                                disabled (2)
                                }
        MAX-ACCESS      read-write
        STATUS          current
        DESCRIPTION
                "The atiStkSwLldpConfigNotif controls, on a per
                port basis, whether or not notifications from the agent
                are enabled. The value enabled(1) means that notifications are
                enabled; the value disabled(2) means that they are not."
        DEFVAL          { disabled }
        ::= { atiStkSwLldpConfigPortEntry 4 }

atiStkSwLldpConfigMgmtAddr      OBJECT-TYPE
        SYNTAX          IpAddress
        MAX-ACCESS      read-only
        STATUS          current
        DESCRIPTION
                "This object displays the IPv4 address to be advertised to neighbors
                (via the Management Address TLV) via specified ports."
        DEFVAL          { '00000000'h } -- 0.0.0.0
        ::= { atiStkSwLldpConfigPortEntry 5 }

atiStkSwLldpConfigTlvSelect  OBJECT-TYPE
        SYNTAX          BITS    {
                                portDesc (31),
                                sysName (30),
                                sysDesc (29),
                                sysCap (28),
                                mgmtAddr (27),
                                portVlan (26),
                                portAndProtocolVlans (25),
                                vlanNames (24),
                                protocolIds (23),
                                macPhyConfig (22),
                                powerMgmt (21),
                                linkAggregation (20),
                                maxFrameSize (19)
                                }
        MAX-ACCESS      read-write
        STATUS          current
        DESCRIPTION
                "This enables specified optional TLVs for transmission in LLDP
                advertisement via the specified ports."
        ::= { atiStkSwLldpConfigPortEntry 6 }

atiStkSwLldpConfigTlvDeselect  OBJECT-TYPE
        SYNTAX          BITS    {
                                portDesc (31),
                                sysName (30),
                                sysDesc (29),
                                sysCap (28),
                                mgmtAddr (27),
                                portVlan (26),
                                portAndProtocolVlans (25),
                                vlanNames (24),
                                protocolIds (23),
                                macPhyConfig (22),
                                powerMgmt (21),
                                linkAggregation (20),
                                maxFrameSize (19)
                                }
        MAX-ACCESS      read-write
        STATUS          current
        DESCRIPTION
                "This disables specified optional TLVs for transmission in LLDP
                advertisement via the specified ports."
        ::= { atiStkSwLldpConfigPortEntry 7 }

atiStkSwLldpConfigMedNotif  OBJECT-TYPE
        SYNTAX          INTEGER {
                                enabled (1),
                                disabled (2)
                                }
        MAX-ACCESS      read-write
        STATUS          current
        DESCRIPTION
                "The atiStkSwLldpConfigMedNotif controls, on a per
                port basis, whether or not MED notifications from the agent
                are enabled. The value enabled(1) means that notifications are
                enabled; the value disabled(2) means that they are not."
        DEFVAL          { disabled }
        ::= { atiStkSwLldpConfigPortEntry 8 }

atiStkSwLldpConfigMedTlvSelect  OBJECT-TYPE
        SYNTAX          BITS    {
                                capabilities (31),
                                networkPolicy (30),
                                location (29),
                                powerMgmtExt (28),
                                inventoryMgmt (27)
                                }
        MAX-ACCESS      read-write
        STATUS          current
        DESCRIPTION
                "This enables specified MED TLVs for transmission in LLDP
                advertisement via the specified ports."
        ::= { atiStkSwLldpConfigPortEntry 9 }

atiStkSwLldpConfigMedTlvDeselect  OBJECT-TYPE
        SYNTAX          BITS    {
                                capabilities (31),
                                networkPolicy (30),
                                location (29),
                                powerMgmtExt (28),
                                inventoryMgmt (27)
                                }
        MAX-ACCESS      read-write
        STATUS          current
        DESCRIPTION
                "This disables specified MED TLVs for transmission in LLDP
                advertisement via the specified ports."
        ::= { atiStkSwLldpConfigPortEntry 10 }

atiStkSwLldpConfigLocCoord  OBJECT-TYPE
        SYNTAX          Integer32
        MAX-ACCESS      read-write
        STATUS          current
        DESCRIPTION
                "This assigns an LLDP Coordinate location information to
                the specified ports. Set 0 to reset."
        ::= { atiStkSwLldpConfigPortEntry 11 }

atiStkSwLldpConfigLocCivic  OBJECT-TYPE
        SYNTAX          Integer32
        MAX-ACCESS      read-write
        STATUS          current
        DESCRIPTION
                "This assigns an LLDP Civic location information to
                the specified ports. Set 0 to reset."
        ::= { atiStkSwLldpConfigPortEntry 12 }

atiStkSwLldpConfigLocElin  OBJECT-TYPE
        SYNTAX          Integer32
        MAX-ACCESS      read-write
        STATUS          current
        DESCRIPTION
                "This assigns an LLDP Elin location information to
                the specified ports. Set 0 to reset."
        ::= { atiStkSwLldpConfigPortEntry 13 }


--  ***********************************************************
--
--                   L L D P    S T A T S
--
--  ***********************************************************

-- atiStkSwLldpStats

atiStkSwLldpStats       OBJECT IDENTIFIER ::= { atiStkSwLldpGroup 2 }

atiStkSwLldpStatsGlobalReset  OBJECT-TYPE
        SYNTAX          INTEGER {
                                yes (1),
                                no (2)
                                }
        MAX-ACCESS      read-write
        STATUS          current
        DESCRIPTION
                "This clears all the LLDP statistics (packet and event counters)."
        ::= { atiStkSwLldpStats 1 }

atiStkSwLldpStatsTotalFramesOut  OBJECT-TYPE
        SYNTAX          Counter32
        MAX-ACCESS      read-only
        STATUS          current
        DESCRIPTION
                "The number of LLDP frames transmitted by this LLDP agent."
        ::= { atiStkSwLldpStats 2 }

atiStkSwLldpStatsTotalFramesIn  OBJECT-TYPE
        SYNTAX          Counter32
        MAX-ACCESS      read-only
        STATUS          current
        DESCRIPTION
                "The number of valid LLDP frames received by this LLDP agent."
        ::= { atiStkSwLldpStats 3 }

atiStkSwLldpStatsTotalFramesInError  OBJECT-TYPE
        SYNTAX          Counter32
        MAX-ACCESS      read-only
        STATUS          current
        DESCRIPTION
                "The number of invalid LLDP frames received by this LLDP
                agent."
        ::= { atiStkSwLldpStats 4 }

atiStkSwLldpStatsTotalFramesInDropped  OBJECT-TYPE
        SYNTAX          Counter32
        MAX-ACCESS      read-only
        STATUS          current
        DESCRIPTION
                "The number of LLDP frames received by this LLDP agent,
                and then discarded for any reason."
        ::= { atiStkSwLldpStats 5 }

atiStkSwLldpStatsTotalTLVsUnrecognized  OBJECT-TYPE
        SYNTAX          Counter32
        MAX-ACCESS      read-only
        STATUS          current
        DESCRIPTION
                "The number of LLDP TLVs received on the given port that
                are not recognized by this LLDP agent."
        ::= { atiStkSwLldpStats 6 }

atiStkSwLldpStatsTotalTLVsDiscarded  OBJECT-TYPE
        SYNTAX          Counter32
        MAX-ACCESS      read-only
        STATUS          current
        DESCRIPTION
                "The number of LLDP TLVs discarded for any reason by this LLDP
                agent."
        ::= { atiStkSwLldpStats 7 }

atiStkSwLldpStatsTotalNewNeighbors  OBJECT-TYPE
        SYNTAX          Counter32
        MAX-ACCESS      read-only
        STATUS          current
        DESCRIPTION
                "The number of times the complete set of information
                advertised by a particular MSAP has been inserted into the
                Neighbor/Remote table."
        ::= { atiStkSwLldpStats 8 }

atiStkSwLldpStatsTotalNeighborsDeleted  OBJECT-TYPE
        SYNTAX          Counter32
        MAX-ACCESS      read-only
        STATUS          current
        DESCRIPTION
                "The number of times the complete set of information
                advertised by a particular MSAP has been deleted from
                the Neighbor/Remote table."
        ::= { atiStkSwLldpStats 9 }

atiStkSwLldpStatsTotalNeighborsDropped  OBJECT-TYPE
        SYNTAX          Counter32
        MAX-ACCESS      read-only
        STATUS          current
        DESCRIPTION
                "The number of times the complete set of information
                advertised by a particular MSAP could not be entered into
                the Neighbor/Remote table."
        ::= { atiStkSwLldpStats 10 }

atiStkSwLldpStatsTotalNeighborsAgedOut  OBJECT-TYPE
        SYNTAX          Counter32
        MAX-ACCESS      read-only
        STATUS          current
        DESCRIPTION
                "The number of times the complete set of information
                advertised by a particular MSAP has been deleted from tables
                contained in the Neighbor/Remote table."
        ::= { atiStkSwLldpStats 11 }

atiStkSwLldpStatsPortTable  OBJECT-TYPE
        SYNTAX          SEQUENCE OF AtiStkSwLldpStatsPortEntry
        MAX-ACCESS      not-accessible
        STATUS          current
        DESCRIPTION
                "A table containing LLDP transmission and reception statistics for
                individual ports."
        ::= { atiStkSwLldpStats 12 }

atiStkSwLldpStatsPortEntry  OBJECT-TYPE
        SYNTAX          AtiStkSwLldpStatsPortEntry
        MAX-ACCESS      not-accessible
        STATUS          current
        DESCRIPTION
                "LLDP frame transmission and reception statistics for a particular port."
        -- INDEX           { atiStkSwLldpStatsModuleId, atiStkSwLldpStatsPortId }
        INDEX           { atiStkSwLldpStatsPortId }
        ::= { atiStkSwLldpStatsPortTable 1 }

AtiStkSwLldpStatsPortEntry ::=
        SEQUENCE {
                atiStkSwLldpStatsModuleId               Integer32,
                atiStkSwLldpStatsPortId                 Integer32,
                atiStkSwLldpStatsFramesOut              Counter32,
                atiStkSwLldpStatsFramesIn               Counter32,
                atiStkSwLldpStatsFramesInError          Counter32,
                atiStkSwLldpStatsFramesInDropped        Counter32,
                atiStkSwLldpStatsTLVsUnrecognized       Counter32,
                atiStkSwLldpStatsTLVsDiscarded          Counter32,
                atiStkSwLldpStatsNewNeighbors           Counter32,
                atiStkSwLldpStatsNeighborsDeleted       Counter32,
                atiStkSwLldpStatsNeighborsDropped       Counter32,
                atiStkSwLldpStatsNeighborsAgedOut       Counter32,
                atiStkSwLldpStatsReset                  INTEGER
        }

atiStkSwLldpStatsModuleId  OBJECT-TYPE
        SYNTAX          Integer32 --(1..8)
        MAX-ACCESS      read-only
        STATUS          current
        DESCRIPTION
                "This object specifies the ID of a module present in the switch
                stack."
        ::= { atiStkSwLldpStatsPortEntry 1 }

atiStkSwLldpStatsPortId OBJECT-TYPE
        SYNTAX          Integer32 (1..50)
        MAX-ACCESS      read-only
        STATUS          current
        DESCRIPTION
                "The index value used to identify the port component
                (contained in the local chassis with the LLDP agent)
                associated with this entry.

                The value of this object is used as a port index to the
                lldpStatsTable."
        ::= { atiStkSwLldpStatsPortEntry 2 }

atiStkSwLldpStatsFramesOut  OBJECT-TYPE
        SYNTAX          Counter32
        MAX-ACCESS      read-only
        STATUS          current
        DESCRIPTION
                "The number of LLDP frames transmitted by this LLDP agent
                on the indicated port."
        REFERENCE
                "IEEE 802.1AB-2005 10.5.2.1"
        ::= { atiStkSwLldpStatsPortEntry 3 }

atiStkSwLldpStatsFramesIn  OBJECT-TYPE
        SYNTAX          Counter32
        MAX-ACCESS      read-only
        STATUS          current
        DESCRIPTION
                "The number of valid LLDP frames received by this LLDP agent
                on the indicated port, while this LLDP agent is enabled."
        REFERENCE
                "IEEE 802.1AB-2005 10.5.2.2"
        ::= { atiStkSwLldpStatsPortEntry 4 }

atiStkSwLldpStatsFramesInError  OBJECT-TYPE
        SYNTAX          Counter32
        MAX-ACCESS      read-only
        STATUS          current
        DESCRIPTION
                "The number of invalid LLDP frames received by this LLDP
                agent on the indicated port, while this LLDP agent is enabled."
        REFERENCE
                "IEEE 802.1AB-2005 10.5.2.2"
        ::= { atiStkSwLldpStatsPortEntry 5 }

atiStkSwLldpStatsFramesInDropped  OBJECT-TYPE
        SYNTAX          Counter32
        MAX-ACCESS      read-only
        STATUS          current
        DESCRIPTION
                "The number of LLDP frames received by this LLDP agent on
                the indicated port, and then discarded for any reason.
                This counter can provide an indication that LLDP header
                formating problems may exist with the local LLDP agent in
                the sending system or that LLDPDU validation problems may
                exist with the local LLDP agent in the receiving system."
        REFERENCE
                "IEEE 802.1AB-2005 10.5.2.2"
        ::= { atiStkSwLldpStatsPortEntry 6 }

atiStkSwLldpStatsTLVsUnrecognized  OBJECT-TYPE
        SYNTAX          Counter32
        MAX-ACCESS      read-only
        STATUS          current
        DESCRIPTION
                "The number of LLDP TLVs received on the given port that
                are not recognized by this LLDP agent on the indicated port.

                An unrecognized TLV is referred to as the TLV whose type value
                is in the range of reserved TLV types (000 1001 - 111 1110)
                in Table 9.1 of IEEE Std 802.1AB-2005.  An unrecognized
                TLV may be a basic management TLV from a later LLDP version."
        REFERENCE
                "IEEE 802.1AB-2005 10.5.2.2"
        ::= { atiStkSwLldpStatsPortEntry 7 }

atiStkSwLldpStatsTLVsDiscarded  OBJECT-TYPE
        SYNTAX          Counter32
        MAX-ACCESS      read-only
        STATUS          current
        DESCRIPTION
                "The number of LLDP TLVs discarded for any reason by this LLDP
                agent on the indicated port."
        REFERENCE
                "IEEE 802.1AB-2005 10.5.2.2"
        ::= { atiStkSwLldpStatsPortEntry 8 }

atiStkSwLldpStatsNewNeighbors  OBJECT-TYPE
        SYNTAX          Counter32
        MAX-ACCESS      read-only
        STATUS          current
        DESCRIPTION
                "The number of times the complete set of information
                advertised by a particular MSAP has been inserted into tables
                contained in the Neighbor/Remote table associated with the
                indicated port."
        ::= { atiStkSwLldpStatsPortEntry 9 }

atiStkSwLldpStatsNeighborsDeleted  OBJECT-TYPE
        SYNTAX          Counter32
        MAX-ACCESS      read-only
        STATUS          current
        DESCRIPTION
                "The number of times the complete set of information
                advertised by a particular MSAP has been deleted from
                the Neighbor/Remote table associated with the indicated port."
        ::= { atiStkSwLldpStatsPortEntry 10 }

atiStkSwLldpStatsNeighborsDropped  OBJECT-TYPE
        SYNTAX          Counter32
        MAX-ACCESS      read-only
        STATUS          current
        DESCRIPTION
                "The number of times the complete set of information
                advertised by a particular MSAP could not be entered into
                the Neighbor/Remote table associated with the indicated
                port because of insufficient resources."
        ::= { atiStkSwLldpStatsPortEntry 11 }

atiStkSwLldpStatsNeighborsAgedOut  OBJECT-TYPE
        SYNTAX          Counter32
        MAX-ACCESS      read-only
        STATUS          current
        DESCRIPTION
                "The counter that represents the number of age-outs that
                occurred on a given port.  An age-out is the number of
                times the complete set of information advertised by a
                particular MSAP has been deleted from tables contained in
                the Neighbor/Remote table because the information timeliness
                interval has expired."
        REFERENCE
                "IEEE 802.1AB-2005 10.5.2.2"
        ::= { atiStkSwLldpStatsPortEntry 12 }

atiStkSwLldpStatsReset  OBJECT-TYPE
        SYNTAX          INTEGER {
                                yes (1),
                                no (2)
                                }
        MAX-ACCESS      read-write
        STATUS          current
        DESCRIPTION
                "This clears all the LLDP statistics (packet and event counters)
                associated with the indicated port."
        ::= { atiStkSwLldpStatsPortEntry 13 }


--  ***********************************************************
--
--          L O C A L    S Y S T E M    D A T A
--
--  ***********************************************************

-- atiStkSwLldpLocalData

atiStkSwLldpLocalData   OBJECT IDENTIFIER ::= { atiStkSwLldpGroup 3 }

atiStkSwLldpLocalInfoTable  OBJECT-TYPE
        SYNTAX          SEQUENCE OF AtiStkSwLldpLocalInfoEntry
        MAX-ACCESS      not-accessible
        STATUS          current
        DESCRIPTION
                "This table contains one or more rows per port information
                associated with the local system known to this agent."
        ::= { atiStkSwLldpLocalData 1 }

atiStkSwLldpLocalInfoEntry  OBJECT-TYPE
        SYNTAX          AtiStkSwLldpLocalInfoEntry
        MAX-ACCESS      not-accessible
        STATUS          current
        DESCRIPTION
                "Information about a particular port component."
        -- INDEX           { atiStkSwLldpLocModuleId, atiStkSwLldpLocPortNum }
        INDEX           { atiStkSwLldpLocPortNum }
        ::= { atiStkSwLldpLocalInfoTable 1 }

AtiStkSwLldpLocalInfoEntry ::=
        SEQUENCE {
                atiStkSwLldpLocModuleId                 Integer32,
                atiStkSwLldpLocPortNum                  Integer32,
                atiStkSwLldpLocChassisIdSubtype         INTEGER,
                atiStkSwLldpLocChassisId                DisplayString,
                atiStkSwLldpLocPortIdSubtype            INTEGER,
                atiStkSwLldpLocPortId                   DisplayString,
                atiStkSwLldpLocTtl                      Integer32,
                atiStkSwLldpLocPortDesc                 DisplayString,
                atiStkSwLldpLocSysName                  DisplayString,
                atiStkSwLldpLocSysDesc                  DisplayString,
                atiStkSwLldpLocSysCapSupported          BITS,
                atiStkSwLldpLocSysCapEnabled            BITS,
                atiStkSwLldpLocManAddrSubtype           INTEGER,
                atiStkSwLldpLocManAddr                  IpAddress, -- DisplayString,
                atiStkSwLldpLocManAddrLen               Integer32,
                atiStkSwLldpLocManAddrIfSubtype         INTEGER,
                atiStkSwLldpLocManAddrIfId              Integer32,
                atiStkSwLldpLocManAddrOID               OBJECT IDENTIFIER
        }

atiStkSwLldpLocModuleId OBJECT-TYPE
        SYNTAX          Integer32 --(1..8)
        MAX-ACCESS      read-only
        STATUS          current
        DESCRIPTION
                "This object specifies the ID of a module present in the switch
                stack."
        ::= { atiStkSwLldpLocalInfoEntry 1 }

atiStkSwLldpLocPortNum  OBJECT-TYPE
        SYNTAX          Integer32 (1..50)
        MAX-ACCESS      read-only
        STATUS          current
        DESCRIPTION
                "The index value used to identify the port component
                (contained in the local chassis with the LLDP agent)
                associated with this entry.

                The value of this object is used as a port index to the
                atiStkSwLldpLocalInfoTable."
        ::= { atiStkSwLldpLocalInfoEntry 2 }

atiStkSwLldpLocChassisIdSubtype  OBJECT-TYPE
        SYNTAX          INTEGER {
                                chassisComponent (1),
                                interfaceAlias (2),
                                portComponent (3),
                                macAddress (4),
                                networkAddress (5),
                                interfaceName (6),
                                local (7)
                                }
        MAX-ACCESS      read-only
        STATUS          current
        DESCRIPTION
                "The type of encoding used to identify the chassis
                associated with the local system."
        REFERENCE
                "IEEE 802.1AB-2005 9.5.2.2"
        ::= { atiStkSwLldpLocalInfoEntry 3 }

atiStkSwLldpLocChassisId  OBJECT-TYPE
        SYNTAX          DisplayString
        MAX-ACCESS      read-only
        STATUS          current
        DESCRIPTION
                "The string value used to identify the chassis component
                associated with the local system."
        REFERENCE
                "IEEE 802.1AB-2005 9.5.2.3"
        ::= { atiStkSwLldpLocalInfoEntry 4 }

atiStkSwLldpLocPortIdSubtype  OBJECT-TYPE
        SYNTAX          INTEGER {
                                interfaceAlias (1),
                                portComponent (2),
                                macAddress (3),
                                networkAddress (4),
                                interfaceName (5),
                                agentCircuitId (6),
                                local (7)
                                }
        MAX-ACCESS      read-only
        STATUS          current
        DESCRIPTION
                "The type of port identifier encoding used in the associated
                atiStkSwLldpLocPortId object."
        REFERENCE
                "IEEE 802.1AB-2005 9.5.3.2"
        ::= { atiStkSwLldpLocalInfoEntry 5 }

atiStkSwLldpLocPortId   OBJECT-TYPE
        SYNTAX          DisplayString
        MAX-ACCESS      read-only
        STATUS          current
        DESCRIPTION
                "The string value used to identify the port component
                associated with a given port in the local system."
        REFERENCE
                "IEEE 802.1AB-2005 9.5.3.3"
        ::= { atiStkSwLldpLocalInfoEntry 6 }

atiStkSwLldpLocTtl      OBJECT-TYPE
        SYNTAX          Integer32
        MAX-ACCESS      read-only
        STATUS          current
        DESCRIPTION
                "Time-to-live advertised by the given port"
        ::= { atiStkSwLldpLocalInfoEntry 7 }

atiStkSwLldpLocPortDesc OBJECT-TYPE
        SYNTAX          DisplayString
        MAX-ACCESS      read-only
        STATUS          current
        DESCRIPTION
                "The string value used to identify the 802 LAN station's port
                description associated with the local system."
        REFERENCE
                "IEEE 802.1AB-2005 9.5.5.2"
        ::= { atiStkSwLldpLocalInfoEntry 8 }

atiStkSwLldpLocSysName  OBJECT-TYPE
        SYNTAX          DisplayString
        MAX-ACCESS      read-only
        STATUS          current
        DESCRIPTION
                "The string value used to identify the system name of the
                local system."
        REFERENCE
                "IEEE 802.1AB-2005 9.5.6.2"
        ::= { atiStkSwLldpLocalInfoEntry 9 }

atiStkSwLldpLocSysDesc  OBJECT-TYPE
        SYNTAX          DisplayString
        MAX-ACCESS      read-only
        STATUS          current
        DESCRIPTION
                "The string value used to identify the system description
                of the local system."
        REFERENCE
                "IEEE 802.1AB-2005 9.5.7.2"
        ::= { atiStkSwLldpLocalInfoEntry 10 }

atiStkSwLldpLocSysCapSupported  OBJECT-TYPE
        SYNTAX          BITS    {
                                other (0),
                                repeater (1),
                                bridge (2),
                                wlanAccessPoint (3),
                                router (4),
                                telephone (5),
                                docsisCableDevice (6),
                                stationOnly (7)
                                }
        MAX-ACCESS      read-only
        STATUS          current
        DESCRIPTION
                "The bitmap value used to identify which system capabilities
                are supported on the local system."
        REFERENCE
                "IEEE 802.1AB-2005 9.5.8.1"
        ::= { atiStkSwLldpLocalInfoEntry 11 }

atiStkSwLldpLocSysCapEnabled  OBJECT-TYPE
        SYNTAX          BITS    {
                                other (0),
                                repeater (1),
                                bridge (2),
                                wlanAccessPoint (3),
                                router (4),
                                telephone (5),
                                docsisCableDevice (6),
                                stationOnly (7)
                                }
        MAX-ACCESS      read-only
        STATUS          current
        DESCRIPTION
                "The bitmap value used to identify which system capabilities
                are enabled on the local system."
        REFERENCE
                "IEEE 802.1AB-2005 9.5.8.2"
        ::= { atiStkSwLldpLocalInfoEntry 12 }

atiStkSwLldpLocManAddrSubtype  OBJECT-TYPE
        SYNTAX          INTEGER { -- AddressFamilyNumbers FROM IANA-ADDRESS-FAMILY-NUMBERS-MIB;
                                other (0),
                                ipV4 (1),
                                ipV6 (2),
                                nsap (3),
                                hdlc (4),
                                bbn1822 (5),
                                all802 (6),
                                e163 (7),
                                e164 (8),
                                f69 (9),
                                x121 (10),
                                ipx (11),
                                appleTalk (12),
                                decnetIV (13),
                                banyanVines (14),
                                e164withNsap (15),
                                dns (16),
                                distinguishedName (17), -- (Distinguished Name, per X.500)
                                asNumber (18), -- (16-bit quantity, per the AS number space)
                                xtpOverIpv4 (19),
                                xtpOverIpv6 (20),
                                xtpNativeModeXTP (21),
                                fibreChannelWWPN (22),
                                fibreChannelWWNN (23),
                                gwid (24),
                                afi (25),
                                reserved (65535)
                                }
        MAX-ACCESS      read-only
        STATUS          current
        DESCRIPTION
                "The type of management address identifier encoding used in
                the associated atiStkSwLldpLocManagmentAddr object."
        REFERENCE
                "IEEE 802.1AB-2005 9.5.9.3"
        ::= { atiStkSwLldpLocalInfoEntry 13 }

atiStkSwLldpLocManAddr  OBJECT-TYPE
        SYNTAX          IpAddress
        MAX-ACCESS      read-only
        STATUS          current
        DESCRIPTION
                "The string value used to identify the management address
                component associated with the local system.  The purpose of
                this address is to contact the management entity."
        REFERENCE
                "IEEE 802.1AB-2005 9.5.9.4"
        ::= { atiStkSwLldpLocalInfoEntry 14 }

atiStkSwLldpLocManAddrLen  OBJECT-TYPE
        SYNTAX          Integer32
        MAX-ACCESS      read-only
        STATUS          current
        DESCRIPTION
                "The total lenght of the management address subtype and the
                management address fields in LLDPDUs transmitted by the local
                LLDP agent.The management address length field is needed so that the
                receiving systems that do not implement SNMP will not be
                required to implement an iana family numbers/address length
                equivalency table in order to decode the management address"
        REFERENCE
                "IEEE 802.1AB-2005 9.5.9.2"
        ::= { atiStkSwLldpLocalInfoEntry 15 }

atiStkSwLldpLocManAddrIfSubtype  OBJECT-TYPE
        SYNTAX          INTEGER {
                                unknown (1),
                                ifIndex (2),
                                systemPortNumber (3)
                                }
        MAX-ACCESS      read-only
        STATUS          current
        DESCRIPTION
                "The enumeration value that identifies the interface numbering
                method used for defining the interface number, associated
                with the local system."
        REFERENCE
                "IEEE 802.1AB-2005 9.5.9.5"
        ::= { atiStkSwLldpLocalInfoEntry 16 }

atiStkSwLldpLocManAddrIfId  OBJECT-TYPE
        SYNTAX          Integer32
        MAX-ACCESS      read-only
        STATUS          current
        DESCRIPTION
                "The integer value used to identify the interface number
                regarding the management address component associated with
                the local system."
        REFERENCE
                "IEEE 802.1AB-2005 9.5.9.6"
        ::= { atiStkSwLldpLocalInfoEntry 17 }

atiStkSwLldpLocManAddrOID  OBJECT-TYPE
        SYNTAX          OBJECT IDENTIFIER
        MAX-ACCESS      read-only
        STATUS          current
        DESCRIPTION
                "The OID value used to identify the type of hardware component
                or protocol entity associated with the management address
                advertised by the local system agent."
        REFERENCE
                "IEEE 802.1AB-2005 9.5.9.8"
        ::= { atiStkSwLldpLocalInfoEntry 18 }

------------------------------------------------------------------------------
-- IEEE 802.1 - Local System Information
------------------------------------------------------------------------------

-- atiStkSwLldpLocalDot1Data

atiStkSwLldpDot1LocTable  OBJECT-TYPE
        SYNTAX          SEQUENCE OF AtiStkSwLldpDot1LocEntry
        MAX-ACCESS      not-accessible
        STATUS          current
        DESCRIPTION
                "This table contains one row per port for IEEE 802.1
                organizationally defined LLDP extension on the local system
                known to this agent."
        ::= { atiStkSwLldpLocalData 2 }

atiStkSwLldpDot1LocEntry  OBJECT-TYPE
        SYNTAX          AtiStkSwLldpDot1LocEntry
        MAX-ACCESS      not-accessible
        STATUS          current
        DESCRIPTION
                "Information about IEEE 802.1 organizationally defined
                LLDP extension."
        -- INDEX           { atiStkSwLldpDot1LocModuleId, atiStkSwLldpDot1LocPortNum }
        INDEX           { atiStkSwLldpDot1LocPortNum }
        ::= { atiStkSwLldpDot1LocTable 1 }

AtiStkSwLldpDot1LocEntry ::=
        SEQUENCE {
                atiStkSwLldpDot1LocModuleId             Integer32,
                atiStkSwLldpDot1LocPortNum              Integer32,
                atiStkSwLldpDot1LocPortVlanId           Integer32,
                atiStkSwLldpDot1LocProtoVlanId          Integer32,
                atiStkSwLldpDot1LocProtoVlanSupported   INTEGER,
                atiStkSwLldpDot1LocProtoVlanEnabled     INTEGER,
                atiStkSwLldpDot1LocVlanId               DisplayString,
                atiStkSwLldpDot1LocVlanName             DisplayString,
                atiStkSwLldpDot1LocProtocolId           DisplayString
        }

atiStkSwLldpDot1LocModuleId  OBJECT-TYPE
        SYNTAX          Integer32 --(1..8)
        MAX-ACCESS      read-only
        STATUS          current
        DESCRIPTION
                "This object specifies the ID of a module present in the switch
                stack."
        ::= { atiStkSwLldpDot1LocEntry 1 }

atiStkSwLldpDot1LocPortNum  OBJECT-TYPE
        SYNTAX          Integer32 (1..50)
        MAX-ACCESS      read-only
        STATUS          current
        DESCRIPTION
                "The index value used to identify the port component
                (contained in the local chassis with the LLDP agent)
                associated with this entry."
        ::= { atiStkSwLldpDot1LocEntry 2 }

atiStkSwLldpDot1LocPortVlanId  OBJECT-TYPE
        SYNTAX          Integer32 (0|1..4094)
        MAX-ACCESS      read-only
        STATUS          current
        DESCRIPTION
                "The integer value used to identify the port's VLAN identifier
                associated with the local system.   A value of zero shall
                be used if the system either does not know the PVID or does
                not support port-based VLAN operation."
        REFERENCE
                "IEEE 802.1AB-2005 F.2.1"
        ::= { atiStkSwLldpDot1LocEntry 3 }

--
-- atiStkSwLldpDot1LocProtoVlanTable: Port and Protocol VLAN information
--

atiStkSwLldpDot1LocProtoVlanId  OBJECT-TYPE
        SYNTAX          Integer32 (0|1..4094)
        MAX-ACCESS      read-only
        STATUS          current
        DESCRIPTION
                "The integer value used to identify the port and protocol
                VLANs associated with the given port associated with the
                local system.  A value of zero shall be used if the system
                either does not know the protocol VLAN ID (PPVID) or does
                not support port and protocol VLAN operation."
        REFERENCE
                "IEEE 802.1AB-2005 F.3.2"
        ::= { atiStkSwLldpDot1LocEntry 4 }

atiStkSwLldpDot1LocProtoVlanSupported  OBJECT-TYPE
        SYNTAX          INTEGER {
                                enabled (1),
                                disabled (2)
                                }
        MAX-ACCESS      read-only
        STATUS          current
        DESCRIPTION
                "The truth value used to indicate whether the given port
                (associated with the local system) supports port and protocol
                VLANs."
        REFERENCE
                "IEEE 802.1AB-2005 F.3.1"
        ::= { atiStkSwLldpDot1LocEntry 5 }

atiStkSwLldpDot1LocProtoVlanEnabled  OBJECT-TYPE
        SYNTAX          INTEGER {
                                enabled (1),
                                disabled (2)
                                }
        MAX-ACCESS      read-only
        STATUS          current
        DESCRIPTION
                "The truth value used to indicate whether the port and
                protocol VLANs are enabled on the given port associated with
                the local system."
        REFERENCE
                "IEEE 802.1AB-2005 F.3.1"
        ::= { atiStkSwLldpDot1LocEntry 6 }

--
-- atiStkSwLldpDot1LocVlanNameTable : VLAN name information about the local system
--

atiStkSwLldpDot1LocVlanId  OBJECT-TYPE
        SYNTAX          DisplayString
-- Integer32(1..4094)
-- VlanId FROM Q-BRIDGE-MIB
        MAX-ACCESS      read-only
        STATUS          current
        DESCRIPTION
                "The integer value used to identify the IEEE 802.1Q
                VLAN IDs with which the given port is compatible."
        REFERENCE
                "IEEE 802.1AB-2005 F.4.2"
        ::= { atiStkSwLldpDot1LocEntry 7 }

atiStkSwLldpDot1LocVlanName  OBJECT-TYPE
        SYNTAX          DisplayString
        MAX-ACCESS      read-only
        STATUS          current
        DESCRIPTION
                "The string value used to identify VLAN name identified by the
                Vlan Id associated with the given port on the local system.

                This object should contain the value of the dot1QVLANStaticName
                object (defined in IETF RFC 2674) identified with the given
                atiStkSwLldpDot1LocVlanId."
        REFERENCE
                "IEEE 802.1AB-2005 F.4.4"
        ::= { atiStkSwLldpDot1LocEntry 8 }

--
-- atiStkSwLldpDot1LocProtocolTable : Protocol Identity information
--

atiStkSwLldpDot1LocProtocolId  OBJECT-TYPE
        SYNTAX          DisplayString
        MAX-ACCESS      read-only
        STATUS          current
        DESCRIPTION
                "The octet string value used to identify the protocols
                associated with the given port of the local system."
        REFERENCE
                "IEEE 802.1AB-2005 F.5.3"
        ::= { atiStkSwLldpDot1LocEntry 9 }

------------------------------------------------------------------------------
-- IEEE 802.3 - Local Device Information
------------------------------------------------------------------------------

-- atiStkSwLldpLocalDot3Data

atiStkSwLldpLocalDot3Data  OBJECT IDENTIFIER ::= { atiStkSwLldpLocalData 3 }

atiStkSwLldpDot3LocTable  OBJECT-TYPE
        SYNTAX          SEQUENCE OF AtiStkSwLldpDot3LocEntry
        MAX-ACCESS      not-accessible
        STATUS          current
        DESCRIPTION
                "This table contains one row per port of Ethernet port
                information (as a part of the LLDP 802.3 organizational
                extension) on the local system known to this agent."
        ::= { atiStkSwLldpLocalDot3Data 1 }

atiStkSwLldpDot3LocEntry  OBJECT-TYPE
        SYNTAX          AtiStkSwLldpDot3LocEntry
        MAX-ACCESS      not-accessible
        STATUS          current
        DESCRIPTION
                "Information about a particular port component."
        -- INDEX                { atiStkSwLldpDot3LocModuleId, atiStkSwLldpDot3LocPortNum }
        INDEX           { atiStkSwLldpDot3LocPortNum }
        ::= { atiStkSwLldpDot3LocTable 1 }

AtiStkSwLldpDot3LocEntry ::=
        SEQUENCE {
                atiStkSwLldpDot3LocModuleId                     Integer32,
                atiStkSwLldpDot3LocPortNum                      Integer32,
                atiStkSwLldpDot3LocPortAutoNegSupported         INTEGER,
                atiStkSwLldpDot3LocPortAutoNegEnabled           INTEGER,
                atiStkSwLldpDot3LocPortAutoNegAdvertisedCap     BITS,
                atiStkSwLldpDot3LocPortOperMauType              INTEGER,
                atiStkSwLldpDot3LocPowerPortClass               INTEGER,
                atiStkSwLldpDot3LocPowerMDISupported            INTEGER,
                atiStkSwLldpDot3LocPowerMDIEnabled              INTEGER,
                atiStkSwLldpDot3LocPowerPairControlable         INTEGER,
                atiStkSwLldpDot3LocPowerPairs                   Integer32,
                atiStkSwLldpDot3LocPowerClass                   Integer32,
                atiStkSwLldpDot3LocLinkAggStatus                BITS,
                atiStkSwLldpDot3LocLinkAggPortId                Integer32,
                atiStkSwLldpDot3LocMaxFrameSize                 Integer32
        }

---
--- atiStkSwLldpDot3LocPortTable: Ethernet Port AutoNeg/Speed/Duplex
---                               Information Table
---

atiStkSwLldpDot3LocModuleId  OBJECT-TYPE
        SYNTAX          Integer32 --(1..8)
        MAX-ACCESS      read-only
        STATUS          current
        DESCRIPTION
                "This object specifies the ID of a module present in the switch
                stack."
        ::= { atiStkSwLldpDot3LocEntry 1 }

atiStkSwLldpDot3LocPortNum  OBJECT-TYPE
        SYNTAX          Integer32 (1..50)
        MAX-ACCESS      read-only
        STATUS          current
        DESCRIPTION
                "The index value used to identify the port component
                (contained in the local chassis with the LLDP agent)
                associated with this entry."
        ::= { atiStkSwLldpDot3LocEntry 2 }

atiStkSwLldpDot3LocPortAutoNegSupported  OBJECT-TYPE
        SYNTAX          INTEGER {
                                enabled (1),
                                disabled (2)
                                }
        MAX-ACCESS      read-only
        STATUS          current
        DESCRIPTION
                "The truth value used to indicate whether the given port
                (associated with the local system) supports Auto-negotiation."
        REFERENCE
                "IEEE 802.1AB-2005 G.2.1"
        ::= { atiStkSwLldpDot3LocEntry 3 }

atiStkSwLldpDot3LocPortAutoNegEnabled  OBJECT-TYPE
        SYNTAX          INTEGER {
                                enabled (1),
                                disabled (2)
                                }
        MAX-ACCESS  read-only
        STATUS      current
        DESCRIPTION
                "The truth value used to indicate whether port
                Auto-negotiation is enabled on the given port associated
                with the local system."
        REFERENCE
                "IEEE 802.1AB-2005 G.2.1"
        ::= { atiStkSwLldpDot3LocEntry 4 }

atiStkSwLldpDot3LocPortAutoNegAdvertisedCap  OBJECT-TYPE
        SYNTAX          BITS    {
                                bOther (0),         -- other or unknown
                                b10baseT (1),       -- 10BASE-T  half duplex mode
                                b10baseTFD (2),     -- 10BASE-T  full duplex mode
                                b100baseT4 (3),     -- 100BASE-T4
                                b100baseTX (4),     -- 100BASE-TX half duplex mode
                                b100baseTXFD (5),   -- 100BASE-TX full duplex mode
                                b100baseT2 (6),     -- 100BASE-T2 half duplex mode
                                b100baseT2FD (7),   -- 100BASE-T2 full duplex mode
                                bFdxPause (8),      -- PAUSE for full-duplex links
                                bFdxAPause (9),     -- Asymmetric PAUSE for full-duplex links
                                bFdxSPause (10),    -- Symmetric PAUSE for full-duplex links
                                bFdxBPause (11),    -- Asymmetric and Symmetric PAUSE for full-duplex links
                                b1000baseX (12),    -- 1000BASE-X, -LX, -SX, -CX half duplex mode
                                b1000baseXFD (13),  -- 1000BASE-X, -LX, -SX, -CX full duplex mode
                                b1000baseT (14),    -- 1000BASE-T half duplex mode
                                b1000baseTFD (15)   -- 1000BASE-T full duplex mode
                                }
        MAX-ACCESS      read-only
        STATUS          current
        DESCRIPTION
                "This object contains the value (bitmap) of the
                ifMauAutoNegCapAdvertisedBits object (defined in IETF RFC
                3636) which is associated with the given port on the
                local system."
        REFERENCE
                "IEEE 802.1AB-2005 G.2.2"
        ::= { atiStkSwLldpDot3LocEntry 5 }

atiStkSwLldpDot3LocPortOperMauType  OBJECT-TYPE
        SYNTAX          INTEGER {
                                dot3MauTypeAUI (1),
                                dot3MauType10Base5 (2),
                                dot3MauTypeFoirl (3),
                                dot3MauType10Base2 (4),
                                dot3MauType10BaseT (5),
                                dot3MauType10BaseFP (6),
                                dot3MauType10BaseFB (7),
                                dot3MauType10BaseFL (8),
                                dot3MauType10Broad36 (9),
                                dot3MauType10BaseTHD (10),
                                dot3MauType10BaseTFD (11),
                                dot3MauType10BaseFLHD (12),
                                dot3MauType10BaseFLFD (13),
                                dot3MauType100BaseT4 (14),
                                dot3MauType100BaseTXHD (15),
                                dot3MauType100BaseTXFD (16),
                                dot3MauType100BaseFXHD (17),
                                dot3MauType100BaseFXFD (18),
                                dot3MauType100BaseT2HD (19),
                                dot3MauType100BaseT2FD (20),
                                dot3MauType1000BaseXHD (21),
                                dot3MauType1000BaseXFD (22),
                                dot3MauType1000BaseLXHD (23),
                                dot3MauType1000BaseLXFD (24),
                                dot3MauType1000BaseSXHD (25),
                                dot3MauType1000BaseSXFD (26),
                                dot3MauType1000BaseCXHD (27),
                                dot3MauType1000BaseCXFD (28),
                                dot3MauType1000BaseTHD (29),
                                dot3MauType1000BaseTFD (30),
                                dot3MauType10GigBaseX (31),
                                dot3MauType10GigBaseLX4 (32),
                                dot3MauType10GigBaseR (33),
                                dot3MauType10GigBaseER (34),
                                dot3MauType10GigBaseLR (35),
                                dot3MauType10GigBaseSR (36),
                                dot3MauType10GigBaseW (37),
                                dot3MauType10GigBaseEW (38),
                                dot3MauType10GigBaseLW (39),
                                dot3MauType10GigBaseSW (40)
                                }
        MAX-ACCESS      read-only
        STATUS          current
        DESCRIPTION
                "An integer value that indicates the operational MAU type
                of the given port on the local system.

                This object contains the integer value derived from the
                list position of the corresponding dot3MauType as listed
                in IETF RFC 3636 (or subsequent revisions) and is equal
                to the last number in the respective dot3MauType OID.

                For example, if the ifMauType object is dot3MauType1000BaseTHD
                which corresponds to {dot3MauType 29}, the numerical value of
                this field will be 29. For MAU types not listed in RFC 3636
                (or subsequent revisions), the value of this field shall be
                set to zero."
        REFERENCE
                "IEEE 802.1AB-2005 G.2.3"
        ::= { atiStkSwLldpDot3LocEntry 6 }

---
--- atiStkSwLldpDot3LocPowerTable: Power Ethernet Information Table
---

atiStkSwLldpDot3LocPowerPortClass  OBJECT-TYPE
        SYNTAX          INTEGER {
                                pClassPSE (1),
                                pClassPD (2)
                                }
        MAX-ACCESS      read-only
        STATUS          current
        DESCRIPTION
                "The value that identifies the port Class of the given port
                associated with the local system."
        REFERENCE
                "IEEE 802.1AB-2005 G.3.1"
        ::= { atiStkSwLldpDot3LocEntry 7 }

atiStkSwLldpDot3LocPowerMDISupported  OBJECT-TYPE
        SYNTAX          INTEGER {
                                enabled (1),
                                disabled (2)
                                }
        MAX-ACCESS      read-only
        STATUS          current
        DESCRIPTION
                "The truth value used to indicate whether the MDI power is
                supported on the given port associated with the local system."
        REFERENCE
                "IEEE 802.1AB-2005 G.3.1"
        ::= { atiStkSwLldpDot3LocEntry 8 }

atiStkSwLldpDot3LocPowerMDIEnabled  OBJECT-TYPE
        SYNTAX          INTEGER {
                                enabled (1),
                                disabled (2)
                                }
        MAX-ACCESS      read-only
        STATUS          current
        DESCRIPTION
                "The truth value used to identify whether MDI power is
                enabled on the given port associated with the local system."
        REFERENCE
                "IEEE 802.1AB-2005 G.3.1"
        ::= { atiStkSwLldpDot3LocEntry 9 }

atiStkSwLldpDot3LocPowerPairControlable  OBJECT-TYPE
        SYNTAX          INTEGER {
                                enabled (1),
                                disabled (2)
                                }
        MAX-ACCESS      read-only
        STATUS          current
        DESCRIPTION
                "The truth value is derived from the value of
                pethPsePortPowerPairsControlAbility object (defined in IETF
                RFC 3621) and is used to indicate whether the pair selection
                can be controlled on the given port associated with the
                local system."
        REFERENCE
                "IEEE 802.1AB-2005 G.3.1"
        ::= { atiStkSwLldpDot3LocEntry 10 }

atiStkSwLldpDot3LocPowerPairs  OBJECT-TYPE
        SYNTAX          Integer32 (1|2)
        MAX-ACCESS      read-only
        STATUS          current
        DESCRIPTION
                "This object contains the value of the pethPsePortPowerPairs
                object (defined in IETF RFC 3621) which is associated with
                the given port on the local system."
        REFERENCE
                "IEEE 802.1AB-2005 G.3.2"
        ::= { atiStkSwLldpDot3LocEntry 11 }

atiStkSwLldpDot3LocPowerClass  OBJECT-TYPE
        SYNTAX          Integer32 (1|2|3|4|5)
        MAX-ACCESS      read-only
        STATUS          current
        DESCRIPTION
                "This object contains the value of the
                pethPsePortPowerClassifications object (defined in IETF
                RFC 3621) which is associated with the given port on the
                local system."
        REFERENCE
                "IEEE 802.1AB-2005 G.3.3"
        ::= { atiStkSwLldpDot3LocEntry 12 }

---
--- atiStkSwLldpDot3LocLinkAggTable: Link Aggregation Information Table
---

atiStkSwLldpDot3LocLinkAggStatus  OBJECT-TYPE
        SYNTAX          BITS    {
                                aggCapable (0),
                                aggEnabled (1)
                                }
        MAX-ACCESS      read-only
        STATUS          current
        DESCRIPTION
                "The bitmap value contains the link aggregation capabilities
                and the current aggregation status of the link."
        REFERENCE
                "IEEE 802.1AB-2005 G.4.1"
        ::= { atiStkSwLldpDot3LocEntry 13 }

atiStkSwLldpDot3LocLinkAggPortId  OBJECT-TYPE
        SYNTAX          Integer32 (0|1..2147483647)
        MAX-ACCESS      read-only
        STATUS          current
        DESCRIPTION
                "This object contains the IEEE 802.3 aggregated port
                identifier, aAggPortID (IEEE 802.3-2002, 30.7.2.1.1),
                derived from the ifNumber of the ifIndex for the port
                component in link aggregation.

                If the port is not in link aggregation state and/or it
                does not support link aggregation, this value should be set
                to zero."
        REFERENCE
                "IEEE 802.1AB-2005 G.4.2"
        ::= { atiStkSwLldpDot3LocEntry 14 }

---
--- atiStkSwLldpDot3LocMaxFrameSizeTable: Maximum Frame Size information
---

atiStkSwLldpDot3LocMaxFrameSize  OBJECT-TYPE
        SYNTAX          Integer32 (0..65535)
        MAX-ACCESS      read-only
        STATUS          current
        DESCRIPTION
                "An integer value indicating the maximum supported frame
                size in octets on the given port of the local system."
        REFERENCE
                "IEEE 802.1AB-2005 G.5.1"
        ::= { atiStkSwLldpDot3LocEntry 15 }


------------------------------------------------------------------------------
-- LLDP-MED - Local Device Information
------------------------------------------------------------------------------

-- atiStkSwLldpLocalMedData

atiStkSwLldpLocalMedData  OBJECT IDENTIFIER ::= { atiStkSwLldpLocalData 4 }

atiStkSwLldpMedLocTable OBJECT-TYPE
        SYNTAX          SEQUENCE OF AtiStkSwLldpMedLocEntry
        MAX-ACCESS      not-accessible
        STATUS          current
        DESCRIPTION
                "This table contains one row per port of LLDP-MED
                information on the local system known to this agent."
        ::= { atiStkSwLldpLocalMedData 1 }

atiStkSwLldpMedLocEntry OBJECT-TYPE
        SYNTAX          AtiStkSwLldpMedLocEntry
        MAX-ACCESS      not-accessible
        STATUS          current
        DESCRIPTION
                "Information about a particular port component."
        -- INDEX           { atiStkSwLldpMedLocModuleId, atiStkSwLldpMedLocPortNum }
        INDEX           { atiStkSwLldpMedLocPortNum }
    ::= { atiStkSwLldpMedLocTable 1 }

AtiStkSwLldpMedLocEntry ::=
        SEQUENCE {
                atiStkSwLldpMedLocModuleId              Integer32,
                atiStkSwLldpMedLocPortNum               Integer32,
                atiStkSwLldpMedLocDeviceClass           AtiStkSwLldpMedDeviceClass,
                atiStkSwLldpMedLocCapabilities          AtiStkSwLldpMedCapabilities,
                atiStkSwLldpMedLocMediaPolicyAppType    PolicyAppType,
--              atiStkSwLldpMedLocMediaPolicyVlanID     Integer32,
                atiStkSwLldpMedLocMediaPolicyPriority   Integer32,
                atiStkSwLldpMedLocMediaPolicyDscp       Integer32,
                atiStkSwLldpMedLocMediaPolicyUnknown    TruthValue,
                atiStkSwLldpMedLocMediaPolicyTagged     TruthValue,
                atiStkSwLldpMedLocHardwareRev           DisplayString,
                atiStkSwLldpMedLocFirmwareRev           DisplayString,
                atiStkSwLldpMedLocSoftwareRev           DisplayString,
                atiStkSwLldpMedLocSerialNum             DisplayString,
                atiStkSwLldpMedLocMfgName               DisplayString,
                atiStkSwLldpMedLocModelName             DisplayString,
                atiStkSwLldpMedLocAssetID               DisplayString,
                atiStkSwLldpMedLocCoordLocation         DisplayString,
                atiStkSwLldpMedLocCivicLocation         DisplayString,
                atiStkSwLldpMedLocElinLocation          DisplayString
                }

atiStkSwLldpMedLocModuleId  OBJECT-TYPE
        SYNTAX          Integer32 --(1..8)
        MAX-ACCESS      read-only
        STATUS          current
        DESCRIPTION
                "This object specifies the ID of a module present in the switch
                stack."
        ::= { atiStkSwLldpMedLocEntry 1 }

atiStkSwLldpMedLocPortNum  OBJECT-TYPE
        SYNTAX          Integer32 (1..50)
        MAX-ACCESS      read-only
        STATUS          current
        DESCRIPTION
                "The index value used to identify the port component
                (contained in the local chassis with the LLDP agent)
                associated with this entry."
        ::= { atiStkSwLldpMedLocEntry 2 }

atiStkSwLldpMedLocDeviceClass  OBJECT-TYPE
        SYNTAX          AtiStkSwLldpMedDeviceClass
        MAX-ACCESS      read-only
        STATUS          current
        DESCRIPTION
                "Local Device Class."
        REFERENCE
                "ANSI/TIA-1057, Section 10.2.2.2"
        ::= { atiStkSwLldpMedLocEntry 3 }


atiStkSwLldpMedLocCapabilities  OBJECT-TYPE
        SYNTAX          AtiStkSwLldpMedCapabilities
        MAX-ACCESS      read-only
        STATUS          current
        DESCRIPTION
                "The bitmap includes the MED organizationally defined set of LLDP
                TLVs whose transmission is possible for the respective port
                on the LLDP agent of the device. Each bit in the bitmap corresponds
                to an LLDP-MED subtype associated with a specific TIA TR41.4 MED
                optional TLV. If the bit is set, the agent supports the
                corresponding TLV."
        REFERENCE
                "ANSI/TIA-1057, Section 10.2.2.3"
        ::= { atiStkSwLldpMedLocEntry 4 }

atiStkSwLldpMedLocMediaPolicyAppType  OBJECT-TYPE
        SYNTAX          PolicyAppType
        MAX-ACCESS      read-only
        STATUS          current
        DESCRIPTION
                "The media type that defines the primary function of the
                application for the policy advertised by an endpoint."
        REFERENCE
                "ANSI/TIA-1057, Section 10.2.3.1"
        ::= { atiStkSwLldpMedLocEntry 5 }

--atiStkSwLldpMedLocMediaPolicyVlanID  OBJECT-TYPE
--      SYNTAX          Integer32 (0|1..4094|4095)
--      MAX-ACCESS      read-only
--      STATUS          current
--      DESCRIPTION
--              "An extension of the VLAN Identifier for the port,
--              as defined in IEEE 802.1P-1998.

--              A value of 1 through 4094 is used to define a valid PVID.

--              A value of 0 shall be used if the device is using priority tagged
--              frames, meaning that only the 802.1p priority level is significant
--              and the default VID of the ingress port is being used instead.

--              A value of 4095 is reserved for implementation use."
--      REFERENCE
--              "ANSI/TIA-1057, Section 10.2.3.5"
--    ::= { atiStkSwLldpMedLocEntry 6 }

atiStkSwLldpMedLocMediaPolicyPriority  OBJECT-TYPE
        SYNTAX          Integer32 (0..7)
        MAX-ACCESS      read-only
        STATUS          current
        DESCRIPTION
                "This object contains the value of the 802.1p priority
                which is associated with the given port on the
                local system."
        REFERENCE
                "ANSI/TIA-1057, Section 10.2.3.6 "
        ::= { atiStkSwLldpMedLocEntry 7 }

atiStkSwLldpMedLocMediaPolicyDscp  OBJECT-TYPE
        SYNTAX          Integer32 (0..63)
        MAX-ACCESS      read-only
        STATUS          current
        DESCRIPTION
                "This object contains the value of the Differentiated Service
                Code Point (DSCP) as defined in IETF RFC 2474 and RFC 2475
                which is associated with the given port on the local system."
        REFERENCE
                "ANSI/TIA-1057, Section 10.2.3.7"
        ::= { atiStkSwLldpMedLocEntry 8 }

atiStkSwLldpMedLocMediaPolicyUnknown  OBJECT-TYPE
        SYNTAX          TruthValue
        MAX-ACCESS      read-only
        STATUS          current
        DESCRIPTION
                "A value of 'true' indicates that the
                network policy for the specified application type is
                currently unknown.  In this case, the VLAN ID, the
                layer 2 priority and the DSCP value fields are ignored.
                A value of 'false' indicates that this network policy
                is defined"
        REFERENCE
                "ANSI/TIA-1057, Section 10.2.3.2"
        ::= { atiStkSwLldpMedLocEntry 9 }

atiStkSwLldpMedLocMediaPolicyTagged  OBJECT-TYPE
        SYNTAX          TruthValue
        MAX-ACCESS      read-only
        STATUS          current
        DESCRIPTION
                "A value of 'true' indicates that the application is using a
                tagged VLAN.
                A value of 'false' indicates that for the specific application
                the device either is using an untagged VLAN or does not
                support port based VLAN operation.  In this case, both the
                VLAN ID and the Layer 2 priority fields are ignored and
                only the DSCP value has relevance "
        REFERENCE
                "ANSI/TIA-1057, Section 10.2.3.3"
        ::= { atiStkSwLldpMedLocEntry 10 }


--- Inventory Information
--- Local Inventory Information transmitted by an endpoint

atiStkSwLldpMedLocHardwareRev  OBJECT-TYPE
        SYNTAX          DisplayString (SIZE (0..32))
        MAX-ACCESS      read-only
        STATUS          current
        DESCRIPTION
                "The vendor-specific hardware revision string
                as advertised by the endpoint."
        REFERENCE
                "ANSI/TIA-1057, Section 10.2.6.1"
        ::= { atiStkSwLldpMedLocEntry 11 }

atiStkSwLldpMedLocFirmwareRev  OBJECT-TYPE
        SYNTAX          DisplayString (SIZE (0..32))
        MAX-ACCESS      read-only
        STATUS          current
        DESCRIPTION
                "The vendor-specific firmware revision string
                as advertised by the endpoint."
        REFERENCE
                "ANSI/TIA-1057, Section 10.2.6.2"
        ::= { atiStkSwLldpMedLocEntry 12 }

atiStkSwLldpMedLocSoftwareRev  OBJECT-TYPE
        SYNTAX          DisplayString (SIZE (0..32))
        MAX-ACCESS      read-only
        STATUS          current
        DESCRIPTION
                "The vendor-specific software revision string
                as advertised by the endpoint."
        REFERENCE
                "ANSI/TIA-1057, Section 10.2.6.3"
        ::= { atiStkSwLldpMedLocEntry 13 }

atiStkSwLldpMedLocSerialNum  OBJECT-TYPE
        SYNTAX          DisplayString (SIZE (0..32))
        MAX-ACCESS      read-only
        STATUS          current
        DESCRIPTION
                "The vendor-specific serial number
                as advertised by the endpoint."
        REFERENCE
                "ANSI/TIA-1057, Section 10.2.6.4"
        ::= { atiStkSwLldpMedLocEntry 14 }

atiStkSwLldpMedLocMfgName  OBJECT-TYPE
        SYNTAX          DisplayString (SIZE (0..32))
        MAX-ACCESS      read-only
        STATUS          current
        DESCRIPTION
                "The vendor-specific manufacturer name
                as advertised by the endpoint."
        REFERENCE
                "ANSI/TIA-1057, Section 10.2.6.5"
        ::= { atiStkSwLldpMedLocEntry 15 }

atiStkSwLldpMedLocModelName  OBJECT-TYPE
        SYNTAX          DisplayString (SIZE (0..32))
        MAX-ACCESS      read-only
        STATUS          current
        DESCRIPTION
                "The vendor-specific model name
                as advertised by the endpoint."
        REFERENCE
                "ANSI/TIA-1057, Section 10.2.6.6"
        ::= { atiStkSwLldpMedLocEntry 16 }

atiStkSwLldpMedLocAssetID  OBJECT-TYPE
        SYNTAX          DisplayString (SIZE (0..32))
        MAX-ACCESS      read-only
        STATUS          current
        DESCRIPTION
                "The vendor-specific asset tracking identifier
                as advertised by the endpoint."
        REFERENCE
                "ANSI/TIA-1057, Section 10.2.6.7"
        ::= { atiStkSwLldpMedLocEntry 17 }

--- Location Information
--- Local Location Information transmitted by an endpoint

atiStkSwLldpMedLocCoordLocation  OBJECT-TYPE
        SYNTAX          DisplayString
        MAX-ACCESS      read-only
        STATUS          current
        DESCRIPTION
                "Coordinate based location information"
        REFERENCE
                "ANSI/TIA-1057, Section 10.2.4.3"
        ::= { atiStkSwLldpMedLocEntry 18 }

atiStkSwLldpMedLocCivicLocation  OBJECT-TYPE
        SYNTAX          DisplayString
        MAX-ACCESS      read-only
        STATUS          current
        DESCRIPTION
                "Civic location information"
        REFERENCE
                "ANSI/TIA-1057, Section 10.2.4.3"
        ::= { atiStkSwLldpMedLocEntry 19 }

atiStkSwLldpMedLocElinLocation  OBJECT-TYPE
        SYNTAX          DisplayString
        MAX-ACCESS      read-only
        STATUS          current
        DESCRIPTION
                "Elin location information"
        REFERENCE
                "ANSI/TIA-1057, Section 10.2.4.3"
        ::= { atiStkSwLldpMedLocEntry 20 }


--  ***********************************************************
--
--          R E M O T E    S Y S T E M S    D A T A
--
--  ***********************************************************

-- atiStkSwLldpRemoteData

atiStkSwLldpRemoteData  OBJECT IDENTIFIER ::= { atiStkSwLldpGroup 4 }

atiStkSwLldpRemBaseTable  OBJECT-TYPE
        SYNTAX          SEQUENCE OF AtiStkSwLldpRemBaseEntry
        MAX-ACCESS      not-accessible
        STATUS          current
        DESCRIPTION
                "This table contains one or more rows per physical network
                connection known to this agent."
        ::= { atiStkSwLldpRemoteData 1 }

atiStkSwLldpRemBaseEntry  OBJECT-TYPE
        SYNTAX          AtiStkSwLldpRemBaseEntry
        MAX-ACCESS      not-accessible
        STATUS          current
        DESCRIPTION
                "Information about a particular physical network connection."
        INDEX           { atiStkSwLldpRemIndex }
    ::= { atiStkSwLldpRemBaseTable 1 }

AtiStkSwLldpRemBaseEntry ::=
        SEQUENCE {
                atiStkSwLldpRemModuleNum                Integer32,
                atiStkSwLldpRemPortNum                  Integer32,
                atiStkSwLldpRemIndex                    Integer32,
                atiStkSwLldpRemChassisIdSubtype         INTEGER,
                atiStkSwLldpRemChassisId                DisplayString,
                atiStkSwLldpRemPortIdSubtype            INTEGER,
                atiStkSwLldpRemPortId                   DisplayString,
                atiStkSwLldpRemTtl                      Integer32,
                atiStkSwLldpRemPortDesc                 DisplayString,
                atiStkSwLldpRemSysName                  DisplayString,
                atiStkSwLldpRemSysDesc                  DisplayString,
                atiStkSwLldpRemSysCapSupported          BITS,
                atiStkSwLldpRemSysCapEnabled            BITS,
                atiStkSwLldpRemManAddrSubtype           INTEGER,
                atiStkSwLldpRemManAddr                  IpAddress,
                atiStkSwLldpRemManAddrIfSubtype         INTEGER,
                atiStkSwLldpRemManAddrIfId              Integer32,
                atiStkSwLldpRemManAddrOID               OBJECT IDENTIFIER
        }

atiStkSwLldpRemModuleNum  OBJECT-TYPE
        SYNTAX          Integer32 --(1..8)
        MAX-ACCESS      read-only
        STATUS          current
        DESCRIPTION
                "This object specifies the ID of a module present in the switch
                stack."
        ::= { atiStkSwLldpRemBaseEntry 1 }

atiStkSwLldpRemPortNum  OBJECT-TYPE
        SYNTAX          Integer32 --(1..50)
        MAX-ACCESS      read-only
        STATUS          current
        DESCRIPTION
                "The index value used to identify the port component
                (contained in the local chassis with the LLDP agent)
                associated with this entry.  The atiStkSwLldpRemPortNum
                identifies the port on which the remote system information
                is received."
        ::= { atiStkSwLldpRemBaseEntry 2 }

atiStkSwLldpRemIndex    OBJECT-TYPE
        SYNTAX          Integer32  (0..255)
        MAX-ACCESS      read-only
        STATUS          current
        DESCRIPTION
                "This object represents an arbitrary local integer value used
                by this agent to identify a particular connection instance,
                unique only for the indicated remote system."
        ::= { atiStkSwLldpRemBaseEntry 3 }

atiStkSwLldpRemChassisIdSubtype  OBJECT-TYPE
        SYNTAX          INTEGER {
                                chassisComponent (1),
                                interfaceAlias (2),
                                portComponent (3),
                                macAddress (4),
                                networkAddress (5),
                                interfaceName (6),
                                local (7)
                                }
        MAX-ACCESS      read-only
        STATUS          current
        DESCRIPTION
                "The type of encoding used to identify the chassis associated
                with the remote system."
        REFERENCE
                "IEEE 802.1AB-2005 9.5.2.2"
        ::= { atiStkSwLldpRemBaseEntry 4 }

atiStkSwLldpRemChassisId  OBJECT-TYPE
        SYNTAX          DisplayString
        MAX-ACCESS      read-only
        STATUS          current
        DESCRIPTION
                "The string value used to identify the chassis component
                associated with the remote system."
        REFERENCE
                "IEEE 802.1AB-2005 9.5.2.3"
        ::= { atiStkSwLldpRemBaseEntry 5 }

atiStkSwLldpRemPortIdSubtype  OBJECT-TYPE
        SYNTAX          INTEGER {
                                interfaceAlias (1),
                                portComponent (2),
                                macAddress (3),
                                networkAddress (4),
                                interfaceName (5),
                                agentCircuitId (6),
                                local (7)
                                }
        MAX-ACCESS      read-only
        STATUS          current
        DESCRIPTION
                "The type of port identifier encoding used in the associated
                atiStkSwLldpRemPortId object."
        REFERENCE
                "IEEE 802.1AB-2005 9.5.3.2"
        ::= { atiStkSwLldpRemBaseEntry 6 }

atiStkSwLldpRemPortId   OBJECT-TYPE
        SYNTAX          DisplayString
        MAX-ACCESS      read-only
        STATUS          current
        DESCRIPTION
                "The string value used to identify the port component
                associated with the remote system."
        REFERENCE
                "IEEE 802.1AB-2005 9.5.3.3"
        ::= { atiStkSwLldpRemBaseEntry 7 }

atiStkSwLldpRemTtl      OBJECT-TYPE
        SYNTAX          Integer32
        MAX-ACCESS      read-only
        STATUS          current
        DESCRIPTION
                "Time-to-live advertised by the remote system."
        ::= { atiStkSwLldpRemBaseEntry 8 }

atiStkSwLldpRemPortDesc OBJECT-TYPE
        SYNTAX          DisplayString
        MAX-ACCESS      read-only
        STATUS          current
        DESCRIPTION
                "The string value used to identify the description of
                the given port associated with the remote system."
        REFERENCE
                "IEEE 802.1AB-2005 9.5.5.2"
        ::= { atiStkSwLldpRemBaseEntry 9 }

atiStkSwLldpRemSysName  OBJECT-TYPE
        SYNTAX          DisplayString
        MAX-ACCESS      read-only
        STATUS          current
        DESCRIPTION
                "The string value used to identify the system name of the
                remote system."
        REFERENCE
                "IEEE 802.1AB-2005 9.5.6.2"
        ::= { atiStkSwLldpRemBaseEntry 10 }

atiStkSwLldpRemSysDesc  OBJECT-TYPE
        SYNTAX          DisplayString
        MAX-ACCESS      read-only
        STATUS          current
        DESCRIPTION
                "The string value used to identify the system description
                of the remote system."
        REFERENCE
                "IEEE 802.1AB-2005 9.5.7.2"
        ::= { atiStkSwLldpRemBaseEntry 11 }

atiStkSwLldpRemSysCapSupported  OBJECT-TYPE
        SYNTAX          BITS    {
                                other (0),
                                repeater (1),
                                bridge (2),
                                wlanAccessPoint (3),
                                router (4),
                                telephone (5),
                                docsisCableDevice (6),
                                stationOnly (7)
                                }
        MAX-ACCESS      read-only
        STATUS          current
        DESCRIPTION
                "The bitmap value used to identify which system capabilities
                are supported on the remote system."
        REFERENCE
                "IEEE 802.1AB-2005 9.5.8.1"
        ::= { atiStkSwLldpRemBaseEntry 12 }

atiStkSwLldpRemSysCapEnabled  OBJECT-TYPE
        SYNTAX          BITS    {
                                other (0),
                                repeater (1),
                                bridge (2),
                                wlanAccessPoint (3),
                                router (4),
                                telephone (5),
                                docsisCableDevice (6),
                                stationOnly (7)
                                }
        MAX-ACCESS      read-only
        STATUS          current
        DESCRIPTION
                "The bitmap value used to identify which system capabilities
                are enabled on the remote system."
        REFERENCE
                "IEEE 802.1AB-2005 9.5.8.2"
        ::= { atiStkSwLldpRemBaseEntry 13 }

atiStkSwLldpRemManAddrSubtype  OBJECT-TYPE
        SYNTAX          INTEGER { -- AddressFamilyNumbers FROM IANA-ADDRESS-FAMILY-NUMBERS-MIB;
                                other (0),
                                ipV4 (1),
                                ipV6 (2),
                                nsap (3),
                                hdlc (4),
                                bbn1822 (5),
                                all802 (6),
                                e163 (7),
                                e164 (8),
                                f69 (9),
                                x121 (10),
                                ipx (11),
                                appleTalk (12),
                                decnetIV (13),
                                banyanVines (14),
                                e164withNsap (15),
                                dns (16),
                                distinguishedName (17), -- (Distinguished Name, per X.500)
                                asNumber (18), -- (16-bit quantity, per the AS number space)
                                xtpOverIpv4 (19),
                                xtpOverIpv6 (20),
                                xtpNativeModeXTP (21),
                                fibreChannelWWPN (22),
                                fibreChannelWWNN (23),
                                gwid (24),
                                afi (25),
                                reserved (65535)
                                }
        MAX-ACCESS      read-only
        STATUS          current
        DESCRIPTION
                "The type of management address identifier encoding used in
                the associated atiStkSwLldpRemManAddr object."
        REFERENCE
                "IEEE 802.1AB-2005 9.5.9.3"
        ::= { atiStkSwLldpRemBaseEntry 14 }

atiStkSwLldpRemManAddr  OBJECT-TYPE
        SYNTAX          IpAddress
        MAX-ACCESS      read-only
        STATUS          current
        DESCRIPTION
                "The string value used to identify the management address
                component associated with the remote system.  The purpose
                of this address is to contact the management entity."
        REFERENCE
                "IEEE 802.1AB-2005 9.5.9.4"
        ::= { atiStkSwLldpRemBaseEntry 15 }

atiStkSwLldpRemManAddrIfSubtype  OBJECT-TYPE
        SYNTAX          INTEGER {
                                unknown (1),
                                ifIndex (2),
                                systemPortNumber (3)
                                }
        MAX-ACCESS      read-only
        STATUS          current
        DESCRIPTION
                "The enumeration value that identifies the interface numbering
                method used for defining the interface number, associated
                with the remote system."
        REFERENCE
                "IEEE 802.1AB-2005 9.5.9.5"
        ::= { atiStkSwLldpRemBaseEntry 16 }

atiStkSwLldpRemManAddrIfId  OBJECT-TYPE
        SYNTAX          Integer32
        MAX-ACCESS      read-only
        STATUS          current
        DESCRIPTION
                "The integer value used to identify the interface number
                regarding the management address component associated with
                the remote system."
        REFERENCE
                "IEEE 802.1AB-2005 9.5.9.6"
        ::= { atiStkSwLldpRemBaseEntry 17 }

atiStkSwLldpRemManAddrOID  OBJECT-TYPE
        SYNTAX          OBJECT IDENTIFIER
        MAX-ACCESS      read-only
        STATUS          current
        DESCRIPTION
                "The OID value used to identify the type of hardware component
                or protocol entity associated with the management address
                advertised by the remote system agent."
        REFERENCE
                "IEEE 802.1AB-2005 9.5.9.8"
        ::= { atiStkSwLldpRemBaseEntry 18 }

------------------------------------------------------------------------------
-- IEEE 802.1 - Remote System Information
------------------------------------------------------------------------------

-- atiStkSwLldpRemDot1Data

atiStkSwLldpDot1RemTable  OBJECT-TYPE
        SYNTAX          SEQUENCE OF AtiStkSwLldpDot1RemEntry
        MAX-ACCESS      not-accessible
        STATUS          current
        DESCRIPTION
                "This table contains one or more rows per physical network
                connection known to this agent."
        ::= { atiStkSwLldpRemoteData 2 }

atiStkSwLldpDot1RemEntry  OBJECT-TYPE
        SYNTAX          AtiStkSwLldpDot1RemEntry
        MAX-ACCESS      not-accessible
        STATUS          current
        DESCRIPTION
                "Information about a particular port component."
        INDEX           { atiStkSwLldpDot1RemIndex }
        ::= { atiStkSwLldpDot1RemTable 1 }

AtiStkSwLldpDot1RemEntry ::=
        SEQUENCE {
                atiStkSwLldpDot1RemModuleId             Integer32,
                atiStkSwLldpDot1RemPortNum              Integer32,
                atiStkSwLldpDot1RemIndex                Integer32,
                atiStkSwLldpDot1RemPortVlanId           Integer32,
                atiStkSwLldpDot1RemProtoVlanId          Integer32,
                atiStkSwLldpDot1RemProtoVlanSupported   INTEGER,
                atiStkSwLldpDot1RemProtoVlanEnabled     INTEGER,
                atiStkSwLldpDot1RemVlanId               DisplayString,
                atiStkSwLldpDot1RemVlanName             DisplayString,
                atiStkSwLldpDot1RemProtocolId           DisplayString
        }

atiStkSwLldpDot1RemModuleId  OBJECT-TYPE
        SYNTAX          Integer32 --(1..8)
        MAX-ACCESS      read-only
        STATUS          current
        DESCRIPTION
                "This object specifies the ID of a module present in the switch
                stack."
        ::= { atiStkSwLldpDot1RemEntry 1 }

atiStkSwLldpDot1RemPortNum  OBJECT-TYPE
        SYNTAX          Integer32 --(1..50)
        MAX-ACCESS      read-only
        STATUS          current
        DESCRIPTION
                "The index value used to identify the port component
                (contained in the local chassis with the LLDP agent)
                associated with this entry.  The atiStkSwLldpRemPortNum
                identifies the port on which the remote system information
                is received."
        ::= { atiStkSwLldpDot1RemEntry 2 }

atiStkSwLldpDot1RemIndex  OBJECT-TYPE
        SYNTAX          Integer32 (0..255)
        MAX-ACCESS      read-only
        STATUS          current
        DESCRIPTION
                "This object represents an arbitrary local integer value used
                by this agent to identify a particular connection instance,
        unique only for the indicated remote system."
        ::= { atiStkSwLldpDot1RemEntry 3 }

atiStkSwLldpDot1RemPortVlanId  OBJECT-TYPE
        SYNTAX          Integer32 (0|1..4094)
        MAX-ACCESS      read-only
        STATUS          current
        DESCRIPTION
                "The integer value used to identify the port's VLAN identifier
                associated with the remote system.  if the remote system
                either does not know the PVID or does not support port-based
                VLAN operation, the value of atiStkSwLldpDot1RemPortVlanId should
                be zero."
        REFERENCE
                "IEEE 802.1AB-2005 F.2.1"
        ::= { atiStkSwLldpDot1RemEntry 4 }

--
-- atiStkSwLldpDot1RemProtoVlanTable: Port and Protocol VLAN information
--

atiStkSwLldpDot1RemProtoVlanId  OBJECT-TYPE
        SYNTAX          Integer32 (0|1..4094)
        MAX-ACCESS      read-only
        STATUS          current
        DESCRIPTION
                "The integer value used to identify the port and protocol
                VLANs associated with the given port associated with the
                remote system.

                If port and protocol VLANs are not supported on the given
                port associated with the remote system, or if the port is
                not enabled with any port and protocol VLAN, the value of
                atiStkSwLldpDot1RemProtoVlanId should be zero."
        REFERENCE
                "IEEE 802.1AB-2005 F.3.2"
        ::= { atiStkSwLldpDot1RemEntry 5 }

atiStkSwLldpDot1RemProtoVlanSupported  OBJECT-TYPE
        SYNTAX          INTEGER {
                                enabled (1),
                                disabled (2)
                                }
        MAX-ACCESS      read-only
        STATUS          current
        DESCRIPTION
                "The truth value used to indicate whether the given port
                (associated with the remote system) is capable of supporting
                port and protocol VLANs."
        REFERENCE
                "IEEE 802.1AB-2005 F.3.1"
        ::= { atiStkSwLldpDot1RemEntry 6 }

atiStkSwLldpDot1RemProtoVlanEnabled  OBJECT-TYPE
        SYNTAX          INTEGER {
                                enabled (1),
                                disabled (2)
                                }
        MAX-ACCESS      read-only
        STATUS          current
        DESCRIPTION
                "The truth value used to indicate whether the port and
                protocol VLANs are enabled on the given port associated with
                the remote system."
        REFERENCE
                "IEEE 802.1AB-2005 F.3.1"
        ::= { atiStkSwLldpDot1RemEntry 7 }

--
-- atiStkSwLldpDot1RemVlanNameTable : VLAN name information of the remote
--                                    systems
--

atiStkSwLldpDot1RemVlanId  OBJECT-TYPE
        SYNTAX          DisplayString
        MAX-ACCESS      read-only
        STATUS          current
        DESCRIPTION
                "The integer value used to identify the IEEE 802.1Q
                VLAN IDs with which the given port of the remote system
                is compatible."
        REFERENCE
                "IEEE 802.1AB-2005 F.4.2"
        ::= { atiStkSwLldpDot1RemEntry 8 }

atiStkSwLldpDot1RemVlanName  OBJECT-TYPE
        SYNTAX          DisplayString
        MAX-ACCESS      read-only
        STATUS          current
        DESCRIPTION
                "The string value used to identify VLAN name identified by the
                VLAN Id associated with the remote system."
        REFERENCE
                "IEEE 802.1AB-2005 F.4.4"
        ::= { atiStkSwLldpDot1RemEntry 9 }

--
-- atiStkSwLldpDot1RemProtocolTable : Protocol information of the remote systems
--

atiStkSwLldpDot1RemProtocolId  OBJECT-TYPE
        SYNTAX          DisplayString
        MAX-ACCESS      read-only
        STATUS          current
        DESCRIPTION
                "The octet string value used to identify the protocols
                associated with the given port of remote system."
        REFERENCE
                "IEEE 802.1AB-2005 F.5.3"
        ::= { atiStkSwLldpDot1RemEntry 10 }

------------------------------------------------------------------------------
-- IEEE 802.3 - Remote Device Information
------------------------------------------------------------------------------

-- atiStkSwLldpRemDot3Data

atiStkSwLldpRemDot3Data  OBJECT IDENTIFIER ::= { atiStkSwLldpRemoteData 3 }

atiStkSwLldpDot3RemTable  OBJECT-TYPE
        SYNTAX          SEQUENCE OF AtiStkSwLldpDot3RemEntry
        MAX-ACCESS      not-accessible
        STATUS          current
        DESCRIPTION
                "This table contains Ethernet port information (as a part
                of the LLDP 802.3 organizational extension) of the remote
                system."
        ::= { atiStkSwLldpRemDot3Data 1 }

atiStkSwLldpDot3RemEntry  OBJECT-TYPE
        SYNTAX          AtiStkSwLldpDot3RemEntry
        MAX-ACCESS      not-accessible
        STATUS          current
        DESCRIPTION
                "Information about a particular physical network connection."
        INDEX           { atiStkSwLldpRemIndex }
        ::= { atiStkSwLldpDot3RemTable 1 }

AtiStkSwLldpDot3RemEntry ::=
        SEQUENCE {
                atiStkSwLldpDot3RemModuleNum                    Integer32,
                atiStkSwLldpDot3RemPortNum                      Integer32,
                atiStkSwLldpDot3RemIndex                        Integer32,
                atiStkSwLldpDot3RemPortAutoNegSupported         INTEGER,
                atiStkSwLldpDot3RemPortAutoNegEnabled           INTEGER,
                atiStkSwLldpDot3RemPortAutoNegAdvertisedCap     BITS,
                atiStkSwLldpDot3RemPortOperMauType              INTEGER,
                atiStkSwLldpDot3RemPowerPortClass               INTEGER,
                atiStkSwLldpDot3RemPowerMDISupported            INTEGER,
                atiStkSwLldpDot3RemPowerMDIEnabled              INTEGER,
                atiStkSwLldpDot3RemPowerPairControlable         INTEGER,
                atiStkSwLldpDot3RemPowerPairs                   Integer32,
                atiStkSwLldpDot3RemPowerClass                   Integer32,
                atiStkSwLldpDot3RemLinkAggStatus                BITS,
                atiStkSwLldpDot3RemLinkAggPortId                Integer32,
                atiStkSwLldpDot3RemMaxFrameSize                 Integer32
        }

atiStkSwLldpDot3RemModuleNum  OBJECT-TYPE
        SYNTAX          Integer32 --(1..8)
        MAX-ACCESS      read-only
        STATUS          current
        DESCRIPTION
                "This object specifies the ID of a module present in the switch
                stack."
        ::= { atiStkSwLldpDot3RemEntry 1 }

atiStkSwLldpDot3RemPortNum  OBJECT-TYPE
        SYNTAX          Integer32 --(1..50)
        MAX-ACCESS      read-only
        STATUS          current
        DESCRIPTION
                "The index value used to identify the port component
                (contained in the local chassis with the LLDP agent)
                associated with this entry.  The atiStkSwLldpDot3RemPortNum
                identifies the port on which the remote system information
                is received."
        ::= { atiStkSwLldpDot3RemEntry 2 }

atiStkSwLldpDot3RemIndex  OBJECT-TYPE
        SYNTAX          Integer32
        MAX-ACCESS      read-only
        STATUS          current
        DESCRIPTION
                "This object represents an arbitrary local integer value used
                by this agent to identify a particular connection instance,
                unique only for the indicated remote system."
        ::= { atiStkSwLldpDot3RemEntry 3 }

---
--- atiStkSwLldpDot3RemPortTable: Ethernet Information Table
---

atiStkSwLldpDot3RemPortAutoNegSupported  OBJECT-TYPE
        SYNTAX          INTEGER {
                                enabled (1),
                                disabled (2)
                                }
        MAX-ACCESS      read-only
        STATUS          current
        DESCRIPTION
                "The truth value used to indicate whether the given port
                (associated with remote system) supports Auto-negotiation."
        REFERENCE
                "IEEE 802.1AB-2005 G.2.1"
        ::= { atiStkSwLldpDot3RemEntry 4 }

atiStkSwLldpDot3RemPortAutoNegEnabled  OBJECT-TYPE
        SYNTAX          INTEGER {
                                enabled (1),
                                disabled (2)
                                }
        MAX-ACCESS      read-only
        STATUS          current
        DESCRIPTION
                "The truth value used to indicate whether port
                Auto-negotiation is enabled on the given port associated
                with the remote system."
        REFERENCE
                "IEEE 802.1AB-2005 G.2.1"
        ::= { atiStkSwLldpDot3RemEntry 5 }

atiStkSwLldpDot3RemPortAutoNegAdvertisedCap  OBJECT-TYPE
        SYNTAX          BITS    {
                                bOther (0),             -- other or unknown
                                b10baseT (1),           -- 10BASE-T  half duplex mode
                                b10baseTFD (2),         -- 10BASE-T  full duplex mode
                                b100baseT4 (3),         -- 100BASE-T4
                                b100baseTX (4),         -- 100BASE-TX half duplex mode
                                b100baseTXFD (5),       -- 100BASE-TX full duplex mode
                                b100baseT2 (6),         -- 100BASE-T2 half duplex mode
                                b100baseT2FD (7),       -- 100BASE-T2 full duplex mode
                                bFdxPause (8),          -- PAUSE for full-duplex links
                                bFdxAPause (9),         -- Asymmetric PAUSE for full-duplex links
                                bFdxSPause (10),        -- Symmetric PAUSE for full-duplex links
                                bFdxBPause (11),        -- Asymmetric and Symmetric PAUSE for full-duplex links
                                b1000baseX (12),        -- 1000BASE-X, -LX, -SX, -CX half duplex mode
                                b1000baseXFD (13),      -- 1000BASE-X, -LX, -SX, -CX full duplex mode
                                b1000baseT (14),        -- 1000BASE-T half duplex mode
                                b1000baseTFD (15)       -- 1000BASE-T full duplex mode
                                }
        MAX-ACCESS      read-only
        STATUS          current
        DESCRIPTION
                "This object contains the value (bitmap) of the
                ifMauAutoNegCapAdvertisedBits object (defined in IETF RFC
                3636) which is associated with the given port on the
                remote system."
        REFERENCE
                "IEEE 802.1AB-2005 G.2.2"
        ::= { atiStkSwLldpDot3RemEntry 6 }

atiStkSwLldpDot3RemPortOperMauType  OBJECT-TYPE
        SYNTAX          INTEGER {
                                dot3MauTypeAUI (1),
                                dot3MauType10Base5 (2),
                                dot3MauTypeFoirl (3),
                                dot3MauType10Base2 (4),
                                dot3MauType10BaseT (5),
                                dot3MauType10BaseFP (6),
                                dot3MauType10BaseFB (7),
                                dot3MauType10BaseFL (8),
                                dot3MauType10Broad36 (9),
                                dot3MauType10BaseTHD (10),
                                dot3MauType10BaseTFD (11),
                                dot3MauType10BaseFLHD (12),
                                dot3MauType10BaseFLFD (13),
                                dot3MauType100BaseT4 (14),
                                dot3MauType100BaseTXHD (15),
                                dot3MauType100BaseTXFD (16),
                                dot3MauType100BaseFXHD (17),
                                dot3MauType100BaseFXFD (18),
                                dot3MauType100BaseT2HD (19),
                                dot3MauType100BaseT2FD (20),
                                dot3MauType1000BaseXHD (21),
                                dot3MauType1000BaseXFD (22),
                                dot3MauType1000BaseLXHD (23),
                                dot3MauType1000BaseLXFD (24),
                                dot3MauType1000BaseSXHD (25),
                                dot3MauType1000BaseSXFD (26),
                                dot3MauType1000BaseCXHD (27),
                                dot3MauType1000BaseCXFD (28),
                                dot3MauType1000BaseTHD (29),
                                dot3MauType1000BaseTFD (30),
                                dot3MauType10GigBaseX (31),
                                dot3MauType10GigBaseLX4 (32),
                                dot3MauType10GigBaseR (33),
                                dot3MauType10GigBaseER (34),
                                dot3MauType10GigBaseLR (35),
                                dot3MauType10GigBaseSR (36),
                                dot3MauType10GigBaseW (37),
                                dot3MauType10GigBaseEW (38),
                                dot3MauType10GigBaseLW (39),
                                dot3MauType10GigBaseSW (40)
                                }
        MAX-ACCESS      read-only
        STATUS          current
        DESCRIPTION
                "An integer value that indicates the operational MAU type
                of the sending device.

                This object contains the integer value derived from the
                list position of the corresponding dot3MauType as listed in
                in IETF RFC 3636 (or subsequent revisions) and is equal
                to the last number in the respective dot3MauType OID.

                For example, if the ifMauType object is dot3MauType1000BaseTHD
                which corresponds to {dot3MauType 29}, the numerical value of
                this field will be 29. For MAU types not listed in RFC 3636
                (or subsequent revisions), the value of this field shall be
                set to zero."
        REFERENCE
                "IEEE 802.1AB-2005 G.2.3"
        ::= { atiStkSwLldpDot3RemEntry 7 }

---
--- atiStkSwLldpDot3RemPowerTable: Power Ethernet Information Table
---

atiStkSwLldpDot3RemPowerPortClass  OBJECT-TYPE
        SYNTAX          INTEGER {
                                pClassPSE (1),
                                pClassPD (2)
                                }
        MAX-ACCESS      read-only
        STATUS          current
        DESCRIPTION
                "The value that identifies the port Class of the given port
                associated with the remote system."
        REFERENCE
                "IEEE 802.1AB-2005 G.3.1"
        ::= { atiStkSwLldpDot3RemEntry 8 }

atiStkSwLldpDot3RemPowerMDISupported  OBJECT-TYPE
        SYNTAX          INTEGER {
                                enabled (1),
                                disabled (2)
                                }
        MAX-ACCESS      read-only
        STATUS          current
        DESCRIPTION
                "The truth value used to indicate whether the MDI power
                is supported on the given port associated with the remote
                system."
        REFERENCE
                "IEEE 802.1AB-2005 G.3.1"
        ::= { atiStkSwLldpDot3RemEntry 9 }

atiStkSwLldpDot3RemPowerMDIEnabled  OBJECT-TYPE
        SYNTAX          INTEGER {
                                enabled (1),
                                disabled (2)
                                }
        MAX-ACCESS      read-only
        STATUS          current
        DESCRIPTION
                "The truth value used to identify whether MDI power is
                enabled on the given port associated with the remote system."
        REFERENCE
                "IEEE 802.1AB-2005 G.3.1"
        ::= { atiStkSwLldpDot3RemEntry 10 }

atiStkSwLldpDot3RemPowerPairControlable  OBJECT-TYPE
        SYNTAX          INTEGER {
                                enabled (1),
                                disabled (2)
                                }
        MAX-ACCESS      read-only
        STATUS          current
        DESCRIPTION
                "The truth value is derived from the value of
                pethPsePortPowerPairsControlAbility object (defined in IETF
                RFC 3621) and is used to indicate whether the pair selection
                can be controlled on the given port associated with the
                remote system."
        REFERENCE
                "IEEE 802.1AB-2005 G.3.1"
        ::= { atiStkSwLldpDot3RemEntry 11 }

atiStkSwLldpDot3RemPowerPairs  OBJECT-TYPE
        SYNTAX          Integer32 (1|2)
        MAX-ACCESS      read-only
        STATUS          current
        DESCRIPTION
                "This object contains the value of the pethPsePortPowerPairs
                object (defined in IETF RFC 3621) which is associated with
                the given port on the remote system."
        REFERENCE
                "IEEE 802.1AB-2005 G.3.2"
        ::= { atiStkSwLldpDot3RemEntry 12 }

atiStkSwLldpDot3RemPowerClass  OBJECT-TYPE
        SYNTAX          Integer32 (1|2|3|4|5)
        MAX-ACCESS      read-only
        STATUS          current
        DESCRIPTION
                "This object contains the value of the
                pethPsePortPowerClassifications object (defined in IETF
                RFC 3621) which is associated with the given port on the
                remote system."
        REFERENCE
                "IEEE 802.1AB-2005 G.3.3"
        ::= { atiStkSwLldpDot3RemEntry 13 }

---
--- atiStkSwLldpDot3RemLinkAggTable: Link Aggregation Information Table
---

atiStkSwLldpDot3RemLinkAggStatus  OBJECT-TYPE
        SYNTAX          BITS    {
                                aggCapable (7),
                                aggEnabled (8)
                                }
        MAX-ACCESS      read-only
        STATUS          current
        DESCRIPTION
                "The bitmap value contains the link aggregation capabilities
                and the current aggregation status of the link."
        REFERENCE
                "IEEE 802.1AB-2005 G.4.1"
        ::= { atiStkSwLldpDot3RemEntry 14 }

atiStkSwLldpDot3RemLinkAggPortId  OBJECT-TYPE
        SYNTAX          Integer32 (0|1..2147483647)
        MAX-ACCESS      read-only
        STATUS          current
        DESCRIPTION
                "This object contains the IEEE 802.3 aggregated port
                identifier, aAggPortID (IEEE 802.3-2002, 30.7.2.1.1),
                derived from the ifNumber of the ifIndex for the port
                component associated with the remote system.

                If the remote port is not in link aggregation state and/or
                it does not support link aggregation, this value should be
                zero."
        REFERENCE
                "IEEE 802.1AB-2005 G.4.2"
        ::= { atiStkSwLldpDot3RemEntry 15 }

---
--- atiStkSwLldpDot3RemMaxFrameSizeTable: Maximum Frame Size information
---

atiStkSwLldpDot3RemMaxFrameSize  OBJECT-TYPE
        SYNTAX          Integer32 (0..65535)
        MAX-ACCESS      read-only
        STATUS          current
        DESCRIPTION
                "An integer value indicating the maximum supported frame
                size in octets on the port component associated with the
                remote system."
        REFERENCE
                "IEEE 802.1AB-2005 G.5.1"
        ::= { atiStkSwLldpDot3RemEntry 16 }

------------------------------------------------------------------------------
-- LLDP-MED  - Remote Devices Information
------------------------------------------------------------------------------

-- atiStkSwLldpRemMedData

atiStkSwLldpRemMedData  OBJECT IDENTIFIER ::= { atiStkSwLldpRemoteData 4 }

atiStkSwLldpMedRemTable OBJECT-TYPE
        SYNTAX          SEQUENCE OF AtiStkSwLldpMedRemEntry
        MAX-ACCESS      not-accessible
        STATUS          current
        DESCRIPTION
                "This table contains LLDP-MED information of the remote
                system."
        ::= { atiStkSwLldpRemMedData 1 }

atiStkSwLldpMedRemEntry OBJECT-TYPE
        SYNTAX          AtiStkSwLldpMedRemEntry
        MAX-ACCESS      not-accessible
        STATUS          current
        DESCRIPTION
                "Information about a particular physical network connection."
        INDEX           { atiStkSwLldpRemIndex }
        ::= { atiStkSwLldpMedRemTable 1 }

AtiStkSwLldpMedRemEntry ::=
        SEQUENCE {
                atiStkSwLldpMedRemModuleId              Integer32,
                atiStkSwLldpMedRemPortNum               Integer32,
                atiStkSwLldpMedRemIndex                 Integer32,
                atiStkSwLldpMedRemDeviceClass           AtiStkSwLldpMedDeviceClass,
                atiStkSwLldpMedRemCapabilities          AtiStkSwLldpMedCapabilities,
                atiStkSwLldpMedRemMediaPolicyAppType    PolicyAppType,
                atiStkSwLldpMedRemMediaPolicyVlanID     Integer32,
                atiStkSwLldpMedRemMediaPolicyPriority   Integer32,
                atiStkSwLldpMedRemMediaPolicyDscp       Integer32,
                atiStkSwLldpMedRemMediaPolicyUnknown    TruthValue,
                atiStkSwLldpMedRemMediaPolicyTagged     TruthValue,
                atiStkSwLldpMedRemHardwareRev           DisplayString,
                atiStkSwLldpMedRemFirmwareRev           DisplayString,
                atiStkSwLldpMedRemSoftwareRev           DisplayString,
                atiStkSwLldpMedRemSerialNum             DisplayString,
                atiStkSwLldpMedRemMfgName               DisplayString,
                atiStkSwLldpMedRemModelName             DisplayString,
                atiStkSwLldpMedRemAssetID               DisplayString,
                atiStkSwLldpMedRemXPoEDeviceType        INTEGER,
                atiStkSwLldpMedRemXPoEPSEPowerAv        Gauge32,
                atiStkSwLldpMedRemXPoEPSEPowerSource    INTEGER,
                atiStkSwLldpMedRemXPoEPSEPowerPriority  INTEGER,
                atiStkSwLldpMedRemXPoEPDPowerReq        Gauge32,
                atiStkSwLldpMedRemXPoEPDPowerSource     INTEGER,
                atiStkSwLldpMedRemXPoEPDPowerPriority   INTEGER,
                atiStkSwLldpMedRemCoordLocation         DisplayString,
                atiStkSwLldpMedRemCivicLocation         DisplayString,
                atiStkSwLldpMedRemElinLocation          DisplayString
        }

atiStkSwLldpMedRemModuleId  OBJECT-TYPE
        SYNTAX          Integer32 --(1..8)
        MAX-ACCESS      read-only
        STATUS          current
        DESCRIPTION
                "This object specifies the ID of a module present in the switch
                stack."
        ::= { atiStkSwLldpMedRemEntry 1 }

atiStkSwLldpMedRemPortNum  OBJECT-TYPE
        SYNTAX          Integer32 --(1..50)
        MAX-ACCESS      read-only
        STATUS          current
        DESCRIPTION
                "The index value used to identify the port component
                (contained in the local chassis with the LLDP agent)
                associated with this entry."
        ::= { atiStkSwLldpMedRemEntry 2 }

atiStkSwLldpMedRemIndex OBJECT-TYPE
        SYNTAX          Integer32
        MAX-ACCESS      read-only
        STATUS          current
        DESCRIPTION
                "This object represents an arbitrary local integer value used
                by this agent to identify a particular connection instance,
                unique only for the indicated remote system."
        ::= { atiStkSwLldpMedRemEntry 3 }

atiStkSwLldpMedRemDeviceClass    OBJECT-TYPE
        SYNTAX          AtiStkSwLldpMedDeviceClass
        MAX-ACCESS      read-only
        STATUS          current
        DESCRIPTION
                "Device Class as advertised by the device remotely connected to the
                port."
        REFERENCE
                "ANSI/TIA-1057, Section 10.2.2.2"
        ::= { atiStkSwLldpMedRemEntry 4 }

atiStkSwLldpMedRemCapabilities  OBJECT-TYPE
        SYNTAX          AtiStkSwLldpMedCapabilities
        MAX-ACCESS      read-only
        STATUS          current
        DESCRIPTION
                "The bitmap includes the MED organizationally defined set of LLDP
                TLVs whose transmission is possible on the LLDP agent of the remote
                device connected to this port. Each bit in the bitmap corresponds
                to an LLDP-MED subtype associated with a specific TIA TR41.4 MED
                optional TLV. If the bit is set, the agent has the capability
                to support the corresponding TLV."
        REFERENCE
                "ANSI/TIA-1057, Sections 10.2.2.1"
        ::= { atiStkSwLldpMedRemEntry 5 }

atiStkSwLldpMedRemMediaPolicyAppType  OBJECT-TYPE
        SYNTAX          PolicyAppType
        MAX-ACCESS      not-accessible
        STATUS          current
        DESCRIPTION
                "The media type that defines the primary function of the
                application for the policy advertised by the endpoint connected
                remotely to this port."
        REFERENCE
                "ANSI/TIA-1057, Section 10.2.3.1"
        ::= { atiStkSwLldpMedRemEntry 6 }

atiStkSwLldpMedRemMediaPolicyVlanID  OBJECT-TYPE
        SYNTAX          Integer32 (0|1..4094|4095)
        MAX-ACCESS      read-only
        STATUS          current
        DESCRIPTION
                "An extension of the VLAN Identifier for the remote system
                connected to this port, as defined in IEEE 802.1P-1998.

                A value of 1 through 4094 is used to define a valid PVID.

                A value of 0 shall be used if the device is using priority tagged
                frames, meaning that only the 802.1p priority level is significant
                and the default VID of the ingress port is being used instead.

                A value of 4095 is reserved for implementation use."
        REFERENCE
                "ANSI/TIA-1057, Section 10.2.3.5"
        ::= { atiStkSwLldpMedRemEntry 7 }

atiStkSwLldpMedRemMediaPolicyPriority  OBJECT-TYPE
        SYNTAX          Integer32 (0..7)
        MAX-ACCESS      read-only
        STATUS          current
        DESCRIPTION
                "This object contains the value of the 802.1p priority
                which is associated with the remote system connected at
                given port."
        REFERENCE
                "ANSI/TIA-1057, Section 10.2.3.6"
        ::= { atiStkSwLldpMedRemEntry 8 }

atiStkSwLldpMedRemMediaPolicyDscp  OBJECT-TYPE
        SYNTAX          Integer32 (0..63)
        MAX-ACCESS      read-only
        STATUS          current
        DESCRIPTION
                "This object contains the value of the Differentiated Service
                Code Point (DSCP) as defined in IETF RFC 2474 and RFC 2475
                which is associated with remote system connected at the port."
        REFERENCE
                "ANSI/TIA-1057, Section 10.2.3.7"
        ::= { atiStkSwLldpMedRemEntry 9 }

atiStkSwLldpMedRemMediaPolicyUnknown  OBJECT-TYPE
        SYNTAX          TruthValue
        MAX-ACCESS      read-only
        STATUS          current
        DESCRIPTION
                "A value of 'true' indicates that the
                network policy for the specified application type is
                currently unknown.  In this case, the VLAN ID, the
                layer 2 priority and the DSCP value fields are ignored.
                A value of 'false' indicates that this network policy
                is defined."
        REFERENCE
                "ANSI/TIA-1057, Section 10.2.3.2"
        ::= { atiStkSwLldpMedRemEntry 10 }

atiStkSwLldpMedRemMediaPolicyTagged  OBJECT-TYPE
        SYNTAX          TruthValue
        MAX-ACCESS      read-only
        STATUS          current
        DESCRIPTION
                "A value of 'true' indicates that the application is using a
                tagged VLAN.
                A value of 'false' indicates that for the specific application
                the device either is using an untagged VLAN or does not
                support port based VLAN operation.  In this case, both the
                VLAN ID and the Layer 2 priority fields are ignored and
                only the DSCP value has relevance "
        REFERENCE
                "ANSI/TIA-1057, Section 10.2.3.3"
        ::= { atiStkSwLldpMedRemEntry 11 }

atiStkSwLldpMedRemHardwareRev  OBJECT-TYPE
        SYNTAX          DisplayString (SIZE (0..32))
        MAX-ACCESS      read-only
        STATUS          current
        DESCRIPTION
                "The vendor-specific hardware revision string
                as advertised by the remote endpoint."
        REFERENCE
                "ANSI/TIA-1057, Section 10.2.6.1"
        ::= { atiStkSwLldpMedRemEntry 12 }

atiStkSwLldpMedRemFirmwareRev  OBJECT-TYPE
        SYNTAX          DisplayString (SIZE (0..32))
        MAX-ACCESS      read-only
        STATUS          current
        DESCRIPTION
                "The vendor-specific firmware revision string
                as advertised by the remote endpoint."
        REFERENCE
                "ANSI/TIA-1057, Section 10.2.6.2"
        ::= { atiStkSwLldpMedRemEntry 13 }

atiStkSwLldpMedRemSoftwareRev  OBJECT-TYPE
        SYNTAX          DisplayString (SIZE (0..32))
        MAX-ACCESS      read-only
        STATUS          current
        DESCRIPTION
                "The vendor-specific software revision string
                as advertised by the remote endpoint."
        REFERENCE
                "ANSI/TIA-1057, Section 10.2.6.3"
        ::= { atiStkSwLldpMedRemEntry 14 }

atiStkSwLldpMedRemSerialNum  OBJECT-TYPE
        SYNTAX          DisplayString (SIZE (0..32))
        MAX-ACCESS      read-only
        STATUS          current
        DESCRIPTION
                "The vendor-specific serial number
                as advertised by the remote endpoint."
        REFERENCE
                "ANSI/TIA-1057, Section 10.2.6.4"
        ::= { atiStkSwLldpMedRemEntry 15 }

atiStkSwLldpMedRemMfgName  OBJECT-TYPE
        SYNTAX          DisplayString (SIZE (0..32))
        MAX-ACCESS      read-only
        STATUS          current
        DESCRIPTION
                "The vendor-specific manufacturer name
                as advertised by the remote endpoint."
        REFERENCE
                "ANSI/TIA-1057, Section 10.2.6.5"
        ::= { atiStkSwLldpMedRemEntry 16 }

atiStkSwLldpMedRemModelName  OBJECT-TYPE
        SYNTAX          DisplayString (SIZE (0..32))
        MAX-ACCESS      read-only
        STATUS          current
        DESCRIPTION
                "The vendor-specific model name
                as advertised by the remote endpoint."
        REFERENCE
                "ANSI/TIA-1057, Section 10.2.6.6"
        ::= { atiStkSwLldpMedRemEntry 17 }

atiStkSwLldpMedRemAssetID  OBJECT-TYPE
        SYNTAX          DisplayString (SIZE (0..32))
        MAX-ACCESS      read-only
        STATUS          current
        DESCRIPTION
                "The vendor-specific asset tracking identifier
                as advertised by the remote endpoint."
        REFERENCE
                "ANSI/TIA-1057, Section 10.2.6.7"
        ::= { atiStkSwLldpMedRemEntry 18 }

--- Information about Remote PoE Device Type
---
atiStkSwLldpMedRemXPoEDeviceType  OBJECT-TYPE
        SYNTAX          INTEGER {
                                unknown (1),
                                pseDevice (2),
                                pdDevice (3),
                                none (4)
                                }
        MAX-ACCESS      read-only
        STATUS          current
        DESCRIPTION
                "Defines the type of Power-via-MDI (Power over Ethernet) advertised
                by the remote device.

                A value pseDevice(2) indicates that the device is advertised as a
                Power Sourcing Entity (PSE).

                A value pdDevice(3) indicates that the device is advertised as a
                Powered Device (PD).

                A value none(4) indicates that the device does not support PoE."
        REFERENCE
                "ANSI/TIA-1057, Section 10.2.5.1"
        ::= { atiStkSwLldpMedRemEntry 19 }

--- Extended PoE PSE Information from the remote device
---
atiStkSwLldpMedRemXPoEPSEPowerAv  OBJECT-TYPE
        SYNTAX          Gauge32 (0..1023)
        UNITS           "tenth of watt"
        MAX-ACCESS      read-only
        STATUS          current
        DESCRIPTION
                "This object contains the value of the power available from the
                PSE via this port expressed in units of 0.1 watts on the remote
                device."
        REFERENCE
                "ANSI/TIA-1057, Section 10.2.5.4"
        ::= { atiStkSwLldpMedRemEntry 20 }

atiStkSwLldpMedRemXPoEPSEPowerSource  OBJECT-TYPE
        SYNTAX          INTEGER {
                                unknown (1),
                                primary (2),
                                backup (3)
                                }
        MAX-ACCESS      read-only
        STATUS          current
        DESCRIPTION
                "Defines the type of PSE Power Source advertised
                by the remote device.

                A value primary(2) indicates that the device advertises its power
                source as primary.

                A value backup(3) indicates that the device advertises its power
                Source as backup."
        REFERENCE
                "ANSI/TIA-1057, Section 10.2.5.2"
        ::= { atiStkSwLldpMedRemEntry 21 }

atiStkSwLldpMedRemXPoEPSEPowerPriority  OBJECT-TYPE
        SYNTAX          INTEGER {
                                unknown (1),
                                critical (2),
                                high (3),
                                low (4)
                                }
        MAX-ACCESS      read-only
        STATUS          current
        DESCRIPTION
                "This object contains the value of the PSE power priority
                advertised by the remote device.

                A value critical(2) indicates that the device advertises its power
                priority as critical, as per RFC 3621.

                A value high(3) indicates that the device advertises its power
                priority as high, as per RFC 3621.

                A value low(4) indicates that the device advertises its power
                priority as low, as per RFC 3621."
        REFERENCE
                "ANSI/TIA-1057, Section 10.2.5.3"
        ::= { atiStkSwLldpMedRemEntry 22 }

--- Extended PoE PD Information from the remote device
---
atiStkSwLldpMedRemXPoEPDPowerReq  OBJECT-TYPE
        SYNTAX          Gauge32 (0..1023)
        UNITS           "tenth of watt"
        MAX-ACCESS      read-only
        STATUS          current
        DESCRIPTION
                "This object contains the value of the power required by a
                PD connected remotely to the port
                expressed in units of 0.1 watts."
        REFERENCE
                "ANSI/TIA-1057, Section 10.2.5.4 "
        ::= { atiStkSwLldpMedRemEntry 23 }

atiStkSwLldpMedRemXPoEPDPowerSource  OBJECT-TYPE
        SYNTAX          INTEGER {
                                unknown (1),
                                fromPSE (2),
                                local (3),
                                localAndPSE (4)
                                }
        MAX-ACCESS      read-only
        STATUS          current
        DESCRIPTION
                "Defines the type of Power Source advertised as being used
                by the device connected remotely to the port.

                A value fromPSE(2) indicates that the device advertises its power
                source as received from a PSE.

                A value local(3) indicates that the device advertises its power
                source as local.

                A value localAndPSE(4) indicates that the device advertises its
                power source as using both local and PSE power."
        REFERENCE
                "ANSI/TIA-1057, Section 10.2.5.2"
        ::= { atiStkSwLldpMedRemEntry 24 }

atiStkSwLldpMedRemXPoEPDPowerPriority  OBJECT-TYPE
        SYNTAX          INTEGER {
                                unknown (1),
                                critical (2),
                                high (3),
                                low (4)
                                }
        MAX-ACCESS      read-only
        STATUS          current
        DESCRIPTION
                "Defines the priority advertised as being required by the PD
                connected remotely to the port.

                A value critical(2) indicates that the device advertises its power
                Priority as critical, as per RFC 3621.

                A value high(3) indicates that the device advertises its power
                Priority as high, as per RFC 3621.

                A value low(4) indicates that the device advertises its power
                Priority as low, as per RFC 3621."
        REFERENCE
                "ANSI/TIA-1057, Section 10.2.5.3"
        ::= { atiStkSwLldpMedRemEntry 25 }

atiStkSwLldpMedRemCoordLocation  OBJECT-TYPE
        SYNTAX          DisplayString
        MAX-ACCESS      read-only
        STATUS          current
        DESCRIPTION
                "Coordinate based location information"
        REFERENCE
                "ANSI/TIA-1057, Section 10.2.4.3"
        ::= { atiStkSwLldpMedRemEntry 26 }

atiStkSwLldpMedRemCivicLocation  OBJECT-TYPE
        SYNTAX          DisplayString
        MAX-ACCESS      read-only
        STATUS          current
        DESCRIPTION
                "Civic location information"
        REFERENCE
                "ANSI/TIA-1057, Section 10.2.4.3"
        ::= { atiStkSwLldpMedRemEntry 27 }

atiStkSwLldpMedRemElinLocation  OBJECT-TYPE
        SYNTAX          DisplayString
        MAX-ACCESS      read-only
        STATUS          current
        DESCRIPTION
                "Elin location information"
        REFERENCE
                "ANSI/TIA-1057, Section 10.2.4.3"
        ::= { atiStkSwLldpMedRemEntry 28 }

-- atiStkSwLldpRemResetTable

atiStkSwLldpRemResetTable  OBJECT-TYPE
        SYNTAX          SEQUENCE OF AtiStkSwLldpRemResetEntry
        MAX-ACCESS      not-accessible
        STATUS          current
        DESCRIPTION
                "This table resets the Neighbor Table of the specified port."
        ::= { atiStkSwLldpRemoteData 5 }

atiStkSwLldpRemResetEntry  OBJECT-TYPE
        SYNTAX          AtiStkSwLldpRemResetEntry
        MAX-ACCESS      not-accessible
        STATUS          current
        DESCRIPTION
                "Selection of module and port number for Neighbor Table to be reset."
        INDEX           { atiStkSwLldpRemResetPortNum }
    ::= { atiStkSwLldpRemResetTable 1 }

AtiStkSwLldpRemResetEntry ::=
        SEQUENCE {
                atiStkSwLldpRemResetModuleNum           Integer32,
                atiStkSwLldpRemResetPortNum             Integer32,
                atiStkSwLldpRemReset                    INTEGER
        }

atiStkSwLldpRemResetModuleNum  OBJECT-TYPE
        SYNTAX          Integer32 --(1..8)
        MAX-ACCESS      read-only
        STATUS          current
        DESCRIPTION
                "This object specifies the ID of a module present in the switch
                stack."
        ::= { atiStkSwLldpRemResetEntry 1 }

atiStkSwLldpRemResetPortNum  OBJECT-TYPE
        SYNTAX          Integer32 (1..50)
        MAX-ACCESS      read-only
        STATUS          current
        DESCRIPTION
                "The index value used to identify the port component
                for Neighbor Table to be reset."
        ::= { atiStkSwLldpRemResetEntry 2 }

atiStkSwLldpRemReset    OBJECT-TYPE
        SYNTAX          INTEGER {
                                yes (1),
                                no (2)
                                }
        MAX-ACCESS      read-write
        STATUS          current
        DESCRIPTION
                "Select 'yes' for Neighbor Table to be reset."
        ::= { atiStkSwLldpRemResetEntry 3 }

--
-- atiStkSwLldpCivicLocationTable
--

atiStkSwLldpCivicLocationTable  OBJECT-TYPE
        SYNTAX          SEQUENCE OF AtiStkSwLldpCivicLocationEntry
        MAX-ACCESS      not-accessible
        STATUS          current
        DESCRIPTION
                "A table of the LLDP civic-location."
        ::= { atiStkSwLldpGroup 5 }

atiStkSwLldpCivicLocationEntry  OBJECT-TYPE
        SYNTAX          AtiStkSwLldpCivicLocationEntry
        MAX-ACCESS      not-accessible
        STATUS          current
        DESCRIPTION
                "Attributes of an LLDP civiv-location."
        INDEX           { atiStkSwLldpCivicLocationIdentifier }
        ::= { atiStkSwLldpCivicLocationTable 1 }

AtiStkSwLldpCivicLocationEntry ::=
        SEQUENCE {
                atiStkSwLldpCivicLocationIdentifier     Integer32,
                atiStkSwLldpCivicLocationValid          INTEGER
        }

atiStkSwLldpCivicLocationIdentifier  OBJECT-TYPE
        SYNTAX          Integer32 (0..255)
        MAX-ACCESS      read-only
        STATUS          current
        DESCRIPTION
                "Index into atiStkSwLldpCivicLocationTable."
        ::= { atiStkSwLldpCivicLocationEntry 1 }

atiStkSwLldpCivicLocationValid  OBJECT-TYPE
        SYNTAX          INTEGER {
                                disabled (1),
                                enabled (2)
                                }
        MAX-ACCESS      read-write
        STATUS          current
        DESCRIPTION
                "The civiv-location status."
        DEFVAL          { 1 }
        ::= { atiStkSwLldpCivicLocationEntry 2 }

--
-- atiStkSwLldpCoordLocationTable
--

atiStkSwLldpCoordLocationTable  OBJECT-TYPE
        SYNTAX          SEQUENCE OF AtiStkSwLldpCoordLocationEntry
        MAX-ACCESS      not-accessible
        STATUS          current
        DESCRIPTION
                "A table of the LLDP coord-location."
        ::= { atiStkSwLldpGroup 6 }

atiStkSwLldpCoordLocationEntry  OBJECT-TYPE
        SYNTAX          AtiStkSwLldpCoordLocationEntry
        MAX-ACCESS      not-accessible
        STATUS          current
        DESCRIPTION
                "Attributes of an LLDP coord-location."
        INDEX           { atiStkSwLldpCoordLocationIdentifier }
        ::= { atiStkSwLldpCoordLocationTable 1 }

AtiStkSwLldpCoordLocationEntry ::=
        SEQUENCE {
                atiStkSwLldpCoordLocationIdentifier     Integer32,
                atiStkSwLldpCoordLocationValid          INTEGER
        }

atiStkSwLldpCoordLocationIdentifier  OBJECT-TYPE
        SYNTAX          Integer32 (0..255)
        MAX-ACCESS      read-only
        STATUS          current
        DESCRIPTION
                "Index into atiStkSwLldpCoordLocationTable."
        ::= { atiStkSwLldpCoordLocationEntry 1 }

atiStkSwLldpCoordLocationValid  OBJECT-TYPE
        SYNTAX          INTEGER {
                                disabled (1),
                                enabled (2)
                                }
        MAX-ACCESS      read-write
        STATUS          current
        DESCRIPTION
                "The coord-location status."
        DEFVAL          { 1 }
        ::= { atiStkSwLldpCoordLocationEntry 2 }

--
-- atiStkSwLldpElinLocationTable
--

atiStkSwLldpElinLocationTable  OBJECT-TYPE
        SYNTAX          SEQUENCE OF AtiStkSwLldpElinLocationEntry
        MAX-ACCESS      not-accessible
        STATUS          current
        DESCRIPTION
                "A table of the LLDP elin-location."
        ::= { atiStkSwLldpGroup 7 }

atiStkSwLldpElinLocationEntry  OBJECT-TYPE
        SYNTAX          AtiStkSwLldpElinLocationEntry
        MAX-ACCESS      not-accessible
        STATUS          current
        DESCRIPTION
                "Attributes of an LLDP elin-location."
        INDEX           { atiStkSwLldpElinLocationIdentifier }
        ::= { atiStkSwLldpElinLocationTable 1 }

AtiStkSwLldpElinLocationEntry ::=
        SEQUENCE {
                atiStkSwLldpElinLocationIdentifier      Integer32,
                atiStkSwLldpElinLocationElinId          DisplayString
        }

atiStkSwLldpElinLocationIdentifier  OBJECT-TYPE
        SYNTAX          Integer32 (0..255)
        MAX-ACCESS      read-only
        STATUS          current
        DESCRIPTION
                "Index into atiStkSwLldpElinLocationTable."
        ::= { atiStkSwLldpElinLocationEntry 1 }

atiStkSwLldpElinLocationElinId  OBJECT-TYPE
        SYNTAX          DisplayString
        MAX-ACCESS      read-write
        STATUS          current
        DESCRIPTION
                "The name of the elin-location."
        ::= { atiStkSwLldpElinLocationEntry 2 }

--
-- atiStkSwLldpSetCivicLocationTable
--

atiStkSwLldpSetCivicLocationTable  OBJECT-TYPE
        SYNTAX          SEQUENCE OF AtiStkSwLldpSetCivicLocationEntry
        MAX-ACCESS      not-accessible
        STATUS          current
        DESCRIPTION
                "A table of the LLDP set civic-location."
        ::= { atiStkSwLldpGroup 8 }

atiStkSwLldpSetCivicLocationEntry  OBJECT-TYPE
        SYNTAX          AtiStkSwLldpSetCivicLocationEntry
        MAX-ACCESS      not-accessible
        STATUS          current
        DESCRIPTION
                "Attributes of an LLDP set civic-location."
        INDEX           { atiStkSwLldpSetCivicLocationIdentifier }
        ::= { atiStkSwLldpSetCivicLocationTable 1 }

AtiStkSwLldpSetCivicLocationEntry ::=
        SEQUENCE {
                atiStkSwLldpSetCivicLocationIdentifier                  Integer32,
                atiStkSwLldpSetCivicLocationCountry                     DisplayString,
                atiStkSwLldpSetCivicLocationState                       DisplayString,
                atiStkSwLldpSetCivicLocationCounty                      DisplayString,
                atiStkSwLldpSetCivicLocationCity                        DisplayString,
                atiStkSwLldpSetCivicLocationDivision                    DisplayString,
                atiStkSwLldpSetCivicLocationNeighborhood                DisplayString,
                atiStkSwLldpSetCivicLocationStreetGroup                 DisplayString,
                atiStkSwLldpSetCivicLocationLeadingStreetDirection      DisplayString,
                atiStkSwLldpSetCivicLocationTrailingStreetDirection     DisplayString,
                atiStkSwLldpSetCivicLocationStreetSuffix                DisplayString,
                atiStkSwLldpSetCivicLocationHouseNumber                 DisplayString,
                atiStkSwLldpSetCivicLocationHouseNumberSuffix           DisplayString,
                atiStkSwLldpSetCivicLocationLandmark                    DisplayString,
                atiStkSwLldpSetCivicLocationAdditionalInformation       DisplayString,
                atiStkSwLldpSetCivicLocationName                        DisplayString,
                atiStkSwLldpSetCivicLocationPostalCode                  DisplayString,
                atiStkSwLldpSetCivicLocationBuilding                    DisplayString,
                atiStkSwLldpSetCivicLocationUnit                        DisplayString,
                atiStkSwLldpSetCivicLocationFloor                       DisplayString,
                atiStkSwLldpSetCivicLocationRoom                        DisplayString,
                atiStkSwLldpSetCivicLocationPlaceType                   DisplayString,
                atiStkSwLldpSetCivicLocationPostalCommunityName         DisplayString,
                atiStkSwLldpSetCivicLocationPostOfficeBox               DisplayString,
                atiStkSwLldpSetCivicLocationAdditionalCode              DisplayString,
                atiStkSwLldpSetCivicLocationSeat                        DisplayString,
                atiStkSwLldpSetCivicLocationPrimaryRoadName             DisplayString,
                atiStkSwLldpSetCivicLocationRoadSection                 DisplayString,
                atiStkSwLldpSetCivicLocationBranchRoadName              DisplayString,
                atiStkSwLldpSetCivicLocationSubBranchRoadName           DisplayString,
                atiStkSwLldpSetCivicLocationStreetNamePreModifier       DisplayString,
                atiStkSwLldpSetCivicLocationStreetNamePostModifier      DisplayString,
                atiStkSwLldpSetCivicLocationCreateDeleteIdentifier      INTEGER
        }

atiStkSwLldpSetCivicLocationIdentifier  OBJECT-TYPE
        SYNTAX          Integer32 (0..255)
        MAX-ACCESS      read-only
        STATUS          current
        DESCRIPTION
                "Index into atiStkSwLldpSetCivicLocationTable."
        ::= { atiStkSwLldpSetCivicLocationEntry 1 }

atiStkSwLldpSetCivicLocationCountry  OBJECT-TYPE
        SYNTAX          DisplayString (SIZE(0..250))
        MAX-ACCESS      read-write
        STATUS          current
        DESCRIPTION
                "The country of the civic-location."
        ::= { atiStkSwLldpSetCivicLocationEntry 2 }

atiStkSwLldpSetCivicLocationState  OBJECT-TYPE
        SYNTAX          DisplayString (SIZE(0..250))
        MAX-ACCESS      read-write
        STATUS          current
        DESCRIPTION
                "The state of the civic-location."
        ::= { atiStkSwLldpSetCivicLocationEntry 3 }

atiStkSwLldpSetCivicLocationCounty  OBJECT-TYPE
        SYNTAX          DisplayString (SIZE(0..250))
        MAX-ACCESS      read-write
        STATUS          current
        DESCRIPTION
                "The county of the civic-location."
        ::= { atiStkSwLldpSetCivicLocationEntry 4 }

atiStkSwLldpSetCivicLocationCity  OBJECT-TYPE
        SYNTAX          DisplayString (SIZE(0..250))
        MAX-ACCESS      read-write
        STATUS          current
        DESCRIPTION
                "The city of the civic-location."
        ::= { atiStkSwLldpSetCivicLocationEntry 5 }

atiStkSwLldpSetCivicLocationDivision  OBJECT-TYPE
        SYNTAX          DisplayString (SIZE(0..250))
        MAX-ACCESS      read-write
        STATUS          current
        DESCRIPTION
                "The division of the civic-location."
        ::= { atiStkSwLldpSetCivicLocationEntry 6 }

atiStkSwLldpSetCivicLocationNeighborhood  OBJECT-TYPE
        SYNTAX          DisplayString (SIZE(0..250))
        MAX-ACCESS      read-write
        STATUS          current
        DESCRIPTION
                "The neighborhood of the civic-location."
        ::= { atiStkSwLldpSetCivicLocationEntry 7 }

atiStkSwLldpSetCivicLocationStreetGroup  OBJECT-TYPE
        SYNTAX          DisplayString (SIZE(0..250))
        MAX-ACCESS      read-write
        STATUS          current
        DESCRIPTION
                "The street group of the civic-location."
        ::= { atiStkSwLldpSetCivicLocationEntry 8 }

atiStkSwLldpSetCivicLocationLeadingStreetDirection  OBJECT-TYPE
        SYNTAX          DisplayString (SIZE(0..250))
        MAX-ACCESS      read-write
        STATUS          current
        DESCRIPTION
                "The leading street direction of the civic-location."
        ::= { atiStkSwLldpSetCivicLocationEntry 9 }

atiStkSwLldpSetCivicLocationTrailingStreetDirection  OBJECT-TYPE
        SYNTAX          DisplayString (SIZE(0..250))
        MAX-ACCESS      read-write
        STATUS          current
        DESCRIPTION
                "The trailing street direction of the civic-location."
        ::= { atiStkSwLldpSetCivicLocationEntry 10 }

atiStkSwLldpSetCivicLocationStreetSuffix  OBJECT-TYPE
        SYNTAX          DisplayString (SIZE(0..250))
        MAX-ACCESS      read-write
        STATUS          current
        DESCRIPTION
                "The street suffix of the civic-location."
        ::= { atiStkSwLldpSetCivicLocationEntry 11 }

atiStkSwLldpSetCivicLocationHouseNumber  OBJECT-TYPE
        SYNTAX          DisplayString (SIZE(0..250))
        MAX-ACCESS      read-write
        STATUS          current
        DESCRIPTION
                "The house number of the civic-location."
        ::= { atiStkSwLldpSetCivicLocationEntry 12 }

atiStkSwLldpSetCivicLocationHouseNumberSuffix  OBJECT-TYPE
        SYNTAX          DisplayString (SIZE(0..250))
        MAX-ACCESS      read-write
        STATUS          current
        DESCRIPTION
                "The house number suffix of the civic-location."
        ::= { atiStkSwLldpSetCivicLocationEntry 13 }

atiStkSwLldpSetCivicLocationLandmark  OBJECT-TYPE
        SYNTAX          DisplayString (SIZE(0..250))
        MAX-ACCESS      read-write
        STATUS          current
        DESCRIPTION
                "The landmark of the civic-location."
        ::= { atiStkSwLldpSetCivicLocationEntry 14 }

atiStkSwLldpSetCivicLocationAdditionalInformation  OBJECT-TYPE
        SYNTAX          DisplayString (SIZE(0..250))
        MAX-ACCESS      read-write
        STATUS          current
        DESCRIPTION
                "The additional information of the civic-location."
        ::= { atiStkSwLldpSetCivicLocationEntry 15 }

atiStkSwLldpSetCivicLocationName  OBJECT-TYPE
        SYNTAX          DisplayString (SIZE(0..250))
        MAX-ACCESS      read-write
        STATUS          current
        DESCRIPTION
                "The name of the civic-location."
        ::= { atiStkSwLldpSetCivicLocationEntry 16 }

atiStkSwLldpSetCivicLocationPostalCode  OBJECT-TYPE
        SYNTAX          DisplayString (SIZE(0..250))
        MAX-ACCESS      read-write
        STATUS          current
        DESCRIPTION
                "The postal code of the civic-location."
        ::= { atiStkSwLldpSetCivicLocationEntry 17 }

atiStkSwLldpSetCivicLocationBuilding  OBJECT-TYPE
        SYNTAX          DisplayString (SIZE(0..250))
        MAX-ACCESS      read-write
        STATUS          current
        DESCRIPTION
                "The building of the civic-location."
        ::= { atiStkSwLldpSetCivicLocationEntry 18 }

atiStkSwLldpSetCivicLocationUnit  OBJECT-TYPE
        SYNTAX          DisplayString (SIZE(0..250))
        MAX-ACCESS      read-write
        STATUS          current
        DESCRIPTION
                "The unit of the civic-location."
        ::= { atiStkSwLldpSetCivicLocationEntry 19 }

atiStkSwLldpSetCivicLocationFloor  OBJECT-TYPE
        SYNTAX          DisplayString (SIZE(0..250))
        MAX-ACCESS      read-write
        STATUS          current
        DESCRIPTION
                "The floor of the civic-location."
        ::= { atiStkSwLldpSetCivicLocationEntry 20 }

atiStkSwLldpSetCivicLocationRoom  OBJECT-TYPE
        SYNTAX          DisplayString (SIZE(0..250))
        MAX-ACCESS      read-write
        STATUS          current
        DESCRIPTION
                "The room of the civic-location."
        ::= { atiStkSwLldpSetCivicLocationEntry 21 }

atiStkSwLldpSetCivicLocationPlaceType  OBJECT-TYPE
        SYNTAX          DisplayString (SIZE(0..250))
        MAX-ACCESS      read-write
        STATUS          current
        DESCRIPTION
                "The place type of the civic-location."
        ::= { atiStkSwLldpSetCivicLocationEntry 22 }

atiStkSwLldpSetCivicLocationPostalCommunityName  OBJECT-TYPE
        SYNTAX          DisplayString (SIZE(0..250))
        MAX-ACCESS      read-write
        STATUS          current
        DESCRIPTION
                "The postal community name of the civic-location."
        ::= { atiStkSwLldpSetCivicLocationEntry 23 }

atiStkSwLldpSetCivicLocationPostOfficeBox  OBJECT-TYPE
        SYNTAX          DisplayString (SIZE(0..250))
        MAX-ACCESS      read-write
        STATUS          current
        DESCRIPTION
                "The post office box of the civic-location."
        ::= { atiStkSwLldpSetCivicLocationEntry 24 }

atiStkSwLldpSetCivicLocationAdditionalCode  OBJECT-TYPE
        SYNTAX          DisplayString (SIZE(0..250))
        MAX-ACCESS      read-write
        STATUS          current
        DESCRIPTION
                "The additional code of the civic-location."
        ::= { atiStkSwLldpSetCivicLocationEntry 25 }

atiStkSwLldpSetCivicLocationSeat  OBJECT-TYPE
        SYNTAX          DisplayString (SIZE(0..250))
        MAX-ACCESS      read-write
        STATUS          current
        DESCRIPTION
                "The seat of the civic-location."
        ::= { atiStkSwLldpSetCivicLocationEntry 26 }

atiStkSwLldpSetCivicLocationPrimaryRoadName  OBJECT-TYPE
        SYNTAX          DisplayString (SIZE(0..250))
        MAX-ACCESS      read-write
        STATUS          current
        DESCRIPTION
                "The primary road name of the civic-location."
        ::= { atiStkSwLldpSetCivicLocationEntry 27 }

atiStkSwLldpSetCivicLocationRoadSection  OBJECT-TYPE
        SYNTAX          DisplayString (SIZE(0..250))
        MAX-ACCESS      read-write
        STATUS          current
        DESCRIPTION
                "The road section of the civic-location."
        ::= { atiStkSwLldpSetCivicLocationEntry 28 }

atiStkSwLldpSetCivicLocationBranchRoadName  OBJECT-TYPE
        SYNTAX          DisplayString (SIZE(0..250))
        MAX-ACCESS      read-write
        STATUS          current
        DESCRIPTION
                "The branch road name of the civic-location."
        ::= { atiStkSwLldpSetCivicLocationEntry 29 }

atiStkSwLldpSetCivicLocationSubBranchRoadName  OBJECT-TYPE
        SYNTAX          DisplayString (SIZE(0..250))
        MAX-ACCESS      read-write
        STATUS          current
        DESCRIPTION
                "The sub branch road name of the civic-location."
        ::= { atiStkSwLldpSetCivicLocationEntry 30 }

atiStkSwLldpSetCivicLocationStreetNamePreModifier  OBJECT-TYPE
        SYNTAX          DisplayString (SIZE(0..250))
        MAX-ACCESS      read-write
        STATUS          current
        DESCRIPTION
                "The street name pre modifier of the civic-location."
        ::= { atiStkSwLldpSetCivicLocationEntry 31 }

atiStkSwLldpSetCivicLocationStreetNamePostModifier  OBJECT-TYPE
        SYNTAX          DisplayString (SIZE(0..250))
        MAX-ACCESS      read-write
        STATUS          current
        DESCRIPTION
                "The street name post modifier of the civic-location."
        ::= { atiStkSwLldpSetCivicLocationEntry 32 }

atiStkSwLldpSetCivicLocationCreateDeleteIdentifier  OBJECT-TYPE
        SYNTAX          INTEGER {
                                create (1),
                                delete (2)
                                }
        MAX-ACCESS      read-write
        STATUS          current
        DESCRIPTION
                "Create and delete an identifier"
        ::= { atiStkSwLldpSetCivicLocationEntry 33 }

--
-- atiStkSwLldpSetCoordLocationTable
--

atiStkSwLldpSetCoordLocationTable  OBJECT-TYPE
        SYNTAX          SEQUENCE OF AtiStkSwLldpSetCoordLocationEntry
        MAX-ACCESS      not-accessible
        STATUS          current
        DESCRIPTION
                "A table of the LLDP set Coord-location."
        ::= { atiStkSwLldpGroup 9 }

atiStkSwLldpSetCoordLocationEntry  OBJECT-TYPE
        SYNTAX          AtiStkSwLldpSetCoordLocationEntry
        MAX-ACCESS      not-accessible
        STATUS          current
        DESCRIPTION
                "Attributes of an LLDP set Coord-location."
        INDEX           { atiStkSwLldpSetCoordLocationIdentifier }
        ::= { atiStkSwLldpSetCoordLocationTable 1 }

AtiStkSwLldpSetCoordLocationEntry ::=
        SEQUENCE {
                atiStkSwLldpSetCoordLocationIdentifier          Integer32,
                atiStkSwLldpSetCoordLocationLatitude            DisplayString,
                atiStkSwLldpSetCoordLocationLatResolution       Integer32,
                atiStkSwLldpSetCoordLocationLongitude           DisplayString,
                atiStkSwLldpSetCoordLocationLongiResolution     Integer32,
                atiStkSwLldpSetCoordLocationAltitude            DisplayString,
                atiStkSwLldpSetCoordLocationAltType             INTEGER,
                atiStkSwLldpSetCoordLocationAltResolution       Integer32,
                atiStkSwLldpSetCoordLocationDatum               INTEGER
        }

atiStkSwLldpSetCoordLocationIdentifier  OBJECT-TYPE
        SYNTAX          Integer32 (0..255)
        MAX-ACCESS      read-only
        STATUS          current
        DESCRIPTION
                "Index into atiStkSwLldpSetCoordLocationTable."
        ::= { atiStkSwLldpSetCoordLocationEntry 1 }

atiStkSwLldpSetCoordLocationLatitude  OBJECT-TYPE
        SYNTAX          DisplayString
        MAX-ACCESS      read-write
        STATUS          current
        DESCRIPTION
                "Latitude for set Coord-location."
        ::= { atiStkSwLldpSetCoordLocationEntry 2 }

atiStkSwLldpSetCoordLocationLatResolution  OBJECT-TYPE
        SYNTAX          Integer32 (0..34)
        MAX-ACCESS      read-write
        STATUS          current
        DESCRIPTION
                "Latitude Resolution for set Coord-location."
        ::= { atiStkSwLldpSetCoordLocationEntry 3 }

atiStkSwLldpSetCoordLocationLongitude  OBJECT-TYPE
        SYNTAX          DisplayString
        MAX-ACCESS      read-write
        STATUS          current
        DESCRIPTION
                "Longitude for set Coord-location."
        ::= { atiStkSwLldpSetCoordLocationEntry 4 }

atiStkSwLldpSetCoordLocationLongiResolution  OBJECT-TYPE
        SYNTAX          Integer32 (0..34)
        MAX-ACCESS      read-write
        STATUS          current
        DESCRIPTION
                "Longitude Resolution for set Coord-location."
        ::= { atiStkSwLldpSetCoordLocationEntry 5 }

atiStkSwLldpSetCoordLocationAltitude  OBJECT-TYPE
        SYNTAX          DisplayString
        MAX-ACCESS      read-write
        STATUS          current
        DESCRIPTION
                "Altitude for set Coord-location."
        ::= { atiStkSwLldpSetCoordLocationEntry 6 }

atiStkSwLldpSetCoordLocationAltType  OBJECT-TYPE
        SYNTAX          INTEGER {
                                meters (1),
                                floors (2)
                                }
        MAX-ACCESS      read-write
        STATUS          current
        DESCRIPTION
                "Alt Type for set Coord-location."
        DEFVAL          { 1 }
        ::= { atiStkSwLldpSetCoordLocationEntry 7 }

atiStkSwLldpSetCoordLocationAltResolution  OBJECT-TYPE
        SYNTAX          Integer32 (0..30)
        MAX-ACCESS      read-write
        STATUS          current
        DESCRIPTION
                "Alt Resolution for set Coord-location."
        ::= { atiStkSwLldpSetCoordLocationEntry 8 }

atiStkSwLldpSetCoordLocationDatum  OBJECT-TYPE
        SYNTAX          INTEGER {
                                wgs84 (0),
                                nad83-navd (1),
                                nad83-mllw (2)
                                }
        MAX-ACCESS      read-write
        STATUS          current
        DESCRIPTION
                "Datum for set Coord-location."
        DEFVAL          { 0 }
        ::= { atiStkSwLldpSetCoordLocationEntry 9 }

--
-- sFlow Receiver Table
--

atiSflowRcvrTable       OBJECT-TYPE
        SYNTAX          SEQUENCE OF AtiSflowRcvrEntry
        MAX-ACCESS      not-accessible
        STATUS          current
        DESCRIPTION
                "A table of the receivers of sFlow information."
        ::= { atiSflowRcvrGroup 1 }

atiSflowRcvrEntry       OBJECT-TYPE
        SYNTAX          AtiSflowRcvrEntry
        MAX-ACCESS      not-accessible
        STATUS          current
        DESCRIPTION
                "Attributes of an sFlow Receiver."
        INDEX           { atiSflowRcvrIndex }
        ::= { atiSflowRcvrTable 1 }

AtiSflowRcvrEntry ::=
        SEQUENCE {
                atiSflowRcvrIndex                       Integer32,
                atiSflowRcvrAddress                     IpAddress,
                atiSflowRcvrPort                        Integer32
        }

atiSflowRcvrIndex       OBJECT-TYPE
        SYNTAX          Integer32 (0..255)
        MAX-ACCESS      read-only
        STATUS          current
        DESCRIPTION
                "Index into sFlowReceiverTable."
        ::= { atiSflowRcvrEntry 1 }

atiSflowRcvrAddress     OBJECT-TYPE
        SYNTAX          IpAddress
        MAX-ACCESS      read-write
        STATUS          current
        DESCRIPTION
                "The IP address of the sFlow collector.
                If set to 0.0.0.0 not sFlow datagrams will be sent."
        DEFVAL          { '00000000'h }  -- 0.0.0.0
        ::= { atiSflowRcvrEntry 2 }

atiSflowRcvrPort        OBJECT-TYPE
        SYNTAX          Integer32
        MAX-ACCESS      read-write
        STATUS          current
        DESCRIPTION
                "The destination port for sFlow datagrams."
        DEFVAL          { 6343 }
        ::= { atiSflowRcvrEntry 3 }

--
-- sFlow Flow Sampling Table
--

atiSflowFsTable         OBJECT-TYPE
        SYNTAX          SEQUENCE OF AtiSflowFsEntry
        MAX-ACCESS      not-accessible
        STATUS          current
        DESCRIPTION
                "A table of the flow samplers within a device."
        ::= { atiSflowFsGroup 1 }

atiSflowFsEntry         OBJECT-TYPE
        SYNTAX          AtiSflowFsEntry
        MAX-ACCESS      not-accessible
        STATUS          current
        DESCRIPTION
                "Attributes of a flow sampler."
        INDEX           { atiSflowFsPort }
        ::= { atiSflowFsTable 1 }

AtiSflowFsEntry ::=
        SEQUENCE {
                atiSflowFsPort                          Integer32,
                atiSflowFsPacketSamplingRate            Integer32
        }

atiSflowFsPort          OBJECT-TYPE
        SYNTAX          Integer32 (0..255)
        MAX-ACCESS      read-only
        STATUS          current
        DESCRIPTION
                "The sFlow instance for this flow sampler."
        ::= { atiSflowFsEntry 1 }

atiSflowFsPacketSamplingRate  OBJECT-TYPE
        SYNTAX          Integer32
        MAX-ACCESS      read-write
        STATUS          current
        DESCRIPTION
                "The statistical sampling rate for packet sampling from this
                source.
                Set to N to sample 1/Nth of the packets in the monitored flows.
                An agent should choose its own algorithm to introduce variance
                into the sampling so that exactly every Nth packet is not
                counted. A sampling rate of 1 counts all packets. A sampling
                rate of 0 disables sampling.
                The agent is permitted to have minimum and maximum allowable
                values for the sampling rate. A minimum rate lets the agent
                designer set an upper bound on the overhead associated with
                sampling, and a maximum rate may be the result of hardware
                restrictions (such as counter size). In addition not all values
                between the maximum and minimum may be realizable as the
                sampling rate (again because of implementation considerations).
                When the sampling rate is set the agent is free to adjust the
                value so that it lies between the maximum and minimum values
                and has the closest achievable value.
                When read, the agent must return the actual sampling rate it
                will be using (after the adjustments previously described). The
                sampling algorithm must converge so that over time the number
                of packets sampled approaches 1/Nth of the total number of
                packets in the monitored flows."
        DEFVAL          { 0 }
        ::= { atiSflowFsEntry 2 }

--
-- sFlow Counter Polling Table
--

atiSflowCpTable         OBJECT-TYPE
        SYNTAX          SEQUENCE OF AtiSflowCpEntry
        MAX-ACCESS      not-accessible
        STATUS          current
        DESCRIPTION
                "A table of the counter pollers within a device."
        ::= { atiSflowCpGroup 1 }

atiSflowCpEntry         OBJECT-TYPE
        SYNTAX          AtiSflowCpEntry
        MAX-ACCESS      not-accessible
        STATUS          current
        DESCRIPTION
                "Attributes of a counter poller."
        INDEX           { atiSflowCpPort }
        ::= { atiSflowCpTable 1 }

AtiSflowCpEntry ::=
        SEQUENCE {
                atiSflowCpPort                          Integer32,
                atiSflowCpInterval                      Integer32
        }

atiSflowCpPort          OBJECT-TYPE
        SYNTAX          Integer32 (0..255)
        MAX-ACCESS      read-only
        STATUS          current
        DESCRIPTION
                "The sFlowInstance for this counter poller."
        ::= { atiSflowCpEntry 1 }

atiSflowCpInterval      OBJECT-TYPE
        SYNTAX          Integer32
        MAX-ACCESS      read-write
        STATUS          current
        DESCRIPTION
                "The maximum number of seconds between successive samples of the
                counters associated with this data source. A sampling interval
                of 0 disables counter sampling.
                The agent is permitted to have minimum and maximum allowable
                values for the counter polling interval. A minimum interval
                lets the agent designer set an upper bound on the overhead
                associated with polling, and a maximum interval may be the
                result of implementation restrictions (such as counter size).
                In addition not all values between the maximum and minimum may
                be realizable as the sampling interval (again because of
                implementation considerations).
                When the sampling rate is set the agent is free to adjust the
                value so that it lies between the maximum and minimum values
                and has the closest achievable value.
                When read, the agent must return the actual sampling interval
                it will be using (after the adjustments previously described).
                The sampling algorithm must converge so that over time the
                number of packets sampled approaches 1/Nth of the total number
                of packets in the monitored flows."
        DEFVAL          { 0 }
        ::= { atiSflowCpEntry 2 }

--
-- sFlow Set Table
--

atiSflowSetTable        OBJECT-TYPE
        SYNTAX          SEQUENCE OF AtiSflowSetEntry
        MAX-ACCESS      not-accessible
        STATUS          current
        DESCRIPTION
                "A table of the sFlow set function."
        ::= { atiSflowSetGroup 1 }

atiSflowSetEntry        OBJECT-TYPE
        SYNTAX          AtiSflowSetEntry
        MAX-ACCESS      not-accessible
        STATUS          current
        DESCRIPTION
                "Attributes of an sFlow Set."
        INDEX           { atiSflowSetIndex }
        ::= { atiSflowSetTable 1 }

AtiSflowSetEntry ::=
        SEQUENCE {
                atiSflowSetIndex                        Integer32,
                atiSflowSetAddress                      IpAddress,
                atiSflowSetPort                         Integer32,
                atiSflowSetStatus                       INTEGER
        }

atiSflowSetIndex        OBJECT-TYPE
        SYNTAX          Integer32 (0..255)
        MAX-ACCESS      read-only
        STATUS          current
        DESCRIPTION
                "Index into sFlowSetTable."
        ::= { atiSflowSetEntry 1 }

atiSflowSetAddress      OBJECT-TYPE
        SYNTAX          IpAddress
        MAX-ACCESS      read-only
        STATUS          current
        DESCRIPTION
                "The IP address of the sFlow collector.
                If set to 0.0.0.0 not sFlow datagrams will be sent."
        DEFVAL          { '00000000'h }  -- 0.0.0.0
        ::= { atiSflowSetEntry 2 }

atiSflowSetPort         OBJECT-TYPE
        SYNTAX          Integer32
        MAX-ACCESS      read-only
        STATUS          current
        DESCRIPTION
                "The port for sFlow Sampler or Poller."
        DEFVAL          { 0 }
        ::= { atiSflowSetEntry 3 }

atiSflowSetStatus       OBJECT-TYPE
        SYNTAX          INTEGER {
                                disabled (1),
                                enabled (2)
                                }
        MAX-ACCESS      read-write
        STATUS          current
        DESCRIPTION
                "The set status."
        DEFVAL          { 1 }
        ::= { atiSflowSetEntry 4 }

--
-- sFlow Enable Table
--

atiSflowEnableTable     OBJECT-TYPE
        SYNTAX          SEQUENCE OF AtiSflowEnableEntry
        MAX-ACCESS      not-accessible
        STATUS          current
        DESCRIPTION
                "A table of the sFlow enable function."
        ::= { atiSflowEnableGroup 1 }

atiSflowEnableEntry     OBJECT-TYPE
        SYNTAX          AtiSflowEnableEntry
        MAX-ACCESS      not-accessible
        STATUS          current
        DESCRIPTION
                "Attributes of an sFlow Enable."
        INDEX           { atiSflowEnablePort }
        ::= { atiSflowEnableTable 1 }

AtiSflowEnableEntry ::=
        SEQUENCE {
                atiSflowEnablePort                      Integer32,
                atiSflowEnableStatus                    INTEGER
        }

atiSflowEnablePort      OBJECT-TYPE
        SYNTAX          Integer32 (0..255)
        MAX-ACCESS      read-only
        STATUS          current
        DESCRIPTION
                "Index into sFlowEnableTable."
        ::= { atiSflowEnableEntry 1 }

atiSflowEnableStatus    OBJECT-TYPE
        SYNTAX          INTEGER {
                                disabled(1),
                                enabled(2)
                                }
        MAX-ACCESS      read-write
        STATUS          current
        DESCRIPTION
                "The enable status."
        DEFVAL          { 1 }
        ::= { atiSflowEnableEntry 2 }

--
-- atiStkSwAQoSGroup Tables
--

atiAQosPortConfigurationTable  OBJECT-TYPE
        SYNTAX          SEQUENCE OF AtiAQosPortConfigurationEntry
        MAX-ACCESS      not-accessible
        STATUS          current
        DESCRIPTION
                "atiAQosPortConfigurationTable"
        ::= { atiStkSwAQoSGroup 1 }

atiAQosPortConfigurationEntry  OBJECT-TYPE
        SYNTAX          AtiAQosPortConfigurationEntry
        MAX-ACCESS      not-accessible
        STATUS          current
        DESCRIPTION
                " "
        INDEX { atiAQosPortConfigurationPortId }
        ::= { atiAQosPortConfigurationTable 1 }

AtiAQosPortConfigurationEntry ::=
        SEQUENCE {
                atiAQosPortConfigurationPortId                          Integer32,
                atiAQosPortConfigurationStatus                          INTEGER,
                atiAQosPortConfigurationDefaultQueue                    Integer32,
                atiAQosPortConfigurationSchedularAndQueueWeightList     DisplayString,
                atiAQosPortConfigurationWRREgressRateQ0                 Integer32,
                atiAQosPortConfigurationWRREgressRateQ1                 Integer32,
                atiAQosPortConfigurationWRREgressRateQ2                 Integer32,
                atiAQosPortConfigurationWRREgressRateQ3                 Integer32,
                atiAQosPortConfigurationWRREgressRateQ4                 Integer32,
                atiAQosPortConfigurationWRREgressRateQ5                 Integer32,
                atiAQosPortConfigurationWRREgressRateQ6                 Integer32,
                atiAQosPortConfigurationWRREgressRateQ7                 Integer32
                }

atiAQosPortConfigurationPortId  OBJECT-TYPE
        SYNTAX          Integer32 (0..255)
        MAX-ACCESS      read-only
        STATUS          current
        DESCRIPTION
                "Index into atiAQosPortConfigurationTable"
        ::= { atiAQosPortConfigurationEntry 1 }

atiAQosPortConfigurationStatus  OBJECT-TYPE
        SYNTAX          INTEGER {
                                disable (0),
                                enable (1)
                                }
        MAX-ACCESS      read-write
        STATUS          current
        DESCRIPTION
                "Status"
        ::= { atiAQosPortConfigurationEntry 2 }

atiAQosPortConfigurationDefaultQueue  OBJECT-TYPE
        SYNTAX          Integer32 (0..7)
        MAX-ACCESS      read-write
        STATUS          current
        DESCRIPTION
                "Default queue"
        ::= { atiAQosPortConfigurationEntry 3 }

atiAQosPortConfigurationSchedularAndQueueWeightList  OBJECT-TYPE
        SYNTAX          DisplayString (SIZE(0..255))
        MAX-ACCESS      read-write
        STATUS          current
        DESCRIPTION
                "Schedular and queue weight list"
        ::= { atiAQosPortConfigurationEntry 4 }

atiAQosPortConfigurationWRREgressRateQ0  OBJECT-TYPE
        SYNTAX          Integer32
        MAX-ACCESS      read-write
        STATUS          current
        DESCRIPTION
                "WRR egress rate Queue 0"
        ::= { atiAQosPortConfigurationEntry 5 }

atiAQosPortConfigurationWRREgressRateQ1  OBJECT-TYPE
        SYNTAX          Integer32
        MAX-ACCESS      read-write
        STATUS          current
        DESCRIPTION
                "WRR egress rate Queue 1"
        ::= { atiAQosPortConfigurationEntry 6 }

atiAQosPortConfigurationWRREgressRateQ2  OBJECT-TYPE
        SYNTAX          Integer32
        MAX-ACCESS      read-write
        STATUS          current
        DESCRIPTION
                "WRR egress rate Queue 2"
        ::= { atiAQosPortConfigurationEntry 7 }

atiAQosPortConfigurationWRREgressRateQ3  OBJECT-TYPE
        SYNTAX          Integer32
        MAX-ACCESS      read-write
        STATUS          current
        DESCRIPTION
                "WRR egress rate Queue 3"
        ::= { atiAQosPortConfigurationEntry 8 }

atiAQosPortConfigurationWRREgressRateQ4  OBJECT-TYPE
        SYNTAX          Integer32
        MAX-ACCESS      read-write
        STATUS          current
        DESCRIPTION
                "WRR egress rate Queue 4"
        ::= { atiAQosPortConfigurationEntry 9 }

atiAQosPortConfigurationWRREgressRateQ5  OBJECT-TYPE
        SYNTAX          Integer32
        MAX-ACCESS      read-write
        STATUS          current
        DESCRIPTION
                "WRR egress rate Queue 5"
        ::= { atiAQosPortConfigurationEntry 10 }

atiAQosPortConfigurationWRREgressRateQ6  OBJECT-TYPE
        SYNTAX          Integer32
        MAX-ACCESS      read-write
        STATUS          current
        DESCRIPTION
                "WRR egress rate Queue 6"
        ::= { atiAQosPortConfigurationEntry 11 }

atiAQosPortConfigurationWRREgressRateQ7  OBJECT-TYPE
        SYNTAX          Integer32
        MAX-ACCESS      read-write
        STATUS          current
        DESCRIPTION
                "WRR egress rate Queue 7"
        ::= { atiAQosPortConfigurationEntry 12 }


atiAQosCosQueueMapTable OBJECT-TYPE
        SYNTAX          SEQUENCE OF AtiAQosCosQueueMapEntry
        MAX-ACCESS      not-accessible
        STATUS          current
        DESCRIPTION
                "atiAQosCosQueueMapTable"
        ::= { atiStkSwAQoSGroup 2 }

atiAQosCosQueueMapEntry OBJECT-TYPE
        SYNTAX          AtiAQosCosQueueMapEntry
        MAX-ACCESS      not-accessible
        STATUS          current
        DESCRIPTION
                " "
        INDEX { atiAQosCosQueueMapPortId }
        ::= { atiAQosCosQueueMapTable 1 }

AtiAQosCosQueueMapEntry ::=
        SEQUENCE {
                atiAQosCosQueueMapPortId                Integer32,
                atiAQosCosQueueMapCos0Queue             Integer32,
                atiAQosCosQueueMapCos1Queue             Integer32,
                atiAQosCosQueueMapCos2Queue             Integer32,
                atiAQosCosQueueMapCos3Queue             Integer32,
                atiAQosCosQueueMapCos4Queue             Integer32,
                atiAQosCosQueueMapCos5Queue             Integer32,
                atiAQosCosQueueMapCos6Queue             Integer32,
                atiAQosCosQueueMapCos7Queue             Integer32,
                atiAQosCosQueueMapDefaultMap            INTEGER
                }

atiAQosCosQueueMapPortId  OBJECT-TYPE
        SYNTAX          Integer32 (0..255)
        MAX-ACCESS      read-only
        STATUS          current
        DESCRIPTION
                "Index into atiAQosCosQueueMapTable"
        ::= { atiAQosCosQueueMapEntry 1 }

atiAQosCosQueueMapCos0Queue  OBJECT-TYPE
        SYNTAX          Integer32 (0..7)
        MAX-ACCESS      read-write
        STATUS          current
        DESCRIPTION
                "Cos 0 queue"
        ::= { atiAQosCosQueueMapEntry 2 }

atiAQosCosQueueMapCos1Queue  OBJECT-TYPE
        SYNTAX          Integer32 (0..7)
        MAX-ACCESS      read-write
        STATUS          current
        DESCRIPTION
                "Cos 1 queue"
        ::= { atiAQosCosQueueMapEntry 3 }

atiAQosCosQueueMapCos2Queue  OBJECT-TYPE
        SYNTAX          Integer32 (0..7)
        MAX-ACCESS      read-write
        STATUS          current
        DESCRIPTION
                "Cos 2 queue"
        ::= { atiAQosCosQueueMapEntry 4 }

atiAQosCosQueueMapCos3Queue  OBJECT-TYPE
        SYNTAX          Integer32 (0..7)
        MAX-ACCESS      read-write
        STATUS          current
        DESCRIPTION
                "Cos 3 queue"
        ::= { atiAQosCosQueueMapEntry 5 }

atiAQosCosQueueMapCos4Queue  OBJECT-TYPE
        SYNTAX          Integer32 (0..7)
        MAX-ACCESS      read-write
        STATUS          current
        DESCRIPTION
                "Cos 4 queue"
        ::= { atiAQosCosQueueMapEntry 6 }

atiAQosCosQueueMapCos5Queue  OBJECT-TYPE
        SYNTAX          Integer32 (0..7)
        MAX-ACCESS      read-write
        STATUS          current
        DESCRIPTION
                "Cos 5 queue"
        ::= { atiAQosCosQueueMapEntry 7 }

atiAQosCosQueueMapCos6Queue  OBJECT-TYPE
        SYNTAX          Integer32 (0..7)
        MAX-ACCESS      read-write
        STATUS          current
        DESCRIPTION
                "Cos 6 queue"
        ::= { atiAQosCosQueueMapEntry 8 }

atiAQosCosQueueMapCos7Queue  OBJECT-TYPE
        SYNTAX          Integer32 (0..7)
        MAX-ACCESS      read-write
        STATUS          current
        DESCRIPTION
                "Cos 7 queue"
        ::= { atiAQosCosQueueMapEntry 9 }

atiAQosCosQueueMapDefaultMap  OBJECT-TYPE
        SYNTAX          INTEGER {
                                no  (0),
                                yes (1)
                                }
        MAX-ACCESS      read-write
        STATUS          current
        DESCRIPTION
                "Default map"
        ::= { atiAQosCosQueueMapEntry 10 }


atiAQosDscpQueueMapTable  OBJECT-TYPE
        SYNTAX          SEQUENCE OF AtiAQosDscpQueueMapEntry
        MAX-ACCESS      not-accessible
        STATUS          current
        DESCRIPTION
                "atiAQosDscpQueueMapTable"
        ::= { atiStkSwAQoSGroup 3 }

atiAQosDscpQueueMapEntry  OBJECT-TYPE
        SYNTAX          AtiAQosDscpQueueMapEntry
        MAX-ACCESS      not-accessible
        STATUS          current
        DESCRIPTION
                " "
        INDEX { atiAQosDscpQueueMapPortId }
        ::= { atiAQosDscpQueueMapTable 1 }

AtiAQosDscpQueueMapEntry ::=
        SEQUENCE {
                atiAQosDscpQueueMapPortId               Integer32,
                atiAQosDscpQueueMapQueue0               DisplayString,
                atiAQosDscpQueueMapQueue1               DisplayString,
                atiAQosDscpQueueMapQueue2               DisplayString,
                atiAQosDscpQueueMapQueue3               DisplayString,
                atiAQosDscpQueueMapQueue4               DisplayString,
                atiAQosDscpQueueMapQueue5               DisplayString,
                atiAQosDscpQueueMapQueue6               DisplayString,
                atiAQosDscpQueueMapQueue7               DisplayString,
                atiAQosDscpQueueMapDefaultMap           INTEGER
                }

atiAQosDscpQueueMapPortId  OBJECT-TYPE
        SYNTAX          Integer32 (0..255)
        MAX-ACCESS      read-only
        STATUS          current
        DESCRIPTION
                "Index into atiAQosDscpQueueMapTable"
        ::= { atiAQosDscpQueueMapEntry 1 }

atiAQosDscpQueueMapQueue0  OBJECT-TYPE
        SYNTAX          DisplayString (SIZE(0..150))
        MAX-ACCESS      read-write
        STATUS          current
        DESCRIPTION
                "Queue 0"
        ::= { atiAQosDscpQueueMapEntry 2 }

atiAQosDscpQueueMapQueue1  OBJECT-TYPE
        SYNTAX          DisplayString (SIZE(0..150))
        MAX-ACCESS      read-write
        STATUS          current
        DESCRIPTION
                "Queue 1"
        ::= { atiAQosDscpQueueMapEntry 3 }

atiAQosDscpQueueMapQueue2  OBJECT-TYPE
        SYNTAX          DisplayString (SIZE(0..150))
        MAX-ACCESS      read-write
        STATUS          current
        DESCRIPTION
                "Queue 2"
        ::= { atiAQosDscpQueueMapEntry 4 }

atiAQosDscpQueueMapQueue3  OBJECT-TYPE
        SYNTAX          DisplayString (SIZE(0..150))
        MAX-ACCESS      read-write
        STATUS          current
        DESCRIPTION
                "Queue 3"
        ::= { atiAQosDscpQueueMapEntry 5 }

atiAQosDscpQueueMapQueue4  OBJECT-TYPE
        SYNTAX          DisplayString (SIZE(0..150))
        MAX-ACCESS      read-write
        STATUS          current
        DESCRIPTION
                "Queue 4"
        ::= { atiAQosDscpQueueMapEntry 6 }

atiAQosDscpQueueMapQueue5  OBJECT-TYPE
        SYNTAX          DisplayString (SIZE(0..150))
        MAX-ACCESS      read-write
        STATUS          current
        DESCRIPTION
                "Queue 5"
        ::= { atiAQosDscpQueueMapEntry 7 }

atiAQosDscpQueueMapQueue6  OBJECT-TYPE
        SYNTAX          DisplayString (SIZE(0..150))
        MAX-ACCESS      read-write
        STATUS          current
        DESCRIPTION
                "Queue 6"
        ::= { atiAQosDscpQueueMapEntry 8 }

atiAQosDscpQueueMapQueue7  OBJECT-TYPE
        SYNTAX          DisplayString (SIZE(0..150))
        MAX-ACCESS      read-write
        STATUS          current
        DESCRIPTION
                "Queue 7"
        ::= { atiAQosDscpQueueMapEntry 9 }

atiAQosDscpQueueMapDefaultMap  OBJECT-TYPE
        SYNTAX          INTEGER {
                                no (0),
                                yes (1)
                                }
        MAX-ACCESS      read-write
        STATUS          current
        DESCRIPTION
                "Default map"
        ::= { atiAQosDscpQueueMapEntry 10 }


atiAQosAggregatePolicerTable  OBJECT-TYPE
        SYNTAX          SEQUENCE OF AtiAQosAggregatePolicerEntry
        MAX-ACCESS      not-accessible
        STATUS          current
        DESCRIPTION
                "atiAQosAggregatePolicerTable"
        ::= { atiStkSwAQoSGroup 4 }

atiAQosAggregatePolicerEntry  OBJECT-TYPE
        SYNTAX          AtiAQosAggregatePolicerEntry
        MAX-ACCESS      not-accessible
        STATUS          current
        DESCRIPTION
                " "
        INDEX { atiAQosAggregatePolicerIndex }
        ::= { atiAQosAggregatePolicerTable 1 }

AtiAQosAggregatePolicerEntry ::=
        SEQUENCE {
                atiAQosAggregatePolicerIndex            Integer32,
                atiAQosAggregatePolicerName             DisplayString,
                atiAQosAggregatePolicerRate             INTEGER,
                atiAQosAggregatePolicerCIRkbps          Integer32,
                atiAQosAggregatePolicerCBSb             Integer32,
                atiAQosAggregatePolicerPIRkbps          Integer32,
                atiAQosAggregatePolicerPBSb             Integer32,
                atiAQosAggregatePolicerAction           INTEGER
                }

atiAQosAggregatePolicerIndex  OBJECT-TYPE
        SYNTAX          Integer32 (0..255)
        MAX-ACCESS      read-only
        STATUS          current
        DESCRIPTION
                "Index into atiAQosAggregatePolicerTable"
        ::= { atiAQosAggregatePolicerEntry 1 }

atiAQosAggregatePolicerName  OBJECT-TYPE
        SYNTAX          DisplayString (SIZE(0..255))
        MAX-ACCESS      read-write
        STATUS          current
        DESCRIPTION
                "Aggregate police name"
        ::= { atiAQosAggregatePolicerEntry 2 }

atiAQosAggregatePolicerRate  OBJECT-TYPE
        SYNTAX          INTEGER {
                                single-rate (0),
                                twin-rate (1)
                                }
        MAX-ACCESS      read-write
        STATUS          current
        DESCRIPTION
                "Rate"
        ::= { atiAQosAggregatePolicerEntry 3 }

atiAQosAggregatePolicerCIRkbps  OBJECT-TYPE
        SYNTAX          Integer32 (1..16000000)
        MAX-ACCESS      read-write
        STATUS          current
        DESCRIPTION
                "CIR kbps"
        ::= { atiAQosAggregatePolicerEntry 4 }

atiAQosAggregatePolicerCBSb  OBJECT-TYPE
        SYNTAX          Integer32 (1..1677216)
        MAX-ACCESS      read-write
        STATUS          current
        DESCRIPTION
                "CBS b"
        ::= { atiAQosAggregatePolicerEntry 5 }

atiAQosAggregatePolicerPIRkbps  OBJECT-TYPE
        SYNTAX          Integer32 (1..16000000)
        MAX-ACCESS      read-write
        STATUS          current
        DESCRIPTION
                "PIR kbps"
        ::= { atiAQosAggregatePolicerEntry 6 }

atiAQosAggregatePolicerPBSb  OBJECT-TYPE
        SYNTAX          Integer32 (1..1677216)
        MAX-ACCESS      read-write
        STATUS          current
        DESCRIPTION
                "PBS b"
        ::= { atiAQosAggregatePolicerEntry 7 }

atiAQosAggregatePolicerAction  OBJECT-TYPE
        SYNTAX          INTEGER {
                                drop-red  (14),
                                policed-dscp (1)
                                }
        MAX-ACCESS      read-write
        STATUS          current
        DESCRIPTION
                "Action"
        ::= { atiAQosAggregatePolicerEntry 8 }


atiAQosInterfacePolicyTable  OBJECT-TYPE
        SYNTAX          SEQUENCE OF AtiAQosInterfacePolicyEntry
        MAX-ACCESS      not-accessible
        STATUS          current
        DESCRIPTION
                "atiAQosInterfacePolicyTable"
        ::= { atiStkSwAQoSGroup 5 }

atiAQosInterfacePolicyEntry  OBJECT-TYPE
        SYNTAX          AtiAQosInterfacePolicyEntry
        MAX-ACCESS      not-accessible
        STATUS          current
        DESCRIPTION
                " "
        INDEX { atiAQosInterfacePolicyPortId }
        ::= { atiAQosInterfacePolicyTable 1 }

AtiAQosInterfacePolicyEntry ::=
        SEQUENCE {
                atiAQosInterfacePolicyPortId            Integer32,
                atiAQosInterfacePolicyMapName           DisplayString
                }

atiAQosInterfacePolicyPortId  OBJECT-TYPE
        SYNTAX          Integer32 (0..255)
        MAX-ACCESS      read-only
        STATUS          current
        DESCRIPTION
                "Index into atiAQosInterfacePolicyTable"
        ::= { atiAQosInterfacePolicyEntry 1 }

atiAQosInterfacePolicyMapName  OBJECT-TYPE
        SYNTAX          DisplayString (SIZE(0..255))
        MAX-ACCESS      read-write
        STATUS          current
        DESCRIPTION
                "Policy map name"
        ::= { atiAQosInterfacePolicyEntry 2 }


atiAQosPolicyMapTable   OBJECT-TYPE
        SYNTAX          SEQUENCE OF AtiAQosPolicyMapEntry
        MAX-ACCESS      not-accessible
        STATUS          current
        DESCRIPTION
                "atiAQosPolicyMapTable"
        ::= { atiStkSwAQoSGroup 6 }

atiAQosPolicyMapEntry   OBJECT-TYPE
        SYNTAX          AtiAQosPolicyMapEntry
        MAX-ACCESS      not-accessible
        STATUS          current
        DESCRIPTION
                " "
        INDEX { atiAQosPolicyMapIndex }
        ::= { atiAQosPolicyMapTable  1 }

AtiAQosPolicyMapEntry ::=
        SEQUENCE {
                atiAQosPolicyMapIndex                   Integer32,
                atiAQosPolicyMapPolicyName              DisplayString,
                atiAQosPolicyMapClassName               DisplayString,
                atiAQosPolicyMapDefaultAction           INTEGER,
                atiAQosPolicyMapCosAction               INTEGER,
                atiAQosPolicyMapDscpAction              DisplayString,
                atiAQosPolicyMapIpNextHopAction         IpAddress,
                atiAQosPolicyMapQueueAction             Integer32,
                atiAQosPolicyMapTrustAction             INTEGER,
                atiAQosPolicyMapPoliceAggregateAction   DisplayString,
                atiAQosPolicyMapStormAction             INTEGER,
                atiAQosPolicyMapStormDowntimeAction     Integer32,
                atiAQosPolicyMapStormRateAction         Integer32,
                atiAQosPolicyMapStormWindowAction       Integer32
                }

atiAQosPolicyMapIndex   OBJECT-TYPE
        SYNTAX          Integer32 (0..255)
        MAX-ACCESS      read-only
        STATUS          current
        DESCRIPTION
                "Index into atiAQosPolicyMapTable"
        ::= { atiAQosPolicyMapEntry 1 }

atiAQosPolicyMapPolicyName  OBJECT-TYPE
        SYNTAX          DisplayString (SIZE(0..255))
        MAX-ACCESS      read-write
        STATUS          current
        DESCRIPTION
                "Policy name"
        ::= { atiAQosPolicyMapEntry 2 }

atiAQosPolicyMapClassName  OBJECT-TYPE
        SYNTAX          DisplayString (SIZE(0..255))
        MAX-ACCESS      read-write
        STATUS          current
        DESCRIPTION
                "Class name"
        ::= { atiAQosPolicyMapEntry 3 }

atiAQosPolicyMapDefaultAction  OBJECT-TYPE
        SYNTAX          INTEGER {
                                none (0),
                                permit (1),
                                deny (2)
                                }
        MAX-ACCESS      read-write
        STATUS          current
        DESCRIPTION
                "Action of default class-map "
        ::= { atiAQosPolicyMapEntry 4 }

atiAQosPolicyMapCosAction  OBJECT-TYPE
        SYNTAX          INTEGER {
                                none (0),
                                cos0 (1),
                                cos1 (2),
                                cos2 (3),
                                cos3 (4),
                                cos4 (5),
                                cos5 (6),
                                cos6 (7),
                                cos7 (8)
                                }
        MAX-ACCESS      read-write
        STATUS          current
        DESCRIPTION
                "Cos action"
        ::= { atiAQosPolicyMapEntry 5 }

atiAQosPolicyMapDscpAction  OBJECT-TYPE
        SYNTAX          DisplayString (SIZE(0..255))
        MAX-ACCESS      read-write
        STATUS          current
        DESCRIPTION
                "Dscp action"
        ::= { atiAQosPolicyMapEntry 6 }

atiAQosPolicyMapIpNextHopAction  OBJECT-TYPE
        SYNTAX          IpAddress
        MAX-ACCESS      read-write
        STATUS          current
        DESCRIPTION
                "Ip next hop action"
        ::= { atiAQosPolicyMapEntry 7 }

atiAQosPolicyMapQueueAction  OBJECT-TYPE
        SYNTAX          Integer32
        MAX-ACCESS      read-write
        STATUS          current
        DESCRIPTION
                "Queue action"
        ::= { atiAQosPolicyMapEntry 8 }

atiAQosPolicyMapTrustAction  OBJECT-TYPE
        SYNTAX          INTEGER {
                                cos (0),
                                dscp (1)
                                }
        MAX-ACCESS      read-write
        STATUS          current
        DESCRIPTION
                "Trust action"
        ::= { atiAQosPolicyMapEntry 9 }

atiAQosPolicyMapPoliceAggregateAction  OBJECT-TYPE
        SYNTAX          DisplayString (SIZE(0..255))
        MAX-ACCESS      read-write
        STATUS          current
        DESCRIPTION
                "Police aggregate action"
        ::= { atiAQosPolicyMapEntry 10 }

atiAQosPolicyMapStormAction  OBJECT-TYPE
        SYNTAX          INTEGER {
                                enable (0),
                                disable (1)
                                }
        MAX-ACCESS      read-write
        STATUS          current
        DESCRIPTION
                "Storm action"
        ::= { atiAQosPolicyMapEntry 11 }

atiAQosPolicyMapStormDowntimeAction  OBJECT-TYPE
        SYNTAX          Integer32
        MAX-ACCESS      read-write
        STATUS          current
        DESCRIPTION
                "Storm downtime action"
        ::= { atiAQosPolicyMapEntry 12 }

atiAQosPolicyMapStormRateAction  OBJECT-TYPE
        SYNTAX          Integer32
        MAX-ACCESS      read-write
        STATUS          current
        DESCRIPTION
                "Storm rate action"
        ::= { atiAQosPolicyMapEntry 13 }

atiAQosPolicyMapStormWindowAction  OBJECT-TYPE
        SYNTAX          Integer32
        MAX-ACCESS      read-write
        STATUS          current
        DESCRIPTION
                "Storm window action"
        ::= { atiAQosPolicyMapEntry 14 }


atiAQosClassMapTable    OBJECT-TYPE
        SYNTAX          SEQUENCE OF AtiAQosClassMapEntry
        MAX-ACCESS      not-accessible
        STATUS          current
        DESCRIPTION
                "atiAQosClassMapTable"
        ::= { atiStkSwAQoSGroup 7 }

atiAQosClassMapEntry    OBJECT-TYPE
        SYNTAX          AtiAQosClassMapEntry
        MAX-ACCESS      not-accessible
        STATUS          current
        DESCRIPTION
                " "
        INDEX           { atiAQosClassMapIndex }
        ::= { atiAQosClassMapTable 1 }

AtiAQosClassMapEntry ::=
        SEQUENCE {
                atiAQosClassMapIndex                    Integer32,
                atiAQosClassMapClassName                DisplayString,
                atiAQosClassMapAccessGroupMatch         DisplayString,
                atiAQosClassMapCosMatch                 DisplayString,
                atiAQosClassMapDscpMatch                DisplayString,
                atiAQosClassMapInnerCosMatch            DisplayString,
                atiAQosClassMapInnerVlanMatch           DisplayString,
                atiAQosClassMapIpPrecedenceMatch        DisplayString,
                atiAQosClassMapMacTypeMatch             INTEGER,
                atiAQosClassVlanMatch                   DisplayString,
                atiAQosClassTcpFlagsMatch               INTEGER,
                atiAQosClassL2FormatMatch               DisplayString,
                atiAQosClassL3ProtocolMatch             DisplayString
                }

atiAQosClassMapIndex    OBJECT-TYPE
        SYNTAX          Integer32  (0..255)
        MAX-ACCESS      read-only
        STATUS          current
        DESCRIPTION
                "Index into atiAQosClassMapTable"
        ::= { atiAQosClassMapEntry 1 }

atiAQosClassMapClassName  OBJECT-TYPE
        SYNTAX          DisplayString (SIZE(0..128))
        MAX-ACCESS      read-write
        STATUS          current
        DESCRIPTION
                "Class name"
        ::= { atiAQosClassMapEntry 2 }

atiAQosClassMapAccessGroupMatch OBJECT-TYPE
        SYNTAX          DisplayString
        MAX-ACCESS      read-write
        STATUS          current
        DESCRIPTION
                "Access group match"
        ::= { atiAQosClassMapEntry 3 }

atiAQosClassMapCosMatch OBJECT-TYPE
        SYNTAX          DisplayString
        MAX-ACCESS      read-write
        STATUS          current
        DESCRIPTION
                "Cos match"
        ::= { atiAQosClassMapEntry 4 }

atiAQosClassMapDscpMatch        OBJECT-TYPE
        SYNTAX          DisplayString
        MAX-ACCESS      read-write
        STATUS          current
        DESCRIPTION
                "Dscp match"
        ::= { atiAQosClassMapEntry 5 }

atiAQosClassMapInnerCosMatch  OBJECT-TYPE
        SYNTAX          DisplayString
        MAX-ACCESS      read-write
        STATUS          current
        DESCRIPTION
                "Inner cos match"
        ::= { atiAQosClassMapEntry 6 }

atiAQosClassMapInnerVlanMatch  OBJECT-TYPE
        SYNTAX          DisplayString
        MAX-ACCESS      read-write
        STATUS          current
        DESCRIPTION
                "Inner vlan match"
        ::= { atiAQosClassMapEntry 7 }

atiAQosClassMapIpPrecedenceMatch  OBJECT-TYPE
        SYNTAX          DisplayString
        MAX-ACCESS      read-write
        STATUS          current
        DESCRIPTION
                "Ip precedence vlan match"
        ::= { atiAQosClassMapEntry 8 }

atiAQosClassMapMacTypeMatch  OBJECT-TYPE
        SYNTAX          INTEGER {
                                none (0),
                                l2bcast (1),
                                l2mcast (2),
                                l2ucast (3)
                                }
        MAX-ACCESS      read-write
        STATUS          current
        DESCRIPTION
                "Mac type match"
        ::= { atiAQosClassMapEntry 9 }

atiAQosClassVlanMatch   OBJECT-TYPE
        SYNTAX          DisplayString
        MAX-ACCESS      read-write
        STATUS          current
        DESCRIPTION
                "Vlan match"
        ::= { atiAQosClassMapEntry 10 }

atiAQosClassTcpFlagsMatch  OBJECT-TYPE
        SYNTAX          INTEGER {
                                none (0),
                                fin (1),
                                syn (2),
                                rst (3),
                                ack (4),
                                urg (5)
                                }
        MAX-ACCESS      read-write
        STATUS          current
        DESCRIPTION
                "Tcp flags match"
        ::= { atiAQosClassMapEntry 11 }

atiAQosClassL2FormatMatch  OBJECT-TYPE
        SYNTAX          DisplayString
        MAX-ACCESS      read-write
        STATUS          current
        DESCRIPTION
                "L2 format match"
        ::= { atiAQosClassMapEntry 12 }

atiAQosClassL3ProtocolMatch  OBJECT-TYPE
        SYNTAX          DisplayString
        MAX-ACCESS      read-write
        STATUS          current
        DESCRIPTION
                "L3 protocol match"
        ::= { atiAQosClassMapEntry 13 }


-- atiStkSwDhcpPoolTable

atiStkSwDhcpPoolTable   OBJECT-TYPE
        SYNTAX          SEQUENCE OF AtiStkSwDhcpPoolEntry
        MAX-ACCESS      not-accessible
        STATUS          current
        DESCRIPTION
                "This table contains a list of Dhcp Pool."
        ::= { atiStkSwDhcpSvrGroup 1 }

atiStkSwDhcpPoolEntry   OBJECT-TYPE
        SYNTAX          AtiStkSwDhcpPoolEntry
        MAX-ACCESS      not-accessible
        STATUS          current
        DESCRIPTION
                "This object specifies an entry in 'atiStkSwDhcpPoolTable'
                that describes a DHCP Pool configured on the switch."
        INDEX           { atiDhcpPoolId }
        ::= { atiStkSwDhcpPoolTable 1 }

AtiStkSwDhcpPoolEntry ::=
        SEQUENCE {
                atiDhcpPoolId                           Integer32,
                atiDhcpPoolName                         DisplayString,
                atiDhcpPoolNetwork                      IpAddress,
                atiDhcpPoolNetmask                      IpAddress,
                atiDhcpPoolSubnetmask                   IpAddress,
                atiDhcpPoolRangeList                    DisplayString,
                atiDhcpPoolExpireTime                   Integer32,
                atiDhcpPoolRouterList                   DisplayString,
                atiDhcpPoolDNSSvrList                   DisplayString,
                atiDhcpPoolDomainName                   DisplayString,
                atiDhcpPoolIpAdd                        IpAddress,
                atiDhcpPoolIpDelete                     IpAddress,
                atiDhcpPoolRouterAdd                    IpAddress,
                atiDhcpPoolRouterDelete                 IpAddress,
                atiDhcpPoolDNSAdd                       IpAddress,
                atiDhcpPoolDNSDelete                    IpAddress
                }

atiDhcpPoolId           OBJECT-TYPE
        SYNTAX          Integer32 (1..4094)
        MAX-ACCESS      read-only
        STATUS          current
        DESCRIPTION
                "The Pool ID."
        ::= { atiStkSwDhcpPoolEntry 1 }

atiDhcpPoolName         OBJECT-TYPE
        SYNTAX          DisplayString
        MAX-ACCESS      read-write
        STATUS          current
        DESCRIPTION
                "The atiDhcpPoolName indicates Pool Name."
        ::= { atiStkSwDhcpPoolEntry 2 }

atiDhcpPoolNetwork      OBJECT-TYPE
        SYNTAX          IpAddress
        MAX-ACCESS      read-write
        STATUS          current
        DESCRIPTION
                "Pool Network"
        ::= { atiStkSwDhcpPoolEntry 3 }

atiDhcpPoolNetmask      OBJECT-TYPE
        SYNTAX          IpAddress
        MAX-ACCESS      read-write
        STATUS          current
        DESCRIPTION
                "atiDhcpPoolNetmask"
        ::= { atiStkSwDhcpPoolEntry 4 }

atiDhcpPoolSubnetmask   OBJECT-TYPE
        SYNTAX          IpAddress
        MAX-ACCESS      read-write
        STATUS          current
        DESCRIPTION
                "atiDhcpPoolSubnetmask."
        ::= { atiStkSwDhcpPoolEntry 5 }

atiDhcpPoolRangeList    OBJECT-TYPE
        SYNTAX          DisplayString
        MAX-ACCESS      read-only
        STATUS          current
        DESCRIPTION
                "Range list of this pool."
        ::= { atiStkSwDhcpPoolEntry 6 }

atiDhcpPoolExpireTime   OBJECT-TYPE
        SYNTAX          Integer32 (1..4094)
        MAX-ACCESS      read-write
        STATUS          current
        DESCRIPTION
                "The total expire time"
        ::= { atiStkSwDhcpPoolEntry 7 }

atiDhcpPoolRouterList   OBJECT-TYPE
        SYNTAX          DisplayString
        MAX-ACCESS      read-only
        STATUS          current
        DESCRIPTION
                "atiDhcpPoolRouterList"
        ::= { atiStkSwDhcpPoolEntry 8 }

atiDhcpPoolDNSSvrList   OBJECT-TYPE
        SYNTAX          DisplayString
        MAX-ACCESS      read-only
        STATUS          current
        DESCRIPTION
                "atiDhcpPoolDNSSvrList"
        ::= { atiStkSwDhcpPoolEntry 9 }

atiDhcpPoolDomainName   OBJECT-TYPE
        SYNTAX          DisplayString
        MAX-ACCESS      read-write
        STATUS          current
        DESCRIPTION
                "atiDhcpPoolDomainName"
        ::= { atiStkSwDhcpPoolEntry 10 }

atiDhcpPoolIpAdd        OBJECT-TYPE
        SYNTAX          IpAddress
        MAX-ACCESS      read-write
        STATUS          current
        DESCRIPTION
                "Ip address to be added to range"
        ::= { atiStkSwDhcpPoolEntry 11 }

atiDhcpPoolIpDelete     OBJECT-TYPE
        SYNTAX          IpAddress
        MAX-ACCESS      read-write
        STATUS          current
        DESCRIPTION
                "Ip address to be deleted from range"
        ::= { atiStkSwDhcpPoolEntry 12 }

atiDhcpPoolRouterAdd    OBJECT-TYPE
        SYNTAX          IpAddress
        MAX-ACCESS      read-write
        STATUS          current
        DESCRIPTION
                "The router to be added to router list"
        ::= { atiStkSwDhcpPoolEntry 13 }

atiDhcpPoolRouterDelete OBJECT-TYPE
        SYNTAX          IpAddress
        MAX-ACCESS      read-write
        STATUS          current
        DESCRIPTION
                "The router to be deleted from router list"
        ::= { atiStkSwDhcpPoolEntry 14 }

atiDhcpPoolDNSAdd       OBJECT-TYPE
        SYNTAX          IpAddress
        MAX-ACCESS      read-write
        STATUS          current
        DESCRIPTION
                "The DNS to be added to DNS list"
        ::= { atiStkSwDhcpPoolEntry 15 }

atiDhcpPoolDNSDelete    OBJECT-TYPE
        SYNTAX          IpAddress
        MAX-ACCESS      read-write
        STATUS          current
        DESCRIPTION
                "The DNS to be deleted from DNS list"
        ::= { atiStkSwDhcpPoolEntry 16 }

-- atiStkSwDhcpBindingTable

atiStkSwDhcpBindingTable  OBJECT-TYPE
        SYNTAX          SEQUENCE OF AtiStkSwDhcpBindingEntry
        MAX-ACCESS      not-accessible
        STATUS          current
        DESCRIPTION
                "This table contains a list of Dhcp Binding configured on the switch."
        ::= { atiStkSwDhcpSvrGroup 2 }

atiStkSwDhcpBindingEntry  OBJECT-TYPE
        SYNTAX          AtiStkSwDhcpBindingEntry
        MAX-ACCESS      not-accessible
        STATUS          current
        DESCRIPTION
                "This object specifies an entry in 'atiStkSwDhcpBindingTable'
                that describes a DHCP Binding configured on the switch."
        INDEX           { atiDhcpBindId }
        ::= { atiStkSwDhcpBindingTable 1 }

AtiStkSwDhcpBindingEntry ::=
        SEQUENCE {
                atiDhcpBindingId                        Integer32,
                atiDhcpClientMacAddress                 MacAddress,
                atiDhcpPortNumber                       DisplayString,
                atiDhcpIpAddress                        IpAddress,
                atiDhcpExpireTime                       DisplayString
                }

atiDhcpBindingId OBJECT-TYPE
        SYNTAX          Integer32
        MAX-ACCESS      read-only
        STATUS          current
        DESCRIPTION
                "The atiDhcpBindingId is the Binding Id"
        ::= { atiStkSwDhcpBindingEntry 1 }

atiDhcpClientMacAddress OBJECT-TYPE
        SYNTAX          MacAddress
        MAX-ACCESS      read-only
        STATUS          current
        DESCRIPTION
                "The Client Mac Address is the Client Id"
        ::= { atiStkSwDhcpBindingEntry 2 }

atiDhcpPortNumber       OBJECT-TYPE
        SYNTAX          DisplayString
        MAX-ACCESS      read-only
        STATUS          current
        DESCRIPTION
                "The Port Number indicates which port is offering this ip address."
        ::= { atiStkSwDhcpBindingEntry 3 }

atiDhcpIpAddress        OBJECT-TYPE
        SYNTAX          IpAddress
        MAX-ACCESS      read-only
        STATUS          current
        DESCRIPTION
                "switch offers ip address to client"
        ::= { atiStkSwDhcpBindingEntry 4 }

atiDhcpExpireTime       OBJECT-TYPE
        SYNTAX          DisplayString
        MAX-ACCESS      read-only
        STATUS          current
        DESCRIPTION
                "The ip is valid within this Expire time."
        ::= { atiStkSwDhcpBindingEntry 5 }

-- atiStkSwDhcpStatisticTable

atiStkSwDhcpStatisticTable  OBJECT IDENTIFIER ::= { atiStkSwDhcpSvrGroup 3 }

atiInDiscover           OBJECT-TYPE
        SYNTAX          Integer32 (1..4094)
        MAX-ACCESS      read-only
        STATUS          current
        DESCRIPTION
                "The atiInDiscover reflects the counter of Dhcp Discover input frames."
        ::= { atiStkSwDhcpStatisticTable 1 }

atiInDhcpRequest        OBJECT-TYPE
        SYNTAX          Integer32 (1..4094)
        MAX-ACCESS      read-only
        STATUS          current
        DESCRIPTION
                "The atiInDhcpDiscover reflects the counter of Dhcp Request input frames."
        ::= { atiStkSwDhcpStatisticTable 2 }

atiInDecline            OBJECT-TYPE
        SYNTAX          Integer32 (1..4094)
        MAX-ACCESS      read-only
        STATUS          current
        DESCRIPTION
                "The atiInDecline reflects the counter of Dhcp Decline input frames."
        ::= { atiStkSwDhcpStatisticTable 3 }

atiInRelease            OBJECT-TYPE
        SYNTAX          Integer32 (1..4094)
        MAX-ACCESS      read-only
        STATUS          current
        DESCRIPTION
                "The atiInRelease reflects the counter of Dhcp Release input frames."
        ::= { atiStkSwDhcpStatisticTable 4 }

atiInInform             OBJECT-TYPE
        SYNTAX          Integer32 (1..4094)
        MAX-ACCESS      read-only
        STATUS          current
        DESCRIPTION
                "The atiInInform reflects the counter of Dhcp Inform input frames."
        ::= { atiStkSwDhcpStatisticTable 5 }

atiInBootRequest        OBJECT-TYPE
        SYNTAX          Integer32 (1..4094)
        MAX-ACCESS      read-only
        STATUS          current
        DESCRIPTION
                "The atiInBootRequest reflects the counter of Dhcp Boot Request input frames."
        ::= { atiStkSwDhcpStatisticTable 6 }

atiInLeaseQuery         OBJECT-TYPE
        SYNTAX          Integer32 (1..4094)
        MAX-ACCESS      read-only
        STATUS          current
        DESCRIPTION
                "The atiInLeaseQuery reflects the counter of Dhcp Lease Query input frames."
        ::= { atiStkSwDhcpStatisticTable 7 }

atiOutDhcpOffer         OBJECT-TYPE
        SYNTAX          Integer32 (1..4094)
        MAX-ACCESS      read-only
        STATUS          current
        DESCRIPTION
                "The atiOutDhcpOffer reflects the counter of Dhcp Offer Output frames."
        ::= { atiStkSwDhcpStatisticTable 8 }

atiOutDhcpAck           OBJECT-TYPE
        SYNTAX          Integer32 (1..4094)
        MAX-ACCESS      read-only
        STATUS          current
        DESCRIPTION
                "The atiOutDhcpAck reflects the counter of Dhcp Ack output frames."
        ::= { atiStkSwDhcpStatisticTable 9 }

atiOutDhcpNak           OBJECT-TYPE
        SYNTAX          Integer32 (1..4094)
        MAX-ACCESS      read-only
        STATUS          current
        DESCRIPTION
                "The atiOutDhcpNak reflects the counter of Dhcp Nak output frames."
        ::= { atiStkSwDhcpStatisticTable 10 }

atiOutLeaseUnknown      OBJECT-TYPE
        SYNTAX          Integer32 (1..4094)
        MAX-ACCESS      read-only
        STATUS          current
        DESCRIPTION
                "The atiOutLeaseUnknow reflects the counter of Dhcp Lease Unknown output frames."
        ::= { atiStkSwDhcpStatisticTable 11 }

atiOutLeaseActive       OBJECT-TYPE
        SYNTAX          Integer32 (1..4094)
        MAX-ACCESS      read-only
        STATUS          current
        DESCRIPTION
                "The atiOutLeaseActive reflects the counter of Dhcp Lease Active output frames."
        ::= { atiStkSwDhcpStatisticTable 12 }

atiOutLeaseUnassigned   OBJECT-TYPE
        SYNTAX          Integer32 (1..4094)
        MAX-ACCESS      read-only
        STATUS          current
        DESCRIPTION
                "The atiOutLeaseUnassigned reflects the counter of Dhcp Lease Unassigned output frames."
        ::= { atiStkSwDhcpStatisticTable 13 }

atiOutBootReply         OBJECT-TYPE
        SYNTAX          Integer32 (1..4094)
        MAX-ACCESS      read-only
        STATUS          current
        DESCRIPTION
                "The atiOutBootReply reflects the counter of Dhcp Boot Reply output frames."
        ::= { atiStkSwDhcpStatisticTable 14 }

END
