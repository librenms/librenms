--
-- ISKRATEL-MSAN-MIB.mib
-- MIB generated by MG-SOFT Visual MIB Builder Version 7.0  Build 220
-- Thursday, March 27, 2025 at 15:22:07
--

	ISKRATEL-MSAN-MIB DEFINITIONS ::= BEGIN
 
		IMPORTS
			dot1dBasePort			
				FROM BRIDGE-MIB			
			ifIndex, ifDescr, ifAdminStatus, ifOperStatus, InterfaceIndex			
				FROM IF-MIB			
			InetAddressType, InetAddress, InetAddressIPv6, InetAddressIPv4			
				FROM INET-ADDRESS-MIB			
			dot1qVlanIndex, VlanIndex			
				FROM Q-BRIDGE-MIB			
			enterprises			
				FROM RFC1155-SMI			
			SnmpAdminString			
				FROM SNMP-FRAMEWORK-MIB			
			TimeTicks, IpAddress, Integer32, Unsigned32, Gauge32, 
			Counter32, Counter64, BITS, OBJECT-TYPE, MODULE-IDENTITY, 
			NOTIFICATION-TYPE			
				FROM SNMPv2-SMI			
			DisplayString, RowStatus, MacAddress, TruthValue, TEXTUAL-CONVENTION			
				FROM SNMPv2-TC			
			vdslLineConfProfileName			
				FROM VDSL-LINE-MIB			
			xdsl2LineConfTemplateEntry, xdsl2LineAlarmConfTemplateEntry			
				FROM VDSL2-LINE-MIB;
	
	
		-- 1.3.6.1.4.1.1332.1.1.5
		msan MODULE-IDENTITY 
			LAST-UPDATED "201006221233Z"		-- June 22, 2010 at 12:33 GMT
			ORGANIZATION 
				"Iskratel"
			CONTACT-INFO 
				"Contact-info."
			DESCRIPTION 
				"Description."
			::= { products 5 }

		
	
--
-- Textual conventions
--
	
		VlanList ::= TEXTUAL-CONVENTION
			STATUS current
			DESCRIPTION 
				"Each octet within this value specifies a set of eight
				vlans, with the first octet specifying vlans 1 through
				8, the second octet specifying vlans 9 through 16, etc.
				Within each octet, the most significant bit represents
				the lowest numbered vlan, and the least significant bit
				represents the highest numbered vlan.  Thus, each vlan
				supported is represented by a single bit within the
				value of this object.  If that bit has a value of '1'
				then the associated port is in that vlan; the port is
				not included if the vlans bit has a value of '0'."
			SYNTAX OCTET STRING

		Xdsl2PsdMaskDs ::= TEXTUAL-CONVENTION
			STATUS current
			DESCRIPTION 
				"This is a structure that represents up to 32 PSD mask
				breakpoints.
				Each breakpoint occupies 3 octets: The first
				two octets hold the index of the subcarrier associated with the
				breakpoint.  The third octet holds the PSD reduction at the
				breakpoint from 0 (0 dBm/Hz) to 255 (-127.5 dBm/Hz) using units
				of 0.5 dBm/Hz.
				The subcarrier index is an unsigned number in the range 0 to
				NSCds-1."
			SYNTAX OCTET STRING (SIZE (0..96))

		Xdsl2PsdMaskUs ::= TEXTUAL-CONVENTION
			STATUS current
			DESCRIPTION 
				"This is a structure that represents up to 16 PSD mask breakpoints.
				Each breakpoint occupies 3 octets: The first two octets hold the
				index of the subcarrier associated with the breakpoint.  
				The third octet holds the PSD reduction at the breakpoint from 
				0(0 dBm/Hz) to 255 (-127.5 dBm/Hz) using units of 0.5 dBm/Hz. 
				The subcarrier index is an unsigned number in the range 0 to NSCus-1."
			SYNTAX OCTET STRING (SIZE (0..48))

		PortMask ::= TEXTUAL-CONVENTION
			STATUS current
			DESCRIPTION 
				"Each octet within this value specifies a set of eight
				ports, with the first octet specifying ports 1 through
				8, the second octet specifying ports 9 through 16, etc.
				Within each octet, the most significant bit represents
				the lowest numbered port, and the least significant bit
				represents the highest numbered port.  Thus, each port
				of the bridge is represented by a single bit within the
				value of this object.  If that bit has a value of '1'
				then that port is included in the set of ports; the port
				is not included if its bit has a value of '0'
				 
				When setting this value, the system will ignore 
				configuration for ports not between the first and last 
				valid ports.  Configuration of any port numbers between 
				this range that are not valid ports return a failure 
				message, but will still apply configuration for valid 
				ports."
			SYNTAX OCTET STRING

		PercentByFives ::= TEXTUAL-CONVENTION
			STATUS current
			DESCRIPTION 
				"An unsigned integer representing a value expressed 
				as a percentage with five percent increments."
			SYNTAX Unsigned32 (0 | 5 | 10 | 15 | 20 | 25 | 30 | 35 | 40 | 45 | 50 | 55 | 60 | 65 | 70 | 75 | 80 | 85 | 90 | 95 | 100)

	
--
-- Node definitions
--
	
		-- 1.3.6.1.4.1.1332
		iskratel OBJECT IDENTIFIER ::= { enterprises 1332 }

		
		-- 1.3.6.1.4.1.1332.1
		si2000 OBJECT IDENTIFIER ::= { iskratel 1 }

		
		-- 1.3.6.1.4.1.1332.1.1
		products OBJECT IDENTIFIER ::= { si2000 1 }

		
		-- 1.3.6.1.4.1.1332.1.1.5.1
		msanInfo OBJECT IDENTIFIER ::= { msan 1 }

		
		-- 1.3.6.1.4.1.1332.1.1.5.1.1
		msanShelfInfo OBJECT IDENTIFIER ::= { msanInfo 1 }

		
		-- 1.3.6.1.4.1.1332.1.1.5.1.1.1
		msanShelfId OBJECT-TYPE
			SYNTAX OCTET STRING
			MAX-ACCESS read-only
			STATUS current
			DESCRIPTION
				"MSAN shelf ID."
			::= { msanShelfInfo 1 }

		
		-- 1.3.6.1.4.1.1332.1.1.5.1.1.2
		msanShelfType OBJECT-TYPE
			SYNTAX OCTET STRING
			MAX-ACCESS read-only
			STATUS current
			DESCRIPTION
				"MSAN shelf type."
			::= { msanShelfInfo 2 }

		
		-- 1.3.6.1.4.1.1332.1.1.5.1.1.3
		msanShelfSize OBJECT-TYPE
			SYNTAX Integer32
			MAX-ACCESS read-only
			STATUS current
			DESCRIPTION
				"Size of MSAN shelf (in number of slots)."
			::= { msanShelfInfo 3 }

		
		-- 1.3.6.1.4.1.1332.1.1.5.1.2
		msanBoardInfo OBJECT IDENTIFIER ::= { msanInfo 2 }

		
		-- 1.3.6.1.4.1.1332.1.1.5.1.2.1
		msanBoardTable OBJECT-TYPE
			SYNTAX SEQUENCE OF MsanBoardEntry
			MAX-ACCESS not-accessible
			STATUS deprecated
			DESCRIPTION
				"Description."
			::= { msanBoardInfo 1 }

		
		-- 1.3.6.1.4.1.1332.1.1.5.1.2.1.1
		msanBoardEntry OBJECT-TYPE
			SYNTAX MsanBoardEntry
			MAX-ACCESS not-accessible
			STATUS deprecated
			DESCRIPTION
				"Description."
			INDEX { msanBoardNr }
			::= { msanBoardTable 1 }

		
		MsanBoardEntry ::=
			SEQUENCE { 
				msanBoardNr
					INTEGER,
				msanBoardParentNr
					INTEGER,
				msanBoardPosition
					INTEGER,
				msanBoardType
					OCTET STRING,
				msanBoardId
					OCTET STRING,
				msanBoardSerialNr
					OCTET STRING,
				msanBoardDescription
					OCTET STRING
			 }

		-- 1.3.6.1.4.1.1332.1.1.5.1.2.1.1.1
		msanBoardNr OBJECT-TYPE
			SYNTAX INTEGER (1..1000)
			MAX-ACCESS not-accessible
			STATUS deprecated
			DESCRIPTION
				"Unique identification of a board."
			::= { msanBoardEntry 1 }

		
		-- 1.3.6.1.4.1.1332.1.1.5.1.2.1.1.2
		msanBoardParentNr OBJECT-TYPE
			SYNTAX INTEGER (1..1000)
			MAX-ACCESS read-only
			STATUS deprecated
			DESCRIPTION
				"Unique identification of a parent board."
			::= { msanBoardEntry 2 }

		
		-- 1.3.6.1.4.1.1332.1.1.5.1.2.1.1.3
		msanBoardPosition OBJECT-TYPE
			SYNTAX INTEGER (1..1000)
			MAX-ACCESS read-only
			STATUS deprecated
			DESCRIPTION
				"Position of the board on the parent board."
			::= { msanBoardEntry 3 }

		
		-- 1.3.6.1.4.1.1332.1.1.5.1.2.1.1.4
		msanBoardType OBJECT-TYPE
			SYNTAX OCTET STRING
			MAX-ACCESS read-only
			STATUS deprecated
			DESCRIPTION
				"Type of physical board (e.g. IDC, SGO, SFA, ...)"
			::= { msanBoardEntry 4 }

		
		-- 1.3.6.1.4.1.1332.1.1.5.1.2.1.1.5
		msanBoardId OBJECT-TYPE
			SYNTAX OCTET STRING
			MAX-ACCESS read-only
			STATUS deprecated
			DESCRIPTION
				"Name (actual identification) of a board."
			::= { msanBoardEntry 5 }

		
		-- 1.3.6.1.4.1.1332.1.1.5.1.2.1.1.6
		msanBoardSerialNr OBJECT-TYPE
			SYNTAX OCTET STRING
			MAX-ACCESS read-only
			STATUS deprecated
			DESCRIPTION
				"Serial number of a board."
			::= { msanBoardEntry 6 }

		
		-- 1.3.6.1.4.1.1332.1.1.5.1.2.1.1.7
		msanBoardDescription OBJECT-TYPE
			SYNTAX OCTET STRING
			MAX-ACCESS read-write
			STATUS deprecated
			DESCRIPTION
				"Description of the board."
			::= { msanBoardEntry 7 }

		
		-- 1.3.6.1.4.1.1332.1.1.5.1.3
		msanSwInfo OBJECT IDENTIFIER ::= { msanInfo 3 }

		
		-- 1.3.6.1.4.1.1332.1.1.5.1.3.1
		msanSwSteerVersion OBJECT-TYPE
			SYNTAX DisplayString
			MAX-ACCESS read-only
			STATUS current
			DESCRIPTION
				"The unique steer code for this software. "
			::= { msanSwInfo 1 }

		
		-- 1.3.6.1.4.1.1332.1.1.5.1.3.2
		msanSwBuildDirectory OBJECT-TYPE
			SYNTAX DisplayString
			MAX-ACCESS read-only
			STATUS current
			DESCRIPTION
				"The directory where software was build on. "
			::= { msanSwInfo 2 }

		
		-- 1.3.6.1.4.1.1332.1.1.5.1.3.3
		msanSwBuildTime OBJECT-TYPE
			SYNTAX DisplayString
			MAX-ACCESS read-only
			STATUS current
			DESCRIPTION
				"The time when the software was built.  (DateAndTime textual convention, from SNMPv2-TC)"
			::= { msanSwInfo 3 }

		
		-- 1.3.6.1.4.1.1332.1.1.5.1.3.4
		msanSwBranch OBJECT-TYPE
			SYNTAX DisplayString
			MAX-ACCESS read-only
			STATUS current
			DESCRIPTION
				"The repository branch where the software was built from."
			::= { msanSwInfo 4 }

		
		-- 1.3.6.1.4.1.1332.1.1.5.1.3.5
		msanSwBuildReference OBJECT-TYPE
			SYNTAX Integer32
			MAX-ACCESS read-only
			STATUS current
			DESCRIPTION
				"The repository reference number of the software build branch. "
			::= { msanSwInfo 5 }

		
		-- 1.3.6.1.4.1.1332.1.1.5.1.3.6
		msanSwILVersion OBJECT-TYPE
			SYNTAX DisplayString
			MAX-ACCESS read-only
			STATUS current
			DESCRIPTION
				"The unique IL steer code for this software. "
			::= { msanSwInfo 6 }

		
		-- 1.3.6.1.4.1.1332.1.1.5.1.3.7
		msanSwIpmiVersion OBJECT-TYPE
			SYNTAX DisplayString
			MAX-ACCESS read-only
			STATUS current
			DESCRIPTION
				"The major version.minor version/IPMI version supported(HEX) number of the IPMI currently running on the switch. 
				For example, if the major version was 1 and the minor version was 2, the format would be '1.2/0'."
			::= { msanSwInfo 7 }

		
		-- 1.3.6.1.4.1.1332.1.1.5.1.3.8
		msanSwBspVersion OBJECT-TYPE
			SYNTAX DisplayString
			MAX-ACCESS read-only
			STATUS current
			DESCRIPTION
				"The release.version/id number of the BSP software currently running on the switch. 
				For example, if the release was 1 and the version was 2, the format would be '1.2/0'."
			::= { msanSwInfo 8 }

		
		-- 1.3.6.1.4.1.1332.1.1.5.1.3.9
		msanSwCPLDVersion OBJECT-TYPE
			SYNTAX DisplayString
			MAX-ACCESS read-only
			STATUS current
			DESCRIPTION
				"CPLD (Complex Programmable Logic Device) SW version"
			::= { msanSwInfo 9 }

		
		-- 1.3.6.1.4.1.1332.1.1.5.1.3.10
		msanReservePackage OBJECT-TYPE
			SYNTAX DisplayString
			MAX-ACCESS read-only
			STATUS current
			DESCRIPTION
				"Name of the reserve package on disk if it exists. "
			::= { msanSwInfo 10 }

		
		-- 1.3.6.1.4.1.1332.1.1.5.1.3.11
		msanSwComponentTable OBJECT-TYPE
			SYNTAX SEQUENCE OF MsanSwComponentEntry
			MAX-ACCESS not-accessible
			STATUS current
			DESCRIPTION
				"Description."
			::= { msanSwInfo 11 }

		
		-- 1.3.6.1.4.1.1332.1.1.5.1.3.11.1
		msanSwComponentEntry OBJECT-TYPE
			SYNTAX MsanSwComponentEntry
			MAX-ACCESS not-accessible
			STATUS current
			DESCRIPTION
				"Description."
			INDEX { msanSwComponentId }
			::= { msanSwComponentTable 1 }

		
		MsanSwComponentEntry ::=
			SEQUENCE { 
				msanSwComponentId
					Integer32,
				msanSwComponentName
					DisplayString,
				msanSwComponentSteerVersion
					DisplayString,
				msanSwComponentType
					INTEGER,
				msanSwComponentExternalVersion
					DisplayString
			 }

		-- 1.3.6.1.4.1.1332.1.1.5.1.3.11.1.1
		msanSwComponentId OBJECT-TYPE
			SYNTAX Integer32
			MAX-ACCESS not-accessible
			STATUS current
			DESCRIPTION
				"Unique index of SW component."
			::= { msanSwComponentEntry 1 }

		
		-- 1.3.6.1.4.1.1332.1.1.5.1.3.11.1.2
		msanSwComponentName OBJECT-TYPE
			SYNTAX DisplayString
			MAX-ACCESS read-only
			STATUS current
			DESCRIPTION
				"Name of software component (e.g. ES, EV, EF, EA)."
			::= { msanSwComponentEntry 2 }

		
		-- 1.3.6.1.4.1.1332.1.1.5.1.3.11.1.3
		msanSwComponentSteerVersion OBJECT-TYPE
			SYNTAX DisplayString
			MAX-ACCESS read-only
			STATUS current
			DESCRIPTION
				"Code version for this software component."
			::= { msanSwComponentEntry 3 }

		
		-- 1.3.6.1.4.1.1332.1.1.5.1.3.11.1.4
		msanSwComponentType OBJECT-TYPE
			SYNTAX INTEGER
				{
				application(1),
				platform(2)
				}
			MAX-ACCESS read-only
			STATUS current
			DESCRIPTION
				"Type of SW component."
			::= { msanSwComponentEntry 4 }

		
		-- 1.3.6.1.4.1.1332.1.1.5.1.3.11.1.5
		msanSwComponentExternalVersion OBJECT-TYPE
			SYNTAX DisplayString
			MAX-ACCESS read-only
			STATUS current
			DESCRIPTION
				"External code version of this software component."
			::= { msanSwComponentEntry 5 }

		
		-- 1.3.6.1.4.1.1332.1.1.5.1.4
		msanOtherInfo OBJECT IDENTIFIER ::= { msanInfo 4 }

		
		-- 1.3.6.1.4.1.1332.1.1.5.1.4.1
		msanSnmpSetErrorReason OBJECT-TYPE
			SYNTAX DisplayString
			MAX-ACCESS read-only
			STATUS current
			DESCRIPTION
				"Last error description of SNMP set command."
			::= { msanOtherInfo 1 }

		
		-- 1.3.6.1.4.1.1332.1.1.5.1.5
		msanLicense OBJECT IDENTIFIER ::= { msanInfo 5 }

		
		-- 1.3.6.1.4.1.1332.1.1.5.1.5.1
		msanLicenseGlobal OBJECT IDENTIFIER ::= { msanLicense 1 }

		
		-- 1.3.6.1.4.1.1332.1.1.5.1.5.1.1
		msanLicenseId OBJECT-TYPE
			SYNTAX DisplayString
			MAX-ACCESS read-only
			STATUS deprecated
			DESCRIPTION
				"License ID."
			::= { msanLicenseGlobal 1 }

		
		-- 1.3.6.1.4.1.1332.1.1.5.1.5.1.2
		msanLicenseCreationDate OBJECT-TYPE
			SYNTAX DisplayString
			MAX-ACCESS read-only
			STATUS deprecated
			DESCRIPTION
				"Licence creation date."
			::= { msanLicenseGlobal 2 }

		
		-- 1.3.6.1.4.1.1332.1.1.5.1.5.1.3
		msanLicenseExpirationDate OBJECT-TYPE
			SYNTAX DisplayString
			MAX-ACCESS read-only
			STATUS deprecated
			DESCRIPTION
				"Licence expiration date."
			::= { msanLicenseGlobal 3 }

		
		-- 1.3.6.1.4.1.1332.1.1.5.1.5.1.4
		msanLicenseCustomerId OBJECT-TYPE
			SYNTAX DisplayString
			MAX-ACCESS read-only
			STATUS deprecated
			DESCRIPTION
				"License customer  ID."
			::= { msanLicenseGlobal 4 }

		
		-- 1.3.6.1.4.1.1332.1.1.5.1.5.1.5
		msanLicenseActivate OBJECT-TYPE
			SYNTAX INTEGER
				{
				enable(1),
				disable(2)
				}
			MAX-ACCESS read-write
			STATUS deprecated
			DESCRIPTION
				"Activate licence files from local disk."
			DEFVAL { disable }
			::= { msanLicenseGlobal 5 }

		
		-- 1.3.6.1.4.1.1332.1.1.5.1.5.1.6
		msanLicenseFileGet OBJECT-TYPE
			SYNTAX DisplayString
			MAX-ACCESS read-write
			STATUS current
			DESCRIPTION
				"msanLicenseFileGet parameter is used to start transfer of  license file (extension .lic) from external tftp or ftp server to local file.
				Next syntax must be used for tftp or ftp transfer:
				tftp://<IP>|<hostname>[:<port>]/[<path>/]<remote_file_name> [<local_file_name>]
				ftp://<usr>[:<pass>]@<IP>|<hostname>[:<port>]/[<path>/]<remote_file_name>  [<local_file_name>]
				"
			DEFVAL { ''b }
			::= { msanLicenseGlobal 6 }

		
		-- 1.3.6.1.4.1.1332.1.1.5.1.5.2
		msanLicenseOnuTable OBJECT-TYPE
			SYNTAX SEQUENCE OF MsanLicenseOnuEntry
			MAX-ACCESS not-accessible
			STATUS current
			DESCRIPTION
				"Description."
			::= { msanLicense 2 }

		
		-- 1.3.6.1.4.1.1332.1.1.5.1.5.2.1
		msanLicenseOnuEntry OBJECT-TYPE
			SYNTAX MsanLicenseOnuEntry
			MAX-ACCESS not-accessible
			STATUS current
			DESCRIPTION
				" "
			INDEX { msanLicenseOnuVendorId }
			::= { msanLicenseOnuTable 1 }

		
		MsanLicenseOnuEntry ::=
			SEQUENCE { 
				msanLicenseOnuVendorId
					DisplayString
			 }

		-- 1.3.6.1.4.1.1332.1.1.5.1.5.2.1.1
		msanLicenseOnuVendorId OBJECT-TYPE
			SYNTAX DisplayString
			MAX-ACCESS not-accessible
			STATUS current
			DESCRIPTION
				"Licensed ONU vendor ID."
			::= { msanLicenseOnuEntry 1 }

		
		-- 1.3.6.1.4.1.1332.1.1.5.1.5.3
		msanLicenseFileTable OBJECT-TYPE
			SYNTAX SEQUENCE OF MsanLicenseFileEntry
			MAX-ACCESS not-accessible
			STATUS current
			DESCRIPTION
				"Description."
			::= { msanLicense 3 }

		
		-- 1.3.6.1.4.1.1332.1.1.5.1.5.3.1
		msanLicenseFileEntry OBJECT-TYPE
			SYNTAX MsanLicenseFileEntry
			MAX-ACCESS not-accessible
			STATUS current
			DESCRIPTION
				"Description."
			INDEX { msanLicenseFileName }
			::= { msanLicenseFileTable 1 }

		
		MsanLicenseFileEntry ::=
			SEQUENCE { 
				msanLicenseFileName
					DisplayString,
				msanLicenseFileRowStatus
					RowStatus,
				msanLicenseFileActivate
					INTEGER
			 }

		-- 1.3.6.1.4.1.1332.1.1.5.1.5.3.1.1
		msanLicenseFileName OBJECT-TYPE
			SYNTAX DisplayString
			MAX-ACCESS not-accessible
			STATUS current
			DESCRIPTION
				"License file name (extension .lic)"
			::= { msanLicenseFileEntry 1 }

		
		-- 1.3.6.1.4.1.1332.1.1.5.1.5.3.1.2
		msanLicenseFileRowStatus OBJECT-TYPE
			SYNTAX RowStatus
			MAX-ACCESS read-write
			STATUS current
			DESCRIPTION
				"The row status object controls the creation/deletion of rows in this table. 
				Its semantics are the same as those for the RowStatus textual convention specified for SNMPv2.
				Setting this object to destroy(6) will remove this entry.
				Read values: active(1).
				Other values are currently not supported."
			::= { msanLicenseFileEntry 2 }

		
		-- 1.3.6.1.4.1.1332.1.1.5.1.5.3.1.3
		msanLicenseFileActivate OBJECT-TYPE
			SYNTAX INTEGER
				{
				enable(1),
				disable(2)
				}
			MAX-ACCESS read-write
			STATUS current
			DESCRIPTION
				"Activate licence file from local disk."
			::= { msanLicenseFileEntry 3 }

		
		-- 1.3.6.1.4.1.1332.1.1.5.1.5.4
		msanActiveLicenseTable OBJECT-TYPE
			SYNTAX SEQUENCE OF MsanActiveLicenseEntry
			MAX-ACCESS not-accessible
			STATUS current
			DESCRIPTION
				"Description."
			::= { msanLicense 4 }

		
		-- 1.3.6.1.4.1.1332.1.1.5.1.5.4.1
		msanActiveLicenseEntry OBJECT-TYPE
			SYNTAX MsanActiveLicenseEntry
			MAX-ACCESS not-accessible
			STATUS current
			DESCRIPTION
				"Description."
			INDEX { msanActiveLicenseType }
			::= { msanActiveLicenseTable 1 }

		
		MsanActiveLicenseEntry ::=
			SEQUENCE { 
				msanActiveLicenseType
					INTEGER,
				msanActiveLicenceFileName
					DisplayString,
				msanActiveLicenseId
					DisplayString,
				msanActiveLicenseCreationDate
					DisplayString,
				msanActiveLicenseExpirationDate
					DisplayString,
				msanActiveLicenseCustomerId
					DisplayString,
				msanActiveLicenseNodeId
					DisplayString,
				msanActiveLicenseNodeMaxOltPorts
					Integer32
			 }

		-- 1.3.6.1.4.1.1332.1.1.5.1.5.4.1.2
		msanActiveLicenseType OBJECT-TYPE
			SYNTAX INTEGER
				{
				generalLicense(1),
				nodeLicense(2)
				}
			MAX-ACCESS not-accessible
			STATUS current
			DESCRIPTION
				"License type."
			::= { msanActiveLicenseEntry 2 }

		
		-- 1.3.6.1.4.1.1332.1.1.5.1.5.4.1.3
		msanActiveLicenceFileName OBJECT-TYPE
			SYNTAX DisplayString
			MAX-ACCESS read-only
			STATUS current
			DESCRIPTION
				"License file name (extension .lic)"
			::= { msanActiveLicenseEntry 3 }

		
		-- 1.3.6.1.4.1.1332.1.1.5.1.5.4.1.5
		msanActiveLicenseId OBJECT-TYPE
			SYNTAX DisplayString
			MAX-ACCESS read-only
			STATUS current
			DESCRIPTION
				"License ID."
			::= { msanActiveLicenseEntry 5 }

		
		-- 1.3.6.1.4.1.1332.1.1.5.1.5.4.1.6
		msanActiveLicenseCreationDate OBJECT-TYPE
			SYNTAX DisplayString
			MAX-ACCESS read-only
			STATUS current
			DESCRIPTION
				"Licence creation date."
			::= { msanActiveLicenseEntry 6 }

		
		-- 1.3.6.1.4.1.1332.1.1.5.1.5.4.1.7
		msanActiveLicenseExpirationDate OBJECT-TYPE
			SYNTAX DisplayString
			MAX-ACCESS read-only
			STATUS current
			DESCRIPTION
				"Licence expiration date."
			::= { msanActiveLicenseEntry 7 }

		
		-- 1.3.6.1.4.1.1332.1.1.5.1.5.4.1.8
		msanActiveLicenseCustomerId OBJECT-TYPE
			SYNTAX DisplayString
			MAX-ACCESS read-only
			STATUS current
			DESCRIPTION
				"License customer  ID."
			DEFVAL { ''b }
			::= { msanActiveLicenseEntry 8 }

		
		-- 1.3.6.1.4.1.1332.1.1.5.1.5.4.1.9
		msanActiveLicenseNodeId OBJECT-TYPE
			SYNTAX DisplayString
			MAX-ACCESS read-only
			STATUS current
			DESCRIPTION
				"Node ID."
			DEFVAL { ''b }
			::= { msanActiveLicenseEntry 9 }

		
		-- 1.3.6.1.4.1.1332.1.1.5.1.5.4.1.10
		msanActiveLicenseNodeMaxOltPorts OBJECT-TYPE
			SYNTAX Integer32
			MAX-ACCESS read-only
			STATUS current
			DESCRIPTION
				"Maximum number of supported OLT ports."
			::= { msanActiveLicenseEntry 10 }

		
		-- 1.3.6.1.4.1.1332.1.1.5.1.6
		msanResources OBJECT IDENTIFIER ::= { msanInfo 6 }

		
		-- 1.3.6.1.4.1.1332.1.1.5.1.6.1
		msanCpu OBJECT IDENTIFIER ::= { msanResources 1 }

		
		-- 1.3.6.1.4.1.1332.1.1.5.1.6.1.1
		msanCpuCurUsage OBJECT-TYPE
			SYNTAX INTEGER (0..100)
			UNITS "Percent"
			MAX-ACCESS read-only
			STATUS current
			DESCRIPTION
				"Current CPU Usage in the last 10 sec."
			::= { msanCpu 1 }

		
		-- 1.3.6.1.4.1.1332.1.1.5.1.6.1.2
		msanCpuMaxUsage OBJECT-TYPE
			SYNTAX INTEGER (0..100)
			UNITS "Percent"
			MAX-ACCESS read-only
			STATUS current
			DESCRIPTION
				"Maximum CPU Usage."
			::= { msanCpu 2 }

		
		-- 1.3.6.1.4.1.1332.1.1.5.1.6.1.3
		msanCpuMinUsage OBJECT-TYPE
			SYNTAX INTEGER (0..100)
			UNITS "Percent"
			MAX-ACCESS read-only
			STATUS current
			DESCRIPTION
				"Minimum CPU Usage."
			::= { msanCpu 3 }

		
		-- 1.3.6.1.4.1.1332.1.1.5.1.6.1.4
		msanCpuAvgUsage OBJECT-TYPE
			SYNTAX INTEGER (0..100)
			UNITS "Percent"
			MAX-ACCESS read-only
			STATUS current
			DESCRIPTION
				"Average CPU Usage."
			::= { msanCpu 4 }

		
		-- 1.3.6.1.4.1.1332.1.1.5.1.6.1.10
		msanCpuDetailTable OBJECT-TYPE
			SYNTAX SEQUENCE OF MsanCpuDetailEntry
			MAX-ACCESS not-accessible
			STATUS current
			DESCRIPTION
				"Description."
			::= { msanCpu 10 }

		
		-- 1.3.6.1.4.1.1332.1.1.5.1.6.1.10.1
		msanCpuDetailEntry OBJECT-TYPE
			SYNTAX MsanCpuDetailEntry
			MAX-ACCESS not-accessible
			STATUS current
			DESCRIPTION
				"Description."
			INDEX { msanCpuDetailId }
			::= { msanCpuDetailTable 1 }

		
		MsanCpuDetailEntry ::=
			SEQUENCE { 
				msanCpuDetailId
					Integer32,
				msanCpuDetailCurUsage
					INTEGER,
				msanCpuDetailMaxUsage
					INTEGER,
				msanCpuDetailMinUsage
					INTEGER,
				msanCpuDetailAvgUsage
					INTEGER
			 }

		-- 1.3.6.1.4.1.1332.1.1.5.1.6.1.10.1.1
		msanCpuDetailId OBJECT-TYPE
			SYNTAX Integer32
			MAX-ACCESS not-accessible
			STATUS current
			DESCRIPTION
				"CPU unit ID."
			::= { msanCpuDetailEntry 1 }

		
		-- 1.3.6.1.4.1.1332.1.1.5.1.6.1.10.1.2
		msanCpuDetailCurUsage OBJECT-TYPE
			SYNTAX INTEGER
			UNITS "Percent"
			MAX-ACCESS read-only
			STATUS current
			DESCRIPTION
				"Current Usage of specified CPU in the last 10 sec."
			::= { msanCpuDetailEntry 2 }

		
		-- 1.3.6.1.4.1.1332.1.1.5.1.6.1.10.1.3
		msanCpuDetailMaxUsage OBJECT-TYPE
			SYNTAX INTEGER
			UNITS "Percent"
			MAX-ACCESS read-only
			STATUS current
			DESCRIPTION
				"Maximum Usage of specified CPU."
			::= { msanCpuDetailEntry 3 }

		
		-- 1.3.6.1.4.1.1332.1.1.5.1.6.1.10.1.4
		msanCpuDetailMinUsage OBJECT-TYPE
			SYNTAX INTEGER
			UNITS "Percent"
			MAX-ACCESS read-only
			STATUS current
			DESCRIPTION
				"Minimum Usage of specified CPU."
			::= { msanCpuDetailEntry 4 }

		
		-- 1.3.6.1.4.1.1332.1.1.5.1.6.1.10.1.5
		msanCpuDetailAvgUsage OBJECT-TYPE
			SYNTAX INTEGER
			UNITS "Percent"
			MAX-ACCESS read-only
			STATUS current
			DESCRIPTION
				"Average Usage of specified CPU."
			::= { msanCpuDetailEntry 5 }

		
		-- 1.3.6.1.4.1.1332.1.1.5.1.6.2
		msanDisk OBJECT IDENTIFIER ::= { msanResources 2 }

		
		-- 1.3.6.1.4.1.1332.1.1.5.1.6.2.1
		msanDiskTable OBJECT-TYPE
			SYNTAX SEQUENCE OF MsanDiskEntry
			MAX-ACCESS not-accessible
			STATUS current
			DESCRIPTION
				"Description."
			::= { msanDisk 1 }

		
		-- 1.3.6.1.4.1.1332.1.1.5.1.6.2.1.1
		msanDiskEntry OBJECT-TYPE
			SYNTAX MsanDiskEntry
			MAX-ACCESS not-accessible
			STATUS current
			DESCRIPTION
				"Description."
			INDEX { msanDiskType }
			::= { msanDiskTable 1 }

		
		MsanDiskEntry ::=
			SEQUENCE { 
				msanDiskType
					INTEGER,
				msanDiskTotalSpace
					Unsigned32,
				msanDiskFreeSpace
					Unsigned32,
				msanDiskUsedSpace
					Unsigned32
			 }

		-- 1.3.6.1.4.1.1332.1.1.5.1.6.2.1.1.1
		msanDiskType OBJECT-TYPE
			SYNTAX INTEGER
				{
				activeDisk(1),
				backupDisk(2),
				logDisk(3)
				}
			MAX-ACCESS not-accessible
			STATUS current
			DESCRIPTION
				"Disk type."
			::= { msanDiskEntry 1 }

		
		-- 1.3.6.1.4.1.1332.1.1.5.1.6.2.1.1.2
		msanDiskTotalSpace OBJECT-TYPE
			SYNTAX Unsigned32
			UNITS "kB"
			MAX-ACCESS read-only
			STATUS current
			DESCRIPTION
				"Total disk space of selected type."
			::= { msanDiskEntry 2 }

		
		-- 1.3.6.1.4.1.1332.1.1.5.1.6.2.1.1.3
		msanDiskFreeSpace OBJECT-TYPE
			SYNTAX Unsigned32
			UNITS "kB"
			MAX-ACCESS read-only
			STATUS current
			DESCRIPTION
				"Free disk space of selected type."
			::= { msanDiskEntry 3 }

		
		-- 1.3.6.1.4.1.1332.1.1.5.1.6.2.1.1.4
		msanDiskUsedSpace OBJECT-TYPE
			SYNTAX Unsigned32
			UNITS "kB"
			MAX-ACCESS read-only
			STATUS current
			DESCRIPTION
				"Used disk space of selected type."
			::= { msanDiskEntry 4 }

		
		-- 1.3.6.1.4.1.1332.1.1.5.1.6.3
		msanMemory OBJECT IDENTIFIER ::= { msanResources 3 }

		
		-- 1.3.6.1.4.1.1332.1.1.5.1.6.3.1
		msanMemoryTotal OBJECT-TYPE
			SYNTAX Unsigned32
			UNITS "kB"
			MAX-ACCESS read-only
			STATUS current
			DESCRIPTION
				"Description."
			::= { msanMemory 1 }

		
		-- 1.3.6.1.4.1.1332.1.1.5.1.6.3.2
		msanMemoryFree OBJECT-TYPE
			SYNTAX Unsigned32
			UNITS "kB"
			MAX-ACCESS read-only
			STATUS current
			DESCRIPTION
				"Description."
			::= { msanMemory 2 }

		
		-- 1.3.6.1.4.1.1332.1.1.5.1.6.3.3
		msanMemoryAllocated OBJECT-TYPE
			SYNTAX Unsigned32
			UNITS "kB"
			MAX-ACCESS read-only
			STATUS current
			DESCRIPTION
				"Description."
			::= { msanMemory 3 }

		
		-- 1.3.6.1.4.1.1332.1.1.5.3
		msanAdditionalConf OBJECT IDENTIFIER ::= { msan 3 }

		
		-- 1.3.6.1.4.1.1332.1.1.5.3.1
		msanSystem OBJECT IDENTIFIER ::= { msanAdditionalConf 1 }

		
		-- 1.3.6.1.4.1.1332.1.1.5.3.1.1
		msanDateTime OBJECT-TYPE
			SYNTAX OCTET STRING
			MAX-ACCESS read-write
			STATUS current
			DESCRIPTION
				"Board date and time in format: dd/MM/yyyy HH:mm:ss."
			::= { msanSystem 1 }

		
		-- 1.3.6.1.4.1.1332.1.1.5.3.1.2
		msanShelfIdConf OBJECT-TYPE
			SYNTAX OCTET STRING
			MAX-ACCESS read-write
			STATUS current
			DESCRIPTION
				"MSAN Shelf ID."
			::= { msanSystem 2 }

		
		-- 1.3.6.1.4.1.1332.1.1.5.3.1.3
		msanConfData OBJECT-TYPE
			SYNTAX INTEGER
				{
				saved(1),
				notSaved(2)
				}
			MAX-ACCESS read-only
			STATUS current
			DESCRIPTION
				"Configured data saved or not saved to file on local file system."
			::= { msanSystem 3 }

		
		-- 1.3.6.1.4.1.1332.1.1.5.3.1.4
		msanSwUpgrade OBJECT-TYPE
			SYNTAX OCTET STRING
			MAX-ACCESS read-write
			STATUS deprecated
			DESCRIPTION
				"msanSWUpgrade parameetr is used to start SW upgrade from external http or ftp server.
				User must set the next string value:         <repository URL> <package name> [|reboot|]
				
				<repository URL> = http|ftp://<IP>|<hostname>[:<port>]/[<path>/]
				
				
				Procedure uses anonymous type of identification.
				If a non standard port is used, this port must be also specified in the repository URL.
				'reboot' option is used only on boards with multiple SW packages support."
			::= { msanSystem 4 }

		
		-- 1.3.6.1.4.1.1332.1.1.5.3.1.5
		msanCliScriptCreate OBJECT-TYPE
			SYNTAX OCTET STRING (SIZE (0..32))
			MAX-ACCESS read-write
			STATUS current
			DESCRIPTION
				"When set with a non-empty string, current configuration will be saved to script file with that name
				(name must end with .scr).
				If file already exists it's overwritten.
				On Get request this object will always return an empty string."
			::= { msanSystem 5 }

		
		-- 1.3.6.1.4.1.1332.1.1.5.3.1.6
		msanCliScriptTable OBJECT-TYPE
			SYNTAX SEQUENCE OF MsanCliScriptEntry
			MAX-ACCESS not-accessible
			STATUS current
			DESCRIPTION
				"Description."
			::= { msanSystem 6 }

		
		-- 1.3.6.1.4.1.1332.1.1.5.3.1.6.1
		msanCliScriptEntry OBJECT-TYPE
			SYNTAX MsanCliScriptEntry
			MAX-ACCESS not-accessible
			STATUS current
			DESCRIPTION
				"Description."
			INDEX { msanCliScriptName }
			::= { msanCliScriptTable 1 }

		
		MsanCliScriptEntry ::=
			SEQUENCE { 
				msanCliScriptName
					OCTET STRING,
				msanCliScriptApply
					INTEGER,
				msanCliScriptApplyStatus
					INTEGER,
				msanCliScriptRowStatus
					RowStatus
			 }

		-- 1.3.6.1.4.1.1332.1.1.5.3.1.6.1.1
		msanCliScriptName OBJECT-TYPE
			SYNTAX OCTET STRING (SIZE (1..32))
			MAX-ACCESS not-accessible
			STATUS current
			DESCRIPTION
				"CLI script name"
			::= { msanCliScriptEntry 1 }

		
		-- 1.3.6.1.4.1.1332.1.1.5.3.1.6.1.2
		msanCliScriptApply OBJECT-TYPE
			SYNTAX INTEGER
				{
				enable(1),
				disable(2)
				}
			MAX-ACCESS read-write
			STATUS current
			DESCRIPTION
				"When set to enable(1) selected selected CLI script is applied."
			::= { msanCliScriptEntry 2 }

		
		-- 1.3.6.1.4.1.1332.1.1.5.3.1.6.1.3
		msanCliScriptApplyStatus OBJECT-TYPE
			SYNTAX INTEGER
				{
				notInitiated(1),
				inProcess(2)
				}
			MAX-ACCESS read-only
			STATUS current
			DESCRIPTION
				"Status of CLI script apply request"
			::= { msanCliScriptEntry 3 }

		
		-- 1.3.6.1.4.1.1332.1.1.5.3.1.6.1.4
		msanCliScriptRowStatus OBJECT-TYPE
			SYNTAX RowStatus
			MAX-ACCESS read-create
			STATUS current
			DESCRIPTION
				"The row status object controls the creation/deletion of rows in this table. 
				Its semantics are the same as those for the RowStatus textual convention specified for SNMPv2.
				Setting this object to destroy(6) will remove this entry.
				Read values: active(1).
				Other values are currently not supported."
			::= { msanCliScriptEntry 4 }

		
		-- 1.3.6.1.4.1.1332.1.1.5.3.1.7
		msanCliPrompt OBJECT-TYPE
			SYNTAX OCTET STRING (SIZE (0..64))
			MAX-ACCESS read-write
			STATUS current
			DESCRIPTION
				"CLI prompt value."
			::= { msanSystem 7 }

		
		-- 1.3.6.1.4.1.1332.1.1.5.3.1.8
		msanChassisId OBJECT-TYPE
			SYNTAX Integer32 (1..99)
			MAX-ACCESS read-write
			STATUS current
			DESCRIPTION
				"MSAN Chassis ID."
			::= { msanSystem 8 }

		
		-- 1.3.6.1.4.1.1332.1.1.5.3.1.9
		msanSwBootPackageTable OBJECT-TYPE
			SYNTAX SEQUENCE OF MsanSwBootPackageEntry
			MAX-ACCESS not-accessible
			STATUS current
			DESCRIPTION
				"Description."
			::= { msanSystem 9 }

		
		-- 1.3.6.1.4.1.1332.1.1.5.3.1.9.1
		msanSwBootPackageEntry OBJECT-TYPE
			SYNTAX MsanSwBootPackageEntry
			MAX-ACCESS not-accessible
			STATUS current
			DESCRIPTION
				"Description."
			INDEX { msanSwBootPackageName }
			::= { msanSwBootPackageTable 1 }

		
		MsanSwBootPackageEntry ::=
			SEQUENCE { 
				msanSwBootPackageName
					DisplayString,
				msanSwBootPackageStatus
					INTEGER
			 }

		-- 1.3.6.1.4.1.1332.1.1.5.3.1.9.1.1
		msanSwBootPackageName OBJECT-TYPE
			SYNTAX DisplayString
			MAX-ACCESS read-only
			STATUS current
			DESCRIPTION
				"SW package name on local disk."
			::= { msanSwBootPackageEntry 1 }

		
		-- 1.3.6.1.4.1.1332.1.1.5.3.1.9.1.2
		msanSwBootPackageStatus OBJECT-TYPE
			SYNTAX INTEGER
				{
				currentActive(1),
				nextActive(2),
				backup(3),
				none(4),
				fail(5)
				}
			MAX-ACCESS read-write
			STATUS current
			DESCRIPTION
				"SW package status. 
				You can set only nextActive(2) value. Other values are read-only."
			::= { msanSwBootPackageEntry 2 }

		
		-- 1.3.6.1.4.1.1332.1.1.5.3.1.10
		msanSystemSwUpgrade OBJECT IDENTIFIER ::= { msanSystem 10 }

		
		-- 1.3.6.1.4.1.1332.1.1.5.3.1.10.1
		msanSystemSwUpgradeStart OBJECT-TYPE
			SYNTAX INTEGER
				{
				enable(1),
				disable(2)
				}
			MAX-ACCESS read-write
			STATUS current
			DESCRIPTION
				"Control of SW upgrade procedure.
				When set to enable(1) transfer of SW package from defined server is started."
			DEFVAL { disable }
			::= { msanSystemSwUpgrade 1 }

		
		-- 1.3.6.1.4.1.1332.1.1.5.3.1.10.2
		msanSystemSwUpgradeStatus OBJECT-TYPE
			SYNTAX INTEGER
				{
				inprogress(1),
				successful(2),
				failed(3),
				notInitiated(4)
				}
			MAX-ACCESS read-only
			STATUS current
			DESCRIPTION
				"The SW upgrade status info."
			DEFVAL { notInitiated }
			::= { msanSystemSwUpgrade 2 }

		
		-- 1.3.6.1.4.1.1332.1.1.5.3.1.10.3
		msanSystemSwUpgradeServerIpAddressType OBJECT-TYPE
			SYNTAX InetAddressType
			MAX-ACCESS read-write
			STATUS current
			DESCRIPTION
				"Specifies the type of the upgrade server address: ipv4[1], ipv6[2]."
			DEFVAL { ipv4 }
			::= { msanSystemSwUpgrade 3 }

		
		-- 1.3.6.1.4.1.1332.1.1.5.3.1.10.4
		msanSystemSwUpgradeServerIpAddress OBJECT-TYPE
			SYNTAX InetAddress
			MAX-ACCESS read-write
			STATUS current
			DESCRIPTION
				"The remote SW upgrade server IP address."
			::= { msanSystemSwUpgrade 4 }

		
		-- 1.3.6.1.4.1.1332.1.1.5.3.1.10.5
		msanSystemSwUpgradeServerDnsName OBJECT-TYPE
			SYNTAX DisplayString
			MAX-ACCESS read-write
			STATUS current
			DESCRIPTION
				"The remote SW upgrade server dns name."
			DEFVAL { ''b }
			::= { msanSystemSwUpgrade 5 }

		
		-- 1.3.6.1.4.1.1332.1.1.5.3.1.10.6
		msanSystemSwUpgradeProtocol OBJECT-TYPE
			SYNTAX INTEGER
				{
				tftp(1),
				ftp(2),
				sftp(3)
				}
			MAX-ACCESS read-write
			STATUS current
			DESCRIPTION
				"The SW upgrade protocol."
			DEFVAL { tftp }
			::= { msanSystemSwUpgrade 6 }

		
		-- 1.3.6.1.4.1.1332.1.1.5.3.1.10.7
		msanSystemSwUpgradeProtocolPortId OBJECT-TYPE
			SYNTAX Integer32 (-1..65535)
			MAX-ACCESS read-write
			STATUS current
			DESCRIPTION
				"The SW upgrade protocol port number.
				If value is set to -1, standard protocol number is used."
			DEFVAL { -1 }
			::= { msanSystemSwUpgrade 7 }

		
		-- 1.3.6.1.4.1.1332.1.1.5.3.1.10.8
		msanSystemSwUpgradeUserName OBJECT-TYPE
			SYNTAX DisplayString
			MAX-ACCESS read-write
			STATUS current
			DESCRIPTION
				"The username used in SW upgrade protocol.
				
				When sftp upgrade protocol is used, username must be set."
			DEFVAL { ''b }
			::= { msanSystemSwUpgrade 8 }

		
		-- 1.3.6.1.4.1.1332.1.1.5.3.1.10.9
		msanSystemSwUpgradeUserPassword OBJECT-TYPE
			SYNTAX DisplayString
			MAX-ACCESS read-write
			STATUS current
			DESCRIPTION
				"The user password used in SW upgrade protocol.
				
				When sftp upgrade protocol is used, username must be set."
			DEFVAL { ''b }
			::= { msanSystemSwUpgrade 9 }

		
		-- 1.3.6.1.4.1.1332.1.1.5.3.1.10.10
		msanSystemSwUpgradePath OBJECT-TYPE
			SYNTAX DisplayString
			MAX-ACCESS read-write
			STATUS current
			DESCRIPTION
				"The path to the SW package location."
			DEFVAL { ''b }
			::= { msanSystemSwUpgrade 10 }

		
		-- 1.3.6.1.4.1.1332.1.1.5.3.1.10.11
		msanSystemSwUpgradePackageName OBJECT-TYPE
			SYNTAX DisplayString
			MAX-ACCESS read-write
			STATUS current
			DESCRIPTION
				"The SW package name"
			DEFVAL { ''b }
			::= { msanSystemSwUpgrade 11 }

		
		-- 1.3.6.1.4.1.1332.1.1.5.3.1.10.20
		msanSystemSwUpgradeStatusAddInfo OBJECT-TYPE
			SYNTAX DisplayString
			MAX-ACCESS read-only
			STATUS current
			DESCRIPTION
				"SW upgrade status additional info."
			::= { msanSystemSwUpgrade 20 }

		
		-- 1.3.6.1.4.1.1332.1.1.5.3.1.11
		msanSystemLogsUpload OBJECT IDENTIFIER ::= { msanSystem 11 }

		
		-- 1.3.6.1.4.1.1332.1.1.5.3.1.11.1
		msanSystemLogsUploadStart OBJECT-TYPE
			SYNTAX INTEGER
				{
				enableActive(1),
				disable(2),
				enableStandby(3)
				}
			MAX-ACCESS read-write
			STATUS current
			DESCRIPTION
				"Control of system logs upload procedure.
				When set to enable_active(1) transfer of file from active board to defined server is started.
				When set to enable_standby(3) transfer of file from standby (peer) board to defined server is started.
				"
			DEFVAL { disable }
			::= { msanSystemLogsUpload 1 }

		
		-- 1.3.6.1.4.1.1332.1.1.5.3.1.11.2
		msanSystemLogsUploadStatus OBJECT-TYPE
			SYNTAX INTEGER
				{
				inprogress(1),
				successful(2),
				failed(3),
				notInitiated(4)
				}
			MAX-ACCESS read-only
			STATUS current
			DESCRIPTION
				"The system logs upload status info."
			DEFVAL { notInitiated }
			::= { msanSystemLogsUpload 2 }

		
		-- 1.3.6.1.4.1.1332.1.1.5.3.1.11.3
		msanSystemLogsUploadServerIpAddressType OBJECT-TYPE
			SYNTAX InetAddressType
			MAX-ACCESS read-write
			STATUS current
			DESCRIPTION
				"Specifies the type of the system logs upload server address: ipv4[1], ipv6[2]."
			DEFVAL { ipv4 }
			::= { msanSystemLogsUpload 3 }

		
		-- 1.3.6.1.4.1.1332.1.1.5.3.1.11.4
		msanSystemLogsUploadServerIpAddress OBJECT-TYPE
			SYNTAX InetAddress
			MAX-ACCESS read-write
			STATUS current
			DESCRIPTION
				"The remote system logs upload server IP address."
			::= { msanSystemLogsUpload 4 }

		
		-- 1.3.6.1.4.1.1332.1.1.5.3.1.11.5
		msanSystemLogsUploadServerDnsName OBJECT-TYPE
			SYNTAX DisplayString
			MAX-ACCESS read-write
			STATUS current
			DESCRIPTION
				"The remote system logs upload server dns name."
			DEFVAL { ''b }
			::= { msanSystemLogsUpload 5 }

		
		-- 1.3.6.1.4.1.1332.1.1.5.3.1.11.6
		msanSystemLogsUploadProtocol OBJECT-TYPE
			SYNTAX INTEGER
				{
				tftp(1),
				ftp(2),
				sftp(3)
				}
			MAX-ACCESS read-write
			STATUS current
			DESCRIPTION
				"The system logs upload protocol."
			DEFVAL { tftp }
			::= { msanSystemLogsUpload 6 }

		
		-- 1.3.6.1.4.1.1332.1.1.5.3.1.11.7
		msanSystemLogsUploadProtocolPortId OBJECT-TYPE
			SYNTAX Integer32 (-1..65535)
			MAX-ACCESS read-write
			STATUS current
			DESCRIPTION
				"The system logs upload protocol port number.
				If value is set to -1, standard protocol number is used."
			DEFVAL { -1 }
			::= { msanSystemLogsUpload 7 }

		
		-- 1.3.6.1.4.1.1332.1.1.5.3.1.11.8
		msanSystemLogsUploadUserName OBJECT-TYPE
			SYNTAX DisplayString
			MAX-ACCESS read-write
			STATUS current
			DESCRIPTION
				"The username used in system logs upload protocol.
				
				When sftp upgrade protocol is used, username must be set."
			DEFVAL { ''b }
			::= { msanSystemLogsUpload 8 }

		
		-- 1.3.6.1.4.1.1332.1.1.5.3.1.11.9
		msanSystemLogsUploadUserPassword OBJECT-TYPE
			SYNTAX DisplayString
			MAX-ACCESS read-write
			STATUS current
			DESCRIPTION
				"The user password used in system logs upload protocol.
				
				When sftp upgrade protocol is used, username must be set."
			DEFVAL { ''b }
			::= { msanSystemLogsUpload 9 }

		
		-- 1.3.6.1.4.1.1332.1.1.5.3.1.11.10
		msanSystemLogsUploadPath OBJECT-TYPE
			SYNTAX DisplayString
			MAX-ACCESS read-write
			STATUS current
			DESCRIPTION
				"The path to the system logs file location."
			DEFVAL { ''b }
			::= { msanSystemLogsUpload 10 }

		
		-- 1.3.6.1.4.1.1332.1.1.5.3.1.11.11
		msanSystemLogsUploadFileName OBJECT-TYPE
			SYNTAX DisplayString
			MAX-ACCESS read-write
			STATUS current
			DESCRIPTION
				"The system logs file name"
			DEFVAL { ''b }
			::= { msanSystemLogsUpload 11 }

		
		-- 1.3.6.1.4.1.1332.1.1.5.3.1.12
		msanSystemAutoSaveConfig OBJECT IDENTIFIER ::= { msanSystem 12 }

		
		-- 1.3.6.1.4.1.1332.1.1.5.3.1.12.1
		msanSystemAutoSaveConfigStatus OBJECT-TYPE
			SYNTAX INTEGER
				{
				active(1),
				inactive(2)
				}
			MAX-ACCESS read-only
			STATUS current
			DESCRIPTION
				"Description."
			::= { msanSystemAutoSaveConfig 1 }

		
		-- 1.3.6.1.4.1.1332.1.1.5.3.1.12.2
		msanSystemAutoSaveConfigMaxTimeout OBJECT-TYPE
			SYNTAX Integer32
			MAX-ACCESS read-only
			STATUS current
			DESCRIPTION
				"Initial (max) number of seconds until timer for automatic saveconfig elapses."
			::= { msanSystemAutoSaveConfig 2 }

		
		-- 1.3.6.1.4.1.1332.1.1.5.3.1.12.3
		msanSystemAutoSaveConfigCurrTimeout OBJECT-TYPE
			SYNTAX Integer32
			MAX-ACCESS read-only
			STATUS current
			DESCRIPTION
				"Current number of seconds until timer for automatic saveconfig elapses."
			::= { msanSystemAutoSaveConfig 3 }

		
		-- 1.3.6.1.4.1.1332.1.1.5.3.1.13
		msanConfFileType OBJECT-TYPE
			SYNTAX INTEGER
				{
				automatic(1),
				manual(2),
				notExists(3),
				manualMns(4)
				}
			MAX-ACCESS read-only
			STATUS current
			DESCRIPTION
				"Last saved configuration status – denotes whether current configuration file 
				has been built by automatic or manual cli/snmp or manual mns procedure. "
			::= { msanSystem 13 }

		
		-- 1.3.6.1.4.1.1332.1.1.5.3.1.14
		msanHttpServer OBJECT-TYPE
			SYNTAX INTEGER
				{
				enable(1),
				disable(2)
				}
			MAX-ACCESS read-write
			STATUS current
			DESCRIPTION
				"HTTP server activity."
			DEFVAL { disable }
			::= { msanSystem 14 }

		
		-- 1.3.6.1.4.1.1332.1.1.5.3.3
		msanProfiles OBJECT IDENTIFIER ::= { msanAdditionalConf 3 }

		
		-- 1.3.6.1.4.1.1332.1.1.5.3.3.1
		msanVDSLProfileTable OBJECT-TYPE
			SYNTAX SEQUENCE OF MsanVDSLProfileEntry
			MAX-ACCESS not-accessible
			STATUS current
			DESCRIPTION
				"Description."
			::= { msanProfiles 1 }

		
		-- 1.3.6.1.4.1.1332.1.1.5.3.3.1.1
		msanVDSLProfileEntry OBJECT-TYPE
			SYNTAX MsanVDSLProfileEntry
			MAX-ACCESS not-accessible
			STATUS current
			DESCRIPTION
				"Description."
			INDEX { vdslLineConfProfileName }
			::= { msanVDSLProfileTable 1 }

		
		MsanVDSLProfileEntry ::=
			SEQUENCE { 
				msanVDSLProfileType
					INTEGER,
				msanVDSL2LineProfile
					INTEGER
			 }

		-- 1.3.6.1.4.1.1332.1.1.5.3.3.1.1.1
		msanVDSLProfileType OBJECT-TYPE
			SYNTAX INTEGER
				{
				other(1),
				default(2),
				local(3),
				global(4)
				}
			MAX-ACCESS read-write
			STATUS current
			DESCRIPTION
				"Profile type:
				- other ~ none of the following
				- defaut ~ default profile
				- local ~ local configured profile type
				- global ~ global configured profile type"
			::= { msanVDSLProfileEntry 1 }

		
		-- 1.3.6.1.4.1.1332.1.1.5.3.3.1.1.2
		msanVDSL2LineProfile OBJECT-TYPE
			SYNTAX INTEGER
				{
				vdsl2profile8c(1),
				vdsl2profile8d(2),
				vdsl2profile12a(3),
				vdsl2profile12b(4),
				vdsl2profile17a(5)
				}
			MAX-ACCESS read-write
			STATUS current
			DESCRIPTION
				"VDSL2 profile"
			::= { msanVDSLProfileEntry 2 }

		
		-- 1.3.6.1.4.1.1332.1.1.5.3.3.2
		msanServiceProfile OBJECT IDENTIFIER ::= { msanProfiles 2 }

		
		-- 1.3.6.1.4.1.1332.1.1.5.3.3.2.1
		msanServiceProfileTable OBJECT-TYPE
			SYNTAX SEQUENCE OF MsanServiceProfileEntry
			MAX-ACCESS not-accessible
			STATUS current
			DESCRIPTION
				"Service Profile table "
			::= { msanServiceProfile 1 }

		
		-- 1.3.6.1.4.1.1332.1.1.5.3.3.2.1.1
		msanServiceProfileEntry OBJECT-TYPE
			SYNTAX MsanServiceProfileEntry
			MAX-ACCESS not-accessible
			STATUS current
			DESCRIPTION
				"Service Profile table entry."
			INDEX { msanServiceProfileName }
			::= { msanServiceProfileTable 1 }

		
		MsanServiceProfileEntry ::=
			SEQUENCE { 
				msanServiceProfileName
					DisplayString,
				msanServiceProfileProtection
					INTEGER,
				msanServiceProfileStatus
					INTEGER,
				msanServiceProfileServiceFlowProfileName
					DisplayString,
				msanServiceProfileMulticastProfileName
					DisplayString,
				msanServiceProfileVlanProfileName
					DisplayString,
				msanServiceProfileL2cpProfileName
					DisplayString,
				msanServiceProfileSecurityProfileName
					DisplayString,
				msanServiceProfileAtmVpi
					Integer32,
				msanServiceProfileAtmVci
					Integer32,
				msanServiceProfileDhcpRa
					INTEGER,
				msanServiceProfileDhcpRaTrustClients
					INTEGER,
				msanServiceProfileDhcpRaOpt82UnicastExtension
					INTEGER,
				msanServiceProfileDhcpRaOpt82Insert
					INTEGER,
				msanServiceProfileDhcpRaRemoteId
					OCTET STRING,
				msanServiceProfileDhcpRaRateLimit
					Unsigned32,
				msanServiceProfilePppoeIA
					INTEGER,
				msanServiceProfilePppoeIARateLimit
					Unsigned32,
				msanServiceProfileDescription
					DisplayString,
				msanServiceProfileRowStatus
					RowStatus,
				msanServiceProfileDhcpRaInterfaceIdStandard
					INTEGER,
				msanServiceProfileDhcpv6Ra
					INTEGER,
				msanServiceProfileDhcpv6RaTrustClients
					INTEGER,
				msanServiceProfileDhcpv6RaInterfaceIdStandard
					INTEGER,
				msanServiceProfileDhcpv6RaRemoteId
					OCTET STRING,
				msanServiceProfileDhcpv6RaRemoteIdEnterpriseNum
					INTEGER,
				msanServiceProfileDhcpRaCircuitIdType
					INTEGER,
				msanServiceProfilePPPoeIACircuitIdType
					INTEGER,
				msanServiceProfileDhcpRaCircuitIdCustomFormat
					DisplayString,
				msanServiceProfileDhcpRaRemoteIdCustomFormat
					DisplayString,
				msanServiceProfilePPPoeIACircuitIdCustomFormat
					DisplayString,
				msanServiceProfilePPPoeIARemoteIdCustomFormat
					DisplayString,
				msanServiceProfileDhcpv6RaInterfaceIdType
					INTEGER,
				msanServiceProfileDhcpv6RaInterfaceIdCustomFormat
					DisplayString,
				msanServiceProfileDhcpv6RaRemoteIdCustomFormat
					DisplayString,
				msanServiceProfileOnuFlowProfileName
					DisplayString,
				msanServiceProfileOnuVlanProfileName
					DisplayString,
				msanServiceProfileOnuMulticastProfileName
					DisplayString,
				msanServiceProfileOnuTcontProfileName
					DisplayString,
				msanServiceProfileOnuVirtGemPortId
					Integer32,
				msanServiceProfileOnuTpType
					INTEGER,
				msanServiceProfileOnuTpUniBitMap
					OCTET STRING,
				msanServiceProfileUsage
					INTEGER,
				msanServiceProfileOnuAcsServerProfileName
					DisplayString,
				msanServiceProfileOnuAcsServerVeipId
					INTEGER
			 }

		-- 1.3.6.1.4.1.1332.1.1.5.3.3.2.1.1.1
		msanServiceProfileName OBJECT-TYPE
			SYNTAX DisplayString (SIZE (1..64))
			MAX-ACCESS not-accessible
			STATUS current
			DESCRIPTION
				"Name for service profile."
			::= { msanServiceProfileEntry 1 }

		
		-- 1.3.6.1.4.1.1332.1.1.5.3.3.2.1.1.2
		msanServiceProfileProtection OBJECT-TYPE
			SYNTAX INTEGER
				{
				unprotected(0),
				protected(1)
				}
			MAX-ACCESS read-write
			STATUS obsolete
			DESCRIPTION
				"If protection flag is set to protected (1), other profile values cannot be edited.
				
				Protection flag is always  protected (1) and it can't be changed if  profile is assigned as dynamic:
				msanServiceProfileStatus = dynamic(2)"
			DEFVAL { unprotected }
			::= { msanServiceProfileEntry 2 }

		
		-- 1.3.6.1.4.1.1332.1.1.5.3.3.2.1.1.3
		msanServiceProfileStatus OBJECT-TYPE
			SYNTAX INTEGER
				{
				static(1),
				dynamic(2)
				}
			MAX-ACCESS read-only
			STATUS obsolete
			DESCRIPTION
				"Profile status. 
				If status is dynamic, profile values can't be edited."
			::= { msanServiceProfileEntry 3 }

		
		-- 1.3.6.1.4.1.1332.1.1.5.3.3.2.1.1.4
		msanServiceProfileServiceFlowProfileName OBJECT-TYPE
			SYNTAX DisplayString
			MAX-ACCESS read-write
			STATUS current
			DESCRIPTION
				"Index of used service flow profile (this profile must be set before), which indicates
				row in msanServiceFlowProfileTable.
				Empty string indicates that parameter has not been defined."
			::= { msanServiceProfileEntry 4 }

		
		-- 1.3.6.1.4.1.1332.1.1.5.3.3.2.1.1.5
		msanServiceProfileMulticastProfileName OBJECT-TYPE
			SYNTAX DisplayString
			MAX-ACCESS read-write
			STATUS current
			DESCRIPTION
				"Index of used multicast profile (this profile must be set before), which indicates
				row in msanMulticastProfileTable.
				Empty string indicates that parameter has not been defined."
			::= { msanServiceProfileEntry 5 }

		
		-- 1.3.6.1.4.1.1332.1.1.5.3.3.2.1.1.6
		msanServiceProfileVlanProfileName OBJECT-TYPE
			SYNTAX DisplayString
			MAX-ACCESS read-write
			STATUS current
			DESCRIPTION
				"Index of used vlan profile (this profile must be set before), which indicates
				row in msanVlanProfileTable.
				Empty string indicates that parameter has not been defined."
			::= { msanServiceProfileEntry 6 }

		
		-- 1.3.6.1.4.1.1332.1.1.5.3.3.2.1.1.7
		msanServiceProfileL2cpProfileName OBJECT-TYPE
			SYNTAX DisplayString
			MAX-ACCESS read-write
			STATUS current
			DESCRIPTION
				"Index of used L2CP profile (this profile must be set before), which indicates
				row in msanL2cpProfileTable.
				Empty string indicates that parameter has not been defined."
			::= { msanServiceProfileEntry 7 }

		
		-- 1.3.6.1.4.1.1332.1.1.5.3.3.2.1.1.8
		msanServiceProfileSecurityProfileName OBJECT-TYPE
			SYNTAX DisplayString
			MAX-ACCESS read-write
			STATUS current
			DESCRIPTION
				"Index of used security profile (this profile must be set before), which indicates
				row in msanSecurityProfileTable.
				Empty string indicates that parameter has not been defined."
			::= { msanServiceProfileEntry 8 }

		
		-- 1.3.6.1.4.1.1332.1.1.5.3.3.2.1.1.9
		msanServiceProfileAtmVpi OBJECT-TYPE
			SYNTAX Integer32 (-1..255)
			MAX-ACCESS read-write
			STATUS current
			DESCRIPTION
				"Virtual Path Identifier.
				A value of -1 indicates that parameter has not been defined."
			DEFVAL { -1 }
			::= { msanServiceProfileEntry 9 }

		
		-- 1.3.6.1.4.1.1332.1.1.5.3.3.2.1.1.10
		msanServiceProfileAtmVci OBJECT-TYPE
			SYNTAX Integer32 (-1 | 32..65535)
			MAX-ACCESS read-write
			STATUS current
			DESCRIPTION
				"Virtual Channel Identifier.
				A value of -1 indicates that parameter has not been defined."
			DEFVAL { -1 }
			::= { msanServiceProfileEntry 10 }

		
		-- 1.3.6.1.4.1.1332.1.1.5.3.3.2.1.1.11
		msanServiceProfileDhcpRa OBJECT-TYPE
			SYNTAX INTEGER
				{
				disable(0),
				allowClients(1),
				allowServers(2),
				allowAll(3)
				}
			MAX-ACCESS read-write
			STATUS current
			DESCRIPTION
				"Dynamic Host Configuration Protocol Relay Agent.
				DHCP RA and PPPoE IA can not be included simultaneously."
			DEFVAL { disable }
			::= { msanServiceProfileEntry 11 }

		
		-- 1.3.6.1.4.1.1332.1.1.5.3.3.2.1.1.12
		msanServiceProfileDhcpRaTrustClients OBJECT-TYPE
			SYNTAX INTEGER
				{
				notTrust(0),
				trust(1)
				}
			MAX-ACCESS read-write
			STATUS current
			DESCRIPTION
				"DHCP RA Trust Clients.
				Effective only if DHCP-RA is in either allow-all or allow-client mode."
			DEFVAL { notTrust }
			::= { msanServiceProfileEntry 12 }

		
		-- 1.3.6.1.4.1.1332.1.1.5.3.3.2.1.1.13
		msanServiceProfileDhcpRaOpt82UnicastExtension OBJECT-TYPE
			SYNTAX INTEGER
				{
				notUsed(0),
				used(1)
				}
			MAX-ACCESS read-write
			STATUS current
			DESCRIPTION
				"DHCP RA option82 unicast extension.
				Effective only if DHCP-RA is in either allow-all or allow-client mode."
			DEFVAL { notUsed }
			::= { msanServiceProfileEntry 13 }

		
		-- 1.3.6.1.4.1.1332.1.1.5.3.3.2.1.1.14
		msanServiceProfileDhcpRaOpt82Insert OBJECT-TYPE
			SYNTAX INTEGER
				{
				notInsert(0),
				insert(1)
				}
			MAX-ACCESS read-write
			STATUS current
			DESCRIPTION
				"DHCP Relay Agent Insert Option 82.
				Effective only if DHCP-RA is in either allow-all or allow-client mode."
			DEFVAL { notInsert }
			::= { msanServiceProfileEntry 14 }

		
		-- 1.3.6.1.4.1.1332.1.1.5.3.3.2.1.1.15
		msanServiceProfileDhcpRaRemoteId OBJECT-TYPE
			SYNTAX OCTET STRING (SIZE (0..63))
			MAX-ACCESS read-write
			STATUS deprecated
			DESCRIPTION
				"DHCP Relay Agent Remote Identification.
				Effective only if DHCP-RA is in either allow-all or allow-client mode."
			DEFVAL { "" }
			::= { msanServiceProfileEntry 15 }

		
		-- 1.3.6.1.4.1.1332.1.1.5.3.3.2.1.1.16
		msanServiceProfileDhcpRaRateLimit OBJECT-TYPE
			SYNTAX Unsigned32 (0..1000)
			MAX-ACCESS read-write
			STATUS current
			DESCRIPTION
				"Max rate for DHCP Relay Agent.
				"
			DEFVAL { 5 }
			::= { msanServiceProfileEntry 16 }

		
		-- 1.3.6.1.4.1.1332.1.1.5.3.3.2.1.1.17
		msanServiceProfilePppoeIA OBJECT-TYPE
			SYNTAX INTEGER
				{
				disable(0),
				enable(1)
				}
			MAX-ACCESS read-write
			STATUS current
			DESCRIPTION
				"Point-to-Point Protocol over Ethernet Intermediate Agent.
				DHCP RA and PPPoE IA can not be included simultaneously."
			DEFVAL { disable }
			::= { msanServiceProfileEntry 17 }

		
		-- 1.3.6.1.4.1.1332.1.1.5.3.3.2.1.1.18
		msanServiceProfilePppoeIARateLimit OBJECT-TYPE
			SYNTAX Unsigned32 (0..1000)
			MAX-ACCESS read-write
			STATUS current
			DESCRIPTION
				"Max rate for PPPoE IA.
				"
			DEFVAL { 5 }
			::= { msanServiceProfileEntry 18 }

		
		-- 1.3.6.1.4.1.1332.1.1.5.3.3.2.1.1.19
		msanServiceProfileDescription OBJECT-TYPE
			SYNTAX DisplayString (SIZE (0..255))
			MAX-ACCESS read-write
			STATUS current
			DESCRIPTION
				"Attribute specifies text which describes the associated object."
			::= { msanServiceProfileEntry 19 }

		
		-- 1.3.6.1.4.1.1332.1.1.5.3.3.2.1.1.20
		msanServiceProfileRowStatus OBJECT-TYPE
			SYNTAX RowStatus
			MAX-ACCESS read-create
			STATUS current
			DESCRIPTION
				"The row status object controls the creation/deletion of rows in this table. 
				Its semantics are the same as those for the RowStatus textual convention specified for SNMPv2.
				For row creation use createAndWait(5).
				Value active(1) will activate and value destroy(6) will remove this entry.
				Other values are currently not supported.
				
				Row can be activated only if msanServiceProfileServiceFlowProfileName is specified."
			::= { msanServiceProfileEntry 20 }

		
		-- 1.3.6.1.4.1.1332.1.1.5.3.3.2.1.1.21
		msanServiceProfileDhcpRaInterfaceIdStandard OBJECT-TYPE
			SYNTAX INTEGER
				{
				enable(1),
				disable(2)
				}
			MAX-ACCESS read-write
			STATUS deprecated
			DESCRIPTION
				"DHCP RA Standard Interface Id (Circuit Id) syntax mode."
			DEFVAL { disable }
			::= { msanServiceProfileEntry 21 }

		
		-- 1.3.6.1.4.1.1332.1.1.5.3.3.2.1.1.22
		msanServiceProfileDhcpv6Ra OBJECT-TYPE
			SYNTAX INTEGER
				{
				disable(0),
				allowClients(1)
				}
			MAX-ACCESS read-write
			STATUS current
			DESCRIPTION
				"State of DHCPv6 Relay Agent on the port."
			DEFVAL { enable }
			::= { msanServiceProfileEntry 22 }

		
		-- 1.3.6.1.4.1.1332.1.1.5.3.3.2.1.1.23
		msanServiceProfileDhcpv6RaTrustClients OBJECT-TYPE
			SYNTAX INTEGER
				{
				notTrust(0),
				trust(1)
				}
			MAX-ACCESS read-write
			STATUS current
			DESCRIPTION
				"DHCPv6 Relay Agent Trust Clients.
				Effective only if DHCPv6-RA is in allow-client mode."
			DEFVAL { notTrust }
			::= { msanServiceProfileEntry 23 }

		
		-- 1.3.6.1.4.1.1332.1.1.5.3.3.2.1.1.24
		msanServiceProfileDhcpv6RaInterfaceIdStandard OBJECT-TYPE
			SYNTAX INTEGER
				{
				enable(1),
				disable(2)
				}
			MAX-ACCESS read-write
			STATUS deprecated
			DESCRIPTION
				"DHCPv6 RA Standard Interface Id syntax mode."
			DEFVAL { enable }
			::= { msanServiceProfileEntry 24 }

		
		-- 1.3.6.1.4.1.1332.1.1.5.3.3.2.1.1.25
		msanServiceProfileDhcpv6RaRemoteId OBJECT-TYPE
			SYNTAX OCTET STRING
			MAX-ACCESS read-write
			STATUS deprecated
			DESCRIPTION
				"DHCPv6 Remote Id value.
				"
			DEFVAL { "" }
			::= { msanServiceProfileEntry 25 }

		
		-- 1.3.6.1.4.1.1332.1.1.5.3.3.2.1.1.26
		msanServiceProfileDhcpv6RaRemoteIdEnterpriseNum OBJECT-TYPE
			SYNTAX INTEGER (1..999999)
			MAX-ACCESS read-write
			STATUS current
			DESCRIPTION
				"DHCPv6 Remote Id enterprise number.
				"
			DEFVAL { 1332 }
			::= { msanServiceProfileEntry 26 }

		
		-- 1.3.6.1.4.1.1332.1.1.5.3.3.2.1.1.27
		msanServiceProfileDhcpRaCircuitIdType OBJECT-TYPE
			SYNTAX INTEGER
				{
				iskratel(1),
				standard(2),
				atm(3),
				custom(4)
				}
			MAX-ACCESS read-write
			STATUS current
			DESCRIPTION
				"DHCP Circuit Id syntax mode."
			DEFVAL { iskratel }
			::= { msanServiceProfileEntry 27 }

		
		-- 1.3.6.1.4.1.1332.1.1.5.3.3.2.1.1.28
		msanServiceProfilePPPoeIACircuitIdType OBJECT-TYPE
			SYNTAX INTEGER
				{
				iskratel(1),
				atm(3),
				custom(4)
				}
			MAX-ACCESS read-write
			STATUS current
			DESCRIPTION
				"PPPoE Circuit Id syntax mode per port."
			::= { msanServiceProfileEntry 28 }

		
		-- 1.3.6.1.4.1.1332.1.1.5.3.3.2.1.1.29
		msanServiceProfileDhcpRaCircuitIdCustomFormat OBJECT-TYPE
			SYNTAX DisplayString
			MAX-ACCESS read-write
			STATUS current
			DESCRIPTION
				"DHCP Circuit Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanServiceProfileEntry 29 }

		
		-- 1.3.6.1.4.1.1332.1.1.5.3.3.2.1.1.30
		msanServiceProfileDhcpRaRemoteIdCustomFormat OBJECT-TYPE
			SYNTAX DisplayString
			MAX-ACCESS read-write
			STATUS current
			DESCRIPTION
				"DHCP Remote Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanServiceProfileEntry 30 }

		
		-- 1.3.6.1.4.1.1332.1.1.5.3.3.2.1.1.31
		msanServiceProfilePPPoeIACircuitIdCustomFormat OBJECT-TYPE
			SYNTAX DisplayString
			MAX-ACCESS read-write
			STATUS current
			DESCRIPTION
				"PPPoE Circuit Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanServiceProfileEntry 31 }

		
		-- 1.3.6.1.4.1.1332.1.1.5.3.3.2.1.1.32
		msanServiceProfilePPPoeIARemoteIdCustomFormat OBJECT-TYPE
			SYNTAX DisplayString
			MAX-ACCESS read-write
			STATUS current
			DESCRIPTION
				"PPPoE Remote Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanServiceProfileEntry 32 }

		
		-- 1.3.6.1.4.1.1332.1.1.5.3.3.2.1.1.33
		msanServiceProfileDhcpv6RaInterfaceIdType OBJECT-TYPE
			SYNTAX INTEGER
				{
				iskratel(1),
				standard(2),
				custom(3)
				}
			MAX-ACCESS read-write
			STATUS current
			DESCRIPTION
				"DHCPv6  Interface Id syntax mode."
			DEFVAL { standard }
			::= { msanServiceProfileEntry 33 }

		
		-- 1.3.6.1.4.1.1332.1.1.5.3.3.2.1.1.34
		msanServiceProfileDhcpv6RaInterfaceIdCustomFormat OBJECT-TYPE
			SYNTAX DisplayString
			MAX-ACCESS read-write
			STATUS current
			DESCRIPTION
				"DHCPv6 Interface Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanServiceProfileEntry 34 }

		
		-- 1.3.6.1.4.1.1332.1.1.5.3.3.2.1.1.35
		msanServiceProfileDhcpv6RaRemoteIdCustomFormat OBJECT-TYPE
			SYNTAX DisplayString
			MAX-ACCESS read-write
			STATUS current
			DESCRIPTION
				"DHCPv6 Remote Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanServiceProfileEntry 35 }

		
		-- 1.3.6.1.4.1.1332.1.1.5.3.3.2.1.1.50
		msanServiceProfileOnuFlowProfileName OBJECT-TYPE
			SYNTAX DisplayString
			MAX-ACCESS read-write
			STATUS current
			DESCRIPTION
				"Index of used ONU Flow profile (this profile must be set before), which indicates
				row in msanOnuFlowProfileTable.
				Empty string indicates that parameter has not been defined."
			::= { msanServiceProfileEntry 50 }

		
		-- 1.3.6.1.4.1.1332.1.1.5.3.3.2.1.1.51
		msanServiceProfileOnuVlanProfileName OBJECT-TYPE
			SYNTAX DisplayString
			MAX-ACCESS read-write
			STATUS current
			DESCRIPTION
				"Index of used ONU Vlan profile (this profile must be set before), which indicates
				row in msanOnuVlanProfileTable.
				Empty string indicates that parameter has not been defined."
			::= { msanServiceProfileEntry 51 }

		
		-- 1.3.6.1.4.1.1332.1.1.5.3.3.2.1.1.52
		msanServiceProfileOnuMulticastProfileName OBJECT-TYPE
			SYNTAX DisplayString
			MAX-ACCESS read-write
			STATUS current
			DESCRIPTION
				"Index of used ONU Multicast profile (this profile must be set before), which indicates
				row in msanOnuMulticastProfileTable.
				Empty string indicates that parameter has not been defined."
			::= { msanServiceProfileEntry 52 }

		
		-- 1.3.6.1.4.1.1332.1.1.5.3.3.2.1.1.53
		msanServiceProfileOnuTcontProfileName OBJECT-TYPE
			SYNTAX DisplayString
			MAX-ACCESS read-write
			STATUS current
			DESCRIPTION
				"Index of used ONU T-CONT profile (this profile must be set before), which indicates
				row in msanOnuTcontProfileTable.
				Empty string indicates that parameter has not been defined."
			::= { msanServiceProfileEntry 53 }

		
		-- 1.3.6.1.4.1.1332.1.1.5.3.3.2.1.1.54
		msanServiceProfileOnuVirtGemPortId OBJECT-TYPE
			SYNTAX Integer32 (1..32)
			MAX-ACCESS read-write
			STATUS current
			DESCRIPTION
				"Virtual GEM Port ID."
			DEFVAL { 1 }
			::= { msanServiceProfileEntry 54 }

		
		-- 1.3.6.1.4.1.1332.1.1.5.3.3.2.1.1.55
		msanServiceProfileOnuTpType OBJECT-TYPE
			SYNTAX INTEGER
				{
				veip(1),
				ipHost(2),
				ethernetUni(3)
				}
			MAX-ACCESS read-write
			STATUS current
			DESCRIPTION
				"ONU termination point type."
			::= { msanServiceProfileEntry 55 }

		
		-- 1.3.6.1.4.1.1332.1.1.5.3.3.2.1.1.56
		msanServiceProfileOnuTpUniBitMap OBJECT-TYPE
			SYNTAX OCTET STRING (SIZE (0..2))
			MAX-ACCESS read-write
			STATUS current
			DESCRIPTION
				"ONU Ethernet UNI ports bitmap (max 16 ports). This parameter can be set only 
				when msanServiceProfileOnuTpType has value ethernetUni(3)."
			::= { msanServiceProfileEntry 56 }

		
		-- 1.3.6.1.4.1.1332.1.1.5.3.3.2.1.1.57
		msanServiceProfileUsage OBJECT-TYPE
			SYNTAX INTEGER
				{
				attached(1),
				notAttached(2)
				}
			MAX-ACCESS read-only
			STATUS current
			DESCRIPTION
				"Profile usage.
				If profile is attached,  profile values can't be edited."
			::= { msanServiceProfileEntry 57 }

		
		-- 1.3.6.1.4.1.1332.1.1.5.3.3.2.1.1.58
		msanServiceProfileOnuAcsServerProfileName OBJECT-TYPE
			SYNTAX DisplayString
			MAX-ACCESS read-write
			STATUS current
			DESCRIPTION
				"Index of used ONU ACS Server profile (this profile must be set before), which indicates
				row in msanOnuAcsServerProfileTable.
				Empty string indicates that parameter has not been defined."
			::= { msanServiceProfileEntry 58 }

		
		-- 1.3.6.1.4.1.1332.1.1.5.3.3.2.1.1.59
		msanServiceProfileOnuAcsServerVeipId OBJECT-TYPE
			SYNTAX INTEGER
			MAX-ACCESS read-write
			STATUS obsolete
			DESCRIPTION
				"ONU Veip ID which is used for ACS Server configuration defined in 
				relevant msanServiceProfileOnuAcsServerProfileTable instance."
			::= { msanServiceProfileEntry 59 }

		
		-- 1.3.6.1.4.1.1332.1.1.5.3.3.2.2
		msanServicePortProfileTable OBJECT-TYPE
			SYNTAX SEQUENCE OF MsanServicePortProfileEntry
			MAX-ACCESS not-accessible
			STATUS current
			DESCRIPTION
				"A connection between service profiles and device ports"
			::= { msanServiceProfile 2 }

		
		-- 1.3.6.1.4.1.1332.1.1.5.3.3.2.2.1
		msanServicePortProfileEntry OBJECT-TYPE
			SYNTAX MsanServicePortProfileEntry
			MAX-ACCESS not-accessible
			STATUS current
			DESCRIPTION
				"Service Profile Port table entry.
				
				In case of GPON access blade, ifIndex for ONU interface (ifDescr=0/x/y) is calculated with formula:
				ifIndex=max_olt_port_number(8 or 16)+(x-1)*128+y   "
			INDEX { ifIndex, msanServiceProfileName }
			::= { msanServicePortProfileTable 1 }

		
		MsanServicePortProfileEntry ::=
			SEQUENCE { 
				msanServicePortProfileRowStatus
					RowStatus,
				msanServicePortProfileOnuTpUniBitMap
					OCTET STRING,
				msanServicePortDataCVid
					Integer32,
				msanServicePortDataSVid
					Integer32
			 }

		-- 1.3.6.1.4.1.1332.1.1.5.3.3.2.2.1.1
		msanServicePortProfileRowStatus OBJECT-TYPE
			SYNTAX RowStatus
			MAX-ACCESS read-create
			STATUS current
			DESCRIPTION
				"The row status object controls the creation/deletion of rows in this table. 
				Its semantics are the same as those for the RowStatus textual convention specified for SNMPv2.
				For row creation use createAndGo(4) or createAndWait(5).
				Setting this object to destroy(6) will remove this entry.
				When row is created you can't change values of parameters in this row.
				Read values: active(1).
				Other values are currently not supported.
				
				In case of GPON access blade, ifIndex for ONU interface (ifDescr=0/x/y) is calculated with formula:
				ifIndex=max_olt_port_number(8 or 16)+(x-1)*128+y   "
			::= { msanServicePortProfileEntry 1 }

		
		-- 1.3.6.1.4.1.1332.1.1.5.3.3.2.2.1.2
		msanServicePortProfileOnuTpUniBitMap OBJECT-TYPE
			SYNTAX OCTET STRING (SIZE (0..2))
			MAX-ACCESS read-create
			STATUS current
			DESCRIPTION
				"ONU Ethernet UNI ports bitmap (max 16 ports). "
			::= { msanServicePortProfileEntry 2 }

		
		-- 1.3.6.1.4.1.1332.1.1.5.3.3.2.2.1.3
		msanServicePortDataCVid OBJECT-TYPE
			SYNTAX Integer32
			MAX-ACCESS read-write
			STATUS current
			DESCRIPTION
				"C-VLAN Id.
				A value of -1 indicates that parameter has not been defined."
			DEFVAL { -1 }
			::= { msanServicePortProfileEntry 3 }

		
		-- 1.3.6.1.4.1.1332.1.1.5.3.3.2.2.1.4
		msanServicePortDataSVid OBJECT-TYPE
			SYNTAX Integer32
			MAX-ACCESS read-write
			STATUS current
			DESCRIPTION
				"S-VLAN Id.
				A value of -1 indicates that parameter has not been defined."
			DEFVAL { -1 }
			::= { msanServicePortProfileEntry 4 }

		
		-- 1.3.6.1.4.1.1332.1.1.5.3.3.3
		msanServiceFlowProfile OBJECT IDENTIFIER ::= { msanProfiles 3 }

		
		-- 1.3.6.1.4.1.1332.1.1.5.3.3.3.1
		msanServiceFlowProfileTable OBJECT-TYPE
			SYNTAX SEQUENCE OF MsanServiceFlowProfileEntry
			MAX-ACCESS not-accessible
			STATUS current
			DESCRIPTION
				"Service Flow Profile table "
			::= { msanServiceFlowProfile 1 }

		
		-- 1.3.6.1.4.1.1332.1.1.5.3.3.3.1.1
		msanServiceFlowProfileEntry OBJECT-TYPE
			SYNTAX MsanServiceFlowProfileEntry
			MAX-ACCESS not-accessible
			STATUS current
			DESCRIPTION
				"Service Flow Profile table entry."
			INDEX { msanServiceFlowProfileName }
			::= { msanServiceFlowProfileTable 1 }

		
		MsanServiceFlowProfileEntry ::=
			SEQUENCE { 
				msanServiceFlowProfileName
					DisplayString,
				msanServiceFlowProfileProtection
					INTEGER,
				msanServiceFlowProfileStatus
					INTEGER,
				msanServiceFlowProfileMatchUsAny
					INTEGER,
				msanServiceFlowProfileMatchUsMacDestAddr
					MacAddress,
				msanServiceFlowProfileMatchUsMacDestMask
					MacAddress,
				msanServiceFlowProfileMatchUsMacSrcAddr
					MacAddress,
				msanServiceFlowProfileMatchUsMacSrcMask
					MacAddress,
				msanServiceFlowProfileMatchUsCPcp
					Integer32,
				msanServiceFlowProfileMatchUsSPcp
					Integer32,
				msanServiceFlowProfileMatchUsVlanProfile
					INTEGER,
				msanServiceFlowProfileMatchUsCVlanIdRange
					OCTET STRING,
				msanServiceFlowProfileMatchUsSVlanIdRange
					OCTET STRING,
				msanServiceFlowProfileMatchUsEthertype
					Integer32,
				msanServiceFlowProfileMatchUsIpProtocol
					Integer32,
				msanServiceFlowProfileMatchUsIpSrcAddr
					IpAddress,
				msanServiceFlowProfileMatchUsIpSrcMask
					IpAddress,
				msanServiceFlowProfileMatchUsIpDestAddr
					IpAddress,
				msanServiceFlowProfileMatchUsIpDestMask
					IpAddress,
				msanServiceFlowProfileMatchUsIpDscp
					Integer32,
				msanServiceFlowProfileMatchUsIpCsc
					Integer32,
				msanServiceFlowProfileMatchUsIpDropPrecedence
					INTEGER,
				msanServiceFlowProfileMatchUsTcpSrcPort
					Integer32,
				msanServiceFlowProfileMatchUsTcpDestPort
					Integer32,
				msanServiceFlowProfileMatchUsUdpSrcPort
					Integer32,
				msanServiceFlowProfileMatchUsUdpDstPort
					Integer32,
				msanServiceFlowProfileMatchDsAny
					INTEGER,
				msanServiceFlowProfileMatchDsMacDestAddr
					MacAddress,
				msanServiceFlowProfileMatchDsMacDestMask
					MacAddress,
				msanServiceFlowProfileMatchDsMacSrcAddr
					MacAddress,
				msanServiceFlowProfileMatchDsMacSrcMask
					MacAddress,
				msanServiceFlowProfileMatchDsCPcp
					Integer32,
				msanServiceFlowProfileMatchDsSPcp
					Integer32,
				msanServiceFlowProfileMatchDsVlanProfile
					INTEGER,
				msanServiceFlowProfileMatchDsCVlanIdRange
					OCTET STRING,
				msanServiceFlowProfileMatchDsSVlanIdRange
					OCTET STRING,
				msanServiceFlowProfileMatchDsEthertype
					Integer32,
				msanServiceFlowProfileMatchDsIpProtocol
					Integer32,
				msanServiceFlowProfileMatchDsIpSrcAddr
					IpAddress,
				msanServiceFlowProfileMatchDsIpSrcMask
					IpAddress,
				msanServiceFlowProfileMatchDsIpDestAddr
					IpAddress,
				msanServiceFlowProfileMatchDsIpDestMask
					IpAddress,
				msanServiceFlowProfileMatchDsIpDscp
					Integer32,
				msanServiceFlowProfileMatchDsIpCsc
					Integer32,
				msanServiceFlowProfileMatchDsIpDropPrecedence
					INTEGER,
				msanServiceFlowProfileMatchDsTcpSrcPort
					Integer32,
				msanServiceFlowProfileMatchDsTcpDestPort
					Integer32,
				msanServiceFlowProfileMatchDsUdpSrcPort
					Integer32,
				msanServiceFlowProfileMatchDsUdpDstPort
					Integer32,
				msanServiceFlowProfileUsCdr
					Integer32,
				msanServiceFlowProfileUsCdrBurstSize
					Integer32,
				msanServiceFlowProfileUsPdr
					Integer32,
				msanServiceFlowProfileUsPdrBurstSize
					Integer32,
				msanServiceFlowProfileUsMarkPcp
					INTEGER,
				msanServiceFlowProfileUsMarkPcpValue
					INTEGER,
				msanServiceFlowProfileUsMarkDscp
					INTEGER,
				msanServiceFlowProfileUsMarkDscpValue
					INTEGER,
				msanServiceFlowProfileDsCdr
					Integer32,
				msanServiceFlowProfileDsCdrBurstSize
					Integer32,
				msanServiceFlowProfileDsPdr
					Integer32,
				msanServiceFlowProfileDsPdrBurstSize
					Integer32,
				msanServiceFlowProfileDsMarkPcp
					INTEGER,
				msanServiceFlowProfileDsMarkPcpValue
					INTEGER,
				msanServiceFlowProfileDsMarkDscp
					INTEGER,
				msanServiceFlowProfileDsMarkDscpValue
					INTEGER,
				msanServiceFlowProfileDsQueuingPriority
					INTEGER,
				msanServiceFlowProfileDsSchedulingMode
					INTEGER,
				msanServiceFlowProfileDescription
					DisplayString,
				msanServiceFlowProfileRowStatus
					RowStatus,
				msanServiceFlowProfileMatchUsIpv6SrcAddr
					InetAddressIPv6,
				msanServiceFlowProfileMatchUsIpv6SrcAddrMaskLen
					Integer32,
				msanServiceFlowProfileMatchUsIpv6DestAddr
					InetAddressIPv6,
				msanServiceFlowProfileMatchUsIpv6DestAddrMaskLen
					Integer32,
				msanServiceFlowProfileMatchDsIpv6SrcAddr
					InetAddressIPv6,
				msanServiceFlowProfileMatchDsIpv6SrcAddrMaskLen
					Integer32,
				msanServiceFlowProfileMatchDsIpv6DestAddr
					InetAddressIPv6,
				msanServiceFlowProfileMatchDsIpv6DestAddrMaskLen
					Integer32,
				msanServiceFlowProfileUsage
					INTEGER
			 }

		-- 1.3.6.1.4.1.1332.1.1.5.3.3.3.1.1.1
		msanServiceFlowProfileName OBJECT-TYPE
			SYNTAX DisplayString (SIZE (1..32))
			MAX-ACCESS not-accessible
			STATUS current
			DESCRIPTION
				"Service Flow Profile Name."
			::= { msanServiceFlowProfileEntry 1 }

		
		-- 1.3.6.1.4.1.1332.1.1.5.3.3.3.1.1.2
		msanServiceFlowProfileProtection OBJECT-TYPE
			SYNTAX INTEGER
				{
				unprotected(0),
				protected(1)
				}
			MAX-ACCESS read-write
			STATUS obsolete
			DESCRIPTION
				"If protection flag is set to protected (1), other profile values cannot be edited.
				
				Protection flag is always  protected (1) and it can't be changed if  profile is assigned as dynamic:
				msanServiceFlowProfileStatus = dynamic(2)"
			DEFVAL { unprotected }
			::= { msanServiceFlowProfileEntry 2 }

		
		-- 1.3.6.1.4.1.1332.1.1.5.3.3.3.1.1.3
		msanServiceFlowProfileStatus OBJECT-TYPE
			SYNTAX INTEGER
				{
				static(1),
				dynamic(2)
				}
			MAX-ACCESS read-only
			STATUS obsolete
			DESCRIPTION
				"Profile status. 
				If status is dynamic, profile values can't be edited."
			::= { msanServiceFlowProfileEntry 3 }

		
		-- 1.3.6.1.4.1.1332.1.1.5.3.3.3.1.1.4
		msanServiceFlowProfileMatchUsAny OBJECT-TYPE
			SYNTAX INTEGER
				{
				enable(1),
				disable(2)
				}
			MAX-ACCESS read-write
			STATUS current
			DESCRIPTION
				"Match every upstream packet frame."
			DEFVAL { disable }
			::= { msanServiceFlowProfileEntry 4 }

		
		-- 1.3.6.1.4.1.1332.1.1.5.3.3.3.1.1.5
		msanServiceFlowProfileMatchUsMacDestAddr OBJECT-TYPE
			SYNTAX MacAddress
			MAX-ACCESS read-write
			STATUS current
			DESCRIPTION
				"Match upstream packet frame with specified destination MAC address.
				Empty string indicates that parameter has not been defined"
			DEFVAL { ''b }
			::= { msanServiceFlowProfileEntry 5 }

		
		-- 1.3.6.1.4.1.1332.1.1.5.3.3.3.1.1.6
		msanServiceFlowProfileMatchUsMacDestMask OBJECT-TYPE
			SYNTAX MacAddress
			MAX-ACCESS read-write
			STATUS current
			DESCRIPTION
				"This mask value identifies the portion of msanServiceFlowProfileMatchUsMacDestAddr 
				that is compared with upstream packet.
				Empty string indicates that parameter has not been defined"
			DEFVAL { ''b }
			::= { msanServiceFlowProfileEntry 6 }

		
		-- 1.3.6.1.4.1.1332.1.1.5.3.3.3.1.1.7
		msanServiceFlowProfileMatchUsMacSrcAddr OBJECT-TYPE
			SYNTAX MacAddress
			MAX-ACCESS read-write
			STATUS current
			DESCRIPTION
				"Match upstream packet frame with specified source MAC address.
				Empty string indicates that parameter has not been defined"
			DEFVAL { ''b }
			::= { msanServiceFlowProfileEntry 7 }

		
		-- 1.3.6.1.4.1.1332.1.1.5.3.3.3.1.1.8
		msanServiceFlowProfileMatchUsMacSrcMask OBJECT-TYPE
			SYNTAX MacAddress
			MAX-ACCESS read-write
			STATUS current
			DESCRIPTION
				"This mask value identifies the portion of msanServiceFlowProfileMatchUsMacSrcAddr 
				that is compared with upstream packet.
				Empty string indicates that parameter has not been defined"
			DEFVAL { ''b }
			::= { msanServiceFlowProfileEntry 8 }

		
		-- 1.3.6.1.4.1.1332.1.1.5.3.3.3.1.1.9
		msanServiceFlowProfileMatchUsCPcp OBJECT-TYPE
			SYNTAX Integer32
			MAX-ACCESS read-write
			STATUS current
			DESCRIPTION
				"Match upstream packet frame with specified Customer PCP (Priority Code Point) - 
				PCP is also known as class of service (CoS) bits.
				A value of -1 indicates that parameter has not been defined."
			DEFVAL { -1 }
			::= { msanServiceFlowProfileEntry 9 }

		
		-- 1.3.6.1.4.1.1332.1.1.5.3.3.3.1.1.10
		msanServiceFlowProfileMatchUsSPcp OBJECT-TYPE
			SYNTAX Integer32
			MAX-ACCESS read-write
			STATUS current
			DESCRIPTION
				"Match upstream packet frame with specified Service PCP  (Priority Code Point).
				PCP is also known as class of service (CoS) bits.
				A value of -1 indicates that parameter has not been defined."
			DEFVAL { -1 }
			::= { msanServiceFlowProfileEntry 10 }

		
		-- 1.3.6.1.4.1.1332.1.1.5.3.3.3.1.1.11
		msanServiceFlowProfileMatchUsVlanProfile OBJECT-TYPE
			SYNTAX INTEGER
				{
				enable(1),
				disable(2)
				}
			MAX-ACCESS read-write
			STATUS current
			DESCRIPTION
				"Match upstream packet frame with VLAN Id values from VLAN Service Profile (msanVlanProfileTable).
				"
			DEFVAL { disable }
			::= { msanServiceFlowProfileEntry 11 }

		
		-- 1.3.6.1.4.1.1332.1.1.5.3.3.3.1.1.12
		msanServiceFlowProfileMatchUsCVlanIdRange OBJECT-TYPE
			SYNTAX OCTET STRING (SIZE (0..512))
			MAX-ACCESS read-write
			STATUS current
			DESCRIPTION
				"Match upstream packet frame with specified list (bitmask) of Customer VLAN Id.
				An empty string indicates that parameter has not been defined."
			DEFVAL { ''b }
			::= { msanServiceFlowProfileEntry 12 }

		
		-- 1.3.6.1.4.1.1332.1.1.5.3.3.3.1.1.13
		msanServiceFlowProfileMatchUsSVlanIdRange OBJECT-TYPE
			SYNTAX OCTET STRING (SIZE (0..512))
			MAX-ACCESS read-write
			STATUS current
			DESCRIPTION
				"Match upstream packet frame with specified list (bitmask) of Service VLAN Id.
				An empty string indicates that parameter has not been defined."
			DEFVAL { ''b }
			::= { msanServiceFlowProfileEntry 13 }

		
		-- 1.3.6.1.4.1.1332.1.1.5.3.3.3.1.1.14
		msanServiceFlowProfileMatchUsEthertype OBJECT-TYPE
			SYNTAX Integer32 (-1..65535)
			MAX-ACCESS read-write
			STATUS current
			DESCRIPTION
				"Match upstream packet frame with specified EtherType value.
				A value of -1 indicates that parameter has not been defined."
			DEFVAL { -1 }
			::= { msanServiceFlowProfileEntry 14 }

		
		-- 1.3.6.1.4.1.1332.1.1.5.3.3.3.1.1.15
		msanServiceFlowProfileMatchUsIpProtocol OBJECT-TYPE
			SYNTAX Integer32 (-1..255)
			MAX-ACCESS read-write
			STATUS current
			DESCRIPTION
				"Match upstream packet frame with specified IP protocol value.
				A value of -1 indicates that parameter has not been defined.
				Some of standard protocol values:
				   icmp - 1
				   igmp - 2
				   ip - 4 (ip in ip encapsulation)
				   tcp - 6
				   udp - 17"
			DEFVAL { -1 }
			::= { msanServiceFlowProfileEntry 15 }

		
		-- 1.3.6.1.4.1.1332.1.1.5.3.3.3.1.1.16
		msanServiceFlowProfileMatchUsIpSrcAddr OBJECT-TYPE
			SYNTAX IpAddress
			MAX-ACCESS read-write
			STATUS current
			DESCRIPTION
				"Match upstream packet frame with specified source IP address.
				Empty string indicates that parameter has not been defined."
			DEFVAL { ''h }
			::= { msanServiceFlowProfileEntry 16 }

		
		-- 1.3.6.1.4.1.1332.1.1.5.3.3.3.1.1.17
		msanServiceFlowProfileMatchUsIpSrcMask OBJECT-TYPE
			SYNTAX IpAddress
			MAX-ACCESS read-write
			STATUS current
			DESCRIPTION
				"This mask value identifies the portion of msanServiceFlowProfileMatchUsIpSrcAddr 
				that is compared with upstream packet.
				Empty string indicates that parameter has not been defined"
			DEFVAL { ''h }
			::= { msanServiceFlowProfileEntry 17 }

		
		-- 1.3.6.1.4.1.1332.1.1.5.3.3.3.1.1.18
		msanServiceFlowProfileMatchUsIpDestAddr OBJECT-TYPE
			SYNTAX IpAddress
			MAX-ACCESS read-write
			STATUS current
			DESCRIPTION
				"Match upstream packet frame with specified destination IP address.
				Empty string indicates that parameter has not been defined."
			DEFVAL { ''h }
			::= { msanServiceFlowProfileEntry 18 }

		
		-- 1.3.6.1.4.1.1332.1.1.5.3.3.3.1.1.19
		msanServiceFlowProfileMatchUsIpDestMask OBJECT-TYPE
			SYNTAX IpAddress
			MAX-ACCESS read-write
			STATUS current
			DESCRIPTION
				"This mask value identifies the portion of msanServiceFlowProfileMatchUsIpDestAddr 
				that is compared with upstream packet.
				Empty string indicates that parameter has not been defined"
			DEFVAL { ''h }
			::= { msanServiceFlowProfileEntry 19 }

		
		-- 1.3.6.1.4.1.1332.1.1.5.3.3.3.1.1.20
		msanServiceFlowProfileMatchUsIpDscp OBJECT-TYPE
			SYNTAX Integer32 (-1..63)
			MAX-ACCESS read-write
			STATUS current
			DESCRIPTION
				"Match upstream packet frame with specified CSC (Class Selector Code Point) = IP precedence (part of TOS field) value.
				A value of -1 indicates that parameter has not been defined."
			DEFVAL { -1 }
			::= { msanServiceFlowProfileEntry 20 }

		
		-- 1.3.6.1.4.1.1332.1.1.5.3.3.3.1.1.21
		msanServiceFlowProfileMatchUsIpCsc OBJECT-TYPE
			SYNTAX Integer32 (-1..7)
			MAX-ACCESS read-write
			STATUS current
			DESCRIPTION
				"Match upstream packet frame with specified IP precedence (part of TOS field) value.
				A value of -1 indicates that parameter has not been defined."
			DEFVAL { -1 }
			::= { msanServiceFlowProfileEntry 21 }

		
		-- 1.3.6.1.4.1.1332.1.1.5.3.3.3.1.1.22
		msanServiceFlowProfileMatchUsIpDropPrecedence OBJECT-TYPE
			SYNTAX INTEGER
				{
				notDefined(-1),
				noDrop(0),
				lowDrop(1),
				mediumDrop(2),
				highDrop(3)
				}
			MAX-ACCESS read-write
			STATUS current
			DESCRIPTION
				"Match upstream packet frame with specified Drop precedence two bits value:
				noDrop(0)          -> 00
				lowDrop(1)         -> 01 
				mediumDrop(2)      -> 10
				highDrop(3)        -> 11
				
				A value of -1 indicates that parameter has not been defined."
			DEFVAL { notDefined }
			::= { msanServiceFlowProfileEntry 22 }

		
		-- 1.3.6.1.4.1.1332.1.1.5.3.3.3.1.1.23
		msanServiceFlowProfileMatchUsTcpSrcPort OBJECT-TYPE
			SYNTAX Integer32 (-1..65535)
			MAX-ACCESS read-write
			STATUS current
			DESCRIPTION
				"Match upstream packet frame with specified source TCP port number.
				A value of -1 indicates that parameter has not been defined."
			DEFVAL { -1 }
			::= { msanServiceFlowProfileEntry 23 }

		
		-- 1.3.6.1.4.1.1332.1.1.5.3.3.3.1.1.24
		msanServiceFlowProfileMatchUsTcpDestPort OBJECT-TYPE
			SYNTAX Integer32 (-1..65535)
			MAX-ACCESS read-write
			STATUS current
			DESCRIPTION
				"Match upstream packet frame with specified destination TCP port number.
				A value of -1 indicates that parameter has not been defined."
			DEFVAL { -1 }
			::= { msanServiceFlowProfileEntry 24 }

		
		-- 1.3.6.1.4.1.1332.1.1.5.3.3.3.1.1.25
		msanServiceFlowProfileMatchUsUdpSrcPort OBJECT-TYPE
			SYNTAX Integer32 (-1..65535)
			MAX-ACCESS read-write
			STATUS current
			DESCRIPTION
				"Match upstream packet frame with specified source UDP port number.
				A value of -1 indicates that parameter has not been defined."
			DEFVAL { -1 }
			::= { msanServiceFlowProfileEntry 25 }

		
		-- 1.3.6.1.4.1.1332.1.1.5.3.3.3.1.1.26
		msanServiceFlowProfileMatchUsUdpDstPort OBJECT-TYPE
			SYNTAX Integer32 (-1..65535)
			MAX-ACCESS read-write
			STATUS current
			DESCRIPTION
				"Match upstream packet frame with specified destination UDP port number.
				A value of -1 indicates that parameter has not been defined."
			DEFVAL { -1 }
			::= { msanServiceFlowProfileEntry 26 }

		
		-- 1.3.6.1.4.1.1332.1.1.5.3.3.3.1.1.27
		msanServiceFlowProfileMatchDsAny OBJECT-TYPE
			SYNTAX INTEGER
				{
				enable(1),
				disable(2)
				}
			MAX-ACCESS read-write
			STATUS current
			DESCRIPTION
				"Match every downstream packet frame."
			DEFVAL { disable }
			::= { msanServiceFlowProfileEntry 27 }

		
		-- 1.3.6.1.4.1.1332.1.1.5.3.3.3.1.1.28
		msanServiceFlowProfileMatchDsMacDestAddr OBJECT-TYPE
			SYNTAX MacAddress
			MAX-ACCESS read-write
			STATUS current
			DESCRIPTION
				"Match downstream packet frame with specified destination MAC address.
				Empty string indicates that parameter has not been defined"
			DEFVAL { ''b }
			::= { msanServiceFlowProfileEntry 28 }

		
		-- 1.3.6.1.4.1.1332.1.1.5.3.3.3.1.1.29
		msanServiceFlowProfileMatchDsMacDestMask OBJECT-TYPE
			SYNTAX MacAddress
			MAX-ACCESS read-write
			STATUS current
			DESCRIPTION
				"This mask value identifies the portion of msanServiceFlowProfileMatchDsMacDestAddr 
				that is compared with downstream packet.
				Empty string indicates that parameter has not been defined"
			DEFVAL { ''b }
			::= { msanServiceFlowProfileEntry 29 }

		
		-- 1.3.6.1.4.1.1332.1.1.5.3.3.3.1.1.30
		msanServiceFlowProfileMatchDsMacSrcAddr OBJECT-TYPE
			SYNTAX MacAddress
			MAX-ACCESS read-write
			STATUS current
			DESCRIPTION
				"Match downstream packet frame with specified source MAC address.
				Empty string indicates that parameter has not been defined"
			DEFVAL { ''b }
			::= { msanServiceFlowProfileEntry 30 }

		
		-- 1.3.6.1.4.1.1332.1.1.5.3.3.3.1.1.31
		msanServiceFlowProfileMatchDsMacSrcMask OBJECT-TYPE
			SYNTAX MacAddress
			MAX-ACCESS read-write
			STATUS current
			DESCRIPTION
				"This mask value identifies the portion of msanServiceFlowProfileMatchDsMacSrcAddr 
				that is compared with downstream packet.
				Empty string indicates that parameter has not been defined"
			DEFVAL { ''b }
			::= { msanServiceFlowProfileEntry 31 }

		
		-- 1.3.6.1.4.1.1332.1.1.5.3.3.3.1.1.32
		msanServiceFlowProfileMatchDsCPcp OBJECT-TYPE
			SYNTAX Integer32
			MAX-ACCESS read-write
			STATUS current
			DESCRIPTION
				"Match downstream packet frame with specified Customer PCP (Priority Code Point) - 
				PCP is also known as class of service (CoS) bits.
				A value of -1 indicates that parameter has not been defined."
			DEFVAL { -1 }
			::= { msanServiceFlowProfileEntry 32 }

		
		-- 1.3.6.1.4.1.1332.1.1.5.3.3.3.1.1.33
		msanServiceFlowProfileMatchDsSPcp OBJECT-TYPE
			SYNTAX Integer32
			MAX-ACCESS read-write
			STATUS current
			DESCRIPTION
				"Match downstream packet frame with specified Service PCP  (Priority Code Point).
				PCP is also known as class of service (CoS) bits.
				A value of -1 indicates that parameter has not been defined."
			DEFVAL { -1 }
			::= { msanServiceFlowProfileEntry 33 }

		
		-- 1.3.6.1.4.1.1332.1.1.5.3.3.3.1.1.34
		msanServiceFlowProfileMatchDsVlanProfile OBJECT-TYPE
			SYNTAX INTEGER
				{
				enable(1),
				disable(2)
				}
			MAX-ACCESS read-write
			STATUS current
			DESCRIPTION
				"Match downstream packet frame with VLAN Id values from VLAN Service Profile (msanVlanProfileTable).
				"
			DEFVAL { disable }
			::= { msanServiceFlowProfileEntry 34 }

		
		-- 1.3.6.1.4.1.1332.1.1.5.3.3.3.1.1.35
		msanServiceFlowProfileMatchDsCVlanIdRange OBJECT-TYPE
			SYNTAX OCTET STRING (SIZE (0..512))
			MAX-ACCESS read-write
			STATUS current
			DESCRIPTION
				"Match downstream packet frame with specified list (bitmask) of Customer VLAN Id.
				An emptya string indicates that parameter has not been defined."
			DEFVAL { ''b }
			::= { msanServiceFlowProfileEntry 35 }

		
		-- 1.3.6.1.4.1.1332.1.1.5.3.3.3.1.1.36
		msanServiceFlowProfileMatchDsSVlanIdRange OBJECT-TYPE
			SYNTAX OCTET STRING (SIZE (0..512))
			MAX-ACCESS read-write
			STATUS current
			DESCRIPTION
				"Match downstream packet frame with specified list (bitmask) of Service VLAN Id.
				An empty string indicates that parameter has not been defined."
			DEFVAL { ''b }
			::= { msanServiceFlowProfileEntry 36 }

		
		-- 1.3.6.1.4.1.1332.1.1.5.3.3.3.1.1.37
		msanServiceFlowProfileMatchDsEthertype OBJECT-TYPE
			SYNTAX Integer32 (-1..65535)
			MAX-ACCESS read-write
			STATUS current
			DESCRIPTION
				"Match downstream packet frame with specified EtherType value.
				A value of -1 indicates that parameter has not been defined."
			DEFVAL { -1 }
			::= { msanServiceFlowProfileEntry 37 }

		
		-- 1.3.6.1.4.1.1332.1.1.5.3.3.3.1.1.38
		msanServiceFlowProfileMatchDsIpProtocol OBJECT-TYPE
			SYNTAX Integer32 (-1..255)
			MAX-ACCESS read-write
			STATUS current
			DESCRIPTION
				"Match downstream packet frame with specified IP protocol value.
				A value of -1 indicates that parameter has not been defined.
				Some of standard protocol values:
				   icmp - 1
				   igmp - 2
				   ip - 4 (ip in ip encapsulation)
				   tcp - 6
				   udp - 17"
			DEFVAL { -1 }
			::= { msanServiceFlowProfileEntry 38 }

		
		-- 1.3.6.1.4.1.1332.1.1.5.3.3.3.1.1.39
		msanServiceFlowProfileMatchDsIpSrcAddr OBJECT-TYPE
			SYNTAX IpAddress
			MAX-ACCESS read-write
			STATUS current
			DESCRIPTION
				"Match downstream packet frame with specified source IP address.
				Empty string indicates that parameter has not been defined."
			DEFVAL { ''h }
			::= { msanServiceFlowProfileEntry 39 }

		
		-- 1.3.6.1.4.1.1332.1.1.5.3.3.3.1.1.40
		msanServiceFlowProfileMatchDsIpSrcMask OBJECT-TYPE
			SYNTAX IpAddress
			MAX-ACCESS read-write
			STATUS current
			DESCRIPTION
				"This mask value identifies the portion of msanServiceFlowProfileMatchDsIpSrcAddr 
				that is compared with downstream packet.
				Empty string indicates that parameter has not been defined"
			DEFVAL { ''h }
			::= { msanServiceFlowProfileEntry 40 }

		
		-- 1.3.6.1.4.1.1332.1.1.5.3.3.3.1.1.41
		msanServiceFlowProfileMatchDsIpDestAddr OBJECT-TYPE
			SYNTAX IpAddress
			MAX-ACCESS read-write
			STATUS current
			DESCRIPTION
				"Match downstream packet frame with specified destination IP address.
				Empty string indicates that parameter has not been defined."
			DEFVAL { ''h }
			::= { msanServiceFlowProfileEntry 41 }

		
		-- 1.3.6.1.4.1.1332.1.1.5.3.3.3.1.1.42
		msanServiceFlowProfileMatchDsIpDestMask OBJECT-TYPE
			SYNTAX IpAddress
			MAX-ACCESS read-write
			STATUS current
			DESCRIPTION
				"This mask value identifies the portion of msanServiceFlowProfileMatchDsIpDestAddr 
				that is compared with downstream packet.
				Empty string indicates that parameter has not been defined"
			DEFVAL { ''h }
			::= { msanServiceFlowProfileEntry 42 }

		
		-- 1.3.6.1.4.1.1332.1.1.5.3.3.3.1.1.43
		msanServiceFlowProfileMatchDsIpDscp OBJECT-TYPE
			SYNTAX Integer32 (-1..63)
			MAX-ACCESS read-write
			STATUS current
			DESCRIPTION
				"Match downstream packet frame with specified IP DSCP value.
				A value of -1 indicates that parameter has not been defined."
			DEFVAL { -1 }
			::= { msanServiceFlowProfileEntry 43 }

		
		-- 1.3.6.1.4.1.1332.1.1.5.3.3.3.1.1.44
		msanServiceFlowProfileMatchDsIpCsc OBJECT-TYPE
			SYNTAX Integer32 (-1..7)
			MAX-ACCESS read-write
			STATUS current
			DESCRIPTION
				"Match downstream packet frame with specified CSC (Class Selector Code Point) = IP precedence (part of TOS field) value.
				A value of -1 indicates that parameter has not been defined."
			DEFVAL { -1 }
			::= { msanServiceFlowProfileEntry 44 }

		
		-- 1.3.6.1.4.1.1332.1.1.5.3.3.3.1.1.45
		msanServiceFlowProfileMatchDsIpDropPrecedence OBJECT-TYPE
			SYNTAX INTEGER
				{
				notDefined(-1),
				noDrop(0),
				lowDrop(1),
				mediumDrop(2),
				highDrop(3)
				}
			MAX-ACCESS read-write
			STATUS current
			DESCRIPTION
				"Match downstream packet frame with specified Drop precedence two bits value:
				noDrop(0)          -> 00
				lowDrop(1)         -> 01 
				mediumDrop(2)      -> 10
				highDrop(3)        -> 11
				
				A value of -1 indicates that parameter has not been defined."
			DEFVAL { notDefined }
			::= { msanServiceFlowProfileEntry 45 }

		
		-- 1.3.6.1.4.1.1332.1.1.5.3.3.3.1.1.46
		msanServiceFlowProfileMatchDsTcpSrcPort OBJECT-TYPE
			SYNTAX Integer32 (-1..65535)
			MAX-ACCESS read-write
			STATUS current
			DESCRIPTION
				"Match downstream packet frame with specified source TCP port number.
				A value of -1 indicates that parameter has not been defined."
			DEFVAL { -1 }
			::= { msanServiceFlowProfileEntry 46 }

		
		-- 1.3.6.1.4.1.1332.1.1.5.3.3.3.1.1.47
		msanServiceFlowProfileMatchDsTcpDestPort OBJECT-TYPE
			SYNTAX Integer32 (-1..65535)
			MAX-ACCESS read-write
			STATUS current
			DESCRIPTION
				"Match downstream packet frame with specified destination TCP port number.
				A value of -1 indicates that parameter has not been defined."
			DEFVAL { -1 }
			::= { msanServiceFlowProfileEntry 47 }

		
		-- 1.3.6.1.4.1.1332.1.1.5.3.3.3.1.1.48
		msanServiceFlowProfileMatchDsUdpSrcPort OBJECT-TYPE
			SYNTAX Integer32 (-1..65535)
			MAX-ACCESS read-write
			STATUS current
			DESCRIPTION
				"Match downstream packet frame with specified source UDP port number.
				A value of -1 indicates that parameter has not been defined."
			DEFVAL { -1 }
			::= { msanServiceFlowProfileEntry 48 }

		
		-- 1.3.6.1.4.1.1332.1.1.5.3.3.3.1.1.49
		msanServiceFlowProfileMatchDsUdpDstPort OBJECT-TYPE
			SYNTAX Integer32 (-1..65535)
			MAX-ACCESS read-write
			STATUS current
			DESCRIPTION
				"Match downstream packet frame with specified destination UDP port number.
				A value of -1 indicates that parameter has not been defined."
			DEFVAL { -1 }
			::= { msanServiceFlowProfileEntry 49 }

		
		-- 1.3.6.1.4.1.1332.1.1.5.3.3.3.1.1.50
		msanServiceFlowProfileUsCdr OBJECT-TYPE
			SYNTAX Integer32 (0..1000000)
			UNITS "kbps"
			MAX-ACCESS read-write
			STATUS current
			DESCRIPTION
				"Upstream committed data rate (E-CDR) in kbps (0 – 1000000)."
			DEFVAL { 0 }
			::= { msanServiceFlowProfileEntry 50 }

		
		-- 1.3.6.1.4.1.1332.1.1.5.3.3.3.1.1.51
		msanServiceFlowProfileUsCdrBurstSize OBJECT-TYPE
			SYNTAX Integer32 (0..16384)
			UNITS "kB"
			MAX-ACCESS read-write
			STATUS current
			DESCRIPTION
				"Upstream committed data rate burst size in kB (0 – 16384).
				
				When parameter is set to 0 (default), it's automatically updated to default 
				burst size in according with current msanQoSProfileInCdr value."
			DEFVAL { 0 }
			::= { msanServiceFlowProfileEntry 51 }

		
		-- 1.3.6.1.4.1.1332.1.1.5.3.3.3.1.1.52
		msanServiceFlowProfileUsPdr OBJECT-TYPE
			SYNTAX Integer32 (0..1000000)
			UNITS "kbps"
			MAX-ACCESS read-write
			STATUS current
			DESCRIPTION
				"Upstream peak data rate (E-PDR) in kbps (0 – 1000000)."
			DEFVAL { 0 }
			::= { msanServiceFlowProfileEntry 52 }

		
		-- 1.3.6.1.4.1.1332.1.1.5.3.3.3.1.1.53
		msanServiceFlowProfileUsPdrBurstSize OBJECT-TYPE
			SYNTAX Integer32 (0..16384)
			UNITS "kB"
			MAX-ACCESS read-write
			STATUS current
			DESCRIPTION
				"Upstream peak data rate burst size in kB (0 – 16384).
				
				When parameter is set to 0 (default), it's automatically updated to default 
				burst size in according with current msanQoSProfileInPdr value."
			DEFVAL { 0 }
			::= { msanServiceFlowProfileEntry 53 }

		
		-- 1.3.6.1.4.1.1332.1.1.5.3.3.3.1.1.54
		msanServiceFlowProfileUsMarkPcp OBJECT-TYPE
			SYNTAX INTEGER
				{
				none(1),
				copyFromCsc(2),
				userValue(3)
				}
			MAX-ACCESS read-write
			STATUS current
			DESCRIPTION
				"Type of upstrem PCP marking.
				If set to userValue(3), parameter msanServiceFlowProfileUsMarkPcpValue is used.
				A value of none(1) indicates that parameter has not been defined"
			DEFVAL { none }
			::= { msanServiceFlowProfileEntry 54 }

		
		-- 1.3.6.1.4.1.1332.1.1.5.3.3.3.1.1.55
		msanServiceFlowProfileUsMarkPcpValue OBJECT-TYPE
			SYNTAX INTEGER (-1..7)
			MAX-ACCESS read-write
			STATUS current
			DESCRIPTION
				"Mark upstream packets with specified PCP (Priority Code Point) value (0-7) = CoS.
				A value of -1 indicates that parameter has not been defined"
			DEFVAL { -1 }
			::= { msanServiceFlowProfileEntry 55 }

		
		-- 1.3.6.1.4.1.1332.1.1.5.3.3.3.1.1.56
		msanServiceFlowProfileUsMarkDscp OBJECT-TYPE
			SYNTAX INTEGER
				{
				none(1),
				copyFromPcp(2),
				userValue(3)
				}
			MAX-ACCESS read-write
			STATUS current
			DESCRIPTION
				"Type of upstrem DSCP marking.
				If set to userValue(3), parameter msanServiceFlowProfileUsMarkDscpValue is used.
				A value of none(1) indicates that parameter has not been defined"
			DEFVAL { none }
			::= { msanServiceFlowProfileEntry 56 }

		
		-- 1.3.6.1.4.1.1332.1.1.5.3.3.3.1.1.57
		msanServiceFlowProfileUsMarkDscpValue OBJECT-TYPE
			SYNTAX INTEGER (-1..63)
			MAX-ACCESS read-write
			STATUS current
			DESCRIPTION
				"Mark upstream packets with specified DSCP (Diffserv Code Point) value (0-63).
				A value of -1 indicates that parameter has not been defined"
			DEFVAL { -1 }
			::= { msanServiceFlowProfileEntry 57 }

		
		-- 1.3.6.1.4.1.1332.1.1.5.3.3.3.1.1.58
		msanServiceFlowProfileDsCdr OBJECT-TYPE
			SYNTAX Integer32 (0..1000000)
			UNITS "kbps"
			MAX-ACCESS read-write
			STATUS current
			DESCRIPTION
				"Downstream committed data rate (E-CDR) in kbps (0 – 1000000)."
			DEFVAL { 0 }
			::= { msanServiceFlowProfileEntry 58 }

		
		-- 1.3.6.1.4.1.1332.1.1.5.3.3.3.1.1.59
		msanServiceFlowProfileDsCdrBurstSize OBJECT-TYPE
			SYNTAX Integer32 (0..16384)
			UNITS "kB"
			MAX-ACCESS read-write
			STATUS current
			DESCRIPTION
				"Downstream committed data rate burst size in kB (0 – 16384).
				
				When parameter is set to 0 (default), it's automatically updated to default 
				burst size in according with current msanQoSProfileOutCdr value."
			DEFVAL { 0 }
			::= { msanServiceFlowProfileEntry 59 }

		
		-- 1.3.6.1.4.1.1332.1.1.5.3.3.3.1.1.60
		msanServiceFlowProfileDsPdr OBJECT-TYPE
			SYNTAX Integer32 (0..1000000)
			UNITS "kbps"
			MAX-ACCESS read-write
			STATUS current
			DESCRIPTION
				"Downstream peak data rate (E-PDR) in kbps (0 – 1000000)."
			DEFVAL { 0 }
			::= { msanServiceFlowProfileEntry 60 }

		
		-- 1.3.6.1.4.1.1332.1.1.5.3.3.3.1.1.61
		msanServiceFlowProfileDsPdrBurstSize OBJECT-TYPE
			SYNTAX Integer32 (0..16384)
			UNITS "kB"
			MAX-ACCESS read-write
			STATUS current
			DESCRIPTION
				"Downstream peak data rate burst size in kB (0 – 16384).
				
				When parameter is set to 0 (default), it's automatically updated to default 
				burst size in according with current msanQoSProfileOutCdr value.
				"
			DEFVAL { 0 }
			::= { msanServiceFlowProfileEntry 61 }

		
		-- 1.3.6.1.4.1.1332.1.1.5.3.3.3.1.1.62
		msanServiceFlowProfileDsMarkPcp OBJECT-TYPE
			SYNTAX INTEGER
				{
				none(1),
				copyFromCsc(2),
				userValue(3)
				}
			MAX-ACCESS read-write
			STATUS current
			DESCRIPTION
				"Type of downstream  PCP marking.
				If set to userValue(3), parameter msanServiceFlowProfileDsMarkPcpValue is used.
				A value of none(1) indicates that parameter has not been defined"
			DEFVAL { none }
			::= { msanServiceFlowProfileEntry 62 }

		
		-- 1.3.6.1.4.1.1332.1.1.5.3.3.3.1.1.63
		msanServiceFlowProfileDsMarkPcpValue OBJECT-TYPE
			SYNTAX INTEGER (-1..7)
			MAX-ACCESS read-write
			STATUS current
			DESCRIPTION
				"Mark downstream packets with specified PCP (Priority Code Point) value (0-7) = CoS.
				A value of -1 indicates that parameter has not been defined"
			DEFVAL { -1 }
			::= { msanServiceFlowProfileEntry 63 }

		
		-- 1.3.6.1.4.1.1332.1.1.5.3.3.3.1.1.64
		msanServiceFlowProfileDsMarkDscp OBJECT-TYPE
			SYNTAX INTEGER
				{
				none(1),
				copyFromPcp(2),
				userValue(3)
				}
			MAX-ACCESS read-write
			STATUS current
			DESCRIPTION
				"Type of downstrem DSCP marking.
				If set to userValue(3), parameter msanServiceFlowProfileDsMarkDscpValue is used.
				A value of none(1) indicates that parameter has not been defined"
			DEFVAL { none }
			::= { msanServiceFlowProfileEntry 64 }

		
		-- 1.3.6.1.4.1.1332.1.1.5.3.3.3.1.1.65
		msanServiceFlowProfileDsMarkDscpValue OBJECT-TYPE
			SYNTAX INTEGER (-1..63)
			MAX-ACCESS read-write
			STATUS current
			DESCRIPTION
				"Mark downstream packets with specified DSCP (Diffserv Code Point) value (0-63).
				A value of -1 indicates that parameter has not been defined"
			DEFVAL { -1 }
			::= { msanServiceFlowProfileEntry 65 }

		
		-- 1.3.6.1.4.1.1332.1.1.5.3.3.3.1.1.66
		msanServiceFlowProfileDsQueuingPriority OBJECT-TYPE
			SYNTAX INTEGER (0..7)
			MAX-ACCESS read-write
			STATUS current
			DESCRIPTION
				"Queuing Priority of Service Flow Profile. 
				"
			DEFVAL { 0 }
			::= { msanServiceFlowProfileEntry 66 }

		
		-- 1.3.6.1.4.1.1332.1.1.5.3.3.3.1.1.67
		msanServiceFlowProfileDsSchedulingMode OBJECT-TYPE
			SYNTAX INTEGER
				{
				weighted(1),
				strict(2)
				}
			MAX-ACCESS read-write
			STATUS current
			DESCRIPTION
				"Scheduling Mode"
			DEFVAL { weighted }
			::= { msanServiceFlowProfileEntry 67 }

		
		-- 1.3.6.1.4.1.1332.1.1.5.3.3.3.1.1.68
		msanServiceFlowProfileDescription OBJECT-TYPE
			SYNTAX DisplayString (SIZE (0..255))
			MAX-ACCESS read-write
			STATUS current
			DESCRIPTION
				"Attribute specifies text which describes the associated object."
			::= { msanServiceFlowProfileEntry 68 }

		
		-- 1.3.6.1.4.1.1332.1.1.5.3.3.3.1.1.69
		msanServiceFlowProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanServiceFlowProfileEntry 69 }

		
		-- 1.3.6.1.4.1.1332.1.1.5.3.3.3.1.1.70
		msanServiceFlowProfileMatchUsIpv6SrcAddr OBJECT-TYPE
			SYNTAX InetAddressIPv6
			MAX-ACCESS read-write
			STATUS current
			DESCRIPTION
				"Match upstream packet frame with specified source IPv6 address.
				Empty string indicates that parameter has not been defined."
			DEFVAL { ''b }
			::= { msanServiceFlowProfileEntry 70 }

		
		-- 1.3.6.1.4.1.1332.1.1.5.3.3.3.1.1.71
		msanServiceFlowProfileMatchUsIpv6SrcAddrMaskLen OBJECT-TYPE
			SYNTAX Integer32 (0..128)
			MAX-ACCESS read-write
			STATUS current
			DESCRIPTION
				"This mask value identifies the portion of msanServiceFlowProfileMatchUsIpv6SrcAddr
				that is compared with upstream packet.
				"
			DEFVAL { 0 }
			::= { msanServiceFlowProfileEntry 71 }

		
		-- 1.3.6.1.4.1.1332.1.1.5.3.3.3.1.1.72
		msanServiceFlowProfileMatchUsIpv6DestAddr OBJECT-TYPE
			SYNTAX InetAddressIPv6
			MAX-ACCESS read-write
			STATUS current
			DESCRIPTION
				"Match upstream packet frame with specified destination IPv6 address.
				Empty string indicates that parameter has not been defined.
				"
			DEFVAL { ''b }
			::= { msanServiceFlowProfileEntry 72 }

		
		-- 1.3.6.1.4.1.1332.1.1.5.3.3.3.1.1.73
		msanServiceFlowProfileMatchUsIpv6DestAddrMaskLen OBJECT-TYPE
			SYNTAX Integer32 (0..128)
			MAX-ACCESS read-write
			STATUS current
			DESCRIPTION
				"This mask value identifies the portion of msanServiceFlowProfileMatchUsIpv6DestAddr
				that is compared with upstream packet.
				"
			DEFVAL { 0 }
			::= { msanServiceFlowProfileEntry 73 }

		
		-- 1.3.6.1.4.1.1332.1.1.5.3.3.3.1.1.74
		msanServiceFlowProfileMatchDsIpv6SrcAddr OBJECT-TYPE
			SYNTAX InetAddressIPv6
			MAX-ACCESS read-write
			STATUS current
			DESCRIPTION
				"Match downstream packet frame with specified source IPv6 address.
				Empty string indicates that parameter has not been defined."
			DEFVAL { ''b }
			::= { msanServiceFlowProfileEntry 74 }

		
		-- 1.3.6.1.4.1.1332.1.1.5.3.3.3.1.1.75
		msanServiceFlowProfileMatchDsIpv6SrcAddrMaskLen OBJECT-TYPE
			SYNTAX Integer32 (0..128)
			MAX-ACCESS read-write
			STATUS current
			DESCRIPTION
				"This mask value identifies the portion of msanServiceFlowProfileMatchDsIpv6SrcAddr
				that is compared with downstream packet.
				"
			DEFVAL { 0 }
			::= { msanServiceFlowProfileEntry 75 }

		
		-- 1.3.6.1.4.1.1332.1.1.5.3.3.3.1.1.76
		msanServiceFlowProfileMatchDsIpv6DestAddr OBJECT-TYPE
			SYNTAX InetAddressIPv6
			MAX-ACCESS read-write
			STATUS current
			DESCRIPTION
				"Match downstream packet frame with specified destination IPv6 address.
				Empty string indicates that parameter has not been defined.
				"
			DEFVAL { ''b }
			::= { msanServiceFlowProfileEntry 76 }

		
		-- 1.3.6.1.4.1.1332.1.1.5.3.3.3.1.1.77
		msanServiceFlowProfileMatchDsIpv6DestAddrMaskLen OBJECT-TYPE
			SYNTAX Integer32 (0..128)
			MAX-ACCESS read-write
			STATUS current
			DESCRIPTION
				"This mask value identifies the portion of msanServiceFlowProfileMatchDsIpv6DestAddr
				that is compared with downstrem packet.
				"
			DEFVAL { 0 }
			::= { msanServiceFlowProfileEntry 77 }

		
		-- 1.3.6.1.4.1.1332.1.1.5.3.3.3.1.1.78
		msanServiceFlowProfileUsage OBJECT-TYPE
			SYNTAX INTEGER
				{
				attached(1),
				notAttached(2)
				}
			MAX-ACCESS read-only
			STATUS current
			DESCRIPTION
				"Profile usage.
				If profile is attached,  profile values can't be edited."
			::= { msanServiceFlowProfileEntry 78 }

		
		-- 1.3.6.1.4.1.1332.1.1.5.3.3.4
		msanVlanProfile OBJECT IDENTIFIER ::= { msanProfiles 4 }

		
		-- 1.3.6.1.4.1.1332.1.1.5.3.3.4.1
		msanVlanProfileTable OBJECT-TYPE
			SYNTAX SEQUENCE OF MsanVlanProfileEntry
			MAX-ACCESS not-accessible
			STATUS current
			DESCRIPTION
				"Vlan Profile table "
			::= { msanVlanProfile 1 }

		
		-- 1.3.6.1.4.1.1332.1.1.5.3.3.4.1.1
		msanVlanProfileEntry OBJECT-TYPE
			SYNTAX MsanVlanProfileEntry
			MAX-ACCESS not-accessible
			STATUS current
			DESCRIPTION
				"Vlan Profile table entry."
			INDEX { msanVlanProfileName }
			::= { msanVlanProfileTable 1 }

		
		MsanVlanProfileEntry ::=
			SEQUENCE { 
				msanVlanProfileName
					DisplayString,
				msanVlanProfileProtection
					INTEGER,
				msanVlanProfileStatus
					INTEGER,
				msanVlanProfileCVid
					OCTET STRING,
				msanVlanProfileCVidNative
					Integer32,
				msanVlanProfileCVidRemark
					Integer32,
				msanVlanProfileSVid
					Integer32,
				msanVlanProfileSEtherType
					Integer32,
				msanVlanProfileDescription
					DisplayString,
				msanVlanProfileRowStatus
					RowStatus,
				msanVlanProfileNetworkPortCTag
					INTEGER,
				msanVlanProfileUsage
					INTEGER,
				msanVlanProfileCVidExternal
					INTEGER,
				msanVlanProfileCVidNativeExternal
					INTEGER,
				msanVlanProfileCVidRemarkExternal
					INTEGER,
				msanVlanProfileSVidExternal
					INTEGER
			 }

		-- 1.3.6.1.4.1.1332.1.1.5.3.3.4.1.1.1
		msanVlanProfileName OBJECT-TYPE
			SYNTAX DisplayString (SIZE (1..32))
			MAX-ACCESS not-accessible
			STATUS current
			DESCRIPTION
				"Name for the VLAN profile."
			::= { msanVlanProfileEntry 1 }

		
		-- 1.3.6.1.4.1.1332.1.1.5.3.3.4.1.1.2
		msanVlanProfileProtection OBJECT-TYPE
			SYNTAX INTEGER
				{
				unprotected(0),
				protected(1)
				}
			MAX-ACCESS read-write
			STATUS obsolete
			DESCRIPTION
				"If protection flag is set to protected (1), other profile values cannot be edited.
				
				Protection flag is always  protected (1) and it can't be changed if  profile is assigned as dynamic:
				msanVlanProfileStatus = dynamic(2)"
			DEFVAL { unprotected }
			::= { msanVlanProfileEntry 2 }

		
		-- 1.3.6.1.4.1.1332.1.1.5.3.3.4.1.1.3
		msanVlanProfileStatus OBJECT-TYPE
			SYNTAX INTEGER
				{
				static(1),
				dynamic(2)
				}
			MAX-ACCESS read-only
			STATUS obsolete
			DESCRIPTION
				"Profile status. 
				If status is dynamic, profile values can't be edited."
			::= { msanVlanProfileEntry 3 }

		
		-- 1.3.6.1.4.1.1332.1.1.5.3.3.4.1.1.4
		msanVlanProfileCVid OBJECT-TYPE
			SYNTAX OCTET STRING (SIZE (0..512))
			MAX-ACCESS read-write
			STATUS current
			DESCRIPTION
				"Customer VLANs Identification (bit mask)."
			DEFVAL { "" }
			::= { msanVlanProfileEntry 4 }

		
		-- 1.3.6.1.4.1.1332.1.1.5.3.3.4.1.1.5
		msanVlanProfileCVidNative OBJECT-TYPE
			SYNTAX Integer32 (-1..4094)
			MAX-ACCESS read-write
			STATUS current
			DESCRIPTION
				"Nativ C-VLAN Id.
				A value of -1 indicates that parameter has not been defined."
			DEFVAL { -1 }
			::= { msanVlanProfileEntry 5 }

		
		-- 1.3.6.1.4.1.1332.1.1.5.3.3.4.1.1.6
		msanVlanProfileCVidRemark OBJECT-TYPE
			SYNTAX Integer32 (-1..4094)
			MAX-ACCESS read-write
			STATUS current
			DESCRIPTION
				"Remark C-VLAN Id.
				A value of -1 indicates that parameter has not been defined."
			DEFVAL { -1 }
			::= { msanVlanProfileEntry 6 }

		
		-- 1.3.6.1.4.1.1332.1.1.5.3.3.4.1.1.7
		msanVlanProfileSVid OBJECT-TYPE
			SYNTAX Integer32 (-1..4094)
			MAX-ACCESS read-write
			STATUS current
			DESCRIPTION
				"S-VLAN Id.
				A value of -1 indicates that parameter has not been defined."
			DEFVAL { -1 }
			::= { msanVlanProfileEntry 7 }

		
		-- 1.3.6.1.4.1.1332.1.1.5.3.3.4.1.1.8
		msanVlanProfileSEtherType OBJECT-TYPE
			SYNTAX Integer32
			MAX-ACCESS read-write
			STATUS current
			DESCRIPTION
				"Ether Type value. "
			DEFVAL { '88a8'h }
			::= { msanVlanProfileEntry 8 }

		
		-- 1.3.6.1.4.1.1332.1.1.5.3.3.4.1.1.10
		msanVlanProfileDescription OBJECT-TYPE
			SYNTAX DisplayString (SIZE (0..255))
			MAX-ACCESS read-write
			STATUS current
			DESCRIPTION
				"Attribute specifies text which describes the associated object."
			::= { msanVlanProfileEntry 10 }

		
		-- 1.3.6.1.4.1.1332.1.1.5.3.3.4.1.1.11
		msanVlanProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanVlanProfileEntry 11 }

		
		-- 1.3.6.1.4.1.1332.1.1.5.3.3.4.1.1.12
		msanVlanProfileNetworkPortCTag OBJECT-TYPE
			SYNTAX INTEGER
				{
				use(1),
				notUse(2)
				}
			MAX-ACCESS read-write
			STATUS current
			DESCRIPTION
				"Usage of C-VLAN tag on network port. 
				If assigned as notUse(2) in upstream direction, C-VLAN tag is removed."
			DEFVAL { use }
			::= { msanVlanProfileEntry 12 }

		
		-- 1.3.6.1.4.1.1332.1.1.5.3.3.4.1.1.13
		msanVlanProfileUsage OBJECT-TYPE
			SYNTAX INTEGER
				{
				attached(1),
				notAttached(2)
				}
			MAX-ACCESS read-only
			STATUS current
			DESCRIPTION
				"Profile usage.
				If profile is attached,  profile values can't be edited."
			::= { msanVlanProfileEntry 13 }

		
		-- 1.3.6.1.4.1.1332.1.1.5.3.3.4.1.1.14
		msanVlanProfileCVidExternal OBJECT-TYPE
			SYNTAX INTEGER
				{
				enable(1),
				disable(2)
				}
			MAX-ACCESS read-write
			STATUS current
			DESCRIPTION
				"Use external parameter msanProfilePortDataCVid as C-VLAN Id."
			DEFVAL { disable }
			::= { msanVlanProfileEntry 14 }

		
		-- 1.3.6.1.4.1.1332.1.1.5.3.3.4.1.1.15
		msanVlanProfileCVidNativeExternal OBJECT-TYPE
			SYNTAX INTEGER
				{
				enable(1),
				disable(2)
				}
			MAX-ACCESS read-write
			STATUS current
			DESCRIPTION
				"Use external parameter msanProfilePortDataCVid as Native C-VLAN Id."
			DEFVAL { disable }
			::= { msanVlanProfileEntry 15 }

		
		-- 1.3.6.1.4.1.1332.1.1.5.3.3.4.1.1.16
		msanVlanProfileCVidRemarkExternal OBJECT-TYPE
			SYNTAX INTEGER
				{
				enable(1),
				disable(2)
				}
			MAX-ACCESS read-write
			STATUS current
			DESCRIPTION
				"Use external parameter msanProfilePortDataCVid as Remark C-VLAN Id."
			DEFVAL { disable }
			::= { msanVlanProfileEntry 16 }

		
		-- 1.3.6.1.4.1.1332.1.1.5.3.3.4.1.1.17
		msanVlanProfileSVidExternal OBJECT-TYPE
			SYNTAX INTEGER
				{
				enable(1),
				disable(2)
				}
			MAX-ACCESS read-write
			STATUS current
			DESCRIPTION
				"Use external parameter msanProfilePortDataSVid as S-VLAN Id."
			DEFVAL { disable }
			::= { msanVlanProfileEntry 17 }

		
		-- 1.3.6.1.4.1.1332.1.1.5.3.3.4.2
		msanVlanPortProfileTable OBJECT-TYPE
			SYNTAX SEQUENCE OF MsanVlanPortProfileEntry
			MAX-ACCESS not-accessible
			STATUS current
			DESCRIPTION
				"A connection between VLAN profiles and device ports"
			::= { msanVlanProfile 2 }

		
		-- 1.3.6.1.4.1.1332.1.1.5.3.3.4.2.1
		msanVlanPortProfileEntry OBJECT-TYPE
			SYNTAX MsanVlanPortProfileEntry
			MAX-ACCESS not-accessible
			STATUS current
			DESCRIPTION
				"Service Profile Port table entry.
				
				In case of GPON access blade, ifIndex for ONU interface (ifDescr=0/x/y) is calculated with formula:
				ifIndex=max_olt_port_number(8 or 16)+(x-1)*128+y   "
			INDEX { ifIndex, msanVlanProfileName }
			::= { msanVlanPortProfileTable 1 }

		
		MsanVlanPortProfileEntry ::=
			SEQUENCE { 
				msanVlanPortProfileRowStatus
					RowStatus
			 }

		-- 1.3.6.1.4.1.1332.1.1.5.3.3.4.2.1.1
		msanVlanPortProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported.
				
				In case of GPON access blade, ifIndex for ONU interface (ifDescr=0/x/y) is calculated with formula:
				ifIndex=max_olt_port_number(8 or 16)+(x-1)*128+y   "
			::= { msanVlanPortProfileEntry 1 }

		
		-- 1.3.6.1.4.1.1332.1.1.5.3.3.5
		msanMulticastProfile OBJECT IDENTIFIER ::= { msanProfiles 5 }

		
		-- 1.3.6.1.4.1.1332.1.1.5.3.3.5.1
		msanMulticastProfileTable OBJECT-TYPE
			SYNTAX SEQUENCE OF MsanMulticastProfileEntry
			MAX-ACCESS not-accessible
			STATUS current
			DESCRIPTION
				"Multicast Profile table "
			::= { msanMulticastProfile 1 }

		
		-- 1.3.6.1.4.1.1332.1.1.5.3.3.5.1.1
		msanMulticastProfileEntry OBJECT-TYPE
			SYNTAX MsanMulticastProfileEntry
			MAX-ACCESS not-accessible
			STATUS current
			DESCRIPTION
				"Multicast Profile table entry."
			INDEX { msanMulticastProfileName }
			::= { msanMulticastProfileTable 1 }

		
		MsanMulticastProfileEntry ::=
			SEQUENCE { 
				msanMulticastProfileName
					DisplayString,
				msanMulticastProfileProtection
					INTEGER,
				msanMulticastProfileStatus
					INTEGER,
				msanMulticastProfileIgmpSnooping
					INTEGER,
				msanMulticastProfileIgmpSnoopingFastLeave
					INTEGER,
				msanMulticastProfileIgmpSnoopingSuppression
					INTEGER,
				msanMulticastProfileIgmpProxy
					INTEGER,
				msanMulticastProfileIgmpProxyIpAddress
					IpAddress,
				msanMulticastProfileIgmpFiltering
					INTEGER,
				msanMulticastProfileMulticastGroupLimit
					Unsigned32,
				msanMulticastProfileMvr
					INTEGER,
				msanMulticastProfileDescription
					DisplayString,
				msanMulticastProfileRowStatus
					RowStatus,
				msanMulticastProfileIgmpProxyProtocolVersion
					INTEGER,
				msanMulticastProfileUsage
					INTEGER
			 }

		-- 1.3.6.1.4.1.1332.1.1.5.3.3.5.1.1.1
		msanMulticastProfileName OBJECT-TYPE
			SYNTAX DisplayString (SIZE (1..32))
			MAX-ACCESS not-accessible
			STATUS current
			DESCRIPTION
				"Name for the Multicast profile."
			::= { msanMulticastProfileEntry 1 }

		
		-- 1.3.6.1.4.1.1332.1.1.5.3.3.5.1.1.2
		msanMulticastProfileProtection OBJECT-TYPE
			SYNTAX INTEGER
				{
				unprotected(0),
				protected(1)
				}
			MAX-ACCESS read-write
			STATUS obsolete
			DESCRIPTION
				"If protection flag is set to protected (1), other profile values cannot be edited.
				
				Protection flag is always  protected (1) and it can't be changed if  profile is assigned as dynamic:
				msanMulticastProfileStatus = dynamic(2)"
			DEFVAL { unprotected }
			::= { msanMulticastProfileEntry 2 }

		
		-- 1.3.6.1.4.1.1332.1.1.5.3.3.5.1.1.3
		msanMulticastProfileStatus OBJECT-TYPE
			SYNTAX INTEGER
				{
				static(1),
				dynamic(2)
				}
			MAX-ACCESS read-only
			STATUS obsolete
			DESCRIPTION
				"Profile status. 
				If status is dynamic, profile values can't be edited."
			::= { msanMulticastProfileEntry 3 }

		
		-- 1.3.6.1.4.1.1332.1.1.5.3.3.5.1.1.4
		msanMulticastProfileIgmpSnooping OBJECT-TYPE
			SYNTAX INTEGER
				{
				disableAndDiscard(0),
				enable(1),
				enableAndUnknownGroupFlood(2),
				disableAndBroadcast(3)
				}
			MAX-ACCESS read-write
			STATUS current
			DESCRIPTION
				"IGMP snnoping"
			DEFVAL { disableAndDiscard }
			::= { msanMulticastProfileEntry 4 }

		
		-- 1.3.6.1.4.1.1332.1.1.5.3.3.5.1.1.5
		msanMulticastProfileIgmpSnoopingFastLeave OBJECT-TYPE
			SYNTAX INTEGER
				{
				disable(0),
				enable(1)
				}
			MAX-ACCESS read-write
			STATUS current
			DESCRIPTION
				"IGMP Snooping Fast Leave."
			DEFVAL { disable }
			::= { msanMulticastProfileEntry 5 }

		
		-- 1.3.6.1.4.1.1332.1.1.5.3.3.5.1.1.6
		msanMulticastProfileIgmpSnoopingSuppression OBJECT-TYPE
			SYNTAX INTEGER
				{
				disable(0),
				enable(1)
				}
			MAX-ACCESS read-write
			STATUS current
			DESCRIPTION
				"IGMP Snooping Suppression."
			DEFVAL { disable }
			::= { msanMulticastProfileEntry 6 }

		
		-- 1.3.6.1.4.1.1332.1.1.5.3.3.5.1.1.7
		msanMulticastProfileIgmpProxy OBJECT-TYPE
			SYNTAX INTEGER
				{
				disable(0),
				enable(1)
				}
			MAX-ACCESS read-write
			STATUS current
			DESCRIPTION
				"IGMP proxy."
			DEFVAL { disable }
			::= { msanMulticastProfileEntry 7 }

		
		-- 1.3.6.1.4.1.1332.1.1.5.3.3.5.1.1.8
		msanMulticastProfileIgmpProxyIpAddress OBJECT-TYPE
			SYNTAX IpAddress
			MAX-ACCESS read-write
			STATUS current
			DESCRIPTION
				"IGMP proxy IP address."
			::= { msanMulticastProfileEntry 8 }

		
		-- 1.3.6.1.4.1.1332.1.1.5.3.3.5.1.1.9
		msanMulticastProfileIgmpFiltering OBJECT-TYPE
			SYNTAX INTEGER
				{
				allowAll(0),
				allowReports(1),
				allowQueries(2),
				dropAll(3)
				}
			MAX-ACCESS read-write
			STATUS current
			DESCRIPTION
				"IGMP filtering."
			DEFVAL { allowReports }
			::= { msanMulticastProfileEntry 9 }

		
		-- 1.3.6.1.4.1.1332.1.1.5.3.3.5.1.1.10
		msanMulticastProfileMulticastGroupLimit OBJECT-TYPE
			SYNTAX Unsigned32 (0..30)
			MAX-ACCESS read-write
			STATUS current
			DESCRIPTION
				"Multicast group limit. 
				A value of 0 indicates not limit."
			::= { msanMulticastProfileEntry 10 }

		
		-- 1.3.6.1.4.1.1332.1.1.5.3.3.5.1.1.11
		msanMulticastProfileMvr OBJECT-TYPE
			SYNTAX INTEGER
				{
				disable(0),
				enable(1)
				}
			MAX-ACCESS read-write
			STATUS current
			DESCRIPTION
				"Multicast VLAN Registration."
			DEFVAL { disable }
			::= { msanMulticastProfileEntry 11 }

		
		-- 1.3.6.1.4.1.1332.1.1.5.3.3.5.1.1.12
		msanMulticastProfileDescription OBJECT-TYPE
			SYNTAX DisplayString (SIZE (0..255))
			MAX-ACCESS read-write
			STATUS current
			DESCRIPTION
				"Attribute specifies text which describes the associated object."
			::= { msanMulticastProfileEntry 12 }

		
		-- 1.3.6.1.4.1.1332.1.1.5.3.3.5.1.1.13
		msanMulticastProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastProfileEntry 13 }

		
		-- 1.3.6.1.4.1.1332.1.1.5.3.3.5.1.1.14
		msanMulticastProfileIgmpProxyProtocolVersion OBJECT-TYPE
			SYNTAX INTEGER
				{
				useGlobalIgmpSettings(1),
				igmpv2(2),
				igmpv3(3)
				}
			MAX-ACCESS read-write
			STATUS current
			DESCRIPTION
				"IGMP version of IGMP message sent by Proxy in downstream direction."
			DEFVAL { useGlobalIgmpSettings }
			::= { msanMulticastProfileEntry 14 }

		
		-- 1.3.6.1.4.1.1332.1.1.5.3.3.5.1.1.15
		msanMulticastProfileUsage OBJECT-TYPE
			SYNTAX INTEGER
				{
				attached(1),
				notAttached(2)
				}
			MAX-ACCESS read-only
			STATUS current
			DESCRIPTION
				"Profile usage.
				If profile is attached,  profile values can't be edited."
			::= { msanMulticastProfileEntry 15 }

		
		-- 1.3.6.1.4.1.1332.1.1.5.3.3.5.2
		msanMulticastProfileStaticGroupTable OBJECT-TYPE
			SYNTAX SEQUENCE OF MsanMulticastProfileStaticGroupEntry
			MAX-ACCESS not-accessible
			STATUS current
			DESCRIPTION
				"Connection between 
				multicast_profile and multicast_static_group table "
			::= { msanMulticastProfile 2 }

		
		-- 1.3.6.1.4.1.1332.1.1.5.3.3.5.2.1
		msanMulticastProfileStaticGroupEntry OBJECT-TYPE
			SYNTAX MsanMulticastProfileStaticGroupEntry
			MAX-ACCESS not-accessible
			STATUS current
			DESCRIPTION
				"Multicast Profile Group table entry."
			INDEX { msanMulticastProfileName, msanMulticastProfileStaticGroupIpAddr }
			::= { msanMulticastProfileStaticGroupTable 1 }

		
		MsanMulticastProfileStaticGroupEntry ::=
			SEQUENCE { 
				msanMulticastProfileStaticGroupIpAddr
					IpAddress,
				msanMulticastProfileStaticGroupRowStatus
					RowStatus
			 }

		-- 1.3.6.1.4.1.1332.1.1.5.3.3.5.2.1.1
		msanMulticastProfileStaticGroupIpAddr OBJECT-TYPE
			SYNTAX IpAddress
			MAX-ACCESS not-accessible
			STATUS current
			DESCRIPTION
				"Description."
			::= { msanMulticastProfileStaticGroupEntry 1 }

		
		-- 1.3.6.1.4.1.1332.1.1.5.3.3.5.2.1.9
		msanMulticastProfileStaticGroupRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastProfileStaticGroupEntry 9 }

		
		-- 1.3.6.1.4.1.1332.1.1.5.3.3.6
		msanSecurityProfile OBJECT IDENTIFIER ::= { msanProfiles 6 }

		
		-- 1.3.6.1.4.1.1332.1.1.5.3.3.6.1
		msanSecurityProfileTable OBJECT-TYPE
			SYNTAX SEQUENCE OF MsanSecurityProfileEntry
			MAX-ACCESS not-accessible
			STATUS current
			DESCRIPTION
				"Security Profile table "
			::= { msanSecurityProfile 1 }

		
		-- 1.3.6.1.4.1.1332.1.1.5.3.3.6.1.1
		msanSecurityProfileEntry OBJECT-TYPE
			SYNTAX MsanSecurityProfileEntry
			MAX-ACCESS not-accessible
			STATUS current
			DESCRIPTION
				"Security Profile table entry."
			INDEX { msanSecurityProfileName }
			::= { msanSecurityProfileTable 1 }

		
		MsanSecurityProfileEntry ::=
			SEQUENCE { 
				msanSecurityProfileName
					DisplayString,
				msanSecurityProfileProtection
					INTEGER,
				msanSecurityProfileStatus
					INTEGER,
				msanSecurityProfileProtectedPort
					INTEGER,
				msanSecurityProfileMacSg
					INTEGER,
				msanSecurityProfileMacLimit
					Unsigned32,
				msanSecurityProfilePortSecurity
					INTEGER,
				msanSecurityProfileIpSg
					INTEGER,
				msanSecurityProfileIpSgBindingLimit
					Unsigned32,
				msanSecurityProfileIpSgFilteringMode
					INTEGER,
				msanSecurityProfileArpInspec
					INTEGER,
				msanSecurityProfileMacForward
					INTEGER,
				msanSecurityProfileDescription
					DisplayString,
				msanSecurityProfileRowStatus
					RowStatus,
				msanSecurityProfileIpSgIpv6
					INTEGER,
				msanSecurityProfileIpSgBindingLimitDhcpv6
					Unsigned32,
				msanSecurityProfileIpSgBindingLimitND
					Unsigned32,
				msanSecurityProfileStormControlBroadcast
					Integer32,
				msanSecurityProfileStormControlMulticast
					Integer32,
				msanSecurityProfileStormControlUnicast
					Integer32,
				msanSecurityProfileAppRateLimitDhcp
					Integer32,
				msanSecurityProfileAppRateLimitIgmp
					Integer32,
				msanSecurityProfileAppRateLimitPppoe
					Integer32,
				msanSecurityProfileAppRateLimitStp
					Integer32,
				msanSecurityProfileAppRateLimitMn
					Integer32,
				msanSecurityProfileUsage
					INTEGER
			 }

		-- 1.3.6.1.4.1.1332.1.1.5.3.3.6.1.1.1
		msanSecurityProfileName OBJECT-TYPE
			SYNTAX DisplayString (SIZE (1..32))
			MAX-ACCESS not-accessible
			STATUS current
			DESCRIPTION
				"Name of the security profile."
			::= { msanSecurityProfileEntry 1 }

		
		-- 1.3.6.1.4.1.1332.1.1.5.3.3.6.1.1.2
		msanSecurityProfileProtection OBJECT-TYPE
			SYNTAX INTEGER
				{
				unprotected(0),
				protected(1)
				}
			MAX-ACCESS read-write
			STATUS obsolete
			DESCRIPTION
				"If protection flag is set to protected (1), other profile values cannot be edited.
				
				Protection flag is always  protected (1) and it can't be changed if  profile is assigned as dynamic:
				msanSecurityProfileStatus = dynamic(2)"
			DEFVAL { unprotected }
			::= { msanSecurityProfileEntry 2 }

		
		-- 1.3.6.1.4.1.1332.1.1.5.3.3.6.1.1.3
		msanSecurityProfileStatus OBJECT-TYPE
			SYNTAX INTEGER
				{
				static(1),
				dynamic(2)
				}
			MAX-ACCESS read-only
			STATUS obsolete
			DESCRIPTION
				"Profile status. 
				If status is dynamic, profile values can't be edited."
			::= { msanSecurityProfileEntry 3 }

		
		-- 1.3.6.1.4.1.1332.1.1.5.3.3.6.1.1.4
		msanSecurityProfileProtectedPort OBJECT-TYPE
			SYNTAX INTEGER
				{
				disable(0),
				enable(1)
				}
			MAX-ACCESS read-write
			STATUS current
			DESCRIPTION
				"Security profile protected port"
			DEFVAL { disable }
			::= { msanSecurityProfileEntry 4 }

		
		-- 1.3.6.1.4.1.1332.1.1.5.3.3.6.1.1.5
		msanSecurityProfileMacSg OBJECT-TYPE
			SYNTAX INTEGER
				{
				disable(0),
				enable(1)
				}
			MAX-ACCESS read-write
			STATUS current
			DESCRIPTION
				"Mac source guard"
			DEFVAL { disable }
			::= { msanSecurityProfileEntry 5 }

		
		-- 1.3.6.1.4.1.1332.1.1.5.3.3.6.1.1.6
		msanSecurityProfileMacLimit OBJECT-TYPE
			SYNTAX Unsigned32 (0..64)
			MAX-ACCESS read-write
			STATUS current
			DESCRIPTION
				"MAC limit
				A value of 0 indicates that parameter has not been defined."
			DEFVAL { 0 }
			::= { msanSecurityProfileEntry 6 }

		
		-- 1.3.6.1.4.1.1332.1.1.5.3.3.6.1.1.7
		msanSecurityProfilePortSecurity OBJECT-TYPE
			SYNTAX INTEGER
				{
				disable(0),
				enable(1)
				}
			MAX-ACCESS read-write
			STATUS current
			DESCRIPTION
				"Port security"
			DEFVAL { disable }
			::= { msanSecurityProfileEntry 7 }

		
		-- 1.3.6.1.4.1.1332.1.1.5.3.3.6.1.1.8
		msanSecurityProfileIpSg OBJECT-TYPE
			SYNTAX INTEGER
				{
				disable(0),
				enable(1)
				}
			MAX-ACCESS read-write
			STATUS current
			DESCRIPTION
				"IP source guard"
			DEFVAL { disable }
			::= { msanSecurityProfileEntry 8 }

		
		-- 1.3.6.1.4.1.1332.1.1.5.3.3.6.1.1.9
		msanSecurityProfileIpSgBindingLimit OBJECT-TYPE
			SYNTAX Unsigned32 (0..15)
			MAX-ACCESS read-write
			STATUS current
			DESCRIPTION
				"IP source guard binding limit.
				Value 0 defines there is no limit.
				"
			DEFVAL { 4 }
			::= { msanSecurityProfileEntry 9 }

		
		-- 1.3.6.1.4.1.1332.1.1.5.3.3.6.1.1.10
		msanSecurityProfileIpSgFilteringMode OBJECT-TYPE
			SYNTAX INTEGER
				{
				ipSourceAddress(1),
				ipAndMacSourceAddress(2)
				}
			MAX-ACCESS read-write
			STATUS current
			DESCRIPTION
				"IP source guard filtering mode"
			DEFVAL { ipAndMacSourceAddress }
			::= { msanSecurityProfileEntry 10 }

		
		-- 1.3.6.1.4.1.1332.1.1.5.3.3.6.1.1.12
		msanSecurityProfileArpInspec OBJECT-TYPE
			SYNTAX INTEGER
				{
				disable(0),
				enable(1)
				}
			MAX-ACCESS read-write
			STATUS current
			DESCRIPTION
				"Dynamic ARP inspection"
			DEFVAL { disable }
			::= { msanSecurityProfileEntry 12 }

		
		-- 1.3.6.1.4.1.1332.1.1.5.3.3.6.1.1.13
		msanSecurityProfileMacForward OBJECT-TYPE
			SYNTAX INTEGER
				{
				disable(0),
				enable(1)
				}
			MAX-ACCESS read-write
			STATUS current
			DESCRIPTION
				"MAC forwarding"
			DEFVAL { disable }
			::= { msanSecurityProfileEntry 13 }

		
		-- 1.3.6.1.4.1.1332.1.1.5.3.3.6.1.1.14
		msanSecurityProfileDescription OBJECT-TYPE
			SYNTAX DisplayString (SIZE (0..255))
			MAX-ACCESS read-write
			STATUS current
			DESCRIPTION
				"Attribute specifies text which describes the associated object."
			::= { msanSecurityProfileEntry 14 }

		
		-- 1.3.6.1.4.1.1332.1.1.5.3.3.6.1.1.15
		msanSecurityProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanSecurityProfileEntry 15 }

		
		-- 1.3.6.1.4.1.1332.1.1.5.3.3.6.1.1.16
		msanSecurityProfileIpSgIpv6 OBJECT-TYPE
			SYNTAX INTEGER
				{
				disable(0),
				enable(1)
				}
			MAX-ACCESS read-write
			STATUS current
			DESCRIPTION
				"IPv6 source guard"
			DEFVAL { disable }
			::= { msanSecurityProfileEntry 16 }

		
		-- 1.3.6.1.4.1.1332.1.1.5.3.3.6.1.1.17
		msanSecurityProfileIpSgBindingLimitDhcpv6 OBJECT-TYPE
			SYNTAX Unsigned32 (0..15)
			MAX-ACCESS read-write
			STATUS current
			DESCRIPTION
				"IPSG binding limit for DHCPv6 (IPv6 DHCP).
				Value 0 defines there is no limit.
				"
			DEFVAL { 4 }
			::= { msanSecurityProfileEntry 17 }

		
		-- 1.3.6.1.4.1.1332.1.1.5.3.3.6.1.1.18
		msanSecurityProfileIpSgBindingLimitND OBJECT-TYPE
			SYNTAX Unsigned32 (0..15)
			MAX-ACCESS read-write
			STATUS current
			DESCRIPTION
				"IPSG binding limit for ND (IPv6 Neighbor Discovery).
				Value 0 defines there is no limit.
				"
			DEFVAL { 4 }
			::= { msanSecurityProfileEntry 18 }

		
		-- 1.3.6.1.4.1.1332.1.1.5.3.3.6.1.1.19
		msanSecurityProfileStormControlBroadcast OBJECT-TYPE
			SYNTAX Integer32 (-1..65535)
			UNITS "pps"
			MAX-ACCESS read-write
			STATUS current
			DESCRIPTION
				"Max data rate (pps)  of broadcast packets on port at which storm control drops them.
				Value -1 defines that functionality is disabled."
			DEFVAL { -1 }
			::= { msanSecurityProfileEntry 19 }

		
		-- 1.3.6.1.4.1.1332.1.1.5.3.3.6.1.1.20
		msanSecurityProfileStormControlMulticast OBJECT-TYPE
			SYNTAX Integer32 (-1..65535)
			UNITS "pps"
			MAX-ACCESS read-write
			STATUS current
			DESCRIPTION
				"Max data rate (pps)  of multicast packets on port at which storm control drops them.
				Value -1 defines that functionality is disabled."
			DEFVAL { -1 }
			::= { msanSecurityProfileEntry 20 }

		
		-- 1.3.6.1.4.1.1332.1.1.5.3.3.6.1.1.21
		msanSecurityProfileStormControlUnicast OBJECT-TYPE
			SYNTAX Integer32 (-1..65535)
			UNITS "pps"
			MAX-ACCESS read-write
			STATUS current
			DESCRIPTION
				"Max data rate (pps)  of unicast packets on port at which storm control drops them.
				Value -1 defines that functionality is disabled."
			DEFVAL { -1 }
			::= { msanSecurityProfileEntry 21 }

		
		-- 1.3.6.1.4.1.1332.1.1.5.3.3.6.1.1.22
		msanSecurityProfileAppRateLimitDhcp OBJECT-TYPE
			SYNTAX Integer32 (-1..1000)
			UNITS "pps"
			MAX-ACCESS read-write
			STATUS current
			DESCRIPTION
				"Max data rate (pps)  of DHCP packets on port  at which application rate limit drops them.
				Value -1 defines that functionality is disabled.
				"
			DEFVAL { -1 }
			::= { msanSecurityProfileEntry 22 }

		
		-- 1.3.6.1.4.1.1332.1.1.5.3.3.6.1.1.23
		msanSecurityProfileAppRateLimitIgmp OBJECT-TYPE
			SYNTAX Integer32 (-1..1000)
			UNITS "pps"
			MAX-ACCESS read-write
			STATUS current
			DESCRIPTION
				"Max data rate (pps)  of IGMP packets on port  at which application rate limit drops them.
				Value -1 defines that functionality is disabled.
				"
			DEFVAL { -1 }
			::= { msanSecurityProfileEntry 23 }

		
		-- 1.3.6.1.4.1.1332.1.1.5.3.3.6.1.1.24
		msanSecurityProfileAppRateLimitPppoe OBJECT-TYPE
			SYNTAX Integer32 (-1..1000)
			UNITS "pps"
			MAX-ACCESS read-write
			STATUS current
			DESCRIPTION
				"Max data rate (pps)  of PPPoE packets on port  at which application rate limit drops them.
				Value -1 defines that functionality is disabled.
				"
			DEFVAL { -1 }
			::= { msanSecurityProfileEntry 24 }

		
		-- 1.3.6.1.4.1.1332.1.1.5.3.3.6.1.1.25
		msanSecurityProfileAppRateLimitStp OBJECT-TYPE
			SYNTAX Integer32 (-1..1000)
			UNITS "pps"
			MAX-ACCESS read-write
			STATUS current
			DESCRIPTION
				"Max data rate (pps)  of STP packets on port  at which application rate limit drops them.
				Value -1 defines that functionality is disabled.
				"
			DEFVAL { -1 }
			::= { msanSecurityProfileEntry 25 }

		
		-- 1.3.6.1.4.1.1332.1.1.5.3.3.6.1.1.26
		msanSecurityProfileAppRateLimitMn OBJECT-TYPE
			SYNTAX Integer32 (-1..1000)
			UNITS "pps"
			MAX-ACCESS read-write
			STATUS current
			DESCRIPTION
				"Max data rate (pps)  of IP packets on MN CPU port  at which application rate limit drops them.
				Value -1 defines that functionality is disabled.
				"
			DEFVAL { -1 }
			::= { msanSecurityProfileEntry 26 }

		
		-- 1.3.6.1.4.1.1332.1.1.5.3.3.6.1.1.27
		msanSecurityProfileUsage OBJECT-TYPE
			SYNTAX INTEGER
				{
				attached(1),
				notAttached(2)
				}
			MAX-ACCESS read-only
			STATUS current
			DESCRIPTION
				"Profile usage.
				If profile is attached,  profile values can't be edited."
			::= { msanSecurityProfileEntry 27 }

		
		-- 1.3.6.1.4.1.1332.1.1.5.3.3.6.3
		msanSecurityAclProfileTable OBJECT-TYPE
			SYNTAX SEQUENCE OF MsanSecurityAclProfileEntry
			MAX-ACCESS not-accessible
			STATUS current
			DESCRIPTION
				"A connection between security profiles and access lists"
			::= { msanSecurityProfile 3 }

		
		-- 1.3.6.1.4.1.1332.1.1.5.3.3.6.3.1
		msanSecurityAclProfileEntry OBJECT-TYPE
			SYNTAX MsanSecurityAclProfileEntry
			MAX-ACCESS not-accessible
			STATUS current
			DESCRIPTION
				"Service Profile Port table entry."
			INDEX { msanSecurityProfileName, msanSecurityAclProfileAclDirection, msanSecurityAclProfileSequence, msanSecurityAclProfileAclType, msanSecurityAclProfileAclId
				 }
			::= { msanSecurityAclProfileTable 1 }

		
		MsanSecurityAclProfileEntry ::=
			SEQUENCE { 
				msanSecurityAclProfileAclDirection
					INTEGER,
				msanSecurityAclProfileSequence
					Unsigned32,
				msanSecurityAclProfileAclType
					INTEGER,
				msanSecurityAclProfileAclId
					Unsigned32,
				msanSecurityAclProfileRowStatus
					RowStatus
			 }

		-- 1.3.6.1.4.1.1332.1.1.5.3.3.6.3.1.1
		msanSecurityAclProfileAclDirection OBJECT-TYPE
			SYNTAX INTEGER
				{
				inbound(1),
				outbound(2)
				}
			MAX-ACCESS not-accessible
			STATUS current
			DESCRIPTION
				"The direction to which this ACL instance applies."
			::= { msanSecurityAclProfileEntry 1 }

		
		-- 1.3.6.1.4.1.1332.1.1.5.3.3.6.3.1.2
		msanSecurityAclProfileSequence OBJECT-TYPE
			SYNTAX Unsigned32 (1..2147483647)
			MAX-ACCESS not-accessible
			STATUS current
			DESCRIPTION
				"The relative evaluation sequence of this ACL for this
				interface and direction.  When multiple ACLs are allowed 
				for a given interface and direction, the sequence number 
				determines the order in which the list of ACLs are evaluated,
				with lower sequence numbers given higher precedence.  The
				sequence number value is arbitrary, but must be a unique
				non-zero value for a given interface and direction.
				
				Setting this object to an existing sequence number 
				value for a given interface and direction causes the 
				ACL corresponding to that value to be replaced with this ACL."
			::= { msanSecurityAclProfileEntry 2 }

		
		-- 1.3.6.1.4.1.1332.1.1.5.3.3.6.3.1.3
		msanSecurityAclProfileAclType OBJECT-TYPE
			SYNTAX INTEGER
				{
				ip(1),
				mac(2)
				}
			MAX-ACCESS not-accessible
			STATUS current
			DESCRIPTION
				"The type of this ACL, which is used to interpret the 
				aclIfId object value."
			::= { msanSecurityAclProfileEntry 3 }

		
		-- 1.3.6.1.4.1.1332.1.1.5.3.3.6.3.1.4
		msanSecurityAclProfileAclId OBJECT-TYPE
			SYNTAX Unsigned32
			MAX-ACCESS not-accessible
			STATUS current
			DESCRIPTION
				"The ACL identifier value. 
				For the IP ACLs, the actual ACL number is its identifier
				as follows:  IP standard ranges from 1-99, IP extended
				ranges from 100-199, and IP advanced ranges 200-299."
			::= { msanSecurityAclProfileEntry 4 }

		
		-- 1.3.6.1.4.1.1332.1.1.5.3.3.6.3.1.5
		msanSecurityAclProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanSecurityAclProfileEntry 5 }

		
		-- 1.3.6.1.4.1.1332.1.1.5.3.3.7
		msanL2cpProfile OBJECT IDENTIFIER ::= { msanProfiles 7 }

		
		-- 1.3.6.1.4.1.1332.1.1.5.3.3.7.1
		msanL2cpProfileTable OBJECT-TYPE
			SYNTAX SEQUENCE OF MsanL2cpProfileEntry
			MAX-ACCESS not-accessible
			STATUS current
			DESCRIPTION
				"L2CP (Layer 2 Control Protocol) Profile table "
			::= { msanL2cpProfile 1 }

		
		-- 1.3.6.1.4.1.1332.1.1.5.3.3.7.1.1
		msanL2cpProfileEntry OBJECT-TYPE
			SYNTAX MsanL2cpProfileEntry
			MAX-ACCESS not-accessible
			STATUS current
			DESCRIPTION
				"L2cp Profile table entry."
			INDEX { msanL2cpProfileName }
			::= { msanL2cpProfileTable 1 }

		
		MsanL2cpProfileEntry ::=
			SEQUENCE { 
				msanL2cpProfileName
					DisplayString,
				msanL2cpProfileProtection
					INTEGER,
				msanL2cpProfileStatus
					INTEGER,
				msanL2cpProfileDescription
					DisplayString,
				msanL2cpProfileRowStatus
					RowStatus,
				msanL2cpProfileUsage
					INTEGER
			 }

		-- 1.3.6.1.4.1.1332.1.1.5.3.3.7.1.1.1
		msanL2cpProfileName OBJECT-TYPE
			SYNTAX DisplayString (SIZE (1..32))
			MAX-ACCESS not-accessible
			STATUS current
			DESCRIPTION
				"Name of the L2CP profile."
			::= { msanL2cpProfileEntry 1 }

		
		-- 1.3.6.1.4.1.1332.1.1.5.3.3.7.1.1.2
		msanL2cpProfileProtection OBJECT-TYPE
			SYNTAX INTEGER
				{
				unprotected(0),
				protected(1)
				}
			MAX-ACCESS read-write
			STATUS obsolete
			DESCRIPTION
				"If protection flag is set to protected (1), other profile values cannot be edited.
				
				Protection flag is always  protected (1) and it can't be changed if  profile is assigned as dynamic:
				msanL2cpProfileStatus = dynamic(2)"
			DEFVAL { unprotected }
			::= { msanL2cpProfileEntry 2 }

		
		-- 1.3.6.1.4.1.1332.1.1.5.3.3.7.1.1.3
		msanL2cpProfileStatus OBJECT-TYPE
			SYNTAX INTEGER
				{
				static(1),
				dynamic(2)
				}
			MAX-ACCESS read-only
			STATUS obsolete
			DESCRIPTION
				"Profile status. 
				If status is dynamic, profile values can't be edited."
			::= { msanL2cpProfileEntry 3 }

		
		-- 1.3.6.1.4.1.1332.1.1.5.3.3.7.1.1.4
		msanL2cpProfileDescription OBJECT-TYPE
			SYNTAX DisplayString (SIZE (0..255))
			MAX-ACCESS read-write
			STATUS current
			DESCRIPTION
				"Attribute specifies text which describes the associated object."
			::= { msanL2cpProfileEntry 4 }

		
		-- 1.3.6.1.4.1.1332.1.1.5.3.3.7.1.1.5
		msanL2cpProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanL2cpProfileEntry 5 }

		
		-- 1.3.6.1.4.1.1332.1.1.5.3.3.7.1.1.6
		msanL2cpProfileUsage OBJECT-TYPE
			SYNTAX INTEGER
				{
				attached(1),
				notAttached(2)
				}
			MAX-ACCESS read-only
			STATUS current
			DESCRIPTION
				"Profile usage.
				If profile is attached,  profile values can't be edited."
			::= { msanL2cpProfileEntry 6 }

		
		-- 1.3.6.1.4.1.1332.1.1.5.3.3.7.2
		msanL2cpProtocolTable OBJECT-TYPE
			SYNTAX SEQUENCE OF MsanL2cpProtocolEntry
			MAX-ACCESS not-accessible
			STATUS current
			DESCRIPTION
				"Table with list of L2CP protocols"
			::= { msanL2cpProfile 2 }

		
		-- 1.3.6.1.4.1.1332.1.1.5.3.3.7.2.1
		msanL2cpProtocolEntry OBJECT-TYPE
			SYNTAX MsanL2cpProtocolEntry
			MAX-ACCESS not-accessible
			STATUS current
			DESCRIPTION
				"Description."
			INDEX { msanL2cpProtocolName }
			::= { msanL2cpProtocolTable 1 }

		
		MsanL2cpProtocolEntry ::=
			SEQUENCE { 
				msanL2cpProtocolName
					DisplayString,
				msanL2cpProtocolMacDestAddr
					MacAddress,
				msanL2cpProtocolEthertype
					Integer32,
				msanL2cpProtocolSubtype
					Integer32,
				msanL2cpProtocolRowStatus
					RowStatus
			 }

		-- 1.3.6.1.4.1.1332.1.1.5.3.3.7.2.1.1
		msanL2cpProtocolName OBJECT-TYPE
			SYNTAX DisplayString (SIZE (1..32))
			MAX-ACCESS not-accessible
			STATUS current
			DESCRIPTION
				"L2CP protocol name"
			::= { msanL2cpProtocolEntry 1 }

		
		-- 1.3.6.1.4.1.1332.1.1.5.3.3.7.2.1.2
		msanL2cpProtocolMacDestAddr OBJECT-TYPE
			SYNTAX MacAddress
			MAX-ACCESS read-write
			STATUS current
			DESCRIPTION
				"MAC destination address of L2CP protocol.
				Empty string indicates that protocol is related to any MAC address."
			DEFVAL { ''b }
			::= { msanL2cpProtocolEntry 2 }

		
		-- 1.3.6.1.4.1.1332.1.1.5.3.3.7.2.1.3
		msanL2cpProtocolEthertype OBJECT-TYPE
			SYNTAX Integer32 (0..65535)
			MAX-ACCESS read-write
			STATUS current
			DESCRIPTION
				"L2CP protocol Ethertype.
				A value of 65535 indicates that parameter has not been defined."
			DEFVAL { 65535 }
			::= { msanL2cpProtocolEntry 3 }

		
		-- 1.3.6.1.4.1.1332.1.1.5.3.3.7.2.1.4
		msanL2cpProtocolSubtype OBJECT-TYPE
			SYNTAX Integer32 (0..255)
			MAX-ACCESS read-write
			STATUS current
			DESCRIPTION
				"L2CP protocol subtype.
				A value of 255 indicates that parameter has not been defined."
			DEFVAL { 255 }
			::= { msanL2cpProtocolEntry 4 }

		
		-- 1.3.6.1.4.1.1332.1.1.5.3.3.7.2.1.5
		msanL2cpProtocolRowStatus OBJECT-TYPE
			SYNTAX RowStatus
			MAX-ACCESS read-create
			STATUS current
			DESCRIPTION
				"The row status object controls the creation/deletion of rows in this table. 
				Its semantics are the same as those for the RowStatus textual convention specified for SNMPv2.
				For row creation use createAndWait(5).
				Value active(1) will activate and value destroy(6) will remove this entry.
				Other values are currently not supported."
			::= { msanL2cpProtocolEntry 5 }

		
		-- 1.3.6.1.4.1.1332.1.1.5.3.3.7.3
		msanL2cpProfileProtocolTable OBJECT-TYPE
			SYNTAX SEQUENCE OF MsanL2cpProfileProtocolEntry
			MAX-ACCESS not-accessible
			STATUS current
			DESCRIPTION
				"Table with connection between profiles and protocols"
			::= { msanL2cpProfile 3 }

		
		-- 1.3.6.1.4.1.1332.1.1.5.3.3.7.3.1
		msanL2cpProfileProtocolEntry OBJECT-TYPE
			SYNTAX MsanL2cpProfileProtocolEntry
			MAX-ACCESS not-accessible
			STATUS current
			DESCRIPTION
				"Description."
			INDEX { msanL2cpProfileName, msanL2cpProtocolName }
			::= { msanL2cpProfileProtocolTable 1 }

		
		MsanL2cpProfileProtocolEntry ::=
			SEQUENCE { 
				msanL2cpProfileProtocolRule
					INTEGER,
				msanL2cpProfileProtocolRowStatus
					RowStatus
			 }

		-- 1.3.6.1.4.1.1332.1.1.5.3.3.7.3.1.1
		msanL2cpProfileProtocolRule OBJECT-TYPE
			SYNTAX INTEGER
				{
				discard(1),
				peer(2),
				tunnel(3)
				}
			MAX-ACCESS read-write
			STATUS current
			DESCRIPTION
				"L2CP protocol rule."
			::= { msanL2cpProfileProtocolEntry 1 }

		
		-- 1.3.6.1.4.1.1332.1.1.5.3.3.7.3.1.2
		msanL2cpProfileProtocolRowStatus OBJECT-TYPE
			SYNTAX RowStatus
			MAX-ACCESS read-create
			STATUS current
			DESCRIPTION
				"The row status object controls the creation/deletion of rows in this table. 
				Its semantics are the same as those for the RowStatus textual convention specified for SNMPv2.
				For row creation use createAndWait(5).
				Value active(1) will activate and value destroy(6) will remove this entry.
				Other values are currently not supported.
				
				Row can be activated only when msanL2cpProfileProtocolRule is set."
			::= { msanL2cpProfileProtocolEntry 2 }

		
		-- 1.3.6.1.4.1.1332.1.1.5.3.3.7.4
		msanL2cpProfileVlanTable OBJECT-TYPE
			SYNTAX SEQUENCE OF MsanL2cpProfileVlanEntry
			MAX-ACCESS not-accessible
			STATUS current
			DESCRIPTION
				"Table is used for connecting l2cp profile with vlan_id."
			::= { msanL2cpProfile 4 }

		
		-- 1.3.6.1.4.1.1332.1.1.5.3.3.7.4.1
		msanL2cpProfileVlanEntry OBJECT-TYPE
			SYNTAX MsanL2cpProfileVlanEntry
			MAX-ACCESS not-accessible
			STATUS current
			DESCRIPTION
				"Description."
			INDEX { msanL2cpProfileName, dot1qVlanIndex }
			::= { msanL2cpProfileVlanTable 1 }

		
		MsanL2cpProfileVlanEntry ::=
			SEQUENCE { 
				msanL2cpProfileVlanRowStatus
					RowStatus
			 }

		-- 1.3.6.1.4.1.1332.1.1.5.3.3.7.4.1.1
		msanL2cpProfileVlanRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanL2cpProfileVlanEntry 1 }

		
		-- 1.3.6.1.4.1.1332.1.1.5.3.3.8
		msanXdslProfile OBJECT IDENTIFIER ::= { msanProfiles 8 }

		
		-- 1.3.6.1.4.1.1332.1.1.5.3.3.8.1
		msanXdsl2LineConfTemplateTable OBJECT-TYPE
			SYNTAX SEQUENCE OF MsanXdsl2LineConfTemplateEntry
			MAX-ACCESS not-accessible
			STATUS current
			DESCRIPTION
				"Description."
			::= { msanXdslProfile 1 }

		
		-- 1.3.6.1.4.1.1332.1.1.5.3.3.8.1.1
		msanXdsl2LineConfTemplateEntry OBJECT-TYPE
			SYNTAX MsanXdsl2LineConfTemplateEntry
			MAX-ACCESS not-accessible
			STATUS current
			DESCRIPTION
				"Description."
			AUGMENTS { xdsl2LineConfTemplateEntry }
			::= { msanXdsl2LineConfTemplateTable 1 }

		
		MsanXdsl2LineConfTemplateEntry ::=
			SEQUENCE { 
				msanXdsl2LineConfTempProtection
					INTEGER,
				msanXdsl2LineConfTempStatus
					INTEGER
			 }

		-- 1.3.6.1.4.1.1332.1.1.5.3.3.8.1.1.1
		msanXdsl2LineConfTempProtection OBJECT-TYPE
			SYNTAX INTEGER
				{
				unprotected(0),
				protected(1)
				}
			MAX-ACCESS read-write
			STATUS current
			DESCRIPTION
				"If protection flag is set to protected (1), other profile values cannot be edited.
				
				Protection flag is always  protected (1) and it can't be changed if  profile is assigned as dynamic:
				msanAclProfileStatus = dynamic(2)"
			DEFVAL { unprotected }
			::= { msanXdsl2LineConfTemplateEntry 1 }

		
		-- 1.3.6.1.4.1.1332.1.1.5.3.3.8.1.1.2
		msanXdsl2LineConfTempStatus OBJECT-TYPE
			SYNTAX INTEGER
				{
				static(1),
				dynamic(2)
				}
			MAX-ACCESS read-only
			STATUS current
			DESCRIPTION
				"Profile status. 
				If status is dynamic, profile values can't be edited."
			::= { msanXdsl2LineConfTemplateEntry 2 }

		
		-- 1.3.6.1.4.1.1332.1.1.5.3.3.8.2
		msanXdsl2LineAlarmConfTemplateTable OBJECT-TYPE
			SYNTAX SEQUENCE OF MsanXdsl2LineAlarmConfTemplateEntry
			MAX-ACCESS not-accessible
			STATUS current
			DESCRIPTION
				"Description."
			::= { msanXdslProfile 2 }

		
		-- 1.3.6.1.4.1.1332.1.1.5.3.3.8.2.1
		msanXdsl2LineAlarmConfTemplateEntry OBJECT-TYPE
			SYNTAX MsanXdsl2LineAlarmConfTemplateEntry
			MAX-ACCESS not-accessible
			STATUS current
			DESCRIPTION
				"Description."
			AUGMENTS { xdsl2LineAlarmConfTemplateEntry }
			::= { msanXdsl2LineAlarmConfTemplateTable 1 }

		
		MsanXdsl2LineAlarmConfTemplateEntry ::=
			SEQUENCE { 
				msanXdsl2LineAlarmConfTempProtection
					INTEGER,
				msanXdsl2LineAlarmConfTempStatus
					INTEGER
			 }

		-- 1.3.6.1.4.1.1332.1.1.5.3.3.8.2.1.1
		msanXdsl2LineAlarmConfTempProtection OBJECT-TYPE
			SYNTAX INTEGER
				{
				unprotected(0),
				protected(1)
				}
			MAX-ACCESS read-write
			STATUS current
			DESCRIPTION
				"If protection flag is set to protected (1), other profile values cannot be edited.
				
				Protection flag is always  protected (1) and it can't be changed if  profile is assigned as dynamic:
				msanAclProfileStatus = dynamic(2)"
			DEFVAL { unprotected }
			::= { msanXdsl2LineAlarmConfTemplateEntry 1 }

		
		-- 1.3.6.1.4.1.1332.1.1.5.3.3.8.2.1.2
		msanXdsl2LineAlarmConfTempStatus OBJECT-TYPE
			SYNTAX INTEGER
				{
				static(1),
				dynamic(2)
				}
			MAX-ACCESS read-only
			STATUS current
			DESCRIPTION
				"Profile status. 
				If status is dynamic, profile values can't be edited."
			::= { msanXdsl2LineAlarmConfTemplateEntry 2 }

		
		-- 1.3.6.1.4.1.1332.1.1.5.3.3.20
		msanOnuFlowProfile OBJECT IDENTIFIER ::= { msanProfiles 20 }

		
		-- 1.3.6.1.4.1.1332.1.1.5.3.3.20.1
		msanOnuFlowProfileTable OBJECT-TYPE
			SYNTAX SEQUENCE OF MsanOnuFlowProfileEntry
			MAX-ACCESS not-accessible
			STATUS current
			DESCRIPTION
				"Description."
			::= { msanOnuFlowProfile 1 }

		
		-- 1.3.6.1.4.1.1332.1.1.5.3.3.20.1.1
		msanOnuFlowProfileEntry OBJECT-TYPE
			SYNTAX MsanOnuFlowProfileEntry
			MAX-ACCESS not-accessible
			STATUS current
			DESCRIPTION
				"Description."
			INDEX { msanOnuFlowProfileName }
			::= { msanOnuFlowProfileTable 1 }

		
		MsanOnuFlowProfileEntry ::=
			SEQUENCE { 
				msanOnuFlowProfileName
					DisplayString,
				msanOnuFlowProfileMatchUsCVlanIdRange
					OCTET STRING,
				msanOnuFlowProfileMatchUsCPcp
					Integer32,
				msanOnuFlowProfileUsCdr
					Integer32,
				msanOnuFlowProfileUsPdr
					Integer32,
				msanOnuFlowProfileUsFlowPriority
					INTEGER,
				msanOnuFlowProfileDsFlowPriority
					INTEGER,
				msanOnuFlowProfileRowStatus
					RowStatus,
				msanOnuFlowProfileUsage
					INTEGER,
				msanOnuFlowProfileDsOnuScheduling
					INTEGER
			 }

		-- 1.3.6.1.4.1.1332.1.1.5.3.3.20.1.1.1
		msanOnuFlowProfileName OBJECT-TYPE
			SYNTAX DisplayString (SIZE (0..64))
			MAX-ACCESS not-accessible
			STATUS current
			DESCRIPTION
				"ONU Flow Profile Name."
			::= { msanOnuFlowProfileEntry 1 }

		
		-- 1.3.6.1.4.1.1332.1.1.5.3.3.20.1.1.10
		msanOnuFlowProfileMatchUsCVlanIdRange OBJECT-TYPE
			SYNTAX OCTET STRING (SIZE (0..512))
			MAX-ACCESS read-write
			STATUS current
			DESCRIPTION
				"Match ONU upstream packet frame with specified list (bitmask) of Customer VLAN Id.
				An empty string indicates that parameter has not been defined."
			DEFVAL { ''b }
			::= { msanOnuFlowProfileEntry 10 }

		
		-- 1.3.6.1.4.1.1332.1.1.5.3.3.20.1.1.11
		msanOnuFlowProfileMatchUsCPcp OBJECT-TYPE
			SYNTAX Integer32
			MAX-ACCESS read-write
			STATUS current
			DESCRIPTION
				"Match ONU upstream packet frame with specified Customer PCP (Priority Code Point) - 
				PCP is also known as class of service (CoS) bits.
				A value of -1 indicates that parameter has not been defined."
			DEFVAL { -1 }
			::= { msanOnuFlowProfileEntry 11 }

		
		-- 1.3.6.1.4.1.1332.1.1.5.3.3.20.1.1.12
		msanOnuFlowProfileUsCdr OBJECT-TYPE
			SYNTAX Integer32 (128..2500000)
			UNITS "kbps"
			MAX-ACCESS read-write
			STATUS current
			DESCRIPTION
				"ONU upstream committed data rate (E-CDR) in kbps.
				Any rate value can be entered, but is rounded up to the multiple of 64 kbps.
				
				Limitation: Commited rate cannot be higher than peak rate."
			::= { msanOnuFlowProfileEntry 12 }

		
		-- 1.3.6.1.4.1.1332.1.1.5.3.3.20.1.1.13
		msanOnuFlowProfileUsPdr OBJECT-TYPE
			SYNTAX Integer32 (128..2500000)
			UNITS "kbps"
			MAX-ACCESS read-write
			STATUS current
			DESCRIPTION
				"ONU upstream peak data rate (E-PDR) in kbps.
				Any rate value can be entered, but is rounded up to the multiple of 64 kbps.
				
				Limitation: Peak rate cannot be lower than guaranteed rate."
			::= { msanOnuFlowProfileEntry 13 }

		
		-- 1.3.6.1.4.1.1332.1.1.5.3.3.20.1.1.14
		msanOnuFlowProfileUsFlowPriority OBJECT-TYPE
			SYNTAX INTEGER (0..7)
			MAX-ACCESS read-write
			STATUS current
			DESCRIPTION
				"ONU upstream flow priority ."
			::= { msanOnuFlowProfileEntry 14 }

		
		-- 1.3.6.1.4.1.1332.1.1.5.3.3.20.1.1.15
		msanOnuFlowProfileDsFlowPriority OBJECT-TYPE
			SYNTAX INTEGER (0..7)
			MAX-ACCESS read-write
			STATUS current
			DESCRIPTION
				"ONU downstream flow priority ."
			::= { msanOnuFlowProfileEntry 15 }

		
		-- 1.3.6.1.4.1.1332.1.1.5.3.3.20.1.1.50
		msanOnuFlowProfileRowStatus OBJECT-TYPE
			SYNTAX RowStatus
			MAX-ACCESS read-write
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanOnuFlowProfileEntry 50 }

		
		-- 1.3.6.1.4.1.1332.1.1.5.3.3.20.1.1.51
		msanOnuFlowProfileUsage OBJECT-TYPE
			SYNTAX INTEGER
				{
				attached(1),
				notAttached(2)
				}
			MAX-ACCESS read-only
			STATUS current
			DESCRIPTION
				"Profile usage.
				If profile is attached,  profile values can't be edited."
			::= { msanOnuFlowProfileEntry 51 }

		
		-- 1.3.6.1.4.1.1332.1.1.5.3.3.20.1.1.52
		msanOnuFlowProfileDsOnuScheduling OBJECT-TYPE
			SYNTAX INTEGER
				{
				enable(1),
				disable(2)
				}
			MAX-ACCESS read-write
			STATUS current
			DESCRIPTION
				"ONU downstream onu scheduling"
			DEFVAL { disable }
			::= { msanOnuFlowProfileEntry 52 }

		
		-- 1.3.6.1.4.1.1332.1.1.5.3.3.21
		msanOnuVlanProfile OBJECT IDENTIFIER ::= { msanProfiles 21 }

		
		-- 1.3.6.1.4.1.1332.1.1.5.3.3.21.1
		msanOnuVlanProfileTable OBJECT-TYPE
			SYNTAX SEQUENCE OF MsanOnuVlanProfileEntry
			MAX-ACCESS not-accessible
			STATUS current
			DESCRIPTION
				"description"
			::= { msanOnuVlanProfile 1 }

		
		-- 1.3.6.1.4.1.1332.1.1.5.3.3.21.1.1
		msanOnuVlanProfileEntry OBJECT-TYPE
			SYNTAX MsanOnuVlanProfileEntry
			MAX-ACCESS not-accessible
			STATUS current
			DESCRIPTION
				"Row Description"
			INDEX { msanOnuVlanProfileName }
			::= { msanOnuVlanProfileTable 1 }

		
		MsanOnuVlanProfileEntry ::=
			SEQUENCE { 
				msanOnuVlanProfileName
					DisplayString,
				msanOnuVlanProfileDownstreamMode
					INTEGER,
				msanOnuVlanProfileInputTPID
					Unsigned32,
				msanOnuVlanProfileOutputTPID
					Unsigned32,
				msanOnuVlanProfileRowStatus
					RowStatus,
				msanOnuVlanProfileUsage
					INTEGER,
				msanOnuVlanProfileDscpPcpMap
					INTEGER
			 }

		-- 1.3.6.1.4.1.1332.1.1.5.3.3.21.1.1.1
		msanOnuVlanProfileName OBJECT-TYPE
			SYNTAX DisplayString (SIZE (1..64))
			MAX-ACCESS not-accessible
			STATUS current
			DESCRIPTION
				"ONU Vlan Profile Name."
			::= { msanOnuVlanProfileEntry 1 }

		
		-- 1.3.6.1.4.1.1332.1.1.5.3.3.21.1.1.2
		msanOnuVlanProfileDownstreamMode OBJECT-TYPE
			SYNTAX INTEGER
				{
				enable(1),
				disable(2)
				}
			MAX-ACCESS read-write
			STATUS current
			DESCRIPTION
				"Enable maping in downstream direction also.
				
				When enabled, downstream tagging operation is performed 
				in inverse order of that in upstream direction.
				
				When disabled, all downstream frames are forwarded unmodified."
			DEFVAL { enable }
			::= { msanOnuVlanProfileEntry 2 }

		
		-- 1.3.6.1.4.1.1332.1.1.5.3.3.21.1.1.3
		msanOnuVlanProfileInputTPID OBJECT-TYPE
			SYNTAX Unsigned32
			MAX-ACCESS read-write
			STATUS current
			DESCRIPTION
				"Input TPID (Tag Protocol Identifier). 
				Default value is 0x8100."
			DEFVAL { '8100'h }
			::= { msanOnuVlanProfileEntry 3 }

		
		-- 1.3.6.1.4.1.1332.1.1.5.3.3.21.1.1.4
		msanOnuVlanProfileOutputTPID OBJECT-TYPE
			SYNTAX Unsigned32
			MAX-ACCESS read-write
			STATUS current
			DESCRIPTION
				"Output TPID (Tag Protocol Identifier). 
				Default value is 0x88A8."
			DEFVAL { '88A8'h }
			::= { msanOnuVlanProfileEntry 4 }

		
		-- 1.3.6.1.4.1.1332.1.1.5.3.3.21.1.1.50
		msanOnuVlanProfileRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanOnuVlanProfileEntry 50 }

		
		-- 1.3.6.1.4.1.1332.1.1.5.3.3.21.1.1.51
		msanOnuVlanProfileUsage OBJECT-TYPE
			SYNTAX INTEGER
				{
				attached(1),
				notAttached(2)
				}
			MAX-ACCESS read-only
			STATUS current
			DESCRIPTION
				"Profile usage.
				If profile is attached,  profile values can't be edited."
			::= { msanOnuVlanProfileEntry 51 }

		
		-- 1.3.6.1.4.1.1332.1.1.5.3.3.21.1.1.52
		msanOnuVlanProfileDscpPcpMap OBJECT-TYPE
			SYNTAX INTEGER
				{
				disable(1),
				ipPrecedenceToPcp(2)
				}
			MAX-ACCESS read-write
			STATUS current
			DESCRIPTION
				"DSCP to PCP mapping"
			DEFVAL { disable }
			::= { msanOnuVlanProfileEntry 52 }

		
		-- 1.3.6.1.4.1.1332.1.1.5.3.3.21.2
		msanOnuVlanProfileRuleTable OBJECT-TYPE
			SYNTAX SEQUENCE OF MsanOnuVlanProfileRuleEntry
			MAX-ACCESS not-accessible
			STATUS current
			DESCRIPTION
				"description"
			::= { msanOnuVlanProfile 2 }

		
		-- 1.3.6.1.4.1.1332.1.1.5.3.3.21.2.1
		msanOnuVlanProfileRuleEntry OBJECT-TYPE
			SYNTAX MsanOnuVlanProfileRuleEntry
			MAX-ACCESS not-accessible
			STATUS current
			DESCRIPTION
				"Row Description"
			INDEX { msanOnuVlanProfileName, msanOnuVlanProfileRuleId }
			::= { msanOnuVlanProfileRuleTable 1 }

		
		MsanOnuVlanProfileRuleEntry ::=
			SEQUENCE { 
				msanOnuVlanProfileRuleId
					Integer32,
				msanOnuVlanProfileRuleMatchSVlanId
					Integer32,
				msanOnuVlanProfileRuleMatchSPcp
					Integer32,
				msanOnuVlanProfileRuleMatchSTPID
					INTEGER,
				msanOnuVlanProfileRuleMatchCVlanId
					Integer32,
				msanOnuVlanProfileRuleMatchCPcp
					Integer32,
				msanOnuVlanProfileRuleMatchCTPID
					INTEGER,
				msanOnuVlanProfileRuleMatchEthertype
					INTEGER,
				msanOnuVlanProfileRuleRemoveTags
					INTEGER,
				msanOnuVlanProfileRuleAddSTag
					INTEGER,
				msanOnuVlanProfileRuleAddSPcp
					INTEGER,
				msanOnuVlanProfileRuleAddSVlanId
					Integer32,
				msanOnuVlanProfileRuleAddSTPID
					INTEGER,
				msanOnuVlanProfileRuleAddCTag
					INTEGER,
				msanOnuVlanProfileRuleAddCPcp
					INTEGER,
				msanOnuVlanProfileRuleAddCVlanId
					Integer32,
				msanOnuVlanProfileRuleAddCTPID
					INTEGER,
				msanOnuVlanProfileRuleRowStatus
					RowStatus
			 }

		-- 1.3.6.1.4.1.1332.1.1.5.3.3.21.2.1.1
		msanOnuVlanProfileRuleId OBJECT-TYPE
			SYNTAX Integer32
			MAX-ACCESS not-accessible
			STATUS current
			DESCRIPTION
				"ONU Vlan Rule Index."
			::= { msanOnuVlanProfileRuleEntry 1 }

		
		-- 1.3.6.1.4.1.1332.1.1.5.3.3.21.2.1.4
		msanOnuVlanProfileRuleMatchSVlanId OBJECT-TYPE
			SYNTAX Integer32 (-1..4096)
			MAX-ACCESS read-write
			STATUS current
			DESCRIPTION
				"Match frames with selected S-VLAN (outer) ID:
				0 .. 4094  Match received frames with this S-VLAN ID.
				4096 Match received frames without S-TAG.
				-1  Do not match by S-VLAN ID (Default).
				"
			DEFVAL { 4096 }
			::= { msanOnuVlanProfileRuleEntry 4 }

		
		-- 1.3.6.1.4.1.1332.1.1.5.3.3.21.2.1.5
		msanOnuVlanProfileRuleMatchSPcp OBJECT-TYPE
			SYNTAX Integer32 (-1..7)
			MAX-ACCESS read-write
			STATUS current
			DESCRIPTION
				"Match frames with selected S-PCP (outer) value:
				0..7 Match received frames on this S-PCP priority (P bit) value.
				-1 Do not match on S-PCP (default).
				"
			DEFVAL { -1 }
			::= { msanOnuVlanProfileRuleEntry 5 }

		
		-- 1.3.6.1.4.1.1332.1.1.5.3.3.21.2.1.6
		msanOnuVlanProfileRuleMatchSTPID OBJECT-TYPE
			SYNTAX INTEGER
				{
				do-not-match(0),
				match-value-8100(1),
				match-input-tpid(2)
				}
			MAX-ACCESS read-write
			STATUS current
			DESCRIPTION
				"Match frames with selected S-TPID (outer):
				0 do not match on S-TPID
				1 match on S-TPID value 0x8100
				2 match on value of parameter msanOnuVlanProfileInputTPID"
			DEFVAL { do-not-match }
			::= { msanOnuVlanProfileRuleEntry 6 }

		
		-- 1.3.6.1.4.1.1332.1.1.5.3.3.21.2.1.7
		msanOnuVlanProfileRuleMatchCVlanId OBJECT-TYPE
			SYNTAX Integer32 (-1..4096)
			MAX-ACCESS read-write
			STATUS current
			DESCRIPTION
				"Match frames with selected C-VLAN (inner) ID:
				0 .. 4094  Match received frames with this C-VLAN ID.
				4096 Match received frames without C-TAG.
				-1  Do not match by C-VLAN ID (Default).
				"
			DEFVAL { 4096 }
			::= { msanOnuVlanProfileRuleEntry 7 }

		
		-- 1.3.6.1.4.1.1332.1.1.5.3.3.21.2.1.8
		msanOnuVlanProfileRuleMatchCPcp OBJECT-TYPE
			SYNTAX Integer32
			MAX-ACCESS read-write
			STATUS current
			DESCRIPTION
				"Match frames with selected C-PCP (inner) value:
				0..7 Match received frames on this C-PCP priority (P bit) value.
				-1 Do not match on C-PCP (default).
				"
			::= { msanOnuVlanProfileRuleEntry 8 }

		
		-- 1.3.6.1.4.1.1332.1.1.5.3.3.21.2.1.9
		msanOnuVlanProfileRuleMatchCTPID OBJECT-TYPE
			SYNTAX INTEGER
				{
				do-not-match(0),
				match-value-8100(1),
				match-input-tpid(2)
				}
			MAX-ACCESS read-write
			STATUS current
			DESCRIPTION
				"Match frames with selected C-TPID (inner):
				0 do not match on C-TPID
				1 match on C-TPID value 0x8100
				2 match on value of parameter msanOnuVlanProfileInputTPID"
			DEFVAL { do-not-match }
			::= { msanOnuVlanProfileRuleEntry 9 }

		
		-- 1.3.6.1.4.1.1332.1.1.5.3.3.21.2.1.11
		msanOnuVlanProfileRuleMatchEthertype OBJECT-TYPE
			SYNTAX INTEGER
				{
				do-not-match(0),
				ipoe(1),
				pppoe(2),
				arp(3),
				ipv6(4)
				}
			MAX-ACCESS read-write
			STATUS current
			DESCRIPTION
				"Match frames with selected Ethertype value.
				Standard values:
				IPoE(1)   0x0800
				PPPoE(2)  0x8863 or 0x8864
				ARP(3)   0x0806
				IPv6(4)   0x86DD
				
				 A value 0 indicates that parameter is not used for match criteria.
				
				"
			DEFVAL { do-not-match }
			::= { msanOnuVlanProfileRuleEntry 11 }

		
		-- 1.3.6.1.4.1.1332.1.1.5.3.3.21.2.1.12
		msanOnuVlanProfileRuleRemoveTags OBJECT-TYPE
			SYNTAX INTEGER
				{
				do-not-remove(1),
				remove-outer(2),
				remove-both(3),
				discard-frame(4)
				}
			MAX-ACCESS read-write
			STATUS current
			DESCRIPTION
				"VLAN tags to remove.
				"
			DEFVAL { do-not-remove }
			::= { msanOnuVlanProfileRuleEntry 12 }

		
		-- 1.3.6.1.4.1.1332.1.1.5.3.3.21.2.1.13
		msanOnuVlanProfileRuleAddSTag OBJECT-TYPE
			SYNTAX INTEGER
				{
				enable(1),
				disable(2)
				}
			MAX-ACCESS read-write
			STATUS current
			DESCRIPTION
				"Add a S-TAG."
			DEFVAL { disable }
			::= { msanOnuVlanProfileRuleEntry 13 }

		
		-- 1.3.6.1.4.1.1332.1.1.5.3.3.21.2.1.14
		msanOnuVlanProfileRuleAddSPcp OBJECT-TYPE
			SYNTAX INTEGER (0..10)
			MAX-ACCESS read-write
			STATUS current
			DESCRIPTION
				"Set priority in added S-TAG:
				0..7 insert this priority value to the S-TAG
				8 copy the C-TAG priority value of the received frame.
				9 copy the S-TAG priority value of the received frame.
				10 copy the DSCP value of the received frame."
			DEFVAL { 0 }
			::= { msanOnuVlanProfileRuleEntry 14 }

		
		-- 1.3.6.1.4.1.1332.1.1.5.3.3.21.2.1.15
		msanOnuVlanProfileRuleAddSVlanId OBJECT-TYPE
			SYNTAX Integer32 (0..4097)
			MAX-ACCESS read-write
			STATUS current
			DESCRIPTION
				"Set VID in added S-TAG:
				000..4094 Use this value as the VID in the added S-TAG.
				4096 copy the C-VID value of the received frame.
				4097 copy the S-VID value of the received frame.
				
				"
			DEFVAL { 0 }
			::= { msanOnuVlanProfileRuleEntry 15 }

		
		-- 1.3.6.1.4.1.1332.1.1.5.3.3.21.2.1.16
		msanOnuVlanProfileRuleAddSTPID OBJECT-TYPE
			SYNTAX INTEGER
				{
				set-value-0x8100(1),
				use-output-tpid(2),
				copy-c-tpid(3),
				copy-s-tpid(4)
				}
			MAX-ACCESS read-write
			STATUS current
			DESCRIPTION
				"Set TPID in added S-TAG:
				0 do not change (use default value)
				1 set to value 0x8100
				2 copy the value of parameter msanOnuVlanProfileOutputTPID
				3 copy the C-TPID value of the received frame.
				4 copy the S-TPID value of the received frame.
				
				"
			DEFVAL { copy-c-tpid }
			::= { msanOnuVlanProfileRuleEntry 16 }

		
		-- 1.3.6.1.4.1.1332.1.1.5.3.3.21.2.1.17
		msanOnuVlanProfileRuleAddCTag OBJECT-TYPE
			SYNTAX INTEGER
				{
				enable(1),
				disable(2)
				}
			MAX-ACCESS read-write
			STATUS current
			DESCRIPTION
				"Add a S-TAG.
				"
			DEFVAL { disable }
			::= { msanOnuVlanProfileRuleEntry 17 }

		
		-- 1.3.6.1.4.1.1332.1.1.5.3.3.21.2.1.18
		msanOnuVlanProfileRuleAddCPcp OBJECT-TYPE
			SYNTAX INTEGER (0..10)
			MAX-ACCESS read-write
			STATUS current
			DESCRIPTION
				"Set priority in added C-TAG:
				0..7 insert this priority value to the C-TAG
				8 copy the C-TAG priority value of the received frame.
				9 copy the S-TAG priority value of the received frame.
				10 copy the DSCP value of the received frame."
			DEFVAL { 0 }
			::= { msanOnuVlanProfileRuleEntry 18 }

		
		-- 1.3.6.1.4.1.1332.1.1.5.3.3.21.2.1.19
		msanOnuVlanProfileRuleAddCVlanId OBJECT-TYPE
			SYNTAX Integer32 (0..4097)
			MAX-ACCESS read-write
			STATUS current
			DESCRIPTION
				"Set VID in added C-TAG:
				000..4094 Use this value as the VID in the added C-TAG.
				4096 copy the C-VID value of the received frame.
				4097 copy the S-VID value of the received frame.
				
				"
			DEFVAL { 0 }
			::= { msanOnuVlanProfileRuleEntry 19 }

		
		-- 1.3.6.1.4.1.1332.1.1.5.3.3.21.2.1.20
		msanOnuVlanProfileRuleAddCTPID OBJECT-TYPE
			SYNTAX INTEGER
				{
				set-value-0x8100(1),
				use-output-tpid(2),
				copy-c-tpid(3),
				copy-s-tpid(4)
				}
			MAX-ACCESS read-write
			STATUS current
			DESCRIPTION
				"Set TPID in added S-TAG:
				0 do not change (use default value)
				1 set to value 0x8100
				2 copy the value of parameter msanOnuVlanProfileOutputTPID
				3 copy the C-TPID value of the received frame.
				4 copy the S-TPID value of the received frame.
				
				"
			DEFVAL { copy-c-tpid }
			::= { msanOnuVlanProfileRuleEntry 20 }

		
		-- 1.3.6.1.4.1.1332.1.1.5.3.3.21.2.1.50
		msanOnuVlanProfileRuleRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndWait(5).
				For row activation use active(1).
				For row deletion use destroy(6) ).
						
				Other values are currently not supported."
			::= { msanOnuVlanProfileRuleEntry 50 }

		
		-- 1.3.6.1.4.1.1332.1.1.5.3.3.22
		msanOnuMulticastProfile OBJECT IDENTIFIER ::= { msanProfiles 22 }

		
		-- 1.3.6.1.4.1.1332.1.1.5.3.3.22.1
		msanOnuMulticastProfileTable OBJECT-TYPE
			SYNTAX SEQUENCE OF MsanOnuMulticastProfileEntry
			MAX-ACCESS not-accessible
			STATUS current
			DESCRIPTION
				"Description."
			::= { msanOnuMulticastProfile 1 }

		
		-- 1.3.6.1.4.1.1332.1.1.5.3.3.22.1.1
		msanOnuMulticastProfileEntry OBJECT-TYPE
			SYNTAX MsanOnuMulticastProfileEntry
			MAX-ACCESS not-accessible
			STATUS current
			DESCRIPTION
				"Description."
			INDEX { msanOnuMulticastProfileName }
			::= { msanOnuMulticastProfileTable 1 }

		
		MsanOnuMulticastProfileEntry ::=
			SEQUENCE { 
				msanOnuMulticastProfileName
					DisplayString,
				msanOnuMulticastProfileIgmpMode
					INTEGER,
				msanOnuMulticastProfileIgmpProxy
					INTEGER,
				msanOnuMulticastProfileIgmpSnoopingFastLeave
					INTEGER,
				msanOnuMulticastProfileUsIgmpTciVlanId
					INTEGER,
				msanOnuMulticastProfileUsIgmpTciPcpValue
					Integer32,
				msanOnuMulticastProfileUsIgmpTciCtrlMode
					INTEGER,
				msanOnuMulticastProfileDsVlanTagging
					INTEGER,
				msanOnuMulticastProfileDsGemPort
					Integer32,
				msanOnuMulticastProfileRowStatus
					RowStatus,
				msanOnuMulticastProfileUsage
					INTEGER
			 }

		-- 1.3.6.1.4.1.1332.1.1.5.3.3.22.1.1.1
		msanOnuMulticastProfileName OBJECT-TYPE
			SYNTAX DisplayString (SIZE (1..64))
			MAX-ACCESS not-accessible
			STATUS current
			DESCRIPTION
				"ONU Multicast Profile Name."
			::= { msanOnuMulticastProfileEntry 1 }

		
		-- 1.3.6.1.4.1.1332.1.1.5.3.3.22.1.1.10
		msanOnuMulticastProfileIgmpMode OBJECT-TYPE
			SYNTAX INTEGER
				{
				flooding(1),
				snooping(2)
				}
			MAX-ACCESS read-write
			STATUS current
			DESCRIPTION
				"ONU IGMP Mode."
			DEFVAL { flooding }
			::= { msanOnuMulticastProfileEntry 10 }

		
		-- 1.3.6.1.4.1.1332.1.1.5.3.3.22.1.1.11
		msanOnuMulticastProfileIgmpProxy OBJECT-TYPE
			SYNTAX INTEGER
				{
				enable(1),
				disable(2)
				}
			MAX-ACCESS read-write
			STATUS current
			DESCRIPTION
				"ONU IGMP Proxy admin state."
			DEFVAL { disable }
			::= { msanOnuMulticastProfileEntry 11 }

		
		-- 1.3.6.1.4.1.1332.1.1.5.3.3.22.1.1.12
		msanOnuMulticastProfileIgmpSnoopingFastLeave OBJECT-TYPE
			SYNTAX INTEGER
				{
				enable(1),
				disable(2)
				}
			MAX-ACCESS read-write
			STATUS current
			DESCRIPTION
				"ONU IGMP Snooping Fast Leave admin state."
			DEFVAL { enable }
			::= { msanOnuMulticastProfileEntry 12 }

		
		-- 1.3.6.1.4.1.1332.1.1.5.3.3.22.1.1.13
		msanOnuMulticastProfileUsIgmpTciVlanId OBJECT-TYPE
			SYNTAX INTEGER (0..4094)
			MAX-ACCESS read-write
			STATUS current
			DESCRIPTION
				"ONU Upstream IGMP TCI (Tag Control Information) VLAN ID.
				
				Value 0 means that parameter is not defined."
			::= { msanOnuMulticastProfileEntry 13 }

		
		-- 1.3.6.1.4.1.1332.1.1.5.3.3.22.1.1.14
		msanOnuMulticastProfileUsIgmpTciPcpValue OBJECT-TYPE
			SYNTAX Integer32 (-1..7)
			MAX-ACCESS read-write
			STATUS current
			DESCRIPTION
				"ONU Upstream IGMP TCI (Tag Control Information) PCP (Priority Code Point) value (0-7) = CoS.
				"
			DEFVAL { 0 }
			::= { msanOnuMulticastProfileEntry 14 }

		
		-- 1.3.6.1.4.1.1332.1.1.5.3.3.22.1.1.15
		msanOnuMulticastProfileUsIgmpTciCtrlMode OBJECT-TYPE
			SYNTAX INTEGER
				{
				transparent(1),
				add(2),
				replace(3),
				replace-vid-only(4),
				smart(5)
				}
			MAX-ACCESS read-write
			STATUS current
			DESCRIPTION
				"ONU Upstream IGMP TCI (Tag Control Information) Control mode."
			DEFVAL { smart }
			::= { msanOnuMulticastProfileEntry 15 }

		
		-- 1.3.6.1.4.1.1332.1.1.5.3.3.22.1.1.16
		msanOnuMulticastProfileDsVlanTagging OBJECT-TYPE
			SYNTAX INTEGER
				{
				enable(1),
				disable(2)
				}
			MAX-ACCESS read-write
			STATUS current
			DESCRIPTION
				"ONU Downstream tagging of multicast traffic."
			::= { msanOnuMulticastProfileEntry 16 }

		
		-- 1.3.6.1.4.1.1332.1.1.5.3.3.22.1.1.17
		msanOnuMulticastProfileDsGemPort OBJECT-TYPE
			SYNTAX Integer32 (3800..4000)
			MAX-ACCESS read-write
			STATUS current
			DESCRIPTION
				"Downstream multicast GEM port number. 
				Standard values are 3800 - 3999.
				Default value is 4000 (Undefined)."
			DEFVAL { 4000 }
			::= { msanOnuMulticastProfileEntry 17 }

		
		-- 1.3.6.1.4.1.1332.1.1.5.3.3.22.1.1.50
		msanOnuMulticastProfileRowStatus OBJECT-TYPE
			SYNTAX RowStatus
			MAX-ACCESS read-write
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanOnuMulticastProfileEntry 50 }

		
		-- 1.3.6.1.4.1.1332.1.1.5.3.3.22.1.1.51
		msanOnuMulticastProfileUsage OBJECT-TYPE
			SYNTAX INTEGER
				{
				attached(1),
				notAttached(2)
				}
			MAX-ACCESS read-only
			STATUS current
			DESCRIPTION
				"Profile usage.
				If profile is attached,  profile values can't be edited."
			::= { msanOnuMulticastProfileEntry 51 }

		
		-- 1.3.6.1.4.1.1332.1.1.5.3.3.23
		msanOnuTcontProfile OBJECT IDENTIFIER ::= { msanProfiles 23 }

		
		-- 1.3.6.1.4.1.1332.1.1.5.3.3.23.1
		msanOnuTcontProfileTable OBJECT-TYPE
			SYNTAX SEQUENCE OF MsanOnuTcontProfileEntry
			MAX-ACCESS not-accessible
			STATUS current
			DESCRIPTION
				"Description."
			::= { msanOnuTcontProfile 1 }

		
		-- 1.3.6.1.4.1.1332.1.1.5.3.3.23.1.1
		msanOnuTcontProfileEntry OBJECT-TYPE
			SYNTAX MsanOnuTcontProfileEntry
			MAX-ACCESS not-accessible
			STATUS current
			DESCRIPTION
				"Description."
			INDEX { msanOnuTcontProfileName }
			::= { msanOnuTcontProfileTable 1 }

		
		MsanOnuTcontProfileEntry ::=
			SEQUENCE { 
				msanOnuTcontProfileName
					DisplayString,
				msanOnuTcontProfileTcontId
					INTEGER,
				msanOnuTcontProfileTcontType
					INTEGER,
				msanOnuTcontProfileFixedDataRate
					Integer32,
				msanOnuTcontProfileAssuredDataRate
					Integer32,
				msanOnuTcontProfileMaxDataRate
					Integer32,
				msanOnuTcontProfileRowStatus
					RowStatus,
				msanOnuTcontProfileUsage
					INTEGER
			 }

		-- 1.3.6.1.4.1.1332.1.1.5.3.3.23.1.1.1
		msanOnuTcontProfileName OBJECT-TYPE
			SYNTAX DisplayString (SIZE (1..64))
			MAX-ACCESS not-accessible
			STATUS current
			DESCRIPTION
				"ONU T-CONT Profile Name."
			::= { msanOnuTcontProfileEntry 1 }

		
		-- 1.3.6.1.4.1.1332.1.1.5.3.3.23.1.1.10
		msanOnuTcontProfileTcontId OBJECT-TYPE
			SYNTAX INTEGER (1..8)
			MAX-ACCESS read-write
			STATUS current
			DESCRIPTION
				"ONU T-CONT index."
			DEFVAL { 1 }
			::= { msanOnuTcontProfileEntry 10 }

		
		-- 1.3.6.1.4.1.1332.1.1.5.3.3.23.1.1.11
		msanOnuTcontProfileTcontType OBJECT-TYPE
			SYNTAX INTEGER (1..5)
			MAX-ACCESS read-write
			STATUS current
			DESCRIPTION
				"ONU T-CONT type."
			DEFVAL { 5 }
			::= { msanOnuTcontProfileEntry 11 }

		
		-- 1.3.6.1.4.1.1332.1.1.5.3.3.23.1.1.12
		msanOnuTcontProfileFixedDataRate OBJECT-TYPE
			SYNTAX Integer32 (128..2500000)
			UNITS "kbps"
			MAX-ACCESS read-write
			STATUS current
			DESCRIPTION
				"ONU T-CONT Fixed data rate.
				Any rate value can be entered, but is rounded up to the multiple of 64 kbps.
				
				Limitation: Maximum rate cannot be lower than the sum of fixed and assured rates."
			DEFVAL { 128 }
			::= { msanOnuTcontProfileEntry 12 }

		
		-- 1.3.6.1.4.1.1332.1.1.5.3.3.23.1.1.13
		msanOnuTcontProfileAssuredDataRate OBJECT-TYPE
			SYNTAX Integer32 (0..2500000)
			UNITS "kbps"
			MAX-ACCESS read-write
			STATUS current
			DESCRIPTION
				"ONU T-CONT Assured data rate  (256 - 2500000 kbps).
				Default value is 0, meaning that no rate is configured.
				Any rate value can be entered, but is rounded up to the multiple of 64 kbps.
				
				Limitation: Maximum rate cannot be lower than the sum of fixed and assured rates."
			DEFVAL { 0 }
			::= { msanOnuTcontProfileEntry 13 }

		
		-- 1.3.6.1.4.1.1332.1.1.5.3.3.23.1.1.14
		msanOnuTcontProfileMaxDataRate OBJECT-TYPE
			SYNTAX Integer32 (128..2500000)
			UNITS "kbps"
			MAX-ACCESS read-write
			STATUS current
			DESCRIPTION
				"ONU T-CONT Maximum data rate.
				Any rate value can be entered, but is rounded up to the multiple of 64 kbps.
				
				Limitation: Maximum rate cannot be lower than the sum of fixed and assured rates"
			DEFVAL { 1024 }
			::= { msanOnuTcontProfileEntry 14 }

		
		-- 1.3.6.1.4.1.1332.1.1.5.3.3.23.1.1.50
		msanOnuTcontProfileRowStatus OBJECT-TYPE
			SYNTAX RowStatus
			MAX-ACCESS read-write
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanOnuTcontProfileEntry 50 }

		
		-- 1.3.6.1.4.1.1332.1.1.5.3.3.23.1.1.51
		msanOnuTcontProfileUsage OBJECT-TYPE
			SYNTAX INTEGER
				{
				attached(1),
				notAttached(2)
				}
			MAX-ACCESS read-only
			STATUS current
			DESCRIPTION
				"Profile usage.
				If profile is attached,  profile values can't be edited."
			::= { msanOnuTcontProfileEntry 51 }

		
		-- 1.3.6.1.4.1.1332.1.1.5.3.3.24
		msanOnuAcsServerProfile OBJECT IDENTIFIER ::= { msanProfiles 24 }

		
		-- 1.3.6.1.4.1.1332.1.1.5.3.3.24.1
		msanOnuAcsServerProfileTable OBJECT-TYPE
			SYNTAX SEQUENCE OF MsanOnuAcsServerProfileEntry
			MAX-ACCESS not-accessible
			STATUS current
			DESCRIPTION
				"Description."
			::= { msanOnuAcsServerProfile 1 }

		
		-- 1.3.6.1.4.1.1332.1.1.5.3.3.24.1.1
		msanOnuAcsServerProfileEntry OBJECT-TYPE
			SYNTAX MsanOnuAcsServerProfileEntry
			MAX-ACCESS not-accessible
			STATUS current
			DESCRIPTION
				"Description."
			INDEX { msanOnuAcsServerProfileName }
			::= { msanOnuAcsServerProfileTable 1 }

		
		MsanOnuAcsServerProfileEntry ::=
			SEQUENCE { 
				msanOnuAcsServerProfileName
					DisplayString,
				msanOnuAcsServerProfileUrl
					DisplayString,
				msanOnuAcsServerProfileUserName
					DisplayString,
				msanOnuAcsServerProfilePassword
					DisplayString,
				msanOnuAcsServerProfileAddressType
					InetAddressType,
				msanOnuAcsServerProfileAddress
					InetAddress,
				msanOnuAcsServerProfilePortId
					Integer32,
				msanOnuAcsServerProfileProtocol
					INTEGER,
				msanOnuAcsServerProfileRowStatus
					RowStatus
			 }

		-- 1.3.6.1.4.1.1332.1.1.5.3.3.24.1.1.1
		msanOnuAcsServerProfileName OBJECT-TYPE
			SYNTAX DisplayString
			MAX-ACCESS not-accessible
			STATUS current
			DESCRIPTION
				"Name of ONU ACS Server Profile"
			::= { msanOnuAcsServerProfileEntry 1 }

		
		-- 1.3.6.1.4.1.1332.1.1.5.3.3.24.1.1.2
		msanOnuAcsServerProfileUrl OBJECT-TYPE
			SYNTAX DisplayString (SIZE (0..32))
			MAX-ACCESS read-write
			STATUS current
			DESCRIPTION
				"URL of the ACS server in form:
				<http|https>://<IP>|<hostname>[:<port>][/<path>]"
			DEFVAL { ''b }
			::= { msanOnuAcsServerProfileEntry 2 }

		
		-- 1.3.6.1.4.1.1332.1.1.5.3.3.24.1.1.3
		msanOnuAcsServerProfileUserName OBJECT-TYPE
			SYNTAX DisplayString
			MAX-ACCESS read-write
			STATUS current
			DESCRIPTION
				"Username used for ACS Server connection."
			DEFVAL { ''b }
			::= { msanOnuAcsServerProfileEntry 3 }

		
		-- 1.3.6.1.4.1.1332.1.1.5.3.3.24.1.1.4
		msanOnuAcsServerProfilePassword OBJECT-TYPE
			SYNTAX DisplayString (SIZE (0..32))
			MAX-ACCESS read-write
			STATUS current
			DESCRIPTION
				"Username used for ACS Server connection."
			DEFVAL { ''b }
			::= { msanOnuAcsServerProfileEntry 4 }

		
		-- 1.3.6.1.4.1.1332.1.1.5.3.3.24.1.1.5
		msanOnuAcsServerProfileAddressType OBJECT-TYPE
			SYNTAX InetAddressType
			MAX-ACCESS read-write
			STATUS obsolete
			DESCRIPTION
				"Specifies the type of the ACS Server IP address:
				                     unknown(0),
				                     ipv4(1),   
				                     ipv6(2),    
				                     dns(16)    
				"
			DEFVAL { ipv4 }
			::= { msanOnuAcsServerProfileEntry 5 }

		
		-- 1.3.6.1.4.1.1332.1.1.5.3.3.24.1.1.6
		msanOnuAcsServerProfileAddress OBJECT-TYPE
			SYNTAX InetAddress
			MAX-ACCESS read-write
			STATUS obsolete
			DESCRIPTION
				"ACS Server IP address (or hostname)"
			::= { msanOnuAcsServerProfileEntry 6 }

		
		-- 1.3.6.1.4.1.1332.1.1.5.3.3.24.1.1.7
		msanOnuAcsServerProfilePortId OBJECT-TYPE
			SYNTAX Integer32 (-1..65535)
			MAX-ACCESS read-write
			STATUS obsolete
			DESCRIPTION
				"ACS Service Port number
				If value is set to -1, standard protocol number is used."
			DEFVAL { -1 }
			::= { msanOnuAcsServerProfileEntry 7 }

		
		-- 1.3.6.1.4.1.1332.1.1.5.3.3.24.1.1.8
		msanOnuAcsServerProfileProtocol OBJECT-TYPE
			SYNTAX INTEGER
				{
				tcp(1),
				ssl(2),
				tsl(3)
				}
			MAX-ACCESS read-write
			STATUS obsolete
			DESCRIPTION
				"ACS Service Protocol
				"
			DEFVAL { tcp }
			::= { msanOnuAcsServerProfileEntry 8 }

		
		-- 1.3.6.1.4.1.1332.1.1.5.3.3.24.1.1.9
		msanOnuAcsServerProfileRowStatus OBJECT-TYPE
			SYNTAX RowStatus
			MAX-ACCESS read-create
			STATUS current
			DESCRIPTION
				"The row status object controls the creation/deletion of rows in this table. 
				Its semantics are the same as those for the RowStatus textual convention specified for SNMPv2.
				For row creation use createAndWait(5).
				Value active(1) will activate and value destroy(6) will remove this entry.
				Other values are currently not supported.
				
				Row can be created only when all required parameters are set:
				- msanOnuAcsServerProfileUrl
				- msanOnuAcsServerProfileUserName
				- msanOnuAcsServerProfilePassword"
			::= { msanOnuAcsServerProfileEntry 9 }

		
		-- 1.3.6.1.4.1.1332.1.1.5.3.3.50
		msanProfilePortDataTable OBJECT-TYPE
			SYNTAX SEQUENCE OF MsanProfilePortDataEntry
			MAX-ACCESS not-accessible
			STATUS current
			DESCRIPTION
				"Description."
			::= { msanProfiles 50 }

		
		-- 1.3.6.1.4.1.1332.1.1.5.3.3.50.1
		msanProfilePortDataEntry OBJECT-TYPE
			SYNTAX MsanProfilePortDataEntry
			MAX-ACCESS not-accessible
			STATUS current
			DESCRIPTION
				"In case of GPON access blade, ifIndex for ONU interface (ifDescr=0/x/y) is calculated with formula:
				ifIndex=max_olt_port_number(8 or 16)+(x-1)*128+y   "
			INDEX { ifIndex }
			::= { msanProfilePortDataTable 1 }

		
		MsanProfilePortDataEntry ::=
			SEQUENCE { 
				msanProfilePortDataCVid
					Integer32,
				msanProfilePortDataSVid
					Integer32
			 }

		-- 1.3.6.1.4.1.1332.1.1.5.3.3.50.1.1
		msanProfilePortDataCVid OBJECT-TYPE
			SYNTAX Integer32 (-1..4094)
			MAX-ACCESS read-write
			STATUS current
			DESCRIPTION
				"C-VLAN Id.
				A value of -1 indicates that parameter has not been defined."
			DEFVAL { -1 }
			::= { msanProfilePortDataEntry 1 }

		
		-- 1.3.6.1.4.1.1332.1.1.5.3.3.50.1.2
		msanProfilePortDataSVid OBJECT-TYPE
			SYNTAX Integer32 (-1..4094)
			MAX-ACCESS read-write
			STATUS current
			DESCRIPTION
				"S-VLAN Id.
				A value of -1 indicates that parameter has not been defined."
			DEFVAL { -1 }
			::= { msanProfilePortDataEntry 2 }

		
		-- 1.3.6.1.4.1.1332.1.1.5.3.3.100
		msanProfileConfigStatus OBJECT-TYPE
			SYNTAX INTEGER
				{
				enable(1),
				disable(2)
				}
			MAX-ACCESS read-write
			STATUS current
			DESCRIPTION
				"Profile configuration  status."
			DEFVAL { disable }
			::= { msanProfiles 100 }

		
		-- 1.3.6.1.4.1.1332.1.1.5.3.4
		msanDhcpRelay OBJECT IDENTIFIER ::= { msanAdditionalConf 4 }

		
		-- 1.3.6.1.4.1.1332.1.1.5.3.4.1
		msanDhcpRaGlobal OBJECT IDENTIFIER ::= { msanDhcpRelay 1 }

		
		-- 1.3.6.1.4.1.1332.1.1.5.3.4.1.1
		msanDhcpRaStatus OBJECT-TYPE
			SYNTAX INTEGER
				{
				enable(1),
				disable(2)
				}
			MAX-ACCESS read-write
			STATUS current
			DESCRIPTION
				"DHCP Relay Agent status."
			::= { msanDhcpRaGlobal 1 }

		
		-- 1.3.6.1.4.1.1332.1.1.5.3.4.1.2
		msanDhcpRaMode OBJECT-TYPE
			SYNTAX INTEGER
				{
				full(1),
				simplified(2)
				}
			MAX-ACCESS read-write
			STATUS current
			DESCRIPTION
				"Specifies if the DHCP Relay Agent mode is to be Simple or Full. Default value is Full."
			::= { msanDhcpRaGlobal 2 }

		
		-- 1.3.6.1.4.1.1332.1.1.5.3.4.1.3
		msanDhcpRaCircuitType OBJECT-TYPE
			SYNTAX INTEGER
				{
				trusted(1),
				untrusted(2)
				}
			MAX-ACCESS read-write
			STATUS current
			DESCRIPTION
				"Specifies DHCP RA Circuit type as trusted(1) or untrusted(2)."
			::= { msanDhcpRaGlobal 3 }

		
		-- 1.3.6.1.4.1.1332.1.1.5.3.4.1.4
		msanDhcpRaOpt82 OBJECT-TYPE
			SYNTAX INTEGER
				{
				enable(1),
				disable(2)
				}
			MAX-ACCESS read-write
			STATUS current
			DESCRIPTION
				"Specifies DHCP Relay Agent general option 82 insertion status .
				
				"
			::= { msanDhcpRaGlobal 4 }

		
		-- 1.3.6.1.4.1.1332.1.1.5.3.4.1.5
		msanDhcpRaOpt82ReplyMode OBJECT-TYPE
			SYNTAX INTEGER
				{
				keep(1),
				remove(2)
				}
			MAX-ACCESS read-write
			STATUS current
			DESCRIPTION
				"Specifies DHCP Relay Agent keep/remove option 82 in replies. "
			::= { msanDhcpRaGlobal 5 }

		
		-- 1.3.6.1.4.1.1332.1.1.5.3.4.1.6
		msanDhcpRaOpt82CircuitIdStatus OBJECT-TYPE
			SYNTAX INTEGER
				{
				enable(1),
				disable(2)
				}
			MAX-ACCESS read-write
			STATUS current
			DESCRIPTION
				"Specifies the disable/enable inserting Circuit ID suboption. Default value is Enable."
			::= { msanDhcpRaGlobal 6 }

		
		-- 1.3.6.1.4.1.1332.1.1.5.3.4.1.7
		msanDhcpRaOpt82RemoteIdStatus OBJECT-TYPE
			SYNTAX INTEGER
				{
				enable(1),
				disable(2)
				}
			MAX-ACCESS read-write
			STATUS current
			DESCRIPTION
				"Specifies the disable/enable inserting Remote ID suboption. Default value is Enable."
			::= { msanDhcpRaGlobal 7 }

		
		-- 1.3.6.1.4.1.1332.1.1.5.3.4.1.8
		msanDhcpRaOpt82UnicastExtStatus OBJECT-TYPE
			SYNTAX INTEGER
				{
				enable(1),
				disable(2)
				}
			MAX-ACCESS read-write
			STATUS current
			DESCRIPTION
				"The desired state of insertion of option 82 in unicast frames."
			DEFVAL { disable }
			::= { msanDhcpRaGlobal 8 }

		
		-- 1.3.6.1.4.1.1332.1.1.5.3.4.1.9
		msanDhcpRaFullModeSrvIpAddr OBJECT-TYPE
			SYNTAX IpAddress
			MAX-ACCESS read-write
			STATUS current
			DESCRIPTION
				"The IP address of default DHCP Server for VLANs where DHCP RA is enabled
				in full mode (parameter msanDhcpRaVlanMode)."
			::= { msanDhcpRaGlobal 9 }

		
		-- 1.3.6.1.4.1.1332.1.1.5.3.4.1.10
		msanDhcpRaOpt82CircuitIdInnerVlan OBJECT-TYPE
			SYNTAX INTEGER
				{
				enable(1),
				disable(2)
				}
			MAX-ACCESS read-write
			STATUS current
			DESCRIPTION
				"Include Inner VLAN (C-VLAN) in Circuit Id when port is in DVLAN Tunneling mode (msanPortDVlanTagMode = enable)."
			DEFVAL { disable }
			::= { msanDhcpRaGlobal 10 }

		
		-- 1.3.6.1.4.1.1332.1.1.5.3.4.1.11
		msanDhcpRaCircuitIdCustomFormat OBJECT-TYPE
			SYNTAX DisplayString
			MAX-ACCESS read-write
			STATUS current
			DESCRIPTION
				"DHCP Circuit Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanDhcpRaGlobal 11 }

		
		-- 1.3.6.1.4.1.1332.1.1.5.3.4.1.12
		msanDhcpRaRemoteIdCustomFormat OBJECT-TYPE
			SYNTAX DisplayString
			MAX-ACCESS read-write
			STATUS current
			DESCRIPTION
				"DHCP Remote Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "$PORT_REM_ID" }
			::= { msanDhcpRaGlobal 12 }

		
		-- 1.3.6.1.4.1.1332.1.1.5.3.4.2
		msanDhcpRaPortConfigTable OBJECT-TYPE
			SYNTAX SEQUENCE OF MsanDhcpRaPortConfigEntry
			MAX-ACCESS not-accessible
			STATUS current
			DESCRIPTION
				"Table od DHCP RA parameters per port."
			::= { msanDhcpRelay 2 }

		
		-- 1.3.6.1.4.1.1332.1.1.5.3.4.2.1
		msanDhcpRaPortConfigEntry OBJECT-TYPE
			SYNTAX MsanDhcpRaPortConfigEntry
			MAX-ACCESS not-accessible
			STATUS current
			DESCRIPTION
				"Description."
			INDEX { ifIndex }
			::= { msanDhcpRaPortConfigTable 1 }

		
		MsanDhcpRaPortConfigEntry ::=
			SEQUENCE { 
				msanDhcpRaPortState
					INTEGER,
				msanDhcpRaPortCircuitId
					OCTET STRING,
				msanDhcpRaPortRemoteId
					OCTET STRING,
				msanDhcpRaPortMeter
					INTEGER,
				msanDhcpRaPortMaxDataRate
					Integer32,
				msanDhcpRaPortCircuitType
					INTEGER,
				msanDhcpRaPortOpt82
					INTEGER,
				msanDhcpRaPortOpt82ReplyMode
					INTEGER,
				msanDhcpRaPortOpt82UnicastExtStatus
					INTEGER,
				msanDhcpRaPortCircuitIdType
					INTEGER
			 }

		-- 1.3.6.1.4.1.1332.1.1.5.3.4.2.1.1
		msanDhcpRaPortState OBJECT-TYPE
			SYNTAX INTEGER
				{
				enable(1),
				enableCli(2),
				enableSrv(3),
				disable(4)
				}
			MAX-ACCESS read-write
			STATUS current
			DESCRIPTION
				"State of DHCP Relay Agent on the port (enable, disable, enable-client, enable-server) "
			::= { msanDhcpRaPortConfigEntry 1 }

		
		-- 1.3.6.1.4.1.1332.1.1.5.3.4.2.1.2
		msanDhcpRaPortCircuitId OBJECT-TYPE
			SYNTAX OCTET STRING
			MAX-ACCESS read-only
			STATUS current
			DESCRIPTION
				"Option 82 Circuit Id for the port."
			::= { msanDhcpRaPortConfigEntry 2 }

		
		-- 1.3.6.1.4.1.1332.1.1.5.3.4.2.1.3
		msanDhcpRaPortRemoteId OBJECT-TYPE
			SYNTAX OCTET STRING
			MAX-ACCESS read-write
			STATUS current
			DESCRIPTION
				"Option 82 Remote Id for the port."
			::= { msanDhcpRaPortConfigEntry 3 }

		
		-- 1.3.6.1.4.1.1332.1.1.5.3.4.2.1.4
		msanDhcpRaPortMeter OBJECT-TYPE
			SYNTAX INTEGER
				{
				enable(1),
				disable(2)
				}
			MAX-ACCESS read-write
			STATUS current
			DESCRIPTION
				"Enable or disable DHCP metering on port."
			::= { msanDhcpRaPortConfigEntry 4 }

		
		-- 1.3.6.1.4.1.1332.1.1.5.3.4.2.1.5
		msanDhcpRaPortMaxDataRate OBJECT-TYPE
			SYNTAX Integer32
			UNITS "kb/s"
			MAX-ACCESS read-write
			STATUS current
			DESCRIPTION
				"Allowed throughput of incoming DHCP traffic on a port (kb/s)"
			::= { msanDhcpRaPortConfigEntry 5 }

		
		-- 1.3.6.1.4.1.1332.1.1.5.3.4.2.1.6
		msanDhcpRaPortCircuitType OBJECT-TYPE
			SYNTAX INTEGER
				{
				trusted(1),
				untrusted(2),
				notConfigured(3)
				}
			MAX-ACCESS read-write
			STATUS current
			DESCRIPTION
				"Specifies DHCP RA Circuit type per port as trusted(1) or untrusted(2)."
			DEFVAL { notConfigured }
			::= { msanDhcpRaPortConfigEntry 6 }

		
		-- 1.3.6.1.4.1.1332.1.1.5.3.4.2.1.7
		msanDhcpRaPortOpt82 OBJECT-TYPE
			SYNTAX INTEGER
				{
				enable(1),
				disable(2),
				notConfigured(3)
				}
			MAX-ACCESS read-write
			STATUS current
			DESCRIPTION
				"Specifies DHCP Relay Agent option 82 insertion status per port."
			DEFVAL { notConfigured }
			::= { msanDhcpRaPortConfigEntry 7 }

		
		-- 1.3.6.1.4.1.1332.1.1.5.3.4.2.1.8
		msanDhcpRaPortOpt82ReplyMode OBJECT-TYPE
			SYNTAX INTEGER
				{
				keep(1),
				remove(2),
				notConfigured(3)
				}
			MAX-ACCESS read-write
			STATUS current
			DESCRIPTION
				"Specifies DHCP Relay Agent keep/remove option 82 in replies per port."
			DEFVAL { notConfigured }
			::= { msanDhcpRaPortConfigEntry 8 }

		
		-- 1.3.6.1.4.1.1332.1.1.5.3.4.2.1.9
		msanDhcpRaPortOpt82UnicastExtStatus OBJECT-TYPE
			SYNTAX INTEGER
				{
				enable(1),
				disable(2),
				notConfigured(3)
				}
			MAX-ACCESS read-write
			STATUS current
			DESCRIPTION
				"The desired state of insertion of option 82 in unicast frames per port."
			DEFVAL { notConfigured }
			::= { msanDhcpRaPortConfigEntry 9 }

		
		-- 1.3.6.1.4.1.1332.1.1.5.3.4.2.1.10
		msanDhcpRaPortCircuitIdType OBJECT-TYPE
			SYNTAX INTEGER
				{
				iskratel(1),
				standard(2),
				atm(3)
				}
			MAX-ACCESS read-write
			STATUS current
			DESCRIPTION
				"Circuit Id syntax mode per port."
			DEFVAL { iskratel }
			::= { msanDhcpRaPortConfigEntry 10 }

		
		-- 1.3.6.1.4.1.1332.1.1.5.3.4.3
		msanDhcpRaFullModeVlanTable OBJECT-TYPE
			SYNTAX SEQUENCE OF MsanDhcpRaFullModeVlanEntry
			MAX-ACCESS not-accessible
			STATUS current
			DESCRIPTION
				"Description."
			::= { msanDhcpRelay 3 }

		
		-- 1.3.6.1.4.1.1332.1.1.5.3.4.3.1
		msanDhcpRaFullModeVlanEntry OBJECT-TYPE
			SYNTAX MsanDhcpRaFullModeVlanEntry
			MAX-ACCESS not-accessible
			STATUS current
			DESCRIPTION
				"Description."
			INDEX { msanDhcpRaFullModeVlanId, msanDhcpRaFullModeVlanSrvIpAddr }
			::= { msanDhcpRaFullModeVlanTable 1 }

		
		MsanDhcpRaFullModeVlanEntry ::=
			SEQUENCE { 
				msanDhcpRaFullModeVlanId
					Integer32,
				msanDhcpRaFullModeVlanSrvIpAddr
					IpAddress,
				msanDhcpRaFullModeVlanRowStatus
					RowStatus
			 }

		-- 1.3.6.1.4.1.1332.1.1.5.3.4.3.1.1
		msanDhcpRaFullModeVlanId OBJECT-TYPE
			SYNTAX Integer32 (1..4094)
			MAX-ACCESS not-accessible
			STATUS current
			DESCRIPTION
				"The VLAN identifier (refers to dot1qVlanIndex) where DHCP Client resides."
			::= { msanDhcpRaFullModeVlanEntry 1 }

		
		-- 1.3.6.1.4.1.1332.1.1.5.3.4.3.1.2
		msanDhcpRaFullModeVlanSrvIpAddr OBJECT-TYPE
			SYNTAX IpAddress
			MAX-ACCESS not-accessible
			STATUS current
			DESCRIPTION
				"The IP address of DHCP Server for specified VLAN."
			::= { msanDhcpRaFullModeVlanEntry 2 }

		
		-- 1.3.6.1.4.1.1332.1.1.5.3.4.3.1.3
		msanDhcpRaFullModeVlanRowStatus OBJECT-TYPE
			SYNTAX RowStatus
			MAX-ACCESS read-create
			STATUS current
			DESCRIPTION
				"The row status object controls the creation/deletion of rows in this table. Its semantics are the same as those for the RowStatus textual convention specified for SNMPv2.
				Setting this object to createAndGo(4) creates a row in this table.
				Setting this object to destroy(6) will remove this entry.
				Read values: active(1).
				Other values are currently not supported."
			::= { msanDhcpRaFullModeVlanEntry 3 }

		
		-- 1.3.6.1.4.1.1332.1.1.5.3.4.4
		msanDhcpRaStatGlobal OBJECT IDENTIFIER ::= { msanDhcpRelay 4 }

		
		-- 1.3.6.1.4.1.1332.1.1.5.3.4.4.1
		msanDhcpRaStatGlobalDiscover OBJECT-TYPE
			SYNTAX Counter32
			MAX-ACCESS read-only
			STATUS current
			DESCRIPTION
				"Number of DHCP DISCOVER packets. "
			::= { msanDhcpRaStatGlobal 1 }

		
		-- 1.3.6.1.4.1.1332.1.1.5.3.4.4.2
		msanDhcpRaStatGlobalRequest OBJECT-TYPE
			SYNTAX Counter32
			MAX-ACCESS read-only
			STATUS current
			DESCRIPTION
				"Number of DHCP REQUEST packets."
			::= { msanDhcpRaStatGlobal 2 }

		
		-- 1.3.6.1.4.1.1332.1.1.5.3.4.4.3
		msanDhcpRaStatGlobalOffer OBJECT-TYPE
			SYNTAX Counter32
			MAX-ACCESS read-only
			STATUS current
			DESCRIPTION
				"Number of DHCP OFFER packets."
			::= { msanDhcpRaStatGlobal 3 }

		
		-- 1.3.6.1.4.1.1332.1.1.5.3.4.4.4
		msanDhcpRaStatGlobalACK OBJECT-TYPE
			SYNTAX Counter32
			MAX-ACCESS read-only
			STATUS current
			DESCRIPTION
				"Number of DHCP ACKNOWLAGE (ACK) packets."
			::= { msanDhcpRaStatGlobal 4 }

		
		-- 1.3.6.1.4.1.1332.1.1.5.3.4.4.5
		msanDhcpRaStatGlobalNAK OBJECT-TYPE
			SYNTAX Counter32
			MAX-ACCESS read-only
			STATUS current
			DESCRIPTION
				"Number of NOT ACKNOWLAGE (NAK) packets."
			::= { msanDhcpRaStatGlobal 5 }

		
		-- 1.3.6.1.4.1.1332.1.1.5.3.4.4.6
		msanDhcpRaStatGlobalDecline OBJECT-TYPE
			SYNTAX Counter32
			MAX-ACCESS read-only
			STATUS current
			DESCRIPTION
				"Number of DHCP DECLINE packets."
			::= { msanDhcpRaStatGlobal 6 }

		
		-- 1.3.6.1.4.1.1332.1.1.5.3.4.4.7
		msanDhcpRaStatGlobalMaxPacketSizeExceeded OBJECT-TYPE
			SYNTAX Counter32
			MAX-ACCESS read-only
			STATUS current
			DESCRIPTION
				"Number of DHCP packets with max. packet size exceeded. "
			::= { msanDhcpRaStatGlobal 7 }

		
		-- 1.3.6.1.4.1.1332.1.1.5.3.4.4.8
		msanDhcpRaStatGlobalFrameErr OBJECT-TYPE
			SYNTAX Counter32
			MAX-ACCESS read-only
			STATUS current
			DESCRIPTION
				"Number of DHCP packets with errors in frames. "
			::= { msanDhcpRaStatGlobal 8 }

		
		-- 1.3.6.1.4.1.1332.1.1.5.3.4.4.9
		msanDhcpRaStatGlobalOpt82Present OBJECT-TYPE
			SYNTAX Counter32
			MAX-ACCESS read-only
			STATUS current
			DESCRIPTION
				"Number of DHCP packets with Option 82 or giaddr present. "
			::= { msanDhcpRaStatGlobal 9 }

		
		-- 1.3.6.1.4.1.1332.1.1.5.3.4.4.10
		msanDhcpRaStatGlobalFrameUnsync OBJECT-TYPE
			SYNTAX Counter32
			MAX-ACCESS read-only
			STATUS current
			DESCRIPTION
				"Number of packets with frames not synchronized with state machines."
			::= { msanDhcpRaStatGlobal 10 }

		
		-- 1.3.6.1.4.1.1332.1.1.5.3.4.4.11
		msanDhcpRaStatGlobalStatRelease OBJECT-TYPE
			SYNTAX Counter32
			MAX-ACCESS read-only
			STATUS current
			DESCRIPTION
				"Number of received DHCP RELEASE packets."
			::= { msanDhcpRaStatGlobal 11 }

		
		-- 1.3.6.1.4.1.1332.1.1.5.3.4.4.12
		msanDhcpRaStatGlobalStatInform OBJECT-TYPE
			SYNTAX Counter32
			MAX-ACCESS read-only
			STATUS current
			DESCRIPTION
				"Number of received DHCP INFORM packets."
			::= { msanDhcpRaStatGlobal 12 }

		
		-- 1.3.6.1.4.1.1332.1.1.5.3.4.5
		msanDhcpRaStatTable OBJECT-TYPE
			SYNTAX SEQUENCE OF MsanDhcpRaStatEntry
			MAX-ACCESS not-accessible
			STATUS current
			DESCRIPTION
				"Description."
			::= { msanDhcpRelay 5 }

		
		-- 1.3.6.1.4.1.1332.1.1.5.3.4.5.1
		msanDhcpRaStatEntry OBJECT-TYPE
			SYNTAX MsanDhcpRaStatEntry
			MAX-ACCESS not-accessible
			STATUS current
			DESCRIPTION
				"Description."
			INDEX { ifIndex }
			::= { msanDhcpRaStatTable 1 }

		
		MsanDhcpRaStatEntry ::=
			SEQUENCE { 
				msanDhcpRaStatDiscover
					Counter32,
				msanDhcpRaStatRequest
					Counter32,
				msanDhcpRaStatOffer
					Counter32,
				msanDhcpRaStatACK
					Counter32,
				msanDhcpRaStatNAK
					Counter32,
				msanDhcpRaStatDecline
					Counter32,
				msanDhcpRaStatMaxPacketSizeExceeded
					Counter32,
				msanDhcpRaStatFrameErr
					Counter32,
				msanDhcpRaStatOpt82Present
					Counter32,
				msanDhcpRaStatFrameUnsync
					Counter32,
				msanDhcpRaStatRelease
					Counter32,
				msanDhcpRaStatInform
					Counter32
			 }

		-- 1.3.6.1.4.1.1332.1.1.5.3.4.5.1.1
		msanDhcpRaStatDiscover OBJECT-TYPE
			SYNTAX Counter32
			MAX-ACCESS read-only
			STATUS current
			DESCRIPTION
				"Number of received DHCP DISCOVER packets."
			::= { msanDhcpRaStatEntry 1 }

		
		-- 1.3.6.1.4.1.1332.1.1.5.3.4.5.1.2
		msanDhcpRaStatRequest OBJECT-TYPE
			SYNTAX Counter32
			MAX-ACCESS read-only
			STATUS current
			DESCRIPTION
				"Number of received DHCP REQUEST packets."
			::= { msanDhcpRaStatEntry 2 }

		
		-- 1.3.6.1.4.1.1332.1.1.5.3.4.5.1.3
		msanDhcpRaStatOffer OBJECT-TYPE
			SYNTAX Counter32
			MAX-ACCESS read-only
			STATUS current
			DESCRIPTION
				"Number of received DHCP OFFER packets."
			::= { msanDhcpRaStatEntry 3 }

		
		-- 1.3.6.1.4.1.1332.1.1.5.3.4.5.1.4
		msanDhcpRaStatACK OBJECT-TYPE
			SYNTAX Counter32
			MAX-ACCESS read-only
			STATUS current
			DESCRIPTION
				"Number of received DHCP ACKNOWLAGE (ACK) packets."
			::= { msanDhcpRaStatEntry 4 }

		
		-- 1.3.6.1.4.1.1332.1.1.5.3.4.5.1.5
		msanDhcpRaStatNAK OBJECT-TYPE
			SYNTAX Counter32
			MAX-ACCESS read-only
			STATUS current
			DESCRIPTION
				"Number of received DHCP NOT ACKNOWLAGE (NAK) packets."
			::= { msanDhcpRaStatEntry 5 }

		
		-- 1.3.6.1.4.1.1332.1.1.5.3.4.5.1.6
		msanDhcpRaStatDecline OBJECT-TYPE
			SYNTAX Counter32
			MAX-ACCESS read-only
			STATUS current
			DESCRIPTION
				"Number of received DHCP DECLINE packets."
			::= { msanDhcpRaStatEntry 6 }

		
		-- 1.3.6.1.4.1.1332.1.1.5.3.4.5.1.7
		msanDhcpRaStatMaxPacketSizeExceeded OBJECT-TYPE
			SYNTAX Counter32
			MAX-ACCESS read-only
			STATUS current
			DESCRIPTION
				"Number of received DHCP packets with max. packet size exceeded. "
			::= { msanDhcpRaStatEntry 7 }

		
		-- 1.3.6.1.4.1.1332.1.1.5.3.4.5.1.8
		msanDhcpRaStatFrameErr OBJECT-TYPE
			SYNTAX Counter32
			MAX-ACCESS read-only
			STATUS current
			DESCRIPTION
				"Number of received DHCP packets with errors in frames. "
			::= { msanDhcpRaStatEntry 8 }

		
		-- 1.3.6.1.4.1.1332.1.1.5.3.4.5.1.9
		msanDhcpRaStatOpt82Present OBJECT-TYPE
			SYNTAX Counter32
			MAX-ACCESS read-only
			STATUS current
			DESCRIPTION
				"Number of received DHCP packets with Option 82 or giaddr present. "
			::= { msanDhcpRaStatEntry 9 }

		
		-- 1.3.6.1.4.1.1332.1.1.5.3.4.5.1.10
		msanDhcpRaStatFrameUnsync OBJECT-TYPE
			SYNTAX Counter32
			MAX-ACCESS read-only
			STATUS current
			DESCRIPTION
				"Number of received packets with frames not synchronized with state machines."
			::= { msanDhcpRaStatEntry 10 }

		
		-- 1.3.6.1.4.1.1332.1.1.5.3.4.5.1.11
		msanDhcpRaStatRelease OBJECT-TYPE
			SYNTAX Counter32
			MAX-ACCESS read-only
			STATUS current
			DESCRIPTION
				"Number of received DHCP RELEASE packets."
			::= { msanDhcpRaStatEntry 11 }

		
		-- 1.3.6.1.4.1.1332.1.1.5.3.4.5.1.12
		msanDhcpRaStatInform OBJECT-TYPE
			SYNTAX Counter32
			MAX-ACCESS read-only
			STATUS current
			DESCRIPTION
				"Number of received DHCP INFORM packets."
			::= { msanDhcpRaStatEntry 12 }

		
		-- 1.3.6.1.4.1.1332.1.1.5.3.4.6
		msanDhcpRaVlanConfigTable OBJECT-TYPE
			SYNTAX SEQUENCE OF MsanDhcpRaVlanConfigEntry
			MAX-ACCESS not-accessible
			STATUS current
			DESCRIPTION
				"Table od DHCP RA parameters per Vlan."
			::= { msanDhcpRelay 6 }

		
		-- 1.3.6.1.4.1.1332.1.1.5.3.4.6.1
		msanDhcpRaVlanConfigEntry OBJECT-TYPE
			SYNTAX MsanDhcpRaVlanConfigEntry
			MAX-ACCESS not-accessible
			STATUS current
			DESCRIPTION
				"Description."
			INDEX { dot1qVlanIndex }
			::= { msanDhcpRaVlanConfigTable 1 }

		
		MsanDhcpRaVlanConfigEntry ::=
			SEQUENCE { 
				msanDhcpRaVlanState
					INTEGER,
				msanDhcpRaVlanMode
					INTEGER,
				msanDhcpRaVlanOpt82
					INTEGER,
				msanDhcpRaVlanOpt82ReplyMode
					INTEGER,
				msanDhcpRaVlanOpt82UnicastExtStatus
					INTEGER,
				msanDhcpRaVlanCircuitIdType
					INTEGER
			 }

		-- 1.3.6.1.4.1.1332.1.1.5.3.4.6.1.1
		msanDhcpRaVlanState OBJECT-TYPE
			SYNTAX INTEGER
				{
				disable(1),
				notConfigured(2)
				}
			MAX-ACCESS read-write
			STATUS current
			DESCRIPTION
				"DHCP RA state for specified VLAN ID. Value notConfigured(2) means, that 
				global setting is used(msanDhcpRaStatus)."
			DEFVAL { notConfigured }
			::= { msanDhcpRaVlanConfigEntry 1 }

		
		-- 1.3.6.1.4.1.1332.1.1.5.3.4.6.1.2
		msanDhcpRaVlanMode OBJECT-TYPE
			SYNTAX INTEGER
				{
				full(1),
				simplified(2),
				notConfigured(3)
				}
			MAX-ACCESS read-write
			STATUS current
			DESCRIPTION
				"DHCP RA mode for specified VLAN ID. Value notConfigured(1) means, that 
				global setting is used(msanDhcpRaMode)."
			DEFVAL { notConfigured }
			::= { msanDhcpRaVlanConfigEntry 2 }

		
		-- 1.3.6.1.4.1.1332.1.1.5.3.4.6.1.3
		msanDhcpRaVlanOpt82 OBJECT-TYPE
			SYNTAX INTEGER
				{
				enable(1),
				disable(2),
				notConfigured(3)
				}
			MAX-ACCESS read-write
			STATUS current
			DESCRIPTION
				"Specifies DHCP Relay Agent option 82 insertion status per vlan."
			DEFVAL { notConfigured }
			::= { msanDhcpRaVlanConfigEntry 3 }

		
		-- 1.3.6.1.4.1.1332.1.1.5.3.4.6.1.4
		msanDhcpRaVlanOpt82ReplyMode OBJECT-TYPE
			SYNTAX INTEGER
				{
				keep(1),
				remove(2),
				notConfigured(3)
				}
			MAX-ACCESS read-write
			STATUS current
			DESCRIPTION
				"Specifies DHCP Relay Agent keep/remove option 82 in replies per vlan."
			DEFVAL { notConfigured }
			::= { msanDhcpRaVlanConfigEntry 4 }

		
		-- 1.3.6.1.4.1.1332.1.1.5.3.4.6.1.5
		msanDhcpRaVlanOpt82UnicastExtStatus OBJECT-TYPE
			SYNTAX INTEGER
				{
				enable(1),
				disable(2),
				notConfigured(3)
				}
			MAX-ACCESS read-write
			STATUS current
			DESCRIPTION
				"The desired state of insertion of option 82 in unicast frames per vlan."
			DEFVAL { notConfigured }
			::= { msanDhcpRaVlanConfigEntry 5 }

		
		-- 1.3.6.1.4.1.1332.1.1.5.3.4.6.1.6
		msanDhcpRaVlanCircuitIdType OBJECT-TYPE
			SYNTAX INTEGER
				{
				iskratel(1),
				standard(2),
				notConfigured(3)
				}
			MAX-ACCESS read-write
			STATUS current
			DESCRIPTION
				"Circuit Id syntax mode per vlan."
			DEFVAL { notConfigured }
			::= { msanDhcpRaVlanConfigEntry 6 }

		
		-- 1.3.6.1.4.1.1332.1.1.5.3.4.7
		msanDhcpRaPortVlanConfigTable OBJECT-TYPE
			SYNTAX SEQUENCE OF MsanDhcpRaPortVlanConfigEntry
			MAX-ACCESS not-accessible
			STATUS current
			DESCRIPTION
				"Description."
			::= { msanDhcpRelay 7 }

		
		-- 1.3.6.1.4.1.1332.1.1.5.3.4.7.1
		msanDhcpRaPortVlanConfigEntry OBJECT-TYPE
			SYNTAX MsanDhcpRaPortVlanConfigEntry
			MAX-ACCESS not-accessible
			STATUS current
			DESCRIPTION
				"Description."
			INDEX { ifIndex, dot1qVlanIndex }
			::= { msanDhcpRaPortVlanConfigTable 1 }

		
		MsanDhcpRaPortVlanConfigEntry ::=
			SEQUENCE { 
				msanDhcpRaPortVlanRemoteId
					OCTET STRING,
				msanDhcpRaPortVlanConfigRowStatus
					RowStatus,
				msanDhcpRaPortVlanCircuitIdType
					INTEGER,
				msanDhcpRaPortVlanCircuitId
					DisplayString
			 }

		-- 1.3.6.1.4.1.1332.1.1.5.3.4.7.1.1
		msanDhcpRaPortVlanRemoteId OBJECT-TYPE
			SYNTAX OCTET STRING
			MAX-ACCESS read-write
			STATUS current
			DESCRIPTION
				"The VLAN identifier (refers to dot1qVlanIndex) where DHCP Client resides."
			DEFVAL { "" }
			::= { msanDhcpRaPortVlanConfigEntry 1 }

		
		-- 1.3.6.1.4.1.1332.1.1.5.3.4.7.1.2
		msanDhcpRaPortVlanConfigRowStatus OBJECT-TYPE
			SYNTAX RowStatus
			MAX-ACCESS read-create
			STATUS current
			DESCRIPTION
				"The row status object controls the creation/deletion of rows in this table. 
				For row creation use createAndWait(5) [createAndGo(4) is not supported]."
			::= { msanDhcpRaPortVlanConfigEntry 2 }

		
		-- 1.3.6.1.4.1.1332.1.1.5.3.4.7.1.3
		msanDhcpRaPortVlanCircuitIdType OBJECT-TYPE
			SYNTAX INTEGER
				{
				iskratel(1),
				standard(2),
				notConfigured(3),
				custom(4)
				}
			MAX-ACCESS read-write
			STATUS current
			DESCRIPTION
				"Circuit Id syntax mode per vlan per port."
			DEFVAL { notConfigured }
			::= { msanDhcpRaPortVlanConfigEntry 3 }

		
		-- 1.3.6.1.4.1.1332.1.1.5.3.4.7.1.4
		msanDhcpRaPortVlanCircuitId OBJECT-TYPE
			SYNTAX DisplayString
			MAX-ACCESS read-only
			STATUS current
			DESCRIPTION
				"Option 82 Circuit Id per vlan per port."
			::= { msanDhcpRaPortVlanConfigEntry 4 }

		
		-- 1.3.6.1.4.1.1332.1.1.5.3.4.100
		msanDhcpv6RaGlobal OBJECT IDENTIFIER ::= { msanDhcpRelay 100 }

		
		-- 1.3.6.1.4.1.1332.1.1.5.3.4.100.1
		msanDhcpv6RaState OBJECT-TYPE
			SYNTAX INTEGER
				{
				enable(1),
				disable(2)
				}
			MAX-ACCESS read-write
			STATUS current
			DESCRIPTION
				"DHCPv6 Relay Agent status."
			DEFVAL { disable }
			::= { msanDhcpv6RaGlobal 1 }

		
		-- 1.3.6.1.4.1.1332.1.1.5.3.4.100.2
		msanDhcpv6RaMode OBJECT-TYPE
			SYNTAX INTEGER { ldra(1) }
			MAX-ACCESS read-write
			STATUS current
			DESCRIPTION
				"DHCPv6 Relay Agent mode.
				ldra = Lightweight DHCPRv6"
			DEFVAL { ldra }
			::= { msanDhcpv6RaGlobal 2 }

		
		-- 1.3.6.1.4.1.1332.1.1.5.3.4.100.3
		msanDhcpv6RaInterfaceIdStandard OBJECT-TYPE
			SYNTAX INTEGER
				{
				enable(1),
				disable(2)
				}
			MAX-ACCESS read-write
			STATUS current
			DESCRIPTION
				"DHCPv6 RA Standard Interface Id type."
			DEFVAL { enable }
			::= { msanDhcpv6RaGlobal 3 }

		
		-- 1.3.6.1.4.1.1332.1.1.5.3.4.100.4
		msanDhcpv6RaInterfaceIdInnerVlan OBJECT-TYPE
			SYNTAX Integer32
			MAX-ACCESS read-write
			STATUS current
			DESCRIPTION
				"Include Inner VLAN (C-VLAN) in Circuit Id when port is in DVLAN Tunneling mode (msanPortDVlanTagMode = enable)."
			::= { msanDhcpv6RaGlobal 4 }

		
		-- 1.3.6.1.4.1.1332.1.1.5.3.4.100.5
		msanDhcpv6RaInterfaceIdCustomFormat OBJECT-TYPE
			SYNTAX DisplayString
			MAX-ACCESS read-write
			STATUS current
			DESCRIPTION
				"DHCPv6 Interface Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanDhcpv6RaGlobal 5 }

		
		-- 1.3.6.1.4.1.1332.1.1.5.3.4.100.6
		msanDhcpv6RaRemoteIdCustomFormat OBJECT-TYPE
			SYNTAX DisplayString
			MAX-ACCESS read-write
			STATUS current
			DESCRIPTION
				"DHCPv6  Remote Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "$PORT_REM_ID" }
			::= { msanDhcpv6RaGlobal 6 }

		
		-- 1.3.6.1.4.1.1332.1.1.5.3.4.101
		msanDhcpv6RaStatistics OBJECT IDENTIFIER ::= { msanDhcpRelay 101 }

		
		-- 1.3.6.1.4.1.1332.1.1.5.3.4.101.1
		msanDhcpv6RaPortStatTable OBJECT-TYPE
			SYNTAX SEQUENCE OF MsanDhcpv6RaPortStatEntry
			MAX-ACCESS not-accessible
			STATUS current
			DESCRIPTION
				"Description."
			::= { msanDhcpv6RaStatistics 1 }

		
		-- 1.3.6.1.4.1.1332.1.1.5.3.4.101.1.1
		msanDhcpv6RaPortStatEntry OBJECT-TYPE
			SYNTAX MsanDhcpv6RaPortStatEntry
			MAX-ACCESS not-accessible
			STATUS current
			DESCRIPTION
				"Description."
			INDEX { ifIndex }
			::= { msanDhcpv6RaPortStatTable 1 }

		
		MsanDhcpv6RaPortStatEntry ::=
			SEQUENCE { 
				msanDhcpv6PortRaStatSolicit
					Integer32,
				msanDhcpv6PortRaStatAdvertise
					Integer32,
				msanDhcpv6PortRaStatRequest
					Integer32,
				msanDhcpv6PortRaStatReply
					Integer32,
				msanDhcpv6PortRaStatRenew
					Integer32,
				msanDhcpv6PortRaStatRebind
					Integer32,
				msanDhcpv6PortRaStatDecline
					Integer32,
				msanDhcpv6PortRaStatReconfigure
					Integer32,
				msanDhcpv6PortRaStatRelease
					Integer32,
				msanDhcpv6PortRaStatInformRequest
					Integer32,
				msanDhcpv6PortRaStatRelayForward
					Integer32,
				msanDhcpv6PortRaStatRelayReply
					Integer32,
				msanDhcpv6PortRaStatOversizeError
					Integer32,
				msanDhcpv6PortRaStatFrameError
					Integer32,
				msanDhcpv6PortRaStatFrameUnsyncError
					Integer32,
				msanDhcpv6PortRaStatSysError
					Integer32
			 }

		-- 1.3.6.1.4.1.1332.1.1.5.3.4.101.1.1.1
		msanDhcpv6PortRaStatSolicit OBJECT-TYPE
			SYNTAX Integer32
			MAX-ACCESS read-only
			STATUS current
			DESCRIPTION
				"Number of received DHCPv6 solicit packets."
			::= { msanDhcpv6RaPortStatEntry 1 }

		
		-- 1.3.6.1.4.1.1332.1.1.5.3.4.101.1.1.2
		msanDhcpv6PortRaStatAdvertise OBJECT-TYPE
			SYNTAX Integer32
			MAX-ACCESS read-only
			STATUS current
			DESCRIPTION
				"Number of received DHCPv6 advertise packets."
			::= { msanDhcpv6RaPortStatEntry 2 }

		
		-- 1.3.6.1.4.1.1332.1.1.5.3.4.101.1.1.3
		msanDhcpv6PortRaStatRequest OBJECT-TYPE
			SYNTAX Integer32
			MAX-ACCESS read-only
			STATUS current
			DESCRIPTION
				"Number of received DHCPv6 request packets."
			::= { msanDhcpv6RaPortStatEntry 3 }

		
		-- 1.3.6.1.4.1.1332.1.1.5.3.4.101.1.1.4
		msanDhcpv6PortRaStatReply OBJECT-TYPE
			SYNTAX Integer32
			MAX-ACCESS read-only
			STATUS current
			DESCRIPTION
				"Number of received DHCPv6 reply packets."
			::= { msanDhcpv6RaPortStatEntry 4 }

		
		-- 1.3.6.1.4.1.1332.1.1.5.3.4.101.1.1.5
		msanDhcpv6PortRaStatRenew OBJECT-TYPE
			SYNTAX Integer32
			MAX-ACCESS read-only
			STATUS current
			DESCRIPTION
				"Number of received DHCPv6 renew packets."
			::= { msanDhcpv6RaPortStatEntry 5 }

		
		-- 1.3.6.1.4.1.1332.1.1.5.3.4.101.1.1.6
		msanDhcpv6PortRaStatRebind OBJECT-TYPE
			SYNTAX Integer32
			MAX-ACCESS read-only
			STATUS current
			DESCRIPTION
				"Number of received DHCPv6 rebind packets."
			::= { msanDhcpv6RaPortStatEntry 6 }

		
		-- 1.3.6.1.4.1.1332.1.1.5.3.4.101.1.1.7
		msanDhcpv6PortRaStatDecline OBJECT-TYPE
			SYNTAX Integer32
			MAX-ACCESS read-only
			STATUS current
			DESCRIPTION
				"Number of received DHCPv6 decline packets."
			::= { msanDhcpv6RaPortStatEntry 7 }

		
		-- 1.3.6.1.4.1.1332.1.1.5.3.4.101.1.1.8
		msanDhcpv6PortRaStatReconfigure OBJECT-TYPE
			SYNTAX Integer32
			MAX-ACCESS read-only
			STATUS current
			DESCRIPTION
				"Number of received DHCPv6 reconfigure packets."
			::= { msanDhcpv6RaPortStatEntry 8 }

		
		-- 1.3.6.1.4.1.1332.1.1.5.3.4.101.1.1.9
		msanDhcpv6PortRaStatRelease OBJECT-TYPE
			SYNTAX Integer32
			MAX-ACCESS read-only
			STATUS current
			DESCRIPTION
				"Number of received DHCPv6 release packets."
			::= { msanDhcpv6RaPortStatEntry 9 }

		
		-- 1.3.6.1.4.1.1332.1.1.5.3.4.101.1.1.10
		msanDhcpv6PortRaStatInformRequest OBJECT-TYPE
			SYNTAX Integer32
			MAX-ACCESS read-only
			STATUS current
			DESCRIPTION
				"Number of received DHCPv6 inform request packets."
			::= { msanDhcpv6RaPortStatEntry 10 }

		
		-- 1.3.6.1.4.1.1332.1.1.5.3.4.101.1.1.11
		msanDhcpv6PortRaStatRelayForward OBJECT-TYPE
			SYNTAX Integer32
			MAX-ACCESS read-only
			STATUS current
			DESCRIPTION
				"Number of received DHCPv6 relay forward packets."
			::= { msanDhcpv6RaPortStatEntry 11 }

		
		-- 1.3.6.1.4.1.1332.1.1.5.3.4.101.1.1.12
		msanDhcpv6PortRaStatRelayReply OBJECT-TYPE
			SYNTAX Integer32
			MAX-ACCESS read-only
			STATUS current
			DESCRIPTION
				"Number of received DHCPv6 relay reply packets."
			::= { msanDhcpv6RaPortStatEntry 12 }

		
		-- 1.3.6.1.4.1.1332.1.1.5.3.4.101.1.1.100
		msanDhcpv6PortRaStatOversizeError OBJECT-TYPE
			SYNTAX Integer32
			MAX-ACCESS read-only
			STATUS current
			DESCRIPTION
				"Number of discarded packets because max packet size exceeded."
			::= { msanDhcpv6RaPortStatEntry 100 }

		
		-- 1.3.6.1.4.1.1332.1.1.5.3.4.101.1.1.101
		msanDhcpv6PortRaStatFrameError OBJECT-TYPE
			SYNTAX Integer32
			MAX-ACCESS read-only
			STATUS current
			DESCRIPTION
				"Number of discarded packets because frame error."
			::= { msanDhcpv6RaPortStatEntry 101 }

		
		-- 1.3.6.1.4.1.1332.1.1.5.3.4.101.1.1.102
		msanDhcpv6PortRaStatFrameUnsyncError OBJECT-TYPE
			SYNTAX Integer32
			MAX-ACCESS read-only
			STATUS current
			DESCRIPTION
				"Number of received packets with frames not synchronized with state machines."
			::= { msanDhcpv6RaPortStatEntry 102 }

		
		-- 1.3.6.1.4.1.1332.1.1.5.3.4.101.1.1.103
		msanDhcpv6PortRaStatSysError OBJECT-TYPE
			SYNTAX Integer32
			MAX-ACCESS read-only
			STATUS current
			DESCRIPTION
				"Number of discarded packets because system  error."
			::= { msanDhcpv6RaPortStatEntry 103 }

		
		-- 1.3.6.1.4.1.1332.1.1.5.3.4.101.100
		msanDhcpv6RaStatSolicit OBJECT-TYPE
			SYNTAX Counter32
			MAX-ACCESS read-only
			STATUS current
			DESCRIPTION
				"Number of received DHCPv6 solicit packets."
			::= { msanDhcpv6RaStatistics 100 }

		
		-- 1.3.6.1.4.1.1332.1.1.5.3.4.101.101
		msanDhcpv6RaStatAdvertise OBJECT-TYPE
			SYNTAX Counter32
			MAX-ACCESS read-only
			STATUS current
			DESCRIPTION
				"Number of received DHCPv6 advertise packets."
			::= { msanDhcpv6RaStatistics 101 }

		
		-- 1.3.6.1.4.1.1332.1.1.5.3.4.101.102
		msanDhcpv6RaStatRequest OBJECT-TYPE
			SYNTAX Counter32
			MAX-ACCESS read-only
			STATUS current
			DESCRIPTION
				"Number of received DHCPv6 request packets."
			::= { msanDhcpv6RaStatistics 102 }

		
		-- 1.3.6.1.4.1.1332.1.1.5.3.4.101.103
		msanDhcpv6RaStatReply OBJECT-TYPE
			SYNTAX Counter32
			MAX-ACCESS read-only
			STATUS current
			DESCRIPTION
				"Number of received DHCPv6 reply packets."
			::= { msanDhcpv6RaStatistics 103 }

		
		-- 1.3.6.1.4.1.1332.1.1.5.3.4.101.104
		msanDhcpv6RaStatRenew OBJECT-TYPE
			SYNTAX Counter32
			MAX-ACCESS read-only
			STATUS current
			DESCRIPTION
				"Number of received DHCPv6 renew packets."
			::= { msanDhcpv6RaStatistics 104 }

		
		-- 1.3.6.1.4.1.1332.1.1.5.3.4.101.105
		msanDhcpv6RaStatRebind OBJECT-TYPE
			SYNTAX Counter32
			MAX-ACCESS read-only
			STATUS current
			DESCRIPTION
				"Number of received DHCPv6 rebind packets."
			::= { msanDhcpv6RaStatistics 105 }

		
		-- 1.3.6.1.4.1.1332.1.1.5.3.4.101.106
		msanDhcpv6RaStatDecline OBJECT-TYPE
			SYNTAX Counter32
			MAX-ACCESS read-only
			STATUS current
			DESCRIPTION
				"Number of received DHCPv6 decline packets."
			::= { msanDhcpv6RaStatistics 106 }

		
		-- 1.3.6.1.4.1.1332.1.1.5.3.4.101.107
		msanDhcpv6RaStatReconfigure OBJECT-TYPE
			SYNTAX Counter32
			MAX-ACCESS read-only
			STATUS current
			DESCRIPTION
				"Number of received DHCPv6 reconfigure packets."
			::= { msanDhcpv6RaStatistics 107 }

		
		-- 1.3.6.1.4.1.1332.1.1.5.3.4.101.108
		msanDhcpv6RaStatRelease OBJECT-TYPE
			SYNTAX Counter32
			MAX-ACCESS read-only
			STATUS current
			DESCRIPTION
				"Number of received DHCPv6 reconfigure packets."
			::= { msanDhcpv6RaStatistics 108 }

		
		-- 1.3.6.1.4.1.1332.1.1.5.3.4.101.109
		msanDhcpv6RaStatInformRequest OBJECT-TYPE
			SYNTAX Counter32
			MAX-ACCESS read-only
			STATUS current
			DESCRIPTION
				"Number of received DHCPv6 inform request packets."
			::= { msanDhcpv6RaStatistics 109 }

		
		-- 1.3.6.1.4.1.1332.1.1.5.3.4.101.110
		msanDhcpv6RaStatRelayForward OBJECT-TYPE
			SYNTAX Counter32
			MAX-ACCESS read-only
			STATUS current
			DESCRIPTION
				"Number of received DHCPv6 Relay Forward packets."
			::= { msanDhcpv6RaStatistics 110 }

		
		-- 1.3.6.1.4.1.1332.1.1.5.3.4.101.112
		msanDhcpv6RaStatRelayReply OBJECT-TYPE
			SYNTAX Counter32
			MAX-ACCESS read-only
			STATUS current
			DESCRIPTION
				"Number of received DHCPv6 Relay Reply packets."
			::= { msanDhcpv6RaStatistics 112 }

		
		-- 1.3.6.1.4.1.1332.1.1.5.3.4.101.200
		msanDhcpv6RaStatOversizeError OBJECT-TYPE
			SYNTAX Counter32
			MAX-ACCESS read-only
			STATUS current
			DESCRIPTION
				"Number of discarded packets because max packet size exceeded."
			::= { msanDhcpv6RaStatistics 200 }

		
		-- 1.3.6.1.4.1.1332.1.1.5.3.4.101.201
		msanDhcpv6RaStatFrameError OBJECT-TYPE
			SYNTAX Counter32
			MAX-ACCESS read-only
			STATUS current
			DESCRIPTION
				"Number of discareded packets because errors in frame."
			::= { msanDhcpv6RaStatistics 201 }

		
		-- 1.3.6.1.4.1.1332.1.1.5.3.4.101.202
		msanDhcpv6RaStatFrameUnsyncError OBJECT-TYPE
			SYNTAX Counter32
			MAX-ACCESS read-only
			STATUS current
			DESCRIPTION
				"Number of received packets with frames not synchronized with state machines."
			::= { msanDhcpv6RaStatistics 202 }

		
		-- 1.3.6.1.4.1.1332.1.1.5.3.4.101.203
		msanDhcpv6RaStatSysError OBJECT-TYPE
			SYNTAX Counter32
			MAX-ACCESS read-only
			STATUS current
			DESCRIPTION
				"Number of discared packets because system error."
			::= { msanDhcpv6RaStatistics 203 }

		
		-- 1.3.6.1.4.1.1332.1.1.5.3.4.102
		msanDhcpv6RaPortConfigTable OBJECT-TYPE
			SYNTAX SEQUENCE OF MsanDhcpv6RaPortConfigEntry
			MAX-ACCESS not-accessible
			STATUS current
			DESCRIPTION
				"Table od DHCP RA parameters per port."
			::= { msanDhcpRelay 102 }

		
		-- 1.3.6.1.4.1.1332.1.1.5.3.4.102.1
		msanDhcpv6RaPortConfigEntry OBJECT-TYPE
			SYNTAX MsanDhcpv6RaPortConfigEntry
			MAX-ACCESS not-accessible
			STATUS current
			DESCRIPTION
				"Description."
			INDEX { ifIndex }
			::= { msanDhcpv6RaPortConfigTable 1 }

		
		MsanDhcpv6RaPortConfigEntry ::=
			SEQUENCE { 
				msanDhcpv6RaPortState
					INTEGER,
				msanDhcpv6RaPortTrusted
					INTEGER,
				msanDhcpv6RaPortInterfaceIdStandard
					INTEGER,
				msanDhcpv6RaPortInterfaceId
					OCTET STRING,
				msanDhcpv6RaPortRemoteId
					OCTET STRING,
				msanDhcpv6RaPortRemoteIdEnterpriseNum
					INTEGER
			 }

		-- 1.3.6.1.4.1.1332.1.1.5.3.4.102.1.1
		msanDhcpv6RaPortState OBJECT-TYPE
			SYNTAX INTEGER
				{
				enable(1),
				enableCli(2),
				enableSrv(3),
				disable(4)
				}
			MAX-ACCESS read-write
			STATUS current
			DESCRIPTION
				"State of DHCPv6 Relay Agent on the port (enable, disable, enable-client, enable-server) "
			DEFVAL { enable }
			::= { msanDhcpv6RaPortConfigEntry 1 }

		
		-- 1.3.6.1.4.1.1332.1.1.5.3.4.102.1.2
		msanDhcpv6RaPortTrusted OBJECT-TYPE
			SYNTAX INTEGER
				{
				enable(1),
				disable(2)
				}
			MAX-ACCESS read-write
			STATUS current
			DESCRIPTION
				"Specifies DHCP RA Circuit type per port as trusted(1) or untrusted(2).
				Default value for user ports is untrusted(2) and for network ports trusted(1).
				"
			::= { msanDhcpv6RaPortConfigEntry 2 }

		
		-- 1.3.6.1.4.1.1332.1.1.5.3.4.102.1.3
		msanDhcpv6RaPortInterfaceIdStandard OBJECT-TYPE
			SYNTAX INTEGER
				{
				enable(1),
				disable(2)
				}
			MAX-ACCESS read-write
			STATUS current
			DESCRIPTION
				"DHCPv6 RA Standard Interface Id syntax mode."
			DEFVAL { enable }
			::= { msanDhcpv6RaPortConfigEntry 3 }

		
		-- 1.3.6.1.4.1.1332.1.1.5.3.4.102.1.4
		msanDhcpv6RaPortInterfaceId OBJECT-TYPE
			SYNTAX OCTET STRING
			MAX-ACCESS read-only
			STATUS current
			DESCRIPTION
				"DHCPv6 Interface Id."
			::= { msanDhcpv6RaPortConfigEntry 4 }

		
		-- 1.3.6.1.4.1.1332.1.1.5.3.4.102.1.5
		msanDhcpv6RaPortRemoteId OBJECT-TYPE
			SYNTAX OCTET STRING
			MAX-ACCESS read-write
			STATUS current
			DESCRIPTION
				"DHCPv6 Remote Id value for the port.
				If empty string, remote id is not added to DHCPv6 package."
			DEFVAL { "" }
			::= { msanDhcpv6RaPortConfigEntry 5 }

		
		-- 1.3.6.1.4.1.1332.1.1.5.3.4.102.1.6
		msanDhcpv6RaPortRemoteIdEnterpriseNum OBJECT-TYPE
			SYNTAX INTEGER (1..999999)
			MAX-ACCESS read-write
			STATUS current
			DESCRIPTION
				"DHCPv6 Remote Id enterprise number for the port.
				"
			DEFVAL { 1332 }
			::= { msanDhcpv6RaPortConfigEntry 6 }

		
		-- 1.3.6.1.4.1.1332.1.1.5.3.4.103
		msanDhcpv6RaVlanConfigTable OBJECT-TYPE
			SYNTAX SEQUENCE OF MsanDhcpv6RaVlanConfigEntry
			MAX-ACCESS not-accessible
			STATUS current
			DESCRIPTION
				"Table od DHCP RA parameters per Vlan."
			::= { msanDhcpRelay 103 }

		
		-- 1.3.6.1.4.1.1332.1.1.5.3.4.103.1
		msanDhcpv6RaVlanConfigEntry OBJECT-TYPE
			SYNTAX MsanDhcpv6RaVlanConfigEntry
			MAX-ACCESS not-accessible
			STATUS current
			DESCRIPTION
				"Description."
			INDEX { dot1qVlanIndex }
			::= { msanDhcpv6RaVlanConfigTable 1 }

		
		MsanDhcpv6RaVlanConfigEntry ::=
			SEQUENCE { 
				msanDhcpv6RaVlanState
					INTEGER,
				msanDhcpv6RaVlanInterfaceIdStandard
					INTEGER
			 }

		-- 1.3.6.1.4.1.1332.1.1.5.3.4.103.1.1
		msanDhcpv6RaVlanState OBJECT-TYPE
			SYNTAX INTEGER
				{
				enable(1),
				disable(2)
				}
			MAX-ACCESS read-write
			STATUS current
			DESCRIPTION
				"DHCP RA state for specified VLAN ID. "
			DEFVAL { enable }
			::= { msanDhcpv6RaVlanConfigEntry 1 }

		
		-- 1.3.6.1.4.1.1332.1.1.5.3.4.103.1.2
		msanDhcpv6RaVlanInterfaceIdStandard OBJECT-TYPE
			SYNTAX INTEGER
				{
				enable(1),
				disable(2)
				}
			MAX-ACCESS read-write
			STATUS current
			DESCRIPTION
				"DHCPv6 RA Standard Interface Id syntax mode."
			DEFVAL { enable }
			::= { msanDhcpv6RaVlanConfigEntry 2 }

		
		-- 1.3.6.1.4.1.1332.1.1.5.3.4.104
		msanDhcpv6RaPortVlanConfigTable OBJECT-TYPE
			SYNTAX SEQUENCE OF MsanDhcpv6RaPortVlanConfigEntry
			MAX-ACCESS not-accessible
			STATUS current
			DESCRIPTION
				"Description."
			::= { msanDhcpRelay 104 }

		
		-- 1.3.6.1.4.1.1332.1.1.5.3.4.104.1
		msanDhcpv6RaPortVlanConfigEntry OBJECT-TYPE
			SYNTAX MsanDhcpv6RaPortVlanConfigEntry
			MAX-ACCESS not-accessible
			STATUS current
			DESCRIPTION
				"Description."
			INDEX { ifIndex, dot1qVlanIndex }
			::= { msanDhcpv6RaPortVlanConfigTable 1 }

		
		MsanDhcpv6RaPortVlanConfigEntry ::=
			SEQUENCE { 
				msanDhcpv6RaPortVlanRemoteId
					OCTET STRING,
				msanDhcpv6RaPortVlanRemoteIdEnterpriseNum
					INTEGER,
				msanDhcpv6RaPortVlanRowStatus
					RowStatus
			 }

		-- 1.3.6.1.4.1.1332.1.1.5.3.4.104.1.1
		msanDhcpv6RaPortVlanRemoteId OBJECT-TYPE
			SYNTAX OCTET STRING
			MAX-ACCESS read-write
			STATUS current
			DESCRIPTION
				"DHCPv6 Remote Id value for specified vlan_id per port.
				"
			DEFVAL { "" }
			::= { msanDhcpv6RaPortVlanConfigEntry 1 }

		
		-- 1.3.6.1.4.1.1332.1.1.5.3.4.104.1.2
		msanDhcpv6RaPortVlanRemoteIdEnterpriseNum OBJECT-TYPE
			SYNTAX INTEGER (1..999999)
			MAX-ACCESS read-write
			STATUS current
			DESCRIPTION
				"DHCPv6 Remote Id enterprise number for specified vlan_id per port.
				"
			DEFVAL { 1332 }
			::= { msanDhcpv6RaPortVlanConfigEntry 2 }

		
		-- 1.3.6.1.4.1.1332.1.1.5.3.4.104.1.3
		msanDhcpv6RaPortVlanRowStatus OBJECT-TYPE
			SYNTAX RowStatus
			MAX-ACCESS read-create
			STATUS current
			DESCRIPTION
				"The row status object controls the creation/deletion of rows in this table. 
				For row creation use createAndWait(5) [createAndGo(4) is not supported]."
			::= { msanDhcpv6RaPortVlanConfigEntry 3 }

		
		-- 1.3.6.1.4.1.1332.1.1.5.3.5
		msanSntp OBJECT IDENTIFIER ::= { msanAdditionalConf 5 }

		
		-- 1.3.6.1.4.1.1332.1.1.5.3.5.1
		msanSntpGlobal OBJECT IDENTIFIER ::= { msanSntp 1 }

		
		-- 1.3.6.1.4.1.1332.1.1.5.3.5.1.1
		msanSntpTzOffset OBJECT-TYPE
			SYNTAX OCTET STRING
			MAX-ACCESS read-write
			STATUS current
			DESCRIPTION
				"Specifies the time zone offset time in format hh:mm. Allowed range is -12 to 13."
			::= { msanSntpGlobal 1 }

		
		-- 1.3.6.1.4.1.1332.1.1.5.3.5.1.2
		msanSntpTzName OBJECT-TYPE
			SYNTAX OCTET STRING (SIZE (0..32))
			MAX-ACCESS read-write
			STATUS current
			DESCRIPTION
				"Time Zone name."
			::= { msanSntpGlobal 2 }

		
		-- 1.3.6.1.4.1.1332.1.1.5.3.5.1.3
		msanSntpTzDstOffset OBJECT-TYPE
			SYNTAX OCTET STRING
			MAX-ACCESS read-write
			STATUS current
			DESCRIPTION
				"Specifies the daylight saving time offset time in format hh:mm. Allowed range is -12 to 13."
			::= { msanSntpGlobal 3 }

		
		-- 1.3.6.1.4.1.1332.1.1.5.3.5.1.4
		msanSntpTzDstStartMonth OBJECT-TYPE
			SYNTAX Integer32 (1..12)
			MAX-ACCESS read-write
			STATUS current
			DESCRIPTION
				"Specifies the daylight saving time start month. "
			::= { msanSntpGlobal 4 }

		
		-- 1.3.6.1.4.1.1332.1.1.5.3.5.1.5
		msanSntpTzDstStartWeek OBJECT-TYPE
			SYNTAX Integer32 (1..5)
			MAX-ACCESS read-write
			STATUS current
			DESCRIPTION
				"Specifies the daylight saving time start week."
			::= { msanSntpGlobal 5 }

		
		-- 1.3.6.1.4.1.1332.1.1.5.3.5.1.6
		msanSntpTzDstStartDayInWeek OBJECT-TYPE
			SYNTAX INTEGER
				{
				monday(1),
				tuesday(2),
				wednesday(3),
				thursday(4),
				friday(5),
				saturday(6),
				sunday(7)
				}
			MAX-ACCESS read-write
			STATUS current
			DESCRIPTION
				"Specifies the daylight saving time start day in week."
			::= { msanSntpGlobal 6 }

		
		-- 1.3.6.1.4.1.1332.1.1.5.3.5.1.7
		msanSntpTzDstStartTime OBJECT-TYPE
			SYNTAX OCTET STRING
			MAX-ACCESS read-write
			STATUS current
			DESCRIPTION
				"Specifies the daylight saving time start time. Allowed range is 00:00 to 23:59."
			::= { msanSntpGlobal 7 }

		
		-- 1.3.6.1.4.1.1332.1.1.5.3.5.1.8
		msanSntpTzDstEndMonth OBJECT-TYPE
			SYNTAX Integer32 (1..12)
			MAX-ACCESS read-write
			STATUS current
			DESCRIPTION
				"Specifies the daylight saving time end month."
			::= { msanSntpGlobal 8 }

		
		-- 1.3.6.1.4.1.1332.1.1.5.3.5.1.9
		msanSntpTzDstEndWeek OBJECT-TYPE
			SYNTAX Integer32 (1..5)
			MAX-ACCESS read-write
			STATUS current
			DESCRIPTION
				"Specifies the daylight saving time end week."
			::= { msanSntpGlobal 9 }

		
		-- 1.3.6.1.4.1.1332.1.1.5.3.5.1.10
		msanSntpTzDstEndDayInWeek OBJECT-TYPE
			SYNTAX INTEGER
				{
				monday(1),
				tuesday(2),
				wednesday(3),
				thursday(4),
				friday(5),
				saturday(6),
				sunday(7)
				}
			MAX-ACCESS read-write
			STATUS current
			DESCRIPTION
				"Specifies the daylight saving time end start day in week."
			::= { msanSntpGlobal 10 }

		
		-- 1.3.6.1.4.1.1332.1.1.5.3.5.1.11
		msanSntpTzDstEndTime OBJECT-TYPE
			SYNTAX OCTET STRING
			MAX-ACCESS read-write
			STATUS current
			DESCRIPTION
				"Specifies the daylight saving time end time. Allowed range is 00:00 to 23:59"
			::= { msanSntpGlobal 11 }

		
		-- 1.3.6.1.4.1.1332.1.1.5.3.7
		msanSnmp OBJECT IDENTIFIER ::= { msanAdditionalConf 7 }

		
		-- 1.3.6.1.4.1.1332.1.1.5.3.7.1
		msanSnmpGlobal OBJECT IDENTIFIER ::= { msanSnmp 1 }

		
		-- 1.3.6.1.4.1.1332.1.1.5.3.7.1.1
		msanSnmpTrapRecvUdpPort OBJECT-TYPE
			SYNTAX Unsigned32 (0..65535)
			MAX-ACCESS read-write
			STATUS current
			DESCRIPTION
				"The UDP Port where SNMP traps are to be sent."
			::= { msanSnmpGlobal 1 }

		
		-- 1.3.6.1.4.1.1332.1.1.5.3.7.1.2
		msanIfOperStatusChangeCnt OBJECT-TYPE
			SYNTAX Integer32
			MAX-ACCESS read-only
			STATUS current
			DESCRIPTION
				"Interface operational status change counter."
			::= { msanSnmpGlobal 2 }

		
		-- 1.3.6.1.4.1.1332.1.1.5.3.7.2
		msanSnmpNotifications OBJECT IDENTIFIER ::= { msanSnmp 2 }

		
		-- 1.3.6.1.4.1.1332.1.1.5.3.7.2.1
		msanSnmpOnuIfStatusChanged NOTIFICATION-TYPE
			OBJECTS { ifDescr, ifAdminStatus, ifOperStatus, msanOnuInfoSerialNumber, msanOnuInfoVersion, 
				msanOnuInfoEquipmentId, msanOnuInfoOnuHardwareType, msanOnuInfoOnuImageInstance0Version, msanOnuInfoOnuImageInstance0Valid, msanOnuInfoOnuImageInstance0Activate, 
				msanOnuInfoOnuImageInstance1Version, msanOnuInfoOnuImageInstance1Valid, msanOnuInfoOnuImageInstance1Activate, msanOnuInfoOnuMacAddress, msanOnuIfOperStatusChangeCnt
				 }
			STATUS current
			DESCRIPTION 
				"ONU interface status changed notification."
			::= { msanSnmpNotifications 1 }

		
		-- 1.3.6.1.4.1.1332.1.1.5.3.7.2.2
		msanSnmpOnuBlackListAdded NOTIFICATION-TYPE
			OBJECTS { ifDescr, msanOnuBlackListSerialNumber, msanOnuBlackListPassword, msanOnuBlackListCause, msanOnuBlackListChangeCnt
				 }
			STATUS current
			DESCRIPTION 
				"ONU added to Blacklist notification."
			::= { msanSnmpNotifications 2 }

		
		-- 1.3.6.1.4.1.1332.1.1.5.3.7.2.3
		msanSnmpOnuBlackListRemoved NOTIFICATION-TYPE
			OBJECTS { ifDescr, msanOnuBlackListSerialNumber, msanOnuBlackListChangeCnt }
			STATUS current
			DESCRIPTION 
				"ONU removed from Blacklist notification."
			::= { msanSnmpNotifications 3 }

		
		-- 1.3.6.1.4.1.1332.1.1.5.3.7.2.4
		msanSnmpIfStatusChanged NOTIFICATION-TYPE
			OBJECTS { ifDescr, ifAdminStatus, ifOperStatus, msanIfOperStatusChangeCnt }
			STATUS current
			DESCRIPTION 
				"Interface status changed notification."
			::= { msanSnmpNotifications 4 }

		
		-- 1.3.6.1.4.1.1332.1.1.5.3.8
		msanIgmpSnooping OBJECT IDENTIFIER ::= { msanAdditionalConf 8 }

		
		-- 1.3.6.1.4.1.1332.1.1.5.3.8.1
		msanIgmpSnoopingGlobal OBJECT IDENTIFIER ::= { msanIgmpSnooping 1 }

		
		-- 1.3.6.1.4.1.1332.1.1.5.3.8.1.1
		msanIgmpSnoopingReportSuppression OBJECT-TYPE
			SYNTAX INTEGER
				{
				disable(0),
				enable(1)
				}
			MAX-ACCESS read-write
			STATUS current
			DESCRIPTION
				"Report suppression mode for IGMP Snooping for the switch.
				"
			::= { msanIgmpSnoopingGlobal 1 }

		
		-- 1.3.6.1.4.1.1332.1.1.5.3.8.1.2
		msanIgmpSnoopingAdminState OBJECT-TYPE
			SYNTAX INTEGER
				{
				disableAndDiscard(0),
				disableAndBroadcast(1),
				enable(2),
				enableAndUnknownGroupFlood(3),
				enableAndMrouterFlood(4)
				}
			MAX-ACCESS read-write
			STATUS current
			DESCRIPTION
				"IGMP snooping global state.
				
				Values enableAndUnknownGroupFlood(3)  and enableAndMrouterFlood(4) are relevant only
				for MSAN Ethernet switch (ES) products, where enableAndUnknownGroupFlood(3) is supported 
				only on IDC board."
			::= { msanIgmpSnoopingGlobal 2 }

		
		-- 1.3.6.1.4.1.1332.1.1.5.3.8.1.3
		msanIgmpSnoopingLoggingVlanId OBJECT-TYPE
			SYNTAX Integer32 (0..4094)
			MAX-ACCESS read-write
			STATUS current
			DESCRIPTION
				"VLAN Id on which IGMP snooping logging is performed. Value 0 means that logging is disabled. "
			::= { msanIgmpSnoopingGlobal 3 }

		
		-- 1.3.6.1.4.1.1332.1.1.5.3.8.1.4
		msanIgmpSnoopingViolationAction OBJECT-TYPE
			SYNTAX INTEGER
				{
				remove(1),
				discard(2)
				}
			MAX-ACCESS read-write
			STATUS current
			DESCRIPTION
				"Removing one of the existing (the oldest) multicast group membership, or
				discarding a new group membership request.
				"
			::= { msanIgmpSnoopingGlobal 4 }

		
		-- 1.3.6.1.4.1.1332.1.1.5.3.8.1.5
		msanIgmpSnoopingFastLeaveAdminMode OBJECT-TYPE
			SYNTAX INTEGER
				{
				enable(1),
				disable(2)
				}
			MAX-ACCESS read-write
			STATUS current
			DESCRIPTION
				"This enables or disables IGMP Snooping Fast-Leave on user ports."
			DEFVAL { enable }
			::= { msanIgmpSnoopingGlobal 5 }

		
		-- 1.3.6.1.4.1.1332.1.1.5.3.8.1.6
		msanIgmpSnoopingGroupMembershipInterval OBJECT-TYPE
			SYNTAX Integer32 (2..3600)
			MAX-ACCESS read-write
			STATUS current
			DESCRIPTION
				"The amount of time in seconds that a switch will wait for a report
				from a particular group on the selected interface before deleting the
				interface from the entry. 
				This value must be greater than msanIgmpSnoopingMaxResponseTime
				"
			DEFVAL { 260 }
			::= { msanIgmpSnoopingGlobal 6 }

		
		-- 1.3.6.1.4.1.1332.1.1.5.3.8.1.7
		msanIgmpSnoopingMaxResponseTime OBJECT-TYPE
			SYNTAX Integer32 (1..3599)
			MAX-ACCESS read-write
			STATUS current
			DESCRIPTION
				"The amount of time in seconds a switch will wait on a report after sending
				a query on the selected interface.  
				This value must be less than msanIgmpSnoopingGroupMembershipInterval
				"
			DEFVAL { '10'b }
			::= { msanIgmpSnoopingGlobal 7 }

		
		-- 1.3.6.1.4.1.1332.1.1.5.3.8.1.8
		msanIgmpVersion OBJECT-TYPE
			SYNTAX INTEGER
				{
				igmpAll(1),
				igmpVersion2(2),
				igmpVersion3(3)
				}
			MAX-ACCESS read-write
			STATUS current
			DESCRIPTION
				"Version of processed IGMP frames."
			DEFVAL { igmpAll }
			::= { msanIgmpSnoopingGlobal 8 }

		
		-- 1.3.6.1.4.1.1332.1.1.5.3.8.1.9
		msanIgmpClear OBJECT-TYPE
			SYNTAX INTEGER
				{
				enable(1),
				disable(2)
				}
			MAX-ACCESS read-write
			STATUS current
			DESCRIPTION
				"Clear all IGMP snooping entries."
			::= { msanIgmpSnoopingGlobal 9 }

		
		-- 1.3.6.1.4.1.1332.1.1.5.3.8.2
		msanIgmpSnoopingTable OBJECT-TYPE
			SYNTAX SEQUENCE OF MsanIgmpSnoopingEntry
			MAX-ACCESS not-accessible
			STATUS current
			DESCRIPTION
				"Description."
			::= { msanIgmpSnooping 2 }

		
		-- 1.3.6.1.4.1.1332.1.1.5.3.8.2.1
		msanIgmpSnoopingEntry OBJECT-TYPE
			SYNTAX MsanIgmpSnoopingEntry
			MAX-ACCESS not-accessible
			STATUS current
			DESCRIPTION
				"Description."
			INDEX { ifIndex }
			::= { msanIgmpSnoopingTable 1 }

		
		MsanIgmpSnoopingEntry ::=
			SEQUENCE { 
				msanIgmpSnoopingIntfStandaloneQuerier
					Integer32,
				msanIgmpSnoopingIntfFilter
					INTEGER,
				msanIgmpSnoopingGroupLimit
					INTEGER
			 }

		-- 1.3.6.1.4.1.1332.1.1.5.3.8.2.1.1
		msanIgmpSnoopingIntfStandaloneQuerier OBJECT-TYPE
			SYNTAX Integer32
			UNITS "seconds"
			MAX-ACCESS read-write
			STATUS current
			DESCRIPTION
				"Specify the period of time in seconds you want the IGMP Standalone Querier generate IGMP query packets. Value must be higher than 
				msanIgmpSnoopingMaxResponseTime and lower than msanIgmpSnoopingGroupMembershipInterval or 0. 
				The default is 0. A value of zero indicates that standalone querier is disabled.
				IGMP SA Querier can be activated only on one interface at the same time. "
			::= { msanIgmpSnoopingEntry 1 }

		
		-- 1.3.6.1.4.1.1332.1.1.5.3.8.2.1.2
		msanIgmpSnoopingIntfFilter OBJECT-TYPE
			SYNTAX INTEGER
				{
				allowAll(0),
				allowReports(1),
				allowQueries(2),
				dropAll(3)
				}
			MAX-ACCESS read-write
			STATUS current
			DESCRIPTION
				"Filtering of IGMP join/leave reports or queries frames. "
			::= { msanIgmpSnoopingEntry 2 }

		
		-- 1.3.6.1.4.1.1332.1.1.5.3.8.2.1.3
		msanIgmpSnoopingGroupLimit OBJECT-TYPE
			SYNTAX INTEGER (0..10)
			MAX-ACCESS read-write
			STATUS current
			DESCRIPTION
				"A maximum numbers of IGMP groups per interface.
				Value 0 means no limits."
			::= { msanIgmpSnoopingEntry 3 }

		
		-- 1.3.6.1.4.1.1332.1.1.5.3.8.3
		msanSwitchIGMPVlanCurrentMrouterTable OBJECT-TYPE
			SYNTAX SEQUENCE OF MsanSwitchIGMPVlanCurrentMrouterEntry
			MAX-ACCESS not-accessible
			STATUS current
			DESCRIPTION
				"Description."
			::= { msanIgmpSnooping 3 }

		
		-- 1.3.6.1.4.1.1332.1.1.5.3.8.3.1
		msanSwitchIGMPVlanCurrentMrouterEntry OBJECT-TYPE
			SYNTAX MsanSwitchIGMPVlanCurrentMrouterEntry
			MAX-ACCESS not-accessible
			STATUS current
			DESCRIPTION
				"Description."
			INDEX { ifIndex, dot1qVlanIndex }
			::= { msanSwitchIGMPVlanCurrentMrouterTable 1 }

		
		MsanSwitchIGMPVlanCurrentMrouterEntry ::=
			SEQUENCE { 
				msanSwitchIGMPVlanCurrentMrouterEnableState
					Integer32
			 }

		-- 1.3.6.1.4.1.1332.1.1.5.3.8.3.1.1
		msanSwitchIGMPVlanCurrentMrouterEnableState OBJECT-TYPE
			SYNTAX Integer32
			MAX-ACCESS read-only
			STATUS current
			DESCRIPTION
				"Returns per-interface per-vlan pairs where IGMP Mrouter is enabled. "
			::= { msanSwitchIGMPVlanCurrentMrouterEntry 1 }

		
		-- 1.3.6.1.4.1.1332.1.1.5.3.8.4
		msanSwitchIGMPSnoopingStaticIntfMulticastRouterTable OBJECT-TYPE
			SYNTAX SEQUENCE OF MsanSwitchIGMPSnoopingStaticIntfMulticastRouterEntry
			MAX-ACCESS not-accessible
			STATUS current
			DESCRIPTION
				"Description."
			REFERENCE
				"agentSwitchIGMPSnoopingIntfTable - 1.3.6.1.4.1.6132.1.1.1.2.8.7.1"
			::= { msanIgmpSnooping 4 }

		
		-- 1.3.6.1.4.1.1332.1.1.5.3.8.4.1
		msanSwitchIGMPSnoopingStaticIntfMulticastRouterEntry OBJECT-TYPE
			SYNTAX MsanSwitchIGMPSnoopingStaticIntfMulticastRouterEntry
			MAX-ACCESS not-accessible
			STATUS current
			DESCRIPTION
				"Description."
			INDEX { ifIndex }
			::= { msanSwitchIGMPSnoopingStaticIntfMulticastRouterTable 1 }

		
		MsanSwitchIGMPSnoopingStaticIntfMulticastRouterEntry ::=
			SEQUENCE { 
				msanSwitchIGMPSnoopingIntfIndex
					Unsigned32,
				msanSwitchIGMPSnoopingIntfAdminMode
					INTEGER,
				msanSwitchIGMPSnoopingIntfGroupMembershipInterval
					Integer32,
				msanSwitchIGMPSnoopingIntfMaxResponseTime
					Integer32,
				msanSwitchIGMPSnoopingIntfMRPExpirationTime
					Integer32,
				msanSwitchIGMPSnoopingIntfFastLeaveAdminMode
					INTEGER,
				msanSwitchIGMPSnoopingStaticIntfMulticastRouterMode
					INTEGER,
				msanSwitchIGMPSnoopingIntfVlanIDs
					VlanList
			 }

		-- 1.3.6.1.4.1.1332.1.1.5.3.8.4.1.1
		msanSwitchIGMPSnoopingIntfIndex OBJECT-TYPE
			SYNTAX Unsigned32 (1..65535)
			MAX-ACCESS read-only
			STATUS current
			DESCRIPTION
				"The port number to be selected. Each port maps to an interface."
			::= { msanSwitchIGMPSnoopingStaticIntfMulticastRouterEntry 1 }

		
		-- 1.3.6.1.4.1.1332.1.1.5.3.8.4.1.2
		msanSwitchIGMPSnoopingIntfAdminMode OBJECT-TYPE
			SYNTAX INTEGER
				{
				enable(1),
				disable(2)
				}
			MAX-ACCESS read-write
			STATUS deprecated
			DESCRIPTION
				"This enables or disables IGMP Snooping on a selected interface."
			DEFVAL { disable }
			::= { msanSwitchIGMPSnoopingStaticIntfMulticastRouterEntry 2 }

		
		-- 1.3.6.1.4.1.1332.1.1.5.3.8.4.1.3
		msanSwitchIGMPSnoopingIntfGroupMembershipInterval OBJECT-TYPE
			SYNTAX Integer32 (2..3600)
			MAX-ACCESS read-write
			STATUS deprecated
			DESCRIPTION
				"The amount of time in seconds that a switch will wait for a report
				from a particular group on the selected interface before deleting the
				interface from the entry. This value must be greater than
				agentSwitchIGMPSnoopingIntfMaxResponseTime."
			DEFVAL { 260 }
			::= { msanSwitchIGMPSnoopingStaticIntfMulticastRouterEntry 3 }

		
		-- 1.3.6.1.4.1.1332.1.1.5.3.8.4.1.4
		msanSwitchIGMPSnoopingIntfMaxResponseTime OBJECT-TYPE
			SYNTAX Integer32 (1..3599)
			MAX-ACCESS read-write
			STATUS deprecated
			DESCRIPTION
				"The amount of time in seconds a switch will wait after sending
				a query on the selected interface because it did not receive a report for
				a particular group in that interface.  This value must be less
				than agentSwitchIGMPSnoopingIntfGroupMembershipInterval."
			DEFVAL { 10 }
			::= { msanSwitchIGMPSnoopingStaticIntfMulticastRouterEntry 4 }

		
		-- 1.3.6.1.4.1.1332.1.1.5.3.8.4.1.5
		msanSwitchIGMPSnoopingIntfMRPExpirationTime OBJECT-TYPE
			SYNTAX Integer32 (0..3600)
			MAX-ACCESS read-write
			STATUS deprecated
			DESCRIPTION
				"The amount of time in seconds that a switch will wait for a query to be
				received on the selected interface before the interface is removed from
				the list of interfaces with multicast routers attached."
			DEFVAL { 0 }
			::= { msanSwitchIGMPSnoopingStaticIntfMulticastRouterEntry 5 }

		
		-- 1.3.6.1.4.1.1332.1.1.5.3.8.4.1.6
		msanSwitchIGMPSnoopingIntfFastLeaveAdminMode OBJECT-TYPE
			SYNTAX INTEGER
				{
				enable(1),
				disable(2)
				}
			MAX-ACCESS read-write
			STATUS deprecated
			DESCRIPTION
				"This enables or disables IGMP Snooping Fast-Leave on specified interface."
			DEFVAL { disable }
			::= { msanSwitchIGMPSnoopingStaticIntfMulticastRouterEntry 6 }

		
		-- 1.3.6.1.4.1.1332.1.1.5.3.8.4.1.7
		msanSwitchIGMPSnoopingStaticIntfMulticastRouterMode OBJECT-TYPE
			SYNTAX INTEGER
				{
				enable(1),
				disable(2)
				}
			MAX-ACCESS read-write
			STATUS current
			DESCRIPTION
				"Mode of static IGMP Mrouter on selected interface."
			::= { msanSwitchIGMPSnoopingStaticIntfMulticastRouterEntry 7 }

		
		-- 1.3.6.1.4.1.1332.1.1.5.3.8.4.1.8
		msanSwitchIGMPSnoopingIntfVlanIDs OBJECT-TYPE
			SYNTAX VlanList
			MAX-ACCESS read-only
			STATUS deprecated
			DESCRIPTION
				"This field lists all the VlanIDs which include the selected interface."
			::= { msanSwitchIGMPSnoopingStaticIntfMulticastRouterEntry 8 }

		
		-- 1.3.6.1.4.1.1332.1.1.5.3.8.5
		msanSwitchIGMPVlanStaticMrouterTable OBJECT-TYPE
			SYNTAX SEQUENCE OF MsanSwitchIGMPVlanStaticMrouterEntry
			MAX-ACCESS not-accessible
			STATUS deprecated
			DESCRIPTION
				"Description."
			::= { msanIgmpSnooping 5 }

		
		-- 1.3.6.1.4.1.1332.1.1.5.3.8.5.1
		msanSwitchIGMPVlanStaticMrouterEntry OBJECT-TYPE
			SYNTAX MsanSwitchIGMPVlanStaticMrouterEntry
			MAX-ACCESS not-accessible
			STATUS deprecated
			DESCRIPTION
				"Description."
			INDEX { ifIndex, dot1qVlanIndex }
			::= { msanSwitchIGMPVlanStaticMrouterTable 1 }

		
		MsanSwitchIGMPVlanStaticMrouterEntry ::=
			SEQUENCE { 
				msanSwitchIGMPVlanStaticMrouterEnableState
					RowStatus
			 }

		-- 1.3.6.1.4.1.1332.1.1.5.3.8.5.1.1
		msanSwitchIGMPVlanStaticMrouterEnableState OBJECT-TYPE
			SYNTAX RowStatus
			MAX-ACCESS read-create
			STATUS deprecated
			DESCRIPTION
				"Object used to create a new row or modify or destroy an existing row in manner described in the definition of the RowStatus textual. 
				Supported states are Active(1), CreateAndGo(4) and Destroy(6).
				
				Row is created with CreateAndGo(4). This enables IGMP Mrouter on a per-interface per-vlan basis and 
				the row goes to Active(1). The row is removed with Destroy(6) and IGMP Mrouter on this interface/VLAN pair is disabled. 
				
				Values NotInService(2), NotReady(3) and CreateAndWait(5) are not supported."
			::= { msanSwitchIGMPVlanStaticMrouterEntry 1 }

		
		-- 1.3.6.1.4.1.1332.1.1.5.3.8.6
		msanSwitchIGMPSnoopingVlanTable OBJECT-TYPE
			SYNTAX SEQUENCE OF MsanSwitchIGMPSnoopingVlanEntry
			MAX-ACCESS not-accessible
			STATUS current
			DESCRIPTION
				"A table of the IGMP Snooping Vlan configuration entries."
			REFERENCE
				"agentSwitchIGMPSnoopingVlanTable - 1.3.6.1.4.1.6132.1.1.1.2.8.8.1"
			::= { msanIgmpSnooping 6 }

		
		-- 1.3.6.1.4.1.1332.1.1.5.3.8.6.1
		msanSwitchIGMPSnoopingVlanEntry OBJECT-TYPE
			SYNTAX MsanSwitchIGMPSnoopingVlanEntry
			MAX-ACCESS not-accessible
			STATUS current
			DESCRIPTION
				"Represents entry for a IGMP Snooping Vlan."
			INDEX { dot1qVlanIndex }
			::= { msanSwitchIGMPSnoopingVlanTable 1 }

		
		MsanSwitchIGMPSnoopingVlanEntry ::=
			SEQUENCE { 
				msanSwitchIGMPSnoopingVlanAdminMode
					INTEGER,
				msanSwitchIGMPSnoopingVlanGroupMembershipInterval
					Integer32,
				msanSwitchIGMPSnoopingVlanMaxResponseTime
					Integer32,
				msanSwitchIGMPSnoopingVlanFastLeaveAdminMode
					INTEGER,
				msanSwitchIGMPSnoopingVlanMRPExpirationTime
					Integer32,
				msanSwitchIGMPSnoopingVlanAdminState
					INTEGER
			 }

		-- 1.3.6.1.4.1.1332.1.1.5.3.8.6.1.1
		msanSwitchIGMPSnoopingVlanAdminMode OBJECT-TYPE
			SYNTAX INTEGER
				{
				disable(0),
				enable(1)
				}
			MAX-ACCESS read-write
			STATUS deprecated
			DESCRIPTION
				"This enables or disables IGMP Snooping on a selected Vlan interface."
			DEFVAL { disable }
			::= { msanSwitchIGMPSnoopingVlanEntry 1 }

		
		-- 1.3.6.1.4.1.1332.1.1.5.3.8.6.1.2
		msanSwitchIGMPSnoopingVlanGroupMembershipInterval OBJECT-TYPE
			SYNTAX Integer32 (2..3600)
			MAX-ACCESS read-write
			STATUS deprecated
			DESCRIPTION
				"The amount of time in seconds that a switch will wait for a report
				from a particular group on the selected vlan before deleting the
				interface participating in the vlan from the entry. This value must
				be greater than agentSwitchIGMPSnoopingIntfMaxResponseTime."
			DEFVAL { 260 }
			::= { msanSwitchIGMPSnoopingVlanEntry 2 }

		
		-- 1.3.6.1.4.1.1332.1.1.5.3.8.6.1.3
		msanSwitchIGMPSnoopingVlanMaxResponseTime OBJECT-TYPE
			SYNTAX Integer32 (1..3599)
			MAX-ACCESS read-write
			STATUS deprecated
			DESCRIPTION
				"The amount of time in seconds a switch will wait after sending
				a query on the selected vlan because it did not receive a report for
				a particular group in the interface participating in the vlan.
				This value must be less than
				agentSwitchIGMPSnoopingIntfGroupMembershipInterval."
			DEFVAL { 10 }
			::= { msanSwitchIGMPSnoopingVlanEntry 3 }

		
		-- 1.3.6.1.4.1.1332.1.1.5.3.8.6.1.4
		msanSwitchIGMPSnoopingVlanFastLeaveAdminMode OBJECT-TYPE
			SYNTAX INTEGER
				{
				disable(0),
				enable(1)
				}
			MAX-ACCESS read-write
			STATUS deprecated
			DESCRIPTION
				"This enables or disables IGMP Snooping on the selected vlan."
			DEFVAL { disable }
			::= { msanSwitchIGMPSnoopingVlanEntry 4 }

		
		-- 1.3.6.1.4.1.1332.1.1.5.3.8.6.1.5
		msanSwitchIGMPSnoopingVlanMRPExpirationTime OBJECT-TYPE
			SYNTAX Integer32 (0..3600)
			MAX-ACCESS read-write
			STATUS deprecated
			DESCRIPTION
				"The amount of time in seconds that a switch will wait for a query to be
				received on the selected interface participating in the vlan before the
				interface is removed from the list of interfaces with multicast routers
				attached. This parameter is configurable only for exisiting Vlans."
			DEFVAL { 0 }
			::= { msanSwitchIGMPSnoopingVlanEntry 5 }

		
		-- 1.3.6.1.4.1.1332.1.1.5.3.8.6.1.6
		msanSwitchIGMPSnoopingVlanAdminState OBJECT-TYPE
			SYNTAX INTEGER
				{
				disableAndDiscard(0),
				disableAndBroadcast(1),
				enable(2),
				enableAndUnknownGroupFlood(3)
				}
			MAX-ACCESS read-write
			STATUS current
			DESCRIPTION
				"IGMP Snooping state on a selected Vlan interface.
				
				This parameter is ignored if global msanIgmpSnoopingAdminState value
				is disableAndDiscard(0) or disableAndBroadcast(1)."
			DEFVAL { disableAndDiscard }
			::= { msanSwitchIGMPSnoopingVlanEntry 6 }

		
		-- 1.3.6.1.4.1.1332.1.1.5.3.8.7
		msanSwitchIGMPProxyVlanTable OBJECT-TYPE
			SYNTAX SEQUENCE OF MsanSwitchIGMPProxyVlanEntry
			MAX-ACCESS not-accessible
			STATUS current
			DESCRIPTION
				"A table of the IGMP Proxy Vlan configuration entries."
			::= { msanIgmpSnooping 7 }

		
		-- 1.3.6.1.4.1.1332.1.1.5.3.8.7.1
		msanSwitchIGMPProxyVlanEntry OBJECT-TYPE
			SYNTAX MsanSwitchIGMPProxyVlanEntry
			MAX-ACCESS not-accessible
			STATUS current
			DESCRIPTION
				" "
			INDEX { dot1qVlanIndex, msanSwitchIGMPProxyVlanIpAddr }
			::= { msanSwitchIGMPProxyVlanTable 1 }

		
		MsanSwitchIGMPProxyVlanEntry ::=
			SEQUENCE { 
				msanSwitchIGMPProxyVlanIpAddr
					IpAddress,
				msanSwitchIGMPProxyVlanRowStatus
					RowStatus
			 }

		-- 1.3.6.1.4.1.1332.1.1.5.3.8.7.1.1
		msanSwitchIGMPProxyVlanIpAddr OBJECT-TYPE
			SYNTAX IpAddress
			MAX-ACCESS not-accessible
			STATUS current
			DESCRIPTION
				"IGMP Proxy IP address. If set to 0.0.0.0, default IP address is 
				used (IP address of MN interface -> msanNetworkIPAddress)."
			::= { msanSwitchIGMPProxyVlanEntry 1 }

		
		-- 1.3.6.1.4.1.1332.1.1.5.3.8.7.1.2
		msanSwitchIGMPProxyVlanRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanSwitchIGMPProxyVlanEntry 2 }

		
		-- 1.3.6.1.4.1.1332.1.1.5.3.8.8
		msanIgmpStatistics OBJECT IDENTIFIER ::= { msanIgmpSnooping 8 }

		
		-- 1.3.6.1.4.1.1332.1.1.5.3.8.8.1
		msanIgmpStatGlobal OBJECT IDENTIFIER ::= { msanIgmpStatistics 1 }

		
		-- 1.3.6.1.4.1.1332.1.1.5.3.8.8.1.1
		msanIgmpStatRxV1 OBJECT-TYPE
			SYNTAX Counter32
			MAX-ACCESS read-only
			STATUS current
			DESCRIPTION
				"Number of received IGMP v1 packets."
			::= { msanIgmpStatGlobal 1 }

		
		-- 1.3.6.1.4.1.1332.1.1.5.3.8.8.1.2
		msanIgmpStatRxV2Join OBJECT-TYPE
			SYNTAX Counter32
			MAX-ACCESS read-only
			STATUS current
			DESCRIPTION
				"Number of received IGMP v2 join packets."
			::= { msanIgmpStatGlobal 2 }

		
		-- 1.3.6.1.4.1.1332.1.1.5.3.8.8.1.3
		msanIgmpStatRxV2Leave OBJECT-TYPE
			SYNTAX Counter32
			MAX-ACCESS read-only
			STATUS current
			DESCRIPTION
				"Number of received IGMP v2 leave packets."
			::= { msanIgmpStatGlobal 3 }

		
		-- 1.3.6.1.4.1.1332.1.1.5.3.8.8.1.4
		msanIgmpStatRxV3Report OBJECT-TYPE
			SYNTAX Counter32
			MAX-ACCESS read-only
			STATUS current
			DESCRIPTION
				"Number of received IGMP v3 report packets."
			::= { msanIgmpStatGlobal 4 }

		
		-- 1.3.6.1.4.1.1332.1.1.5.3.8.8.1.5
		msanIgmpStatRxQuery OBJECT-TYPE
			SYNTAX Counter32
			MAX-ACCESS read-only
			STATUS current
			DESCRIPTION
				"Number of received IGMP query  packets."
			::= { msanIgmpStatGlobal 5 }

		
		-- 1.3.6.1.4.1.1332.1.1.5.3.8.8.1.6
		msanIgmpStatRxError OBJECT-TYPE
			SYNTAX Counter32
			MAX-ACCESS read-only
			STATUS current
			DESCRIPTION
				"Number of received corrupted or unknown IGMP packets."
			::= { msanIgmpStatGlobal 6 }

		
		-- 1.3.6.1.4.1.1332.1.1.5.3.8.8.1.7
		msanIgmpStatRxBlockByIgmpFilter OBJECT-TYPE
			SYNTAX Counter32
			MAX-ACCESS read-only
			STATUS current
			DESCRIPTION
				"Number of received  IGMP packets blocked by IGMP filter."
			::= { msanIgmpStatGlobal 7 }

		
		-- 1.3.6.1.4.1.1332.1.1.5.3.8.8.1.8
		msanIgmpStatRxBlockByMcastAcl OBJECT-TYPE
			SYNTAX Counter32
			MAX-ACCESS read-only
			STATUS current
			DESCRIPTION
				"Number of received  IGMP packets blocked by Multicast ACL."
			::= { msanIgmpStatGlobal 8 }

		
		-- 1.3.6.1.4.1.1332.1.1.5.3.8.8.1.9
		msanIgmpStatRxBlockByMcastCac OBJECT-TYPE
			SYNTAX Counter32
			MAX-ACCESS read-only
			STATUS current
			DESCRIPTION
				"Number of received  IGMP packets blocked by Multicast CAC."
			::= { msanIgmpStatGlobal 9 }

		
		-- 1.3.6.1.4.1.1332.1.1.5.3.8.8.1.10
		msanIgmpStatRxBlockByIgmpVersion OBJECT-TYPE
			SYNTAX Counter32
			MAX-ACCESS read-only
			STATUS current
			DESCRIPTION
				"Number of received  IGMP packets blocked by IGMP Version Control."
			::= { msanIgmpStatGlobal 10 }

		
		-- 1.3.6.1.4.1.1332.1.1.5.3.8.8.2
		msanIgmpPortStatTable OBJECT-TYPE
			SYNTAX SEQUENCE OF MsanIgmpPortStatEntry
			MAX-ACCESS not-accessible
			STATUS current
			DESCRIPTION
				"Description."
			::= { msanIgmpStatistics 2 }

		
		-- 1.3.6.1.4.1.1332.1.1.5.3.8.8.2.1
		msanIgmpPortStatEntry OBJECT-TYPE
			SYNTAX MsanIgmpPortStatEntry
			MAX-ACCESS not-accessible
			STATUS current
			DESCRIPTION
				"Description."
			INDEX { ifIndex }
			::= { msanIgmpPortStatTable 1 }

		
		MsanIgmpPortStatEntry ::=
			SEQUENCE { 
				msanIgmpPortStatRxV1
					Counter32,
				msanIgmpPortStatTxV1
					Counter32,
				msanIgmpPortStatRxV2Join
					Counter32,
				msanIgmpPortStatTxV2Join
					Counter32,
				msanIgmpPortStatRxV2Leave
					Counter32,
				msanIgmpPortStatTxV2Leave
					Counter32,
				msanIgmpPortStatRxV3Report
					Counter32,
				msanIgmpPortStatTxV3Report
					Counter32,
				msanIgmpPortStatRxQuery
					Counter32,
				msanIgmpPortStatRxError
					Counter32,
				msanIgmpPortStatRxBlockByIgmpFilter
					Counter32,
				msanIgmpPortStatRxBlockByMcastAcl
					Counter32,
				msanIgmpPortStatRxBlockByMcastCac
					Counter32,
				msanIgmpPortStatTxQuery
					Counter32,
				msanIgmpPortStatRxBlockByIgmpVersion
					Counter32
			 }

		-- 1.3.6.1.4.1.1332.1.1.5.3.8.8.2.1.1
		msanIgmpPortStatRxV1 OBJECT-TYPE
			SYNTAX Counter32
			MAX-ACCESS read-only
			STATUS current
			DESCRIPTION
				"Number of received IGMP v1 packets."
			::= { msanIgmpPortStatEntry 1 }

		
		-- 1.3.6.1.4.1.1332.1.1.5.3.8.8.2.1.2
		msanIgmpPortStatTxV1 OBJECT-TYPE
			SYNTAX Counter32
			MAX-ACCESS read-only
			STATUS current
			DESCRIPTION
				"Number of transmitted IGMP v1 packets."
			::= { msanIgmpPortStatEntry 2 }

		
		-- 1.3.6.1.4.1.1332.1.1.5.3.8.8.2.1.3
		msanIgmpPortStatRxV2Join OBJECT-TYPE
			SYNTAX Counter32
			MAX-ACCESS read-only
			STATUS current
			DESCRIPTION
				"Number of received IGMP v2 join packets."
			::= { msanIgmpPortStatEntry 3 }

		
		-- 1.3.6.1.4.1.1332.1.1.5.3.8.8.2.1.4
		msanIgmpPortStatTxV2Join OBJECT-TYPE
			SYNTAX Counter32
			MAX-ACCESS read-only
			STATUS current
			DESCRIPTION
				"Number of transmitted IGMP v2 join packets."
			::= { msanIgmpPortStatEntry 4 }

		
		-- 1.3.6.1.4.1.1332.1.1.5.3.8.8.2.1.5
		msanIgmpPortStatRxV2Leave OBJECT-TYPE
			SYNTAX Counter32
			MAX-ACCESS read-only
			STATUS current
			DESCRIPTION
				"Number of received IGMP v2 leave packets."
			::= { msanIgmpPortStatEntry 5 }

		
		-- 1.3.6.1.4.1.1332.1.1.5.3.8.8.2.1.6
		msanIgmpPortStatTxV2Leave OBJECT-TYPE
			SYNTAX Counter32
			MAX-ACCESS read-only
			STATUS current
			DESCRIPTION
				"Number of transmitted IGMP v2 leave packets."
			::= { msanIgmpPortStatEntry 6 }

		
		-- 1.3.6.1.4.1.1332.1.1.5.3.8.8.2.1.7
		msanIgmpPortStatRxV3Report OBJECT-TYPE
			SYNTAX Counter32
			MAX-ACCESS read-only
			STATUS current
			DESCRIPTION
				"Number of received IGMP v3 report packets."
			::= { msanIgmpPortStatEntry 7 }

		
		-- 1.3.6.1.4.1.1332.1.1.5.3.8.8.2.1.8
		msanIgmpPortStatTxV3Report OBJECT-TYPE
			SYNTAX Counter32
			MAX-ACCESS read-only
			STATUS current
			DESCRIPTION
				"Number of transmitted IGMP v3 report packets."
			::= { msanIgmpPortStatEntry 8 }

		
		-- 1.3.6.1.4.1.1332.1.1.5.3.8.8.2.1.9
		msanIgmpPortStatRxQuery OBJECT-TYPE
			SYNTAX Counter32
			MAX-ACCESS read-only
			STATUS current
			DESCRIPTION
				"Number of received IGMP query  packets."
			::= { msanIgmpPortStatEntry 9 }

		
		-- 1.3.6.1.4.1.1332.1.1.5.3.8.8.2.1.10
		msanIgmpPortStatRxError OBJECT-TYPE
			SYNTAX Counter32
			MAX-ACCESS read-only
			STATUS current
			DESCRIPTION
				"Number of received corrupted or unknown IGMP packets."
			::= { msanIgmpPortStatEntry 10 }

		
		-- 1.3.6.1.4.1.1332.1.1.5.3.8.8.2.1.11
		msanIgmpPortStatRxBlockByIgmpFilter OBJECT-TYPE
			SYNTAX Counter32
			MAX-ACCESS read-only
			STATUS current
			DESCRIPTION
				"Number of received  IGMP packets blocked by IGMP filter."
			::= { msanIgmpPortStatEntry 11 }

		
		-- 1.3.6.1.4.1.1332.1.1.5.3.8.8.2.1.12
		msanIgmpPortStatRxBlockByMcastAcl OBJECT-TYPE
			SYNTAX Counter32
			MAX-ACCESS read-only
			STATUS current
			DESCRIPTION
				"Number of received  IGMP packets blocked by Multicast ACL."
			::= { msanIgmpPortStatEntry 12 }

		
		-- 1.3.6.1.4.1.1332.1.1.5.3.8.8.2.1.13
		msanIgmpPortStatRxBlockByMcastCac OBJECT-TYPE
			SYNTAX Counter32
			MAX-ACCESS read-only
			STATUS current
			DESCRIPTION
				"Number of received  IGMP packets blocked by Multicast CAC."
			::= { msanIgmpPortStatEntry 13 }

		
		-- 1.3.6.1.4.1.1332.1.1.5.3.8.8.2.1.14
		msanIgmpPortStatTxQuery OBJECT-TYPE
			SYNTAX Counter32
			MAX-ACCESS read-only
			STATUS current
			DESCRIPTION
				"Number of transmitted IGMP query  packets."
			::= { msanIgmpPortStatEntry 14 }

		
		-- 1.3.6.1.4.1.1332.1.1.5.3.8.8.2.1.15
		msanIgmpPortStatRxBlockByIgmpVersion OBJECT-TYPE
			SYNTAX Counter32
			MAX-ACCESS read-only
			STATUS current
			DESCRIPTION
				"Number of received  IGMP packets blocked by IGMP Version."
			::= { msanIgmpPortStatEntry 15 }

		
		-- 1.3.6.1.4.1.1332.1.1.5.3.10
		msanPort OBJECT IDENTIFIER ::= { msanAdditionalConf 10 }

		
		-- 1.3.6.1.4.1.1332.1.1.5.3.10.1
		msanPortGlobal OBJECT IDENTIFIER ::= { msanPort 1 }

		
		-- 1.3.6.1.4.1.1332.1.1.5.3.10.2
		msanPortTable OBJECT-TYPE
			SYNTAX SEQUENCE OF MsanPortEntry
			MAX-ACCESS not-accessible
			STATUS current
			DESCRIPTION
				"Description."
			::= { msanPort 2 }

		
		-- 1.3.6.1.4.1.1332.1.1.5.3.10.2.1
		msanPortEntry OBJECT-TYPE
			SYNTAX MsanPortEntry
			MAX-ACCESS not-accessible
			STATUS current
			DESCRIPTION
				"Description."
			INDEX { ifIndex }
			::= { msanPortTable 1 }

		
		MsanPortEntry ::=
			SEQUENCE { 
				msanPortMNFlag
					INTEGER,
				msanPortMasterSlave
					INTEGER,
				msanPortNegCapAdvertisedBits
					BITS,
				msanPortSpeedDuplex
					INTEGER,
				msanPortStpP2PAutoState
					INTEGER,
				msanPortUsageType
					INTEGER
			 }

		-- 1.3.6.1.4.1.1332.1.1.5.3.10.2.1.1
		msanPortMNFlag OBJECT-TYPE
			SYNTAX INTEGER
				{
				enable(1),
				disable(2)
				}
			MAX-ACCESS read-write
			STATUS current
			DESCRIPTION
				"This object determines whether to allow or not allow management access to a specific link. The factory default is enabled. "
			DEFVAL { enable }
			::= { msanPortEntry 1 }

		
		-- 1.3.6.1.4.1.1332.1.1.5.3.10.2.1.6
		msanPortMasterSlave OBJECT-TYPE
			SYNTAX INTEGER
				{
				none(1),
				master(2),
				slave(3)
				}
			MAX-ACCESS read-write
			STATUS current
			DESCRIPTION
				"This object determines whether Gb port should be master or slave. Set to none when 
				auto-negotiation and for non-Gb ports."
			DEFVAL { none }
			::= { msanPortEntry 6 }

		
		-- 1.3.6.1.4.1.1332.1.1.5.3.10.2.1.7
		msanPortNegCapAdvertisedBits OBJECT-TYPE
			SYNTAX BITS
				{
				bOther(0),
				b10baseT(1),
				b10baseTFD(2),
				b100baseT4(3),
				b100baseTX(4),
				b100baseTXFD(5),
				b100baseT2(6),
				b100baseT2FD(7),
				bFdxPause(8),
				bFdxAPause(9),
				bFdxSPause(10),
				bFdxBPause(11),
				b1000baseX(12),
				b1000baseXFD(13),
				b1000baseT(14),
				b1000baseTFD(15)
				}
			MAX-ACCESS read-write
			STATUS current
			DESCRIPTION
				"A value that uniquely identifies the set of capabilities advertised by 
				the local auto-negotiation entity.
				
				Note that the local auto-negotiation entity may advertise some capabilities 
				beyond the scope of this MIB. This is indicated by returning the bit value 
				bOther in addition to any bit values for capabilities that are listed above.
				
				Only b1000baseXFD(13) and b1000baseTFD(15) are currently supported."
			REFERENCE
				"[IEEE 802.3 Std], 30.6.1.1.6, aAutoNegAdvertisedTechnologyAbility; 
				ifMauAutoNegCapAdvertisedBits (OID 1.3.6.1.2.1.26.5.1.1.11)"
			::= { msanPortEntry 7 }

		
		-- 1.3.6.1.4.1.1332.1.1.5.3.10.2.1.8
		msanPortSpeedDuplex OBJECT-TYPE
			SYNTAX INTEGER
				{
				speed10MbpsHD(10),
				speed10MbpsFD(11),
				speed100MbpsHD(15),
				speed100MbpsFD(16),
				speed100MbpsFDFiber(18),
				speed1000MbpsFDFiber(26),
				speed1000MbpsFD(30),
				speed10GbpsFDFiber(31)
				}
			MAX-ACCESS read-write
			STATUS current
			DESCRIPTION
				"Speed and duplex mode of the interface."
			::= { msanPortEntry 8 }

		
		-- 1.3.6.1.4.1.1332.1.1.5.3.10.2.1.20
		msanPortStpP2PAutoState OBJECT-TYPE
			SYNTAX INTEGER
				{
				enable(1),
				disable(2)
				}
			MAX-ACCESS read-write
			STATUS current
			DESCRIPTION
				"The field extends ISKRATEL-MSAN-BASICCONF-MIB.agentStpCstPortOperPointToPoint by the <auto> value."
			DEFVAL { enable }
			::= { msanPortEntry 20 }

		
		-- 1.3.6.1.4.1.1332.1.1.5.3.10.2.1.21
		msanPortUsageType OBJECT-TYPE
			SYNTAX INTEGER
				{
				uplink(1),
				access(2)
				}
			MAX-ACCESS read-write
			STATUS current
			DESCRIPTION
				"This object specifies the type of an interface whether it is an uplink or access port.
				If you change this value you must save configuration and restart network element.
				"
			::= { msanPortEntry 21 }

		
		-- 1.3.6.1.4.1.1332.1.1.5.3.11
		msanPppoeIA OBJECT IDENTIFIER ::= { msanAdditionalConf 11 }

		
		-- 1.3.6.1.4.1.1332.1.1.5.3.11.1
		msanPppoeIAGlobal OBJECT IDENTIFIER ::= { msanPppoeIA 1 }

		
		-- 1.3.6.1.4.1.1332.1.1.5.3.11.1.1
		msanPppoeIAStatus OBJECT-TYPE
			SYNTAX INTEGER
				{
				enable(1),
				disable(2)
				}
			MAX-ACCESS read-write
			STATUS current
			DESCRIPTION
				"Specifies if the PPPOE Intermadiate Agent Service is to be Enabled or Disabled."
			::= { msanPppoeIAGlobal 1 }

		
		-- 1.3.6.1.4.1.1332.1.1.5.3.11.1.2
		msanPppoeIAVsaReplyMode OBJECT-TYPE
			SYNTAX INTEGER
				{
				keep(1),
				remove(2)
				}
			MAX-ACCESS read-write
			STATUS current
			DESCRIPTION
				"Specifies PPPOE Intermadiate Agent keep/remove option 82 in replies."
			::= { msanPppoeIAGlobal 2 }

		
		-- 1.3.6.1.4.1.1332.1.1.5.3.11.1.3
		msanPppoeIACircuitIdStatus OBJECT-TYPE
			SYNTAX INTEGER
				{
				enable(1),
				disable(2)
				}
			MAX-ACCESS read-write
			STATUS current
			DESCRIPTION
				"Specifies the disable/enable inserting Circuit ID suboption."
			::= { msanPppoeIAGlobal 3 }

		
		-- 1.3.6.1.4.1.1332.1.1.5.3.11.1.4
		msanPppoeIARemoteIdStatus OBJECT-TYPE
			SYNTAX INTEGER
				{
				enable(1),
				disable(2)
				}
			MAX-ACCESS read-write
			STATUS current
			DESCRIPTION
				"Specifies the disable/enable inserting Remote ID suboption."
			::= { msanPppoeIAGlobal 4 }

		
		-- 1.3.6.1.4.1.1332.1.1.5.3.11.1.5
		msanPppoeIACircuitIdInnerVlan OBJECT-TYPE
			SYNTAX INTEGER
				{
				enable(1),
				disable(2)
				}
			MAX-ACCESS read-write
			STATUS current
			DESCRIPTION
				"Include Inner VLAN (C-VLAN) in Circuit Id when port is in DVLAN Tunneling mode (msanPortDVlanTagMode = enable)."
			DEFVAL { disable }
			::= { msanPppoeIAGlobal 5 }

		
		-- 1.3.6.1.4.1.1332.1.1.5.3.11.1.6
		msanPppoeIACircuitIdCustomFormat OBJECT-TYPE
			SYNTAX DisplayString
			MAX-ACCESS read-write
			STATUS current
			DESCRIPTION
				"PPPoE Circuit Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "" }
			::= { msanPppoeIAGlobal 6 }

		
		-- 1.3.6.1.4.1.1332.1.1.5.3.11.1.7
		msanPppoeIARemoteIdCustomFormat OBJECT-TYPE
			SYNTAX DisplayString
			MAX-ACCESS read-write
			STATUS current
			DESCRIPTION
				"PPPoE Remote Id Custom format definition composed of arbitrary characters and variable macros.
				
				Use '$[h][[0|s]<len>][d[<delim>]]<macro>' format to specify:
				    h  HEX variable format
				    0|s  left padding with zeroes or spaces
				    <len> - maximum variable length
				    d  use custom delimiter for MAC/IP
				    <delim> - delimiting character
				    <macro>  variable macro
				
				Supported macros:
				$SHELF              - A string variable representing the shelf name as configured
				                             or acquired by this device.
				$CHASSIS           - A numeric variable ranging [0..99] and representing numerical
				                              identification of shelf.
				$PANEL               - Panel indicator: 0  front panel, 1  back panel.
				$INTF_TYPE        - Interface type: eth, dsl, gpon, mng, lag, atm, etc.
				$AGENT_BOARD - Local board position (slot number) of DHCP Relay Agent.
				$PORT                 - ID of local port the DHCP packet is received on.
				$PORT_REM_ID  - Complete remoteID string is inserted, as configured per
				                              pertaining interface.
				$INTF                   - ID of local interface the DHCP packet is received on in form
				                              as used in interface configuration (e.g.: 1/2/1).
				$INTF_DSCR       - Interface description string taken exactly as configured
				                              using 'description' command.
				$PVC_INTF          - ID of PVC interface the DHCP packet is received from (ADSL only).
				$VPI                     - ID of ATM VPI the DHCP packet is received in (ADSL only).
				$VCI                     - ID of ATM VCI the DHCP packet is received in (ADSL only).
				$CLNT_MAC        - MAC address of DHCP client sending the packet.
				$AGENT_MAC      - Local DHCP Relay Agent MAC address. If this is a switching device
				                              MNG address is used. If this is a routing device MAC address
				                              of the receiving interface is used.
				$AGENT_IPV4      - Local DHCP Relay Agent IP address. Management IPv4 address
				                               is used if this is a switching device, or IPv4 address of
				                               receiving interface is used if this is a routing device.
				$VLAN                  - Outermost VLAN ID in which the DHCP packet has been received.
				                               In case of single tagged frame this is VLAN ID of the frame.
				                               In case of double (QinQ) tagged frame, this is service
				                               provider VLAN ID.
				$VLAN_NAME      - The VLAN name, as it has been configured by user,
				                               of outermost VLAN in which the DHCP packet is received.
				$CVID                   - Valid only for double (QinQ) tagged frames. Customer (inner)
				                               VLAN ID in which the DHCP packet has been received.
				$SYSNAME          - System name as configured in SNMP agent on this device.
				$LOCATION          - Location as configured in SNMP agent on this device.
				$CONTACT           - Contact as configured in SNMP agent on this device.
				$HEX                    - Arbitrary array of hexadecimal values.
				                               Format: $<arbitrary hex values>HEX
				"
			DEFVAL { "$PORT_REM_ID" }
			::= { msanPppoeIAGlobal 7 }

		
		-- 1.3.6.1.4.1.1332.1.1.5.3.11.2
		msanPppoeIAPortTable OBJECT-TYPE
			SYNTAX SEQUENCE OF MsanPppoeIAPortEntry
			MAX-ACCESS not-accessible
			STATUS current
			DESCRIPTION
				"Description."
			::= { msanPppoeIA 2 }

		
		-- 1.3.6.1.4.1.1332.1.1.5.3.11.2.1
		msanPppoeIAPortEntry OBJECT-TYPE
			SYNTAX MsanPppoeIAPortEntry
			MAX-ACCESS not-accessible
			STATUS current
			DESCRIPTION
				"Description."
			INDEX { ifIndex }
			::= { msanPppoeIAPortTable 1 }

		
		MsanPppoeIAPortEntry ::=
			SEQUENCE { 
				msanPppoeIAPortStatus
					INTEGER,
				msanPppoeIAPortRemoteId
					OCTET STRING,
				msanPppoeIAPortCircuitType
					INTEGER,
				msanPppoeIAPortCircuitIdType
					INTEGER
			 }

		-- 1.3.6.1.4.1.1332.1.1.5.3.11.2.1.1
		msanPppoeIAPortStatus OBJECT-TYPE
			SYNTAX INTEGER
				{
				enable(1),
				disable(2),
				enableClient(3),
				enableServer(4)
				}
			MAX-ACCESS read-write
			STATUS current
			DESCRIPTION
				"State of PPPoE Intermadiate Agent on the port"
			::= { msanPppoeIAPortEntry 1 }

		
		-- 1.3.6.1.4.1.1332.1.1.5.3.11.2.1.2
		msanPppoeIAPortRemoteId OBJECT-TYPE
			SYNTAX OCTET STRING
			MAX-ACCESS read-write
			STATUS current
			DESCRIPTION
				"Remote Id for the port."
			::= { msanPppoeIAPortEntry 2 }

		
		-- 1.3.6.1.4.1.1332.1.1.5.3.11.2.1.3
		msanPppoeIAPortCircuitType OBJECT-TYPE
			SYNTAX INTEGER
				{
				trusted(1),
				untrusted(2)
				}
			MAX-ACCESS read-write
			STATUS current
			DESCRIPTION
				"PPPoE IA Circuit type per port."
			DEFVAL { untrusted }
			::= { msanPppoeIAPortEntry 3 }

		
		-- 1.3.6.1.4.1.1332.1.1.5.3.11.2.1.4
		msanPppoeIAPortCircuitIdType OBJECT-TYPE
			SYNTAX INTEGER
				{
				iskratel(1),
				atm(3)
				}
			MAX-ACCESS read-write
			STATUS current
			DESCRIPTION
				"Circuit Id syntax mode per port."
			::= { msanPppoeIAPortEntry 4 }

		
		-- 1.3.6.1.4.1.1332.1.1.5.3.11.3
		msanPppoeIaStatistics OBJECT IDENTIFIER ::= { msanPppoeIA 3 }

		
		-- 1.3.6.1.4.1.1332.1.1.5.3.11.3.1
		msanPppoeIaStatPADI OBJECT-TYPE
			SYNTAX Counter32
			MAX-ACCESS read-only
			STATUS current
			DESCRIPTION
				"Number of PADI packets."
			::= { msanPppoeIaStatistics 1 }

		
		-- 1.3.6.1.4.1.1332.1.1.5.3.11.3.2
		msanPppoeIaStatPADR OBJECT-TYPE
			SYNTAX Counter32
			MAX-ACCESS read-only
			STATUS current
			DESCRIPTION
				"Number of PADR packets."
			::= { msanPppoeIaStatistics 2 }

		
		-- 1.3.6.1.4.1.1332.1.1.5.3.11.3.3
		msanPppoeIaStatPADO OBJECT-TYPE
			SYNTAX Counter32
			MAX-ACCESS read-only
			STATUS current
			DESCRIPTION
				"Number of PADO packets."
			::= { msanPppoeIaStatistics 3 }

		
		-- 1.3.6.1.4.1.1332.1.1.5.3.11.3.4
		msanPppoeIaStatPADS OBJECT-TYPE
			SYNTAX Counter32
			MAX-ACCESS read-only
			STATUS current
			DESCRIPTION
				"Number of PADS packets."
			::= { msanPppoeIaStatistics 4 }

		
		-- 1.3.6.1.4.1.1332.1.1.5.3.11.3.5
		msanPppoeIaStatPADT OBJECT-TYPE
			SYNTAX Counter32
			MAX-ACCESS read-only
			STATUS current
			DESCRIPTION
				"Number of PADT packets."
			::= { msanPppoeIaStatistics 5 }

		
		-- 1.3.6.1.4.1.1332.1.1.5.3.11.3.6
		msanPppoeIaStatUnsutableFrames OBJECT-TYPE
			SYNTAX Counter32
			MAX-ACCESS read-only
			STATUS current
			DESCRIPTION
				"Number of packets with unsutable frame."
			::= { msanPppoeIaStatistics 6 }

		
		-- 1.3.6.1.4.1.1332.1.1.5.3.11.3.7
		msanPppoeIaStatUnknownFrames OBJECT-TYPE
			SYNTAX Counter32
			MAX-ACCESS read-only
			STATUS current
			DESCRIPTION
				"Number of packets with unknown frame."
			::= { msanPppoeIaStatistics 7 }

		
		-- 1.3.6.1.4.1.1332.1.1.5.3.11.3.8
		msanPppoeIaStatInvalidFrames OBJECT-TYPE
			SYNTAX Counter32
			MAX-ACCESS read-only
			STATUS current
			DESCRIPTION
				"Number of packets with invalid frame."
			::= { msanPppoeIaStatistics 8 }

		
		-- 1.3.6.1.4.1.1332.1.1.5.3.11.3.9
		msanPppoeIaPortStatisticsTable OBJECT-TYPE
			SYNTAX SEQUENCE OF MsanPppoeIaPortStatisticsEntry
			MAX-ACCESS not-accessible
			STATUS current
			DESCRIPTION
				"Description."
			::= { msanPppoeIaStatistics 9 }

		
		-- 1.3.6.1.4.1.1332.1.1.5.3.11.3.9.1
		msanPppoeIaPortStatisticsEntry OBJECT-TYPE
			SYNTAX MsanPppoeIaPortStatisticsEntry
			MAX-ACCESS not-accessible
			STATUS current
			DESCRIPTION
				"Description."
			INDEX { ifIndex }
			::= { msanPppoeIaPortStatisticsTable 1 }

		
		MsanPppoeIaPortStatisticsEntry ::=
			SEQUENCE { 
				msanPppoeIaPortStatPADI
					Counter32,
				msanPppoeIaPortStatPADR
					Counter32,
				msanPppoeIaPortStatPADO
					Counter32,
				msanPppoeIaPortStatPADS
					Counter32,
				msanPppoeIaPortStatPADT
					Counter32,
				msanPppoeIaPortStatUnsutableFrames
					Counter32,
				msanPppoeIaPortStatUnknownFrames
					Counter32,
				msanPppoeIaPortStatInvalidFrames
					Counter32
			 }

		-- 1.3.6.1.4.1.1332.1.1.5.3.11.3.9.1.1
		msanPppoeIaPortStatPADI OBJECT-TYPE
			SYNTAX Counter32
			MAX-ACCESS read-only
			STATUS current
			DESCRIPTION
				"Number of PADI packets on the port. "
			::= { msanPppoeIaPortStatisticsEntry 1 }

		
		-- 1.3.6.1.4.1.1332.1.1.5.3.11.3.9.1.2
		msanPppoeIaPortStatPADR OBJECT-TYPE
			SYNTAX Counter32
			MAX-ACCESS read-only
			STATUS current
			DESCRIPTION
				"Number of PADR packets on the port. "
			::= { msanPppoeIaPortStatisticsEntry 2 }

		
		-- 1.3.6.1.4.1.1332.1.1.5.3.11.3.9.1.3
		msanPppoeIaPortStatPADO OBJECT-TYPE
			SYNTAX Counter32
			MAX-ACCESS read-only
			STATUS current
			DESCRIPTION
				"Number of PADO packets on the port. "
			::= { msanPppoeIaPortStatisticsEntry 3 }

		
		-- 1.3.6.1.4.1.1332.1.1.5.3.11.3.9.1.4
		msanPppoeIaPortStatPADS OBJECT-TYPE
			SYNTAX Counter32
			MAX-ACCESS read-only
			STATUS current
			DESCRIPTION
				"Number of PADS packets on the port. "
			::= { msanPppoeIaPortStatisticsEntry 4 }

		
		-- 1.3.6.1.4.1.1332.1.1.5.3.11.3.9.1.5
		msanPppoeIaPortStatPADT OBJECT-TYPE
			SYNTAX Counter32
			MAX-ACCESS read-only
			STATUS current
			DESCRIPTION
				"Number of PADT packets on the port. "
			::= { msanPppoeIaPortStatisticsEntry 5 }

		
		-- 1.3.6.1.4.1.1332.1.1.5.3.11.3.9.1.6
		msanPppoeIaPortStatUnsutableFrames OBJECT-TYPE
			SYNTAX Counter32
			MAX-ACCESS read-only
			STATUS current
			DESCRIPTION
				"Number of packets with unsutable frame on the port. "
			::= { msanPppoeIaPortStatisticsEntry 6 }

		
		-- 1.3.6.1.4.1.1332.1.1.5.3.11.3.9.1.7
		msanPppoeIaPortStatUnknownFrames OBJECT-TYPE
			SYNTAX Counter32
			MAX-ACCESS read-only
			STATUS current
			DESCRIPTION
				"Number of packets with unknown frame on the port. "
			::= { msanPppoeIaPortStatisticsEntry 7 }

		
		-- 1.3.6.1.4.1.1332.1.1.5.3.11.3.9.1.8
		msanPppoeIaPortStatInvalidFrames OBJECT-TYPE
			SYNTAX Counter32
			MAX-ACCESS read-only
			STATUS current
			DESCRIPTION
				"Number of packets with invalid frame on the port. "
			::= { msanPppoeIaPortStatisticsEntry 8 }

		
		-- 1.3.6.1.4.1.1332.1.1.5.3.11.4
		msanPppoeIaVlanTable OBJECT-TYPE
			SYNTAX SEQUENCE OF MsanPppoeIaVlanEntry
			MAX-ACCESS not-accessible
			STATUS current
			DESCRIPTION
				"Description."
			::= { msanPppoeIA 4 }

		
		-- 1.3.6.1.4.1.1332.1.1.5.3.11.4.1
		msanPppoeIaVlanEntry OBJECT-TYPE
			SYNTAX MsanPppoeIaVlanEntry
			MAX-ACCESS not-accessible
			STATUS current
			DESCRIPTION
				"Description."
			INDEX { dot1qVlanIndex }
			::= { msanPppoeIaVlanTable 1 }

		
		MsanPppoeIaVlanEntry ::=
			SEQUENCE { 
				msanPppoeIaVlanStatus
					INTEGER
			 }

		-- 1.3.6.1.4.1.1332.1.1.5.3.11.4.1.1
		msanPppoeIaVlanStatus OBJECT-TYPE
			SYNTAX INTEGER
				{
				enable(1),
				disable(2)
				}
			MAX-ACCESS read-write
			STATUS current
			DESCRIPTION
				"State of PPPoE Intermadiate Agent per VLAN."
			::= { msanPppoeIaVlanEntry 1 }

		
		-- 1.3.6.1.4.1.1332.1.1.5.3.12
		msanQoS OBJECT IDENTIFIER ::= { msanAdditionalConf 12 }

		
		-- 1.3.6.1.4.1.1332.1.1.5.3.12.1
		msanQosGlobal OBJECT IDENTIFIER ::= { msanQoS 1 }

		
		-- 1.3.6.1.4.1.1332.1.1.5.3.12.2
		msanIpAclRuleTable OBJECT-TYPE
			SYNTAX SEQUENCE OF MsanIpAclRuleEntry
			MAX-ACCESS not-accessible
			STATUS current
			DESCRIPTION
				"This table extends aclTable/aclRuleTable."
			::= { msanQoS 2 }

		
		-- 1.3.6.1.4.1.1332.1.1.5.3.12.2.1
		msanIpAclRuleEntry OBJECT-TYPE
			SYNTAX MsanIpAclRuleEntry
			MAX-ACCESS not-accessible
			STATUS current
			DESCRIPTION
				"This table extends aclTable/aclRuleTable."
			INDEX { msanIpAclIndex, msanIpAclRuleIndex }
			::= { msanIpAclRuleTable 1 }

		
		MsanIpAclRuleEntry ::=
			SEQUENCE { 
				msanIpAclIndex
					Integer32,
				msanIpAclRuleIndex
					Integer32,
				msanIpAclRuleAssignVlanId
					Integer32,
				msanIpAclRuleAssignCoSPriority
					Integer32,
				msanIpAclRuleEgressIntf
					Integer32,
				msanIpAclRuleAssignVlanId2
					Integer32,
				msanIpAclRuleRemoveVlanId
					INTEGER,
				msanIpAclRuleIcmpType
					INTEGER,
				msanIpAclRuleDestMacAddr
					MacAddress,
				msanIpAclRuleDestMacMask
					MacAddress,
				msanIpAclRuleSrcMacAddr
					MacAddress,
				msanIpAclRuleSrcMacMask
					MacAddress,
				msanIpAclRuleCos
					INTEGER,
				msanIpAclRuleCos2
					INTEGER,
				msanIpAclRuleVlanId
					Unsigned32,
				msanIpAclRuleVlanId2
					Unsigned32,
				msanIpAclRuleCVlanId
					Integer32,
				msanIpAclRuleSVlanId
					Integer32,
				msanIpAclRuleAssignCVlanId
					Integer32,
				msanIpAclRuleAssignSVlanId
					Integer32,
				msanIpAclRuleRemoveSVlanId
					INTEGER,
				msanIpAclRuleVlanIdRangeStart
					Unsigned32,
				msanIpAclRuleVlanIdRangeEnd
					Unsigned32,
				msanIpAclRuleVlanId2RangeStart
					Unsigned32,
				msanIpAclRuleVlanId2RangeEnd
					Unsigned32,
				msanIpAclRuleSVlanIdRangeStart
					Unsigned32,
				msanIpAclRuleSVlanIdRangeEnd
					Unsigned32,
				msanIpAclRuleCVlanIdRangeStart
					Unsigned32,
				msanIpAclRuleCVlanIdRangeEnd
					Unsigned32,
				msanIpAclRuleSrcIpv6Address
					InetAddressIPv6,
				msanIpAclRuleSrcIpv6AddressMaskLen
					Integer32,
				msanIpAclRuleDestIpv6Address
					InetAddressIPv6,
				msanIpAclRuleDestIpv6AddressMaskLen
					Integer32,
				msanIpAclRuleAssignCPcp
					Integer32,
				msanIpAclRuleAssignSPcp
					Integer32
			 }

		-- 1.3.6.1.4.1.1332.1.1.5.3.12.2.1.1
		msanIpAclIndex OBJECT-TYPE
			SYNTAX Integer32 (1..199)
			MAX-ACCESS not-accessible
			STATUS current
			DESCRIPTION
				"This is aclIndex in aclTable"
			::= { msanIpAclRuleEntry 1 }

		
		-- 1.3.6.1.4.1.1332.1.1.5.3.12.2.1.2
		msanIpAclRuleIndex OBJECT-TYPE
			SYNTAX Integer32 (1..9)
			MAX-ACCESS not-accessible
			STATUS current
			DESCRIPTION
				"The index of the IP ACL rule (aclRuleIndex in aclRuleTable)."
			::= { msanIpAclRuleEntry 2 }

		
		-- 1.3.6.1.4.1.1332.1.1.5.3.12.2.1.3
		msanIpAclRuleAssignVlanId OBJECT-TYPE
			SYNTAX Integer32 (0..4095)
			MAX-ACCESS read-write
			STATUS obsolete
			DESCRIPTION
				"Assign VLAN Id."
			::= { msanIpAclRuleEntry 3 }

		
		-- 1.3.6.1.4.1.1332.1.1.5.3.12.2.1.4
		msanIpAclRuleAssignCoSPriority OBJECT-TYPE
			SYNTAX Integer32
			MAX-ACCESS read-write
			STATUS obsolete
			DESCRIPTION
				"Assign CoS priority"
			::= { msanIpAclRuleEntry 4 }

		
		-- 1.3.6.1.4.1.1332.1.1.5.3.12.2.1.5
		msanIpAclRuleEgressIntf OBJECT-TYPE
			SYNTAX Integer32
			MAX-ACCESS read-write
			STATUS obsolete
			DESCRIPTION
				"Egress interface ID (ifIndex/ifTable)."
			::= { msanIpAclRuleEntry 5 }

		
		-- 1.3.6.1.4.1.1332.1.1.5.3.12.2.1.6
		msanIpAclRuleAssignVlanId2 OBJECT-TYPE
			SYNTAX Integer32 (0..4095)
			MAX-ACCESS read-write
			STATUS obsolete
			DESCRIPTION
				"Assign Secondary VLAN ID -> add (if not exists) or change."
			::= { msanIpAclRuleEntry 6 }

		
		-- 1.3.6.1.4.1.1332.1.1.5.3.12.2.1.7
		msanIpAclRuleRemoveVlanId OBJECT-TYPE
			SYNTAX INTEGER
				{
				enable(1),
				disable(2)
				}
			MAX-ACCESS read-write
			STATUS obsolete
			DESCRIPTION
				"Remove VLAN Id (outer)."
			DEFVAL { disable }
			::= { msanIpAclRuleEntry 7 }

		
		-- 1.3.6.1.4.1.1332.1.1.5.3.12.2.1.8
		msanIpAclRuleIcmpType OBJECT-TYPE
			SYNTAX INTEGER
				{
				echoReply(0),
				destinationUnreachable(3),
				sourceQuench(4),
				redirect(5),
				echoRequest(8),
				routerAdvertisement(9),
				routerSolicitation(10),
				timeExceeded(11),
				parameterProblem(12),
				timestampRequest(13),
				timestampReply(14),
				informationRequest(15),
				informationReply(16),
				addressMaskRequest(17),
				addressMaskReply(18)
				}
			MAX-ACCESS read-write
			STATUS obsolete
			DESCRIPTION
				"ICMP message type used in the MAC ACL Classification.
				
				This parameter is used if  aclRuleProtocol is set to icmp(1)."
			::= { msanIpAclRuleEntry 8 }

		
		-- 1.3.6.1.4.1.1332.1.1.5.3.12.2.1.9
		msanIpAclRuleDestMacAddr OBJECT-TYPE
			SYNTAX MacAddress
			MAX-ACCESS read-write
			STATUS current
			DESCRIPTION
				"The Destination MAC address used in the Advanced IP ACL Classification.
				
				Advanced IP ACL:    msanIpAclIndex  value in range 200 ... 299"
			::= { msanIpAclRuleEntry 9 }

		
		-- 1.3.6.1.4.1.1332.1.1.5.3.12.2.1.10
		msanIpAclRuleDestMacMask OBJECT-TYPE
			SYNTAX MacAddress
			MAX-ACCESS read-write
			STATUS current
			DESCRIPTION
				"The Destination MAC address mask used in the Advanced IP Classification. 
				
				This mask value identifies the portion of the msanIpAclRuleDestMacAddr
				that is compared against a packet. A non-contiguous mask value is 
				permitted.
				
				Advanced IP ACL:    msanIpAclIndex value in range 200 ... 299"
			::= { msanIpAclRuleEntry 10 }

		
		-- 1.3.6.1.4.1.1332.1.1.5.3.12.2.1.11
		msanIpAclRuleSrcMacAddr OBJECT-TYPE
			SYNTAX MacAddress
			MAX-ACCESS read-write
			STATUS current
			DESCRIPTION
				"The Source MAC address used in the Advanced IP ACL Classification.
				
				Advanced IP ACL:    msanIpAclIndex value in range 200 ... 299"
			::= { msanIpAclRuleEntry 11 }

		
		-- 1.3.6.1.4.1.1332.1.1.5.3.12.2.1.12
		msanIpAclRuleSrcMacMask OBJECT-TYPE
			SYNTAX MacAddress
			MAX-ACCESS read-write
			STATUS current
			DESCRIPTION
				"The Source MAC address mask used in the Advanced IP Classification. 
				
				This mask value identifies the portion of the msanIpAclRuleSrcMacAddr
				that is compared against a packet. A non-contiguous mask value is 
				permitted.
				
				Advanced IP ACL:    msanIpAclIndex value in range 200 ... 299"
			::= { msanIpAclRuleEntry 12 }

		
		-- 1.3.6.1.4.1.1332.1.1.5.3.12.2.1.13
		msanIpAclRuleCos OBJECT-TYPE
			SYNTAX INTEGER (0..7)
			MAX-ACCESS read-write
			STATUS current
			DESCRIPTION
				"The Class of Service (COS) used in the Advanced IP Classification.
				
				This is the three-bit user priority field in the 802.1Q tag 
				header of a tagged Ethernet frame. For frames containing a 
				double VLAN tag, this field is located in the first/outer tag.
				
				Advanced IP ACL:    msanIpAclIndex value in range 200 ... 299
				"
			::= { msanIpAclRuleEntry 13 }

		
		-- 1.3.6.1.4.1.1332.1.1.5.3.12.2.1.14
		msanIpAclRuleCos2 OBJECT-TYPE
			SYNTAX INTEGER (0..7)
			MAX-ACCESS read-write
			STATUS current
			DESCRIPTION
				"The Secondary Class of Service (COS) used in the Advanced IP Classification.
				
				This is the three-bit user priority field in the second 802.1Q tag 
				header of a tagged Ethernet frame. 
				
				Advanced IP ACL:    msanIpAclIndex value in range 200 ... 299
				"
			::= { msanIpAclRuleEntry 14 }

		
		-- 1.3.6.1.4.1.1332.1.1.5.3.12.2.1.15
		msanIpAclRuleVlanId OBJECT-TYPE
			SYNTAX Unsigned32 (0..4095)
			MAX-ACCESS read-write
			STATUS obsolete
			DESCRIPTION
				"The VLAN ID value used in the Advanced IP Classification.
				
				The VLAN ID field is defined as the 12-bit VLAN identifier
				in the 802.1Q tag header of a tagged Ethernet frame.  This is 
				contained in the first/outer tag of a double VLAN tagged frame.
				
				Advanced IP ACL:    msanIpAclIndex value in range 200 ... 299
				"
			::= { msanIpAclRuleEntry 15 }

		
		-- 1.3.6.1.4.1.1332.1.1.5.3.12.2.1.16
		msanIpAclRuleVlanId2 OBJECT-TYPE
			SYNTAX Unsigned32 (0..4095)
			MAX-ACCESS read-write
			STATUS obsolete
			DESCRIPTION
				"The Secondary VLAN ID value used in the Advanced IP Classification.
				
				The VLAN ID field is defined as the 12-bit VLAN identifier
				in the second 802.1Q tag header of a tagged Ethernet frame.  
				
				Advanced IP ACL:    msanIpAclIndex value in range 200 ... 299
				"
			::= { msanIpAclRuleEntry 16 }

		
		-- 1.3.6.1.4.1.1332.1.1.5.3.12.2.1.17
		msanIpAclRuleCVlanId OBJECT-TYPE
			SYNTAX Integer32 (0..4095)
			MAX-ACCESS read-write
			STATUS current
			DESCRIPTION
				"The C-customer VLAN ID value used in the Advanced IP Classification.
				
				The VLAN ID field is defined as the 12-bit VLAN identifier
				in the second 802.1Q tag header of a tagged Ethernet frame.  
				
				Advanced IP ACL:    msanIpAclIndex value in range 200 ... 299"
			::= { msanIpAclRuleEntry 17 }

		
		-- 1.3.6.1.4.1.1332.1.1.5.3.12.2.1.18
		msanIpAclRuleSVlanId OBJECT-TYPE
			SYNTAX Integer32 (0..4095)
			MAX-ACCESS read-write
			STATUS current
			DESCRIPTION
				"The S-service VLAN ID value used in the Advanced IP Classification.
				
				The VLAN ID field is defined as the 12-bit VLAN identifier
				in the 802.1Q tag header of a tagged Ethernet frame.  This is 
				contained in the first/outer tag of a double VLAN tagged frame.
				
				Advanced IP ACL:    msanIpAclIndex value in range 200 ... 299"
			::= { msanIpAclRuleEntry 18 }

		
		-- 1.3.6.1.4.1.1332.1.1.5.3.12.2.1.19
		msanIpAclRuleAssignCVlanId OBJECT-TYPE
			SYNTAX Integer32 (0..4095)
			MAX-ACCESS read-write
			STATUS current
			DESCRIPTION
				"Assign C VLAN ID -> add (if not exists) or change.
				
				Used in the Advanced IP Classification.
				Advanced IP ACL:    msanIpAclIndex value in range 200 ... 299"
			::= { msanIpAclRuleEntry 19 }

		
		-- 1.3.6.1.4.1.1332.1.1.5.3.12.2.1.20
		msanIpAclRuleAssignSVlanId OBJECT-TYPE
			SYNTAX Integer32 (0..4095)
			MAX-ACCESS read-write
			STATUS current
			DESCRIPTION
				"Assign S VLAN ID -> add (if not exists) or change.
				
				Used in the Advanced IP Classification.
				Advanced IP ACL:    msanIpAclIndex value in range 200 ... 299"
			::= { msanIpAclRuleEntry 20 }

		
		-- 1.3.6.1.4.1.1332.1.1.5.3.12.2.1.21
		msanIpAclRuleRemoveSVlanId OBJECT-TYPE
			SYNTAX INTEGER
				{
				enable(1),
				disable(2)
				}
			MAX-ACCESS read-write
			STATUS current
			DESCRIPTION
				"Remove S-service VLAN ID.
				
				Used in the Advanced IP Classification.
				Advanced IP ACL:    msanIpAclIndex value in range 200 ... 299"
			::= { msanIpAclRuleEntry 21 }

		
		-- 1.3.6.1.4.1.1332.1.1.5.3.12.2.1.22
		msanIpAclRuleVlanIdRangeStart OBJECT-TYPE
			SYNTAX Unsigned32 (0..4095)
			MAX-ACCESS read-write
			STATUS obsolete
			DESCRIPTION
				"The VLAN ID range start value used in the Advanced IP Classification.
				Setting this value greater than the current msanIpAclRuleVlanIdRangeEnd
				changes the VLAN ID range end to the same value as the range start.
				
				The VLAN ID field is defined as the 12-bit VLAN identifier
				in the 802.1Q tag header of a tagged Ethernet frame.  This is 
				contained in the first/outer tag of a double VLAN tagged frame.
				
				Advanced IP ACL:    msanIpAclIndex value in range 200 ... 299"
			::= { msanIpAclRuleEntry 22 }

		
		-- 1.3.6.1.4.1.1332.1.1.5.3.12.2.1.23
		msanIpAclRuleVlanIdRangeEnd OBJECT-TYPE
			SYNTAX Unsigned32 (0..4095)
			MAX-ACCESS read-write
			STATUS obsolete
			DESCRIPTION
				"The VLAN ID range end value used in the Advanced IP Classification.
				Setting this value less than the current msanIpAclRuleVlanIdRangeStart
				changes the VLAN ID range start to the same value as the range end.
				
				The VLAN ID field is defined as the 12-bit VLAN identifier
				in the 802.1Q tag header of a tagged Ethernet frame.  This is 
				contained in the first/outer tag of a double VLAN tagged frame.
				
				Advanced IP ACL:    msanIpAclIndex value in range 200 ... 299"
			::= { msanIpAclRuleEntry 23 }

		
		-- 1.3.6.1.4.1.1332.1.1.5.3.12.2.1.24
		msanIpAclRuleVlanId2RangeStart OBJECT-TYPE
			SYNTAX Unsigned32 (0..4095)
			MAX-ACCESS read-write
			STATUS obsolete
			DESCRIPTION
				"The Secondary VLAN ID range start value used in the Advanced IP Classification.
				Setting this value greater than the current msanIpAclRuleVlanId2RangeEnd
				changes the VLAN ID range end to the same value as the range start.
				
				The VLAN ID field is defined as the 12-bit VLAN identifier
				in the second 802.1Q tag header of a tagged Ethernet frame.
				
				Advanced IP ACL:    msanIpAclIndex value in range 200 ... 299"
			::= { msanIpAclRuleEntry 24 }

		
		-- 1.3.6.1.4.1.1332.1.1.5.3.12.2.1.25
		msanIpAclRuleVlanId2RangeEnd OBJECT-TYPE
			SYNTAX Unsigned32 (0..4095)
			MAX-ACCESS read-write
			STATUS obsolete
			DESCRIPTION
				"The Secondary VLAN ID range end value used in the Advanced IP Classification.
				Setting this value less than the current msanIpAclRuleVlanId2RangeStart
				changes the VLAN ID range start to the same value as the range end.
				
				The VLAN ID field is defined as the 12-bit VLAN identifier
				in the second 802.1Q tag header of a tagged Ethernet frame.
				
				Advanced IP ACL:    msanIpAclIndex value in range 200 ... 299"
			::= { msanIpAclRuleEntry 25 }

		
		-- 1.3.6.1.4.1.1332.1.1.5.3.12.2.1.26
		msanIpAclRuleSVlanIdRangeStart OBJECT-TYPE
			SYNTAX Unsigned32 (0..4095)
			MAX-ACCESS read-write
			STATUS current
			DESCRIPTION
				"The S-service VLAN ID range start value used in the Advanced IP Classification.
				Setting this value greater than the current msanIpAclRuleSVlanIdRangeEnd
				changes the VLAN ID range end to the same value as the range start.
				
				Advanced IP ACL:    msanIpAclIndex value in range 200 ... 299"
			::= { msanIpAclRuleEntry 26 }

		
		-- 1.3.6.1.4.1.1332.1.1.5.3.12.2.1.27
		msanIpAclRuleSVlanIdRangeEnd OBJECT-TYPE
			SYNTAX Unsigned32 (0..4095)
			MAX-ACCESS read-write
			STATUS current
			DESCRIPTION
				"The S-service VLAN ID range end value used in the Advanced IP Classification.
				Setting this value less than the current msanIpAclRuleSVlanIdRangeStart
				changes the VLAN ID range start to the same value as the range end.
				
				Advanced IP ACL:    msanIpAclIndex value in range 200 ... 299"
			::= { msanIpAclRuleEntry 27 }

		
		-- 1.3.6.1.4.1.1332.1.1.5.3.12.2.1.28
		msanIpAclRuleCVlanIdRangeStart OBJECT-TYPE
			SYNTAX Unsigned32 (0..4095)
			MAX-ACCESS read-write
			STATUS current
			DESCRIPTION
				"The C-customer VLAN ID range start value used in the Advanced IP Classification.
				Setting this value greater than the current msanIpAclRuleCVlanIdRangeEnd
				changes the VLAN ID range end to the same value as the range start.
				
				Advanced IP ACL:    msanIpAclIndex value in range 200 ... 299"
			::= { msanIpAclRuleEntry 28 }

		
		-- 1.3.6.1.4.1.1332.1.1.5.3.12.2.1.29
		msanIpAclRuleCVlanIdRangeEnd OBJECT-TYPE
			SYNTAX Unsigned32 (0..4095)
			MAX-ACCESS read-write
			STATUS current
			DESCRIPTION
				"The C-customer VLAN ID range end value used in the Advanced IP Classification.
				Setting this value less than the current msanIpAclRuleCVlanIdRangeStart
				changes the VLAN ID range start to the same value as the range end.
				
				Advanced IP ACL:    msanIpAclIndex value in range 200 ... 299"
			::= { msanIpAclRuleEntry 29 }

		
		-- 1.3.6.1.4.1.1332.1.1.5.3.12.2.1.31
		msanIpAclRuleSrcIpv6Address OBJECT-TYPE
			SYNTAX InetAddressIPv6
			MAX-ACCESS read-write
			STATUS current
			DESCRIPTION
				"The Source IPv6 Address used in the ACL Classification.
				"
			::= { msanIpAclRuleEntry 31 }

		
		-- 1.3.6.1.4.1.1332.1.1.5.3.12.2.1.32
		msanIpAclRuleSrcIpv6AddressMaskLen OBJECT-TYPE
			SYNTAX Integer32 (0..128)
			MAX-ACCESS read-write
			STATUS current
			DESCRIPTION
				"The length of the prefix (in bits) associated with the
				IPv6 source address of this entry (msanIpAclRuleSrcIpv6Address).
				
				Value 0 indicates that parameter has not been defined."
			DEFVAL { 0 }
			::= { msanIpAclRuleEntry 32 }

		
		-- 1.3.6.1.4.1.1332.1.1.5.3.12.2.1.33
		msanIpAclRuleDestIpv6Address OBJECT-TYPE
			SYNTAX InetAddressIPv6
			MAX-ACCESS read-write
			STATUS current
			DESCRIPTION
				"The Destination IPv6 Address used in the ACL Classification.
				"
			::= { msanIpAclRuleEntry 33 }

		
		-- 1.3.6.1.4.1.1332.1.1.5.3.12.2.1.34
		msanIpAclRuleDestIpv6AddressMaskLen OBJECT-TYPE
			SYNTAX Integer32 (0..128)
			MAX-ACCESS read-write
			STATUS current
			DESCRIPTION
				"The length of the prefix (in bits) associated with the
				IPv6 destination address of this entry (msanIpAclRuleDestIpv6Address).
				
				Value 0 indicates that parameter has not been defined."
			DEFVAL { 0 }
			::= { msanIpAclRuleEntry 34 }

		
		-- 1.3.6.1.4.1.1332.1.1.5.3.12.2.1.35
		msanIpAclRuleAssignCPcp OBJECT-TYPE
			SYNTAX Integer32 (0..4095)
			MAX-ACCESS read-write
			STATUS current
			DESCRIPTION
				"Assign Customer PCP (Priority Code Point) - 
				PCP is also known as Class of Service (CoS) bits.
				A value of -1 indicates that parameter has not been defined.
				This parameter can be used only if msanIpAclRuleAssignCVlanId is already set.
				
				Used in the Advanced IP Classification.
				Advanced IP ACL:    msanIpAclIndex value in range 200 ... 299"
			::= { msanIpAclRuleEntry 35 }

		
		-- 1.3.6.1.4.1.1332.1.1.5.3.12.2.1.36
		msanIpAclRuleAssignSPcp OBJECT-TYPE
			SYNTAX Integer32 (0..4095)
			MAX-ACCESS read-write
			STATUS current
			DESCRIPTION
				"Assign Service PCP  (Priority Code Point).
				PCP is also known as Class of Service (CoS) bits.
				A value of -1 indicates that parameter has not been defined.
				This parameter can be used only if msanIpAclRuleAssignSVlanId is already set.
				
				Used in the Advanced IP Classification.
				Advanced IP ACL:    msanIpAclIndex value in range 200 ... 299"
			::= { msanIpAclRuleEntry 36 }

		
		-- 1.3.6.1.4.1.1332.1.1.5.3.12.3
		msanMacAclRuleTable OBJECT-TYPE
			SYNTAX SEQUENCE OF MsanMacAclRuleEntry
			MAX-ACCESS not-accessible
			STATUS current
			DESCRIPTION
				"This table extends aclMacTable/aclMacRuleTable."
			::= { msanQoS 3 }

		
		-- 1.3.6.1.4.1.1332.1.1.5.3.12.3.1
		msanMacAclRuleEntry OBJECT-TYPE
			SYNTAX MsanMacAclRuleEntry
			MAX-ACCESS not-accessible
			STATUS current
			DESCRIPTION
				"This table extends aclMacTable/aclMacRuleTable."
			INDEX { msanMacAclIndex, msanMacAclRuleIndex }
			::= { msanMacAclRuleTable 1 }

		
		MsanMacAclRuleEntry ::=
			SEQUENCE { 
				msanMacAclIndex
					Integer32,
				msanMacAclRuleIndex
					Integer32,
				msanMacAclRuleEgressIntf
					Integer32,
				msanMacAclRuleAssignVlanId
					Integer32,
				msanMacAclRuleAssignCoSPriority
					Integer32,
				msanMacAclRuleAssignVlanId2
					Integer32,
				msanMacAclRuleRemoveVlanId
					INTEGER,
				msanMacAclRuleCVlanId
					Integer32,
				msanMacAclRuleSVlanId
					Integer32,
				msanMacAclRuleAssignCVlanId
					Integer32,
				msanMacAclRuleAssignSVlanId
					Integer32,
				msanMacAclRuleRemoveSVlanId
					INTEGER,
				msanMacAclRuleSVlanIdRangeStart
					Unsigned32,
				msanMacAclRuleSVlanIdRangeEnd
					Unsigned32,
				msanMacAclRuleCVlanIdRangeStart
					Unsigned32,
				msanMacAclRuleCVlanIdRangeEnd
					Unsigned32,
				msanMacAclRuleAssignCPcp
					Integer32,
				msanMacAclRuleAssignSPcp
					Integer32
			 }

		-- 1.3.6.1.4.1.1332.1.1.5.3.12.3.1.1
		msanMacAclIndex OBJECT-TYPE
			SYNTAX Integer32 (1..1000)
			MAX-ACCESS not-accessible
			STATUS current
			DESCRIPTION
				"This is aclMacIndex in aclMacTable"
			::= { msanMacAclRuleEntry 1 }

		
		-- 1.3.6.1.4.1.1332.1.1.5.3.12.3.1.2
		msanMacAclRuleIndex OBJECT-TYPE
			SYNTAX Integer32 (1..1000)
			MAX-ACCESS not-accessible
			STATUS current
			DESCRIPTION
				"The index of the MAC ACL rule (aclMACRuleIndex in aclMACRuleTable)."
			::= { msanMacAclRuleEntry 2 }

		
		-- 1.3.6.1.4.1.1332.1.1.5.3.12.3.1.3
		msanMacAclRuleEgressIntf OBJECT-TYPE
			SYNTAX Integer32
			MAX-ACCESS read-write
			STATUS obsolete
			DESCRIPTION
				"Egress Interface ID (ifIndex/ifTable)."
			::= { msanMacAclRuleEntry 3 }

		
		-- 1.3.6.1.4.1.1332.1.1.5.3.12.3.1.4
		msanMacAclRuleAssignVlanId OBJECT-TYPE
			SYNTAX Integer32 (0..4095)
			MAX-ACCESS read-write
			STATUS obsolete
			DESCRIPTION
				"Assign VLAN Id."
			::= { msanMacAclRuleEntry 4 }

		
		-- 1.3.6.1.4.1.1332.1.1.5.3.12.3.1.5
		msanMacAclRuleAssignCoSPriority OBJECT-TYPE
			SYNTAX Integer32
			MAX-ACCESS read-write
			STATUS obsolete
			DESCRIPTION
				"Assign CoS priority"
			::= { msanMacAclRuleEntry 5 }

		
		-- 1.3.6.1.4.1.1332.1.1.5.3.12.3.1.6
		msanMacAclRuleAssignVlanId2 OBJECT-TYPE
			SYNTAX Integer32 (0..4095)
			MAX-ACCESS read-write
			STATUS obsolete
			DESCRIPTION
				"Assign Secondary VLAN ID -> add (if not exists) or change."
			::= { msanMacAclRuleEntry 6 }

		
		-- 1.3.6.1.4.1.1332.1.1.5.3.12.3.1.7
		msanMacAclRuleRemoveVlanId OBJECT-TYPE
			SYNTAX INTEGER
				{
				enable(1),
				disable(2)
				}
			MAX-ACCESS read-write
			STATUS obsolete
			DESCRIPTION
				"Remove outer VLAN Id (outer)."
			DEFVAL { disable }
			::= { msanMacAclRuleEntry 7 }

		
		-- 1.3.6.1.4.1.1332.1.1.5.3.12.3.1.8
		msanMacAclRuleCVlanId OBJECT-TYPE
			SYNTAX Integer32
			MAX-ACCESS read-write
			STATUS current
			DESCRIPTION
				"C-customer Vlan ID"
			::= { msanMacAclRuleEntry 8 }

		
		-- 1.3.6.1.4.1.1332.1.1.5.3.12.3.1.9
		msanMacAclRuleSVlanId OBJECT-TYPE
			SYNTAX Integer32
			MAX-ACCESS read-write
			STATUS current
			DESCRIPTION
				"S-service Vlan ID"
			::= { msanMacAclRuleEntry 9 }

		
		-- 1.3.6.1.4.1.1332.1.1.5.3.12.3.1.10
		msanMacAclRuleAssignCVlanId OBJECT-TYPE
			SYNTAX Integer32 (0..4095)
			MAX-ACCESS read-write
			STATUS current
			DESCRIPTION
				"Assign C-customer  VLAN ID -> add (if not exists) or change."
			::= { msanMacAclRuleEntry 10 }

		
		-- 1.3.6.1.4.1.1332.1.1.5.3.12.3.1.11
		msanMacAclRuleAssignSVlanId OBJECT-TYPE
			SYNTAX Integer32 (0..4095)
			MAX-ACCESS read-write
			STATUS current
			DESCRIPTION
				"Assign S-service VLAN ID -> add (if not exists) or change."
			::= { msanMacAclRuleEntry 11 }

		
		-- 1.3.6.1.4.1.1332.1.1.5.3.12.3.1.12
		msanMacAclRuleRemoveSVlanId OBJECT-TYPE
			SYNTAX INTEGER
				{
				enable(1),
				disable(2)
				}
			MAX-ACCESS read-write
			STATUS current
			DESCRIPTION
				"Remove S-service VLAN ID."
			::= { msanMacAclRuleEntry 12 }

		
		-- 1.3.6.1.4.1.1332.1.1.5.3.12.3.1.13
		msanMacAclRuleSVlanIdRangeStart OBJECT-TYPE
			SYNTAX Unsigned32 (0..4095)
			MAX-ACCESS read-write
			STATUS current
			DESCRIPTION
				"The S-service VLAN ID range start value.
				Setting this value greater than the current msanMacAclRuleSVlanIdRangeEnd
				changes the VLAN ID range end to the same value as the range start.
				"
			::= { msanMacAclRuleEntry 13 }

		
		-- 1.3.6.1.4.1.1332.1.1.5.3.12.3.1.14
		msanMacAclRuleSVlanIdRangeEnd OBJECT-TYPE
			SYNTAX Unsigned32 (0..4095)
			MAX-ACCESS read-write
			STATUS current
			DESCRIPTION
				"The S-service VLAN ID range end value.
				Setting this value less than the current msanMacAclRuleSVlanIdRangeStart
				changes the VLAN ID range start to the same value as the range end."
			::= { msanMacAclRuleEntry 14 }

		
		-- 1.3.6.1.4.1.1332.1.1.5.3.12.3.1.15
		msanMacAclRuleCVlanIdRangeStart OBJECT-TYPE
			SYNTAX Unsigned32 (0..4095)
			MAX-ACCESS read-write
			STATUS current
			DESCRIPTION
				"The C-customer VLAN ID range start value.
				Setting this value greater than the current msanMacAclRuleCVlanIdRangeEnd
				changes the VLAN ID range end to the same value as the range start.
				"
			::= { msanMacAclRuleEntry 15 }

		
		-- 1.3.6.1.4.1.1332.1.1.5.3.12.3.1.16
		msanMacAclRuleCVlanIdRangeEnd OBJECT-TYPE
			SYNTAX Unsigned32 (0..4095)
			MAX-ACCESS read-write
			STATUS current
			DESCRIPTION
				"The C-customer VLAN ID range end value.
				Setting this value less than the current msanMacAclRuleCVlanIdRangeStart
				changes the VLAN ID range start to the same value as the range end."
			::= { msanMacAclRuleEntry 16 }

		
		-- 1.3.6.1.4.1.1332.1.1.5.3.12.3.1.17
		msanMacAclRuleAssignCPcp OBJECT-TYPE
			SYNTAX Integer32 (0..4095)
			MAX-ACCESS read-write
			STATUS current
			DESCRIPTION
				"Assign Customer PCP (Priority Code Point) - 
				PCP is also known as Class of Service (CoS) bits.
				A value of -1 indicates that parameter has not been defined.
				This parameter can be used only if msanMacAclRuleAssignCVlanId is already set.
				"
			::= { msanMacAclRuleEntry 17 }

		
		-- 1.3.6.1.4.1.1332.1.1.5.3.12.3.1.18
		msanMacAclRuleAssignSPcp OBJECT-TYPE
			SYNTAX Integer32 (0..4095)
			MAX-ACCESS read-write
			STATUS current
			DESCRIPTION
				"Assign Service PCP (Priority Code Point) - 
				PCP is also known as Class of Service (CoS) bits.
				A value of -1 indicates that parameter has not been defined.
				This parameter can be used only if msanMacAclRuleAssignSVlanId is already set.
				"
			::= { msanMacAclRuleEntry 18 }

		
		-- 1.3.6.1.4.1.1332.1.1.5.3.12.4
		msanCosQueueControlTable OBJECT-TYPE
			SYNTAX SEQUENCE OF MsanCosQueueControlEntry
			MAX-ACCESS not-accessible
			STATUS current
			DESCRIPTION
				"Description."
			::= { msanQoS 4 }

		
		-- 1.3.6.1.4.1.1332.1.1.5.3.12.4.1
		msanCosQueueControlEntry OBJECT-TYPE
			SYNTAX MsanCosQueueControlEntry
			MAX-ACCESS not-accessible
			STATUS current
			DESCRIPTION
				"Description."
			INDEX { ifIndex }
			::= { msanCosQueueControlTable 1 }

		
		MsanCosQueueControlEntry ::=
			SEQUENCE { 
				msanCosQueueControlIntfBurstSize
					Integer32,
				msanCosQueueIntfShapingRate
					Unsigned32
			 }

		-- 1.3.6.1.4.1.1332.1.1.5.3.12.4.1.1
		msanCosQueueControlIntfBurstSize OBJECT-TYPE
			SYNTAX Integer32
			UNITS "kilobyte"
			MAX-ACCESS read-write
			STATUS current
			DESCRIPTION
				"Specifies the maximum number of uncommitted bytes that the switch will try to send into the network. It is the number of bytes that are sent at a rate, 
				higher than committed and that the next device in the network must be able to buffer without notifying a congestion. Default value is 0. 
				Valid values are 16, 20, 28, 40, 76, 140, 268 and 524 kilobytes. Configuring shaping rate without burst size will take the maximum possible value of burst, which is 524 KB. "
			::= { msanCosQueueControlEntry 1 }

		
		-- 1.3.6.1.4.1.1332.1.1.5.3.12.4.1.2
		msanCosQueueIntfShapingRate OBJECT-TYPE
			SYNTAX Unsigned32 (0..10000000)
			UNITS "kbps"
			MAX-ACCESS read-write
			STATUS current
			DESCRIPTION
				"Specifies the maximum bandwidth allowed, typically used to shape 
				the outbound transmission rate. This value is controlled independently 
				of any per-queue maximum bandwidth configuration. It is effectively a 
				second-level shaping mechanism. 
				Default value is 0. Valid Range is 0 to 10000000 kbps. The value 0 means 
				maximum is unlimited."
			::= { msanCosQueueControlEntry 2 }

		
		-- 1.3.6.1.4.1.1332.1.1.5.3.12.5
		msanCosQueueTable OBJECT-TYPE
			SYNTAX SEQUENCE OF MsanCosQueueEntry
			MAX-ACCESS not-accessible
			STATUS current
			DESCRIPTION
				"Table of class-of-service queue configuration 
				parameters for the specified interface.
				
				This is extension of the table agentCosQueueTable. "
			REFERENCE
				"agentCosQueueTable  - 1.3.6.1.4.1.6132.1.1.3.3.2.4"
			::= { msanQoS 5 }

		
		-- 1.3.6.1.4.1.1332.1.1.5.3.12.5.1
		msanCosQueueEntry OBJECT-TYPE
			SYNTAX MsanCosQueueEntry
			MAX-ACCESS not-accessible
			STATUS current
			DESCRIPTION
				"Each entry describes a single class-of-service (COS) 
				queue for a given Interface Index. The number of 
				configurable COS queues for an interface vary based 
				on device capabilities.
				
				All objects defined for this table entry contain a 
				default value corresponding to a typical, 
				non-preferential treatment of packets traversing the 
				interface's COS queues."
			REFERENCE
				"agentCosQueueTable  - 1.3.6.1.4.1.6132.1.1.3.3.2.4"
			INDEX { ifIndex, msanCosQueueIndex }
			::= { msanCosQueueTable 1 }

		
		MsanCosQueueEntry ::=
			SEQUENCE { 
				msanCosQueueIndex
					Integer32,
				msanCosQueueWeight
					INTEGER,
				msanCosQueueLength
					INTEGER
			 }

		-- 1.3.6.1.4.1.1332.1.1.5.3.12.5.1.1
		msanCosQueueIndex OBJECT-TYPE
			SYNTAX Integer32 (0..1000)
			MAX-ACCESS not-accessible
			STATUS current
			DESCRIPTION
				"The COS queue index, numbered 0 to (n-1), where n is 
				the total number of configurable interface queues for 
				the device as indicated by agentCosQueueNumQueuesPerPort.
				In general, a higher numbered queue index is used to 
				support higher priority traffic, although actual 
				operation may be altered via configuration through 
				this table."
			::= { msanCosQueueEntry 1 }

		
		-- 1.3.6.1.4.1.1332.1.1.5.3.12.5.1.2
		msanCosQueueWeight OBJECT-TYPE
			SYNTAX INTEGER (0..32)
			MAX-ACCESS read-write
			STATUS current
			DESCRIPTION
				"Weight of the queue being used in egress scheduling algorithm."
			::= { msanCosQueueEntry 2 }

		
		-- 1.3.6.1.4.1.1332.1.1.5.3.12.5.1.3
		msanCosQueueLength OBJECT-TYPE
			SYNTAX INTEGER (2..156)
			MAX-ACCESS read-write
			STATUS current
			DESCRIPTION
				"Length of the queue in kB. "
			DEFVAL { 40 }
			::= { msanCosQueueEntry 3 }

		
		-- 1.3.6.1.4.1.1332.1.1.5.3.12.6
		msanCosMapIntfTrustTable OBJECT-TYPE
			SYNTAX SEQUENCE OF MsanCosMapIntfTrustEntry
			MAX-ACCESS not-accessible
			STATUS current
			DESCRIPTION
				"Description."
			::= { msanQoS 6 }

		
		-- 1.3.6.1.4.1.1332.1.1.5.3.12.6.1
		msanCosMapIntfTrustEntry OBJECT-TYPE
			SYNTAX MsanCosMapIntfTrustEntry
			MAX-ACCESS not-accessible
			STATUS current
			DESCRIPTION
				"Description."
			INDEX { ifIndex }
			::= { msanCosMapIntfTrustTable 1 }

		
		MsanCosMapIntfTrustEntry ::=
			SEQUENCE { 
				msanCosMapIntfTrustMode
					INTEGER
			 }

		-- 1.3.6.1.4.1.1332.1.1.5.3.12.6.1.1
		msanCosMapIntfTrustMode OBJECT-TYPE
			SYNTAX INTEGER
				{
				untrusted(1),
				trustDot1p(2),
				trustIpPrecedence(3),
				trustIpDscp(4)
				}
			MAX-ACCESS read-write
			STATUS current
			DESCRIPTION
				"This is copy of LVL7 parameter agentCosMapIntfTrustMode, 
				except that index 0 is not supported.
				
				The class of service trust mode of an interface.  
				When set to a trusted mode, the appropriate COS 
				mapping table is used as follows:
				 	  
				   trustDot1p(2) : dot1dTrafficClassTable
				   trustIpPrecedence(3): agentCosMapIpPrecTable
				   trustIpDscp(4): agentCosMapIpDscpTable 
				 	  
				For an untrusted(1) interface, packets are handled in 
				accordance with the dot1dPortDefaultUserPriority value 
				of the ingress port.
				"
			::= { msanCosMapIntfTrustEntry 1 }

		
		-- 1.3.6.1.4.1.1332.1.1.5.3.12.7
		msanQosProfileTable OBJECT-TYPE
			SYNTAX SEQUENCE OF MsanQosProfileEntry
			MAX-ACCESS not-accessible
			STATUS current
			DESCRIPTION
				"Description."
			::= { msanQoS 7 }

		
		-- 1.3.6.1.4.1.1332.1.1.5.3.12.7.1
		msanQosProfileEntry OBJECT-TYPE
			SYNTAX MsanQosProfileEntry
			MAX-ACCESS not-accessible
			STATUS current
			DESCRIPTION
				"Description."
			INDEX { msanQosProfileName }
			::= { msanQosProfileTable 1 }

		
		MsanQosProfileEntry ::=
			SEQUENCE { 
				msanQosProfileName
					OCTET STRING,
				msanQosProfileMatchInAny
					INTEGER,
				msanQosProfileMatchInMacDestAddr
					MacAddress,
				msanQosProfileMatchInMacDestMask
					MacAddress,
				msanQosProfileMatchInMacSrcAddr
					MacAddress,
				msanQosProfileMatchInMacSrcMask
					MacAddress,
				msanQosProfileMatchInCos
					Integer32,
				msanQosProfileMatchInCos2
					Integer32,
				msanQosProfileMatchInVlanId
					Integer32,
				msanQosProfileMatchInVlanId2
					Integer32,
				msanQosProfileMatchInEthertype
					Integer32,
				msanQosProfileMatchInIpProtocol
					Integer32,
				msanQosProfileMatchInIpSrcAddr
					IpAddress,
				msanQosProfileMatchInIpSrcMask
					IpAddress,
				msanQosProfileMatchInIpDestAddr
					IpAddress,
				msanQosProfileMatchInIpDestMask
					IpAddress,
				msanQosProfileMatchInIpDscp
					Integer32,
				msanQosProfileMatchInIpPrecedence
					Integer32,
				msanQosProfileMatchInIpTosBits
					OCTET STRING,
				msanQosProfileMatchInIpTosMask
					OCTET STRING,
				msanQosProfileMatchInL4SrcPort
					Integer32,
				msanQosProfileMatchInL4DestPort
					Integer32,
				msanQosProfileMatchOutAny
					INTEGER,
				msanQosProfileMatchOutMacDestAddr
					MacAddress,
				msanQosProfileMatchOutMacDestMask
					MacAddress,
				msanQosProfileMatchOutMacSrcAddr
					MacAddress,
				msanQosProfileMatchOutMacSrcMask
					MacAddress,
				msanQosProfileMatchOutCos
					Integer32,
				msanQosProfileMatchOutCos2
					Integer32,
				msanQosProfileMatchOutVlanId
					Integer32,
				msanQosProfileMatchOutVlanId2
					Integer32,
				msanQosProfileMatchOutEthertype
					Integer32,
				msanQosProfileMatchOutIpProtocol
					Integer32,
				msanQosProfileMatchOutIpSrcAddr
					IpAddress,
				msanQosProfileMatchOutIpSrcMask
					IpAddress,
				msanQosProfileMatchOutIpDestAddr
					IpAddress,
				msanQosProfileMatchOutIpDestMask
					IpAddress,
				msanQosProfileMatchOutIpDscp
					Integer32,
				msanQosProfileMatchOutIpPrecedence
					Integer32,
				msanQosProfileMatchOutIpTosBits
					OCTET STRING,
				msanQosProfileMatchOutIpTosMask
					OCTET STRING,
				msanQosProfileMatchOutL4SrcPort
					Integer32,
				msanQosProfileMatchOutL4DestPort
					Integer32,
				msanQosProfileInCdr
					Integer32,
				msanQosProfileInPdr
					Integer32,
				msanQosProfileOutCdr
					Integer32,
				msanQosProfileOutPdr
					Integer32,
				msanQosProfileInTrustMode
					INTEGER,
				msanQosProfileInMarkCos
					INTEGER,
				msanQosProfileInMarkDscp
					INTEGER,
				msanQosProfileRowStatus
					RowStatus,
				msanQosProfilePriority
					INTEGER,
				msanQosProfileInCdrBurstSize
					Integer32,
				msanQosProfileInPdrBurstSize
					Integer32,
				msanQosProfileOutCdrBurstSize
					Integer32,
				msanQosProfileOutPdrBurstSize
					Integer32,
				msanQosProfileMatchInSrcIpv6Address
					InetAddressIPv6,
				msanQosProfileMatchInSrcIpv6AddressMaskLen
					Integer32,
				msanQosProfileMatchInDestIpv6Address
					InetAddressIPv6,
				msanQosProfileMatchInDestIpv6AddressMaskLen
					Integer32,
				msanQosProfileMatchOutSrcIpv6Address
					InetAddressIPv6,
				msanQosProfileMatchOutSrcIpv6AddressMaskLen
					Integer32,
				msanQosProfileMatchOutDestIpv6Address
					InetAddressIPv6,
				msanQosProfileMatchOutDestIpv6AddressMaskLen
					Integer32
			 }

		-- 1.3.6.1.4.1.1332.1.1.5.3.12.7.1.1
		msanQosProfileName OBJECT-TYPE
			SYNTAX OCTET STRING (SIZE (1..32))
			MAX-ACCESS not-accessible
			STATUS current
			DESCRIPTION
				"QoS profile name."
			::= { msanQosProfileEntry 1 }

		
		-- 1.3.6.1.4.1.1332.1.1.5.3.12.7.1.2
		msanQosProfileMatchInAny OBJECT-TYPE
			SYNTAX INTEGER
				{
				enable(1),
				disable(2)
				}
			MAX-ACCESS read-write
			STATUS current
			DESCRIPTION
				"Match every incoming packet frame."
			DEFVAL { disable }
			::= { msanQosProfileEntry 2 }

		
		-- 1.3.6.1.4.1.1332.1.1.5.3.12.7.1.3
		msanQosProfileMatchInMacDestAddr OBJECT-TYPE
			SYNTAX MacAddress
			MAX-ACCESS read-write
			STATUS current
			DESCRIPTION
				"Match incoming packet frame with specified destination MAC address.
				Empty string indicates that parameter has not been defined"
			DEFVAL { ''b }
			::= { msanQosProfileEntry 3 }

		
		-- 1.3.6.1.4.1.1332.1.1.5.3.12.7.1.4
		msanQosProfileMatchInMacDestMask OBJECT-TYPE
			SYNTAX MacAddress
			MAX-ACCESS read-write
			STATUS current
			DESCRIPTION
				"This mask value identifies the portion of msanQosProfileMatchInMacDestAddr that 
				is compared with input packet.
				Empty string indicates that parameter has not been defined"
			DEFVAL { ''b }
			::= { msanQosProfileEntry 4 }

		
		-- 1.3.6.1.4.1.1332.1.1.5.3.12.7.1.5
		msanQosProfileMatchInMacSrcAddr OBJECT-TYPE
			SYNTAX MacAddress
			MAX-ACCESS read-write
			STATUS current
			DESCRIPTION
				"Match incoming packet frame with specified source MAC address.
				Empty string indicates that parameter has not been defined"
			DEFVAL { ''b }
			::= { msanQosProfileEntry 5 }

		
		-- 1.3.6.1.4.1.1332.1.1.5.3.12.7.1.6
		msanQosProfileMatchInMacSrcMask OBJECT-TYPE
			SYNTAX MacAddress
			MAX-ACCESS read-write
			STATUS current
			DESCRIPTION
				"This mask value identifies the portion of msanQosProfileMatchInMacSrcAddr that 
				is compared with input packet.
				Empty string indicates that parameter has not been defined"
			DEFVAL { ''b }
			::= { msanQosProfileEntry 6 }

		
		-- 1.3.6.1.4.1.1332.1.1.5.3.12.7.1.7
		msanQosProfileMatchInCos OBJECT-TYPE
			SYNTAX Integer32 (-1..7)
			MAX-ACCESS read-write
			STATUS current
			DESCRIPTION
				"Match incoming packet frame with specified CoS value (0-7).
				A value of -1 indicates that parameter has not been defined"
			DEFVAL { -1 }
			::= { msanQosProfileEntry 7 }

		
		-- 1.3.6.1.4.1.1332.1.1.5.3.12.7.1.8
		msanQosProfileMatchInCos2 OBJECT-TYPE
			SYNTAX Integer32 (-1..7)
			MAX-ACCESS read-write
			STATUS current
			DESCRIPTION
				"Match incoming packet frame with specified secondary (C-TAG) CoS value (0-7).
				A value of -1 indicates that parameter has not been defined"
			DEFVAL { -1 }
			::= { msanQosProfileEntry 8 }

		
		-- 1.3.6.1.4.1.1332.1.1.5.3.12.7.1.9
		msanQosProfileMatchInVlanId OBJECT-TYPE
			SYNTAX Integer32 (-1..4094)
			MAX-ACCESS read-write
			STATUS current
			DESCRIPTION
				"Match incoming packet frame with specified VLAN ID value (1-4094).
				A value of -1 indicates that parameter has not been defined"
			DEFVAL { -1 }
			::= { msanQosProfileEntry 9 }

		
		-- 1.3.6.1.4.1.1332.1.1.5.3.12.7.1.10
		msanQosProfileMatchInVlanId2 OBJECT-TYPE
			SYNTAX Integer32 (-1..4094)
			MAX-ACCESS read-write
			STATUS current
			DESCRIPTION
				"Match incoming packet frame with specified secondary (C-TAG) VLAN ID value (1-4094).
				A value of -1 indicates that parameter has not been defined"
			DEFVAL { -1 }
			::= { msanQosProfileEntry 10 }

		
		-- 1.3.6.1.4.1.1332.1.1.5.3.12.7.1.11
		msanQosProfileMatchInEthertype OBJECT-TYPE
			SYNTAX Integer32 (-1..65535)
			MAX-ACCESS read-write
			STATUS current
			DESCRIPTION
				"Match incoming packet frame with specified EtherType value.
				A value of -1 indicates that parameter has not been defined."
			DEFVAL { -1 }
			::= { msanQosProfileEntry 11 }

		
		-- 1.3.6.1.4.1.1332.1.1.5.3.12.7.1.12
		msanQosProfileMatchInIpProtocol OBJECT-TYPE
			SYNTAX Integer32 (-1..255)
			MAX-ACCESS read-write
			STATUS current
			DESCRIPTION
				"Match incoming packet frame with specified IP protocol value.
				A value of -1 indicates that parameter has not been defined.
				Some of standard protocol values:
				   icmp - 1
				   igmp - 2
				   ip - 4 (ip in ip encapsulation)
				   tcp - 6
				   udp - 17"
			DEFVAL { -1 }
			::= { msanQosProfileEntry 12 }

		
		-- 1.3.6.1.4.1.1332.1.1.5.3.12.7.1.13
		msanQosProfileMatchInIpSrcAddr OBJECT-TYPE
			SYNTAX IpAddress
			MAX-ACCESS read-write
			STATUS current
			DESCRIPTION
				"Match incoming packet frame with specified source IP address.
				Empty string indicates that parameter has not been defined."
			DEFVAL { ''h }
			::= { msanQosProfileEntry 13 }

		
		-- 1.3.6.1.4.1.1332.1.1.5.3.12.7.1.14
		msanQosProfileMatchInIpSrcMask OBJECT-TYPE
			SYNTAX IpAddress
			MAX-ACCESS read-write
			STATUS current
			DESCRIPTION
				"This mask value identifies the portion of msanQosProfileMatchInIpSrcAddr that 
				is compared with input packet.
				Empty string indicates that parameter has not been defined"
			DEFVAL { ''h }
			::= { msanQosProfileEntry 14 }

		
		-- 1.3.6.1.4.1.1332.1.1.5.3.12.7.1.15
		msanQosProfileMatchInIpDestAddr OBJECT-TYPE
			SYNTAX IpAddress
			MAX-ACCESS read-write
			STATUS current
			DESCRIPTION
				"Match incoming packet frame with specified destination IP address.
				Empty string indicates that parameter has not been defined."
			DEFVAL { ''h }
			::= { msanQosProfileEntry 15 }

		
		-- 1.3.6.1.4.1.1332.1.1.5.3.12.7.1.16
		msanQosProfileMatchInIpDestMask OBJECT-TYPE
			SYNTAX IpAddress
			MAX-ACCESS read-write
			STATUS current
			DESCRIPTION
				"This mask value identifies the portion of msanQosProfileMatchInIpDestAddr that 
				is compared with input packet.
				Empty string indicates that parameter has not been defined"
			DEFVAL { ''h }
			::= { msanQosProfileEntry 16 }

		
		-- 1.3.6.1.4.1.1332.1.1.5.3.12.7.1.17
		msanQosProfileMatchInIpDscp OBJECT-TYPE
			SYNTAX Integer32 (-1..63)
			MAX-ACCESS read-write
			STATUS current
			DESCRIPTION
				"Match incoming packet frame with specified IP DSCP value.
				A value of -1 indicates that parameter has not been defined."
			DEFVAL { -1 }
			::= { msanQosProfileEntry 17 }

		
		-- 1.3.6.1.4.1.1332.1.1.5.3.12.7.1.18
		msanQosProfileMatchInIpPrecedence OBJECT-TYPE
			SYNTAX Integer32 (-1..7)
			MAX-ACCESS read-write
			STATUS current
			DESCRIPTION
				"Match incoming packet frame with specified IP precedence (part of TOS field) value.
				A value of -1 indicates that parameter has not been defined."
			DEFVAL { -1 }
			::= { msanQosProfileEntry 18 }

		
		-- 1.3.6.1.4.1.1332.1.1.5.3.12.7.1.19
		msanQosProfileMatchInIpTosBits OBJECT-TYPE
			SYNTAX OCTET STRING (SIZE (0..1))
			MAX-ACCESS read-write
			STATUS current
			DESCRIPTION
				"Match incoming packet frame with specified IP TOS bits value.
				Empty string indicates that parameter has not been defined."
			DEFVAL { ''b }
			::= { msanQosProfileEntry 19 }

		
		-- 1.3.6.1.4.1.1332.1.1.5.3.12.7.1.20
		msanQosProfileMatchInIpTosMask OBJECT-TYPE
			SYNTAX OCTET STRING (SIZE (0..1))
			MAX-ACCESS read-write
			STATUS current
			DESCRIPTION
				"This mask value identifies the portion of msanQosProfileMatchInIpTosBits that 
				is compared against a packet. 
				Empty string indicates that parameter has not been defined."
			DEFVAL { ''b }
			::= { msanQosProfileEntry 20 }

		
		-- 1.3.6.1.4.1.1332.1.1.5.3.12.7.1.21
		msanQosProfileMatchInL4SrcPort OBJECT-TYPE
			SYNTAX Integer32 (-1..65535)
			MAX-ACCESS read-write
			STATUS current
			DESCRIPTION
				"Match incoming packet frame with specified source TCP/UDP port number.
				A value of -1 indicates that parameter has not been defined."
			DEFVAL { -1 }
			::= { msanQosProfileEntry 21 }

		
		-- 1.3.6.1.4.1.1332.1.1.5.3.12.7.1.22
		msanQosProfileMatchInL4DestPort OBJECT-TYPE
			SYNTAX Integer32 (-1..65535)
			MAX-ACCESS read-write
			STATUS current
			DESCRIPTION
				"Match incoming packet frame with specified destination TCP/UDP port number in downstream direction.
				A value of -1 indicates that parameter has not been defined."
			DEFVAL { -1 }
			::= { msanQosProfileEntry 22 }

		
		-- 1.3.6.1.4.1.1332.1.1.5.3.12.7.1.23
		msanQosProfileMatchOutAny OBJECT-TYPE
			SYNTAX INTEGER
				{
				enable(1),
				disable(2)
				}
			MAX-ACCESS read-write
			STATUS current
			DESCRIPTION
				"Match every outgoing packet frame in upstream direction."
			DEFVAL { disable }
			::= { msanQosProfileEntry 23 }

		
		-- 1.3.6.1.4.1.1332.1.1.5.3.12.7.1.24
		msanQosProfileMatchOutMacDestAddr OBJECT-TYPE
			SYNTAX MacAddress
			MAX-ACCESS read-write
			STATUS current
			DESCRIPTION
				"Match outgoing packet frame with specified destination MAC address.
				Empty string indicates that parameter has not been defined"
			DEFVAL { ''b }
			::= { msanQosProfileEntry 24 }

		
		-- 1.3.6.1.4.1.1332.1.1.5.3.12.7.1.25
		msanQosProfileMatchOutMacDestMask OBJECT-TYPE
			SYNTAX MacAddress
			MAX-ACCESS read-write
			STATUS current
			DESCRIPTION
				"This mask value identifies the portion of msanQosProfileMatchOutMacDestAddr that 
				is compared with output packet.
				Empty string indicates that parameter has not been defined"
			DEFVAL { ''b }
			::= { msanQosProfileEntry 25 }

		
		-- 1.3.6.1.4.1.1332.1.1.5.3.12.7.1.26
		msanQosProfileMatchOutMacSrcAddr OBJECT-TYPE
			SYNTAX MacAddress
			MAX-ACCESS read-write
			STATUS current
			DESCRIPTION
				"Match outgoing packet frame with specified source MAC address.
				Empty string indicates that parameter has not been defined"
			DEFVAL { ''b }
			::= { msanQosProfileEntry 26 }

		
		-- 1.3.6.1.4.1.1332.1.1.5.3.12.7.1.27
		msanQosProfileMatchOutMacSrcMask OBJECT-TYPE
			SYNTAX MacAddress
			MAX-ACCESS read-write
			STATUS current
			DESCRIPTION
				"This mask value identifies the portion of msanQosProfileMatchOutMacSrcAddr that 
				is compared with output packet.
				Empty string indicates that parameter has not been defined"
			DEFVAL { ''b }
			::= { msanQosProfileEntry 27 }

		
		-- 1.3.6.1.4.1.1332.1.1.5.3.12.7.1.28
		msanQosProfileMatchOutCos OBJECT-TYPE
			SYNTAX Integer32 (-1..7)
			MAX-ACCESS read-write
			STATUS current
			DESCRIPTION
				"Match outgoing packet frame with specified CoS value (0-7).
				A value of -1 indicates that parameter has not been defined"
			DEFVAL { -1 }
			::= { msanQosProfileEntry 28 }

		
		-- 1.3.6.1.4.1.1332.1.1.5.3.12.7.1.29
		msanQosProfileMatchOutCos2 OBJECT-TYPE
			SYNTAX Integer32 (-1..7)
			MAX-ACCESS read-write
			STATUS current
			DESCRIPTION
				"Match outgoing packet frame with specified secondary (C-TAG) CoS value (0-7).
				A value of -1 indicates that parameter has not been defined"
			DEFVAL { -1 }
			::= { msanQosProfileEntry 29 }

		
		-- 1.3.6.1.4.1.1332.1.1.5.3.12.7.1.30
		msanQosProfileMatchOutVlanId OBJECT-TYPE
			SYNTAX Integer32 (-1..4094)
			MAX-ACCESS read-write
			STATUS current
			DESCRIPTION
				"Match outgoing packet frame with specified VLAN ID value (1-4094).
				A value of -1 indicates that parameter has not been defined"
			DEFVAL { -1 }
			::= { msanQosProfileEntry 30 }

		
		-- 1.3.6.1.4.1.1332.1.1.5.3.12.7.1.31
		msanQosProfileMatchOutVlanId2 OBJECT-TYPE
			SYNTAX Integer32 (-1..4094)
			MAX-ACCESS read-write
			STATUS current
			DESCRIPTION
				"Match outgoing packet frame with specified secondary (C-TAG) VLAN ID value (1-4094).
				A value of -1 indicates that parameter has not been defined"
			DEFVAL { -1 }
			::= { msanQosProfileEntry 31 }

		
		-- 1.3.6.1.4.1.1332.1.1.5.3.12.7.1.32
		msanQosProfileMatchOutEthertype OBJECT-TYPE
			SYNTAX Integer32 (-1..65535)
			MAX-ACCESS read-write
			STATUS current
			DESCRIPTION
				"Match outgoing packet frame with specified EtherType value.
				A value of -1 indicates that parameter has not been defined."
			DEFVAL { -1 }
			::= { msanQosProfileEntry 32 }

		
		-- 1.3.6.1.4.1.1332.1.1.5.3.12.7.1.33
		msanQosProfileMatchOutIpProtocol OBJECT-TYPE
			SYNTAX Integer32 (-1..255)
			MAX-ACCESS read-write
			STATUS current
			DESCRIPTION
				"Match outgoing packet frame with specified IP protocol value in upstream direction.
				A value of -1 indicates that parameter has not been defined.
				Some of standard protocol values:
				   icmp - 1
				   igmp - 2
				   ip - 4 (ip in ip encapsulation)
				   tcp - 6
				   udp - 17"
			DEFVAL { -1 }
			::= { msanQosProfileEntry 33 }

		
		-- 1.3.6.1.4.1.1332.1.1.5.3.12.7.1.34
		msanQosProfileMatchOutIpSrcAddr OBJECT-TYPE
			SYNTAX IpAddress
			MAX-ACCESS read-write
			STATUS current
			DESCRIPTION
				"Match outgoing packet frame with specified source IP address.
				Empty string indicates that parameter has not been defined."
			DEFVAL { ''h }
			::= { msanQosProfileEntry 34 }

		
		-- 1.3.6.1.4.1.1332.1.1.5.3.12.7.1.35
		msanQosProfileMatchOutIpSrcMask OBJECT-TYPE
			SYNTAX IpAddress
			MAX-ACCESS read-write
			STATUS current
			DESCRIPTION
				"This mask value identifies the portion of msanQosProfileMatchOutIpSrcAddr that 
				is compared with output packet.
				Empty string indicates that parameter has not been defined"
			DEFVAL { ''h }
			::= { msanQosProfileEntry 35 }

		
		-- 1.3.6.1.4.1.1332.1.1.5.3.12.7.1.36
		msanQosProfileMatchOutIpDestAddr OBJECT-TYPE
			SYNTAX IpAddress
			MAX-ACCESS read-write
			STATUS current
			DESCRIPTION
				"Match outgoing packet frame with specified destination IP address.
				Empty string indicates that parameter has not been defined."
			DEFVAL { ''h }
			::= { msanQosProfileEntry 36 }

		
		-- 1.3.6.1.4.1.1332.1.1.5.3.12.7.1.37
		msanQosProfileMatchOutIpDestMask OBJECT-TYPE
			SYNTAX IpAddress
			MAX-ACCESS read-write
			STATUS current
			DESCRIPTION
				"This mask value identifies the portion of msanQosProfileMatchOutIpDestAddr that 
				is compared with output packet.
				Empty string indicates that parameter has not been defined"
			DEFVAL { ''h }
			::= { msanQosProfileEntry 37 }

		
		-- 1.3.6.1.4.1.1332.1.1.5.3.12.7.1.38
		msanQosProfileMatchOutIpDscp OBJECT-TYPE
			SYNTAX Integer32 (-1..63)
			MAX-ACCESS read-write
			STATUS current
			DESCRIPTION
				"Match outgoing packet frame with specified IP DSCP value.
				A value of -1 indicates that parameter has not been defined."
			DEFVAL { -1 }
			::= { msanQosProfileEntry 38 }

		
		-- 1.3.6.1.4.1.1332.1.1.5.3.12.7.1.39
		msanQosProfileMatchOutIpPrecedence OBJECT-TYPE
			SYNTAX Integer32 (-1..7)
			MAX-ACCESS read-write
			STATUS current
			DESCRIPTION
				"Match outgoing packet frame with specified IP precedence (part of TOS field) value.
				A value of -1 indicates that parameter has not been defined."
			DEFVAL { -1 }
			::= { msanQosProfileEntry 39 }

		
		-- 1.3.6.1.4.1.1332.1.1.5.3.12.7.1.40
		msanQosProfileMatchOutIpTosBits OBJECT-TYPE
			SYNTAX OCTET STRING (SIZE (0..1))
			MAX-ACCESS read-write
			STATUS current
			DESCRIPTION
				"Match outgoing packet frame with specified IP TOS bits value.
				Empty string indicates that parameter has not been defined."
			DEFVAL { ''b }
			::= { msanQosProfileEntry 40 }

		
		-- 1.3.6.1.4.1.1332.1.1.5.3.12.7.1.41
		msanQosProfileMatchOutIpTosMask OBJECT-TYPE
			SYNTAX OCTET STRING (SIZE (0..1))
			MAX-ACCESS read-write
			STATUS current
			DESCRIPTION
				"This mask value identifies the portion of msanQosProfileMatchOutIpTosBits that 
				is compared with output packet.
				Empty string indicates that parameter has not been defined"
			DEFVAL { ''b }
			::= { msanQosProfileEntry 41 }

		
		-- 1.3.6.1.4.1.1332.1.1.5.3.12.7.1.42
		msanQosProfileMatchOutL4SrcPort OBJECT-TYPE
			SYNTAX Integer32 (-1..65535)
			MAX-ACCESS read-write
			STATUS current
			DESCRIPTION
				"Match outgoing packet frame with specified source TCP/UDP port number in upstream direction.
				A value of -1 indicates that parameter has not been defined."
			DEFVAL { -1 }
			::= { msanQosProfileEntry 42 }

		
		-- 1.3.6.1.4.1.1332.1.1.5.3.12.7.1.43
		msanQosProfileMatchOutL4DestPort OBJECT-TYPE
			SYNTAX Integer32 (-1..65535)
			MAX-ACCESS read-write
			STATUS current
			DESCRIPTION
				"Match outgoing packet frame with specified destination TCP/UDP port number.
				A value of -1 indicates that parameter has not been defined."
			DEFVAL { -1 }
			::= { msanQosProfileEntry 43 }

		
		-- 1.3.6.1.4.1.1332.1.1.5.3.12.7.1.44
		msanQosProfileInCdr OBJECT-TYPE
			SYNTAX Integer32 (-1..1000000)
			UNITS "kbps"
			MAX-ACCESS read-write
			STATUS current
			DESCRIPTION
				"Incoming committed data rate (E-CDR) in kbps (0 – 1000000).
				A value of -1 indicates that parameter has not been defined."
			DEFVAL { 0 }
			::= { msanQosProfileEntry 44 }

		
		-- 1.3.6.1.4.1.1332.1.1.5.3.12.7.1.45
		msanQosProfileInPdr OBJECT-TYPE
			SYNTAX Integer32 (-1..1000000)
			UNITS "kbps"
			MAX-ACCESS read-write
			STATUS current
			DESCRIPTION
				"Incoming peak data rate (E-PDR) in kbps (0 – 1000000).
				A value of -1 indicates that parameter has not been defined."
			DEFVAL { 0 }
			::= { msanQosProfileEntry 45 }

		
		-- 1.3.6.1.4.1.1332.1.1.5.3.12.7.1.46
		msanQosProfileOutCdr OBJECT-TYPE
			SYNTAX Integer32 (-1..1000000)
			UNITS "kbps"
			MAX-ACCESS read-write
			STATUS current
			DESCRIPTION
				"Outgoing committed data rate (E-CDR) in kbps (0 – 1000000).
				A value of -1 indicates that parameter has not been defined."
			DEFVAL { 0 }
			::= { msanQosProfileEntry 46 }

		
		-- 1.3.6.1.4.1.1332.1.1.5.3.12.7.1.47
		msanQosProfileOutPdr OBJECT-TYPE
			SYNTAX Integer32 (-1..1000000)
			UNITS "kbps"
			MAX-ACCESS read-write
			STATUS current
			DESCRIPTION
				"Outgoing peak data rate (E-PDR) in kbps (0 – 1000000).
				A value of -1 indicates that parameter has not been defined."
			DEFVAL { 0 }
			::= { msanQosProfileEntry 47 }

		
		-- 1.3.6.1.4.1.1332.1.1.5.3.12.7.1.48
		msanQosProfileInTrustMode OBJECT-TYPE
			SYNTAX INTEGER
				{
				untrusted(1),
				trustCos(2),
				trustDscp(3),
				untrustMarkCos(4),
				untrustMarkDscp(5)
				}
			MAX-ACCESS read-write
			STATUS current
			DESCRIPTION
				"Trust mode for incoming packets which correspond to this profile.
				Default value is untrusted(1).
				
				Value untrustMarkCos(4) can be set if parameter msanQosProfileInMarkCos value
				is grater than -1.
				Value untrustMarkCos(5) can be set if parameter msanQosProfileInMarkDscp value
				is grater than -1."
			DEFVAL { untrusted }
			::= { msanQosProfileEntry 48 }

		
		-- 1.3.6.1.4.1.1332.1.1.5.3.12.7.1.49
		msanQosProfileInMarkCos OBJECT-TYPE
			SYNTAX INTEGER (-1..7)
			MAX-ACCESS read-write
			STATUS current
			DESCRIPTION
				"Mark incoming packets with specified CoS value (0-7).
				A value of -1 indicates that parameter has not been defined"
			DEFVAL { -1 }
			::= { msanQosProfileEntry 49 }

		
		-- 1.3.6.1.4.1.1332.1.1.5.3.12.7.1.50
		msanQosProfileInMarkDscp OBJECT-TYPE
			SYNTAX INTEGER (-1..63)
			MAX-ACCESS read-write
			STATUS current
			DESCRIPTION
				"Mark incoming packets with specified IP DSCP value.
				A value of -1 indicates that parameter has not been defined."
			DEFVAL { -1 }
			::= { msanQosProfileEntry 50 }

		
		-- 1.3.6.1.4.1.1332.1.1.5.3.12.7.1.51
		msanQosProfileRowStatus OBJECT-TYPE
			SYNTAX RowStatus
			MAX-ACCESS read-create
			STATUS current
			DESCRIPTION
				"The row status object controls the creation/deletion of rows in this table. 
				Its semantics are the same as those for the RowStatus textual convention specified for SNMPv2.
				For row creation use createAndWait(5).
				Value active(1) will activate and value destroy(6) will remove this entry.
				Other values are currently not supported.
				"
			::= { msanQosProfileEntry 51 }

		
		-- 1.3.6.1.4.1.1332.1.1.5.3.12.7.1.52
		msanQosProfilePriority OBJECT-TYPE
			SYNTAX INTEGER
				{
				normal(1),
				high(2)
				}
			MAX-ACCESS read-write
			STATUS current
			DESCRIPTION
				"Priority of QoS profile. 
				On interface can be linked only one QoS profile 
				with high(2) prority (msanQoSIntProfileTable)"
			DEFVAL { normal }
			::= { msanQosProfileEntry 52 }

		
		-- 1.3.6.1.4.1.1332.1.1.5.3.12.7.1.53
		msanQosProfileInCdrBurstSize OBJECT-TYPE
			SYNTAX Integer32
			UNITS "kB"
			MAX-ACCESS read-write
			STATUS current
			DESCRIPTION
				"Incoming committed data rate burst size in kB (0 – 16384).
				
				When parameter is set to 0 (default), it's automatically updated to default 
				burst size in according with current msanQoSProfileInCdr value.
				
				"
			::= { msanQosProfileEntry 53 }

		
		-- 1.3.6.1.4.1.1332.1.1.5.3.12.7.1.54
		msanQosProfileInPdrBurstSize OBJECT-TYPE
			SYNTAX Integer32
			UNITS "kB"
			MAX-ACCESS read-write
			STATUS current
			DESCRIPTION
				"Incoming peak data rate burst size in kB (0 – 16384).
				
				When parameter is set to 0 (default), it's automatically updated to default 
				burst size in according with current msanQoSProfileInPdr value.
				"
			::= { msanQosProfileEntry 54 }

		
		-- 1.3.6.1.4.1.1332.1.1.5.3.12.7.1.55
		msanQosProfileOutCdrBurstSize OBJECT-TYPE
			SYNTAX Integer32
			UNITS "kB"
			MAX-ACCESS read-write
			STATUS current
			DESCRIPTION
				"Outgoing committed data rate burst size in kB (0 – 16384).
				
				When parameter is set to 0 (default), it's automatically updated to default 
				burst size in according with current msanQoSProfileOutCdr value.
				
				"
			::= { msanQosProfileEntry 55 }

		
		-- 1.3.6.1.4.1.1332.1.1.5.3.12.7.1.56
		msanQosProfileOutPdrBurstSize OBJECT-TYPE
			SYNTAX Integer32
			UNITS "kB"
			MAX-ACCESS read-write
			STATUS current
			DESCRIPTION
				"Outgoing peak data rate burst size in kB (0 – 16384).
				
				
				When parameter is set to 0 (default), it's automatically updated to default 
				burst size in according with current msanQoSProfileOutCdr value.
				"
			DEFVAL { 64 }
			::= { msanQosProfileEntry 56 }

		
		-- 1.3.6.1.4.1.1332.1.1.5.3.12.7.1.58
		msanQosProfileMatchInSrcIpv6Address OBJECT-TYPE
			SYNTAX InetAddressIPv6
			MAX-ACCESS read-write
			STATUS current
			DESCRIPTION
				"Match incoming packet frame with specified source IPv6 address.
				
				Empty string indicates that parameter has not been defined."
			::= { msanQosProfileEntry 58 }

		
		-- 1.3.6.1.4.1.1332.1.1.5.3.12.7.1.59
		msanQosProfileMatchInSrcIpv6AddressMaskLen OBJECT-TYPE
			SYNTAX Integer32 (0..128)
			MAX-ACCESS read-write
			STATUS current
			DESCRIPTION
				"The length of the prefix (in bits) associated with the
				incoming IPv6 source address of this entry (msanQosProfileMatchInSrcIpv6Address).
				
				Value 0 indicates that parameter has not been defined."
			DEFVAL { 0 }
			::= { msanQosProfileEntry 59 }

		
		-- 1.3.6.1.4.1.1332.1.1.5.3.12.7.1.60
		msanQosProfileMatchInDestIpv6Address OBJECT-TYPE
			SYNTAX InetAddressIPv6
			MAX-ACCESS read-write
			STATUS current
			DESCRIPTION
				"Match incoming packet frame with specified destination IPv6 address.
				
				Empty string indicates that parameter has not been defined."
			::= { msanQosProfileEntry 60 }

		
		-- 1.3.6.1.4.1.1332.1.1.5.3.12.7.1.61
		msanQosProfileMatchInDestIpv6AddressMaskLen OBJECT-TYPE
			SYNTAX Integer32 (0..128)
			MAX-ACCESS read-write
			STATUS current
			DESCRIPTION
				"The length of the prefix (in bits) associated with the
				incoming IPv6 destination address of this entry (msanQosProfileMatchInDestIpv6Address).
				
				Value 0 indicates that parameter has not been defined."
			DEFVAL { 0 }
			::= { msanQosProfileEntry 61 }

		
		-- 1.3.6.1.4.1.1332.1.1.5.3.12.7.1.63
		msanQosProfileMatchOutSrcIpv6Address OBJECT-TYPE
			SYNTAX InetAddressIPv6
			MAX-ACCESS read-write
			STATUS current
			DESCRIPTION
				"Match outgoing packet frame with specified source IPv6 address.
				
				Empty string indicates that parameter has not been defined."
			::= { msanQosProfileEntry 63 }

		
		-- 1.3.6.1.4.1.1332.1.1.5.3.12.7.1.64
		msanQosProfileMatchOutSrcIpv6AddressMaskLen OBJECT-TYPE
			SYNTAX Integer32 (0..128)
			MAX-ACCESS read-write
			STATUS current
			DESCRIPTION
				"The length of the prefix (in bits) associated with the
				outcoming IPv6 source address of this entry (msanQosProfileMatchOutSrcIpv6Address).
				
				Value 0 indicates that parameter has not been defined."
			DEFVAL { 0 }
			::= { msanQosProfileEntry 64 }

		
		-- 1.3.6.1.4.1.1332.1.1.5.3.12.7.1.65
		msanQosProfileMatchOutDestIpv6Address OBJECT-TYPE
			SYNTAX InetAddressIPv6
			MAX-ACCESS read-write
			STATUS current
			DESCRIPTION
				"Match outcoming packet frame with specified destination IPv6 address.
				
				Empty string indicates that parameter has not been defined."
			::= { msanQosProfileEntry 65 }

		
		-- 1.3.6.1.4.1.1332.1.1.5.3.12.7.1.66
		msanQosProfileMatchOutDestIpv6AddressMaskLen OBJECT-TYPE
			SYNTAX Integer32 (0..128)
			MAX-ACCESS read-write
			STATUS current
			DESCRIPTION
				"The length of the prefix (in bits) associated with the
				outcoming IPv6 destination address of this entry (msanQosProfileMatchOutDestIpv6Address).
				
				Value 0 indicates that parameter has not been defined."
			DEFVAL { 0 }
			::= { msanQosProfileEntry 66 }

		
		-- 1.3.6.1.4.1.1332.1.1.5.3.12.8
		msanQosIntfProfileTable OBJECT-TYPE
			SYNTAX SEQUENCE OF MsanQosIntfProfileEntry
			MAX-ACCESS not-accessible
			STATUS current
			DESCRIPTION
				"This table connects selected QoS profiles (msanQoSProfileName) to specified interfaces (ifIndex)."
			::= { msanQoS 8 }

		
		-- 1.3.6.1.4.1.1332.1.1.5.3.12.8.1
		msanQosIntfProfileEntry OBJECT-TYPE
			SYNTAX MsanQosIntfProfileEntry
			MAX-ACCESS not-accessible
			STATUS current
			DESCRIPTION
				"Description."
			INDEX { ifIndex, msanQosProfileName }
			::= { msanQosIntfProfileTable 1 }

		
		MsanQosIntfProfileEntry ::=
			SEQUENCE { 
				msanQosIntfProfileAtmVpi
					Integer32,
				msanQosIntfProfileAtmVci
					Integer32,
				msanQosIntfProfileRowStatus
					RowStatus
			 }

		-- 1.3.6.1.4.1.1332.1.1.5.3.12.8.1.1
		msanQosIntfProfileAtmVpi OBJECT-TYPE
			SYNTAX Integer32 (-1..65535)
			MAX-ACCESS read-write
			STATUS current
			DESCRIPTION
				"ATM Virtual path identifier of the ADSL interface.
				Value -1 indicates that parameter has not been defined."
			DEFVAL { -1 }
			::= { msanQosIntfProfileEntry 1 }

		
		-- 1.3.6.1.4.1.1332.1.1.5.3.12.8.1.2
		msanQosIntfProfileAtmVci OBJECT-TYPE
			SYNTAX Integer32 (-1..65535)
			MAX-ACCESS read-write
			STATUS current
			DESCRIPTION
				"ATM Virtual channel identifier of the ADSL interface.
				Value -1 indicates that parameter has not been defined."
			DEFVAL { -1 }
			::= { msanQosIntfProfileEntry 2 }

		
		-- 1.3.6.1.4.1.1332.1.1.5.3.12.8.1.3
		msanQosIntfProfileRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndWait(5).
				For row activation use active(1).
				For row deactivation use notInService(2).
				For row deletion use destroy(6).
				
				Other values are currently not supported.
				
				On interface can be linked only one QoS profile with high(2) prority (msanQosProfilePriority)"
			::= { msanQosIntfProfileEntry 3 }

		
		-- 1.3.6.1.4.1.1332.1.1.5.3.12.9
		msanQosStatistics OBJECT IDENTIFIER ::= { msanQoS 9 }

		
		-- 1.3.6.1.4.1.1332.1.1.5.3.12.9.1
		msanQosPortStatTable OBJECT-TYPE
			SYNTAX SEQUENCE OF MsanQosPortStatEntry
			MAX-ACCESS not-accessible
			STATUS current
			DESCRIPTION
				"Description."
			::= { msanQosStatistics 1 }

		
		-- 1.3.6.1.4.1.1332.1.1.5.3.12.9.1.1
		msanQosPortStatEntry OBJECT-TYPE
			SYNTAX MsanQosPortStatEntry
			MAX-ACCESS not-accessible
			STATUS current
			DESCRIPTION
				"Description."
			INDEX { ifIndex }
			::= { msanQosPortStatTable 1 }

		
		MsanQosPortStatEntry ::=
			SEQUENCE { 
				msanQosPortStatInDroppedFrames
					Counter32,
				msanQosPortStatOutDroppedFrames
					Counter32
			 }

		-- 1.3.6.1.4.1.1332.1.1.5.3.12.9.1.1.1
		msanQosPortStatInDroppedFrames OBJECT-TYPE
			SYNTAX Counter32
			MAX-ACCESS read-only
			STATUS current
			DESCRIPTION
				"Number of dropped frames per port in incoming direction."
			::= { msanQosPortStatEntry 1 }

		
		-- 1.3.6.1.4.1.1332.1.1.5.3.12.9.1.1.2
		msanQosPortStatOutDroppedFrames OBJECT-TYPE
			SYNTAX Counter32
			MAX-ACCESS read-only
			STATUS current
			DESCRIPTION
				"Number of dropped frames per port in outgoing direction."
			::= { msanQosPortStatEntry 2 }

		
		-- 1.3.6.1.4.1.1332.1.1.5.3.12.9.2
		msanQosPortProfileStatTable OBJECT-TYPE
			SYNTAX SEQUENCE OF MsanQosPortProfileStatEntry
			MAX-ACCESS not-accessible
			STATUS current
			DESCRIPTION
				"Description."
			::= { msanQosStatistics 2 }

		
		-- 1.3.6.1.4.1.1332.1.1.5.3.12.9.2.1
		msanQosPortProfileStatEntry OBJECT-TYPE
			SYNTAX MsanQosPortProfileStatEntry
			MAX-ACCESS not-accessible
			STATUS current
			DESCRIPTION
				"Description."
			INDEX { ifIndex, msanQosProfileName }
			::= { msanQosPortProfileStatTable 1 }

		
		MsanQosPortProfileStatEntry ::=
			SEQUENCE { 
				msanQosPortProfileStatQueueCurrent
					Integer32,
				msanQosPortProfileStatQueueAverage
					Integer32,
				msanQosPortProfileStatQueueMax
					Integer32
			 }

		-- 1.3.6.1.4.1.1332.1.1.5.3.12.9.2.1.1
		msanQosPortProfileStatQueueCurrent OBJECT-TYPE
			SYNTAX Integer32
			MAX-ACCESS read-only
			STATUS current
			DESCRIPTION
				"Current queue occupation per profile per port (in number of packets) ."
			::= { msanQosPortProfileStatEntry 1 }

		
		-- 1.3.6.1.4.1.1332.1.1.5.3.12.9.2.1.2
		msanQosPortProfileStatQueueAverage OBJECT-TYPE
			SYNTAX Integer32
			MAX-ACCESS read-only
			STATUS current
			DESCRIPTION
				"Average queue occupation per profile per port (in number of packets) ."
			::= { msanQosPortProfileStatEntry 2 }

		
		-- 1.3.6.1.4.1.1332.1.1.5.3.12.9.2.1.3
		msanQosPortProfileStatQueueMax OBJECT-TYPE
			SYNTAX Integer32
			MAX-ACCESS read-only
			STATUS current
			DESCRIPTION
				"Maximum queue occupation per profile per port (in number of packets) ."
			::= { msanQosPortProfileStatEntry 3 }

		
		-- 1.3.6.1.4.1.1332.1.1.5.3.12.10
		msanIpAclTable OBJECT-TYPE
			SYNTAX SEQUENCE OF MsanIpAclEntry
			MAX-ACCESS not-accessible
			STATUS current
			DESCRIPTION
				"Description."
			::= { msanQoS 10 }

		
		-- 1.3.6.1.4.1.1332.1.1.5.3.12.10.1
		msanIpAclEntry OBJECT-TYPE
			SYNTAX MsanIpAclEntry
			MAX-ACCESS not-accessible
			STATUS current
			DESCRIPTION
				"Description."
			INDEX { msanIpAclId }
			::= { msanIpAclTable 1 }

		
		MsanIpAclEntry ::=
			SEQUENCE { 
				msanIpAclId
					Integer32,
				msanIpAclProtection
					INTEGER,
				msanIpAclStatus
					INTEGER
			 }

		-- 1.3.6.1.4.1.1332.1.1.5.3.12.10.1.1
		msanIpAclId OBJECT-TYPE
			SYNTAX Integer32 (1..199)
			MAX-ACCESS not-accessible
			STATUS current
			DESCRIPTION
				"This is aclIndex in aclTable (1.3.6.1.4.1.1332.1.1.5.2.3.2.1)"
			::= { msanIpAclEntry 1 }

		
		-- 1.3.6.1.4.1.1332.1.1.5.3.12.10.1.2
		msanIpAclProtection OBJECT-TYPE
			SYNTAX INTEGER
				{
				unprotected(0),
				protected(1)
				}
			MAX-ACCESS read-write
			STATUS current
			DESCRIPTION
				"If protection flag is set to protected (1), other profile values cannot be edited.
				
				Protection flag is always  protected (1) and it can't be changed if  profile is assigned as dynamic:
				msanAclProfileStatus = dynamic(2)"
			DEFVAL { unprotected }
			::= { msanIpAclEntry 2 }

		
		-- 1.3.6.1.4.1.1332.1.1.5.3.12.10.1.4
		msanIpAclStatus OBJECT-TYPE
			SYNTAX INTEGER
				{
				static(1),
				dynamic(2)
				}
			MAX-ACCESS read-only
			STATUS current
			DESCRIPTION
				"Profile status. 
				If status is dynamic, profile values can't be edited."
			::= { msanIpAclEntry 4 }

		
		-- 1.3.6.1.4.1.1332.1.1.5.3.12.11
		msanMacAclTable OBJECT-TYPE
			SYNTAX SEQUENCE OF MsanMacAclEntry
			MAX-ACCESS not-accessible
			STATUS current
			DESCRIPTION
				"Description."
			::= { msanQoS 11 }

		
		-- 1.3.6.1.4.1.1332.1.1.5.3.12.11.1
		msanMacAclEntry OBJECT-TYPE
			SYNTAX MsanMacAclEntry
			MAX-ACCESS not-accessible
			STATUS current
			DESCRIPTION
				"Description."
			INDEX { msanMacAclId }
			::= { msanMacAclTable 1 }

		
		MsanMacAclEntry ::=
			SEQUENCE { 
				msanMacAclId
					Integer32,
				msanMacAclProtection
					INTEGER,
				msanMacAclStatus
					INTEGER
			 }

		-- 1.3.6.1.4.1.1332.1.1.5.3.12.11.1.1
		msanMacAclId OBJECT-TYPE
			SYNTAX Integer32 (1..199)
			MAX-ACCESS not-accessible
			STATUS current
			DESCRIPTION
				"This is aclMacIndex in aclMacTable (1.3.6.1.4.1.1332.1.1.5.2.3.2.6)"
			::= { msanMacAclEntry 1 }

		
		-- 1.3.6.1.4.1.1332.1.1.5.3.12.11.1.3
		msanMacAclProtection OBJECT-TYPE
			SYNTAX INTEGER
				{
				unprotected(0),
				protected(1)
				}
			MAX-ACCESS read-write
			STATUS current
			DESCRIPTION
				"If protection flag is set to protected (1), other profile values cannot be edited.
				
				Protection flag is always  protected (1) and it can't be changed if  profile is assigned as dynamic:
				msanMacAclStatus = dynamic(2)"
			DEFVAL { unprotected }
			::= { msanMacAclEntry 3 }

		
		-- 1.3.6.1.4.1.1332.1.1.5.3.12.11.1.4
		msanMacAclStatus OBJECT-TYPE
			SYNTAX INTEGER
				{
				static(1),
				dynamic(2)
				}
			MAX-ACCESS read-only
			STATUS current
			DESCRIPTION
				"Profile status. 
				If status is dynamic, profile values can't be edited."
			::= { msanMacAclEntry 4 }

		
		-- 1.3.6.1.4.1.1332.1.1.5.3.12.12
		msanQosPortTable OBJECT-TYPE
			SYNTAX SEQUENCE OF MsanQosPortEntry
			MAX-ACCESS not-accessible
			STATUS current
			DESCRIPTION
				"Description."
			::= { msanQoS 12 }

		
		-- 1.3.6.1.4.1.1332.1.1.5.3.12.12.1
		msanQosPortEntry OBJECT-TYPE
			SYNTAX MsanQosPortEntry
			MAX-ACCESS not-accessible
			STATUS current
			DESCRIPTION
				"Description."
			INDEX { msanQosPortIfIndex, msanQosPortDirection }
			::= { msanQosPortTable 1 }

		
		MsanQosPortEntry ::=
			SEQUENCE { 
				msanQosPortIfIndex
					Integer32,
				msanQosPortDirection
					INTEGER,
				msanQosPortPeakDataRate
					Integer32,
				msanQosPortPeakBurstSize
					Integer32,
				msanQosPortPeakDroppedFrames
					Unsigned32
			 }

		-- 1.3.6.1.4.1.1332.1.1.5.3.12.12.1.1
		msanQosPortIfIndex OBJECT-TYPE
			SYNTAX Integer32
			MAX-ACCESS not-accessible
			STATUS current
			DESCRIPTION
				"Index of GPON ONU interface (from ifTable).
				
				ifIndex value of selected ONU interface (ifDescr=0/x/y) is calculated by formula:
				ifIndex=max_olt_port_number(8 or 16)+(x-1)*128+y "
			::= { msanQosPortEntry 1 }

		
		-- 1.3.6.1.4.1.1332.1.1.5.3.12.12.1.2
		msanQosPortDirection OBJECT-TYPE
			SYNTAX INTEGER
				{
				downstream(1),
				upstream(2)
				}
			MAX-ACCESS not-accessible
			STATUS current
			DESCRIPTION
				"Data traffic direction which defines QoS action:
				downstream(1) -> shaping
				upstream(2) -> policing"
			::= { msanQosPortEntry 2 }

		
		-- 1.3.6.1.4.1.1332.1.1.5.3.12.12.1.3
		msanQosPortPeakDataRate OBJECT-TYPE
			SYNTAX Integer32 (0 | 64..1000000)
			UNITS "kbps"
			MAX-ACCESS read-create
			STATUS current
			DESCRIPTION
				"Peak data rate in kbps (0 | 64  - 1000000).
				Value 0 (default)  means -> no rate limit"
			DEFVAL { 0 }
			::= { msanQosPortEntry 3 }

		
		-- 1.3.6.1.4.1.1332.1.1.5.3.12.12.1.4
		msanQosPortPeakBurstSize OBJECT-TYPE
			SYNTAX Integer32 (0..16384)
			UNITS "kB"
			MAX-ACCESS read-write
			STATUS current
			DESCRIPTION
				"Peak data rate burst size in kB (0 - 16384).
				This parameter can be set only when peak data rate value (msanQosPortPeakDataRate) is not 0.
				
				When parameter is set to 0 (default), it's automatically updated to default 
				burst size value according to current peak data rate (msanQosPortPeakDataRate)."
			DEFVAL { 0 }
			::= { msanQosPortEntry 4 }

		
		-- 1.3.6.1.4.1.1332.1.1.5.3.12.12.1.5
		msanQosPortPeakDroppedFrames OBJECT-TYPE
			SYNTAX Unsigned32
			MAX-ACCESS read-only
			STATUS current
			DESCRIPTION
				"Dropped frames counter (peak data rate is exceeded)"
			::= { msanQosPortEntry 5 }

		
		-- 1.3.6.1.4.1.1332.1.1.5.3.13
		msanForwardingDb OBJECT IDENTIFIER ::= { msanAdditionalConf 13 }

		
		-- 1.3.6.1.4.1.1332.1.1.5.3.13.3
		msanForwardingDbGlobal OBJECT IDENTIFIER ::= { msanForwardingDb 3 }

		
		-- 1.3.6.1.4.1.1332.1.1.5.3.13.3.1
		msanAddressLearningMode OBJECT-TYPE
			SYNTAX INTEGER
				{
				macOnly(1),
				noMacOnly(2)
				}
			MAX-ACCESS read-write
			STATUS deprecated
			DESCRIPTION
				"Specifies how source MAC addresses are associated with the interfaces on the switch. If mode is specified as nomaconly, 
				source MAC addresses are learned as pairs of incoming VLAN ID and the source MAC address. If mode is specified as maconly, 
				all source MAC addresses are learned in a specified VLAN, VLAN ID of the VLAN the packet was received from is not remembered. 
				This mode is used for General Purpose Service Based Tagging."
			::= { msanForwardingDbGlobal 1 }

		
		-- 1.3.6.1.4.1.1332.1.1.5.3.13.3.2
		msanAddressLearningVlanId OBJECT-TYPE
			SYNTAX Integer32 (1..4094)
			MAX-ACCESS read-write
			STATUS deprecated
			DESCRIPTION
				"This is the VLAN ID which is used for learning source MAC addresses in maconly mode. All learned MAC addresses 
				will be marked as received from this VLAN. VLAN with this VLAN ID is created on the switch and all physical intefaces 
				are added to this VLAN. This VLAN ID cannot be used for configuring other VLANs on the switch."
			::= { msanForwardingDbGlobal 2 }

		
		-- 1.3.6.1.4.1.1332.1.1.5.3.13.3.3
		msanSwitchAddressAgingTimeout OBJECT-TYPE
			SYNTAX INTEGER (10..1000000)
			MAX-ACCESS read-write
			STATUS current
			DESCRIPTION
				"The FDB entry's address aging timeout (in seconds)."
			DEFVAL { 300 }
			::= { msanForwardingDbGlobal 3 }

		
		-- 1.3.6.1.4.1.1332.1.1.5.3.14
		msanDiagnostics OBJECT IDENTIFIER ::= { msanAdditionalConf 14 }

		
		-- 1.3.6.1.4.1.1332.1.1.5.3.14.1
		msanDiagnosticsGlobal OBJECT IDENTIFIER ::= { msanDiagnostics 1 }

		
		-- 1.3.6.1.4.1.1332.1.1.5.3.14.1.1
		msanDiagnosticsFanSpeedLevel OBJECT-TYPE
			SYNTAX Integer32
			MAX-ACCESS read-only
			STATUS current
			DESCRIPTION
				"MSAN shelf fan current speed level. Higher level defines higer speed.
				Level 0 means fan is stopped. Maximum level is defined by 
				parameter msanDiagnosticsMaxFanSpeedLevel"
			::= { msanDiagnosticsGlobal 1 }

		
		-- 1.3.6.1.4.1.1332.1.1.5.3.14.1.2
		msanDiagnosticsMaxFanSpeedLevel OBJECT-TYPE
			SYNTAX Integer32
			MAX-ACCESS read-only
			STATUS current
			DESCRIPTION
				"MSAN shelf fan max speed level."
			::= { msanDiagnosticsGlobal 2 }

		
		-- 1.3.6.1.4.1.1332.1.1.5.3.14.2
		msanDiagnosticsTestTable OBJECT-TYPE
			SYNTAX SEQUENCE OF MsanDiagnosticsTestEntry
			MAX-ACCESS not-accessible
			STATUS current
			DESCRIPTION
				"Description."
			::= { msanDiagnostics 2 }

		
		-- 1.3.6.1.4.1.1332.1.1.5.3.14.2.1
		msanDiagnosticsTestEntry OBJECT-TYPE
			SYNTAX MsanDiagnosticsTestEntry
			MAX-ACCESS not-accessible
			STATUS current
			DESCRIPTION
				"Description."
			INDEX { msanDiagnosticsTestCode }
			::= { msanDiagnosticsTestTable 1 }

		
		MsanDiagnosticsTestEntry ::=
			SEQUENCE { 
				msanDiagnosticsTestCode
					Integer32,
				msanDiagnosticsTestName
					OCTET STRING,
				msanDiagnosticsTestActivity
					INTEGER,
				msanDiagnosticsTestTime
					Unsigned32,
				msanDiagnosticsTestPriority
					INTEGER,
				msanDiagnosticsTestType
					INTEGER,
				msanDiagnosticsTestTimeMin
					Integer32,
				msanDiagnosticsTestTimeMax
					Integer32
			 }

		-- 1.3.6.1.4.1.1332.1.1.5.3.14.2.1.1
		msanDiagnosticsTestCode OBJECT-TYPE
			SYNTAX Integer32 (0..99999999)
			MAX-ACCESS not-accessible
			STATUS current
			DESCRIPTION
				"Unique identification of a test program."
			::= { msanDiagnosticsTestEntry 1 }

		
		-- 1.3.6.1.4.1.1332.1.1.5.3.14.2.1.2
		msanDiagnosticsTestName OBJECT-TYPE
			SYNTAX OCTET STRING
			MAX-ACCESS read-only
			STATUS current
			DESCRIPTION
				"The name of a test program."
			::= { msanDiagnosticsTestEntry 2 }

		
		-- 1.3.6.1.4.1.1332.1.1.5.3.14.2.1.3
		msanDiagnosticsTestActivity OBJECT-TYPE
			SYNTAX INTEGER
				{
				testOn(1),
				testOff(2)
				}
			MAX-ACCESS read-write
			STATUS current
			DESCRIPTION
				"Specifies the Test activity parameter for the diagnostic. "
			::= { msanDiagnosticsTestEntry 3 }

		
		-- 1.3.6.1.4.1.1332.1.1.5.3.14.2.1.4
		msanDiagnosticsTestTime OBJECT-TYPE
			SYNTAX Unsigned32 (100..999999900)
			MAX-ACCESS read-write
			STATUS current
			DESCRIPTION
				"Test time, whose interpretation depends on test running mode:
				
				- for cyclical tests, it means the period at which the test is 
				  carried out one after another (time unit is milisecond)
				
				- for all others, it means time of day in the form 'hhmmss' 
				  (e.g. '224950') at which the test begins.
				"
			::= { msanDiagnosticsTestEntry 4 }

		
		-- 1.3.6.1.4.1.1332.1.1.5.3.14.2.1.6
		msanDiagnosticsTestPriority OBJECT-TYPE
			SYNTAX INTEGER
				{
				low(0),
				medium(1),
				high(2),
				veryHigh(3)
				}
			MAX-ACCESS read-write
			STATUS current
			DESCRIPTION
				"Test priority parameter for the diagnostic."
			::= { msanDiagnosticsTestEntry 6 }

		
		-- 1.3.6.1.4.1.1332.1.1.5.3.14.2.1.7
		msanDiagnosticsTestType OBJECT-TYPE
			SYNTAX INTEGER
				{
				testAtReload(1),
				testPeriodically(2),
				testDaily(3)
				}
			MAX-ACCESS read-only
			STATUS current
			DESCRIPTION
				" 
				Type of starting the test. 
				
				DECIMAL VALUE   DESCRIPTION
				      1	        At start-up & Recovery
				      2	        Periodical 
				      3	        Daily 
				"
			::= { msanDiagnosticsTestEntry 7 }

		
		-- 1.3.6.1.4.1.1332.1.1.5.3.14.2.1.8
		msanDiagnosticsTestTimeMin OBJECT-TYPE
			SYNTAX Integer32
			MAX-ACCESS read-only
			STATUS current
			DESCRIPTION
				"Minimum possible value of parameter msanDiagnosticTestTime."
			::= { msanDiagnosticsTestEntry 8 }

		
		-- 1.3.6.1.4.1.1332.1.1.5.3.14.2.1.9
		msanDiagnosticsTestTimeMax OBJECT-TYPE
			SYNTAX Integer32
			MAX-ACCESS read-only
			STATUS current
			DESCRIPTION
				"Maximum possible value of parameter msanDiagnosticTestTime."
			::= { msanDiagnosticsTestEntry 9 }

		
		-- 1.3.6.1.4.1.1332.1.1.5.3.14.3
		msanDiagnosticsErrorTable OBJECT-TYPE
			SYNTAX SEQUENCE OF MsanDiagnosticsErrorEntry
			MAX-ACCESS not-accessible
			STATUS current
			DESCRIPTION
				"Description."
			::= { msanDiagnostics 3 }

		
		-- 1.3.6.1.4.1.1332.1.1.5.3.14.3.1
		msanDiagnosticsErrorEntry OBJECT-TYPE
			SYNTAX MsanDiagnosticsErrorEntry
			MAX-ACCESS not-accessible
			STATUS current
			DESCRIPTION
				"Description."
			INDEX { msanDiagnosticsErrorCode }
			::= { msanDiagnosticsErrorTable 1 }

		
		MsanDiagnosticsErrorEntry ::=
			SEQUENCE { 
				msanDiagnosticsErrorCode
					Integer32,
				msanDiagnosticsErrorDescription
					OCTET STRING,
				msanDiagnosticsErrorPriority
					INTEGER,
				msanDiagnosticsErrorObjectType
					OCTET STRING,
				msanDiagnosticsErrorMeasure
					OCTET STRING,
				msanDiagnosticsErrorMeasureActive
					INTEGER,
				msanDiagnosticsErrorProbableCause
					Integer32,
				msanDiagnosticsErrorObjectTypeId
					Integer32,
				msanDiagnosticsErrorMeasureId
					Integer32
			 }

		-- 1.3.6.1.4.1.1332.1.1.5.3.14.3.1.1
		msanDiagnosticsErrorCode OBJECT-TYPE
			SYNTAX Integer32 (0..99999999)
			MAX-ACCESS not-accessible
			STATUS current
			DESCRIPTION
				"Unique identification of an error reported during testing an object."
			::= { msanDiagnosticsErrorEntry 1 }

		
		-- 1.3.6.1.4.1.1332.1.1.5.3.14.3.1.2
		msanDiagnosticsErrorDescription OBJECT-TYPE
			SYNTAX OCTET STRING
			MAX-ACCESS read-only
			STATUS current
			DESCRIPTION
				"Description of the error code."
			::= { msanDiagnosticsErrorEntry 2 }

		
		-- 1.3.6.1.4.1.1332.1.1.5.3.14.3.1.3
		msanDiagnosticsErrorPriority OBJECT-TYPE
			SYNTAX INTEGER
				{
				critical(1),
				major(2),
				minor(3),
				warning(4)
				}
			MAX-ACCESS read-write
			STATUS current
			DESCRIPTION
				"Error priority."
			::= { msanDiagnosticsErrorEntry 3 }

		
		-- 1.3.6.1.4.1.1332.1.1.5.3.14.3.1.4
		msanDiagnosticsErrorObjectType OBJECT-TYPE
			SYNTAX OCTET STRING
			MAX-ACCESS read-only
			STATUS current
			DESCRIPTION
				"Object type - List of values can be found in alr_def.h"
			::= { msanDiagnosticsErrorEntry 4 }

		
		-- 1.3.6.1.4.1.1332.1.1.5.3.14.3.1.5
		msanDiagnosticsErrorMeasure OBJECT-TYPE
			SYNTAX OCTET STRING
			MAX-ACCESS read-only
			STATUS current
			DESCRIPTION
				"Measure (what is done when an error occurs, for instance reset the node, ...) - List of values can be found in alr_def.h"
			::= { msanDiagnosticsErrorEntry 5 }

		
		-- 1.3.6.1.4.1.1332.1.1.5.3.14.3.1.6
		msanDiagnosticsErrorMeasureActive OBJECT-TYPE
			SYNTAX INTEGER
				{
				notActive(0),
				active(1)
				}
			MAX-ACCESS read-write
			STATUS current
			DESCRIPTION
				"Activity of measure. With setting this parameter to notActive(0), you can prevent excecution of measure."
			DEFVAL { active }
			::= { msanDiagnosticsErrorEntry 6 }

		
		-- 1.3.6.1.4.1.1332.1.1.5.3.14.3.1.7
		msanDiagnosticsErrorProbableCause OBJECT-TYPE
			SYNTAX Integer32
			MAX-ACCESS read-only
			STATUS current
			DESCRIPTION
				"Probable cause."
			::= { msanDiagnosticsErrorEntry 7 }

		
		-- 1.3.6.1.4.1.1332.1.1.5.3.14.3.1.8
		msanDiagnosticsErrorObjectTypeId OBJECT-TYPE
			SYNTAX Integer32
			MAX-ACCESS read-only
			STATUS current
			DESCRIPTION
				"Object type ID- List of values can be found in alr_def.h"
			::= { msanDiagnosticsErrorEntry 8 }

		
		-- 1.3.6.1.4.1.1332.1.1.5.3.14.3.1.9
		msanDiagnosticsErrorMeasureId OBJECT-TYPE
			SYNTAX Integer32
			MAX-ACCESS read-only
			STATUS current
			DESCRIPTION
				"Measure (what is done when an error occurs, for instance reset the node, ...) - List of values can be found in alr_def.h"
			::= { msanDiagnosticsErrorEntry 9 }

		
		-- 1.3.6.1.4.1.1332.1.1.5.3.14.4
		msanDiagnosticsTempTable OBJECT-TYPE
			SYNTAX SEQUENCE OF MsanDiagnosticsTempEntry
			MAX-ACCESS not-accessible
			STATUS current
			DESCRIPTION
				"Description."
			::= { msanDiagnostics 4 }

		
		-- 1.3.6.1.4.1.1332.1.1.5.3.14.4.1
		msanDiagnosticsTempEntry OBJECT-TYPE
			SYNTAX MsanDiagnosticsTempEntry
			MAX-ACCESS not-accessible
			STATUS current
			DESCRIPTION
				"Description."
			INDEX { msanDiagnosticsTempSensorID }
			::= { msanDiagnosticsTempTable 1 }

		
		MsanDiagnosticsTempEntry ::=
			SEQUENCE { 
				msanDiagnosticsTempSensorID
					Integer32,
				msanDiagnosticsTempSensorName
					OCTET STRING,
				msanDiagnosticsTempCurrent
					Integer32,
				msanDiagnosticsTempCriticUnderheatThreshold
					Integer32,
				msanDiagnosticsTempUnderheatThreshold
					Integer32,
				msanDiagnosticsTempOverheatThreshold
					Integer32,
				msanDiagnosticsTempCriticOverheatThreshold
					Integer32
			 }

		-- 1.3.6.1.4.1.1332.1.1.5.3.14.4.1.1
		msanDiagnosticsTempSensorID OBJECT-TYPE
			SYNTAX Integer32 (0..100)
			MAX-ACCESS not-accessible
			STATUS current
			DESCRIPTION
				"Temperature sensor ID."
			::= { msanDiagnosticsTempEntry 1 }

		
		-- 1.3.6.1.4.1.1332.1.1.5.3.14.4.1.2
		msanDiagnosticsTempSensorName OBJECT-TYPE
			SYNTAX OCTET STRING
			MAX-ACCESS read-only
			STATUS current
			DESCRIPTION
				"Temperature sensor name."
			::= { msanDiagnosticsTempEntry 2 }

		
		-- 1.3.6.1.4.1.1332.1.1.5.3.14.4.1.3
		msanDiagnosticsTempCurrent OBJECT-TYPE
			SYNTAX Integer32
			MAX-ACCESS read-only
			STATUS current
			DESCRIPTION
				"Current temperature of the specified sensor in [deg C]."
			::= { msanDiagnosticsTempEntry 3 }

		
		-- 1.3.6.1.4.1.1332.1.1.5.3.14.4.1.4
		msanDiagnosticsTempCriticUnderheatThreshold OBJECT-TYPE
			SYNTAX Integer32
			MAX-ACCESS read-only
			STATUS current
			DESCRIPTION
				"Sensor critical underheat threshold temperature limit in [deg C]."
			::= { msanDiagnosticsTempEntry 4 }

		
		-- 1.3.6.1.4.1.1332.1.1.5.3.14.4.1.5
		msanDiagnosticsTempUnderheatThreshold OBJECT-TYPE
			SYNTAX Integer32
			MAX-ACCESS read-only
			STATUS current
			DESCRIPTION
				"Sensor underheat temperature threshold limit in [deg C]."
			::= { msanDiagnosticsTempEntry 5 }

		
		-- 1.3.6.1.4.1.1332.1.1.5.3.14.4.1.6
		msanDiagnosticsTempOverheatThreshold OBJECT-TYPE
			SYNTAX Integer32
			MAX-ACCESS read-only
			STATUS current
			DESCRIPTION
				"Sensor overheat threshold temperature limit in [deg C]."
			::= { msanDiagnosticsTempEntry 6 }

		
		-- 1.3.6.1.4.1.1332.1.1.5.3.14.4.1.7
		msanDiagnosticsTempCriticOverheatThreshold OBJECT-TYPE
			SYNTAX Integer32
			MAX-ACCESS read-only
			STATUS current
			DESCRIPTION
				"Sensor critical overheat threshold temperature limit in [deg C]."
			::= { msanDiagnosticsTempEntry 7 }

		
		-- 1.3.6.1.4.1.1332.1.1.5.3.14.5
		msanDiagnosticsErrorFilterTable OBJECT-TYPE
			SYNTAX SEQUENCE OF MsanDiagnosticsErrorFilterEntry
			MAX-ACCESS not-accessible
			STATUS current
			DESCRIPTION
				"Description."
			::= { msanDiagnostics 5 }

		
		-- 1.3.6.1.4.1.1332.1.1.5.3.14.5.1
		msanDiagnosticsErrorFilterEntry OBJECT-TYPE
			SYNTAX MsanDiagnosticsErrorFilterEntry
			MAX-ACCESS not-accessible
			STATUS current
			DESCRIPTION
				"Description."
			INDEX { msanDiagnosticsErrorFilterErrMask, msanDiagnosticsErrorFilterObjMask }
			::= { msanDiagnosticsErrorFilterTable 1 }

		
		MsanDiagnosticsErrorFilterEntry ::=
			SEQUENCE { 
				msanDiagnosticsErrorFilterErrMask
					OCTET STRING,
				msanDiagnosticsErrorFilterObjMask
					OCTET STRING,
				msanDiagnosticsErrorFilterRowStatus
					RowStatus
			 }

		-- 1.3.6.1.4.1.1332.1.1.5.3.14.5.1.1
		msanDiagnosticsErrorFilterErrMask OBJECT-TYPE
			SYNTAX OCTET STRING (SIZE (1..20))
			MAX-ACCESS not-accessible
			STATUS current
			DESCRIPTION
				"Error code in ascii format. Regular expression describing one or more error codes."
			::= { msanDiagnosticsErrorFilterEntry 1 }

		
		-- 1.3.6.1.4.1.1332.1.1.5.3.14.5.1.2
		msanDiagnosticsErrorFilterObjMask OBJECT-TYPE
			SYNTAX OCTET STRING (SIZE (1..40))
			MAX-ACCESS not-accessible
			STATUS current
			DESCRIPTION
				"Type of object, which alarming is filtered for. Regular expression describing one or more test objects. "
			::= { msanDiagnosticsErrorFilterEntry 2 }

		
		-- 1.3.6.1.4.1.1332.1.1.5.3.14.5.1.3
		msanDiagnosticsErrorFilterRowStatus OBJECT-TYPE
			SYNTAX RowStatus
			MAX-ACCESS read-create
			STATUS current
			DESCRIPTION
				"The row status object controls the creation/deletion of rows in this table. Its semantics are the same as those for the RowStatus textual convention specified for SNMPv2.
				Setting this object to createAndGo(4) creates a row in this table.
				Setting this object to destroy(6) will remove this entry.
				Read values: active(1).
				Other values are currently not supported."
			::= { msanDiagnosticsErrorFilterEntry 3 }

		
		-- 1.3.6.1.4.1.1332.1.1.5.3.14.6
		msanDiagnosticsErrorSeverityTable OBJECT-TYPE
			SYNTAX SEQUENCE OF MsanDiagnosticsErrorSeverityEntry
			MAX-ACCESS not-accessible
			STATUS current
			DESCRIPTION
				"Description."
			::= { msanDiagnostics 6 }

		
		-- 1.3.6.1.4.1.1332.1.1.5.3.14.6.1
		msanDiagnosticsErrorSeverityEntry OBJECT-TYPE
			SYNTAX MsanDiagnosticsErrorSeverityEntry
			MAX-ACCESS not-accessible
			STATUS current
			DESCRIPTION
				"Description."
			INDEX { msanDiagnosticsErrorSeverityErrCode, msanDiagnosticsErrorSeverityObjMask }
			::= { msanDiagnosticsErrorSeverityTable 1 }

		
		MsanDiagnosticsErrorSeverityEntry ::=
			SEQUENCE { 
				msanDiagnosticsErrorSeverityErrCode
					Integer32,
				msanDiagnosticsErrorSeverityErrPriority
					INTEGER,
				msanDiagnosticsErrorSeverityObjMask
					OCTET STRING,
				msanDiagnosticsErrorSeverityRowStatus
					RowStatus
			 }

		-- 1.3.6.1.4.1.1332.1.1.5.3.14.6.1.1
		msanDiagnosticsErrorSeverityErrCode OBJECT-TYPE
			SYNTAX Integer32
			MAX-ACCESS not-accessible
			STATUS current
			DESCRIPTION
				"Unique identification of an error reported during testing an object. 
				All error codes are stated in alr_def.h (KFMT)"
			::= { msanDiagnosticsErrorSeverityEntry 1 }

		
		-- 1.3.6.1.4.1.1332.1.1.5.3.14.6.1.2
		msanDiagnosticsErrorSeverityErrPriority OBJECT-TYPE
			SYNTAX INTEGER
				{
				critical(1),
				major(2),
				minor(3),
				warning(4)
				}
			MAX-ACCESS read-create
			STATUS current
			DESCRIPTION
				"Priority of error. "
			::= { msanDiagnosticsErrorSeverityEntry 2 }

		
		-- 1.3.6.1.4.1.1332.1.1.5.3.14.6.1.3
		msanDiagnosticsErrorSeverityObjMask OBJECT-TYPE
			SYNTAX OCTET STRING (SIZE (1..40))
			MAX-ACCESS not-accessible
			STATUS current
			DESCRIPTION
				"Type of object, which alarming is filtered for. Regular expression describing one or more test objects. "
			::= { msanDiagnosticsErrorSeverityEntry 3 }

		
		-- 1.3.6.1.4.1.1332.1.1.5.3.14.6.1.4
		msanDiagnosticsErrorSeverityRowStatus OBJECT-TYPE
			SYNTAX RowStatus
			MAX-ACCESS read-create
			STATUS current
			DESCRIPTION
				"The row status object controls the creation/deletion of rows in this table. Its semantics are the same as those for the RowStatus textual convention specified for SNMPv2.
				For row creation use createAndWait(5) [createAndGo(4) is not supported].
				"
			::= { msanDiagnosticsErrorSeverityEntry 4 }

		
		-- 1.3.6.1.4.1.1332.1.1.5.3.14.7
		msanDiagnosticsExtAlrSensorTable OBJECT-TYPE
			SYNTAX SEQUENCE OF MsanDiagnosticsExtAlrSensorEntry
			MAX-ACCESS not-accessible
			STATUS current
			DESCRIPTION
				"Description."
			::= { msanDiagnostics 7 }

		
		-- 1.3.6.1.4.1.1332.1.1.5.3.14.7.1
		msanDiagnosticsExtAlrSensorEntry OBJECT-TYPE
			SYNTAX MsanDiagnosticsExtAlrSensorEntry
			MAX-ACCESS not-accessible
			STATUS current
			DESCRIPTION
				"Description."
			INDEX { msanDiagnosticsExtAlrSensorName }
			::= { msanDiagnosticsExtAlrSensorTable 1 }

		
		MsanDiagnosticsExtAlrSensorEntry ::=
			SEQUENCE { 
				msanDiagnosticsExtAlrSensorName
					DisplayString,
				msanDiagnosticsExtAlrSensorAlarm
					INTEGER,
				msanDiagnosticsExtAlrSensorLogic
					INTEGER
			 }

		-- 1.3.6.1.4.1.1332.1.1.5.3.14.7.1.1
		msanDiagnosticsExtAlrSensorName OBJECT-TYPE
			SYNTAX DisplayString
			MAX-ACCESS not-accessible
			STATUS current
			DESCRIPTION
				"Description."
			::= { msanDiagnosticsExtAlrSensorEntry 1 }

		
		-- 1.3.6.1.4.1.1332.1.1.5.3.14.7.1.2
		msanDiagnosticsExtAlrSensorAlarm OBJECT-TYPE
			SYNTAX INTEGER
				{
				enable(1),
				disable(2)
				}
			MAX-ACCESS read-write
			STATUS current
			DESCRIPTION
				"Description."
			::= { msanDiagnosticsExtAlrSensorEntry 2 }

		
		-- 1.3.6.1.4.1.1332.1.1.5.3.14.7.1.3
		msanDiagnosticsExtAlrSensorLogic OBJECT-TYPE
			SYNTAX INTEGER
				{
				open(1),
				close(2)
				}
			MAX-ACCESS read-write
			STATUS current
			DESCRIPTION
				"Description."
			::= { msanDiagnosticsExtAlrSensorEntry 3 }

		
		-- 1.3.6.1.4.1.1332.1.1.5.3.14.8
		msanDiagnosticsFanTable OBJECT-TYPE
			SYNTAX SEQUENCE OF MsanDiagnosticsFanEntry
			MAX-ACCESS not-accessible
			STATUS current
			DESCRIPTION
				"Description."
			::= { msanDiagnostics 8 }

		
		-- 1.3.6.1.4.1.1332.1.1.5.3.14.8.1
		msanDiagnosticsFanEntry OBJECT-TYPE
			SYNTAX MsanDiagnosticsFanEntry
			MAX-ACCESS not-accessible
			STATUS current
			DESCRIPTION
				"Description."
			INDEX { msanDiagnosticsFanId }
			::= { msanDiagnosticsFanTable 1 }

		
		MsanDiagnosticsFanEntry ::=
			SEQUENCE { 
				msanDiagnosticsFanId
					Integer32,
				msanDiagnosticsFanCurrentRpm
					Integer32,
				msanDiagnosticsFanCurrentPercentRpm
					Integer32
			 }

		-- 1.3.6.1.4.1.1332.1.1.5.3.14.8.1.1
		msanDiagnosticsFanId OBJECT-TYPE
			SYNTAX Integer32
			MAX-ACCESS not-accessible
			STATUS current
			DESCRIPTION
				"Fan id"
			::= { msanDiagnosticsFanEntry 1 }

		
		-- 1.3.6.1.4.1.1332.1.1.5.3.14.8.1.2
		msanDiagnosticsFanCurrentRpm OBJECT-TYPE
			SYNTAX Integer32
			MAX-ACCESS read-only
			STATUS current
			DESCRIPTION
				"Fan current RPM (rotations per minute) "
			::= { msanDiagnosticsFanEntry 2 }

		
		-- 1.3.6.1.4.1.1332.1.1.5.3.14.8.1.3
		msanDiagnosticsFanCurrentPercentRpm OBJECT-TYPE
			SYNTAX Integer32
			MAX-ACCESS read-only
			STATUS current
			DESCRIPTION
				"Fan current percent of Max RPM (rotations per minute) "
			::= { msanDiagnosticsFanEntry 3 }

		
		-- 1.3.6.1.4.1.1332.1.1.5.3.15
		msanPpp OBJECT IDENTIFIER ::= { msanAdditionalConf 15 }

		
		-- 1.3.6.1.4.1.1332.1.1.5.3.15.1
		msanPppGlobal OBJECT IDENTIFIER ::= { msanPpp 1 }

		
		-- 1.3.6.1.4.1.1332.1.1.5.3.15.1.1
		msanPppLocalIpAddress OBJECT-TYPE
			SYNTAX IpAddress
			MAX-ACCESS read-write
			STATUS current
			DESCRIPTION
				"Local IP address for PPP connection"
			::= { msanPppGlobal 1 }

		
		-- 1.3.6.1.4.1.1332.1.1.5.3.15.1.2
		msanPppRemoteIpAddress OBJECT-TYPE
			SYNTAX IpAddress
			MAX-ACCESS read-write
			STATUS current
			DESCRIPTION
				"Remote IP address for PPP connection"
			::= { msanPppGlobal 2 }

		
		-- 1.3.6.1.4.1.1332.1.1.5.3.15.1.3
		msanPppAuthProtocol OBJECT-TYPE
			SYNTAX INTEGER
				{
				none(0),
				chap(1),
				pap(2)
				}
			MAX-ACCESS read-write
			STATUS current
			DESCRIPTION
				"PPP authentication protocol. For MPS connection use CHAP."
			::= { msanPppGlobal 3 }

		
		-- 1.3.6.1.4.1.1332.1.1.5.3.15.1.4
		msanPppEchoInterval OBJECT-TYPE
			SYNTAX Integer32
			UNITS "seconds"
			MAX-ACCESS read-write
			STATUS current
			DESCRIPTION
				"LCP echo interval (in seconds) for session breakdown identification."
			::= { msanPppGlobal 4 }

		
		-- 1.3.6.1.4.1.1332.1.1.5.3.15.1.5
		msanPppVanJacobsonCompression OBJECT-TYPE
			SYNTAX INTEGER
				{
				enable(1),
				disable(2)
				}
			MAX-ACCESS read-write
			STATUS current
			DESCRIPTION
				"Control of VanJacobson compression. For MPS connection it must be disabled."
			::= { msanPppGlobal 5 }

		
		-- 1.3.6.1.4.1.1332.1.1.5.3.15.1.6
		msanPppAdminState OBJECT-TYPE
			SYNTAX INTEGER
				{
				enable(1),
				disable(2)
				}
			MAX-ACCESS read-write
			STATUS current
			DESCRIPTION
				"Global PPP connection administrative state."
			::= { msanPppGlobal 6 }

		
		-- 1.3.6.1.4.1.1332.1.1.5.3.16
		msanAlarmPanel OBJECT IDENTIFIER ::= { msanAdditionalConf 16 }

		
		-- 1.3.6.1.4.1.1332.1.1.5.3.16.1
		msanAlarmPanelGlobal OBJECT IDENTIFIER ::= { msanAlarmPanel 1 }

		
		-- 1.3.6.1.4.1.1332.1.1.5.3.16.1.1
		msanAlarmPanelAudioAlarmPriority OBJECT-TYPE
			SYNTAX INTEGER
				{
				critical(1),
				major(2),
				minor(3)
				}
			MAX-ACCESS read-write
			STATUS current
			DESCRIPTION
				"Alarm Panel Audio Alarm Priority."
			::= { msanAlarmPanelGlobal 1 }

		
		-- 1.3.6.1.4.1.1332.1.1.5.3.16.1.2
		msanAlarmPanelSerialPortType OBJECT-TYPE
			SYNTAX INTEGER
				{
				noConnection(1),
				mps(2),
				alarmPanel(3)
				}
			MAX-ACCESS read-write
			STATUS current
			DESCRIPTION
				"Type of equipment connected to serial port."
			::= { msanAlarmPanelGlobal 2 }

		
		-- 1.3.6.1.4.1.1332.1.1.5.3.16.2
		msanAlarmPanelTable OBJECT-TYPE
			SYNTAX SEQUENCE OF MsanAlarmPanelEntry
			MAX-ACCESS not-accessible
			STATUS current
			DESCRIPTION
				"Description."
			::= { msanAlarmPanel 2 }

		
		-- 1.3.6.1.4.1.1332.1.1.5.3.16.2.1
		msanAlarmPanelEntry OBJECT-TYPE
			SYNTAX MsanAlarmPanelEntry
			MAX-ACCESS not-accessible
			STATUS current
			DESCRIPTION
				"Description."
			INDEX { msanAlarmPanelIndex }
			::= { msanAlarmPanelTable 1 }

		
		MsanAlarmPanelEntry ::=
			SEQUENCE { 
				msanAlarmPanelIndex
					Integer32,
				msanAlarmPanelConnectionState
					INTEGER,
				msanAlarmPanelAdminState
					INTEGER
			 }

		-- 1.3.6.1.4.1.1332.1.1.5.3.16.2.1.1
		msanAlarmPanelIndex OBJECT-TYPE
			SYNTAX Integer32 (1..16)
			MAX-ACCESS not-accessible
			STATUS current
			DESCRIPTION
				"Unique identification of an alarm panel."
			::= { msanAlarmPanelEntry 1 }

		
		-- 1.3.6.1.4.1.1332.1.1.5.3.16.2.1.2
		msanAlarmPanelConnectionState OBJECT-TYPE
			SYNTAX INTEGER
				{
				up(1),
				down(2)
				}
			MAX-ACCESS read-only
			STATUS current
			DESCRIPTION
				"Alarm panel connection status"
			::= { msanAlarmPanelEntry 2 }

		
		-- 1.3.6.1.4.1.1332.1.1.5.3.16.2.1.3
		msanAlarmPanelAdminState OBJECT-TYPE
			SYNTAX INTEGER
				{
				unequipped(0),
				equipped(1)
				}
			MAX-ACCESS read-write
			STATUS current
			DESCRIPTION
				"Flag determining whether an alarm panel is equipped or not."
			::= { msanAlarmPanelEntry 3 }

		
		-- 1.3.6.1.4.1.1332.1.1.5.3.16.3
		msanAlarmPanelIndicatorTable OBJECT-TYPE
			SYNTAX SEQUENCE OF MsanAlarmPanelIndicatorEntry
			MAX-ACCESS not-accessible
			STATUS current
			DESCRIPTION
				"Description."
			::= { msanAlarmPanel 3 }

		
		-- 1.3.6.1.4.1.1332.1.1.5.3.16.3.1
		msanAlarmPanelIndicatorEntry OBJECT-TYPE
			SYNTAX MsanAlarmPanelIndicatorEntry
			MAX-ACCESS not-accessible
			STATUS current
			DESCRIPTION
				"Description."
			INDEX { msanAlarmPanelIndex, msanAlarmPanelIndicatorIndex }
			::= { msanAlarmPanelIndicatorTable 1 }

		
		MsanAlarmPanelIndicatorEntry ::=
			SEQUENCE { 
				msanAlarmPanelIndicatorIndex
					Integer32,
				msanAlarmPanelIndicatorErrCode
					Integer32
			 }

		-- 1.3.6.1.4.1.1332.1.1.5.3.16.3.1.1
		msanAlarmPanelIndicatorIndex OBJECT-TYPE
			SYNTAX Integer32 (1..15)
			MAX-ACCESS not-accessible
			STATUS current
			DESCRIPTION
				"Alarm panel indicator number. "
			::= { msanAlarmPanelIndicatorEntry 1 }

		
		-- 1.3.6.1.4.1.1332.1.1.5.3.16.3.1.2
		msanAlarmPanelIndicatorErrCode OBJECT-TYPE
			SYNTAX Integer32
			MAX-ACCESS read-write
			STATUS current
			DESCRIPTION
				"Alarm panel indicator error number."
			::= { msanAlarmPanelIndicatorEntry 2 }

		
		-- 1.3.6.1.4.1.1332.1.1.5.3.16.4
		msanAlarmPanelInputTable OBJECT-TYPE
			SYNTAX SEQUENCE OF MsanAlarmPanelInputEntry
			MAX-ACCESS not-accessible
			STATUS current
			DESCRIPTION
				"Description."
			::= { msanAlarmPanel 4 }

		
		-- 1.3.6.1.4.1.1332.1.1.5.3.16.4.1
		msanAlarmPanelInputEntry OBJECT-TYPE
			SYNTAX MsanAlarmPanelInputEntry
			MAX-ACCESS not-accessible
			STATUS current
			DESCRIPTION
				"Description."
			INDEX { msanAlarmPanelIndex, msanAlarmPanelInputIndex }
			::= { msanAlarmPanelInputTable 1 }

		
		MsanAlarmPanelInputEntry ::=
			SEQUENCE { 
				msanAlarmPanelInputIndex
					Integer32,
				msanAlarmPanelInputErrCode
					Integer32,
				msanAlarmPanelInputActiveLevel
					INTEGER
			 }

		-- 1.3.6.1.4.1.1332.1.1.5.3.16.4.1.1
		msanAlarmPanelInputIndex OBJECT-TYPE
			SYNTAX Integer32 (1..15)
			MAX-ACCESS not-accessible
			STATUS current
			DESCRIPTION
				"Alarm panel input sensor number."
			::= { msanAlarmPanelInputEntry 1 }

		
		-- 1.3.6.1.4.1.1332.1.1.5.3.16.4.1.2
		msanAlarmPanelInputErrCode OBJECT-TYPE
			SYNTAX Integer32
			MAX-ACCESS read-write
			STATUS current
			DESCRIPTION
				"Alarm panel input sensor error code."
			::= { msanAlarmPanelInputEntry 2 }

		
		-- 1.3.6.1.4.1.1332.1.1.5.3.16.4.1.3
		msanAlarmPanelInputActiveLevel OBJECT-TYPE
			SYNTAX INTEGER
				{
				low(0),
				high(1)
				}
			MAX-ACCESS read-write
			STATUS current
			DESCRIPTION
				"Alarm panel input sensor active level."
			::= { msanAlarmPanelInputEntry 3 }

		
		-- 1.3.6.1.4.1.1332.1.1.5.3.17
		msanMvr OBJECT IDENTIFIER ::= { msanAdditionalConf 17 }

		
		-- 1.3.6.1.4.1.1332.1.1.5.3.17.1
		msanMvrGlobal OBJECT IDENTIFIER ::= { msanMvr 1 }

		
		-- 1.3.6.1.4.1.1332.1.1.5.3.17.2
		msanMvrPortTable OBJECT-TYPE
			SYNTAX SEQUENCE OF MsanMvrPortEntry
			MAX-ACCESS not-accessible
			STATUS current
			DESCRIPTION
				"Description."
			::= { msanMvr 2 }

		
		-- 1.3.6.1.4.1.1332.1.1.5.3.17.2.1
		msanMvrPortEntry OBJECT-TYPE
			SYNTAX MsanMvrPortEntry
			MAX-ACCESS not-accessible
			STATUS current
			DESCRIPTION
				"Description."
			INDEX { ifIndex }
			::= { msanMvrPortTable 1 }

		
		MsanMvrPortEntry ::=
			SEQUENCE { 
				msanMvrPortAdminMode
					INTEGER
			 }

		-- 1.3.6.1.4.1.1332.1.1.5.3.17.2.1.1
		msanMvrPortAdminMode OBJECT-TYPE
			SYNTAX INTEGER
				{
				enable(1),
				disable(2)
				}
			MAX-ACCESS read-write
			STATUS current
			DESCRIPTION
				"Administrative mode for Multicast VLAN Registration (a.k.a. Service Based Tagging) for the selected interface"
			::= { msanMvrPortEntry 1 }

		
		-- 1.3.6.1.4.1.1332.1.1.5.3.17.3
		msanMvrMulticastGroupTable OBJECT-TYPE
			SYNTAX SEQUENCE OF MsanMvrMulticastGroupEntry
			MAX-ACCESS not-accessible
			STATUS current
			DESCRIPTION
				"Description."
			::= { msanMvr 3 }

		
		-- 1.3.6.1.4.1.1332.1.1.5.3.17.3.1
		msanMvrMulticastGroupEntry OBJECT-TYPE
			SYNTAX MsanMvrMulticastGroupEntry
			MAX-ACCESS not-accessible
			STATUS current
			DESCRIPTION
				"Description."
			INDEX { msanMvrMulticastGroupMVlanId, msanMvrMulticastGroupStartIp }
			::= { msanMvrMulticastGroupTable 1 }

		
		MsanMvrMulticastGroupEntry ::=
			SEQUENCE { 
				msanMvrMulticastGroupMVlanId
					Integer32,
				msanMvrMulticastGroupStartIp
					IpAddress,
				msanMvrMulticastGroupEndIp
					IpAddress,
				msanMvrMulticastGroupRowStatus
					RowStatus
			 }

		-- 1.3.6.1.4.1.1332.1.1.5.3.17.3.1.1
		msanMvrMulticastGroupMVlanId OBJECT-TYPE
			SYNTAX Integer32
			MAX-ACCESS not-accessible
			STATUS current
			DESCRIPTION
				"VLAN ID (refers to dot1qVlanIndex) where MVR functionality is used."
			::= { msanMvrMulticastGroupEntry 1 }

		
		-- 1.3.6.1.4.1.1332.1.1.5.3.17.3.1.2
		msanMvrMulticastGroupStartIp OBJECT-TYPE
			SYNTAX IpAddress
			MAX-ACCESS not-accessible
			STATUS current
			DESCRIPTION
				"Start IP Address of the multicast group range."
			::= { msanMvrMulticastGroupEntry 2 }

		
		-- 1.3.6.1.4.1.1332.1.1.5.3.17.3.1.3
		msanMvrMulticastGroupEndIp OBJECT-TYPE
			SYNTAX IpAddress
			MAX-ACCESS read-create
			STATUS current
			DESCRIPTION
				"End IP Address of the multicast group range."
			::= { msanMvrMulticastGroupEntry 3 }

		
		-- 1.3.6.1.4.1.1332.1.1.5.3.17.3.1.4
		msanMvrMulticastGroupRowStatus OBJECT-TYPE
			SYNTAX RowStatus
			MAX-ACCESS read-create
			STATUS current
			DESCRIPTION
				"The row status object controls the creation/deletion of rows in this table. 
				For row creation use createAndWait(5) [createAndGo(4) is not supported]."
			::= { msanMvrMulticastGroupEntry 4 }

		
		-- 1.3.6.1.4.1.1332.1.1.5.3.17.4
		msanMvrConfigTable OBJECT-TYPE
			SYNTAX SEQUENCE OF MsanMvrConfigEntry
			MAX-ACCESS not-accessible
			STATUS current
			DESCRIPTION
				"Description."
			::= { msanMvr 4 }

		
		-- 1.3.6.1.4.1.1332.1.1.5.3.17.4.1
		msanMvrConfigEntry OBJECT-TYPE
			SYNTAX MsanMvrConfigEntry
			MAX-ACCESS not-accessible
			STATUS current
			DESCRIPTION
				"Description."
			INDEX { ifIndex, msanMvrConfigCVlanId, msanMvrConfigMVlanId }
			::= { msanMvrConfigTable 1 }

		
		MsanMvrConfigEntry ::=
			SEQUENCE { 
				msanMvrConfigCVlanId
					Integer32,
				msanMvrConfigMVlanId
					Integer32,
				msanMvrConfigCos
					Integer32,
				msanMvrConfigRowStatus
					RowStatus
			 }

		-- 1.3.6.1.4.1.1332.1.1.5.3.17.4.1.1
		msanMvrConfigCVlanId OBJECT-TYPE
			SYNTAX Integer32 (1..4094)
			MAX-ACCESS not-accessible
			STATUS current
			DESCRIPTION
				"Customer VLAN ID for the selected interface from which 
				IGMP Join/Leave messages will be remarked."
			::= { msanMvrConfigEntry 1 }

		
		-- 1.3.6.1.4.1.1332.1.1.5.3.17.4.1.2
		msanMvrConfigMVlanId OBJECT-TYPE
			SYNTAX Integer32 (1..4092)
			MAX-ACCESS not-accessible
			STATUS current
			DESCRIPTION
				"Service provider multicast VLAN ID for the selected interface 
				to which IGMP Join/Leave messages will be remarked."
			::= { msanMvrConfigEntry 2 }

		
		-- 1.3.6.1.4.1.1332.1.1.5.3.17.4.1.3
		msanMvrConfigCos OBJECT-TYPE
			SYNTAX Integer32 (-1..7)
			MAX-ACCESS read-write
			STATUS current
			DESCRIPTION
				"Output CoS priority on the selected interface. IGMP messages received from 
				this interface will have this priority when they are transmitted into service provider
				multicast VLAN. 
				
				Value '-1' defines that original CoS value is not changed."
			DEFVAL { 0 }
			::= { msanMvrConfigEntry 3 }

		
		-- 1.3.6.1.4.1.1332.1.1.5.3.17.4.1.4
		msanMvrConfigRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMvrConfigEntry 4 }

		
		-- 1.3.6.1.4.1.1332.1.1.5.3.17.5
		msanMvrDvlanTable OBJECT-TYPE
			SYNTAX SEQUENCE OF MsanMvrDvlanEntry
			MAX-ACCESS not-accessible
			STATUS current
			DESCRIPTION
				"Description."
			::= { msanMvr 5 }

		
		-- 1.3.6.1.4.1.1332.1.1.5.3.17.5.1
		msanMvrDvlanEntry OBJECT-TYPE
			SYNTAX MsanMvrDvlanEntry
			MAX-ACCESS not-accessible
			STATUS current
			DESCRIPTION
				"Description."
			INDEX { ifIndex }
			::= { msanMvrDvlanTable 1 }

		
		MsanMvrDvlanEntry ::=
			SEQUENCE { 
				msanMvrDvlanRmOuterTagStatus
					INTEGER,
				msanMvrDvlanEthertypeRewriteStatus
					INTEGER
			 }

		-- 1.3.6.1.4.1.1332.1.1.5.3.17.5.1.1
		msanMvrDvlanRmOuterTagStatus OBJECT-TYPE
			SYNTAX INTEGER
				{
				enable(1),
				disable(2)
				}
			MAX-ACCESS read-write
			STATUS current
			DESCRIPTION
				"The desired state of removing outer tags on IGMP packets funcionality."
			DEFVAL { disable }
			::= { msanMvrDvlanEntry 1 }

		
		-- 1.3.6.1.4.1.1332.1.1.5.3.17.5.1.2
		msanMvrDvlanEthertypeRewriteStatus OBJECT-TYPE
			SYNTAX INTEGER
				{
				enable(1),
				disable(2)
				}
			MAX-ACCESS read-write
			STATUS current
			DESCRIPTION
				"The desired state of rewriting ether type from outer vlan tag to inner vlan 
				tag."
			DEFVAL { disable }
			::= { msanMvrDvlanEntry 2 }

		
		-- 1.3.6.1.4.1.1332.1.1.5.3.18
		msanRemoteAccess OBJECT IDENTIFIER ::= { msanAdditionalConf 18 }

		
		-- 1.3.6.1.4.1.1332.1.1.5.3.18.1
		msanRemoteAccessGlobal OBJECT IDENTIFIER ::= { msanRemoteAccess 1 }

		
		-- 1.3.6.1.4.1.1332.1.1.5.3.18.2
		msanRemoteAccessFilterTable OBJECT-TYPE
			SYNTAX SEQUENCE OF MsanRemoteAccessFilterEntry
			MAX-ACCESS not-accessible
			STATUS deprecated
			DESCRIPTION
				"Description."
			::= { msanRemoteAccess 2 }

		
		-- 1.3.6.1.4.1.1332.1.1.5.3.18.2.1
		msanRemoteAccessFilterEntry OBJECT-TYPE
			SYNTAX MsanRemoteAccessFilterEntry
			MAX-ACCESS not-accessible
			STATUS deprecated
			DESCRIPTION
				"Description."
			INDEX { msanRemoteAccessFilterRuleIndex }
			::= { msanRemoteAccessFilterTable 1 }

		
		MsanRemoteAccessFilterEntry ::=
			SEQUENCE { 
				msanRemoteAccessFilterRuleIndex
					INTEGER,
				msanRemoteAccessFilterIp
					IpAddress,
				msanRemoteAccessFilterNetmask
					IpAddress,
				msanRemoteAccessFilterAction
					INTEGER,
				msanRemoteAccessFilterRowStatus
					RowStatus
			 }

		-- 1.3.6.1.4.1.1332.1.1.5.3.18.2.1.1
		msanRemoteAccessFilterRuleIndex OBJECT-TYPE
			SYNTAX INTEGER (1..200)
			MAX-ACCESS not-accessible
			STATUS deprecated
			DESCRIPTION
				"Rule's index. Index should be continued, without gaps. "
			::= { msanRemoteAccessFilterEntry 1 }

		
		-- 1.3.6.1.4.1.1332.1.1.5.3.18.2.1.2
		msanRemoteAccessFilterIp OBJECT-TYPE
			SYNTAX IpAddress
			MAX-ACCESS read-create
			STATUS deprecated
			DESCRIPTION
				"IP Address of the rule."
			::= { msanRemoteAccessFilterEntry 2 }

		
		-- 1.3.6.1.4.1.1332.1.1.5.3.18.2.1.3
		msanRemoteAccessFilterNetmask OBJECT-TYPE
			SYNTAX IpAddress
			MAX-ACCESS read-create
			STATUS deprecated
			DESCRIPTION
				"Netmask of the rule."
			::= { msanRemoteAccessFilterEntry 3 }

		
		-- 1.3.6.1.4.1.1332.1.1.5.3.18.2.1.4
		msanRemoteAccessFilterAction OBJECT-TYPE
			SYNTAX INTEGER
				{
				accept(1),
				deny(2)
				}
			MAX-ACCESS read-create
			STATUS deprecated
			DESCRIPTION
				"Action to be taken with a packet: accept or deny it."
			::= { msanRemoteAccessFilterEntry 4 }

		
		-- 1.3.6.1.4.1.1332.1.1.5.3.18.2.1.5
		msanRemoteAccessFilterRowStatus OBJECT-TYPE
			SYNTAX RowStatus
			MAX-ACCESS read-create
			STATUS deprecated
			DESCRIPTION
				"The row status object controls the creation/deletion of rows in this table. 
				For row creation use createAndWait(5) [createAndGo(4) is not supported]."
			::= { msanRemoteAccessFilterEntry 5 }

		
		-- 1.3.6.1.4.1.1332.1.1.5.3.19
		msanDslSpecific OBJECT IDENTIFIER ::= { msanAdditionalConf 19 }

		
		-- 1.3.6.1.4.1.1332.1.1.5.3.19.1
		msanDslSpecificGlobal OBJECT IDENTIFIER ::= { msanDslSpecific 1 }

		
		-- 1.3.6.1.4.1.1332.1.1.5.3.19.1.1
		msanDslSpecificSystemState OBJECT-TYPE
			SYNTAX INTEGER
				{
				operational(4),
				notReady(12)
				}
			MAX-ACCESS read-only
			STATUS current
			DESCRIPTION
				"VDSL system operational state. For normal blade operation this value should be operational (4). 
				If value differ from 4, VDSL driver is not operational."
			::= { msanDslSpecificGlobal 1 }

		
		-- 1.3.6.1.4.1.1332.1.1.5.3.19.1.2
		msanDslSpecificSystemFirmware OBJECT-TYPE
			SYNTAX OCTET STRING
			MAX-ACCESS read-only
			STATUS current
			DESCRIPTION
				"VDSL firmware version."
			::= { msanDslSpecificGlobal 2 }

		
		-- 1.3.6.1.4.1.1332.1.1.5.3.19.1.3
		msanDslSpecificVectoringAdminMode OBJECT-TYPE
			SYNTAX INTEGER
				{
				enable(1),
				disable(2)
				}
			MAX-ACCESS read-write
			STATUS current
			DESCRIPTION
				"DSL vectoring admin mode."
			DEFVAL { disable }
			::= { msanDslSpecificGlobal 3 }

		
		-- 1.3.6.1.4.1.1332.1.1.5.3.19.3
		msanDslSpecificTable OBJECT-TYPE
			SYNTAX SEQUENCE OF MsanDslSpecificEntry
			MAX-ACCESS not-accessible
			STATUS current
			DESCRIPTION
				"Description."
			::= { msanDslSpecific 3 }

		
		-- 1.3.6.1.4.1.1332.1.1.5.3.19.3.1
		msanDslSpecificEntry OBJECT-TYPE
			SYNTAX MsanDslSpecificEntry
			MAX-ACCESS not-accessible
			STATUS current
			DESCRIPTION
				"Description."
			INDEX { ifIndex }
			::= { msanDslSpecificTable 1 }

		
		MsanDslSpecificEntry ::=
			SEQUENCE { 
				msanDslSpecificDsPsdMask
					OCTET STRING,
				msanDslSpecificUsPsdMask
					OCTET STRING,
				msanDslSpecificLineState
					INTEGER,
				msanDslSpecificMaxDelayDs
					Integer32,
				msanDslSpecificMaxDelayUs
					Integer32,
				msanDslSpecificMinProtectionDs
					Integer32,
				msanDslSpecificMinProtectionUs
					Integer32,
				msanDslSpecificMaxSnrmDs
					Unsigned32,
				msanDslSpecificMinSnrmDs
					Unsigned32,
				msanDslSpecificMaxSnrmUs
					Unsigned32,
				msanDslSpecificMinSnrmUs
					Unsigned32,
				msanDslSpecificRaUsNrmDs
					Unsigned32,
				msanDslSpecificRaUsNrmUs
					Unsigned32,
				msanDslSpecificRaUsTimeDs
					Unsigned32,
				msanDslSpecificRaUsTimeUs
					Unsigned32,
				msanDslSpecificRaDsNrmDs
					Unsigned32,
				msanDslSpecificRaDsNrmUs
					Unsigned32,
				msanDslSpecificRaDsTimeDs
					Unsigned32,
				msanDslSpecificRaDsTimeUs
					Unsigned32,
				msanDslSpecificL0Time
					Unsigned32,
				msanDslSpecificL2Time
					Unsigned32,
				msanDslSpecificL2Atpr
					Unsigned32,
				msanDslSpecificL2Atprt
					Unsigned32,
				msanDslSpecificScMaskDs
					OCTET STRING,
				msanDslSpecificScMaskUs
					OCTET STRING,
				msanDslSpecificRfiBands
					OCTET STRING,
				msanDslSpecificMaxNomPsdDs
					Integer32,
				msanDslSpecificMaxNomPsdUs
					Integer32,
				msanDslSpecificMaxNomAtpDs
					Unsigned32,
				msanDslSpecificMaxNomAtpUs
					Unsigned32,
				msanDslSpecificMaxAggRxPwrUs
					Integer32,
				msanDslSpecificClassMask
					INTEGER,
				msanDslSpecificDpboEsEL
					Unsigned32,
				msanDslSpecificUpboKLF
					INTEGER,
				msanDslSpecificUpboKL
					Unsigned32,
				msanDslSpecificSelt
					INTEGER,
				msanDslSpecificSeltStatus
					INTEGER,
				msanDslSpecificPhyRDs
					INTEGER,
				msanDslSpecificPhyRUs
					INTEGER,
				msanDslSpecificUpboUs1a
					INTEGER,
				msanDslSpecificUpboUs1b
					INTEGER,
				msanDslSpecificUpboUs2a
					INTEGER,
				msanDslSpecificUpboUs2b
					INTEGER,
				msanDslSpecificUpboUs3a
					INTEGER,
				msanDslSpecificUpboUs3b
					INTEGER,
				msanDslSpecificUpboUs4a
					INTEGER,
				msanDslSpecificUpboUs4b
					INTEGER,
				msanDslSpecificDpboEPsdMask
					OCTET STRING,
				msanDslSpecificDpboEsCmA
					Unsigned32,
				msanDslSpecificDpboEsCmB
					Unsigned32,
				msanDslSpecificDpboEsCmC
					Unsigned32,
				msanDslSpecificDpboMus
					Unsigned32,
				msanDslSpecificDpboFMin
					Unsigned32,
				msanDslSpecificDpboFMax
					Unsigned32,
				msanDslSpecificVectorModeEnable
					BITS,
				msanDslSpecificVectorModeState
					BITS
			 }

		-- 1.3.6.1.4.1.1332.1.1.5.3.19.3.1.1
		msanDslSpecificDsPsdMask OBJECT-TYPE
			SYNTAX OCTET STRING
			MAX-ACCESS read-write
			STATUS current
			DESCRIPTION
				"Unique name of the downstream PSD mask as defined by msanDslPsdMaskDsName."
			DEFVAL { "" }
			::= { msanDslSpecificEntry 1 }

		
		-- 1.3.6.1.4.1.1332.1.1.5.3.19.3.1.2
		msanDslSpecificUsPsdMask OBJECT-TYPE
			SYNTAX OCTET STRING
			MAX-ACCESS read-write
			STATUS current
			DESCRIPTION
				"Unique name of the upstream PSD mask as defined by msanDslPsdMaskUsName."
			DEFVAL { "ANSI_FTTCab_M11" }
			::= { msanDslSpecificEntry 2 }

		
		-- 1.3.6.1.4.1.1332.1.1.5.3.19.3.1.3
		msanDslSpecificLineState OBJECT-TYPE
			SYNTAX INTEGER
				{
				quiet(0),
				idle(1),
				activateInitTrain(2),
				activeFullPower(3),
				activeLowPower(4),
				unitFail(5),
				atpPtmLoopback(6),
				dspDigitalLoopback(7),
				lineDriverDigitalLoopback(8),
				hybridLoopback(9),
				testMode(10),
				loopDiagnosticsDeltInit(11),
				loopDiagnosticsDelt(12),
				seltInits(13),
				selt(14),
				lowPowerL3(15)
				}
			MAX-ACCESS read-only
			STATUS current
			DESCRIPTION
				"VDSL system operational state. For normal blade operation this value should be active(3). 
				If value is differ from 3, VDSL driver is not operational."
			::= { msanDslSpecificEntry 3 }

		
		-- 1.3.6.1.4.1.1332.1.1.5.3.19.3.1.4
		msanDslSpecificMaxDelayDs OBJECT-TYPE
			SYNTAX Integer32 (-1..63)
			UNITS "milliseconds"
			MAX-ACCESS read-write
			STATUS current
			DESCRIPTION
				"Maximum interleave delay for the downstream interleaved channel.
				-1 means that value from profile will be used (xdsl2ChConfProfMaxDelayDs).
				
				This object is created based on xdsl2ChConfProfMaxDelayDs (VDSL2-LINE MIB)"
			::= { msanDslSpecificEntry 4 }

		
		-- 1.3.6.1.4.1.1332.1.1.5.3.19.3.1.5
		msanDslSpecificMaxDelayUs OBJECT-TYPE
			SYNTAX Integer32 (-1..63)
			UNITS "milliseconds"
			MAX-ACCESS read-write
			STATUS current
			DESCRIPTION
				"Maximum interleave delay for the upstream interleaved channel.
				-1 means that value from profile will be used (xdsl2ChConfProfMaxDelayUs).
				
				This object is created based on xdsl2ChConfProfMaxDelayUs (VDSL2-LINE MIB)"
			::= { msanDslSpecificEntry 5 }

		
		-- 1.3.6.1.4.1.1332.1.1.5.3.19.3.1.6
		msanDslSpecificMinProtectionDs OBJECT-TYPE
			SYNTAX Integer32 (-1..160)
			UNITS "symbols"
			MAX-ACCESS read-write
			STATUS current
			DESCRIPTION
				"Downstream impulse noise protection.
				-1 means that value from profile will be used (xdsl2ChConfProfMinProtectionDs)
				
				This object is created based on xdsl2ChConfProfMinProtectionDs(VDSL2-LINE MIB)"
			::= { msanDslSpecificEntry 6 }

		
		-- 1.3.6.1.4.1.1332.1.1.5.3.19.3.1.7
		msanDslSpecificMinProtectionUs OBJECT-TYPE
			SYNTAX Integer32 (-1..160)
			MAX-ACCESS read-write
			STATUS current
			DESCRIPTION
				"Upstream impulse noise protection.
				-1 means that value from profile will be used (xdsl2ChConfProfMinProtectionUs)
				
				This object is created based on xdsl2ChConfProfMinProtectionUs(VDSL2-LINE MIB)"
			::= { msanDslSpecificEntry 7 }

		
		-- 1.3.6.1.4.1.1332.1.1.5.3.19.3.1.8
		msanDslSpecificMaxSnrmDs OBJECT-TYPE
			SYNTAX Unsigned32 (0..310)
			UNITS "0.1 dB"
			MAX-ACCESS read-write
			STATUS current
			DESCRIPTION
				"Downstream maximum Signal/Noise Margin.
				
				This object is created based on xdsl2LConfProfMaxSnrmDs (VDSL2-LINE MIB)"
			::= { msanDslSpecificEntry 8 }

		
		-- 1.3.6.1.4.1.1332.1.1.5.3.19.3.1.9
		msanDslSpecificMinSnrmDs OBJECT-TYPE
			SYNTAX Unsigned32 (0..310)
			UNITS "0.1 dB"
			MAX-ACCESS read-write
			STATUS current
			DESCRIPTION
				"Downstream minimum Signal/Noise Margin.
				
				This object is created based on xdsl2LConfProfMinSnrmDs (VDSL2-LINE MIB)"
			::= { msanDslSpecificEntry 9 }

		
		-- 1.3.6.1.4.1.1332.1.1.5.3.19.3.1.10
		msanDslSpecificMaxSnrmUs OBJECT-TYPE
			SYNTAX Unsigned32 (0..310)
			UNITS "0.1 dB"
			MAX-ACCESS read-write
			STATUS current
			DESCRIPTION
				"Upstream maximum Signal/Noise Margin.
				
				This object is created based on xdsl2LConfProfMaxSnrmUs (VDSL2-LINE MIB)"
			::= { msanDslSpecificEntry 10 }

		
		-- 1.3.6.1.4.1.1332.1.1.5.3.19.3.1.11
		msanDslSpecificMinSnrmUs OBJECT-TYPE
			SYNTAX Unsigned32 (0..310)
			UNITS "0.1 dB"
			MAX-ACCESS read-write
			STATUS current
			DESCRIPTION
				"Upstream minimum Signal/Noise Margin.
				
				This object is created based on xdsl2LConfProfMinSnrmUs (VDSL2-LINE MIB)"
			::= { msanDslSpecificEntry 11 }

		
		-- 1.3.6.1.4.1.1332.1.1.5.3.19.3.1.12
		msanDslSpecificRaUsNrmDs OBJECT-TYPE
			SYNTAX Unsigned32 (0..310)
			UNITS "0.1 dB"
			MAX-ACCESS read-write
			STATUS current
			DESCRIPTION
				"The Downstream Up-Shift Noise Margin (for dynamic rate adaptive
				mode).
				
				This object is created based on xdsl2LConfProfRaUsNrmDs (VDSL2-LINE MIB)"
			::= { msanDslSpecificEntry 12 }

		
		-- 1.3.6.1.4.1.1332.1.1.5.3.19.3.1.13
		msanDslSpecificRaUsNrmUs OBJECT-TYPE
			SYNTAX Unsigned32 (0..310)
			UNITS "0.1 dB"
			MAX-ACCESS read-write
			STATUS current
			DESCRIPTION
				"The Upstream Up-Shift Noise Margin (for dynamic rate adaptive mode).
				
				This object is created based on xdsl2LConfProfRaUsNrmUs (VDSL2-LINE MIB)"
			::= { msanDslSpecificEntry 13 }

		
		-- 1.3.6.1.4.1.1332.1.1.5.3.19.3.1.14
		msanDslSpecificRaUsTimeDs OBJECT-TYPE
			SYNTAX Unsigned32 (0..16383)
			UNITS "seconds"
			MAX-ACCESS read-write
			STATUS current
			DESCRIPTION
				"The Downstream Up-Shift Time Interval (for rate dynamic adaptive
				mode). 
				
				This object is created based on xdsl2LConfProfRaUsTimeDs (VDSL2-LINE MIB)"
			::= { msanDslSpecificEntry 14 }

		
		-- 1.3.6.1.4.1.1332.1.1.5.3.19.3.1.15
		msanDslSpecificRaUsTimeUs OBJECT-TYPE
			SYNTAX Unsigned32 (0..16383)
			UNITS "seconds"
			MAX-ACCESS read-write
			STATUS current
			DESCRIPTION
				"The Upstream Up-Shift Time Interval (for rate dynamic adaptive
				mode). 
				
				This object is created based on xdsl2LConfProfRaUsTimeUs (VDSL2-LINE MIB)"
			::= { msanDslSpecificEntry 15 }

		
		-- 1.3.6.1.4.1.1332.1.1.5.3.19.3.1.16
		msanDslSpecificRaDsNrmDs OBJECT-TYPE
			SYNTAX Unsigned32 (0..310)
			UNITS "0.1 dB"
			MAX-ACCESS read-write
			STATUS current
			DESCRIPTION
				"The Downstream Down-Shift Noise Margin (for dynamic rate adaptive
				mode).
				
				This object is created based on xdsl2LConfProfRaDsNrmDs (VDSL2-LINE MIB)"
			::= { msanDslSpecificEntry 16 }

		
		-- 1.3.6.1.4.1.1332.1.1.5.3.19.3.1.17
		msanDslSpecificRaDsNrmUs OBJECT-TYPE
			SYNTAX Unsigned32 (0..310)
			UNITS "0.1 dB"
			MAX-ACCESS read-write
			STATUS current
			DESCRIPTION
				"The Upstream Down-Shift Noise Margin (for dynamic rate adaptive mode).
				
				This object is created based on xdsl2LConfProfRaDsNrmUs (VDSL2-LINE MIB)"
			::= { msanDslSpecificEntry 17 }

		
		-- 1.3.6.1.4.1.1332.1.1.5.3.19.3.1.18
		msanDslSpecificRaDsTimeDs OBJECT-TYPE
			SYNTAX Unsigned32 (0..16383)
			UNITS "seconds"
			MAX-ACCESS read-write
			STATUS current
			DESCRIPTION
				"The Downstream Down-Shift Time Interval (for rate dynamic adaptive
				mode). 
				
				This object is created based on xdsl2LConfProfRaDsTimeDs (VDSL2-LINE MIB)"
			::= { msanDslSpecificEntry 18 }

		
		-- 1.3.6.1.4.1.1332.1.1.5.3.19.3.1.19
		msanDslSpecificRaDsTimeUs OBJECT-TYPE
			SYNTAX Unsigned32 (0..16383)
			UNITS "seconds"
			MAX-ACCESS read-write
			STATUS current
			DESCRIPTION
				"The Upstream Down-Shift Time Interval (for rate dynamic adaptive
				mode). 
				
				This object is created based on xdsl2LConfProfRaDsTimeUs (VDSL2-LINE MIB)"
			::= { msanDslSpecificEntry 19 }

		
		-- 1.3.6.1.4.1.1332.1.1.5.3.19.3.1.20
		msanDslSpecificL0Time OBJECT-TYPE
			SYNTAX Unsigned32 (0..255)
			UNITS "seconds"
			MAX-ACCESS read-write
			STATUS current
			DESCRIPTION
				"The minimum time between an exit from the L2 state and the next entry
				into the L2 state.
				
				This object is created based on xdsl2LConfProfL0Time (VDSL2-LINE MIB)"
			::= { msanDslSpecificEntry 20 }

		
		-- 1.3.6.1.4.1.1332.1.1.5.3.19.3.1.21
		msanDslSpecificL2Time OBJECT-TYPE
			SYNTAX Unsigned32 (0..255)
			UNITS "seconds"
			MAX-ACCESS read-write
			STATUS current
			DESCRIPTION
				"The minimum time between an entry into the L2 state and the first
				power trim in the L2 state and between two consecutive power trims in
				the L2 State.
				
				This object is created based on xdsl2LConfProfL2Time (VDSL2-LINE MIB)"
			::= { msanDslSpecificEntry 21 }

		
		-- 1.3.6.1.4.1.1332.1.1.5.3.19.3.1.22
		msanDslSpecificL2Atpr OBJECT-TYPE
			SYNTAX Unsigned32 (0..31)
			UNITS "dB"
			MAX-ACCESS read-write
			STATUS current
			DESCRIPTION
				"The maximum aggregate transmit power reduction that can be performed
				at transition of L0 to L2 state or through a single power trim in the
				L2 state.
				
				This object is created based on xdsl2LConfProfL2Atpr (VDSL2-LINE MIB)"
			::= { msanDslSpecificEntry 22 }

		
		-- 1.3.6.1.4.1.1332.1.1.5.3.19.3.1.23
		msanDslSpecificL2Atprt OBJECT-TYPE
			SYNTAX Unsigned32 (0..31)
			UNITS "dB"
			MAX-ACCESS read-write
			STATUS current
			DESCRIPTION
				"The total maximum aggregate transmit power reduction that can be
				performed in an L2 state.
				
				This object is created based on xdsl2LConfProfL2Atprt (VDSL2-LINE MIB)"
			::= { msanDslSpecificEntry 23 }

		
		-- 1.3.6.1.4.1.1332.1.1.5.3.19.3.1.24
		msanDslSpecificScMaskDs OBJECT-TYPE
			SYNTAX OCTET STRING (SIZE (0..512))
			MAX-ACCESS read-write
			STATUS current
			DESCRIPTION
				"Downstream Sub-carriers mask. A bitmap of 4096 bits that allows
				masking up to 4096 downstream sub-carriers. 
				If bit is set to '1', the respective downstream sub-carrier is
				masked (not used), and if set to '0', the respective sub-carrier is
				unmasked.
				
				This object is created based on xdsl2LConfProfScMaskDs (VDSL2-LINE MIB)
				"
			::= { msanDslSpecificEntry 24 }

		
		-- 1.3.6.1.4.1.1332.1.1.5.3.19.3.1.25
		msanDslSpecificScMaskUs OBJECT-TYPE
			SYNTAX OCTET STRING (SIZE (0..512))
			MAX-ACCESS read-write
			STATUS current
			DESCRIPTION
				"Upstream Sub-carriers mask. A bitmap of 4096 bits that allows
				masking up to 4096 downstream sub-carriers. 
				If bit is set to '1', the respective downstream sub-carrier is
				masked (not used), and if set to '0', the respective sub-carrier is
				unmasked.
				
				This object is created based on xdsl2LConfProfScMaskUs (VDSL2-LINE MIB)"
			::= { msanDslSpecificEntry 25 }

		
		-- 1.3.6.1.4.1.1332.1.1.5.3.19.3.1.26
		msanDslSpecificRfiBands OBJECT-TYPE
			SYNTAX OCTET STRING (SIZE (0..64))
			MAX-ACCESS read-write
			STATUS current
			DESCRIPTION
				"For VDLS, this configuration parameter defines the bands where the
				PSD shall be reduced. Each band shall be represented by a start and
				stop subcarrier indices with a subcarrier spacing of 4.3125 kHz. Up to
				16 bands may be specified. This parameter defines the RFI bands for
				both upstream and downstream          directions. Each RFI band is
				represented by 4 octets: 16 bit start sub-carrier index followed by a
				16 bit stop sub-carrier index.
				
				This object is created based on xdsl2LConfProfRfiBands (VDSL2-LINE MIB)
				"
			::= { msanDslSpecificEntry 26 }

		
		-- 1.3.6.1.4.1.1332.1.1.5.3.19.3.1.27
		msanDslSpecificMaxNomPsdDs OBJECT-TYPE
			SYNTAX Integer32 (-600..-300)
			UNITS "0.1 dBm/Hz"
			MAX-ACCESS read-write
			STATUS current
			DESCRIPTION
				"The maximum nominal transmit PSD in the downstream direction during
				initialization and Showtime. (0.1 dBm/Hz - physical values are -60 to
				-30 dBm/Hz).
				
				This object is created based on xdsl2LConfProfMaxNomPsdDs (VDSL2-LINE MIB)"
			::= { msanDslSpecificEntry 27 }

		
		-- 1.3.6.1.4.1.1332.1.1.5.3.19.3.1.28
		msanDslSpecificMaxNomPsdUs OBJECT-TYPE
			SYNTAX Integer32 (-600..-300)
			UNITS "0.1 dBm/Hz"
			MAX-ACCESS read-write
			STATUS current
			DESCRIPTION
				"The maximum nominal transmit PSD in the upstream direction during
				initialization and Showtime. (0.1 dBm/Hz - physical values are -60 to
				-30 dBm/Hz).
				
				This object is created based on xdsl2LConfProfMaxNomPsdUs (VDSL2-LINE MIB)"
			::= { msanDslSpecificEntry 28 }

		
		-- 1.3.6.1.4.1.1332.1.1.5.3.19.3.1.29
		msanDslSpecificMaxNomAtpDs OBJECT-TYPE
			SYNTAX Unsigned32 (0..255)
			UNITS "0.1 dBm"
			MAX-ACCESS read-write
			STATUS current
			DESCRIPTION
				"The maximum nominal aggregate transmit power in the downstream
				direction during initialization and Showtime. (0.1 dBm - physical
				values are 0 to 25.5 dBm).
				
				This object is created based on xdsl2LConfProfMaxNomAtpDs (VDSL2-LINE MIB)"
			::= { msanDslSpecificEntry 29 }

		
		-- 1.3.6.1.4.1.1332.1.1.5.3.19.3.1.30
		msanDslSpecificMaxNomAtpUs OBJECT-TYPE
			SYNTAX Unsigned32 (0..255)
			UNITS "0.1 dBm"
			MAX-ACCESS read-write
			STATUS current
			DESCRIPTION
				"The maximum nominal aggregate transmit power in the upstream
				direction during initialization and Showtime. (0.1 dBm - physical
				values are 0 to 25.5 dBm).
				
				This object is created based on xdsl2LConfProfMaxNomAtpUs (VDSL2-LINE MIB)"
			::= { msanDslSpecificEntry 30 }

		
		-- 1.3.6.1.4.1.1332.1.1.5.3.19.3.1.31
		msanDslSpecificMaxAggRxPwrUs OBJECT-TYPE
			SYNTAX Integer32 (-255..255)
			UNITS "0.1 dBm"
			MAX-ACCESS read-write
			STATUS current
			DESCRIPTION
				"The maximum upstream aggregate receive power over the relevant set of
				sub-carriers.. (0.1 dBm - physical values are -25.5 to 25.5 dBm).
				
				This object is created based on xdsl2LConfProfMaxAggRxPwrUs (VDSL2-LINE MIB)"
			::= { msanDslSpecificEntry 31 }

		
		-- 1.3.6.1.4.1.1332.1.1.5.3.19.3.1.32
		msanDslSpecificClassMask OBJECT-TYPE
			SYNTAX INTEGER
				{
				b998M1xA(1),
				b998M1xB(2),
				b998M1xNUS0(3),
				b998M2xA(4),
				b998M2xM(5),
				b998M2xB(6),
				b998M2xNUS0(7),
				b998E17M2xNUS0(8),
				b998E17M2xNUS0M(9),
				b998ADE17M2xNUS0M(10),
				b998ADE17M2xA(11),
				b998ADE17M2xB(12),
				b997M1cA7(13),
				b997M1xM8(14),
				b997M1xM(15),
				b997M2xM8(16),
				b997M2xA(17),
				b997M2xM(18),
				bHPE17M1NUS0(19),
				bHPE30M1NUS0(20),
				b997E17M2xA(21)
				}
			MAX-ACCESS read-write
			STATUS current
			DESCRIPTION
				"Predefined PSD mask.
				
				This object is created based on xdsl2LConfProfClassMask (VDSL2-LINE MIB)"
			DEFVAL { b998E17M2xNUS0 }
			::= { msanDslSpecificEntry 32 }

		
		-- 1.3.6.1.4.1.1332.1.1.5.3.19.3.1.35
		msanDslSpecificDpboEsEL OBJECT-TYPE
			SYNTAX Unsigned32 (0..511)
			UNITS "0.5 dB"
			MAX-ACCESS read-write
			STATUS current
			DESCRIPTION
				"Assumed electrical length of cables (E-side cables) connecting
				exchange based DSL services to a remote flexibility point (cabinet).
				The electrical length is defined as the loss (in dB) of an equivalent
				length of hypothetical cable at a reference frequency. 0 dB (coded as
				0) to 255.5 dB (coded as 511) in steps of 0.5 dB.
				
				This object is created based on xdsl2LConfProfDpboEsEL (VDSL2-LINE MIB)
				"
			::= { msanDslSpecificEntry 35 }

		
		-- 1.3.6.1.4.1.1332.1.1.5.3.19.3.1.36
		msanDslSpecificUpboKLF OBJECT-TYPE
			SYNTAX INTEGER
				{
				auto(1),
				override(2),
				disableUpbo(3)
				}
			MAX-ACCESS read-write
			STATUS current
			DESCRIPTION
				"Defines the upstream power backoff force mode.
				The three possible mode values are:
				 auto(1),
				 override(2),
				 disableUpbo(3).
				
				This object is created based on xdsl2LConfProfUpboKLF (VDSL2-LINE MIB)"
			::= { msanDslSpecificEntry 36 }

		
		-- 1.3.6.1.4.1.1332.1.1.5.3.19.3.1.37
		msanDslSpecificUpboKL OBJECT-TYPE
			SYNTAX Unsigned32 (0..1280)
			UNITS "0.1 dB"
			MAX-ACCESS read-write
			STATUS current
			DESCRIPTION
				"This configuration parameter defines the electrical length expressed
				in dB at 1MHz, configured by the CO-MIB. The value ranges from 0
				(coded as 0) to 128 dB (coded as 1280) in steps of 0.1 dB.
				
				This object is created based on xdsl2LConfProfUpboKL (VDSL2-LINE MIB)"
			::= { msanDslSpecificEntry 37 }

		
		-- 1.3.6.1.4.1.1332.1.1.5.3.19.3.1.39
		msanDslSpecificSelt OBJECT-TYPE
			SYNTAX INTEGER
				{
				inhibit(1),
				force(2)
				}
			MAX-ACCESS read-write
			STATUS current
			DESCRIPTION
				"Defines whether the line should be forced into the SELT (Single-Ended Loop Testing) 
				diagnostics mode by the near-end xTU of this line.
				Upon completion of the loop diagnostic mode procedures, the Access Node shall set 
				this object to 'inhibit'.
				The results of the SELT procedure are stored in the table msanDslSeltStatusTable.
				The status of the loop diagnostic procedure is indicated by msanDslSpecificSeltStatus.
				"
			DEFVAL { inhibit }
			::= { msanDslSpecificEntry 39 }

		
		-- 1.3.6.1.4.1.1332.1.1.5.3.19.3.1.40
		msanDslSpecificSeltStatus OBJECT-TYPE
			SYNTAX INTEGER
				{
				none(1),
				success(2),
				inProgress(3),
				unsupported(4),
				cannotRun(5),
				aborted(6),
				failed(7),
				illegalMode(8),
				adminUp(9),
				tableFull(10),
				noResources(11),
				undefinedError(12)
				}
			MAX-ACCESS read-only
			STATUS current
			DESCRIPTION
				"SELT (Single-Ended Loop Testing) status of dsl line. "
			::= { msanDslSpecificEntry 40 }

		
		-- 1.3.6.1.4.1.1332.1.1.5.3.19.3.1.41
		msanDslSpecificPhyRDs OBJECT-TYPE
			SYNTAX INTEGER
				{
				disabled(1),
				enabled(2),
				auto(3)
				}
			MAX-ACCESS read-write
			STATUS current
			DESCRIPTION
				"Physical Layer Retransmission configuration in the downstream direction. "
			DEFVAL { auto }
			::= { msanDslSpecificEntry 41 }

		
		-- 1.3.6.1.4.1.1332.1.1.5.3.19.3.1.42
		msanDslSpecificPhyRUs OBJECT-TYPE
			SYNTAX INTEGER
				{
				disabled(1),
				enabled(2),
				auto(3)
				}
			MAX-ACCESS read-write
			STATUS current
			DESCRIPTION
				"Physical Layer Retransmission configuration in the upstream direction. "
			DEFVAL { auto }
			::= { msanDslSpecificEntry 42 }

		
		-- 1.3.6.1.4.1.1332.1.1.5.3.19.3.1.43
		msanDslSpecificUpboUs1a OBJECT-TYPE
			SYNTAX INTEGER (4000..8095)
			UNITS "0.01 dBm/Hz"
			MAX-ACCESS read-write
			STATUS current
			DESCRIPTION
				"ITU-T G.997.1, paragraph #7.3.1.2.14 (UPBOPSD-pb)
				
				Parameter defines the 'a' reference parameter of the UPBO reference PSD 
				used to compute the upstream power back-off for the upstream band. 
				A UPBO PSD defined for each band shall consist of two parameters [a, b]. 
				
				Parameter 'a' (xdsl2LConfProfUpboPsdA) ranges from 40 dBm/Hz (coded as 
				4000) to 80.95 dBm/Hz (coded as 8095) in steps of 0.01 dBm/Hz; and 
				parameter 'b' (xdsl2LConfProfUpboPsdB) ranges from 0 dBm/Hz (coded as 0) 
				to 40.95 dBm/Hz (coded as 4095) in steps of 0.01 dBm/Hz.  
				
				The UPBO reference PSD at the frequency 'f' expressed in MHz shall be 
				equal to '-a-b(SQRT(f))'. Setting xdsl2LConfProfUpboPsdA to 4000 and 
				xdsl2LConfProfUpboPsdB to 0 is  a special configuration to disable UPBO in 
				the respective  upstream band."
			DEFVAL { 4000 }
			::= { msanDslSpecificEntry 43 }

		
		-- 1.3.6.1.4.1.1332.1.1.5.3.19.3.1.44
		msanDslSpecificUpboUs1b OBJECT-TYPE
			SYNTAX INTEGER (0..4095)
			UNITS "0.01 dBm/Hz"
			MAX-ACCESS read-write
			STATUS current
			DESCRIPTION
				"ITU-T G.997.1, paragraph #7.3.1.2.14 (UPBOPSD-pb)
				
				Parameter defines the 'b' reference parameter of the UPBO 
				reference PSD used to compute the upstream power back-off for the 
				upstream band. Parameter 'b' (xdsl2LConfProfUpboPsdB) ranges from 
				0 dBm/Hz (coded as 0) to 40.95 dBm/Hz (coded as 4095) in steps of 0.01 dBm/Hz. 
				"
			DEFVAL { 0 }
			::= { msanDslSpecificEntry 44 }

		
		-- 1.3.6.1.4.1.1332.1.1.5.3.19.3.1.45
		msanDslSpecificUpboUs2a OBJECT-TYPE
			SYNTAX INTEGER (4000..8095)
			UNITS "0.01 dBm/Hz"
			MAX-ACCESS read-write
			STATUS current
			DESCRIPTION
				"ITU-T G.997.1, paragraph #7.3.1.2.14 (UPBOPSD-pb)
				
				Parameter defines the 'a' reference parameter of the UPBO reference PSD 
				used to compute the upstream power back-off for the upstream band. 
				A UPBO PSD defined for each band shall consist of two parameters [a, b]. 
				
				Parameter 'a' (xdsl2LConfProfUpboPsdA) ranges from 40 dBm/Hz (coded as 
				4000) to 80.95 dBm/Hz (coded as 8095) in steps of 0.01 dBm/Hz; and 
				parameter 'b' (xdsl2LConfProfUpboPsdB) ranges from 0 dBm/Hz (coded as 0) 
				to 40.95 dBm/Hz (coded as 4095) in steps of 0.01 dBm/Hz.  
				
				The UPBO reference PSD at the frequency 'f' expressed in MHz shall be 
				equal to '-a-b(SQRT(f))'. Setting xdsl2LConfProfUpboPsdA to 4000 and 
				xdsl2LConfProfUpboPsdB to 0 is  a special configuration to disable UPBO in 
				the respective  upstream band."
			DEFVAL { 4000 }
			::= { msanDslSpecificEntry 45 }

		
		-- 1.3.6.1.4.1.1332.1.1.5.3.19.3.1.46
		msanDslSpecificUpboUs2b OBJECT-TYPE
			SYNTAX INTEGER (0..4095)
			UNITS "0.01 dBm/Hz"
			MAX-ACCESS read-write
			STATUS current
			DESCRIPTION
				"ITU-T G.997.1, paragraph #7.3.1.2.14 (UPBOPSD-pb)
				
				Parameter defines the 'b' reference parameter of the UPBO 
				reference PSD used to compute the upstream power back-off for the 
				upstream band. Parameter 'b' (xdsl2LConfProfUpboPsdB) ranges from 
				0 dBm/Hz (coded as 0) to 40.95 dBm/Hz (coded as 4095) in steps of 0.01 dBm/Hz. 
				"
			DEFVAL { 0 }
			::= { msanDslSpecificEntry 46 }

		
		-- 1.3.6.1.4.1.1332.1.1.5.3.19.3.1.47
		msanDslSpecificUpboUs3a OBJECT-TYPE
			SYNTAX INTEGER (4000..8095)
			UNITS "0.01 dBm/Hz"
			MAX-ACCESS read-write
			STATUS current
			DESCRIPTION
				"ITU-T G.997.1, paragraph #7.3.1.2.14 (UPBOPSD-pb)
				
				Parameter defines the 'a' reference parameter of the UPBO reference PSD 
				used to compute the upstream power back-off for the upstream band. 
				A UPBO PSD defined for each band shall consist of two parameters [a, b]. 
				
				Parameter 'a' (xdsl2LConfProfUpboPsdA) ranges from 40 dBm/Hz (coded as 
				4000) to 80.95 dBm/Hz (coded as 8095) in steps of 0.01 dBm/Hz; and 
				parameter 'b' (xdsl2LConfProfUpboPsdB) ranges from 0 dBm/Hz (coded as 0) 
				to 40.95 dBm/Hz (coded as 4095) in steps of 0.01 dBm/Hz.  
				
				The UPBO reference PSD at the frequency 'f' expressed in MHz shall be 
				equal to '-a-b(SQRT(f))'. Setting xdsl2LConfProfUpboPsdA to 4000 and 
				xdsl2LConfProfUpboPsdB to 0 is  a special configuration to disable UPBO in 
				the respective  upstream band."
			DEFVAL { 4000 }
			::= { msanDslSpecificEntry 47 }

		
		-- 1.3.6.1.4.1.1332.1.1.5.3.19.3.1.48
		msanDslSpecificUpboUs3b OBJECT-TYPE
			SYNTAX INTEGER (0..4095)
			UNITS "0.01 dBm/Hz"
			MAX-ACCESS read-write
			STATUS current
			DESCRIPTION
				"ITU-T G.997.1, paragraph #7.3.1.2.14 (UPBOPSD-pb)
				
				Parameter defines the 'b' reference parameter of the UPBO 
				reference PSD used to compute the upstream power back-off for the 
				upstream band. Parameter 'b' (xdsl2LConfProfUpboPsdB) ranges from 
				0 dBm/Hz (coded as 0) to 40.95 dBm/Hz (coded as 4095) in steps of 0.01 dBm/Hz. 
				"
			DEFVAL { 0 }
			::= { msanDslSpecificEntry 48 }

		
		-- 1.3.6.1.4.1.1332.1.1.5.3.19.3.1.49
		msanDslSpecificUpboUs4a OBJECT-TYPE
			SYNTAX INTEGER (4000..8095)
			UNITS "0.01 dBm/Hz"
			MAX-ACCESS read-write
			STATUS current
			DESCRIPTION
				"ITU-T G.997.1, paragraph #7.3.1.2.14 (UPBOPSD-pb)
				
				Parameter defines the 'a' reference parameter of the UPBO reference PSD 
				used to compute the upstream power back-off for the upstream band. 
				A UPBO PSD defined for each band shall consist of two parameters [a, b]. 
				
				Parameter 'a' (xdsl2LConfProfUpboPsdA) ranges from 40 dBm/Hz (coded as 
				4000) to 80.95 dBm/Hz (coded as 8095) in steps of 0.01 dBm/Hz; and 
				parameter 'b' (xdsl2LConfProfUpboPsdB) ranges from 0 dBm/Hz (coded as 0) 
				to 40.95 dBm/Hz (coded as 4095) in steps of 0.01 dBm/Hz.  
				
				The UPBO reference PSD at the frequency 'f' expressed in MHz shall be 
				equal to '-a-b(SQRT(f))'. Setting xdsl2LConfProfUpboPsdA to 4000 and 
				xdsl2LConfProfUpboPsdB to 0 is  a special configuration to disable UPBO in 
				the respective  upstream band."
			DEFVAL { 4000 }
			::= { msanDslSpecificEntry 49 }

		
		-- 1.3.6.1.4.1.1332.1.1.5.3.19.3.1.50
		msanDslSpecificUpboUs4b OBJECT-TYPE
			SYNTAX INTEGER (0..4095)
			UNITS "0.01 dBm/Hz"
			MAX-ACCESS read-write
			STATUS current
			DESCRIPTION
				"ITU-T G.997.1, paragraph #7.3.1.2.14 (UPBOPSD-pb)
				
				Parameter defines the 'b' reference parameter of the UPBO 
				reference PSD used to compute the upstream power back-off for the 
				upstream band. Parameter 'b' (xdsl2LConfProfUpboPsdB) ranges from 
				0 dBm/Hz (coded as 0) to 40.95 dBm/Hz (coded as 4095) in steps of 0.01 dBm/Hz. 
				"
			DEFVAL { 0 }
			::= { msanDslSpecificEntry 50 }

		
		-- 1.3.6.1.4.1.1332.1.1.5.3.19.3.1.51
		msanDslSpecificDpboEPsdMask OBJECT-TYPE
			SYNTAX OCTET STRING
			MAX-ACCESS read-write
			STATUS current
			DESCRIPTION
				"DPbo EPsd mask name.
				It should be of the downstream PSD mask as defined by msanDslPsdMaskDsName."
			DEFVAL { "" }
			::= { msanDslSpecificEntry 51 }

		
		-- 1.3.6.1.4.1.1332.1.1.5.3.19.3.1.52
		msanDslSpecificDpboEsCmA OBJECT-TYPE
			SYNTAX Unsigned32 (0..640)
			UNITS "2^-8"
			MAX-ACCESS read-create
			STATUS current
			DESCRIPTION
				"ITU-T G.997.1, paragraph #7.3.1.2.13 (DPBOESCMA)
				
				The E-side Cable Model parameter A (DPBOESCMA) of the cable  model 
				(DPBOESCM) for cables connecting exchange-based DSL services to a remote 
				flexibility point (cabinet), that hosts the xTU-C that is subject to spectrally shaped 
				downstream power back- off (DPBO) depending on this value.
				Possible values shall be coded as unsigned integers representing a scalar value 
				from -1 (coded as 0) to 1.5 (coded as 640) in steps of 2-8 All values in the range are 
				valid.
				"
			REFERENCE
				"ITU-T G.997.1, paragraph #7.3.1.2.13 (DPBOESCMA)"
			DEFVAL { 0 }
			::= { msanDslSpecificEntry 52 }

		
		-- 1.3.6.1.4.1.1332.1.1.5.3.19.3.1.53
		msanDslSpecificDpboEsCmB OBJECT-TYPE
			SYNTAX Unsigned32 (0..640)
			UNITS "2^-8"
			MAX-ACCESS read-create
			STATUS current
			DESCRIPTION
				"ITU-T G.997.1, paragraph #7.3.1.2.13 (DPBOESCMB)
				
				The E-side Cable Model parameter B (DPBOESCMB) of the cable  model 
				(DPBOESCM) for cables connecting exchange-based DSL services to a remote 
				flexibility point (cabinet), that hosts the xTU-C that is subject to spectrally shaped 
				downstream power back- off (DPBO) depending on this value.
				Possible values shall be coded as unsigned integers representing a scalar value 
				from -1 (coded as 0) to 1.5 (coded as 640) in steps of 2-8 All values in the range are 
				valid.
				"
			REFERENCE
				"ITU-T G.997.1, paragraph #7.3.1.2.13 (DPBOESCMB)"
			DEFVAL { 0 }
			::= { msanDslSpecificEntry 53 }

		
		-- 1.3.6.1.4.1.1332.1.1.5.3.19.3.1.54
		msanDslSpecificDpboEsCmC OBJECT-TYPE
			SYNTAX Unsigned32 (0..640)
			UNITS "2^-8"
			MAX-ACCESS read-create
			STATUS current
			DESCRIPTION
				"ITU-T G.997.1, paragraph #7.3.1.2.13 (DPBOESCMC)
				
				The E-side Cable Model parameter C (DPBOESCMC) of the cable  model 
				(DPBOESCM) for cables connecting exchange-based DSL services to a remote 
				flexibility point (cabinet), that hosts the xTU-C that is subject to spectrally shaped 
				downstream power back- off (DPBO) depending on this value.
				Possible values shall be coded as unsigned integers representing a scalar value 
				from -1 (coded as 0) to 1.5 (coded as 640) in steps of 2-8 All values in the range are 
				valid.
				"
			REFERENCE
				"ITU-T G.997.1, paragraph #7.3.1.2.13 (DPBOESCMC)"
			DEFVAL { 0 }
			::= { msanDslSpecificEntry 54 }

		
		-- 1.3.6.1.4.1.1332.1.1.5.3.19.3.1.55
		msanDslSpecificDpboMus OBJECT-TYPE
			SYNTAX Unsigned32 (0..255)
			UNITS "0.5 dBm/Hz"
			MAX-ACCESS read-create
			STATUS current
			DESCRIPTION
				"ITU-T G.997.1, paragraph #7.3.1.2.13 (DPBOMUS)
				
				Assumed Minimum Usable receive PSD mask (in dBm/Hz) for exchange-based 
				services.
				It shall be coded as an unsigned integer representing a PSD mask level from 
				0 dBm/Hz  (coded as 0) to -127.5 dBm/Hz (coded as 255) in steps of 0.5  dBm/Hz.  
				All values in the range are valid.
				"
			REFERENCE
				"ITU-T G.997.1, paragraph #7.3.1.2.13 (DPBOMUS)"
			DEFVAL { 0 }
			::= { msanDslSpecificEntry 55 }

		
		-- 1.3.6.1.4.1.1332.1.1.5.3.19.3.1.56
		msanDslSpecificDpboFMin OBJECT-TYPE
			SYNTAX Unsigned32 (0..2048)
			UNITS "4.3125 kHz"
			MAX-ACCESS read-create
			STATUS current
			DESCRIPTION
				"ITU-T G.997.1, paragraph #7.3.1.2.13 (DPBOFMIN)
				
				Minimum frequency from which the DPBO shall be applied. 
				It ranges from 0 kHz (coded as 0) to 8832 kHz (coded as 2048) in steps of 4.3125 kHz.
				"
			REFERENCE
				"ITU-T G.997.1, paragraph #7.3.1.2.13 (DPBOFMIN)"
			DEFVAL { 32 }
			::= { msanDslSpecificEntry 56 }

		
		-- 1.3.6.1.4.1.1332.1.1.5.3.19.3.1.57
		msanDslSpecificDpboFMax OBJECT-TYPE
			SYNTAX Unsigned32 (32..6956)
			UNITS "4.3125 kHz"
			MAX-ACCESS read-create
			STATUS current
			DESCRIPTION
				"ITU-T G.997.1, paragraph #7.3.1.2.13 (DPBOFMAX)
				
				Maximum frequency at which DPBO may be applied. 
				It ranges from 138 kHz (coded as 32) to 29997.75 kHz (coded as 6956) in steps of 4.3125 kHz.
				"
			REFERENCE
				"ITU-T G.997.1, paragraph #7.3.1.2.13 (DPBOFMAX)"
			DEFVAL { 512 }
			::= { msanDslSpecificEntry 57 }

		
		-- 1.3.6.1.4.1.1332.1.1.5.3.19.3.1.58
		msanDslSpecificVectorModeEnable OBJECT-TYPE
			SYNTAX BITS
				{
				vdsl2Only(0),
				vectoringFriendlyDs(1),
				vectoringFriendlyDsUs(2),
				vectoringFully(3)
				}
			MAX-ACCESS read-write
			STATUS current
			DESCRIPTION
				"Type of vectoring initialization to be allowed by the VTU-O on the line.
				ITU-T G.997.1, paragraph #7.3.1.13.9  (VECTORMODE_ENABLE).
				
				This configuration parameter defines the vectoring initialization type to be 
				allowed by the VTU-O on the line. It is coded in a bit-map representation (0 
				if not allowed, 1 if allowed).
				
				"
			DEFVAL { {  } }
			::= { msanDslSpecificEntry 58 }

		
		-- 1.3.6.1.4.1.1332.1.1.5.3.19.3.1.59
		msanDslSpecificVectorModeState OBJECT-TYPE
			SYNTAX BITS
				{
				vdsl2Only(0),
				vectoringFriendlyDs(1),
				vectoringFriendlyDsUs(2),
				vectoringFully(3)
				}
			MAX-ACCESS read-only
			STATUS current
			DESCRIPTION
				"Current vectoring initialization type on the line.
				
				Line can operate only in common vdsl2 (non/vectoring) 
				or in one of vectoring modes therefore only one bit may be set to 1. "
			::= { msanDslSpecificEntry 59 }

		
		-- 1.3.6.1.4.1.1332.1.1.5.3.19.4
		msanDslPsdMaskDsTable OBJECT-TYPE
			SYNTAX SEQUENCE OF MsanDslPsdMaskDsEntry
			MAX-ACCESS not-accessible
			STATUS current
			DESCRIPTION
				"Management of Downstream PSD Mask (G997.1 #7.3.1.2.9 )"
			::= { msanDslSpecific 4 }

		
		-- 1.3.6.1.4.1.1332.1.1.5.3.19.4.1
		msanDslPsdMaskDsEntry OBJECT-TYPE
			SYNTAX MsanDslPsdMaskDsEntry
			MAX-ACCESS not-accessible
			STATUS current
			DESCRIPTION
				"Description."
			INDEX { msanDslPsdMaskDsName }
			::= { msanDslPsdMaskDsTable 1 }

		
		MsanDslPsdMaskDsEntry ::=
			SEQUENCE { 
				msanDslPsdMaskDsName
					OCTET STRING,
				msanDslPsdMaskDsType
					INTEGER,
				msanDslPsdMaskDsShape
					Xdsl2PsdMaskDs,
				msanDslPsdMaskDsRowStatus
					RowStatus
			 }

		-- 1.3.6.1.4.1.1332.1.1.5.3.19.4.1.1
		msanDslPsdMaskDsName OBJECT-TYPE
			SYNTAX OCTET STRING (SIZE (1..32))
			MAX-ACCESS not-accessible
			STATUS current
			DESCRIPTION
				"Downstream custom PSD mask name."
			::= { msanDslPsdMaskDsEntry 1 }

		
		-- 1.3.6.1.4.1.1332.1.1.5.3.19.4.1.2
		msanDslPsdMaskDsType OBJECT-TYPE
			SYNTAX INTEGER
				{
				default(1),
				configured(2)
				}
			MAX-ACCESS read-only
			STATUS current
			DESCRIPTION
				"Downstream custom PSD mask type.
				
				Possible values:
				default(1) - Default mask prepared by vendor, user is not allowed to delete or change it
				configured(2) - Mask created by user
				"
			DEFVAL { management }
			::= { msanDslPsdMaskDsEntry 2 }

		
		-- 1.3.6.1.4.1.1332.1.1.5.3.19.4.1.3
		msanDslPsdMaskDsShape OBJECT-TYPE
			SYNTAX Xdsl2PsdMaskDs
			MAX-ACCESS read-write
			STATUS current
			DESCRIPTION
				"The downstream PSD mask applicable at the U-C2 reference point.
				
				This parameter is used only for G.992.5 and it may impose PSD
				restrictions (breakpoints) in addition to the Limit PSD mask
				defined in G.992.5.
				This is a string of 32 pairs of values in the following
				structure:
				Octets 0-1 - Index of the first subcarrier used in the context of
				 	             a first breakpoint.
				Octet 2    - The PSD reduction for the subcarrier indicated in
				 	             octets 0 and 1.
				Octets 3-5 - Same, for a second breakpoint.
				Octets 6-8 - Same, for a third breakpoint.
				This architecture continues until octets 94-95, which are
				associated with a 32nd breakpoint.
				Each subcarrier index is an unsigned number in the range 0 and
				NSCds-1.  Each PSD reduction value is in the range 0 (0 dBm/Hz) to
				255 (-127.5 dBm/Hz) with steps of 0.5 dBm/Hz.  Valid values are in
				the range 0 to 190 (0 to -95 dBm/Hz).
				When the number of breakpoints is less than 32, all remaining
				octets are set to the value '0'.  Note that the content of this
				object should be correlated with the subcarrier mask and with
				the RFI setup.
				"
			DEFVAL { '0'h }
			::= { msanDslPsdMaskDsEntry 3 }

		
		-- 1.3.6.1.4.1.1332.1.1.5.3.19.4.1.4
		msanDslPsdMaskDsRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanDslPsdMaskDsEntry 4 }

		
		-- 1.3.6.1.4.1.1332.1.1.5.3.19.5
		msanDslPsdMaskUsTable OBJECT-TYPE
			SYNTAX SEQUENCE OF MsanDslPsdMaskUsEntry
			MAX-ACCESS not-accessible
			STATUS current
			DESCRIPTION
				"Management of Upstream PSD Mask (G997.1 #7.3.1.2.9 )"
			::= { msanDslSpecific 5 }

		
		-- 1.3.6.1.4.1.1332.1.1.5.3.19.5.1
		msanDslPsdMaskUsEntry OBJECT-TYPE
			SYNTAX MsanDslPsdMaskUsEntry
			MAX-ACCESS not-accessible
			STATUS current
			DESCRIPTION
				"Description."
			INDEX { msanDslPsdMaskUsName }
			::= { msanDslPsdMaskUsTable 1 }

		
		MsanDslPsdMaskUsEntry ::=
			SEQUENCE { 
				msanDslPsdMaskUsName
					OCTET STRING,
				msanDslPsdMaskUsType
					INTEGER,
				msanDslPsdMaskUsShape
					Xdsl2PsdMaskUs,
				msanDslPsdMaskUsRowStatus
					RowStatus
			 }

		-- 1.3.6.1.4.1.1332.1.1.5.3.19.5.1.1
		msanDslPsdMaskUsName OBJECT-TYPE
			SYNTAX OCTET STRING (SIZE (1..32))
			MAX-ACCESS not-accessible
			STATUS current
			DESCRIPTION
				"Upstream custom PSD mask name."
			::= { msanDslPsdMaskUsEntry 1 }

		
		-- 1.3.6.1.4.1.1332.1.1.5.3.19.5.1.2
		msanDslPsdMaskUsType OBJECT-TYPE
			SYNTAX INTEGER
				{
				default(1),
				configured(2)
				}
			MAX-ACCESS read-only
			STATUS current
			DESCRIPTION
				"Downstream custom PSD mask type.
				
				Possible values:
				default(1) - Default mask prepared by vendor, user is not allowed to delete or change it
				configured(2) - Mask created by user"
			DEFVAL { management }
			::= { msanDslPsdMaskUsEntry 2 }

		
		-- 1.3.6.1.4.1.1332.1.1.5.3.19.5.1.3
		msanDslPsdMaskUsShape OBJECT-TYPE
			SYNTAX Xdsl2PsdMaskUs
			MAX-ACCESS read-write
			STATUS current
			DESCRIPTION
				"The upstream PSD mask applicable at the U-R2 reference point.
				
				This parameter is used only for G.992.5, and it may impose PSD
				restrictions (breakpoints) in addition to the Limit PSD mask
				defined in G.992.5.
				This is a string of 16 pairs of values in the following
				structure:
				Octets 0-1 - Index of the first subcarrier used in the context of
				 	             a first breakpoint.
				Octet 2    - The PSD reduction for the subcarrier indicated in
				 	             octets 0 and 1.
				Octets 3-5 - Same, for a second breakpoint.
				Octets 6-8 - Same, for a third breakpoint.
				This architecture continues until octets 9-47, which are
				associated with a 16th breakpoint.
				Each subcarrier index is an unsigned number in the range 0 and
				NSCus-1.  Each PSD reduction value is in the range 0 (0 dBm/Hz) to
				255 (-127.5 dBm/Hz) with steps of 0.5 dBm/Hz.  Valid values are in
				the range 0 to 190 (0 to -95 dBm/Hz).
				When the number of breakpoints is less than 16, all remaining
				octets are set to the value '0'.  Note that the content of this
				object should be correlated with the subcarrier mask and with
				the RFI setup.
				"
			DEFVAL { '0'h }
			::= { msanDslPsdMaskUsEntry 3 }

		
		-- 1.3.6.1.4.1.1332.1.1.5.3.19.5.1.4
		msanDslPsdMaskUsRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanDslPsdMaskUsEntry 4 }

		
		-- 1.3.6.1.4.1.1332.1.1.5.3.19.6
		msanDslSeltStatusTable OBJECT-TYPE
			SYNTAX SEQUENCE OF MsanDslSeltStatusEntry
			MAX-ACCESS not-accessible
			STATUS current
			DESCRIPTION
				"Description."
			::= { msanDslSpecific 6 }

		
		-- 1.3.6.1.4.1.1332.1.1.5.3.19.6.1
		msanDslSeltStatusEntry OBJECT-TYPE
			SYNTAX MsanDslSeltStatusEntry
			MAX-ACCESS not-accessible
			STATUS current
			DESCRIPTION
				"Description."
			INDEX { ifIndex }
			::= { msanDslSeltStatusTable 1 }

		
		MsanDslSeltStatusEntry ::=
			SEQUENCE { 
				msanDslSeltStatusNoiseType
					OCTET STRING,
				msanDslSeltStatusNoiseMrgDs
					Integer32,
				msanDslSeltStatusNoiseMrgUs
					Integer32,
				msanDslSeltStatusNumTonesDs
					Integer32,
				msanDslSeltStatusNumTonesUs
					Integer32,
				msanDslSeltStatusMaxRateDs
					Integer32,
				msanDslSeltStatusMaxRateUs
					Integer32,
				msanDslSeltStatusCableType
					OCTET STRING,
				msanDslSeltStatusCableLenght
					Integer32,
				msanDslSeltStatusFitError
					Integer32,
				msanDslSeltStatusLoopTermination
					INTEGER
			 }

		-- 1.3.6.1.4.1.1332.1.1.5.3.19.6.1.1
		msanDslSeltStatusNoiseType OBJECT-TYPE
			SYNTAX OCTET STRING (SIZE (0..30))
			MAX-ACCESS read-only
			STATUS current
			DESCRIPTION
				"Noise type."
			::= { msanDslSeltStatusEntry 1 }

		
		-- 1.3.6.1.4.1.1332.1.1.5.3.19.6.1.2
		msanDslSeltStatusNoiseMrgDs OBJECT-TYPE
			SYNTAX Integer32
			UNITS "0.1 dB"
			MAX-ACCESS read-only
			STATUS current
			DESCRIPTION
				"Noise margin in DS direction. [0.1 dB]"
			::= { msanDslSeltStatusEntry 2 }

		
		-- 1.3.6.1.4.1.1332.1.1.5.3.19.6.1.3
		msanDslSeltStatusNoiseMrgUs OBJECT-TYPE
			SYNTAX Integer32
			UNITS "0.1 dB"
			MAX-ACCESS read-only
			STATUS current
			DESCRIPTION
				"Noise margin in US direction. [0.1 dB]"
			::= { msanDslSeltStatusEntry 3 }

		
		-- 1.3.6.1.4.1.1332.1.1.5.3.19.6.1.4
		msanDslSeltStatusNumTonesDs OBJECT-TYPE
			SYNTAX Integer32
			MAX-ACCESS read-only
			STATUS current
			DESCRIPTION
				"Number of tones used for SELT in DS direction. "
			::= { msanDslSeltStatusEntry 4 }

		
		-- 1.3.6.1.4.1.1332.1.1.5.3.19.6.1.5
		msanDslSeltStatusNumTonesUs OBJECT-TYPE
			SYNTAX Integer32
			MAX-ACCESS read-only
			STATUS current
			DESCRIPTION
				"Number of tones used for SELT in US direction. "
			::= { msanDslSeltStatusEntry 5 }

		
		-- 1.3.6.1.4.1.1332.1.1.5.3.19.6.1.6
		msanDslSeltStatusMaxRateDs OBJECT-TYPE
			SYNTAX Integer32
			UNITS "kbps"
			MAX-ACCESS read-only
			STATUS current
			DESCRIPTION
				"Maximum Downstream capacity [kbps]"
			::= { msanDslSeltStatusEntry 6 }

		
		-- 1.3.6.1.4.1.1332.1.1.5.3.19.6.1.7
		msanDslSeltStatusMaxRateUs OBJECT-TYPE
			SYNTAX Integer32
			UNITS "kbps"
			MAX-ACCESS read-only
			STATUS current
			DESCRIPTION
				"Maximum Upstream capacity [kbps]"
			::= { msanDslSeltStatusEntry 7 }

		
		-- 1.3.6.1.4.1.1332.1.1.5.3.19.6.1.8
		msanDslSeltStatusCableType OBJECT-TYPE
			SYNTAX OCTET STRING (SIZE (0..20))
			MAX-ACCESS read-only
			STATUS current
			DESCRIPTION
				"DSL line loop type."
			::= { msanDslSeltStatusEntry 8 }

		
		-- 1.3.6.1.4.1.1332.1.1.5.3.19.6.1.9
		msanDslSeltStatusCableLenght OBJECT-TYPE
			SYNTAX Integer32
			UNITS "m"
			MAX-ACCESS read-only
			STATUS current
			DESCRIPTION
				"DSL line loop lenght. [m]"
			::= { msanDslSeltStatusEntry 9 }

		
		-- 1.3.6.1.4.1.1332.1.1.5.3.19.6.1.10
		msanDslSeltStatusFitError OBJECT-TYPE
			SYNTAX Integer32
			UNITS "%"
			MAX-ACCESS read-only
			STATUS current
			DESCRIPTION
				"DSL Line lenght fit error. [%]"
			::= { msanDslSeltStatusEntry 10 }

		
		-- 1.3.6.1.4.1.1332.1.1.5.3.19.6.1.11
		msanDslSeltStatusLoopTermination OBJECT-TYPE
			SYNTAX INTEGER
				{
				unknown(1),
				open(2),
				short(3)
				}
			MAX-ACCESS read-only
			STATUS current
			DESCRIPTION
				"Type of DSL line termination. "
			::= { msanDslSeltStatusEntry 11 }

		
		-- 1.3.6.1.4.1.1332.1.1.5.3.19.7
		msanDslAtmPvcTable OBJECT-TYPE
			SYNTAX SEQUENCE OF MsanDslAtmPvcEntry
			MAX-ACCESS not-accessible
			STATUS current
			DESCRIPTION
				"ATM PVC configuration of the ADSL port"
			::= { msanDslSpecific 7 }

		
		-- 1.3.6.1.4.1.1332.1.1.5.3.19.7.1
		msanDslAtmPvcEntry OBJECT-TYPE
			SYNTAX MsanDslAtmPvcEntry
			MAX-ACCESS not-accessible
			STATUS current
			DESCRIPTION
				"Description."
			INDEX { ifIndex }
			::= { msanDslAtmPvcTable 1 }

		
		MsanDslAtmPvcEntry ::=
			SEQUENCE { 
				msanDslAtmPvcVpi
					Integer32,
				msanDslAtmPvcVci
					Integer32
			 }

		-- 1.3.6.1.4.1.1332.1.1.5.3.19.7.1.2
		msanDslAtmPvcVpi OBJECT-TYPE
			SYNTAX Integer32 (-1..255)
			MAX-ACCESS read-write
			STATUS current
			DESCRIPTION
				"ATM Virtual path identifier of the ADSL PVC interface.
				Value -1 indicates that parameter has not been defined."
			DEFVAL { -1 }
			::= { msanDslAtmPvcEntry 2 }

		
		-- 1.3.6.1.4.1.1332.1.1.5.3.19.7.1.3
		msanDslAtmPvcVci OBJECT-TYPE
			SYNTAX Integer32 (31..65535)
			MAX-ACCESS read-write
			STATUS current
			DESCRIPTION
				"ATM Virtual channel identifier of the ADSL PVC interface.
				Value 31 indicates that parameter has not been defined."
			DEFVAL { 31 }
			::= { msanDslAtmPvcEntry 3 }

		
		-- 1.3.6.1.4.1.1332.1.1.5.3.20
		msanPortMirroring OBJECT IDENTIFIER ::= { msanAdditionalConf 20 }

		
		-- 1.3.6.1.4.1.1332.1.1.5.3.20.1
		msanPortMirroringGlobal OBJECT IDENTIFIER ::= { msanPortMirroring 1 }

		
		-- 1.3.6.1.4.1.1332.1.1.5.3.20.2
		msanPortMirroringTable OBJECT-TYPE
			SYNTAX SEQUENCE OF MsanPortMirroringEntry
			MAX-ACCESS not-accessible
			STATUS current
			DESCRIPTION
				"Description."
			::= { msanPortMirroring 2 }

		
		-- 1.3.6.1.4.1.1332.1.1.5.3.20.2.1
		msanPortMirroringEntry OBJECT-TYPE
			SYNTAX MsanPortMirroringEntry
			MAX-ACCESS not-accessible
			STATUS current
			DESCRIPTION
				"Description."
			INDEX { msanPortMirroringSessionId }
			::= { msanPortMirroringTable 1 }

		
		MsanPortMirroringEntry ::=
			SEQUENCE { 
				msanPortMirroringSessionId
					Integer32,
				msanPortMirroringAdminState
					INTEGER,
				msanPortMirroringDestPort
					Integer32
			 }

		-- 1.3.6.1.4.1.1332.1.1.5.3.20.2.1.1
		msanPortMirroringSessionId OBJECT-TYPE
			SYNTAX Integer32
			MAX-ACCESS not-accessible
			STATUS current
			DESCRIPTION
				"The Session number of this mirroring entry."
			::= { msanPortMirroringEntry 1 }

		
		-- 1.3.6.1.4.1.1332.1.1.5.3.20.2.1.2
		msanPortMirroringAdminState OBJECT-TYPE
			SYNTAX INTEGER
				{
				disable(0),
				enable(1)
				}
			MAX-ACCESS read-write
			STATUS current
			DESCRIPTION
				"The status of this port mirroring session. "
			::= { msanPortMirroringEntry 2 }

		
		-- 1.3.6.1.4.1.1332.1.1.5.3.20.2.1.3
		msanPortMirroringDestPort OBJECT-TYPE
			SYNTAX Integer32
			MAX-ACCESS read-write
			STATUS current
			DESCRIPTION
				"The port which traffic from the mirrored ports will be sent to.
				Port value is ifIndex from ifTable. Value 0 means, port is not defined."
			::= { msanPortMirroringEntry 3 }

		
		-- 1.3.6.1.4.1.1332.1.1.5.3.20.3
		msanPortMirroringMemberTable OBJECT-TYPE
			SYNTAX SEQUENCE OF MsanPortMirroringMemberEntry
			MAX-ACCESS not-accessible
			STATUS current
			DESCRIPTION
				"Description."
			::= { msanPortMirroring 3 }

		
		-- 1.3.6.1.4.1.1332.1.1.5.3.20.3.1
		msanPortMirroringMemberEntry OBJECT-TYPE
			SYNTAX MsanPortMirroringMemberEntry
			MAX-ACCESS not-accessible
			STATUS current
			DESCRIPTION
				"Description."
			INDEX { msanPortMirroringSessionId, msanPortMirroringMemberSrcPort }
			::= { msanPortMirroringMemberTable 1 }

		
		MsanPortMirroringMemberEntry ::=
			SEQUENCE { 
				msanPortMirroringMemberSrcPort
					Integer32,
				msanPortMirroringMemberDirection
					INTEGER,
				msanPortMirroringMemberRowStatus
					RowStatus
			 }

		-- 1.3.6.1.4.1.1332.1.1.5.3.20.3.1.1
		msanPortMirroringMemberSrcPort OBJECT-TYPE
			SYNTAX Integer32
			MAX-ACCESS not-accessible
			STATUS current
			DESCRIPTION
				"The port from which traffic will be sent to the destination port. "
			::= { msanPortMirroringMemberEntry 1 }

		
		-- 1.3.6.1.4.1.1332.1.1.5.3.20.3.1.2
		msanPortMirroringMemberDirection OBJECT-TYPE
			SYNTAX INTEGER
				{
				tx(1),
				rx(2),
				txAndRx(3)
				}
			MAX-ACCESS read-create
			STATUS current
			DESCRIPTION
				"The direction of the data to be mirrored on this source port. "
			::= { msanPortMirroringMemberEntry 2 }

		
		-- 1.3.6.1.4.1.1332.1.1.5.3.20.3.1.3
		msanPortMirroringMemberRowStatus OBJECT-TYPE
			SYNTAX RowStatus
			MAX-ACCESS read-create
			STATUS current
			DESCRIPTION
				"The row status object controls the creation/deletion of rows in this table. 
				For row creation use createAndWait(5) [createAndGo(4) is not supported]."
			::= { msanPortMirroringMemberEntry 3 }

		
		-- 1.3.6.1.4.1.1332.1.1.5.3.21
		msanResetWithDelay OBJECT IDENTIFIER ::= { msanAdditionalConf 21 }

		
		-- 1.3.6.1.4.1.1332.1.1.5.3.21.1
		msanResetWithDelayGlobal OBJECT IDENTIFIER ::= { msanResetWithDelay 1 }

		
		-- 1.3.6.1.4.1.1332.1.1.5.3.21.1.1
		msanResetDelay OBJECT-TYPE
			SYNTAX INTEGER (0..3600)
			UNITS "seconds"
			MAX-ACCESS read-write
			STATUS current
			DESCRIPTION
				"Delay in seconds before reset will be performed. If set to 0, reset countdown is stopped and reset is cancelled. 
				This parameter returns number of seconds before reset. If it returns 0, reset with delay was not initiated. "
			::= { msanResetWithDelayGlobal 1 }

		
		-- 1.3.6.1.4.1.1332.1.1.5.3.22
		msanMacTable OBJECT IDENTIFIER ::= { msanAdditionalConf 22 }

		
		-- 1.3.6.1.4.1.1332.1.1.5.3.22.1
		msanMacTableGlobal OBJECT IDENTIFIER ::= { msanMacTable 1 }

		
		-- 1.3.6.1.4.1.1332.1.1.5.3.22.1.1
		msanMacTableLength OBJECT-TYPE
			SYNTAX Unsigned32
			MAX-ACCESS read-only
			STATUS current
			DESCRIPTION
				"Maximum number of MAC addresses (total length of MAC table). "
			::= { msanMacTableGlobal 1 }

		
		-- 1.3.6.1.4.1.1332.1.1.5.3.22.1.2
		msanMacTableUsed OBJECT-TYPE
			SYNTAX Unsigned32
			MAX-ACCESS read-only
			STATUS current
			DESCRIPTION
				"Number of entries in MAC table."
			::= { msanMacTableGlobal 2 }

		
		-- 1.3.6.1.4.1.1332.1.1.5.3.22.2
		msanMacTableCAMTable OBJECT-TYPE
			SYNTAX SEQUENCE OF MsanMacTableCAMEntry
			MAX-ACCESS not-accessible
			STATUS current
			DESCRIPTION
				"Description."
			::= { msanMacTable 2 }

		
		-- 1.3.6.1.4.1.1332.1.1.5.3.22.2.1
		msanMacTableCAMEntry OBJECT-TYPE
			SYNTAX MsanMacTableCAMEntry
			MAX-ACCESS not-accessible
			STATUS current
			DESCRIPTION
				"Description."
			INDEX { msanMacTableCAMIndex }
			::= { msanMacTableCAMTable 1 }

		
		MsanMacTableCAMEntry ::=
			SEQUENCE { 
				msanMacTableCAMIndex
					Integer32,
				msanMacTableMacAddress
					MacAddress,
				msanMacTablePort
					Integer32,
				msanMacTableVLAN
					Integer32,
				msanMacTableType
					INTEGER
			 }

		-- 1.3.6.1.4.1.1332.1.1.5.3.22.2.1.1
		msanMacTableCAMIndex OBJECT-TYPE
			SYNTAX Integer32
			MAX-ACCESS not-accessible
			STATUS current
			DESCRIPTION
				"Id of the CAM entry."
			::= { msanMacTableCAMEntry 1 }

		
		-- 1.3.6.1.4.1.1332.1.1.5.3.22.2.1.2
		msanMacTableMacAddress OBJECT-TYPE
			SYNTAX MacAddress
			MAX-ACCESS read-only
			STATUS current
			DESCRIPTION
				"MAC address of the CAM entry. "
			::= { msanMacTableCAMEntry 2 }

		
		-- 1.3.6.1.4.1.1332.1.1.5.3.22.2.1.3
		msanMacTablePort OBJECT-TYPE
			SYNTAX Integer32
			MAX-ACCESS read-only
			STATUS current
			DESCRIPTION
				"The port on which MAC address was learned or defined. "
			::= { msanMacTableCAMEntry 3 }

		
		-- 1.3.6.1.4.1.1332.1.1.5.3.22.2.1.4
		msanMacTableVLAN OBJECT-TYPE
			SYNTAX Integer32
			MAX-ACCESS read-only
			STATUS current
			DESCRIPTION
				"VLAN id of the learned or defined MAC address. "
			::= { msanMacTableCAMEntry 4 }

		
		-- 1.3.6.1.4.1.1332.1.1.5.3.22.2.1.5
		msanMacTableType OBJECT-TYPE
			SYNTAX INTEGER
				{
				learned(1),
				managment(2),
				static(3)
				}
			MAX-ACCESS read-only
			STATUS current
			DESCRIPTION
				"Type of the MAC address.  "
			::= { msanMacTableCAMEntry 5 }

		
		-- 1.3.6.1.4.1.1332.1.1.5.3.23
		msanAcs OBJECT IDENTIFIER ::= { msanAdditionalConf 23 }

		
		-- 1.3.6.1.4.1.1332.1.1.5.3.23.1
		msanAcsGlobal OBJECT IDENTIFIER ::= { msanAcs 1 }

		
		-- 1.3.6.1.4.1.1332.1.1.5.3.23.1.1
		msanAcsServerUrl OBJECT-TYPE
			SYNTAX OCTET STRING
			MAX-ACCESS read-write
			STATUS current
			DESCRIPTION
				"This is URL of the ACS server in form:  <http|https>://<IP>|<hostname>[:<port>]/[<path>/]
				If hostname is used, msanDnsIpAddress and msanAcsDomainName must also be set. "
			::= { msanAcsGlobal 1 }

		
		-- 1.3.6.1.4.1.1332.1.1.5.3.23.1.2
		msanPrimaryDnsIpAddress OBJECT-TYPE
			SYNTAX IpAddress
			MAX-ACCESS read-write
			STATUS current
			DESCRIPTION
				"This specifies the primary DNS server IP . "
			::= { msanAcsGlobal 2 }

		
		-- 1.3.6.1.4.1.1332.1.1.5.3.23.1.3
		msanSecondaryDnsIpAddress OBJECT-TYPE
			SYNTAX IpAddress
			MAX-ACCESS read-write
			STATUS current
			DESCRIPTION
				"This specifies the secondary DNS server IP . "
			::= { msanAcsGlobal 3 }

		
		-- 1.3.6.1.4.1.1332.1.1.5.3.23.1.4
		msanAcsDomainName OBJECT-TYPE
			SYNTAX OCTET STRING
			MAX-ACCESS read-write
			STATUS current
			DESCRIPTION
				"Domain name. "
			::= { msanAcsGlobal 4 }

		
		-- 1.3.6.1.4.1.1332.1.1.5.3.23.1.5
		msanAcsClientStatus OBJECT-TYPE
			SYNTAX INTEGER
				{
				enable(1),
				disable(2)
				}
			MAX-ACCESS read-write
			STATUS current
			DESCRIPTION
				"ACS client administrative status."
			::= { msanAcsGlobal 5 }

		
		-- 1.3.6.1.4.1.1332.1.1.5.3.23.1.6
		msanAcsBackupConf OBJECT-TYPE
			SYNTAX INTEGER
				{
				enable(1),
				disable(2)
				}
			MAX-ACCESS read-write
			STATUS current
			DESCRIPTION
				"Back up configuration (as CLI script) to ACS server."
			::= { msanAcsGlobal 6 }

		
		-- 1.3.6.1.4.1.1332.1.1.5.3.24
		msanStp OBJECT IDENTIFIER ::= { msanAdditionalConf 24 }

		
		-- 1.3.6.1.4.1.1332.1.1.5.3.24.1
		msanStpGlobal OBJECT IDENTIFIER ::= { msanStp 1 }

		
		-- 1.3.6.1.4.1.1332.1.1.5.3.24.2
		msanStpBpduFilterTable OBJECT-TYPE
			SYNTAX SEQUENCE OF MsanStpBpduFilterEntry
			MAX-ACCESS not-accessible
			STATUS current
			DESCRIPTION
				"Description."
			::= { msanStp 2 }

		
		-- 1.3.6.1.4.1.1332.1.1.5.3.24.2.1
		msanStpBpduFilterEntry OBJECT-TYPE
			SYNTAX MsanStpBpduFilterEntry
			MAX-ACCESS not-accessible
			STATUS current
			DESCRIPTION
				"Description."
			INDEX { ifIndex }
			::= { msanStpBpduFilterTable 1 }

		
		MsanStpBpduFilterEntry ::=
			SEQUENCE { 
				msanStpBpduFilter
					INTEGER
			 }

		-- 1.3.6.1.4.1.1332.1.1.5.3.24.2.1.1
		msanStpBpduFilter OBJECT-TYPE
			SYNTAX INTEGER
				{
				disable(0),
				enable(1)
				}
			MAX-ACCESS read-write
			STATUS current
			DESCRIPTION
				"Defines how BPDU packets are handled in case stp_port_state is disabled. 
				
				0   disable - If stp_port_state is disabled on interface, forward all
				BPDUs unchanged to all other interfaces that also have stp_port_state
				disabled. 
				1   enable - If stp_port_state is disabled on interface, drop all
				BPDUs received on the interface. "
			::= { msanStpBpduFilterEntry 1 }

		
		-- 1.3.6.1.4.1.1332.1.1.5.3.24.3
		msanStpSwitchConfigGroup OBJECT IDENTIFIER ::= { msanStp 3 }

		
		-- 1.3.6.1.4.1.1332.1.1.5.3.24.3.1
		msanStpCstBridgePriority OBJECT-TYPE
			SYNTAX Unsigned32 (0..61440)
			MAX-ACCESS read-write
			STATUS current
			DESCRIPTION
				"The CSTP bridge priority in instance 0. The priority is 
				in the increments of 4096. The recommended default value is 32768."
			::= { msanStpSwitchConfigGroup 1 }

		
		-- 1.3.6.1.4.1.1332.1.1.5.3.24.4
		msanStpMstTable OBJECT-TYPE
			SYNTAX SEQUENCE OF MsanStpMstEntry
			MAX-ACCESS not-accessible
			STATUS current
			DESCRIPTION
				"Description."
			REFERENCE
				"agentStpMstTable - 1.3.6.1.4.1.6132.1.1.1.2.15.10"
			::= { msanStp 4 }

		
		-- 1.3.6.1.4.1.1332.1.1.5.3.24.4.1
		msanStpMstEntry OBJECT-TYPE
			SYNTAX MsanStpMstEntry
			MAX-ACCESS not-accessible
			STATUS current
			DESCRIPTION
				"Description."
			INDEX { msanStpMstId }
			::= { msanStpMstTable 1 }

		
		MsanStpMstEntry ::=
			SEQUENCE { 
				msanStpMstId
					Unsigned32,
				msanStpMstBridgePriority
					Unsigned32,
				msanStpMstRowStatus
					RowStatus
			 }

		-- 1.3.6.1.4.1.1332.1.1.5.3.24.4.1.1
		msanStpMstId OBJECT-TYPE
			SYNTAX Unsigned32
			MAX-ACCESS not-accessible
			STATUS current
			DESCRIPTION
				"The MSTP instance ID. Instance 0 is not shown. "
			::= { msanStpMstEntry 1 }

		
		-- 1.3.6.1.4.1.1332.1.1.5.3.24.4.1.2
		msanStpMstBridgePriority OBJECT-TYPE
			SYNTAX Unsigned32 (0..61440)
			MAX-ACCESS read-create
			STATUS current
			DESCRIPTION
				"The MSTP bridge priority in a specific instance. The priority is 
				in the increments of 4096. The recommended default value is 32768."
			::= { msanStpMstEntry 2 }

		
		-- 1.3.6.1.4.1.1332.1.1.5.3.24.4.1.3
		msanStpMstRowStatus OBJECT-TYPE
			SYNTAX RowStatus
			MAX-ACCESS read-create
			STATUS current
			DESCRIPTION
				"The MSTP instance status. Instance 0 is not shown. 
				
				Supported values:
				active(1) - valid instance.
				createAndGo(4) - used to create a new instance. 
				destroy(6)     - removes an instance."
			::= { msanStpMstEntry 3 }

		
		-- 1.3.6.1.4.1.1332.1.1.5.3.24.5
		msanStpMstVlanTable OBJECT-TYPE
			SYNTAX SEQUENCE OF MsanStpMstVlanEntry
			MAX-ACCESS not-accessible
			STATUS current
			DESCRIPTION
				"Description."
			REFERENCE
				"agentStpMstTable - 1.3.6.1.4.1.6132.1.1.1.2.15.10"
			::= { msanStp 5 }

		
		-- 1.3.6.1.4.1.1332.1.1.5.3.24.5.1
		msanStpMstVlanEntry OBJECT-TYPE
			SYNTAX MsanStpMstVlanEntry
			MAX-ACCESS not-accessible
			STATUS current
			DESCRIPTION
				"Description."
			INDEX { dot1qVlanIndex, msanStpMstId }
			::= { msanStpMstVlanTable 1 }

		
		MsanStpMstVlanEntry ::=
			SEQUENCE { 
				msanStpMstVlanRowStatus
					RowStatus
			 }

		-- 1.3.6.1.4.1.1332.1.1.5.3.24.5.1.1
		msanStpMstVlanRowStatus OBJECT-TYPE
			SYNTAX RowStatus
			MAX-ACCESS read-create
			STATUS current
			DESCRIPTION
				"The association status of an MSTP instance and a VLAN.
				Instance 0 is not shown. 
				
				Supported values:
				active(1)      - valid association between an MSTP instance and a VLAN.
				createAndGo(4) - used to create a new association between an MSTP instance and a VLAN.
				destroy(6)     - removes the association between an MSTP instance and a VLAN."
			::= { msanStpMstVlanEntry 1 }

		
		-- 1.3.6.1.4.1.1332.1.1.5.3.24.6
		msanStpMstPortTable OBJECT-TYPE
			SYNTAX SEQUENCE OF MsanStpMstPortEntry
			MAX-ACCESS not-accessible
			STATUS current
			DESCRIPTION
				"MST port table."
			REFERENCE
				"agentStpMstPortTable - 1.3.6.1.4.1.6132.1.1.1.2.15.11"
			::= { msanStp 6 }

		
		-- 1.3.6.1.4.1.1332.1.1.5.3.24.6.1
		msanStpMstPortEntry OBJECT-TYPE
			SYNTAX MsanStpMstPortEntry
			MAX-ACCESS not-accessible
			STATUS current
			DESCRIPTION
				"MST port entry."
			INDEX { ifIndex, msanStpMstId }
			::= { msanStpMstPortTable 1 }

		
		MsanStpMstPortEntry ::=
			SEQUENCE { 
				msanStpMstPortPathCost
					Unsigned32,
				msanStpMstPortPriority
					Unsigned32
			 }

		-- 1.3.6.1.4.1.1332.1.1.5.3.24.6.1.1
		msanStpMstPortPathCost OBJECT-TYPE
			SYNTAX Unsigned32 (0..200000000)
			MAX-ACCESS read-write
			STATUS current
			DESCRIPTION
				"The MSTP port path cost in a specific instance. The default value will 
				correspond to the recommendation specified in IEEE 802.1s Table 13-2 
				which varies depending upon link speed.
				Instance 0 is not shown."
			::= { msanStpMstPortEntry 1 }

		
		-- 1.3.6.1.4.1.1332.1.1.5.3.24.6.1.2
		msanStpMstPortPriority OBJECT-TYPE
			SYNTAX Unsigned32 (0..240)
			MAX-ACCESS read-write
			STATUS current
			DESCRIPTION
				"The MSTP port priority in a specific instance. The priority is 
				in the increments of 16. The default value is 128.
				Instance 0 is not shown."
			DEFVAL { 128 }
			::= { msanStpMstPortEntry 2 }

		
		-- 1.3.6.1.4.1.1332.1.1.5.3.24.7
		msanStpPortTable OBJECT-TYPE
			SYNTAX SEQUENCE OF MsanStpPortEntry
			MAX-ACCESS not-accessible
			STATUS current
			DESCRIPTION
				"Description."
			::= { msanStp 7 }

		
		-- 1.3.6.1.4.1.1332.1.1.5.3.24.7.1
		msanStpPortEntry OBJECT-TYPE
			SYNTAX MsanStpPortEntry
			MAX-ACCESS not-accessible
			STATUS current
			DESCRIPTION
				"Description."
			INDEX { ifIndex }
			::= { msanStpPortTable 1 }

		
		MsanStpPortEntry ::=
			SEQUENCE { 
				msanStpPortHelloTime
					Integer32
			 }

		-- 1.3.6.1.4.1.1332.1.1.5.3.24.7.1.1
		msanStpPortHelloTime OBJECT-TYPE
			SYNTAX Integer32 (0..10)
			MAX-ACCESS read-write
			STATUS current
			DESCRIPTION
				"Hello time for the STP port. The default value is 0 (Not configured)."
			::= { msanStpPortEntry 1 }

		
		-- 1.3.6.1.4.1.1332.1.1.5.3.24.8
		msanStpCstPortTable OBJECT-TYPE
			SYNTAX SEQUENCE OF MsanStpCstPortEntry
			MAX-ACCESS not-accessible
			STATUS current
			DESCRIPTION
				"Description."
			::= { msanStp 8 }

		
		-- 1.3.6.1.4.1.1332.1.1.5.3.24.8.1
		msanStpCstPortEntry OBJECT-TYPE
			SYNTAX MsanStpCstPortEntry
			MAX-ACCESS not-accessible
			STATUS current
			DESCRIPTION
				"Description."
			INDEX { ifIndex }
			::= { msanStpCstPortTable 1 }

		
		MsanStpCstPortEntry ::=
			SEQUENCE { 
				msanStpCstPortPathCost
					Unsigned32,
				msanStpCstExtPortPathCost
					Unsigned32
			 }

		-- 1.3.6.1.4.1.1332.1.1.5.3.24.8.1.1
		msanStpCstPortPathCost OBJECT-TYPE
			SYNTAX Unsigned32 (0..200000000)
			MAX-ACCESS read-write
			STATUS current
			DESCRIPTION
				"The MSTP port path cost in CIST. The default value will 
				correspond to the recommendation specified in IEEE 802.1s Table 13-2 
				which varies depending upon link speed.
				"
			::= { msanStpCstPortEntry 1 }

		
		-- 1.3.6.1.4.1.1332.1.1.5.3.24.8.1.2
		msanStpCstExtPortPathCost OBJECT-TYPE
			SYNTAX Unsigned32 (0..200000000)
			MAX-ACCESS read-write
			STATUS current
			DESCRIPTION
				"The MSTP external port path cost in CIST. The default value varies depending upon the link speed."
			::= { msanStpCstPortEntry 2 }

		
		-- 1.3.6.1.4.1.1332.1.1.5.3.25
		msanAuthentication OBJECT IDENTIFIER ::= { msanAdditionalConf 25 }

		
		-- 1.3.6.1.4.1.1332.1.1.5.3.25.1
		msanAuthenticationGlobal OBJECT IDENTIFIER ::= { msanAuthentication 1 }

		
		-- 1.3.6.1.4.1.1332.1.1.5.3.25.2
		msanAuthenticationListCreate OBJECT-TYPE
			SYNTAX DisplayString (SIZE (1..15))
			MAX-ACCESS read-write
			STATUS deprecated
			DESCRIPTION
				"Authentication List Create
				If set to a non empty string, creates a new Authentication List for
				configuration."
			::= { msanAuthentication 2 }

		
		-- 1.3.6.1.4.1.1332.1.1.5.3.25.3
		msanAuthenticationListTable OBJECT-TYPE
			SYNTAX SEQUENCE OF MsanAuthenticationListEntry
			MAX-ACCESS not-accessible
			STATUS current
			DESCRIPTION
				"Description."
			::= { msanAuthentication 3 }

		
		-- 1.3.6.1.4.1.1332.1.1.5.3.25.3.1
		msanAuthenticationListEntry OBJECT-TYPE
			SYNTAX MsanAuthenticationListEntry
			MAX-ACCESS not-accessible
			STATUS current
			DESCRIPTION
				"Description."
			INDEX { msanAuthenticationListName }
			::= { msanAuthenticationListTable 1 }

		
		MsanAuthenticationListEntry ::=
			SEQUENCE { 
				msanAuthenticationListName
					DisplayString,
				msanAuthenticationListMethod1
					INTEGER,
				msanAuthenticationListMethod2
					INTEGER,
				msanAuthenticationListMethod3
					INTEGER,
				msanAuthenticationListStatus
					RowStatus
			 }

		-- 1.3.6.1.4.1.1332.1.1.5.3.25.3.1.1
		msanAuthenticationListName OBJECT-TYPE
			SYNTAX DisplayString (SIZE (1..15))
			MAX-ACCESS not-accessible
			STATUS current
			DESCRIPTION
				"Authenticaiton List Name
				Unique name used to identify the Authentication List from other tables."
			::= { msanAuthenticationListEntry 1 }

		
		-- 1.3.6.1.4.1.1332.1.1.5.3.25.3.1.2
		msanAuthenticationListMethod1 OBJECT-TYPE
			SYNTAX INTEGER
				{
				local(1),
				radius(2),
				reject(3),
				tacacs(4)
				}
			MAX-ACCESS read-create
			STATUS current
			DESCRIPTION
				"Authenticion List Method 1
				Configures the first authentication method to use when this list is 
				specified."
			::= { msanAuthenticationListEntry 2 }

		
		-- 1.3.6.1.4.1.1332.1.1.5.3.25.3.1.3
		msanAuthenticationListMethod2 OBJECT-TYPE
			SYNTAX INTEGER
				{
				undefined(1),
				local(2),
				radius(3),
				reject(4),
				tacacs(5)
				}
			MAX-ACCESS read-create
			STATUS current
			DESCRIPTION
				"Authenticion List Method 2
				Configures the second authentication method to use when this list is 
				specified."
			::= { msanAuthenticationListEntry 3 }

		
		-- 1.3.6.1.4.1.1332.1.1.5.3.25.3.1.4
		msanAuthenticationListMethod3 OBJECT-TYPE
			SYNTAX INTEGER
				{
				undefined(1),
				local(2),
				radius(3),
				reject(4),
				tacacs(5)
				}
			MAX-ACCESS read-create
			STATUS current
			DESCRIPTION
				"Authenticion List Method 3
				Configures the third authentication method to use when this list is 
				specified."
			::= { msanAuthenticationListEntry 4 }

		
		-- 1.3.6.1.4.1.1332.1.1.5.3.25.3.1.5
		msanAuthenticationListStatus OBJECT-TYPE
			SYNTAX RowStatus
			MAX-ACCESS read-create
			STATUS current
			DESCRIPTION
				"The status of the Authentication List.
				
				Supported values:
				active(1)      - indicates a valid Authenticaiton List
				createAndGo (4) 
				destroy(6)     - removes the Authentication List."
			::= { msanAuthenticationListEntry 5 }

		
		-- 1.3.6.1.4.1.1332.1.1.5.3.26
		msanPortSecurity OBJECT IDENTIFIER ::= { msanAdditionalConf 26 }

		
		-- 1.3.6.1.4.1.1332.1.1.5.3.26.1
		msanPortSecurityGlobal OBJECT IDENTIFIER ::= { msanPortSecurity 1 }

		
		-- 1.3.6.1.4.1.1332.1.1.5.3.26.2
		msanPortSecurityStatMacTable OBJECT-TYPE
			SYNTAX SEQUENCE OF MsanPortSecurityStatMacEntry
			MAX-ACCESS not-accessible
			STATUS current
			DESCRIPTION
				"Description."
			::= { msanPortSecurity 2 }

		
		-- 1.3.6.1.4.1.1332.1.1.5.3.26.2.1
		msanPortSecurityStatMacEntry OBJECT-TYPE
			SYNTAX MsanPortSecurityStatMacEntry
			MAX-ACCESS not-accessible
			STATUS current
			DESCRIPTION
				"Description."
			INDEX { msanPortSecurityStatMacIf, msanPortSecurityStatMacVlanId, msanPortSecurityStatMacMacAddress }
			::= { msanPortSecurityStatMacTable 1 }

		
		MsanPortSecurityStatMacEntry ::=
			SEQUENCE { 
				msanPortSecurityStatMacIf
					Integer32,
				msanPortSecurityStatMacVlanId
					INTEGER,
				msanPortSecurityStatMacMacAddress
					MacAddress,
				msanPortSecurityStatMacRowStatus
					RowStatus
			 }

		-- 1.3.6.1.4.1.1332.1.1.5.3.26.2.1.1
		msanPortSecurityStatMacIf OBJECT-TYPE
			SYNTAX Integer32
			MAX-ACCESS not-accessible
			STATUS current
			DESCRIPTION
				"Unique numerical identification of the interface."
			::= { msanPortSecurityStatMacEntry 1 }

		
		-- 1.3.6.1.4.1.1332.1.1.5.3.26.2.1.2
		msanPortSecurityStatMacVlanId OBJECT-TYPE
			SYNTAX INTEGER (1..4094)
			MAX-ACCESS not-accessible
			STATUS current
			DESCRIPTION
				"VLAN identification."
			::= { msanPortSecurityStatMacEntry 2 }

		
		-- 1.3.6.1.4.1.1332.1.1.5.3.26.2.1.3
		msanPortSecurityStatMacMacAddress OBJECT-TYPE
			SYNTAX MacAddress
			MAX-ACCESS not-accessible
			STATUS current
			DESCRIPTION
				"Statically locked MAC addresses for port."
			::= { msanPortSecurityStatMacEntry 3 }

		
		-- 1.3.6.1.4.1.1332.1.1.5.3.26.2.1.5
		msanPortSecurityStatMacRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanPortSecurityStatMacEntry 5 }

		
		-- 1.3.6.1.4.1.1332.1.1.5.3.26.3
		msanPortSecurityPortVlanTable OBJECT-TYPE
			SYNTAX SEQUENCE OF MsanPortSecurityPortVlanEntry
			MAX-ACCESS not-accessible
			STATUS current
			DESCRIPTION
				"Description."
			::= { msanPortSecurity 3 }

		
		-- 1.3.6.1.4.1.1332.1.1.5.3.26.3.1
		msanPortSecurityPortVlanEntry OBJECT-TYPE
			SYNTAX MsanPortSecurityPortVlanEntry
			MAX-ACCESS not-accessible
			STATUS current
			DESCRIPTION
				"Description."
			INDEX { ifIndex, dot1qVlanIndex }
			::= { msanPortSecurityPortVlanTable 1 }

		
		MsanPortSecurityPortVlanEntry ::=
			SEQUENCE { 
				msanPortSecurityPortVlanDynamicLimit
					Integer32,
				msanPortSecurityPortVlanRowStatus
					RowStatus
			 }

		-- 1.3.6.1.4.1.1332.1.1.5.3.26.3.1.1
		msanPortSecurityPortVlanDynamicLimit OBJECT-TYPE
			SYNTAX Integer32 (1..64)
			MAX-ACCESS read-write
			STATUS current
			DESCRIPTION
				"The limit of dynamically learned MAC addresses  per vlan on selected port.
				
				"
			::= { msanPortSecurityPortVlanEntry 1 }

		
		-- 1.3.6.1.4.1.1332.1.1.5.3.26.3.1.2
		msanPortSecurityPortVlanRowStatus OBJECT-TYPE
			SYNTAX RowStatus
			MAX-ACCESS read-write
			STATUS current
			DESCRIPTION
				"The row status object controls the creation/deletion of rows in this table.
				Its semantics are the same as those for the RowStatus textual convention specified for SNMPv2.
				For row creation use createAndWait(5).
				For row activation use active(1).
				For row deletion use destroy(6).
					
				Other values are currently not supported."
			::= { msanPortSecurityPortVlanEntry 2 }

		
		-- 1.3.6.1.4.1.1332.1.1.5.3.27
		msanLag OBJECT IDENTIFIER ::= { msanAdditionalConf 27 }

		
		-- 1.3.6.1.4.1.1332.1.1.5.3.27.1
		msanLagGlobal OBJECT IDENTIFIER ::= { msanLag 1 }

		
		-- 1.3.6.1.4.1.1332.1.1.5.3.27.2
		msanLagDetailedConfigTable OBJECT-TYPE
			SYNTAX SEQUENCE OF MsanLagDetailedConfigEntry
			MAX-ACCESS not-accessible
			STATUS current
			DESCRIPTION
				"A detailed table of the switch's LAG config entries. "
			REFERENCE
				"agentLagDetailedConfigTable"
			::= { msanLag 2 }

		
		-- 1.3.6.1.4.1.1332.1.1.5.3.27.2.1
		msanLagDetailedConfigEntry OBJECT-TYPE
			SYNTAX MsanLagDetailedConfigEntry
			MAX-ACCESS not-accessible
			STATUS current
			DESCRIPTION
				"Switch's LAG config entry"
			INDEX { msanLagDetailedLagIndex, msanLagDetailedIfIndex }
			::= { msanLagDetailedConfigTable 1 }

		
		MsanLagDetailedConfigEntry ::=
			SEQUENCE { 
				msanLagDetailedLagIndex
					Integer32,
				msanLagDetailedIfIndex
					Integer32,
				msanLagDetailedPortSpeed
					OBJECT IDENTIFIER,
				msanLagDetailedPortStatus
					INTEGER,
				msanLagDetailedRowStatus
					RowStatus
			 }

		-- 1.3.6.1.4.1.1332.1.1.5.3.27.2.1.1
		msanLagDetailedLagIndex OBJECT-TYPE
			SYNTAX Integer32
			MAX-ACCESS not-accessible
			STATUS current
			DESCRIPTION
				"LAG index"
			::= { msanLagDetailedConfigEntry 1 }

		
		-- 1.3.6.1.4.1.1332.1.1.5.3.27.2.1.2
		msanLagDetailedIfIndex OBJECT-TYPE
			SYNTAX Integer32
			MAX-ACCESS not-accessible
			STATUS current
			DESCRIPTION
				"LAG port index"
			::= { msanLagDetailedConfigEntry 2 }

		
		-- 1.3.6.1.4.1.1332.1.1.5.3.27.2.1.3
		msanLagDetailedPortSpeed OBJECT-TYPE
			SYNTAX OBJECT IDENTIFIER
			MAX-ACCESS read-create
			STATUS current
			DESCRIPTION
				"LAG port speed.  See agentPortType for a description and list
				of valid values."
			::= { msanLagDetailedConfigEntry 3 }

		
		-- 1.3.6.1.4.1.1332.1.1.5.3.27.2.1.4
		msanLagDetailedPortStatus OBJECT-TYPE
			SYNTAX INTEGER
				{
				active(1),
				inactive(2)
				}
			MAX-ACCESS read-only
			STATUS current
			DESCRIPTION
				"LAG port status.
				
				active(1)   - Actively participating in the LAG.
				inactive(2) - Not participating in the LAG."
			::= { msanLagDetailedConfigEntry 4 }

		
		-- 1.3.6.1.4.1.1332.1.1.5.3.27.2.1.5
		msanLagDetailedRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanLagDetailedConfigEntry 5 }

		
		-- 1.3.6.1.4.1.1332.1.1.5.3.27.3
		msanLagTable OBJECT-TYPE
			SYNTAX SEQUENCE OF MsanLagEntry
			MAX-ACCESS not-accessible
			STATUS current
			DESCRIPTION
				"Config table of additional LAG parameters."
			::= { msanLag 3 }

		
		-- 1.3.6.1.4.1.1332.1.1.5.3.27.3.1
		msanLagEntry OBJECT-TYPE
			SYNTAX MsanLagEntry
			MAX-ACCESS not-accessible
			STATUS current
			DESCRIPTION
				"Description."
			INDEX { msanLagIndex }
			::= { msanLagTable 1 }

		
		MsanLagEntry ::=
			SEQUENCE { 
				msanLagIndex
					Integer32,
				msanLagMaxFrameSize
					Integer32,
				msanLagDVlanTagMode
					INTEGER
			 }

		-- 1.3.6.1.4.1.1332.1.1.5.3.27.3.1.1
		msanLagIndex OBJECT-TYPE
			SYNTAX Integer32
			MAX-ACCESS not-accessible
			STATUS current
			DESCRIPTION
				"LAG index. Value corresponds to ifIndex for LAG interfaces in ifTable."
			::= { msanLagEntry 1 }

		
		-- 1.3.6.1.4.1.1332.1.1.5.3.27.3.1.2
		msanLagMaxFrameSize OBJECT-TYPE
			SYNTAX Integer32
			MAX-ACCESS read-write
			STATUS current
			DESCRIPTION
				"This object identifies the currently configured maximum frame size
				value for this LAG interface. 
				"
			::= { msanLagEntry 2 }

		
		-- 1.3.6.1.4.1.1332.1.1.5.3.27.3.1.3
		msanLagDVlanTagMode OBJECT-TYPE
			SYNTAX INTEGER
				{
				enable(1),
				disable(2)
				}
			MAX-ACCESS read-write
			STATUS current
			DESCRIPTION
				"Controls the Double Vlan Tag mode on this LAG interface."
			::= { msanLagEntry 3 }

		
		-- 1.3.6.1.4.1.1332.1.1.5.3.28
		msanRadiusServer OBJECT IDENTIFIER ::= { msanAdditionalConf 28 }

		
		-- 1.3.6.1.4.1.1332.1.1.5.3.28.1
		msanRadiusServerGlobal OBJECT IDENTIFIER ::= { msanRadiusServer 1 }

		
		-- 1.3.6.1.4.1.1332.1.1.5.3.28.2
		msanRadiusServerConfigTable OBJECT-TYPE
			SYNTAX SEQUENCE OF MsanRadiusServerConfigEntry
			MAX-ACCESS not-accessible
			STATUS current
			DESCRIPTION
				"Table with information about Radius Authentication Server IP
				Addresses, port numbers and shared secret"
			::= { msanRadiusServer 2 }

		
		-- 1.3.6.1.4.1.1332.1.1.5.3.28.2.1
		msanRadiusServerConfigEntry OBJECT-TYPE
			SYNTAX MsanRadiusServerConfigEntry
			MAX-ACCESS not-accessible
			STATUS current
			DESCRIPTION
				"Entry consisting of configuration data for a Radius 
				Authentication Server."
			INDEX { msanRadiusServerAddress }
			::= { msanRadiusServerConfigTable 1 }

		
		MsanRadiusServerConfigEntry ::=
			SEQUENCE { 
				msanRadiusServerAddress
					IpAddress,
				msanRadiusServerPort
					Unsigned32,
				msanRadiusServerSecret
					DisplayString,
				msanRadiusServerPrimaryMode
					INTEGER,
				msanRadiusServerCurrentMode
					INTEGER,
				msanRadiusServerMsgAuth
					INTEGER,
				msanRadiusServerStatus
					RowStatus
			 }

		-- 1.3.6.1.4.1.1332.1.1.5.3.28.2.1.1
		msanRadiusServerAddress OBJECT-TYPE
			SYNTAX IpAddress
			MAX-ACCESS not-accessible
			STATUS current
			DESCRIPTION
				"IP Address of the configured RADIUS server.
				This object cannot be changed after creation."
			::= { msanRadiusServerConfigEntry 1 }

		
		-- 1.3.6.1.4.1.1332.1.1.5.3.28.2.1.2
		msanRadiusServerPort OBJECT-TYPE
			SYNTAX Unsigned32 (0..65535)
			MAX-ACCESS read-write
			STATUS current
			DESCRIPTION
				"Port number for the RADIUS server."
			DEFVAL { 1812 }
			::= { msanRadiusServerConfigEntry 2 }

		
		-- 1.3.6.1.4.1.1332.1.1.5.3.28.2.1.3
		msanRadiusServerSecret OBJECT-TYPE
			SYNTAX DisplayString (SIZE (0..20))
			MAX-ACCESS read-write
			STATUS current
			DESCRIPTION
				"Configured shared sercret for the RADIUS server."
			::= { msanRadiusServerConfigEntry 3 }

		
		-- 1.3.6.1.4.1.1332.1.1.5.3.28.2.1.4
		msanRadiusServerPrimaryMode OBJECT-TYPE
			SYNTAX INTEGER
				{
				enable(1),
				disable(2)
				}
			MAX-ACCESS read-write
			STATUS current
			DESCRIPTION
				"Configure the RADIUS server to be the primary server. If there is any 
				other server that is configured to be primary, that server is set to be 
				a seconday server and this entry is set Primary."
			::= { msanRadiusServerConfigEntry 4 }

		
		-- 1.3.6.1.4.1.1332.1.1.5.3.28.2.1.5
		msanRadiusServerCurrentMode OBJECT-TYPE
			SYNTAX INTEGER
				{
				yes(1),
				no(2)
				}
			MAX-ACCESS read-only
			STATUS current
			DESCRIPTION
				"Indicate if the RADIUS server is the current server in user for
				authentication."
			::= { msanRadiusServerConfigEntry 5 }

		
		-- 1.3.6.1.4.1.1332.1.1.5.3.28.2.1.6
		msanRadiusServerMsgAuth OBJECT-TYPE
			SYNTAX INTEGER
				{
				enable(1),
				disable(2)
				}
			MAX-ACCESS read-write
			STATUS current
			DESCRIPTION
				"Enable or disable the message authenticator attribute for this 
				RADIUS server."
			::= { msanRadiusServerConfigEntry 6 }

		
		-- 1.3.6.1.4.1.1332.1.1.5.3.28.2.1.7
		msanRadiusServerStatus OBJECT-TYPE
			SYNTAX RowStatus
			MAX-ACCESS read-create
			STATUS current
			DESCRIPTION
				"Creates or destroys a RADIUS Authentication server entry.
				
				active(1)       - This entry is active.
				createAndGo(4)  - Creates a new entry.
				destroy(6)      - Deletes an entry."
			::= { msanRadiusServerConfigEntry 7 }

		
		-- 1.3.6.1.4.1.1332.1.1.5.3.29
		msanNetwork OBJECT IDENTIFIER ::= { msanAdditionalConf 29 }

		
		-- 1.3.6.1.4.1.1332.1.1.5.3.29.1
		msanNetworkGlobal OBJECT IDENTIFIER ::= { msanNetwork 1 }

		
		-- 1.3.6.1.4.1.1332.1.1.5.3.29.1.1
		msanNetworkIPAddress OBJECT-TYPE
			SYNTAX IpAddress
			MAX-ACCESS read-write
			STATUS current
			DESCRIPTION
				"The switch's network ip address"
			::= { msanNetworkGlobal 1 }

		
		-- 1.3.6.1.4.1.1332.1.1.5.3.29.1.2
		msanNetworkSubnetMask OBJECT-TYPE
			SYNTAX IpAddress
			MAX-ACCESS read-write
			STATUS current
			DESCRIPTION
				"The switch's network subnet mask"
			::= { msanNetworkGlobal 2 }

		
		-- 1.3.6.1.4.1.1332.1.1.5.3.29.1.3
		msanNetworkDefaultGateway OBJECT-TYPE
			SYNTAX IpAddress
			MAX-ACCESS read-write
			STATUS current
			DESCRIPTION
				"The switch's network default gateway"
			::= { msanNetworkGlobal 3 }

		
		-- 1.3.6.1.4.1.1332.1.1.5.3.29.1.4
		msanNetworkDhcpSrvIpAddr OBJECT-TYPE
			SYNTAX IpAddress
			MAX-ACCESS read-only
			STATUS current
			DESCRIPTION
				"IP address of DHCP server used by DHCP client."
			::= { msanNetworkGlobal 4 }

		
		-- 1.3.6.1.4.1.1332.1.1.5.3.29.1.5
		msanNetworkDhcpSrvVendorSpecific OBJECT-TYPE
			SYNTAX INTEGER
				{
				enable(1),
				disable(2)
				}
			MAX-ACCESS read-write
			STATUS current
			DESCRIPTION
				"DHCP client uses only vendor specific DHCP servers 
				(when client sends opt. 60 to server, it should return expected vendor specific value in opt. 43)"
			::= { msanNetworkGlobal 5 }

		
		-- 1.3.6.1.4.1.1332.1.1.5.3.29.1.6
		msanNetworkDhcpClientLeaseObtained OBJECT-TYPE
			SYNTAX OCTET STRING
			MAX-ACCESS read-only
			STATUS current
			DESCRIPTION
				"The date and time when DHCP lease was obtained. 
				"
			::= { msanNetworkGlobal 6 }

		
		-- 1.3.6.1.4.1.1332.1.1.5.3.29.1.7
		msanNetworkDhcpClientLeaseExpires OBJECT-TYPE
			SYNTAX OCTET STRING
			MAX-ACCESS read-only
			STATUS current
			DESCRIPTION
				"The date and time for which the DHCP lease is valid."
			::= { msanNetworkGlobal 7 }

		
		-- 1.3.6.1.4.1.1332.1.1.5.3.29.1.8
		msanNetworkDhcpClientLocalOpt82 OBJECT-TYPE
			SYNTAX INTEGER
				{
				enable(1),
				disable(2)
				}
			MAX-ACCESS read-write
			STATUS current
			DESCRIPTION
				"DHCP client adds relay agent information option into its own outgoing frames."
			::= { msanNetworkGlobal 8 }

		
		-- 1.3.6.1.4.1.1332.1.1.5.3.29.2
		msanNetworkDhcpClientVlanTable OBJECT-TYPE
			SYNTAX SEQUENCE OF MsanNetworkDhcpClientVlanEntry
			MAX-ACCESS not-accessible
			STATUS current
			DESCRIPTION
				"DHCP client configuration per vlan id."
			::= { msanNetwork 2 }

		
		-- 1.3.6.1.4.1.1332.1.1.5.3.29.2.1
		msanNetworkDhcpClientVlanEntry OBJECT-TYPE
			SYNTAX MsanNetworkDhcpClientVlanEntry
			MAX-ACCESS not-accessible
			STATUS current
			DESCRIPTION
				"Description."
			INDEX { dot1qVlanIndex }
			::= { msanNetworkDhcpClientVlanTable 1 }

		
		MsanNetworkDhcpClientVlanEntry ::=
			SEQUENCE { 
				msanNetworkDhcpClientVlanLocalOpt82
					INTEGER
			 }

		-- 1.3.6.1.4.1.1332.1.1.5.3.29.2.1.1
		msanNetworkDhcpClientVlanLocalOpt82 OBJECT-TYPE
			SYNTAX INTEGER
				{
				enable(1),
				disable(2)
				}
			MAX-ACCESS read-write
			STATUS current
			DESCRIPTION
				"DHCP client on specified vlan adds relay agent information option into its own outgoing frames."
			DEFVAL { disable }
			::= { msanNetworkDhcpClientVlanEntry 1 }

		
		-- 1.3.6.1.4.1.1332.1.1.5.3.30
		msanStormControl OBJECT IDENTIFIER ::= { msanAdditionalConf 30 }

		
		-- 1.3.6.1.4.1.1332.1.1.5.3.30.1
		msanStormControlGlobal OBJECT IDENTIFIER ::= { msanStormControl 1 }

		
		-- 1.3.6.1.4.1.1332.1.1.5.3.30.2
		msanPortStormControlTable OBJECT-TYPE
			SYNTAX SEQUENCE OF MsanPortStormControlEntry
			MAX-ACCESS not-accessible
			STATUS current
			DESCRIPTION
				"Description."
			::= { msanStormControl 2 }

		
		-- 1.3.6.1.4.1.1332.1.1.5.3.30.2.1
		msanPortStormControlEntry OBJECT-TYPE
			SYNTAX MsanPortStormControlEntry
			MAX-ACCESS not-accessible
			STATUS current
			DESCRIPTION
				"Description."
			INDEX { ifIndex }
			::= { msanPortStormControlTable 1 }

		
		MsanPortStormControlEntry ::=
			SEQUENCE { 
				msanPortBroadcastControlMode
					INTEGER,
				msanPortBroadcastControlThreshold
					Integer32,
				msanPortMulticastControlMode
					INTEGER,
				msanPortMulticastControlThreshold
					Integer32,
				msanPortUnicastControlMode
					INTEGER,
				msanPortUnicastControlThreshold
					Integer32
			 }

		-- 1.3.6.1.4.1.1332.1.1.5.3.30.2.1.1
		msanPortBroadcastControlMode OBJECT-TYPE
			SYNTAX INTEGER
				{
				enable(1),
				disable(2)
				}
			MAX-ACCESS read-write
			STATUS current
			DESCRIPTION
				"he switch config broadcast allows you to enable or disable 
				broadcast storm recovery mode. When you specify Enable for Broadcast 
				Storm Recovery and the broadcast traffic on any Ethernet port exceeds 
				the configured threshold, the switch blocks (discards) the broadcast
				traffic.
				"
			::= { msanPortStormControlEntry 1 }

		
		-- 1.3.6.1.4.1.1332.1.1.5.3.30.2.1.2
		msanPortBroadcastControlThreshold OBJECT-TYPE
			SYNTAX Integer32
			UNITS "packets per second"
			MAX-ACCESS read-write
			STATUS current
			DESCRIPTION
				"Specify the data rate at which broadcast storm control activates (packets per second)"
			::= { msanPortStormControlEntry 2 }

		
		-- 1.3.6.1.4.1.1332.1.1.5.3.30.2.1.3
		msanPortMulticastControlMode OBJECT-TYPE
			SYNTAX INTEGER
				{
				enable(1),
				disable(2)
				}
			MAX-ACCESS read-write
			STATUS current
			DESCRIPTION
				"The switch config multicast allows you to enable or disable 
				multicast storm recovery mode. When you specify Enable for multicast 
				Storm Recovery and the multicast traffic on any Ethernet port exceeds 
				the configured threshold, the switch blocks (discards) the multicast
				traffic"
			::= { msanPortStormControlEntry 3 }

		
		-- 1.3.6.1.4.1.1332.1.1.5.3.30.2.1.4
		msanPortMulticastControlThreshold OBJECT-TYPE
			SYNTAX Integer32
			UNITS "packets per second"
			MAX-ACCESS read-write
			STATUS current
			DESCRIPTION
				"Specify the data rate at which multicast storm control activates (packets per second)"
			::= { msanPortStormControlEntry 4 }

		
		-- 1.3.6.1.4.1.1332.1.1.5.3.30.2.1.5
		msanPortUnicastControlMode OBJECT-TYPE
			SYNTAX INTEGER
				{
				enable(1),
				disable(2)
				}
			MAX-ACCESS read-write
			STATUS current
			DESCRIPTION
				"The switch config unicast allows you to enable or disable 
				unicast storm recovery mode. When you specify Enable for unicast 
				Storm Recovery and the unknown unicast traffic on any Ethernet port exceeds 
				the configured threshold, the switch blocks (discards) the unknown unicast
				traffic.
				"
			::= { msanPortStormControlEntry 5 }

		
		-- 1.3.6.1.4.1.1332.1.1.5.3.30.2.1.6
		msanPortUnicastControlThreshold OBJECT-TYPE
			SYNTAX Integer32
			UNITS "packets per second"
			MAX-ACCESS read-write
			STATUS current
			DESCRIPTION
				"Specify the data rate at which unicast storm control activates (packets per second)"
			::= { msanPortStormControlEntry 6 }

		
		-- 1.3.6.1.4.1.1332.1.1.5.3.31
		msanUserConfig OBJECT IDENTIFIER ::= { msanAdditionalConf 31 }

		
		-- 1.3.6.1.4.1.1332.1.1.5.3.31.1
		msanUserConfigGlobal OBJECT IDENTIFIER ::= { msanUserConfig 1 }

		
		-- 1.3.6.1.4.1.1332.1.1.5.3.31.1.1
		msanUserConfigCheckPassword OBJECT-TYPE
			SYNTAX OCTET STRING (SIZE (0..255))
			MAX-ACCESS read-write
			STATUS current
			DESCRIPTION
				"Parameter is used to check user's password. String must
				be written in next format: user_name password
				First blank space is used as delimeter between user_name and
				password. 
				
				If password is ok and user has write permission,
				noError(0) code is returned.
				
				If password is ok but user has only read permission,
				noAccess(6) error code is returned.
				
				If password is not valid or user is not configured, 
				inconsistentValue(12) error code is returned.
				"
			::= { msanUserConfigGlobal 1 }

		
		-- 1.3.6.1.4.1.1332.1.1.5.3.31.2
		msanUserConfigTable OBJECT-TYPE
			SYNTAX SEQUENCE OF MsanUserConfigEntry
			MAX-ACCESS not-accessible
			STATUS current
			DESCRIPTION
				"Description."
			::= { msanUserConfig 2 }

		
		-- 1.3.6.1.4.1.1332.1.1.5.3.31.2.1
		msanUserConfigEntry OBJECT-TYPE
			SYNTAX MsanUserConfigEntry
			MAX-ACCESS not-accessible
			STATUS current
			DESCRIPTION
				"Description."
			INDEX { msanUserIndex }
			::= { msanUserConfigTable 1 }

		
		MsanUserConfigEntry ::=
			SEQUENCE { 
				msanUserIndex
					Integer32,
				msanUserAccessMode
					INTEGER
			 }

		-- 1.3.6.1.4.1.1332.1.1.5.3.31.2.1.1
		msanUserIndex OBJECT-TYPE
			SYNTAX Integer32
			MAX-ACCESS not-accessible
			STATUS current
			DESCRIPTION
				"User Config Index"
			::= { msanUserConfigEntry 1 }

		
		-- 1.3.6.1.4.1.1332.1.1.5.3.31.2.1.2
		msanUserAccessMode OBJECT-TYPE
			SYNTAX INTEGER
				{
				read(1),
				write(2)
				}
			MAX-ACCESS read-write
			STATUS current
			DESCRIPTION
				"User Access Mode"
			::= { msanUserConfigEntry 2 }

		
		-- 1.3.6.1.4.1.1332.1.1.5.3.32
		msanSfp OBJECT IDENTIFIER ::= { msanAdditionalConf 32 }

		
		-- 1.3.6.1.4.1.1332.1.1.5.3.32.1
		msanSfpGlobal OBJECT IDENTIFIER ::= { msanSfp 1 }

		
		-- 1.3.6.1.4.1.1332.1.1.5.3.32.2
		msanSfpInfoTable OBJECT-TYPE
			SYNTAX SEQUENCE OF MsanSfpInfoEntry
			MAX-ACCESS not-accessible
			STATUS current
			DESCRIPTION
				"Description."
			::= { msanSfp 2 }

		
		-- 1.3.6.1.4.1.1332.1.1.5.3.32.2.1
		msanSfpInfoEntry OBJECT-TYPE
			SYNTAX MsanSfpInfoEntry
			MAX-ACCESS not-accessible
			STATUS current
			DESCRIPTION
				"Description."
			INDEX { ifIndex }
			::= { msanSfpInfoTable 1 }

		
		MsanSfpInfoEntry ::=
			SEQUENCE { 
				msanSfpInfoState
					INTEGER,
				msanSfpInfoInterfaceType
					INTEGER,
				msanSfpInfoNominalBitrate
					Integer32,
				msanSfpInfoNominalRange
					OCTET STRING,
				msanSfpInfoVendor
					OCTET STRING,
				msanSfpInfoIeeeVendorId
					Integer32,
				msanSfpInfoPartNr
					OCTET STRING,
				msanSfpInfoRevisionNr
					OCTET STRING,
				msanSfpInfoSerialNr
					OCTET STRING,
				msanSfpInfoManufacturingDate
					OCTET STRING,
				msanSfpInfoWavelength
					Integer32,
				msanSfpInfoVendorPN
					DisplayString,
				msanSfpInfoSfpType
					INTEGER
			 }

		-- 1.3.6.1.4.1.1332.1.1.5.3.32.2.1.1
		msanSfpInfoState OBJECT-TYPE
			SYNTAX INTEGER
				{
				adminOff(1),
				operational(2),
				operWithAl(3),
				loss(4),
				notAvaliable(5),
				presNoDiag(6),
				notPresent(7)
				}
			MAX-ACCESS read-only
			STATUS current
			DESCRIPTION
				"Module state value on port. Ports which support SFP module are from
				1 to 10 and from 15 to 28. State value adminOff means that specific
				port is administrative disabled and we can not read data from module
				on that port. Operational state means that SFP module is present and
				it works perfect. State operWithAl(operational with alarm) means 
				that SFP module is present, but it works with internal alarms.
				Loss(Loss of signal) state means that SFP module is present but it
				have loss of signal. PresNoDiag(Present, no diagnostic) state means
				that SFP module is present but diagnostic is not supported.
				NotAvaliable state means that admin. mode of specific port has 
				disabled value and SFP state is not avaliable. 
				NotPresent state means that SFP module is not present.
				"
			::= { msanSfpInfoEntry 1 }

		
		-- 1.3.6.1.4.1.1332.1.1.5.3.32.2.1.2
		msanSfpInfoInterfaceType OBJECT-TYPE
			SYNTAX INTEGER
				{
				sfp(1),
				not(2),
				no(3),
				ad(4),
				xfp(5)
				}
			MAX-ACCESS read-only
			STATUS current
			DESCRIPTION
				"Transceiver(module) type. 
				Module type can be SFP, NOT(mudule type is not SFP), 
				NO(no module on port), AD(admin. disabled port) and XFP."
			::= { msanSfpInfoEntry 2 }

		
		-- 1.3.6.1.4.1.1332.1.1.5.3.32.2.1.3
		msanSfpInfoNominalBitrate OBJECT-TYPE
			SYNTAX Integer32
			MAX-ACCESS read-only
			STATUS current
			DESCRIPTION
				"Module(SFP) nominal bitrate value measure in Mbit/s.
				If parameter is not available, value -1 is used."
			::= { msanSfpInfoEntry 3 }

		
		-- 1.3.6.1.4.1.1332.1.1.5.3.32.2.1.4
		msanSfpInfoNominalRange OBJECT-TYPE
			SYNTAX OCTET STRING
			MAX-ACCESS read-only
			STATUS current
			DESCRIPTION
				"Module(SFP) nominal range value. 
				Nominal range value can support five different link lengths.
				Link length value and nominal range units are defined depends
				on value of nominal range.
				We can get link length value which can support 9/125 um fiber 
				and nominal range measure  in km units. 
				We can get link length value which can support 9/125 um fiber 
				and nominal range measure in 100m units.
				We can get link length value which can support 50/125 um fiber 
				and nominal range measure in 10m units. 
				We can get link length value which can support 62,5/125 um fiber 
				and nominal range measure in 10m units.
				We can get link length value which can support cooper 
				and nominal range measure in m units. 
				"
			::= { msanSfpInfoEntry 4 }

		
		-- 1.3.6.1.4.1.1332.1.1.5.3.32.2.1.5
		msanSfpInfoVendor OBJECT-TYPE
			SYNTAX OCTET STRING
			MAX-ACCESS read-only
			STATUS current
			DESCRIPTION
				"Module(SFP) vendor name."
			::= { msanSfpInfoEntry 5 }

		
		-- 1.3.6.1.4.1.1332.1.1.5.3.32.2.1.6
		msanSfpInfoIeeeVendorId OBJECT-TYPE
			SYNTAX Integer32
			MAX-ACCESS read-only
			STATUS current
			DESCRIPTION
				"Module(SFP) vendor IEEE company ID.
				If parameter is not available, value -1 is used."
			::= { msanSfpInfoEntry 6 }

		
		-- 1.3.6.1.4.1.1332.1.1.5.3.32.2.1.7
		msanSfpInfoPartNr OBJECT-TYPE
			SYNTAX OCTET STRING
			MAX-ACCESS read-only
			STATUS current
			DESCRIPTION
				"Module(SFP) part number."
			::= { msanSfpInfoEntry 7 }

		
		-- 1.3.6.1.4.1.1332.1.1.5.3.32.2.1.8
		msanSfpInfoRevisionNr OBJECT-TYPE
			SYNTAX OCTET STRING
			MAX-ACCESS read-only
			STATUS current
			DESCRIPTION
				"Module(SFP) revision number."
			::= { msanSfpInfoEntry 8 }

		
		-- 1.3.6.1.4.1.1332.1.1.5.3.32.2.1.9
		msanSfpInfoSerialNr OBJECT-TYPE
			SYNTAX OCTET STRING
			MAX-ACCESS read-only
			STATUS current
			DESCRIPTION
				"Module(SFP) serial number."
			::= { msanSfpInfoEntry 9 }

		
		-- 1.3.6.1.4.1.1332.1.1.5.3.32.2.1.10
		msanSfpInfoManufacturingDate OBJECT-TYPE
			SYNTAX OCTET STRING
			MAX-ACCESS read-only
			STATUS current
			DESCRIPTION
				"Module(SFP) manufacturing date."
			::= { msanSfpInfoEntry 10 }

		
		-- 1.3.6.1.4.1.1332.1.1.5.3.32.2.1.11
		msanSfpInfoWavelength OBJECT-TYPE
			SYNTAX Integer32
			MAX-ACCESS read-only
			STATUS current
			DESCRIPTION
				"Module(SFP) laser wavelength measure in nanometers.
				If parameter is not available, value -1 is used."
			::= { msanSfpInfoEntry 11 }

		
		-- 1.3.6.1.4.1.1332.1.1.5.3.32.2.1.12
		msanSfpInfoVendorPN OBJECT-TYPE
			SYNTAX DisplayString
			MAX-ACCESS read-only
			STATUS current
			DESCRIPTION
				"Module(SFP) vendor Part Number"
			::= { msanSfpInfoEntry 12 }

		
		-- 1.3.6.1.4.1.1332.1.1.5.3.32.2.1.13
		msanSfpInfoSfpType OBJECT-TYPE
			SYNTAX INTEGER
				{
				GPON(1),
				XGSPON(2),
				Combo(3),
				P2P(4),
				Undefined(5)
				}
			MAX-ACCESS read-only
			STATUS current
			DESCRIPTION
				"SFP Type"
			::= { msanSfpInfoEntry 13 }

		
		-- 1.3.6.1.4.1.1332.1.1.5.3.32.3
		msanSfpDiagnosticsTable OBJECT-TYPE
			SYNTAX SEQUENCE OF MsanSfpDiagnosticsEntry
			MAX-ACCESS not-accessible
			STATUS current
			DESCRIPTION
				"Description."
			::= { msanSfp 3 }

		
		-- 1.3.6.1.4.1.1332.1.1.5.3.32.3.1
		msanSfpDiagnosticsEntry OBJECT-TYPE
			SYNTAX MsanSfpDiagnosticsEntry
			MAX-ACCESS not-accessible
			STATUS current
			DESCRIPTION
				"Description."
			INDEX { ifIndex }
			::= { msanSfpDiagnosticsTable 1 }

		
		MsanSfpDiagnosticsEntry ::=
			SEQUENCE { 
				msanSfpDiagnosticsSignal
					INTEGER,
				msanSfpDiagnosticsTempCurrent
					Integer32,
				msanSfpDiagnosticsTempMin
					Integer32,
				msanSfpDiagnosticsTempMax
					Integer32,
				msanSfpDiagnosticsVoltageCurrent
					Integer32,
				msanSfpDiagnosticsVoltageMin
					Integer32,
				msanSfpDiagnosticsVoltageMax
					Integer32,
				msanSfpDiagnosticsTxBiasCrrCurrent
					Integer32,
				msanSfpDiagnosticsTxBiasCrrMin
					Integer32,
				msanSfpDiagnosticsTxBiasCrrMax
					Integer32,
				msanSfpDiagnosticsTxPowerCurrent
					Integer32,
				msanSfpDiagnosticsTxPowerMin
					Integer32,
				msanSfpDiagnosticsTxPowerMax
					Integer32,
				msanSfpDiagnosticsRxPowerCurrent
					Integer32,
				msanSfpDiagnosticsRxPowerMin
					Integer32,
				msanSfpDiagnosticsRxPowerMax
					Integer32,
				msanSfpDiagnosticsTempStatus
					INTEGER,
				msanSfpDiagnosticsVoltageStatus
					INTEGER,
				msanSfpDiagnosticsTxBiasStatus
					INTEGER,
				msanSfpDiagnosticsTxPowerStatus
					INTEGER,
				msanSfpDiagnosticsRxPowerStatus
					INTEGER,
				msanSfpDiagnosticsTxPowerCurrentDBm
					Integer32,
				msanSfpDiagnosticsRxPowerCurrentDBm
					Integer32
			 }

		-- 1.3.6.1.4.1.1332.1.1.5.3.32.3.1.1
		msanSfpDiagnosticsSignal OBJECT-TYPE
			SYNTAX INTEGER
				{
				loss(1),
				ok(2),
				notSupported(3)
				}
			MAX-ACCESS read-only
			STATUS current
			DESCRIPTION
				"Module(SFP) signal value. 
				If diagnostic for SFP module is supported than value can be 
				OK(signal is ok) or loss(loss of signal), in the other case
				the value is set on notSupported becouse diagnostic is not
				supported(-1)."
			::= { msanSfpDiagnosticsEntry 1 }

		
		-- 1.3.6.1.4.1.1332.1.1.5.3.32.3.1.2
		msanSfpDiagnosticsTempCurrent OBJECT-TYPE
			SYNTAX Integer32
			MAX-ACCESS read-only
			STATUS current
			DESCRIPTION
				"Current SFP module temperature value in [deg C].
				If diagnostic is not supported for SFP module then 
				current temperature is set on not supported value(-129). "
			::= { msanSfpDiagnosticsEntry 2 }

		
		-- 1.3.6.1.4.1.1332.1.1.5.3.32.3.1.3
		msanSfpDiagnosticsTempMin OBJECT-TYPE
			SYNTAX Integer32
			MAX-ACCESS read-only
			STATUS current
			DESCRIPTION
				"SFP module minimum temperature threshold limit in [deg C].
				If diagnostic is not supported for SFP module then minimum
				temperature threshold limit is set on not supported value(-129). "
			::= { msanSfpDiagnosticsEntry 3 }

		
		-- 1.3.6.1.4.1.1332.1.1.5.3.32.3.1.4
		msanSfpDiagnosticsTempMax OBJECT-TYPE
			SYNTAX Integer32
			MAX-ACCESS read-only
			STATUS current
			DESCRIPTION
				"SFP module maximum temperature threshold limit in [deg C].
				If diagnostic is not supported for SFP module then maximum 
				temperature threshold limit is set on not supported value(-129). "
			::= { msanSfpDiagnosticsEntry 4 }

		
		-- 1.3.6.1.4.1.1332.1.1.5.3.32.3.1.6
		msanSfpDiagnosticsVoltageCurrent OBJECT-TYPE
			SYNTAX Integer32
			UNITS "0.01 V"
			MAX-ACCESS read-only
			STATUS current
			DESCRIPTION
				"Current SFP module supply voltage value in [V].
				If diagnostic is not supported for SFP module then 
				current supply voltage is set on not supported value(-1). "
			::= { msanSfpDiagnosticsEntry 6 }

		
		-- 1.3.6.1.4.1.1332.1.1.5.3.32.3.1.7
		msanSfpDiagnosticsVoltageMin OBJECT-TYPE
			SYNTAX Integer32
			UNITS "0.01 V"
			MAX-ACCESS read-only
			STATUS current
			DESCRIPTION
				"SFP module minimum supply voltage threshold limit in [V].
				If diagnostic is not supported for SFP module then minimum 
				supply voltage threshold limit is set on not supported value(-1). "
			::= { msanSfpDiagnosticsEntry 7 }

		
		-- 1.3.6.1.4.1.1332.1.1.5.3.32.3.1.8
		msanSfpDiagnosticsVoltageMax OBJECT-TYPE
			SYNTAX Integer32
			UNITS "0.01 V"
			MAX-ACCESS read-only
			STATUS current
			DESCRIPTION
				"SFP module maximum supply voltage threshold  limit in [V].
				If diagnostic is not supported for SFP module then maximum 
				supply voltage threshold limit is set on not supported value(-1). "
			::= { msanSfpDiagnosticsEntry 8 }

		
		-- 1.3.6.1.4.1.1332.1.1.5.3.32.3.1.9
		msanSfpDiagnosticsTxBiasCrrCurrent OBJECT-TYPE
			SYNTAX Integer32
			UNITS "0.01 mA"
			MAX-ACCESS read-only
			STATUS current
			DESCRIPTION
				"Current SFP module Tx Bias Current  value in [mA].
				If diagnostic is not supported for SFP module then 
				current Tx Bias Current is set on not supported value(-1). "
			::= { msanSfpDiagnosticsEntry 9 }

		
		-- 1.3.6.1.4.1.1332.1.1.5.3.32.3.1.10
		msanSfpDiagnosticsTxBiasCrrMin OBJECT-TYPE
			SYNTAX Integer32
			UNITS "0.01 mA"
			MAX-ACCESS read-only
			STATUS current
			DESCRIPTION
				"SFP module minimum Tx Bias Current threshold limit in [mA].
				If diagnostic is not supported for SFP module then minimum 
				Tx Bias Current threshold limit is set on not supported value(-1). "
			::= { msanSfpDiagnosticsEntry 10 }

		
		-- 1.3.6.1.4.1.1332.1.1.5.3.32.3.1.11
		msanSfpDiagnosticsTxBiasCrrMax OBJECT-TYPE
			SYNTAX Integer32
			UNITS "0.01 mA"
			MAX-ACCESS read-only
			STATUS current
			DESCRIPTION
				"SFP module maximum Tx Bias Current threshold  limit in [mA].
				If diagnostic is not supported for SFP module then maximum 
				Tx Bias Current threshold  limit is set on not supported value(-1). "
			::= { msanSfpDiagnosticsEntry 11 }

		
		-- 1.3.6.1.4.1.1332.1.1.5.3.32.3.1.12
		msanSfpDiagnosticsTxPowerCurrent OBJECT-TYPE
			SYNTAX Integer32
			UNITS "0.01 mW"
			MAX-ACCESS read-only
			STATUS current
			DESCRIPTION
				"Current SFP module transmitted optical output power value in [mW].
				If diagnostic is not supported for SFP module then current 
				transmitted optical output power is set on not supported value(-1). "
			::= { msanSfpDiagnosticsEntry 12 }

		
		-- 1.3.6.1.4.1.1332.1.1.5.3.32.3.1.13
		msanSfpDiagnosticsTxPowerMin OBJECT-TYPE
			SYNTAX Integer32
			UNITS "0.01 mW"
			MAX-ACCESS read-only
			STATUS current
			DESCRIPTION
				"SFP module minimum transmitted optical output power threshold limit 
				in [mW]. If diagnostic is not supported for SFP module then minimum 
				transmitted optical output power is set on not supported value(-1). "
			::= { msanSfpDiagnosticsEntry 13 }

		
		-- 1.3.6.1.4.1.1332.1.1.5.3.32.3.1.14
		msanSfpDiagnosticsTxPowerMax OBJECT-TYPE
			SYNTAX Integer32
			UNITS "0.01 mW"
			MAX-ACCESS read-only
			STATUS current
			DESCRIPTION
				"SFP module maximum transmitted optical output power threshold  limit
				in [mW]. If diagnostic is not supported for SFP module then maximum 
				transmitted optical output power is set on not supported value(-1)."
			::= { msanSfpDiagnosticsEntry 14 }

		
		-- 1.3.6.1.4.1.1332.1.1.5.3.32.3.1.15
		msanSfpDiagnosticsRxPowerCurrent OBJECT-TYPE
			SYNTAX Integer32
			UNITS "0.01 mW"
			MAX-ACCESS read-only
			STATUS current
			DESCRIPTION
				"Current SFP module received optical input power value in [mW].
				If diagnostic is not supported for SFP module then current 
				received optical input power is set on not supported value(-1). "
			::= { msanSfpDiagnosticsEntry 15 }

		
		-- 1.3.6.1.4.1.1332.1.1.5.3.32.3.1.16
		msanSfpDiagnosticsRxPowerMin OBJECT-TYPE
			SYNTAX Integer32
			UNITS "0.01 mW"
			MAX-ACCESS read-only
			STATUS current
			DESCRIPTION
				"SFP module minimum received optical input power threshold limit 
				in [mW]. If diagnostic is not supported for SFP module then minimum 
				received optical input power is set on not supported value(-1). "
			::= { msanSfpDiagnosticsEntry 16 }

		
		-- 1.3.6.1.4.1.1332.1.1.5.3.32.3.1.17
		msanSfpDiagnosticsRxPowerMax OBJECT-TYPE
			SYNTAX Integer32
			UNITS "0.01 mW"
			MAX-ACCESS read-only
			STATUS current
			DESCRIPTION
				"SFP module maximum received optical input power threshold  limit 
				in [mW]. If diagnostic is not supported for SFP module then maximum 
				received optical input power is set on not supported value(-1). "
			::= { msanSfpDiagnosticsEntry 17 }

		
		-- 1.3.6.1.4.1.1332.1.1.5.3.32.3.1.19
		msanSfpDiagnosticsTempStatus OBJECT-TYPE
			SYNTAX INTEGER
				{
				sfpDiagNoAlarm(1),
				sfpDiagAlarm(2),
				notAvailable(3)
				}
			MAX-ACCESS read-only
			STATUS current
			DESCRIPTION
				"Temperature alarm status.
				"
			::= { msanSfpDiagnosticsEntry 19 }

		
		-- 1.3.6.1.4.1.1332.1.1.5.3.32.3.1.20
		msanSfpDiagnosticsVoltageStatus OBJECT-TYPE
			SYNTAX INTEGER
				{
				sfpDiagNoAlarm(1),
				sfpDiagAlarm(2),
				notAvailable(3)
				}
			MAX-ACCESS read-only
			STATUS current
			DESCRIPTION
				"Voltage alarm status."
			::= { msanSfpDiagnosticsEntry 20 }

		
		-- 1.3.6.1.4.1.1332.1.1.5.3.32.3.1.21
		msanSfpDiagnosticsTxBiasStatus OBJECT-TYPE
			SYNTAX INTEGER
				{
				sfpDiagNoAlarm(1),
				sfpDiagAlarm(2),
				notAvailable(3)
				}
			MAX-ACCESS read-only
			STATUS current
			DESCRIPTION
				"TX bias alarm status."
			::= { msanSfpDiagnosticsEntry 21 }

		
		-- 1.3.6.1.4.1.1332.1.1.5.3.32.3.1.22
		msanSfpDiagnosticsTxPowerStatus OBJECT-TYPE
			SYNTAX INTEGER
				{
				sfpDiagNoAlarm(1),
				sfpDiagAlarm(2),
				notAvailable(3)
				}
			MAX-ACCESS read-only
			STATUS current
			DESCRIPTION
				"TX power alarm status."
			::= { msanSfpDiagnosticsEntry 22 }

		
		-- 1.3.6.1.4.1.1332.1.1.5.3.32.3.1.23
		msanSfpDiagnosticsRxPowerStatus OBJECT-TYPE
			SYNTAX INTEGER
				{
				sfpDiagNoAlarm(1),
				sfpDiagAlarm(2),
				notAvailable(3)
				}
			MAX-ACCESS read-only
			STATUS current
			DESCRIPTION
				"RX power alarm status."
			::= { msanSfpDiagnosticsEntry 23 }

		
		-- 1.3.6.1.4.1.1332.1.1.5.3.32.3.1.24
		msanSfpDiagnosticsTxPowerCurrentDBm OBJECT-TYPE
			SYNTAX Integer32
			UNITS "0.01 dBm"
			MAX-ACCESS read-only
			STATUS current
			DESCRIPTION
				"Current SFP module transmitted optical output power value in [dBM].
				
				If diagnostic is not supported for SFP module then current 
				transmitted optical input power is set on not supported value(-100000). 
				"
			::= { msanSfpDiagnosticsEntry 24 }

		
		-- 1.3.6.1.4.1.1332.1.1.5.3.32.3.1.25
		msanSfpDiagnosticsRxPowerCurrentDBm OBJECT-TYPE
			SYNTAX Integer32
			UNITS "0.01 dBm"
			MAX-ACCESS read-only
			STATUS current
			DESCRIPTION
				"Current SFP module received optical input power value in [dBm].
				
				If diagnostic is not supported for SFP module then current 
				reveived optical input power is set on not supported value(-100000). 
				"
			::= { msanSfpDiagnosticsEntry 25 }

		
		-- 1.3.6.1.4.1.1332.1.1.5.3.34
		msanMacSg OBJECT IDENTIFIER ::= { msanAdditionalConf 34 }

		
		-- 1.3.6.1.4.1.1332.1.1.5.3.34.1
		msanMacSgGlobal OBJECT IDENTIFIER ::= { msanMacSg 1 }

		
		-- 1.3.6.1.4.1.1332.1.1.5.3.34.1.1
		msanMacSgStatus OBJECT-TYPE
			SYNTAX INTEGER
				{
				enable(1),
				disable(2)
				}
			MAX-ACCESS read-write
			STATUS current
			DESCRIPTION
				"Administrative state of MAC Source Guard on the system."
			::= { msanMacSgGlobal 1 }

		
		-- 1.3.6.1.4.1.1332.1.1.5.3.34.2
		msanMacSgPortTable OBJECT-TYPE
			SYNTAX SEQUENCE OF MsanMacSgPortEntry
			MAX-ACCESS not-accessible
			STATUS current
			DESCRIPTION
				"Description."
			::= { msanMacSg 2 }

		
		-- 1.3.6.1.4.1.1332.1.1.5.3.34.2.1
		msanMacSgPortEntry OBJECT-TYPE
			SYNTAX MsanMacSgPortEntry
			MAX-ACCESS not-accessible
			STATUS current
			DESCRIPTION
				"Description."
			INDEX { ifIndex }
			::= { msanMacSgPortTable 1 }

		
		MsanMacSgPortEntry ::=
			SEQUENCE { 
				msanMacSgPortStatus
					INTEGER,
				msanMacSgPortViolationsCounter
					Integer32
			 }

		-- 1.3.6.1.4.1.1332.1.1.5.3.34.2.1.1
		msanMacSgPortStatus OBJECT-TYPE
			SYNTAX INTEGER
				{
				enable(1),
				disable(2)
				}
			MAX-ACCESS read-write
			STATUS current
			DESCRIPTION
				"Administrative state of MAC Source Guard on interface."
			::= { msanMacSgPortEntry 1 }

		
		-- 1.3.6.1.4.1.1332.1.1.5.3.34.2.1.2
		msanMacSgPortViolationsCounter OBJECT-TYPE
			SYNTAX Integer32
			MAX-ACCESS read-only
			STATUS current
			DESCRIPTION
				"MAC Source Guard Violations counter"
			::= { msanMacSgPortEntry 2 }

		
		-- 1.3.6.1.4.1.1332.1.1.5.3.35
		msanErrorDisable OBJECT IDENTIFIER ::= { msanAdditionalConf 35 }

		
		-- 1.3.6.1.4.1.1332.1.1.5.3.35.1
		msanErrorDisableGlobal OBJECT IDENTIFIER ::= { msanErrorDisable 1 }

		
		-- 1.3.6.1.4.1.1332.1.1.5.3.35.1.1
		msanErrorDisableInterval OBJECT-TYPE
			SYNTAX Integer32
			UNITS "minutes"
			MAX-ACCESS read-write
			STATUS current
			DESCRIPTION
				"The interval in minutes that will pass since error-disabled interface 
				will be enabled. This parameter has effect only if ErrorDisable Recovery 
				is enabled.
				"
			::= { msanErrorDisableGlobal 1 }

		
		-- 1.3.6.1.4.1.1332.1.1.5.3.35.1.2
		msanErrorDisableMacSgDetectionStatus OBJECT-TYPE
			SYNTAX INTEGER
				{
				enable(1),
				disable(2)
				}
			MAX-ACCESS read-write
			STATUS current
			DESCRIPTION
				"Administrative state of ErrorDisable Detection for MAC Source Guard cause. 
				If enabled, interface will be error-disabled when MAC Source Guard violation 
				is detected.
				"
			::= { msanErrorDisableGlobal 2 }

		
		-- 1.3.6.1.4.1.1332.1.1.5.3.35.1.3
		msanErrorDisableMacSgRecoveryStatus OBJECT-TYPE
			SYNTAX INTEGER
				{
				enable(1),
				disable(2)
				}
			MAX-ACCESS read-write
			STATUS current
			DESCRIPTION
				"Administrative state of ErrorDisable Recovery for MAC Source Guard cause. 
				If enabled, interface will be automatically recovered when error-disabled 
				due to MAC Source Guard violation."
			::= { msanErrorDisableGlobal 3 }

		
		-- 1.3.6.1.4.1.1332.1.1.5.3.35.2
		msanErrorDisablePortTable OBJECT-TYPE
			SYNTAX SEQUENCE OF MsanErrorDisablePortEntry
			MAX-ACCESS not-accessible
			STATUS current
			DESCRIPTION
				"Description."
			::= { msanErrorDisable 2 }

		
		-- 1.3.6.1.4.1.1332.1.1.5.3.35.2.1
		msanErrorDisablePortEntry OBJECT-TYPE
			SYNTAX MsanErrorDisablePortEntry
			MAX-ACCESS not-accessible
			STATUS current
			DESCRIPTION
				"Description."
			INDEX { ifIndex }
			::= { msanErrorDisablePortTable 1 }

		
		MsanErrorDisablePortEntry ::=
			SEQUENCE { 
				msanErrorDisablePortStatus
					INTEGER,
				msanErrorDisablePortCause
					OCTET STRING,
				msanErrorDisablePortTimeLeft
					Integer32,
				msanErrorDisablePortCounter
					Integer32
			 }

		-- 1.3.6.1.4.1.1332.1.1.5.3.35.2.1.1
		msanErrorDisablePortStatus OBJECT-TYPE
			SYNTAX INTEGER
				{
				regular(1),
				errorDisable(2)
				}
			MAX-ACCESS read-only
			STATUS current
			DESCRIPTION
				"This parameter shows which interfaces are in errorDisable(2) 
				recovery administrative state."
			::= { msanErrorDisablePortEntry 1 }

		
		-- 1.3.6.1.4.1.1332.1.1.5.3.35.2.1.2
		msanErrorDisablePortCause OBJECT-TYPE
			SYNTAX OCTET STRING
			MAX-ACCESS read-only
			STATUS current
			DESCRIPTION
				"Cause for errorDisable(2) status on interface."
			::= { msanErrorDisablePortEntry 2 }

		
		-- 1.3.6.1.4.1.1332.1.1.5.3.35.2.1.3
		msanErrorDisablePortTimeLeft OBJECT-TYPE
			SYNTAX Integer32
			UNITS "sec"
			MAX-ACCESS read-only
			STATUS current
			DESCRIPTION
				"Time in seconds which defines how much time left for
				interface to stay in errorDisable(2) state."
			::= { msanErrorDisablePortEntry 3 }

		
		-- 1.3.6.1.4.1.1332.1.1.5.3.35.2.1.4
		msanErrorDisablePortCounter OBJECT-TYPE
			SYNTAX Integer32
			MAX-ACCESS read-only
			STATUS current
			DESCRIPTION
				"The number of times the specified interface has been in errorDisable(2) state."
			::= { msanErrorDisablePortEntry 4 }

		
		-- 1.3.6.1.4.1.1332.1.1.5.3.36
		msanAdsl OBJECT IDENTIFIER ::= { msanAdditionalConf 36 }

		
		-- 1.3.6.1.4.1.1332.1.1.5.3.36.1
		msanAdslGlobal OBJECT IDENTIFIER ::= { msanAdsl 1 }

		
		-- 1.3.6.1.4.1.1332.1.1.5.3.36.2
		msanAdslAtucPhysExtnTable OBJECT-TYPE
			SYNTAX SEQUENCE OF MsanAdslAtucPhysExtnEntry
			MAX-ACCESS not-accessible
			STATUS current
			DESCRIPTION
				"This table provides one row for each ATUC. This table is an extention to adslAtucPhysTable defined in rfc-2662."
			::= { msanAdsl 2 }

		
		-- 1.3.6.1.4.1.1332.1.1.5.3.36.2.1
		msanAdslAtucPhysExtnEntry OBJECT-TYPE
			SYNTAX MsanAdslAtucPhysExtnEntry
			MAX-ACCESS not-accessible
			STATUS current
			DESCRIPTION
				"An entry (conceptual row) in the msanAdslAtucPhysExtnTable.
				The Table is indexed by ifIndex."
			INDEX { ifIndex }
			::= { msanAdslAtucPhysExtnTable 1 }

		
		MsanAdslAtucPhysExtnEntry ::=
			SEQUENCE { 
				msanAdslAtucPhysExtnOpState
					INTEGER,
				msanAdslAtucPhysExtnActualStd
					INTEGER,
				msanAdslAtucPhysExtnBertError
					Integer32,
				msanAdslAtucPhysExtnTxAtmCellCounter
					Counter32,
				msanAdslAtucPhysExtnRxAtmCellCounter
					Integer32,
				msanAdslAtucPhysExtnStartProgress
					Integer32,
				msanAdslAtucPhysExtnIdleBertError
					Integer32,
				msanAdslAtucPhysExtnIdleBertCells
					Integer32,
				msanAdslAtucPhysExtnBertSync
					INTEGER,
				msanAdslAtucPhysExtnParametricTestResult
					INTEGER,
				msanAdslAtucPhysExtnSeltInfoValid
					INTEGER,
				msanAdslAtucPhysExtnSeltLoopLen
					Integer32,
				msanAdslAtucPhysExtnSeltLoopEnd
					INTEGER,
				msanAdslAtucPhysExtnSeltLoopGauge
					INTEGER,
				msanAdslAtucPhysExtnSeltUpShannonCap
					Gauge32,
				msanAdslAtucPhysExtnSeltDownShannonCap
					Gauge32,
				msanAdslAtucPhysExtnSeltInbandNoise
					OCTET STRING,
				msanAdslAtucPhysExtnSeltTerminationResp
					OCTET STRING,
				msanAdslAtucPhysExtnSeltUpMgnAtRate
					OCTET STRING,
				msanAdslAtucPhysExtnSeltDownMgnAtRate
					OCTET STRING,
				msanAdslAtucPhysExtnDataBoostStatus
					INTEGER,
				msanAdslAtucPhysExtnTestArray
					OCTET STRING,
				msanAdslAtucPhysExtnChanPerfCD
					Integer32,
				msanAdslAtucPhysExtnChanPerfBE
					Integer32,
				msanAdslAtucPhysExtnDeltHLINSCus
					Integer32,
				msanAdslAtucPhysExtnDeltHLINpsus
					OCTET STRING,
				msanAdslAtucPhysExtnDeltHLOGMTus
					Integer32,
				msanAdslAtucPhysExtnDeltHLOGpsus
					OCTET STRING,
				msanAdslAtucPhysExtnDeltQLNMTus
					Integer32,
				msanAdslAtucPhysExtnDeltQLNpsus
					OCTET STRING,
				msanAdslAtucPhysExtnDeltLastTxState
					INTEGER,
				msanAdslAtucPhysExtnPMState
					INTEGER,
				msanAdslAtucPhysExtnChanPerfCU
					Integer32,
				msanAdslAtucPhysExtnExtendedPsdStatus
					TruthValue,
				msanAdslAtucPhysExtnChipVersion
					Integer32,
				msanAdslAtucPhysExtnPilotTone
					Integer32,
				msanAdslAtucMSGds
					Gauge32,
				msanAdslAtucPhysExtnPsdMaskMode
					INTEGER,
				msanAdslAtucPhysExtnDeltSNRMTus
					Integer32,
				msanAdslAtucPhysExtnDeltCurrStatus
					INTEGER,
				msanAdslAtucSATN
					Integer32,
				msanAdslAtucPhysExtnSystemVendorId
					OCTET STRING,
				msanAdslAtucPhysExtnSelfTestResult
					Gauge32,
				msanAdslAtucPhysExtnG9941VendorId
					OCTET STRING,
				msanAdslAtucPhysExtnTsspsUs
					OCTET STRING,
				msanAdslAtucPhysExtnActPsdUs
					Integer32,
				msanAdslAtucPhysExtnGainspsUs
					OCTET STRING,
				msanAdslAtucPhysExtnStartBin
					Integer32,
				msanAdslAtucPhysExtnStartupErrorCode
					INTEGER,
				msanAdslAtucPhysExtnBitSwapCount
					Unsigned32,
				msanAdslAtucPhysExtnModPhase
					INTEGER
			 }

		-- 1.3.6.1.4.1.1332.1.1.5.3.36.2.1.1
		msanAdslAtucPhysExtnOpState OBJECT-TYPE
			SYNTAX INTEGER
				{
				idle(0),
				data(1),
				handshake(16),
				training(24),
				llTest(128),
				dlTest(131),
				txTest(132),
				framerSync(26),
				fastRetrainInProg(27),
				bootupLoad(8),
				atmLpTest(133),
				discovery(46),
				deltTraining(139),
				delt(140)
				}
			MAX-ACCESS read-only
			STATUS current
			DESCRIPTION
				"This object indicates the operational state of the ATU. Values include idle, handshake, training, etc."
			::= { msanAdslAtucPhysExtnEntry 1 }

		
		-- 1.3.6.1.4.1.1332.1.1.5.3.36.2.1.2
		msanAdslAtucPhysExtnActualStd OBJECT-TYPE
			SYNTAX INTEGER
				{
				t1413(0),
				gLite(1),
				gDmt(2),
				alctl14(3),
				multimode(4),
				adi(5),
				alctl(6),
				t1413auto(9),
				adslPlus(48),
				gspanPlus(64),
				adsl2(26),
				adsl2Plus(27),
				readsl2(28),
				adsl2Auto(29),
				adsl2PlusAuto(30),
				gspanPlusPlus(80)
				}
			MAX-ACCESS read-only
			STATUS current
			DESCRIPTION
				"This object provides actual ATU-C configuration based on outcome of negotiation with ATU-R. In this case, the parameter provides actual standard used for the connection."
			::= { msanAdslAtucPhysExtnEntry 2 }

		
		-- 1.3.6.1.4.1.1332.1.1.5.3.36.2.1.3
		msanAdslAtucPhysExtnBertError OBJECT-TYPE
			SYNTAX Integer32
			MAX-ACCESS read-only
			STATUS current
			DESCRIPTION
				"This object indicates the No. of bit errors detected during BERT."
			::= { msanAdslAtucPhysExtnEntry 3 }

		
		-- 1.3.6.1.4.1.1332.1.1.5.3.36.2.1.4
		msanAdslAtucPhysExtnTxAtmCellCounter OBJECT-TYPE
			SYNTAX Counter32
			MAX-ACCESS read-only
			STATUS current
			DESCRIPTION
				"This object Provides transmit ATM cell counter."
			::= { msanAdslAtucPhysExtnEntry 4 }

		
		-- 1.3.6.1.4.1.1332.1.1.5.3.36.2.1.5
		msanAdslAtucPhysExtnRxAtmCellCounter OBJECT-TYPE
			SYNTAX Integer32
			MAX-ACCESS read-only
			STATUS current
			DESCRIPTION
				"This object Provides receive ATM cell counter."
			::= { msanAdslAtucPhysExtnEntry 5 }

		
		-- 1.3.6.1.4.1.1332.1.1.5.3.36.2.1.6
		msanAdslAtucPhysExtnStartProgress OBJECT-TYPE
			SYNTAX Integer32
			MAX-ACCESS read-only
			STATUS current
			DESCRIPTION
				"This object provides current detailed start up information to be used for debugging."
			::= { msanAdslAtucPhysExtnEntry 6 }

		
		-- 1.3.6.1.4.1.1332.1.1.5.3.36.2.1.7
		msanAdslAtucPhysExtnIdleBertError OBJECT-TYPE
			SYNTAX Integer32
			MAX-ACCESS read-only
			STATUS current
			DESCRIPTION
				"Number of bit errors."
			::= { msanAdslAtucPhysExtnEntry 7 }

		
		-- 1.3.6.1.4.1.1332.1.1.5.3.36.2.1.8
		msanAdslAtucPhysExtnIdleBertCells OBJECT-TYPE
			SYNTAX Integer32
			MAX-ACCESS read-only
			STATUS current
			DESCRIPTION
				"Number of idle cells."
			::= { msanAdslAtucPhysExtnEntry 8 }

		
		-- 1.3.6.1.4.1.1332.1.1.5.3.36.2.1.9
		msanAdslAtucPhysExtnBertSync OBJECT-TYPE
			SYNTAX INTEGER
				{
				bertOutOfSync(0),
				bertInSync(128)
				}
			MAX-ACCESS read-only
			STATUS current
			DESCRIPTION
				"Indicates if the Signal is in Sync or not."
			::= { msanAdslAtucPhysExtnEntry 9 }

		
		-- 1.3.6.1.4.1.1332.1.1.5.3.36.2.1.10
		msanAdslAtucPhysExtnParametricTestResult OBJECT-TYPE
			SYNTAX INTEGER
				{
				ok(0),
				fail(1),
				dspIfFail(2)
				}
			MAX-ACCESS read-only
			STATUS current
			DESCRIPTION
				"Indicates the Result of the Parametric Test conducted on the Xcvr."
			::= { msanAdslAtucPhysExtnEntry 10 }

		
		-- 1.3.6.1.4.1.1332.1.1.5.3.36.2.1.11
		msanAdslAtucPhysExtnSeltInfoValid OBJECT-TYPE
			SYNTAX INTEGER
				{
				true(1),
				notConnected(32768),
				lostConnection(33024),
				noResponseSeltEngine(33280)
				}
			MAX-ACCESS read-only
			STATUS current
			DESCRIPTION
				"Indicates the information validity for the SELT operation conducted on the Xcvr."
			::= { msanAdslAtucPhysExtnEntry 11 }

		
		-- 1.3.6.1.4.1.1332.1.1.5.3.36.2.1.12
		msanAdslAtucPhysExtnSeltLoopLen OBJECT-TYPE
			SYNTAX Integer32
			MAX-ACCESS read-only
			STATUS current
			DESCRIPTION
				"Indicates the LOOP Length in Feet once when the SELT information is valid on the Xcvr."
			::= { msanAdslAtucPhysExtnEntry 12 }

		
		-- 1.3.6.1.4.1.1332.1.1.5.3.36.2.1.13
		msanAdslAtucPhysExtnSeltLoopEnd OBJECT-TYPE
			SYNTAX INTEGER
				{
				open(0),
				short(1),
				unknown(2)
				}
			MAX-ACCESS read-only
			STATUS current
			DESCRIPTION
				"Indicates whether the loop is short or open once when the SELT information is valid on the Xcvr."
			::= { msanAdslAtucPhysExtnEntry 13 }

		
		-- 1.3.6.1.4.1.1332.1.1.5.3.36.2.1.14
		msanAdslAtucPhysExtnSeltLoopGauge OBJECT-TYPE
			SYNTAX INTEGER
				{
				greater26awg(-1),
				equal26awg(0),
				equal24awg(1),
				less26awg(2),
				unknownAwg(3)
				}
			MAX-ACCESS read-only
			STATUS current
			DESCRIPTION
				"Indicates the LOOP wire_gauge information once when the SELT information is valid on the Xcvr."
			::= { msanAdslAtucPhysExtnEntry 14 }

		
		-- 1.3.6.1.4.1.1332.1.1.5.3.36.2.1.15
		msanAdslAtucPhysExtnSeltUpShannonCap OBJECT-TYPE
			SYNTAX Gauge32
			MAX-ACCESS read-only
			STATUS current
			DESCRIPTION
				"Indicates the LOOP Upstream Shannon Capacity (in bps) once when the SELT information is valid on the Xcvr."
			::= { msanAdslAtucPhysExtnEntry 15 }

		
		-- 1.3.6.1.4.1.1332.1.1.5.3.36.2.1.16
		msanAdslAtucPhysExtnSeltDownShannonCap OBJECT-TYPE
			SYNTAX Gauge32
			MAX-ACCESS read-only
			STATUS current
			DESCRIPTION
				"Indicates the LOOP Downstream Shannon Capacity (in bps) once when the SELT information is valid on the Xcvr."
			::= { msanAdslAtucPhysExtnEntry 16 }

		
		-- 1.3.6.1.4.1.1332.1.1.5.3.36.2.1.17
		msanAdslAtucPhysExtnSeltInbandNoise OBJECT-TYPE
			SYNTAX OCTET STRING (SIZE (0..2048))
			MAX-ACCESS read-only
			STATUS current
			DESCRIPTION
				"512 values that indicate inband noise length in dBM/Hz, covering both bands from 0 to 1.1 MHz."
			::= { msanAdslAtucPhysExtnEntry 17 }

		
		-- 1.3.6.1.4.1.1332.1.1.5.3.36.2.1.18
		msanAdslAtucPhysExtnSeltTerminationResp OBJECT-TYPE
			SYNTAX OCTET STRING (SIZE (0..720))
			MAX-ACCESS read-only
			STATUS current
			DESCRIPTION
				"180 discrete values that indicate termination response magnitude from 0 to 18Kft."
			::= { msanAdslAtucPhysExtnEntry 18 }

		
		-- 1.3.6.1.4.1.1332.1.1.5.3.36.2.1.19
		msanAdslAtucPhysExtnSeltUpMgnAtRate OBJECT-TYPE
			SYNTAX OCTET STRING (SIZE (0..1200))
			MAX-ACCESS read-only
			STATUS current
			DESCRIPTION
				"300 values that indicate SNR margin in dB/10 at a particular rate are provided, at 100K increments, up to 15 Mbps."
			::= { msanAdslAtucPhysExtnEntry 19 }

		
		-- 1.3.6.1.4.1.1332.1.1.5.3.36.2.1.20
		msanAdslAtucPhysExtnSeltDownMgnAtRate OBJECT-TYPE
			SYNTAX OCTET STRING (SIZE (0..1200))
			MAX-ACCESS read-only
			STATUS current
			DESCRIPTION
				"300 values that indicate SNR margin in dB/10 at a particular rate are provided, at 100K increments, up to 15 Mbps."
			::= { msanAdslAtucPhysExtnEntry 20 }

		
		-- 1.3.6.1.4.1.1332.1.1.5.3.36.2.1.21
		msanAdslAtucPhysExtnDataBoostStatus OBJECT-TYPE
			SYNTAX INTEGER
				{
				enabled(32768),
				disabled(0)
				}
			MAX-ACCESS read-only
			STATUS current
			DESCRIPTION
				"This object indicates whether DataBoost is utilized for the connection."
			::= { msanAdslAtucPhysExtnEntry 21 }

		
		-- 1.3.6.1.4.1.1332.1.1.5.3.36.2.1.22
		msanAdslAtucPhysExtnTestArray OBJECT-TYPE
			SYNTAX OCTET STRING (SIZE (0..1024))
			MAX-ACCESS read-only
			STATUS current
			DESCRIPTION
				"This object indicates the Parametric Test Array. Every Four octets refer to one element in this array of octets."
			::= { msanAdslAtucPhysExtnEntry 22 }

		
		-- 1.3.6.1.4.1.1332.1.1.5.3.36.2.1.23
		msanAdslAtucPhysExtnChanPerfCD OBJECT-TYPE
			SYNTAX Integer32
			MAX-ACCESS read-only
			STATUS current
			DESCRIPTION
				"The near-end delineated total cell count performance parameter is a count of the total number of cells passed through the cell delineation and HEC function process operating on the ATM Data Path while in the SYNC state. (Not available for ADSL)."
			::= { msanAdslAtucPhysExtnEntry 23 }

		
		-- 1.3.6.1.4.1.1332.1.1.5.3.36.2.1.24
		msanAdslAtucPhysExtnChanPerfBE OBJECT-TYPE
			SYNTAX Integer32
			MAX-ACCESS read-only
			STATUS current
			DESCRIPTION
				"The near-end idle bit error count performance parameter is a count of the number of bit errors in the idle cell payload received in the ATM Data Path at the near-end. (Not available for ADSL)."
			::= { msanAdslAtucPhysExtnEntry 24 }

		
		-- 1.3.6.1.4.1.1332.1.1.5.3.36.2.1.25
		msanAdslAtucPhysExtnDeltHLINSCus OBJECT-TYPE
			SYNTAX Integer32
			MAX-ACCESS read-only
			STATUS current
			DESCRIPTION
				"DELT-related parameter that provides the scale factor to be applied to the upstream Hlin(f) values.(Not available for ADSL and ADSL2plus)."
			::= { msanAdslAtucPhysExtnEntry 25 }

		
		-- 1.3.6.1.4.1.1332.1.1.5.3.36.2.1.26
		msanAdslAtucPhysExtnDeltHLINpsus OBJECT-TYPE
			SYNTAX OCTET STRING (SIZE (0..128))
			MAX-ACCESS read-only
			STATUS current
			DESCRIPTION
				"DELT-related parameter that provides an array of complex upstream Hlin(f) values in linear scale. (Not available for ADSL and ADSL2plus).  Every two octets refer to one element in this array of octets."
			::= { msanAdslAtucPhysExtnEntry 26 }

		
		-- 1.3.6.1.4.1.1332.1.1.5.3.36.2.1.27
		msanAdslAtucPhysExtnDeltHLOGMTus OBJECT-TYPE
			SYNTAX Integer32
			MAX-ACCESS read-only
			STATUS current
			DESCRIPTION
				"DELT-related parameter that provides the number of symbols used to measure the upstream Hlog(f).(Not available for ADSL and ADSL2plus)."
			::= { msanAdslAtucPhysExtnEntry 27 }

		
		-- 1.3.6.1.4.1.1332.1.1.5.3.36.2.1.28
		msanAdslAtucPhysExtnDeltHLOGpsus OBJECT-TYPE
			SYNTAX OCTET STRING (SIZE (0..64))
			MAX-ACCESS read-only
			STATUS current
			DESCRIPTION
				"DELT-related parameter that provides an array of real upstream Hlog(f) values in dB. (Not available for ADSL and ADSL2plus). Every two octets refer to one element in this array of octets."
			::= { msanAdslAtucPhysExtnEntry 28 }

		
		-- 1.3.6.1.4.1.1332.1.1.5.3.36.2.1.29
		msanAdslAtucPhysExtnDeltQLNMTus OBJECT-TYPE
			SYNTAX Integer32
			MAX-ACCESS read-only
			STATUS current
			DESCRIPTION
				"DELT-related parameter that provides the number of symbols used to measure the upstream QLN(f) values. (Not available for ADSL and ADSL2plus)."
			::= { msanAdslAtucPhysExtnEntry 29 }

		
		-- 1.3.6.1.4.1.1332.1.1.5.3.36.2.1.30
		msanAdslAtucPhysExtnDeltQLNpsus OBJECT-TYPE
			SYNTAX OCTET STRING (SIZE (0..32))
			MAX-ACCESS read-only
			STATUS current
			DESCRIPTION
				"DELT-related parameter that provides an array of real upstream QLN(f) values in dB. (Not available for ADSL and ADSL2plus). Every two octets refer to one element in this array of octets."
			::= { msanAdslAtucPhysExtnEntry 30 }

		
		-- 1.3.6.1.4.1.1332.1.1.5.3.36.2.1.31
		msanAdslAtucPhysExtnDeltLastTxState OBJECT-TYPE
			SYNTAX INTEGER
				{
				dmtatucg9941(0),
				dmtatucquiet1(1),
				dmtatuccomb1(2),
				dmtatucquiet2(3),
				dmtatuccomb2(4),
				dmtatucicomb1(5),
				dmtatuclineprob(6),
				dmtatucquiet3(7),
				dmtatuccomb3(8),
				dmtatucicomb2(9),
				dmtatucmsgfmt(10),
				dmtatucmsgpcb(11),
				dmtatucquiet4(12),
				dmtatucreverb1(13),
				dmtatuctref1(14),
				dmtatucreverb2(15),
				dmtatucect(16),
				dmtatucreverb3(17),
				dmtatuctref2(18),
				dmtatucreverb4(19),
				dmtatucsegue1(20),
				dmtatucmsg1(21),
				dmtatucreverb5(22),
				dmtatucsegue2(23),
				dmtatucmedley(24),
				dmtatucexchmarker(25),
				dmtatucmsg2(26),
				dmtatucreverb6(27),
				dmtatucsegue3(28),
				dmtatucparams(29),
				dmtatucreverb7(30),
				dmtatucsegue4(31),
				dmtatucshowtime(32)
				}
			MAX-ACCESS read-only
			STATUS current
			DESCRIPTION
				"DELT-related parameter that provides last successful transmitted initialization state by the ATU-C. (Not available for ADSL and ADSL2plus)."
			::= { msanAdslAtucPhysExtnEntry 31 }

		
		-- 1.3.6.1.4.1.1332.1.1.5.3.36.2.1.32
		msanAdslAtucPhysExtnPMState OBJECT-TYPE
			SYNTAX INTEGER
				{
				l0(0),
				l2(2),
				l3(3)
				}
			MAX-ACCESS read-only
			STATUS current
			DESCRIPTION
				"Line Power Management State. (Not available for ADSL)."
			::= { msanAdslAtucPhysExtnEntry 32 }

		
		-- 1.3.6.1.4.1.1332.1.1.5.3.36.2.1.33
		msanAdslAtucPhysExtnChanPerfCU OBJECT-TYPE
			SYNTAX Integer32
			MAX-ACCESS read-only
			STATUS current
			DESCRIPTION
				" The near-end user total cell count performance parameter is a count of the total number of cells in the ATM Data Path delivered at the V-C (for ATU-C) or T-R (for ATU-R) interface. (Not available for ADSL)."
			::= { msanAdslAtucPhysExtnEntry 33 }

		
		-- 1.3.6.1.4.1.1332.1.1.5.3.36.2.1.34
		msanAdslAtucPhysExtnExtendedPsdStatus OBJECT-TYPE
			SYNTAX TruthValue
			MAX-ACCESS read-only
			STATUS current
			DESCRIPTION
				"Conexant parameter that indicates whether an extended upstream PSD is used - for G.Span Plus mode of operation only. Only supported for G.Span Plus, therefore this parameter is not valid for ADSL2/ADSL2plus modes of operation."
			::= { msanAdslAtucPhysExtnEntry 34 }

		
		-- 1.3.6.1.4.1.1332.1.1.5.3.36.2.1.35
		msanAdslAtucPhysExtnChipVersion OBJECT-TYPE
			SYNTAX Integer32
			MAX-ACCESS read-only
			STATUS current
			DESCRIPTION
				"Conexant parameter that indicates the DSP version number."
			::= { msanAdslAtucPhysExtnEntry 35 }

		
		-- 1.3.6.1.4.1.1332.1.1.5.3.36.2.1.36
		msanAdslAtucPhysExtnPilotTone OBJECT-TYPE
			SYNTAX Integer32
			MAX-ACCESS read-only
			STATUS current
			DESCRIPTION
				"Conexant parameter that indicates the Pilot Tone Index."
			::= { msanAdslAtucPhysExtnEntry 36 }

		
		-- 1.3.6.1.4.1.1332.1.1.5.3.36.2.1.37
		msanAdslAtucMSGds OBJECT-TYPE
			SYNTAX Gauge32
			MAX-ACCESS read-only
			STATUS current
			DESCRIPTION
				"Indicates the Overhead Channel. This feature is not supported by DSLPHY as yet."
			::= { msanAdslAtucPhysExtnEntry 37 }

		
		-- 1.3.6.1.4.1.1332.1.1.5.3.36.2.1.38
		msanAdslAtucPhysExtnPsdMaskMode OBJECT-TYPE
			SYNTAX INTEGER
				{
				coMsk2(0),
				flatMsk(3),
				cabMsk2(4),
				coMsk2Rfi(32768),
				flatMskRfi(32771),
				cabMsk2Rfi(32772),
				coMsk2Rfi0(49152),
				adsl2NonovlpM1(275),
				adsl2NonovlpM2(291),
				adsl2NonovlpFlat(259)
				}
			MAX-ACCESS read-only
			STATUS current
			DESCRIPTION
				"Conexant parameter that indicates the actual Psd Mask currently being used."
			::= { msanAdslAtucPhysExtnEntry 38 }

		
		-- 1.3.6.1.4.1.1332.1.1.5.3.36.2.1.39
		msanAdslAtucPhysExtnDeltSNRMTus OBJECT-TYPE
			SYNTAX Integer32
			MAX-ACCESS read-only
			STATUS current
			DESCRIPTION
				"DELT-related parameter that provides the number of symbols used to measure the upstream SNR(f) values. (Not available for ADSL and ADSL2plus)"
			::= { msanAdslAtucPhysExtnEntry 39 }

		
		-- 1.3.6.1.4.1.1332.1.1.5.3.36.2.1.40
		msanAdslAtucPhysExtnDeltCurrStatus OBJECT-TYPE
			SYNTAX INTEGER
				{
				success(255),
				failedInsufficientCapacity(17),
				failedCrcError(34),
				failedTimeOut(68),
				failedUnexpectedContent(136),
				failedUnknown(0)
				}
			MAX-ACCESS read-only
			STATUS current
			DESCRIPTION
				"This Conexant parameter indicates the current status of Atuc Line in DELT mode."
			::= { msanAdslAtucPhysExtnEntry 40 }

		
		-- 1.3.6.1.4.1.1332.1.1.5.3.36.2.1.41
		msanAdslAtucSATN OBJECT-TYPE
			SYNTAX Integer32
			MAX-ACCESS read-only
			STATUS current
			DESCRIPTION
				"DELT-related parameter that provides the upstream signal attenuation (length = 4 bytes). (Not available for ADSL and ADSL2plus). For further details, Refer to Section 7.5.1.9 Revised Recommendation G.997.1."
			::= { msanAdslAtucPhysExtnEntry 41 }

		
		-- 1.3.6.1.4.1.1332.1.1.5.3.36.2.1.42
		msanAdslAtucPhysExtnSystemVendorId OBJECT-TYPE
			SYNTAX OCTET STRING (SIZE (0..9))
			MAX-ACCESS read-only
			STATUS current
			DESCRIPTION
				"Indicates the Vendor ID as inserted by the ATU-C in the Overhead Messages(ADSL2). Typically identifies the ATU-C system integrator which usually refers to the vendor of the smallest field-replaceable unit. ATU-C System Vendor ID may not be the same as ATU-C Vendor ID. It is not available for ADSL. This is string of 8 octets containing 2 octet country code , 4 octet vendor id and 2 octet vendor revision number."
			::= { msanAdslAtucPhysExtnEntry 42 }

		
		-- 1.3.6.1.4.1.1332.1.1.5.3.36.2.1.43
		msanAdslAtucPhysExtnSelfTestResult OBJECT-TYPE
			SYNTAX Gauge32
			MAX-ACCESS read-only
			STATUS current
			DESCRIPTION
				"Defines the ATU-C selftest result. The most significant octet is: 00 hex if the self-test passed or 01 hex if the self-test failed. Interpretation of the other octets is vendor discretionary and can be interpreted in combination with G.994.1 and system Vendor IDs. For further details, refer to Section 7.4.9 Revised Recommendation G.997.1."
			::= { msanAdslAtucPhysExtnEntry 43 }

		
		-- 1.3.6.1.4.1.1332.1.1.5.3.36.2.1.44
		msanAdslAtucPhysExtnG9941VendorId OBJECT-TYPE
			SYNTAX OCTET STRING (SIZE (0..9))
			MAX-ACCESS read-only
			STATUS current
			DESCRIPTION
				"Indicates the Vendor ID as inserted by the ATU-C in the G.994.1 CL message. Typically identifies the vendor of the ATU-C G.994.1 functionality. This is string of 8 octets containing 2 octet country code , 4 octet vendor id and 2 octet vendor revision number. For further details, refer to Section 7.4.1 Revised Recommendation G.997.1."
			::= { msanAdslAtucPhysExtnEntry 44 }

		
		-- 1.3.6.1.4.1.1332.1.1.5.3.36.2.1.45
		msanAdslAtucPhysExtnTsspsUs OBJECT-TYPE
			SYNTAX OCTET STRING (SIZE (0..128))
			MAX-ACCESS read-only
			STATUS current
			DESCRIPTION
				"This parameter provides the Upstream Transmit Spectrum Shaping parameter expressed as the set of break points exchanged during G994.1. Each breakpoint consists in a subcarrier index and the associated shaping parameter. Value of this parameter is in range 0 - 127, in multiples of -0.5 dB. 127 is a special value indicating the subcarrier is not transmitted. It is available only for ADSL2/ADSL2plus.For further details, Refer to Section 7.5.1.21.5 Revised Recommendation G.997.1."
			::= { msanAdslAtucPhysExtnEntry 45 }

		
		-- 1.3.6.1.4.1.1332.1.1.5.3.36.2.1.46
		msanAdslAtucPhysExtnActPsdUs OBJECT-TYPE
			SYNTAX Integer32
			MAX-ACCESS read-only
			STATUS current
			DESCRIPTION
				"This parameter defines the average upstream transmit power spectrum density over the used subcarriers delivered by the ATU-C at the U-C reference point, at the instant of measurement. It's value ranges from -90 to 0, in 0.1 dB/Hz steps. It is available only for ADSL2/ADSL2plus. For further details, Refer to Section 7.5.1.14 Revised Recommendation G.997.1."
			::= { msanAdslAtucPhysExtnEntry 46 }

		
		-- 1.3.6.1.4.1.1332.1.1.5.3.36.2.1.47
		msanAdslAtucPhysExtnGainspsUs OBJECT-TYPE
			SYNTAX OCTET STRING (SIZE (0..128))
			MAX-ACCESS read-only
			STATUS current
			DESCRIPTION
				"This parameter defines the upstream gains allocation table per subcarrier. It is an array of integer values in the 0 to 4093 range for subcarriers 0 to NSCus-1. The gain value is represented as a multiple of 1/512 on linear scale. It is supported for ADSL2/ADSl2plus only."
			::= { msanAdslAtucPhysExtnEntry 47 }

		
		-- 1.3.6.1.4.1.1332.1.1.5.3.36.2.1.48
		msanAdslAtucPhysExtnStartBin OBJECT-TYPE
			SYNTAX Integer32
			MAX-ACCESS read-only
			STATUS current
			DESCRIPTION
				"This Gspan++ parameter indicates the start bin of the bit loading up array."
			::= { msanAdslAtucPhysExtnEntry 48 }

		
		-- 1.3.6.1.4.1.1332.1.1.5.3.36.2.1.49
		msanAdslAtucPhysExtnStartupErrorCode OBJECT-TYPE
			SYNTAX INTEGER
				{
				startupErrorCodeOk(0),
				startupErrorCodeMaxnomPsdDs(1),
				startupErrorCodeMaxnomPsdUs(65536),
				startupErrorCodePsdMaskDs(2),
				startupErrorCodePsdMaskUs(131072),
				startupErrorCodeMaxnomAtpDs(4),
				startupErrorCodeMaxnomAtpUs(262144)
				}
			MAX-ACCESS read-only
			STATUS current
			DESCRIPTION
				"Conexant parameter which indicates the startup error code."
			::= { msanAdslAtucPhysExtnEntry 49 }

		
		-- 1.3.6.1.4.1.1332.1.1.5.3.36.2.1.50
		msanAdslAtucPhysExtnBitSwapCount OBJECT-TYPE
			SYNTAX Unsigned32
			MAX-ACCESS read-only
			STATUS current
			DESCRIPTION
				"This Conexant parameter indicates the bit swap count. It can read only in data mode"
			::= { msanAdslAtucPhysExtnEntry 50 }

		
		-- 1.3.6.1.4.1.1332.1.1.5.3.36.2.1.51
		msanAdslAtucPhysExtnModPhase OBJECT-TYPE
			SYNTAX INTEGER
				{
				flatRateCheck(0),
				snrMeasure(1),
				modRateCheck(2),
				modShowtime(3),
				flatShowtime(4)
				}
			MAX-ACCESS read-only
			STATUS current
			DESCRIPTION
				"Conexant parameter to monitor the status of MoD"
			::= { msanAdslAtucPhysExtnEntry 51 }

		
		-- 1.3.6.1.4.1.1332.1.1.5.3.36.3
		msanAdslLineExtnTable OBJECT-TYPE
			SYNTAX SEQUENCE OF MsanAdslLineExtnEntry
			MAX-ACCESS not-accessible
			STATUS current
			DESCRIPTION
				"This table includes common attributes describing both ends of the line.  It is required for all ADSL physical interfaces. This Table is an extension to adslLineTable defined in rfc-2662."
			::= { msanAdsl 3 }

		
		-- 1.3.6.1.4.1.1332.1.1.5.3.36.3.1
		msanAdslLineExtnEntry OBJECT-TYPE
			SYNTAX MsanAdslLineExtnEntry
			MAX-ACCESS not-accessible
			STATUS current
			DESCRIPTION
				"An entry (conceptual row) in the msanAdslLineExtnTable.
				The Table is indexed by ifIndex."
			INDEX { ifIndex }
			::= { msanAdslLineExtnTable 1 }

		
		MsanAdslLineExtnEntry ::=
			SEQUENCE { 
				msanAdslLineExtnAction
					INTEGER,
				msanAdslLineExtnUtopiaL2RxAddr
					INTEGER,
				msanAdslLineExtnUtopiaL2TxAddr
					INTEGER,
				msanAdslLineExtnTransAtucCap
					BITS,
				msanAdslLineExtnTransAtucActual
					BITS,
				msanAdslLineExtnClockType
					INTEGER,
				msanAdslLineExtnLineDmtTrellis
					INTEGER,
				msanAdslLineExtnTransAturCap
					BITS,
				msanAdslLineExtnPMConfPMSF
					INTEGER,
				msanAdslLineExtnDeltConfLDSF
					INTEGER,
				msanAdslLineExtnTransAtucConfig
					BITS,
				msanAdslLineExtnAtucCurrOutputPwr
					Integer32,
				msanAdslLineExtnAtucBinSNRMargin
					OCTET STRING,
				msanAdslLineExtnUtopiaL2RxAddrSecond
					INTEGER,
				msanAdslLineExtnUtopiaL2TxAddrSecond
					INTEGER,
				msanAdslLineExtnDsBinSnrUpdate
					INTEGER,
				msanAdslLineExtnServiceType
					INTEGER
			 }

		-- 1.3.6.1.4.1.1332.1.1.5.3.36.3.1.1
		msanAdslLineExtnAction OBJECT-TYPE
			SYNTAX INTEGER
				{
				startup(0),
				spectrumReverb(5),
				analogLb(6),
				digitalLb(7),
				atmLp(10),
				spectrumMedley(26),
				spectrumPilot(27),
				spectrumCMtpr(30),
				spectrumRMtpr(32),
				hybridLossTest(8193),
				rcvLinearityTest(8194),
				rcvFilterTest(8195),
				rcvPowerPerBinTest(8196),
				idleNoisePerBinTest(8198),
				totalIdleNoiseTest(8197),
				selt(4134),
				shutdown(101),
				wakeup(102),
				abortReq(2)
				}
			MAX-ACCESS read-write
			STATUS current
			DESCRIPTION
				"this object indicates parameter that allows actions on a per line basis. These actions include abort, startup, and tests."
			::= { msanAdslLineExtnEntry 1 }

		
		-- 1.3.6.1.4.1.1332.1.1.5.3.36.3.1.2
		msanAdslLineExtnUtopiaL2RxAddr OBJECT-TYPE
			SYNTAX INTEGER (0..254)
			MAX-ACCESS read-only
			STATUS current
			DESCRIPTION
				"This object indicates UTOPIA Level 2 Rx address for a line."
			::= { msanAdslLineExtnEntry 2 }

		
		-- 1.3.6.1.4.1.1332.1.1.5.3.36.3.1.3
		msanAdslLineExtnUtopiaL2TxAddr OBJECT-TYPE
			SYNTAX INTEGER (0..254)
			MAX-ACCESS read-only
			STATUS current
			DESCRIPTION
				"This object indicates UTOPIA Level 2 Tx address for a line."
			::= { msanAdslLineExtnEntry 3 }

		
		-- 1.3.6.1.4.1.1332.1.1.5.3.36.3.1.4
		msanAdslLineExtnTransAtucCap OBJECT-TYPE
			SYNTAX BITS
				{
				ansit1413(0),
				etsi(1),
				q9921PotsNonOverlapped(2),
				q9921PotsOverlapped(3),
				q9921IsdnNonOverlapped(4),
				q9921isdnOverlapped(5),
				q9921tcmIsdnNonOverlapped(6),
				q9921tcmIsdnOverlapped(7),
				q9922potsNonOverlapeed(8),
				q9922potsOverlapped(9),
				q9922tcmIsdnNonOverlapped(10),
				q9922tcmIsdnOverlapped(11),
				q9921tcmIsdnSymmetric(12),
				adslPlusPotsNonOverlapped(13),
				q9921GspanPlusPotsNonOverlapped(31),
				q9921GspanPlusPotsOverlapped(30),
				vdslNonOverlapped(25),
				vdslOverlapped(24),
				q9923Adsl2PotsOverlapped(29),
				q9923Adsl2PotsNonOverlapped(28),
				q9925Adsl2PlusPotsOverlapped(27),
				q9925Adsl2PlusPotsNonOverlapped(26),
				q9923Readsl2PotsOverlapped(22),
				q9923Readsl2PotsNonOverlapped(23),
				adslPlusPotsOverlapped(18),
				q9921GspanPlusPlusPotsNonOverlapped(20),
				q9921GspanPlusPlusPotsOverlapped(21),
				q9923IsdnNonOverlapped(34),
				q9923IsdnOverlapped(35),
				q9925IsdnNonOverlapped(42),
				q9925IsdnOverlapped(43),
				q9923AnnexMPotsExtUsNonOverlapped(56),
				q9923AnnexMPotsExtUsOverlapped(57),
				q9925AnnexMPotsExtUsNonOverlapped(60),
				q9925AnnexMPotsExtUsOverlapped(61)
				}
			MAX-ACCESS read-only
			STATUS current
			DESCRIPTION
				"The transmission modes that the ATU-C is capable of supporting. The modes available are limited by the design of the equipment. REFERENCE Section 7.3.2 ITU G.997.1."
			::= { msanAdslLineExtnEntry 4 }

		
		-- 1.3.6.1.4.1.1332.1.1.5.3.36.3.1.5
		msanAdslLineExtnTransAtucActual OBJECT-TYPE
			SYNTAX BITS
				{
				ansit1413(0),
				etsi(1),
				q9921PotsNonOverlapped(2),
				q9921PotsOverlapped(3),
				q9921IsdnNonOverlapped(4),
				q9921isdnOverlapped(5),
				q9921tcmIsdnNonOverlapped(6),
				q9921tcmIsdnOverlapped(7),
				q9922potsNonOverlapeed(8),
				q9922potsOverlapped(9),
				q9922tcmIsdnNonOverlapped(10),
				q9922tcmIsdnOverlapped(11),
				q9921tcmIsdnSymmetric(12),
				adslPlusPotsNonOverlapped(13),
				q9921GspanPlusPotsNonOverlapped(31),
				q9921GspanPlusPotsOverlapped(30),
				vdslNonOverlapped(25),
				vdslOverlapped(24),
				q9923Adsl2PotsOverlapped(29),
				q9923Adsl2PotsNonOverlapped(28),
				q9925Adsl2PlusPotsOverlapped(27),
				q9925Adsl2PlusPotsNonOverlapped(26),
				q9923Readsl2PotsOverlapped(22),
				q9923Readsl2PotsNonOverlapped(23),
				adslPlusPotsOverlapped(18),
				q9921GspanPlusPlusPotsNonOverlapped(20),
				q9921GspanPlusPlusPotsOverlapped(21),
				q9923IsdnNonOverlapped(34),
				q9923IsdnOverlapped(35),
				q9925IsdnNonOverlapped(42),
				q9925IsdnOverlapped(43),
				q9923AnnexMPotsExtUsNonOverlapped(56),
				q9923AnnexMPotsExtUsOverlapped(57),
				q9925AnnexMPotsExtUsNonOverlapped(60),
				q9925AnnexMPotsExtUsOverlapped(61)
				}
			MAX-ACCESS read-only
			STATUS current
			DESCRIPTION
				"The transmission mode of the ATU-C. This object returns if there is no mode currently known. The initialization with the ATU-R will determine the mode used. REFERENCE Section 7.3.2 ITU G.997.1."
			::= { msanAdslLineExtnEntry 5 }

		
		-- 1.3.6.1.4.1.1332.1.1.5.3.36.3.1.6
		msanAdslLineExtnClockType OBJECT-TYPE
			SYNTAX INTEGER
				{
				oscillator(0),
				crystal(4)
				}
			MAX-ACCESS read-only
			STATUS current
			DESCRIPTION
				"This object indicates parameter to set use of either crystal or oscillator."
			::= { msanAdslLineExtnEntry 6 }

		
		-- 1.3.6.1.4.1.1332.1.1.5.3.36.3.1.7
		msanAdslLineExtnLineDmtTrellis OBJECT-TYPE
			SYNTAX INTEGER
				{
				trellisOn(1),
				trellisOff(2)
				}
			MAX-ACCESS read-only
			STATUS current
			DESCRIPTION
				"Parameter that indicates whether trellis coding has been enabled or disabled. Trellis coding should always be enabled for its clear performance advantage."
			::= { msanAdslLineExtnEntry 7 }

		
		-- 1.3.6.1.4.1.1332.1.1.5.3.36.3.1.8
		msanAdslLineExtnTransAturCap OBJECT-TYPE
			SYNTAX BITS
				{
				ansit1413(0),
				etsi(1),
				q9921PotsNonOverlapped(2),
				q9921PotsOverlapped(3),
				q9921IsdnNonOverlapped(4),
				q9921isdnOverlapped(5),
				q9921tcmIsdnNonOverlapped(6),
				q9921tcmIsdnOverlapped(7),
				q9922potsNonOverlapeed(8),
				q9922potsOverlapped(9),
				q9922tcmIsdnNonOverlapped(10),
				q9922tcmIsdnOverlapped(11),
				q9921tcmIsdnSymmetric(12),
				adslPlusPotsNonOverlapped(13),
				q9921GspanPlusPotsNonOverlapped(31),
				q9921GspanPlusPotsOverlapped(30),
				vdslNonOverlapped(25),
				vdslOverlapped(24),
				q9923Adsl2PotsOverlapped(29),
				q9923Adsl2PotsNonOverlapped(28),
				q9925Adsl2PlusPotsOverlapped(27),
				q9925Adsl2PlusPotsNonOverlapped(26),
				q9923Readsl2PotsOverlapped(22),
				q9923Readsl2PotsNonOverlapped(23),
				adslPlusPotsOverlapped(18),
				q9921GspanPlusPlusPotsNonOverlapped(20),
				q9921GspanPlusPlusPotsOverlapped(21),
				q9923IsdnNonOverlapped(34),
				q9923IsdnOverlapped(35),
				q9925IsdnNonOverlapped(42),
				q9925IsdnOverlapped(43),
				q9923AnnexMPotsExtUsNonOverlapped(56),
				q9923AnnexMPotsExtUsOverlapped(57),
				q9925AnnexMPotsExtUsNonOverlapped(60),
				q9925AnnexMPotsExtUsOverlapped(61)
				}
			MAX-ACCESS read-only
			STATUS current
			DESCRIPTION
				"The transmission modes that the ATU-R is capable of supporting. The modes available are limited by the design of the equipment."
			::= { msanAdslLineExtnEntry 8 }

		
		-- 1.3.6.1.4.1.1332.1.1.5.3.36.3.1.9
		msanAdslLineExtnPMConfPMSF OBJECT-TYPE
			SYNTAX INTEGER
				{
				l3ToL0StateForce(0),
				l0ToL2StateForce(2),
				l3StateForce(3),
				l2ToL0StateForce(4)
				}
			MAX-ACCESS read-write
			STATUS current
			DESCRIPTION
				"PM-related parameter used by the ATU-C to force a change in the line state.(Not available for ADSL/ADSL2Plus)."
			::= { msanAdslLineExtnEntry 9 }

		
		-- 1.3.6.1.4.1.1332.1.1.5.3.36.3.1.10
		msanAdslLineExtnDeltConfLDSF OBJECT-TYPE
			SYNTAX INTEGER
				{
				inhibit(0),
				force(1)
				}
			MAX-ACCESS read-write
			STATUS current
			DESCRIPTION
				"DELT-related parameter used by the ATU-C to force the line into loop diagnostics mode.(Not available for ADSL and ADSL2plus)."
			::= { msanAdslLineExtnEntry 10 }

		
		-- 1.3.6.1.4.1.1332.1.1.5.3.36.3.1.11
		msanAdslLineExtnTransAtucConfig OBJECT-TYPE
			SYNTAX BITS
				{
				ansit1413(0),
				etsi(1),
				q9921PotsNonOverlapped(2),
				q9921PotsOverlapped(3),
				q9921IsdnNonOverlapped(4),
				q9921isdnOverlapped(5),
				q9921tcmIsdnNonOverlapped(6),
				q9921tcmIsdnOverlapped(7),
				q9922potsNonOverlapeed(8),
				q9922potsOverlapped(9),
				q9922tcmIsdnNonOverlapped(10),
				q9922tcmIsdnOverlapped(11),
				q9921tcmIsdnSymmetric(12),
				adslPlusPotsNonOverlapped(13),
				q9921GspanPlusPotsNonOverlapped(31),
				q9921GspanPlusPotsOverlapped(30),
				q9923Adsl2PotsOverlapped(29),
				q9923Adsl2PotsNonOverlapped(28),
				q9925Adsl2PlusPotsOverlapped(27),
				q9925Adsl2PlusPotsNonOverlapped(26),
				q9923Readsl2PotsOverlapped(22),
				q9923Readsl2PotsNonOverlapped(23),
				adslPlusPotsOverlapped(18),
				q9921GspanPlusPlusPotsNonOverlapped(20),
				q9921GspanPlusPlusPotsOverlapped(21),
				q9923IsdnNonOverlapped(34),
				q9923IsdnOverlapped(35),
				q9925IsdnNonOverlapped(42),
				q9925IsdnOverlapped(43),
				q9923AnnexMPotsExtUsNonOverlapped(56),
				q9923AnnexMPotsExtUsOverlapped(57),
				q9925AnnexMPotsExtUsNonOverlapped(60),
				q9925AnnexMPotsExtUsOverlapped(61)
				}
			MAX-ACCESS read-write
			STATUS current
			DESCRIPTION
				"The transmission modes that the ATU-C is capable of supporting. The modes available are limited by the design of the equipment. REFERENCE Section 7.3.2 ITU G.997.1."
			::= { msanAdslLineExtnEntry 11 }

		
		-- 1.3.6.1.4.1.1332.1.1.5.3.36.3.1.12
		msanAdslLineExtnAtucCurrOutputPwr OBJECT-TYPE
			SYNTAX Integer32
			MAX-ACCESS read-only
			STATUS current
			DESCRIPTION
				"This parameter indicates the measure of total output power transmitted by this ATU. The value of this parameter is dynamic and will also show the change in Tx power due to Power Management. For example, the value will decrease in L2 low power mode. This value can be negative"
			::= { msanAdslLineExtnEntry 12 }

		
		-- 1.3.6.1.4.1.1332.1.1.5.3.36.3.1.13
		msanAdslLineExtnAtucBinSNRMargin OBJECT-TYPE
			SYNTAX OCTET STRING (SIZE (0..64))
			MAX-ACCESS read-only
			STATUS current
			DESCRIPTION
				"This Conexant parameter is an array of upstream SNR Margin values in dB. Each array entry represents the SNR Margin value for particular sub carrier."
			::= { msanAdslLineExtnEntry 13 }

		
		-- 1.3.6.1.4.1.1332.1.1.5.3.36.3.1.14
		msanAdslLineExtnUtopiaL2RxAddrSecond OBJECT-TYPE
			SYNTAX INTEGER (0..254)
			MAX-ACCESS read-only
			STATUS current
			DESCRIPTION
				"Conexant parameter to set UTOPIA Level 2 Rx address for the secondary bearer channel in case of Dual Latency."
			::= { msanAdslLineExtnEntry 14 }

		
		-- 1.3.6.1.4.1.1332.1.1.5.3.36.3.1.15
		msanAdslLineExtnUtopiaL2TxAddrSecond OBJECT-TYPE
			SYNTAX INTEGER (0..254)
			MAX-ACCESS read-only
			STATUS current
			DESCRIPTION
				"Conexant parameter to set UTOPIA Level 2 Tx address for the secondary bearer channel in case of Dual Latency."
			::= { msanAdslLineExtnEntry 15 }

		
		-- 1.3.6.1.4.1.1332.1.1.5.3.36.3.1.16
		msanAdslLineExtnDsBinSnrUpdate OBJECT-TYPE
			SYNTAX INTEGER
				{
				disable(0),
				enable(1)
				}
			MAX-ACCESS read-write
			STATUS current
			DESCRIPTION
				"Conexant parameter to enable or disable collection of downstream SNR bin status"
			::= { msanAdslLineExtnEntry 16 }

		
		-- 1.3.6.1.4.1.1332.1.1.5.3.36.3.1.17
		msanAdslLineExtnServiceType OBJECT-TYPE
			SYNTAX INTEGER
				{
				multimode(1),
				reserved(2),
				t1413(3),
				gDmt(4),
				adsl2plus(6),
				adsl2(7),
				adsl2plusAutoAnnexM(8),
				adsl2AutoAnnexM(9),
				reAdsl2(10)
				}
			MAX-ACCESS read-only
			STATUS current
			DESCRIPTION
				"The service type configured in ADSL configuration profile which applies for this line.
				Supported values:
				1:  multimode
				2:  reserved
				3:  T1_413
				4:  G.DMT
				6:  ADSL2+
				7:  ADSL2
				8:  ADSL2+ AUTO[+Annex M]
				9:  ADSL2 AUTO[+Annex M]
				10: READSL2"
			::= { msanAdslLineExtnEntry 17 }

		
		-- 1.3.6.1.4.1.1332.1.1.5.3.36.4
		msanAdslAturPhysExtnTable OBJECT-TYPE
			SYNTAX SEQUENCE OF MsanAdslAturPhysExtnEntry
			MAX-ACCESS not-accessible
			STATUS current
			DESCRIPTION
				"This table is an extention to adslAtucPhysTable defined in rfc-2662. This table provides one row for each ATUR. Each row contains the Physical Layer Parameters table for that ATUR."
			::= { msanAdsl 4 }

		
		-- 1.3.6.1.4.1.1332.1.1.5.3.36.4.1
		msanAdslAturPhysExtnEntry OBJECT-TYPE
			SYNTAX MsanAdslAturPhysExtnEntry
			MAX-ACCESS not-accessible
			STATUS current
			DESCRIPTION
				"An entry (conceptual row) in the msanAdslAturPhysExtnTable.
				The Table is indexed by ifIndex."
			INDEX { ifIndex }
			::= { msanAdslAturPhysExtnTable 1 }

		
		MsanAdslAturPhysExtnEntry ::=
			SEQUENCE { 
				msanAdslAturPhysExtnConfig
					OCTET STRING,
				msanAdslAturPhysExtnChanPerfCD
					Integer32,
				msanAdslAturPhysExtnChanPerfCU
					Integer32,
				msanAdslAturPhysExtnChanPerfBE
					Integer32,
				msanAdslAturPhysExtnDeltHLINSCds
					Integer32,
				msanAdslAturPhysExtnDeltHLINpsds
					OCTET STRING,
				msanAdslAturPhysExtnDeltHLOGMTds
					Integer32,
				msanAdslAturPhysExtnDeltHLOGpsus
					OCTET STRING,
				msanAdslAturPhysExtnDeltQLNMTds
					Integer32,
				msanAdslAturPhysExtnDeltQLNpsds
					OCTET STRING,
				msanAdslAturPhysExtnDeltLastTxState
					INTEGER,
				msanAdslAturMSGus
					Gauge32,
				msanAdslAturDeltSNRMTds
					Gauge32,
				msanAdslAturSATN
					Integer32,
				msanAdslAturPhysExtnSystemVendorId
					OCTET STRING,
				msanAdslAturPhysExtnGainspsDs
					OCTET STRING,
				msanAdslAturPhysExtnSelfTestResult
					Gauge32,
				msanAdslAturPhysExtnG9941VendorId
					OCTET STRING,
				msanAdslAturPhysExtnTsspsDs
					OCTET STRING,
				msanAdslAturPhysExtnActPsdDs
					Integer32,
				msanAdslAturPhysExtnBitSwapCount
					Unsigned32,
				msanAdslAturPhysExtnPsdMaskMode
					INTEGER
			 }

		-- 1.3.6.1.4.1.1332.1.1.5.3.36.4.1.1
		msanAdslAturPhysExtnConfig OBJECT-TYPE
			SYNTAX OCTET STRING (SIZE (0..30))
			MAX-ACCESS read-only
			STATUS current
			DESCRIPTION
				"This object provides the upstream and downstream ATU-R configuration data, as defined in T1.413 i2, Sections 6.4, 6.6, 7.4, 7.6 and Table 27."
			::= { msanAdslAturPhysExtnEntry 1 }

		
		-- 1.3.6.1.4.1.1332.1.1.5.3.36.4.1.2
		msanAdslAturPhysExtnChanPerfCD OBJECT-TYPE
			SYNTAX Integer32
			MAX-ACCESS read-only
			STATUS current
			DESCRIPTION
				"The far-end delineated total cell count performance parameter is a count of the total number of cells passed through the cell delineation and HEC function process operating on the ATM Data Path while in the SYNC state.(Not available for ADSL)."
			::= { msanAdslAturPhysExtnEntry 2 }

		
		-- 1.3.6.1.4.1.1332.1.1.5.3.36.4.1.3
		msanAdslAturPhysExtnChanPerfCU OBJECT-TYPE
			SYNTAX Integer32
			MAX-ACCESS read-only
			STATUS current
			DESCRIPTION
				"The far-end user total cell count performance parameter is a count of the total number of cells in the ATM Data Path delivered at the V-C (for ATU-C) or T-R (for ATUR) interface. (Not available for ADSL)."
			::= { msanAdslAturPhysExtnEntry 3 }

		
		-- 1.3.6.1.4.1.1332.1.1.5.3.36.4.1.4
		msanAdslAturPhysExtnChanPerfBE OBJECT-TYPE
			SYNTAX Integer32
			MAX-ACCESS read-only
			STATUS current
			DESCRIPTION
				"The far-end idle bit error count performance parameter is a count of the number of bit errors in the idle cell payload received in the ATM Data Path at the far-end. (Not available for ADSL)."
			::= { msanAdslAturPhysExtnEntry 4 }

		
		-- 1.3.6.1.4.1.1332.1.1.5.3.36.4.1.5
		msanAdslAturPhysExtnDeltHLINSCds OBJECT-TYPE
			SYNTAX Integer32
			MAX-ACCESS read-only
			STATUS current
			DESCRIPTION
				"DELT-related parameter that provides the scale factor to be applied to the downstream Hlin(f) values.(Not available for ADSL and ADSL2plus)."
			::= { msanAdslAturPhysExtnEntry 5 }

		
		-- 1.3.6.1.4.1.1332.1.1.5.3.36.4.1.6
		msanAdslAturPhysExtnDeltHLINpsds OBJECT-TYPE
			SYNTAX OCTET STRING (SIZE (0..2048))
			MAX-ACCESS read-only
			STATUS current
			DESCRIPTION
				"DELT-related parameter that provides an array of complex downstream Hlin(f) values in linear scale. (Not available for ADSL and ADSL2plus). Every two octets refer to one element in this array of octets."
			::= { msanAdslAturPhysExtnEntry 6 }

		
		-- 1.3.6.1.4.1.1332.1.1.5.3.36.4.1.7
		msanAdslAturPhysExtnDeltHLOGMTds OBJECT-TYPE
			SYNTAX Integer32
			MAX-ACCESS read-only
			STATUS current
			DESCRIPTION
				"DELT-related parameter that provides the number of symbols used to measure the downstream Hlog(f). (Not available for ADSL and ADSL2plus)."
			::= { msanAdslAturPhysExtnEntry 7 }

		
		-- 1.3.6.1.4.1.1332.1.1.5.3.36.4.1.8
		msanAdslAturPhysExtnDeltHLOGpsus OBJECT-TYPE
			SYNTAX OCTET STRING (SIZE (0..1024))
			MAX-ACCESS read-only
			STATUS current
			DESCRIPTION
				"DELT-related parameter that provides an array of real downstream Hlog(f) values in dB. (Not available for ADSL and ADSL2plus)."
			::= { msanAdslAturPhysExtnEntry 8 }

		
		-- 1.3.6.1.4.1.1332.1.1.5.3.36.4.1.9
		msanAdslAturPhysExtnDeltQLNMTds OBJECT-TYPE
			SYNTAX Integer32
			MAX-ACCESS read-only
			STATUS current
			DESCRIPTION
				"DELT-related parameter that provides the number of symbols used to measure the downstream QLN(f) values. (Not available for ADSL and ADSL2plus)."
			::= { msanAdslAturPhysExtnEntry 9 }

		
		-- 1.3.6.1.4.1.1332.1.1.5.3.36.4.1.10
		msanAdslAturPhysExtnDeltQLNpsds OBJECT-TYPE
			SYNTAX OCTET STRING (SIZE (0..512))
			MAX-ACCESS read-only
			STATUS current
			DESCRIPTION
				"DELT-related parameter that provides an array of real downstream QLN(f) values in dB. (Not available for ADSL and ADSL2plus). Every two octets refer to one element in this array of octets."
			::= { msanAdslAturPhysExtnEntry 10 }

		
		-- 1.3.6.1.4.1.1332.1.1.5.3.36.4.1.11
		msanAdslAturPhysExtnDeltLastTxState OBJECT-TYPE
			SYNTAX INTEGER
				{
				dmtaturg9941(0),
				dmtaturquiet1(1),
				dmtaturcomb1(2),
				dmtaturquiet2(3),
				dmtaturcomb2(4),
				dmtaturicomb1(5),
				dmtaturlineprob(6),
				dmtaturquiet3(7),
				dmtaturcomb3(8),
				dmtaturicomb2(9),
				dmtaturmsgfmt(10),
				dmtaturmsgpcb(11),
				dmtaturreverb1(12),
				dmtaturquiet4(13),
				dmtaturreverb2(14),
				dmtaturquiet5(15),
				dmtaturreverb3(16),
				dmtaturect(17),
				dmtaturreverb4(18),
				dmtatursegue1(19),
				dmtaturreverb5(20),
				dmtatursegue2(21),
				dmtaturmsg1(22),
				dmtaturmedley(23),
				dmtaturexchmarker(24),
				dmtaturmsg2(25),
				dmtaturreverb6(26),
				dmtatursegue3(27),
				dmtaturparams(28),
				dmtaturreverb7(29),
				dmtatursegue4(30),
				dmtaturshowtime(31)
				}
			MAX-ACCESS read-only
			STATUS current
			DESCRIPTION
				"DELT-related parameter that provides last successful transmitted initialization state by the ATU-R. (Not available for ADSL and ADSL2plus)."
			::= { msanAdslAturPhysExtnEntry 11 }

		
		-- 1.3.6.1.4.1.1332.1.1.5.3.36.4.1.12
		msanAdslAturMSGus OBJECT-TYPE
			SYNTAX Gauge32
			MAX-ACCESS read-only
			STATUS current
			DESCRIPTION
				"Indicates the Overhead Channel.  This feature is not supported by DSLPHY as yet."
			::= { msanAdslAturPhysExtnEntry 12 }

		
		-- 1.3.6.1.4.1.1332.1.1.5.3.36.4.1.13
		msanAdslAturDeltSNRMTds OBJECT-TYPE
			SYNTAX Gauge32
			MAX-ACCESS read-only
			STATUS current
			DESCRIPTION
				"DELT-related parameter that provides the number of symbols used to measure the downstream SNR(f) values. (Not available for ADSL and ADSL2plus)"
			::= { msanAdslAturPhysExtnEntry 13 }

		
		-- 1.3.6.1.4.1.1332.1.1.5.3.36.4.1.14
		msanAdslAturSATN OBJECT-TYPE
			SYNTAX Integer32
			MAX-ACCESS read-only
			STATUS current
			DESCRIPTION
				"DELT-related parameter that provides the downtream signal attenuation (length = 4 bytes). (Not available for ADSL and ADSL2plus). For further details, Refer to Section 7.5.1.9 Revised Recommendation G.997.1."
			::= { msanAdslAturPhysExtnEntry 14 }

		
		-- 1.3.6.1.4.1.1332.1.1.5.3.36.4.1.15
		msanAdslAturPhysExtnSystemVendorId OBJECT-TYPE
			SYNTAX OCTET STRING (SIZE (0..9))
			MAX-ACCESS read-only
			STATUS current
			DESCRIPTION
				"Indicates the Vendor ID as inserted by the ATU-R in the Embedded Operations Channel(ADSL). Typically identiies the ATU-R system integrator which usually refers to the vendor of the smallest field-replaceable unit. ATU-R System Vendor ID may not be the same as ATU-R G.994.1 Vendor ID. For ADSL2, provides the Vendor ID as inserted by the ATU-R in the Overhead Messages. It is not available for ADSL. This is string of 8 octets containing 2 octet country code , 4 octet vendor id and 2 octet vendor revision number."
			::= { msanAdslAturPhysExtnEntry 15 }

		
		-- 1.3.6.1.4.1.1332.1.1.5.3.36.4.1.16
		msanAdslAturPhysExtnGainspsDs OBJECT-TYPE
			SYNTAX OCTET STRING (SIZE (0..1024))
			MAX-ACCESS read-only
			STATUS current
			DESCRIPTION
				"This parameter defines the downstream gains allocation table per bin. For further details, Refer to Section 7.5.1.21.3 Revised Recommendation G.997.1. It is supported for ADSL2/ADSl2plus only."
			::= { msanAdslAturPhysExtnEntry 16 }

		
		-- 1.3.6.1.4.1.1332.1.1.5.3.36.4.1.17
		msanAdslAturPhysExtnSelfTestResult OBJECT-TYPE
			SYNTAX Gauge32
			MAX-ACCESS read-only
			STATUS current
			DESCRIPTION
				"Defines the ATU-R selftest result. The most significant octet is: 00 hex if the self-test passed or 01 hex if the self-test failed. Interpretation of the other octets is vendor discretionary and can be interpreted in combination with G.994.1 and system Vendor IDs. For further details, refer to Section 7.4.10 Revised Recommendation G.997.1."
			::= { msanAdslAturPhysExtnEntry 17 }

		
		-- 1.3.6.1.4.1.1332.1.1.5.3.36.4.1.18
		msanAdslAturPhysExtnG9941VendorId OBJECT-TYPE
			SYNTAX OCTET STRING (SIZE (0..9))
			MAX-ACCESS read-only
			STATUS current
			DESCRIPTION
				"Indicates the Vendor ID as inserted by the ATU-R in the G.994.1 CLR message.The G.994.1 Vendor ID typically identifies the vendor of the ATU-R G.994.1 functionality. This is string of 8 octets containing 2 octet country code , 4 octet vendor id and 2 octet vendor revision number. For further details, refer to Section 7.4.2 Revised Recommendation G.997.1."
			::= { msanAdslAturPhysExtnEntry 18 }

		
		-- 1.3.6.1.4.1.1332.1.1.5.3.36.4.1.19
		msanAdslAturPhysExtnTsspsDs OBJECT-TYPE
			SYNTAX OCTET STRING (SIZE (0..128))
			MAX-ACCESS read-only
			STATUS current
			DESCRIPTION
				"This parameter provides the Downstream Transmit Spectrum Shaping parameter expressed as the set of break points exchanged during G994.1. Value of this parameter is in range 0 - 127, in multiples of -0.5 dB. 127 is a special value indicating the subcarrier is not transmitted. It is available only for ADSL2/ADSL2plus. For further details, Refer to Section 7.5.1.21.5 Revised Recommendation G.997.1"
			::= { msanAdslAturPhysExtnEntry 19 }

		
		-- 1.3.6.1.4.1.1332.1.1.5.3.36.4.1.20
		msanAdslAturPhysExtnActPsdDs OBJECT-TYPE
			SYNTAX Integer32
			MAX-ACCESS read-only
			STATUS current
			DESCRIPTION
				"This parameter defines the average downstream transmit power spectrum density over the used subcarriers delivered by the ATU-C at the U-C reference point, at the instant of measurement. It's value ranges from -90 to 0, in 0.1 dB/Hz steps. It is available only for ADSL2/ADSL2plus.For further details, Refer to Section 7.5.1.14 Revised Recommendation G.997.1."
			::= { msanAdslAturPhysExtnEntry 20 }

		
		-- 1.3.6.1.4.1.1332.1.1.5.3.36.4.1.21
		msanAdslAturPhysExtnBitSwapCount OBJECT-TYPE
			SYNTAX Unsigned32
			MAX-ACCESS read-only
			STATUS current
			DESCRIPTION
				"This Conexant parameter indicates the bit swap count. It can read only in data mode"
			::= { msanAdslAturPhysExtnEntry 21 }

		
		-- 1.3.6.1.4.1.1332.1.1.5.3.36.4.1.22
		msanAdslAturPhysExtnPsdMaskMode OBJECT-TYPE
			SYNTAX INTEGER
				{
				coMsk2(0),
				flatMsk(3),
				cabMsk2(4),
				coMsk2Rfi(32768),
				flatMskRfi(32771),
				cabMsk2Rfi(32772),
				coMsk2Rfi0(49152),
				adsl2NonovlpM1(275),
				adsl2NonovlpM2(291),
				adsl2NonovlpFlat(259)
				}
			MAX-ACCESS read-only
			STATUS current
			DESCRIPTION
				"This conexant parameter that indicates the actual PSD Mask currently being used by ATU-R"
			::= { msanAdslAturPhysExtnEntry 22 }

		
		-- 1.3.6.1.4.1.1332.1.1.5.3.37
		msanEaps OBJECT IDENTIFIER ::= { msanAdditionalConf 37 }

		
		-- 1.3.6.1.4.1.1332.1.1.5.3.37.1
		msanEapsGlobal OBJECT IDENTIFIER ::= { msanEaps 1 }

		
		-- 1.3.6.1.4.1.1332.1.1.5.3.37.1.1
		msanEapsAdminState OBJECT-TYPE
			SYNTAX INTEGER
				{
				enable(1),
				disable(2)
				}
			MAX-ACCESS read-write
			STATUS current
			DESCRIPTION
				"Global EAPS administrative state."
			DEFVAL { disable }
			::= { msanEapsGlobal 1 }

		
		-- 1.3.6.1.4.1.1332.1.1.5.3.37.2
		msanEapsDomainTable OBJECT-TYPE
			SYNTAX SEQUENCE OF MsanEapsDomainEntry
			MAX-ACCESS not-accessible
			STATUS current
			DESCRIPTION
				"EAPS domain configuration."
			::= { msanEaps 2 }

		
		-- 1.3.6.1.4.1.1332.1.1.5.3.37.2.1
		msanEapsDomainEntry OBJECT-TYPE
			SYNTAX MsanEapsDomainEntry
			MAX-ACCESS not-accessible
			STATUS current
			DESCRIPTION
				"Description."
			INDEX { msanEapsDomainName }
			::= { msanEapsDomainTable 1 }

		
		MsanEapsDomainEntry ::=
			SEQUENCE { 
				msanEapsDomainName
					OCTET STRING,
				msanEapsDomainDeviceRole
					INTEGER,
				msanEapsDomainHelloTime
					INTEGER,
				msanEapsDomainFailTimeout
					INTEGER,
				msanEapsDomainAdminState
					INTEGER,
				msanEapsDomainPrimaryIfIndex
					Integer32,
				msanEapsDomainSecondaryIfIndex
					Integer32,
				msanEapsDomainCntrlVlanId
					Integer32,
				msanEapsDomainRowStatus
					RowStatus
			 }

		-- 1.3.6.1.4.1.1332.1.1.5.3.37.2.1.2
		msanEapsDomainName OBJECT-TYPE
			SYNTAX OCTET STRING (SIZE (1..12))
			MAX-ACCESS not-accessible
			STATUS current
			DESCRIPTION
				"Description of the EAPS domain. Each msanEapsDomainName value in this 
				table must be unique."
			::= { msanEapsDomainEntry 2 }

		
		-- 1.3.6.1.4.1.1332.1.1.5.3.37.2.1.3
		msanEapsDomainDeviceRole OBJECT-TYPE
			SYNTAX INTEGER
				{
				master(1),
				transit(2)
				}
			MAX-ACCESS read-write
			STATUS current
			DESCRIPTION
				"Role of the node in the EAPS domain (Master or Transit)"
			DEFVAL { transit }
			::= { msanEapsDomainEntry 3 }

		
		-- 1.3.6.1.4.1.1332.1.1.5.3.37.2.1.4
		msanEapsDomainHelloTime OBJECT-TYPE
			SYNTAX INTEGER (1..15)
			MAX-ACCESS read-write
			STATUS current
			DESCRIPTION
				"EAPS domain hello frame send interval.
				This value must be lower than msanEapsDomainFailTimeout"
			DEFVAL { 1 }
			::= { msanEapsDomainEntry 4 }

		
		-- 1.3.6.1.4.1.1332.1.1.5.3.37.2.1.5
		msanEapsDomainFailTimeout OBJECT-TYPE
			SYNTAX INTEGER (2..300)
			MAX-ACCESS read-write
			STATUS current
			DESCRIPTION
				"EAPS fail timeout.
				This value must be higher than msanEapsDomainHelloTime"
			DEFVAL { 3 }
			::= { msanEapsDomainEntry 5 }

		
		-- 1.3.6.1.4.1.1332.1.1.5.3.37.2.1.6
		msanEapsDomainAdminState OBJECT-TYPE
			SYNTAX INTEGER
				{
				enable(1),
				disable(2)
				}
			MAX-ACCESS read-write
			STATUS current
			DESCRIPTION
				"EAPS domain administrative state.
				State can be changed from disable to enable only when all parameters
				in this table are defined."
			DEFVAL { disable }
			::= { msanEapsDomainEntry 6 }

		
		-- 1.3.6.1.4.1.1332.1.1.5.3.37.2.1.7
		msanEapsDomainPrimaryIfIndex OBJECT-TYPE
			SYNTAX Integer32
			MAX-ACCESS read-write
			STATUS current
			DESCRIPTION
				"EAPS primary interface. The value must be different from msanEapsSecondaryIfIndex.
				
				The interface identified by a particular value of this index is the same
				interface as identified by the same value of ifIndex. 
				ifType of selected interface can be ethernetCsmacd(6) or ieee8023adLag (161).
				
				This parameter can be undefined when EAPS domain is created and msanEapsDomainAdminState
				is disable.
				
				
				
				"
			::= { msanEapsDomainEntry 7 }

		
		-- 1.3.6.1.4.1.1332.1.1.5.3.37.2.1.8
		msanEapsDomainSecondaryIfIndex OBJECT-TYPE
			SYNTAX Integer32
			MAX-ACCESS read-write
			STATUS current
			DESCRIPTION
				"EAPS secondary interface. The value must be different from msanEapsPrimaryIfIndex.
				
				The interface identified by a particular value of this index is the same
				interface as identified by the same value of ifIndex. 
				ifType of selected interface can be ethernetCsmacd(6) or ieee8023adLag (161).
				
				This parameter can be undefined when EAPS domain is created and msanEapsDomainAdminState
				is disable.
				
				"
			::= { msanEapsDomainEntry 8 }

		
		-- 1.3.6.1.4.1.1332.1.1.5.3.37.2.1.9
		msanEapsDomainCntrlVlanId OBJECT-TYPE
			SYNTAX Integer32
			MAX-ACCESS read-write
			STATUS current
			DESCRIPTION
				"EAPS control VLAN ID.
				Selected VLAN ID must exists in dot1qVlanStaticTable.
				
				This parameter can be undefined when EAPS domain is created and msanEapsDomainAdminState
				is disable.
				"
			::= { msanEapsDomainEntry 9 }

		
		-- 1.3.6.1.4.1.1332.1.1.5.3.37.2.1.10
		msanEapsDomainRowStatus OBJECT-TYPE
			SYNTAX RowStatus
			MAX-ACCESS read-create
			STATUS current
			DESCRIPTION
				"The row status object controls the creation/deletion of rows in this table. 
				For row creation use createAndWait(5) [createAndGo(4) is not supported].
				
				If msanEapsDomainAdminState is disable, created row can be actived by row status object
				also when next parameters are not defined:
				- msanEapsDomainPrimaryifIndex
				- msanEapsDomainSecondaryifIndex
				- msanEapsDomainCntrlVlanId
				"
			::= { msanEapsDomainEntry 10 }

		
		-- 1.3.6.1.4.1.1332.1.1.5.3.37.3
		msanEapsDomainProtVlanTable OBJECT-TYPE
			SYNTAX SEQUENCE OF MsanEapsDomainProtVlanEntry
			MAX-ACCESS not-accessible
			STATUS current
			DESCRIPTION
				"List of protected VLANs for EAPS domain."
			::= { msanEaps 3 }

		
		-- 1.3.6.1.4.1.1332.1.1.5.3.37.3.1
		msanEapsDomainProtVlanEntry OBJECT-TYPE
			SYNTAX MsanEapsDomainProtVlanEntry
			MAX-ACCESS not-accessible
			STATUS current
			DESCRIPTION
				"Description."
			INDEX { msanEapsDomainName, dot1qVlanIndex }
			::= { msanEapsDomainProtVlanTable 1 }

		
		MsanEapsDomainProtVlanEntry ::=
			SEQUENCE { 
				msanEapsDomainProtVlanRowStatus
					RowStatus
			 }

		-- 1.3.6.1.4.1.1332.1.1.5.3.37.3.1.1
		msanEapsDomainProtVlanRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanEapsDomainProtVlanEntry 1 }

		
		-- 1.3.6.1.4.1.1332.1.1.5.3.38
		msanCpe OBJECT IDENTIFIER ::= { msanAdditionalConf 38 }

		
		-- 1.3.6.1.4.1.1332.1.1.5.3.38.1
		msanCpeGlobal OBJECT IDENTIFIER ::= { msanCpe 1 }

		
		-- 1.3.6.1.4.1.1332.1.1.5.3.38.1.1
		msanCpeReset OBJECT-TYPE
			SYNTAX Unsigned32
			UNITS "ifIndex"
			MAX-ACCESS read-write
			STATUS current
			DESCRIPTION
				"Reset CPE equipment connected to selected interface index (ifIndex)."
			DEFVAL { 0 }
			::= { msanCpeGlobal 1 }

		
		-- 1.3.6.1.4.1.1332.1.1.5.3.38.1.2
		msanCpeSendConfig OBJECT-TYPE
			SYNTAX Unsigned32
			UNITS "ifIndex"
			MAX-ACCESS read-write
			STATUS current
			DESCRIPTION
				"Apply configuration to CPE equipment connected to 
				selected interface index (ifIndex)."
			DEFVAL { 0 }
			::= { msanCpeGlobal 2 }

		
		-- 1.3.6.1.4.1.1332.1.1.5.3.38.1.3
		msanCpeApiMajorVersion OBJECT-TYPE
			SYNTAX OCTET STRING (SIZE (0..32))
			MAX-ACCESS read-only
			STATUS current
			DESCRIPTION
				"CPE API major version information."
			::= { msanCpeGlobal 3 }

		
		-- 1.3.6.1.4.1.1332.1.1.5.3.38.1.4
		msanCpeApiMinorVersion OBJECT-TYPE
			SYNTAX OCTET STRING (SIZE (0..32))
			MAX-ACCESS read-only
			STATUS current
			DESCRIPTION
				"CPE API minor version information."
			::= { msanCpeGlobal 4 }

		
		-- 1.3.6.1.4.1.1332.1.1.5.3.38.2
		msanCpeTypeTable OBJECT-TYPE
			SYNTAX SEQUENCE OF MsanCpeTypeEntry
			MAX-ACCESS not-accessible
			STATUS current
			DESCRIPTION
				"List of possible CPE types."
			::= { msanCpe 2 }

		
		-- 1.3.6.1.4.1.1332.1.1.5.3.38.2.1
		msanCpeTypeEntry OBJECT-TYPE
			SYNTAX MsanCpeTypeEntry
			MAX-ACCESS not-accessible
			STATUS current
			DESCRIPTION
				"Description."
			INDEX { msanCpeTypeName }
			::= { msanCpeTypeTable 1 }

		
		MsanCpeTypeEntry ::=
			SEQUENCE { 
				msanCpeTypeName
					OCTET STRING,
				msanCpeTypePortNum
					Integer32
			 }

		-- 1.3.6.1.4.1.1332.1.1.5.3.38.2.1.1
		msanCpeTypeName OBJECT-TYPE
			SYNTAX OCTET STRING (SIZE (0..20))
			MAX-ACCESS not-accessible
			STATUS current
			DESCRIPTION
				"Usage name of CPE model."
			::= { msanCpeTypeEntry 1 }

		
		-- 1.3.6.1.4.1.1332.1.1.5.3.38.2.1.2
		msanCpeTypePortNum OBJECT-TYPE
			SYNTAX Integer32
			MAX-ACCESS read-write
			STATUS current
			DESCRIPTION
				"Number of CPE user ports."
			::= { msanCpeTypeEntry 2 }

		
		-- 1.3.6.1.4.1.1332.1.1.5.3.38.3
		msanCpeIntfTypeTable OBJECT-TYPE
			SYNTAX SEQUENCE OF MsanCpeIntfTypeEntry
			MAX-ACCESS not-accessible
			STATUS current
			DESCRIPTION
				"Tabel defines which CPE model can be connected to selected interface."
			::= { msanCpe 3 }

		
		-- 1.3.6.1.4.1.1332.1.1.5.3.38.3.1
		msanCpeIntfTypeEntry OBJECT-TYPE
			SYNTAX MsanCpeIntfTypeEntry
			MAX-ACCESS not-accessible
			STATUS current
			DESCRIPTION
				"Description."
			INDEX { ifIndex, msanCpeTypeName }
			::= { msanCpeIntfTypeTable 1 }

		
		MsanCpeIntfTypeEntry ::=
			SEQUENCE { 
				msanCpeIntfTypeRowStatus
					RowStatus,
				msanCpeIntfTypeHwVersion
					OCTET STRING,
				msanCpeIntfTypeSwVersion
					OCTET STRING
			 }

		-- 1.3.6.1.4.1.1332.1.1.5.3.38.3.1.1
		msanCpeIntfTypeRowStatus OBJECT-TYPE
			SYNTAX RowStatus
			MAX-ACCESS read-create
			STATUS current
			DESCRIPTION
				"The row status object controls the creation/deletion of rows in this table. 
				Setting this object to createAndGo(4) creates a row in this table.
				Setting this object to destroy(6) will remove this entry.
				Read values: active(1).
				Other values are currently not supported.
				"
			::= { msanCpeIntfTypeEntry 1 }

		
		-- 1.3.6.1.4.1.1332.1.1.5.3.38.3.1.2
		msanCpeIntfTypeHwVersion OBJECT-TYPE
			SYNTAX OCTET STRING (SIZE (0..32))
			MAX-ACCESS read-only
			STATUS current
			DESCRIPTION
				"Connected CPE hardware version."
			::= { msanCpeIntfTypeEntry 2 }

		
		-- 1.3.6.1.4.1.1332.1.1.5.3.38.3.1.3
		msanCpeIntfTypeSwVersion OBJECT-TYPE
			SYNTAX OCTET STRING (SIZE (0..32))
			MAX-ACCESS read-only
			STATUS current
			DESCRIPTION
				"Connected CPE software version."
			::= { msanCpeIntfTypeEntry 3 }

		
		-- 1.3.6.1.4.1.1332.1.1.5.3.38.4
		msanCpeIntfPortTable OBJECT-TYPE
			SYNTAX SEQUENCE OF MsanCpeIntfPortEntry
			MAX-ACCESS not-accessible
			STATUS current
			DESCRIPTION
				"Table of CPE ports parameters"
			::= { msanCpe 4 }

		
		-- 1.3.6.1.4.1.1332.1.1.5.3.38.4.1
		msanCpeIntfPortEntry OBJECT-TYPE
			SYNTAX MsanCpeIntfPortEntry
			MAX-ACCESS not-accessible
			STATUS current
			DESCRIPTION
				"Description."
			INDEX { ifIndex, msanCpeIntfPortId }
			::= { msanCpeIntfPortTable 1 }

		
		MsanCpeIntfPortEntry ::=
			SEQUENCE { 
				msanCpeIntfPortId
					INTEGER,
				msanCpeIntfPortPowerMode
					INTEGER,
				msanCpeIntfPortLinkMode
					INTEGER,
				msanCpeIntfPortPvid
					INTEGER,
				msanCpeIntfPortCos
					INTEGER,
				msanCpeIntfPortOverrideVid
					INTEGER,
				msanCpeIntfPortOverrideCos
					INTEGER,
				msanCpeIntfPortProtection
					INTEGER,
				msanCpeIntfPortStatus
					INTEGER
			 }

		-- 1.3.6.1.4.1.1332.1.1.5.3.38.4.1.1
		msanCpeIntfPortId OBJECT-TYPE
			SYNTAX INTEGER
			MAX-ACCESS not-accessible
			STATUS current
			DESCRIPTION
				"CPE port ID (1 .. n)."
			::= { msanCpeIntfPortEntry 1 }

		
		-- 1.3.6.1.4.1.1332.1.1.5.3.38.4.1.2
		msanCpeIntfPortPowerMode OBJECT-TYPE
			SYNTAX INTEGER
				{
				normal(0),
				fullPowerDown(1),
				sleep(2)
				}
			MAX-ACCESS read-write
			STATUS current
			DESCRIPTION
				"Power mode of the CPE port. When port is in Sleep(2) mode, 
				automatic wake-up is also activated.  
				"
			DEFVAL { normal }
			::= { msanCpeIntfPortEntry 2 }

		
		-- 1.3.6.1.4.1.1332.1.1.5.3.38.4.1.3
		msanCpeIntfPortLinkMode OBJECT-TYPE
			SYNTAX INTEGER
				{
				autonegotiation(0),
				speed100MbpsFD(1),
				speed100MbpsHD(2),
				speed10MbpsFD(3),
				speed10MbpsHD(4)
				}
			MAX-ACCESS read-write
			STATUS current
			DESCRIPTION
				"Speed and duplex mode of the CPE port."
			DEFVAL { autonegotiation }
			::= { msanCpeIntfPortEntry 3 }

		
		-- 1.3.6.1.4.1.1332.1.1.5.3.38.4.1.4
		msanCpeIntfPortPvid OBJECT-TYPE
			SYNTAX INTEGER (1..4094)
			MAX-ACCESS read-write
			STATUS current
			DESCRIPTION
				"Default Vlan ID (pVID) for selected CPE port."
			DEFVAL { 1 }
			::= { msanCpeIntfPortEntry 4 }

		
		-- 1.3.6.1.4.1.1332.1.1.5.3.38.4.1.5
		msanCpeIntfPortCos OBJECT-TYPE
			SYNTAX INTEGER (0..7)
			MAX-ACCESS read-write
			STATUS current
			DESCRIPTION
				"Default CoS bit settings for the CPE port."
			DEFVAL { 0 }
			::= { msanCpeIntfPortEntry 5 }

		
		-- 1.3.6.1.4.1.1332.1.1.5.3.38.4.1.6
		msanCpeIntfPortOverrideVid OBJECT-TYPE
			SYNTAX INTEGER
				{
				enable(1),
				disable(2)
				}
			MAX-ACCESS read-write
			STATUS current
			DESCRIPTION
				"When enable(1)VLAN ID of received tagged frame on selected CPE port
				is overwritten with default VLAN ID (msanCpeIntfPortPvid)."
			DEFVAL { disable }
			::= { msanCpeIntfPortEntry 6 }

		
		-- 1.3.6.1.4.1.1332.1.1.5.3.38.4.1.7
		msanCpeIntfPortOverrideCos OBJECT-TYPE
			SYNTAX INTEGER
				{
				enable(1),
				disable(2)
				}
			MAX-ACCESS read-write
			STATUS current
			DESCRIPTION
				"When enable(1)CoS value of received tagged frame on selected CPE port
				is overwritten with default CoS bit settings (msanCpeIntfPortCos)."
			DEFVAL { disable }
			::= { msanCpeIntfPortEntry 7 }

		
		-- 1.3.6.1.4.1.1332.1.1.5.3.38.4.1.8
		msanCpeIntfPortProtection OBJECT-TYPE
			SYNTAX INTEGER
				{
				unprotected(0),
				protected(1)
				}
			MAX-ACCESS read-write
			STATUS current
			DESCRIPTION
				"If protection flag is set to protected (1), other profile values cannot be edited.
				
				Protection flag is always  protected (1) and it can't be changed if  profile is assigned as dynamic:
				msanAclProfileStatus = dynamic(2)"
			DEFVAL { unprotected }
			::= { msanCpeIntfPortEntry 8 }

		
		-- 1.3.6.1.4.1.1332.1.1.5.3.38.4.1.9
		msanCpeIntfPortStatus OBJECT-TYPE
			SYNTAX INTEGER
				{
				static(1),
				dynamic(2)
				}
			MAX-ACCESS read-only
			STATUS current
			DESCRIPTION
				"Profile status. 
				If status is dynamic, profile values can't be edited."
			::= { msanCpeIntfPortEntry 9 }

		
		-- 1.3.6.1.4.1.1332.1.1.5.3.38.5
		msanCpeTrafficTable OBJECT-TYPE
			SYNTAX SEQUENCE OF MsanCpeTrafficEntry
			MAX-ACCESS not-accessible
			STATUS current
			DESCRIPTION
				"Description."
			::= { msanCpe 5 }

		
		-- 1.3.6.1.4.1.1332.1.1.5.3.38.5.1
		msanCpeTrafficEntry OBJECT-TYPE
			SYNTAX MsanCpeTrafficEntry
			MAX-ACCESS not-accessible
			STATUS current
			DESCRIPTION
				"Description."
			INDEX { msanCpeTrafficId }
			::= { msanCpeTrafficTable 1 }

		
		MsanCpeTrafficEntry ::=
			SEQUENCE { 
				msanCpeTrafficId
					Integer32,
				msanCpeTrafficName
					OCTET STRING,
				msanCpeTrafficSpeed
					Integer32,
				msanCpeTrafficFlowCntrlMode
					INTEGER,
				msanCpeTrafficRowStatus
					RowStatus,
				msanCpeTrafficProtection
					INTEGER,
				msanCpeTrafficStatus
					INTEGER
			 }

		-- 1.3.6.1.4.1.1332.1.1.5.3.38.5.1.1
		msanCpeTrafficId OBJECT-TYPE
			SYNTAX Integer32
			MAX-ACCESS not-accessible
			STATUS current
			DESCRIPTION
				"Number identifying traffic configuration (1 .. n)."
			::= { msanCpeTrafficEntry 1 }

		
		-- 1.3.6.1.4.1.1332.1.1.5.3.38.5.1.2
		msanCpeTrafficName OBJECT-TYPE
			SYNTAX OCTET STRING (SIZE (0..40))
			MAX-ACCESS read-write
			STATUS current
			DESCRIPTION
				"Name identifying traffic configuration. Must be unique value."
			::= { msanCpeTrafficEntry 2 }

		
		-- 1.3.6.1.4.1.1332.1.1.5.3.38.5.1.3
		msanCpeTrafficSpeed OBJECT-TYPE
			SYNTAX Integer32 (0..100000)
			UNITS "kbit/s"
			MAX-ACCESS read-write
			STATUS current
			DESCRIPTION
				"Maximum bitrate of services using this traffic configuration.
				Domain value is 0-100000kbit/s, where:
				- for speeds below 1Mbit/s step is 64kbit/s
				- for speeds above 1Mbit/s step is 1000kbit/s"
			::= { msanCpeTrafficEntry 3 }

		
		-- 1.3.6.1.4.1.1332.1.1.5.3.38.5.1.4
		msanCpeTrafficFlowCntrlMode OBJECT-TYPE
			SYNTAX INTEGER
				{
				enable(1),
				disable(2)
				}
			MAX-ACCESS read-write
			STATUS current
			DESCRIPTION
				"Flow control mode. When enable(1) and speed is to be exceeded, device will send
				PAUSE flow control packet. If disable(2) packet will be just dropped."
			DEFVAL { disable }
			::= { msanCpeTrafficEntry 4 }

		
		-- 1.3.6.1.4.1.1332.1.1.5.3.38.5.1.5
		msanCpeTrafficRowStatus OBJECT-TYPE
			SYNTAX RowStatus
			MAX-ACCESS read-create
			STATUS current
			DESCRIPTION
				"The row status object controls the creation/deletion of rows in this table. 
				For row creation use createAndWait(5) [createAndGo(4) is not supported].
				Setting this object to active(1) will activate this entry, if msanCpeTrafficName is defined.
				Setting this object to destroy(6) will remove this entry.
				"
			::= { msanCpeTrafficEntry 5 }

		
		-- 1.3.6.1.4.1.1332.1.1.5.3.38.5.1.6
		msanCpeTrafficProtection OBJECT-TYPE
			SYNTAX INTEGER
				{
				unprotected(0),
				protected(1)
				}
			MAX-ACCESS read-write
			STATUS current
			DESCRIPTION
				"If protection flag is set to protected (1), other profile values cannot be edited.
				
				Protection flag is always  protected (1) and it can't be changed if  profile is assigned as dynamic:
				msanAclProfileStatus = dynamic(2)"
			DEFVAL { unprotected }
			::= { msanCpeTrafficEntry 6 }

		
		-- 1.3.6.1.4.1.1332.1.1.5.3.38.5.1.7
		msanCpeTrafficStatus OBJECT-TYPE
			SYNTAX INTEGER
				{
				static(1),
				dynamic(2)
				}
			MAX-ACCESS read-only
			STATUS current
			DESCRIPTION
				"Profile status. 
				If status is dynamic, profile values can't be edited."
			::= { msanCpeTrafficEntry 7 }

		
		-- 1.3.6.1.4.1.1332.1.1.5.3.38.6
		msanCpeServiceTable OBJECT-TYPE
			SYNTAX SEQUENCE OF MsanCpeServiceEntry
			MAX-ACCESS not-accessible
			STATUS current
			DESCRIPTION
				"Description."
			::= { msanCpe 6 }

		
		-- 1.3.6.1.4.1.1332.1.1.5.3.38.6.1
		msanCpeServiceEntry OBJECT-TYPE
			SYNTAX MsanCpeServiceEntry
			MAX-ACCESS not-accessible
			STATUS current
			DESCRIPTION
				"Description."
			INDEX { msanCpeServiceId }
			::= { msanCpeServiceTable 1 }

		
		MsanCpeServiceEntry ::=
			SEQUENCE { 
				msanCpeServiceId
					Integer32,
				msanCpeServiceName
					OCTET STRING,
				msanCpeServiceCVlanId
					Integer32,
				msanCpeServiceCCos
					Integer32,
				msanCpeServiceTrafficId
					Integer32,
				msanCpeServiceUntaggedPorts
					OCTET STRING,
				msanCpeServiceTaggedPorts
					OCTET STRING,
				msanCpeServiceCMltcstMode
					INTEGER,
				msanCpeServiceRowStatus
					RowStatus,
				msanCpeServiceTypeName
					OCTET STRING,
				msanCpeServiceProtection
					INTEGER,
				msanCpeServiceStatus
					INTEGER
			 }

		-- 1.3.6.1.4.1.1332.1.1.5.3.38.6.1.1
		msanCpeServiceId OBJECT-TYPE
			SYNTAX Integer32
			MAX-ACCESS not-accessible
			STATUS current
			DESCRIPTION
				"Number identifying service configuration (0 .. n)."
			::= { msanCpeServiceEntry 1 }

		
		-- 1.3.6.1.4.1.1332.1.1.5.3.38.6.1.2
		msanCpeServiceName OBJECT-TYPE
			SYNTAX OCTET STRING (SIZE (0..40))
			MAX-ACCESS read-write
			STATUS current
			DESCRIPTION
				"Name identifying service. Must be unique value."
			::= { msanCpeServiceEntry 2 }

		
		-- 1.3.6.1.4.1.1332.1.1.5.3.38.6.1.3
		msanCpeServiceCVlanId OBJECT-TYPE
			SYNTAX Integer32 (1..4094)
			MAX-ACCESS read-write
			STATUS current
			DESCRIPTION
				"Customer VLAN ID, used for all frames belong to this service."
			DEFVAL { 1 }
			::= { msanCpeServiceEntry 3 }

		
		-- 1.3.6.1.4.1.1332.1.1.5.3.38.6.1.4
		msanCpeServiceCCos OBJECT-TYPE
			SYNTAX Integer32 (0..7)
			MAX-ACCESS read-write
			STATUS current
			DESCRIPTION
				"CoS bit settings for all frames belonging to this service."
			DEFVAL { 0 }
			::= { msanCpeServiceEntry 4 }

		
		-- 1.3.6.1.4.1.1332.1.1.5.3.38.6.1.5
		msanCpeServiceTrafficId OBJECT-TYPE
			SYNTAX Integer32
			MAX-ACCESS read-write
			STATUS current
			DESCRIPTION
				"Reference to parameter msanCpeTrafficId (1 .. n), which identifies traffic configuration .
				Value 0 is used when traffic configuration is not defined."
			DEFVAL { 0 }
			::= { msanCpeServiceEntry 5 }

		
		-- 1.3.6.1.4.1.1332.1.1.5.3.38.6.1.6
		msanCpeServiceUntaggedPorts OBJECT-TYPE
			SYNTAX OCTET STRING (SIZE (0..2))
			MAX-ACCESS read-write
			STATUS current
			DESCRIPTION
				"The set of ports (bitmask) which should transmit egress packets as untagged.  
				When untagged frame is received on this ports set, appropriate default VLAN ID
				(msanCpeIntfPortPvid) and default CoS bits (msanCpeIntfPortCos) are set."
			DEFVAL { '0'h }
			::= { msanCpeServiceEntry 6 }

		
		-- 1.3.6.1.4.1.1332.1.1.5.3.38.6.1.7
		msanCpeServiceTaggedPorts OBJECT-TYPE
			SYNTAX OCTET STRING (SIZE (0..2))
			MAX-ACCESS read-write
			STATUS current
			DESCRIPTION
				"The set of ports (bitmask) where frames can be received only if they have 
				appropriate Customer VLAN ID (msanCpeServiceCVlanId). Otherwise they are dropped.
				When transmitting frames to this set of ports, VLAN tags are not removed.
				 "
			DEFVAL { '0'h }
			::= { msanCpeServiceEntry 7 }

		
		-- 1.3.6.1.4.1.1332.1.1.5.3.38.6.1.8
		msanCpeServiceCMltcstMode OBJECT-TYPE
			SYNTAX INTEGER
				{
				disableIGMPprocessing(0),
				igmpV2SnoopNormalLeave(1),
				igmpV2SnoopFastLeave(2)
				}
			MAX-ACCESS read-write
			STATUS current
			DESCRIPTION
				"Mode of multicast operation for this service."
			DEFVAL { disableIGMPprocessing }
			::= { msanCpeServiceEntry 8 }

		
		-- 1.3.6.1.4.1.1332.1.1.5.3.38.6.1.9
		msanCpeServiceRowStatus OBJECT-TYPE
			SYNTAX RowStatus
			MAX-ACCESS read-create
			STATUS current
			DESCRIPTION
				"The row status object controls the creation/deletion of rows in this table. 
				For row creation use createAndWait(5) [createAndGo(4) is not supported].
				Setting this object to active(1) will activate this entry, if msanCpeServiceName 
				and msanCpeServiceTrafficId are defined.
				Setting this object to destroy(6) will remove this entry.
				"
			::= { msanCpeServiceEntry 9 }

		
		-- 1.3.6.1.4.1.1332.1.1.5.3.38.6.1.10
		msanCpeServiceTypeName OBJECT-TYPE
			SYNTAX OCTET STRING (SIZE (0..20))
			MAX-ACCESS read-write
			STATUS current
			DESCRIPTION
				"Usage name of CPE model. 
				Must be one of predefined msanCpeTypeName values."
			::= { msanCpeServiceEntry 10 }

		
		-- 1.3.6.1.4.1.1332.1.1.5.3.38.6.1.11
		msanCpeServiceProtection OBJECT-TYPE
			SYNTAX INTEGER
				{
				unprotected(0),
				protected(1)
				}
			MAX-ACCESS read-write
			STATUS current
			DESCRIPTION
				"If protection flag is set to protected (1), other profile values cannot be edited.
				
				Protection flag is always  protected (1) and it can't be changed if  profile is assigned as dynamic:
				msanAclProfileStatus = dynamic(2)"
			DEFVAL { unprotected }
			::= { msanCpeServiceEntry 11 }

		
		-- 1.3.6.1.4.1.1332.1.1.5.3.38.6.1.12
		msanCpeServiceStatus OBJECT-TYPE
			SYNTAX INTEGER
				{
				static(1),
				dynamic(2)
				}
			MAX-ACCESS read-only
			STATUS current
			DESCRIPTION
				"Profile status. 
				If status is dynamic, profile values can't be edited."
			::= { msanCpeServiceEntry 12 }

		
		-- 1.3.6.1.4.1.1332.1.1.5.3.38.7
		msanCpeIntfServiceTable OBJECT-TYPE
			SYNTAX SEQUENCE OF MsanCpeIntfServiceEntry
			MAX-ACCESS not-accessible
			STATUS current
			DESCRIPTION
				"This table links CPE ports on selected interface with appropriate service."
			::= { msanCpe 7 }

		
		-- 1.3.6.1.4.1.1332.1.1.5.3.38.7.1
		msanCpeIntfServiceEntry OBJECT-TYPE
			SYNTAX MsanCpeIntfServiceEntry
			MAX-ACCESS not-accessible
			STATUS current
			DESCRIPTION
				"Description."
			INDEX { ifIndex, msanCpeServiceId }
			::= { msanCpeIntfServiceTable 1 }

		
		MsanCpeIntfServiceEntry ::=
			SEQUENCE { 
				msanCpeIntfServiceRowStatus
					RowStatus
			 }

		-- 1.3.6.1.4.1.1332.1.1.5.3.38.7.1.1
		msanCpeIntfServiceRowStatus OBJECT-TYPE
			SYNTAX RowStatus
			MAX-ACCESS read-create
			STATUS current
			DESCRIPTION
				"The row status object controls the creation/deletion of rows in this table. 
				Setting this object to createAndGo(4) creates a row in this table.
				Setting this object to destroy(6) will remove this entry.
				Read values: active(1).
				Other values are currently not supported."
			::= { msanCpeIntfServiceEntry 1 }

		
		-- 1.3.6.1.4.1.1332.1.1.5.3.39
		msanBoard OBJECT IDENTIFIER ::= { msanAdditionalConf 39 }

		
		-- 1.3.6.1.4.1.1332.1.1.5.3.39.1
		msanBoardGlobal OBJECT IDENTIFIER ::= { msanBoard 1 }

		
		-- 1.3.6.1.4.1.1332.1.1.5.3.39.1.1
		msanBoardReset OBJECT-TYPE
			SYNTAX INTEGER
			MAX-ACCESS read-write
			STATUS current
			DESCRIPTION
				"Reset board in specified shelf slot ID (>0)."
			DEFVAL { 0 }
			::= { msanBoardGlobal 1 }

		
		-- 1.3.6.1.4.1.1332.1.1.5.3.39.2
		msanBoardConfTable OBJECT-TYPE
			SYNTAX SEQUENCE OF MsanBoardConfEntry
			MAX-ACCESS not-accessible
			STATUS current
			DESCRIPTION
				"Description."
			::= { msanBoard 2 }

		
		-- 1.3.6.1.4.1.1332.1.1.5.3.39.2.1
		msanBoardConfEntry OBJECT-TYPE
			SYNTAX MsanBoardConfEntry
			MAX-ACCESS not-accessible
			STATUS current
			DESCRIPTION
				"Description."
			INDEX { msanBoardConfNr }
			::= { msanBoardConfTable 1 }

		
		MsanBoardConfEntry ::=
			SEQUENCE { 
				msanBoardConfNr
					INTEGER,
				msanBoardConfParentNr
					INTEGER,
				msanBoardConfPosition
					INTEGER,
				msanBoardConfType
					DisplayString,
				msanBoardConfRequiredId
					DisplayString,
				msanBoardConfActualId
					DisplayString,
				msanBoardConfSerialNr
					DisplayString,
				msanBoardConfDescription
					DisplayString,
				msanBoardConfStatus
					INTEGER,
				msanBoardConfRowStatus
					RowStatus,
				msanBoardConfSwSteerVersion
					DisplayString,
				msanBoardConfSwBuildDirectory
					DisplayString,
				msanBoardConfSwBuildTime
					DisplayString,
				msanBoardConfSwBranch
					DisplayString,
				msanBoardConfSwBuildReference
					DisplayString,
				msanBoardConfSwBackupSteerVersion
					DisplayString,
				msanBoardConfSwBackupStatus
					INTEGER,
				msanBoardConfPowerConsumption
					Gauge32
			 }

		-- 1.3.6.1.4.1.1332.1.1.5.3.39.2.1.1
		msanBoardConfNr OBJECT-TYPE
			SYNTAX INTEGER (1..1000)
			MAX-ACCESS not-accessible
			STATUS current
			DESCRIPTION
				"Unique identification of a board."
			::= { msanBoardConfEntry 1 }

		
		-- 1.3.6.1.4.1.1332.1.1.5.3.39.2.1.2
		msanBoardConfParentNr OBJECT-TYPE
			SYNTAX INTEGER (1..1000)
			MAX-ACCESS read-write
			STATUS current
			DESCRIPTION
				"Unique identification of a parent board."
			::= { msanBoardConfEntry 2 }

		
		-- 1.3.6.1.4.1.1332.1.1.5.3.39.2.1.3
		msanBoardConfPosition OBJECT-TYPE
			SYNTAX INTEGER (1..1000)
			MAX-ACCESS read-write
			STATUS current
			DESCRIPTION
				"Position of the board on the parent board.
				"
			::= { msanBoardConfEntry 3 }

		
		-- 1.3.6.1.4.1.1332.1.1.5.3.39.2.1.4
		msanBoardConfType OBJECT-TYPE
			SYNTAX DisplayString
			MAX-ACCESS read-only
			STATUS current
			DESCRIPTION
				"Type of physical board (e.g. IDC, SGO, SFA, ...). This value is automatically 
				set according to msanBoardConfRequiredId."
			::= { msanBoardConfEntry 4 }

		
		-- 1.3.6.1.4.1.1332.1.1.5.3.39.2.1.5
		msanBoardConfRequiredId OBJECT-TYPE
			SYNTAX DisplayString
			MAX-ACCESS read-write
			STATUS current
			DESCRIPTION
				"Required identification of a board, which is one of available msanBoardListId
				values (e.g. UTA6041BA)."
			::= { msanBoardConfEntry 5 }

		
		-- 1.3.6.1.4.1.1332.1.1.5.3.39.2.1.6
		msanBoardConfActualId OBJECT-TYPE
			SYNTAX DisplayString
			MAX-ACCESS read-only
			STATUS current
			DESCRIPTION
				"Actual identification of a board (e.g. UTA6041BA050 - last three numbers define board version)."
			::= { msanBoardConfEntry 6 }

		
		-- 1.3.6.1.4.1.1332.1.1.5.3.39.2.1.7
		msanBoardConfSerialNr OBJECT-TYPE
			SYNTAX DisplayString
			MAX-ACCESS read-only
			STATUS current
			DESCRIPTION
				"Serial number of a board."
			::= { msanBoardConfEntry 7 }

		
		-- 1.3.6.1.4.1.1332.1.1.5.3.39.2.1.8
		msanBoardConfDescription OBJECT-TYPE
			SYNTAX DisplayString
			MAX-ACCESS read-write
			STATUS current
			DESCRIPTION
				"Description of the board."
			::= { msanBoardConfEntry 8 }

		
		-- 1.3.6.1.4.1.1332.1.1.5.3.39.2.1.9
		msanBoardConfStatus OBJECT-TYPE
			SYNTAX INTEGER
				{
				boardPresentRunning(1),
				boardPresentNotAccessible(2),
				boardNotPresent(3),
				boardPresentInitProcess(4)
				}
			MAX-ACCESS read-only
			STATUS current
			DESCRIPTION
				"Physical status of configured board."
			::= { msanBoardConfEntry 9 }

		
		-- 1.3.6.1.4.1.1332.1.1.5.3.39.2.1.10
		msanBoardConfRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndWait(5).
				For row activation use active(1).
				For row deactivation use notInService(2).
				For row deletion use destroy(6) (board with management interface can not be deleted).
				
				Other values are currently not supported.
				
				For row activation next terms must be accomplished:
				- all requested values (they don't have default definition) must be set
				- msanBoardConfId is one of available msanBoardListId values "
			::= { msanBoardConfEntry 10 }

		
		-- 1.3.6.1.4.1.1332.1.1.5.3.39.2.1.11
		msanBoardConfSwSteerVersion OBJECT-TYPE
			SYNTAX DisplayString
			MAX-ACCESS read-only
			STATUS current
			DESCRIPTION
				"The unique steer code of installed software. "
			::= { msanBoardConfEntry 11 }

		
		-- 1.3.6.1.4.1.1332.1.1.5.3.39.2.1.12
		msanBoardConfSwBuildDirectory OBJECT-TYPE
			SYNTAX DisplayString
			MAX-ACCESS read-only
			STATUS current
			DESCRIPTION
				"The directory where installed software was build on. "
			::= { msanBoardConfEntry 12 }

		
		-- 1.3.6.1.4.1.1332.1.1.5.3.39.2.1.13
		msanBoardConfSwBuildTime OBJECT-TYPE
			SYNTAX DisplayString
			MAX-ACCESS read-only
			STATUS current
			DESCRIPTION
				"The time when the installed software was built.  (DateAndTime textual convention, from SNMPv2-TC)
				"
			::= { msanBoardConfEntry 13 }

		
		-- 1.3.6.1.4.1.1332.1.1.5.3.39.2.1.14
		msanBoardConfSwBranch OBJECT-TYPE
			SYNTAX DisplayString
			MAX-ACCESS read-only
			STATUS current
			DESCRIPTION
				"The repository branch where the installed software was built from."
			::= { msanBoardConfEntry 14 }

		
		-- 1.3.6.1.4.1.1332.1.1.5.3.39.2.1.15
		msanBoardConfSwBuildReference OBJECT-TYPE
			SYNTAX DisplayString
			MAX-ACCESS read-only
			STATUS current
			DESCRIPTION
				"The repository reference number of the installed software build branch. "
			::= { msanBoardConfEntry 15 }

		
		-- 1.3.6.1.4.1.1332.1.1.5.3.39.2.1.16
		msanBoardConfSwBackupSteerVersion OBJECT-TYPE
			SYNTAX DisplayString
			MAX-ACCESS read-only
			STATUS current
			DESCRIPTION
				"The unique steer code of installed backup software. "
			::= { msanBoardConfEntry 16 }

		
		-- 1.3.6.1.4.1.1332.1.1.5.3.39.2.1.17
		msanBoardConfSwBackupStatus OBJECT-TYPE
			SYNTAX INTEGER
				{
				currentActive(1),
				nextActive(2),
				backup(3),
				none(4),
				fail(5)
				}
			MAX-ACCESS read-only
			STATUS current
			DESCRIPTION
				"Backup software package status"
			::= { msanBoardConfEntry 17 }

		
		-- 1.3.6.1.4.1.1332.1.1.5.3.39.2.1.18
		msanBoardConfPowerConsumption OBJECT-TYPE
			SYNTAX Gauge32
			UNITS "Watts"
			MAX-ACCESS read-only
			STATUS current
			DESCRIPTION
				"Measured usage power expressed in Watts."
			::= { msanBoardConfEntry 18 }

		
		-- 1.3.6.1.4.1.1332.1.1.5.3.39.3
		msanBoardListTable OBJECT-TYPE
			SYNTAX SEQUENCE OF MsanBoardListEntry
			MAX-ACCESS not-accessible
			STATUS current
			DESCRIPTION
				"Description."
			::= { msanBoard 3 }

		
		-- 1.3.6.1.4.1.1332.1.1.5.3.39.3.1
		msanBoardListEntry OBJECT-TYPE
			SYNTAX MsanBoardListEntry
			MAX-ACCESS not-accessible
			STATUS current
			DESCRIPTION
				"Description."
			INDEX { msanBoardListId }
			::= { msanBoardListTable 1 }

		
		MsanBoardListEntry ::=
			SEQUENCE { 
				msanBoardListId
					DisplayString,
				msanBoardListType
					DisplayString
			 }

		-- 1.3.6.1.4.1.1332.1.1.5.3.39.3.1.1
		msanBoardListId OBJECT-TYPE
			SYNTAX DisplayString
			MAX-ACCESS read-only
			STATUS current
			DESCRIPTION
				"Identification of supported board (e.g. UTA6041BA)."
			::= { msanBoardListEntry 1 }

		
		-- 1.3.6.1.4.1.1332.1.1.5.3.39.3.1.2
		msanBoardListType OBJECT-TYPE
			SYNTAX DisplayString
			MAX-ACCESS read-only
			STATUS current
			DESCRIPTION
				"Type of physical board (e.g. IDC, SGO, SFA, ...)."
			::= { msanBoardListEntry 2 }

		
		-- 1.3.6.1.4.1.1332.1.1.5.3.40
		msanFtpServer OBJECT IDENTIFIER ::= { msanAdditionalConf 40 }

		
		-- 1.3.6.1.4.1.1332.1.1.5.3.40.1
		msanFtpServerGlobal OBJECT IDENTIFIER ::= { msanFtpServer 1 }

		
		-- 1.3.6.1.4.1.1332.1.1.5.3.40.1.1
		msanFtpServerAdminState OBJECT-TYPE
			SYNTAX INTEGER
				{
				enable(1),
				disable(2)
				}
			MAX-ACCESS read-write
			STATUS current
			DESCRIPTION
				"FTP server administrative state."
			DEFVAL { disable }
			::= { msanFtpServerGlobal 1 }

		
		-- 1.3.6.1.4.1.1332.1.1.5.3.41
		msanAppRateLimit OBJECT IDENTIFIER ::= { msanAdditionalConf 41 }

		
		-- 1.3.6.1.4.1.1332.1.1.5.3.41.1
		msanAppRateLimitGlobal OBJECT IDENTIFIER ::= { msanAppRateLimit 1 }

		
		-- 1.3.6.1.4.1.1332.1.1.5.3.41.2
		msanAppRateLimitTable OBJECT-TYPE
			SYNTAX SEQUENCE OF MsanAppRateLimitEntry
			MAX-ACCESS not-accessible
			STATUS current
			DESCRIPTION
				"Description."
			::= { msanAppRateLimit 2 }

		
		-- 1.3.6.1.4.1.1332.1.1.5.3.41.2.1
		msanAppRateLimitEntry OBJECT-TYPE
			SYNTAX MsanAppRateLimitEntry
			MAX-ACCESS not-accessible
			STATUS current
			DESCRIPTION
				"Description."
			INDEX { ifIndex }
			::= { msanAppRateLimitTable 1 }

		
		MsanAppRateLimitEntry ::=
			SEQUENCE { 
				msanAppRateLimitDhcp
					Integer32,
				msanAppRateLimitDhcpState
					INTEGER,
				msanAppRateLimitPppoe
					Integer32,
				msanAppRateLimitPppoeState
					INTEGER,
				msanAppRateLimitIgmp
					Integer32,
				msanAppRateLimitIgmpState
					INTEGER,
				msanAppRateLimitStp
					Integer32,
				msanAppRateLimitStpState
					INTEGER,
				msanAppRateLimitMn
					Integer32,
				msanAppRateLimitMnState
					INTEGER
			 }

		-- 1.3.6.1.4.1.1332.1.1.5.3.41.2.1.1
		msanAppRateLimitDhcp OBJECT-TYPE
			SYNTAX Integer32 (0..1000)
			UNITS "pps"
			MAX-ACCESS read-write
			STATUS current
			DESCRIPTION
				"Maximum number of received DHCP packets in one second (pps) per interface."
			::= { msanAppRateLimitEntry 1 }

		
		-- 1.3.6.1.4.1.1332.1.1.5.3.41.2.1.2
		msanAppRateLimitDhcpState OBJECT-TYPE
			SYNTAX INTEGER
				{
				enable(1),
				disable(2)
				}
			MAX-ACCESS read-write
			STATUS current
			DESCRIPTION
				"Administrative state of DHCP traffic rate limiting."
			DEFVAL { enable }
			::= { msanAppRateLimitEntry 2 }

		
		-- 1.3.6.1.4.1.1332.1.1.5.3.41.2.1.3
		msanAppRateLimitPppoe OBJECT-TYPE
			SYNTAX Integer32 (0..1000)
			UNITS "pps"
			MAX-ACCESS read-write
			STATUS current
			DESCRIPTION
				"Maximum number of received PPPoE packets in one second (pps) per interface."
			::= { msanAppRateLimitEntry 3 }

		
		-- 1.3.6.1.4.1.1332.1.1.5.3.41.2.1.4
		msanAppRateLimitPppoeState OBJECT-TYPE
			SYNTAX INTEGER
				{
				enable(1),
				disable(2)
				}
			MAX-ACCESS read-write
			STATUS current
			DESCRIPTION
				"Administrative state of PPPoE traffic rate limiting."
			::= { msanAppRateLimitEntry 4 }

		
		-- 1.3.6.1.4.1.1332.1.1.5.3.41.2.1.5
		msanAppRateLimitIgmp OBJECT-TYPE
			SYNTAX Integer32 (0..1000)
			UNITS "pps"
			MAX-ACCESS read-write
			STATUS current
			DESCRIPTION
				"Maximum number of received DHCP packets in one second (pps) per interface.
				"
			::= { msanAppRateLimitEntry 5 }

		
		-- 1.3.6.1.4.1.1332.1.1.5.3.41.2.1.6
		msanAppRateLimitIgmpState OBJECT-TYPE
			SYNTAX INTEGER
				{
				enable(1),
				disable(2)
				}
			MAX-ACCESS read-write
			STATUS current
			DESCRIPTION
				"Administrative state of IGMP traffic rate limiting."
			::= { msanAppRateLimitEntry 6 }

		
		-- 1.3.6.1.4.1.1332.1.1.5.3.41.2.1.7
		msanAppRateLimitStp OBJECT-TYPE
			SYNTAX Integer32 (0..1000)
			UNITS "pps"
			MAX-ACCESS read-write
			STATUS current
			DESCRIPTION
				"Maximum number of received STP packets in one second (pps) per interface.
				"
			::= { msanAppRateLimitEntry 7 }

		
		-- 1.3.6.1.4.1.1332.1.1.5.3.41.2.1.8
		msanAppRateLimitStpState OBJECT-TYPE
			SYNTAX INTEGER
				{
				enable(1),
				disable(2)
				}
			MAX-ACCESS read-write
			STATUS current
			DESCRIPTION
				"Administrative state of STP traffic rate limiting."
			::= { msanAppRateLimitEntry 8 }

		
		-- 1.3.6.1.4.1.1332.1.1.5.3.41.2.1.9
		msanAppRateLimitMn OBJECT-TYPE
			SYNTAX Integer32 (0..1000)
			UNITS "pps"
			MAX-ACCESS read-write
			STATUS current
			DESCRIPTION
				"Maximum number of received MN packets (management traffic) in one second (pps) per interface.
				"
			::= { msanAppRateLimitEntry 9 }

		
		-- 1.3.6.1.4.1.1332.1.1.5.3.41.2.1.10
		msanAppRateLimitMnState OBJECT-TYPE
			SYNTAX INTEGER
				{
				enable(1),
				disable(2)
				}
			MAX-ACCESS read-write
			STATUS current
			DESCRIPTION
				"Administrative state of MN traffic rate limiting."
			::= { msanAppRateLimitEntry 10 }

		
		-- 1.3.6.1.4.1.1332.1.1.5.3.50
		msanMlinec OBJECT IDENTIFIER ::= { msanAdditionalConf 50 }

		
		-- 1.3.6.1.4.1.1332.1.1.5.3.50.1
		msanMlinecGlobal OBJECT IDENTIFIER ::= { msanMlinec 1 }

		
		-- 1.3.6.1.4.1.1332.1.1.5.3.50.1.1
		msanMlinecAdminState OBJECT-TYPE
			SYNTAX INTEGER
				{
				enable(1),
				disable(2)
				}
			MAX-ACCESS read-write
			STATUS current
			DESCRIPTION
				"MLINEC (Multi-Link Network Connectivity) administrative state."
			::= { msanMlinecGlobal 1 }

		
		-- 1.3.6.1.4.1.1332.1.1.5.3.100
		msanMulticast OBJECT IDENTIFIER ::= { msanAdditionalConf 100 }

		
		-- 1.3.6.1.4.1.1332.1.1.5.3.100.1
		msanMulticastGlobal OBJECT IDENTIFIER ::= { msanMulticast 1 }

		
		-- 1.3.6.1.4.1.1332.1.1.5.3.100.2
		msanMulticastIntfStaticGroupTable OBJECT-TYPE
			SYNTAX SEQUENCE OF MsanMulticastIntfStaticGroupEntry
			MAX-ACCESS not-accessible
			STATUS deprecated
			DESCRIPTION
				"The table attaches static multicast groups to the interfaces."
			::= { msanMulticast 2 }

		
		-- 1.3.6.1.4.1.1332.1.1.5.3.100.2.1
		msanMulticastIntfStaticGroupEntry OBJECT-TYPE
			SYNTAX MsanMulticastIntfStaticGroupEntry
			MAX-ACCESS not-accessible
			STATUS deprecated
			DESCRIPTION
				"Description."
			INDEX { ifIndex, msanMulticastIntfStaticGroupIPAddr }
			::= { msanMulticastIntfStaticGroupTable 1 }

		
		MsanMulticastIntfStaticGroupEntry ::=
			SEQUENCE { 
				msanMulticastIntfStaticGroupIPAddr
					IpAddress,
				msanMulticastIntfStaticGroupRowStatus
					RowStatus
			 }

		-- 1.3.6.1.4.1.1332.1.1.5.3.100.2.1.1
		msanMulticastIntfStaticGroupIPAddr OBJECT-TYPE
			SYNTAX IpAddress
			MAX-ACCESS not-accessible
			STATUS deprecated
			DESCRIPTION
				"IP multicast address of valid multicast group."
			::= { msanMulticastIntfStaticGroupEntry 1 }

		
		-- 1.3.6.1.4.1.1332.1.1.5.3.100.2.1.2
		msanMulticastIntfStaticGroupRowStatus OBJECT-TYPE
			SYNTAX RowStatus
			MAX-ACCESS read-create
			STATUS deprecated
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastIntfStaticGroupEntry 2 }

		
		-- 1.3.6.1.4.1.1332.1.1.5.3.100.3
		msanMulticastGroupTable OBJECT-TYPE
			SYNTAX SEQUENCE OF MsanMulticastGroupEntry
			MAX-ACCESS not-accessible
			STATUS current
			DESCRIPTION
				"Description."
			::= { msanMulticast 3 }

		
		-- 1.3.6.1.4.1.1332.1.1.5.3.100.3.1
		msanMulticastGroupEntry OBJECT-TYPE
			SYNTAX MsanMulticastGroupEntry
			MAX-ACCESS not-accessible
			STATUS current
			DESCRIPTION
				"Description."
			INDEX { dot1qVlanIndex, msanMulticastGroupIpAddr }
			::= { msanMulticastGroupTable 1 }

		
		MsanMulticastGroupEntry ::=
			SEQUENCE { 
				msanMulticastGroupIpAddr
					IpAddress,
				msanMulticastGroupName
					OCTET STRING,
				msanMulticastGroupRowStatus
					RowStatus
			 }

		-- 1.3.6.1.4.1.1332.1.1.5.3.100.3.1.1
		msanMulticastGroupIpAddr OBJECT-TYPE
			SYNTAX IpAddress
			MAX-ACCESS not-accessible
			STATUS current
			DESCRIPTION
				"IP multicast address of valid multicast group."
			::= { msanMulticastGroupEntry 1 }

		
		-- 1.3.6.1.4.1.1332.1.1.5.3.100.3.1.2
		msanMulticastGroupName OBJECT-TYPE
			SYNTAX OCTET STRING
			MAX-ACCESS read-write
			STATUS current
			DESCRIPTION
				"Name of multicast group.
				"
			::= { msanMulticastGroupEntry 2 }

		
		-- 1.3.6.1.4.1.1332.1.1.5.3.100.3.1.3
		msanMulticastGroupRowStatus OBJECT-TYPE
			SYNTAX RowStatus
			MAX-ACCESS read-create
			STATUS current
			DESCRIPTION
				"The row status object controls the creation/deletion of rows in this table. 
				For row creation use createAndWait(5) [createAndGo(4) is not supported]."
			::= { msanMulticastGroupEntry 3 }

		
		-- 1.3.6.1.4.1.1332.1.1.5.3.100.4
		msanMulticastAclListTable OBJECT-TYPE
			SYNTAX SEQUENCE OF MsanMulticastAclListEntry
			MAX-ACCESS not-accessible
			STATUS deprecated
			DESCRIPTION
				"The table below assigns the symbolic names to the specific multicast ACLs."
			::= { msanMulticast 4 }

		
		-- 1.3.6.1.4.1.1332.1.1.5.3.100.4.1
		msanMulticastAclListEntry OBJECT-TYPE
			SYNTAX MsanMulticastAclListEntry
			MAX-ACCESS not-accessible
			STATUS deprecated
			DESCRIPTION
				"Description."
			INDEX { msanMulticastAclListId }
			::= { msanMulticastAclListTable 1 }

		
		MsanMulticastAclListEntry ::=
			SEQUENCE { 
				msanMulticastAclListId
					INTEGER,
				msanMulticastAclListName
					SnmpAdminString,
				msanMulticastAclListRowStatus
					RowStatus
			 }

		-- 1.3.6.1.4.1.1332.1.1.5.3.100.4.1.1
		msanMulticastAclListId OBJECT-TYPE
			SYNTAX INTEGER (0..255)
			MAX-ACCESS not-accessible
			STATUS deprecated
			DESCRIPTION
				"Multicast List id. Integer from 0 to 255.
				"
			::= { msanMulticastAclListEntry 1 }

		
		-- 1.3.6.1.4.1.1332.1.1.5.3.100.4.1.2
		msanMulticastAclListName OBJECT-TYPE
			SYNTAX SnmpAdminString
			MAX-ACCESS read-write
			STATUS deprecated
			DESCRIPTION
				"ACL list symbolic name. Should be unique."
			::= { msanMulticastAclListEntry 2 }

		
		-- 1.3.6.1.4.1.1332.1.1.5.3.100.4.1.3
		msanMulticastAclListRowStatus OBJECT-TYPE
			SYNTAX RowStatus
			MAX-ACCESS read-create
			STATUS deprecated
			DESCRIPTION
				"The row status object controls the creation/deletion of rows in this table.
				Its semantics are the same as those for the RowStatus textual convention specified for SNMPv2.
				For row creation use createAndWait(5).
				For row activation use active(1).
				For row deletion use destroy(6).
				
				Other values are currently not supported."
			::= { msanMulticastAclListEntry 3 }

		
		-- 1.3.6.1.4.1.1332.1.1.5.3.100.5
		msanMulticastAclListGroupTable OBJECT-TYPE
			SYNTAX SEQUENCE OF MsanMulticastAclListGroupEntry
			MAX-ACCESS not-accessible
			STATUS deprecated
			DESCRIPTION
				"The table below links the multicast groups to the ACL."
			::= { msanMulticast 5 }

		
		-- 1.3.6.1.4.1.1332.1.1.5.3.100.5.1
		msanMulticastAclListGroupEntry OBJECT-TYPE
			SYNTAX MsanMulticastAclListGroupEntry
			MAX-ACCESS not-accessible
			STATUS deprecated
			DESCRIPTION
				"Description."
			INDEX { msanMulticastAclListId, msanMulticastAclGroupIpAddr }
			::= { msanMulticastAclListGroupTable 1 }

		
		MsanMulticastAclListGroupEntry ::=
			SEQUENCE { 
				msanMulticastAclGroupIpAddr
					IpAddress,
				msanMulticastAclListGroupRowStatus
					RowStatus
			 }

		-- 1.3.6.1.4.1.1332.1.1.5.3.100.5.1.1
		msanMulticastAclGroupIpAddr OBJECT-TYPE
			SYNTAX IpAddress
			MAX-ACCESS not-accessible
			STATUS deprecated
			DESCRIPTION
				"IP multicast address of valid ACL multicast group."
			::= { msanMulticastAclListGroupEntry 1 }

		
		-- 1.3.6.1.4.1.1332.1.1.5.3.100.5.1.2
		msanMulticastAclListGroupRowStatus OBJECT-TYPE
			SYNTAX RowStatus
			MAX-ACCESS read-create
			STATUS deprecated
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastAclListGroupEntry 2 }

		
		-- 1.3.6.1.4.1.1332.1.1.5.3.100.6
		msanMulticastAclIntfListTable OBJECT-TYPE
			SYNTAX SEQUENCE OF MsanMulticastAclIntfListEntry
			MAX-ACCESS not-accessible
			STATUS deprecated
			DESCRIPTION
				"The table below assigns the multicast ACL to the interfaces"
			::= { msanMulticast 6 }

		
		-- 1.3.6.1.4.1.1332.1.1.5.3.100.6.1
		msanMulticastAclIntfListEntry OBJECT-TYPE
			SYNTAX MsanMulticastAclIntfListEntry
			MAX-ACCESS not-accessible
			STATUS deprecated
			DESCRIPTION
				"Description."
			INDEX { ifIndex, msanMulticastAclListId }
			::= { msanMulticastAclIntfListTable 1 }

		
		MsanMulticastAclIntfListEntry ::=
			SEQUENCE { 
				msanMulticastAclIntfListMode
					INTEGER,
				msanMulticastAclIntfListRowStatus
					RowStatus
			 }

		-- 1.3.6.1.4.1.1332.1.1.5.3.100.6.1.1
		msanMulticastAclIntfListMode OBJECT-TYPE
			SYNTAX INTEGER
				{
				accept(1),
				deny(2)
				}
			MAX-ACCESS read-write
			STATUS deprecated
			DESCRIPTION
				"Defines the mode in which interface for specified ACL list works.
				"
			::= { msanMulticastAclIntfListEntry 1 }

		
		-- 1.3.6.1.4.1.1332.1.1.5.3.100.6.1.2
		msanMulticastAclIntfListRowStatus OBJECT-TYPE
			SYNTAX RowStatus
			MAX-ACCESS read-create
			STATUS deprecated
			DESCRIPTION
				"The row status object controls the creation/deletion of rows in this table.
				Its semantics are the same as those for the RowStatus textual convention specified for SNMPv2.
				For row creation use createAndWait(5).
				For row activation use active(1).
				For row deletion use destroy(6).
				
				Other values are currently not supported."
			::= { msanMulticastAclIntfListEntry 2 }

		
		-- 1.3.6.1.4.1.1332.1.1.5.3.100.7
		msanMulticastAclListVlanGroupTable OBJECT-TYPE
			SYNTAX SEQUENCE OF MsanMulticastAclListVlanGroupEntry
			MAX-ACCESS not-accessible
			STATUS deprecated
			DESCRIPTION
				"The table below links the multicast groups to the ACL."
			::= { msanMulticast 7 }

		
		-- 1.3.6.1.4.1.1332.1.1.5.3.100.7.1
		msanMulticastAclListVlanGroupEntry OBJECT-TYPE
			SYNTAX MsanMulticastAclListVlanGroupEntry
			MAX-ACCESS not-accessible
			STATUS deprecated
			DESCRIPTION
				"Description."
			INDEX { msanMulticastAclListId, dot1qVlanIndex, msanMulticastAclListVlanGroupIpAddr }
			::= { msanMulticastAclListVlanGroupTable 1 }

		
		MsanMulticastAclListVlanGroupEntry ::=
			SEQUENCE { 
				msanMulticastAclListVlanGroupIpAddr
					IpAddress,
				msanMulticastAclListVlanGroupRowStatus
					RowStatus
			 }

		-- 1.3.6.1.4.1.1332.1.1.5.3.100.7.1.1
		msanMulticastAclListVlanGroupIpAddr OBJECT-TYPE
			SYNTAX IpAddress
			MAX-ACCESS not-accessible
			STATUS deprecated
			DESCRIPTION
				"IP multicast address of valid ACL multicast group."
			::= { msanMulticastAclListVlanGroupEntry 1 }

		
		-- 1.3.6.1.4.1.1332.1.1.5.3.100.7.1.2
		msanMulticastAclListVlanGroupRowStatus OBJECT-TYPE
			SYNTAX RowStatus
			MAX-ACCESS read-create
			STATUS deprecated
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastAclListVlanGroupEntry 2 }

		
		-- 1.3.6.1.4.1.1332.1.1.5.3.100.8
		msanMulticastIntfVlanStaticGroupTable OBJECT-TYPE
			SYNTAX SEQUENCE OF MsanMulticastIntfVlanStaticGroupEntry
			MAX-ACCESS not-accessible
			STATUS current
			DESCRIPTION
				"Description."
			::= { msanMulticast 8 }

		
		-- 1.3.6.1.4.1.1332.1.1.5.3.100.8.1
		msanMulticastIntfVlanStaticGroupEntry OBJECT-TYPE
			SYNTAX MsanMulticastIntfVlanStaticGroupEntry
			MAX-ACCESS not-accessible
			STATUS current
			DESCRIPTION
				"Description."
			INDEX { ifIndex, dot1qVlanIndex, msanMulticastIntfVlanStaticGroupIpAddr }
			::= { msanMulticastIntfVlanStaticGroupTable 1 }

		
		MsanMulticastIntfVlanStaticGroupEntry ::=
			SEQUENCE { 
				msanMulticastIntfVlanStaticGroupIpAddr
					IpAddress,
				msanMulticastIntfVlanStaticGroupRowStatus
					RowStatus
			 }

		-- 1.3.6.1.4.1.1332.1.1.5.3.100.8.1.1
		msanMulticastIntfVlanStaticGroupIpAddr OBJECT-TYPE
			SYNTAX IpAddress
			MAX-ACCESS not-accessible
			STATUS current
			DESCRIPTION
				"IP multicast address of valid multicast group."
			::= { msanMulticastIntfVlanStaticGroupEntry 1 }

		
		-- 1.3.6.1.4.1.1332.1.1.5.3.100.8.1.2
		msanMulticastIntfVlanStaticGroupRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastIntfVlanStaticGroupEntry 2 }

		
		-- 1.3.6.1.4.1.1332.1.1.5.3.100.9
		msanMulticastAccessListTable OBJECT-TYPE
			SYNTAX SEQUENCE OF MsanMulticastAccessListEntry
			MAX-ACCESS not-accessible
			STATUS current
			DESCRIPTION
				"The table below assigns the symbolic names to the specific multicast ACLs."
			::= { msanMulticast 9 }

		
		-- 1.3.6.1.4.1.1332.1.1.5.3.100.9.1
		msanMulticastAccessListEntry OBJECT-TYPE
			SYNTAX MsanMulticastAccessListEntry
			MAX-ACCESS not-accessible
			STATUS current
			DESCRIPTION
				"Description."
			INDEX { msanMulticastAccessListName }
			::= { msanMulticastAccessListTable 1 }

		
		MsanMulticastAccessListEntry ::=
			SEQUENCE { 
				msanMulticastAccessListName
					OCTET STRING,
				msanMulticastAccessListRowStatus
					RowStatus
			 }

		-- 1.3.6.1.4.1.1332.1.1.5.3.100.9.1.1
		msanMulticastAccessListName OBJECT-TYPE
			SYNTAX OCTET STRING (SIZE (1..32))
			MAX-ACCESS not-accessible
			STATUS current
			DESCRIPTION
				"ACL list symbolic name. Should be unique."
			::= { msanMulticastAccessListEntry 1 }

		
		-- 1.3.6.1.4.1.1332.1.1.5.3.100.9.1.2
		msanMulticastAccessListRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndGo(4).
				For row activation use active(1).
				For row deletion use destroy(6).
				
				Other values are currently not supported."
			::= { msanMulticastAccessListEntry 2 }

		
		-- 1.3.6.1.4.1.1332.1.1.5.3.100.10
		msanMulticastAccessListGroupTable OBJECT-TYPE
			SYNTAX SEQUENCE OF MsanMulticastAccessListGroupEntry
			MAX-ACCESS not-accessible
			STATUS current
			DESCRIPTION
				"The table below links the multicast addresses to the ACL list"
			::= { msanMulticast 10 }

		
		-- 1.3.6.1.4.1.1332.1.1.5.3.100.10.1
		msanMulticastAccessListGroupEntry OBJECT-TYPE
			SYNTAX MsanMulticastAccessListGroupEntry
			MAX-ACCESS not-accessible
			STATUS current
			DESCRIPTION
				"Description."
			INDEX { msanMulticastAccessListName, dot1qVlanIndex, msanMulticastAccessListGroupIpAddr }
			::= { msanMulticastAccessListGroupTable 1 }

		
		MsanMulticastAccessListGroupEntry ::=
			SEQUENCE { 
				msanMulticastAccessListGroupIpAddr
					IpAddress,
				msanMulticastAccessListGroupRowStatus
					RowStatus
			 }

		-- 1.3.6.1.4.1.1332.1.1.5.3.100.10.1.1
		msanMulticastAccessListGroupIpAddr OBJECT-TYPE
			SYNTAX IpAddress
			MAX-ACCESS not-accessible
			STATUS current
			DESCRIPTION
				"IP multicast address of valid ACL multicast group."
			::= { msanMulticastAccessListGroupEntry 1 }

		
		-- 1.3.6.1.4.1.1332.1.1.5.3.100.10.1.2
		msanMulticastAccessListGroupRowStatus OBJECT-TYPE
			SYNTAX RowStatus
			MAX-ACCESS read-create
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastAccessListGroupEntry 2 }

		
		-- 1.3.6.1.4.1.1332.1.1.5.3.100.11
		msanMulticastAccessListIntfTable OBJECT-TYPE
			SYNTAX SEQUENCE OF MsanMulticastAccessListIntfEntry
			MAX-ACCESS not-accessible
			STATUS current
			DESCRIPTION
				"The table below assigns the multicast ACL list to the interfaces"
			::= { msanMulticast 11 }

		
		-- 1.3.6.1.4.1.1332.1.1.5.3.100.11.1
		msanMulticastAccessListIntfEntry OBJECT-TYPE
			SYNTAX MsanMulticastAccessListIntfEntry
			MAX-ACCESS not-accessible
			STATUS current
			DESCRIPTION
				"Description."
			INDEX { ifIndex, msanMulticastAccessListName }
			::= { msanMulticastAccessListIntfTable 1 }

		
		MsanMulticastAccessListIntfEntry ::=
			SEQUENCE { 
				msanMulticastAccessListIntfMode
					INTEGER,
				msanMulticastAccessListIntfRowStatus
					RowStatus
			 }

		-- 1.3.6.1.4.1.1332.1.1.5.3.100.11.1.1
		msanMulticastAccessListIntfMode OBJECT-TYPE
			SYNTAX INTEGER
				{
				accept(1),
				deny(2)
				}
			MAX-ACCESS read-write
			STATUS current
			DESCRIPTION
				"Defines the mode in which interface for specified ACL list works.
				"
			::= { msanMulticastAccessListIntfEntry 1 }

		
		-- 1.3.6.1.4.1.1332.1.1.5.3.100.11.1.2
		msanMulticastAccessListIntfRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndWait(5).
				For row activation use active(1).
				For row deletion use destroy(6).
				
				Other values are currently not supported."
			::= { msanMulticastAccessListIntfEntry 2 }

		
		-- 1.3.6.1.4.1.1332.1.1.5.3.100.12
		msanSwitchMFDBTable OBJECT-TYPE
			SYNTAX SEQUENCE OF MsanSwitchMFDBEntry
			MAX-ACCESS not-accessible
			STATUS current
			DESCRIPTION
				"The Multicast Forwarding Database table"
			::= { msanMulticast 12 }

		
		-- 1.3.6.1.4.1.1332.1.1.5.3.100.12.1
		msanSwitchMFDBEntry OBJECT-TYPE
			SYNTAX MsanSwitchMFDBEntry
			MAX-ACCESS not-accessible
			STATUS current
			DESCRIPTION
				"Contains Forwarding and Filtering information per Component User, Vlan Index, and MAC Address."
			INDEX { msanSwitchMFDBProtocolType, msanSwitchMFDBVlanId, msanSwitchMFDBMacAddress }
			::= { msanSwitchMFDBTable 1 }

		
		MsanSwitchMFDBEntry ::=
			SEQUENCE { 
				msanSwitchMFDBProtocolType
					INTEGER,
				msanSwitchMFDBVlanId
					VlanIndex,
				msanSwitchMFDBMacAddress
					MacAddress,
				msanSwitchMFDBType
					INTEGER,
				msanSwitchMFDBDescription
					DisplayString,
				msanSwitchMFDBForwardingPortMask
					PortMask,
				msanSwitchMFDBFilteringPortMask
					PortMask
			 }

		-- 1.3.6.1.4.1.1332.1.1.5.3.100.12.1.1
		msanSwitchMFDBProtocolType OBJECT-TYPE
			SYNTAX INTEGER
				{
				static(1),
				gmrp(2),
				igmp(3)
				}
			MAX-ACCESS read-only
			STATUS current
			DESCRIPTION
				"The component that is responsible for this entry in the Multicast 
				Forwarding Database."
			::= { msanSwitchMFDBEntry 1 }

		
		-- 1.3.6.1.4.1.1332.1.1.5.3.100.12.1.2
		msanSwitchMFDBVlanId OBJECT-TYPE
			SYNTAX VlanIndex
			MAX-ACCESS read-only
			STATUS current
			DESCRIPTION
				"Vlan Index for which this entry is associated with."
			::= { msanSwitchMFDBEntry 2 }

		
		-- 1.3.6.1.4.1.1332.1.1.5.3.100.12.1.3
		msanSwitchMFDBMacAddress OBJECT-TYPE
			SYNTAX MacAddress
			MAX-ACCESS read-only
			STATUS current
			DESCRIPTION
				"A multicast MAC address for which the switch has forwarding and or 
				filtering information."
			::= { msanSwitchMFDBEntry 3 }

		
		-- 1.3.6.1.4.1.1332.1.1.5.3.100.12.1.4
		msanSwitchMFDBType OBJECT-TYPE
			SYNTAX INTEGER
				{
				static(1),
				dynamic(2)
				}
			MAX-ACCESS read-only
			STATUS current
			DESCRIPTION
				"This displays the type of the entry. 
				
				static(1)  - Entries configured by the end user
				dynamic(2) - Entries added as a result of a learning process or protocol"
			::= { msanSwitchMFDBEntry 4 }

		
		-- 1.3.6.1.4.1.1332.1.1.5.3.100.12.1.5
		msanSwitchMFDBDescription OBJECT-TYPE
			SYNTAX DisplayString
			MAX-ACCESS read-only
			STATUS current
			DESCRIPTION
				"Text description of this multicast table entry."
			::= { msanSwitchMFDBEntry 5 }

		
		-- 1.3.6.1.4.1.1332.1.1.5.3.100.12.1.6
		msanSwitchMFDBForwardingPortMask OBJECT-TYPE
			SYNTAX PortMask
			MAX-ACCESS read-only
			STATUS current
			DESCRIPTION
				"BitMask indicating which ports this entry indicates should be forwarded.
				
				To obtain port numbers from interface numbers, use the objects
				agentPortDot1dBasePort and agentPortIfIndex in the agentPortConfigTable 
				table."
			::= { msanSwitchMFDBEntry 6 }

		
		-- 1.3.6.1.4.1.1332.1.1.5.3.100.12.1.7
		msanSwitchMFDBFilteringPortMask OBJECT-TYPE
			SYNTAX PortMask
			MAX-ACCESS read-only
			STATUS current
			DESCRIPTION
				"BitMask indicating which ports this entry indicates should be filtered.
				
				To obtain port numbers from interface numbers, use the objects
				agentPortDot1dBasePort and agentPortIfIndex in the agentPortConfigTable 
				table."
			::= { msanSwitchMFDBEntry 7 }

		
		-- 1.3.6.1.4.1.1332.1.1.5.3.100.13
		msanMulticastStaticClientTable OBJECT-TYPE
			SYNTAX SEQUENCE OF MsanMulticastStaticClientEntry
			MAX-ACCESS not-accessible
			STATUS current
			DESCRIPTION
				"Description."
			::= { msanMulticast 13 }

		
		-- 1.3.6.1.4.1.1332.1.1.5.3.100.13.1
		msanMulticastStaticClientEntry OBJECT-TYPE
			SYNTAX MsanMulticastStaticClientEntry
			MAX-ACCESS not-accessible
			STATUS current
			DESCRIPTION
				"Description."
			INDEX { dot1qVlanIndex, msanMulticastStaticClientIpAddr }
			::= { msanMulticastStaticClientTable 1 }

		
		MsanMulticastStaticClientEntry ::=
			SEQUENCE { 
				msanMulticastStaticClientIpAddr
					IpAddress,
				msanMulticastStaticClientRowStatus
					RowStatus
			 }

		-- 1.3.6.1.4.1.1332.1.1.5.3.100.13.1.1
		msanMulticastStaticClientIpAddr OBJECT-TYPE
			SYNTAX IpAddress
			MAX-ACCESS not-accessible
			STATUS current
			DESCRIPTION
				"Multicast static client IP address on specified vlan_id."
			::= { msanMulticastStaticClientEntry 1 }

		
		-- 1.3.6.1.4.1.1332.1.1.5.3.100.13.1.2
		msanMulticastStaticClientRowStatus OBJECT-TYPE
			SYNTAX RowStatus
			MAX-ACCESS read-write
			STATUS current
			DESCRIPTION
				"The row status object controls the creation/deletion of rows in this table. 
				Its semantics are the same as those for the RowStatus textual convention specified for SNMPv2.
				Setting this object to createAndGo(4) creates a row in this table.
				Setting this object to destroy(6) will remove this entry.
				Read values: active(1).
				Other values are currently not supported."
			::= { msanMulticastStaticClientEntry 2 }

		
		-- 1.3.6.1.4.1.1332.1.1.5.3.101
		msanFiltering OBJECT IDENTIFIER ::= { msanAdditionalConf 101 }

		
		-- 1.3.6.1.4.1.1332.1.1.5.3.101.2
		msanFilteringGlobal OBJECT IDENTIFIER ::= { msanFiltering 2 }

		
		-- 1.3.6.1.4.1.1332.1.1.5.3.101.3
		msanFilteringFilterTable OBJECT-TYPE
			SYNTAX SEQUENCE OF MsanFilteringFilterEntry
			MAX-ACCESS not-accessible
			STATUS deprecated
			DESCRIPTION
				"Defines a list of filters."
			::= { msanFiltering 3 }

		
		-- 1.3.6.1.4.1.1332.1.1.5.3.101.3.1
		msanFilteringFilterEntry OBJECT-TYPE
			SYNTAX MsanFilteringFilterEntry
			MAX-ACCESS not-accessible
			STATUS deprecated
			DESCRIPTION
				"Description."
			INDEX { msanFilteringFilterId }
			::= { msanFilteringFilterTable 1 }

		
		MsanFilteringFilterEntry ::=
			SEQUENCE { 
				msanFilteringFilterId
					Integer32,
				msanFilteringFilterName
					OCTET STRING,
				msanFilteringFilterType
					INTEGER,
				msanFilteringFilterRowStatus
					RowStatus
			 }

		-- 1.3.6.1.4.1.1332.1.1.5.3.101.3.1.1
		msanFilteringFilterId OBJECT-TYPE
			SYNTAX Integer32 (1..64 | 301..500)
			MAX-ACCESS read-write
			STATUS deprecated
			DESCRIPTION
				"Filter identity."
			::= { msanFilteringFilterEntry 1 }

		
		-- 1.3.6.1.4.1.1332.1.1.5.3.101.3.1.2
		msanFilteringFilterName OBJECT-TYPE
			SYNTAX OCTET STRING
			MAX-ACCESS read-write
			STATUS deprecated
			DESCRIPTION
				"Name of filter to be shown."
			::= { msanFilteringFilterEntry 2 }

		
		-- 1.3.6.1.4.1.1332.1.1.5.3.101.3.1.3
		msanFilteringFilterType OBJECT-TYPE
			SYNTAX INTEGER
				{
				static(1),
				dynamic(2)
				}
			MAX-ACCESS read-only
			STATUS deprecated
			DESCRIPTION
				"Type of filter (static or dynamic)."
			::= { msanFilteringFilterEntry 3 }

		
		-- 1.3.6.1.4.1.1332.1.1.5.3.101.3.1.4
		msanFilteringFilterRowStatus OBJECT-TYPE
			SYNTAX RowStatus
			MAX-ACCESS read-create
			STATUS deprecated
			DESCRIPTION
				"SNMP row status.
				
				Supported values:
				active(1) - valid entry;
				createAndGo(4) - used to create a new entry;
				destroy(6) - removes the entry."
			DEFVAL { active }
			::= { msanFilteringFilterEntry 4 }

		
		-- 1.3.6.1.4.1.1332.1.1.5.3.101.4
		msanFilteringAssignFilterTable OBJECT-TYPE
			SYNTAX SEQUENCE OF MsanFilteringAssignFilterEntry
			MAX-ACCESS not-accessible
			STATUS deprecated
			DESCRIPTION
				"This table defines a list of filters assigned to interface."
			::= { msanFiltering 4 }

		
		-- 1.3.6.1.4.1.1332.1.1.5.3.101.4.1
		msanFilteringAssignFilterEntry OBJECT-TYPE
			SYNTAX MsanFilteringAssignFilterEntry
			MAX-ACCESS not-accessible
			STATUS deprecated
			DESCRIPTION
				"Description."
			INDEX { ifIndex, msanFilteringFilterId }
			::= { msanFilteringAssignFilterTable 1 }

		
		MsanFilteringAssignFilterEntry ::=
			SEQUENCE { 
				msanFilteringAssignFilterVid
					Integer32,
				msanFilteringAssignFilterCos
					Integer32,
				msanFilteringAssignFilterDscp
					Integer32,
				msanFilteringAssignFilterPrec
					Integer32,
				msanFilteringAssignFilterRowStatus
					RowStatus
			 }

		-- 1.3.6.1.4.1.1332.1.1.5.3.101.4.1.1
		msanFilteringAssignFilterVid OBJECT-TYPE
			SYNTAX Integer32 (0..4094)
			MAX-ACCESS read-write
			STATUS deprecated
			DESCRIPTION
				"ID of VLAN to be filtered."
			::= { msanFilteringAssignFilterEntry 1 }

		
		-- 1.3.6.1.4.1.1332.1.1.5.3.101.4.1.2
		msanFilteringAssignFilterCos OBJECT-TYPE
			SYNTAX Integer32 (0..7)
			MAX-ACCESS read-write
			STATUS deprecated
			DESCRIPTION
				"CoS value to be filtered."
			::= { msanFilteringAssignFilterEntry 2 }

		
		-- 1.3.6.1.4.1.1332.1.1.5.3.101.4.1.3
		msanFilteringAssignFilterDscp OBJECT-TYPE
			SYNTAX Integer32 (0..63)
			MAX-ACCESS read-write
			STATUS deprecated
			DESCRIPTION
				"DSCP field."
			::= { msanFilteringAssignFilterEntry 3 }

		
		-- 1.3.6.1.4.1.1332.1.1.5.3.101.4.1.4
		msanFilteringAssignFilterPrec OBJECT-TYPE
			SYNTAX Integer32 (0..7)
			MAX-ACCESS read-write
			STATUS deprecated
			DESCRIPTION
				"Precedence in DSCP tag."
			::= { msanFilteringAssignFilterEntry 4 }

		
		-- 1.3.6.1.4.1.1332.1.1.5.3.101.4.1.5
		msanFilteringAssignFilterRowStatus OBJECT-TYPE
			SYNTAX RowStatus
			MAX-ACCESS read-create
			STATUS deprecated
			DESCRIPTION
				"SNMP row status.
				
				Supported values:
				active(1) - valid entry;
				createAndGo(4) - used to create a new entry;
				destroy(6) - removes the entry."
			DEFVAL { active }
			::= { msanFilteringAssignFilterEntry 5 }

		
		-- 1.3.6.1.4.1.1332.1.1.5.3.101.5
		msanFilteringRuleTable OBJECT-TYPE
			SYNTAX SEQUENCE OF MsanFilteringRuleEntry
			MAX-ACCESS not-accessible
			STATUS deprecated
			DESCRIPTION
				"This table defines a list of filtering rules associated to filters."
			::= { msanFiltering 5 }

		
		-- 1.3.6.1.4.1.1332.1.1.5.3.101.5.1
		msanFilteringRuleEntry OBJECT-TYPE
			SYNTAX MsanFilteringRuleEntry
			MAX-ACCESS not-accessible
			STATUS deprecated
			DESCRIPTION
				"Description."
			INDEX { msanFilteringRuleId, msanFilteringFilterId }
			::= { msanFilteringRuleTable 1 }

		
		MsanFilteringRuleEntry ::=
			SEQUENCE { 
				msanFilteringRuleId
					Integer32,
				msanFilteringRuleResponse
					INTEGER,
				msanFilteringRuleFromMac
					MacAddress,
				msanFilteringRuleFromMacMask
					MacAddress,
				msanFilteringRuleFromIp
					IpAddress,
				msanFilteringRuleFromMask
					IpAddress,
				msanFilteringRuleFromPortLow
					Unsigned32,
				msanFilteringRuleFromPortHigh
					Unsigned32,
				msanFilteringRuleToMac
					MacAddress,
				msanFilteringRuleToMacMask
					MacAddress,
				msanFilteringRuleToIp
					IpAddress,
				msanFilteringRuleToMask
					IpAddress,
				msanFilteringRuleToPortLow
					Unsigned32,
				msanFilteringRuleToPortHigh
					Unsigned32,
				msanFilteringRuleEtherProto
					OCTET STRING,
				msanFilteringRuleIpProto
					OCTET STRING,
				msanFilteringRuleIcmType
					Unsigned32,
				msanFilteringRulePrec
					Unsigned32,
				msanFilteringRuleTos
					Unsigned32,
				msanFilteringRuleVid
					Unsigned32,
				msanFilteringRuleCos
					Unsigned32,
				msanFilteringRuleTag
					INTEGER,
				msanFilteringRuleRowStatus
					RowStatus
			 }

		-- 1.3.6.1.4.1.1332.1.1.5.3.101.5.1.1
		msanFilteringRuleId OBJECT-TYPE
			SYNTAX Integer32 (1..65535)
			MAX-ACCESS read-only
			STATUS deprecated
			DESCRIPTION
				"Filtering rule identity."
			::= { msanFilteringRuleEntry 1 }

		
		-- 1.3.6.1.4.1.1332.1.1.5.3.101.5.1.2
		msanFilteringRuleResponse OBJECT-TYPE
			SYNTAX INTEGER
				{
				accept(1),
				deny(2)
				}
			MAX-ACCESS read-write
			STATUS deprecated
			DESCRIPTION
				"Filter response."
			::= { msanFilteringRuleEntry 2 }

		
		-- 1.3.6.1.4.1.1332.1.1.5.3.101.5.1.3
		msanFilteringRuleFromMac OBJECT-TYPE
			SYNTAX MacAddress
			MAX-ACCESS read-write
			STATUS deprecated
			DESCRIPTION
				"Source Ethernet address."
			::= { msanFilteringRuleEntry 3 }

		
		-- 1.3.6.1.4.1.1332.1.1.5.3.101.5.1.4
		msanFilteringRuleFromMacMask OBJECT-TYPE
			SYNTAX MacAddress
			MAX-ACCESS read-write
			STATUS deprecated
			DESCRIPTION
				"Source Ethernet address mask."
			::= { msanFilteringRuleEntry 4 }

		
		-- 1.3.6.1.4.1.1332.1.1.5.3.101.5.1.5
		msanFilteringRuleFromIp OBJECT-TYPE
			SYNTAX IpAddress
			MAX-ACCESS read-write
			STATUS deprecated
			DESCRIPTION
				"Source IP address."
			::= { msanFilteringRuleEntry 5 }

		
		-- 1.3.6.1.4.1.1332.1.1.5.3.101.5.1.6
		msanFilteringRuleFromMask OBJECT-TYPE
			SYNTAX IpAddress
			MAX-ACCESS read-write
			STATUS deprecated
			DESCRIPTION
				"Source IP address mask."
			::= { msanFilteringRuleEntry 6 }

		
		-- 1.3.6.1.4.1.1332.1.1.5.3.101.5.1.7
		msanFilteringRuleFromPortLow OBJECT-TYPE
			SYNTAX Unsigned32 (0..65535)
			MAX-ACCESS read-write
			STATUS deprecated
			DESCRIPTION
				"The lowest number of a source TCP or UDP port."
			::= { msanFilteringRuleEntry 7 }

		
		-- 1.3.6.1.4.1.1332.1.1.5.3.101.5.1.8
		msanFilteringRuleFromPortHigh OBJECT-TYPE
			SYNTAX Unsigned32 (0..65535)
			MAX-ACCESS read-write
			STATUS deprecated
			DESCRIPTION
				"The highest number of a source TCP or UDP port.."
			::= { msanFilteringRuleEntry 8 }

		
		-- 1.3.6.1.4.1.1332.1.1.5.3.101.5.1.9
		msanFilteringRuleToMac OBJECT-TYPE
			SYNTAX MacAddress
			MAX-ACCESS read-write
			STATUS deprecated
			DESCRIPTION
				"Destination Ethernet address."
			::= { msanFilteringRuleEntry 9 }

		
		-- 1.3.6.1.4.1.1332.1.1.5.3.101.5.1.10
		msanFilteringRuleToMacMask OBJECT-TYPE
			SYNTAX MacAddress
			MAX-ACCESS read-write
			STATUS deprecated
			DESCRIPTION
				"Destination Ethernet address mask."
			::= { msanFilteringRuleEntry 10 }

		
		-- 1.3.6.1.4.1.1332.1.1.5.3.101.5.1.11
		msanFilteringRuleToIp OBJECT-TYPE
			SYNTAX IpAddress
			MAX-ACCESS read-write
			STATUS deprecated
			DESCRIPTION
				"Destination IP address."
			::= { msanFilteringRuleEntry 11 }

		
		-- 1.3.6.1.4.1.1332.1.1.5.3.101.5.1.12
		msanFilteringRuleToMask OBJECT-TYPE
			SYNTAX IpAddress
			MAX-ACCESS read-write
			STATUS deprecated
			DESCRIPTION
				"Destination IP address mask."
			::= { msanFilteringRuleEntry 12 }

		
		-- 1.3.6.1.4.1.1332.1.1.5.3.101.5.1.13
		msanFilteringRuleToPortLow OBJECT-TYPE
			SYNTAX Unsigned32 (0..65535)
			MAX-ACCESS read-write
			STATUS deprecated
			DESCRIPTION
				"The lowest number of a destination TCP or UDP port."
			::= { msanFilteringRuleEntry 13 }

		
		-- 1.3.6.1.4.1.1332.1.1.5.3.101.5.1.14
		msanFilteringRuleToPortHigh OBJECT-TYPE
			SYNTAX Unsigned32 (0..65535)
			MAX-ACCESS read-write
			STATUS deprecated
			DESCRIPTION
				"The highest number of a destination TCP or UDP port."
			::= { msanFilteringRuleEntry 14 }

		
		-- 1.3.6.1.4.1.1332.1.1.5.3.101.5.1.15
		msanFilteringRuleEtherProto OBJECT-TYPE
			SYNTAX OCTET STRING
			MAX-ACCESS read-write
			STATUS deprecated
			DESCRIPTION
				"Ethernet protocol to be filtered."
			::= { msanFilteringRuleEntry 15 }

		
		-- 1.3.6.1.4.1.1332.1.1.5.3.101.5.1.16
		msanFilteringRuleIpProto OBJECT-TYPE
			SYNTAX OCTET STRING
			MAX-ACCESS read-write
			STATUS deprecated
			DESCRIPTION
				"IP protocol to be filtered."
			::= { msanFilteringRuleEntry 16 }

		
		-- 1.3.6.1.4.1.1332.1.1.5.3.101.5.1.17
		msanFilteringRuleIcmType OBJECT-TYPE
			SYNTAX Unsigned32 (0..255)
			MAX-ACCESS read-write
			STATUS deprecated
			DESCRIPTION
				"ICMP type. ICMP sends an error message to the transmitter of IP packets and provides
				information at IP packet processing."
			::= { msanFilteringRuleEntry 17 }

		
		-- 1.3.6.1.4.1.1332.1.1.5.3.101.5.1.18
		msanFilteringRulePrec OBJECT-TYPE
			SYNTAX Unsigned32 (0..7)
			MAX-ACCESS read-write
			STATUS deprecated
			DESCRIPTION
				"Precedence in DSCP tag."
			::= { msanFilteringRuleEntry 18 }

		
		-- 1.3.6.1.4.1.1332.1.1.5.3.101.5.1.19
		msanFilteringRuleTos OBJECT-TYPE
			SYNTAX Unsigned32 (0..15)
			MAX-ACCESS read-write
			STATUS deprecated
			DESCRIPTION
				"TOS to be filtered."
			::= { msanFilteringRuleEntry 19 }

		
		-- 1.3.6.1.4.1.1332.1.1.5.3.101.5.1.20
		msanFilteringRuleVid OBJECT-TYPE
			SYNTAX Unsigned32 (0..4094)
			MAX-ACCESS read-write
			STATUS deprecated
			DESCRIPTION
				"ID of VLAN to be filtered."
			::= { msanFilteringRuleEntry 20 }

		
		-- 1.3.6.1.4.1.1332.1.1.5.3.101.5.1.21
		msanFilteringRuleCos OBJECT-TYPE
			SYNTAX Unsigned32 (0..7)
			MAX-ACCESS read-write
			STATUS deprecated
			DESCRIPTION
				"CoS value to be filtered."
			::= { msanFilteringRuleEntry 21 }

		
		-- 1.3.6.1.4.1.1332.1.1.5.3.101.5.1.22
		msanFilteringRuleTag OBJECT-TYPE
			SYNTAX INTEGER
				{
				untagged(1),
				tagged(2),
				qinq-tagged(3)
				}
			MAX-ACCESS read-write
			STATUS deprecated
			DESCRIPTION
				"802.1Q tag."
			::= { msanFilteringRuleEntry 22 }

		
		-- 1.3.6.1.4.1.1332.1.1.5.3.101.5.1.23
		msanFilteringRuleRowStatus OBJECT-TYPE
			SYNTAX RowStatus
			MAX-ACCESS read-create
			STATUS deprecated
			DESCRIPTION
				"SNMP row status.
				
				Supported values:
				active(1) - valid entry;
				createAndGo(4) - used to create a new entry;
				destroy(6) - removes the entry."
			DEFVAL { active }
			::= { msanFilteringRuleEntry 23 }

		
		-- 1.3.6.1.4.1.1332.1.1.5.3.101.6
		msanFilteringAttachedFilterTable OBJECT-TYPE
			SYNTAX SEQUENCE OF MsanFilteringAttachedFilterEntry
			MAX-ACCESS not-accessible
			STATUS deprecated
			DESCRIPTION
				"This table defines information about filters attached to interface."
			::= { msanFiltering 6 }

		
		-- 1.3.6.1.4.1.1332.1.1.5.3.101.6.1
		msanFilteringAttachedFilterEntry OBJECT-TYPE
			SYNTAX MsanFilteringAttachedFilterEntry
			MAX-ACCESS not-accessible
			STATUS deprecated
			DESCRIPTION
				"Description."
			INDEX { ifIndex, msanFilteringFilterId }
			::= { msanFilteringAttachedFilterTable 1 }

		
		MsanFilteringAttachedFilterEntry ::=
			SEQUENCE { 
				msanFilteringAttachedFilterDirect
					INTEGER,
				msanFilteringAttachedFilterRowStatus
					RowStatus
			 }

		-- 1.3.6.1.4.1.1332.1.1.5.3.101.6.1.1
		msanFilteringAttachedFilterDirect OBJECT-TYPE
			SYNTAX INTEGER
				{
				in(1),
				out(2)
				}
			MAX-ACCESS read-write
			STATUS deprecated
			DESCRIPTION
				"Point of attaching a filter."
			::= { msanFilteringAttachedFilterEntry 1 }

		
		-- 1.3.6.1.4.1.1332.1.1.5.3.101.6.1.2
		msanFilteringAttachedFilterRowStatus OBJECT-TYPE
			SYNTAX RowStatus
			MAX-ACCESS read-create
			STATUS deprecated
			DESCRIPTION
				"SNMP row status.
				
				Supported values:
				active(1) - valid entry;
				createAndGo(4) - used to create a new entry;
				destroy(6) - removes the entry."
			::= { msanFilteringAttachedFilterEntry 2 }

		
		-- 1.3.6.1.4.1.1332.1.1.5.3.102
		msanBridge OBJECT IDENTIFIER ::= { msanAdditionalConf 102 }

		
		-- 1.3.6.1.4.1.1332.1.1.5.3.102.1
		msanBridgeGlobal OBJECT IDENTIFIER ::= { msanBridge 1 }

		
		-- 1.3.6.1.4.1.1332.1.1.5.3.102.1.1
		msanBridgeMode OBJECT-TYPE
			SYNTAX INTEGER
				{
				bridge(1),
				ccx(2)
				}
			MAX-ACCESS read-write
			STATUS deprecated
			DESCRIPTION
				"A bridge operating mode.
				bridge(1)
				ccx(2)
				"
			::= { msanBridgeGlobal 1 }

		
		-- 1.3.6.1.4.1.1332.1.1.5.3.102.1.2
		msanBridgeMacTableSize OBJECT-TYPE
			SYNTAX INTEGER (64..4095)
			MAX-ACCESS read-write
			STATUS deprecated
			DESCRIPTION
				"The maximum MAC table size"
			::= { msanBridgeGlobal 2 }

		
		-- 1.3.6.1.4.1.1332.1.1.5.3.102.1.3
		msanBridgeRedAdminMode OBJECT-TYPE
			SYNTAX INTEGER
				{
				enable(1),
				disable(2)
				}
			MAX-ACCESS read-write
			STATUS deprecated
			DESCRIPTION
				"Enable or disable Random Early Discard functionality."
			::= { msanBridgeGlobal 3 }

		
		-- 1.3.6.1.4.1.1332.1.1.5.3.102.2
		msanBridgeCCXTable OBJECT-TYPE
			SYNTAX SEQUENCE OF MsanBridgeCCXEntry
			MAX-ACCESS not-accessible
			STATUS deprecated
			DESCRIPTION
				"The table contents the information about all CCX pairs."
			::= { msanBridge 2 }

		
		-- 1.3.6.1.4.1.1332.1.1.5.3.102.2.1
		msanBridgeCCXEntry OBJECT-TYPE
			SYNTAX MsanBridgeCCXEntry
			MAX-ACCESS not-accessible
			STATUS deprecated
			DESCRIPTION
				"Description."
			INDEX { msanBridgeCCXInterface1, msanBridgeCCXInterface2 }
			::= { msanBridgeCCXTable 1 }

		
		MsanBridgeCCXEntry ::=
			SEQUENCE { 
				msanBridgeCCXInterface1
					InterfaceIndex,
				msanBridgeCCXInterface2
					InterfaceIndex,
				msanBridgeCCXRowStatus
					RowStatus
			 }

		-- 1.3.6.1.4.1.1332.1.1.5.3.102.2.1.1
		msanBridgeCCXInterface1 OBJECT-TYPE
			SYNTAX InterfaceIndex
			MAX-ACCESS read-create
			STATUS deprecated
			DESCRIPTION
				"The first interface to make cross-connection exchange"
			::= { msanBridgeCCXEntry 1 }

		
		-- 1.3.6.1.4.1.1332.1.1.5.3.102.2.1.2
		msanBridgeCCXInterface2 OBJECT-TYPE
			SYNTAX InterfaceIndex
			MAX-ACCESS read-create
			STATUS deprecated
			DESCRIPTION
				"The second interface to make cross-connection exchange"
			::= { msanBridgeCCXEntry 2 }

		
		-- 1.3.6.1.4.1.1332.1.1.5.3.102.2.1.3
		msanBridgeCCXRowStatus OBJECT-TYPE
			SYNTAX RowStatus
			MAX-ACCESS read-create
			STATUS deprecated
			DESCRIPTION
				"The row status object controls the creation/deletion of rows in this table. Its semantics are the same as those for the RowStatus textual convention specified for SNMPv2.
				Setting this object to createAndGo(4) creates a row in this table.
				Setting this object to destroy(6) will remove this entry.
				Read values: active(1).
				Other values are currently not supported."
			::= { msanBridgeCCXEntry 3 }

		
		-- 1.3.6.1.4.1.1332.1.1.5.3.103
		msanIPSG OBJECT IDENTIFIER ::= { msanAdditionalConf 103 }

		
		-- 1.3.6.1.4.1.1332.1.1.5.3.103.1
		msanIPSGGlobal OBJECT IDENTIFIER ::= { msanIPSG 1 }

		
		-- 1.3.6.1.4.1.1332.1.1.5.3.103.1.1
		msanIPSGAdminMode OBJECT-TYPE
			SYNTAX INTEGER
				{
				enable(1),
				disable(2)
				}
			MAX-ACCESS read-write
			STATUS current
			DESCRIPTION
				"Enable/disable IPv4 source guard for all interfaces"
			::= { msanIPSGGlobal 1 }

		
		-- 1.3.6.1.4.1.1332.1.1.5.3.103.1.2
		msanIPSGStoreAdminMode OBJECT-TYPE
			SYNTAX INTEGER
				{
				enable(1),
				disable(2)
				}
			MAX-ACCESS read-write
			STATUS current
			DESCRIPTION
				"Enable/disable storing of the IP-MAC binds to the interoperation table."
			::= { msanIPSGGlobal 2 }

		
		-- 1.3.6.1.4.1.1332.1.1.5.3.103.1.3
		msanIPSGIpv6AdminMode OBJECT-TYPE
			SYNTAX INTEGER
				{
				enable(1),
				disable(2)
				}
			MAX-ACCESS read-write
			STATUS current
			DESCRIPTION
				"Enable/disable IPv6 source guard for all interfaces"
			::= { msanIPSGGlobal 3 }

		
		-- 1.3.6.1.4.1.1332.1.1.5.3.103.1.4
		msanIPSGClearDynamicBinds OBJECT-TYPE
			SYNTAX INTEGER
				{
				disable(1),
				clear-all(2),
				clear-dhcpv4(3),
				clear-dhcpv6(4),
				clear-nd(5)
				}
			MAX-ACCESS read-write
			STATUS current
			DESCRIPTION
				"Clear IPSG snooping tables for all ports."
			::= { msanIPSGGlobal 4 }

		
		-- 1.3.6.1.4.1.1332.1.1.5.3.103.2
		msanIPSGIntfTable OBJECT-TYPE
			SYNTAX SEQUENCE OF MsanIPSGIntfEntry
			MAX-ACCESS not-accessible
			STATUS current
			DESCRIPTION
				"Description."
			::= { msanIPSG 2 }

		
		-- 1.3.6.1.4.1.1332.1.1.5.3.103.2.1
		msanIPSGIntfEntry OBJECT-TYPE
			SYNTAX MsanIPSGIntfEntry
			MAX-ACCESS not-accessible
			STATUS current
			DESCRIPTION
				"Description."
			INDEX { ifIndex }
			::= { msanIPSGIntfTable 1 }

		
		MsanIPSGIntfEntry ::=
			SEQUENCE { 
				msanIPSGIntfAdminMode
					INTEGER,
				msanIPSGIntfBindsLimit
					Integer32,
				msanIPSGIntfFilteringMode
					INTEGER,
				msanIPSGIntfIpv6AdminMode
					INTEGER,
				msanIPSGIntfBindsLimitDhcpv6
					Integer32,
				msanIPSGIntfBindsLimitND
					Integer32,
				msanIPSGIntfClearDynamicBinds
					INTEGER
			 }

		-- 1.3.6.1.4.1.1332.1.1.5.3.103.2.1.1
		msanIPSGIntfAdminMode OBJECT-TYPE
			SYNTAX INTEGER
				{
				enable(1),
				disable(2)
				}
			MAX-ACCESS read-write
			STATUS current
			DESCRIPTION
				"Enable/disable IP Source Guard for the selected interface."
			DEFVAL { disable }
			::= { msanIPSGIntfEntry 1 }

		
		-- 1.3.6.1.4.1.1332.1.1.5.3.103.2.1.2
		msanIPSGIntfBindsLimit OBJECT-TYPE
			SYNTAX Integer32 (0..15)
			MAX-ACCESS read-write
			STATUS current
			DESCRIPTION
				"IPSG binding limit for DHCPv4 snooping table per interface.
				Value 0 defines there is no limit."
			DEFVAL { 4 }
			::= { msanIPSGIntfEntry 2 }

		
		-- 1.3.6.1.4.1.1332.1.1.5.3.103.2.1.3
		msanIPSGIntfFilteringMode OBJECT-TYPE
			SYNTAX INTEGER
				{
				iponly(1),
				ipmac(2)
				}
			MAX-ACCESS read-write
			STATUS current
			DESCRIPTION
				"Sets the traffic filtering type. Traffic can be filtered either by IP or by both IP and MAC address."
			DEFVAL { iponly }
			::= { msanIPSGIntfEntry 3 }

		
		-- 1.3.6.1.4.1.1332.1.1.5.3.103.2.1.4
		msanIPSGIntfIpv6AdminMode OBJECT-TYPE
			SYNTAX INTEGER
				{
				enable(1),
				disable(2)
				}
			MAX-ACCESS read-write
			STATUS current
			DESCRIPTION
				"Enable/disable IPv6 Source Guard for the selected interface."
			DEFVAL { disable }
			::= { msanIPSGIntfEntry 4 }

		
		-- 1.3.6.1.4.1.1332.1.1.5.3.103.2.1.5
		msanIPSGIntfBindsLimitDhcpv6 OBJECT-TYPE
			SYNTAX Integer32 (0..15)
			MAX-ACCESS read-write
			STATUS current
			DESCRIPTION
				"IPSG binding limit for DHCPv6 (IPv6 DHCP)snooping table per interface.
				Value 0 defines there is no limit."
			DEFVAL { 4 }
			::= { msanIPSGIntfEntry 5 }

		
		-- 1.3.6.1.4.1.1332.1.1.5.3.103.2.1.6
		msanIPSGIntfBindsLimitND OBJECT-TYPE
			SYNTAX Integer32 (0..15)
			MAX-ACCESS read-write
			STATUS current
			DESCRIPTION
				"IPSG binding limit for ND (IPv6 Neighbor Discovery) snooping table per interface
				Value 0 defines there is no limit."
			DEFVAL { 4 }
			::= { msanIPSGIntfEntry 6 }

		
		-- 1.3.6.1.4.1.1332.1.1.5.3.103.2.1.7
		msanIPSGIntfClearDynamicBinds OBJECT-TYPE
			SYNTAX INTEGER
				{
				disable(1),
				clear-all(2),
				clear-dhcpv4(3),
				clear-dhcpv6(4),
				clear-nd(5)
				}
			MAX-ACCESS read-write
			STATUS current
			DESCRIPTION
				"Clear IPSG snooping tables per interface"
			::= { msanIPSGIntfEntry 7 }

		
		-- 1.3.6.1.4.1.1332.1.1.5.3.103.3
		msanIPSGBindingsTable OBJECT-TYPE
			SYNTAX SEQUENCE OF MsanIPSGBindingsEntry
			MAX-ACCESS not-accessible
			STATUS deprecated
			DESCRIPTION
				"DThe table for storing IP source binding"
			::= { msanIPSG 3 }

		
		-- 1.3.6.1.4.1.1332.1.1.5.3.103.3.1
		msanIPSGBindingsEntry OBJECT-TYPE
			SYNTAX MsanIPSGBindingsEntry
			MAX-ACCESS not-accessible
			STATUS deprecated
			DESCRIPTION
				"Description."
			INDEX { ifIndex, msanIPSGBindVlan, msanIPSGBindMac }
			::= { msanIPSGBindingsTable 1 }

		
		MsanIPSGBindingsEntry ::=
			SEQUENCE { 
				msanIPSGBindIp
					IpAddress,
				msanIPSGBindVlan
					VlanIndex,
				msanIPSGBindMac
					MacAddress,
				msanIPSGBindLeaseRemainingTime
					TimeTicks,
				msanIPSGBindType
					INTEGER,
				msanIPSGBindMatchedFrames
					Counter32,
				msanIPSGBindRowStatus
					RowStatus
			 }

		-- 1.3.6.1.4.1.1332.1.1.5.3.103.3.1.1
		msanIPSGBindIp OBJECT-TYPE
			SYNTAX IpAddress
			MAX-ACCESS read-write
			STATUS deprecated
			DESCRIPTION
				"Allowed IP address"
			::= { msanIPSGBindingsEntry 1 }

		
		-- 1.3.6.1.4.1.1332.1.1.5.3.103.3.1.2
		msanIPSGBindVlan OBJECT-TYPE
			SYNTAX VlanIndex
			MAX-ACCESS read-only
			STATUS deprecated
			DESCRIPTION
				"Allowed VLAN number"
			::= { msanIPSGBindingsEntry 2 }

		
		-- 1.3.6.1.4.1.1332.1.1.5.3.103.3.1.3
		msanIPSGBindMac OBJECT-TYPE
			SYNTAX MacAddress
			MAX-ACCESS read-only
			STATUS deprecated
			DESCRIPTION
				"Allowed MAC address"
			::= { msanIPSGBindingsEntry 3 }

		
		-- 1.3.6.1.4.1.1332.1.1.5.3.103.3.1.4
		msanIPSGBindLeaseRemainingTime OBJECT-TYPE
			SYNTAX TimeTicks
			MAX-ACCESS read-only
			STATUS deprecated
			DESCRIPTION
				"The period for which the DHCP lease is valid. 
				It is displayed in days, hours, minutes, and seconds.
				
				For static IPSG bindings this value is set to 0 (infinitive)."
			::= { msanIPSGBindingsEntry 4 }

		
		-- 1.3.6.1.4.1.1332.1.1.5.3.103.3.1.5
		msanIPSGBindType OBJECT-TYPE
			SYNTAX INTEGER
				{
				static(1),
				dynamic(2)
				}
			MAX-ACCESS read-only
			STATUS deprecated
			DESCRIPTION
				"Type of IPSG binding."
			::= { msanIPSGBindingsEntry 5 }

		
		-- 1.3.6.1.4.1.1332.1.1.5.3.103.3.1.6
		msanIPSGBindMatchedFrames OBJECT-TYPE
			SYNTAX Counter32
			MAX-ACCESS read-only
			STATUS deprecated
			DESCRIPTION
				"Number of matched frames for selected IPSG binding."
			::= { msanIPSGBindingsEntry 6 }

		
		-- 1.3.6.1.4.1.1332.1.1.5.3.103.3.1.7
		msanIPSGBindRowStatus OBJECT-TYPE
			SYNTAX RowStatus
			MAX-ACCESS read-create
			STATUS deprecated
			DESCRIPTION
				"The row status object controls the creation/deletion of rows in this table.
				Its semantics are the same as those for the RowStatus textual convention specified for SNMPv2.
				For row creation use createAndWait(5).
				For row activation use active(1).
				For row deletion use destroy(6).
				
				Other values are currently not supported.
				
				For row activation next terms must be accomplished:
				- msanIPSGBindIp must be defined "
			::= { msanIPSGBindingsEntry 7 }

		
		-- 1.3.6.1.4.1.1332.1.1.5.3.103.4
		msanIPSGIpv4PortStaticBindTable OBJECT-TYPE
			SYNTAX SEQUENCE OF MsanIPSGIpv4PortStaticBindEntry
			MAX-ACCESS not-accessible
			STATUS current
			DESCRIPTION
				"Description."
			::= { msanIPSG 4 }

		
		-- 1.3.6.1.4.1.1332.1.1.5.3.103.4.1
		msanIPSGIpv4PortStaticBindEntry OBJECT-TYPE
			SYNTAX MsanIPSGIpv4PortStaticBindEntry
			MAX-ACCESS not-accessible
			STATUS current
			DESCRIPTION
				"Description."
			INDEX { ifIndex, msanIPSGIpv4PortStaticBindMacAddress, msanIPSGIpv4PortStaticBindVlanId, msanIPSGIpv4PortStaticBindIpAddress }
			::= { msanIPSGIpv4PortStaticBindTable 1 }

		
		MsanIPSGIpv4PortStaticBindEntry ::=
			SEQUENCE { 
				msanIPSGIpv4PortStaticBindMacAddress
					MacAddress,
				msanIPSGIpv4PortStaticBindVlanId
					VlanIndex,
				msanIPSGIpv4PortStaticBindIpAddress
					InetAddressIPv4,
				msanIPSGIpv4PortStaticBindMatchedFrames
					Counter32,
				msanIPSGIpv4PortStaticBindRowStatus
					RowStatus
			 }

		-- 1.3.6.1.4.1.1332.1.1.5.3.103.4.1.1
		msanIPSGIpv4PortStaticBindMacAddress OBJECT-TYPE
			SYNTAX MacAddress
			MAX-ACCESS not-accessible
			STATUS current
			DESCRIPTION
				"Allowed MAC address"
			::= { msanIPSGIpv4PortStaticBindEntry 1 }

		
		-- 1.3.6.1.4.1.1332.1.1.5.3.103.4.1.2
		msanIPSGIpv4PortStaticBindVlanId OBJECT-TYPE
			SYNTAX VlanIndex
			MAX-ACCESS not-accessible
			STATUS current
			DESCRIPTION
				"Allowed VLAN number"
			::= { msanIPSGIpv4PortStaticBindEntry 2 }

		
		-- 1.3.6.1.4.1.1332.1.1.5.3.103.4.1.3
		msanIPSGIpv4PortStaticBindIpAddress OBJECT-TYPE
			SYNTAX InetAddressIPv4
			MAX-ACCESS not-accessible
			STATUS current
			DESCRIPTION
				"Allowed IPv4 address"
			::= { msanIPSGIpv4PortStaticBindEntry 3 }

		
		-- 1.3.6.1.4.1.1332.1.1.5.3.103.4.1.4
		msanIPSGIpv4PortStaticBindMatchedFrames OBJECT-TYPE
			SYNTAX Counter32
			MAX-ACCESS read-only
			STATUS current
			DESCRIPTION
				"Number of matched frames for selected IPSG binding."
			::= { msanIPSGIpv4PortStaticBindEntry 4 }

		
		-- 1.3.6.1.4.1.1332.1.1.5.3.103.4.1.5
		msanIPSGIpv4PortStaticBindRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndGo(4).
				For row activation use active(1).
				For row deletion use destroy(6).
				
				Other values are currently not supported."
			::= { msanIPSGIpv4PortStaticBindEntry 5 }

		
		-- 1.3.6.1.4.1.1332.1.1.5.3.103.5
		msanIPSGIpv6PortStaticBindTable OBJECT-TYPE
			SYNTAX SEQUENCE OF MsanIPSGIpv6PortStaticBindEntry
			MAX-ACCESS not-accessible
			STATUS current
			DESCRIPTION
				"Description."
			::= { msanIPSG 5 }

		
		-- 1.3.6.1.4.1.1332.1.1.5.3.103.5.1
		msanIPSGIpv6PortStaticBindEntry OBJECT-TYPE
			SYNTAX MsanIPSGIpv6PortStaticBindEntry
			MAX-ACCESS not-accessible
			STATUS current
			DESCRIPTION
				"Description."
			INDEX { ifIndex, msanIPSGIpv6PortStaticBindMacAddress, msanIPSGIpv6PortStaticBindVlanId, msanIPSGIpv6PortStaticBindIpAddress }
			::= { msanIPSGIpv6PortStaticBindTable 1 }

		
		MsanIPSGIpv6PortStaticBindEntry ::=
			SEQUENCE { 
				msanIPSGIpv6PortStaticBindMacAddress
					MacAddress,
				msanIPSGIpv6PortStaticBindVlanId
					VlanIndex,
				msanIPSGIpv6PortStaticBindIpAddress
					InetAddressIPv6,
				msanIPSGIpv6PortStaticBindMatchedFrames
					Counter32,
				msanIPSGIpv6PortStaticBindRowStatus
					RowStatus
			 }

		-- 1.3.6.1.4.1.1332.1.1.5.3.103.5.1.1
		msanIPSGIpv6PortStaticBindMacAddress OBJECT-TYPE
			SYNTAX MacAddress
			MAX-ACCESS not-accessible
			STATUS current
			DESCRIPTION
				"Allowed MAC address"
			::= { msanIPSGIpv6PortStaticBindEntry 1 }

		
		-- 1.3.6.1.4.1.1332.1.1.5.3.103.5.1.2
		msanIPSGIpv6PortStaticBindVlanId OBJECT-TYPE
			SYNTAX VlanIndex
			MAX-ACCESS not-accessible
			STATUS current
			DESCRIPTION
				"Allowed VLAN number"
			::= { msanIPSGIpv6PortStaticBindEntry 2 }

		
		-- 1.3.6.1.4.1.1332.1.1.5.3.103.5.1.3
		msanIPSGIpv6PortStaticBindIpAddress OBJECT-TYPE
			SYNTAX InetAddressIPv6
			MAX-ACCESS not-accessible
			STATUS current
			DESCRIPTION
				"Allowed IPv6 address"
			::= { msanIPSGIpv6PortStaticBindEntry 3 }

		
		-- 1.3.6.1.4.1.1332.1.1.5.3.103.5.1.4
		msanIPSGIpv6PortStaticBindMatchedFrames OBJECT-TYPE
			SYNTAX Counter32
			MAX-ACCESS read-only
			STATUS current
			DESCRIPTION
				"Number of matched frames for selected IPSG binding."
			::= { msanIPSGIpv6PortStaticBindEntry 4 }

		
		-- 1.3.6.1.4.1.1332.1.1.5.3.103.5.1.5
		msanIPSGIpv6PortStaticBindRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndGo(4).
				For row activation use active(1).
				For row deletion use destroy(6).
				
				Other values are currently not supported."
			::= { msanIPSGIpv6PortStaticBindEntry 5 }

		
		-- 1.3.6.1.4.1.1332.1.1.5.3.103.6
		msanIPSGPortBindCurrentTable OBJECT-TYPE
			SYNTAX SEQUENCE OF MsanIPSGPortBindCurrentEntry
			MAX-ACCESS not-accessible
			STATUS current
			DESCRIPTION
				"DThe table for storing IP source binding"
			::= { msanIPSG 6 }

		
		-- 1.3.6.1.4.1.1332.1.1.5.3.103.6.1
		msanIPSGPortBindCurrentEntry OBJECT-TYPE
			SYNTAX MsanIPSGPortBindCurrentEntry
			MAX-ACCESS not-accessible
			STATUS current
			DESCRIPTION
				"Description."
			INDEX { msanIPSGPortBindCurrentId }
			::= { msanIPSGPortBindCurrentTable 1 }

		
		MsanIPSGPortBindCurrentEntry ::=
			SEQUENCE { 
				msanIPSGPortBindCurrentId
					Integer32,
				msanIPSGPortBindCurrentIfIndex
					InterfaceIndex,
				msanIPSGPortBindCurrentMacAddress
					MacAddress,
				msanIPSGPortBindCurrentVlanId
					VlanIndex,
				msanIPSGPortBindCurrentIpAddressType
					InetAddressType,
				msanIPSGPortBindCurrentIpAddress
					InetAddress,
				msanIPSGPortBindCurrentLeaseRemainingTime
					TimeTicks,
				msanIPSGPortBindCurrentType
					INTEGER,
				msanIPSGPortBindCurrentMatchedFrames
					Counter32
			 }

		-- 1.3.6.1.4.1.1332.1.1.5.3.103.6.1.1
		msanIPSGPortBindCurrentId OBJECT-TYPE
			SYNTAX Integer32
			MAX-ACCESS not-accessible
			STATUS current
			DESCRIPTION
				"Table index."
			::= { msanIPSGPortBindCurrentEntry 1 }

		
		-- 1.3.6.1.4.1.1332.1.1.5.3.103.6.1.2
		msanIPSGPortBindCurrentIfIndex OBJECT-TYPE
			SYNTAX InterfaceIndex
			MAX-ACCESS read-only
			STATUS current
			DESCRIPTION
				"Port index (ifIndex value)."
			::= { msanIPSGPortBindCurrentEntry 2 }

		
		-- 1.3.6.1.4.1.1332.1.1.5.3.103.6.1.3
		msanIPSGPortBindCurrentMacAddress OBJECT-TYPE
			SYNTAX MacAddress
			MAX-ACCESS read-only
			STATUS current
			DESCRIPTION
				"Allowed MAC address"
			::= { msanIPSGPortBindCurrentEntry 3 }

		
		-- 1.3.6.1.4.1.1332.1.1.5.3.103.6.1.4
		msanIPSGPortBindCurrentVlanId OBJECT-TYPE
			SYNTAX VlanIndex
			MAX-ACCESS read-only
			STATUS current
			DESCRIPTION
				"Allowed VLAN number"
			::= { msanIPSGPortBindCurrentEntry 4 }

		
		-- 1.3.6.1.4.1.1332.1.1.5.3.103.6.1.5
		msanIPSGPortBindCurrentIpAddressType OBJECT-TYPE
			SYNTAX InetAddressType
			MAX-ACCESS read-only
			STATUS current
			DESCRIPTION
				"Specifies the type of ip address: ipv4[1], ipv6[2]."
			::= { msanIPSGPortBindCurrentEntry 5 }

		
		-- 1.3.6.1.4.1.1332.1.1.5.3.103.6.1.6
		msanIPSGPortBindCurrentIpAddress OBJECT-TYPE
			SYNTAX InetAddress
			MAX-ACCESS read-only
			STATUS current
			DESCRIPTION
				"Allowed IP address"
			::= { msanIPSGPortBindCurrentEntry 6 }

		
		-- 1.3.6.1.4.1.1332.1.1.5.3.103.6.1.7
		msanIPSGPortBindCurrentLeaseRemainingTime OBJECT-TYPE
			SYNTAX TimeTicks
			MAX-ACCESS read-only
			STATUS current
			DESCRIPTION
				"The period for which the DHCP lease is valid. 
				It is displayed in days, hours, minutes, and seconds.
				
				For static IPSG bindings this value is set to 0 (infinitive)."
			::= { msanIPSGPortBindCurrentEntry 7 }

		
		-- 1.3.6.1.4.1.1332.1.1.5.3.103.6.1.8
		msanIPSGPortBindCurrentType OBJECT-TYPE
			SYNTAX INTEGER
				{
				static(1),
				dynamic-dhcpv4(2),
				dynamic-dhcpv6(3),
				dynamic-nd(4)
				}
			MAX-ACCESS read-only
			STATUS current
			DESCRIPTION
				"Type of IPSG binding."
			::= { msanIPSGPortBindCurrentEntry 8 }

		
		-- 1.3.6.1.4.1.1332.1.1.5.3.103.6.1.9
		msanIPSGPortBindCurrentMatchedFrames OBJECT-TYPE
			SYNTAX Counter32
			MAX-ACCESS read-only
			STATUS current
			DESCRIPTION
				"Number of matched frames for selected IPSG binding."
			::= { msanIPSGPortBindCurrentEntry 9 }

		
		-- 1.3.6.1.4.1.1332.1.1.5.3.105
		msanVlan OBJECT IDENTIFIER ::= { msanAdditionalConf 105 }

		
		-- 1.3.6.1.4.1.1332.1.1.5.3.105.1
		msanVlanGlobal OBJECT IDENTIFIER ::= { msanVlan 1 }

		
		-- 1.3.6.1.4.1.1332.1.1.5.3.105.1.1
		msanDVlanTagMode OBJECT-TYPE
			SYNTAX INTEGER
				{
				enable(1),
				disable(2)
				}
			MAX-ACCESS read-write
			STATUS deprecated
			DESCRIPTION
				"Controls the Double Vlan Tag mode on the system."
			::= { msanVlanGlobal 1 }

		
		-- 1.3.6.1.4.1.1332.1.1.5.3.105.1.2
		msanVlanRemarkAdminState OBJECT-TYPE
			SYNTAX INTEGER
				{
				enable(1),
				disable(2)
				}
			MAX-ACCESS read-write
			STATUS deprecated
			DESCRIPTION
				"Global VLAN Remarking administrative state."
			DEFVAL { disable }
			::= { msanVlanGlobal 2 }

		
		-- 1.3.6.1.4.1.1332.1.1.5.3.105.1.3
		msanInternalVlanId OBJECT-TYPE
			SYNTAX Integer32
			MAX-ACCESS read-write
			STATUS current
			DESCRIPTION
				"Internal Vlan ID."
			::= { msanVlanGlobal 3 }

		
		-- 1.3.6.1.4.1.1332.1.1.5.3.105.2
		msanPortVlanTable OBJECT-TYPE
			SYNTAX SEQUENCE OF MsanPortVlanEntry
			MAX-ACCESS not-accessible
			STATUS deprecated
			DESCRIPTION
				"Vlan config parameters per port."
			::= { msanVlan 2 }

		
		-- 1.3.6.1.4.1.1332.1.1.5.3.105.2.1
		msanPortVlanEntry OBJECT-TYPE
			SYNTAX MsanPortVlanEntry
			MAX-ACCESS not-accessible
			STATUS deprecated
			DESCRIPTION
				"Description."
			INDEX { ifIndex }
			::= { msanPortVlanTable 1 }

		
		MsanPortVlanEntry ::=
			SEQUENCE { 
				msanPortVlanMode
					INTEGER,
				msanPortVlanStackPriority
					INTEGER,
				msanPortVlanStackVlanId
					Integer32
			 }

		-- 1.3.6.1.4.1.1332.1.1.5.3.105.2.1.1
		msanPortVlanMode OBJECT-TYPE
			SYNTAX INTEGER
				{
				access(0),
				trunk(1),
				dot1qtunnel(2),
				vlanStacking(3)
				}
			MAX-ACCESS read-write
			STATUS deprecated
			DESCRIPTION
				"Interface vlan mode."
			::= { msanPortVlanEntry 1 }

		
		-- 1.3.6.1.4.1.1332.1.1.5.3.105.2.1.2
		msanPortVlanStackPriority OBJECT-TYPE
			SYNTAX INTEGER
				{
				mapPriorityFromOuterTag(0),
				priority1(1),
				priority2(2),
				priority3(3),
				priority4(4),
				priority5(5),
				priority6(6),
				priority7(7)
				}
			MAX-ACCESS read-write
			STATUS deprecated
			DESCRIPTION
				"Priority of inner tag when interface is in vlanStacking mode (msanPortVlanMode=vlanStacking)."
			::= { msanPortVlanEntry 2 }

		
		-- 1.3.6.1.4.1.1332.1.1.5.3.105.2.1.3
		msanPortVlanStackVlanId OBJECT-TYPE
			SYNTAX Integer32
			MAX-ACCESS read-write
			STATUS deprecated
			DESCRIPTION
				"Vlan ID of inner tag when interface is in vlanStacking mode (msanPortVlanMode=vlanStacking).
				"
			::= { msanPortVlanEntry 3 }

		
		-- 1.3.6.1.4.1.1332.1.1.5.3.105.3
		msanPortDVlanMapTable OBJECT-TYPE
			SYNTAX SEQUENCE OF MsanPortDVlanMapEntry
			MAX-ACCESS not-accessible
			STATUS deprecated
			DESCRIPTION
				"Ingress mapping of inner VID to outer VID different from default
				(PVID) mapping.
				"
			::= { msanVlan 3 }

		
		-- 1.3.6.1.4.1.1332.1.1.5.3.105.3.1
		msanPortDVlanMapEntry OBJECT-TYPE
			SYNTAX MsanPortDVlanMapEntry
			MAX-ACCESS not-accessible
			STATUS deprecated
			DESCRIPTION
				"Description."
			INDEX { ifIndex, msanPortDVlanMapInTagVlanId }
			::= { msanPortDVlanMapTable 1 }

		
		MsanPortDVlanMapEntry ::=
			SEQUENCE { 
				msanPortDVlanMapInTagVlanId
					Integer32,
				msanPortDVlanMapOutTagVlanId
					Integer32,
				msanPortDVlanMapRowStatus
					RowStatus
			 }

		-- 1.3.6.1.4.1.1332.1.1.5.3.105.3.1.1
		msanPortDVlanMapInTagVlanId OBJECT-TYPE
			SYNTAX Integer32
			MAX-ACCESS not-accessible
			STATUS deprecated
			DESCRIPTION
				"Inner tag VLAN ID. DVlan functionality is used when interface is in dot1qtunnel mode."
			::= { msanPortDVlanMapEntry 1 }

		
		-- 1.3.6.1.4.1.1332.1.1.5.3.105.3.1.2
		msanPortDVlanMapOutTagVlanId OBJECT-TYPE
			SYNTAX Integer32
			MAX-ACCESS read-create
			STATUS deprecated
			DESCRIPTION
				"Outer tag VLAN ID added for inner tag VLAN ID (msanPortDVlanMapInTagVlanId).
				DVlan functionality is used when interface is in dot1qtunnel mode.
				
				Value of -1 indicates that outer tag is not added for selected inner tag VLAN ID."
			::= { msanPortDVlanMapEntry 2 }

		
		-- 1.3.6.1.4.1.1332.1.1.5.3.105.3.1.3
		msanPortDVlanMapRowStatus OBJECT-TYPE
			SYNTAX RowStatus
			MAX-ACCESS read-create
			STATUS deprecated
			DESCRIPTION
				"The row status object controls the creation/deletion of rows in this table. 
				For row creation use createAndWait(5) [createAndGo(4) is not supported].
				Setting this object to active(1) will activate this entry.
				Setting this object to destroy(6) will remove this entry.
				
				"
			::= { msanPortDVlanMapEntry 3 }

		
		-- 1.3.6.1.4.1.1332.1.1.5.3.105.4
		msanPortVlanRemarkTable OBJECT-TYPE
			SYNTAX SEQUENCE OF MsanPortVlanRemarkEntry
			MAX-ACCESS not-accessible
			STATUS current
			DESCRIPTION
				"Vlan remarking table for ingress traffic (per port).
				
				Note: All defined Vlan remarking rules for ingress traffic  also add , automatically, 
				reverse Vlan remarking rule for egress traffic on same port."
			::= { msanVlan 4 }

		
		-- 1.3.6.1.4.1.1332.1.1.5.3.105.4.1
		msanPortVlanRemarkEntry OBJECT-TYPE
			SYNTAX MsanPortVlanRemarkEntry
			MAX-ACCESS not-accessible
			STATUS current
			DESCRIPTION
				"Description."
			INDEX { ifIndex, msanPortVlanRemarkSrcVlanId }
			::= { msanPortVlanRemarkTable 1 }

		
		MsanPortVlanRemarkEntry ::=
			SEQUENCE { 
				msanPortVlanRemarkSrcVlanId
					Integer32,
				msanPortVlanRemarkDstVlanId
					Integer32,
				msanPortVlanRemarkRowStatus
					RowStatus
			 }

		-- 1.3.6.1.4.1.1332.1.1.5.3.105.4.1.1
		msanPortVlanRemarkSrcVlanId OBJECT-TYPE
			SYNTAX Integer32 (1..4094)
			MAX-ACCESS read-write
			STATUS current
			DESCRIPTION
				"Ingress traffic Source VLAN ID which will be changed to Destination VLAN ID
				(msanPortVlanRemarkDstVlanId) by VLAN remarking rule."
			::= { msanPortVlanRemarkEntry 1 }

		
		-- 1.3.6.1.4.1.1332.1.1.5.3.105.4.1.2
		msanPortVlanRemarkDstVlanId OBJECT-TYPE
			SYNTAX Integer32 (1..4094)
			MAX-ACCESS read-write
			STATUS current
			DESCRIPTION
				"Destination VLAN ID to which will be changed Source VLAN ID of ingress traffic (msanPortVlanRemarkSrcVlanId) 
				by VLAN remarking rule."
			::= { msanPortVlanRemarkEntry 2 }

		
		-- 1.3.6.1.4.1.1332.1.1.5.3.105.4.1.3
		msanPortVlanRemarkRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndWait(5).
				For row activation use active(1).
				For row deletion use destroy(6).
				
				Other values are currently not supported.
				
				For row activation next terms must be accomplished:
				- msanPortVlanRemarkDstVlanId must be defined (default value not defined)
				
				Note: All defined Vlan remarking rules for ingress traffic  also add , automatically, 
				reverse Vlan remarking rule for egress traffic on same port.
				"
			::= { msanPortVlanRemarkEntry 3 }

		
		-- 1.3.6.1.4.1.1332.1.1.5.3.105.5
		msanPortDVlanTable OBJECT-TYPE
			SYNTAX SEQUENCE OF MsanPortDVlanEntry
			MAX-ACCESS not-accessible
			STATUS current
			DESCRIPTION
				"Description."
			::= { msanVlan 5 }

		
		-- 1.3.6.1.4.1.1332.1.1.5.3.105.5.1
		msanPortDVlanEntry OBJECT-TYPE
			SYNTAX MsanPortDVlanEntry
			MAX-ACCESS not-accessible
			STATUS current
			DESCRIPTION
				"Description."
			INDEX { ifIndex }
			::= { msanPortDVlanTable 1 }

		
		MsanPortDVlanEntry ::=
			SEQUENCE { 
				msanPortDVlanTagMode
					INTEGER,
				msanPortDVlanStackVlanId
					Integer32,
				msanPortDVlanStackPriority
					INTEGER
			 }

		-- 1.3.6.1.4.1.1332.1.1.5.3.105.5.1.1
		msanPortDVlanTagMode OBJECT-TYPE
			SYNTAX INTEGER
				{
				enable(1),
				disable(2)
				}
			MAX-ACCESS read-write
			STATUS current
			DESCRIPTION
				"Administrative state of 802.1Q tunneling (DVLAN) mode."
			DEFVAL { disable }
			::= { msanPortDVlanEntry 1 }

		
		-- 1.3.6.1.4.1.1332.1.1.5.3.105.5.1.2
		msanPortDVlanStackVlanId OBJECT-TYPE
			SYNTAX Integer32
			MAX-ACCESS read-write
			STATUS current
			DESCRIPTION
				"Vlan ID of inner tag when interface is in vlanStacking mode.
				
				Interface is in vlanStacking mode when msanPortDVlanTagMode=enable and 
				msanPortDVlanStackVlanId>=0.
				
				msanPortDVlanStackVlanId value of -1 indicates that vlanStacking mode is not activated."
			::= { msanPortDVlanEntry 2 }

		
		-- 1.3.6.1.4.1.1332.1.1.5.3.105.5.1.3
		msanPortDVlanStackPriority OBJECT-TYPE
			SYNTAX INTEGER
				{
				priority0(0),
				priority1(1),
				priority2(2),
				priority3(3),
				priority4(4),
				priority5(5),
				priority6(6),
				priority7(7)
				}
			MAX-ACCESS read-write
			STATUS current
			DESCRIPTION
				"Priority of inner tag when interface is in vlanStacking mode.
				
				Interface is in vlanStacking mode when msanPortDVlanTagMode=enable and 
				msanPortDVlanStackVlanId>=0."
			DEFVAL { priority0 }
			::= { msanPortDVlanEntry 3 }

		
		-- 1.3.6.1.4.1.1332.1.1.5.3.105.6
		msanPortDVlanConfigTable OBJECT-TYPE
			SYNTAX SEQUENCE OF MsanPortDVlanConfigEntry
			MAX-ACCESS not-accessible
			STATUS current
			DESCRIPTION
				"Ingress mapping of inner VID to outer VID different from default
				(PVID) mapping.
				"
			::= { msanVlan 6 }

		
		-- 1.3.6.1.4.1.1332.1.1.5.3.105.6.1
		msanPortDVlanConfigEntry OBJECT-TYPE
			SYNTAX MsanPortDVlanConfigEntry
			MAX-ACCESS not-accessible
			STATUS current
			DESCRIPTION
				"Description."
			INDEX { ifIndex, msanDVlanConfigInTagVlanId, msanDVlanConfigInTagPriority }
			::= { msanPortDVlanConfigTable 1 }

		
		MsanPortDVlanConfigEntry ::=
			SEQUENCE { 
				msanDVlanConfigInTagVlanId
					Integer32,
				msanDVlanConfigInTagPriority
					INTEGER,
				msanDVlanConfigOutTagVlanId
					Integer32,
				msanDVlanConfigOutTagPriority
					INTEGER,
				msanDVlanConfigRowStatus
					RowStatus
			 }

		-- 1.3.6.1.4.1.1332.1.1.5.3.105.6.1.1
		msanDVlanConfigInTagVlanId OBJECT-TYPE
			SYNTAX Integer32
			MAX-ACCESS not-accessible
			STATUS current
			DESCRIPTION
				"Inner tag VLAN ID. DVlan functionality is used when interface is in dot1qtunnel mode."
			::= { msanPortDVlanConfigEntry 1 }

		
		-- 1.3.6.1.4.1.1332.1.1.5.3.105.6.1.2
		msanDVlanConfigInTagPriority OBJECT-TYPE
			SYNTAX INTEGER
				{
				priority0(0),
				priority1(1),
				priority2(2),
				priority3(3),
				priority4(4),
				priority5(5),
				priority6(6),
				priority7(7),
				unspecified(8)
				}
			MAX-ACCESS not-accessible
			STATUS current
			DESCRIPTION
				"Priority of inner tag.
				Value unspecified(8) defines that rule line applies to all packets with 
				appropriate msanDVlanConfigInTagVlanId, except if packet match to other more specific rule."
			::= { msanPortDVlanConfigEntry 2 }

		
		-- 1.3.6.1.4.1.1332.1.1.5.3.105.6.1.3
		msanDVlanConfigOutTagVlanId OBJECT-TYPE
			SYNTAX Integer32
			MAX-ACCESS read-create
			STATUS current
			DESCRIPTION
				"Outer tag VLAN ID added for inner tag VLAN ID (msanPortDVlanConfigInTagVlanId).
				DVlan functionality is used when interface is in dot1qtunnel mode.
				
				Value of -1 indicates that outer tag is not added for selected inner tag VLAN ID."
			::= { msanPortDVlanConfigEntry 3 }

		
		-- 1.3.6.1.4.1.1332.1.1.5.3.105.6.1.4
		msanDVlanConfigOutTagPriority OBJECT-TYPE
			SYNTAX INTEGER
				{
				priority0(0),
				priority1(1),
				priority2(2),
				priority3(3),
				priority4(4),
				priority5(5),
				priority6(6),
				priority7(7),
				unspecified(8)
				}
			MAX-ACCESS read-write
			STATUS current
			DESCRIPTION
				"Priority of outer tag.
				Value unspecified(8) defines that msanDVlanMapInTagPriority is copied to outer tag."
			DEFVAL { priority0 }
			::= { msanPortDVlanConfigEntry 4 }

		
		-- 1.3.6.1.4.1.1332.1.1.5.3.105.6.1.5
		msanDVlanConfigRowStatus OBJECT-TYPE
			SYNTAX RowStatus
			MAX-ACCESS read-create
			STATUS current
			DESCRIPTION
				"The row status object controls the creation/deletion of rows in this table. 
				For row creation use createAndWait(5) [createAndGo(4) is not supported].
				Setting this object to active(1) will activate this entry.
				Setting this object to destroy(6) will remove this entry.
				
				"
			::= { msanPortDVlanConfigEntry 5 }

		
		-- 1.3.6.1.4.1.1332.1.1.5.3.105.7
		msanPortVlanRemarkAdminTable OBJECT-TYPE
			SYNTAX SEQUENCE OF MsanPortVlanRemarkAdminEntry
			MAX-ACCESS not-accessible
			STATUS current
			DESCRIPTION
				"Description."
			::= { msanVlan 7 }

		
		-- 1.3.6.1.4.1.1332.1.1.5.3.105.7.1
		msanPortVlanRemarkAdminEntry OBJECT-TYPE
			SYNTAX MsanPortVlanRemarkAdminEntry
			MAX-ACCESS not-accessible
			STATUS current
			DESCRIPTION
				"Description."
			INDEX { ifIndex }
			::= { msanPortVlanRemarkAdminTable 1 }

		
		MsanPortVlanRemarkAdminEntry ::=
			SEQUENCE { 
				msanPortVlanRemarkAdminMode
					INTEGER
			 }

		-- 1.3.6.1.4.1.1332.1.1.5.3.105.7.1.1
		msanPortVlanRemarkAdminMode OBJECT-TYPE
			SYNTAX INTEGER
				{
				enable(1),
				disable(2)
				}
			MAX-ACCESS read-write
			STATUS current
			DESCRIPTION
				"Administrative mode for VLAN Remarking"
			::= { msanPortVlanRemarkAdminEntry 1 }

		
		-- 1.3.6.1.4.1.1332.1.1.5.3.105.8
		msanUplinkPortVlanTable OBJECT-TYPE
			SYNTAX SEQUENCE OF MsanUplinkPortVlanEntry
			MAX-ACCESS not-accessible
			STATUS current
			DESCRIPTION
				"Description."
			::= { msanVlan 8 }

		
		-- 1.3.6.1.4.1.1332.1.1.5.3.105.8.1
		msanUplinkPortVlanEntry OBJECT-TYPE
			SYNTAX MsanUplinkPortVlanEntry
			MAX-ACCESS not-accessible
			STATUS current
			DESCRIPTION
				"Description."
			INDEX { ifIndex, msanUplinkPortVlanId }
			::= { msanUplinkPortVlanTable 1 }

		
		MsanUplinkPortVlanEntry ::=
			SEQUENCE { 
				msanUplinkPortVlanId
					Integer32,
				msanUplinkPortVlanMode
					INTEGER,
				msanUplinkPortVlanMulticastMode
					INTEGER,
				msanUplinkPortVlanRowStatus
					RowStatus
			 }

		-- 1.3.6.1.4.1.1332.1.1.5.3.105.8.1.1
		msanUplinkPortVlanId OBJECT-TYPE
			SYNTAX Integer32 (0..4094)
			MAX-ACCESS not-accessible
			STATUS current
			DESCRIPTION
				"Vlan ID."
			::= { msanUplinkPortVlanEntry 1 }

		
		-- 1.3.6.1.4.1.1332.1.1.5.3.105.8.1.2
		msanUplinkPortVlanMode OBJECT-TYPE
			SYNTAX INTEGER
				{
				tagged(1),
				native(2),
				unconfigured(3)
				}
			MAX-ACCESS read-write
			STATUS current
			DESCRIPTION
				"Vlan Mode."
			::= { msanUplinkPortVlanEntry 2 }

		
		-- 1.3.6.1.4.1.1332.1.1.5.3.105.8.1.3
		msanUplinkPortVlanMulticastMode OBJECT-TYPE
			SYNTAX INTEGER
				{
				discarding(1),
				flooding(2),
				snooping(3),
				snoopingAndFloodUnknown(4),
				undefined(5)
				}
			MAX-ACCESS read-write
			STATUS current
			DESCRIPTION
				"Vlan Multicast Mode.
				This parameter can't be set if msanUplinkPortVlanMulticastMode=unconfigured(3)"
			DEFVAL { undefined }
			::= { msanUplinkPortVlanEntry 3 }

		
		-- 1.3.6.1.4.1.1332.1.1.5.3.105.8.1.4
		msanUplinkPortVlanRowStatus OBJECT-TYPE
			SYNTAX RowStatus
			MAX-ACCESS read-write
			STATUS current
			DESCRIPTION
				"The row status object controls the creation/deletion of rows in this table. 
				For row creation use createAndWait(5) [createAndGo(4) is not supported].
				
				Setting object to active(1) will activate this entry ->
				INFO: parameter msanUplinkPortVlanMode must be defined.
				
				Setting object to destroy(6) will remove this entry.
				
				"
			::= { msanUplinkPortVlanEntry 4 }

		
		-- 1.3.6.1.4.1.1332.1.1.5.3.105.9
		msanVlanPortStatisticsTable OBJECT-TYPE
			SYNTAX SEQUENCE OF MsanVlanPortStatisticsEntry
			MAX-ACCESS not-accessible
			STATUS current
			DESCRIPTION
				"Description."
			::= { msanVlan 9 }

		
		-- 1.3.6.1.4.1.1332.1.1.5.3.105.9.1
		msanVlanPortStatisticsEntry OBJECT-TYPE
			SYNTAX MsanVlanPortStatisticsEntry
			MAX-ACCESS not-accessible
			STATUS current
			DESCRIPTION
				"Description."
			INDEX { ifIndex, msanVlanPortStatisticsVlanId }
			::= { msanVlanPortStatisticsTable 1 }

		
		MsanVlanPortStatisticsEntry ::=
			SEQUENCE { 
				msanVlanPortStatisticsVlanId
					Integer32,
				msanVlanPortStatisticsInFrames
					Counter64,
				msanVlanPortStatisticsOutFrames
					Counter64,
				msanVlanPortStatisticsInDiscarded
					Counter64,
				msanVlanPortStatisticsInOctets
					Counter64,
				msanVlanPortStatisticsOutOctets
					Counter64
			 }

		-- 1.3.6.1.4.1.1332.1.1.5.3.105.9.1.1
		msanVlanPortStatisticsVlanId OBJECT-TYPE
			SYNTAX Integer32 (0..4094)
			MAX-ACCESS not-accessible
			STATUS current
			DESCRIPTION
				"Description."
			::= { msanVlanPortStatisticsEntry 1 }

		
		-- 1.3.6.1.4.1.1332.1.1.5.3.105.9.1.2
		msanVlanPortStatisticsInFrames OBJECT-TYPE
			SYNTAX Counter64
			MAX-ACCESS read-only
			STATUS current
			DESCRIPTION
				"The number of valid frames received by this port from
				 its segment which were classified as belonging to this
				 VLAN."
			::= { msanVlanPortStatisticsEntry 2 }

		
		-- 1.3.6.1.4.1.1332.1.1.5.3.105.9.1.3
		msanVlanPortStatisticsOutFrames OBJECT-TYPE
			SYNTAX Counter64
			MAX-ACCESS read-only
			STATUS current
			DESCRIPTION
				"The number of valid frames transmitted by this port to
				 its segment from the local forwarding process for this
				 VLAN."
			::= { msanVlanPortStatisticsEntry 3 }

		
		-- 1.3.6.1.4.1.1332.1.1.5.3.105.9.1.4
		msanVlanPortStatisticsInDiscarded OBJECT-TYPE
			SYNTAX Counter64
			MAX-ACCESS read-only
			STATUS current
			DESCRIPTION
				"The number of valid frames received by this port from
				 its segment which were classified as belonging to this
				 VLAN which were discarded due to VLAN related reasons.
				 Specifically, the IEEE 802.1Q counters for Discard
				"
			::= { msanVlanPortStatisticsEntry 4 }

		
		-- 1.3.6.1.4.1.1332.1.1.5.3.105.9.1.5
		msanVlanPortStatisticsInOctets OBJECT-TYPE
			SYNTAX Counter64
			MAX-ACCESS read-only
			STATUS current
			DESCRIPTION
				"The number of valid frames octets received by this port from
				 its segment which were classified as belonging to this
				 VLAN."
			::= { msanVlanPortStatisticsEntry 5 }

		
		-- 1.3.6.1.4.1.1332.1.1.5.3.105.9.1.6
		msanVlanPortStatisticsOutOctets OBJECT-TYPE
			SYNTAX Counter64
			MAX-ACCESS read-only
			STATUS current
			DESCRIPTION
				"The number of valid frames octets transmitted by this port to
				 its segment from the local forwarding process for this
				 VLAN."
			::= { msanVlanPortStatisticsEntry 6 }

		
		-- 1.3.6.1.4.1.1332.1.1.5.3.106
		msanAtm OBJECT IDENTIFIER ::= { msanAdditionalConf 106 }

		
		-- 1.3.6.1.4.1.1332.1.1.5.3.106.1
		msanAtmGlobal OBJECT IDENTIFIER ::= { msanAtm 1 }

		
		-- 1.3.6.1.4.1.1332.1.1.5.3.106.2
		msanPortAtmPvcTable OBJECT-TYPE
			SYNTAX SEQUENCE OF MsanPortAtmPvcEntry
			MAX-ACCESS not-accessible
			STATUS current
			DESCRIPTION
				"Description."
			::= { msanAtm 2 }

		
		-- 1.3.6.1.4.1.1332.1.1.5.3.106.2.1
		msanPortAtmPvcEntry OBJECT-TYPE
			SYNTAX MsanPortAtmPvcEntry
			MAX-ACCESS not-accessible
			STATUS current
			DESCRIPTION
				"Description."
			INDEX { ifIndex, msanPortAtmPvcVpi, msanPortAtmPvcVci }
			::= { msanPortAtmPvcTable 1 }

		
		MsanPortAtmPvcEntry ::=
			SEQUENCE { 
				msanPortAtmPvcVpi
					Integer32,
				msanPortAtmPvcVci
					Integer32,
				msanPortAtmPvcPvid
					INTEGER,
				msanPortAtmPvcRowStatus
					RowStatus
			 }

		-- 1.3.6.1.4.1.1332.1.1.5.3.106.2.1.1
		msanPortAtmPvcVpi OBJECT-TYPE
			SYNTAX Integer32 (0..255)
			MAX-ACCESS not-accessible
			STATUS current
			DESCRIPTION
				"ATM-PVC(Permanent Virtual Circuits) VPI(Virtual Path Identifier) value."
			::= { msanPortAtmPvcEntry 1 }

		
		-- 1.3.6.1.4.1.1332.1.1.5.3.106.2.1.2
		msanPortAtmPvcVci OBJECT-TYPE
			SYNTAX Integer32 (32..255)
			MAX-ACCESS not-accessible
			STATUS current
			DESCRIPTION
				"ATM-PVC(Permanent Virtual Circuits) VCI(Virtual Channel Identifier) value."
			::= { msanPortAtmPvcEntry 2 }

		
		-- 1.3.6.1.4.1.1332.1.1.5.3.106.2.1.3
		msanPortAtmPvcPvid OBJECT-TYPE
			SYNTAX INTEGER (0..4094)
			MAX-ACCESS read-write
			STATUS current
			DESCRIPTION
				"The PVID, the VLAN ID assigned to untagged frames or
				Priority-Tagged frames received on this ATM-PVC(Permanent Virtual Circuits).
				
				Value 0 defines that PVID is not set."
			DEFVAL { '0'b }
			::= { msanPortAtmPvcEntry 3 }

		
		-- 1.3.6.1.4.1.1332.1.1.5.3.106.2.1.4
		msanPortAtmPvcRowStatus OBJECT-TYPE
			SYNTAX RowStatus
			MAX-ACCESS read-create
			STATUS current
			DESCRIPTION
				"The row status object controls the creation/deletion of rows in this table. 
				For row creation use createAndWait(5) [createAndGo(4) is not supported].
				Setting this object to active(1) will activate this entry.
				Setting this object to destroy(6) will remove this entry."
			::= { msanPortAtmPvcEntry 4 }

		
		-- 1.3.6.1.4.1.1332.1.1.5.3.107
		msanEnergyMeter OBJECT IDENTIFIER ::= { msanAdditionalConf 107 }

		
		-- 1.3.6.1.4.1.1332.1.1.5.3.107.1
		msanEnergyMeterGlobal OBJECT IDENTIFIER ::= { msanEnergyMeter 1 }

		
		-- 1.3.6.1.4.1.1332.1.1.5.3.107.1.1
		msanEnergyMeterIpAddress OBJECT-TYPE
			SYNTAX IpAddress
			MAX-ACCESS read-write
			STATUS current
			DESCRIPTION
				"Energy meter's Ip address."
			::= { msanEnergyMeterGlobal 1 }

		
		-- 1.3.6.1.4.1.1332.1.1.5.3.107.1.2
		msanEnergyMeterTcpPort OBJECT-TYPE
			SYNTAX Unsigned32 (0..65535)
			MAX-ACCESS read-write
			STATUS current
			DESCRIPTION
				"Energy meter's Tcp port."
			::= { msanEnergyMeterGlobal 2 }

		
		-- 1.3.6.1.4.1.1332.1.1.5.3.107.1.3
		msanEnergyMeterAddress OBJECT-TYPE
			SYNTAX Unsigned32
			MAX-ACCESS read-write
			STATUS current
			DESCRIPTION
				"Energy meter's address."
			::= { msanEnergyMeterGlobal 3 }

		
		-- 1.3.6.1.4.1.1332.1.1.5.3.107.1.4
		msanEnergyMeterPassword OBJECT-TYPE
			SYNTAX Unsigned32
			MAX-ACCESS read-write
			STATUS deprecated
			DESCRIPTION
				"Energy meter's password."
			DEFVAL { 0 }
			::= { msanEnergyMeterGlobal 4 }

		
		-- 1.3.6.1.4.1.1332.1.1.5.3.107.1.5
		msanEnergyMeterSerialNo OBJECT-TYPE
			SYNTAX OCTET STRING (SIZE (1..128))
			MAX-ACCESS read-only
			STATUS current
			DESCRIPTION
				"Energy meter's serial number."
			::= { msanEnergyMeterGlobal 5 }

		
		-- 1.3.6.1.4.1.1332.1.1.5.3.107.1.6
		msanEnergyMeterDateTime OBJECT-TYPE
			SYNTAX OCTET STRING
			MAX-ACCESS read-only
			STATUS current
			DESCRIPTION
				"Energy meter's date and time in format: 
				year-month-day, hour:minutes:seconds"
			::= { msanEnergyMeterGlobal 6 }

		
		-- 1.3.6.1.4.1.1332.1.1.5.3.107.1.7
		msanEnergyMeterCurrTariff OBJECT-TYPE
			SYNTAX Unsigned32
			MAX-ACCESS read-only
			STATUS current
			DESCRIPTION
				"Energy meter's current active tariff."
			::= { msanEnergyMeterGlobal 7 }

		
		-- 1.3.6.1.4.1.1332.1.1.5.3.107.1.8
		msanEnergyMeterCurrPower OBJECT-TYPE
			SYNTAX Unsigned32
			UNITS "0.01 kW"
			MAX-ACCESS read-only
			STATUS current
			DESCRIPTION
				"Energy meter's current measured power."
			::= { msanEnergyMeterGlobal 8 }

		
		-- 1.3.6.1.4.1.1332.1.1.5.3.107.1.9
		msanEnergyMeterCoreVersion OBJECT-TYPE
			SYNTAX Unsigned32
			MAX-ACCESS read-only
			STATUS current
			DESCRIPTION
				"Energy meter's current version number."
			::= { msanEnergyMeterGlobal 9 }

		
		-- 1.3.6.1.4.1.1332.1.1.5.3.107.1.10
		msanEnergyMeterFwType OBJECT-TYPE
			SYNTAX Unsigned32
			MAX-ACCESS read-only
			STATUS current
			DESCRIPTION
				"Energy meter's current firmware type."
			::= { msanEnergyMeterGlobal 10 }

		
		-- 1.3.6.1.4.1.1332.1.1.5.3.107.1.11
		msanEnergyMeterFwVersion OBJECT-TYPE
			SYNTAX Unsigned32
			MAX-ACCESS read-only
			STATUS deprecated
			DESCRIPTION
				"Energy meter's current firmware version."
			::= { msanEnergyMeterGlobal 11 }

		
		-- 1.3.6.1.4.1.1332.1.1.5.3.107.1.12
		msanEnergyMeterFwCreationDate OBJECT-TYPE
			SYNTAX OCTET STRING
			MAX-ACCESS read-only
			STATUS current
			DESCRIPTION
				"Energy meter's current firmware creation date in format: 
				year-month-day"
			::= { msanEnergyMeterGlobal 12 }

		
		-- 1.3.6.1.4.1.1332.1.1.5.3.107.1.13
		msanEnergyMeterStdPassword OBJECT-TYPE
			SYNTAX DisplayString (SIZE (0..8))
			MAX-ACCESS read-write
			STATUS current
			DESCRIPTION
				"Energy meter's password as ASCII string 
				(according to used standard  IEC 61107-2001 / IEC 62056-21)."
			::= { msanEnergyMeterGlobal 13 }

		
		-- 1.3.6.1.4.1.1332.1.1.5.3.107.1.14
		msanEnergyMeterStdFwVersion OBJECT-TYPE
			SYNTAX DisplayString
			MAX-ACCESS read-only
			STATUS current
			DESCRIPTION
				"Energy meter's current firmware version as ASCII string 
				(according to used standard  IEC 61107-2001 / IEC 62056-21)."
			::= { msanEnergyMeterGlobal 14 }

		
		-- 1.3.6.1.4.1.1332.1.1.5.3.107.2
		msanEnergyMeterEnergyTable OBJECT-TYPE
			SYNTAX SEQUENCE OF MsanEnergyMeterEnergyEntry
			MAX-ACCESS not-accessible
			STATUS current
			DESCRIPTION
				"Energy values."
			::= { msanEnergyMeter 2 }

		
		-- 1.3.6.1.4.1.1332.1.1.5.3.107.2.1
		msanEnergyMeterEnergyEntry OBJECT-TYPE
			SYNTAX MsanEnergyMeterEnergyEntry
			MAX-ACCESS not-accessible
			STATUS current
			DESCRIPTION
				"Description."
			INDEX { msanEnergyMeterTariff, msanEnergyMeterDepth }
			::= { msanEnergyMeterEnergyTable 1 }

		
		MsanEnergyMeterEnergyEntry ::=
			SEQUENCE { 
				msanEnergyMeterTariff
					Unsigned32,
				msanEnergyMeterDepth
					Unsigned32,
				msanEnergyMeterEnergyValue
					Unsigned32
			 }

		-- 1.3.6.1.4.1.1332.1.1.5.3.107.2.1.1
		msanEnergyMeterTariff OBJECT-TYPE
			SYNTAX Unsigned32 (1..8)
			MAX-ACCESS not-accessible
			STATUS current
			DESCRIPTION
				"This is msanEnergyMeterTariff index in msanEnergyMeterEnergyTable
				Defines tariff. 1 – tariff No1, 1 – tariff No2, …, 8 - tariff No8"
			::= { msanEnergyMeterEnergyEntry 1 }

		
		-- 1.3.6.1.4.1.1332.1.1.5.3.107.2.1.2
		msanEnergyMeterDepth OBJECT-TYPE
			SYNTAX Unsigned32 (1..13)
			MAX-ACCESS not-accessible
			STATUS current
			DESCRIPTION
				"This is msanEnergyMeterDepth index in msanEnergyMeterEnergyTable. 
				Defines time span. 
				1 – current value, 
				2 – value at the end of previous month, 
				3 – value at the end of 2. month ago, …, 13 –value at the end of the 12. month ago"
			::= { msanEnergyMeterEnergyEntry 2 }

		
		-- 1.3.6.1.4.1.1332.1.1.5.3.107.2.1.3
		msanEnergyMeterEnergyValue OBJECT-TYPE
			SYNTAX Unsigned32
			UNITS "0.01 kWh"
			MAX-ACCESS read-only
			STATUS current
			DESCRIPTION
				"Energy value."
			::= { msanEnergyMeterEnergyEntry 3 }

		
		-- 1.3.6.1.4.1.1332.1.1.5.3.107.3
		msanEnergyMeterEnergySumTable OBJECT-TYPE
			SYNTAX SEQUENCE OF MsanEnergyMeterEnergySumEntry
			MAX-ACCESS not-accessible
			STATUS current
			DESCRIPTION
				"Energy sum values of all tariffs."
			::= { msanEnergyMeter 3 }

		
		-- 1.3.6.1.4.1.1332.1.1.5.3.107.3.1
		msanEnergyMeterEnergySumEntry OBJECT-TYPE
			SYNTAX MsanEnergyMeterEnergySumEntry
			MAX-ACCESS not-accessible
			STATUS current
			DESCRIPTION
				"Description."
			INDEX { msanEnergyMeterDepth }
			::= { msanEnergyMeterEnergySumTable 1 }

		
		MsanEnergyMeterEnergySumEntry ::=
			SEQUENCE { 
				msanEnergyMeterEnergySumValue
					Unsigned32
			 }

		-- 1.3.6.1.4.1.1332.1.1.5.3.107.3.1.1
		msanEnergyMeterEnergySumValue OBJECT-TYPE
			SYNTAX Unsigned32
			UNITS "0.01 kWh"
			MAX-ACCESS read-only
			STATUS current
			DESCRIPTION
				"Energy sum value of all tariffs"
			::= { msanEnergyMeterEnergySumEntry 1 }

		
		-- 1.3.6.1.4.1.1332.1.1.5.3.108
		msanArpInspection OBJECT IDENTIFIER ::= { msanAdditionalConf 108 }

		
		-- 1.3.6.1.4.1.1332.1.1.5.3.108.1
		msanArpInspectionGlobal OBJECT IDENTIFIER ::= { msanArpInspection 1 }

		
		-- 1.3.6.1.4.1.1332.1.1.5.3.108.1.1
		msanArpInspectionAdminMode OBJECT-TYPE
			SYNTAX INTEGER
				{
				enable(1),
				disable(2)
				}
			MAX-ACCESS read-write
			STATUS current
			DESCRIPTION
				"Enable/disable global dynamic arp inspection "
			::= { msanArpInspectionGlobal 1 }

		
		-- 1.3.6.1.4.1.1332.1.1.5.3.108.2
		msanArpInspectionPortTable OBJECT-TYPE
			SYNTAX SEQUENCE OF MsanArpInspectionPortEntry
			MAX-ACCESS not-accessible
			STATUS current
			DESCRIPTION
				"Arp Inspection."
			::= { msanArpInspection 2 }

		
		-- 1.3.6.1.4.1.1332.1.1.5.3.108.2.1
		msanArpInspectionPortEntry OBJECT-TYPE
			SYNTAX MsanArpInspectionPortEntry
			MAX-ACCESS not-accessible
			STATUS current
			DESCRIPTION
				"Description."
			INDEX { ifIndex }
			::= { msanArpInspectionPortTable 1 }

		
		MsanArpInspectionPortEntry ::=
			SEQUENCE { 
				msanArpInspectionPortAdminMode
					INTEGER,
				msanArpInspectionPortStatDroppedFrames
					INTEGER
			 }

		-- 1.3.6.1.4.1.1332.1.1.5.3.108.2.1.1
		msanArpInspectionPortAdminMode OBJECT-TYPE
			SYNTAX INTEGER
				{
				enable(1),
				disable(2)
				}
			MAX-ACCESS read-write
			STATUS current
			DESCRIPTION
				"Enable/disable dynamic arp inspection for the selected interface."
			DEFVAL { disable }
			::= { msanArpInspectionPortEntry 1 }

		
		-- 1.3.6.1.4.1.1332.1.1.5.3.108.2.1.2
		msanArpInspectionPortStatDroppedFrames OBJECT-TYPE
			SYNTAX INTEGER
			MAX-ACCESS read-only
			STATUS current
			DESCRIPTION
				"Number of discarded ARP packets on interface."
			::= { msanArpInspectionPortEntry 2 }

		
		-- 1.3.6.1.4.1.1332.1.1.5.3.108.3
		msanArpInspectionVlanTable OBJECT-TYPE
			SYNTAX SEQUENCE OF MsanArpInspectionVlanEntry
			MAX-ACCESS not-accessible
			STATUS current
			DESCRIPTION
				"Arp Inspection."
			::= { msanArpInspection 3 }

		
		-- 1.3.6.1.4.1.1332.1.1.5.3.108.3.1
		msanArpInspectionVlanEntry OBJECT-TYPE
			SYNTAX MsanArpInspectionVlanEntry
			MAX-ACCESS not-accessible
			STATUS current
			DESCRIPTION
				"Description."
			INDEX { dot1qVlanIndex }
			::= { msanArpInspectionVlanTable 1 }

		
		MsanArpInspectionVlanEntry ::=
			SEQUENCE { 
				msanArpInspectionVlanAdminMode
					INTEGER,
				msanArpInspectionVlanStatDroppedFrames
					INTEGER
			 }

		-- 1.3.6.1.4.1.1332.1.1.5.3.108.3.1.1
		msanArpInspectionVlanAdminMode OBJECT-TYPE
			SYNTAX INTEGER
				{
				enable(1),
				disable(2)
				}
			MAX-ACCESS read-write
			STATUS current
			DESCRIPTION
				"Enable/disable dynamic arp inspection per vlan."
			DEFVAL { disable }
			::= { msanArpInspectionVlanEntry 1 }

		
		-- 1.3.6.1.4.1.1332.1.1.5.3.108.3.1.2
		msanArpInspectionVlanStatDroppedFrames OBJECT-TYPE
			SYNTAX INTEGER
			MAX-ACCESS read-only
			STATUS current
			DESCRIPTION
				"Number of discarded ARP packets per vlan."
			::= { msanArpInspectionVlanEntry 2 }

		
		-- 1.3.6.1.4.1.1332.1.1.5.3.109
		msanIsa OBJECT IDENTIFIER ::= { msanAdditionalConf 109 }

		
		-- 1.3.6.1.4.1.1332.1.1.5.3.109.1
		msanIsaGlobal OBJECT IDENTIFIER ::= { msanIsa 1 }

		
		-- 1.3.6.1.4.1.1332.1.1.5.3.109.1.1
		msanIsaTalAdminMode OBJECT-TYPE
			SYNTAX INTEGER
				{
				enable(1),
				disable(2)
				}
			MAX-ACCESS read-write
			STATUS current
			DESCRIPTION
				"ISA TAL functionality global admin mode."
			DEFVAL { disable }
			::= { msanIsaGlobal 1 }

		
		-- 1.3.6.1.4.1.1332.1.1.5.3.109.1.2
		msanIsaDasServerPort OBJECT-TYPE
			SYNTAX Unsigned32 (0..65535)
			MAX-ACCESS read-write
			STATUS current
			DESCRIPTION
				"ISA Radius DAS (Dynamic Authorization Server) port number."
			DEFVAL { 3799 }
			::= { msanIsaGlobal 2 }

		
		-- 1.3.6.1.4.1.1332.1.1.5.3.109.1.3
		msanIsaDasServerSecret OBJECT-TYPE
			SYNTAX DisplayString (SIZE (0..16))
			MAX-ACCESS read-write
			STATUS current
			DESCRIPTION
				"ISA Radius DAS  (Dynamic Authorization Server) shared secret."
			::= { msanIsaGlobal 3 }

		
		-- 1.3.6.1.4.1.1332.1.1.5.3.109.1.4
		msanIsaRadiusServerRetries OBJECT-TYPE
			SYNTAX Unsigned32 (1..15)
			MAX-ACCESS read-write
			STATUS current
			DESCRIPTION
				"Maximum number of retransmissions of a ISA Radius request packet."
			DEFVAL { 3 }
			::= { msanIsaGlobal 4 }

		
		-- 1.3.6.1.4.1.1332.1.1.5.3.109.1.5
		msanIsaRadiusServerTimeout OBJECT-TYPE
			SYNTAX Unsigned32 (1..30)
			UNITS "seconds"
			MAX-ACCESS read-write
			STATUS current
			DESCRIPTION
				"Time out duration (in seconds) before packets are retransmitted to ISA Radius server"
			DEFVAL { 3 }
			::= { msanIsaGlobal 5 }

		
		-- 1.3.6.1.4.1.1332.1.1.5.3.109.2
		msanIsaStatistics OBJECT IDENTIFIER ::= { msanIsa 2 }

		
		-- 1.3.6.1.4.1.1332.1.1.5.3.109.2.1
		msanIsaPortStatTable OBJECT-TYPE
			SYNTAX SEQUENCE OF MsanIsaPortStatEntry
			MAX-ACCESS not-accessible
			STATUS current
			DESCRIPTION
				"Description."
			::= { msanIsaStatistics 1 }

		
		-- 1.3.6.1.4.1.1332.1.1.5.3.109.2.1.1
		msanIsaPortStatEntry OBJECT-TYPE
			SYNTAX MsanIsaPortStatEntry
			MAX-ACCESS not-accessible
			STATUS current
			DESCRIPTION
				"Description."
			INDEX { ifIndex }
			::= { msanIsaPortStatTable 1 }

		
		MsanIsaPortStatEntry ::=
			SEQUENCE { 
				msanIsaPortStatTalMatchedFrames
					Counter32,
				msanIsaPortStatTalDroppedFrames
					Counter32,
				msanIsaPortStatAuthenReqSent
					Counter32,
				msanIsaPortStatAuthenReqConfirmed
					Counter32,
				msanIsaPortStatAuthenReqRejected
					Counter32,
				msanIsaPortStatAuthenTimeoutExpired
					Counter32,
				msanIsaPortStatAuthorReqSent
					Counter32,
				msanIsaPortStatAuthorReqConfirmed
					Counter32,
				msanIsaPortStatAuthorReqRejected
					Counter32,
				msanIsaPortStatAuthorTimeoutExpired
					Counter32
			 }

		-- 1.3.6.1.4.1.1332.1.1.5.3.109.2.1.1.1
		msanIsaPortStatTalMatchedFrames OBJECT-TYPE
			SYNTAX Counter32
			MAX-ACCESS read-only
			STATUS current
			DESCRIPTION
				"Number of TAL matched frames."
			::= { msanIsaPortStatEntry 1 }

		
		-- 1.3.6.1.4.1.1332.1.1.5.3.109.2.1.1.2
		msanIsaPortStatTalDroppedFrames OBJECT-TYPE
			SYNTAX Counter32
			MAX-ACCESS read-only
			STATUS current
			DESCRIPTION
				"Number of TAL dropped frames."
			::= { msanIsaPortStatEntry 2 }

		
		-- 1.3.6.1.4.1.1332.1.1.5.3.109.2.1.1.3
		msanIsaPortStatAuthenReqSent OBJECT-TYPE
			SYNTAX Counter32
			MAX-ACCESS read-only
			STATUS current
			DESCRIPTION
				"Number of sent Authentication requests."
			::= { msanIsaPortStatEntry 3 }

		
		-- 1.3.6.1.4.1.1332.1.1.5.3.109.2.1.1.4
		msanIsaPortStatAuthenReqConfirmed OBJECT-TYPE
			SYNTAX Counter32
			MAX-ACCESS read-only
			STATUS current
			DESCRIPTION
				"Number of confirmed Authentication requests."
			::= { msanIsaPortStatEntry 4 }

		
		-- 1.3.6.1.4.1.1332.1.1.5.3.109.2.1.1.6
		msanIsaPortStatAuthenReqRejected OBJECT-TYPE
			SYNTAX Counter32
			MAX-ACCESS read-only
			STATUS current
			DESCRIPTION
				"Number of rejected Authentication requests."
			::= { msanIsaPortStatEntry 6 }

		
		-- 1.3.6.1.4.1.1332.1.1.5.3.109.2.1.1.7
		msanIsaPortStatAuthenTimeoutExpired OBJECT-TYPE
			SYNTAX Counter32
			MAX-ACCESS read-only
			STATUS current
			DESCRIPTION
				"Number of expired Authentication timeouts."
			::= { msanIsaPortStatEntry 7 }

		
		-- 1.3.6.1.4.1.1332.1.1.5.3.109.2.1.1.8
		msanIsaPortStatAuthorReqSent OBJECT-TYPE
			SYNTAX Counter32
			MAX-ACCESS read-only
			STATUS current
			DESCRIPTION
				"Number of sent Authorization requests."
			::= { msanIsaPortStatEntry 8 }

		
		-- 1.3.6.1.4.1.1332.1.1.5.3.109.2.1.1.9
		msanIsaPortStatAuthorReqConfirmed OBJECT-TYPE
			SYNTAX Counter32
			MAX-ACCESS read-only
			STATUS current
			DESCRIPTION
				"Number of confirmed Authorization requests."
			::= { msanIsaPortStatEntry 9 }

		
		-- 1.3.6.1.4.1.1332.1.1.5.3.109.2.1.1.10
		msanIsaPortStatAuthorReqRejected OBJECT-TYPE
			SYNTAX Counter32
			MAX-ACCESS read-only
			STATUS current
			DESCRIPTION
				"Number of rejected Authorization requests."
			::= { msanIsaPortStatEntry 10 }

		
		-- 1.3.6.1.4.1.1332.1.1.5.3.109.2.1.1.11
		msanIsaPortStatAuthorTimeoutExpired OBJECT-TYPE
			SYNTAX Counter32
			MAX-ACCESS read-only
			STATUS current
			DESCRIPTION
				"Number of expired Authorization timeouts."
			::= { msanIsaPortStatEntry 11 }

		
		-- 1.3.6.1.4.1.1332.1.1.5.3.109.2.2
		msanIsaStatLoginReq OBJECT-TYPE
			SYNTAX Counter32
			MAX-ACCESS read-only
			STATUS current
			DESCRIPTION
				"Cumulative number of Login requests."
			::= { msanIsaStatistics 2 }

		
		-- 1.3.6.1.4.1.1332.1.1.5.3.109.2.3
		msanIsaStatLoginUnsuccessfulReq OBJECT-TYPE
			SYNTAX Counter32
			MAX-ACCESS read-only
			STATUS current
			DESCRIPTION
				"Number of unsuccessful login requests."
			::= { msanIsaStatistics 3 }

		
		-- 1.3.6.1.4.1.1332.1.1.5.3.109.3
		msanIsaRadiusServerTable OBJECT-TYPE
			SYNTAX SEQUENCE OF MsanIsaRadiusServerEntry
			MAX-ACCESS not-accessible
			STATUS current
			DESCRIPTION
				"Description."
			::= { msanIsa 3 }

		
		-- 1.3.6.1.4.1.1332.1.1.5.3.109.3.1
		msanIsaRadiusServerEntry OBJECT-TYPE
			SYNTAX MsanIsaRadiusServerEntry
			MAX-ACCESS not-accessible
			STATUS current
			DESCRIPTION
				"Description."
			INDEX { msanIsaRadiusServerIpAddress, msanIsaRadiusServerType }
			::= { msanIsaRadiusServerTable 1 }

		
		MsanIsaRadiusServerEntry ::=
			SEQUENCE { 
				msanIsaRadiusServerIpAddress
					IpAddress,
				msanIsaRadiusServerType
					INTEGER,
				msanIsaRadiusServerPort
					Unsigned32,
				msanIsaRadiusServerSecret
					DisplayString,
				msanIsaRadiusServerPrimaryMode
					INTEGER,
				msanIsaRadiusServerRowStatus
					RowStatus
			 }

		-- 1.3.6.1.4.1.1332.1.1.5.3.109.3.1.1
		msanIsaRadiusServerIpAddress OBJECT-TYPE
			SYNTAX IpAddress
			MAX-ACCESS not-accessible
			STATUS current
			DESCRIPTION
				"ISA Radius server IP address.
				"
			::= { msanIsaRadiusServerEntry 1 }

		
		-- 1.3.6.1.4.1.1332.1.1.5.3.109.3.1.2
		msanIsaRadiusServerType OBJECT-TYPE
			SYNTAX INTEGER
				{
				authentication(1),
				accounting(2)
				}
			MAX-ACCESS not-accessible
			STATUS current
			DESCRIPTION
				"ISA Radius server type."
			::= { msanIsaRadiusServerEntry 2 }

		
		-- 1.3.6.1.4.1.1332.1.1.5.3.109.3.1.3
		msanIsaRadiusServerPort OBJECT-TYPE
			SYNTAX Unsigned32 (0..65535)
			MAX-ACCESS read-write
			STATUS current
			DESCRIPTION
				" ISA Radius server port number. 
				
				If msanIsaRadiusServerType = authentication(1) then default port value is 1812.
				If msanIsaRadiusServerType = accounting(2) then default port value is 1813."
			::= { msanIsaRadiusServerEntry 3 }

		
		-- 1.3.6.1.4.1.1332.1.1.5.3.109.3.1.4
		msanIsaRadiusServerSecret OBJECT-TYPE
			SYNTAX DisplayString (SIZE (0..16))
			MAX-ACCESS read-write
			STATUS current
			DESCRIPTION
				"ISA Radius server shared secret."
			DEFVAL { "" }
			::= { msanIsaRadiusServerEntry 4 }

		
		-- 1.3.6.1.4.1.1332.1.1.5.3.109.3.1.5
		msanIsaRadiusServerPrimaryMode OBJECT-TYPE
			SYNTAX INTEGER
				{
				primary(1),
				secondary(2)
				}
			MAX-ACCESS read-write
			STATUS current
			DESCRIPTION
				"ISA Radius server primary mode.
				Only one server can be defined as primary(1)."
			::= { msanIsaRadiusServerEntry 5 }

		
		-- 1.3.6.1.4.1.1332.1.1.5.3.109.3.1.6
		msanIsaRadiusServerRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndWait(5).
				For row activation use active(1).
				For row deletion use destroy(6).
				
				Other values are currently not supported.
				
				For row activation parameter msanIsaRadiusServerType must be defined."
			::= { msanIsaRadiusServerEntry 6 }

		
		-- 1.3.6.1.4.1.1332.1.1.5.3.109.5
		msanIsaPortTable OBJECT-TYPE
			SYNTAX SEQUENCE OF MsanIsaPortEntry
			MAX-ACCESS not-accessible
			STATUS current
			DESCRIPTION
				"Description."
			::= { msanIsa 5 }

		
		-- 1.3.6.1.4.1.1332.1.1.5.3.109.5.1
		msanIsaPortEntry OBJECT-TYPE
			SYNTAX MsanIsaPortEntry
			MAX-ACCESS not-accessible
			STATUS current
			DESCRIPTION
				"Description."
			INDEX { ifIndex }
			::= { msanIsaPortTable 1 }

		
		MsanIsaPortEntry ::=
			SEQUENCE { 
				msanIsaPortTalAdminMode
					INTEGER,
				msanIsaPortAuthentication
					INTEGER,
				msanIsaPortAuthorization
					INTEGER,
				msanIsaPortAccounting
					INTEGER,
				msanIsaPortLoginMask
					BITS,
				msanIsaPortLoginUserPatternMask
					OCTET STRING,
				msanIsaPortTalAutomaticReq
					INTEGER
			 }

		-- 1.3.6.1.4.1.1332.1.1.5.3.109.5.1.1
		msanIsaPortTalAdminMode OBJECT-TYPE
			SYNTAX INTEGER
				{
				enable(1),
				disable(2)
				}
			MAX-ACCESS read-write
			STATUS current
			DESCRIPTION
				"ISA TAL functionality admin mode."
			DEFVAL { disable }
			::= { msanIsaPortEntry 1 }

		
		-- 1.3.6.1.4.1.1332.1.1.5.3.109.5.1.2
		msanIsaPortAuthentication OBJECT-TYPE
			SYNTAX INTEGER
				{
				enable(1),
				disable(2)
				}
			MAX-ACCESS read-write
			STATUS current
			DESCRIPTION
				"ISA Authentication administrative state."
			DEFVAL { enable }
			::= { msanIsaPortEntry 2 }

		
		-- 1.3.6.1.4.1.1332.1.1.5.3.109.5.1.3
		msanIsaPortAuthorization OBJECT-TYPE
			SYNTAX INTEGER
				{
				enable(1),
				disable(2)
				}
			MAX-ACCESS read-write
			STATUS current
			DESCRIPTION
				"ISA Authorization administrative state."
			DEFVAL { enable }
			::= { msanIsaPortEntry 3 }

		
		-- 1.3.6.1.4.1.1332.1.1.5.3.109.5.1.4
		msanIsaPortAccounting OBJECT-TYPE
			SYNTAX INTEGER
				{
				enable(1),
				disable(2)
				}
			MAX-ACCESS read-write
			STATUS current
			DESCRIPTION
				"ISA Accounting administrative state."
			DEFVAL { disable }
			::= { msanIsaPortEntry 4 }

		
		-- 1.3.6.1.4.1.1332.1.1.5.3.109.5.1.5
		msanIsaPortLoginMask OBJECT-TYPE
			SYNTAX BITS
				{
				circuitId(0),
				remoteId(1),
				vendorId(2),
				clientId(3),
				sourceMAC(4),
				sourceIP(5),
				userPattern(6)
				}
			MAX-ACCESS read-write
			STATUS current
			DESCRIPTION
				"ISA login mask."
			DEFVAL { { circuitId } }
			::= { msanIsaPortEntry 5 }

		
		-- 1.3.6.1.4.1.1332.1.1.5.3.109.5.1.6
		msanIsaPortLoginUserPatternMask OBJECT-TYPE
			SYNTAX OCTET STRING (SIZE (0..128))
			MAX-ACCESS read-write
			STATUS current
			DESCRIPTION
				"This mask value identifies the portion of input packet that 
				is send to Radius server, if userPattern bit is set in msanIsaPortLoginMask.
				Empty string indicates that parameter has not been defined."
			::= { msanIsaPortEntry 6 }

		
		-- 1.3.6.1.4.1.1332.1.1.5.3.109.5.1.7
		msanIsaPortTalAutomaticReq OBJECT-TYPE
			SYNTAX INTEGER
				{
				enable(1),
				disable(2)
				}
			MAX-ACCESS read-write
			STATUS current
			DESCRIPTION
				"TAL automatic request state."
			DEFVAL { disable }
			::= { msanIsaPortEntry 7 }

		
		-- 1.3.6.1.4.1.1332.1.1.5.3.109.6
		msanIsaTalPortMatchTable OBJECT-TYPE
			SYNTAX SEQUENCE OF MsanIsaTalPortMatchEntry
			MAX-ACCESS not-accessible
			STATUS current
			DESCRIPTION
				"Description."
			::= { msanIsa 6 }

		
		-- 1.3.6.1.4.1.1332.1.1.5.3.109.6.1
		msanIsaTalPortMatchEntry OBJECT-TYPE
			SYNTAX MsanIsaTalPortMatchEntry
			MAX-ACCESS not-accessible
			STATUS current
			DESCRIPTION
				"Description."
			INDEX { ifIndex }
			::= { msanIsaTalPortMatchTable 1 }

		
		MsanIsaTalPortMatchEntry ::=
			SEQUENCE { 
				msanIsaTalPortMatchEthertype
					Integer32,
				msanIsaTalPortMatchMacSrcAddr
					MacAddress,
				msanIsaTalPortMatchMacSrcMask
					MacAddress,
				msanIsaTalPortMatchVlanId
					Integer32,
				msanIsaTalPortMatchIpSrcAddr
					IpAddress,
				msanIsaTalPortMatchIpSrcMask
					IpAddress,
				msanIsaTalPortMatchDhcpType
					INTEGER,
				msanIsaTalPortMatchDhcpOpt60VendorId
					DisplayString,
				msanIsaTalPortMatchDhcpOpt61ClientId
					DisplayString,
				msanIsaTalPortMatchDhcpOpt61ClientIdMacAddr
					MacAddress,
				msanIsaTalPortMatchDhcpOpt82RemoteId
					DisplayString,
				msanIsaTalPortMatchUserBits
					OCTET STRING,
				msanIsaTalPortMatchUserMask
					OCTET STRING
			 }

		-- 1.3.6.1.4.1.1332.1.1.5.3.109.6.1.1
		msanIsaTalPortMatchEthertype OBJECT-TYPE
			SYNTAX Integer32 (-1..65535)
			MAX-ACCESS read-write
			STATUS current
			DESCRIPTION
				"Match incoming packet frame with specified EtherType value.
				A value of -1 indicates that parameter has not been defined.
				"
			DEFVAL { -1 }
			::= { msanIsaTalPortMatchEntry 1 }

		
		-- 1.3.6.1.4.1.1332.1.1.5.3.109.6.1.2
		msanIsaTalPortMatchMacSrcAddr OBJECT-TYPE
			SYNTAX MacAddress
			MAX-ACCESS read-write
			STATUS current
			DESCRIPTION
				"Match incoming  packet frame with specified Source MAC address.
				Empty string indicates that parameter has not been defined."
			DEFVAL { ''b }
			::= { msanIsaTalPortMatchEntry 2 }

		
		-- 1.3.6.1.4.1.1332.1.1.5.3.109.6.1.3
		msanIsaTalPortMatchMacSrcMask OBJECT-TYPE
			SYNTAX MacAddress
			MAX-ACCESS read-write
			STATUS current
			DESCRIPTION
				"This mask value identifies the portion of msanIsaTalPortMatchMacSrcAddr that 
				is compared with input packet.
				Empty string indicates that parameter has not been defined
				"
			DEFVAL { ''b }
			::= { msanIsaTalPortMatchEntry 3 }

		
		-- 1.3.6.1.4.1.1332.1.1.5.3.109.6.1.4
		msanIsaTalPortMatchVlanId OBJECT-TYPE
			SYNTAX Integer32 (-1..4094)
			MAX-ACCESS read-write
			STATUS current
			DESCRIPTION
				"Match incoming packet frame with specified VLAN ID value (1-4094).
				A value of -1 indicates that parameter has not been defined
				"
			::= { msanIsaTalPortMatchEntry 4 }

		
		-- 1.3.6.1.4.1.1332.1.1.5.3.109.6.1.5
		msanIsaTalPortMatchIpSrcAddr OBJECT-TYPE
			SYNTAX IpAddress
			MAX-ACCESS read-write
			STATUS current
			DESCRIPTION
				"Match incoming packet frame with specified source IP address.
				Empty string indicates that parameter has not been defined.
				"
			DEFVAL { ''h }
			::= { msanIsaTalPortMatchEntry 5 }

		
		-- 1.3.6.1.4.1.1332.1.1.5.3.109.6.1.6
		msanIsaTalPortMatchIpSrcMask OBJECT-TYPE
			SYNTAX IpAddress
			MAX-ACCESS read-write
			STATUS current
			DESCRIPTION
				"This mask value identifies the portion of msanIsaTalPortMatchIpSrcAddr that 
				is compared with input packet.
				Empty string indicates that parameter has not been defined
				
				"
			DEFVAL { ''h }
			::= { msanIsaTalPortMatchEntry 6 }

		
		-- 1.3.6.1.4.1.1332.1.1.5.3.109.6.1.7
		msanIsaTalPortMatchDhcpType OBJECT-TYPE
			SYNTAX INTEGER
				{
				undefined(0),
				discover(1),
				request(2)
				}
			MAX-ACCESS read-write
			STATUS current
			DESCRIPTION
				"Match incoming  packet frame with specified DHCP type value.
				"
			DEFVAL { undefined }
			::= { msanIsaTalPortMatchEntry 7 }

		
		-- 1.3.6.1.4.1.1332.1.1.5.3.109.6.1.8
		msanIsaTalPortMatchDhcpOpt60VendorId OBJECT-TYPE
			SYNTAX DisplayString
			MAX-ACCESS read-write
			STATUS current
			DESCRIPTION
				"Match incoming packet frame with specified DHCP option 60 vendorId value.
				Empty string indicates that parameter has not been defined."
			DEFVAL { "" }
			::= { msanIsaTalPortMatchEntry 8 }

		
		-- 1.3.6.1.4.1.1332.1.1.5.3.109.6.1.9
		msanIsaTalPortMatchDhcpOpt61ClientId OBJECT-TYPE
			SYNTAX DisplayString
			MAX-ACCESS read-write
			STATUS current
			DESCRIPTION
				"Match incoming  packet frame with specified DHCP option 61 clientId value.
				Empty string indicates that parameter has not been defined."
			DEFVAL { "" }
			::= { msanIsaTalPortMatchEntry 9 }

		
		-- 1.3.6.1.4.1.1332.1.1.5.3.109.6.1.10
		msanIsaTalPortMatchDhcpOpt61ClientIdMacAddr OBJECT-TYPE
			SYNTAX MacAddress
			MAX-ACCESS read-write
			STATUS current
			DESCRIPTION
				"Match incoming packet frame with specified DHCP option 61 MAC address.
				Empty string indicates that parameter has not been defined."
			DEFVAL { ''b }
			::= { msanIsaTalPortMatchEntry 10 }

		
		-- 1.3.6.1.4.1.1332.1.1.5.3.109.6.1.11
		msanIsaTalPortMatchDhcpOpt82RemoteId OBJECT-TYPE
			SYNTAX DisplayString
			MAX-ACCESS read-write
			STATUS current
			DESCRIPTION
				"Match incoming  packet frame with specified DHCP option 82 remoteId value.
				Empty string indicates that parameter has not been defined."
			DEFVAL { "" }
			::= { msanIsaTalPortMatchEntry 11 }

		
		-- 1.3.6.1.4.1.1332.1.1.5.3.109.6.1.12
		msanIsaTalPortMatchUserBits OBJECT-TYPE
			SYNTAX OCTET STRING (SIZE (0..128))
			MAX-ACCESS read-write
			STATUS current
			DESCRIPTION
				"Match incoming  packet frame with specified user defined bits.
				Empty string indicates that parameter has not been defined."
			DEFVAL { ''h }
			::= { msanIsaTalPortMatchEntry 12 }

		
		-- 1.3.6.1.4.1.1332.1.1.5.3.109.6.1.13
		msanIsaTalPortMatchUserMask OBJECT-TYPE
			SYNTAX OCTET STRING (SIZE (0..128))
			MAX-ACCESS read-write
			STATUS current
			DESCRIPTION
				"This mask value identifies the portion of msanIsaTalPortMatchUserBits that 
				is compared with input packet.
				Empty string indicates that parameter has not been defined."
			DEFVAL { ''h }
			::= { msanIsaTalPortMatchEntry 13 }

		
		-- 1.3.6.1.4.1.1332.1.1.5.3.109.7
		msanIsaTalPatternMatchTable OBJECT-TYPE
			SYNTAX SEQUENCE OF MsanIsaTalPatternMatchEntry
			MAX-ACCESS not-accessible
			STATUS current
			DESCRIPTION
				"This table is used to store the pattern match name, pattern
				rules and the corresponding login mask for the pattern match."
			::= { msanIsa 7 }

		
		-- 1.3.6.1.4.1.1332.1.1.5.3.109.7.1
		msanIsaTalPatternMatchEntry OBJECT-TYPE
			SYNTAX MsanIsaTalPatternMatchEntry
			MAX-ACCESS not-accessible
			STATUS current
			DESCRIPTION
				"Each entry in this table contains the 
				a unique pattern match along with the loginmask to identify the user login packets."
			INDEX { msanIsaTalPatternMatchName }
			::= { msanIsaTalPatternMatchTable 1 }

		
		MsanIsaTalPatternMatchEntry ::=
			SEQUENCE { 
				msanIsaTalPatternMatchName
					OCTET STRING,
				msanIsaTalPatternMatchEthertype
					Integer32,
				msanIsaTalPatternMatchMacSrcAddr
					MacAddress,
				msanIsaTalPatternMatchMacSrcMask
					MacAddress,
				msanIsaTalPatternMatchVlanId
					Integer32,
				msanIsaTalPatternMatchIpSrcAddr
					IpAddress,
				msanIsaTalPatternMatchIpSrcMask
					IpAddress,
				msanIsaTalPatternMatchDhcpType
					INTEGER,
				msanIsaTalPatternMatchDhcpOpt60VendorId
					DisplayString,
				msanIsaTalPatternMatchDhcpOpt61ClientId
					DisplayString,
				msanIsaTalPatternMatchDhcpOpt61ClientIdMacAddr
					MacAddress,
				msanIsaTalPatternMatchDhcpOpt82RemoteId
					DisplayString,
				msanIsaTalPatternMatchUserBits
					OCTET STRING,
				msanIsaTalPatternMatchUserMask
					OCTET STRING,
				msanIsaTalPatternMatchLoginMask
					BITS,
				msanIsaTalPatternMatchRowStatus
					RowStatus
			 }

		-- 1.3.6.1.4.1.1332.1.1.5.3.109.7.1.1
		msanIsaTalPatternMatchName OBJECT-TYPE
			SYNTAX OCTET STRING (SIZE (1..64))
			MAX-ACCESS not-accessible
			STATUS current
			DESCRIPTION
				"Pattern match name."
			::= { msanIsaTalPatternMatchEntry 1 }

		
		-- 1.3.6.1.4.1.1332.1.1.5.3.109.7.1.2
		msanIsaTalPatternMatchEthertype OBJECT-TYPE
			SYNTAX Integer32 (-1..65535)
			MAX-ACCESS read-write
			STATUS current
			DESCRIPTION
				"Match incoming packet frame with specified EtherType value.
				A value of -1 indicates that parameter has not been defined.
				"
			DEFVAL { -1 }
			::= { msanIsaTalPatternMatchEntry 2 }

		
		-- 1.3.6.1.4.1.1332.1.1.5.3.109.7.1.3
		msanIsaTalPatternMatchMacSrcAddr OBJECT-TYPE
			SYNTAX MacAddress
			MAX-ACCESS read-write
			STATUS current
			DESCRIPTION
				"Match incoming  packet frame with specified Source MAC address.
				Empty string indicates that parameter has not been defined."
			DEFVAL { ''b }
			::= { msanIsaTalPatternMatchEntry 3 }

		
		-- 1.3.6.1.4.1.1332.1.1.5.3.109.7.1.4
		msanIsaTalPatternMatchMacSrcMask OBJECT-TYPE
			SYNTAX MacAddress
			MAX-ACCESS read-write
			STATUS current
			DESCRIPTION
				"This mask value identifies the portion of 
				msanIsaTalPatternMatchMacSrcAddr that is compared with input
				packet. Empty string indicates that parameter has not been 
				defined"
			DEFVAL { ''b }
			::= { msanIsaTalPatternMatchEntry 4 }

		
		-- 1.3.6.1.4.1.1332.1.1.5.3.109.7.1.5
		msanIsaTalPatternMatchVlanId OBJECT-TYPE
			SYNTAX Integer32 (-1..4094)
			MAX-ACCESS read-write
			STATUS current
			DESCRIPTION
				"Match incoming packet frame with specified VLAN ID value
				(1-4094). A value of -1 indicates that parameter has not been
				defined"
			::= { msanIsaTalPatternMatchEntry 5 }

		
		-- 1.3.6.1.4.1.1332.1.1.5.3.109.7.1.6
		msanIsaTalPatternMatchIpSrcAddr OBJECT-TYPE
			SYNTAX IpAddress
			MAX-ACCESS read-write
			STATUS current
			DESCRIPTION
				"Match incoming packet frame with specified source IP address.
				Empty string indicates that parameter has not been defined.
				"
			DEFVAL { ''h }
			::= { msanIsaTalPatternMatchEntry 6 }

		
		-- 1.3.6.1.4.1.1332.1.1.5.3.109.7.1.7
		msanIsaTalPatternMatchIpSrcMask OBJECT-TYPE
			SYNTAX IpAddress
			MAX-ACCESS read-write
			STATUS current
			DESCRIPTION
				"This mask value identifies the portion of
				msanIsaTalPatternMatchIpSrcAddr that is compared with input 
				packet.	Empty string indicates that parameter has not been
				defined"
			DEFVAL { ''h }
			::= { msanIsaTalPatternMatchEntry 7 }

		
		-- 1.3.6.1.4.1.1332.1.1.5.3.109.7.1.8
		msanIsaTalPatternMatchDhcpType OBJECT-TYPE
			SYNTAX INTEGER
				{
				undefined(0),
				discover(1),
				request(2)
				}
			MAX-ACCESS read-write
			STATUS current
			DESCRIPTION
				"Match incoming  packet frame with specified DHCP type value.
				"
			DEFVAL { undefined }
			::= { msanIsaTalPatternMatchEntry 8 }

		
		-- 1.3.6.1.4.1.1332.1.1.5.3.109.7.1.9
		msanIsaTalPatternMatchDhcpOpt60VendorId OBJECT-TYPE
			SYNTAX DisplayString
			MAX-ACCESS read-write
			STATUS current
			DESCRIPTION
				"Match incoming packet frame with specified DHCP option 60
				vendorId value.	Empty string indicates that parameter has not
				been defined."
			DEFVAL { "" }
			::= { msanIsaTalPatternMatchEntry 9 }

		
		-- 1.3.6.1.4.1.1332.1.1.5.3.109.7.1.10
		msanIsaTalPatternMatchDhcpOpt61ClientId OBJECT-TYPE
			SYNTAX DisplayString
			MAX-ACCESS read-write
			STATUS current
			DESCRIPTION
				"Match incoming  packet frame with specified DHCP option 61
				clientId value.	Empty string indicates that parameter has not
				been defined."
			DEFVAL { "" }
			::= { msanIsaTalPatternMatchEntry 10 }

		
		-- 1.3.6.1.4.1.1332.1.1.5.3.109.7.1.11
		msanIsaTalPatternMatchDhcpOpt61ClientIdMacAddr OBJECT-TYPE
			SYNTAX MacAddress
			MAX-ACCESS read-write
			STATUS current
			DESCRIPTION
				"Match incoming packet frame with specified DHCP option 61 MAC
				address. Empty string indicates that parameter has not been 
				defined."
			DEFVAL { ''b }
			::= { msanIsaTalPatternMatchEntry 11 }

		
		-- 1.3.6.1.4.1.1332.1.1.5.3.109.7.1.12
		msanIsaTalPatternMatchDhcpOpt82RemoteId OBJECT-TYPE
			SYNTAX DisplayString
			MAX-ACCESS read-write
			STATUS current
			DESCRIPTION
				"Match incoming  packet frame with specified DHCP option 82
				remoteId value.	Empty string indicates that parameter has not
				been defined."
			DEFVAL { "" }
			::= { msanIsaTalPatternMatchEntry 12 }

		
		-- 1.3.6.1.4.1.1332.1.1.5.3.109.7.1.13
		msanIsaTalPatternMatchUserBits OBJECT-TYPE
			SYNTAX OCTET STRING (SIZE (0..128))
			MAX-ACCESS read-write
			STATUS current
			DESCRIPTION
				"Match incoming  packet frame with specified user defined bits.
				Empty string indicates that parameter has not been defined."
			DEFVAL { ''h }
			::= { msanIsaTalPatternMatchEntry 13 }

		
		-- 1.3.6.1.4.1.1332.1.1.5.3.109.7.1.14
		msanIsaTalPatternMatchUserMask OBJECT-TYPE
			SYNTAX OCTET STRING (SIZE (0..128))
			MAX-ACCESS read-write
			STATUS current
			DESCRIPTION
				"This mask value identifies the portion of
				msanIsaTalPatternMatchUserBits that is compared with input
				packet. Empty string indicates that parameter has not been
				defined."
			DEFVAL { ''h }
			::= { msanIsaTalPatternMatchEntry 14 }

		
		-- 1.3.6.1.4.1.1332.1.1.5.3.109.7.1.15
		msanIsaTalPatternMatchLoginMask OBJECT-TYPE
			SYNTAX BITS
				{
				circuitId(0),
				remoteId(1),
				vendorId(2),
				clientId(3),
				sourceMAC(4),
				sourceIP(5),
				userPattern(6)
				}
			MAX-ACCESS read-write
			STATUS current
			DESCRIPTION
				"Login mask for the current pattern match. This is used to
				generate the UserId."
			DEFVAL { { circuitId } }
			::= { msanIsaTalPatternMatchEntry 15 }

		
		-- 1.3.6.1.4.1.1332.1.1.5.3.109.7.1.16
		msanIsaTalPatternMatchRowStatus OBJECT-TYPE
			SYNTAX RowStatus
			MAX-ACCESS read-write
			STATUS current
			DESCRIPTION
				"The row status object controls the creation/deletion of rows
				in this table.
				                            Its semantics are the same as those for the RowStatus textual
				convention specified for SNMPv2.
				A new row is created using createAndWait(5)
				[createAndGo(4) is not supported]
				The value active(1) activates the entry.
				                            Setting this object to destroy6) will remove this entry."
			::= { msanIsaTalPatternMatchEntry 16 }

		
		-- 1.3.6.1.4.1.1332.1.1.5.3.109.8
		msanIsaTalPortPatternMatchTable OBJECT-TYPE
			SYNTAX SEQUENCE OF MsanIsaTalPortPatternMatchEntry
			MAX-ACCESS not-accessible
			STATUS current
			DESCRIPTION
				"A connection between Pattern Matches and device ports. 
				An entry is created in this table whenever a pattern match need to be
				attached to a downlink port."
			::= { msanIsa 8 }

		
		-- 1.3.6.1.4.1.1332.1.1.5.3.109.8.1
		msanIsaTalPortPatternMatchEntry OBJECT-TYPE
			SYNTAX MsanIsaTalPortPatternMatchEntry
			MAX-ACCESS not-accessible
			STATUS current
			DESCRIPTION
				"Each entry in this table contains the 
				a unique pattern match on a port along with the loginmask to identify the user login packets."
			INDEX { ifIndex, msanIsaTalPatternMatchName }
			::= { msanIsaTalPortPatternMatchTable 1 }

		
		MsanIsaTalPortPatternMatchEntry ::=
			SEQUENCE { 
				msanIsaTalPortPatternMatchRowStatus
					RowStatus
			 }

		-- 1.3.6.1.4.1.1332.1.1.5.3.109.8.1.1
		msanIsaTalPortPatternMatchRowStatus OBJECT-TYPE
			SYNTAX RowStatus
			MAX-ACCESS read-create
			STATUS current
			DESCRIPTION
				"The row status object controls the creation/deletion of rows
				in this table.
				Its semantics are the same as those for the RowStatus textual
				convention specified for SNMPv2.
				Setting this object to createAndGo(4) creates a row in this table.
				Setting this object to destroy(6) will remove this entry.
				Read values: active(1).
				Other values are currently not supported."
			::= { msanIsaTalPortPatternMatchEntry 1 }

		
		-- 1.3.6.1.4.1.1332.1.1.5.3.110
		msanSync OBJECT IDENTIFIER ::= { msanAdditionalConf 110 }

		
		-- 1.3.6.1.4.1.1332.1.1.5.3.110.1
		msanSyncGlobal OBJECT IDENTIFIER ::= { msanSync 1 }

		
		-- 1.3.6.1.4.1.1332.1.1.5.3.110.2
		msanSyncTable OBJECT-TYPE
			SYNTAX SEQUENCE OF MsanSyncEntry
			MAX-ACCESS not-accessible
			STATUS current
			DESCRIPTION
				"Description."
			::= { msanSync 2 }

		
		-- 1.3.6.1.4.1.1332.1.1.5.3.110.2.1
		msanSyncEntry OBJECT-TYPE
			SYNTAX MsanSyncEntry
			MAX-ACCESS not-accessible
			STATUS current
			DESCRIPTION
				"Description."
			INDEX { msanSyncBoardPosition, msanSyncSourcePriority }
			::= { msanSyncTable 1 }

		
		MsanSyncEntry ::=
			SEQUENCE { 
				msanSyncBoardPosition
					INTEGER,
				msanSyncSourcePriority
					INTEGER,
				msanSyncSourceType
					INTEGER,
				msanSyncSourceId
					INTEGER,
				msanSyncSourceEthPortId
					InterfaceIndex,
				msanSyncDestinationType
					INTEGER,
				msanSyncDestinationMlvdsId
					INTEGER,
				msanSyncSourceSuitability
					INTEGER,
				msanSyncSourceActivity
					INTEGER,
				msanSyncRowStatus
					RowStatus
			 }

		-- 1.3.6.1.4.1.1332.1.1.5.3.110.2.1.1
		msanSyncBoardPosition OBJECT-TYPE
			SYNTAX INTEGER (1..20)
			MAX-ACCESS not-accessible
			STATUS current
			DESCRIPTION
				"Central ethernet board position."
			::= { msanSyncEntry 1 }

		
		-- 1.3.6.1.4.1.1332.1.1.5.3.110.2.1.2
		msanSyncSourcePriority OBJECT-TYPE
			SYNTAX INTEGER (1..6)
			MAX-ACCESS not-accessible
			STATUS current
			DESCRIPTION
				"Synchronization source priority: 1-first priority, 2-second priority....."
			::= { msanSyncEntry 2 }

		
		-- 1.3.6.1.4.1.1332.1.1.5.3.110.2.1.3
		msanSyncSourceType OBJECT-TYPE
			SYNTAX INTEGER
				{
				ext-2mhz(4),
				ext-10mhz(5),
				ext-1hz(6),
				mlvds-bp(8),
				pps-bp(14),
				ptp-eth(15),
				sync-eth(16),
				free-run(40)
				}
			MAX-ACCESS read-write
			STATUS current
			DESCRIPTION
				"Synchronization source type:
				ext-2mhz(4) - synchronization on extended source 2MHz,
				ext-10mhz(5) - synchronization on extended source 10MHz,
				ext-1hz(6) - synchronization on extended source 1Hz,
				mlvds-bp(8) - synchronization on MLVDS,
				pps-bp(14) - synchronization on PPS,
				ptp-eth(15)- synchronization on PtP Ethernet,
				sync-eth(16) - synchronization on Synchronous Ethernet,
				free-run(40) - free-run synchronization"
			::= { msanSyncEntry 3 }

		
		-- 1.3.6.1.4.1.1332.1.1.5.3.110.2.1.4
		msanSyncSourceId OBJECT-TYPE
			SYNTAX INTEGER
				{
				input-1(1),
				input-2(2)
				}
			MAX-ACCESS read-write
			STATUS current
			DESCRIPTION
				"Synchronization source identity.
				
				msanSyncSourceId can be used when msanSyncSourceType has one of values:
				- ext-2mhz(4), 
				- ext-10mhz(5), 
				- ext-1hz(6), 
				- mlvds-bp(8), 
				- pps-bp(14),
				- free-run(40)
				
				msanSyncSourceId can be set only to input-1(1), when msanSyncSourceType 
				is pps-bp(14) or free-run(40).
				"
			::= { msanSyncEntry 4 }

		
		-- 1.3.6.1.4.1.1332.1.1.5.3.110.2.1.5
		msanSyncSourceEthPortId OBJECT-TYPE
			SYNTAX InterfaceIndex
			MAX-ACCESS read-write
			STATUS current
			DESCRIPTION
				"Synchronization source ethernet Port Id (value of ifIndex).
				
				msanSyncSourceEthPortId can be used, when msanSyncSourceType 
				has ptp-eth(15) or sync-eth(16) value."
			::= { msanSyncEntry 5 }

		
		-- 1.3.6.1.4.1.1332.1.1.5.3.110.2.1.6
		msanSyncDestinationType OBJECT-TYPE
			SYNTAX INTEGER
				{
				local(0),
				global(10)
				}
			MAX-ACCESS read-write
			STATUS current
			DESCRIPTION
				"Synchronization destination type:
				local(0) - synchronization signal is used only on local board
				global(0) - synchronization signal is sent to MLVDS bus"
			::= { msanSyncEntry 6 }

		
		-- 1.3.6.1.4.1.1332.1.1.5.3.110.2.1.7
		msanSyncDestinationMlvdsId OBJECT-TYPE
			SYNTAX INTEGER
				{
				mlvds-1(1),
				mlvds-2(2)
				}
			MAX-ACCESS read-write
			STATUS current
			DESCRIPTION
				"Destination MLVDS bus Identity.
				This parameter is used when msanSyncDestinationType has global(1) value."
			::= { msanSyncEntry 7 }

		
		-- 1.3.6.1.4.1.1332.1.1.5.3.110.2.1.8
		msanSyncSourceSuitability OBJECT-TYPE
			SYNTAX INTEGER
				{
				undefined(0),
				suitable(1),
				unsuitable(2)
				}
			MAX-ACCESS read-only
			STATUS current
			DESCRIPTION
				"Source Suitability."
			::= { msanSyncEntry 8 }

		
		-- 1.3.6.1.4.1.1332.1.1.5.3.110.2.1.9
		msanSyncSourceActivity OBJECT-TYPE
			SYNTAX INTEGER
				{
				undefined(0),
				active(1),
				inactive(2)
				}
			MAX-ACCESS read-only
			STATUS current
			DESCRIPTION
				"Source Activity ."
			::= { msanSyncEntry 9 }

		
		-- 1.3.6.1.4.1.1332.1.1.5.3.110.2.1.10
		msanSyncRowStatus OBJECT-TYPE
			SYNTAX RowStatus
			MAX-ACCESS read-create
			STATUS current
			DESCRIPTION
				"The row status object controls the creation/deletion of rows in this table.
				Its semantics are the same as those for the RowStatus textual convention specified for SNMPv2.
				For row creation use createAndWait(5).
				For row activation use active(1).
				For row deletion use destroy(6).
				 	
				Other values are currently not supported.
				 	
				For row activation next terms must be defined
				- msanSyncSourceType
				- msanSyncSourceMlvdsId or msanSyncSourcePortId 
				- msanSyncDestionationType
				- msanSyncDestionaMlvdsId if msanSyncDestionType=global(10)
				"
			::= { msanSyncEntry 10 }

		
		-- 1.3.6.1.4.1.1332.1.1.5.3.111
		msanOnu OBJECT IDENTIFIER ::= { msanAdditionalConf 111 }

		
		-- 1.3.6.1.4.1.1332.1.1.5.3.111.1
		msanOnuGlobal OBJECT IDENTIFIER ::= { msanOnu 1 }

		
		-- 1.3.6.1.4.1.1332.1.1.5.3.111.1.1
		msanOnuUpgradeMethodManualStart OBJECT-TYPE
			SYNTAX INTEGER
				{
				enable(1),
				disable(2)
				}
			MAX-ACCESS read-write
			STATUS current
			DESCRIPTION
				"Start ONU manual upgrade method according to configuration in msanOnuUpgradeTable."
			DEFVAL { disable }
			::= { msanOnuGlobal 1 }

		
		-- 1.3.6.1.4.1.1332.1.1.5.3.111.1.10
		msanOnuAuthMetod OBJECT-TYPE
			SYNTAX INTEGER
				{
				serial(1),
				password(2),
				serialAndPassword(3),
				noAuthentication(4)
				}
			MAX-ACCESS read-write
			STATUS current
			DESCRIPTION
				"ONU authentication method."
			DEFVAL { serial }
			::= { msanOnuGlobal 10 }

		
		-- 1.3.6.1.4.1.1332.1.1.5.3.111.1.11
		msanOnuAuthAutoLearning OBJECT-TYPE
			SYNTAX INTEGER
				{
				enable(1),
				disable(2)
				}
			MAX-ACCESS read-write
			STATUS current
			DESCRIPTION
				"ONU serial number auto learning"
			DEFVAL { enable }
			::= { msanOnuGlobal 11 }

		
		-- 1.3.6.1.4.1.1332.1.1.5.3.111.1.13
		msanOnuBlackListChangeCnt OBJECT-TYPE
			SYNTAX Integer32
			MAX-ACCESS read-only
			STATUS current
			DESCRIPTION
				"ONU Blacklist change counter."
			::= { msanOnuGlobal 13 }

		
		-- 1.3.6.1.4.1.1332.1.1.5.3.111.1.14
		msanOnuIfOperStatusChangeCnt OBJECT-TYPE
			SYNTAX Integer32
			MAX-ACCESS read-only
			STATUS current
			DESCRIPTION
				"ONUs interface operational status change counter."
			::= { msanOnuGlobal 14 }

		
		-- 1.3.6.1.4.1.1332.1.1.5.3.111.1.15
		msanOnuDataEncryption OBJECT-TYPE
			SYNTAX INTEGER
				{
				enable(1),
				disable(2)
				}
			MAX-ACCESS read-write
			STATUS current
			DESCRIPTION
				"ONU/GEM downstream data encryption."
			::= { msanOnuGlobal 15 }

		
		-- 1.3.6.1.4.1.1332.1.1.5.3.111.1.16
		msanOnuDefaultConfigFileGet OBJECT-TYPE
			SYNTAX DisplayString
			MAX-ACCESS read-write
			STATUS current
			DESCRIPTION
				"msanOnuDefaultConfigFileGet parameter is used to start transfer of  ONU default config file from external tftp or ftp server to local file.
				Next syntax must be used for tftp or ftp transfer:
				tftp://<IP>|<hostname>[:<port>]/[<path>/]<remote_file_name> [<local_file_name>]
				ftp://<usr>[:<pass>]@<IP>|<hostname>[:<port>]/[<path>/]<remote_file_name>  [<local_file_name>]
				"
			DEFVAL { ''b }
			::= { msanOnuGlobal 16 }

		
		-- 1.3.6.1.4.1.1332.1.1.5.3.111.1.17
		msanOnuXgsAuthMetod OBJECT-TYPE
			SYNTAX INTEGER
				{
				serial(1),
				registrationid(2),
				serialAndRegistrationid(3),
				noAuthentication(4)
				}
			MAX-ACCESS read-write
			STATUS current
			DESCRIPTION
				"XGSPON ONU authentication method."
			DEFVAL { serial }
			::= { msanOnuGlobal 17 }

		
		-- 1.3.6.1.4.1.1332.1.1.5.3.111.2
		msanOnuCfgTable OBJECT-TYPE
			SYNTAX SEQUENCE OF MsanOnuCfgEntry
			MAX-ACCESS not-accessible
			STATUS current
			DESCRIPTION
				" "
			::= { msanOnu 2 }

		
		-- 1.3.6.1.4.1.1332.1.1.5.3.111.2.1
		msanOnuCfgEntry OBJECT-TYPE
			SYNTAX MsanOnuCfgEntry
			MAX-ACCESS not-accessible
			STATUS current
			DESCRIPTION
				"In case of GPON access blade, ifIndex (msanOnuCfgifIndex) for ONU interface (ifDescr=0/x/y) is calculated with formula:
				ifIndex=max_olt_port_number(8 or 16)+(x-1)*128+y   "
			INDEX { msanOnuCfgIfIndex }
			::= { msanOnuCfgTable 1 }

		
		MsanOnuCfgEntry ::=
			SEQUENCE { 
				msanOnuCfgIfIndex
					Integer32,
				msanOnuCfgPassword
					DisplayString,
				msanOnuCfgEnablePm
					INTEGER,
				msanOnuCfgSerialNumber
					DisplayString,
				msanOnuCfgAdminState
					INTEGER,
				msanOnuCfgOnuDhcpMode
					INTEGER,
				msanOnuCfgOnuIpAddress
					IpAddress,
				msanOnuCfgOnuIPMask
					IpAddress,
				msanOnuCfgOnuDefaultGateway
					IpAddress,
				msanOnuCfgOnuReset
					INTEGER,
				msanOnuCfgOnuResetBackupImage
					INTEGER,
				msanOnuCfgDefaultConfigFile
					DisplayString,
				msanOnuCfgSendConfig
					INTEGER,
				msanOnuCfgSendConfigStatus
					INTEGER,
				msanOnuCfgOnuResync
					INTEGER,
				msanOnuCfgOnuResetFactoryDefault
					INTEGER,
				msanOnuCfgPowerMeasurementsStart
					INTEGER,
				msanOnuCfgRegistrationId
					DisplayString,
				msanOnuCfgOnuPrimaryDnsIpAddress
					IpAddress,
				msanOnuCfgOnuSecondaryDnsIpAddress
					IpAddress,
				msanOnuCfgDataEncryption
					INTEGER
			 }

		-- 1.3.6.1.4.1.1332.1.1.5.3.111.2.1.1
		msanOnuCfgIfIndex OBJECT-TYPE
			SYNTAX Integer32
			MAX-ACCESS not-accessible
			STATUS current
			DESCRIPTION
				"Index of ONU interface (from ifTable)."
			::= { msanOnuCfgEntry 1 }

		
		-- 1.3.6.1.4.1.1332.1.1.5.3.111.2.1.2
		msanOnuCfgPassword OBJECT-TYPE
			SYNTAX DisplayString (SIZE (0..20))
			MAX-ACCESS read-create
			STATUS current
			DESCRIPTION
				"The expected password of the ONU."
			::= { msanOnuCfgEntry 2 }

		
		-- 1.3.6.1.4.1.1332.1.1.5.3.111.2.1.3
		msanOnuCfgEnablePm OBJECT-TYPE
			SYNTAX INTEGER
				{
				enable(1),
				disable(2)
				}
			MAX-ACCESS read-create
			STATUS current
			DESCRIPTION
				"ONU  PM (Performance Management) collection. "
			::= { msanOnuCfgEntry 3 }

		
		-- 1.3.6.1.4.1.1332.1.1.5.3.111.2.1.4
		msanOnuCfgSerialNumber OBJECT-TYPE
			SYNTAX DisplayString (SIZE (0..12))
			MAX-ACCESS read-create
			STATUS current
			DESCRIPTION
				"The expected serial number (12 bytes), which  is unique for each ONU. It is defined in ITU-T G.984.3 
				and contains the vendor id and version number. The first four bytes are an ASCII encoded 
				vendor ID four letter mnemonic. The next eight bytes are an ASCII encoded version number (four hex values).
				Example: ISKT01C2AA5B
				
				To delete serial number use empty string."
			::= { msanOnuCfgEntry 4 }

		
		-- 1.3.6.1.4.1.1332.1.1.5.3.111.2.1.5
		msanOnuCfgAdminState OBJECT-TYPE
			SYNTAX INTEGER
				{
				enable(1),
				disable(2)
				}
			MAX-ACCESS read-create
			STATUS current
			DESCRIPTION
				"This attribute enable(1) and disable(2) the functions performed by this managed entity. 
				When the administrative state is set to disable(lock), all user functions are blocked, and alarms, TCAs 
				and AVCs for this managed entity and all dependent managed entities are no longer generated. 
				"
			::= { msanOnuCfgEntry 5 }

		
		-- 1.3.6.1.4.1.1332.1.1.5.3.111.2.1.6
		msanOnuCfgOnuDhcpMode OBJECT-TYPE
			SYNTAX INTEGER
				{
				enable(1),
				disable(2)
				}
			MAX-ACCESS read-create
			STATUS current
			DESCRIPTION
				"ONU DHCP client mode.
				"
			::= { msanOnuCfgEntry 6 }

		
		-- 1.3.6.1.4.1.1332.1.1.5.3.111.2.1.7
		msanOnuCfgOnuIpAddress OBJECT-TYPE
			SYNTAX IpAddress
			MAX-ACCESS read-create
			STATUS current
			DESCRIPTION
				"The current IP address of the ONU. This column can be written only if the DHCP mode 
				is set to false. If the DHCP mode is set to true, this column can NOT be written."
			::= { msanOnuCfgEntry 7 }

		
		-- 1.3.6.1.4.1.1332.1.1.5.3.111.2.1.8
		msanOnuCfgOnuIPMask OBJECT-TYPE
			SYNTAX IpAddress
			MAX-ACCESS read-create
			STATUS current
			DESCRIPTION
				"The current IP Mask of the ONU. This column can be written only if the DHCP mode is 
				set to false. If the DHCP mode is set to true, this column can NOT be written."
			::= { msanOnuCfgEntry 8 }

		
		-- 1.3.6.1.4.1.1332.1.1.5.3.111.2.1.9
		msanOnuCfgOnuDefaultGateway OBJECT-TYPE
			SYNTAX IpAddress
			MAX-ACCESS read-create
			STATUS current
			DESCRIPTION
				"The current default gateway of the ONU. This column can be written only if the DHCP 
				mode is set to false. If the DHCP mode is set to true, this column can NOT be written."
			::= { msanOnuCfgEntry 9 }

		
		-- 1.3.6.1.4.1.1332.1.1.5.3.111.2.1.10
		msanOnuCfgOnuReset OBJECT-TYPE
			SYNTAX INTEGER
				{
				enable(1),
				disable(2)
				}
			MAX-ACCESS read-write
			STATUS current
			DESCRIPTION
				"Set this option to ¡enable¡to initiate a reboot action on the ONU. This column can be 
				used to reboot the ONU after Software upgrade. After the reboot command is sent to the ONU, 
				this column is set to ¡disable¡again by the OLT application. "
			::= { msanOnuCfgEntry 10 }

		
		-- 1.3.6.1.4.1.1332.1.1.5.3.111.2.1.11
		msanOnuCfgOnuResetBackupImage OBJECT-TYPE
			SYNTAX INTEGER
				{
				enable(1),
				disable(2)
				}
			MAX-ACCESS read-write
			STATUS current
			DESCRIPTION
				"Set this option to 'enable' to initiate a reboot action on the ONU and 
				switch to a backup SW image."
			::= { msanOnuCfgEntry 11 }

		
		-- 1.3.6.1.4.1.1332.1.1.5.3.111.2.1.12
		msanOnuCfgDefaultConfigFile OBJECT-TYPE
			SYNTAX DisplayString
			MAX-ACCESS read-create
			STATUS current
			DESCRIPTION
				"ONU config default file (this is reference to msanOnuDefaultConfigFileName)."
			::= { msanOnuCfgEntry 12 }

		
		-- 1.3.6.1.4.1.1332.1.1.5.3.111.2.1.13
		msanOnuCfgSendConfig OBJECT-TYPE
			SYNTAX INTEGER
				{
				enable(1),
				disable(2)
				}
			MAX-ACCESS read-write
			STATUS current
			DESCRIPTION
				"Send default config file and config attributes to ONU."
			DEFVAL { disable }
			::= { msanOnuCfgEntry 13 }

		
		-- 1.3.6.1.4.1.1332.1.1.5.3.111.2.1.14
		msanOnuCfgSendConfigStatus OBJECT-TYPE
			SYNTAX INTEGER
				{
				ok(1),
				pending(2),
				notApplicable(3),
				error(4),
				wrongStatus(5),
				notStarted(6)
				}
			MAX-ACCESS read-only
			STATUS current
			DESCRIPTION
				"Status of sending default config file and config attributes to ONU."
			DEFVAL { notStarted }
			::= { msanOnuCfgEntry 14 }

		
		-- 1.3.6.1.4.1.1332.1.1.5.3.111.2.1.15
		msanOnuCfgOnuResync OBJECT-TYPE
			SYNTAX INTEGER
				{
				enable(1),
				disable(2)
				}
			MAX-ACCESS read-write
			STATUS current
			DESCRIPTION
				"Re-sync OMCI MIB"
			DEFVAL { disable }
			::= { msanOnuCfgEntry 15 }

		
		-- 1.3.6.1.4.1.1332.1.1.5.3.111.2.1.16
		msanOnuCfgOnuResetFactoryDefault OBJECT-TYPE
			SYNTAX INTEGER
				{
				enable(1),
				disable(2)
				}
			MAX-ACCESS read-write
			STATUS current
			DESCRIPTION
				"Set this option to 'enable' to initiate a reboot to factory default action on the ONU."
			::= { msanOnuCfgEntry 16 }

		
		-- 1.3.6.1.4.1.1332.1.1.5.3.111.2.1.17
		msanOnuCfgPowerMeasurementsStart OBJECT-TYPE
			SYNTAX INTEGER
				{
				enable(1),
				disable(2)
				}
			MAX-ACCESS read-write
			STATUS current
			DESCRIPTION
				"Start ONU/OLT  Rx/Tx Power Measurements "
			DEFVAL { disable }
			::= { msanOnuCfgEntry 17 }

		
		-- 1.3.6.1.4.1.1332.1.1.5.3.111.2.1.18
		msanOnuCfgRegistrationId OBJECT-TYPE
			SYNTAX DisplayString (SIZE (0..36))
			MAX-ACCESS read-create
			STATUS current
			DESCRIPTION
				"The expected Registrationid of the XGSPON ONU."
			::= { msanOnuCfgEntry 18 }

		
		-- 1.3.6.1.4.1.1332.1.1.5.3.111.2.1.19
		msanOnuCfgOnuPrimaryDnsIpAddress OBJECT-TYPE
			SYNTAX IpAddress
			MAX-ACCESS read-create
			STATUS current
			DESCRIPTION
				"The Primary DNS server IP. This parameter can be written only if the DHCP mode 
				is set to false. If the DHCP mode is set to true, this column can NOT be written."
			::= { msanOnuCfgEntry 19 }

		
		-- 1.3.6.1.4.1.1332.1.1.5.3.111.2.1.20
		msanOnuCfgOnuSecondaryDnsIpAddress OBJECT-TYPE
			SYNTAX IpAddress
			MAX-ACCESS read-create
			STATUS current
			DESCRIPTION
				"The Secondary DNS server IP. This parameter can be written only if the DHCP mode 
				is set to false. If the DHCP mode is set to true, this column can NOT be written."
			::= { msanOnuCfgEntry 20 }

		
		-- 1.3.6.1.4.1.1332.1.1.5.3.111.2.1.21
		msanOnuCfgDataEncryption OBJECT-TYPE
			SYNTAX INTEGER
				{
				enable(1),
				disable(2)
				}
			MAX-ACCESS read-write
			STATUS current
			DESCRIPTION
				"ONU/GEM downstream data encryption."
			::= { msanOnuCfgEntry 21 }

		
		-- 1.3.6.1.4.1.1332.1.1.5.3.111.3
		msanOnuInfoTable OBJECT-TYPE
			SYNTAX SEQUENCE OF MsanOnuInfoEntry
			MAX-ACCESS not-accessible
			STATUS current
			DESCRIPTION
				" "
			::= { msanOnu 3 }

		
		-- 1.3.6.1.4.1.1332.1.1.5.3.111.3.1
		msanOnuInfoEntry OBJECT-TYPE
			SYNTAX MsanOnuInfoEntry
			MAX-ACCESS not-accessible
			STATUS current
			DESCRIPTION
				"Row Description"
			INDEX { msanOnuInfoIfIndex }
			::= { msanOnuInfoTable 1 }

		
		MsanOnuInfoEntry ::=
			SEQUENCE { 
				msanOnuInfoIfIndex
					Integer32,
				msanOnuInfoPrimaryStatus
					INTEGER,
				msanOnuInfoEqualizationDelay
					Unsigned32,
				msanOnuInfoPowerLevel
					INTEGER,
				msanOnuInfoVendorId
					DisplayString,
				msanOnuInfoVersion
					DisplayString,
				msanOnuInfoTrafficManagementOption
					INTEGER,
				msanOnuInfoOperState
					INTEGER,
				msanOnuInfoEquipmentId
					OCTET STRING,
				msanOnuInfoOmccVersion
					INTEGER,
				msanOnuInfoOnuHardwareType
					Unsigned32,
				msanOnuInfoHardwareRevision
					Unsigned32,
				msanOnuInfoSecurityCapability
					Unsigned32,
				msanOnuInfoTotalPriorityQueueNumber
					Unsigned32,
				msanOnuInfoTotalTrafficSchedulerNumber
					Unsigned32,
				msanOnuInfoTotalGemPortNumber
					Unsigned32,
				msanOnuInfoTotalTcontNumber
					Unsigned32,
				msanOnuInfoTotalEthernetUniNumber
					Unsigned32,
				msanOnuInfoTotalPotsUniNumber
					Unsigned32,
				msanOnuInfoSysUpTime
					Unsigned32,
				msanOnuInfoOnuImageInstance0Version
					DisplayString,
				msanOnuInfoOnuImageInstance0Valid
					TruthValue,
				msanOnuInfoOnuImageInstance0Activate
					TruthValue,
				msanOnuInfoOnuImageInstance0Commit
					TruthValue,
				msanOnuInfoOnuImageInstance1Version
					DisplayString,
				msanOnuInfoOnuImageInstance1Valid
					TruthValue,
				msanOnuInfoOnuImageInstance1Activate
					TruthValue,
				msanOnuInfoOnuImageInstance1Commit
					TruthValue,
				msanOnuInfoOnuMacAddress
					MacAddress,
				msanOnuInfoOnuDhcpMode
					TruthValue,
				msanOnuInfoOnuIpAddress
					IpAddress,
				msanOnuInfoOnuIpMask
					IpAddress,
				msanOnuInfoOnuDefaultGateway
					IpAddress,
				msanOnuInfoOnuFastLeaveCapability
					Unsigned32,
				msanOnuInfoSerialNumber
					DisplayString,
				msanOnuInfoPassword
					DisplayString,
				msanOnuInfoRxPower
					Integer32,
				msanOnuInfoTxPower
					Integer32,
				msanOnuInfoOltRxPower
					Integer32,
				msanOnuInfoTemp
					Integer32,
				msanOnuInfoPowerMeasurementsStarted
					DisplayString,
				msanOnuInfoDistance
					Gauge32,
				msanOnuInfoDeactivateReason
					DisplayString,
				msanOnuInfoRegistrationid
					DisplayString
			 }

		-- 1.3.6.1.4.1.1332.1.1.5.3.111.3.1.1
		msanOnuInfoIfIndex OBJECT-TYPE
			SYNTAX Integer32
			MAX-ACCESS not-accessible
			STATUS current
			DESCRIPTION
				"Index of ONU interface (from ifTable)."
			::= { msanOnuInfoEntry 1 }

		
		-- 1.3.6.1.4.1.1332.1.1.5.3.111.3.1.2
		msanOnuInfoPrimaryStatus OBJECT-TYPE
			SYNTAX INTEGER
				{
				invalid(0),
				inactive(1),
				activatePending(2),
				active(3),
				deactivatePending(4),
				disablePending(5),
				disabled(6)
				}
			MAX-ACCESS read-only
			STATUS current
			DESCRIPTION
				"invalid(0), inactive(1), activatePending(2), active(3),deactivatePending(4), 
				disablePending(5), disabled(6) "
			::= { msanOnuInfoEntry 2 }

		
		-- 1.3.6.1.4.1.1332.1.1.5.3.111.3.1.3
		msanOnuInfoEqualizationDelay OBJECT-TYPE
			SYNTAX Unsigned32
			MAX-ACCESS read-only
			STATUS current
			DESCRIPTION
				"Equalization delay for display."
			::= { msanOnuInfoEntry 3 }

		
		-- 1.3.6.1.4.1.1332.1.1.5.3.111.3.1.4
		msanOnuInfoPowerLevel OBJECT-TYPE
			SYNTAX INTEGER
			MAX-ACCESS read-only
			STATUS current
			DESCRIPTION
				"Power level."
			::= { msanOnuInfoEntry 4 }

		
		-- 1.3.6.1.4.1.1332.1.1.5.3.111.3.1.5
		msanOnuInfoVendorId OBJECT-TYPE
			SYNTAX DisplayString (SIZE (4))
			MAX-ACCESS read-only
			STATUS current
			DESCRIPTION
				"This attribute identifies the vendor of the ONT.It is the same as 
				the four most significant bytes of the ONT serial number as specified in 
				ITU-T Rec. G.984.3. (R) (mandatory) (4 bytes). "
			::= { msanOnuInfoEntry 5 }

		
		-- 1.3.6.1.4.1.1332.1.1.5.3.111.3.1.7
		msanOnuInfoVersion OBJECT-TYPE
			SYNTAX DisplayString
			MAX-ACCESS read-only
			STATUS current
			DESCRIPTION
				"This attribute identifies the version of the ONT as defined by the 
				vendor. Then character value ¡°0¡± indicates that version information is not
				available or applicable."
			::= { msanOnuInfoEntry 7 }

		
		-- 1.3.6.1.4.1.1332.1.1.5.3.111.3.1.8
		msanOnuInfoTrafficManagementOption OBJECT-TYPE
			SYNTAX INTEGER
				{
				priorityControlledAndFlexiblyScheduledUpstreamTraffic(0),
				rateControlledUpstreamTraffic(1)
				}
			MAX-ACCESS read-only
			STATUS current
			DESCRIPTION
				"This attribute identifies the upstream traffic management function implemented
				in the ONT. There are two options: 
				0 Priority controlled and flexibly scheduled upstream traffic. The traffic scheduler and 
						priority queue mechanism are used for upstream traffic. 
				1 Rate controlled upstream traffic. The maximum upstream traffic of each individual 
						connection is guaranteed"
			DEFVAL { 0 }
			::= { msanOnuInfoEntry 8 }

		
		-- 1.3.6.1.4.1.1332.1.1.5.3.111.3.1.9
		msanOnuInfoOperState OBJECT-TYPE
			SYNTAX INTEGER
				{
				enabled(1),
				disabled(2),
				unknown(3)
				}
			MAX-ACCESS read-only
			STATUS current
			DESCRIPTION
				"This attribute reports whether the managed entity is currently capable of performing its
				function."
			::= { msanOnuInfoEntry 9 }

		
		-- 1.3.6.1.4.1.1332.1.1.5.3.111.3.1.10
		msanOnuInfoEquipmentId OBJECT-TYPE
			SYNTAX OCTET STRING (SIZE (20))
			MAX-ACCESS read-only
			STATUS current
			DESCRIPTION
				"This attribute may be used to identify the specific type of ONT. In North America, 
				this may be the equipment CLEI code. (R) (optional) (20 bytes)."
			::= { msanOnuInfoEntry 10 }

		
		-- 1.3.6.1.4.1.1332.1.1.5.3.111.3.1.11
		msanOnuInfoOmccVersion OBJECT-TYPE
			SYNTAX INTEGER
				{
				g-984-4(128),
				g-984-4amd1(129),
				g-984-4amd2(130),
				g-984-4amd3(131),
				g-984-42007to2008(132)
				}
			MAX-ACCESS read-only
			STATUS current
			DESCRIPTION
				"This attribute identifies the version of the OMCC protocol being used by the ONT. 
				This allows the OLT to manage a network with ONTs that support different OMCC versions. 
				Release levels of G.984.4 may be supported with the following code points: 
				0x80 G.984.4 06/04. Note: for historic reasons, this codepoint may also appear in ONTs that
						support later versions of G.984.4. 
				0x81 G.984.4 amd 1 (06/05) ITU-T Rec. G.984.4 (02/2008) 51 
				0x82 G.984.4 amd 2 (03/06) 
				0x83 G.984.4 amd 3 (12/06) 
				0x84 G.984.4 2007-2008 current draft (R) (mandatory) (1 byte)"
			::= { msanOnuInfoEntry 11 }

		
		-- 1.3.6.1.4.1.1332.1.1.5.3.111.3.1.12
		msanOnuInfoOnuHardwareType OBJECT-TYPE
			SYNTAX Unsigned32
			MAX-ACCESS read-only
			STATUS current
			DESCRIPTION
				"Most significant byte of vendor product code which provides a vendor-specific product 
				code for the ONT.(R) (optional) (2 bytes)."
			::= { msanOnuInfoEntry 12 }

		
		-- 1.3.6.1.4.1.1332.1.1.5.3.111.3.1.13
		msanOnuInfoHardwareRevision OBJECT-TYPE
			SYNTAX Unsigned32
			MAX-ACCESS read-only
			STATUS obsolete
			DESCRIPTION
				"Least significant byte of vendor product code which provides a vendor-specific product 
				code or the ONT.(R) (optional) (2 bytes). "
			::= { msanOnuInfoEntry 13 }

		
		-- 1.3.6.1.4.1.1332.1.1.5.3.111.3.1.14
		msanOnuInfoSecurityCapability OBJECT-TYPE
			SYNTAX Unsigned32 (1..255)
			MAX-ACCESS read-only
			STATUS current
			DESCRIPTION
				"This attribute advertises the security capabilities of the ONT. The following codepoints
				are defined: 
				1 Reserved 
				2 AES 
				3..255 Reserved (R) (mandatory) (1 byte). "
			DEFVAL { 2 }
			::= { msanOnuInfoEntry 14 }

		
		-- 1.3.6.1.4.1.1332.1.1.5.3.111.3.1.15
		msanOnuInfoTotalPriorityQueueNumber OBJECT-TYPE
			SYNTAX Unsigned32
			MAX-ACCESS read-only
			STATUS current
			DESCRIPTION
				"This attribute reports the total number of priority queues that are not associated with 
				a circuit pack, but with the ONT in its entirety. The maximum value is 0x0FFF. Upon ME instantiation, 
				he ONT sets this attribute to the value that represents its capabilities. (R) (mandatory) (2 bytes). "
			::= { msanOnuInfoEntry 15 }

		
		-- 1.3.6.1.4.1.1332.1.1.5.3.111.3.1.16
		msanOnuInfoTotalTrafficSchedulerNumber OBJECT-TYPE
			SYNTAX Unsigned32
			MAX-ACCESS read-only
			STATUS current
			DESCRIPTION
				"This attribute reports the total number of traffic schedulers that are not associated 
				with a circuit pack, but with the ONT in its entirety. The ONT supports null function, HOL scheduling 
				and WRR from the priority control and guarantee of minimum rate control points of view, respectively. 
				If the ONT has no traffic schedulers, this attribute is 0. (R) (mandatory) (1 byte)."
			::= { msanOnuInfoEntry 16 }

		
		-- 1.3.6.1.4.1.1332.1.1.5.3.111.3.1.17
		msanOnuInfoTotalGemPortNumber OBJECT-TYPE
			SYNTAX Unsigned32 (0..4095)
			MAX-ACCESS read-only
			STATUS current
			DESCRIPTION
				"This attribute reports the total number of GEM port-IDs supported by the ONT. The maximum
				value is 0x0FFF. Upon ME instantiation, the ONT sets this attribute to the value that represents
				its capabilities. (R) (optional) (2 bytes)."
			::= { msanOnuInfoEntry 17 }

		
		-- 1.3.6.1.4.1.1332.1.1.5.3.111.3.1.18
		msanOnuInfoTotalTcontNumber OBJECT-TYPE
			SYNTAX Unsigned32
			MAX-ACCESS read-only
			STATUS current
			DESCRIPTION
				"This attribute reports the total number of T-CONTs supported by the ONT."
			::= { msanOnuInfoEntry 18 }

		
		-- 1.3.6.1.4.1.1332.1.1.5.3.111.3.1.19
		msanOnuInfoTotalEthernetUniNumber OBJECT-TYPE
			SYNTAX Unsigned32
			MAX-ACCESS read-only
			STATUS current
			DESCRIPTION
				"The number of Ethernet UNI ports."
			::= { msanOnuInfoEntry 19 }

		
		-- 1.3.6.1.4.1.1332.1.1.5.3.111.3.1.20
		msanOnuInfoTotalPotsUniNumber OBJECT-TYPE
			SYNTAX Unsigned32
			MAX-ACCESS read-only
			STATUS current
			DESCRIPTION
				"The number of POTS UNI ports."
			::= { msanOnuInfoEntry 20 }

		
		-- 1.3.6.1.4.1.1332.1.1.5.3.111.3.1.21
		msanOnuInfoSysUpTime OBJECT-TYPE
			SYNTAX Unsigned32
			MAX-ACCESS read-only
			STATUS current
			DESCRIPTION
				"This attribute counts the 10 ms intervals since the ONT was last initialized. It rolls 
				over to 0 when full. (See RFC 1213.) (R) (optional) (4 bytes)."
			::= { msanOnuInfoEntry 21 }

		
		-- 1.3.6.1.4.1.1332.1.1.5.3.111.3.1.22
		msanOnuInfoOnuImageInstance0Version OBJECT-TYPE
			SYNTAX DisplayString
			MAX-ACCESS read-only
			STATUS current
			DESCRIPTION
				"This attribute identifies the version of the ONT as defined by the 
				vendor. Then character value ¡°0¡± indicates that version information is not
				available or applicable. (R) (mandatory) (14 bytes)."
			::= { msanOnuInfoEntry 22 }

		
		-- 1.3.6.1.4.1.1332.1.1.5.3.111.3.1.23
		msanOnuInfoOnuImageInstance0Valid OBJECT-TYPE
			SYNTAX TruthValue
			MAX-ACCESS read-only
			STATUS current
			DESCRIPTION
				"The valid flag of ONU image instance 0."
			::= { msanOnuInfoEntry 23 }

		
		-- 1.3.6.1.4.1.1332.1.1.5.3.111.3.1.24
		msanOnuInfoOnuImageInstance0Activate OBJECT-TYPE
			SYNTAX TruthValue
			MAX-ACCESS read-only
			STATUS current
			DESCRIPTION
				"The activate flag of ONU image instance 0."
			::= { msanOnuInfoEntry 24 }

		
		-- 1.3.6.1.4.1.1332.1.1.5.3.111.3.1.25
		msanOnuInfoOnuImageInstance0Commit OBJECT-TYPE
			SYNTAX TruthValue
			MAX-ACCESS read-only
			STATUS current
			DESCRIPTION
				"The commit flag of ONU image instance 0."
			::= { msanOnuInfoEntry 25 }

		
		-- 1.3.6.1.4.1.1332.1.1.5.3.111.3.1.26
		msanOnuInfoOnuImageInstance1Version OBJECT-TYPE
			SYNTAX DisplayString
			MAX-ACCESS read-only
			STATUS current
			DESCRIPTION
				"This attribute identifies the version of the ONT as defined by the 
				vendor. Then character value ¡°0¡± indicates that version information is not
				available or applicable. (R) (mandatory) (14 bytes). "
			::= { msanOnuInfoEntry 26 }

		
		-- 1.3.6.1.4.1.1332.1.1.5.3.111.3.1.27
		msanOnuInfoOnuImageInstance1Valid OBJECT-TYPE
			SYNTAX TruthValue
			MAX-ACCESS read-only
			STATUS current
			DESCRIPTION
				"The valid flag of ONU image instance 1 "
			::= { msanOnuInfoEntry 27 }

		
		-- 1.3.6.1.4.1.1332.1.1.5.3.111.3.1.28
		msanOnuInfoOnuImageInstance1Activate OBJECT-TYPE
			SYNTAX TruthValue
			MAX-ACCESS read-only
			STATUS current
			DESCRIPTION
				"The activate flag of ONU image instance 1."
			::= { msanOnuInfoEntry 28 }

		
		-- 1.3.6.1.4.1.1332.1.1.5.3.111.3.1.29
		msanOnuInfoOnuImageInstance1Commit OBJECT-TYPE
			SYNTAX TruthValue
			MAX-ACCESS read-only
			STATUS current
			DESCRIPTION
				"The commit flag of ONU image instance 1."
			::= { msanOnuInfoEntry 29 }

		
		-- 1.3.6.1.4.1.1332.1.1.5.3.111.3.1.30
		msanOnuInfoOnuMacAddress OBJECT-TYPE
			SYNTAX MacAddress
			MAX-ACCESS read-only
			STATUS current
			DESCRIPTION
				"The MAC address of the ONU in hexadecimal format."
			::= { msanOnuInfoEntry 30 }

		
		-- 1.3.6.1.4.1.1332.1.1.5.3.111.3.1.31
		msanOnuInfoOnuDhcpMode OBJECT-TYPE
			SYNTAX TruthValue
			MAX-ACCESS read-only
			STATUS current
			DESCRIPTION
				"ONU DHCP mode: 
				1 Enabled 
				2 Disabled "
			DEFVAL { 2 }
			::= { msanOnuInfoEntry 31 }

		
		-- 1.3.6.1.4.1.1332.1.1.5.3.111.3.1.32
		msanOnuInfoOnuIpAddress OBJECT-TYPE
			SYNTAX IpAddress
			MAX-ACCESS read-only
			STATUS current
			DESCRIPTION
				"The current IP address of the ONU. "
			::= { msanOnuInfoEntry 32 }

		
		-- 1.3.6.1.4.1.1332.1.1.5.3.111.3.1.33
		msanOnuInfoOnuIpMask OBJECT-TYPE
			SYNTAX IpAddress
			MAX-ACCESS read-only
			STATUS current
			DESCRIPTION
				"The current IP Mask of the ONU. "
			::= { msanOnuInfoEntry 33 }

		
		-- 1.3.6.1.4.1.1332.1.1.5.3.111.3.1.34
		msanOnuInfoOnuDefaultGateway OBJECT-TYPE
			SYNTAX IpAddress
			MAX-ACCESS read-only
			STATUS current
			DESCRIPTION
				"The current default gateway of the ONU. "
			::= { msanOnuInfoEntry 34 }

		
		-- 1.3.6.1.4.1.1332.1.1.5.3.111.3.1.35
		msanOnuInfoOnuFastLeaveCapability OBJECT-TYPE
			SYNTAX Unsigned32 (0..16)
			MAX-ACCESS read-only
			STATUS current
			DESCRIPTION
				"This attribute specifies Fast leave capability. It¡¯s carried in a proprietary OMCI remote DEBUG ME,
				Bit value 0 not support
				Bit value 1 support
				
				Bit 0 fast leave in CTC distributed mode
				Bit 1 non fast leave in CTC distributed mode
				Bit 2 fast leave in CTC controllable mode
				Bit 3 non fast leave in CTC controllable mode
				"
			DEFVAL { 2 }
			::= { msanOnuInfoEntry 35 }

		
		-- 1.3.6.1.4.1.1332.1.1.5.3.111.3.1.36
		msanOnuInfoSerialNumber OBJECT-TYPE
			SYNTAX DisplayString (SIZE (12))
			MAX-ACCESS read-only
			STATUS current
			DESCRIPTION
				"Current serial number, which  is unique for each ONU. It is defined in ITU-T G.984.3 
				and contains the vendor id and version number. The first four bytes are an ASCII encoded 
				vendor ID four letter mnemonic. The next eight bytes are an ASCII encoded version number (four hex values).
				Example: ISKT01C2AA5B"
			::= { msanOnuInfoEntry 36 }

		
		-- 1.3.6.1.4.1.1332.1.1.5.3.111.3.1.37
		msanOnuInfoPassword OBJECT-TYPE
			SYNTAX DisplayString (SIZE (0..20))
			MAX-ACCESS read-only
			STATUS current
			DESCRIPTION
				"Received password of the ONU."
			::= { msanOnuInfoEntry 37 }

		
		-- 1.3.6.1.4.1.1332.1.1.5.3.111.3.1.38
		msanOnuInfoRxPower OBJECT-TYPE
			SYNTAX Integer32
			UNITS "0.01 dBm"
			MAX-ACCESS read-only
			STATUS current
			DESCRIPTION
				"ONU receive (Rx) power measurement."
			::= { msanOnuInfoEntry 38 }

		
		-- 1.3.6.1.4.1.1332.1.1.5.3.111.3.1.39
		msanOnuInfoTxPower OBJECT-TYPE
			SYNTAX Integer32
			UNITS "0.01 dBm"
			MAX-ACCESS read-only
			STATUS current
			DESCRIPTION
				"ONU transmit (Tx) power measurement."
			::= { msanOnuInfoEntry 39 }

		
		-- 1.3.6.1.4.1.1332.1.1.5.3.111.3.1.40
		msanOnuInfoOltRxPower OBJECT-TYPE
			SYNTAX Integer32
			UNITS "0.01 dBm"
			MAX-ACCESS read-only
			STATUS current
			DESCRIPTION
				"OLT receive (Rx) power measurement."
			::= { msanOnuInfoEntry 40 }

		
		-- 1.3.6.1.4.1.1332.1.1.5.3.111.3.1.41
		msanOnuInfoTemp OBJECT-TYPE
			SYNTAX Integer32
			UNITS "Celsius"
			MAX-ACCESS read-only
			STATUS current
			DESCRIPTION
				"ONU current temperature (in Celsius)."
			::= { msanOnuInfoEntry 41 }

		
		-- 1.3.6.1.4.1.1332.1.1.5.3.111.3.1.42
		msanOnuInfoPowerMeasurementsStarted OBJECT-TYPE
			SYNTAX DisplayString (SIZE (0..20))
			MAX-ACCESS read-only
			STATUS current
			DESCRIPTION
				"Info when Rx/Tx power measurements were started."
			::= { msanOnuInfoEntry 42 }

		
		-- 1.3.6.1.4.1.1332.1.1.5.3.111.3.1.43
		msanOnuInfoDistance OBJECT-TYPE
			SYNTAX Gauge32
			UNITS "metre"
			MAX-ACCESS read-only
			STATUS current
			DESCRIPTION
				"ONU distance in metre."
			::= { msanOnuInfoEntry 43 }

		
		-- 1.3.6.1.4.1.1332.1.1.5.3.111.3.1.44
		msanOnuInfoDeactivateReason OBJECT-TYPE
			SYNTAX DisplayString
			MAX-ACCESS read-only
			STATUS current
			DESCRIPTION
				"ONU deactivate reason."
			::= { msanOnuInfoEntry 44 }

		
		-- 1.3.6.1.4.1.1332.1.1.5.3.111.3.1.45
		msanOnuInfoRegistrationid OBJECT-TYPE
			SYNTAX DisplayString (SIZE (0..36))
			MAX-ACCESS read-only
			STATUS current
			DESCRIPTION
				"Received Registrationid of the XGSPON ONU."
			::= { msanOnuInfoEntry 45 }

		
		-- 1.3.6.1.4.1.1332.1.1.5.3.111.4
		msanOnuUpgradeTable OBJECT-TYPE
			SYNTAX SEQUENCE OF MsanOnuUpgradeEntry
			MAX-ACCESS not-accessible
			STATUS current
			DESCRIPTION
				"Description."
			::= { msanOnu 4 }

		
		-- 1.3.6.1.4.1.1332.1.1.5.3.111.4.1
		msanOnuUpgradeEntry OBJECT-TYPE
			SYNTAX MsanOnuUpgradeEntry
			MAX-ACCESS not-accessible
			STATUS current
			DESCRIPTION
				"Description."
			INDEX { msanOnuUpgradeMethod }
			::= { msanOnuUpgradeTable 1 }

		
		MsanOnuUpgradeEntry ::=
			SEQUENCE { 
				msanOnuUpgradeMethod
					INTEGER,
				msanOnuUpgradeOption
					INTEGER,
				msanOnuUpgradeRebootMode
					INTEGER,
				msanOnuUpgradeImageInstance
					Integer32,
				msanOnuUpgradeScheduledTime
					DisplayString,
				msanOnuUpgradeRebootScheduledTime
					DisplayString,
				msanOnuUpgradeParticipantPortListBitMap
					OCTET STRING,
				msanOnuUpgradeProgressDownloadPortListBitMap
					OCTET STRING,
				msanOnuUpgradeProgressActivatePortListBitMap
					OCTET STRING,
				msanOnuUpgradeProgressCommitPortListBitMap
					OCTET STRING,
				msanOnuUpgradeProgressFinalPortListBitMap
					OCTET STRING,
				msanOnuUpgradeResultFinalPortListBitMap
					OCTET STRING
			 }

		-- 1.3.6.1.4.1.1332.1.1.5.3.111.4.1.1
		msanOnuUpgradeMethod OBJECT-TYPE
			SYNTAX INTEGER
				{
				manual(1),
				scheduled(2),
				automatic(3)
				}
			MAX-ACCESS not-accessible
			STATUS current
			DESCRIPTION
				" 	1 Manual - in which the EMS initiates upgrade operation.
				Manual upgrade procedure starts when global parameter msanOnuUpgradeMethodManualStart
				              is set to enable. 
				
				2 Scheduled - in which the EMS specifies the ONU list and the time when the upgrade 
				should start. Only one scheduled task entry can exist in the table, and it is  always valid even 
				             after their execution. 
				
				3 Automatic - in which the ONU is upgraded automatically when it is 
				discovered. Only one automatic task entry can exist in the 
				table, and it is always valid even after its execution. "
			::= { msanOnuUpgradeEntry 1 }

		
		-- 1.3.6.1.4.1.1332.1.1.5.3.111.4.1.2
		msanOnuUpgradeOption OBJECT-TYPE
			SYNTAX INTEGER
				{
				normal(1),
				forced(2)
				}
			MAX-ACCESS read-only
			STATUS current
			DESCRIPTION
				"ONU upgrade option: 
				1 Normal. If the target version is newer than the current version, then the image download will start.  
				2 Forced. The image download will always start. 
				"
			DEFVAL { normal }
			::= { msanOnuUpgradeEntry 2 }

		
		-- 1.3.6.1.4.1.1332.1.1.5.3.111.4.1.3
		msanOnuUpgradeRebootMode OBJECT-TYPE
			SYNTAX INTEGER
				{
				automatic(1),
				manual(2),
				scheduled(3)
				}
			MAX-ACCESS read-write
			STATUS current
			DESCRIPTION
				"It defines the reboot action after the image is downloaded to the ONU: 
				1 - Automatic. ONU will be rebooted during image activation. The complete upgrade 
				    procedure will be executed automatically: download -> activate (reboot) -> commit. 
				2 - Manual. The following upgrade procedure will be executed: download -> commit. The 
				    ONU can be rebooted via onuReset of ONU configuration table. 
				3 - Scheduled. The ONU will be rebooted automatically at onuUpgradeRebootScheduledTime. The 
				    following upgrade procedure will be executed: download -> commit -> activate (reboot) at 
				    onuUpgradeRebootScheduledTime. 
				"
			DEFVAL { automatic }
			::= { msanOnuUpgradeEntry 3 }

		
		-- 1.3.6.1.4.1.1332.1.1.5.3.111.4.1.4
		msanOnuUpgradeImageInstance OBJECT-TYPE
			SYNTAX Integer32
			MAX-ACCESS read-write
			STATUS obsolete
			DESCRIPTION
				"ONU image instance selection: 
				1 Automatic. The instance which is not committed will be upgraded. For ONU which 
				 has only one image instance, OLT will always upgrade this image instance 0"
			DEFVAL { 1 }
			::= { msanOnuUpgradeEntry 4 }

		
		-- 1.3.6.1.4.1.1332.1.1.5.3.111.4.1.5
		msanOnuUpgradeScheduledTime OBJECT-TYPE
			SYNTAX DisplayString
			UNITS "hh:mm:ss"
			MAX-ACCESS read-write
			STATUS current
			DESCRIPTION
				"The time at which the ONU will be upgraded scheduledly. This column is used only if the 
				msanOnuUpgradeMethod is set to 2 - Scheduled. The format of the string is hh:mm:ss which means 
				the upgrade can be repeated every 24 hours.
				"
			DEFVAL { "23:30:00" }
			::= { msanOnuUpgradeEntry 5 }

		
		-- 1.3.6.1.4.1.1332.1.1.5.3.111.4.1.6
		msanOnuUpgradeRebootScheduledTime OBJECT-TYPE
			SYNTAX DisplayString
			UNITS " hh:mm:ss"
			MAX-ACCESS read-write
			STATUS current
			DESCRIPTION
				"The time at which the ONU will be rebooted. This column is used only if the msanOnuUpgradeRebootMode 
				is set to 3, Scheduled. The format of the string is hh:mm:ss which means the reboot can be repeated 
				every 24 hours after a successful upgrade. The reboot on a particular ONU should not happen if there is 
				no any actual upgrade on it. 
				"
			::= { msanOnuUpgradeEntry 6 }

		
		-- 1.3.6.1.4.1.1332.1.1.5.3.111.4.1.7
		msanOnuUpgradeParticipantPortListBitMap OBJECT-TYPE
			SYNTAX OCTET STRING (SIZE (0..2048))
			MAX-ACCESS read-write
			STATUS current
			DESCRIPTION
				"ONU upgrade participant port list bit map.To include an ONU in upgrade, set the corresponding bit to 1.
				It's assumed that each slot has 8 or 16 OLT PON ports and each OLT PON port has 128 ONUs.Nonexist ports in the 
				port list bit map should be reserved and set to 0 if the actual capacity of PON ports and ONUs of the line 
				card in the slot is less than the above maximum assumption"
			DEFVAL { "" }
			::= { msanOnuUpgradeEntry 7 }

		
		-- 1.3.6.1.4.1.1332.1.1.5.3.111.4.1.8
		msanOnuUpgradeProgressDownloadPortListBitMap OBJECT-TYPE
			SYNTAX OCTET STRING (SIZE (0..2048))
			MAX-ACCESS read-only
			STATUS current
			DESCRIPTION
				"ONU upgrade progress download port list bit map. Since an ONU enters the image download stage, the corresponding 
				bit representing this ONU will remain as 1.
				It's assumed that each slot has 8 or 16 OLT PON ports and each OLT PON port has 128 ONUs.Nonexist ports in the 
				port list bit map should be reserved and set to 0 if the actual capacity of PON ports and ONUs of the line 
				card in the slot is less than the above maximum assumption"
			DEFVAL { "" }
			::= { msanOnuUpgradeEntry 8 }

		
		-- 1.3.6.1.4.1.1332.1.1.5.3.111.4.1.9
		msanOnuUpgradeProgressActivatePortListBitMap OBJECT-TYPE
			SYNTAX OCTET STRING (SIZE (0..2048))
			MAX-ACCESS read-only
			STATUS current
			DESCRIPTION
				"ONU upgrade progress activate port list bit map. Since an ONU enters image activate stage, the corresponding bit 
				representing this ONU will remain as 1.
				It's assumed that each slot has 8 or 16 OLT PON ports and each OLT PON port has 128 ONUs.Nonexist ports in the 
				port list bit map should be reserved and set to 0 if the actual capacity of PON ports and ONUs of the line 
				card in the slot is less than the above maximum assumption"
			DEFVAL { "" }
			::= { msanOnuUpgradeEntry 9 }

		
		-- 1.3.6.1.4.1.1332.1.1.5.3.111.4.1.10
		msanOnuUpgradeProgressCommitPortListBitMap OBJECT-TYPE
			SYNTAX OCTET STRING (SIZE (0..2048))
			MAX-ACCESS read-only
			STATUS current
			DESCRIPTION
				"ONU upgrade progress commit port list bit map. Since an ONU enters image commit stage, the corresponding bit representing 
				this ONU will remain as 1.
				It's assumed that each slot has 8 or 16 OLT PON ports and each OLT PON port has 128 ONUs.Nonexist ports in the 
				port list bit map should be reserved and set to 0 if the actual capacity of PON ports and ONUs of the line 
				card in the slot is less than the above maximum assumption"
			DEFVAL { "" }
			::= { msanOnuUpgradeEntry 10 }

		
		-- 1.3.6.1.4.1.1332.1.1.5.3.111.4.1.11
		msanOnuUpgradeProgressFinalPortListBitMap OBJECT-TYPE
			SYNTAX OCTET STRING (SIZE (0..2048))
			MAX-ACCESS read-only
			STATUS current
			DESCRIPTION
				"ONU upgrade progress final port list bit map. Whenever the upgrade procedure for an ONU is finished, regardless of success 
				or failure, the corresponding bit representing this ONU will become 1.
				It's assumed that each slot has 8 or 16 OLT PON ports and each OLT PON port has 128 ONUs.Nonexist ports in the 
				port list bit map should be reserved and set to 0 if the actual capacity of PON ports and ONUs of the line 
				card in the slot is less than the above maximum assumption"
			DEFVAL { "" }
			::= { msanOnuUpgradeEntry 11 }

		
		-- 1.3.6.1.4.1.1332.1.1.5.3.111.4.1.12
		msanOnuUpgradeResultFinalPortListBitMap OBJECT-TYPE
			SYNTAX OCTET STRING (SIZE (0..2048))
			MAX-ACCESS read-only
			STATUS current
			DESCRIPTION
				"ONU upgrade result port list bit map. Whenever an ONU encounters failure in any stage, then the corresponding bit representing 
				this ONU will become 1, and the upgrade procedure won't proceed to the next stage for this particular ONU.
				It's assumed that each slot has 8 or 16 OLT PON ports and each OLT PON port has 128 ONUs.Nonexist ports in the 
				port list bit map should be reserved and set to 0 if the actual capacity of PON ports and ONUs of the line 
				card in the slot is less than the above maximum assumption"
			DEFVAL { "" }
			::= { msanOnuUpgradeEntry 12 }

		
		-- 1.3.6.1.4.1.1332.1.1.5.3.111.5
		msanOnuUpgradeHwTypeTable OBJECT-TYPE
			SYNTAX SEQUENCE OF MsanOnuUpgradeHwTypeEntry
			MAX-ACCESS not-accessible
			STATUS current
			DESCRIPTION
				"Description."
			::= { msanOnu 5 }

		
		-- 1.3.6.1.4.1.1332.1.1.5.3.111.5.1
		msanOnuUpgradeHwTypeEntry OBJECT-TYPE
			SYNTAX MsanOnuUpgradeHwTypeEntry
			MAX-ACCESS not-accessible
			STATUS current
			DESCRIPTION
				"Description."
			INDEX { msanOnuUpgradeHwTypeVendorId, msanOnuUpgradeHwTypeHwType, msanOnuUpgradeHwTypeMethod }
			::= { msanOnuUpgradeHwTypeTable 1 }

		
		MsanOnuUpgradeHwTypeEntry ::=
			SEQUENCE { 
				msanOnuUpgradeHwTypeVendorId
					DisplayString,
				msanOnuUpgradeHwTypeHwType
					Integer32,
				msanOnuUpgradeHwTypeMethod
					INTEGER,
				msanOnuUpgradeHwTypeHwRevision
					DisplayString,
				msanOnuUpgradeHwTypeFwRevision
					DisplayString,
				msanOnuUpgradeHwTypeImageName
					DisplayString,
				msanOnuUpgradeHwTypeImagePath
					DisplayString,
				msanOnuUpgradeHwTypeServerName
					DisplayString,
				msanOnuUpgradeHwTypeRowStatus
					RowStatus
			 }

		-- 1.3.6.1.4.1.1332.1.1.5.3.111.5.1.1
		msanOnuUpgradeHwTypeVendorId OBJECT-TYPE
			SYNTAX DisplayString (SIZE (4))
			MAX-ACCESS not-accessible
			STATUS current
			DESCRIPTION
				"Description."
			::= { msanOnuUpgradeHwTypeEntry 1 }

		
		-- 1.3.6.1.4.1.1332.1.1.5.3.111.5.1.2
		msanOnuUpgradeHwTypeHwType OBJECT-TYPE
			SYNTAX Integer32
			MAX-ACCESS not-accessible
			STATUS current
			DESCRIPTION
				"ONU model which need firmware upgrade."
			::= { msanOnuUpgradeHwTypeEntry 2 }

		
		-- 1.3.6.1.4.1.1332.1.1.5.3.111.5.1.3
		msanOnuUpgradeHwTypeMethod OBJECT-TYPE
			SYNTAX INTEGER
				{
				manual(1),
				scheduled(2),
				automatic(3)
				}
			MAX-ACCESS not-accessible
			STATUS current
			DESCRIPTION
				"Upgrade method:
				1 Manual 
				2 Scheduled 
				3 Automatic."
			::= { msanOnuUpgradeHwTypeEntry 3 }

		
		-- 1.3.6.1.4.1.1332.1.1.5.3.111.5.1.4
		msanOnuUpgradeHwTypeHwRevision OBJECT-TYPE
			SYNTAX DisplayString (SIZE (0..63))
			MAX-ACCESS read-write
			STATUS obsolete
			DESCRIPTION
				"ONU upgrade hardware revision.
				"
			DEFVAL { ''b }
			::= { msanOnuUpgradeHwTypeEntry 4 }

		
		-- 1.3.6.1.4.1.1332.1.1.5.3.111.5.1.5
		msanOnuUpgradeHwTypeFwRevision OBJECT-TYPE
			SYNTAX DisplayString (SIZE (0..28))
			MAX-ACCESS read-write
			STATUS current
			DESCRIPTION
				"ONU upgrade firmware revision. "
			DEFVAL { "0.0" }
			::= { msanOnuUpgradeHwTypeEntry 5 }

		
		-- 1.3.6.1.4.1.1332.1.1.5.3.111.5.1.6
		msanOnuUpgradeHwTypeImageName OBJECT-TYPE
			SYNTAX DisplayString (SIZE (0..256))
			MAX-ACCESS read-write
			STATUS current
			DESCRIPTION
				"ONU upgrade image name."
			::= { msanOnuUpgradeHwTypeEntry 6 }

		
		-- 1.3.6.1.4.1.1332.1.1.5.3.111.5.1.7
		msanOnuUpgradeHwTypeImagePath OBJECT-TYPE
			SYNTAX DisplayString (SIZE (0..112))
			MAX-ACCESS read-write
			STATUS current
			DESCRIPTION
				"ONU upgrade image folder path."
			DEFVAL { "" }
			::= { msanOnuUpgradeHwTypeEntry 7 }

		
		-- 1.3.6.1.4.1.1332.1.1.5.3.111.5.1.8
		msanOnuUpgradeHwTypeServerName OBJECT-TYPE
			SYNTAX DisplayString (SIZE (0..16))
			MAX-ACCESS read-write
			STATUS current
			DESCRIPTION
				"ONU upgrade server name. 
				This is a parameter msanOnuUpgradeServerName from msanOnuUpgradeServerTable."
			::= { msanOnuUpgradeHwTypeEntry 8 }

		
		-- 1.3.6.1.4.1.1332.1.1.5.3.111.5.1.9
		msanOnuUpgradeHwTypeRowStatus OBJECT-TYPE
			SYNTAX RowStatus
			MAX-ACCESS read-create
			STATUS current
			DESCRIPTION
				"The row status object controls the creation/deletion of rows in this table. 
				For row creation use createAndWait(5) [createAndGo(4) is not supported].
				Setting this object to active(1) will activate this entry.
				Setting this object to destroy(6) will remove this entry.
				
				Row can be activated only if msanOnuUpgradeHwTypeImageName and
				msanOnuUpgradeHwTypeServerName  are specified.
				
				"
			::= { msanOnuUpgradeHwTypeEntry 9 }

		
		-- 1.3.6.1.4.1.1332.1.1.5.3.111.6
		msanOnuVirtGemPortInfoTable OBJECT-TYPE
			SYNTAX SEQUENCE OF MsanOnuVirtGemPortInfoEntry
			MAX-ACCESS not-accessible
			STATUS current
			DESCRIPTION
				"Description."
			::= { msanOnu 6 }

		
		-- 1.3.6.1.4.1.1332.1.1.5.3.111.6.1
		msanOnuVirtGemPortInfoEntry OBJECT-TYPE
			SYNTAX MsanOnuVirtGemPortInfoEntry
			MAX-ACCESS not-accessible
			STATUS current
			DESCRIPTION
				"Description."
			INDEX { msanOnuVirtGemPortInfoIfIndex }
			::= { msanOnuVirtGemPortInfoTable 1 }

		
		MsanOnuVirtGemPortInfoEntry ::=
			SEQUENCE { 
				msanOnuVirtGemPortInfoIfIndex
					Integer32,
				msanOnuVirtGemPortInfoOltGemPortNo
					Gauge32,
				msanOnuVirtGemPortInfoOltAllocId
					Gauge32,
				msanOnuVirtGemPortInfoTcontIndex
					Gauge32
			 }

		-- 1.3.6.1.4.1.1332.1.1.5.3.111.6.1.1
		msanOnuVirtGemPortInfoIfIndex OBJECT-TYPE
			SYNTAX Integer32
			MAX-ACCESS not-accessible
			STATUS current
			DESCRIPTION
				"Index of Virtual GEM Port (from ifTable)."
			::= { msanOnuVirtGemPortInfoEntry 1 }

		
		-- 1.3.6.1.4.1.1332.1.1.5.3.111.6.1.2
		msanOnuVirtGemPortInfoOltGemPortNo OBJECT-TYPE
			SYNTAX Gauge32
			MAX-ACCESS read-only
			STATUS current
			DESCRIPTION
				"GEM port no which is assigned dynamically by OLT."
			::= { msanOnuVirtGemPortInfoEntry 2 }

		
		-- 1.3.6.1.4.1.1332.1.1.5.3.111.6.1.3
		msanOnuVirtGemPortInfoOltAllocId OBJECT-TYPE
			SYNTAX Gauge32
			MAX-ACCESS read-only
			STATUS current
			DESCRIPTION
				"Alloc-ID which is assigned dynamically by OLT, a dynamic Alloc-ID is one-to-one mapped to 
				a static T-CONT index."
			::= { msanOnuVirtGemPortInfoEntry 3 }

		
		-- 1.3.6.1.4.1.1332.1.1.5.3.111.6.1.4
		msanOnuVirtGemPortInfoTcontIndex OBJECT-TYPE
			SYNTAX Gauge32
			MAX-ACCESS read-only
			STATUS current
			DESCRIPTION
				"Static T-CONT index from ONU's perspective."
			::= { msanOnuVirtGemPortInfoEntry 4 }

		
		-- 1.3.6.1.4.1.1332.1.1.5.3.111.7
		msanOnuVirtGemPortStatTable OBJECT-TYPE
			SYNTAX SEQUENCE OF MsanOnuVirtGemPortStatEntry
			MAX-ACCESS not-accessible
			STATUS current
			DESCRIPTION
				"This table displays performance statistics for Virtual Gem Ports."
			::= { msanOnu 7 }

		
		-- 1.3.6.1.4.1.1332.1.1.5.3.111.7.1
		msanOnuVirtGemPortStatEntry OBJECT-TYPE
			SYNTAX MsanOnuVirtGemPortStatEntry
			MAX-ACCESS not-accessible
			STATUS current
			DESCRIPTION
				"Serves as an index for this table. Identifies the
				15 interval in which PM was collected. The value
				0 identifies the current interval. Value 1 identifies
				the latest 15 minute interval and value 96
				identifies the last 15 minute interval in a a 24 hour period."
			INDEX { msanOnuVirtGemPortStatIfIndex, msanOnuVirtGemPortStatIntervalId }
			::= { msanOnuVirtGemPortStatTable 1 }

		
		MsanOnuVirtGemPortStatEntry ::=
			SEQUENCE { 
				msanOnuVirtGemPortStatIfIndex
					Integer32,
				msanOnuVirtGemPortStatIntervalId
					INTEGER,
				msanOnuVirtGemPortStatInFrames
					Counter64,
				msanOnuVirtGemPortStatInOctets
					Counter64,
				msanOnuVirtGemPortStatOutFrames
					Counter64,
				msanOnuVirtGemPortStatOutOctets
					Counter64
			 }

		-- 1.3.6.1.4.1.1332.1.1.5.3.111.7.1.1
		msanOnuVirtGemPortStatIfIndex OBJECT-TYPE
			SYNTAX Integer32
			MAX-ACCESS not-accessible
			STATUS current
			DESCRIPTION
				"Index of Virtual GEM Port (from ifTable)."
			::= { msanOnuVirtGemPortStatEntry 1 }

		
		-- 1.3.6.1.4.1.1332.1.1.5.3.111.7.1.2
		msanOnuVirtGemPortStatIntervalId OBJECT-TYPE
			SYNTAX INTEGER (0..96)
			MAX-ACCESS not-accessible
			STATUS current
			DESCRIPTION
				"Serves as an index for this table. Identifies the
				15 interval in which PM was collected. The value
				0 identifies the current interval. Value 1 identifies
				the latest 15 minute interval and value 96
				identifies the last 15 minute interval in a a 24 hour period.
				"
			::= { msanOnuVirtGemPortStatEntry 2 }

		
		-- 1.3.6.1.4.1.1332.1.1.5.3.111.7.1.3
		msanOnuVirtGemPortStatInFrames OBJECT-TYPE
			SYNTAX Counter64
			MAX-ACCESS read-only
			STATUS current
			DESCRIPTION
				"The total number of gpon frames received on the interface."
			::= { msanOnuVirtGemPortStatEntry 3 }

		
		-- 1.3.6.1.4.1.1332.1.1.5.3.111.7.1.4
		msanOnuVirtGemPortStatInOctets OBJECT-TYPE
			SYNTAX Counter64
			MAX-ACCESS read-only
			STATUS current
			DESCRIPTION
				"The total number of octets received on the interface.
				"
			::= { msanOnuVirtGemPortStatEntry 4 }

		
		-- 1.3.6.1.4.1.1332.1.1.5.3.111.7.1.5
		msanOnuVirtGemPortStatOutFrames OBJECT-TYPE
			SYNTAX Counter64
			MAX-ACCESS read-only
			STATUS current
			DESCRIPTION
				"The total number of gpon frames transmitted out of the
				interface."
			::= { msanOnuVirtGemPortStatEntry 5 }

		
		-- 1.3.6.1.4.1.1332.1.1.5.3.111.7.1.6
		msanOnuVirtGemPortStatOutOctets OBJECT-TYPE
			SYNTAX Counter64
			MAX-ACCESS read-only
			STATUS current
			DESCRIPTION
				"The total number of octets transmitted out of the
				interface
				"
			::= { msanOnuVirtGemPortStatEntry 6 }

		
		-- 1.3.6.1.4.1.1332.1.1.5.3.111.8
		msanOnuBlackListTable OBJECT-TYPE
			SYNTAX SEQUENCE OF MsanOnuBlackListEntry
			MAX-ACCESS not-accessible
			STATUS current
			DESCRIPTION
				"Table for displaying the ONUs in black list per OLT ports.
				"
			::= { msanOnu 8 }

		
		-- 1.3.6.1.4.1.1332.1.1.5.3.111.8.1
		msanOnuBlackListEntry OBJECT-TYPE
			SYNTAX MsanOnuBlackListEntry
			MAX-ACCESS not-accessible
			STATUS current
			DESCRIPTION
				"Description."
			INDEX { msanOnuBlackListIfIndex, msanOnuBlackListSerialNumber }
			::= { msanOnuBlackListTable 1 }

		
		MsanOnuBlackListEntry ::=
			SEQUENCE { 
				msanOnuBlackListIfIndex
					Integer32,
				msanOnuBlackListSerialNumber
					DisplayString,
				msanOnuBlackListPassword
					DisplayString,
				msanOnuBlackListCause
					INTEGER,
				msanOnuBlackListRegistrationid
					DisplayString
			 }

		-- 1.3.6.1.4.1.1332.1.1.5.3.111.8.1.1
		msanOnuBlackListIfIndex OBJECT-TYPE
			SYNTAX Integer32
			MAX-ACCESS not-accessible
			STATUS current
			DESCRIPTION
				"Index of OLT port (from ifTable)."
			::= { msanOnuBlackListEntry 1 }

		
		-- 1.3.6.1.4.1.1332.1.1.5.3.111.8.1.2
		msanOnuBlackListSerialNumber OBJECT-TYPE
			SYNTAX DisplayString (SIZE (12))
			MAX-ACCESS not-accessible
			STATUS current
			DESCRIPTION
				"The serial number. Index for this table.
				The serial number is unique for each ONT.
				It is defined in ITU-T G.984.3 
				and contains the vendor id and version number. The first four bytes are an ASCII encoded 
				vendor ID four letter mnemonic. The next eight bytes are an ASCII encoded version number (four hex values).
				Example: ISKT01C2AA5B
				"
			::= { msanOnuBlackListEntry 2 }

		
		-- 1.3.6.1.4.1.1332.1.1.5.3.111.8.1.3
		msanOnuBlackListPassword OBJECT-TYPE
			SYNTAX DisplayString (SIZE (0..20))
			MAX-ACCESS read-only
			STATUS current
			DESCRIPTION
				"Received ONU password."
			::= { msanOnuBlackListEntry 3 }

		
		-- 1.3.6.1.4.1.1332.1.1.5.3.111.8.1.4
		msanOnuBlackListCause OBJECT-TYPE
			SYNTAX INTEGER
				{
				invalid(1),
				unknownSerialnum(2),
				passwordMismatch(3),
				antiRogueOnu(4),
				failedToRanging(5),
				linkIdMismatch(6),
				registrationIdMismatch(7),
				passwordUnknown(8),
				registrationidUnknown(9)
				}
			MAX-ACCESS read-only
			STATUS current
			DESCRIPTION
				"The cause of entering black list.
				"
			::= { msanOnuBlackListEntry 4 }

		
		-- 1.3.6.1.4.1.1332.1.1.5.3.111.8.1.5
		msanOnuBlackListRegistrationid OBJECT-TYPE
			SYNTAX DisplayString (SIZE (0..36))
			MAX-ACCESS read-only
			STATUS current
			DESCRIPTION
				"Received Registrationid of XGSPON ONU password."
			::= { msanOnuBlackListEntry 5 }

		
		-- 1.3.6.1.4.1.1332.1.1.5.3.111.9
		msanOnuUpgradeServerTable OBJECT-TYPE
			SYNTAX SEQUENCE OF MsanOnuUpgradeServerEntry
			MAX-ACCESS not-accessible
			STATUS current
			DESCRIPTION
				"Description."
			::= { msanOnu 9 }

		
		-- 1.3.6.1.4.1.1332.1.1.5.3.111.9.1
		msanOnuUpgradeServerEntry OBJECT-TYPE
			SYNTAX MsanOnuUpgradeServerEntry
			MAX-ACCESS not-accessible
			STATUS current
			DESCRIPTION
				"Description."
			INDEX { msanOnuUpgradeServerName }
			::= { msanOnuUpgradeServerTable 1 }

		
		MsanOnuUpgradeServerEntry ::=
			SEQUENCE { 
				msanOnuUpgradeServerName
					DisplayString,
				msanOnuUpgradeServerIpAddress
					IpAddress,
				msanOnuUpgradeServerUserName
					DisplayString,
				msanOnuUpgradeServerUserPassword
					DisplayString,
				msanOnuUpgradeServerProtocol
					INTEGER,
				msanOnuUpgradeServerProtocolPortId
					Integer32,
				msanOnuUpgradeServerRowStatus
					RowStatus
			 }

		-- 1.3.6.1.4.1.1332.1.1.5.3.111.9.1.1
		msanOnuUpgradeServerName OBJECT-TYPE
			SYNTAX DisplayString (SIZE (0..16))
			MAX-ACCESS not-accessible
			STATUS current
			DESCRIPTION
				"ONU SW upgrade server name."
			::= { msanOnuUpgradeServerEntry 1 }

		
		-- 1.3.6.1.4.1.1332.1.1.5.3.111.9.1.2
		msanOnuUpgradeServerIpAddress OBJECT-TYPE
			SYNTAX IpAddress
			MAX-ACCESS read-write
			STATUS current
			DESCRIPTION
				"ONU SW upgrade server IP address."
			::= { msanOnuUpgradeServerEntry 2 }

		
		-- 1.3.6.1.4.1.1332.1.1.5.3.111.9.1.3
		msanOnuUpgradeServerUserName OBJECT-TYPE
			SYNTAX DisplayString (SIZE (0..16))
			MAX-ACCESS read-write
			STATUS current
			DESCRIPTION
				"Username used in ONU SW upgrade protocol."
			DEFVAL { "anonymous" }
			::= { msanOnuUpgradeServerEntry 3 }

		
		-- 1.3.6.1.4.1.1332.1.1.5.3.111.9.1.4
		msanOnuUpgradeServerUserPassword OBJECT-TYPE
			SYNTAX DisplayString (SIZE (0..32))
			MAX-ACCESS read-write
			STATUS current
			DESCRIPTION
				"User password used in ONU SW upgrade protocol."
			DEFVAL { "anonymous" }
			::= { msanOnuUpgradeServerEntry 4 }

		
		-- 1.3.6.1.4.1.1332.1.1.5.3.111.9.1.5
		msanOnuUpgradeServerProtocol OBJECT-TYPE
			SYNTAX INTEGER { ftp(1) }
			MAX-ACCESS read-write
			STATUS current
			DESCRIPTION
				"ONU SW upgrade protocol type."
			DEFVAL { ftp }
			::= { msanOnuUpgradeServerEntry 5 }

		
		-- 1.3.6.1.4.1.1332.1.1.5.3.111.9.1.6
		msanOnuUpgradeServerProtocolPortId OBJECT-TYPE
			SYNTAX Integer32 (0..65535)
			MAX-ACCESS read-write
			STATUS current
			DESCRIPTION
				"ONU SW upgrade protocol port number.
				
				If value is set to -1, standard protocol number is used."
			::= { msanOnuUpgradeServerEntry 6 }

		
		-- 1.3.6.1.4.1.1332.1.1.5.3.111.9.1.7
		msanOnuUpgradeServerRowStatus OBJECT-TYPE
			SYNTAX RowStatus
			MAX-ACCESS read-write
			STATUS current
			DESCRIPTION
				"The row status object controls the creation/deletion of rows in this table.
				Its semantics are the same as those for the RowStatus textual convention specified for SNMPv2.
				For row creation use createAndWait(5).
				For row activation use active(1).
				For row deletion use destroy(6).
				
				Other values are currently not supported.
				
				For row activation parameter msanOnuSwUpgradeServerIpAddress must be defined."
			::= { msanOnuUpgradeServerEntry 7 }

		
		-- 1.3.6.1.4.1.1332.1.1.5.3.111.10
		msanOnuEthPortInfoTable OBJECT-TYPE
			SYNTAX SEQUENCE OF MsanOnuEthPortInfoEntry
			MAX-ACCESS not-accessible
			STATUS current
			DESCRIPTION
				"Description."
			::= { msanOnu 10 }

		
		-- 1.3.6.1.4.1.1332.1.1.5.3.111.10.1
		msanOnuEthPortInfoEntry OBJECT-TYPE
			SYNTAX MsanOnuEthPortInfoEntry
			MAX-ACCESS not-accessible
			STATUS current
			DESCRIPTION
				"Description."
			INDEX { msanOnuEthPortInfoOnuIfIndex, msanOnuEthPortInfoUniId }
			::= { msanOnuEthPortInfoTable 1 }

		
		MsanOnuEthPortInfoEntry ::=
			SEQUENCE { 
				msanOnuEthPortInfoOnuIfIndex
					Integer32,
				msanOnuEthPortInfoUniId
					Integer32,
				msanOnuEthPortInfoAdminState
					INTEGER,
				msanOnuEthPortInfoOperState
					INTEGER,
				msanOnuEthPortInfoType
					INTEGER,
				msanOnuEthPortInfoSpeed
					INTEGER,
				msanOnuEthPortInfoDuplex
					INTEGER
			 }

		-- 1.3.6.1.4.1.1332.1.1.5.3.111.10.1.1
		msanOnuEthPortInfoOnuIfIndex OBJECT-TYPE
			SYNTAX Integer32
			MAX-ACCESS not-accessible
			STATUS current
			DESCRIPTION
				"Index of ONU (from ifTable)."
			::= { msanOnuEthPortInfoEntry 1 }

		
		-- 1.3.6.1.4.1.1332.1.1.5.3.111.10.1.2
		msanOnuEthPortInfoUniId OBJECT-TYPE
			SYNTAX Integer32
			MAX-ACCESS not-accessible
			STATUS current
			DESCRIPTION
				"ONU Ethernet Port (UNI) identifier."
			::= { msanOnuEthPortInfoEntry 2 }

		
		-- 1.3.6.1.4.1.1332.1.1.5.3.111.10.1.3
		msanOnuEthPortInfoAdminState OBJECT-TYPE
			SYNTAX INTEGER
				{
				enable(1),
				disable(2),
				notAvailable(3)
				}
			MAX-ACCESS read-only
			STATUS current
			DESCRIPTION
				"ONU eth port (UNI) administration state."
			::= { msanOnuEthPortInfoEntry 3 }

		
		-- 1.3.6.1.4.1.1332.1.1.5.3.111.10.1.4
		msanOnuEthPortInfoOperState OBJECT-TYPE
			SYNTAX INTEGER
				{
				up(1),
				down(2),
				notAvailable(3)
				}
			MAX-ACCESS read-only
			STATUS current
			DESCRIPTION
				"ONU eth port (UNI) operational state."
			::= { msanOnuEthPortInfoEntry 4 }

		
		-- 1.3.6.1.4.1.1332.1.1.5.3.111.10.1.5
		msanOnuEthPortInfoType OBJECT-TYPE
			SYNTAX INTEGER
				{
				fE(1),
				gE(2),
				notAvailable(3),
				tengE(4)
				}
			MAX-ACCESS read-only
			STATUS current
			DESCRIPTION
				"Type of ONU eth port (UNI)."
			::= { msanOnuEthPortInfoEntry 5 }

		
		-- 1.3.6.1.4.1.1332.1.1.5.3.111.10.1.6
		msanOnuEthPortInfoSpeed OBJECT-TYPE
			SYNTAX INTEGER
				{
				mbps10(1),
				mbps100(2),
				mbps1000(3),
				notAvailable(4),
				mbps2500(5),
				mbps5000(6),
				mbps10000(7),
				mbps25000(8),
				mbps40000(9)
				}
			MAX-ACCESS read-only
			STATUS current
			DESCRIPTION
				"Speed of ONU eth port (UNI).
				"
			::= { msanOnuEthPortInfoEntry 6 }

		
		-- 1.3.6.1.4.1.1332.1.1.5.3.111.10.1.7
		msanOnuEthPortInfoDuplex OBJECT-TYPE
			SYNTAX INTEGER
				{
				full(1),
				half(2),
				notAvailable(3)
				}
			MAX-ACCESS read-only
			STATUS current
			DESCRIPTION
				"Duplex mode of ONU eth port (UNI)."
			::= { msanOnuEthPortInfoEntry 7 }

		
		-- 1.3.6.1.4.1.1332.1.1.5.3.111.11
		msanOnuEthPortStatTable OBJECT-TYPE
			SYNTAX SEQUENCE OF MsanOnuEthPortStatEntry
			MAX-ACCESS not-accessible
			STATUS current
			DESCRIPTION
				"Description."
			::= { msanOnu 11 }

		
		-- 1.3.6.1.4.1.1332.1.1.5.3.111.11.1
		msanOnuEthPortStatEntry OBJECT-TYPE
			SYNTAX MsanOnuEthPortStatEntry
			MAX-ACCESS not-accessible
			STATUS current
			DESCRIPTION
				"Description."
			INDEX { msanOnuEthPortStatOnuIfIndex, msanOnuEthPortStatUniId, msanOnuEthPortStatIntervalId }
			::= { msanOnuEthPortStatTable 1 }

		
		MsanOnuEthPortStatEntry ::=
			SEQUENCE { 
				msanOnuEthPortStatOnuIfIndex
					Integer32,
				msanOnuEthPortStatUniId
					Integer32,
				msanOnuEthPortStatIntervalId
					INTEGER,
				msanOnuEthPortStatInPkts
					Counter64,
				msanOnuEthPortStatInUcastPkts
					Counter64,
				msanOnuEthPortStatInMcastPkts
					Counter64,
				msanOnuEthPortStatInBcastPkts
					Counter64,
				msanOnuEthPortStatInOctets
					Counter64,
				msanOnuEthPortStatInPkts64Octets
					Counter64,
				msanOnuEthPortStatInPkts64to127Octets
					Counter64,
				msanOnuEthPortStatInPkts128to255Octets
					Counter64,
				msanOnuEthPortStatInPkts256to511Octets
					Counter64,
				msanOnuEthPortStatInPkts512to1023Octets
					Counter64,
				msanOnuEthPortStatInPkts1024to1518Octets
					Counter64,
				msanOnuEthPortStatInDiscards
					Counter64,
				msanOnuEthPortStatInUndersizePkts
					Counter64,
				msanOnuEthPortStatInOversizePkts
					Counter64,
				msanOnuEthPortStatInFragments
					Counter64,
				msanOnuEthPortStatInJabbers
					Counter64,
				msanOnuEthPortStatInFcsErrors
					Counter64,
				msanOnuEthPortStatInBufferOverflows
					Counter64,
				msanOnuEthPortStatInAlignmentError
					Counter64,
				msanOnuEthPortStatInInternalMACReceiveError
					Counter64,
				msanOnuEthPortStatOutPkts
					Counter64,
				msanOnuEthPortStatOutUcastPkts
					Counter64,
				msanOnuEthPortStatOutMcastPkts
					Counter64,
				msanOnuEthPortStatOutBcastPkts
					Counter64,
				msanOnuEthPortStatOutDiscards
					Counter64,
				msanOnuEthPortStatOutFcsErrors
					Counter64,
				msanOnuEthPortStatOutExcessiveCollisions
					Counter64,
				msanOnuEthPortStatOutLateCollisions
					Counter64,
				msanOnuEthPortStatOutBufferOverflows
					Counter64,
				msanOnuEthPortStatOutSingleCollisionPkts
					Counter64,
				msanOnuEthPortStatOutMultipleCollisionsPkts
					Counter64,
				msanOnuEthPortStatOutDeferredTransmission
					Counter64,
				msanOnuEthPortStatOutInternalMACTransmitError
					Counter64,
				msanOnuEthPortStatSQEs
					Counter64,
				msanOnuEthPortStatCarrierSenseError
					Counter64
			 }

		-- 1.3.6.1.4.1.1332.1.1.5.3.111.11.1.1
		msanOnuEthPortStatOnuIfIndex OBJECT-TYPE
			SYNTAX Integer32
			MAX-ACCESS not-accessible
			STATUS current
			DESCRIPTION
				"Index of ONU (from ifTable)."
			::= { msanOnuEthPortStatEntry 1 }

		
		-- 1.3.6.1.4.1.1332.1.1.5.3.111.11.1.2
		msanOnuEthPortStatUniId OBJECT-TYPE
			SYNTAX Integer32
			MAX-ACCESS not-accessible
			STATUS current
			DESCRIPTION
				"ONU Ethernet Port (UNI) identifier."
			::= { msanOnuEthPortStatEntry 2 }

		
		-- 1.3.6.1.4.1.1332.1.1.5.3.111.11.1.3
		msanOnuEthPortStatIntervalId OBJECT-TYPE
			SYNTAX INTEGER (0..96)
			MAX-ACCESS not-accessible
			STATUS current
			DESCRIPTION
				"Serves as an index for this table. Identifies the
				15 interval in which PM was collected. The value
				0 identifies the current interval. Value 1 identifies
				the latest 15 minute interval and value 96
				identifies the last 15 minute interval in a a 24 hour period.
				"
			::= { msanOnuEthPortStatEntry 3 }

		
		-- 1.3.6.1.4.1.1332.1.1.5.3.111.11.1.4
		msanOnuEthPortStatInPkts OBJECT-TYPE
			SYNTAX Counter64
			UNITS "Packets"
			MAX-ACCESS read-only
			STATUS current
			DESCRIPTION
				"The total number of received ethernet packets."
			::= { msanOnuEthPortStatEntry 4 }

		
		-- 1.3.6.1.4.1.1332.1.1.5.3.111.11.1.5
		msanOnuEthPortStatInUcastPkts OBJECT-TYPE
			SYNTAX Counter64
			UNITS "Packets"
			MAX-ACCESS read-only
			STATUS current
			DESCRIPTION
				"The number of received unicast ethernet packets."
			::= { msanOnuEthPortStatEntry 5 }

		
		-- 1.3.6.1.4.1.1332.1.1.5.3.111.11.1.6
		msanOnuEthPortStatInMcastPkts OBJECT-TYPE
			SYNTAX Counter64
			UNITS "Packets"
			MAX-ACCESS read-only
			STATUS current
			DESCRIPTION
				"The number of received multicast ethernet packets."
			::= { msanOnuEthPortStatEntry 6 }

		
		-- 1.3.6.1.4.1.1332.1.1.5.3.111.11.1.7
		msanOnuEthPortStatInBcastPkts OBJECT-TYPE
			SYNTAX Counter64
			UNITS "Packets"
			MAX-ACCESS read-only
			STATUS current
			DESCRIPTION
				"The number of received broadcast ethernet packets."
			::= { msanOnuEthPortStatEntry 7 }

		
		-- 1.3.6.1.4.1.1332.1.1.5.3.111.11.1.8
		msanOnuEthPortStatInOctets OBJECT-TYPE
			SYNTAX Counter64
			UNITS "Octets"
			MAX-ACCESS read-only
			STATUS current
			DESCRIPTION
				"The total number of octets received on the interface,
				including framing characters.
				"
			::= { msanOnuEthPortStatEntry 8 }

		
		-- 1.3.6.1.4.1.1332.1.1.5.3.111.11.1.9
		msanOnuEthPortStatInPkts64Octets OBJECT-TYPE
			SYNTAX Counter64
			UNITS "Packets"
			MAX-ACCESS read-only
			STATUS current
			DESCRIPTION
				"The number of received packets (including bad packets)
				that were 64 octets long, excluding framing bitsbut including FCS.
				"
			::= { msanOnuEthPortStatEntry 9 }

		
		-- 1.3.6.1.4.1.1332.1.1.5.3.111.11.1.10
		msanOnuEthPortStatInPkts64to127Octets OBJECT-TYPE
			SYNTAX Counter64
			UNITS "Packets"
			MAX-ACCESS read-only
			STATUS current
			DESCRIPTION
				"The number of received packets (including bad packets)
				that were 65..127 octets long,
				excluding framing bits but including FCS. "
			::= { msanOnuEthPortStatEntry 10 }

		
		-- 1.3.6.1.4.1.1332.1.1.5.3.111.11.1.11
		msanOnuEthPortStatInPkts128to255Octets OBJECT-TYPE
			SYNTAX Counter64
			UNITS "Packets"
			MAX-ACCESS read-only
			STATUS current
			DESCRIPTION
				"The number of received ethernet packets that were between 128 and 255 octets in length."
			::= { msanOnuEthPortStatEntry 11 }

		
		-- 1.3.6.1.4.1.1332.1.1.5.3.111.11.1.12
		msanOnuEthPortStatInPkts256to511Octets OBJECT-TYPE
			SYNTAX Counter64
			UNITS "Packets"
			MAX-ACCESS read-only
			STATUS current
			DESCRIPTION
				"The number of received ethernet packets that were between 256 and 511 octets in length."
			::= { msanOnuEthPortStatEntry 12 }

		
		-- 1.3.6.1.4.1.1332.1.1.5.3.111.11.1.13
		msanOnuEthPortStatInPkts512to1023Octets OBJECT-TYPE
			SYNTAX Counter64
			UNITS "Packets"
			MAX-ACCESS read-only
			STATUS current
			DESCRIPTION
				"The number of received ethernet packets that were between 256 and 511 octets in length."
			::= { msanOnuEthPortStatEntry 13 }

		
		-- 1.3.6.1.4.1.1332.1.1.5.3.111.11.1.14
		msanOnuEthPortStatInPkts1024to1518Octets OBJECT-TYPE
			SYNTAX Counter64
			UNITS "Packets"
			MAX-ACCESS read-only
			STATUS current
			DESCRIPTION
				"The number of received ethernet packets that were between 512 and 1518 octets in length."
			::= { msanOnuEthPortStatEntry 14 }

		
		-- 1.3.6.1.4.1.1332.1.1.5.3.111.11.1.15
		msanOnuEthPortStatInDiscards OBJECT-TYPE
			SYNTAX Counter64
			UNITS "Packets"
			MAX-ACCESS read-only
			STATUS current
			DESCRIPTION
				"The number of discarded received ethernet packets."
			::= { msanOnuEthPortStatEntry 15 }

		
		-- 1.3.6.1.4.1.1332.1.1.5.3.111.11.1.16
		msanOnuEthPortStatInUndersizePkts OBJECT-TYPE
			SYNTAX Counter64
			UNITS "Packets"
			MAX-ACCESS read-only
			STATUS current
			DESCRIPTION
				"The number of packets received that were
				less than 64 octets long  and were otherwise well
				formed.
				"
			::= { msanOnuEthPortStatEntry 16 }

		
		-- 1.3.6.1.4.1.1332.1.1.5.3.111.11.1.17
		msanOnuEthPortStatInOversizePkts OBJECT-TYPE
			SYNTAX Counter64
			UNITS "Packets"
			MAX-ACCESS read-only
			STATUS current
			DESCRIPTION
				"The total number of packets received that were
				longer than 1518 octets (excluding framing bits,
				but including FCS octets) and were otherwise
				well formed.
				
				"
			::= { msanOnuEthPortStatEntry 17 }

		
		-- 1.3.6.1.4.1.1332.1.1.5.3.111.11.1.18
		msanOnuEthPortStatInFragments OBJECT-TYPE
			SYNTAX Counter64
			UNITS "Packets"
			MAX-ACCESS read-only
			STATUS current
			DESCRIPTION
				"The number of packets received that were less than
				64 octets long, excluding framing 
				bits but including FCS octets, and had either a bad
				Packet check sequence (FCS) with an integral 
				number of octets (FCS error) or a bad FCS with a non-integral
				number of octets (alignment error). 
				It is entirely normal for this attribute to increment.
				This is because it counts both runts (which are normal 
				occurrences due to collisions) and noise hits. 
				
				"
			::= { msanOnuEthPortStatEntry 18 }

		
		-- 1.3.6.1.4.1.1332.1.1.5.3.111.11.1.19
		msanOnuEthPortStatInJabbers OBJECT-TYPE
			SYNTAX Counter64
			UNITS "Packets"
			MAX-ACCESS read-only
			STATUS current
			DESCRIPTION
				"The number of packets received that were longer than
				1518 octets, excluding framing bits but including FCS octets, 
				and had either a bad Packet check sequence (FCS) with an integral 
				number of octets (FCS error) or a bad FCS with a non-integral
				number of octets (alignment error). 
				The range to detect jabber is between 20 ms and 150 ms.
				
				
				"
			::= { msanOnuEthPortStatEntry 19 }

		
		-- 1.3.6.1.4.1.1332.1.1.5.3.111.11.1.20
		msanOnuEthPortStatInFcsErrors OBJECT-TYPE
			SYNTAX Counter64
			UNITS "Packets"
			MAX-ACCESS read-only
			STATUS current
			DESCRIPTION
				"The number of received ethernet packets with FCS error."
			::= { msanOnuEthPortStatEntry 20 }

		
		-- 1.3.6.1.4.1.1332.1.1.5.3.111.11.1.21
		msanOnuEthPortStatInBufferOverflows OBJECT-TYPE
			SYNTAX Counter64
			UNITS "Packets"
			MAX-ACCESS read-only
			STATUS current
			DESCRIPTION
				"This attribute counts the number of times that
				the receive buffer overflowed."
			::= { msanOnuEthPortStatEntry 21 }

		
		-- 1.3.6.1.4.1.1332.1.1.5.3.111.11.1.22
		msanOnuEthPortStatInAlignmentError OBJECT-TYPE
			SYNTAX Counter64
			UNITS "Packets"
			MAX-ACCESS read-only
			STATUS current
			DESCRIPTION
				"This attribute counts received Packets that were
				not an integral number of octets in length 
				and did not pass the FCS check.
				"
			::= { msanOnuEthPortStatEntry 22 }

		
		-- 1.3.6.1.4.1.1332.1.1.5.3.111.11.1.23
		msanOnuEthPortStatInInternalMACReceiveError OBJECT-TYPE
			SYNTAX Counter64
			UNITS "Packets"
			MAX-ACCESS read-only
			STATUS current
			DESCRIPTION
				"This attribute counts Packets whose reception
				failed due to an internal MAC sublayer receive error 
				"
			::= { msanOnuEthPortStatEntry 23 }

		
		-- 1.3.6.1.4.1.1332.1.1.5.3.111.11.1.24
		msanOnuEthPortStatOutPkts OBJECT-TYPE
			SYNTAX Counter64
			UNITS "Packets"
			MAX-ACCESS read-only
			STATUS current
			DESCRIPTION
				"The total number of transmitted ethernet packets."
			::= { msanOnuEthPortStatEntry 24 }

		
		-- 1.3.6.1.4.1.1332.1.1.5.3.111.11.1.25
		msanOnuEthPortStatOutUcastPkts OBJECT-TYPE
			SYNTAX Counter64
			UNITS "Packets"
			MAX-ACCESS read-only
			STATUS current
			DESCRIPTION
				"The number of transmitted unicast ethernet packets."
			::= { msanOnuEthPortStatEntry 25 }

		
		-- 1.3.6.1.4.1.1332.1.1.5.3.111.11.1.26
		msanOnuEthPortStatOutMcastPkts OBJECT-TYPE
			SYNTAX Counter64
			UNITS "Packets"
			MAX-ACCESS read-only
			STATUS current
			DESCRIPTION
				"The number of transmitted multicast ethernet packets."
			::= { msanOnuEthPortStatEntry 26 }

		
		-- 1.3.6.1.4.1.1332.1.1.5.3.111.11.1.27
		msanOnuEthPortStatOutBcastPkts OBJECT-TYPE
			SYNTAX Counter64
			UNITS "Packets"
			MAX-ACCESS read-only
			STATUS current
			DESCRIPTION
				"The number of transmitted broadcast ethernet packets."
			::= { msanOnuEthPortStatEntry 27 }

		
		-- 1.3.6.1.4.1.1332.1.1.5.3.111.11.1.28
		msanOnuEthPortStatOutDiscards OBJECT-TYPE
			SYNTAX Counter64
			UNITS "Packets"
			MAX-ACCESS read-only
			STATUS current
			DESCRIPTION
				"The number of discarded transmitted ethernet packets."
			::= { msanOnuEthPortStatEntry 28 }

		
		-- 1.3.6.1.4.1.1332.1.1.5.3.111.11.1.29
		msanOnuEthPortStatOutFcsErrors OBJECT-TYPE
			SYNTAX Counter64
			UNITS "Packets"
			MAX-ACCESS read-only
			STATUS current
			DESCRIPTION
				"The number of transmitted ethernet packets with FCS error."
			::= { msanOnuEthPortStatEntry 29 }

		
		-- 1.3.6.1.4.1.1332.1.1.5.3.111.11.1.30
		msanOnuEthPortStatOutExcessiveCollisions OBJECT-TYPE
			SYNTAX Counter64
			UNITS "Packets"
			MAX-ACCESS read-only
			STATUS current
			DESCRIPTION
				"This attribute counts Packets whose transmission
				failed due to excessive collisions. 
				"
			::= { msanOnuEthPortStatEntry 30 }

		
		-- 1.3.6.1.4.1.1332.1.1.5.3.111.11.1.31
		msanOnuEthPortStatOutLateCollisions OBJECT-TYPE
			SYNTAX Counter64
			UNITS "Packets"
			MAX-ACCESS read-only
			STATUS current
			DESCRIPTION
				"This attribute counts the number of times that
				a collision was detected later than 512 bit 
				times into the transmission of a packet.
				
				"
			::= { msanOnuEthPortStatEntry 31 }

		
		-- 1.3.6.1.4.1.1332.1.1.5.3.111.11.1.32
		msanOnuEthPortStatOutBufferOverflows OBJECT-TYPE
			SYNTAX Counter64
			UNITS "Packets"
			MAX-ACCESS read-only
			STATUS current
			DESCRIPTION
				"This attribute counts the number of times that
				the transmit buffer overflowed.
				
				
				"
			::= { msanOnuEthPortStatEntry 32 }

		
		-- 1.3.6.1.4.1.1332.1.1.5.3.111.11.1.33
		msanOnuEthPortStatOutSingleCollisionPkts OBJECT-TYPE
			SYNTAX Counter64
			UNITS "Packets"
			MAX-ACCESS read-only
			STATUS current
			DESCRIPTION
				"This attribute counts successfully transmitted
				Packets whose transmission was delayed by 
				exactly one collision. 
				
				"
			::= { msanOnuEthPortStatEntry 33 }

		
		-- 1.3.6.1.4.1.1332.1.1.5.3.111.11.1.34
		msanOnuEthPortStatOutMultipleCollisionsPkts OBJECT-TYPE
			SYNTAX Counter64
			UNITS "Packets"
			MAX-ACCESS read-only
			STATUS current
			DESCRIPTION
				"This attribute counts successfully transmitted
				Packets whose transmission was delayed by 
				more than one collision.
				
				
				"
			::= { msanOnuEthPortStatEntry 34 }

		
		-- 1.3.6.1.4.1.1332.1.1.5.3.111.11.1.35
		msanOnuEthPortStatOutDeferredTransmission OBJECT-TYPE
			SYNTAX Counter64
			UNITS "Packets"
			MAX-ACCESS read-only
			STATUS current
			DESCRIPTION
				"This attribute counts Packets whose first
				transmission attempt was delayed because the medium 
				was busy. The count does not include Packets
				involved in collisions.
				
				
				"
			::= { msanOnuEthPortStatEntry 35 }

		
		-- 1.3.6.1.4.1.1332.1.1.5.3.111.11.1.36
		msanOnuEthPortStatOutInternalMACTransmitError OBJECT-TYPE
			SYNTAX Counter64
			UNITS "Packets"
			MAX-ACCESS read-only
			STATUS current
			DESCRIPTION
				"This attribute counts Packets whose transmission
				failed due to an internal MAC sublayer transmit error.
				
				
				"
			::= { msanOnuEthPortStatEntry 36 }

		
		-- 1.3.6.1.4.1.1332.1.1.5.3.111.11.1.37
		msanOnuEthPortStatSQEs OBJECT-TYPE
			SYNTAX Counter64
			MAX-ACCESS read-only
			STATUS current
			DESCRIPTION
				"This attribute counts the number of times that
				the SQE test error message was generated by 
				the PLS sublayer.
				
				
				
				"
			::= { msanOnuEthPortStatEntry 37 }

		
		-- 1.3.6.1.4.1.1332.1.1.5.3.111.11.1.38
		msanOnuEthPortStatCarrierSenseError OBJECT-TYPE
			SYNTAX Counter64
			MAX-ACCESS read-only
			STATUS current
			DESCRIPTION
				"This attribute counts the number of times that
				carrier sense was lost or never asserted when 
				attempting to transmit a Packet.
				
				
				
				"
			::= { msanOnuEthPortStatEntry 38 }

		
		-- 1.3.6.1.4.1.1332.1.1.5.3.111.12
		msanOnuDefaultConfigFileTable OBJECT-TYPE
			SYNTAX SEQUENCE OF MsanOnuDefaultConfigFileEntry
			MAX-ACCESS not-accessible
			STATUS current
			DESCRIPTION
				"Description."
			::= { msanOnu 12 }

		
		-- 1.3.6.1.4.1.1332.1.1.5.3.111.12.1
		msanOnuDefaultConfigFileEntry OBJECT-TYPE
			SYNTAX MsanOnuDefaultConfigFileEntry
			MAX-ACCESS not-accessible
			STATUS current
			DESCRIPTION
				"Description."
			INDEX { msanOnuDefaultConfigFileName }
			::= { msanOnuDefaultConfigFileTable 1 }

		
		MsanOnuDefaultConfigFileEntry ::=
			SEQUENCE { 
				msanOnuDefaultConfigFileName
					DisplayString,
				msanOnuDefaultConfigFileRowStatus
					RowStatus
			 }

		-- 1.3.6.1.4.1.1332.1.1.5.3.111.12.1.1
		msanOnuDefaultConfigFileName OBJECT-TYPE
			SYNTAX DisplayString
			MAX-ACCESS not-accessible
			STATUS current
			DESCRIPTION
				"ONU default config file name."
			::= { msanOnuDefaultConfigFileEntry 1 }

		
		-- 1.3.6.1.4.1.1332.1.1.5.3.111.12.1.2
		msanOnuDefaultConfigFileRowStatus OBJECT-TYPE
			SYNTAX RowStatus
			MAX-ACCESS read-write
			STATUS current
			DESCRIPTION
				"The row status object controls the creation/deletion of rows in this table. 
				Its semantics are the same as those for the RowStatus textual convention specified for SNMPv2.
				Setting this object to destroy(6) will remove this entry.
				Read values: active(1).
				Other values are currently not supported."
			::= { msanOnuDefaultConfigFileEntry 2 }

		
		-- 1.3.6.1.4.1.1332.1.1.5.3.111.13
		msanOnuCfgAttributeTable OBJECT-TYPE
			SYNTAX SEQUENCE OF MsanOnuCfgAttributeEntry
			MAX-ACCESS not-accessible
			STATUS current
			DESCRIPTION
				"Description."
			::= { msanOnu 13 }

		
		-- 1.3.6.1.4.1.1332.1.1.5.3.111.13.1
		msanOnuCfgAttributeEntry OBJECT-TYPE
			SYNTAX MsanOnuCfgAttributeEntry
			MAX-ACCESS not-accessible
			STATUS current
			DESCRIPTION
				"Description."
			INDEX { msanOnuCfgAttributeIfIndex, msanOnuCfgAttributeId }
			::= { msanOnuCfgAttributeTable 1 }

		
		MsanOnuCfgAttributeEntry ::=
			SEQUENCE { 
				msanOnuCfgAttributeIfIndex
					Integer32,
				msanOnuCfgAttributeId
					Integer32,
				msanOnuCfgAttributeName
					DisplayString,
				msanOnuCfgAttributeValue
					DisplayString,
				msanOnuCfgAttributeRowStatus
					RowStatus
			 }

		-- 1.3.6.1.4.1.1332.1.1.5.3.111.13.1.2
		msanOnuCfgAttributeIfIndex OBJECT-TYPE
			SYNTAX Integer32
			MAX-ACCESS not-accessible
			STATUS current
			DESCRIPTION
				"Index of ONU interface (from ifTable)."
			::= { msanOnuCfgAttributeEntry 2 }

		
		-- 1.3.6.1.4.1.1332.1.1.5.3.111.13.1.3
		msanOnuCfgAttributeId OBJECT-TYPE
			SYNTAX Integer32
			MAX-ACCESS not-accessible
			STATUS current
			DESCRIPTION
				"Onu Attribute Id"
			::= { msanOnuCfgAttributeEntry 3 }

		
		-- 1.3.6.1.4.1.1332.1.1.5.3.111.13.1.4
		msanOnuCfgAttributeName OBJECT-TYPE
			SYNTAX DisplayString
			MAX-ACCESS read-write
			STATUS current
			DESCRIPTION
				"ONU config attribute name."
			DEFVAL { ''b }
			::= { msanOnuCfgAttributeEntry 4 }

		
		-- 1.3.6.1.4.1.1332.1.1.5.3.111.13.1.5
		msanOnuCfgAttributeValue OBJECT-TYPE
			SYNTAX DisplayString
			MAX-ACCESS read-write
			STATUS current
			DESCRIPTION
				"ONU config attribute value"
			DEFVAL { ''b }
			::= { msanOnuCfgAttributeEntry 5 }

		
		-- 1.3.6.1.4.1.1332.1.1.5.3.111.13.1.6
		msanOnuCfgAttributeRowStatus OBJECT-TYPE
			SYNTAX RowStatus
			MAX-ACCESS read-write
			STATUS current
			DESCRIPTION
				"The row status object controls the creation/deletion of rows in this table.
				Its semantics are the same as those for the RowStatus textual convention specified for SNMPv2.
				For row creation use createAndGo(4).
				For row activation use active(1).
				For row deletion use destroy(6).
				
				Other values are currently not supported."
			::= { msanOnuCfgAttributeEntry 6 }

		
		-- 1.3.6.1.4.1.1332.1.1.5.3.111.14
		msanOnuVideoAniPortTable OBJECT-TYPE
			SYNTAX SEQUENCE OF MsanOnuVideoAniPortEntry
			MAX-ACCESS not-accessible
			STATUS current
			DESCRIPTION
				"Description."
			::= { msanOnu 14 }

		
		-- 1.3.6.1.4.1.1332.1.1.5.3.111.14.1
		msanOnuVideoAniPortEntry OBJECT-TYPE
			SYNTAX MsanOnuVideoAniPortEntry
			MAX-ACCESS not-accessible
			STATUS current
			DESCRIPTION
				"Description."
			INDEX { msanOnuVideoAniPortOnuIfIndex, msanOnuVideoAniPortAniId }
			::= { msanOnuVideoAniPortTable 1 }

		
		MsanOnuVideoAniPortEntry ::=
			SEQUENCE { 
				msanOnuVideoAniPortOnuIfIndex
					Integer32,
				msanOnuVideoAniPortAniId
					Integer32,
				msanOnuVideoAniPortAdminState
					INTEGER,
				msanOnuVideoAniPortOperState
					INTEGER,
				msanOnuVideoAniPortRowStatus
					RowStatus,
				msanOnuVideoAniPortTotalOpticalPowerLevel
					Integer32
			 }

		-- 1.3.6.1.4.1.1332.1.1.5.3.111.14.1.1
		msanOnuVideoAniPortOnuIfIndex OBJECT-TYPE
			SYNTAX Integer32
			MAX-ACCESS not-accessible
			STATUS current
			DESCRIPTION
				"Index of ONU (from ifTable)."
			::= { msanOnuVideoAniPortEntry 1 }

		
		-- 1.3.6.1.4.1.1332.1.1.5.3.111.14.1.2
		msanOnuVideoAniPortAniId OBJECT-TYPE
			SYNTAX Integer32
			MAX-ACCESS not-accessible
			STATUS current
			DESCRIPTION
				"ONU Video ANI Port identifier."
			::= { msanOnuVideoAniPortEntry 2 }

		
		-- 1.3.6.1.4.1.1332.1.1.5.3.111.14.1.3
		msanOnuVideoAniPortAdminState OBJECT-TYPE
			SYNTAX INTEGER
				{
				enable(1),
				disable(2)
				}
			MAX-ACCESS read-only
			STATUS current
			DESCRIPTION
				"ONU Video ANI port  administration state."
			::= { msanOnuVideoAniPortEntry 3 }

		
		-- 1.3.6.1.4.1.1332.1.1.5.3.111.14.1.4
		msanOnuVideoAniPortOperState OBJECT-TYPE
			SYNTAX INTEGER
				{
				up(1),
				down(2),
				notAvailable(3)
				}
			MAX-ACCESS read-only
			STATUS current
			DESCRIPTION
				"ONU Video ANI port  operational state."
			::= { msanOnuVideoAniPortEntry 4 }

		
		-- 1.3.6.1.4.1.1332.1.1.5.3.111.14.1.5
		msanOnuVideoAniPortRowStatus OBJECT-TYPE
			SYNTAX RowStatus
			MAX-ACCESS read-write
			STATUS current
			DESCRIPTION
				"The row status object controls the creation/deletion of rows in this table.
				Its semantics are the same as those for the RowStatus textual convention specified for SNMPv2.
				For row creation use createAndGo(4).
				For row activation use active(1).
				For row deletion use destroy(6).
				
				Other values are currently not supported."
			::= { msanOnuVideoAniPortEntry 5 }

		
		-- 1.3.6.1.4.1.1332.1.1.5.3.111.14.1.6
		msanOnuVideoAniPortTotalOpticalPowerLevel OBJECT-TYPE
			SYNTAX Integer32
			UNITS "dBuW"
			MAX-ACCESS read-only
			STATUS current
			DESCRIPTION
				"ONU Video ANI port  Total Optical Power Level [dBuW].
				Info: -1 defines that value is not available."
			::= { msanOnuVideoAniPortEntry 6 }

		
		-- 1.3.6.1.4.1.1332.1.1.5.3.111.15
		msanOnuVideoUniPortTable OBJECT-TYPE
			SYNTAX SEQUENCE OF MsanOnuVideoUniPortEntry
			MAX-ACCESS not-accessible
			STATUS current
			DESCRIPTION
				"Description."
			::= { msanOnu 15 }

		
		-- 1.3.6.1.4.1.1332.1.1.5.3.111.15.1
		msanOnuVideoUniPortEntry OBJECT-TYPE
			SYNTAX MsanOnuVideoUniPortEntry
			MAX-ACCESS not-accessible
			STATUS current
			DESCRIPTION
				"Description."
			INDEX { msanOnuVideoUniPortOnuIfIndex, msanOnuVideoUniPortUniId }
			::= { msanOnuVideoUniPortTable 1 }

		
		MsanOnuVideoUniPortEntry ::=
			SEQUENCE { 
				msanOnuVideoUniPortOnuIfIndex
					Integer32,
				msanOnuVideoUniPortUniId
					Integer32,
				msanOnuVideoUniPortAdminState
					INTEGER,
				msanOnuVideoUniPortOperState
					INTEGER,
				msanOnuVideoUniPortRowStatus
					RowStatus
			 }

		-- 1.3.6.1.4.1.1332.1.1.5.3.111.15.1.1
		msanOnuVideoUniPortOnuIfIndex OBJECT-TYPE
			SYNTAX Integer32
			MAX-ACCESS not-accessible
			STATUS current
			DESCRIPTION
				"Index of ONU (from ifTable)."
			::= { msanOnuVideoUniPortEntry 1 }

		
		-- 1.3.6.1.4.1.1332.1.1.5.3.111.15.1.2
		msanOnuVideoUniPortUniId OBJECT-TYPE
			SYNTAX Integer32
			MAX-ACCESS not-accessible
			STATUS current
			DESCRIPTION
				"ONU Video Ani Port identifier."
			::= { msanOnuVideoUniPortEntry 2 }

		
		-- 1.3.6.1.4.1.1332.1.1.5.3.111.15.1.3
		msanOnuVideoUniPortAdminState OBJECT-TYPE
			SYNTAX INTEGER
				{
				enable(1),
				disable(2)
				}
			MAX-ACCESS read-only
			STATUS current
			DESCRIPTION
				"ONU Video UNI port  administration state."
			::= { msanOnuVideoUniPortEntry 3 }

		
		-- 1.3.6.1.4.1.1332.1.1.5.3.111.15.1.4
		msanOnuVideoUniPortOperState OBJECT-TYPE
			SYNTAX INTEGER
				{
				up(1),
				down(2),
				notAvailable(3)
				}
			MAX-ACCESS read-only
			STATUS current
			DESCRIPTION
				"ONU Video UNI port  operational state."
			::= { msanOnuVideoUniPortEntry 4 }

		
		-- 1.3.6.1.4.1.1332.1.1.5.3.111.15.1.5
		msanOnuVideoUniPortRowStatus OBJECT-TYPE
			SYNTAX RowStatus
			MAX-ACCESS read-write
			STATUS current
			DESCRIPTION
				"The row status object controls the creation/deletion of rows in this table.
				Its semantics are the same as those for the RowStatus textual convention specified for SNMPv2.
				For row creation use createAndGo(4).
				For row activation use active(1).
				For row deletion use destroy(6).
				
				Other values are currently not supported."
			::= { msanOnuVideoUniPortEntry 5 }

		
		-- 1.3.6.1.4.1.1332.1.1.5.3.111.16
		msanOnuEthPortConfTable OBJECT-TYPE
			SYNTAX SEQUENCE OF MsanOnuEthPortConfEntry
			MAX-ACCESS not-accessible
			STATUS current
			DESCRIPTION
				"Description."
			::= { msanOnu 16 }

		
		-- 1.3.6.1.4.1.1332.1.1.5.3.111.16.1
		msanOnuEthPortConfEntry OBJECT-TYPE
			SYNTAX MsanOnuEthPortConfEntry
			MAX-ACCESS not-accessible
			STATUS current
			DESCRIPTION
				"Description."
			INDEX { msanOnuEthPortConfOnuIfIndex, msanOnuEthPortConfUniId }
			::= { msanOnuEthPortConfTable 1 }

		
		MsanOnuEthPortConfEntry ::=
			SEQUENCE { 
				msanOnuEthPortConfOnuIfIndex
					Integer32,
				msanOnuEthPortConfUniId
					Integer32,
				msanOnuEthPortConfAdminState
					INTEGER
			 }

		-- 1.3.6.1.4.1.1332.1.1.5.3.111.16.1.1
		msanOnuEthPortConfOnuIfIndex OBJECT-TYPE
			SYNTAX Integer32
			MAX-ACCESS not-accessible
			STATUS current
			DESCRIPTION
				"Index of ONU (from ifTable)."
			::= { msanOnuEthPortConfEntry 1 }

		
		-- 1.3.6.1.4.1.1332.1.1.5.3.111.16.1.2
		msanOnuEthPortConfUniId OBJECT-TYPE
			SYNTAX Integer32
			MAX-ACCESS not-accessible
			STATUS current
			DESCRIPTION
				"ONU Ethernet Port (UNI) identifier."
			::= { msanOnuEthPortConfEntry 2 }

		
		-- 1.3.6.1.4.1.1332.1.1.5.3.111.16.1.3
		msanOnuEthPortConfAdminState OBJECT-TYPE
			SYNTAX INTEGER
				{
				enable(1),
				disable(2),
				poe(3),
				unconfigured(4)
				}
			MAX-ACCESS read-write
			STATUS current
			DESCRIPTION
				"ONU eth port (UNI) administration state forced by OLT side."
			::= { msanOnuEthPortConfEntry 3 }

		
		-- 1.3.6.1.4.1.1332.1.1.5.3.112
		msanOlt OBJECT IDENTIFIER ::= { msanAdditionalConf 112 }

		
		-- 1.3.6.1.4.1.1332.1.1.5.3.112.1
		msanOltGlobal OBJECT IDENTIFIER ::= { msanOlt 1 }

		
		-- 1.3.6.1.4.1.1332.1.1.5.3.112.1.1
		msanOltBlackListRefresh OBJECT-TYPE
			SYNTAX INTEGER
				{
				enable(1),
				disable(2)
				}
			MAX-ACCESS read-write
			STATUS current
			DESCRIPTION
				"Set this option to enable to initiate a blacklist refresh for all OLT ports."
			::= { msanOltGlobal 1 }

		
		-- 1.3.6.1.4.1.1332.1.1.5.3.112.1.2
		msanOltProtectSwitchHeartbeatRepetitionDelay OBJECT-TYPE
			SYNTAX Integer32 (100..5000)
			UNITS "miliseconds"
			MAX-ACCESS read-write
			STATUS current
			DESCRIPTION
				"OLT Protection Switching Heartbeat repetition delay."
			::= { msanOltGlobal 2 }

		
		-- 1.3.6.1.4.1.1332.1.1.5.3.112.1.3
		msanOltProtectSwitchHeartbeatLossThreshold OBJECT-TYPE
			SYNTAX Integer32 (1..10)
			MAX-ACCESS read-write
			STATUS current
			DESCRIPTION
				"OLT Protection Switching Heartbeat loss threshold."
			::= { msanOltGlobal 3 }

		
		-- 1.3.6.1.4.1.1332.1.1.5.3.112.2
		msanOltPortTable OBJECT-TYPE
			SYNTAX SEQUENCE OF MsanOltPortEntry
			MAX-ACCESS not-accessible
			STATUS current
			DESCRIPTION
				" "
			::= { msanOlt 2 }

		
		-- 1.3.6.1.4.1.1332.1.1.5.3.112.2.1
		msanOltPortEntry OBJECT-TYPE
			SYNTAX MsanOltPortEntry
			MAX-ACCESS not-accessible
			STATUS current
			DESCRIPTION
				"Row Description"
			INDEX { msanOltPortIfIndex }
			::= { msanOltPortTable 1 }

		
		MsanOltPortEntry ::=
			SEQUENCE { 
				msanOltPortIfIndex
					Integer32,
				msanOltPortOnuDiscoveryMode
					INTEGER,
				msanOltPortOnuDiscoveryInterval
					Unsigned32,
				msanOltPortDbaCycleTime
					Unsigned32,
				msanOltPortLinkMinDistance
					INTEGER,
				msanOltPortLinkMaxDistance
					INTEGER,
				msanOltPortLosThreshold
					INTEGER,
				msanOltPortLofThreshold
					INTEGER,
				msanOltPortBlackListRefresh
					INTEGER,
				msanOltPortUsEstAvailTotalBw
					Integer32,
				msanOltPortUsEstAvailFixedBw
					Integer32,
				msanOltPortUsActAvailTotalBw
					Integer32,
				msanOltPortUsActAvailFixedBw
					Integer32,
				msanOltPortEncryptKeyExchange
					INTEGER,
				msanOltPortEncryptKeyExchangeInterval
					Integer32,
				msanOltPortTransciverVendorPN
					DisplayString,
				msanOltPortRogueOnuDetection
					INTEGER,
				msanOltPortOnuPhyPowerLevel
					INTEGER,
				msanOltPortPowerMeasurementsStart
					INTEGER,
				msanOltPortDsFec
					INTEGER
			 }

		-- 1.3.6.1.4.1.1332.1.1.5.3.112.2.1.2
		msanOltPortIfIndex OBJECT-TYPE
			SYNTAX Integer32
			MAX-ACCESS not-accessible
			STATUS current
			DESCRIPTION
				"Index of OLT port (from ifTable)."
			::= { msanOltPortEntry 2 }

		
		-- 1.3.6.1.4.1.1332.1.1.5.3.112.2.1.5
		msanOltPortOnuDiscoveryMode OBJECT-TYPE
			SYNTAX INTEGER
				{
				autoPeriodic(1),
				manualEnabledOnceThenDisabled(2),
				disabled(3)
				}
			MAX-ACCESS read-write
			STATUS current
			DESCRIPTION
				"ONU discovery mode: 
				1 Auto periodic (onuDiscoveryInterval is the 
				period) 
				2 Manual enabled once then disabled 
				3 Disabled "
			DEFVAL { 1 }
			::= { msanOltPortEntry 5 }

		
		-- 1.3.6.1.4.1.1332.1.1.5.3.112.2.1.6
		msanOltPortOnuDiscoveryInterval OBJECT-TYPE
			SYNTAX Unsigned32 (1..3600)
			MAX-ACCESS read-write
			STATUS current
			DESCRIPTION
				"ONU discovery interval, i.e., serial Number acquisition 
				interval in seconds. The value ranges from 1 to 3600 "
			DEFVAL { 30 }
			::= { msanOltPortEntry 6 }

		
		-- 1.3.6.1.4.1.1332.1.1.5.3.112.2.1.7
		msanOltPortDbaCycleTime OBJECT-TYPE
			SYNTAX Unsigned32 (2..8)
			MAX-ACCESS read-write
			STATUS current
			DESCRIPTION
				"Upstream bandwidth assignment cycle time. only support 2ms, 4ms and 8ms."
			DEFVAL { 8 }
			::= { msanOltPortEntry 7 }

		
		-- 1.3.6.1.4.1.1332.1.1.5.3.112.2.1.8
		msanOltPortLinkMinDistance OBJECT-TYPE
			SYNTAX INTEGER (0..60)
			UNITS "km"
			MAX-ACCESS read-write
			STATUS current
			DESCRIPTION
				"Minimum PON link distance.
				
				Maximum allowed interval between msanOltPortLinkMinDistance and msanOltPortLinkMaxDistance
				is 20km."
			::= { msanOltPortEntry 8 }

		
		-- 1.3.6.1.4.1.1332.1.1.5.3.112.2.1.9
		msanOltPortLinkMaxDistance OBJECT-TYPE
			SYNTAX INTEGER (0..60)
			UNITS "km"
			MAX-ACCESS read-write
			STATUS current
			DESCRIPTION
				"Maximum PON link distance.
				
				Maximum allowed interval between msanOltPortLinkMinDistance and msanOltPortLinkMaxDistance
				is 20km."
			::= { msanOltPortEntry 9 }

		
		-- 1.3.6.1.4.1.1332.1.1.5.3.112.2.1.10
		msanOltPortLosThreshold OBJECT-TYPE
			SYNTAX INTEGER (1..10)
			MAX-ACCESS read-only
			STATUS current
			DESCRIPTION
				"The number of consecutive upstream frames that had valid alloc id for which no optical signal was received from
				any ONT on the link. After this many number of frames, a LOS alarm will be raised.
				WARNING: The default value = 4 is set by G984.3 Standard. Modify for debug purposes only."
			DEFVAL { 4 }
			::= { msanOltPortEntry 10 }

		
		-- 1.3.6.1.4.1.1332.1.1.5.3.112.2.1.11
		msanOltPortLofThreshold OBJECT-TYPE
			SYNTAX INTEGER (1..10)
			MAX-ACCESS read-only
			STATUS current
			DESCRIPTION
				"The number of consecutive upstream frames from an ONT that are lost. After this many number of frames, a LOFi 
				alarm will be raised.
				WARNING: The default value = 4 is set by G984.3 Standard. Modify for debug purposes only."
			DEFVAL { 4 }
			::= { msanOltPortEntry 11 }

		
		-- 1.3.6.1.4.1.1332.1.1.5.3.112.2.1.12
		msanOltPortBlackListRefresh OBJECT-TYPE
			SYNTAX INTEGER
				{
				enable(1),
				disable(2)
				}
			MAX-ACCESS read-write
			STATUS current
			DESCRIPTION
				"Set this option to ¡enable¡to initiate a blacklist refresh for this OLT port."
			::= { msanOltPortEntry 12 }

		
		-- 1.3.6.1.4.1.1332.1.1.5.3.112.2.1.13
		msanOltPortUsEstAvailTotalBw OBJECT-TYPE
			SYNTAX Integer32
			UNITS "kbps"
			MAX-ACCESS read-only
			STATUS current
			DESCRIPTION
				"OLT interface estimated available total upstream bandwidth."
			::= { msanOltPortEntry 13 }

		
		-- 1.3.6.1.4.1.1332.1.1.5.3.112.2.1.14
		msanOltPortUsEstAvailFixedBw OBJECT-TYPE
			SYNTAX Integer32
			UNITS "kbps"
			MAX-ACCESS read-only
			STATUS current
			DESCRIPTION
				"OLT interface estimated available fixed upstream bandwidth."
			::= { msanOltPortEntry 14 }

		
		-- 1.3.6.1.4.1.1332.1.1.5.3.112.2.1.15
		msanOltPortUsActAvailTotalBw OBJECT-TYPE
			SYNTAX Integer32
			UNITS "kbps"
			MAX-ACCESS read-only
			STATUS current
			DESCRIPTION
				"OLT interface actual available total upstream bandwidth."
			::= { msanOltPortEntry 15 }

		
		-- 1.3.6.1.4.1.1332.1.1.5.3.112.2.1.16
		msanOltPortUsActAvailFixedBw OBJECT-TYPE
			SYNTAX Integer32
			UNITS "kbps"
			MAX-ACCESS read-only
			STATUS current
			DESCRIPTION
				"OLT interface actual available total upstream bandwidth."
			::= { msanOltPortEntry 16 }

		
		-- 1.3.6.1.4.1.1332.1.1.5.3.112.2.1.17
		msanOltPortEncryptKeyExchange OBJECT-TYPE
			SYNTAX INTEGER
				{
				enable(1),
				disable(2)
				}
			MAX-ACCESS read-write
			STATUS current
			DESCRIPTION
				"Encryption key exchange."
			::= { msanOltPortEntry 17 }

		
		-- 1.3.6.1.4.1.1332.1.1.5.3.112.2.1.18
		msanOltPortEncryptKeyExchangeInterval OBJECT-TYPE
			SYNTAX Integer32 (30..26000)
			UNITS "seconds"
			MAX-ACCESS read-write
			STATUS current
			DESCRIPTION
				"Encryption key exchange interval."
			::= { msanOltPortEntry 18 }

		
		-- 1.3.6.1.4.1.1332.1.1.5.3.112.2.1.19
		msanOltPortTransciverVendorPN OBJECT-TYPE
			SYNTAX DisplayString
			MAX-ACCESS read-only
			STATUS current
			DESCRIPTION
				"GPON SFP type"
			::= { msanOltPortEntry 19 }

		
		-- 1.3.6.1.4.1.1332.1.1.5.3.112.2.1.20
		msanOltPortRogueOnuDetection OBJECT-TYPE
			SYNTAX INTEGER
				{
				enable(1),
				disable(2)
				}
			MAX-ACCESS read-write
			STATUS current
			DESCRIPTION
				"Rogue ONU detection."
			::= { msanOltPortEntry 20 }

		
		-- 1.3.6.1.4.1.1332.1.1.5.3.112.2.1.21
		msanOltPortOnuPhyPowerLevel OBJECT-TYPE
			SYNTAX INTEGER
				{
				normal(1),
				level3dB(2),
				level6dB(3)
				}
			MAX-ACCESS read-write
			STATUS current
			DESCRIPTION
				" ONU phy power leveling"
			::= { msanOltPortEntry 21 }

		
		-- 1.3.6.1.4.1.1332.1.1.5.3.112.2.1.22
		msanOltPortPowerMeasurementsStart OBJECT-TYPE
			SYNTAX INTEGER
				{
				enable(1),
				disable(2)
				}
			MAX-ACCESS read-write
			STATUS current
			DESCRIPTION
				"Start ONU/OLT  Rx/Tx Power Measurements "
			DEFVAL { disable }
			::= { msanOltPortEntry 22 }

		
		-- 1.3.6.1.4.1.1332.1.1.5.3.112.2.1.23
		msanOltPortDsFec OBJECT-TYPE
			SYNTAX INTEGER
				{
				enable(1),
				disable(2)
				}
			MAX-ACCESS read-write
			STATUS current
			DESCRIPTION
				"Start ONU/OLT  Rx/Tx Power Measurements "
			DEFVAL { disable }
			::= { msanOltPortEntry 23 }

		
		-- 1.3.6.1.4.1.1332.1.1.5.3.112.3
		msanOltPortStatTable OBJECT-TYPE
			SYNTAX SEQUENCE OF MsanOltPortStatEntry
			MAX-ACCESS not-accessible
			STATUS current
			DESCRIPTION
				"Description."
			::= { msanOlt 3 }

		
		-- 1.3.6.1.4.1.1332.1.1.5.3.112.3.1
		msanOltPortStatEntry OBJECT-TYPE
			SYNTAX MsanOltPortStatEntry
			MAX-ACCESS not-accessible
			STATUS current
			DESCRIPTION
				"Description."
			INDEX { msanOltPortStatIfIndex, msanOltPortStatIntervalId }
			::= { msanOltPortStatTable 1 }

		
		MsanOltPortStatEntry ::=
			SEQUENCE { 
				msanOltPortStatIfIndex
					Integer32,
				msanOltPortStatIntervalId
					INTEGER,
				msanOltPortStatInOmciPkts
					Counter64,
				msanOltPortStatInCpuPkts
					Counter64,
				msanOltPortStatInPktsDiscarded
					Counter64,
				msanOltPortStatInPktsUndersize
					Counter64,
				msanOltPortStatInPktsOversize
					Counter64,
				msanOltPortStatInPktsCrcError
					Counter64,
				msanOltPortStatInPktsKeyError
					Counter64,
				msanOltPortStatOutPktsTpidError
					Counter64,
				msanOltPortStatOutPktsVidError
					Counter64,
				msanOltPortStatInPktsFragmentError
					Counter64,
				msanOltPortStatInGemFrames
					Counter64,
				msanOltPortStatInGemFramesDiscarded
					Counter64,
				msanOltPortStatInGemFramesIdle
					Counter64,
				msanOltPortStatInGemFramesCorrected
					Counter64,
				msanOltPortStatInGemFramesIllegal
					Counter64,
				msanOltPortStatInAllocationsValid
					Counter64,
				msanOltPortStatInAllocationsInvalid
					Counter64,
				msanOltPortStatInAllocationsDisabled
					Counter64,
				msanOltPortStatInPloamMsgs
					Counter64,
				msanOltPortStatInPloamMsgsNonIdle
					Counter64,
				msanOltPortStatInPloamMsgsError
					Counter64,
				msanOltPortStatInPloamMsgsDiscarded
					Counter64,
				msanOltPortStatInFecCodewords
					Counter64,
				msanOltPortStatInFecCodewordsUncorrected
					Counter64,
				msanOltPortStatInBip8Bytes
					Counter64,
				msanOltPortStatInBip8Errors
					Counter64,
				msanOltPortStatOutOmciPkts
					Counter64,
				msanOltPortStatOutCpuPkts
					Counter64,
				msanOltPortStatOutPktsDiscarded
					Counter64,
				msanOltPortStatOutGemFrames
					Counter64,
				msanOltPortStatOutPloamMsgs
					Counter64
			 }

		-- 1.3.6.1.4.1.1332.1.1.5.3.112.3.1.1
		msanOltPortStatIfIndex OBJECT-TYPE
			SYNTAX Integer32
			MAX-ACCESS not-accessible
			STATUS current
			DESCRIPTION
				"Index of OLT interface (from ifTable)."
			::= { msanOltPortStatEntry 1 }

		
		-- 1.3.6.1.4.1.1332.1.1.5.3.112.3.1.2
		msanOltPortStatIntervalId OBJECT-TYPE
			SYNTAX INTEGER (0..96)
			MAX-ACCESS not-accessible
			STATUS current
			DESCRIPTION
				"Serves as an index for this table. Identifies the
				15 interval in which PM was collected. The value
				0 identifies the current interval. Value 1 identifies
				the latest 15 minute interval and value 96
				identifies the last 15 minute interval in a a 24 hour period.
				"
			::= { msanOltPortStatEntry 2 }

		
		-- 1.3.6.1.4.1.1332.1.1.5.3.112.3.1.3
		msanOltPortStatInOmciPkts OBJECT-TYPE
			SYNTAX Counter64
			UNITS "Packets"
			MAX-ACCESS read-only
			STATUS current
			DESCRIPTION
				"Received OMCI packets."
			::= { msanOltPortStatEntry 3 }

		
		-- 1.3.6.1.4.1.1332.1.1.5.3.112.3.1.4
		msanOltPortStatInCpuPkts OBJECT-TYPE
			SYNTAX Counter64
			UNITS "Packets"
			MAX-ACCESS read-only
			STATUS current
			DESCRIPTION
				"Received CPU packets."
			::= { msanOltPortStatEntry 4 }

		
		-- 1.3.6.1.4.1.1332.1.1.5.3.112.3.1.5
		msanOltPortStatInPktsDiscarded OBJECT-TYPE
			SYNTAX Counter64
			UNITS "Packets"
			MAX-ACCESS read-only
			STATUS current
			DESCRIPTION
				"Number of dropped received packets."
			::= { msanOltPortStatEntry 5 }

		
		-- 1.3.6.1.4.1.1332.1.1.5.3.112.3.1.6
		msanOltPortStatInPktsUndersize OBJECT-TYPE
			SYNTAX Counter64
			UNITS "Packets"
			MAX-ACCESS read-only
			STATUS current
			DESCRIPTION
				"Received packets dropped due to length too short."
			::= { msanOltPortStatEntry 6 }

		
		-- 1.3.6.1.4.1.1332.1.1.5.3.112.3.1.7
		msanOltPortStatInPktsOversize OBJECT-TYPE
			SYNTAX Counter64
			UNITS "Packets"
			MAX-ACCESS read-only
			STATUS current
			DESCRIPTION
				"Received packets dropped due to length too long."
			::= { msanOltPortStatEntry 7 }

		
		-- 1.3.6.1.4.1.1332.1.1.5.3.112.3.1.8
		msanOltPortStatInPktsCrcError OBJECT-TYPE
			SYNTAX Counter64
			UNITS "Packets"
			MAX-ACCESS read-only
			STATUS current
			DESCRIPTION
				"Received packets dropped due to CRC error."
			::= { msanOltPortStatEntry 8 }

		
		-- 1.3.6.1.4.1.1332.1.1.5.3.112.3.1.9
		msanOltPortStatInPktsKeyError OBJECT-TYPE
			SYNTAX Counter64
			UNITS "Packets"
			MAX-ACCESS read-only
			STATUS current
			DESCRIPTION
				"Received packets dropped due to Key error."
			::= { msanOltPortStatEntry 9 }

		
		-- 1.3.6.1.4.1.1332.1.1.5.3.112.3.1.10
		msanOltPortStatOutPktsTpidError OBJECT-TYPE
			SYNTAX Counter64
			UNITS "Packets"
			MAX-ACCESS read-only
			STATUS current
			DESCRIPTION
				"Received packet dropped due to TPID error."
			::= { msanOltPortStatEntry 10 }

		
		-- 1.3.6.1.4.1.1332.1.1.5.3.112.3.1.11
		msanOltPortStatOutPktsVidError OBJECT-TYPE
			SYNTAX Counter64
			UNITS "Packets"
			MAX-ACCESS read-only
			STATUS current
			DESCRIPTION
				"Received packet dropped due to VID error."
			::= { msanOltPortStatEntry 11 }

		
		-- 1.3.6.1.4.1.1332.1.1.5.3.112.3.1.12
		msanOltPortStatInPktsFragmentError OBJECT-TYPE
			SYNTAX Counter64
			UNITS "Packets"
			MAX-ACCESS read-only
			STATUS current
			DESCRIPTION
				"Received packet dropped due to fragmentation error."
			::= { msanOltPortStatEntry 12 }

		
		-- 1.3.6.1.4.1.1332.1.1.5.3.112.3.1.13
		msanOltPortStatInGemFrames OBJECT-TYPE
			SYNTAX Counter64
			UNITS "Frames"
			MAX-ACCESS read-only
			STATUS current
			DESCRIPTION
				"Received GEM frames."
			::= { msanOltPortStatEntry 13 }

		
		-- 1.3.6.1.4.1.1332.1.1.5.3.112.3.1.14
		msanOltPortStatInGemFramesDiscarded OBJECT-TYPE
			SYNTAX Counter64
			UNITS "Frames"
			MAX-ACCESS read-only
			STATUS current
			DESCRIPTION
				"Number of corrected received GEM frames."
			::= { msanOltPortStatEntry 14 }

		
		-- 1.3.6.1.4.1.1332.1.1.5.3.112.3.1.15
		msanOltPortStatInGemFramesIdle OBJECT-TYPE
			SYNTAX Counter64
			UNITS "Frames"
			MAX-ACCESS read-only
			STATUS current
			DESCRIPTION
				"Number of idle received GEM frames."
			::= { msanOltPortStatEntry 15 }

		
		-- 1.3.6.1.4.1.1332.1.1.5.3.112.3.1.16
		msanOltPortStatInGemFramesCorrected OBJECT-TYPE
			SYNTAX Counter64
			UNITS "Frames"
			MAX-ACCESS read-only
			STATUS current
			DESCRIPTION
				"Number of corrected received GEM frames."
			::= { msanOltPortStatEntry 16 }

		
		-- 1.3.6.1.4.1.1332.1.1.5.3.112.3.1.17
		msanOltPortStatInGemFramesIllegal OBJECT-TYPE
			SYNTAX Counter64
			UNITS "Frames"
			MAX-ACCESS read-only
			STATUS current
			DESCRIPTION
				"Number of illegal received GEM frames."
			::= { msanOltPortStatEntry 17 }

		
		-- 1.3.6.1.4.1.1332.1.1.5.3.112.3.1.18
		msanOltPortStatInAllocationsValid OBJECT-TYPE
			SYNTAX Counter64
			UNITS "Allocations"
			MAX-ACCESS read-only
			STATUS current
			DESCRIPTION
				"Number of received valid allocations."
			::= { msanOltPortStatEntry 18 }

		
		-- 1.3.6.1.4.1.1332.1.1.5.3.112.3.1.19
		msanOltPortStatInAllocationsInvalid OBJECT-TYPE
			SYNTAX Counter64
			UNITS "Allocations"
			MAX-ACCESS read-only
			STATUS current
			DESCRIPTION
				"Number of received invalid allocations."
			::= { msanOltPortStatEntry 19 }

		
		-- 1.3.6.1.4.1.1332.1.1.5.3.112.3.1.20
		msanOltPortStatInAllocationsDisabled OBJECT-TYPE
			SYNTAX Counter64
			UNITS "Allocations"
			MAX-ACCESS read-only
			STATUS current
			DESCRIPTION
				"Number of received disabled allocations."
			::= { msanOltPortStatEntry 20 }

		
		-- 1.3.6.1.4.1.1332.1.1.5.3.112.3.1.21
		msanOltPortStatInPloamMsgs OBJECT-TYPE
			SYNTAX Counter64
			UNITS "PLOAM messages"
			MAX-ACCESS read-only
			STATUS current
			DESCRIPTION
				"Number of received PLOAM (physical layer operations and maintenance) messages."
			::= { msanOltPortStatEntry 21 }

		
		-- 1.3.6.1.4.1.1332.1.1.5.3.112.3.1.22
		msanOltPortStatInPloamMsgsNonIdle OBJECT-TYPE
			SYNTAX Counter64
			UNITS "Messages"
			MAX-ACCESS read-only
			STATUS current
			DESCRIPTION
				"Number of received non-idle PLOAM (physical layer operations and maintenance) messages."
			::= { msanOltPortStatEntry 22 }

		
		-- 1.3.6.1.4.1.1332.1.1.5.3.112.3.1.23
		msanOltPortStatInPloamMsgsError OBJECT-TYPE
			SYNTAX Counter64
			UNITS "Messages"
			MAX-ACCESS read-only
			STATUS current
			DESCRIPTION
				"Number of received PLOAM (physical layer operations and maintenance) messages with errors."
			::= { msanOltPortStatEntry 23 }

		
		-- 1.3.6.1.4.1.1332.1.1.5.3.112.3.1.24
		msanOltPortStatInPloamMsgsDiscarded OBJECT-TYPE
			SYNTAX Counter64
			UNITS "Messages"
			MAX-ACCESS read-only
			STATUS current
			DESCRIPTION
				"Number of discarded PLOAM (physical layer operations and maintenance) messages."
			::= { msanOltPortStatEntry 24 }

		
		-- 1.3.6.1.4.1.1332.1.1.5.3.112.3.1.25
		msanOltPortStatInFecCodewords OBJECT-TYPE
			SYNTAX Counter64
			UNITS "Codewords"
			MAX-ACCESS read-only
			STATUS current
			DESCRIPTION
				"Number of received FEC (Forward error correction) codewords."
			::= { msanOltPortStatEntry 25 }

		
		-- 1.3.6.1.4.1.1332.1.1.5.3.112.3.1.26
		msanOltPortStatInFecCodewordsUncorrected OBJECT-TYPE
			SYNTAX Counter64
			UNITS "Codewords"
			MAX-ACCESS read-only
			STATUS current
			DESCRIPTION
				"Number of received uncorrected FEC (Forward error correction) codewords."
			::= { msanOltPortStatEntry 26 }

		
		-- 1.3.6.1.4.1.1332.1.1.5.3.112.3.1.27
		msanOltPortStatInBip8Bytes OBJECT-TYPE
			SYNTAX Counter64
			UNITS "Bytes"
			MAX-ACCESS read-only
			STATUS current
			DESCRIPTION
				"Number of received bytes protected by Bip8."
			::= { msanOltPortStatEntry 27 }

		
		-- 1.3.6.1.4.1.1332.1.1.5.3.112.3.1.28
		msanOltPortStatInBip8Errors OBJECT-TYPE
			SYNTAX Counter64
			UNITS "Bytes"
			MAX-ACCESS read-only
			STATUS current
			DESCRIPTION
				"Number of received Bip8 errors."
			::= { msanOltPortStatEntry 28 }

		
		-- 1.3.6.1.4.1.1332.1.1.5.3.112.3.1.29
		msanOltPortStatOutOmciPkts OBJECT-TYPE
			SYNTAX Counter64
			UNITS "Packets"
			MAX-ACCESS read-only
			STATUS current
			DESCRIPTION
				"Transmitted OMCI packets."
			::= { msanOltPortStatEntry 29 }

		
		-- 1.3.6.1.4.1.1332.1.1.5.3.112.3.1.30
		msanOltPortStatOutCpuPkts OBJECT-TYPE
			SYNTAX Counter64
			UNITS "Packets"
			MAX-ACCESS read-only
			STATUS current
			DESCRIPTION
				"Transmitted CPU packets."
			::= { msanOltPortStatEntry 30 }

		
		-- 1.3.6.1.4.1.1332.1.1.5.3.112.3.1.31
		msanOltPortStatOutPktsDiscarded OBJECT-TYPE
			SYNTAX Counter64
			UNITS "Packets"
			MAX-ACCESS read-only
			STATUS current
			DESCRIPTION
				"Number of dropped transmitted packets because of illegal length."
			::= { msanOltPortStatEntry 31 }

		
		-- 1.3.6.1.4.1.1332.1.1.5.3.112.3.1.32
		msanOltPortStatOutGemFrames OBJECT-TYPE
			SYNTAX Counter64
			UNITS "Frames"
			MAX-ACCESS read-only
			STATUS current
			DESCRIPTION
				"Transmitted GEM frames."
			::= { msanOltPortStatEntry 32 }

		
		-- 1.3.6.1.4.1.1332.1.1.5.3.112.3.1.33
		msanOltPortStatOutPloamMsgs OBJECT-TYPE
			SYNTAX Counter64
			UNITS "PLOAM messages"
			MAX-ACCESS read-only
			STATUS current
			DESCRIPTION
				"Number of transmitted PLOAM (physical layer operations and maintenance) messages."
			::= { msanOltPortStatEntry 33 }

		
		-- 1.3.6.1.4.1.1332.1.1.5.3.112.4
		msanOltOnuPortStatTable OBJECT-TYPE
			SYNTAX SEQUENCE OF MsanOltOnuPortStatEntry
			MAX-ACCESS not-accessible
			STATUS current
			DESCRIPTION
				"Description."
			::= { msanOlt 4 }

		
		-- 1.3.6.1.4.1.1332.1.1.5.3.112.4.1
		msanOltOnuPortStatEntry OBJECT-TYPE
			SYNTAX MsanOltOnuPortStatEntry
			MAX-ACCESS not-accessible
			STATUS current
			DESCRIPTION
				"Description."
			INDEX { msanOltOnuPortStatIfIndex }
			::= { msanOltOnuPortStatTable 1 }

		
		MsanOltOnuPortStatEntry ::=
			SEQUENCE { 
				msanOltOnuPortStatIfIndex
					Integer32,
				msanOltOnuPortStatInFecCodewords
					Counter64,
				msanOltOnuPortStatInFecBytesCorrected
					Counter64,
				msanOltOnuPortStatInFecCodewordsCorrected
					Counter64,
				msanOltOnuPortStatInFecCodewordsUncorrected
					Counter64,
				msanOltOnuPortStatInBip8Bytes
					Counter64,
				msanOltOnuPortStatInBip8Errors
					Counter64,
				msanOltOnuPortStatInPloamMsgsCrcError
					Counter64,
				msanOltOnuPortStatInPloamMsgsNonIdle
					Counter64,
				msanOltOnuPortStatInDriftPositive
					Counter64,
				msanOltOnuPortStatInDriftNegative
					Counter64,
				msanOltOnuPortStatInOmciPkts
					Counter64,
				msanOltOnuPortStatInOmciPktsCrcError
					Counter64,
				msanOltOnuPortStatInBerReported
					Counter64,
				msanOltOnuPortStatInLcdgErrors
					Counter64,
				msanOltOnuPortStatInRdiErrors
					Counter64,
				msanOltOnuPortStatUnreceivedBurst
					Counter64,
				msanOltOnuPortStatInDelimiterMissEvents
					Counter64
			 }

		-- 1.3.6.1.4.1.1332.1.1.5.3.112.4.1.1
		msanOltOnuPortStatIfIndex OBJECT-TYPE
			SYNTAX Integer32
			MAX-ACCESS not-accessible
			STATUS current
			DESCRIPTION
				"Index of ONU interface  (from ifTable)."
			::= { msanOltOnuPortStatEntry 1 }

		
		-- 1.3.6.1.4.1.1332.1.1.5.3.112.4.1.2
		msanOltOnuPortStatInFecCodewords OBJECT-TYPE
			SYNTAX Counter64
			UNITS "Codewords"
			MAX-ACCESS read-only
			STATUS current
			DESCRIPTION
				"Number of received FEC (Forward error correction) codewords.
				"
			::= { msanOltOnuPortStatEntry 2 }

		
		-- 1.3.6.1.4.1.1332.1.1.5.3.112.4.1.3
		msanOltOnuPortStatInFecBytesCorrected OBJECT-TYPE
			SYNTAX Counter64
			UNITS "Bytes"
			MAX-ACCESS read-only
			STATUS current
			DESCRIPTION
				"Number of received corrected FEC (Forward error correction) bytes."
			::= { msanOltOnuPortStatEntry 3 }

		
		-- 1.3.6.1.4.1.1332.1.1.5.3.112.4.1.4
		msanOltOnuPortStatInFecCodewordsCorrected OBJECT-TYPE
			SYNTAX Counter64
			UNITS "Codewords"
			MAX-ACCESS read-only
			STATUS current
			DESCRIPTION
				"Number of received corrected FEC (Forward error correction) codewords."
			::= { msanOltOnuPortStatEntry 4 }

		
		-- 1.3.6.1.4.1.1332.1.1.5.3.112.4.1.5
		msanOltOnuPortStatInFecCodewordsUncorrected OBJECT-TYPE
			SYNTAX Counter64
			UNITS "Codewords"
			MAX-ACCESS read-only
			STATUS current
			DESCRIPTION
				"Number of received uncorrected FEC (Forward error correction) codewords."
			::= { msanOltOnuPortStatEntry 5 }

		
		-- 1.3.6.1.4.1.1332.1.1.5.3.112.4.1.6
		msanOltOnuPortStatInBip8Bytes OBJECT-TYPE
			SYNTAX Counter64
			UNITS "Bytes"
			MAX-ACCESS read-only
			STATUS current
			DESCRIPTION
				"Number of received bytes protected by Bip8."
			::= { msanOltOnuPortStatEntry 6 }

		
		-- 1.3.6.1.4.1.1332.1.1.5.3.112.4.1.7
		msanOltOnuPortStatInBip8Errors OBJECT-TYPE
			SYNTAX Counter64
			MAX-ACCESS read-only
			STATUS current
			DESCRIPTION
				"Number of received  Bip8 errors."
			::= { msanOltOnuPortStatEntry 7 }

		
		-- 1.3.6.1.4.1.1332.1.1.5.3.112.4.1.8
		msanOltOnuPortStatInPloamMsgsCrcError OBJECT-TYPE
			SYNTAX Counter64
			UNITS "Messages"
			MAX-ACCESS read-only
			STATUS current
			DESCRIPTION
				"Number of received PLOAM (physical layer operations and maintenance) messages with CRC error."
			::= { msanOltOnuPortStatEntry 8 }

		
		-- 1.3.6.1.4.1.1332.1.1.5.3.112.4.1.9
		msanOltOnuPortStatInPloamMsgsNonIdle OBJECT-TYPE
			SYNTAX Counter64
			UNITS "Messages"
			MAX-ACCESS read-only
			STATUS current
			DESCRIPTION
				"Number of received non-idle PLOAM (physical layer operations and maintenance) messages."
			::= { msanOltOnuPortStatEntry 9 }

		
		-- 1.3.6.1.4.1.1332.1.1.5.3.112.4.1.10
		msanOltOnuPortStatInDriftPositive OBJECT-TYPE
			SYNTAX Counter64
			MAX-ACCESS read-only
			STATUS current
			DESCRIPTION
				"Number of accumulated positive drift in bits."
			::= { msanOltOnuPortStatEntry 10 }

		
		-- 1.3.6.1.4.1.1332.1.1.5.3.112.4.1.11
		msanOltOnuPortStatInDriftNegative OBJECT-TYPE
			SYNTAX Counter64
			MAX-ACCESS read-only
			STATUS current
			DESCRIPTION
				"Number of accumulated negative drift in bits."
			::= { msanOltOnuPortStatEntry 11 }

		
		-- 1.3.6.1.4.1.1332.1.1.5.3.112.4.1.12
		msanOltOnuPortStatInOmciPkts OBJECT-TYPE
			SYNTAX Counter64
			UNITS "Packets"
			MAX-ACCESS read-only
			STATUS current
			DESCRIPTION
				"Number of received OMCI packets."
			::= { msanOltOnuPortStatEntry 12 }

		
		-- 1.3.6.1.4.1.1332.1.1.5.3.112.4.1.13
		msanOltOnuPortStatInOmciPktsCrcError OBJECT-TYPE
			SYNTAX Counter64
			UNITS "Packets"
			MAX-ACCESS read-only
			STATUS current
			DESCRIPTION
				"Number of received OMCI packets with CRC error."
			::= { msanOltOnuPortStatEntry 13 }

		
		-- 1.3.6.1.4.1.1332.1.1.5.3.112.4.1.14
		msanOltOnuPortStatInBerReported OBJECT-TYPE
			SYNTAX Counter64
			MAX-ACCESS read-only
			STATUS current
			DESCRIPTION
				"Accumulated REI error count reported by the ONU."
			::= { msanOltOnuPortStatEntry 14 }

		
		-- 1.3.6.1.4.1.1332.1.1.5.3.112.4.1.15
		msanOltOnuPortStatInLcdgErrors OBJECT-TYPE
			SYNTAX Counter64
			MAX-ACCESS read-only
			STATUS current
			DESCRIPTION
				"Number of received LCDG errors."
			::= { msanOltOnuPortStatEntry 15 }

		
		-- 1.3.6.1.4.1.1332.1.1.5.3.112.4.1.16
		msanOltOnuPortStatInRdiErrors OBJECT-TYPE
			SYNTAX Counter64
			MAX-ACCESS read-only
			STATUS current
			DESCRIPTION
				"Number of received RDI errors."
			::= { msanOltOnuPortStatEntry 16 }

		
		-- 1.3.6.1.4.1.1332.1.1.5.3.112.4.1.17
		msanOltOnuPortStatUnreceivedBurst OBJECT-TYPE
			SYNTAX Counter64
			MAX-ACCESS read-only
			STATUS current
			DESCRIPTION
				"Un-received burst allocated to the ONU."
			::= { msanOltOnuPortStatEntry 17 }

		
		-- 1.3.6.1.4.1.1332.1.1.5.3.112.4.1.18
		msanOltOnuPortStatInDelimiterMissEvents OBJECT-TYPE
			SYNTAX Counter64
			MAX-ACCESS read-only
			STATUS current
			DESCRIPTION
				"Un-received burst allocated to the ONU."
			::= { msanOltOnuPortStatEntry 18 }

		
		-- 1.3.6.1.4.1.1332.1.1.5.3.112.5
		msanOltProtectSwitchPairTable OBJECT-TYPE
			SYNTAX SEQUENCE OF MsanOltProtectSwitchPairEntry
			MAX-ACCESS not-accessible
			STATUS current
			DESCRIPTION
				"Description."
			::= { msanOlt 5 }

		
		-- 1.3.6.1.4.1.1332.1.1.5.3.112.5.1
		msanOltProtectSwitchPairEntry OBJECT-TYPE
			SYNTAX MsanOltProtectSwitchPairEntry
			MAX-ACCESS not-accessible
			STATUS current
			DESCRIPTION
				"Description."
			INDEX { msanOltProtectSwitchPairName }
			::= { msanOltProtectSwitchPairTable 1 }

		
		MsanOltProtectSwitchPairEntry ::=
			SEQUENCE { 
				msanOltProtectSwitchPairName
					DisplayString,
				msanOltProtectSwitchPairPrimaryIfIndex
					Integer32,
				msanOltProtectSwitchPairPrimaryIpAddress
					IpAddress,
				msanOltProtectSwitchPairSecondaryIfIndex
					Integer32,
				msanOltProtectSwitchPairSecondaryIpAddress
					IpAddress,
				msanOltProtectSwitchPairType
					INTEGER,
				msanOltProtectSwitchPairTimeout
					Integer32,
				msanOltProtectSwitchPairActive
					INTEGER,
				msanOltProtectSwitchPairStatus
					INTEGER,
				msanOltProtectSwitchPairSwitchOver
					INTEGER,
				msanOltProtectSwitchPairRowStatus
					Integer32
			 }

		-- 1.3.6.1.4.1.1332.1.1.5.3.112.5.1.1
		msanOltProtectSwitchPairName OBJECT-TYPE
			SYNTAX DisplayString
			MAX-ACCESS not-accessible
			STATUS current
			DESCRIPTION
				"OLT Protection Switching Pair name."
			::= { msanOltProtectSwitchPairEntry 1 }

		
		-- 1.3.6.1.4.1.1332.1.1.5.3.112.5.1.2
		msanOltProtectSwitchPairPrimaryIfIndex OBJECT-TYPE
			SYNTAX Integer32
			MAX-ACCESS read-write
			STATUS current
			DESCRIPTION
				"OLT Protection Switching Pair: Index of Primary OLT interface  (from ifTable).
				
				Value 0 defines that parameter is not set."
			::= { msanOltProtectSwitchPairEntry 2 }

		
		-- 1.3.6.1.4.1.1332.1.1.5.3.112.5.1.3
		msanOltProtectSwitchPairPrimaryIpAddress OBJECT-TYPE
			SYNTAX IpAddress
			MAX-ACCESS read-only
			STATUS current
			DESCRIPTION
				"OLT Protection Switching Pair: IP Address of Primary OLT interface."
			::= { msanOltProtectSwitchPairEntry 3 }

		
		-- 1.3.6.1.4.1.1332.1.1.5.3.112.5.1.4
		msanOltProtectSwitchPairSecondaryIfIndex OBJECT-TYPE
			SYNTAX Integer32
			MAX-ACCESS read-write
			STATUS current
			DESCRIPTION
				"OLT Protection Switching Pair: Index of Secondary OLT interface  (from ifTable).
				
				Value 0 defines that parameter is not set."
			::= { msanOltProtectSwitchPairEntry 4 }

		
		-- 1.3.6.1.4.1.1332.1.1.5.3.112.5.1.5
		msanOltProtectSwitchPairSecondaryIpAddress OBJECT-TYPE
			SYNTAX IpAddress
			MAX-ACCESS read-write
			STATUS current
			DESCRIPTION
				"OLT Protection Switching Pair: IP Address of Secondary OLT interface "
			::= { msanOltProtectSwitchPairEntry 5 }

		
		-- 1.3.6.1.4.1.1332.1.1.5.3.112.5.1.6
		msanOltProtectSwitchPairType OBJECT-TYPE
			SYNTAX INTEGER { b(1) }
			MAX-ACCESS read-only
			STATUS current
			DESCRIPTION
				"OLT Protection Switching Pair type"
			::= { msanOltProtectSwitchPairEntry 6 }

		
		-- 1.3.6.1.4.1.1332.1.1.5.3.112.5.1.7
		msanOltProtectSwitchPairTimeout OBJECT-TYPE
			SYNTAX Integer32
			UNITS "miliseconds"
			MAX-ACCESS read-only
			STATUS obsolete
			DESCRIPTION
				"OLT Protection Switching Pair connection timeout."
			::= { msanOltProtectSwitchPairEntry 7 }

		
		-- 1.3.6.1.4.1.1332.1.1.5.3.112.5.1.8
		msanOltProtectSwitchPairActive OBJECT-TYPE
			SYNTAX INTEGER
				{
				primary(1),
				secondary(2),
				none(3)
				}
			MAX-ACCESS read-only
			STATUS current
			DESCRIPTION
				"OLT Protection Switching Pair currently active side."
			::= { msanOltProtectSwitchPairEntry 8 }

		
		-- 1.3.6.1.4.1.1332.1.1.5.3.112.5.1.9
		msanOltProtectSwitchPairStatus OBJECT-TYPE
			SYNTAX INTEGER
				{
				active(1),
				notInService(2)
				}
			MAX-ACCESS read-only
			STATUS current
			DESCRIPTION
				"OLT Protection Switching Pair connection status."
			::= { msanOltProtectSwitchPairEntry 9 }

		
		-- 1.3.6.1.4.1.1332.1.1.5.3.112.5.1.10
		msanOltProtectSwitchPairSwitchOver OBJECT-TYPE
			SYNTAX INTEGER
				{
				enable(1),
				disable(2)
				}
			MAX-ACCESS read-write
			STATUS current
			DESCRIPTION
				"OLT Protection Switching Pair switch over action."
			DEFVAL { disable }
			::= { msanOltProtectSwitchPairEntry 10 }

		
		-- 1.3.6.1.4.1.1332.1.1.5.3.112.5.1.11
		msanOltProtectSwitchPairRowStatus OBJECT-TYPE
			SYNTAX Integer32
			MAX-ACCESS read-write
			STATUS current
			DESCRIPTION
				"The row status object controls the creation/deletion of rows in this table. 
				Its semantics are the same as those for the RowStatus textual convention specified for SNMPv2.
				For row creation use createAndWait(5).
				For row activation use active(1).
				For row deletion use destroy(6).
				 	
				Other values are currently not supported.
				 	
				For row activation at least parameters msanOltProtectSwitchPairPrimaryIfIndex and
				msanOltProtectSwitchPairSecondaryIfIndex must be defined."
			::= { msanOltProtectSwitchPairEntry 11 }

		
		-- 1.3.6.1.4.1.1332.1.1.5.3.112.6
		msanOltPortSumStatTable OBJECT-TYPE
			SYNTAX SEQUENCE OF MsanOltPortSumStatEntry
			MAX-ACCESS not-accessible
			STATUS current
			DESCRIPTION
				"Description."
			::= { msanOlt 6 }

		
		-- 1.3.6.1.4.1.1332.1.1.5.3.112.6.1
		msanOltPortSumStatEntry OBJECT-TYPE
			SYNTAX MsanOltPortSumStatEntry
			MAX-ACCESS not-accessible
			STATUS current
			DESCRIPTION
				"Description."
			INDEX { msanOltPortSumStatIfIndex }
			::= { msanOltPortSumStatTable 1 }

		
		MsanOltPortSumStatEntry ::=
			SEQUENCE { 
				msanOltPortSumStatIfIndex
					Integer32,
				msanOltPortSumStatInOmciPkts
					Counter64,
				msanOltPortSumStatInCpuPkts
					Counter64,
				msanOltPortSumStatInPktsDiscarded
					Counter64,
				msanOltPortSumStatInPktsUndersize
					Counter64,
				msanOltPortSumStatInPktsOversize
					Counter64,
				msanOltPortSumStatInPktsCrcError
					Counter64,
				msanOltPortSumStatInPktsKeyError
					Counter64,
				msanOltPortSumStatOutPktsTpidError
					Counter64,
				msanOltPortSumStatOutPktsVidError
					Counter64,
				msanOltPortSumStatInPktsFragmentError
					Counter64,
				msanOltPortSumStatInGemFrames
					Counter64,
				msanOltPortSumStatInGemFramesDiscarded
					Counter64,
				msanOltPortSumStatInGemFramesIdle
					Counter64,
				msanOltPortSumStatInGemFramesCorrected
					Counter64,
				msanOltPortSumStatInGemFramesIllegal
					Counter64,
				msanOltPortSumStatInAllocationsValid
					Counter64,
				msanOltPortSumStatInAllocationsInvalid
					Counter64,
				msanOltPortSumStatInAllocationsDisabled
					Counter64,
				msanOltPortSumStatInPloamMsgs
					Counter64,
				msanOltPortSumStatInPloamMsgsNonIdle
					Counter64,
				msanOltPortSumStatInPloamMsgsError
					Counter64,
				msanOltPortSumStatInPloamMsgsDiscarded
					Counter64,
				msanOltPortSumStatInFecCodewords
					Counter64,
				msanOltPortSumStatInFecCodewordsUncorrected
					Counter64,
				msanOltPortSumStatInBip8Bytes
					Counter64,
				msanOltPortSumStatInBip8Errors
					Counter64,
				msanOltPortSumStatOutOmciPkts
					Counter64,
				msanOltPortSumStatOutCpuPkts
					Counter64,
				msanOltPortSumStatOutPktsDiscarded
					Counter64,
				msanOltPortSumStatOutGemFrames
					Counter64,
				msanOltPortSumStatOutPloamMsgs
					Counter64
			 }

		-- 1.3.6.1.4.1.1332.1.1.5.3.112.6.1.1
		msanOltPortSumStatIfIndex OBJECT-TYPE
			SYNTAX Integer32
			MAX-ACCESS not-accessible
			STATUS current
			DESCRIPTION
				"Index of OLT interface (from ifTable)."
			::= { msanOltPortSumStatEntry 1 }

		
		-- 1.3.6.1.4.1.1332.1.1.5.3.112.6.1.3
		msanOltPortSumStatInOmciPkts OBJECT-TYPE
			SYNTAX Counter64
			UNITS "Packets"
			MAX-ACCESS read-only
			STATUS current
			DESCRIPTION
				"Received OMCI packets."
			::= { msanOltPortSumStatEntry 3 }

		
		-- 1.3.6.1.4.1.1332.1.1.5.3.112.6.1.4
		msanOltPortSumStatInCpuPkts OBJECT-TYPE
			SYNTAX Counter64
			UNITS "Packets"
			MAX-ACCESS read-only
			STATUS current
			DESCRIPTION
				"Received CPU packets."
			::= { msanOltPortSumStatEntry 4 }

		
		-- 1.3.6.1.4.1.1332.1.1.5.3.112.6.1.5
		msanOltPortSumStatInPktsDiscarded OBJECT-TYPE
			SYNTAX Counter64
			UNITS "Packets"
			MAX-ACCESS read-only
			STATUS current
			DESCRIPTION
				"Number of dropped received packets."
			::= { msanOltPortSumStatEntry 5 }

		
		-- 1.3.6.1.4.1.1332.1.1.5.3.112.6.1.6
		msanOltPortSumStatInPktsUndersize OBJECT-TYPE
			SYNTAX Counter64
			UNITS "Packets"
			MAX-ACCESS read-only
			STATUS current
			DESCRIPTION
				"Received packets dropped due to length too short."
			::= { msanOltPortSumStatEntry 6 }

		
		-- 1.3.6.1.4.1.1332.1.1.5.3.112.6.1.7
		msanOltPortSumStatInPktsOversize OBJECT-TYPE
			SYNTAX Counter64
			UNITS "Packets"
			MAX-ACCESS read-only
			STATUS current
			DESCRIPTION
				"Received packets dropped due to length too long."
			::= { msanOltPortSumStatEntry 7 }

		
		-- 1.3.6.1.4.1.1332.1.1.5.3.112.6.1.8
		msanOltPortSumStatInPktsCrcError OBJECT-TYPE
			SYNTAX Counter64
			UNITS "Packets"
			MAX-ACCESS read-only
			STATUS current
			DESCRIPTION
				"Received packets dropped due to CRC error."
			::= { msanOltPortSumStatEntry 8 }

		
		-- 1.3.6.1.4.1.1332.1.1.5.3.112.6.1.9
		msanOltPortSumStatInPktsKeyError OBJECT-TYPE
			SYNTAX Counter64
			UNITS "Packets"
			MAX-ACCESS read-only
			STATUS current
			DESCRIPTION
				"Received packets dropped due to Key error."
			::= { msanOltPortSumStatEntry 9 }

		
		-- 1.3.6.1.4.1.1332.1.1.5.3.112.6.1.10
		msanOltPortSumStatOutPktsTpidError OBJECT-TYPE
			SYNTAX Counter64
			UNITS "Packets"
			MAX-ACCESS read-only
			STATUS current
			DESCRIPTION
				"Received packet dropped due to TPID error."
			::= { msanOltPortSumStatEntry 10 }

		
		-- 1.3.6.1.4.1.1332.1.1.5.3.112.6.1.11
		msanOltPortSumStatOutPktsVidError OBJECT-TYPE
			SYNTAX Counter64
			UNITS "Packets"
			MAX-ACCESS read-only
			STATUS current
			DESCRIPTION
				"Received packet dropped due to VID error."
			::= { msanOltPortSumStatEntry 11 }

		
		-- 1.3.6.1.4.1.1332.1.1.5.3.112.6.1.12
		msanOltPortSumStatInPktsFragmentError OBJECT-TYPE
			SYNTAX Counter64
			UNITS "Packets"
			MAX-ACCESS read-only
			STATUS current
			DESCRIPTION
				"Received packet dropped due to fragmentation error."
			::= { msanOltPortSumStatEntry 12 }

		
		-- 1.3.6.1.4.1.1332.1.1.5.3.112.6.1.13
		msanOltPortSumStatInGemFrames OBJECT-TYPE
			SYNTAX Counter64
			UNITS "Frames"
			MAX-ACCESS read-only
			STATUS current
			DESCRIPTION
				"Received GEM frames."
			::= { msanOltPortSumStatEntry 13 }

		
		-- 1.3.6.1.4.1.1332.1.1.5.3.112.6.1.14
		msanOltPortSumStatInGemFramesDiscarded OBJECT-TYPE
			SYNTAX Counter64
			UNITS "Frames"
			MAX-ACCESS read-only
			STATUS current
			DESCRIPTION
				"Number of corrected received GEM frames."
			::= { msanOltPortSumStatEntry 14 }

		
		-- 1.3.6.1.4.1.1332.1.1.5.3.112.6.1.15
		msanOltPortSumStatInGemFramesIdle OBJECT-TYPE
			SYNTAX Counter64
			UNITS "Frames"
			MAX-ACCESS read-only
			STATUS current
			DESCRIPTION
				"Number of idle received GEM frames."
			::= { msanOltPortSumStatEntry 15 }

		
		-- 1.3.6.1.4.1.1332.1.1.5.3.112.6.1.16
		msanOltPortSumStatInGemFramesCorrected OBJECT-TYPE
			SYNTAX Counter64
			UNITS "Frames"
			MAX-ACCESS read-only
			STATUS current
			DESCRIPTION
				"Number of corrected received GEM frames."
			::= { msanOltPortSumStatEntry 16 }

		
		-- 1.3.6.1.4.1.1332.1.1.5.3.112.6.1.17
		msanOltPortSumStatInGemFramesIllegal OBJECT-TYPE
			SYNTAX Counter64
			UNITS "Frames"
			MAX-ACCESS read-only
			STATUS current
			DESCRIPTION
				"Number of illegal received GEM frames."
			::= { msanOltPortSumStatEntry 17 }

		
		-- 1.3.6.1.4.1.1332.1.1.5.3.112.6.1.18
		msanOltPortSumStatInAllocationsValid OBJECT-TYPE
			SYNTAX Counter64
			UNITS "Allocations"
			MAX-ACCESS read-only
			STATUS current
			DESCRIPTION
				"Number of received valid allocations."
			::= { msanOltPortSumStatEntry 18 }

		
		-- 1.3.6.1.4.1.1332.1.1.5.3.112.6.1.19
		msanOltPortSumStatInAllocationsInvalid OBJECT-TYPE
			SYNTAX Counter64
			UNITS "Allocations"
			MAX-ACCESS read-only
			STATUS current
			DESCRIPTION
				"Number of received invalid allocations."
			::= { msanOltPortSumStatEntry 19 }

		
		-- 1.3.6.1.4.1.1332.1.1.5.3.112.6.1.20
		msanOltPortSumStatInAllocationsDisabled OBJECT-TYPE
			SYNTAX Counter64
			UNITS "Allocations"
			MAX-ACCESS read-only
			STATUS current
			DESCRIPTION
				"Number of received disabled allocations."
			::= { msanOltPortSumStatEntry 20 }

		
		-- 1.3.6.1.4.1.1332.1.1.5.3.112.6.1.21
		msanOltPortSumStatInPloamMsgs OBJECT-TYPE
			SYNTAX Counter64
			UNITS "PLOAM messages"
			MAX-ACCESS read-only
			STATUS current
			DESCRIPTION
				"Number of received PLOAM (physical layer operations and maintenance) messages."
			::= { msanOltPortSumStatEntry 21 }

		
		-- 1.3.6.1.4.1.1332.1.1.5.3.112.6.1.22
		msanOltPortSumStatInPloamMsgsNonIdle OBJECT-TYPE
			SYNTAX Counter64
			UNITS "Messages"
			MAX-ACCESS read-only
			STATUS current
			DESCRIPTION
				"Number of received non-idle PLOAM (physical layer operations and maintenance) messages."
			::= { msanOltPortSumStatEntry 22 }

		
		-- 1.3.6.1.4.1.1332.1.1.5.3.112.6.1.23
		msanOltPortSumStatInPloamMsgsError OBJECT-TYPE
			SYNTAX Counter64
			UNITS "Messages"
			MAX-ACCESS read-only
			STATUS current
			DESCRIPTION
				"Number of received PLOAM (physical layer operations and maintenance) messages with errors."
			::= { msanOltPortSumStatEntry 23 }

		
		-- 1.3.6.1.4.1.1332.1.1.5.3.112.6.1.24
		msanOltPortSumStatInPloamMsgsDiscarded OBJECT-TYPE
			SYNTAX Counter64
			UNITS "Messages"
			MAX-ACCESS read-only
			STATUS current
			DESCRIPTION
				"Number of discarded PLOAM (physical layer operations and maintenance) messages."
			::= { msanOltPortSumStatEntry 24 }

		
		-- 1.3.6.1.4.1.1332.1.1.5.3.112.6.1.25
		msanOltPortSumStatInFecCodewords OBJECT-TYPE
			SYNTAX Counter64
			UNITS "Codewords"
			MAX-ACCESS read-only
			STATUS current
			DESCRIPTION
				"Number of received FEC (Forward error correction) codewords."
			::= { msanOltPortSumStatEntry 25 }

		
		-- 1.3.6.1.4.1.1332.1.1.5.3.112.6.1.26
		msanOltPortSumStatInFecCodewordsUncorrected OBJECT-TYPE
			SYNTAX Counter64
			UNITS "Codewords"
			MAX-ACCESS read-only
			STATUS current
			DESCRIPTION
				"Number of received uncorrected FEC (Forward error correction) codewords."
			::= { msanOltPortSumStatEntry 26 }

		
		-- 1.3.6.1.4.1.1332.1.1.5.3.112.6.1.27
		msanOltPortSumStatInBip8Bytes OBJECT-TYPE
			SYNTAX Counter64
			UNITS "Bytes"
			MAX-ACCESS read-only
			STATUS current
			DESCRIPTION
				"Number of received bytes protected by Bip8."
			::= { msanOltPortSumStatEntry 27 }

		
		-- 1.3.6.1.4.1.1332.1.1.5.3.112.6.1.28
		msanOltPortSumStatInBip8Errors OBJECT-TYPE
			SYNTAX Counter64
			UNITS "Bytes"
			MAX-ACCESS read-only
			STATUS current
			DESCRIPTION
				"Number of received Bip8 errors."
			::= { msanOltPortSumStatEntry 28 }

		
		-- 1.3.6.1.4.1.1332.1.1.5.3.112.6.1.29
		msanOltPortSumStatOutOmciPkts OBJECT-TYPE
			SYNTAX Counter64
			UNITS "Packets"
			MAX-ACCESS read-only
			STATUS current
			DESCRIPTION
				"Transmitted OMCI packets."
			::= { msanOltPortSumStatEntry 29 }

		
		-- 1.3.6.1.4.1.1332.1.1.5.3.112.6.1.30
		msanOltPortSumStatOutCpuPkts OBJECT-TYPE
			SYNTAX Counter64
			UNITS "Packets"
			MAX-ACCESS read-only
			STATUS current
			DESCRIPTION
				"Transmitted CPU packets."
			::= { msanOltPortSumStatEntry 30 }

		
		-- 1.3.6.1.4.1.1332.1.1.5.3.112.6.1.31
		msanOltPortSumStatOutPktsDiscarded OBJECT-TYPE
			SYNTAX Counter64
			UNITS "Packets"
			MAX-ACCESS read-only
			STATUS current
			DESCRIPTION
				"Number of dropped transmitted packets because of illegal length."
			::= { msanOltPortSumStatEntry 31 }

		
		-- 1.3.6.1.4.1.1332.1.1.5.3.112.6.1.32
		msanOltPortSumStatOutGemFrames OBJECT-TYPE
			SYNTAX Counter64
			UNITS "Frames"
			MAX-ACCESS read-only
			STATUS current
			DESCRIPTION
				"Transmitted GEM frames."
			::= { msanOltPortSumStatEntry 32 }

		
		-- 1.3.6.1.4.1.1332.1.1.5.3.112.6.1.33
		msanOltPortSumStatOutPloamMsgs OBJECT-TYPE
			SYNTAX Counter64
			UNITS "PLOAM messages"
			MAX-ACCESS read-only
			STATUS current
			DESCRIPTION
				"Number of transmitted PLOAM (physical layer operations and maintenance) messages."
			::= { msanOltPortSumStatEntry 33 }

		
		-- 1.3.6.1.4.1.1332.1.1.5.3.113
		msanTacacsServer OBJECT IDENTIFIER ::= { msanAdditionalConf 113 }

		
		-- 1.3.6.1.4.1.1332.1.1.5.3.113.1
		msanTacacsServerGlobal OBJECT IDENTIFIER ::= { msanTacacsServer 1 }

		
		-- 1.3.6.1.4.1.1332.1.1.5.3.113.1.1
		msanTacacsServerTimeout OBJECT-TYPE
			SYNTAX Integer32 (1..30)
			UNITS "seconds"
			MAX-ACCESS read-write
			STATUS current
			DESCRIPTION
				"TACACS server response timeout value."
			DEFVAL { '10'b }
			::= { msanTacacsServerGlobal 1 }

		
		-- 1.3.6.1.4.1.1332.1.1.5.3.113.2
		msanTacacsServerTable OBJECT-TYPE
			SYNTAX SEQUENCE OF MsanTacacsServerEntry
			MAX-ACCESS not-accessible
			STATUS current
			DESCRIPTION
				"Table with information about Radius Authentication Server IP
				Addresses, port numbers and shared secret"
			::= { msanTacacsServer 2 }

		
		-- 1.3.6.1.4.1.1332.1.1.5.3.113.2.1
		msanTacacsServerEntry OBJECT-TYPE
			SYNTAX MsanTacacsServerEntry
			MAX-ACCESS not-accessible
			STATUS current
			DESCRIPTION
				"Entry consisting of configuration data for a Radius 
				Authentication Server."
			INDEX { msanTacacsServerIpAddress }
			::= { msanTacacsServerTable 1 }

		
		MsanTacacsServerEntry ::=
			SEQUENCE { 
				msanTacacsServerIpAddress
					IpAddress,
				msanTacacsServerPort
					Unsigned32,
				msanTacacsServerSecret
					DisplayString,
				msanTacacsServerPrimaryMode
					INTEGER,
				msanTacacsServerCurrentMode
					INTEGER,
				msanTacacsServerStatus
					RowStatus
			 }

		-- 1.3.6.1.4.1.1332.1.1.5.3.113.2.1.1
		msanTacacsServerIpAddress OBJECT-TYPE
			SYNTAX IpAddress
			MAX-ACCESS not-accessible
			STATUS current
			DESCRIPTION
				"IP Address of the configured TACACS server.
				This object cannot be changed after creation."
			::= { msanTacacsServerEntry 1 }

		
		-- 1.3.6.1.4.1.1332.1.1.5.3.113.2.1.2
		msanTacacsServerPort OBJECT-TYPE
			SYNTAX Unsigned32 (0..65535)
			MAX-ACCESS read-write
			STATUS current
			DESCRIPTION
				"TCP/UDP port number of the TACACS server."
			DEFVAL { 49 }
			::= { msanTacacsServerEntry 2 }

		
		-- 1.3.6.1.4.1.1332.1.1.5.3.113.2.1.3
		msanTacacsServerSecret OBJECT-TYPE
			SYNTAX DisplayString (SIZE (0..48))
			MAX-ACCESS read-write
			STATUS current
			DESCRIPTION
				"Configured shared secret for the TACACS server."
			DEFVAL { ''b }
			::= { msanTacacsServerEntry 3 }

		
		-- 1.3.6.1.4.1.1332.1.1.5.3.113.2.1.4
		msanTacacsServerPrimaryMode OBJECT-TYPE
			SYNTAX INTEGER
				{
				enable(1),
				disable(2)
				}
			MAX-ACCESS read-write
			STATUS current
			DESCRIPTION
				"Configure the TACACS server to be the primary server. If there is any 
				other server that is configured to be primary, that server is set to be 
				a seconday server and this entry is set Primary."
			::= { msanTacacsServerEntry 4 }

		
		-- 1.3.6.1.4.1.1332.1.1.5.3.113.2.1.5
		msanTacacsServerCurrentMode OBJECT-TYPE
			SYNTAX INTEGER
				{
				yes(1),
				no(2)
				}
			MAX-ACCESS read-only
			STATUS current
			DESCRIPTION
				"Indicates if the TACACS server is the current server in user for
				authentication."
			::= { msanTacacsServerEntry 5 }

		
		-- 1.3.6.1.4.1.1332.1.1.5.3.113.2.1.6
		msanTacacsServerStatus OBJECT-TYPE
			SYNTAX RowStatus
			MAX-ACCESS read-create
			STATUS current
			DESCRIPTION
				"Creates or destroys a TACACS server entry.
				
				active(1)       - This entry is active.
				createAndGo(4)  - Creates a new entry.
				destroy(6)      - Deletes an entry."
			::= { msanTacacsServerEntry 6 }

		
	
	END

--
-- ISKRATEL-MSAN-MIB.mib
--
