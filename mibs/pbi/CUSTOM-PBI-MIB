CUSTOM-PBI-MIB DEFINITIONS ::= BEGIN

IMPORTS
    MODULE-IDENTITY, OBJECT-TYPE,
    Unsigned32, Counter64
        FROM SNMPv2-SMI
    DisplayString, TruthValue
        FROM SNMPv2-TC
    enterprises
        FROM SNMPv2-SMI;

pbi MODULE-IDENTITY
    LAST-UPDATED "201809150000Z"
    ORGANIZATION "LibreNMS"
    CONTACT-INFO "Neil Lathwood:   gh+n@laf.io"

    DESCRIPTION  "The MIB for PBI based devices."
    ::= { enterprises 1070 }

global OBJECT IDENTIFIER ::= { pbi 3 }

global2 OBJECT IDENTIFIER ::= { global 1 }

global3 OBJECT IDENTIFIER ::= { global2 1 }

global4 OBJECT IDENTIFIER ::= { global3 104 }

global5 OBJECT IDENTIFIER ::= { global4 1 }

global6 OBJECT IDENTIFIER ::= { global5 1 }

cnPower OBJECT-TYPE
     SYNTAX      TenthdBmV
     UNITS       "dBmV"
     MAX-ACCESS  read-only
     STATUS      current
     DESCRIPTION
         "Power Levels"
     ::= { global6 8 }

END
