--MWRM-NETWORK-MIB VERSION 1.8.5.20
--MWRM (MicroWave-Radio-MIB)
MWRM-NETWORK-MIB DEFINITIONS ::= BEGIN

IMPORTS
--    Ipv6Address          FROM IPV6-TC
--	Counter, enterprises, Gauge, IpAddress 	FROM RFC1155-SMI
	Counter32, enterprises, Gauge32, IpAddress 	FROM SNMPv2-SMI
	DisplayString, ifIndex  		FROM RFC1213-MIB
	RowStatus						FROM SNMPv2-TC
	MacAddress						FROM SNMPv2-TC
	OBJECT-TYPE          			FROM SNMPv2-SMI
	TRAP-TYPE            			FROM RFC-1215

	EnableDisable			FROM MWRM-UNIT-MIB
	EnableDisableSMI2  		FROM MWRM-UNIT-MIB
	OffOn					FROM MWRM-UNIT-MIB
	MetricImperial			FROM MWRM-UNIT-MIB
	AllowedNotAllowed 		FROM MWRM-UNIT-MIB
	ProgressStatus 			FROM MWRM-UNIT-MIB
	Severity 				FROM MWRM-UNIT-MIB
	NoYes					FROM MWRM-UNIT-MIB
	DownUp					FROM MWRM-UNIT-MIB
	TrailIfType 			FROM MWRM-UNIT-MIB
	PmTableType 			FROM MWRM-UNIT-MIB
	RateMbps				FROM MWRM-UNIT-MIB
	HalfFull				FROM MWRM-UNIT-MIB
	BerLevel				FROM MWRM-UNIT-MIB
	SignalLevel				FROM MWRM-UNIT-MIB
	LoopbackType			FROM MWRM-UNIT-MIB
	QueueName				FROM MWRM-UNIT-MIB
	RadioId					FROM MWRM-UNIT-MIB
	RfuId					FROM MWRM-UNIT-MIB
	SwCommand 				FROM MWRM-UNIT-MIB
	TrailProtectedType		FROM MWRM-UNIT-MIB
	ClockSrc 				FROM MWRM-UNIT-MIB
	SlotId 					FROM MWRM-UNIT-MIB
	Integrity				FROM MWRM-UNIT-MIB
	GreenYellow 			FROM MWRM-UNIT-MIB
	InputSeverity 			FROM MWRM-UNIT-MIB
	SwCommandTimer 			FROM MWRM-UNIT-MIB;

microwave-radio OBJECT IDENTIFIER ::= { enterprises 2281 }
genEquip OBJECT IDENTIFIER ::= { microwave-radio 10}
genEquipUnit OBJECT IDENTIFIER ::= { genEquip 1}

-- Local enumeration types
MediaType ::= INTEGER {
				auto-type(0),
				rj45(1),
				sfp(2),
				radio(3),
				pwe3(4)
				}

AutoNegMode ::= INTEGER {
				off(0),
				on(1),
				restart(2)
				}

SpeedDefs ::= INTEGER {
				speed-10(0),
				speed-100(1),
				speed-1000(2),
				speed-2500(3),
				speed-10000(4)
				}

MasterSalveSetMode ::= INTEGER {
				auto(0),
				slave(1),
				master(2)
				}

FlowControl ::= INTEGER {
				disable(0),
				rx(1),
				tx-rx(2)
				}

PortType ::= INTEGER {
				management(0),
				line(1),
				radio(2),
				pwe(3),
				cpu(4)
				}

EdgePortType ::= INTEGER {
				none(0),
				edge(1)
				}

TrustMode ::= INTEGER {
				untrust(0),
				trust(1)
				}

ServiceType ::= INTEGER {
				mng(0),
				mp(1),
				p2p(2)
				}

ServiceSubType ::= INTEGER {
				ethernet(0),
				tdm(1),
				pwe(2)
				}

ServiceAdmin ::= INTEGER {
				reserved(0),
				operational(1)
				}

ServiceCosMode ::= INTEGER {
				default-cos(0),
				preserve-sp-cos(1)
				}

SPType ::= INTEGER {
				sap(0),
				snp(1),
				mng(2),
				pipe(3)
				}

SPSubType ::= INTEGER {
				dot1q(0),
				s-tag(1),
				bundle-c(2),
				bundle-s(3),
				all-to-one(4),
				qinq(5)
				}

DisableAllowed ::= INTEGER {
				disable(0),
				allow(1)
				}

SPCosMode ::= INTEGER {
				sp-def-cos(0),
				interface-decision(1),
				pc1(2),
				tcam(3)
				}

SplitHorizonGroup ::= INTEGER {
				group-a(0),
				group-b(1),
				group-c(2),
				group-d(3)
				}

TrueFalse ::= INTEGER {
				false(0),
				true(1)
				}

PolicerType ::= INTEGER {
				mef-trtcm(0)
				}

PolicerColorMode ::= INTEGER {
				color-blind(0),
				color-aware(1)
				}

PWfpClockSignal ::= INTEGER  {
						sync(0),
						unframed(1),
						e1-mf(2),
						e1-mf-crc(3),
						ds1-d4(4),
						ds1-esf(5)
					}

PWCclockSysRef ::= INTEGER {
						none(0),
						front-panel(1),
						clock-recovery(2)
					}

PWCDiffClockSrc ::= INTEGER {
						none(0),
						front-panel(1),
						sys-ref(2),
						clock-1588(3)
					}

PWRtpTimeStampMode ::= INTEGER  {
						absolute(0),
						differential(1)
					}

PWTunnelPsnType ::= INTEGER {
						upd-ip(0),
						eth(1),
						mpls(2)
					}

PWTunnelVlanType ::= INTEGER  {
						none(0),
						c-type(1),
						s-type(2)
					}

PWPDHClockSource ::= INTEGER {
						sys-ref(0),
						rx-sdh(1),
						internal(2)
					}

TunnelGroupProtectionCmd ::= INTEGER {
						no-request(0),
						force-switch(1),
						manual-switch(2),
						lockout(3),
						clear(4)
					}

PWSOAMccmInterval ::= INTEGER {
						n3-3-ms(0),
						n10-ms(1),
						n100-ms(2),
						n1-s(3),
						n10-s(4),
						n1-m(5),
						n10-m(6)
					}

Dot1CfmInterfaceStatus ::= INTEGER {
						no-interface(0),
						up(1),
						down(2),
						testing(3),
						unknown(4),
						dormant(5),
						not-present(6),
						lower-layer-down(7)
					}

BurstType ::= INTEGER {
						short(0),
						long(1)
			}

IfMgrTrueFalse ::= INTEGER {
				true(1),
				false(2)
				}

MibTrueFalse ::= INTEGER {
				true(1),
				false(2)
				}

G8032LastState ::= INTEGER {
					nr(0),
					raps-nr(1),
					raps-rb-nr(2),
					running-wtb(3),
					expired-wtb(4),
					running-wtr(5),
					expired-wtr(6),
					ms(7),
					raps-ms(8),
					raps-sd(9),
					clear-sd(10),
					local-sd(11),
					raps-sf(12),
					clear-sf(13),
					local-sf(14),
					raps-fs(15),
					fs(16),
					clear(17)
				}

TDMLoopbackType ::=	INTEGER {
						none(0),
						towards-line(1),
						towards-system(2)
					}

RSTLoopbackType ::=	INTEGER {
						none(0),
						towards-system(1),
						towards-line(2)
					}

LBState ::=INTEGER {
					soamLbInactive(0),
					soamLbActive(1),
					soamLbStopped(2),
					soamLbCompleted(3),
					soamLbFailed(4)
				}

-- Network
genEquipNetwork		OBJECT IDENTIFIER ::= {genEquip 2}

genEquipNetworkRemoteIp		OBJECT-TYPE
		SYNTAX 		IpAddress
		ACCESS		read-only
        STATUS		obsolete
        DESCRIPTION
"This value indicates the Remote IP address."
::= { genEquipNetwork 1 }

genEquipNetworkMateIp 		OBJECT-TYPE
        SYNTAX		IpAddress
        ACCESS  	read-only
        STATUS 		mandatory
        DESCRIPTION
"This value indicates the Mate IP address. (same as genEquipProtectionMateIPAddr)"
::= { genEquipNetwork 2 }

genEquipNetworkAgentIp		OBJECT-TYPE
        SYNTAX		IpAddress
        ACCESS  	read-only
        STATUS 		obsolete
        DESCRIPTION
"This value indicates the Agent IP address. (same as genEquipNetworkManagmentLocalIp)"
::= { genEquipNetwork 3 }


--- Network Managment information
genEquipNetworkManagment OBJECT IDENTIFIER ::= { genEquipNetwork 4}

genEquipNetworkManagmentLocalIp		OBJECT-TYPE
		SYNTAX 		IpAddress
		ACCESS		read-write
        STATUS		mandatory
        DESCRIPTION
		"This value indicates the local IP address. (same as genEquipNetworkAgentIp)"
::= { genEquipNetworkManagment 1 }

genEquipNetworkManagmentLocalSubnetMask		OBJECT-TYPE
		SYNTAX 		IpAddress
		ACCESS		read-write
        STATUS		mandatory
        DESCRIPTION
		"This value indicates the local subnet mask. (for example 255.255.255.0)"
::= { genEquipNetworkManagment 2 }

genEquipNetworkManagmentLocalDefaultGateway		OBJECT-TYPE
		SYNTAX 		IpAddress
		ACCESS		read-write
        STATUS		mandatory
        DESCRIPTION
		"This value indicates the local default gateway."
::= { genEquipNetworkManagment 3 }

genEquipNetworkManagmentLocalHWAddr		OBJECT-TYPE
		SYNTAX 		MacAddress
		ACCESS		read-only
        STATUS		mandatory
        DESCRIPTION
		"This value indicates the MAC Address used for management (related to the management IP address of the system)."
::= { genEquipNetworkManagment 4 }

genEquipNetworkManagmentRemoteSubnetMask		OBJECT-TYPE
		SYNTAX 		IpAddress
		ACCESS		read-write
        STATUS		obsolete
        DESCRIPTION
		"This value indicates the Remote subnet mask.(for example 255.255.255.0)"
::= { genEquipNetworkManagment 5 }

genEquipNetworkManagmentNumOfPorts		OBJECT-TYPE
		SYNTAX 		INTEGER (0..3)
		ACCESS		read-write
        STATUS		mandatory
        DESCRIPTION
		"This value indicates the number of management ports."
::= { genEquipNetworkManagment 6 }

genEquipNetworkManagmentInBandVLAN		OBJECT-TYPE
		SYNTAX 		INTEGER (1..4090)
		ACCESS		read-write
        STATUS		mandatory
        DESCRIPTION
		"This value indicates the number of in-band VLANs."
::= { genEquipNetworkManagment 7 }

genEquipNetworkManagmentPortType		OBJECT-TYPE
		SYNTAX 		INTEGER { outOfBand(0), inBand(1) }
		ACCESS		read-write
        STATUS		mandatory
        DESCRIPTION
		"This is a configurable option to use in-band or out-of-band management."
::= { genEquipNetworkManagment 8 }

genEquipNetworkManagmentPortCapacity		OBJECT-TYPE
		SYNTAX 		INTEGER {
					n64(0),
					n128(1),
					n256(2),
					n512(3),
					n1024(4),
					n2048(5)
		}
		ACCESS		read-write
        STATUS		mandatory
        DESCRIPTION
		"This value indicates a limit rate for the management port capacity in kbps."
::= { genEquipNetworkManagment 9 }

genEquipNetworkManagmentPortAutoNegotiation		OBJECT-TYPE
		SYNTAX 		OffOn
		ACCESS		read-write
        STATUS		mandatory
        DESCRIPTION
		"Enable or disable the Auto Negotiation option, on all management ports."
::= { genEquipNetworkManagment 10 }

genEquipNetworkManagmentPortRate		OBJECT-TYPE
		SYNTAX 		INTEGER {
				not-applicable(-1),
				n10(0),
				n100(1),
				n1000(2)
		}
		ACCESS		read-write
        STATUS		mandatory
        DESCRIPTION
		"This value indicates the port rate in Mbps (all management ports).
		Possible values are:
		- n10(0) 10Mbps
		- n100(1) 100Mbps
		- n1000(2) 1000Mbps"
::= { genEquipNetworkManagment 11 }

genEquipNetworkManagmentPortDuplex		OBJECT-TYPE
		SYNTAX 		INTEGER { half(0), full(1) }
		ACCESS		read-write
        STATUS		mandatory
        DESCRIPTION
		"This value indicates the port duplex value, for all management ports."
::= { genEquipNetworkManagment 12 }

genEquipNetworkManagmentBlockMngTowardsLine		OBJECT-TYPE
		SYNTAX 		EnableDisable
		ACCESS		read-write
        STATUS		mandatory
        DESCRIPTION
		"Blocking the in-band management frames to egress via the Ethernet line interface in pipe application."
::= { genEquipNetworkManagment 13 }

genEquipNetworkManagmentIpAddrCfgTable  OBJECT-TYPE
        SYNTAX  SEQUENCE OF GenEquipNetworkManagmentIpAddrCfgEntry
        ACCESS  not-accessible
        STATUS mandatory
        DESCRIPTION
        "This table keeps the information about the neighbour attributes, such as IP address, MAC address, slot,
         port number and description. It can be used by the NMS for topology discovery."
        ::= { genEquipNetworkManagment 20 }

genEquipNetworkManagmentIpAddrCfgEntry OBJECT-TYPE
        SYNTAX GenEquipNetworkManagmentIpAddrCfgEntry
        ACCESS not-accessible
        STATUS mandatory
          DESCRIPTION
          "This table keeps the information about the neighbour attributes, such as IP address, MAC address, slot,
         port number and description. It can be used by the NMS for topology discovery."
        INDEX { genEquipNetworkManagmentIpAddrCfgMngId }
        ::= { genEquipNetworkManagmentIpAddrCfgTable 1 }

GenEquipNetworkManagmentIpAddrCfgEntry ::=
		SEQUENCE {
			genEquipNetworkManagmentIpAddrCfgMngId
				INTEGER,
			genEquipNetworkManagmentIpAddrCfgIpv4Address
            	IpAddress,
			genEquipNetworkManagmentIpAddrCfgIpv4SubnetMask
				IpAddress,
			genEquipNetworkManagmentIpAddrCfgDefaultGateway
				IpAddress,
			genEquipNetworkManagmentIpAddrCfgIpv6Address
				OCTET STRING,
			genEquipNetworkManagmentIpAddrCfgIpv6PrefixLength
				INTEGER,
			genEquipNetworkManagmentIpAddrCfgDefaultGatewayIPv6
				OCTET STRING
}

genEquipNetworkManagmentIpAddrCfgMngId OBJECT-TYPE
        SYNTAX INTEGER
        ACCESS read-write
        STATUS mandatory
        DESCRIPTION
        "Management Ifindex."
        ::= { genEquipNetworkManagmentIpAddrCfgEntry 1 }

genEquipNetworkManagmentIpAddrCfgIpv4Address OBJECT-TYPE
		SYNTAX IpAddress
        ACCESS read-write
        STATUS mandatory
        DESCRIPTION
        "This value indicates the local IP address"
        ::= { genEquipNetworkManagmentIpAddrCfgEntry 2 }

genEquipNetworkManagmentIpAddrCfgIpv4SubnetMask OBJECT-TYPE
        SYNTAX IpAddress
        ACCESS read-write
        STATUS mandatory
        DESCRIPTION
         "This value indicates the local subnet mask. (for example 255.255.255.0)"
        ::= { genEquipNetworkManagmentIpAddrCfgEntry 3 }

genEquipNetworkManagmentIpAddrCfgDefaultGateway OBJECT-TYPE
        SYNTAX IpAddress
        ACCESS read-write
        STATUS mandatory
        DESCRIPTION
        "This value indicates the local default gateway."
        ::= { genEquipNetworkManagmentIpAddrCfgEntry 4 }

genEquipNetworkManagmentIpAddrCfgIpv6Address OBJECT-TYPE
        SYNTAX OCTET STRING (SIZE(0..16))
        ACCESS read-write
        STATUS mandatory
        DESCRIPTION
        "This value indicates the Local IPv6.
		y is a 16-bit hexadecimal field of the form xxxx, where x takes values from 0 to F."
        ::= { genEquipNetworkManagmentIpAddrCfgEntry 5 }

genEquipNetworkManagmentIpAddrCfgIpv6PrefixLength OBJECT-TYPE
        SYNTAX INTEGER
        ACCESS read-write
        STATUS mandatory
        DESCRIPTION
        "IPv6 Prefix-Length specifies the IPv6 subnet."
        ::= { genEquipNetworkManagmentIpAddrCfgEntry 6 }

genEquipNetworkManagmentIpAddrCfgDefaultGatewayIPv6 OBJECT-TYPE
        SYNTAX OCTET STRING (SIZE(0..16))
        ACCESS read-write
        STATUS mandatory
        DESCRIPTION
        "This value indicates the local IPv6 default gateway."
        ::= { genEquipNetworkManagmentIpAddrCfgEntry 7 }


--- IP Table information
genEquipNetworkIP OBJECT IDENTIFIER ::= { genEquipNetwork 5}

genEquipNetworkIPTable  OBJECT-TYPE
        SYNTAX  SEQUENCE OF GenEquipNetworkIPEntry
        ACCESS  not-accessible
        STATUS mandatory
        DESCRIPTION
        "This table keeps the information about the neighbour attributes, such as IP address, MAC address, slot,
         port number and description. It can be used by the NMS for topology discovery."
        ::= { genEquipNetworkIP 1 }

genEquipNetworkIPEntry OBJECT-TYPE
        SYNTAX GenEquipNetworkIPEntry
        ACCESS not-accessible
        STATUS mandatory
          DESCRIPTION
          "This table keeps the information about the neighbour attributes, such as IP address, MAC address, slot,
         port number and description. It can be used by the NMS for topology discovery."
        INDEX { ifIndex }
        ::= { genEquipNetworkIPTable 1 }

GenEquipNetworkIPEntry ::=
		SEQUENCE {
			genEquipNetworkIPEthernetPort
				INTEGER,
			genEquipNetworkIPPeerMacAddr
            	OCTET STRING,
			genEquipNetworkIPPeerIPAddr
              IpAddress,
			genEquipNetworkIPPeerSlotID
				INTEGER,
			genEquipNetworkIPPeerPortNumber
				INTEGER,
			genEquipNetworkIPPeerDescr
				DisplayString,
			genEquipNetworkIPPeerNodeToNodeConnection
				EnableDisable
}

genEquipNetworkIPEthernetPort OBJECT-TYPE
        SYNTAX INTEGER
        ACCESS read-only
        STATUS mandatory
        DESCRIPTION
        "Ethernet port (local port) is the index of the table, to be taken from ifIndex."
        ::= { genEquipNetworkIPEntry 1 }

genEquipNetworkIPPeerMacAddr OBJECT-TYPE
		SYNTAX OCTET STRING
        ACCESS read-write
        STATUS mandatory
        DESCRIPTION
        "The Peer (far-end) Mac address of the managed NE (CPU) connected on the local Ethernet port"
        ::= { genEquipNetworkIPEntry 2 }

genEquipNetworkIPPeerIPAddr OBJECT-TYPE
        SYNTAX IpAddress
        ACCESS read-write
        STATUS mandatory
        DESCRIPTION
         "The Peer (far-end) IP address of the managed NE (CPU) connected on the local Ethernet port"
        ::= { genEquipNetworkIPEntry 3 }

genEquipNetworkIPPeerSlotID OBJECT-TYPE
        SYNTAX INTEGER (0..31)
        ACCESS read-write
        STATUS mandatory
        DESCRIPTION
        "The Peer (far-end) slot-id of the managed NE connected on the local Ethernet port."
        ::= { genEquipNetworkIPEntry 4 }

genEquipNetworkIPPeerPortNumber OBJECT-TYPE
        SYNTAX INTEGER (0..255)
        ACCESS read-write
        STATUS mandatory
        DESCRIPTION
        "The Peer (far-end) port number of the managed NE connected on the local Ethernet port. The port number is sequential
        starting with 1"
        ::= { genEquipNetworkIPEntry 5 }

genEquipNetworkIPPeerDescr OBJECT-TYPE
        SYNTAX DisplayString (SIZE(0..64))
        ACCESS read-write
        STATUS mandatory
        DESCRIPTION
        "User defined description for the peer port"
        ::= { genEquipNetworkIPEntry 6 }

genEquipNetworkIPPeerNodeToNodeConnection OBJECT-TYPE
        SYNTAX EnableDisable
        ACCESS read-write
        STATUS mandatory
        DESCRIPTION
        "Node To Node Connection.
        This column is relevant only for STM-1/OC-3 connections.
        if this parameter is enabled, it means that the STM-1/OC-3 port is connected with another microwave-radio NE,
        the STM-1/OC-3 port is not an access port, it is used by the NMS to find TDM trails."
        ::= { genEquipNetworkIPEntry 7 }


genEquipNetworkIPClearAllPeerInfo OBJECT-TYPE
        SYNTAX OffOn
        ACCESS read-write
        STATUS mandatory
        DESCRIPTION
        "This parameter is a command to clear the neighbor IP table info"
        ::= { genEquipNetworkIP 2 }

genEquipNetworkFloatingIp		OBJECT-TYPE
        SYNTAX		IpAddress
        ACCESS  	read-write
        STATUS 		mandatory
        DESCRIPTION
"This value indicates the floating IP used when system is in protection mode.
This address must differ from system's own IP address (genEquipNetworkAgentIp)
as well as mate unit's (genEquipProtectionMateIPAddr)and must be in the same subnet.
A value of 0.0.0.0 will disable the feature."
::= { genEquipNetwork 6 }

genEquipNetworkAgentIpV6		OBJECT-TYPE
        SYNTAX		DisplayString
        ACCESS  	read-only
        STATUS 		mandatory
        DESCRIPTION "This value indicates the agent IP V6. This parameter will be use for Trap only."
::= { genEquipNetwork 7 }

-- Services Configuration
genEquipServices	OBJECT IDENTIFIER ::= {genEquip 8}
-- Ethernet Switch
genEquipEthernetSwitch	OBJECT IDENTIFIER ::= {genEquipServices 1}

-- Ethernet Switch configuration
genEquipEthernetSwitchCfg	OBJECT IDENTIFIER ::= {genEquipEthernetSwitch 1}

genEquipEthernetSwitchCfgAppType OBJECT-TYPE
        SYNTAX INTEGER {
			single-pipe(1),
			managed-switch(2),
			metro-switch(3)
		}
        ACCESS read-write
        STATUS mandatory
        DESCRIPTION
        "The mode of the switch application. Note, managed-switch or metro-swtich require license.
        Single-pipe: No switching is done, the NE acts as a Pipe.
        Managed-switch: The switch application is configured as IEEE 802.1Q switch.
        Metro-switch: The switch application is configured as IEEE 802.1ad switch."
        ::= { genEquipEthernetSwitchCfg 1 }

genEquipEthernetSwitchCfgVIDTable  OBJECT-TYPE
        SYNTAX  SEQUENCE OF GenEquipEthernetSwitchCfgVIDEntry
        ACCESS  not-accessible
        STATUS mandatory
        DESCRIPTION
        "The switch VLAN table."
        ::= { genEquipEthernetSwitchCfg 2 }

genEquipEthernetSwitchCfgVIDEntry OBJECT-TYPE
        SYNTAX GenEquipEthernetSwitchCfgVIDEntry
        ACCESS not-accessible
        STATUS mandatory
          DESCRIPTION
          "The switch VLAN table."
        INDEX { genEquipEthernetSwitchCfgVIDIndex }
        ::= { genEquipEthernetSwitchCfgVIDTable 1 }

GenEquipEthernetSwitchCfgVIDEntry ::=
		SEQUENCE {
			genEquipEthernetSwitchCfgVIDIndex
				INTEGER,
			genEquipEthernetSwitchCfgVIDName
				DisplayString,
			genEquipEthernetSwitchCfgVIDState
				INTEGER,
			genEquipEthernetSwitchCfgVIDMemberPorts
				DisplayString,
			genEquipEthernetSwitchCfgVIDEVCID
				DisplayString,
			genEquipEthernetSwitchCfgVIDEVCDescription
				DisplayString,
			genEquipEthernetSwitchCfgVIDRowStatus
				RowStatus
}

genEquipEthernetSwitchCfgVIDIndex OBJECT-TYPE
        SYNTAX INTEGER  (0..4095)
        ACCESS read-write
        STATUS mandatory
        DESCRIPTION
        "VLAN number, the index of the table."
        ::= { genEquipEthernetSwitchCfgVIDEntry 1 }

genEquipEthernetSwitchCfgVIDName OBJECT-TYPE
        SYNTAX DisplayString
        ACCESS read-write
        STATUS mandatory
        DESCRIPTION
        "VLAN name."
        ::= { genEquipEthernetSwitchCfgVIDEntry 2 }

genEquipEthernetSwitchCfgVIDState OBJECT-TYPE
        SYNTAX INTEGER {
					suspend(1),
					active(2)
		}
        ACCESS read-write
        STATUS mandatory
        DESCRIPTION
        "VLAN state."
        ::= { genEquipEthernetSwitchCfgVIDEntry 3 }

genEquipEthernetSwitchCfgVIDMemberPorts OBJECT-TYPE
        SYNTAX DisplayString
        ACCESS read-write
        STATUS mandatory
        DESCRIPTION
        "A string that indicates in which ports this VLAN is allowed. Port numbers are separated by spaces"
        ::= { genEquipEthernetSwitchCfgVIDEntry 4 }

genEquipEthernetSwitchCfgVIDEVCID OBJECT-TYPE
        SYNTAX DisplayString
        ACCESS read-write
        STATUS mandatory
        DESCRIPTION
        "This parameter defines a name for the Ethernet service running over this VLAN.
		This information is used by the NMS as a service identifier"
        ::= { genEquipEthernetSwitchCfgVIDEntry 5 }

genEquipEthernetSwitchCfgVIDEVCDescription OBJECT-TYPE
        SYNTAX DisplayString
        ACCESS read-write
        STATUS mandatory
        DESCRIPTION
        "This parameter allows adding a description for the Ethernet service running over this VLAN.
		This information is informational only for users purposes"
        ::= { genEquipEthernetSwitchCfgVIDEntry 6 }

genEquipEthernetSwitchCfgVIDRowStatus OBJECT-TYPE
        SYNTAX RowStatus -- active(1),notInService(2),notReady(3),createAndGo(4),createAndWait(5),destroy(6)
        ACCESS read-write
        STATUS mandatory
        DESCRIPTION
        "The raw status of the vlan table."
        ::= { genEquipEthernetSwitchCfgVIDEntry 30 }

genEquipEthernetSwitchCfgPbbteEthertype  OBJECT-TYPE
        SYNTAX  INTEGER (0..65535)
        ACCESS  read-write
        STATUS mandatory
        DESCRIPTION
        "The PBB-TE-Tag ethertype value"
        ::= { genEquipEthernetSwitchCfg 3 }

genEquipEthernetSwitchCfgProviderEthertype  OBJECT-TYPE
        SYNTAX  INTEGER {
					i0x8100(0),
					i0x88A8(1),
					i0x9100(2),
					i0x9200(3)
		}
        ACCESS  read-write
        STATUS mandatory
        DESCRIPTION
        "Ethertype of the provider VLANS (S-tag). This parameter configures the Marvell switch
		and it applys for all the ethernet ports. Possible choises are { 0x8100 , 0x9100 , 0x88A8 , 0x9200 }."
        ::= { genEquipEthernetSwitchCfg 4 }

genEquipEthernetSwitchCfgJumboModeAdmin  OBJECT-TYPE
        SYNTAX  EnableDisable
        ACCESS  read-write
        STATUS mandatory
        DESCRIPTION
        "This configuration defines the Ethernet Maximal Transmit Unit (MTU) size.
        When jumbo mode is enabled, MTU=9612 bytes. When disabled, MTU=1632 bytes.
        This configuration applies to all Ethernet traffic ports except management ports"
        ::= { genEquipEthernetSwitchCfg 5 }


-- Ethernet Switch xSTP
genEquipEthernetSwitchXSTP	OBJECT IDENTIFIER ::= {genEquipEthernetSwitch 2}

genEquipEthernetSwitchXSTPProtocol OBJECT-TYPE
        SYNTAX INTEGER {
					disable(0),
					stp(1),
					rstp(2),
					ring-rstp(3),
					mstp(4),
					ring-mstp(5)
		}
        ACCESS read-write
        STATUS mandatory
        DESCRIPTION
        "Selection of the xSTP protocol. Note that not all protocols may be available in all software releases"
        ::= { genEquipEthernetSwitchXSTP 1 }

-- Ethernet Switch RSTP family (Ring RSTP or RSTP)
genEquipEthernetSwitchXSTPParams	OBJECT IDENTIFIER ::= {genEquipEthernetSwitchXSTP 2}


genEquipEthernetSwitchXSTPBridgeID OBJECT-TYPE
        SYNTAX DisplayString
        ACCESS read-only
        STATUS mandatory
        DESCRIPTION
        "The RSTP bridge ID"
        ::= { genEquipEthernetSwitchXSTPParams 1 }

genEquipEthernetSwitchXSTPRootID OBJECT-TYPE
        SYNTAX DisplayString
        ACCESS read-only
        STATUS mandatory
        DESCRIPTION
        "The RSTP root id."
        ::= { genEquipEthernetSwitchXSTPParams 2 }

genEquipEthernetSwitchXSTPRootPath OBJECT-TYPE
        SYNTAX INTEGER
        ACCESS read-only
        STATUS mandatory
        DESCRIPTION
        "The RSTP root path cost."
        ::= { genEquipEthernetSwitchXSTPParams 3 }

genEquipEthernetSwitchXSTPBridgeRole OBJECT-TYPE
        SYNTAX INTEGER {
					root-bridge(0),
					designated-bridge(1)
		}
        ACCESS read-only
        STATUS mandatory
        DESCRIPTION
        "The bridge role."
        ::= { genEquipEthernetSwitchXSTPParams 4 }

genEquipEthernetSwitchXSTPCfgPriority OBJECT-TYPE
        SYNTAX INTEGER (0..61440)
        ACCESS read-write
        STATUS mandatory
        DESCRIPTION
        "RSTP Bridge priority."
        ::= { genEquipEthernetSwitchXSTPParams 5 }

genEquipEthernetSwitchXSTPParamsEthernetPortsTable  OBJECT-TYPE
        SYNTAX  SEQUENCE OF GenEquipEthernetSwitchXSTPParamsEthernetPortsEntry
        ACCESS  not-accessible
        STATUS mandatory
        DESCRIPTION
        "RSTP port status table."
        ::= { genEquipEthernetSwitchXSTPParams 6 }

genEquipEthernetSwitchXSTPParamsEthernetPortsEntry OBJECT-TYPE
        SYNTAX GenEquipEthernetSwitchXSTPParamsEthernetPortsEntry
        ACCESS not-accessible
        STATUS mandatory
          DESCRIPTION
          "RSTP port status table."
        INDEX { ifIndex }
        ::= { genEquipEthernetSwitchXSTPParamsEthernetPortsTable 1 }

GenEquipEthernetSwitchXSTPParamsEthernetPortsEntry ::=
		SEQUENCE {
			genEquipEthernetSwitchXSTPParamsEthernetPortsState
            	INTEGER,
			genEquipEthernetSwitchXSTPParamsEthernetPortsRole
            	INTEGER,
			genEquipEthernetSwitchXSTPParamsEthernetPortsPathCost
            	INTEGER,
			genEquipEthernetSwitchXSTPParamsEthernetPortsPriority
            	INTEGER,
			genEquipEthernetSwitchXSTPParamsEthernetDesPathCost
            	INTEGER,
			genEquipEthernetSwitchXSTPParamsEthernetEdgePort
            	NoYes
}

genEquipEthernetSwitchXSTPParamsEthernetPortsState OBJECT-TYPE
        SYNTAX INTEGER {
				discarding(0),
				listening(1),
				learning(2),
				forwarding(3),
				blocking(4)
		}
        ACCESS read-only
        STATUS mandatory
        DESCRIPTION
        "RSTP port state."
        ::= { genEquipEthernetSwitchXSTPParamsEthernetPortsEntry 1 }

genEquipEthernetSwitchXSTPParamsEthernetPortsRole OBJECT-TYPE
        SYNTAX INTEGER {
				masterport(0),
				alternate(1),
				rootport(2),
				designated(3),
				disabled(4),
				backup(5)
		}
        ACCESS read-only
        STATUS mandatory
        DESCRIPTION
        "RSTP port role."
        ::= { genEquipEthernetSwitchXSTPParamsEthernetPortsEntry 2 }

genEquipEthernetSwitchXSTPParamsEthernetPortsPathCost OBJECT-TYPE
        SYNTAX INTEGER (1..200000000)
        ACCESS read-write
        STATUS mandatory
        DESCRIPTION
        "RSTP configured path cost."
        ::= { genEquipEthernetSwitchXSTPParamsEthernetPortsEntry 3 }

genEquipEthernetSwitchXSTPParamsEthernetPortsPriority OBJECT-TYPE
        SYNTAX INTEGER (0..240)
        ACCESS read-write
        STATUS mandatory
        DESCRIPTION
        "RSTP configured port priority."
        ::= { genEquipEthernetSwitchXSTPParamsEthernetPortsEntry 4 }

genEquipEthernetSwitchXSTPParamsEthernetDesPathCost OBJECT-TYPE
        SYNTAX INTEGER
        ACCESS read-only
        STATUS mandatory
        DESCRIPTION
        "RSTP designated path cost. This is the path cost to the root port from this local port."
        ::= { genEquipEthernetSwitchXSTPParamsEthernetPortsEntry 5 }

genEquipEthernetSwitchXSTPParamsEthernetEdgePort OBJECT-TYPE
        SYNTAX NoYes
        ACCESS read-write
        STATUS mandatory
        DESCRIPTION
        "This parameter indicates if the port is an Edge port or not."
        ::= { genEquipEthernetSwitchXSTPParamsEthernetPortsEntry 6 }




-- Ethernet Switch QoS & Rate Limiting
genEquipEthernetSwitchQoS	OBJECT IDENTIFIER ::= {genEquipEthernetSwitch 3}

genEquipEthernetSwitchQoSTable  OBJECT-TYPE
        SYNTAX  SEQUENCE OF GenEquipEthernetSwitchQoSEntry
        ACCESS  not-accessible
        STATUS mandatory
        DESCRIPTION
        "The switch application, QoS Table."
        ::= { genEquipEthernetSwitchQoS 1 }

genEquipEthernetSwitchQoSEntry OBJECT-TYPE
        SYNTAX GenEquipEthernetSwitchQoSEntry
        ACCESS not-accessible
        STATUS mandatory
        DESCRIPTION
          "The switch application, QoS Table, per Ethernet port based on ifIndex."
        INDEX { ifIndex }
        ::= { genEquipEthernetSwitchQoSTable 1 }

GenEquipEthernetSwitchQoSEntry ::=
		SEQUENCE {
			genEquipEthernetSwitchQoSFirstCrit
            	INTEGER,
			genEquipEthernetSwitchQoSSecondCrit
            	INTEGER,
			genEquipEthernetSwitchQoSThirdCrit
            	INTEGER,
			genEquipEthernetSwitchQoSDefClassification
            	INTEGER,
			genEquipEthernetSwitchQoSEgressSched
            	INTEGER,
			genEquipEthernetSwitchQoSEgressShaper
            	OffOn,
			genEquipEthernetSwitchQoSEgressShaperRate
            	INTEGER,
			genEquipEthernetSwitchQoSIngressPolicer
            	DisplayString
}

genEquipEthernetSwitchQoSFirstCrit OBJECT-TYPE
        SYNTAX INTEGER {
					disable(0),
					queueDecision(1),
					pbitOverride(2),
					queueAndPbitOverride(3)
		}
        ACCESS read-write
        STATUS mandatory
        DESCRIPTION
        "First classification criteria. This is the first criteria which will be evaluated for incoming frames.
	   queueDecision causes classification by defined static MAC address.
	   pbitOverride causes classification by pbits.
	   queueAndPbitOverridecauses classification by defined static MAC address, and changes the pbits accordingly."
        ::= { genEquipEthernetSwitchQoSEntry 1 }

genEquipEthernetSwitchQoSSecondCrit OBJECT-TYPE
        SYNTAX INTEGER {
					disable(0),
					queueDecision(1),
					pbitOverride(2),
					queueAndPbitOverride(3)
		}
        ACCESS read-write
        STATUS mandatory
        DESCRIPTION
       "Second classification criteria. Applicable if match with first criteria is not found.
	  queueDecision causes classification by defined VLAN to queue mapping.
	  pbitOverride causes classification by pbits.
	  queueAndPbitOverrideclassification by defined VLAN to queue mapping, and changes the pbits accordingly."

        ::= { genEquipEthernetSwitchQoSEntry 2 }

genEquipEthernetSwitchQoSThirdCrit OBJECT-TYPE
        SYNTAX INTEGER {
					ipTosPriority(0),
					vlanPbitspriority(1),
					ipTosOverVlanPbitsPriority(2),
					vlanPbitsOverIpTosPriority(3),
					portPriority(4)
		}
        ACCESS read-write
        STATUS mandatory
        DESCRIPTION
        "Third classification criteria. Applicable if match with first or second criteria is not found.
	  ipTosPriority causes classification by defined IP TOS to queue mapping only.
	  vlanPbitspriority causes classification by pbits only.
	  ipTosOverVlanPbitsPriority causes classification by IP TOS and then by pbits .
	  ipTosOverVlanPbitsPriority causes classification by pbits and then by IP TOS.
	  portPriority causes port-based classification according to port priority."
        ::= { genEquipEthernetSwitchQoSEntry 3 }

genEquipEthernetSwitchQoSDefClassification OBJECT-TYPE
        SYNTAX INTEGER {
					first(0),
					second(1),
					third(2),
					fourth(3)
		}
        ACCESS read-write
        STATUS mandatory
        DESCRIPTION
        "Default classification for frame that does suit to the previous classifications.
        Choosing first will classify this frame as the first criteria for example."
        ::= { genEquipEthernetSwitchQoSEntry 4 }

genEquipEthernetSwitchQoSEgressSched OBJECT-TYPE
        SYNTAX INTEGER {
				allQueuesStrict(0),
				fourthQueueStrict(1),
				fourthThirdQueuesStrict(2),
				allQueuesHrr(3)
		}
        ACCESS read-write
        STATUS mandatory
        DESCRIPTION
        "Egress scheduler options."
        ::= { genEquipEthernetSwitchQoSEntry 5 }

genEquipEthernetSwitchQoSEgressShaper OBJECT-TYPE
        SYNTAX OffOn
        ACCESS read-write
        STATUS mandatory
        DESCRIPTION
        "Enable/Disable egress shaping."
        ::= { genEquipEthernetSwitchQoSEntry 6 }

genEquipEthernetSwitchQoSEgressShaperRate OBJECT-TYPE
        SYNTAX INTEGER (64..1000000)
        ACCESS read-write
        STATUS mandatory
        DESCRIPTION
        "Egress shaper rate."
        ::= { genEquipEthernetSwitchQoSEntry 7 }

genEquipEthernetSwitchQoSIngressPolicer OBJECT-TYPE
        SYNTAX DisplayString
        ACCESS read-write
        STATUS mandatory
        DESCRIPTION
        "Ingress policer (rate limiting) name assiciated with this port.
        The policer Name is defined in genEquipEthernetSwitchQoSPolicerNameName (in a table)"
        ::= { genEquipEthernetSwitchQoSEntry 8 }


-- VLAN Pbit Remap table
genEquipEthernetSwitchVlanPbitRemapTable  OBJECT-TYPE
        SYNTAX  SEQUENCE OF GenEquipEthernetSwitchVlanPbitRemapEntry
        ACCESS  not-accessible
        STATUS mandatory
        DESCRIPTION
        "VLAN priority bits remapping table."
        ::= { genEquipEthernetSwitchQoS 2 }

genEquipEthernetSwitchVlanPbitRemapEntry OBJECT-TYPE
        SYNTAX GenEquipEthernetSwitchVlanPbitRemapEntry
        ACCESS not-accessible
        STATUS mandatory
          DESCRIPTION
          "VLAN priority bits remap table."
        INDEX { ifIndex, genEquipEthernetSwitchVlanPbitRemapPbit }
        ::= { genEquipEthernetSwitchVlanPbitRemapTable 1 }

GenEquipEthernetSwitchVlanPbitRemapEntry ::=
		SEQUENCE {
			genEquipEthernetSwitchVlanPbitRemapPbit
            	INTEGER,
			genEquipEthernetSwitchVlanPbitRemapRemappedPbit
            	INTEGER
}

genEquipEthernetSwitchVlanPbitRemapPbit OBJECT-TYPE
        SYNTAX INTEGER
        ACCESS read-only
        STATUS mandatory
        DESCRIPTION
        "The ingress Pbit."
        ::= { genEquipEthernetSwitchVlanPbitRemapEntry 1 }

genEquipEthernetSwitchVlanPbitRemapRemappedPbit OBJECT-TYPE
        SYNTAX INTEGER
        ACCESS read-write
        STATUS mandatory
        DESCRIPTION
        "The remapped Pbit."
        ::= { genEquipEthernetSwitchVlanPbitRemapEntry 2 }

-- VLAN Id Queue
genEquipEthernetSwitchQoSVLANIdToQueueTable  OBJECT-TYPE
        SYNTAX  SEQUENCE OF GenEquipEthernetSwitchQoSVLANIdToQueueEntry
        ACCESS  not-accessible
        STATUS mandatory
        DESCRIPTION
        "VLAN Id to Queue mapping table."
        ::= { genEquipEthernetSwitchQoS 3 }

genEquipEthernetSwitchQoSVLANIdToQueueEntry OBJECT-TYPE
        SYNTAX GenEquipEthernetSwitchQoSVLANIdToQueueEntry
        ACCESS not-accessible
        STATUS mandatory
          DESCRIPTION
          "VLAN Id to Queue mapping table."
        INDEX { genEquipEthernetSwitchCfgVIDIndex }  -- list of all defined vlans (vlan index)
        ::= { genEquipEthernetSwitchQoSVLANIdToQueueTable 1 }

GenEquipEthernetSwitchQoSVLANIdToQueueEntry ::=
		SEQUENCE {
			genEquipEthernetSwitchQoSVLANIdToQueueQueue
            	QueueName
}


genEquipEthernetSwitchQoSVLANIdToQueueQueue OBJECT-TYPE
        SYNTAX QueueName
        ACCESS read-write
        STATUS mandatory
        DESCRIPTION
        "Queue for the vlan."
        ::= { genEquipEthernetSwitchQoSVLANIdToQueueEntry 1 }


-- LAG Defenitions
genEquipEthernetSwitchLag	OBJECT IDENTIFIER ::= {genEquipEthernetSwitch 4}

genEquipEthernetSwitchLagDistFunction OBJECT-TYPE
        SYNTAX INTEGER  {
				simple-xor(0),
				hash(1)
		}
        ACCESS read-write
        STATUS mandatory
        DESCRIPTION
        "LAG distribution function. "
        ::= { genEquipEthernetSwitchLag 1 }

genEquipEthernetSwitchLagMaxNumber OBJECT-TYPE
        SYNTAX INTEGER
        ACCESS read-only
        STATUS mandatory
        DESCRIPTION
        "Max number of LAG port groups."
        ::= { genEquipEthernetSwitchLag 2 }


-- Traffic Managment Defenitions
genEquipEthernetSwitchETM	OBJECT IDENTIFIER ::= {genEquipEthernetSwitch 5}

genEquipEthernetSwitchEtmAdmin OBJECT-TYPE
        SYNTAX EnableDisable
        ACCESS read-write
        STATUS mandatory
        DESCRIPTION
        "Enabling/Disabling the entire enhanced TM functionality."
        ::= { genEquipEthernetSwitchETM 1 }

genEquipEthernetSwitchEtmPTPOptimizedTransportModeAdmin OBJECT-TYPE
        SYNTAX EnableDisable
        ACCESS read-write
        STATUS mandatory
        DESCRIPTION
        "Precision Time Protocol low PDV channel admin  Upon enabling all the packets classified to the 8th
		queue will bypass the scheduler and will be sent directly to the Radio Frame.
		Enabling this parameter will fail if Wayside is enabled."
        ::= { genEquipEthernetSwitchETM 2 }

genEquipEthernetSwitchEtmCountersClear OBJECT-TYPE
        SYNTAX OffOn
        ACCESS read-write
        STATUS mandatory
        DESCRIPTION
        "Reset selected module's counters."
        ::= { genEquipEthernetSwitchETM 3 }

genEquipEthernetSwitchEtmPTPOptimizedTransportMode OBJECT-TYPE
        SYNTAX INTEGER {
			high-Cos-Queue-8(0),
			ieee-1588(1)
		}
        ACCESS read-write
        STATUS mandatory
        DESCRIPTION
        "PTP optimized transport channel operation mode. In High-CoS-Queue-8 mode all the frames that will be classified
		to the 8th queue in the traffic manager will be send to the PTP optimized transport channel.
		In IEEE-1588 mode IEEE 1588 frames will be identified automatically based on UDP ports and/or ethertypes."
        ::= { genEquipEthernetSwitchETM 4 }


-- TM Packet classification tables and control parameters.
genEquipEthernetSwitchEtmClassifier	OBJECT IDENTIFIER ::= {genEquipEthernetSwitchETM 6}

-- TM CoS classification by destination MAC address.
genEquipEthernetSwitchEtmClassifierByMac	OBJECT IDENTIFIER ::= {genEquipEthernetSwitchEtmClassifier 1}

genEquipEthernetSwitchEtmClassifierByMacAdmin OBJECT-TYPE
        SYNTAX EnableDisable
        ACCESS read-write
        STATUS mandatory
        DESCRIPTION
        "Enabling/Disabling CoS and color classification by destination MAC addresses."
        ::= { genEquipEthernetSwitchEtmClassifierByMac 1 }

genEquipEthernetSwitchEtmClassifierByMacTable  OBJECT-TYPE
        SYNTAX  SEQUENCE OF GenEquipEthernetSwitchEtmClassifierByMacEntry
        ACCESS  not-accessible
        STATUS mandatory
        DESCRIPTION
        "Table for CoS and color classification by destination MAC address."
        ::= { genEquipEthernetSwitchEtmClassifierByMac 2 }

genEquipEthernetSwitchEtmClassifierByMacEntry OBJECT-TYPE
        SYNTAX GenEquipEthernetSwitchEtmClassifierByMacEntry
        ACCESS not-accessible
        STATUS mandatory
          DESCRIPTION
          "Table for CoS and color classification by destination MAC address."
        INDEX { genEquipEthernetSwitchEtmClassifierByMacIndex }
        ::= { genEquipEthernetSwitchEtmClassifierByMacTable 1 }

GenEquipEthernetSwitchEtmClassifierByMacEntry ::=
		SEQUENCE {
			genEquipEthernetSwitchEtmClassifierByMacIndex
            	INTEGER,
			genEquipEthernetSwitchEtmClassifierByMacValue
            	OCTET STRING,
			genEquipEthernetSwitchEtmClassifierByMacCos
				INTEGER,
			genEquipEthernetSwitchEtmClassifierByMacColor
				GreenYellow,
			genEquipEthernetSwitchEtmClassifierByMacRowStatus
				RowStatus
		}

genEquipEthernetSwitchEtmClassifierByMacIndex OBJECT-TYPE
        SYNTAX INTEGER (1..16)
        ACCESS read-only
        STATUS mandatory
        DESCRIPTION
        "The index is pointing to a table entry. Each entry contains different MAC address."
        ::= { genEquipEthernetSwitchEtmClassifierByMacEntry 1 }

genEquipEthernetSwitchEtmClassifierByMacValue OBJECT-TYPE
		SYNTAX OCTET STRING (SIZE(0..6))
        ACCESS read-write
        STATUS mandatory
        DESCRIPTION
        "MAC Address value for CoS Classification by MAC Table Entry."
        ::= { genEquipEthernetSwitchEtmClassifierByMacEntry 2 }

genEquipEthernetSwitchEtmClassifierByMacCos OBJECT-TYPE
		SYNTAX INTEGER (0..7)
        ACCESS read-write
        STATUS mandatory
        DESCRIPTION
        "CoS value for CoS Classification by MAC Table Entry."
        ::= { genEquipEthernetSwitchEtmClassifierByMacEntry 3 }

genEquipEthernetSwitchEtmClassifierByMacColor OBJECT-TYPE
		SYNTAX GreenYellow
        ACCESS read-write
        STATUS mandatory
        DESCRIPTION
        "Color value for CoS Classification by MAC Table Entry."
        ::= { genEquipEthernetSwitchEtmClassifierByMacEntry 4 }

genEquipEthernetSwitchEtmClassifierByMacRowStatus OBJECT-TYPE
		SYNTAX RowStatus
        ACCESS read-write
        STATUS mandatory
        DESCRIPTION
        "Row Status for this table."
        ::= { genEquipEthernetSwitchEtmClassifierByMacEntry 30 }


-- TM CoS classification by UDP port.
genEquipEthernetSwitchEtmClassifierByUdpPort	OBJECT IDENTIFIER ::= {genEquipEthernetSwitchEtmClassifier 2}

genEquipEthernetSwitchEtmClassifierByUdpPortAdmin OBJECT-TYPE
        SYNTAX EnableDisable
        ACCESS read-write
        STATUS mandatory
        DESCRIPTION
        "Enabling/Disabling CoS and color classification by UDP source and/or destination ports."
        ::= { genEquipEthernetSwitchEtmClassifierByUdpPort 1 }

genEquipEthernetSwitchEtmClassifierByUdpPortTable  OBJECT-TYPE
        SYNTAX  SEQUENCE OF GenEquipEthernetSwitchEtmClassifierByUdpPortEntry
        ACCESS  not-accessible
        STATUS mandatory
        DESCRIPTION
        "Table for CoS and color classification by UDP ports. Classification may be based on source port,
		dest port ,or both - use validity parameter."
        ::= { genEquipEthernetSwitchEtmClassifierByUdpPort 2 }

genEquipEthernetSwitchEtmClassifierByUdpPortEntry OBJECT-TYPE
        SYNTAX GenEquipEthernetSwitchEtmClassifierByUdpPortEntry
        ACCESS not-accessible
        STATUS mandatory
          DESCRIPTION
        "Entry for CoS and color classification by UDP ports. Classification may be based on source port,
		dest port ,or both - use validity parameter."
        INDEX { genEquipEthernetSwitchEtmClassifierByUdpPortIndex }
        ::= { genEquipEthernetSwitchEtmClassifierByUdpPortTable 1 }

GenEquipEthernetSwitchEtmClassifierByUdpPortEntry ::=
		SEQUENCE {
			genEquipEthernetSwitchEtmClassifierByUdpPortIndex
            	INTEGER,
			genEquipEthernetSwitchEtmClassifierByUdpPortSrcPort
            	INTEGER,
			genEquipEthernetSwitchEtmClassifierByUdpPortDestPort
				INTEGER,
			genEquipEthernetSwitchEtmClassifierByUdpPortCos
				INTEGER,
			genEquipEthernetSwitchEtmClassifierByUdpPortColor
				GreenYellow,
			genEquipEthernetSwitchEtmClassifierByUdpPortValidity
				INTEGER,
			genEquipEthernetSwitchEtmClassifierByUdpPortRowStatus
				RowStatus
}

genEquipEthernetSwitchEtmClassifierByUdpPortIndex OBJECT-TYPE
        SYNTAX INTEGER (1..8)
        ACCESS read-only
        STATUS mandatory
        DESCRIPTION
        "The index is pointing to a table entry. Each entry contains different UDP source and destination ports."
        ::= { genEquipEthernetSwitchEtmClassifierByUdpPortEntry 1 }

genEquipEthernetSwitchEtmClassifierByUdpPortSrcPort OBJECT-TYPE
		SYNTAX INTEGER
        ACCESS read-write
        STATUS mandatory
        DESCRIPTION
        "UDP source port value for CoS Classification by UDP ports Table Entry."
        ::= { genEquipEthernetSwitchEtmClassifierByUdpPortEntry 2 }

genEquipEthernetSwitchEtmClassifierByUdpPortDestPort OBJECT-TYPE
		SYNTAX INTEGER
        ACCESS read-write
        STATUS mandatory
        DESCRIPTION
        "UDP dest. port value for CoS Classification by UDP ports Table Entry."
        ::= { genEquipEthernetSwitchEtmClassifierByUdpPortEntry 3 }

genEquipEthernetSwitchEtmClassifierByUdpPortCos OBJECT-TYPE
		SYNTAX INTEGER (0..7)
        ACCESS read-write
        STATUS mandatory
        DESCRIPTION
        "CoS value for CoS Classification by UDP Ports Table Entry."
        ::= { genEquipEthernetSwitchEtmClassifierByUdpPortEntry 4 }

genEquipEthernetSwitchEtmClassifierByUdpPortColor OBJECT-TYPE
		SYNTAX GreenYellow
        ACCESS read-write
        STATUS mandatory
        DESCRIPTION
        "Color value for CoS Classification by UDP ports Table Entry."
        ::= { genEquipEthernetSwitchEtmClassifierByUdpPortEntry 5 }

genEquipEthernetSwitchEtmClassifierByUdpPortValidity OBJECT-TYPE
		SYNTAX INTEGER {
					unused(0),
					src(1),
					dest(2),
					both(3)
		}
        ACCESS read-write
        STATUS mandatory
        DESCRIPTION
        "Validity value for CoS Classification by UDP ports Table Entry."
        ::= { genEquipEthernetSwitchEtmClassifierByUdpPortEntry 6 }

genEquipEthernetSwitchEtmClassifierByUdpPortRowStatus OBJECT-TYPE
		SYNTAX RowStatus
        ACCESS read-write
        STATUS mandatory
        DESCRIPTION
        "Row Status for this table."
        ::= { genEquipEthernetSwitchEtmClassifierByUdpPortEntry 30 }

-- TM CoS classification by Ethertypes.
-- genEquipEthernetSwitchEtmClassifierByEthertypes	OBJECT IDENTIFIER ::= {genEquipEthernetSwitchEtmClassifier 3}
--
-- genEquipEthernetSwitchEtmClassifierByEthertypesAdmin OBJECT-TYPE
--         SYNTAX EnableDisable
--         ACCESS read-write
--         STATUS mandatory
--         DESCRIPTION
--         "Enabling/Disabling CoS and color classification by Ethertypes."
--         ::= { genEquipEthernetSwitchEtmClassifierByEthertypes 1 }
--
-- genEquipEthernetSwitchEtmClassifierByEthertypesTable  OBJECT-TYPE
--         SYNTAX  SEQUENCE OF GenEquipEthernetSwitchEtmClassifierByEthertypesEntry
--         ACCESS  not-accessible
--         STATUS mandatory
--         DESCRIPTION
--         "Table for CoS and color classification by Ethertype."
--         ::= { genEquipEthernetSwitchEtmClassifierByEthertypes 2 }
--
-- genEquipEthernetSwitchEtmClassifierByEthertypesEntry OBJECT-TYPE
--         SYNTAX GenEquipEthernetSwitchEtmClassifierByEthertypesEntry
--         ACCESS not-accessible
--         STATUS mandatory
--           DESCRIPTION
--           "Table entry for CoS and color classification by Ethertype."
--         INDEX { genEquipEthernetSwitchEtmClassifierByEthertypesIndex }
--         ::= { genEquipEthernetSwitchEtmClassifierByEthertypesTable 1 }
--
-- GenEquipEthernetSwitchEtmClassifierByEthertypesEntry ::=
-- 		SEQUENCE {
-- 			genEquipEthernetSwitchEtmClassifierByEthertypesIndex
--             	INTEGER,
-- 			genEquipEthernetSwitchEtmClassifierByEthertypesValue
--             	INTEGER,
-- 			genEquipEthernetSwitchEtmClassifierByEthertypesCos
-- 				INTEGER,
-- 			genEquipEthernetSwitchEtmClassifierByEthertypesColor
-- 				GreenYellow,
-- 			genEquipEthernetSwitchEtmClassifierByEthertypesRowStatus
-- 				RowStatus
-- }
--
-- genEquipEthernetSwitchEtmClassifierByEthertypesIndex OBJECT-TYPE
--         SYNTAX INTEGER (1..16)
--         ACCESS read-only
--         STATUS mandatory
--         DESCRIPTION
--         "The index is pointing to a table entry. Each entry contains different Ethertype value."
--         ::= { genEquipEthernetSwitchEtmClassifierByEthertypesEntry 1 }
--
-- genEquipEthernetSwitchEtmClassifierByEthertypesValue OBJECT-TYPE
-- 		SYNTAX INTEGER
--         ACCESS read-write
--         STATUS mandatory
--         DESCRIPTION
--         "Ethertype tag value for CoS Classification by Ethertype Table Entry."
--         ::= { genEquipEthernetSwitchEtmClassifierByEthertypesEntry 2 }
--
-- genEquipEthernetSwitchEtmClassifierByEthertypesCos OBJECT-TYPE
-- 		SYNTAX INTEGER (0..7)
--         ACCESS read-write
--         STATUS mandatory
--         DESCRIPTION
--         "CoS value for CoS Classification by Ethertype Table Entry."
--         ::= { genEquipEthernetSwitchEtmClassifierByEthertypesEntry 3 }
--
-- genEquipEthernetSwitchEtmClassifierByEthertypesColor OBJECT-TYPE
-- 		SYNTAX GreenYellow
--         ACCESS read-write
--         STATUS mandatory
--         DESCRIPTION
--         "Color value for CoS Classification by Ethertype Table Entry."
--         ::= { genEquipEthernetSwitchEtmClassifierByEthertypesEntry 4 }
--
-- genEquipEthernetSwitchEtmClassifierByEthertypesRowStatus OBJECT-TYPE
-- 		SYNTAX RowStatus
--         ACCESS read-write
--         STATUS mandatory
--         DESCRIPTION
--         "Row Status for this table."
--         ::= { genEquipEthernetSwitchEtmClassifierByEthertypesEntry 30 }
--
-- TM CoS classification by Known PDU MAC addresses.
genEquipEthernetSwitchEtmClassifierByKnownPduMac	OBJECT IDENTIFIER ::= {genEquipEthernetSwitchEtmClassifier 4}

genEquipEthernetSwitchEtmClassifierByKnownPduMacAdmin OBJECT-TYPE
        SYNTAX EnableDisable
        ACCESS read-write
        STATUS mandatory
        DESCRIPTION
        "Enabling/Disabling CoS and color classification by known PDU MAC addresses."
        ::= { genEquipEthernetSwitchEtmClassifierByKnownPduMac 1 }

genEquipEthernetSwitchEtmClassifierByKnownPduMacTable  OBJECT-TYPE
        SYNTAX  SEQUENCE OF GenEquipEthernetSwitchEtmClassifierByKnownPduMacEntry
        ACCESS  not-accessible
        STATUS mandatory
        DESCRIPTION
        "Table for CoS and color classification by known PDU MAC addresses."
        ::= { genEquipEthernetSwitchEtmClassifierByKnownPduMac 2 }

genEquipEthernetSwitchEtmClassifierByKnownPduMacEntry OBJECT-TYPE
        SYNTAX GenEquipEthernetSwitchEtmClassifierByKnownPduMacEntry
        ACCESS not-accessible
        STATUS mandatory
          DESCRIPTION
          "Table entry for CoS and color classification by known PDU MAC addresses."
        INDEX { genEquipEthernetSwitchEtmClassifierByKnownPduMacIndex }
        ::= { genEquipEthernetSwitchEtmClassifierByKnownPduMacTable 1 }

GenEquipEthernetSwitchEtmClassifierByKnownPduMacEntry ::=
		SEQUENCE {
			genEquipEthernetSwitchEtmClassifierByKnownPduMacIndex
            	INTEGER,
			genEquipEthernetSwitchEtmClassifierByKnownPduMacAddress
				OCTET STRING,
			genEquipEthernetSwitchEtmClassifierByKnownPduMacCos
				INTEGER,
			genEquipEthernetSwitchEtmClassifierByKnownPduMacColor
				GreenYellow,
			genEquipEthernetSwitchEtmClassifierByKnownPduMacValidity
				EnableDisable
		}

genEquipEthernetSwitchEtmClassifierByKnownPduMacIndex OBJECT-TYPE
        SYNTAX INTEGER (1..66)
        ACCESS read-only
        STATUS mandatory
        DESCRIPTION
        "The index is pointing to a table entry. Each entry contains different PDU MAC address value."
        ::= { genEquipEthernetSwitchEtmClassifierByKnownPduMacEntry 1 }

genEquipEthernetSwitchEtmClassifierByKnownPduMacAddress OBJECT-TYPE
		SYNTAX OCTET STRING (SIZE(6))
        ACCESS read-only
        STATUS mandatory
        DESCRIPTION
        "CoS value for MAC address Classification by known PDU Table Entry."
        ::= { genEquipEthernetSwitchEtmClassifierByKnownPduMacEntry 2 }

genEquipEthernetSwitchEtmClassifierByKnownPduMacCos OBJECT-TYPE
		SYNTAX INTEGER (0..7)
        ACCESS read-write
        STATUS mandatory
        DESCRIPTION
        "CoS value for CoS Classification by known PDU Table Entry."
        ::= { genEquipEthernetSwitchEtmClassifierByKnownPduMacEntry 3 }

genEquipEthernetSwitchEtmClassifierByKnownPduMacColor OBJECT-TYPE
		SYNTAX GreenYellow
        ACCESS read-write
        STATUS mandatory
        DESCRIPTION
        "Color value for CoS Classification by known PDU Table Entry."
        ::= { genEquipEthernetSwitchEtmClassifierByKnownPduMacEntry 4 }

genEquipEthernetSwitchEtmClassifierByKnownPduMacValidity OBJECT-TYPE
		SYNTAX EnableDisable
        ACCESS read-write
        STATUS mandatory
        DESCRIPTION
        "Validity value for Cos Classification by known PDU Table Entry."
        ::= { genEquipEthernetSwitchEtmClassifierByKnownPduMacEntry 5 }


-- TM CoS classification by Service.
genEquipEthernetSwitchEtmClassifierByService	OBJECT IDENTIFIER ::= {genEquipEthernetSwitchEtmClassifier 5}

genEquipEthernetSwitchEtmClassifierByServiceAdmin OBJECT-TYPE
	 SYNTAX EnableDisable
	 ACCESS read-write
	 STATUS mandatory
	 DESCRIPTION
	 "Enabling/Disabling CoS and color classification by service IDs."
	 ::= { genEquipEthernetSwitchEtmClassifierByService 1 }

genEquipEthernetSwitchEtmClassifierByServiceTable  OBJECT-TYPE
	 SYNTAX  SEQUENCE OF GenEquipEthernetSwitchEtmClassifierByServiceEntry
	 ACCESS  not-accessible
	 STATUS mandatory
	 DESCRIPTION
	 "Table for CoS and color classification by service-ids."
	 ::= { genEquipEthernetSwitchEtmClassifierByService 2 }

genEquipEthernetSwitchEtmClassifierByServiceEntry OBJECT-TYPE
	 SYNTAX GenEquipEthernetSwitchEtmClassifierByServiceEntry
	 ACCESS not-accessible
	 STATUS mandatory
	   DESCRIPTION
	   "Table entry for CoS and color classification by service-ids."
	 INDEX { genEquipEthernetSwitchEtmClassifierByServiceIndex }
	 ::= { genEquipEthernetSwitchEtmClassifierByServiceTable 1 }

GenEquipEthernetSwitchEtmClassifierByServiceEntry ::=
	SEQUENCE {
		genEquipEthernetSwitchEtmClassifierByServiceIndex
			INTEGER,
		genEquipEthernetSwitchEtmClassifierByServiceCos
			INTEGER,
		genEquipEthernetSwitchEtmClassifierByServiceColor
			GreenYellow,
		genEquipEthernetSwitchEtmClassifierByServiceUsage
			EnableDisable
	}

genEquipEthernetSwitchEtmClassifierByServiceIndex OBJECT-TYPE
	 SYNTAX INTEGER (1..256)
	 ACCESS read-only
	 STATUS mandatory
	 DESCRIPTION
	 "The index is pointing to a table entry. Each entry contains a mapping of service-id to CoS."
	 ::= { genEquipEthernetSwitchEtmClassifierByServiceEntry 1 }

genEquipEthernetSwitchEtmClassifierByServiceCos OBJECT-TYPE
	SYNTAX INTEGER (0..7)
	 ACCESS read-write
	 STATUS mandatory
	 DESCRIPTION
	 "CoS value for CoS serviceID Mapping Table Entry."
	 ::= { genEquipEthernetSwitchEtmClassifierByServiceEntry 2 }

genEquipEthernetSwitchEtmClassifierByServiceColor OBJECT-TYPE
	SYNTAX GreenYellow
	 ACCESS read-write
	 STATUS mandatory
	 DESCRIPTION
	 "Color value for CoS serviceId Mapping Table Entry."
	 ::= { genEquipEthernetSwitchEtmClassifierByServiceEntry 3 }

genEquipEthernetSwitchEtmClassifierByServiceUsage OBJECT-TYPE
	SYNTAX EnableDisable
	 ACCESS read-write
	 STATUS mandatory
	 DESCRIPTION
	 "Validity value for CoS serviceID Mapping Table Entry."
	 ::= { genEquipEthernetSwitchEtmClassifierByServiceEntry 4 }

-- TM CoS classification by VLAN P-bits.
genEquipEthernetSwitchEtmClassifierByVlanPbits	OBJECT IDENTIFIER ::= {genEquipEthernetSwitchEtmClassifier 6}

genEquipEthernetSwitchEtmClassifierByVlanPbitsAdmin OBJECT-TYPE
        SYNTAX EnableDisable
        ACCESS read-write
        STATUS mandatory
        DESCRIPTION
        "Enabling/Disabling CoS and color classification by VLAN P-bits and CFI/DEI bit."
        ::= { genEquipEthernetSwitchEtmClassifierByVlanPbits 1 }

-- Vlan table
genEquipEthernetSwitchEtmClassifierByVlanPbitsVlanTable  OBJECT-TYPE
        SYNTAX  SEQUENCE OF GenEquipEthernetSwitchEtmClassifierByVlanPbitsVlanEntry
        ACCESS  not-accessible
        STATUS mandatory
        DESCRIPTION
        "Table for CoS and color classification by VLAN S-tag P-bits and DEI bit."
        ::= { genEquipEthernetSwitchEtmClassifierByVlanPbits 2 }

genEquipEthernetSwitchEtmClassifierByVlanPbitsVlanEntry OBJECT-TYPE
        SYNTAX GenEquipEthernetSwitchEtmClassifierByVlanPbitsVlanEntry
        ACCESS not-accessible
        STATUS mandatory
          DESCRIPTION
          "Table entry for CoS and color classification by VLAN S-tag P-bits and DEI bit."
        INDEX { genEquipEthernetSwitchEtmClassifierByVlanPbitsVlanIndex }
        ::= { genEquipEthernetSwitchEtmClassifierByVlanPbitsVlanTable 1 }

GenEquipEthernetSwitchEtmClassifierByVlanPbitsVlanEntry ::=
		SEQUENCE {
			genEquipEthernetSwitchEtmClassifierByVlanPbitsVlanIndex
            	INTEGER,
			genEquipEthernetSwitchEtmClassifierByVlanPbitsVlanPriority
            	INTEGER,
			genEquipEthernetSwitchEtmClassifierByVlanPbitsVlanDei
				INTEGER,
			genEquipEthernetSwitchEtmClassifierByVlanPbitsVlanCos
				INTEGER,
			genEquipEthernetSwitchEtmClassifierByVlanPbitsVlanColor
				GreenYellow
		}

genEquipEthernetSwitchEtmClassifierByVlanPbitsVlanIndex OBJECT-TYPE
        SYNTAX INTEGER
        ACCESS read-only
        STATUS mandatory
        DESCRIPTION
        "Pbit vlan index to table."
        ::= { genEquipEthernetSwitchEtmClassifierByVlanPbitsVlanEntry 1 }

genEquipEthernetSwitchEtmClassifierByVlanPbitsVlanPriority OBJECT-TYPE
        SYNTAX INTEGER (0..7)
        ACCESS read-only
        STATUS mandatory
        DESCRIPTION
        "Pbit value for regular classification prioritization."
        ::= { genEquipEthernetSwitchEtmClassifierByVlanPbitsVlanEntry 2 }

genEquipEthernetSwitchEtmClassifierByVlanPbitsVlanDei OBJECT-TYPE
        SYNTAX INTEGER (0..1)
        ACCESS read-only
        STATUS mandatory
        DESCRIPTION
        "DEI value for regular classification prioritization by S-tag vlan."
        ::= { genEquipEthernetSwitchEtmClassifierByVlanPbitsVlanEntry 3 }

genEquipEthernetSwitchEtmClassifierByVlanPbitsVlanCos OBJECT-TYPE
		SYNTAX INTEGER (0..7)
        ACCESS read-write
        STATUS mandatory
        DESCRIPTION
        "CoS value for regular classification prioritization by S-tag VLAN."
        ::= { genEquipEthernetSwitchEtmClassifierByVlanPbitsVlanEntry 4 }

genEquipEthernetSwitchEtmClassifierByVlanPbitsVlanColor OBJECT-TYPE
		SYNTAX GreenYellow
        ACCESS read-write
        STATUS mandatory
        DESCRIPTION
        "Color value for regular classification prioritization by S-tag VLAN."
        ::= { genEquipEthernetSwitchEtmClassifierByVlanPbitsVlanEntry 5 }

-- TM CoS classification by IP DSCP bits.
genEquipEthernetSwitchEtmClassifierByDscp	OBJECT IDENTIFIER ::= {genEquipEthernetSwitchEtmClassifier 7}

genEquipEthernetSwitchEtmClassifierByDscpAdmin OBJECT-TYPE
        SYNTAX EnableDisable
        ACCESS read-write
        STATUS mandatory
        DESCRIPTION
        "Enabling/Disabling Cos and color classification by DSCP/TOS bits."
        ::= { genEquipEthernetSwitchEtmClassifierByDscp 1 }

genEquipEthernetSwitchEtmClassifierByDscpTable  OBJECT-TYPE
        SYNTAX  SEQUENCE OF GenEquipEthernetSwitchEtmClassifierByDscpEntry
        ACCESS  not-accessible
        STATUS mandatory
        DESCRIPTION
        "Table for CoS and color classification by DSCP/TOS bits."
        ::= { genEquipEthernetSwitchEtmClassifierByDscp 2 }

genEquipEthernetSwitchEtmClassifierByDscpEntry OBJECT-TYPE
        SYNTAX GenEquipEthernetSwitchEtmClassifierByDscpEntry
        ACCESS not-accessible
        STATUS mandatory
          DESCRIPTION
          "Table entry for CoS and color classification by DSCP/TOS bits."
        INDEX { genEquipEthernetSwitchEtmClassifierByDscpValue }
        ::= { genEquipEthernetSwitchEtmClassifierByDscpTable 1 }

GenEquipEthernetSwitchEtmClassifierByDscpEntry ::=
		SEQUENCE {
			genEquipEthernetSwitchEtmClassifierByDscpValue
            	INTEGER,
			genEquipEthernetSwitchEtmClassifierByDscpCos
				INTEGER,
			genEquipEthernetSwitchEtmClassifierByDscpColor
				GreenYellow
		}

genEquipEthernetSwitchEtmClassifierByDscpValue OBJECT-TYPE
        SYNTAX INTEGER (0..63)
        ACCESS read-only
        STATUS mandatory
        DESCRIPTION
        "The index is pointing to a table entry. Each entry contains different DSCP/TOS bits mapping."
        ::= { genEquipEthernetSwitchEtmClassifierByDscpEntry 1 }

genEquipEthernetSwitchEtmClassifierByDscpCos OBJECT-TYPE
		SYNTAX INTEGER (0..7)
        ACCESS read-write
        STATUS mandatory
        DESCRIPTION
        "CoS value for regular classification prioritization by DSCP-tag."
        ::= { genEquipEthernetSwitchEtmClassifierByDscpEntry 2 }

genEquipEthernetSwitchEtmClassifierByDscpColor OBJECT-TYPE
		SYNTAX GreenYellow
        ACCESS read-write
        STATUS mandatory
        DESCRIPTION
        "Color value for regular classification prioritization by MPLS."
        ::= { genEquipEthernetSwitchEtmClassifierByDscpEntry 3 }

-- TM CoS classification by MPLS experimental bits.
genEquipEthernetSwitchEtmClassifierByMplsExp	OBJECT IDENTIFIER ::= {genEquipEthernetSwitchEtmClassifier 8}

genEquipEthernetSwitchEtmClassifierByMplsExpAdmin OBJECT-TYPE
        SYNTAX EnableDisable
        ACCESS read-write
        STATUS mandatory
        DESCRIPTION
        "Enabling/Disabling CoS and color classification by MPLS experimantal bits."
        ::= { genEquipEthernetSwitchEtmClassifierByMplsExp 1 }

genEquipEthernetSwitchEtmClassifierByMplsExpTable  OBJECT-TYPE
        SYNTAX  SEQUENCE OF GenEquipEthernetSwitchEtmClassifierByMplsExpEntry
        ACCESS  not-accessible
        STATUS mandatory
        DESCRIPTION
        "Table for CoS and color classification by MPLS experimental bits."
        ::= { genEquipEthernetSwitchEtmClassifierByMplsExp 2 }

genEquipEthernetSwitchEtmClassifierByMplsExpEntry OBJECT-TYPE
        SYNTAX GenEquipEthernetSwitchEtmClassifierByMplsExpEntry
        ACCESS not-accessible
        STATUS mandatory
          DESCRIPTION
          "Table entry for CoS and color classification by MPLS experimental bits."
        INDEX { genEquipEthernetSwitchEtmClassifierByMplsExpValue }
        ::= { genEquipEthernetSwitchEtmClassifierByMplsExpTable 1 }

GenEquipEthernetSwitchEtmClassifierByMplsExpEntry ::=
		SEQUENCE {
			genEquipEthernetSwitchEtmClassifierByMplsExpValue
            	INTEGER,
			genEquipEthernetSwitchEtmClassifierByMplsExpCos
				INTEGER,
			genEquipEthernetSwitchEtmClassifierByMplsExpColor
				GreenYellow
		}

genEquipEthernetSwitchEtmClassifierByMplsExpValue OBJECT-TYPE
        SYNTAX INTEGER (0..7)
        ACCESS read-only
        STATUS mandatory
        DESCRIPTION
        "The index is pointing to a table entry. Each entry contains different MPLS experimantal bits mapping."
        ::= { genEquipEthernetSwitchEtmClassifierByMplsExpEntry 1 }

genEquipEthernetSwitchEtmClassifierByMplsExpCos OBJECT-TYPE
		SYNTAX INTEGER (0..7)
        ACCESS read-write
        STATUS mandatory
        DESCRIPTION
        "value for regular classification prioritization by MPLS."
        ::= { genEquipEthernetSwitchEtmClassifierByMplsExpEntry 2 }

genEquipEthernetSwitchEtmClassifierByMplsExpColor OBJECT-TYPE
		SYNTAX GreenYellow
        ACCESS read-write
        STATUS mandatory
        DESCRIPTION
        "Color value for regular classification prioritization by MPLS."
        ::= { genEquipEthernetSwitchEtmClassifierByMplsExpEntry 3 }

-- TM CoS default color defs.
genEquipEthernetSwitchEtmClassifierByDefaultCosColor	OBJECT IDENTIFIER ::= {genEquipEthernetSwitchEtmClassifier 9}

genEquipEthernetSwitchEtmClassifierByDefaultCos OBJECT-TYPE
        SYNTAX INTEGER (0..7)
        ACCESS read-write
        STATUS mandatory
        DESCRIPTION
        "CoS value for regular classification prioritization by default port."
        ::= { genEquipEthernetSwitchEtmClassifierByDefaultCosColor 1 }

genEquipEthernetSwitchEtmClassifierByDefaultColor OBJECT-TYPE
        SYNTAX GreenYellow
        ACCESS read-write
        STATUS mandatory
        DESCRIPTION
        "Table for regular priority by default port mapping table."
        ::= { genEquipEthernetSwitchEtmClassifierByDefaultCosColor 2 }

-- TM CoS classification by Cos To Queue
genEquipEthernetSwitchEtmClassifierByCosToQueue	OBJECT IDENTIFIER ::= {genEquipEthernetSwitchEtmClassifier 10}

genEquipEthernetSwitchEtmClassifierByCosToQueueTable  OBJECT-TYPE
        SYNTAX  SEQUENCE OF GenEquipEthernetSwitchEtmClassifierByCosToQueueEntry
        ACCESS  not-accessible
        STATUS mandatory
        DESCRIPTION
        "Table for VLAN to FlowId mapping ."
        ::= { genEquipEthernetSwitchEtmClassifierByCosToQueue 1 }

genEquipEthernetSwitchEtmClassifierByCosToQueueEntry OBJECT-TYPE
        SYNTAX GenEquipEthernetSwitchEtmClassifierByCosToQueueEntry
        ACCESS not-accessible
        STATUS mandatory
          DESCRIPTION
          "Table for VLAN to FlowId mapping ."
        INDEX { genEquipEthernetSwitchEtmClassifierByCosToQueueIndex }
        ::= { genEquipEthernetSwitchEtmClassifierByCosToQueueTable 1 }

GenEquipEthernetSwitchEtmClassifierByCosToQueueEntry ::=
		SEQUENCE {
			genEquipEthernetSwitchEtmClassifierByCosToQueueIndex
            	INTEGER,
			genEquipEthernetSwitchEtmClassifierByCosToQueueValue
				INTEGER
		}

genEquipEthernetSwitchEtmClassifierByCosToQueueIndex OBJECT-TYPE
        SYNTAX INTEGER
        ACCESS read-only
        STATUS mandatory
        DESCRIPTION
        "The index is pointing to a table entry. Each entry contains a mapping of a different CoS to a queue."
        ::= { genEquipEthernetSwitchEtmClassifierByCosToQueueEntry 1 }

genEquipEthernetSwitchEtmClassifierByCosToQueueValue OBJECT-TYPE
		SYNTAX INTEGER (1..8)
        ACCESS read-write
        STATUS mandatory
        DESCRIPTION
        "Queue index for CoS to Queue Mapping Table Entry."
        ::= { genEquipEthernetSwitchEtmClassifierByCosToQueueEntry 2 }

-- TM CoS classification by Vlan to Service
genEquipEthernetSwitchEtmClassifierVlanidToService	OBJECT IDENTIFIER ::= {genEquipEthernetSwitchEtmClassifier 11}

genEquipEthernetSwitchEtmClassifierVlanidToServiceTable  OBJECT-TYPE
        SYNTAX  SEQUENCE OF GenEquipEthernetSwitchEtmClassifierVlanidToServiceEntry
        ACCESS  not-accessible
        STATUS mandatory
        DESCRIPTION
        "Table for VLAN to Vlan To Servies mapping ."
        ::= { genEquipEthernetSwitchEtmClassifierVlanidToService 1 }

genEquipEthernetSwitchEtmClassifierVlanidToServiceEntry OBJECT-TYPE
        SYNTAX GenEquipEthernetSwitchEtmClassifierVlanidToServiceEntry
        ACCESS not-accessible
        STATUS mandatory
          DESCRIPTION
          "Table for VLAN to Vlan To Servies mapping ."
        INDEX { genEquipEthernetSwitchEtmClassifierByServiceVlanidToServiceIndex }
        ::= { genEquipEthernetSwitchEtmClassifierVlanidToServiceTable 1 }

GenEquipEthernetSwitchEtmClassifierVlanidToServiceEntry ::=
		SEQUENCE {
			genEquipEthernetSwitchEtmClassifierByServiceVlanidToServiceIndex
            	INTEGER,
			genEquipEthernetSwitchEtmClassifierByFlowsVlanidToServiceValue
				INTEGER
		}

genEquipEthernetSwitchEtmClassifierByServiceVlanidToServiceIndex OBJECT-TYPE
        SYNTAX INTEGER
        ACCESS read-only
        STATUS mandatory
        DESCRIPTION
        "The index is pointing to a table entry. Each entry contains a mapping of a different CoS to a queue."
        ::= { genEquipEthernetSwitchEtmClassifierVlanidToServiceEntry 1 }

genEquipEthernetSwitchEtmClassifierByFlowsVlanidToServiceValue OBJECT-TYPE
		SYNTAX INTEGER (1..256)
        ACCESS read-write
        STATUS mandatory
        DESCRIPTION
        "Service ID."
        ::= { genEquipEthernetSwitchEtmClassifierVlanidToServiceEntry 2 }



-- TM Classifier Inband Managment Qos
-- Cos and Color classification by VLAN-ID. Only a single VLAN-ID value can be specified.
-- This is configuration should be used for inband management VLAN-ID classification to the high priority queue.
genEquipEthernetSwitchEtmClassifierInbandMgmtQoS	OBJECT IDENTIFIER ::= {genEquipEthernetSwitchEtmClassifier 12}

genEquipEthernetSwitchEtmClassifierInbandMgmtAdmin OBJECT-TYPE
 		SYNTAX EnableDisable
        ACCESS read-write
        STATUS mandatory
        DESCRIPTION
        "Enabling/Disabling CoS and Color classification by VLAN ID."
        ::= { genEquipEthernetSwitchEtmClassifierInbandMgmtQoS 1 }

genEquipEthernetSwitchEtmClassifierInbandMgmtVlanId OBJECT-TYPE
 		SYNTAX INTEGER (0..4090)
         ACCESS read-write
         STATUS mandatory
         DESCRIPTION
         "Inband Management vlan id. This parameter should be the same as genEquipEthernetSwitchEtmClassifierInbandMgmtVlanId."
         ::= { genEquipEthernetSwitchEtmClassifierInbandMgmtQoS 2 }

genEquipEthernetSwitchEtmClassifierInbandMgmtCos OBJECT-TYPE
 		SYNTAX INTEGER (0..7)
         ACCESS read-write
         STATUS mandatory
         DESCRIPTION
         "Class of Service. Allowed values: [0-7]."
         ::= { genEquipEthernetSwitchEtmClassifierInbandMgmtQoS 3 }

genEquipEthernetSwitchEtmClassifierInbandMgmtColor OBJECT-TYPE
 		SYNTAX GreenYellow
         ACCESS read-write
         STATUS mandatory
         DESCRIPTION
         "Color 1=green ; 0=yellow."
         ::= { genEquipEthernetSwitchEtmClassifierInbandMgmtQoS 4 }


-- TM ACM drop per queue paramters.
--genEquipEthernetSwitchEtmAcmDropPerQueue	OBJECT IDENTIFIER ::= {genEquipEthernetSwitchETM 7}

-- TM Policers configuration and mapping tables and parameters
genEquipEthernetSwitchEtmPolicers	OBJECT IDENTIFIER ::= {genEquipEthernetSwitchETM 8}

genEquipEthernetSwitchEtmPolicerModuleAdmin OBJECT-TYPE
 		SYNTAX EnableDisable
        ACCESS read-write
        STATUS mandatory
        DESCRIPTION
        "Enabling/Disabling Policing."
        ::= { genEquipEthernetSwitchEtmPolicers 1 }

-- Table of Service to Policeer mapping
genEquipEthernetSwitchEtmServiceToPolicerTable  OBJECT-TYPE
        SYNTAX  SEQUENCE OF GenEquipEthernetSwitchEtmServiceToPolicerEntry
        ACCESS  not-accessible
        STATUS mandatory
        DESCRIPTION
        "Table of Service to Policeer mapping."
        ::= { genEquipEthernetSwitchEtmPolicers 2 }

genEquipEthernetSwitchEtmServiceToPolicerEntry OBJECT-TYPE
        SYNTAX GenEquipEthernetSwitchEtmServiceToPolicerEntry
        ACCESS not-accessible
        STATUS mandatory
          DESCRIPTION
          "Table of Service to Policeer mapping."
        INDEX { genEquipEthernetSwitchEtmServiceToPolicerIndex }
        ::= { genEquipEthernetSwitchEtmServiceToPolicerTable 1 }

GenEquipEthernetSwitchEtmServiceToPolicerEntry ::=
		SEQUENCE {
			genEquipEthernetSwitchEtmServiceToPolicerIndex
            	INTEGER,
			genEquipEthernetSwitchEtmServiceToPolicerValue
				INTEGER,
			genEquipEthernetSwitchEtmServiceToPolicerPerCosOption
				EnableDisable
		}

genEquipEthernetSwitchEtmServiceToPolicerIndex OBJECT-TYPE
        SYNTAX INTEGER (1..256)
        ACCESS read-only
        STATUS mandatory
        DESCRIPTION
        "Service Index."
        ::= { genEquipEthernetSwitchEtmServiceToPolicerEntry 1 }

genEquipEthernetSwitchEtmServiceToPolicerValue OBJECT-TYPE
		SYNTAX INTEGER (1..256)
        ACCESS read-write
        STATUS mandatory
        DESCRIPTION
        "Policer to be used for the specific Service."
        ::= { genEquipEthernetSwitchEtmServiceToPolicerEntry 2 }

genEquipEthernetSwitchEtmServiceToPolicerPerCosOption OBJECT-TYPE
		SYNTAX EnableDisable
        ACCESS read-write
        STATUS mandatory
        DESCRIPTION
        "Policer per CoS option. If enabled, each Service will be mapped to 8 policers while each policer will be used
		for a different CoS value. This option can be used only for the pilicers with indeces of multiple of 8. i.e 8,16,24,32,240,248."
        ::= { genEquipEthernetSwitchEtmServiceToPolicerEntry 3 }


-- Table of Policers configuration
genEquipEthernetSwitchEtmPolicerConfigTable  OBJECT-TYPE
        SYNTAX  SEQUENCE OF GenEquipEthernetSwitchEtmPolicerConfigEntry
        ACCESS  not-accessible
        STATUS mandatory
        DESCRIPTION
        "Table of Policers configuration."
        ::= { genEquipEthernetSwitchEtmPolicers 3 }

genEquipEthernetSwitchEtmPolicerConfigEntry OBJECT-TYPE
        SYNTAX GenEquipEthernetSwitchEtmPolicerConfigEntry
        ACCESS not-accessible
        STATUS mandatory
          DESCRIPTION
          "Table of Policers configuration."
        INDEX { genEquipEthernetSwitchEtmPolicerConfigIndex }
        ::= { genEquipEthernetSwitchEtmPolicerConfigTable 1 }

GenEquipEthernetSwitchEtmPolicerConfigEntry ::=
		SEQUENCE {
			genEquipEthernetSwitchEtmPolicerConfigIndex
            	INTEGER,
			genEquipEthernetSwitchEtmPolicerConfigAdmin
            	EnableDisable,
			genEquipEthernetSwitchEtmPolicerConfigColorAware
            	EnableDisable,
			genEquipEthernetSwitchEtmPolicerConfigCir
            	INTEGER,
			genEquipEthernetSwitchEtmPolicerConfigCbs
            	INTEGER,
			genEquipEthernetSwitchEtmPolicerConfigEir
            	INTEGER,
			genEquipEthernetSwitchEtmPolicerConfigEbs
            	INTEGER,
			genEquipEthernetSwitchEtmPolicerConfigCoupling
            	EnableDisable,
			genEquipEthernetSwitchEtmPolicerConfigLineComp
            	INTEGER
		}

genEquipEthernetSwitchEtmPolicerConfigIndex OBJECT-TYPE
        SYNTAX INTEGER (1..256)
        ACCESS read-only
        STATUS mandatory
        DESCRIPTION
        "Service Index."
        ::= { genEquipEthernetSwitchEtmPolicerConfigEntry 1 }

genEquipEthernetSwitchEtmPolicerConfigAdmin OBJECT-TYPE
		SYNTAX EnableDisable
        ACCESS read-write
        STATUS mandatory
        DESCRIPTION
        "Egress policer admin disables/enables the policing feature per policer.
		If not enabled, the policer is in bypass mode (no rate limiting)."
        ::= { genEquipEthernetSwitchEtmPolicerConfigEntry 2 }

genEquipEthernetSwitchEtmPolicerConfigColorAware OBJECT-TYPE
		SYNTAX EnableDisable
        ACCESS read-write
        STATUS mandatory
        DESCRIPTION
        "Whether policer is color aware."
        ::= { genEquipEthernetSwitchEtmPolicerConfigEntry 3 }

genEquipEthernetSwitchEtmPolicerConfigCir OBJECT-TYPE
        SYNTAX INTEGER
        ACCESS read-write
        STATUS mandatory
        DESCRIPTION
        "Egress policer CIR value - the committed rate user requests."
        ::= { genEquipEthernetSwitchEtmPolicerConfigEntry 4 }

genEquipEthernetSwitchEtmPolicerConfigCbs OBJECT-TYPE
        SYNTAX INTEGER (1..128)
        ACCESS read-write
        STATUS mandatory
        DESCRIPTION
        "Egress policer committed burst size value."
        ::= { genEquipEthernetSwitchEtmPolicerConfigEntry 5 }

genEquipEthernetSwitchEtmPolicerConfigEir OBJECT-TYPE
        SYNTAX INTEGER
        ACCESS read-write
        STATUS mandatory
        DESCRIPTION
        "Egress policer EIR value - the excess rate user requests."
        ::= { genEquipEthernetSwitchEtmPolicerConfigEntry 6 }

genEquipEthernetSwitchEtmPolicerConfigEbs OBJECT-TYPE
        SYNTAX INTEGER (1..128)
        ACCESS read-write
        STATUS mandatory
        DESCRIPTION
        "Egress policer excess burst size value (bytes)."
        ::= { genEquipEthernetSwitchEtmPolicerConfigEntry 7 }

genEquipEthernetSwitchEtmPolicerConfigCoupling OBJECT-TYPE
        SYNTAX EnableDisable
        ACCESS read-write
        STATUS mandatory
        DESCRIPTION
        "Egress policer coupling mode."
        ::= { genEquipEthernetSwitchEtmPolicerConfigEntry 8 }

genEquipEthernetSwitchEtmPolicerConfigLineComp OBJECT-TYPE
        SYNTAX INTEGER (0..255)
        ACCESS read-write
        STATUS mandatory
        DESCRIPTION
        "Egress policer line compensation value (bytes)."
        ::= { genEquipEthernetSwitchEtmPolicerConfigEntry 9 }



-- TM Queues configuration
genEquipEthernetSwitchEtmQueues	OBJECT IDENTIFIER ::= {genEquipEthernetSwitchETM 9}

genEquipEthernetSwitchEtmQueuesTable  OBJECT-TYPE
        SYNTAX  SEQUENCE OF GenEquipEthernetSwitchEtmQueuesEntry
        ACCESS  not-accessible
        STATUS mandatory
        DESCRIPTION
        "Table of queue sizes."
        ::= { genEquipEthernetSwitchEtmQueues 1 }

genEquipEthernetSwitchEtmQueuesEntry OBJECT-TYPE
        SYNTAX GenEquipEthernetSwitchEtmQueuesEntry
        ACCESS not-accessible
        STATUS mandatory
          DESCRIPTION
          "Table entry of queue sizes."
        INDEX { genEquipEthernetSwitchEtmQueuesIndex }
        ::= { genEquipEthernetSwitchEtmQueuesTable 1 }

GenEquipEthernetSwitchEtmQueuesEntry ::=
		SEQUENCE {
			genEquipEthernetSwitchEtmQueuesIndex
            	INTEGER,
			genEquipEthernetSwitchEtmQueuesSize
				INTEGER
		}

genEquipEthernetSwitchEtmQueuesIndex OBJECT-TYPE
        SYNTAX INTEGER (1..8)
        ACCESS read-only
        STATUS mandatory
        DESCRIPTION
        "The Index to a queue."
        ::= { genEquipEthernetSwitchEtmQueuesEntry 1 }

genEquipEthernetSwitchEtmQueuesSize OBJECT-TYPE
		SYNTAX INTEGER {
					kbit-0(0),
					kbit-500(1),
					kbit-1000(2),
					kbit-2000(3),
					kbit-4000(4),
					kbit-250(5),
					kbit-3000(6),
					kbit-3500(7)
		}
        ACCESS read-write
        STATUS mandatory
        DESCRIPTION
        "Size of queue[i]"
        ::= { genEquipEthernetSwitchEtmQueuesEntry 2 }

-- TM WRED configuration
genEquipEthernetSwitchEtmWred	OBJECT IDENTIFIER ::= {genEquipEthernetSwitchETM 10}

genEquipEthernetSwitchEtmWredAdmin OBJECT-TYPE
        SYNTAX EnableDisable
        ACCESS read-write
        STATUS mandatory
        DESCRIPTION
        "Enabling/Disabling WRED."
        ::= { genEquipEthernetSwitchEtmWred 1 }


genEquipEthernetSwitchEtmWredThresholdsTable  OBJECT-TYPE
        SYNTAX  SEQUENCE OF GenEquipEthernetSwitchEtmWredThresholdsEntry
        ACCESS  not-accessible
        STATUS mandatory
        DESCRIPTION
        "WRED thresholds per queue."
        ::= { genEquipEthernetSwitchEtmWred 2 }

genEquipEthernetSwitchEtmWredThresholdsEntry OBJECT-TYPE
        SYNTAX GenEquipEthernetSwitchEtmWredThresholdsEntry
        ACCESS not-accessible
        STATUS mandatory
          DESCRIPTION
          "WRED entry thresholds per queue."
        INDEX { genEquipEthernetSwitchEtmWredQueuesIndex }
        ::= { genEquipEthernetSwitchEtmWredThresholdsTable 1 }

GenEquipEthernetSwitchEtmWredThresholdsEntry ::=
		SEQUENCE {
			genEquipEthernetSwitchEtmWredQueuesIndex
            	INTEGER,
			genEquipEthernetSwitchEtmWredThresholdsGreenThLow
				INTEGER,
			genEquipEthernetSwitchEtmWredThresholdsGreenThHigh
				INTEGER,
			genEquipEthernetSwitchEtmWredThresholdsYellowThLow
				INTEGER,
			genEquipEthernetSwitchEtmWredThresholdsYellowThHigh
				INTEGER,
			genEquipEthernetSwitchEtmWredThresholdsGreenMaxDrop
				INTEGER,
			genEquipEthernetSwitchEtmWredThresholdsYellowMaxDrop
				INTEGER
		}

genEquipEthernetSwitchEtmWredQueuesIndex OBJECT-TYPE
        SYNTAX INTEGER (1..8)
        ACCESS read-only
        STATUS mandatory
        DESCRIPTION
        "WRED thresholds per queue."
        ::= { genEquipEthernetSwitchEtmWredThresholdsEntry 1 }

genEquipEthernetSwitchEtmWredThresholdsGreenThLow OBJECT-TYPE
		SYNTAX INTEGER (0..4000)
        ACCESS read-write
        STATUS mandatory
        DESCRIPTION
        "WRED green low threshold  defines the queue level (in Kbits) point
		that the mechanism should start checking if to drop the green frames."
        ::= { genEquipEthernetSwitchEtmWredThresholdsEntry 2 }

genEquipEthernetSwitchEtmWredThresholdsGreenThHigh OBJECT-TYPE
		SYNTAX INTEGER (0..4000)
        ACCESS read-write
        STATUS mandatory
        DESCRIPTION
        "WRED green high threshold defines the queue level of occupancy (in Kbits) point that the WRED
		must drop all arriving green colored frames."
        ::= { genEquipEthernetSwitchEtmWredThresholdsEntry 3 }

genEquipEthernetSwitchEtmWredThresholdsYellowThLow OBJECT-TYPE
		SYNTAX INTEGER (0..4000)
        ACCESS read-write
        STATUS mandatory
        DESCRIPTION
        "WRED yellow low threshold  defines the queue level (in Kbits) point that the mechanism should
		start checking if to drop the yellow frames."
        ::= { genEquipEthernetSwitchEtmWredThresholdsEntry 4 }

genEquipEthernetSwitchEtmWredThresholdsYellowThHigh OBJECT-TYPE
		SYNTAX INTEGER (0..4000)
        ACCESS read-write
        STATUS mandatory
        DESCRIPTION
        "WRED yellow high threshold defines the queue level of occupancy (in Kbits) point that the WRED
		must drop all arriving yellow colored frames."
        ::= { genEquipEthernetSwitchEtmWredThresholdsEntry 5 }

genEquipEthernetSwitchEtmWredThresholdsGreenMaxDrop OBJECT-TYPE
		SYNTAX INTEGER (0..100)
        ACCESS read-write
        STATUS mandatory
        DESCRIPTION
        "WRED green max drop threshold  the probability to drop frame at the green high threshold (in percent based units)."
        ::= { genEquipEthernetSwitchEtmWredThresholdsEntry 6 }

genEquipEthernetSwitchEtmWredThresholdsYellowMaxDrop OBJECT-TYPE
		SYNTAX INTEGER (0..100)
        ACCESS read-write
        STATUS mandatory
        DESCRIPTION
        "WRED yellow max drop threshold  the probability to drop frame at the yellow high threshold (in percent based units)."
        ::= { genEquipEthernetSwitchEtmWredThresholdsEntry 7 }


-- TM Marker configurations
genEquipEthernetSwitchEtmMarker	OBJECT IDENTIFIER ::= {genEquipEthernetSwitchETM 11}

genEquipEthernetSwitchEtmMarkerAdmin OBJECT-TYPE
        SYNTAX EnableDisable
        ACCESS read-write
        STATUS mandatory
        DESCRIPTION
        "Enabling/Disabling marking of VLAN P-bits and DEI/CFI bit at the egress."
        ::= { genEquipEthernetSwitchEtmMarker 1 }


genEquipEthernetSwitchEtmMarkerTable  OBJECT-TYPE
        SYNTAX  SEQUENCE OF GenEquipEthernetSwitchEtmMarkerEntry
        ACCESS  not-accessible
        STATUS mandatory
        DESCRIPTION
        "Table of CoS and color to Pbits and DEI marking for S-VALNS."
        ::= { genEquipEthernetSwitchEtmMarker 2 }

genEquipEthernetSwitchEtmMarkerEntry OBJECT-TYPE
        SYNTAX GenEquipEthernetSwitchEtmMarkerEntry
        ACCESS not-accessible
        STATUS mandatory
          DESCRIPTION
          "Table of CoS and color to Pbits and DEI marking for S-VALNS."
        INDEX { genEquipEthernetSwitchEtmMarkerCoS,
				genEquipEthernetSwitchEtmMarkerColor
		}
        ::= { genEquipEthernetSwitchEtmMarkerTable 1 }

GenEquipEthernetSwitchEtmMarkerEntry ::=
		SEQUENCE {
			genEquipEthernetSwitchEtmMarkerCoS
            	INTEGER,
			genEquipEthernetSwitchEtmMarkerColor
				INTEGER,
			genEquipEthernetSwitchEtmMarkerPbit
				INTEGER,
			genEquipEthernetSwitchEtmMarkerCfi
				INTEGER
		}

genEquipEthernetSwitchEtmMarkerCoS OBJECT-TYPE
        SYNTAX INTEGER (1..8)
        ACCESS read-only
        STATUS mandatory
        DESCRIPTION
        "CoS value as was mapped by the TM calssifier."
        ::= { genEquipEthernetSwitchEtmMarkerEntry 1 }

genEquipEthernetSwitchEtmMarkerColor OBJECT-TYPE
		SYNTAX INTEGER (1..2)
        ACCESS read-only
        STATUS mandatory
        DESCRIPTION
        "Color value as was mapped by the TM calssifier."
        ::= { genEquipEthernetSwitchEtmMarkerEntry 2 }

genEquipEthernetSwitchEtmMarkerPbit OBJECT-TYPE
		SYNTAX INTEGER (1..8)
        ACCESS read-write
        STATUS mandatory
        DESCRIPTION
        "VLAN 802.1p P-bit value to be modified."
        ::= { genEquipEthernetSwitchEtmMarkerEntry 3 }

genEquipEthernetSwitchEtmMarkerCfi OBJECT-TYPE
		SYNTAX INTEGER (1..2)
        ACCESS read-write
        STATUS mandatory
        DESCRIPTION
        "VLAN CFI/DEI value to be modified."
        ::= { genEquipEthernetSwitchEtmMarkerEntry 4 }


-- TM Scheduler configuration
genEquipEthernetSwitchEtmScheduler	OBJECT IDENTIFIER ::= {genEquipEthernetSwitchETM 12}

genEquipEthernetSwitchEtmSchedulerQuantum OBJECT-TYPE
        SYNTAX INTEGER
        ACCESS read-write
        STATUS mandatory
        DESCRIPTION
        "WFQ Quantum for credit calculation in bytes (64, 128, 256, 512)."
        ::= { genEquipEthernetSwitchEtmScheduler 1 }


genEquipEthernetSwitchEtmSchedulerConfigTable  OBJECT-TYPE
        SYNTAX  SEQUENCE OF GenEquipEthernetSwitchEtmSchedulerConfigEntry
        ACCESS  not-accessible
        STATUS mandatory
        DESCRIPTION
        "Table for scheduler configuration: priority and weight for each queue."
        ::= { genEquipEthernetSwitchEtmScheduler 2 }

genEquipEthernetSwitchEtmSchedulerConfigEntry OBJECT-TYPE
        SYNTAX GenEquipEthernetSwitchEtmSchedulerConfigEntry
        ACCESS not-accessible
        STATUS mandatory
        DESCRIPTION
        "Table entry for scheduler configuration: priority and weight for each queue."
        INDEX { genEquipEthernetSwitchEtmSchedulerConfigQueueIndex }
        ::= { genEquipEthernetSwitchEtmSchedulerConfigTable 1 }

GenEquipEthernetSwitchEtmSchedulerConfigEntry ::=
		SEQUENCE {
			genEquipEthernetSwitchEtmSchedulerConfigQueueIndex
            	INTEGER,
			genEquipEthernetSwitchEtmSchedulerConfigPriority
				INTEGER,
			genEquipEthernetSwitchEtmSchedulerConfigWeight
				INTEGER
		}

genEquipEthernetSwitchEtmSchedulerConfigQueueIndex OBJECT-TYPE
        SYNTAX INTEGER (1..8)
        ACCESS read-only
        STATUS mandatory
        DESCRIPTION
        "queue index."
        ::= { genEquipEthernetSwitchEtmSchedulerConfigEntry 1 }

genEquipEthernetSwitchEtmSchedulerConfigPriority OBJECT-TYPE
		SYNTAX INTEGER (1..4)
        ACCESS read-write
        STATUS mandatory
        DESCRIPTION
        "Strict priority of each queue. 4=highest , 1=lowest."
        ::= { genEquipEthernetSwitchEtmSchedulerConfigEntry 2 }

genEquipEthernetSwitchEtmSchedulerConfigWeight OBJECT-TYPE
		SYNTAX INTEGER (0..15)
        ACCESS read-write
        STATUS mandatory
        DESCRIPTION
        "WFQ Weights for each queue"
        ::= { genEquipEthernetSwitchEtmSchedulerConfigEntry 3 }

-- TM Egress shaper configuration
genEquipEthernetSwitchEtmShaper	OBJECT IDENTIFIER ::= {genEquipEthernetSwitchETM 13}

genEquipEthernetSwitchEtmShaperGlobalAdmin OBJECT-TYPE
		SYNTAX EnableDisable
        ACCESS read-write
        STATUS mandatory
        DESCRIPTION
        "Global Shaper admin disables/enables the global shaping feature."
        ::= { genEquipEthernetSwitchEtmShaper 1 }

genEquipEthernetSwitchEtmShaperConfigTable  OBJECT-TYPE
        SYNTAX  SEQUENCE OF GenEquipEthernetSwitchEtmShaperConfigEntry
        ACCESS  not-accessible
        STATUS mandatory
        DESCRIPTION
        "Table of shapers' configurations. Each shaper is on the egress of a queue.."
        ::= { genEquipEthernetSwitchEtmShaper 2 }

genEquipEthernetSwitchEtmShaperConfigEntry OBJECT-TYPE
        SYNTAX GenEquipEthernetSwitchEtmShaperConfigEntry
        ACCESS not-accessible
        STATUS mandatory
        DESCRIPTION
        "Table entry of shapers' configurations. Each shaper is on the egress of a queue.."
        INDEX { genEquipEthernetSwitchEtmShaperConfigIndex }
        ::= { genEquipEthernetSwitchEtmShaperConfigTable 1 }

GenEquipEthernetSwitchEtmShaperConfigEntry ::=
		SEQUENCE {
			genEquipEthernetSwitchEtmShaperConfigIndex
            	INTEGER,
			genEquipEthernetSwitchEtmShaperConfigAdmin
				INTEGER,
			genEquipEthernetSwitchEtmShaperConfigCir
				INTEGER,
			genEquipEthernetSwitchEtmShaperConfigCbs
				INTEGER,
			genEquipEthernetSwitchEtmShaperConfigLineComp
				INTEGER
		}

genEquipEthernetSwitchEtmShaperConfigIndex OBJECT-TYPE
        SYNTAX INTEGER (1..8)
        ACCESS read-only
        STATUS mandatory
        DESCRIPTION
        "queue index."
        ::= { genEquipEthernetSwitchEtmShaperConfigEntry 1 }

genEquipEthernetSwitchEtmShaperConfigAdmin OBJECT-TYPE
		SYNTAX EnableDisable
        ACCESS read-write
        STATUS mandatory
        DESCRIPTION
        "Egress Shaper admin disables/enables the shaping feature per queue."
        ::= { genEquipEthernetSwitchEtmShaperConfigEntry 2 }

genEquipEthernetSwitchEtmShaperConfigCir OBJECT-TYPE
		SYNTAX INTEGER (0..1000000)
        ACCESS read-write
        STATUS mandatory
        DESCRIPTION
        "Egress shaper CIR value - the committed rate as given by the user."
        ::= { genEquipEthernetSwitchEtmShaperConfigEntry 3 }

genEquipEthernetSwitchEtmShaperConfigCbs OBJECT-TYPE
		SYNTAX INTEGER (0..128000)
        ACCESS read-write
        STATUS mandatory
        DESCRIPTION
        "Egress shaper committed burst size value."
        ::= { genEquipEthernetSwitchEtmShaperConfigEntry 4 }

genEquipEthernetSwitchEtmShaperConfigLineComp OBJECT-TYPE
		SYNTAX INTEGER (0..255)
        ACCESS read-write
        STATUS mandatory
        DESCRIPTION
        "Egress shaper line compensation value transmitted IFG + Preamble.
		The shaper adds this value to each arriving frame size."
        ::= { genEquipEthernetSwitchEtmShaperConfigEntry 5 }

-- TM Statistics counters
genEquipEthernetSwitchEtmStatistics	OBJECT IDENTIFIER ::= {genEquipEthernetSwitchETM 14}

genEquipEthernetSwitchEtmStatisticsPortTotalBytesTransmitted OBJECT-TYPE
		SYNTAX INTEGER
        ACCESS read-only
        STATUS mandatory
        DESCRIPTION
        "The number of bytes transmitted via the port (goes into PM)."
        ::= { genEquipEthernetSwitchEtmStatistics 1 }

genEquipEthernetSwitchEtmStatisticsPortTotalUnicastFramesTransmitted OBJECT-TYPE
		SYNTAX INTEGER
        ACCESS read-only
        STATUS mandatory
        DESCRIPTION
        "TThe number of Unicast frames transmitted to the radio port.."
        ::= { genEquipEthernetSwitchEtmStatistics 2 }


genEquipEthernetSwitchEtmStatisticsPortTotalMulticastFramesTransmitted OBJECT-TYPE
		SYNTAX INTEGER
        ACCESS read-only
        STATUS mandatory
        DESCRIPTION
        "The number of Multicast frames transmitted to the radio port.."
        ::= { genEquipEthernetSwitchEtmStatistics 3 }


genEquipEthernetSwitchEtmStatisticsPortTotalBroadcastFramesTransmitted OBJECT-TYPE
		SYNTAX INTEGER
        ACCESS read-only
        STATUS mandatory
        DESCRIPTION
        "The number of Broadcast frames transmitted to the radio port.."
        ::= { genEquipEthernetSwitchEtmStatistics 4 }


genEquipEthernetSwitchEtmStatisticsPortFrames64octTransmitted OBJECT-TYPE
		SYNTAX INTEGER
        ACCESS read-only
        STATUS mandatory
        DESCRIPTION
        "The total number of frames transmitted with a length of exactly 64 Octets."
        ::= { genEquipEthernetSwitchEtmStatistics 5 }


genEquipEthernetSwitchEtmStatisticsPortFrames65to127Transmitted OBJECT-TYPE
		SYNTAX INTEGER
        ACCESS read-only
        STATUS mandatory
        DESCRIPTION
        "The total number of frames transmitted with a length of 65-127 Octets."
        ::= { genEquipEthernetSwitchEtmStatistics 6 }


genEquipEthernetSwitchEtmStatisticsPortFrames128to255Transmitted OBJECT-TYPE
		SYNTAX INTEGER
        ACCESS read-only
        STATUS mandatory
        DESCRIPTION
        "The total number of frames transmitted with a length of 128-255 Octets."
        ::= { genEquipEthernetSwitchEtmStatistics 7 }


genEquipEthernetSwitchEtmStatisticsPortFrames256to511Transmitted OBJECT-TYPE
		SYNTAX INTEGER
        ACCESS read-only
        STATUS mandatory
        DESCRIPTION
        "The total number of frames transmitted with a length of 256-511 Octets)."
        ::= { genEquipEthernetSwitchEtmStatistics 8 }


genEquipEthernetSwitchEtmStatisticsPortFrames512to1023Transmitted OBJECT-TYPE
		SYNTAX INTEGER
        ACCESS read-only
        STATUS mandatory
        DESCRIPTION
        "TThe total number of frames transmitted with a length of 512-1023 Octets."
        ::= { genEquipEthernetSwitchEtmStatistics 9 }


genEquipEthernetSwitchEtmStatisticsPortFrames1024toMtuTransmitted OBJECT-TYPE
		SYNTAX INTEGER
        ACCESS read-only
        STATUS mandatory
        DESCRIPTION
        "The total number of frames transmitted with a length between 1024 and MaxTransmitSize Octets."
        ::= { genEquipEthernetSwitchEtmStatistics 10 }



-- IP Pbits to Queue
genEquipEthernetSwitchQoSIPPbits	OBJECT IDENTIFIER ::= {genEquipEthernetSwitchQoS 4}

genEquipEthernetSwitchQoSIPPbitsIPPrio OBJECT-TYPE
        SYNTAX INTEGER {
			ipPrecedence(0),
			ipv4TOSIPv6(1)  -- diffserv.
		}
        ACCESS read-write
        STATUS mandatory
        DESCRIPTION
        "IP priority options."
        ::= { genEquipEthernetSwitchQoSIPPbits 1 }

genEquipEthernetSwitchQoSIPPbitsTable  OBJECT-TYPE
        SYNTAX  SEQUENCE OF GenEquipEthernetSwitchQoSIPPbitsEntry
        ACCESS  not-accessible
        STATUS mandatory
        DESCRIPTION
        "Mapping of IP pbits to Queue."
        ::= { genEquipEthernetSwitchQoSIPPbits 2 }

genEquipEthernetSwitchQoSIPPbitsEntry OBJECT-TYPE
        SYNTAX GenEquipEthernetSwitchQoSIPPbitsEntry
        ACCESS not-accessible
        STATUS mandatory
          DESCRIPTION
          "Mapping of IP pbits to Queue."
        INDEX { genEquipEthernetSwitchQoSIPPbitsId }
        ::= { genEquipEthernetSwitchQoSIPPbitsTable 1 }

GenEquipEthernetSwitchQoSIPPbitsEntry ::=
		SEQUENCE {
			genEquipEthernetSwitchQoSIPPbitsId
            	INTEGER,
			genEquipEthernetSwitchQoSIPPbitsQueue
            	QueueName
}

genEquipEthernetSwitchQoSIPPbitsId OBJECT-TYPE
        SYNTAX INTEGER
        ACCESS read-only
        STATUS mandatory
        DESCRIPTION
        "The pbit number."
        ::= { genEquipEthernetSwitchQoSIPPbitsEntry 1 }

genEquipEthernetSwitchQoSIPPbitsQueue OBJECT-TYPE
        SYNTAX QueueName
        ACCESS read-write
        STATUS mandatory
        DESCRIPTION
        "the queue for that pbit."
        ::= { genEquipEthernetSwitchQoSIPPbitsEntry 2 }



-- VLAN Pbits to queue

genEquipEthernetSwitchQoSVLANPbitsTable  OBJECT-TYPE
        SYNTAX  SEQUENCE OF GenEquipEthernetSwitchQoSVLANPbitsEntry
        ACCESS  not-accessible
        STATUS mandatory
        DESCRIPTION
        "VLAN pbit to queue mapping table."
        ::= { genEquipEthernetSwitchQoS 5 }

genEquipEthernetSwitchQoSVLANPbitsEntry OBJECT-TYPE
        SYNTAX GenEquipEthernetSwitchQoSVLANPbitsEntry
        ACCESS not-accessible
        STATUS mandatory
          DESCRIPTION
          "VLAN pbit to queue mapping table."
        INDEX { genEquipEthernetSwitchQoSVLANPbitsId }
        ::= { genEquipEthernetSwitchQoSVLANPbitsTable 1 }

GenEquipEthernetSwitchQoSVLANPbitsEntry ::=
		SEQUENCE {
			genEquipEthernetSwitchQoSVLANPbitsId
            	INTEGER,
			genEquipEthernetSwitchQoSVLANPbitsQueue
            	QueueName
}

genEquipEthernetSwitchQoSVLANPbitsId OBJECT-TYPE
        SYNTAX INTEGER  (1..8)
        ACCESS read-only
        STATUS mandatory
        DESCRIPTION
        "The VLAN'S pbit (index of the table)"
        ::= { genEquipEthernetSwitchQoSVLANPbitsEntry 1 }

genEquipEthernetSwitchQoSVLANPbitsQueue OBJECT-TYPE
        SYNTAX QueueName
        ACCESS read-write
        STATUS mandatory
        DESCRIPTION
        "The mapped queue for the corresponding VLAN ."
        ::= { genEquipEthernetSwitchQoSVLANPbitsEntry 2 }


-- Queue Weights
genEquipEthernetSwitchQoSQueueWeightsTable  OBJECT-TYPE
        SYNTAX  SEQUENCE OF GenEquipEthernetSwitchQoSQueueWeightsEntry
        ACCESS  not-accessible
        STATUS mandatory
        DESCRIPTION "Queue weights mapping table."
        ::= { genEquipEthernetSwitchQoS 6 }

genEquipEthernetSwitchQoSQueueWeightsEntry OBJECT-TYPE
        SYNTAX GenEquipEthernetSwitchQoSQueueWeightsEntry
        ACCESS not-accessible
        STATUS mandatory
        DESCRIPTION "Queue weights mapping table."
        INDEX { genEquipEthernetSwitchQoSQueueWeightsId }
        ::= { genEquipEthernetSwitchQoSQueueWeightsTable 1 }

GenEquipEthernetSwitchQoSQueueWeightsEntry ::=
		SEQUENCE {
			genEquipEthernetSwitchQoSQueueWeightsId
            	INTEGER,
			genEquipEthernetSwitchQoSQueueWeightsQueue
            	QueueName,
			genEquipEthernetSwitchQoSQueueWeightsWeight
            	INTEGER
}


genEquipEthernetSwitchQoSQueueWeightsId OBJECT-TYPE
        SYNTAX INTEGER (1..4)
        ACCESS read-only
        STATUS mandatory
        DESCRIPTION
        "Index for this table."
        ::= { genEquipEthernetSwitchQoSQueueWeightsEntry 1 }

genEquipEthernetSwitchQoSQueueWeightsQueue OBJECT-TYPE
        SYNTAX QueueName
        ACCESS read-only
        STATUS mandatory
        DESCRIPTION
        "The queue number."
        ::= { genEquipEthernetSwitchQoSQueueWeightsEntry 2 }

genEquipEthernetSwitchQoSQueueWeightsWeight OBJECT-TYPE
        SYNTAX INTEGER (1..32)
        ACCESS read-write
        STATUS mandatory
        DESCRIPTION
        "The weight for the queue"
        ::= { genEquipEthernetSwitchQoSQueueWeightsEntry 3 }




-- Policer list
-- Policer Name table
genEquipEthernetSwitchQoSPolicerNameTable  OBJECT-TYPE
        SYNTAX  SEQUENCE OF GenEquipEthernetSwitchQoSPolicerNameEntry
        ACCESS  not-accessible
        STATUS mandatory
        DESCRIPTION
        "Table of configured policers."
        ::= { genEquipEthernetSwitchQoS 7 }

genEquipEthernetSwitchQoSPolicerNameEntry OBJECT-TYPE
        SYNTAX GenEquipEthernetSwitchQoSPolicerNameEntry
        ACCESS not-accessible
        STATUS mandatory
        DESCRIPTION "Table of configured policers."
        INDEX { genEquipEthernetSwitchQoSPolicerNameId }
        ::= { genEquipEthernetSwitchQoSPolicerNameTable 1 }

GenEquipEthernetSwitchQoSPolicerNameEntry ::=
		SEQUENCE {
			genEquipEthernetSwitchQoSPolicerNameId
            	INTEGER,
			genEquipEthernetSwitchQoSPolicerNameName
            	DisplayString,
			genEquipEthernetSwitchQoSPolicerNameRowStatus
            	RowStatus
}

genEquipEthernetSwitchQoSPolicerNameId OBJECT-TYPE
        SYNTAX INTEGER
        ACCESS read-only
        STATUS mandatory
        DESCRIPTION
        "Policer ID"
        ::= { genEquipEthernetSwitchQoSPolicerNameEntry 1 }

genEquipEthernetSwitchQoSPolicerNameName OBJECT-TYPE
        SYNTAX DisplayString
        ACCESS read-write
        STATUS mandatory
        DESCRIPTION
        "Policer name."
        ::= { genEquipEthernetSwitchQoSPolicerNameEntry 2 }

genEquipEthernetSwitchQoSPolicerNameRowStatus OBJECT-TYPE
        SYNTAX RowStatus
        ACCESS read-write
        STATUS mandatory
        DESCRIPTION
        "Policer row status."
        ::= { genEquipEthernetSwitchQoSPolicerNameEntry 30 }

-- Policer list table
genEquipEthernetSwitchQoSPolicerListTable  OBJECT-TYPE
        SYNTAX  SEQUENCE OF GenEquipEthernetSwitchQoSPolicerListEntry
        ACCESS  not-accessible
        STATUS mandatory
        DESCRIPTION
        "The policer class table list."
        ::= { genEquipEthernetSwitchQoS 8 }

genEquipEthernetSwitchQoSPolicerListEntry OBJECT-TYPE
        SYNTAX GenEquipEthernetSwitchQoSPolicerListEntry
        ACCESS not-accessible
        STATUS mandatory
          DESCRIPTION
          "The policer class table list."
        INDEX { genEquipEthernetSwitchQoSPolicerNameId, genEquipEthernetSwitchQoSPolicerListId }
        ::= { genEquipEthernetSwitchQoSPolicerListTable 1 }

GenEquipEthernetSwitchQoSPolicerListEntry ::=
		SEQUENCE {
			genEquipEthernetSwitchQoSPolicerListId
            	INTEGER,
			genEquipEthernetSwitchQoSPolicerListName
				DisplayString,
			genEquipEthernetSwitchQoSPolicerListClassName
            	DisplayString,
			genEquipEthernetSwitchQoSPolicerListTrafficType
            	INTEGER,
			genEquipEthernetSwitchQoSPolicerListCIR
            	INTEGER,
			genEquipEthernetSwitchQoSPolicerListCBS
            	INTEGER,
			genEquipEthernetSwitchQoSPolicerListRowStatus
            	RowStatus
}

genEquipEthernetSwitchQoSPolicerListId OBJECT-TYPE
        SYNTAX INTEGER
        ACCESS read-only
        STATUS mandatory
        DESCRIPTION
        "The policer ID."
        ::= { genEquipEthernetSwitchQoSPolicerListEntry 1 }

genEquipEthernetSwitchQoSPolicerListName OBJECT-TYPE
        SYNTAX DisplayString
        ACCESS read-write
        STATUS mandatory
        DESCRIPTION
        "The policer class name"
        ::= { genEquipEthernetSwitchQoSPolicerListEntry 2 }

genEquipEthernetSwitchQoSPolicerListClassName OBJECT-TYPE
        SYNTAX DisplayString
        ACCESS read-write
        STATUS mandatory
        DESCRIPTION
        "The policer class name"
        ::= { genEquipEthernetSwitchQoSPolicerListEntry 3 }

genEquipEthernetSwitchQoSPolicerListTrafficType OBJECT-TYPE
        SYNTAX INTEGER {
	        unknownUcast(1),
	        unknowMulticast(2),
	        broadcast(3),
	        multicast(5),
	        unicast(6),
	        arp(8),
	        tcpData(9),
	        tcpControl(10),
	        udp(11),
	        noTcpUdp(12),
	        firstPriority(13),
	        secondPriority(14),
	        thirdPriority(15),
	        forthPriority(16),
	        allTraffic(17)
        }
        ACCESS read-write
        STATUS mandatory
        DESCRIPTION
        "The traffic type that the policer applies to."
        ::= { genEquipEthernetSwitchQoSPolicerListEntry 4 }

genEquipEthernetSwitchQoSPolicerListCIR OBJECT-TYPE
        SYNTAX INTEGER
        ACCESS read-write
        STATUS mandatory
        DESCRIPTION
        "The CIR (Critical Information Rate) value (in Kbps)"
        ::= { genEquipEthernetSwitchQoSPolicerListEntry 5 }

genEquipEthernetSwitchQoSPolicerListCBS OBJECT-TYPE
        SYNTAX INTEGER
        ACCESS read-write
        STATUS mandatory
        DESCRIPTION
        "The CBS (Critical Burst Size) value (in Bytes)"
        ::= { genEquipEthernetSwitchQoSPolicerListEntry 6 }

genEquipEthernetSwitchQoSPolicerListRowStatus OBJECT-TYPE
        SYNTAX RowStatus
        ACCESS read-write
        STATUS mandatory
        DESCRIPTION
        "Row status of the table."
        ::= { genEquipEthernetSwitchQoSPolicerListEntry 30 }


-- Static MAC
genEquipEthernetSwitchQoSStaticMacTable  OBJECT-TYPE
        SYNTAX  SEQUENCE OF GenEquipEthernetSwitchQoSStaticMacEntry
        ACCESS  not-accessible
        STATUS mandatory
        DESCRIPTION
        "Static MAC forwarding table."
        ::= { genEquipEthernetSwitchQoS 9 }

genEquipEthernetSwitchQoSStaticMacEntry OBJECT-TYPE
        SYNTAX GenEquipEthernetSwitchQoSStaticMacEntry
        ACCESS not-accessible
        STATUS mandatory
          DESCRIPTION
          "Static MAC forwarding table."
        INDEX { genEquipEthernetSwitchQoSStaticMacId }
        ::= { genEquipEthernetSwitchQoSStaticMacTable 1 }

GenEquipEthernetSwitchQoSStaticMacEntry ::=
		SEQUENCE {
			genEquipEthernetSwitchQoSStaticMacId
            	INTEGER,
			genEquipEthernetSwitchQoSStaticMacAddr
            	OCTET STRING,
			genEquipEthernetSwitchQoSStaticMacVlanId
            	INTEGER,
			genEquipEthernetSwitchQoSStaticMacForwardTo
            	INTEGER,
			genEquipEthernetSwitchQoSStaticMacPriority
            	INTEGER,
			genEquipEthernetSwitchQoSStaticMacRowStatus
            	RowStatus
}

genEquipEthernetSwitchQoSStaticMacId OBJECT-TYPE
        SYNTAX INTEGER
        ACCESS read-only
        STATUS mandatory
        DESCRIPTION
        "The index of the table"
        ::= { genEquipEthernetSwitchQoSStaticMacEntry 1 }

genEquipEthernetSwitchQoSStaticMacAddr OBJECT-TYPE
		SYNTAX OCTET STRING
		ACCESS read-write
        STATUS mandatory
        DESCRIPTION
        "Static MAC Address."
        ::= { genEquipEthernetSwitchQoSStaticMacEntry 2 }

genEquipEthernetSwitchQoSStaticMacVlanId OBJECT-TYPE
        SYNTAX INTEGER
        ACCESS read-write
        STATUS mandatory
        DESCRIPTION
        "VLAN ID for this MAC."
        ::= { genEquipEthernetSwitchQoSStaticMacEntry 3 }

genEquipEthernetSwitchQoSStaticMacForwardTo OBJECT-TYPE
        SYNTAX INTEGER
        ACCESS read-write
        STATUS mandatory
        DESCRIPTION
        "The port number to be forwarded to, starting from 1."
        ::= { genEquipEthernetSwitchQoSStaticMacEntry 4 }

genEquipEthernetSwitchQoSStaticMacPriority OBJECT-TYPE
        SYNTAX INTEGER
        ACCESS read-write
        STATUS mandatory
        DESCRIPTION
        "The priority to be given to this MAC address."
        ::= { genEquipEthernetSwitchQoSStaticMacEntry 5 }

genEquipEthernetSwitchQoSStaticMacRowStatus OBJECT-TYPE
        SYNTAX RowStatus
        ACCESS read-write
        STATUS mandatory
        DESCRIPTION
        "The row status of the operation."
        ::= { genEquipEthernetSwitchQoSStaticMacEntry 30 }


-- MSTP
--
genEquipProtocols	OBJECT IDENTIFIER ::= {genEquipEthernetSwitch 6}

genEquipProtocolsMstp	OBJECT IDENTIFIER ::= {genEquipProtocols 1}

--
-- MSTP General attributes - mstp-general-attributes-table
--

genEquipProtocolsMstpGeneralAttributesTable  OBJECT-TYPE
        SYNTAX  SEQUENCE OF GenEquipProtocolsMstpGeneralAttributesEntry
        ACCESS  not-accessible
        STATUS mandatory
        DESCRIPTION
        "A table containing NE configuration and maintenance attributes which are not part of the standard MIB."
        ::= { genEquipProtocolsMstp 1 }

genEquipProtocolsMstpGeneralAttributesEntry OBJECT-TYPE
        SYNTAX GenEquipProtocolsMstpGeneralAttributesEntry
        ACCESS  not-accessible
        STATUS mandatory
        DESCRIPTION
        "A table containing NE configuration and maintenance attributes which are not part of the standard MIB."
        INDEX { genEquipProtocolsMstpGeneralAttributesComponentId }
        ::= { genEquipProtocolsMstpGeneralAttributesTable 1 }

GenEquipProtocolsMstpGeneralAttributesEntry ::=
	SEQUENCE {
		genEquipProtocolsMstpGeneralAttributesComponentId
			INTEGER,
		genEquipProtocolsMstpGeneralAttributesMstpEnabled
			TrueFalse,
		genEquipProtocolsMstpGeneralAttributesNumberOfinstances
			INTEGER,
		genEquipProtocolsMstpGeneralAttributesMigrateTime
			INTEGER,
		genEquipProtocolsMstpGeneralAttributesBpduDestinationMAC
			INTEGER,
		genEquipProtocolsMstpGeneralAttributesFrozen
			TrueFalse,
		genEquipProtocolsMstpGeneralAttributesSdHandling
			INTEGER,
		genEquipProtocolsMstpGeneralAttributesReset
			TrueFalse,
		genEquipProtocolsMstpGeneralAttributesResetCounters
			TrueFalse
	}

genEquipProtocolsMstpGeneralAttributesComponentId OBJECT-TYPE
        SYNTAX  INTEGER
        ACCESS  read-only
        STATUS 	mandatory
        DESCRIPTION
        "Distinguished between multiple virtual bridge instances within a PB or PBB.  In simple situations, i.e. single component the default is 1"
        ::= { genEquipProtocolsMstpGeneralAttributesEntry 1 }

genEquipProtocolsMstpGeneralAttributesMstpEnabled OBJECT-TYPE
        SYNTAX  TrueFalse
        ACCESS  read-write
        STATUS 	mandatory
        DESCRIPTION
        "When set, MSTP protocol is enabled on NE"
        ::= { genEquipProtocolsMstpGeneralAttributesEntry 2 }

genEquipProtocolsMstpGeneralAttributesNumberOfinstances OBJECT-TYPE
        SYNTAX  INTEGER (2..16)
        ACCESS  read-write
        STATUS 	mandatory
        DESCRIPTION
        "Specifies number of instances supported. Value ranges from 2 to 16."
        ::= { genEquipProtocolsMstpGeneralAttributesEntry 3 }

genEquipProtocolsMstpGeneralAttributesMigrateTime OBJECT-TYPE
        SYNTAX  INTEGER
		ACCESS  read-only
        STATUS 	mandatory
        DESCRIPTION
        "When MSTP bridge detects the presence of STP data on one of its ports,
		it migrates after 'MigrateTime' has elapsed, if migrate is enabled."
        ::= { genEquipProtocolsMstpGeneralAttributesEntry 4 }

genEquipProtocolsMstpGeneralAttributesBpduDestinationMAC OBJECT-TYPE
        SYNTAX  INTEGER {
					customer(0),
					provider(1)
					}
		ACCESS  read-write
        STATUS 	mandatory
        DESCRIPTION
        "When set to 'customer', BPDU Dest MAC address should be set to 0x0180-C200-0000.
		Otherwise, BPDU Dest MAC address should be set to 0x0180-C200-0008"
        ::= { genEquipProtocolsMstpGeneralAttributesEntry 5 }

genEquipProtocolsMstpGeneralAttributesFrozen OBJECT-TYPE
        SYNTAX  TrueFalse
        ACCESS  read-write
        STATUS 	mandatory
        DESCRIPTION
        "When set, MSTP protocol stops running in NE., i.e. BPDU are neither processed nor transmitted.
		All ports states are maintained."
        ::= { genEquipProtocolsMstpGeneralAttributesEntry 6 }

genEquipProtocolsMstpGeneralAttributesSdHandling OBJECT-TYPE
        SYNTAX  INTEGER {
					ignored(0),
					sameAsSF(1)
					}
        ACCESS  read-write
        STATUS 	mandatory
        DESCRIPTION
        "When set to 'ignored', SD (Signal Degrade) failures are ignored in MSTP. Otherwise, SD failures are treated same as SF."
        ::= { genEquipProtocolsMstpGeneralAttributesEntry 7 }

genEquipProtocolsMstpGeneralAttributesReset OBJECT-TYPE
        SYNTAX  INTEGER {
					noAction(0),
					reset(1)
					}
        ACCESS  read-write
        STATUS 	mandatory
        DESCRIPTION
        "When set to reset, MSTP Protocol suit is reset"
        ::= { genEquipProtocolsMstpGeneralAttributesEntry 8 }

genEquipProtocolsMstpGeneralAttributesResetCounters OBJECT-TYPE
        SYNTAX  INTEGER {
					noAction(0),
					reset(1)
					}
        ACCESS  read-write
        STATUS 	mandatory
        DESCRIPTION
        "When set to reset, MSTP counters are reset"
        ::= { genEquipProtocolsMstpGeneralAttributesEntry 9 }

--
-- MSTP counters per instance per port - mstp-mstp-port-counters-table
--

genEquipProtocolsMstpCountersTable  OBJECT-TYPE
        SYNTAX  SEQUENCE OF GenEquipProtocolsMstpCountersEntry
        ACCESS  not-accessible
        STATUS mandatory
        DESCRIPTION
        "A table containing MSTP counters per instance per port."
        ::= { genEquipProtocolsMstp 2 }

genEquipProtocolsMstpCountersEntry OBJECT-TYPE
        SYNTAX GenEquipProtocolsMstpCountersEntry
        ACCESS  not-accessible
        STATUS mandatory
        DESCRIPTION
        "A table containing MSTP counters per instance per port."
        INDEX { genEquipProtocolsMstpCountersPortId	}
        ::= { genEquipProtocolsMstpCountersTable 1 }

GenEquipProtocolsMstpCountersEntry ::=
	SEQUENCE {
		genEquipProtocolsMstpCountersPortId
			INTEGER,
		genEquipProtocolsMstpCountersNumberOfReceivedTCN
			INTEGER,
		genEquipProtocolsMstpCountersNumberOfReceivedConfigurationBpdu
			INTEGER,
		genEquipProtocolsMstpCountersNumberOfReceivedRstBpdu
			INTEGER,
		genEquipProtocolsMstpCountersNumberOfReceivedMstBpdu
			INTEGER,
		genEquipProtocolsMstpCountersNumberOfTransmittedTcnBpdu
			INTEGER,
		genEquipProtocolsMstpCountersNumberOfTransmittedConfigurationBpdu
			INTEGER,
		genEquipProtocolsMstpCountersNumberOfTransmittedRstBpdu
			INTEGER,
		genEquipProtocolsMstpCountersNumberOfTransmittedMstBpdu
			INTEGER
	}

genEquipProtocolsMstpCountersPortId OBJECT-TYPE
        SYNTAX  INTEGER
        ACCESS  read-only
        STATUS 	mandatory
        DESCRIPTION
        "Port ID (ifIndex)"
        ::= { genEquipProtocolsMstpCountersEntry 1 }

genEquipProtocolsMstpCountersNumberOfReceivedTCN OBJECT-TYPE
        SYNTAX  INTEGER
        ACCESS  read-only
        STATUS 	mandatory
        DESCRIPTION
        "Number of received TCN"
        ::= { genEquipProtocolsMstpCountersEntry 2 }

genEquipProtocolsMstpCountersNumberOfReceivedConfigurationBpdu OBJECT-TYPE
        SYNTAX  INTEGER
        ACCESS  read-only
        STATUS 	mandatory
        DESCRIPTION
        "Number of received Configuration BPDU."
        ::= { genEquipProtocolsMstpCountersEntry 3 }

genEquipProtocolsMstpCountersNumberOfReceivedRstBpdu OBJECT-TYPE
        SYNTAX  INTEGER
		ACCESS  read-only
        STATUS 	mandatory
        DESCRIPTION
        "Number of received RST BPDU."
        ::= { genEquipProtocolsMstpCountersEntry 4 }

genEquipProtocolsMstpCountersNumberOfReceivedMstBpdu OBJECT-TYPE
        SYNTAX  INTEGER
		ACCESS  read-only
        STATUS 	mandatory
        DESCRIPTION
        "Number of received MST BPDU"
        ::= { genEquipProtocolsMstpCountersEntry 5 }

genEquipProtocolsMstpCountersNumberOfTransmittedTcnBpdu OBJECT-TYPE
        SYNTAX  INTEGER
        ACCESS  read-only
        STATUS 	mandatory
        DESCRIPTION
        "Number Of Transmitted TCN BPDU."
        ::= { genEquipProtocolsMstpCountersEntry 6 }

genEquipProtocolsMstpCountersNumberOfTransmittedConfigurationBpdu OBJECT-TYPE
        SYNTAX  INTEGER
        ACCESS  read-only
        STATUS 	mandatory
        DESCRIPTION
        "Number of transmitted Configuration BPDU."
        ::= { genEquipProtocolsMstpCountersEntry 7 }

genEquipProtocolsMstpCountersNumberOfTransmittedRstBpdu OBJECT-TYPE
        SYNTAX  INTEGER
        ACCESS  read-only
        STATUS 	mandatory
        DESCRIPTION
        "Number of transmitted RST BPDU"
        ::= { genEquipProtocolsMstpCountersEntry 8 }

genEquipProtocolsMstpCountersNumberOfTransmittedMstBpdu OBJECT-TYPE
        SYNTAX  INTEGER
        ACCESS  read-only
        STATUS 	mandatory
        DESCRIPTION
        "Number of transmitted MST BPDU"
        ::= { genEquipProtocolsMstpCountersEntry 9 }


genEquipProtocolsEoam	OBJECT IDENTIFIER ::= {genEquipProtocols 2}

--
-- EOAM Configuration and Status - eoam-bw-vsm-table
--

genEquipProtocolsEoamBwVsmTable  OBJECT-TYPE
        SYNTAX  SEQUENCE OF GenEquipProtocolsEoamBwVsmEntry
        ACCESS  not-accessible
        STATUS mandatory
        DESCRIPTION
        "A Table containing Ethernet OAM Configuration and Status."
        ::= { genEquipProtocolsEoam 1 }

genEquipProtocolsEoamBwVsmEntry OBJECT-TYPE
        SYNTAX GenEquipProtocolsEoamBwVsmEntry
        ACCESS  not-accessible
        STATUS mandatory
        DESCRIPTION
        "A Table entry containing Ethernet OAM Configuration and Status."
        INDEX { genEquipProtocolsEoamBwVsmName }
        ::= { genEquipProtocolsEoamBwVsmTable 1 }

GenEquipProtocolsEoamBwVsmEntry ::=
	SEQUENCE {
		genEquipProtocolsEoamBwVsmName
			DisplayString,
		genEquipProtocolsEoamBwVsmAdmin
			Dot1CfmInterfaceStatus,
		genEquipProtocolsEoamBwVsmPeriod
			INTEGER,
		genEquipProtocolsEoamBwVsmCurrentBw
			INTEGER,
		genEquipProtocolsEoamBwVsmControlIfindex
			INTEGER,
		genEquipProtocolsEoamBwVsmId
			INTEGER,
		genEquipProtocolsEoamBwVsmMonitoredIfindex
			INTEGER,
		genEquipProtocolsEoamBwVsmHoldoff
			INTEGER,
		genEquipProtocolsEoamBwVsmHoldoffStartTime
			INTEGER,
		genEquipProtocolsEoamBwVsmHoldoffState
			INTEGER,
		genEquipProtocolsEoamBwVsmLastSentMsg
			OCTET STRING,
		genEquipProtocolsEoamBwVsmMel
			INTEGER,
		genEquipProtocolsEoamBwVsmMonitoringInterval
			INTEGER,
		genEquipProtocolsEoamBwVsmNominalBw
			INTEGER,
		genEquipProtocolsEoamBwVsmTxMsgCounter
			INTEGER,
		genEquipProtocolsEoamBwVsmVersion
			INTEGER,
		genEquipProtocolsEoamBwVsmVlan
			INTEGER,
		genEquipProtocolsEoamBwVsmResetMsgCounter
			OffOn,
		genEquipProtocolsEoamBwVsmRowStatus
			RowStatus
	}

genEquipProtocolsEoamBwVsmName OBJECT-TYPE
        SYNTAX  DisplayString
        ACCESS  read-only
        STATUS 	mandatory
        DESCRIPTION
        "Name of EOAM entity"
        ::= { genEquipProtocolsEoamBwVsmEntry 1 }

genEquipProtocolsEoamBwVsmAdmin OBJECT-TYPE
        SYNTAX  Dot1CfmInterfaceStatus
        ACCESS  read-write
        STATUS 	mandatory
        DESCRIPTION
        "Eoam Admin. Possible valuew: Up, Down"
        ::= { genEquipProtocolsEoamBwVsmEntry 2 }

genEquipProtocolsEoamBwVsmPeriod OBJECT-TYPE
        SYNTAX  INTEGER
        ACCESS  read-write
        STATUS 	mandatory
        DESCRIPTION
        "The interval of transmitting messages, when current nominal."
        ::= { genEquipProtocolsEoamBwVsmEntry 3 }

genEquipProtocolsEoamBwVsmCurrentBw OBJECT-TYPE
        SYNTAX  INTEGER
		ACCESS  read-only
        STATUS 	mandatory
        DESCRIPTION
        "The Current BW measure by 4 samples (with 250msec interval)"
        ::= { genEquipProtocolsEoamBwVsmEntry 4 }

genEquipProtocolsEoamBwVsmControlIfindex OBJECT-TYPE
        SYNTAX  INTEGER
		ACCESS  read-write
        STATUS 	mandatory
        DESCRIPTION
        "Control Interface of the eoam entity"
        ::= { genEquipProtocolsEoamBwVsmEntry 5 }

genEquipProtocolsEoamBwVsmId OBJECT-TYPE
        SYNTAX  INTEGER
        ACCESS  read-write
        STATUS 	mandatory
        DESCRIPTION
        "EOAM index."
        ::= { genEquipProtocolsEoamBwVsmEntry 6 }

genEquipProtocolsEoamBwVsmMonitoredIfindex OBJECT-TYPE
        SYNTAX  INTEGER
        ACCESS  read-write
        STATUS 	mandatory
        DESCRIPTION
        "Monitored Interface of the eoam entity"
        ::= { genEquipProtocolsEoamBwVsmEntry 7 }

genEquipProtocolsEoamBwVsmHoldoff OBJECT-TYPE
        SYNTAX  INTEGER
        ACCESS  read-write
        STATUS 	mandatory
        DESCRIPTION
        "The holdoff time in which, if BW below nominal, a message is sent"
        ::= { genEquipProtocolsEoamBwVsmEntry 8 }

genEquipProtocolsEoamBwVsmHoldoffStartTime OBJECT-TYPE
        SYNTAX  INTEGER
        ACCESS  read-only
        STATUS 	mandatory
        DESCRIPTION
        "The holdoff start counting time"
        ::= { genEquipProtocolsEoamBwVsmEntry 9 }

genEquipProtocolsEoamBwVsmHoldoffState OBJECT-TYPE
        SYNTAX  INTEGER
        ACCESS  read-only
        STATUS 	mandatory
        DESCRIPTION
        "The holdoff state of the EOAM entity"
        ::= { genEquipProtocolsEoamBwVsmEntry 10 }

genEquipProtocolsEoamBwVsmLastSentMsg OBJECT-TYPE
        SYNTAX  OCTET STRING
        ACCESS  read-only
        STATUS 	mandatory
        DESCRIPTION
        "The last EOAM message transmitted"
        ::= { genEquipProtocolsEoamBwVsmEntry 11 }

genEquipProtocolsEoamBwVsmMel OBJECT-TYPE
        SYNTAX  INTEGER
        ACCESS  read-write
        STATUS 	mandatory
        DESCRIPTION
        "The MEL to be set in the bw-vsm messages"
        ::= { genEquipProtocolsEoamBwVsmEntry 12 }

genEquipProtocolsEoamBwVsmMonitoringInterval OBJECT-TYPE
        SYNTAX  INTEGER
        ACCESS  read-write
        STATUS 	mandatory
        DESCRIPTION
        "The monitoring interval of the average BE calculation"
        ::= { genEquipProtocolsEoamBwVsmEntry 13 }

genEquipProtocolsEoamBwVsmNominalBw OBJECT-TYPE
        SYNTAX  INTEGER
        ACCESS  read-only
        STATUS 	mandatory
        DESCRIPTION
        "The nominal BW of the monitored interface, to be set in the bw-vsm messages"
        ::= { genEquipProtocolsEoamBwVsmEntry 14 }

genEquipProtocolsEoamBwVsmTxMsgCounter OBJECT-TYPE
        SYNTAX  INTEGER
        ACCESS  read-only
        STATUS 	mandatory
        DESCRIPTION
        "The number of transmitted messages"
        ::= { genEquipProtocolsEoamBwVsmEntry 15 }

genEquipProtocolsEoamBwVsmVersion OBJECT-TYPE
        SYNTAX  INTEGER
        ACCESS  read-only
        STATUS 	mandatory
        DESCRIPTION
        "EOAM version used"
        ::= { genEquipProtocolsEoamBwVsmEntry 16 }

genEquipProtocolsEoamBwVsmVlan OBJECT-TYPE
        SYNTAX  INTEGER
        ACCESS  read-write
        STATUS 	mandatory
        DESCRIPTION
        "The VLAN to be set in the bw-vsm messages"
        ::= { genEquipProtocolsEoamBwVsmEntry 17 }

genEquipProtocolsEoamBwVsmResetMsgCounter OBJECT-TYPE
        SYNTAX  OffOn
        ACCESS  read-write
        STATUS 	mandatory
        DESCRIPTION
        "Reset Messages Counter"
        ::= { genEquipProtocolsEoamBwVsmEntry 18 }

genEquipProtocolsEoamBwVsmRowStatus  		OBJECT-TYPE
		SYNTAX 		RowStatus
		ACCESS		read-write
        STATUS		mandatory
        DESCRIPTION
		"Table Mib Row Status."
::= { genEquipProtocolsEoamBwVsmEntry 30 }


genEquipProtocolsG8032Erpi	OBJECT IDENTIFIER ::= {genEquipProtocols 3}

--
-- G8032 ERPI attributes - g8032-erpi-attributes-table
--

genEquipProtocols8032DestMacAddress OBJECT-TYPE
        SYNTAX  OCTET STRING (SIZE(6))
        ACCESS  read-write
        STATUS 	mandatory
        DESCRIPTION
        "G8032 (Resiliency protocol) destination MAC address"
        ::= { genEquipProtocolsG8032Erpi 1 }

genEquipProtocolsG8032NodeId OBJECT-TYPE
        SYNTAX  OCTET STRING (SIZE(10))
        ACCESS  read-only
        STATUS 	mandatory
        DESCRIPTION
        "G.8032 Node ID"
        ::= { genEquipProtocolsG8032Erpi 2 }

--
--
genEquipProtocolsG8032ErpiAttributesTable  OBJECT-TYPE
        SYNTAX  SEQUENCE OF GenEquipProtocolsG8032ErpiAttributesEntry
        ACCESS  not-accessible
        STATUS mandatory
        DESCRIPTION
        "A table containing ERPI attributes."
        ::= { genEquipProtocolsG8032Erpi 10 }

genEquipProtocolsG8032ErpiAttributesEntry OBJECT-TYPE
        SYNTAX GenEquipProtocolsG8032ErpiAttributesEntry
        ACCESS  not-accessible
        STATUS mandatory
        DESCRIPTION
        "A table entry containing ERPI attributes."
        INDEX { genEquipProtocolsG8032ErpiAttributesErpiId }
        ::= { genEquipProtocolsG8032ErpiAttributesTable 1 }

GenEquipProtocolsG8032ErpiAttributesEntry ::=
	SEQUENCE {
		genEquipProtocolsG8032ErpiAttributesErpiId
			INTEGER,
		genEquipProtocolsG8032ErpiAttributesErpiName
			DisplayString,
		genEquipProtocolsG8032ErpiAttributesGuardTime
			INTEGER,
		genEquipProtocolsG8032ErpiAttributesHoldoffTime
			INTEGER,
		genEquipProtocolsG8032ErpiAttributesLastChangeTs
			INTEGER,
		genEquipProtocolsG8032ErpiAttributesLastHpRequest
			G8032LastState,
		genEquipProtocolsG8032ErpiAttributesLastLocalState
			G8032LastState,
		genEquipProtocolsG8032ErpiAttributesLastRemoteState
			G8032LastState,
		genEquipProtocolsG8032ErpiAttributesMegLevel
			INTEGER,
		genEquipProtocolsG8032ErpiAttributesDownMep
			INTEGER,
			genEquipProtocolsG8032ErpiAttributesRevertive
			IfMgrTrueFalse,
		genEquipProtocolsG8032ErpiAttributesRingState
			INTEGER,
		genEquipProtocolsG8032ErpiAttributesRplOwner
			INTEGER,
		genEquipProtocolsG8032ErpiAttributesSdHandling
			IfMgrTrueFalse,
		genEquipProtocolsG8032ErpiAttributesServiceId
			INTEGER,
		genEquipProtocolsG8032ErpiAttributesErpiType
			INTEGER,
		genEquipProtocolsG8032ErpiAttributesVersion
			INTEGER,
		genEquipProtocolsG8032ErpiAttributesVirtualChannel
			INTEGER,
		genEquipProtocolsG8032ErpiAttributesWtr
			INTEGER,
		genEquipProtocolsG8032ErpiAttributesRowStatus
			RowStatus
	}

genEquipProtocolsG8032ErpiAttributesErpiId OBJECT-TYPE
        SYNTAX  INTEGER
        ACCESS  read-only
        STATUS 	mandatory
        DESCRIPTION
        "ERPI ID"
        ::= { genEquipProtocolsG8032ErpiAttributesEntry 1 }

genEquipProtocolsG8032ErpiAttributesErpiName OBJECT-TYPE
        SYNTAX  DisplayString
        ACCESS  read-write
        STATUS 	mandatory
        DESCRIPTION
        "ERPI Name"
        ::= { genEquipProtocolsG8032ErpiAttributesEntry 2 }

genEquipProtocolsG8032ErpiAttributesGuardTime OBJECT-TYPE
        SYNTAX  INTEGER
        ACCESS  read-write
        STATUS 	mandatory
        DESCRIPTION
        "Indicates the ERPI Guard Time; units are msec, steps are 10msec."
        ::= { genEquipProtocolsG8032ErpiAttributesEntry 3 }

genEquipProtocolsG8032ErpiAttributesHoldoffTime OBJECT-TYPE
        SYNTAX  INTEGER
		ACCESS  read-write
        STATUS 	mandatory
        DESCRIPTION
        "The ERPI holdoff Time; units are msec, steps are 100msec.
		Controls the time from failure detection to responding to failure"
        ::= { genEquipProtocolsG8032ErpiAttributesEntry 4 }

genEquipProtocolsG8032ErpiAttributesLastChangeTs OBJECT-TYPE
        SYNTAX  INTEGER
		ACCESS  read-only
        STATUS 	mandatory
        DESCRIPTION
        "Denotes the Timestamp of the last ring state machine transition"
        ::= { genEquipProtocolsG8032ErpiAttributesEntry 5 }

genEquipProtocolsG8032ErpiAttributesLastHpRequest OBJECT-TYPE
        SYNTAX  G8032LastState
        ACCESS  read-only
        STATUS 	mandatory
        DESCRIPTION
        "Describes the last high-priority request."
        ::= { genEquipProtocolsG8032ErpiAttributesEntry 6 }

genEquipProtocolsG8032ErpiAttributesLastLocalState OBJECT-TYPE
        SYNTAX  G8032LastState
        ACCESS  read-only
        STATUS 	mandatory
        DESCRIPTION
        "Describes the current local state that is input to the ERPI state machine"
        ::= { genEquipProtocolsG8032ErpiAttributesEntry 7 }

genEquipProtocolsG8032ErpiAttributesLastRemoteState OBJECT-TYPE
        SYNTAX  G8032LastState
        ACCESS  read-only
        STATUS 	mandatory
        DESCRIPTION
        "Describes the last event received from the far end"
        ::= { genEquipProtocolsG8032ErpiAttributesEntry 8 }

genEquipProtocolsG8032ErpiAttributesMegLevel OBJECT-TYPE
        SYNTAX  INTEGER
        ACCESS  read-write
        STATUS 	mandatory
        DESCRIPTION
        "Indicates MEG LEVEL, when interoperating with SOAM"
        ::= { genEquipProtocolsG8032ErpiAttributesEntry 9 }

genEquipProtocolsG8032ErpiAttributesDownMep OBJECT-TYPE
        SYNTAX  INTEGER
        ACCESS  read-only
        STATUS 	mandatory
        DESCRIPTION
        "Indicates if the ERPI is related to a down MEP and if to which one"
        ::= { genEquipProtocolsG8032ErpiAttributesEntry 10 }

genEquipProtocolsG8032ErpiAttributesRevertive OBJECT-TYPE
        SYNTAX  IfMgrTrueFalse
        ACCESS  read-only
        STATUS 	mandatory
        DESCRIPTION
        "Indicates whether the ERPI is revertive"
        ::= { genEquipProtocolsG8032ErpiAttributesEntry 11 }

genEquipProtocolsG8032ErpiAttributesRingState OBJECT-TYPE
        SYNTAX  INTEGER
        ACCESS  read-only
        STATUS 	mandatory
        DESCRIPTION
        "Describes the state in which id ERPI is assumed.
		Possible states are: Initializing, Idle, Pending, Protecting, FS, MS)"
        ::= { genEquipProtocolsG8032ErpiAttributesEntry 12 }

genEquipProtocolsG8032ErpiAttributesRplOwner OBJECT-TYPE
        SYNTAX  INTEGER {
					none(0),
					west(1),
					east(2),
					sub-ring(3)
				}
        ACCESS  read-write
        STATUS 	mandatory
        DESCRIPTION
        "Indicates whether the ERPI is RPL owner and if such, which ERPI Port is the owner"
        ::= { genEquipProtocolsG8032ErpiAttributesEntry 13 }

genEquipProtocolsG8032ErpiAttributesSdHandling OBJECT-TYPE
        SYNTAX  IfMgrTrueFalse
        ACCESS  read-write
        STATUS 	mandatory
        DESCRIPTION
        "Indicates the ERPI takes into account SD (Signal Degraded) events (BER, capacity degradation)"
        ::= { genEquipProtocolsG8032ErpiAttributesEntry 14 }

genEquipProtocolsG8032ErpiAttributesServiceId OBJECT-TYPE
        SYNTAX  INTEGER
        ACCESS  read-write
        STATUS 	mandatory
        DESCRIPTION
        "Indicates Service ID of the ERPI"
        ::= { genEquipProtocolsG8032ErpiAttributesEntry 15 }

genEquipProtocolsG8032ErpiAttributesErpiType OBJECT-TYPE
        SYNTAX  INTEGER {
					ring(0),
					sub-ring(1),
					ring-with-sub-ring(2)
				}
        ACCESS  read-write
        STATUS 	mandatory
        DESCRIPTION
        "ERPI Type ( ring / sub-ring / ring with sub-ring port)"
        ::= { genEquipProtocolsG8032ErpiAttributesEntry 16 }

genEquipProtocolsG8032ErpiAttributesVersion OBJECT-TYPE
        SYNTAX  INTEGER
        ACCESS  read-write
        STATUS 	mandatory
        DESCRIPTION
        "Indicates the ERPI version number used in the ERPI protocol"
        ::= { genEquipProtocolsG8032ErpiAttributesEntry 17 }

genEquipProtocolsG8032ErpiAttributesVirtualChannel OBJECT-TYPE
        SYNTAX  INTEGER
        ACCESS  read-write
        STATUS 	mandatory
        DESCRIPTION
        "VLAN of virtual channel; 0 denotes no virtual channel"
        ::= { genEquipProtocolsG8032ErpiAttributesEntry 18 }

genEquipProtocolsG8032ErpiAttributesWtr OBJECT-TYPE
        SYNTAX  INTEGER
        ACCESS  read-write
        STATUS 	mandatory
        DESCRIPTION
        "Indicates the ERPI WTR; units are minutes"
        ::= { genEquipProtocolsG8032ErpiAttributesEntry 19 }

genEquipProtocolsG8032ErpiAttributesRowStatus 		OBJECT-TYPE
		SYNTAX 		RowStatus
		ACCESS		read-write
        STATUS		mandatory
        DESCRIPTION
		"Table Mib Row Status."
::= { genEquipProtocolsG8032ErpiAttributesEntry 30 }


--
-- G8032 ERP port attributes - g8032-erpi-port-attributes-table
--

genEquipProtocolsG8032ErpiPortAttributesTable  OBJECT-TYPE
        SYNTAX  SEQUENCE OF GenEquipProtocolsG8032ErpiPortAttributesEntry
        ACCESS  not-accessible
        STATUS mandatory
        DESCRIPTION
        "A table containing ERP port attributes."
        ::= { genEquipProtocolsG8032Erpi 11 }

genEquipProtocolsG8032ErpiPortAttributesEntry OBJECT-TYPE
        SYNTAX GenEquipProtocolsG8032ErpiPortAttributesEntry
        ACCESS  not-accessible
        STATUS mandatory
        DESCRIPTION
        "A table entry containing ERP port attributes."
        INDEX { genEquipProtocolsG8032ErpiPortAttributesErpiId,
				genEquipProtocolsG8032ErpiPortAttributesErpiIfindex}
        ::= { genEquipProtocolsG8032ErpiPortAttributesTable 1 }

GenEquipProtocolsG8032ErpiPortAttributesEntry ::=
	SEQUENCE {
		genEquipProtocolsG8032ErpiPortAttributesErpiId
			INTEGER,
		genEquipProtocolsG8032ErpiPortAttributesErpiIfindex
			INTEGER,
		genEquipProtocolsG8032ErpiPortAttributesActiveState
			IfMgrTrueFalse,
		genEquipProtocolsG8032ErpiPortAttributesDataFwdState
			IfMgrTrueFalse,
		genEquipProtocolsG8032ErpiPortAttributesDefectState
			INTEGER,
		genEquipProtocolsG8032ErpiPortAttributesRapsChannelFwdState
			IfMgrTrueFalse,
		genEquipProtocolsG8032ErpiPortAttributesRplLinkBlockState
			IfMgrTrueFalse,
		genEquipProtocolsG8032ErpiPortAttributesRxInvalidRapsFrames
			INTEGER,
		genEquipProtocolsG8032ErpiPortAttributesRxRapsEvents
			INTEGER,
		genEquipProtocolsG8032ErpiPortAttributesRxRapsFrames
			INTEGER,
		genEquipProtocolsG8032ErpiPortAttributesFs
			INTEGER,
		genEquipProtocolsG8032ErpiPortAttributesMs
			INTEGER,
		genEquipProtocolsG8032ErpiPortAttributesNr
			INTEGER,
		genEquipProtocolsG8032ErpiPortAttributesRb
			INTEGER,
		genEquipProtocolsG8032ErpiPortAttributesSd
			INTEGER,
		genEquipProtocolsG8032ErpiPortAttributesSf
			INTEGER,
		genEquipProtocolsG8032ErpiPortAttributesCapacityDegRatioThreshold
			INTEGER,
		genEquipProtocolsG8032ErpiPortAttributesSpId
			INTEGER,
		genEquipProtocolsG8032ErpiPortAttributesTxRapsCntrol
			IfMgrTrueFalse,
		genEquipProtocolsG8032ErpiPortAttributesTxRapsEvents
			INTEGER,
		genEquipProtocolsG8032ErpiPortAttributesTxRapsFrames
			INTEGER,
		genEquipProtocolsG8032ErpiPortAttributesTxRapsFs
			INTEGER,
		genEquipProtocolsG8032ErpiPortAttributesTxRapsMs
			INTEGER,
		genEquipProtocolsG8032ErpiPortAttributesTxRapsNr
			INTEGER,
		genEquipProtocolsG8032ErpiPortAttributesTxRapsRb
			INTEGER,
		genEquipProtocolsG8032ErpiPortAttributesTxRapsSd
			INTEGER,
		genEquipProtocolsG8032ErpiPortAttributesTxRapsSf
			INTEGER,
		genEquipProtocolsG8032ErpiPortAttributesClearCommand
			INTEGER,
		genEquipProtocolsG8032ErpiPortAttributesRowStatus
			RowStatus,
		genEquipProtocolsG8032ErpiPortAttributesFsCommand
			INTEGER,
		genEquipProtocolsG8032ErpiPortAttributesMsCommand
			INTEGER,
	}

genEquipProtocolsG8032ErpiPortAttributesErpiId OBJECT-TYPE
        SYNTAX  INTEGER
        ACCESS  read-only
        STATUS 	mandatory
        DESCRIPTION
        "Denotes the ERPI ID"
        ::= { genEquipProtocolsG8032ErpiPortAttributesEntry 1 }

genEquipProtocolsG8032ErpiPortAttributesErpiIfindex OBJECT-TYPE
        SYNTAX  INTEGER
        ACCESS  read-only
        STATUS 	mandatory
        DESCRIPTION
        "g8032_erp_port_sp_index"
        ::= { genEquipProtocolsG8032ErpiPortAttributesEntry 2 }

genEquipProtocolsG8032ErpiPortAttributesActiveState OBJECT-TYPE
        SYNTAX  IfMgrTrueFalse
        ACCESS  read-only
        STATUS 	mandatory
        DESCRIPTION
        "Denotes if G8032 port (SP) is active for traffic forwarding or not"
        ::= { genEquipProtocolsG8032ErpiPortAttributesEntry 3 }

genEquipProtocolsG8032ErpiPortAttributesDataFwdState OBJECT-TYPE
        SYNTAX  IfMgrTrueFalse
        ACCESS  read-only
        STATUS 	mandatory
        DESCRIPTION
        "Specifies whether the port is forwarding or blocking data"
        ::= { genEquipProtocolsG8032ErpiPortAttributesEntry 4 }

genEquipProtocolsG8032ErpiPortAttributesDefectState OBJECT-TYPE
        SYNTAX  INTEGER {
					no-defect(0),
					sd-defect(1),
					sf-defect(2)
				}
        ACCESS  read-only
        STATUS 	mandatory
        DESCRIPTION
        "Defines the ERPI Port Oper-state derived from port. It is updates when Oper-state is changed."
        ::= { genEquipProtocolsG8032ErpiPortAttributesEntry 5 }

genEquipProtocolsG8032ErpiPortAttributesRapsChannelFwdState OBJECT-TYPE
        SYNTAX  IfMgrTrueFalse
        ACCESS  read-only
        STATUS 	mandatory
        DESCRIPTION
        "Specifies whether the port is forwarding or blocking raps frames"
        ::= { genEquipProtocolsG8032ErpiPortAttributesEntry 6 }

genEquipProtocolsG8032ErpiPortAttributesRplLinkBlockState OBJECT-TYPE
        SYNTAX  IfMgrTrueFalse
        ACCESS  read-only
        STATUS 	mandatory
        DESCRIPTION
        "Specifies whether the RPL is in blocking state. relevant only for RPL owner"
        ::= { genEquipProtocolsG8032ErpiPortAttributesEntry 7 }

genEquipProtocolsG8032ErpiPortAttributesRxInvalidRapsFrames OBJECT-TYPE
        SYNTAX  INTEGER
        ACCESS  read-only
        STATUS 	mandatory
        DESCRIPTION
        "Number of invalid R-APS PDU received"
        ::= { genEquipProtocolsG8032ErpiPortAttributesEntry 8 }

genEquipProtocolsG8032ErpiPortAttributesRxRapsEvents OBJECT-TYPE
        SYNTAX  INTEGER
        ACCESS  read-only
        STATUS 	mandatory
        DESCRIPTION
        "Number of events R-APS PDU received"
        ::= { genEquipProtocolsG8032ErpiPortAttributesEntry 9 }

genEquipProtocolsG8032ErpiPortAttributesRxRapsFrames OBJECT-TYPE
        SYNTAX  INTEGER
        ACCESS  read-only
        STATUS 	mandatory
        DESCRIPTION
        "Number of R-APS PDU received"
        ::= { genEquipProtocolsG8032ErpiPortAttributesEntry 10 }

genEquipProtocolsG8032ErpiPortAttributesFs OBJECT-TYPE
        SYNTAX  INTEGER
        ACCESS  read-only
        STATUS 	mandatory
        DESCRIPTION
        "Number of FS PDU received"
        ::= { genEquipProtocolsG8032ErpiPortAttributesEntry 11 }

genEquipProtocolsG8032ErpiPortAttributesMs OBJECT-TYPE
        SYNTAX  INTEGER
        ACCESS  read-only
        STATUS 	mandatory
        DESCRIPTION
        "Number of MS PDU received"
        ::= { genEquipProtocolsG8032ErpiPortAttributesEntry 12 }

genEquipProtocolsG8032ErpiPortAttributesNr OBJECT-TYPE
        SYNTAX  INTEGER
        ACCESS  read-only
        STATUS 	mandatory
        DESCRIPTION
        "Number of NR R-APS PDU received"
        ::= { genEquipProtocolsG8032ErpiPortAttributesEntry 13 }

genEquipProtocolsG8032ErpiPortAttributesRb OBJECT-TYPE
        SYNTAX  INTEGER
        ACCESS  read-only
        STATUS 	mandatory
        DESCRIPTION
        "Number of RB R-APS PDU received"
        ::= { genEquipProtocolsG8032ErpiPortAttributesEntry 14 }

genEquipProtocolsG8032ErpiPortAttributesSd OBJECT-TYPE
        SYNTAX  INTEGER
        ACCESS  read-only
        STATUS 	mandatory
        DESCRIPTION
        "Number of SD R-APS PDU received"
        ::= { genEquipProtocolsG8032ErpiPortAttributesEntry 15 }

genEquipProtocolsG8032ErpiPortAttributesSf OBJECT-TYPE
        SYNTAX  INTEGER
        ACCESS  read-only
        STATUS 	mandatory
        DESCRIPTION
        "Number of SF R-APS PDU received"
        ::= { genEquipProtocolsG8032ErpiPortAttributesEntry 17 }

genEquipProtocolsG8032ErpiPortAttributesCapacityDegRatioThreshold OBJECT-TYPE
        SYNTAX  INTEGER
        ACCESS  read-only
        STATUS 	mandatory
        DESCRIPTION
        "The capacity degradation threshold, in percentage,
		from which SD is indicated from this ERPI Port"
        ::= { genEquipProtocolsG8032ErpiPortAttributesEntry 18 }

genEquipProtocolsG8032ErpiPortAttributesSpId OBJECT-TYPE
        SYNTAX  INTEGER
        ACCESS  read-write
        STATUS 	mandatory
        DESCRIPTION
        "Service Point ID"
        ::= { genEquipProtocolsG8032ErpiPortAttributesEntry 19 }

genEquipProtocolsG8032ErpiPortAttributesTxRapsCntrol OBJECT-TYPE
        SYNTAX  IfMgrTrueFalse
        ACCESS  read-only
        STATUS 	mandatory
        DESCRIPTION
        "When value is False, R-APS are not transmitted by ERPI Port"
        ::= { genEquipProtocolsG8032ErpiPortAttributesEntry 20 }

genEquipProtocolsG8032ErpiPortAttributesTxRapsEvents OBJECT-TYPE
        SYNTAX  INTEGER
        ACCESS  read-only
        STATUS 	mandatory
        DESCRIPTION
        "Number of events R-APS PDU transmitted"
        ::= { genEquipProtocolsG8032ErpiPortAttributesEntry 21 }

genEquipProtocolsG8032ErpiPortAttributesTxRapsFrames OBJECT-TYPE
        SYNTAX  INTEGER
        ACCESS  read-only
        STATUS 	mandatory
        DESCRIPTION
        "Number of Total R-APS PDU transmitted"
        ::= { genEquipProtocolsG8032ErpiPortAttributesEntry 22 }

genEquipProtocolsG8032ErpiPortAttributesTxRapsFs OBJECT-TYPE
        SYNTAX  INTEGER
        ACCESS  read-only
        STATUS 	mandatory
        DESCRIPTION
        "Number of FS R-APS PDU transmitted"
        ::= { genEquipProtocolsG8032ErpiPortAttributesEntry 23 }

genEquipProtocolsG8032ErpiPortAttributesTxRapsMs OBJECT-TYPE
        SYNTAX  INTEGER
        ACCESS  read-only
        STATUS 	mandatory
        DESCRIPTION
        "Number of MS R-APS PDU transmitted"
        ::= { genEquipProtocolsG8032ErpiPortAttributesEntry 24 }

genEquipProtocolsG8032ErpiPortAttributesTxRapsNr OBJECT-TYPE
        SYNTAX  INTEGER
        ACCESS  read-only
        STATUS 	mandatory
        DESCRIPTION
        "Number of NR R-APS PDU transmitted"
        ::= { genEquipProtocolsG8032ErpiPortAttributesEntry 25 }

genEquipProtocolsG8032ErpiPortAttributesTxRapsRb OBJECT-TYPE
        SYNTAX  INTEGER
        ACCESS  read-only
        STATUS 	mandatory
        DESCRIPTION
        "Number of RB R-APS PDU transmitted"
        ::= { genEquipProtocolsG8032ErpiPortAttributesEntry 26 }

genEquipProtocolsG8032ErpiPortAttributesTxRapsSd OBJECT-TYPE
        SYNTAX  INTEGER
        ACCESS  read-only
        STATUS 	mandatory
        DESCRIPTION
        "Number of SD R-APS PDU transmitted"
        ::= { genEquipProtocolsG8032ErpiPortAttributesEntry 27 }

genEquipProtocolsG8032ErpiPortAttributesTxRapsSf OBJECT-TYPE
        SYNTAX  INTEGER
        ACCESS  read-only
        STATUS 	mandatory
        DESCRIPTION
        "Number of SF R-APS PDU transmitted"
        ::= { genEquipProtocolsG8032ErpiPortAttributesEntry 28 }

genEquipProtocolsG8032ErpiPortAttributesClearCommand OBJECT-TYPE
        SYNTAX  INTEGER
        ACCESS  read-write
        STATUS 	mandatory
        DESCRIPTION
        "Clear Command"
        ::= { genEquipProtocolsG8032ErpiPortAttributesEntry 29 }

genEquipProtocolsG8032ErpiPortAttributesRowStatus OBJECT-TYPE
        SYNTAX  RowStatus
        ACCESS  read-write
        STATUS 	mandatory
        DESCRIPTION
        "Table Mib Row Status"
        ::= { genEquipProtocolsG8032ErpiPortAttributesEntry 30 }

genEquipProtocolsG8032ErpiPortAttributesFsCommand OBJECT-TYPE
        SYNTAX  INTEGER
        ACCESS  read-write
        STATUS 	mandatory
        DESCRIPTION
        "Force Switch (FS)"
        ::= { genEquipProtocolsG8032ErpiPortAttributesEntry 31 }

genEquipProtocolsG8032ErpiPortAttributesMsCommand OBJECT-TYPE
        SYNTAX  INTEGER
        ACCESS  read-write
        STATUS 	mandatory
        DESCRIPTION
        "Manual Switch (MS)"
        ::= { genEquipProtocolsG8032ErpiPortAttributesEntry 32 }

genEquipProtocolsSoam	OBJECT IDENTIFIER ::= {genEquipProtocols 4}

--
-- SOAM MEP Table - dot1ag-cfm-mep-table
--

genEquipProtocolsSoamMepTable  OBJECT-TYPE
        SYNTAX  SEQUENCE OF GenEquipProtocolsSoamMepEntry
        ACCESS  not-accessible
        STATUS mandatory
        DESCRIPTION
        "A table containg MEP attributes."
        ::= { genEquipProtocolsSoam 10 }

genEquipProtocolsSoamMepEntry OBJECT-TYPE
        SYNTAX GenEquipProtocolsSoamMepEntry
        ACCESS  not-accessible
        STATUS mandatory
        DESCRIPTION
        "A table entry containg MEP attributes."
        INDEX { genEquipProtocolsSoamMepMdIndex, genEquipProtocolsSoamMepMaIndex, genEquipProtocolsSoamMepMepIndentifier }
        ::= { genEquipProtocolsSoamMepTable 1 }

GenEquipProtocolsSoamMepEntry ::=
	SEQUENCE {
		genEquipProtocolsSoamMepMdIndex
			INTEGER,
		genEquipProtocolsSoamMepMaIndex
			INTEGER,
		genEquipProtocolsSoamMepMepIndentifier
			INTEGER,
		genEquipProtocolsSoamMepSpId
			INTEGER,
		genEquipProtocolsSoamMepLastSessionLbmOut
			INTEGER,
		genEquipProtocolsSoamMepLastSessionlbmToSend
			INTEGER,
		genEquipProtocolsSoamMepLastSessionLbrIn
			INTEGER,
		genEquipProtocolsSoamMepLastSessionlbState
			LBState,
		genEquipProtocolsSoamMepLbmOut
			INTEGER
	}

genEquipProtocolsSoamMepMdIndex OBJECT-TYPE
        SYNTAX  INTEGER
        ACCESS  read-only
        STATUS 	mandatory
        DESCRIPTION
        "MD Index"
        ::= { genEquipProtocolsSoamMepEntry 1 }

genEquipProtocolsSoamMepMaIndex OBJECT-TYPE
        SYNTAX  INTEGER
        ACCESS  read-only
        STATUS 	mandatory
        DESCRIPTION
        "MA/MEG Index"
        ::= { genEquipProtocolsSoamMepEntry 2 }

genEquipProtocolsSoamMepMepIndentifier OBJECT-TYPE
        SYNTAX  INTEGER
        ACCESS  read-only
        STATUS 	mandatory
        DESCRIPTION
        "MEP ID"
        ::= { genEquipProtocolsSoamMepEntry 3 }

genEquipProtocolsSoamMepSpId OBJECT-TYPE
        SYNTAX  INTEGER
        ACCESS  read-write
        STATUS 	mandatory
        DESCRIPTION
        "Service Point ID"
        ::= { genEquipProtocolsSoamMepEntry 4 }

genEquipProtocolsSoamMepLastSessionLbmOut OBJECT-TYPE
        SYNTAX  INTEGER
        ACCESS  read-only
        STATUS 	mandatory
        DESCRIPTION
        "Number of LBM frames transmitted during the current/last session"
        ::= { genEquipProtocolsSoamMepEntry 5 }

genEquipProtocolsSoamMepLastSessionlbmToSend OBJECT-TYPE
        SYNTAX  INTEGER
        ACCESS  read-only
        STATUS 	mandatory
        DESCRIPTION
        "Number of LBM frames left to send in the session"
        ::= { genEquipProtocolsSoamMepEntry 6 }

genEquipProtocolsSoamMepLastSessionLbrIn OBJECT-TYPE
        SYNTAX  INTEGER
        ACCESS  read-only
        STATUS 	mandatory
        DESCRIPTION
        "Number of LBR messages received during the current/last session"
        ::= { genEquipProtocolsSoamMepEntry 7 }

genEquipProtocolsSoamMepLastSessionlbState OBJECT-TYPE
        SYNTAX  LBState
        ACCESS  read-only
        STATUS 	mandatory
        DESCRIPTION
        "Specifies the loopback session State"
        ::= { genEquipProtocolsSoamMepEntry 8 }

genEquipProtocolsSoamMepLbmOut OBJECT-TYPE
        SYNTAX  INTEGER
        ACCESS  read-only
        STATUS 	mandatory
        DESCRIPTION
        "Specifies the mumber of the LBM frames transmitted"
        ::= { genEquipProtocolsSoamMepEntry 9 }

--
-- SOAM MA/MEG Network Table - dot1ag-cfm-ma-mef-net-table
--

genEquipProtocolsSoamMegTable  OBJECT-TYPE
        SYNTAX  SEQUENCE OF GenEquipProtocolsSoamMegEntry
        ACCESS  not-accessible
        STATUS mandatory
        DESCRIPTION
        "A table containing SOAM MA/MEG network identical attributes common to 802.1ag."
        ::= { genEquipProtocolsSoam 11 }

genEquipProtocolsSoamMegEntry OBJECT-TYPE
        SYNTAX GenEquipProtocolsSoamMegEntry
        ACCESS  not-accessible
        STATUS mandatory
        DESCRIPTION
        "A table entry containing SOAM MA/MEG network identical attributes common to 802.1ag."
        INDEX { genEquipProtocolsSoamMegMdIndex, genEquipProtocolsSoamMegMaIndex }
        ::= { genEquipProtocolsSoamMegTable 1 }

GenEquipProtocolsSoamMegEntry ::=
	SEQUENCE {
		genEquipProtocolsSoamMegMdIndex
			INTEGER,
		genEquipProtocolsSoamMegMaIndex
			INTEGER,
		genEquipProtocolsSoamMegServiceId
			INTEGER
	}

genEquipProtocolsSoamMegMdIndex OBJECT-TYPE
        SYNTAX  INTEGER
        ACCESS  read-only
        STATUS 	mandatory
        DESCRIPTION
        "MD Index"
        ::= { genEquipProtocolsSoamMegEntry 1 }

genEquipProtocolsSoamMegMaIndex OBJECT-TYPE
        SYNTAX  INTEGER
        ACCESS  read-only
        STATUS 	mandatory
        DESCRIPTION
        "MA/MEG Index"
        ::= { genEquipProtocolsSoamMegEntry 2 }

genEquipProtocolsSoamMegServiceId OBJECT-TYPE
        SYNTAX  INTEGER
        ACCESS  read-write
        STATUS 	mandatory
        DESCRIPTION
        "Service ID"
        ::= { genEquipProtocolsSoamMegEntry 3 }


-- TDM Trails
genEquipTdmTrails	OBJECT IDENTIFIER ::= {genEquipServices 2}

genEquipTdmTrailsTable  OBJECT-TYPE
        SYNTAX  SEQUENCE OF GenEquipTdmTrailsEntry
        ACCESS  not-accessible
        STATUS mandatory
        DESCRIPTION
        "TDM Trails configuration and status table."
        ::= { genEquipTdmTrails 1 }

genEquipTdmTrailsEntry OBJECT-TYPE
        SYNTAX GenEquipTdmTrailsEntry
        ACCESS not-accessible
        STATUS mandatory
          DESCRIPTION
          "TDM Trails PM table."
        INDEX { genEquipTdmTrailID }
        ::= { genEquipTdmTrailsTable 1 }

GenEquipTdmTrailsEntry ::=
		SEQUENCE {
			genEquipTdmTrailID
            	DisplayString,
			genEquipTdmTrailDescr
            	DisplayString,
			genEquipTdmTrailProtected
            	INTEGER,
			genEquipTdmTrailAcmPrio
            	INTEGER,
			genEquipTdmTrailOperStatus
            	INTEGER,
			genEquipTdmTrailAlarmStatus
            	INTEGER,
			genEquipTdmTrailSrcSlot
            	INTEGER,
			genEquipTdmTrailSrcType
            	TrailIfType,
			genEquipTdmTrailSrcNum
            	INTEGER,
			genEquipTdmTrailDest1Slot
            	INTEGER,
			genEquipTdmTrailDest1Type
            	TrailIfType,
			genEquipTdmTrailDest1Num
            	INTEGER,
			genEquipTdmTrailDest2Slot
            	INTEGER,
			genEquipTdmTrailDest2Type
            	TrailIfType,
			genEquipTdmTrailDest2Num
            	INTEGER,
			genEquipTdmTrailProtectedForceActive
            	TrailProtectedType,
			genEquipTdmTrailProtectedActiveTrail
            	TrailProtectedType,
			genEquipTdmTrailProtectedNumOfSwitches
            	INTEGER,
			genEquipTdmTrailPrimaryPathAlarmStatus
            	INTEGER,
			genEquipTdmTrailSecondaryPathAlarmStatus
            	INTEGER,
			genEquipTdmTrailRowStatus
            	RowStatus
}

genEquipTdmTrailID		OBJECT-TYPE
		SYNTAX 		DisplayString
		ACCESS		read-write
        STATUS		mandatory
        DESCRIPTION
		"The Trail ID. This parameter is the index of the table."
::= { genEquipTdmTrailsEntry 1 }

genEquipTdmTrailDescr		OBJECT-TYPE
		SYNTAX 		DisplayString
		ACCESS		read-write
        STATUS		mandatory
        DESCRIPTION
		"Trail description."
::= { genEquipTdmTrailsEntry 2 }

genEquipTdmTrailProtected		OBJECT-TYPE
		SYNTAX 		INTEGER {
						unProtected(0),
						protected(1),
						protectedAbr(2)
		}
		ACCESS		read-write
        STATUS		mandatory
        DESCRIPTION
		"This parameter indicates whether the trail is protected or not."
::= { genEquipTdmTrailsEntry 3 }

genEquipTdmTrailAcmPrio		OBJECT-TYPE
		SYNTAX 		INTEGER {
						low(0),
						high(1)
		}
		ACCESS		read-write
        STATUS		mandatory
        DESCRIPTION
		"The ACM priority of the trail. In case of High priority TDM trail, ACM is enabled on the link and there is a reduction
		of the link capacity, this trail will be prioritized before the low priority trails to be dropped."
::= { genEquipTdmTrailsEntry 4 }

genEquipTdmTrailOperStatus		OBJECT-TYPE
		SYNTAX 		INTEGER {
						reserved(0),
						operational(1)
		}
		ACCESS		read-write
        STATUS		mandatory
        DESCRIPTION
		"The status of the TDM trail. in operational case, the trail is active/enabled and send alarms."
::= { genEquipTdmTrailsEntry 5 }

genEquipTdmTrailAlarmStatus		OBJECT-TYPE
		SYNTAX 		INTEGER
		ACCESS		read-only
        STATUS		mandatory
        DESCRIPTION
		"The alarm status of the trail active path.
		The value is a Bit Map: Id-Mismatch(0x01),
		Excessive-Ber(0x02), Signal-Degrade-Ber(0x04),
		Invalid-Trail-Status(0x08), Signal-Failure(0x10), RDI-Detected(0x20)."
::= { genEquipTdmTrailsEntry 6 }

genEquipTdmTrailSrcSlot		OBJECT-TYPE
		SYNTAX 		INTEGER
		ACCESS		read-write
        STATUS		mandatory
        DESCRIPTION
		"Trail source slot number."
::= { genEquipTdmTrailsEntry 7 }

genEquipTdmTrailSrcType		OBJECT-TYPE
		SYNTAX 		TrailIfType
		ACCESS		read-write
        STATUS		mandatory
        DESCRIPTION
		"The type of the source interface of the trail line(0),	radio(1),stm-1-oc-3(2), sync(4)."
::= { genEquipTdmTrailsEntry 8 }

genEquipTdmTrailSrcNum		OBJECT-TYPE
		SYNTAX 		INTEGER
		ACCESS		read-write
        STATUS		mandatory
        DESCRIPTION
		"The interface number, for example E1 number 5. in case of a line."
::= { genEquipTdmTrailsEntry 9 }

genEquipTdmTrailDest1Slot		OBJECT-TYPE
		SYNTAX 		INTEGER
		ACCESS		read-write
        STATUS		mandatory
        DESCRIPTION
		"The slot destination of the trail."
::= { genEquipTdmTrailsEntry 10 }

genEquipTdmTrailDest1Type		OBJECT-TYPE
		SYNTAX 		TrailIfType
		ACCESS		read-write
        STATUS		mandatory
        DESCRIPTION
		"The interface type destination of the trail."
::= { genEquipTdmTrailsEntry 11 }

genEquipTdmTrailDest1Num		OBJECT-TYPE
		SYNTAX 		INTEGER
		ACCESS		read-write
        STATUS		mandatory
        DESCRIPTION
		"The destination interface number."
::= { genEquipTdmTrailsEntry 12 }

genEquipTdmTrailDest2Slot		OBJECT-TYPE
		SYNTAX 		INTEGER
		ACCESS		read-write
        STATUS		mandatory
        DESCRIPTION
		"A secondary slot number that is being used when protection is enabled. "
::= { genEquipTdmTrailsEntry 13 }

genEquipTdmTrailDest2Type		OBJECT-TYPE
		SYNTAX 		TrailIfType
		ACCESS		read-write
        STATUS		mandatory
        DESCRIPTION
		"A secondary interface type that is being used when protection is enabled."
::= { genEquipTdmTrailsEntry 14 }

genEquipTdmTrailDest2Num		OBJECT-TYPE
		SYNTAX 		INTEGER
		ACCESS		read-write
        STATUS		mandatory
        DESCRIPTION
		"A secondary interface number that is being used when protection is enabled."
::= { genEquipTdmTrailsEntry 15 }

genEquipTdmTrailProtectedForceActive		OBJECT-TYPE
		SYNTAX 		TrailProtectedType
		ACCESS		read-write
        STATUS		mandatory
        DESCRIPTION
		"Force active of the primary or the secondary trails."
::= { genEquipTdmTrailsEntry 16 }

genEquipTdmTrailProtectedActiveTrail		OBJECT-TYPE
		SYNTAX 		TrailProtectedType
		ACCESS		read-only
        STATUS		mandatory
        DESCRIPTION
		"The trail current active path. That tells us Who is the active trail."
::= { genEquipTdmTrailsEntry 17 }

genEquipTdmTrailProtectedNumOfSwitches		OBJECT-TYPE
		SYNTAX 		INTEGER
		ACCESS		read-only
        STATUS		mandatory
        DESCRIPTION
		"The value represent the number of switches in SNCP between the primary and secondary trails.
		Setting this value to 0, clears this counter"
::= { genEquipTdmTrailsEntry 18 }

genEquipTdmTrailPrimaryPathAlarmStatus		OBJECT-TYPE
		SYNTAX 		INTEGER
		ACCESS		read-only
        STATUS		mandatory
        DESCRIPTION
		"The alarm status of the trail primary path.
		The value is a Bit Map: Id-Mismatch(0x01),
		Excessive-Ber(0x02), Signal-Degrade-Ber(0x04),
		Invalid-Trail-Status(0x08), Signal-Failure(0x10), RDI-Detected(0x20)."
::= { genEquipTdmTrailsEntry 19 }

genEquipTdmTrailSecondaryPathAlarmStatus		OBJECT-TYPE
		SYNTAX 		INTEGER
		ACCESS		read-only
        STATUS		mandatory
        DESCRIPTION
		"The alarm status of the trail secondary path.
		The value is a Bit Map: Id-Mismatch(0x01),
		Excessive-Ber(0x02), Signal-Degrade-Ber(0x04),
		Invalid-Trail-Status(0x08), Signal-Failure(0x10), RDI-Detected(0x20)."
::= { genEquipTdmTrailsEntry 20 }

genEquipTdmTrailRowStatus		OBJECT-TYPE
		SYNTAX 		RowStatus
		ACCESS		read-write
        STATUS		mandatory
        DESCRIPTION
		"The Row status of the entry."
::= { genEquipTdmTrailsEntry 30 }

-- Protected trail force active all trails command
genEquipTdmTrailsProtectedForceActiveAllCmd		OBJECT-TYPE
		SYNTAX 		TrailProtectedType
		ACCESS		read-write
        STATUS		mandatory
        DESCRIPTION
		"Force all active trails to be either primary or secondary."
::= { genEquipTdmTrails 2 }

-- Protected trail force operational or reserved all trails command
genEquipTdmTrailsProtectedForceOperationalOrReservedCmd		OBJECT-TYPE
		SYNTAX 		INTEGER {
						reserved(0),
						operational(1),
						idle(30)
		}
		ACCESS		read-write
        STATUS		mandatory
        DESCRIPTION
		"Force all active trails to be either operational or reserved."
::= { genEquipTdmTrails 3 }

genEquipTdmTrailsProtectedRevertiveSwitchTimeout  OBJECT-TYPE
        SYNTAX INTEGER   (0..1800)
		ACCESS		read-write
        STATUS		mandatory
        DESCRIPTION
		"The revertive switch timeout in seconds for revertive protected trails."
::= { genEquipTdmTrails 4 }

genEquipTdmTrailsSwitchCounterClear  OBJECT-TYPE
        SYNTAX 		OffOn
		ACCESS		read-write
        STATUS		mandatory
        DESCRIPTION
		"This parameter will clear the counter for protected switches."
::= { genEquipTdmTrails 5 }

genEquipTdmTrailsDeleteAllTrails  OBJECT-TYPE
		SYNTAX          OffOn
		ACCESS          read-write
		STATUS          mandatory
        DESCRIPTION
        "This parameter will delete all existing trails."
::= { genEquipTdmTrails 6 }

genEquipTdmTrailsRangeVC 		OBJECT-TYPE
		SYNTAX 		INTEGER
		ACCESS		read-write
        STATUS		mandatory
        DESCRIPTION
		"TDM services VC range."
::= { genEquipTdmTrails 7 }

genEquipTdmTrailsOffsetVC 		OBJECT-TYPE
		SYNTAX 		INTEGER
		ACCESS		read-write
        STATUS		mandatory
        DESCRIPTION
		"TDM services VC offset."
::= { genEquipTdmTrails 8 }

genEquipTdmTrailsLatencyOptimizationAdmin 		OBJECT-TYPE
		SYNTAX 		EnableDisable
		ACCESS		read-write
        STATUS		mandatory
        DESCRIPTION
		"Enables/Disables the option of choosing a latency-optimized mode for TDM services."
::= { genEquipTdmTrails 9 }

-- Synchronization
genEquipSynchronization	OBJECT IDENTIFIER ::= {genEquipServices 3}

genEquipSynchronizationSrcTable  OBJECT-TYPE
        SYNTAX  SEQUENCE OF GenEquipSynchronizationSrcEntry
        ACCESS  not-accessible
        STATUS mandatory
        DESCRIPTION
        "Synchronization source table."
        ::= { genEquipSynchronization 1 }

genEquipSynchronizationSrcEntry OBJECT-TYPE
        SYNTAX GenEquipSynchronizationSrcEntry
        ACCESS not-accessible
        STATUS mandatory
          DESCRIPTION
          "Synchronization source table."
        INDEX { genEquipSynchronizationSrcPriority }
        ::= { genEquipSynchronizationSrcTable 1 }

GenEquipSynchronizationSrcEntry ::=
		SEQUENCE {
			genEquipSynchronizationSrcPriority
            	INTEGER,
			genEquipSynchronizationSrcSlot
            	INTEGER,
			genEquipSynchronizationSrcType
            	INTEGER,
			genEquipSynchronizationSrcNum
            	INTEGER,
			genEquipSynchronizationSrcValid
            	INTEGER,
			genEquipSynchronizationSrcTrail
            	EnableDisable,
			genEquipSynchronizationSrcAdmin
            	EnableDisable,
			genEquipSynchronizationSrcQuality
            	INTEGER,
			genEquipSynchronizationSrcReceivedSSM
            	INTEGER,
			genEquipSynchronizationSrcQualityStatus
            	INTEGER

}

genEquipSynchronizationSrcPriority		OBJECT-TYPE
		SYNTAX 		INTEGER (1..8)
		ACCESS		read-only
        STATUS		mandatory
        DESCRIPTION
		"The source for system synchronization (primary, seconday)."
::= { genEquipSynchronizationSrcEntry 1 }

genEquipSynchronizationSrcSlot		OBJECT-TYPE
		SYNTAX 		SlotId
		ACCESS		read-write
        STATUS		mandatory
        DESCRIPTION
		"The slot number of the sync source (1..6).
		Possible values:
		 - standalone(0)
		 - slot1(1)
		 - slot2(2)
		 - slot3(3)
		 - slot4(4)
		 - slot5(5)
		- slot6(6)"
::= { genEquipSynchronizationSrcEntry 2 }

genEquipSynchronizationSrcType		OBJECT-TYPE
		SYNTAX 		INTEGER {
			unknown(-1),
			line(0),
			radio-ch(1),
			stm-vc(2),
			pw(3),
			stm-signal(4),
			ether(5),
			pw-reference-clock(6)
		}
		ACCESS		read-write
        STATUS		mandatory
        DESCRIPTION
		"The interface type (line (PDH), Radio, STM-1/OC-3), or signal coming from the PW card."
::= { genEquipSynchronizationSrcEntry 3 }

genEquipSynchronizationSrcNum		OBJECT-TYPE
		SYNTAX 		INTEGER
		ACCESS		read-write
        STATUS		mandatory
        DESCRIPTION
		"The sync source number: VC in STM-1/OC-3, Radio channel in case the interface is Radio, or E1 number in
		case the interface is PDH (E1s)."
::= { genEquipSynchronizationSrcEntry 4 }

genEquipSynchronizationSrcValid		OBJECT-TYPE
		SYNTAX 		INTEGER {
						not-valid(0),
						valid(1)
		}
		ACCESS		read-only
        STATUS		mandatory
        DESCRIPTION
		"This paremter is the source status, if the source if valid or not.
		In case it is valid, it means that the clock being extracted from the source is ok and can be used.
		In case it is not-valid the source is not in use, each interface will have it's own clock."
::= { genEquipSynchronizationSrcEntry 5 }

genEquipSynchronizationSrcTrail		OBJECT-TYPE
		SYNTAX 		EnableDisable
		ACCESS		read-write
        STATUS		mandatory
        DESCRIPTION
		"This parameter indicates whether the synchronization source is the
		signal of an existing co-located TDM trail used for traffic.
		Enabling this parameter in an interface which does not belong to a trail will fail,
		as well as disabling it for an interface which belongs to a trail."
::= { genEquipSynchronizationSrcEntry 6 }

genEquipSynchronizationSrcAdmin		OBJECT-TYPE
		SYNTAX 		EnableDisable
		ACCESS		read-write
        STATUS		mandatory
        DESCRIPTION
		"Admin state of the sync source (the sync source is enabled or disabled)."
::= { genEquipSynchronizationSrcEntry 7 }

genEquipSynchronizationSrcQuality		OBJECT-TYPE
		SYNTAX 		INTEGER {
						automatic(0),
						prs(1),
						g811(2),
						transit-node(3),
						ssu-a(4),
						unknown(5),
						stratum2(7),
						ssu-b(8),
						stratum3(10),
						g813-8262(11),
						smc(12),
						stratum3e(13),
						do-not-use (15)
		}
		ACCESS		read-write
        STATUS		mandatory
        DESCRIPTION
		"parameter configures the quality of the incoming clock signal."
::= { genEquipSynchronizationSrcEntry 8 }

genEquipSynchronizationSrcReceivedSSM		OBJECT-TYPE
		SYNTAX 		INTEGER
		ACCESS		read-only
        STATUS		mandatory
        DESCRIPTION
		"This parameter shows the current value of the received SSM messages."
::= { genEquipSynchronizationSrcEntry 9 }

genEquipSynchronizationSrcQualityStatus		OBJECT-TYPE
		SYNTAX 		INTEGER {
						automatic(0),
						prs(1),
						g811(2),
						transit-node(3),
						ssu-a(4),
						unknown(5),
						stratum2(7),
						ssu-b(8),
						stratum3(10),
						g813-8262(11),
						smc(12),
						stratum3e(13),
						do-not-use(15),
						failure(16)
		}
		ACCESS		read-only
        STATUS		mandatory
        DESCRIPTION
		"This parameter shows the current quality level of the interface."
::= { genEquipSynchronizationSrcEntry 10 }

-- PW services configuration
genEquipServicesPW	OBJECT IDENTIFIER ::= {genEquipServices 4}

genEquipServicesPWBundlesTable  OBJECT-TYPE
        SYNTAX  SEQUENCE OF GenEquipServicesPWBundlesEntry
        ACCESS  not-accessible
        STATUS mandatory
        DESCRIPTION
        "This table allows configuration of DS0 bundles.
		Notice that the bundle description is not located in this table but in table genEquipServicesPWBundlesDescriptionTable."
        ::= { genEquipServicesPW 1 }

genEquipServicesPWBundlesEntry OBJECT-TYPE
        SYNTAX GenEquipServicesPWBundlesEntry
        ACCESS not-accessible
        STATUS mandatory
		DESCRIPTION
		"This table allows configuration of DS0 bundles.
		Notice that the bundle description is not located in this table but in table genEquipServicesPWBundlesDescriptionTable."
        INDEX { genEquipServicesPWBundlesDs0List, genEquipServicesPWBundlesBundleId }
        ::= { genEquipServicesPWBundlesTable 1 }

GenEquipServicesPWBundlesEntry ::=
		SEQUENCE {
			genEquipServicesPWBundlesBundleId
				INTEGER,
			genEquipServicesPWBundlesDs0List
                INTEGER,
			genEquipServicesPWBundlesRowStatus
				RowStatus
}

genEquipServicesPWBundlesBundleId		OBJECT-TYPE
		SYNTAX 		INTEGER (1..496)
		ACCESS		read-write
        STATUS		mandatory
        DESCRIPTION
		"Unique DS0 bundle ID."
::= { genEquipServicesPWBundlesEntry 1 }

genEquipServicesPWBundlesDs0List		OBJECT-TYPE
		SYNTAX 		INTEGER
		ACCESS		read-write
        STATUS		mandatory
        DESCRIPTION
		"DS0 slot number belonging to a bundle."

::= { genEquipServicesPWBundlesEntry 2 }

genEquipServicesPWBundlesRowStatus		OBJECT-TYPE
		SYNTAX 		RowStatus
		ACCESS		read-write
        STATUS		mandatory
        DESCRIPTION
		"This value is the status of the entry."
::= { genEquipServicesPWBundlesEntry 30 }

-- genEquipServicesPWBundlesDescriptionTable
genEquipServicesPWBundlesDescriptionTable  OBJECT-TYPE
        SYNTAX  SEQUENCE OF GenEquipServicesPWBundlesDescriptionEntry
        ACCESS  not-accessible
        STATUS mandatory
        DESCRIPTION
        "This table allows configuration of DS0 bundles description.
		Notice that the bundle configuration itself is not located in this table but in table genEquipServicesPWBundlesTable."
        ::= { genEquipServicesPW 2 }

genEquipServicesPWBundlesDescriptionEntry OBJECT-TYPE
        SYNTAX GenEquipServicesPWBundlesDescriptionEntry
        ACCESS not-accessible
        STATUS mandatory
		DESCRIPTION
        "This table allows configuration of DS0 bundles description.
		Notice that the bundle configuration itself is not located in this table but in table genEquipServicesPWBundlesTable."
        INDEX { genEquipServicesPWBundlesDescriptionBundleId }
        ::= { genEquipServicesPWBundlesDescriptionTable 1 }

GenEquipServicesPWBundlesDescriptionEntry ::=
		SEQUENCE {
			genEquipServicesPWBundlesDescriptionBundleId
				INTEGER,
			genEquipServicesPWBundlesDescriptionBundleDesc
            	DisplayString,
            genEquipServicesPWBundlesDescriptionBundleAdmin
				EnableDisable,
			genEquipServicesPWBundlesDescriptionBundleOperStatus
				INTEGER,
			genEquipServicesPWBundlesDescriptionBundleTdmPort
            	INTEGER,
			genEquipServicesPWBundlesDescriptionRowStatus
				RowStatus
}

genEquipServicesPWBundlesDescriptionBundleId		OBJECT-TYPE
		SYNTAX 		INTEGER (1..496)
		ACCESS		read-write
        STATUS		mandatory
        DESCRIPTION
		"Unique DS0 bundle ID."
::= { genEquipServicesPWBundlesDescriptionEntry 1 }

genEquipServicesPWBundlesDescriptionBundleDesc		OBJECT-TYPE
		SYNTAX 		DisplayString
		ACCESS		read-write
        STATUS		mandatory
        DESCRIPTION
		"DS0 bundle description."
::= { genEquipServicesPWBundlesDescriptionEntry 2 }

genEquipServicesPWBundlesDescriptionBundleAdmin		OBJECT-TYPE
		SYNTAX 		EnableDisable
		ACCESS		read-write
        STATUS		mandatory
        DESCRIPTION
		"Admin."
::= { genEquipServicesPWBundlesDescriptionEntry 3 }

genEquipServicesPWBundlesDescriptionBundleOperStatus		OBJECT-TYPE
		SYNTAX 		INTEGER  {
						up(1),
						down(2)
		}
		ACCESS		read-only
        STATUS		mandatory
        DESCRIPTION
		"Operational status."
::= { genEquipServicesPWBundlesDescriptionEntry 4 }

genEquipServicesPWBundlesDescriptionBundleTdmPort		OBJECT-TYPE
		SYNTAX 		INTEGER (1..16)
		ACCESS		read-write
        STATUS		mandatory
        DESCRIPTION
		"TDM port from which the channels are assigned to the bundle."
::= { genEquipServicesPWBundlesDescriptionEntry 5 }

genEquipServicesPWBundlesDescriptionRowStatus		OBJECT-TYPE
		SYNTAX 		RowStatus
		ACCESS		read-write
        STATUS		mandatory
        DESCRIPTION
		"This value is the status of the entry."
::= { genEquipServicesPWBundlesDescriptionEntry 30 }

-- PW PSN tunnels Table
genEquipServicesPWPSNTunnelsTable  OBJECT-TYPE
        SYNTAX  SEQUENCE OF GenEquipServicesPWPSNTunnelsEntry
        ACCESS  not-accessible
        STATUS mandatory
        DESCRIPTION
        "This table allows configuration of PSN encapsulations meant for pseudowire services."
        ::= { genEquipServicesPW 3 }

genEquipServicesPWPSNTunnelsEntry OBJECT-TYPE
        SYNTAX GenEquipServicesPWPSNTunnelsEntry
        ACCESS not-accessible
        STATUS mandatory
		DESCRIPTION
		"This table allows configuration of PSN encapsulations meant for pseudowire services."
        INDEX { genEquipServicesPWPSNTunnelsSlotNumber, genEquipServicesPWPSNTunnelsTunnelId }
        ::= { genEquipServicesPWPSNTunnelsTable 1 }

GenEquipServicesPWPSNTunnelsEntry ::=
		SEQUENCE {
			genEquipServicesPWPSNTunnelsSlotNumber
				INTEGER,
			genEquipServicesPWPSNTunnelsTunnelId
            	INTEGER,
			genEquipServicesPWPSNTunnelsPsnType
                INTEGER,
			genEquipServicesPWPSNTunnelsSVid
				INTEGER,
			genEquipServicesPWPSNTunnelsCVid
				EnableDisable,
			genEquipServicesPWPSNTunnelsPBits
				INTEGER,
			genEquipServicesPWPSNTunnelsDestIpAddr
				IpAddress,
			genEquipServicesPWPSNTunnelsDestIpSubnet
				IpAddress,
			genEquipServicesPWPSNTunnelsNextHopIp
				IpAddress,
			genEquipServicesPWPSNTunnelsTosDscp
				INTEGER,
			genEquipServicesPWPSNTunnelsRemoteMacAddr
				OCTET STRING,
			genEquipServicesPWPSNTunnelsSourceIpAddr
				IpAddress,
			genEquipServicesPWPSNTunnelsSourceMacAddr
				OCTET STRING,
-- New part
			genEquipServicesPWPSNTunnelsStatus
				DownUp,
			genEquipServicesPWPSNTunnelsSourceMPLSLabel
				INTEGER,
			genEquipServicesPWPSNTunnelsDestinationMPLSLabel
				INTEGER,
			genEquipServicesPWPSNTunnelsMPLSexp
				INTEGER,
			genEquipServicesPWPSNTunnelsVlanType
				PWTunnelVlanType,
			genEquipServicesPWPSNTunnelsVid
				INTEGER,
			genEquipServicesPWPSNTunnelsMAid
				INTEGER,

			genEquipServicesPWPSNTunnelsRowStatus
				RowStatus
}

genEquipServicesPWPSNTunnelsSlotNumber		OBJECT-TYPE
		SYNTAX 		INTEGER (2..12)
		ACCESS		read-write
        STATUS		mandatory
        DESCRIPTION
		"Slot number where the relevant PW card is inserted."
::= { genEquipServicesPWPSNTunnelsEntry 1 }

genEquipServicesPWPSNTunnelsTunnelId		OBJECT-TYPE
		SYNTAX 		INTEGER (1..512)
		ACCESS		read-write
        STATUS		mandatory
        DESCRIPTION
		"PSN tunnel ID."
::= { genEquipServicesPWPSNTunnelsEntry 2 }

genEquipServicesPWPSNTunnelsPsnType		OBJECT-TYPE
		SYNTAX 		INTEGER {
						udpip(0),
						ethernet(1)
		}
		ACCESS		read-write
        STATUS		mandatory
        DESCRIPTION
		"Psn type supported by this tunnel."

::= { genEquipServicesPWPSNTunnelsEntry 3 }

genEquipServicesPWPSNTunnelsSVid		OBJECT-TYPE
		SYNTAX 		INTEGER (0..4091)
		ACCESS		read-write
        STATUS		mandatory
        DESCRIPTION
		"PSN Tunnel S-VLAN Id."
::= { genEquipServicesPWPSNTunnelsEntry 4 }

genEquipServicesPWPSNTunnelsCVid		OBJECT-TYPE
		SYNTAX 		INTEGER (0..4091)
		ACCESS		read-write
        STATUS		mandatory
        DESCRIPTION
		"PSN Tunnel C-VLAN Id."
::= { genEquipServicesPWPSNTunnelsEntry 5 }

genEquipServicesPWPSNTunnelsPBits		OBJECT-TYPE
		SYNTAX 		INTEGER  (0..7)
		ACCESS		read-write
        STATUS		mandatory
        DESCRIPTION
		"PSN Tunnel P-bits."
::= { genEquipServicesPWPSNTunnelsEntry 6 }

genEquipServicesPWPSNTunnelsDestIpAddr		OBJECT-TYPE
		SYNTAX 		IpAddress
		ACCESS		read-write
        STATUS		mandatory
        DESCRIPTION
		"Destination IP Address for UDP/IP PSN tunnel."
::= { genEquipServicesPWPSNTunnelsEntry 7 }

genEquipServicesPWPSNTunnelsDestIpSubnet		OBJECT-TYPE
		SYNTAX 		IpAddress
		ACCESS		read-write
        STATUS		mandatory
        DESCRIPTION
		"Destination IP Subnet for UDP/IP PSN tunnel."
::= { genEquipServicesPWPSNTunnelsEntry 8 }

genEquipServicesPWPSNTunnelsNextHopIp		OBJECT-TYPE
		SYNTAX 		IpAddress
		ACCESS		read-write
        STATUS		mandatory
        DESCRIPTION
		"Next hop IP Address for UDP/IP PSN tunnel."
::= { genEquipServicesPWPSNTunnelsEntry 9 }

genEquipServicesPWPSNTunnelsTosDscp		OBJECT-TYPE
		SYNTAX 		INTEGER  (0..63)
		ACCESS		read-write
        STATUS		mandatory
        DESCRIPTION
		"PSN Tunnel ToS (DSCP)."
::= { genEquipServicesPWPSNTunnelsEntry 10 }

genEquipServicesPWPSNTunnelsRemoteMacAddr		OBJECT-TYPE
		SYNTAX 		OCTET STRING
		ACCESS		read-write
        STATUS		mandatory
        DESCRIPTION
		"Remote MAC Adress."
::= { genEquipServicesPWPSNTunnelsEntry 11 }

genEquipServicesPWPSNTunnelsSourceIpAddr		OBJECT-TYPE
		SYNTAX 		IpAddress
		ACCESS		read-write
        STATUS		mandatory
        DESCRIPTION
		"Source IP Address."
::= { genEquipServicesPWPSNTunnelsEntry 12 }

genEquipServicesPWPSNTunnelsSourceMacAddr		OBJECT-TYPE
		SYNTAX 		OCTET STRING
		ACCESS		read-write
        STATUS		mandatory
        DESCRIPTION
		"Source MAC Address."
::= { genEquipServicesPWPSNTunnelsEntry 13 }

genEquipServicesPWPSNTunnelsStatus		OBJECT-TYPE
		SYNTAX 		DownUp
		ACCESS		read-write
        STATUS		mandatory
        DESCRIPTION
		"PSN tunnel admin."
::= { genEquipServicesPWPSNTunnelsEntry 14 }

genEquipServicesPWPSNTunnelsSourceMPLSLabel		OBJECT-TYPE
		SYNTAX 		INTEGER  (16..1048575)
		ACCESS		read-write
        STATUS		mandatory
        DESCRIPTION
		"Source MPLS Label."
::= { genEquipServicesPWPSNTunnelsEntry 15 }

genEquipServicesPWPSNTunnelsDestinationMPLSLabel		OBJECT-TYPE
		SYNTAX 		INTEGER  (16..1048575)
		ACCESS		read-write
        STATUS		mandatory
        DESCRIPTION
		"Destination MPLS label."
::= { genEquipServicesPWPSNTunnelsEntry 16 }

genEquipServicesPWPSNTunnelsMPLSexp		OBJECT-TYPE
		SYNTAX 		INTEGER  (0..7)
		ACCESS		read-write
        STATUS		mandatory
        DESCRIPTION
		"MPLS Experimental field."
::= { genEquipServicesPWPSNTunnelsEntry 17 }

genEquipServicesPWPSNTunnelsVlanType		OBJECT-TYPE
		SYNTAX 		PWTunnelVlanType
		ACCESS		read-write
        STATUS		mandatory
        DESCRIPTION
		"VLAN type supported by this PSN tunnel (S-VLAN or C-VLAN)."
::= { genEquipServicesPWPSNTunnelsEntry 18 }

genEquipServicesPWPSNTunnelsVid		OBJECT-TYPE
		SYNTAX 		INTEGER  (0..4094)
		ACCESS		read-write
        STATUS		mandatory
        DESCRIPTION
		"PSN Tunnel VLAN ID."
::= { genEquipServicesPWPSNTunnelsEntry 19 }

genEquipServicesPWPSNTunnelsMAid		OBJECT-TYPE
		SYNTAX 		INTEGER  (0..128)
		ACCESS		read-write
        STATUS		mandatory
        DESCRIPTION
		"Maintenance Association Id."
::= { genEquipServicesPWPSNTunnelsEntry 20 }


genEquipServicesPWPSNTunnelsRowStatus		OBJECT-TYPE
		SYNTAX 		RowStatus
		ACCESS		read-write
        STATUS		mandatory
        DESCRIPTION
		"This value is the status of the entry."
::= { genEquipServicesPWPSNTunnelsEntry 30 }

-- PW Profiles Configuration Table
genEquipServicesPWProfilesTable  OBJECT-TYPE
        SYNTAX  SEQUENCE OF GenEquipServicesPWProfilesEntry
        ACCESS  not-accessible
        STATUS mandatory
        DESCRIPTION
        "This table allows configuration of pseudowire profiles.
		These profiles are used when configuring PW services in table genEquipServicesPWServiceTable."
        ::= { genEquipServicesPW 4 }

genEquipServicesPWProfilesEntry OBJECT-TYPE
        SYNTAX GenEquipServicesPWProfilesEntry
        ACCESS not-accessible
        STATUS mandatory
		DESCRIPTION
        "This table allows configuration of pseudowire profiles.
		These profiles are used when configuring PW services in table genEquipServicesPWServiceTable."
        INDEX { genEquipServicesPWProfilesPWProfileId }
        ::= { genEquipServicesPWProfilesTable 1 }

GenEquipServicesPWProfilesEntry ::=
		SEQUENCE {
			genEquipServicesPWProfilesPWProfileId
				INTEGER,
			genEquipServicesPWProfilesPayloadSize
            	INTEGER,
			genEquipServicesPWProfilesJitterBufferDepth
                INTEGER,
			genEquipServicesPWProfilesLopsDetection
				EnableDisable,
			genEquipServicesPWProfilesRtpHeaderUsed
				NoYes,
			genEquipServicesPWProfilesRtpTimestampMode
				PWRtpTimeStampMode,
			genEquipServicesPWProfilesRtpTimestampAbsFactor
				INTEGER,
			genEquipServicesPWProfilesPayloadSuppression
				EnableDisable,
			genEquipServicesPWProfilesPayloadType
				INTEGER,
			genEquipServicesPWProfilesConseqPacketsInSync
				INTEGER,
			genEquipServicesPWProfilesConseqMissPktsOutSync
				INTEGER,
			genEquipServicesPWProfilesPktLossTimeWindow
				INTEGER,
			genEquipServicesPWProfilesExcessivePktLossThresh
				INTEGER,
			genEquipServicesPWProfilesAlarmThresh
				INTEGER,
			genEquipServicesPWProfilesClearAlarmThresh
				INTEGER,
			genEquipServicesPWProfilesMissingPktsToSes
				INTEGER,
			genEquipServicesPWProfilesDs0Filler
				INTEGER,
			genEquipServicesPWProfilesCasAlarmPattern
				INTEGER,
			genEquipServicesPWProfilesRowStatus
				RowStatus
}

genEquipServicesPWProfilesPWProfileId		OBJECT-TYPE
		SYNTAX 		INTEGER (1..64)
		ACCESS		read-only
        STATUS		mandatory
        DESCRIPTION
		"Unique PW  profile ID."
::= { genEquipServicesPWProfilesEntry 1 }

genEquipServicesPWProfilesPayloadSize		OBJECT-TYPE
		SYNTAX 		INTEGER (0..1500)
		ACCESS		read-write
        STATUS		mandatory
        DESCRIPTION
		"Payload size in bytes."
::= { genEquipServicesPWProfilesEntry 2 }

genEquipServicesPWProfilesJitterBufferDepth		OBJECT-TYPE
		SYNTAX 		INTEGER (1..32)
		ACCESS		read-write
        STATUS		mandatory
        DESCRIPTION
		"Jitter buffer depth (in milliseconds) to allow accommodation to the PSN-specific packet delay variation"
::= { genEquipServicesPWProfilesEntry 3 }

genEquipServicesPWProfilesLopsDetection		OBJECT-TYPE
		SYNTAX 		EnableDisable
		ACCESS		read-write
        STATUS		mandatory
        DESCRIPTION
		"If enabled, LOPS detection is supported."
::= { genEquipServicesPWProfilesEntry 4 }

genEquipServicesPWProfilesRtpHeaderUsed		OBJECT-TYPE
		SYNTAX 		NoYes
		ACCESS		read-write
        STATUS		mandatory
        DESCRIPTION
		"If set to False: an RTP header is not pre-pended to the TDM packet."
::= { genEquipServicesPWProfilesEntry 5 }

genEquipServicesPWProfilesRtpTimestampMode		OBJECT-TYPE
		SYNTAX 		PWRtpTimeStampMode
		ACCESS		read-write
        STATUS		mandatory
        DESCRIPTION
		"RTP timestamp mode"
::= { genEquipServicesPWProfilesEntry 6 }

genEquipServicesPWProfilesRtpTimestampAbsFactor		OBJECT-TYPE
		SYNTAX 		INTEGER (1..65535)
		ACCESS		read-write
        STATUS		mandatory
        DESCRIPTION
		"Multiplication factor for 8KHz units in absolute mode of RTP timestamping."
::= { genEquipServicesPWProfilesEntry 7 }

genEquipServicesPWProfilesPayloadSuppression		OBJECT-TYPE
		SYNTAX 		EnableDisable
		ACCESS		read-write
        STATUS		mandatory
        DESCRIPTION
		"Payload suppression."
::= { genEquipServicesPWProfilesEntry 8 }

genEquipServicesPWProfilesPayloadType		OBJECT-TYPE
		SYNTAX 		INTEGER (1..123)
		ACCESS		read-write
        STATUS		mandatory
        DESCRIPTION
		"Payload type."
::= { genEquipServicesPWProfilesEntry 9 }

genEquipServicesPWProfilesConseqPacketsInSync		OBJECT-TYPE
		SYNTAX 		INTEGER  (1..10)
		ACCESS		read-write
        STATUS		mandatory
        DESCRIPTION
		"Number of consecutive packets with sequential sequence numbers  required to exit LOPS."
::= { genEquipServicesPWProfilesEntry 10 }

genEquipServicesPWProfilesConseqMissPktsOutSync		OBJECT-TYPE
		SYNTAX 		INTEGER (1..15)
		ACCESS		read-write
        STATUS		mandatory
        DESCRIPTION
		"Number of consecutive missing packets required to enter LOPS."
::= { genEquipServicesPWProfilesEntry 11 }

genEquipServicesPWProfilesPktLossTimeWindow		OBJECT-TYPE
		SYNTAX 		INTEGER (1..65535)
		ACCESS		read-write
        STATUS		mandatory
        DESCRIPTION
		"Time for computing average packet loss rate to detect excessive packet loss."
::= { genEquipServicesPWProfilesEntry 12 }

genEquipServicesPWProfilesExcessivePktLossThresh		OBJECT-TYPE
		SYNTAX 		INTEGER (0..100)
		ACCESS		read-write
        STATUS		mandatory
        DESCRIPTION
		"Alarm threshold (in percent) for excessive packet loss."
::= { genEquipServicesPWProfilesEntry 13 }

genEquipServicesPWProfilesAlarmThresh		OBJECT-TYPE
		SYNTAX 		INTEGER (1..65535)
		ACCESS		read-write
        STATUS		mandatory
        DESCRIPTION
		"Delay (in msecs) for persistent alarm setting."
::= { genEquipServicesPWProfilesEntry 14 }

genEquipServicesPWProfilesClearAlarmThresh		OBJECT-TYPE
		SYNTAX 		INTEGER (1..65535)
		ACCESS		read-write
        STATUS		mandatory
        DESCRIPTION
		"Delay (in msecs) for persistent alarm clearing."
::= { genEquipServicesPWProfilesEntry 15 }

genEquipServicesPWProfilesMissingPktsToSes		OBJECT-TYPE
		SYNTAX 		INTEGER (1..100)
		ACCESS		read-write
        STATUS		mandatory
        DESCRIPTION
		"Percent of missing packets detected in 1 second window to cause SES to be counted."
::= { genEquipServicesPWProfilesEntry 16 }

genEquipServicesPWProfilesDs0Filler		OBJECT-TYPE
		SYNTAX 		INTEGER (0..255)
		ACCESS		read-write
        STATUS		mandatory
        DESCRIPTION
		"Byte pattern transmitted on ds0 channels when packets over/underflow the jitter buffer."
::= { genEquipServicesPWProfilesEntry 17 }

genEquipServicesPWProfilesCasAlarmPattern		OBJECT-TYPE
		SYNTAX 		INTEGER (0..15)
		ACCESS		read-write
        STATUS		mandatory
        DESCRIPTION
		"CAS alarm pattern transmitted on E1 interface when packets over/underflow the jitter buffer."
::= { genEquipServicesPWProfilesEntry 18 }

genEquipServicesPWProfilesRowStatus		OBJECT-TYPE
		SYNTAX 		RowStatus
		ACCESS		read-write
        STATUS		mandatory
        DESCRIPTION
		"This value is the status of the entry."
::= { genEquipServicesPWProfilesEntry 30 }


-- PW Service Configuration Table
genEquipServicesPWServiceTable  OBJECT-TYPE
        SYNTAX  SEQUENCE OF GenEquipServicesPWServiceEntry
        ACCESS  not-accessible
        STATUS mandatory
        DESCRIPTION
        "This table allows configuration of pseudowire services, by assigning TDM ports or bundles, PSN tunnels,
		and profiles to a service."
        ::= { genEquipServicesPW 5 }

genEquipServicesPWServiceEntry OBJECT-TYPE
        SYNTAX GenEquipServicesPWServiceEntry
        ACCESS not-accessible
        STATUS mandatory
		DESCRIPTION
        "This table allows configuration of pseudowire services, by assigning TDM ports or bundles, PSN tunnels,
		and profiles to a service."
        INDEX { genEquipServicesPWServicePWId }
        ::= { genEquipServicesPWServiceTable 1 }

GenEquipServicesPWServiceEntry ::=
		SEQUENCE {
			genEquipServicesPWServicePWId
				INTEGER,
			genEquipServicesPWServicePWType
            	INTEGER,
			genEquipServicesPWServicePsnType
                INTEGER,
			genEquipServicesPWServiceTdmPort
				INTEGER,
			genEquipServicesPWServiceDs0bundle
				INTEGER,
			genEquipServicesPWServiceTdmProfileId
				INTEGER,
			genEquipServicesPWServicePsnTunnelProtection
				EnableDisable,
			genEquipServicesPWServicePsnTunnelOrGroupId
				INTEGER,
			genEquipServicesPWServiceSrcUdpPortOrEcid
				INTEGER,
			genEquipServicesPWServiceDstUdpPortOrEcid
				INTEGER,
			genEquipServicesPWServiceAdmin
				EnableDisable,
			genEquipServicesPWServiceCrReference
				EnableDisable,
			genEquipServicesPWServiceOperStatus
				EnableDisable,
			genEquipServicesPWServiceRowStatus
				RowStatus
}

genEquipServicesPWServicePWId		OBJECT-TYPE
		SYNTAX 		INTEGER (1..256)
		ACCESS		read-write
        STATUS		mandatory
        DESCRIPTION
		"Pseudo Wire ID."
::= { genEquipServicesPWServiceEntry 1 }

genEquipServicesPWServicePWType		OBJECT-TYPE
		SYNTAX 		INTEGER {
						e1-satop(0),
						cespsn(1),
						cas-cespsn(2)
		}
		ACCESS		read-write
        STATUS		mandatory
        DESCRIPTION
		"PW type.  E1-satop denotes SAToP. Cespsn Denotes CESoP without CAS signalling,
		and  cas-cespsn denotes CESoP with CAS signalling."
::= { genEquipServicesPWServiceEntry 2 }

genEquipServicesPWServicePsnType		OBJECT-TYPE
		SYNTAX 		INTEGER {
						udpip(0),
						eth(1)
		}
		ACCESS		read-write
        STATUS		mandatory
        DESCRIPTION
		"PSN tunnel type. UDPIP denotes UDP/IP, while eth denotes MEF8 encapsulation."
::= { genEquipServicesPWServiceEntry 3 }

genEquipServicesPWServiceTdmPort		OBJECT-TYPE
		SYNTAX 		INTEGER
		ACCESS		read-write
        STATUS		mandatory
        DESCRIPTION
		"Number of TDM port (for SATOP). This parameter must be zero for CESoP."
::= { genEquipServicesPWServiceEntry 4 }

genEquipServicesPWServiceDs0bundle		OBJECT-TYPE
		SYNTAX 		INTEGER (1..496)
		ACCESS		read-write
        STATUS		mandatory
        DESCRIPTION
		"Number DS0 bundle (for CESoPSN). This parameter must be zero for SAToP."
::= { genEquipServicesPWServiceEntry 5 }

genEquipServicesPWServiceTdmProfileId		OBJECT-TYPE
		SYNTAX 		INTEGER  (1..64)
		ACCESS		read-write
        STATUS		mandatory
        DESCRIPTION
		"TDM configuration profile ID."
::= { genEquipServicesPWServiceEntry 6 }

genEquipServicesPWServicePsnTunnelProtection		OBJECT-TYPE
		SYNTAX 		EnableDisable
		ACCESS		read-write
        STATUS		mandatory
        DESCRIPTION
		"PSN tunnel protection mode."
::= { genEquipServicesPWServiceEntry 7 }

genEquipServicesPWServicePsnTunnelOrGroupId		OBJECT-TYPE
		SYNTAX 		INTEGER (1..512)
		ACCESS		read-write
        STATUS		mandatory
        DESCRIPTION
		"PSN tunnel ID for unprotected or PSN tunnel group ID for protected PSN channel."
::= { genEquipServicesPWServiceEntry 8 }

genEquipServicesPWServiceSrcUdpPortOrEcid		OBJECT-TYPE
		SYNTAX 		INTEGER (1..65535)
		ACCESS		read-write
        STATUS		mandatory
        DESCRIPTION
		"Source UDP Port for UDP IP tunnel or ECID for Ethernet tunnel."
::= { genEquipServicesPWServiceEntry 9 }

genEquipServicesPWServiceDstUdpPortOrEcid		OBJECT-TYPE
		SYNTAX 		INTEGER  (1..65535)
		ACCESS		read-write
        STATUS		mandatory
        DESCRIPTION
		"Destination UDP Port for UDP IP tunnel or ECID for Ethernet tunnel."
::= { genEquipServicesPWServiceEntry 10 }

genEquipServicesPWServiceAdmin		OBJECT-TYPE
		SYNTAX 		EnableDisable
		ACCESS		read-write
        STATUS		mandatory
        DESCRIPTION
		"Admin status."
::= { genEquipServicesPWServiceEntry 11 }

genEquipServicesPWServiceCrReference		OBJECT-TYPE
		SYNTAX 		EnableDisable
		ACCESS		read-write
        STATUS		mandatory
        DESCRIPTION
		"Clock recovery reference."
::= { genEquipServicesPWServiceEntry 12 }

genEquipServicesPWServiceOperStatus		OBJECT-TYPE
		SYNTAX 		EnableDisable
		ACCESS		read-only
        STATUS		mandatory
        DESCRIPTION
		"Operational status."
::= { genEquipServicesPWServiceEntry 13 }

genEquipServicesPWServiceRowStatus		OBJECT-TYPE
		SYNTAX 		RowStatus
		ACCESS		read-write
        STATUS		mandatory
        DESCRIPTION
		"This value is the status of the entry."
::= { genEquipServicesPWServiceEntry 30 }


--
-- NG PW Services
--
genEquipServicesNGPW	OBJECT IDENTIFIER ::= {genEquipServicesPW 6}

--
-- Bundle channel list configuration table - pw-bundle-channel-list-configuration-table
--
genEquipServicesNGPWBundlesTable  OBJECT-TYPE
        SYNTAX  SEQUENCE OF GenEquipServicesNGPWBundlesEntry
        ACCESS  not-accessible
        STATUS mandatory
        DESCRIPTION
        "This table allows definition of the group of timeslots comprising a bundle."
        ::= { genEquipServicesNGPW 1 }

genEquipServicesNGPWBundlesEntry OBJECT-TYPE
        SYNTAX GenEquipServicesNGPWBundlesEntry
        ACCESS not-accessible
        STATUS mandatory
		DESCRIPTION
        "This table entry allows definition of the group of timeslots comprising a bundle."
        INDEX { genEquipServicesNGPWBundlesSlotId, genEquipServicesNGPWBundlesTdmPort, genEquipServicesNGPWBundlesDs0List }
        ::= { genEquipServicesNGPWBundlesTable 1 }

GenEquipServicesNGPWBundlesEntry ::=
		SEQUENCE {
			genEquipServicesNGPWBundlesSlotId
				INTEGER,
			genEquipServicesNGPWBundlesTdmPort
            	INTEGER,
			genEquipServicesNGPWBundlesDs0List
                INTEGER,
			genEquipServicesNGPWBundlesIfIndex
				INTEGER,
			genEquipServicesNGPWBundlesBundleId
				INTEGER,
			genEquipServicesNGPWBundlesRowStatus
				RowStatus
}

genEquipServicesNGPWBundlesSlotId		OBJECT-TYPE
		SYNTAX 		INTEGER (2..12)
		ACCESS		read-only
        STATUS		mandatory
        DESCRIPTION
		"Slot where PW-LIC is inserted."
::= { genEquipServicesNGPWBundlesEntry 1 }

genEquipServicesNGPWBundlesTdmPort		OBJECT-TYPE
		SYNTAX 		INTEGER (1..16)
		ACCESS		read-only
        STATUS		mandatory
        DESCRIPTION
		"TDM Port number."
::= { genEquipServicesNGPWBundlesEntry 2 }

genEquipServicesNGPWBundlesDs0List		OBJECT-TYPE
		SYNTAX 		INTEGER
		ACCESS		read-only
        STATUS		mandatory
        DESCRIPTION
		"Timeslot number to be included in a bundle."
::= { genEquipServicesNGPWBundlesEntry 3 }

genEquipServicesNGPWBundlesIfIndex		OBJECT-TYPE
		SYNTAX 		INTEGER
		ACCESS		read-write
        STATUS		mandatory
        DESCRIPTION
		"iIndex."
::= { genEquipServicesNGPWBundlesEntry 4 }

genEquipServicesNGPWBundlesBundleId		OBJECT-TYPE
		SYNTAX 		INTEGER
		ACCESS		read-write
        STATUS		mandatory
        DESCRIPTION
		"Bundle ID."
::= { genEquipServicesNGPWBundlesEntry 5 }

genEquipServicesNGPWBundlesRowStatus		OBJECT-TYPE
		SYNTAX 		RowStatus
		ACCESS		read-write
        STATUS		mandatory
        DESCRIPTION
		"Row status to allow user add entries dynamically."
::= { genEquipServicesNGPWBundlesEntry 30 }

--
-- Bundle configuration table - pw-bundle-configuration-table
--
genEquipServicesNGPWBundlesDescriptionTable  OBJECT-TYPE
        SYNTAX  SEQUENCE OF GenEquipServicesNGPWBundlesDescriptionEntry
        ACCESS  not-accessible
        STATUS mandatory
        DESCRIPTION
        "This table allows configuring admin state and description for bundles."
        ::= { genEquipServicesNGPW 2 }

genEquipServicesNGPWBundlesDescriptionEntry OBJECT-TYPE
        SYNTAX GenEquipServicesNGPWBundlesDescriptionEntry
        ACCESS not-accessible
        STATUS mandatory
		DESCRIPTION
        "This table entry allows configuring admin state and description for bundles."
        INDEX { genEquipServicesNGPWBundlesDescriptionSlotId, genEquipServicesNGPWBundlesDescriptionBundleId }
        ::= { genEquipServicesNGPWBundlesDescriptionTable 1 }

GenEquipServicesNGPWBundlesDescriptionEntry ::=
		SEQUENCE {
			genEquipServicesNGPWBundlesDescriptionSlotId
				INTEGER,
			genEquipServicesNGPWBundlesDescriptionBundleId
            	INTEGER,
			genEquipServicesNGPWBundlesDescriptionAdmin
                EnableDisableSMI2,
			genEquipServicesNGPWBundlesDescriptionBundleDesc
				DisplayString,
			genEquipServicesNGPWBundlesDescriptionRowStatus
				RowStatus
}

genEquipServicesNGPWBundlesDescriptionSlotId		OBJECT-TYPE
		SYNTAX 		INTEGER (2..12)
		ACCESS		read-only
        STATUS		mandatory
        DESCRIPTION
		"Slot where PW-LIC is inserted."
::= { genEquipServicesNGPWBundlesDescriptionEntry 1 }

genEquipServicesNGPWBundlesDescriptionBundleId		OBJECT-TYPE
		SYNTAX 		INTEGER (1..256)
		ACCESS		read-only
        STATUS		mandatory
        DESCRIPTION
		"Bundle ID."
::= { genEquipServicesNGPWBundlesDescriptionEntry 2 }

genEquipServicesNGPWBundlesDescriptionAdmin		OBJECT-TYPE
		SYNTAX 		EnableDisableSMI2
		ACCESS		read-write
        STATUS		mandatory
        DESCRIPTION
		"Bundle administrative state."
::= { genEquipServicesNGPWBundlesDescriptionEntry 3 }

genEquipServicesNGPWBundlesDescriptionBundleDesc		OBJECT-TYPE
		SYNTAX 		DisplayString
		ACCESS		read-write
        STATUS		mandatory
        DESCRIPTION
		"Bundle description."
::= { genEquipServicesNGPWBundlesDescriptionEntry 4 }

genEquipServicesNGPWBundlesDescriptionRowStatus		OBJECT-TYPE
		SYNTAX 		RowStatus
		ACCESS		read-write
        STATUS		mandatory
        DESCRIPTION
		"Row status to allow user add entries dynamically."
::= { genEquipServicesNGPWBundlesDescriptionEntry 30 }

--
-- PW profile configuraiton table - pw-profile-configuration-table
--
genEquipServicesNGPWProfilesTable  OBJECT-TYPE
        SYNTAX  SEQUENCE OF GenEquipServicesNGPWProfilesEntry
        ACCESS  not-accessible
        STATUS mandatory
        DESCRIPTION
        "This table allows configuration of PW service profiles."
        ::= { genEquipServicesNGPW 3 }

genEquipServicesNGPWProfilesEntry OBJECT-TYPE
        SYNTAX GenEquipServicesNGPWProfilesEntry
        ACCESS not-accessible
        STATUS mandatory
		DESCRIPTION
        "This table entry allows configuration of PW service profiles."
        INDEX { genEquipServicesNGPWProfilesPWProfileId }
        ::= { genEquipServicesNGPWProfilesTable 1 }

GenEquipServicesNGPWProfilesEntry ::=
		SEQUENCE {
			genEquipServicesNGPWProfilesPWProfileId
				INTEGER,
			genEquipServicesNGPWProfilesPayloadSize
				INTEGER,
			genEquipServicesNGPWProfilesJitterBufferDepth
            	INTEGER,
			genEquipServicesNGPWProfilesPayloadSuppression
                EnableDisableSMI2,
			genEquipServicesNGPWProfilesPayloadType
				INTEGER,
			genEquipServicesNGPWProfilesDs0Filler
				INTEGER,
			genEquipServicesNGPWProfilesCasAlarmPattern
				INTEGER,
			genEquipServicesNGPWProfilesRtpHeaderUsed
				EnableDisableSMI2,
			genEquipServicesNGPWProfilesRtpTimestampMode
				PWRtpTimeStampMode,
			genEquipServicesNGPWProfilesRtpTimestampAbsFactor
				INTEGER,
			genEquipServicesNGPWProfilesLopsDetection
				EnableDisableSMI2,
			genEquipServicesNGPWProfilesConseqPacketsInSync
				INTEGER,
			genEquipServicesNGPWProfilesConseqMissPktsOutSync
				INTEGER,
			genEquipServicesNGPWProfilesPktLossTimeWindow
				INTEGER,
			genEquipServicesNGPWProfilesExcessivePktLossThresh
				INTEGER,
			genEquipServicesNGPWProfilesAlarmThresh
				INTEGER,
			genEquipServicesNGPWProfilesClearAlarmThresh
				INTEGER,
			genEquipServicesNGPWProfilesMissingPktsToSes
				INTEGER,
			genEquipServicesNGPWProfilesRowStatus
				RowStatus
}

genEquipServicesNGPWProfilesPWProfileId		OBJECT-TYPE
		SYNTAX 		INTEGER (1..64)
		ACCESS		read-only
        STATUS		mandatory
        DESCRIPTION
		"Unique PW  profile ID."
::= { genEquipServicesNGPWProfilesEntry 1 }

genEquipServicesNGPWProfilesPayloadSize		OBJECT-TYPE
		SYNTAX 		INTEGER
		ACCESS		read-write
        STATUS		mandatory
        DESCRIPTION
		"Payload size, in terms of TDM frames in each packet."
::= { genEquipServicesNGPWProfilesEntry 2 }

genEquipServicesNGPWProfilesJitterBufferDepth		OBJECT-TYPE
		SYNTAX 		INTEGER (1..32)
		ACCESS		read-write
        STATUS		mandatory
        DESCRIPTION
		"Jitter buffer depth (in milliseconds) to allow accommodation to the PSN-specific packet delay variation."
::= { genEquipServicesNGPWProfilesEntry 3 }

genEquipServicesNGPWProfilesPayloadSuppression		OBJECT-TYPE
		SYNTAX 		EnableDisableSMI2
		ACCESS		read-write
        STATUS		mandatory
        DESCRIPTION
		"When enabled, payload is suppresed upon incoming TDM failure."
::= { genEquipServicesNGPWProfilesEntry 4 }

genEquipServicesNGPWProfilesPayloadType		OBJECT-TYPE
		SYNTAX 		INTEGER
		ACCESS		read-write
        STATUS		mandatory
        DESCRIPTION
		"Payload type byte."
::= { genEquipServicesNGPWProfilesEntry 5 }

genEquipServicesNGPWProfilesDs0Filler		OBJECT-TYPE
		SYNTAX 		INTEGER (0..255)
		ACCESS		read-write
        STATUS		mandatory
        DESCRIPTION
		"Byte pattern transmitted on ds0 channels when packets over/underflow the jitter buffer."
::= { genEquipServicesNGPWProfilesEntry 6 }

genEquipServicesNGPWProfilesCasAlarmPattern		OBJECT-TYPE
		SYNTAX 		INTEGER  (0..15)
		ACCESS		read-write
        STATUS		mandatory
        DESCRIPTION
		"CAS alarm pattern transmitted on E1 interface when packets over/underflow the jitter buffer."
::= { genEquipServicesNGPWProfilesEntry 7 }

genEquipServicesNGPWProfilesRtpHeaderUsed		OBJECT-TYPE
		SYNTAX 		EnableDisableSMI2
		ACCESS		read-write
        STATUS		mandatory
        DESCRIPTION
		"If set to False: an RTP header is not pre-pended to the TDM packet."
::= { genEquipServicesNGPWProfilesEntry 8 }

genEquipServicesNGPWProfilesRtpTimestampMode		OBJECT-TYPE
		SYNTAX 		PWRtpTimeStampMode
		ACCESS		read-write
        STATUS		mandatory
        DESCRIPTION
		"RTP timestamp mode."
::= { genEquipServicesNGPWProfilesEntry 9 }

genEquipServicesNGPWProfilesRtpTimestampAbsFactor		OBJECT-TYPE
		SYNTAX 		INTEGER (1..65535)
		ACCESS		read-write
        STATUS		mandatory
        DESCRIPTION
		"Multiplication factor for 8KHz units in absolute mode of RTP timestamping."
::= { genEquipServicesNGPWProfilesEntry 10 }

genEquipServicesNGPWProfilesLopsDetection		OBJECT-TYPE
		SYNTAX 		EnableDisableSMI2
		ACCESS		read-write
        STATUS		mandatory
        DESCRIPTION
		"Timeout for TDM ports loopback."
::= { genEquipServicesNGPWProfilesEntry 11 }

genEquipServicesNGPWProfilesConseqPacketsInSync		OBJECT-TYPE
		SYNTAX 		INTEGER (1..10)
		ACCESS		read-write
        STATUS		mandatory
        DESCRIPTION
		"Number of consecutive packets with sequential sequence numbers  required to exit LOPS."
::= { genEquipServicesNGPWProfilesEntry 12 }

genEquipServicesNGPWProfilesConseqMissPktsOutSync		OBJECT-TYPE
		SYNTAX 		INTEGER (1..15)
		ACCESS		read-write
        STATUS		mandatory
        DESCRIPTION
		"Number of consecutive missing packets required to enter LOPS."
::= { genEquipServicesNGPWProfilesEntry 13 }

genEquipServicesNGPWProfilesPktLossTimeWindow		OBJECT-TYPE
		SYNTAX 		INTEGER (1..65535)
		ACCESS		read-write
        STATUS		mandatory
        DESCRIPTION
		"Time for computing average packet loss rate to detect excessive packet loss."
::= { genEquipServicesNGPWProfilesEntry 14 }

genEquipServicesNGPWProfilesExcessivePktLossThresh		OBJECT-TYPE
		SYNTAX 		INTEGER (1..500)
		ACCESS		read-write
        STATUS		mandatory
        DESCRIPTION
		"Alarm threshold (in percent) for excessive packet loss."
::= { genEquipServicesNGPWProfilesEntry 15 }

genEquipServicesNGPWProfilesAlarmThresh		OBJECT-TYPE
		SYNTAX 		INTEGER (1..65535)
		ACCESS		read-write
        STATUS		mandatory
        DESCRIPTION
		"Delay (in msecs) for persistent alarm setting."
::= { genEquipServicesNGPWProfilesEntry 16 }

genEquipServicesNGPWProfilesClearAlarmThresh		OBJECT-TYPE
		SYNTAX 		INTEGER (1..65535)
		ACCESS		read-write
        STATUS		mandatory
        DESCRIPTION
		"Delay (in msecs) for persistent alarm clearing."
::= { genEquipServicesNGPWProfilesEntry 17 }

genEquipServicesNGPWProfilesMissingPktsToSes		OBJECT-TYPE
		SYNTAX 		INTEGER (1..100)
		ACCESS		read-write
        STATUS		mandatory
        DESCRIPTION
		"TPercent of missing packets detected in 1 second window to cause SES to be counted."
::= { genEquipServicesNGPWProfilesEntry 18 }

genEquipServicesNGPWProfilesRowStatus		OBJECT-TYPE
		SYNTAX 		RowStatus
		ACCESS		read-write
        STATUS		mandatory
        DESCRIPTION
		"Row status to allow user add entries dynamically."
::= { genEquipServicesNGPWProfilesEntry 30 }

--
-- PSN tunnel configuration table - pw-psn-tunnel-configuration-table
--
genEquipServicesNGPWPSNTunnelsTable  OBJECT-TYPE
        SYNTAX  SEQUENCE OF GenEquipServicesNGPWPSNTunnelsEntry
        ACCESS  not-accessible
        STATUS mandatory
        DESCRIPTION
        "This table allows configuration of PSN tunnel encapsulations for PW services."
        ::= { genEquipServicesNGPW 4 }

genEquipServicesNGPWPSNTunnelsEntry OBJECT-TYPE
        SYNTAX GenEquipServicesNGPWPSNTunnelsEntry
        ACCESS not-accessible
        STATUS mandatory
		DESCRIPTION
        "This table entry allows configuration of PSN tunnel encapsulations for PW services."
        INDEX { genEquipServicesNGPWPSNTunnelsSlotID, genEquipServicesNGPWPSNTunnelsTunnelId }
        ::= { genEquipServicesNGPWPSNTunnelsTable 1 }

GenEquipServicesNGPWPSNTunnelsEntry ::=
		SEQUENCE {
			genEquipServicesNGPWPSNTunnelsSlotID
				INTEGER,
			genEquipServicesNGPWPSNTunnelsTunnelId
				INTEGER,
			genEquipServicesNGPWPSNTunnelsAdmin
            	EnableDisableSMI2,
			genEquipServicesNGPWPSNTunnelsPsnType
                PWTunnelPsnType,
			genEquipServicesNGPWPSNTunnelsDestIpAddr
				IpAddress,
			genEquipServicesNGPWPSNTunnelsNextHopIp
				IpAddress,
			genEquipServicesNGPWPSNTunnelsTosDscp
				INTEGER,
			genEquipServicesNGPWPSNTunnelsRemoteMacAddr
				OCTET STRING,
			genEquipServicesNGPWPSNTunnelsSourceMPLSLabel
				INTEGER,
			genEquipServicesNGPWPSNTunnelsDestinationMPLSLabel
				INTEGER,
			genEquipServicesNGPWPSNTunnelsMPLSexp
				INTEGER,
			genEquipServicesNGPWPSNTunnelsVlanType
				PWTunnelVlanType,
			genEquipServicesNGPWPSNTunnelsVid
				INTEGER,
			genEquipServicesNGPWPSNTunnelsPBits
				INTEGER,
			genEquipServicesNGPWPSNTunnelsMaId
				INTEGER,
			genEquipServicesNGPWPSNTunnelsTDMDefectPropagation
				EnableDisableSMI2,
			genEquipServicesNGPWPSNTunnelsRowStatus
				RowStatus
}

genEquipServicesNGPWPSNTunnelsSlotID		OBJECT-TYPE
		SYNTAX 		INTEGER (1..64)
		ACCESS		read-only
        STATUS		mandatory
        DESCRIPTION
		"Slot where PW-LIC is inserted."
::= { genEquipServicesNGPWPSNTunnelsEntry 1 }

genEquipServicesNGPWPSNTunnelsTunnelId		OBJECT-TYPE
		SYNTAX 		INTEGER (1..16)
		ACCESS		read-only
        STATUS		mandatory
        DESCRIPTION
		"PSN Tunnel ID."
::= { genEquipServicesNGPWPSNTunnelsEntry 2 }

genEquipServicesNGPWPSNTunnelsAdmin		OBJECT-TYPE
		SYNTAX 		EnableDisableSMI2
		ACCESS		read-write
        STATUS		mandatory
        DESCRIPTION
		"Payload type byte."
::= { genEquipServicesNGPWPSNTunnelsEntry 3 }


genEquipServicesNGPWPSNTunnelsPsnType		OBJECT-TYPE
		SYNTAX 		PWTunnelPsnType
		ACCESS		read-write
        STATUS		mandatory
        DESCRIPTION
		"PSN tunnel type. UDPIP denotes UDP/IP, while eth denotes MEF8 encapsulation."
::= { genEquipServicesNGPWPSNTunnelsEntry 4 }

genEquipServicesNGPWPSNTunnelsDestIpAddr		OBJECT-TYPE
		SYNTAX 		IpAddress
		ACCESS		read-write
        STATUS		mandatory
        DESCRIPTION
		"Destination IP."
::= { genEquipServicesNGPWPSNTunnelsEntry 5 }

genEquipServicesNGPWPSNTunnelsNextHopIp		OBJECT-TYPE
		SYNTAX 		IpAddress
		ACCESS		read-write
        STATUS		mandatory
        DESCRIPTION
		"Next hop IP Address for UDP/IP PSN tunnel."
::= { genEquipServicesNGPWPSNTunnelsEntry 6 }

genEquipServicesNGPWPSNTunnelsTosDscp		OBJECT-TYPE
		SYNTAX 		INTEGER  (0..63)
		ACCESS		read-write
        STATUS		mandatory
        DESCRIPTION
		"PSN Tunnel ToS (DSCP)."
::= { genEquipServicesNGPWPSNTunnelsEntry 7 }

genEquipServicesNGPWPSNTunnelsRemoteMacAddr		OBJECT-TYPE
		SYNTAX 		OCTET STRING (SIZE(6))
		ACCESS		read-write
        STATUS		mandatory
        DESCRIPTION
		"Remote MAC address."
::= { genEquipServicesNGPWPSNTunnelsEntry 8 }

genEquipServicesNGPWPSNTunnelsSourceMPLSLabel		OBJECT-TYPE
		SYNTAX 		INTEGER
		ACCESS		read-write
        STATUS		mandatory
        DESCRIPTION
		"Source MPLS Label."
::= { genEquipServicesNGPWPSNTunnelsEntry 9 }

genEquipServicesNGPWPSNTunnelsDestinationMPLSLabel		OBJECT-TYPE
		SYNTAX 		INTEGER
		ACCESS		read-write
        STATUS		mandatory
        DESCRIPTION
		"Destination MPLS label."
::= { genEquipServicesNGPWPSNTunnelsEntry 10 }

genEquipServicesNGPWPSNTunnelsMPLSexp		OBJECT-TYPE
		SYNTAX 		INTEGER (0..7)
		ACCESS		read-write
        STATUS		mandatory
        DESCRIPTION
		"MPLS Experimental field."
::= { genEquipServicesNGPWPSNTunnelsEntry 11 }

genEquipServicesNGPWPSNTunnelsVlanType		OBJECT-TYPE
		SYNTAX 		PWTunnelVlanType
		ACCESS		read-write
        STATUS		mandatory
        DESCRIPTION
		"VLAN type supported by this PSN tunnel (S-VLAN or C-VLAN)."
::= { genEquipServicesNGPWPSNTunnelsEntry 12 }

genEquipServicesNGPWPSNTunnelsVid		OBJECT-TYPE
		SYNTAX 		INTEGER (0..4090)
		ACCESS		read-write
        STATUS		mandatory
        DESCRIPTION
		"PSN Tunnel VLAN ID."
::= { genEquipServicesNGPWPSNTunnelsEntry 13 }

genEquipServicesNGPWPSNTunnelsPBits		OBJECT-TYPE
		SYNTAX 		INTEGER (1..7)
		ACCESS		read-write
        STATUS		mandatory
        DESCRIPTION
		"PSN Tunnel P-bits."
::= { genEquipServicesNGPWPSNTunnelsEntry 14 }

genEquipServicesNGPWPSNTunnelsMaId 		OBJECT-TYPE
		SYNTAX 		INTEGER
		ACCESS		read-write
        STATUS		mandatory
        DESCRIPTION
		"Maintenance Association ID."
::= { genEquipServicesNGPWPSNTunnelsEntry 15 }

genEquipServicesNGPWPSNTunnelsTDMDefectPropagation 		OBJECT-TYPE
		SYNTAX 		EnableDisableSMI2
		ACCESS		read-write
        STATUS		mandatory
        DESCRIPTION
		"TDM defect propagation to SOAM. Enable for dual homing configuration."
::= { genEquipServicesNGPWPSNTunnelsEntry 16 }

genEquipServicesNGPWPSNTunnelsRowStatus		OBJECT-TYPE
		SYNTAX 		RowStatus
		ACCESS		read-write
        STATUS		mandatory
        DESCRIPTION
		"Row status to allow user add entries dynamically."
::= { genEquipServicesNGPWPSNTunnelsEntry 30 }

--
-- PW service configuration table - pw-service-configuration-table
--
genEquipServicesNGPWServiceTable  OBJECT-TYPE
        SYNTAX  SEQUENCE OF GenEquipServicesNGPWServiceEntry
        ACCESS  not-accessible
        STATUS mandatory
        DESCRIPTION
        "This table allows definition of PW services."
        ::= { genEquipServicesNGPW 5 }

genEquipServicesNGPWServiceEntry OBJECT-TYPE
        SYNTAX GenEquipServicesNGPWServiceEntry
        ACCESS not-accessible
        STATUS mandatory
		DESCRIPTION
        "This table entry allows definition of PW services."
        INDEX { genEquipServicesNGPWServiceSlotID, genEquipServicesNGPWServicePWId }
        ::= { genEquipServicesNGPWServiceTable 1 }

GenEquipServicesNGPWServiceEntry ::=
		SEQUENCE {
			genEquipServicesNGPWServiceSlotID
				INTEGER,
			genEquipServicesNGPWServicePWId
				INTEGER,
			genEquipServicesNGPWServiceAdmin
            	EnableDisableSMI2,
			genEquipServicesNGPWServicePWType
                INTEGER,
			genEquipServicesNGPWServicePsnType
				PWTunnelPsnType,
			genEquipServicesNGPWServiceDs0bundle
				INTEGER,
			genEquipServicesNGPWServiceTdmProfileId
				INTEGER,
			genEquipServicesNGPWServiceTunnel
				INTEGER,
			genEquipServicesNGPWServiceCrReference
				NoYes,
			genEquipServicesNGPWServiceSrcPsnId
				INTEGER,
			genEquipServicesNGPWServiceDstPsnId
				INTEGER,
			genEquipServicesNGPWServicePsnTunnelProtection
				INTEGER,
			genEquipServicesNGPWServiceRowStatus
				RowStatus
}

genEquipServicesNGPWServiceSlotID		OBJECT-TYPE
		SYNTAX 		INTEGER (1..64)
		ACCESS		read-only
        STATUS		mandatory
        DESCRIPTION
		"Slot where PW-LIC is inserted."
::= { genEquipServicesNGPWServiceEntry 1 }

genEquipServicesNGPWServicePWId		OBJECT-TYPE
		SYNTAX 		INTEGER (1..16)
		ACCESS		read-only
        STATUS		mandatory
        DESCRIPTION
		"Pseudowire ID."
::= { genEquipServicesNGPWServiceEntry 2 }

genEquipServicesNGPWServiceAdmin		OBJECT-TYPE
		SYNTAX 		EnableDisableSMI2
		ACCESS		read-write
        STATUS		mandatory
        DESCRIPTION
		"Administrative status of this PW service."
::= { genEquipServicesNGPWServiceEntry 3 }


genEquipServicesNGPWServicePWType		OBJECT-TYPE
		SYNTAX 		INTEGER {
						satop(0),
						cespsn(1),
						cas-cespsn(2)
					}
		ACCESS		read-write
        STATUS		mandatory
        DESCRIPTION
		"Indicates the emulated service to be carried over the PW service (SAToP, CESoP, CESoP with PSN)."
::= { genEquipServicesNGPWServiceEntry 4 }

genEquipServicesNGPWServicePsnType		OBJECT-TYPE
		SYNTAX 		PWTunnelPsnType
		ACCESS		read-write
        STATUS		mandatory
        DESCRIPTION
		"Indicates the PSN type that the PW service will use over the network."
::= { genEquipServicesNGPWServiceEntry 5 }

genEquipServicesNGPWServiceDs0bundle		OBJECT-TYPE
		SYNTAX 		INTEGER (1..256)
		ACCESS		read-write
        STATUS		mandatory
        DESCRIPTION
		"Number DS0 bundle (for CESoPSN). This parameter must be zero for SAToP."
::= { genEquipServicesNGPWServiceEntry 6 }

genEquipServicesNGPWServiceTdmProfileId		OBJECT-TYPE
		SYNTAX 		INTEGER  (1..64)
		ACCESS		read-write
        STATUS		mandatory
        DESCRIPTION
		"Indicates the PW profile id for this PW service."
::= { genEquipServicesNGPWServiceEntry 7 }

genEquipServicesNGPWServiceTunnel		OBJECT-TYPE
		SYNTAX 		INTEGER (1..16)
		ACCESS		read-write
        STATUS		mandatory
        DESCRIPTION
		"PSN tunnel ID for unprotected or PSN tunnel group ID for protected PSN channel."
::= { genEquipServicesNGPWServiceEntry 8 }

genEquipServicesNGPWServiceCrReference		OBJECT-TYPE
		SYNTAX 		NoYes
		ACCESS		read-write
        STATUS		mandatory
        DESCRIPTION
		"Whether this PW may be used as a reference for clock recovery."
::= { genEquipServicesNGPWServiceEntry 9 }

genEquipServicesNGPWServiceSrcPsnId		OBJECT-TYPE
		SYNTAX 		INTEGER
		ACCESS		read-write
        STATUS		mandatory
        DESCRIPTION
		"Source UDP Port for UDP IP tunnel, ECID for Ethernet tunnel or label for MPLS tunnel."
::= { genEquipServicesNGPWServiceEntry 10 }

genEquipServicesNGPWServiceDstPsnId		OBJECT-TYPE
		SYNTAX 		INTEGER
		ACCESS		read-write
        STATUS		mandatory
        DESCRIPTION
		"Destination UDP Port for UDP IP tunnel, ECID for Ethernet tunnel or label for MPLS tunnel."
::= { genEquipServicesNGPWServiceEntry 11 }

genEquipServicesNGPWServicePsnTunnelProtection		OBJECT-TYPE
		SYNTAX 		INTEGER {
						no(0)
					}
		ACCESS		read-write
        STATUS		mandatory
        DESCRIPTION
		"Indicates whether this PW service is PSN protected."
::= { genEquipServicesNGPWServiceEntry 12 }

genEquipServicesNGPWServiceRowStatus		OBJECT-TYPE
		SYNTAX 		RowStatus
		ACCESS		read-write
        STATUS		mandatory
        DESCRIPTION
		"Row status to allow user add entries dynamically."
::= { genEquipServicesNGPWServiceEntry 30 }

--
-- TDM port configuration table - pw-tdm-port-configuration-table
--
genEquipServicesNGPWTDMPortsTable  OBJECT-TYPE
        SYNTAX  SEQUENCE OF GenEquipServicesNGPWTDMPortsEntry
        ACCESS  not-accessible
        STATUS mandatory
        DESCRIPTION
        "This table allows configuration of TDM ports."
        ::= { genEquipServicesNGPW 6 }

genEquipServicesNGPWTDMPortsEntry OBJECT-TYPE
        SYNTAX GenEquipServicesNGPWTDMPortsEntry
        ACCESS not-accessible
        STATUS mandatory
		DESCRIPTION
        "This table entry allows configuration of TDM ports."
        INDEX { genEquipServicesNGPWTDMPortsSlotID, genEquipServicesNGPWTDMPortsPort }
        ::= { genEquipServicesNGPWTDMPortsTable 1 }

GenEquipServicesNGPWTDMPortsEntry ::=
		SEQUENCE {
			genEquipServicesNGPWTDMPortsSlotID
				INTEGER,
			genEquipServicesNGPWTDMPortsPort
				INTEGER,
			genEquipServicesNGPWTDMPortsIfIndex
            	INTEGER,
			genEquipServicesNGPWTDMPortsAdmin
                EnableDisableSMI2,
			genEquipServicesNGPWTDMPortsLineType
				INTEGER,
			genEquipServicesNGPWTDMPortsLineCoding
				INTEGER,
			genEquipServicesNGPWTDMPortsChannelization
				EnableDisableSMI2,
			genEquipServicesNGPWTDMPortsTimingMode
				INTEGER,
			genEquipServicesNGPWTDMPortsClockSourceRef
				INTEGER,
			genEquipServicesNGPWTDMPortsClkSrcRefPort
				INTEGER,
			genEquipServicesNGPWTDMPortsIdleCode
				INTEGER,
			genEquipServicesNGPWTDMPortsCableLength
				INTEGER,
			genEquipServicesNGPWTDMPortsLoopback
				TDMLoopbackType
}

genEquipServicesNGPWTDMPortsSlotID		OBJECT-TYPE
		SYNTAX 		INTEGER (2..12)
		ACCESS		read-only
        STATUS		mandatory
        DESCRIPTION
		"Slot where PW-LIC is inserted."
::= { genEquipServicesNGPWTDMPortsEntry 1 }

genEquipServicesNGPWTDMPortsPort		OBJECT-TYPE
		SYNTAX 		INTEGER (1..16)
		ACCESS		read-only
        STATUS		mandatory
        DESCRIPTION
		"Physical port number in the card."
::= { genEquipServicesNGPWTDMPortsEntry 2 }

genEquipServicesNGPWTDMPortsIfIndex		OBJECT-TYPE
		SYNTAX 		INTEGER
		ACCESS		read-write
        STATUS		mandatory
        DESCRIPTION
		"ifIndex."
::= { genEquipServicesNGPWTDMPortsEntry 3 }

genEquipServicesNGPWTDMPortsAdmin		OBJECT-TYPE
		SYNTAX 		EnableDisableSMI2
		ACCESS		read-write
        STATUS		mandatory
        DESCRIPTION
		"TDM port administrative state."
::= { genEquipServicesNGPWTDMPortsEntry 4 }

genEquipServicesNGPWTDMPortsLineType		OBJECT-TYPE
		SYNTAX 		INTEGER {
						e1Unframed(0),
						e1(1),
						e1-crc(2),
						e1-mf(3),
						e1-mf-crc(4),
						ds1-d4(5),
						ds1-esf(6)
					}
		ACCESS		read-write
        STATUS		mandatory
        DESCRIPTION
		"Line type of this TDM port."
::= { genEquipServicesNGPWTDMPortsEntry 5 }

genEquipServicesNGPWTDMPortsLineCoding		OBJECT-TYPE
		SYNTAX 		INTEGER {
						hdb3-b8zs(0),
						ami(1)
					}
		ACCESS		read-write
        STATUS		mandatory
        DESCRIPTION
		"Line coding for this port. The value hdb3-b8zs means b8zs for T1 and hdb3 for E1. AMI is only for T1."
::= { genEquipServicesNGPWTDMPortsEntry 6 }

genEquipServicesNGPWTDMPortsChannelization		OBJECT-TYPE
		SYNTAX 		EnableDisableSMI2
		ACCESS		read-write
        STATUS		mandatory
        DESCRIPTION
		"Indication whether this TDM port is channelized into DS0s."
::= { genEquipServicesNGPWTDMPortsEntry 7 }

genEquipServicesNGPWTDMPortsTimingMode		OBJECT-TYPE
		SYNTAX 		INTEGER {
						loop(0),
						absolute(1),
						clock-recovery(2)
					}
		ACCESS		read-write
        STATUS		mandatory
        DESCRIPTION
		"Clock reference for the outgoing TDM signal."
::= { genEquipServicesNGPWTDMPortsEntry 8 }

genEquipServicesNGPWTDMPortsClockSourceRef		OBJECT-TYPE
		SYNTAX 		INTEGER {
						none(0),
						front-panel(1),
						sys-ref(2)
					}

		ACCESS		read-write
        STATUS		mandatory
        DESCRIPTION
		"Clock source reference for Absolute clock mode. ???none??? - for loop or clock-recovery timing modes."
::= { genEquipServicesNGPWTDMPortsEntry 9 }

genEquipServicesNGPWTDMPortsClkSrcRefPort		OBJECT-TYPE
		SYNTAX 		INTEGER (0..16)
		ACCESS		read-write
        STATUS		mandatory
        DESCRIPTION
		"TDM port serving as a clock reference for loop or clock-recovery timing modes."
::= { genEquipServicesNGPWTDMPortsEntry 10 }

genEquipServicesNGPWTDMPortsIdleCode		OBJECT-TYPE
		SYNTAX 		INTEGER
		ACCESS		read-write
        STATUS		mandatory
        DESCRIPTION
		"Value to be transmitted on this TDM port in unused timeslots."
::= { genEquipServicesNGPWTDMPortsEntry 11 }

genEquipServicesNGPWTDMPortsCableLength		OBJECT-TYPE
		SYNTAX 		INTEGER {
						fixed-or-0-133ft(0),
						len-133-266ft(1),
						len-266-399ft(2),
						len-399-533ft(3),
						len-533-655ft(4)
					}
		ACCESS		read-write
        STATUS		mandatory
        DESCRIPTION
		"Cable length for this port. The value fixed-or-0-133ft means fixed for E1 (the only valid value) and 0-133ft for T1."
::= { genEquipServicesNGPWTDMPortsEntry 12 }

genEquipServicesNGPWTDMPortsLoopback 		OBJECT-TYPE
		SYNTAX 		TDMLoopbackType
		ACCESS		read-write
        STATUS		mandatory
        DESCRIPTION
		"Type of required loopback on this TDM port."
::= { genEquipServicesNGPWTDMPortsEntry 13 }

--
-- PSN tunnel status table - pw-psn-tunnel-status-table
--
genEquipServicesNGPWPSNTunnelsStatusTable  OBJECT-TYPE
        SYNTAX  SEQUENCE OF GenEquipServicesNGPWPSNTunnelsStatusEntry
        ACCESS  not-accessible
        STATUS mandatory
        DESCRIPTION
        "This table contains status and information about existing PSN tunnels."
        ::= { genEquipServicesNGPW 7 }

genEquipServicesNGPWPSNTunnelsStatusEntry OBJECT-TYPE
        SYNTAX GenEquipServicesNGPWPSNTunnelsStatusEntry
        ACCESS not-accessible
        STATUS mandatory
		DESCRIPTION
        "This table entry contains status and information about existing PSN tunnels."
        INDEX { genEquipServicesNGPWPSNTunnelsStatusSlotID, genEquipServicesNGPWPSNTunnelsStatusTunnelId }
        ::= { genEquipServicesNGPWPSNTunnelsStatusTable 1 }

GenEquipServicesNGPWPSNTunnelsStatusEntry ::=
		SEQUENCE {
			genEquipServicesNGPWPSNTunnelsStatusSlotID
				INTEGER,
			genEquipServicesNGPWPSNTunnelsStatusTunnelId
            	INTEGER,
			genEquipServicesNGPWPSNTunnelsStatusOperStatus
                DownUp,
			genEquipServicesNGPWPSNTunnelsStatusSourceIpAddr
				IpAddress,
			genEquipServicesNGPWPSNTunnelsStatusSourceMacAddr
				OCTET STRING,
			genEquipServicesNGPWPSNTunnelsStatusRemoteMacAddr
				OCTET STRING
}

genEquipServicesNGPWPSNTunnelsStatusSlotID		OBJECT-TYPE
		SYNTAX 		INTEGER (2..12)
		ACCESS		read-only
        STATUS		mandatory
        DESCRIPTION
		"Slot where PW-LIC is inserted."
::= { genEquipServicesNGPWPSNTunnelsStatusEntry 1 }

genEquipServicesNGPWPSNTunnelsStatusTunnelId		OBJECT-TYPE
		SYNTAX 		INTEGER (1..16)
		ACCESS		read-only
        STATUS		mandatory
        DESCRIPTION
		"PSN Tunnel ID."
::= { genEquipServicesNGPWPSNTunnelsStatusEntry 2 }

genEquipServicesNGPWPSNTunnelsStatusOperStatus		OBJECT-TYPE
		SYNTAX 		DownUp
		ACCESS		read-only
        STATUS		mandatory
        DESCRIPTION
		"PSN tunnel operational state."
::= { genEquipServicesNGPWPSNTunnelsStatusEntry 3 }

genEquipServicesNGPWPSNTunnelsStatusSourceIpAddr		OBJECT-TYPE
		SYNTAX 		IpAddress
		ACCESS		read-only
        STATUS		mandatory
        DESCRIPTION
		"PSN tunnel source IP address."
::= { genEquipServicesNGPWPSNTunnelsStatusEntry 4 }

genEquipServicesNGPWPSNTunnelsStatusSourceMacAddr		OBJECT-TYPE
		SYNTAX 		OCTET STRING (SIZE(6))
		ACCESS		read-only
        STATUS		mandatory
        DESCRIPTION
		"PSN tunnel source MAC address."
::= { genEquipServicesNGPWPSNTunnelsStatusEntry 5 }

genEquipServicesNGPWPSNTunnelsStatusRemoteMacAddr		OBJECT-TYPE
		SYNTAX 		OCTET STRING (SIZE(6))
		ACCESS		read-only
        STATUS		mandatory
        DESCRIPTION
		"PSN tunnel remote MAC address."
::= { genEquipServicesNGPWPSNTunnelsStatusEntry 6 }

--
-- PW service status table - pw-service-status-table
--
genEquipServicesNGPWServiceStatusTable  OBJECT-TYPE
        SYNTAX  SEQUENCE OF GenEquipServicesNGPWServiceStatusEntry
        ACCESS  not-accessible
        STATUS mandatory
        DESCRIPTION
        "This table contains status information of existing PW services."
        ::= { genEquipServicesNGPW 8 }

genEquipServicesNGPWServiceStatusEntry OBJECT-TYPE
        SYNTAX GenEquipServicesNGPWServiceStatusEntry
        ACCESS not-accessible
        STATUS mandatory
		DESCRIPTION
        "This table entry contains status information of existing PW services."
        INDEX { genEquipServicesNGPWServiceStatusSlotID, genEquipServicesNGPWServiceStatusID }
        ::= { genEquipServicesNGPWServiceStatusTable 1 }

GenEquipServicesNGPWServiceStatusEntry ::=
		SEQUENCE {
			genEquipServicesNGPWServiceStatusSlotID
				INTEGER,
			genEquipServicesNGPWServiceStatusID
            	INTEGER,
			genEquipServicesNGPWServiceStatusOperStatus
                DownUp,
			genEquipServicesNGPWServiceStatusClearStats
				NoYes,
			genEquipServicesNGPWServiceStatusTxPkts
				Counter64,
			genEquipServicesNGPWServiceStatusReceivedPkts
				Counter64,
			genEquipServicesNGPWServiceStatusTransitionsLOPS
				Counter64,
			genEquipServicesNGPWServiceStatusJitterBufferOverruns
				Counter64,
			genEquipServicesNGPWServiceStatusBufferDeviations
				Counter64,
			genEquipServicesNGPWServiceStatusMinJitterCount
				Counter64,
			genEquipServicesNGPWServiceStatusMaxJitterCount
				Counter64
}

genEquipServicesNGPWServiceStatusSlotID		OBJECT-TYPE
		SYNTAX 		INTEGER (2..12)
		ACCESS		read-only
        STATUS		mandatory
        DESCRIPTION
		"Slot where PW-LIC is inserted."
::= { genEquipServicesNGPWServiceStatusEntry 1 }

genEquipServicesNGPWServiceStatusID		OBJECT-TYPE
		SYNTAX 		INTEGER (1..16)
		ACCESS		read-only
        STATUS		mandatory
        DESCRIPTION
		"Pseudowire ID."
::= { genEquipServicesNGPWServiceStatusEntry 2 }

genEquipServicesNGPWServiceStatusOperStatus		OBJECT-TYPE
		SYNTAX 		DownUp
		ACCESS		read-only
        STATUS		mandatory
        DESCRIPTION
		"Indicates the operational status of PW service."
::= { genEquipServicesNGPWServiceStatusEntry 3 }

genEquipServicesNGPWServiceStatusClearStats		OBJECT-TYPE
		SYNTAX 		NoYes
		ACCESS		read-write
        STATUS		mandatory
        DESCRIPTION
		"Clear all statistics for this PW service."
::= { genEquipServicesNGPWServiceStatusEntry 4 }

genEquipServicesNGPWServiceStatusTxPkts		OBJECT-TYPE
		SYNTAX 		Counter64
		ACCESS		read-only
        STATUS		mandatory
        DESCRIPTION
		"Number of transmitted packets."
::= { genEquipServicesNGPWServiceStatusEntry 5 }

genEquipServicesNGPWServiceStatusReceivedPkts		OBJECT-TYPE
		SYNTAX 		Counter64
		ACCESS		read-only
        STATUS		mandatory
        DESCRIPTION
		"Number of received packets."
::= { genEquipServicesNGPWServiceStatusEntry 6 }

genEquipServicesNGPWServiceStatusTransitionsLOPS		OBJECT-TYPE
		SYNTAX 		Counter64
		ACCESS		read-only
        STATUS		mandatory
        DESCRIPTION
		"Number of transitions from the normal state to the LOPS."
::= { genEquipServicesNGPWServiceStatusEntry 7 }

genEquipServicesNGPWServiceStatusJitterBufferOverruns		OBJECT-TYPE
		SYNTAX 		Counter64
		ACCESS		read-only
        STATUS		mandatory
        DESCRIPTION
		"Number of jitter buffer overruns."
::= { genEquipServicesNGPWServiceStatusEntry 8 }

genEquipServicesNGPWServiceStatusBufferDeviations		OBJECT-TYPE
		SYNTAX 		Counter64
		ACCESS		read-only
        STATUS		mandatory
        DESCRIPTION
		"Max Jitter Buffer Deviation."
::= { genEquipServicesNGPWServiceStatusEntry 9 }

genEquipServicesNGPWServiceStatusMinJitterCount		OBJECT-TYPE
		SYNTAX 		Counter64
		ACCESS		read-only
        STATUS		mandatory
        DESCRIPTION
		"Minimum jitter buffer usage registered for the last second."
::= { genEquipServicesNGPWServiceStatusEntry 10 }

genEquipServicesNGPWServiceStatusMaxJitterCount		OBJECT-TYPE
		SYNTAX 		Counter64
		ACCESS		read-only
        STATUS		mandatory
        DESCRIPTION
		"Maximum jitter buffer usage registered for the last second."
::= { genEquipServicesNGPWServiceStatusEntry 11 }

--
-- PW TDM port status table - pw-tdm-port-status-table and pw-tdm-port-loopback-status-table
--
genEquipServicesNGPWTDMPortsStatusTable  OBJECT-TYPE
        SYNTAX  SEQUENCE OF GenEquipServicesNGPWTDMPortsStatusEntry
        ACCESS  not-accessible
        STATUS mandatory
        DESCRIPTION
        "This table contains status information about TDM ports."
        ::= { genEquipServicesNGPW 9 }

genEquipServicesNGPWTDMPortsStatusEntry OBJECT-TYPE
        SYNTAX GenEquipServicesNGPWTDMPortsStatusEntry
        ACCESS not-accessible
        STATUS mandatory
		DESCRIPTION
        "This table entry contains status information about TDM ports."
        INDEX { genEquipServicesNGPWTDMPortsStatusIfIndex }
        ::= { genEquipServicesNGPWTDMPortsStatusTable 1 }

GenEquipServicesNGPWTDMPortsStatusEntry ::=
		SEQUENCE {
			genEquipServicesNGPWTDMPortsStatusSlotID
				INTEGER,
			genEquipServicesNGPWTDMPortsStatusPort
            	INTEGER,
			genEquipServicesNGPWTDMPortsStatusIfIndex
                INTEGER,
			genEquipServicesNGPWTDMPortsStatusOperStatus
				DownUp,
			genEquipServicesNGPWTDMPortsStatusLoopbackCounter
				INTEGER,
			genEquipServicesNGPWTDMPortsStatusActualLoopback
				INTEGER,
			genEquipServicesNGPWTDMPortsStatusLineStatus
				INTEGER,
			genEquipServicesNGPWTDMPortsStatusLoopback
				TDMLoopbackType
}

genEquipServicesNGPWTDMPortsStatusSlotID		OBJECT-TYPE
		SYNTAX 		INTEGER (2..12)
		ACCESS		read-only
        STATUS		mandatory
        DESCRIPTION
		"Slot where PW-LIC is inserted."
::= { genEquipServicesNGPWTDMPortsStatusEntry 1 }

genEquipServicesNGPWTDMPortsStatusPort		OBJECT-TYPE
		SYNTAX 		INTEGER (1..16)
		ACCESS		read-only
        STATUS		mandatory
        DESCRIPTION
		"Physical port number in the card."
::= { genEquipServicesNGPWTDMPortsStatusEntry 2 }

genEquipServicesNGPWTDMPortsStatusIfIndex		OBJECT-TYPE
		SYNTAX 		INTEGER
		ACCESS		read-only
        STATUS		mandatory
        DESCRIPTION
		"ifIndex."
::= { genEquipServicesNGPWTDMPortsStatusEntry 3 }

genEquipServicesNGPWTDMPortsStatusOperStatus		OBJECT-TYPE
		SYNTAX 		DownUp
		ACCESS		read-write
        STATUS		mandatory
        DESCRIPTION
		"Operational state of the port."
::= { genEquipServicesNGPWTDMPortsStatusEntry 4 }

genEquipServicesNGPWTDMPortsStatusLoopbackCounter		OBJECT-TYPE
		SYNTAX 		INTEGER
		ACCESS		read-only
        STATUS		mandatory
        DESCRIPTION
		"Loopback time left (in seconds)"
::= { genEquipServicesNGPWTDMPortsStatusEntry 5 }

genEquipServicesNGPWTDMPortsStatusActualLoopback		OBJECT-TYPE
		SYNTAX 		INTEGER
		ACCESS		read-only
        STATUS		mandatory
        DESCRIPTION
		"Actual status of loopback on this TDM port reported by the card."
::= { genEquipServicesNGPWTDMPortsStatusEntry 6 }

genEquipServicesNGPWTDMPortsStatusLineStatus		OBJECT-TYPE
		SYNTAX 		INTEGER
		ACCESS		read-only
        STATUS		mandatory
        DESCRIPTION
		"Currently present line-level PDH alarms."
::= { genEquipServicesNGPWTDMPortsStatusEntry 7 }

genEquipServicesNGPWTDMPortsStatusLoopback		OBJECT-TYPE
		SYNTAX 		TDMLoopbackType
		ACCESS		read-write
        STATUS		mandatory
        DESCRIPTION
		"Type of required loopback on this TDM port."
::= { genEquipServicesNGPWTDMPortsStatusEntry 8 }

--
-- Bundle status table - pw-bundle-status-table
--
genEquipServicesNGPWBundlesStatusTable  OBJECT-TYPE
        SYNTAX  SEQUENCE OF GenEquipServicesNGPWBundlesStatusEntry
        ACCESS  not-accessible
        STATUS mandatory
        DESCRIPTION
        "This table contains the current staus for bundles."
        ::= { genEquipServicesNGPW 10 }

genEquipServicesNGPWBundlesStatusEntry OBJECT-TYPE
        SYNTAX GenEquipServicesNGPWBundlesStatusEntry
        ACCESS not-accessible
        STATUS mandatory
		DESCRIPTION
        "This table contains the current staus for bundles."
        INDEX { genEquipServicesNGPWBundlesStatusSlotID, genEquipServicesNGPWBundlesStatusBundleId }
        ::= { genEquipServicesNGPWBundlesStatusTable 1 }

GenEquipServicesNGPWBundlesStatusEntry ::=
		SEQUENCE {
			genEquipServicesNGPWBundlesStatusSlotID
				INTEGER,
			genEquipServicesNGPWBundlesStatusBundleId
            	INTEGER,
			genEquipServicesNGPWBundlesStatusOperStatus
                DownUp
}

genEquipServicesNGPWBundlesStatusSlotID		OBJECT-TYPE
		SYNTAX 		INTEGER (2..12)
		ACCESS		read-only
        STATUS		mandatory
        DESCRIPTION
		"Slot where PW-LIC is inserted."
::= { genEquipServicesNGPWBundlesStatusEntry 1 }

genEquipServicesNGPWBundlesStatusBundleId		OBJECT-TYPE
		SYNTAX 		INTEGER (1..256)
		ACCESS		read-only
        STATUS		mandatory
        DESCRIPTION
		"Bundle ID."
::= { genEquipServicesNGPWBundlesStatusEntry 2 }

genEquipServicesNGPWBundlesStatusOperStatus		OBJECT-TYPE
		SYNTAX 		DownUp
		ACCESS		read-only
        STATUS		mandatory
        DESCRIPTION
		"Bundle operational state."
::= { genEquipServicesNGPWBundlesStatusEntry 3 }

--
-- PW Tunnel group configuration table - pw-psn-tunnel-group-configuration-table
--

genEquipServicesNGPWPSNTunnelGroupTable  OBJECT-TYPE
        SYNTAX  SEQUENCE OF GenEquipServicesNGPWPSNTunnelGroupEntry
        ACCESS  not-accessible
        STATUS mandatory
        DESCRIPTION
        "This table allows configuration of groups of tunnels for PW path protection."
        ::= { genEquipServicesNGPW 11 }

genEquipServicesNGPWPSNTunnelGroupEntry OBJECT-TYPE
        SYNTAX GenEquipServicesNGPWPSNTunnelGroupEntry
        ACCESS not-accessible
        STATUS mandatory
		DESCRIPTION
		"This table entry allows configuration of groups of tunnels for PW path protection."
        INDEX { genEquipServicesNGPWPSNTunnelGroupSlot,
				genEquipServicesNGPWPSNTunnelGroupId }
        ::= { genEquipServicesNGPWPSNTunnelGroupTable 1 }

GenEquipServicesNGPWPSNTunnelGroupEntry ::=
		SEQUENCE {
			genEquipServicesNGPWPSNTunnelGroupSlot
				INTEGER,
			genEquipServicesNGPWPSNTunnelGroupId
				INTEGER,
			genEquipServicesNGPWPSNTunnelGroupPrimaryId
                INTEGER,
			genEquipServicesNGPWPSNTunnelGroupSecondaryId
                INTEGER,
			genEquipServicesNGPWPSNTunnelGroupAdmin
                EnableDisableSMI2,
			genEquipServicesNGPWPSNTunnelGroupRevertive
				EnableDisableSMI2,
			genEquipServicesNGPWPSNTunnelGroupProtectionMode
				EnableDisableSMI2,
			genEquipServicesNGPWPSNTunnelGroupRowStatus
				RowStatus
}

genEquipServicesNGPWPSNTunnelGroupSlot		OBJECT-TYPE
		SYNTAX 		INTEGER
		ACCESS		read-write
        STATUS		mandatory
        DESCRIPTION
		"Slot where PW-LIC is inserted."
::= { genEquipServicesNGPWPSNTunnelGroupEntry 1 }

genEquipServicesNGPWPSNTunnelGroupId		OBJECT-TYPE
		SYNTAX 		INTEGER
		ACCESS		read-write
        STATUS		mandatory
        DESCRIPTION
		"Indicates the corresponding PSN Tunnel Protection Group."
::= { genEquipServicesNGPWPSNTunnelGroupEntry 2 }

genEquipServicesNGPWPSNTunnelGroupPrimaryId		OBJECT-TYPE
		SYNTAX 		INTEGER
		ACCESS		read-write
        STATUS		mandatory
        DESCRIPTION
		"Tunnel ID for the primary path."

::= { genEquipServicesNGPWPSNTunnelGroupEntry 3 }

genEquipServicesNGPWPSNTunnelGroupSecondaryId		OBJECT-TYPE
		SYNTAX 		INTEGER (1..128)
		ACCESS		read-write
        STATUS		mandatory
        DESCRIPTION
		"Tunnel ID for the secondary path."

::= { genEquipServicesNGPWPSNTunnelGroupEntry 4 }

genEquipServicesNGPWPSNTunnelGroupAdmin		OBJECT-TYPE
		SYNTAX 		EnableDisableSMI2
		ACCESS		read-write
        STATUS		mandatory
        DESCRIPTION
		"Admin."

::= { genEquipServicesNGPWPSNTunnelGroupEntry 5 }

genEquipServicesNGPWPSNTunnelGroupRevertive 		OBJECT-TYPE
		SYNTAX 		EnableDisableSMI2
		ACCESS		read-write
        STATUS		mandatory
        DESCRIPTION
		"Enable for revertive protection. Default is disabled."

::= { genEquipServicesNGPWPSNTunnelGroupEntry 6 }

genEquipServicesNGPWPSNTunnelGroupProtectionMode 		OBJECT-TYPE
		SYNTAX 		EnableDisableSMI2
		ACCESS		read-write
        STATUS		mandatory
        DESCRIPTION
		"Protection mode 1+1."

::= { genEquipServicesNGPWPSNTunnelGroupEntry 7 }

genEquipServicesNGPWPSNTunnelGroupRowStatus		OBJECT-TYPE
		SYNTAX 		RowStatus
		ACCESS		read-write
        STATUS		mandatory
        DESCRIPTION
		"This value is the status of the entry."
::= { genEquipServicesNGPWPSNTunnelGroupEntry 30 }

--
-- PW Tunnel group status table - pw-psn-tunnel-group-status-table
--

genEquipServicesNGPWPSNTunnelGroupStatusTable  OBJECT-TYPE
        SYNTAX  SEQUENCE OF GenEquipServicesNGPWPSNTunnelGroupStatusEntry
        ACCESS  not-accessible
        STATUS mandatory
        DESCRIPTION
        "This table contains status of path protection tunnels."
        ::= { genEquipServicesNGPW 12 }

genEquipServicesNGPWPSNTunnelGroupStatusEntry OBJECT-TYPE
        SYNTAX GenEquipServicesNGPWPSNTunnelGroupStatusEntry
        ACCESS not-accessible
        STATUS mandatory
		DESCRIPTION
		"This table entry contains status of path protection tunnels."
        INDEX { genEquipServicesNGPWPSNTunnelGroupStatusSlot,
				genEquipServicesNGPWPSNTunnelGroupStatusId }
        ::= { genEquipServicesNGPWPSNTunnelGroupStatusTable 1 }

GenEquipServicesNGPWPSNTunnelGroupStatusEntry ::=
		SEQUENCE {
			genEquipServicesNGPWPSNTunnelGroupStatusSlot
				INTEGER,
			genEquipServicesNGPWPSNTunnelGroupStatusId
				INTEGER,
			genEquipServicesNGPWPSNTunnelGroupStatusOperStatus
                DownUp,
			genEquipServicesNGPWPSNTunnelGroupStatusProtectionCommand
                TunnelGroupProtectionCmd,
			genEquipServicesNGPWPSNTunnelGroupStatusProtectionSwitches
                INTEGER,
			genEquipServicesNGPWPSNTunnelGroupStatusActiveTunnel
				INTEGER,
			genEquipServicesNGPWPSNTunnelGroupStatusClearStats
				OffOn,
			genEquipServicesNGPWPSNTunnelGroupStatusRevertiveCountdown
				INTEGER
}

genEquipServicesNGPWPSNTunnelGroupStatusSlot		OBJECT-TYPE
		SYNTAX 		INTEGER
		ACCESS		read-only
        STATUS		mandatory
        DESCRIPTION
		"Slot where PW-LIC is inserted."
::= { genEquipServicesNGPWPSNTunnelGroupStatusEntry 1 }

genEquipServicesNGPWPSNTunnelGroupStatusId		OBJECT-TYPE
		SYNTAX 		INTEGER
		ACCESS		read-only
        STATUS		mandatory
        DESCRIPTION
		"Tunnel group ID."
::= { genEquipServicesNGPWPSNTunnelGroupStatusEntry 2 }

genEquipServicesNGPWPSNTunnelGroupStatusOperStatus		OBJECT-TYPE
		SYNTAX 		DownUp
		ACCESS		read-only
        STATUS		mandatory
        DESCRIPTION
		"Tunnel group operational state."

::= { genEquipServicesNGPWPSNTunnelGroupStatusEntry 3 }

genEquipServicesNGPWPSNTunnelGroupStatusProtectionCommand		OBJECT-TYPE
		SYNTAX 		TunnelGroupProtectionCmd
		ACCESS		read-write
        STATUS		mandatory
        DESCRIPTION
		"User command to perform a path protection switch."

::= { genEquipServicesNGPWPSNTunnelGroupStatusEntry 4 }

genEquipServicesNGPWPSNTunnelGroupStatusProtectionSwitches		OBJECT-TYPE
		SYNTAX 		INTEGER
		ACCESS		read-only
        STATUS		mandatory
        DESCRIPTION
		"A counter of PSN tunnel protection switches."

::= { genEquipServicesNGPWPSNTunnelGroupStatusEntry 5 }

genEquipServicesNGPWPSNTunnelGroupStatusActiveTunnel		OBJECT-TYPE
		SYNTAX 		INTEGER
		ACCESS		read-only
        STATUS		mandatory
        DESCRIPTION
		"Current active PSN tunnel."
::= { genEquipServicesNGPWPSNTunnelGroupStatusEntry 6 }

genEquipServicesNGPWPSNTunnelGroupStatusClearStats		OBJECT-TYPE
		SYNTAX 		OffOn
		ACCESS		read-write
        STATUS		mandatory
        DESCRIPTION
		"User command to clear number of switches counter."
::= { genEquipServicesNGPWPSNTunnelGroupStatusEntry 7 }

genEquipServicesNGPWPSNTunnelGroupStatusRevertiveCountdown		OBJECT-TYPE
		SYNTAX 		OffOn
		ACCESS		read-only
        STATUS		mandatory
        DESCRIPTION
		"Time left until revertive switch is performed."
::= { genEquipServicesNGPWPSNTunnelGroupStatusEntry 8 }


--
-- PW Maintenance Domain configuration table - pw-soam-md-configuration-table
--

genEquipServicesNGPWSOAMMDTable  OBJECT-TYPE
        SYNTAX  SEQUENCE OF GenEquipServicesNGPWSOAMMDEntry
        ACCESS  not-accessible
        STATUS mandatory
        DESCRIPTION
        "This table allows configuration of MD parameters at the PW card."
        ::= { genEquipServicesNGPW 13 }

genEquipServicesNGPWSOAMMDEntry OBJECT-TYPE
        SYNTAX GenEquipServicesNGPWSOAMMDEntry
        ACCESS not-accessible
        STATUS mandatory
		DESCRIPTION
		"This table entry allows configuration of MD parameters at the PW card."
        INDEX { genEquipServicesNGPWSOAMMDSlot,
				genEquipServicesNGPWSOAMMDId }
        ::= { genEquipServicesNGPWSOAMMDTable 1 }

GenEquipServicesNGPWSOAMMDEntry ::=
		SEQUENCE {
			genEquipServicesNGPWSOAMMDSlot
				INTEGER,
			genEquipServicesNGPWSOAMMDId
				INTEGER,
			genEquipServicesNGPWSOAMMDName
                DisplayString,
			genEquipServicesNGPWSOAMMDLevel
                INTEGER,
			genEquipServicesNGPWSOAMMDRowStatus
				RowStatus
}

genEquipServicesNGPWSOAMMDSlot		OBJECT-TYPE
		SYNTAX 		INTEGER
		ACCESS		read-only
        STATUS		mandatory
        DESCRIPTION
		"Slot where PW-LIC is inserted."
::= { genEquipServicesNGPWSOAMMDEntry 1 }

genEquipServicesNGPWSOAMMDId		OBJECT-TYPE
		SYNTAX 		INTEGER
		ACCESS		read-only
        STATUS		mandatory
        DESCRIPTION
		"Maintenance Domain ID."
::= { genEquipServicesNGPWSOAMMDEntry 2 }

genEquipServicesNGPWSOAMMDName		OBJECT-TYPE
		SYNTAX 		DisplayString
		ACCESS		read-write
        STATUS		mandatory
        DESCRIPTION
		"Maintenance Domain Name."

::= { genEquipServicesNGPWSOAMMDEntry 3 }

genEquipServicesNGPWSOAMMDLevel		OBJECT-TYPE
		SYNTAX 		INTEGER
		ACCESS		read-write
        STATUS		mandatory
        DESCRIPTION
		"Maintenance Domain level."

::= { genEquipServicesNGPWSOAMMDEntry 4 }

genEquipServicesNGPWSOAMMDRowStatus		OBJECT-TYPE
		SYNTAX 		RowStatus
		ACCESS		read-write
        STATUS		mandatory
        DESCRIPTION
		"Row status to allow user add entries dynamically."

::= { genEquipServicesNGPWSOAMMDEntry 30 }

--
-- PW Maintenance Association configuration table - pw-soam-ma-configuration-table
--

genEquipServicesNGPWSOAMMATable  OBJECT-TYPE
        SYNTAX  SEQUENCE OF GenEquipServicesNGPWSOAMMAEntry
        ACCESS  not-accessible
        STATUS mandatory
        DESCRIPTION
        "This table allows configuration of MA parameters at the PW card."
        ::= { genEquipServicesNGPW 14 }

genEquipServicesNGPWSOAMMAEntry OBJECT-TYPE
        SYNTAX GenEquipServicesNGPWSOAMMAEntry
        ACCESS not-accessible
        STATUS mandatory
		DESCRIPTION
		"This table entry allows configuration of MA parameters at the PW card."
        INDEX { genEquipServicesNGPWSOAMMASlot,
				genEquipServicesNGPWSOAMMAId }
        ::= { genEquipServicesNGPWSOAMMATable 1 }

GenEquipServicesNGPWSOAMMAEntry ::=
		SEQUENCE {
			genEquipServicesNGPWSOAMMASlot
				INTEGER,
			genEquipServicesNGPWSOAMMAId
				INTEGER,
			genEquipServicesNGPWSOAMMAName
                DisplayString,
			genEquipServicesNGPWSOAMMAMdId
				INTEGER,
			genEquipServicesNGPWSOAMMALocalMepId
				INTEGER,
			genEquipServicesNGPWSOAMMARemoteMepId
				INTEGER,
			genEquipServicesNGPWSOAMMAVid
				INTEGER,
			genEquipServicesNGPWSOAMMAVlanType
				PWTunnelVlanType,
			genEquipServicesNGPWSOAMMACCMAdmin
				EnableDisableSMI2,
			genEquipServicesNGPWSOAMMACCMInterval
				PWSOAMccmInterval,
			genEquipServicesNGPWSOAMMACCMLTMPriority
				INTEGER,
			genEquipServicesNGPWSOAMMARowStatus
				RowStatus
}

genEquipServicesNGPWSOAMMASlot		OBJECT-TYPE
		SYNTAX 		INTEGER
		ACCESS		read-only
        STATUS		mandatory
        DESCRIPTION
		"Slot ID."
::= { genEquipServicesNGPWSOAMMAEntry 1 }

genEquipServicesNGPWSOAMMAId		OBJECT-TYPE
		SYNTAX 		INTEGER
		ACCESS		read-only
        STATUS		mandatory
        DESCRIPTION
		"Maintenance association ID."
::= { genEquipServicesNGPWSOAMMAEntry 2 }

genEquipServicesNGPWSOAMMAName		OBJECT-TYPE
		SYNTAX 		DisplayString
		ACCESS		read-write
        STATUS		mandatory
        DESCRIPTION
		"Maintenance Association name."

::= { genEquipServicesNGPWSOAMMAEntry 3 }

genEquipServicesNGPWSOAMMAMdId		OBJECT-TYPE
		SYNTAX 		INTEGER
		ACCESS		read-write
        STATUS		mandatory
        DESCRIPTION
		"Maintenance Domain ID."

::= { genEquipServicesNGPWSOAMMAEntry 4 }

genEquipServicesNGPWSOAMMALocalMepId		OBJECT-TYPE
		SYNTAX 		INTEGER
		ACCESS		read-write
        STATUS		mandatory
        DESCRIPTION
		"Local MEP ID."

::= { genEquipServicesNGPWSOAMMAEntry 5 }

genEquipServicesNGPWSOAMMARemoteMepId		OBJECT-TYPE
		SYNTAX 		INTEGER
		ACCESS		read-write
        STATUS		mandatory
        DESCRIPTION
		"Remote MEP ID."

::= { genEquipServicesNGPWSOAMMAEntry 6 }

genEquipServicesNGPWSOAMMAVid		OBJECT-TYPE
		SYNTAX 		INTEGER
		ACCESS		read-write
        STATUS		mandatory
        DESCRIPTION
		"VLAN ID of the Maintenance Association."

::= { genEquipServicesNGPWSOAMMAEntry 7 }

genEquipServicesNGPWSOAMMAVlanType		OBJECT-TYPE
		SYNTAX 		PWTunnelVlanType
		ACCESS		read-write
        STATUS		mandatory
        DESCRIPTION
		"VLAN type of the Maintenance Association."

::= { genEquipServicesNGPWSOAMMAEntry 8 }

genEquipServicesNGPWSOAMMACCMAdmin		OBJECT-TYPE
		SYNTAX 		EnableDisableSMI2
		ACCESS		read-write
        STATUS		mandatory
        DESCRIPTION
		"Maintenance Association CCM administrative status."

::= { genEquipServicesNGPWSOAMMAEntry 9 }

genEquipServicesNGPWSOAMMACCMInterval		OBJECT-TYPE
		SYNTAX 		PWSOAMccmInterval
		ACCESS		read-write
        STATUS		mandatory
        DESCRIPTION
		"Maintenance Association CCM Interval."

::= { genEquipServicesNGPWSOAMMAEntry 10 }

genEquipServicesNGPWSOAMMACCMLTMPriority		OBJECT-TYPE
		SYNTAX 		INTEGER
		ACCESS		read-write
        STATUS		mandatory
        DESCRIPTION
		"Maintenance Association link trace message priority."

::= { genEquipServicesNGPWSOAMMAEntry 11 }

genEquipServicesNGPWSOAMMARowStatus		OBJECT-TYPE
		SYNTAX 		RowStatus
		ACCESS		read-write
        STATUS		mandatory
        DESCRIPTION
		"Row status to allow user add entries dynamically."

::= { genEquipServicesNGPWSOAMMAEntry 30 }

--
-- PW Maintenance Association status table - pw-soam-ma-status-table
--

genEquipServicesNGPWSOAMMAStatusTable  OBJECT-TYPE
        SYNTAX  SEQUENCE OF GenEquipServicesNGPWSOAMMAStatusEntry
        ACCESS  not-accessible
        STATUS mandatory
        DESCRIPTION
        "This table shows the SOAM status of each MA at the PW card level."
        ::= { genEquipServicesNGPW 15 }

genEquipServicesNGPWSOAMMAStatusEntry OBJECT-TYPE
        SYNTAX GenEquipServicesNGPWSOAMMAStatusEntry
        ACCESS not-accessible
        STATUS mandatory
		DESCRIPTION
		"This table entry shows the SOAM status of each MA at the PW card level."
        INDEX { genEquipServicesNGPWSOAMMAStatusSlot,
				genEquipServicesNGPWSOAMMAStatusId }
        ::= { genEquipServicesNGPWSOAMMAStatusTable 1 }

GenEquipServicesNGPWSOAMMAStatusEntry ::=
		SEQUENCE {
			genEquipServicesNGPWSOAMMAStatusSlot
				INTEGER,
			genEquipServicesNGPWSOAMMAStatusId
				INTEGER,
			genEquipServicesNGPWSOAMMAStatusRemoteMepMACAddr
                MacAddress,
			genEquipServicesNGPWSOAMMAStatusDefects
				INTEGER
}

genEquipServicesNGPWSOAMMAStatusSlot		OBJECT-TYPE
		SYNTAX 		INTEGER
		ACCESS		read-only
        STATUS		mandatory
        DESCRIPTION
		"Slot ID."
::= { genEquipServicesNGPWSOAMMAStatusEntry 1 }

genEquipServicesNGPWSOAMMAStatusId		OBJECT-TYPE
		SYNTAX 		INTEGER
		ACCESS		read-only
        STATUS		mandatory
        DESCRIPTION
		"Maintenance association ID."
::= { genEquipServicesNGPWSOAMMAStatusEntry 2 }

genEquipServicesNGPWSOAMMAStatusRemoteMepMACAddr		OBJECT-TYPE
		SYNTAX 		MacAddress
		ACCESS		read-only
        STATUS		mandatory
        DESCRIPTION
		"Remote MEP MAC Address."

::= { genEquipServicesNGPWSOAMMAStatusEntry 3 }

genEquipServicesNGPWSOAMMAStatusDefects		OBJECT-TYPE
		SYNTAX 		INTEGER
		ACCESS		read-only
        STATUS		mandatory
        DESCRIPTION
		"Bitmap field: no-alarm (0), RDI (1), MAC-status (2), remote CCM (4), error CCM (8), Cross-connection CCM (16), AIS (32)."

::= { genEquipServicesNGPWSOAMMAStatusEntry 4 }

--
-- Service TDM Scalars.
--
genEquipServicesNGPWTDM	OBJECT IDENTIFIER ::= {genEquipServicesNGPW 20}

genEquipServicesNGPWTDMRevertiveTimer		OBJECT-TYPE
		SYNTAX 		INTEGER
		ACCESS		read-write
        STATUS		mandatory
        DESCRIPTION
		"The WTR (Wait To Restore) timer for revertive switches."
::= { genEquipServicesNGPWTDM 1 }

genEquipServicesNGPWRangeVC 		OBJECT-TYPE
		SYNTAX 		INTEGER
		ACCESS		read-write
        STATUS		mandatory
        DESCRIPTION
		"TDM services VC range."
::= { genEquipServicesNGPWTDM 2 }

genEquipServicesNGPWOffsetVC 		OBJECT-TYPE
		SYNTAX 		INTEGER
		ACCESS		read-write
        STATUS		mandatory
        DESCRIPTION
		"TDM services VC offset."
::= { genEquipServicesNGPWTDM 3 }

genEquipServicesNGPWLatencyOptimizationAdmin 		OBJECT-TYPE
		SYNTAX 		EnableDisable
		ACCESS		read-write
        STATUS		mandatory
        DESCRIPTION
		"Enables/Disables the option of choosing a latency-optimized mode for TDM services."
::= { genEquipServicesNGPWTDM 4 }


--
-- PSN tunnel groups table, (addition for PWC Phase-2)
--
genEquipServicesPWPSNTunnelGroupsTable  OBJECT-TYPE
        SYNTAX  SEQUENCE OF GenEquipServicesPWPSNTunnelGroupsEntry
        ACCESS  not-accessible
        STATUS mandatory
        DESCRIPTION
        "This table allows configuration of PSN protection groups for pseudowire service path protection."
        ::= { genEquipServicesPW 10 }

genEquipServicesPWPSNTunnelGroupsEntry OBJECT-TYPE
        SYNTAX GenEquipServicesPWPSNTunnelGroupsEntry
        ACCESS not-accessible
        STATUS mandatory
		DESCRIPTION
		"This entry table allows configuration of PSN protection groups for pseudowire service path protection."
        INDEX { genEquipServicesPWPSNTunnelGroupsTunnelGroupID }
        ::= { genEquipServicesPWPSNTunnelGroupsTable 1 }

GenEquipServicesPWPSNTunnelGroupsEntry ::=
		SEQUENCE {
			genEquipServicesPWPSNTunnelGroupsTunnelGroupID
				INTEGER,
			genEquipServicesPWPSNTunnelGroupsTunnelIDPrimary
                INTEGER,
			genEquipServicesPWPSNTunnelGroupsTunnelIDSecondary
                INTEGER,
			genEquipServicesPWPSNTunnelGroupsSwitchToStandby
                OffOn,
			genEquipServicesPWPSNTunnelGroupsRowStatus
				RowStatus
}

genEquipServicesPWPSNTunnelGroupsTunnelGroupID		OBJECT-TYPE
		SYNTAX 		INTEGER (1..64)
		ACCESS		read-write
        STATUS		mandatory
        DESCRIPTION
		"PSN Tunnel Group ID."
::= { genEquipServicesPWPSNTunnelGroupsEntry 1 }

genEquipServicesPWPSNTunnelGroupsTunnelIDPrimary		OBJECT-TYPE
		SYNTAX 		INTEGER (1..128)
		ACCESS		read-write
        STATUS		mandatory
        DESCRIPTION
		"Primary PSN tunnel ID."

::= { genEquipServicesPWPSNTunnelGroupsEntry 2 }

genEquipServicesPWPSNTunnelGroupsTunnelIDSecondary		OBJECT-TYPE
		SYNTAX 		INTEGER (1..128)
		ACCESS		read-write
        STATUS		mandatory
        DESCRIPTION
		"Secondary PSN tunnel ID."

::= { genEquipServicesPWPSNTunnelGroupsEntry 3 }

genEquipServicesPWPSNTunnelGroupsSwitchToStandby		OBJECT-TYPE
		SYNTAX 		OffOn
		ACCESS		read-write
        STATUS		mandatory
        DESCRIPTION
		"Force a switch from primary to secondary tunnel."

::= { genEquipServicesPWPSNTunnelGroupsEntry 4 }

genEquipServicesPWPSNTunnelGroupsRowStatus		OBJECT-TYPE
		SYNTAX 		RowStatus
		ACCESS		read-write
        STATUS		mandatory
        DESCRIPTION
		"This value is the status of the entry."
::= { genEquipServicesPWPSNTunnelGroupsEntry 30 }

-- PSN tunnel groups status table, (addition for PWC Phase-2)

genEquipServicesPWPSNTunnelGroupStatusTable  OBJECT-TYPE
        SYNTAX  SEQUENCE OF GenEquipServicesPWPSNTunnelGroupStatusEntry
        ACCESS  not-accessible
        STATUS mandatory
        DESCRIPTION
        "This table allows monitoring of PSN protection groups status."
        ::= { genEquipServicesPW 11 }

genEquipServicesPWPSNTunnelGroupStatusEntry OBJECT-TYPE
        SYNTAX GenEquipServicesPWPSNTunnelGroupStatusEntry
        ACCESS not-accessible
        STATUS mandatory
		DESCRIPTION
		"This table entry allows monitoring of PSN protection groups status."
        INDEX { genEquipServicesPWPSNTunnelGroupStatusTunnelGroupID }
        ::= { genEquipServicesPWPSNTunnelGroupStatusTable 1 }

GenEquipServicesPWPSNTunnelGroupStatusEntry ::=
		SEQUENCE {
			genEquipServicesPWPSNTunnelGroupStatusTunnelGroupID
				INTEGER,
			genEquipServicesPWPSNTunnelGroupStatusCurrActiveTunnel
                INTEGER,
			genEquipServicesPWPSNTunnelGroupStatusNumProtSwitches
                INTEGER
}

genEquipServicesPWPSNTunnelGroupStatusTunnelGroupID		OBJECT-TYPE
		SYNTAX 		INTEGER (1..64)
		ACCESS		read-only
        STATUS		mandatory
        DESCRIPTION
		"PSN Tunnel Group ID."
::= { genEquipServicesPWPSNTunnelGroupStatusEntry 1 }

genEquipServicesPWPSNTunnelGroupStatusCurrActiveTunnel		OBJECT-TYPE
		SYNTAX 		INTEGER {
						primary(0),
						secondary(1)
		}
		ACCESS		read-only
        STATUS		mandatory
        DESCRIPTION
		"Currently active PSN tunnel."

::= { genEquipServicesPWPSNTunnelGroupStatusEntry 2 }

genEquipServicesPWPSNTunnelGroupStatusNumProtSwitches		OBJECT-TYPE
		SYNTAX 		INTEGER
		ACCESS		read-only
        STATUS		mandatory
        DESCRIPTION
		"Counter of PSN tunnel protection switches."

::= { genEquipServicesPWPSNTunnelGroupStatusEntry 3 }

-- SOAM MD definitions table, (addition for PWC Phase-2)

genEquipServicesPWSOAMMDTable  OBJECT-TYPE
        SYNTAX  SEQUENCE OF GenEquipServicesPWSOAMMDEntry
        ACCESS  not-accessible
        STATUS mandatory
        DESCRIPTION
        "This table allows configuration of Ethernet OAM Maintenance Domains for service monitoring and path protection."
        ::= { genEquipServicesPW 12 }

genEquipServicesPWSOAMMDEntry OBJECT-TYPE
        SYNTAX GenEquipServicesPWSOAMMDEntry
        ACCESS not-accessible
        STATUS mandatory
		DESCRIPTION
		"This table entry allows configuration of Ethernet OAM Maintenance Domains for service monitoring and path protection."
        INDEX { genEquipServicesPWSOAMMDDomainID }
        ::= { genEquipServicesPWSOAMMDTable 1 }

GenEquipServicesPWSOAMMDEntry ::=
		SEQUENCE {
			genEquipServicesPWSOAMMDDomainID
				INTEGER,
			genEquipServicesPWSOAMMDDomainName
                DisplayString,
			genEquipServicesPWSOAMMDDomainLevel
                INTEGER,
			genEquipServicesPWSOAMMDRowStatus
				RowStatus
}

genEquipServicesPWSOAMMDDomainID		OBJECT-TYPE
		SYNTAX 		INTEGER (1..8)
		ACCESS		read-write
        STATUS		mandatory
        DESCRIPTION
		"Domain ID."
::= { genEquipServicesPWSOAMMDEntry 1 }

genEquipServicesPWSOAMMDDomainName		OBJECT-TYPE
		SYNTAX 		DisplayString
		ACCESS		read-write
        STATUS		mandatory
        DESCRIPTION
		"Domain Name."

::= { genEquipServicesPWSOAMMDEntry 2 }

genEquipServicesPWSOAMMDDomainLevel		OBJECT-TYPE
		SYNTAX 		INTEGER (0..7)
		ACCESS		read-write
        STATUS		mandatory
        DESCRIPTION
		"Domain Level."

::= { genEquipServicesPWSOAMMDEntry 3 }

genEquipServicesPWSOAMMDRowStatus		OBJECT-TYPE
		SYNTAX 		RowStatus
		ACCESS		read-write
        STATUS		mandatory
        DESCRIPTION
		"This value is the status of the entry."
::= { genEquipServicesPWSOAMMDEntry 30 }

-- SOAM MA definitions table, (addition for PWC Phase-2)

genEquipServicesPWSOAMMATable  OBJECT-TYPE
        SYNTAX  SEQUENCE OF GenEquipServicesPWSOAMMAEntry
        ACCESS  not-accessible
        STATUS mandatory
        DESCRIPTION
        "This table allows configuration of Ethernet OAM Maintenance Association for service monitoring and path protection."
        ::= { genEquipServicesPW 13 }

genEquipServicesPWSOAMMAEntry OBJECT-TYPE
        SYNTAX GenEquipServicesPWSOAMMAEntry
        ACCESS not-accessible
        STATUS mandatory
		DESCRIPTION
		"This table entry allows configuration of Ethernet OAM Maintenance Association for service monitoring and path protection."
        INDEX { genEquipServicesPWSOAMMALocalID }
        ::= { genEquipServicesPWSOAMMATable 1 }

GenEquipServicesPWSOAMMAEntry ::=
		SEQUENCE {
			genEquipServicesPWSOAMMALocalID
				INTEGER,
			genEquipServicesPWSOAMMALocalName
                DisplayString,
			genEquipServicesPWSOAMMADomainID
                INTEGER,
			genEquipServicesPWSOAMMAAdmin
                EnableDisable,
			genEquipServicesPWSOAMMALocalMEP
                INTEGER,
			genEquipServicesPWSOAMMARemoteMEP
                INTEGER,
			genEquipServicesPWSOAMMAVlanType
                INTEGER,
			genEquipServicesPWSOAMMAVlanID
                INTEGER,
			genEquipServicesPWSOAMMACCMInterval
                INTEGER,
			genEquipServicesPWSOAMMACCMAdmin
                EnableDisable,
			genEquipServicesPWSOAMMACCMPriority
                INTEGER,
			genEquipServicesPWSOAMMARemoteMEPAddr
                OCTET STRING,
			genEquipServicesPWSOAMMADefects
                INTEGER,
			genEquipServicesPWSOAMMARowStatus
				RowStatus
}

genEquipServicesPWSOAMMALocalID		OBJECT-TYPE
		SYNTAX 		INTEGER (1..32)
		ACCESS		read-write
        STATUS		mandatory
        DESCRIPTION
		"Maintenance Association local ID."
::= { genEquipServicesPWSOAMMAEntry 1 }

genEquipServicesPWSOAMMALocalName		OBJECT-TYPE
		SYNTAX 		DisplayString
		ACCESS		read-write
        STATUS		mandatory
        DESCRIPTION
		"Maintenance Association local Name."

::= { genEquipServicesPWSOAMMAEntry 2 }

genEquipServicesPWSOAMMADomainID		OBJECT-TYPE
		SYNTAX 		INTEGER (0..7)
		ACCESS		read-write
        STATUS		mandatory
        DESCRIPTION
		"Maintenance Association domain ID."

::= { genEquipServicesPWSOAMMAEntry 3 }

genEquipServicesPWSOAMMAAdmin		OBJECT-TYPE
		SYNTAX 		EnableDisable
		ACCESS		read-write
        STATUS		mandatory
        DESCRIPTION
		"Maintenance Association Admin."

::= { genEquipServicesPWSOAMMAEntry 4 }

genEquipServicesPWSOAMMALocalMEP		OBJECT-TYPE
		SYNTAX 		INTEGER (1..8191)
		ACCESS		read-write
        STATUS		mandatory
        DESCRIPTION
		"Maintenance Association local MEP ID."

::= { genEquipServicesPWSOAMMAEntry 5 }

genEquipServicesPWSOAMMARemoteMEP		OBJECT-TYPE
		SYNTAX 		INTEGER (1..8191)
		ACCESS		read-write
        STATUS		mandatory
        DESCRIPTION
		"Maintenance Association remote MEP ID."

::= { genEquipServicesPWSOAMMAEntry 6 }

genEquipServicesPWSOAMMAVlanType		OBJECT-TYPE
		SYNTAX 		INTEGER {
						none(0),
						c-type(1)
		}
		ACCESS		read-write
        STATUS		mandatory
        DESCRIPTION
		"VLAN type of the Maintenance Association."

::= { genEquipServicesPWSOAMMAEntry 7 }

genEquipServicesPWSOAMMAVlanID		OBJECT-TYPE
		SYNTAX 		INTEGER (0..4090)
		ACCESS		read-write
        STATUS		mandatory
        DESCRIPTION
		"VLAN Id of the Maintenance Association."

::= { genEquipServicesPWSOAMMAEntry 8 }

genEquipServicesPWSOAMMACCMInterval		OBJECT-TYPE
		SYNTAX 		INTEGER {
						nInvalid(0),
						n3-3-msec(1),
						n10-msec(2),
						n100-msec(3),
						n1s(4),
						n10s(5),
						n1min(6),
						n10min(7)
		}

		ACCESS		read-write
        STATUS		mandatory
        DESCRIPTION
		"CCM Interval."

::= { genEquipServicesPWSOAMMAEntry 9 }

genEquipServicesPWSOAMMACCMAdmin		OBJECT-TYPE
		SYNTAX 		EnableDisable
		ACCESS		read-write
        STATUS		mandatory
        DESCRIPTION
		"Maintenance Association CCM admin."

::= { genEquipServicesPWSOAMMAEntry 10 }

genEquipServicesPWSOAMMACCMPriority		OBJECT-TYPE
		SYNTAX 		INTEGER (0..7)
		ACCESS		read-write
        STATUS		mandatory
        DESCRIPTION
		"CCM Priority."

::= { genEquipServicesPWSOAMMAEntry 11 }

genEquipServicesPWSOAMMARemoteMEPAddr		OBJECT-TYPE
		SYNTAX 		OCTET STRING (SIZE(0..6))
		ACCESS		read-write
        STATUS		mandatory
        DESCRIPTION
		"MAC Address of the Maintenance Association Remote MEP."

::= { genEquipServicesPWSOAMMAEntry 12 }

genEquipServicesPWSOAMMADefects		OBJECT-TYPE
		SYNTAX 		INTEGER
		ACCESS		read-write
        STATUS		mandatory
        DESCRIPTION
		"Bitmap field: no-alarm (0), RDI (1), MAC-status (2), remote CCM (4), error CCM (8),
		Cross-connection CCM (16), AIS (32)."

::= { genEquipServicesPWSOAMMAEntry 13 }

genEquipServicesPWSOAMMARowStatus		OBJECT-TYPE
		SYNTAX 		RowStatus
		ACCESS		read-write
        STATUS		mandatory
        DESCRIPTION
		"This value is the status of the entry."
::= { genEquipServicesPWSOAMMAEntry 30 }


--
-- The following are the Services part of Switch application tables
--
genEquipServicesCet	OBJECT IDENTIFIER ::= {genEquipServices 5}

genEquipServicesCetGeneral	OBJECT IDENTIFIER ::= {genEquipServicesCet 1}

genEquipServicesCetSvlanEtherType		OBJECT-TYPE
		SYNTAX 		INTEGER {
						ether-type-0x88a8(0),
						ether-type-0x9100(1),
						ether-type-0x9200(2),
						ether-type-0x8100(3)
		}
		ACCESS		read-write
        STATUS		mandatory
        DESCRIPTION
		"S VLAN Ether type."
::= { genEquipServicesCetGeneral 1 }

genEquipServicesCetAgingTimeout		OBJECT-TYPE
		SYNTAX 		INTEGER (15..3825)
		ACCESS		read-write
        STATUS		mandatory
        DESCRIPTION
		"MAC forwarding entry aging timeout in seconds."
::= { genEquipServicesCetGeneral 2 }


--
-- Switch Application sw-ap-l3-srv-config-table
--

genEquipServicesCetConfigTable  OBJECT-TYPE
        SYNTAX  SEQUENCE OF GenEquipServicesCetConfigEntry
        ACCESS  not-accessible
        STATUS mandatory
        DESCRIPTION
        "Ethernet Services configuration table -
		the table describes the connectivity between the interface of the switch."
        ::= { genEquipServicesCet 2 }

genEquipServicesCetConfigEntry OBJECT-TYPE
        SYNTAX GenEquipServicesCetConfigEntry
        ACCESS not-accessible
        STATUS mandatory
          DESCRIPTION
        "Ethernet Services configuration table entry -
		the table describes the connectivity between the interface of the switch."
        INDEX { genEquipServicesCetConfigIndex }
        ::= { genEquipServicesCetConfigTable 1 }

GenEquipServicesCetConfigEntry ::=
		SEQUENCE {
			genEquipServicesCetConfigIndex
				INTEGER,
			genEquipServicesCetConfigType
				ServiceType,
			genEquipServicesCetConfigAdmin
				ServiceAdmin,
			genEquipServicesCetConfigMacTableSize
				INTEGER,
			genEquipServicesCetConfigDefaultCos
				INTEGER,
			genEquipServicesCetConfigCosMode
				ServiceCosMode,
			genEquipServicesCetConfigEvcId
				DisplayString,
			genEquipServicesCetConfigEvcDescription
				DisplayString,
			genEquipServicesCetConfigSplitHorizon
				EnableDisable,
			genEquipServicesCetConfigResiliencyProtocolInstance
				INTEGER,
			genEquipServicesCetConfigProtectingTrail
				INTEGER,
			genEquipServicesCetConfigProtectingTrailIndex
				INTEGER,
			genEquipServicesCetConfigServiceSubType
				ServiceSubType,
			genEquipServicesCetConfigTrailIndex
				INTEGER,
			genEquipServicesCetConfigRowStatus
				RowStatus
}


genEquipServicesCetConfigIndex		OBJECT-TYPE
		SYNTAX 		INTEGER  (1..1025)
		ACCESS		read-only
        STATUS		mandatory
        DESCRIPTION
		"Service ID."
::= { genEquipServicesCetConfigEntry 1 }

genEquipServicesCetConfigType		OBJECT-TYPE
		SYNTAX 		ServiceType
		ACCESS		read-write
        STATUS		mandatory
        DESCRIPTION
		"Ethernet Service Type (Management, MP, P2P)."
::= { genEquipServicesCetConfigEntry 2 }

genEquipServicesCetConfigAdmin		OBJECT-TYPE
		SYNTAX 		ServiceAdmin
		ACCESS		read-write
        STATUS		mandatory
        DESCRIPTION
		"Service Admin state."
::= { genEquipServicesCetConfigEntry 3 }

genEquipServicesCetConfigMacTableSize		OBJECT-TYPE
		SYNTAX 		INTEGER (16..131072)
		ACCESS		read-write
        STATUS		mandatory
        DESCRIPTION
		"MAC Table size of the service,granularity of 16."
::= { genEquipServicesCetConfigEntry 4 }

genEquipServicesCetConfigDefaultCos		OBJECT-TYPE
		SYNTAX 		INTEGER (0..7)
		ACCESS		read-write
        STATUS		mandatory
        DESCRIPTION
		"Service default CoS."
::= { genEquipServicesCetConfigEntry 5 }

genEquipServicesCetConfigCosMode		OBJECT-TYPE
		SYNTAX 		ServiceCosMode
		ACCESS		read-write
        STATUS		mandatory
        DESCRIPTION
		"Service CoS Color mode."
::= { genEquipServicesCetConfigEntry 6 }

genEquipServicesCetConfigEvcId		OBJECT-TYPE
		SYNTAX 		DisplayString
		ACCESS		read-write
        STATUS		mandatory
        DESCRIPTION
		"Ethernet Virtual Connection (EVC) ID."
::= { genEquipServicesCetConfigEntry 7 }

genEquipServicesCetConfigEvcDescription		OBJECT-TYPE
		SYNTAX 		DisplayString
		ACCESS		read-write
        STATUS		mandatory
        DESCRIPTION
		"Ethernet Virtual Connection (EVC) Description."
::= { genEquipServicesCetConfigEntry 8 }

genEquipServicesCetConfigSplitHorizon		OBJECT-TYPE
		SYNTAX 		EnableDisable
		ACCESS		read-write
        STATUS		mandatory
        DESCRIPTION
		"Split Horizon group Admin."
::= { genEquipServicesCetConfigEntry 9 }

genEquipServicesCetConfigResiliencyProtocolInstance		OBJECT-TYPE
		SYNTAX 		INTEGER
		ACCESS		read-write
        STATUS		mandatory
        DESCRIPTION
		"Resiliency Protocol Instance."
::= { genEquipServicesCetConfigEntry 10 }

genEquipServicesCetConfigProtectingTrail		OBJECT-TYPE
		SYNTAX 		INTEGER
		ACCESS		read-write
        STATUS		mandatory
        DESCRIPTION
		"Protecting trail."
::= { genEquipServicesCetConfigEntry 11 }

genEquipServicesCetConfigProtectingTrailIndex		OBJECT-TYPE
		SYNTAX 		INTEGER
		ACCESS		read-write
        STATUS		mandatory
        DESCRIPTION
		"Protecting trail id."
::= { genEquipServicesCetConfigEntry 12 }

genEquipServicesCetConfigServiceSubType		OBJECT-TYPE
		SYNTAX 		ServiceSubType
		ACCESS		read-write
        STATUS		mandatory
        DESCRIPTION
		"Service sub type (Ethernet / TDM / PWE)"
::= { genEquipServicesCetConfigEntry 13 }

genEquipServicesCetConfigTrailIndex		OBJECT-TYPE
		SYNTAX 		INTEGER
		ACCESS		read-write
        STATUS		mandatory
        DESCRIPTION
		"TDM Trail ID"
::= { genEquipServicesCetConfigEntry 14 }

genEquipServicesCetConfigRowStatus		OBJECT-TYPE
		SYNTAX 		RowStatus
		ACCESS		read-write
        STATUS		mandatory
        DESCRIPTION
		"Table Mib Row Status."
::= { genEquipServicesCetConfigEntry 30 }

--
-- Switch Application sw-ap-srv-status-multicast
--

genEquipServicesCetStatusTable  OBJECT-TYPE
        SYNTAX  SEQUENCE OF GenEquipServicesCetStatusEntry
        ACCESS  not-accessible
        STATUS mandatory
        DESCRIPTION
        "Ethernet Services status table - the table describes the status of the configured services."
        ::= { genEquipServicesCet 3 }

genEquipServicesCetStatusEntry OBJECT-TYPE
        SYNTAX GenEquipServicesCetStatusEntry
        ACCESS not-accessible
        STATUS mandatory
          DESCRIPTION
        "Ethernet Services status table - the table describes the status of the configured services entry."
        INDEX { genEquipServicesCetStatusIndex }
        ::= { genEquipServicesCetStatusTable 1 }

GenEquipServicesCetStatusEntry ::=
		SEQUENCE {
			genEquipServicesCetStatusIndex
				INTEGER,
			genEquipServicesCetStatusMulticast
				EnableDisable
}


genEquipServicesCetStatusIndex		OBJECT-TYPE
		SYNTAX 		INTEGER  (1..1025)
		ACCESS		read-only
        STATUS		mandatory
        DESCRIPTION
		"Service ID."
::= { genEquipServicesCetStatusEntry 1 }

genEquipServicesCetStatusMulticast		OBJECT-TYPE
		SYNTAX 		EnableDisable
		ACCESS		read-only
        STATUS		mandatory
        DESCRIPTION
		"Configured Multicast Group."
::= { genEquipServicesCetStatusEntry 2 }

--
-- Switch Application sw-ap-l4-srv-sp-config-table
--
genEquipServicesCetSpConfigTable  OBJECT-TYPE
        SYNTAX  SEQUENCE OF GenEquipServicesCetSpConfigEntry
        ACCESS  not-accessible
        STATUS mandatory
        DESCRIPTION
        "Ethernet Service Points (SP) configuration table -
		this table describes the ingress and egress attributes (operation) per SPs of each service."
        ::= { genEquipServicesCet 4 }

genEquipServicesCetSpConfigEntry OBJECT-TYPE
        SYNTAX GenEquipServicesCetSpConfigEntry
        ACCESS not-accessible
        STATUS mandatory
          DESCRIPTION
        "Ethernet Service Points (SP) configuration table entry -
		this table describes the ingress and egress attributes (operation) per SPs of each service."
        INDEX { genEquipServicesCetSpConfigServiceIndex,
				genEquipServicesCetSpConfigServicePointIndex }
        ::= { genEquipServicesCetSpConfigTable 1 }

GenEquipServicesCetSpConfigEntry ::=
		SEQUENCE {
			genEquipServicesCetSpConfigServiceIndex
				INTEGER,
			genEquipServicesCetSpConfigServicePointIndex
				INTEGER,
			genEquipServicesCetSpConfigSpType
				SPType,
			genEquipServicesCetSpConfigSpSubtype
				SPSubType,
			genEquipServicesCetSpConfigSpName
				DisplayString,
			genEquipServicesCetSpConfigIfIndex
				INTEGER,
			genEquipServicesCetSpConfigSvlanEncap
				INTEGER,
			genEquipServicesCetSpConfigCvlanEncap
				INTEGER,
			genEquipServicesCetSpConfigLearning
				EnableDisable,
			genEquipServicesCetSpConfigFlooding
				DisableAllowed,
			genEquipServicesCetSpConfigBroadcast
				DisableAllowed,
			genEquipServicesCetSpConfigCosMode
				SPCosMode,
			genEquipServicesCetSpConfigDefCos
				INTEGER,
			genEquipServicesCetSpConfigPclProfileId
				INTEGER,
			genEquipServicesCetSpConfigPclAdmin
				EnableDisable,
			genEquipServicesCetSpConfigMonitorCounterGroup
				INTEGER,
			genEquipServicesCetSpConfigSplitHorizon
				SplitHorizonGroup,
			genEquipServicesCetSpConfigSvlanEgressPreserve
				EnableDisable,
			genEquipServicesCetSpConfigSvlanCosPreserve
				EnableDisable,
			genEquipServicesCetSpConfigCvlanEgressPreserve
				EnableDisable,
			genEquipServicesCetSpConfigCvlanCosPreserve
				EnableDisable,
			genEquipServicesCetSpConfigMarkingMode
				EnableDisable,
			genEquipServicesCetSpConfigServiceClassId
				INTEGER,
			genEquipServicesCetSpConfigTcamClassification
				INTEGER,
			genEquipServicesCetSpConfigRowStatus
				RowStatus
}


genEquipServicesCetSpConfigServiceIndex		OBJECT-TYPE
		SYNTAX 		INTEGER  (1..1025)
		ACCESS		read-only
        STATUS		mandatory
        DESCRIPTION
		"Service ID."
::= { genEquipServicesCetSpConfigEntry 1 }

genEquipServicesCetSpConfigServicePointIndex		OBJECT-TYPE
		SYNTAX 		INTEGER	 (1..32)
		ACCESS		read-only
        STATUS		mandatory
        DESCRIPTION
		"Service Point ID."
::= { genEquipServicesCetSpConfigEntry 2 }

genEquipServicesCetSpConfigSpType		OBJECT-TYPE
		SYNTAX 		SPType
		ACCESS		read-write
        STATUS		mandatory
        DESCRIPTION
		"Service Point Type (SAP, SNP, PIPE, MNG)."
::= { genEquipServicesCetSpConfigEntry 3 }

genEquipServicesCetSpConfigSpSubtype		OBJECT-TYPE
		SYNTAX 		SPSubType
		ACCESS		read-write
        STATUS		mandatory
        DESCRIPTION
		"The Service Point Attached Interface Type."
::= { genEquipServicesCetSpConfigEntry 4 }

genEquipServicesCetSpConfigSpName		OBJECT-TYPE
		SYNTAX 		DisplayString
		ACCESS		read-write
        STATUS		mandatory
        DESCRIPTION
		"Service Point Name."
::= { genEquipServicesCetSpConfigEntry 5 }

genEquipServicesCetSpConfigIfIndex		OBJECT-TYPE
		SYNTAX 		INTEGER
		ACCESS		read-write
        STATUS		mandatory
        DESCRIPTION
		"Ethernet Logical port if-index ID."
::= { genEquipServicesCetSpConfigEntry 6 }

genEquipServicesCetSpConfigSvlanEncap		OBJECT-TYPE
		SYNTAX 		INTEGER (4096..4097)
		ACCESS		read-write
        STATUS		mandatory
        DESCRIPTION
		"S-Vlan Encapsulation."
::= { genEquipServicesCetSpConfigEntry 7 }

genEquipServicesCetSpConfigCvlanEncap		OBJECT-TYPE
		SYNTAX 		INTEGER (0..4097)
		ACCESS		read-write
        STATUS		mandatory
        DESCRIPTION
		"C-Vlan Encapsulation."
::= { genEquipServicesCetSpConfigEntry 8 }

genEquipServicesCetSpConfigLearning		OBJECT-TYPE
		SYNTAX 		EnableDisable
		ACCESS		read-write
        STATUS		mandatory
        DESCRIPTION
		"Service Point Learning Admin (disable / enable)."
::= { genEquipServicesCetSpConfigEntry 9 }

genEquipServicesCetSpConfigFlooding		OBJECT-TYPE
		SYNTAX 		DisableAllowed
		ACCESS		read-write
        STATUS		mandatory
        DESCRIPTION
		"SP Ingress aatribute - Allow Flooding of the incoming packet."
::= { genEquipServicesCetSpConfigEntry 10 }

genEquipServicesCetSpConfigBroadcast		OBJECT-TYPE
		SYNTAX 		DisableAllowed
		ACCESS		read-write
        STATUS		mandatory
        DESCRIPTION
		"SP Ingress aatribute - Allow Broadcast of the incoming packet."
::= { genEquipServicesCetSpConfigEntry 11 }

genEquipServicesCetSpConfigCosMode		OBJECT-TYPE
		SYNTAX 		SPCosMode
		ACCESS		read-write
        STATUS		mandatory
        DESCRIPTION
		"Service Point CoS Color mode."
::= { genEquipServicesCetSpConfigEntry 12 }

genEquipServicesCetSpConfigDefCos		OBJECT-TYPE
		SYNTAX 		INTEGER (0..7)
		ACCESS		read-write
        STATUS		mandatory
        DESCRIPTION
		"Service Point Default CoS."
::= { genEquipServicesCetSpConfigEntry 13 }

genEquipServicesCetSpConfigPclProfileId		OBJECT-TYPE
		SYNTAX 		INTEGER (0..63)
		ACCESS		read-write
        STATUS		mandatory
        DESCRIPTION
		"pcl-profile-id."
::= { genEquipServicesCetSpConfigEntry 14 }

genEquipServicesCetSpConfigPclAdmin		OBJECT-TYPE
		SYNTAX 		EnableDisable
		ACCESS		read-write
        STATUS		mandatory
        DESCRIPTION
		"PCL Admin."
::= { genEquipServicesCetSpConfigEntry 15 }

genEquipServicesCetSpConfigMonitorCounterGroup		OBJECT-TYPE
		SYNTAX 		INTEGER (1..16)
		ACCESS		read-write
        STATUS		mandatory
        DESCRIPTION
		"SP Ingress attribute - Assign the SP to a specific Monitor Counters Group."
::= { genEquipServicesCetSpConfigEntry 16 }

genEquipServicesCetSpConfigSplitHorizon		OBJECT-TYPE
		SYNTAX 		SplitHorizonGroup
		ACCESS		read-write
        STATUS		mandatory
        DESCRIPTION
		"Split Horizon Group."
::= { genEquipServicesCetSpConfigEntry 17 }

genEquipServicesCetSpConfigSvlanEgressPreserve		OBJECT-TYPE
		SYNTAX 		EnableDisable
		ACCESS		read-write
        STATUS		mandatory
        DESCRIPTION
		"SP Egress attribute - Preserve the S VLAN as it was on the Ingress Service Point."
::= { genEquipServicesCetSpConfigEntry 18 }

genEquipServicesCetSpConfigSvlanCosPreserve		OBJECT-TYPE
		SYNTAX 		EnableDisable
		ACCESS		read-write
        STATUS		mandatory
        DESCRIPTION
		"SP Egress attribute - Preserve the S VLAN CoS as it was on the Ingress Service Point."
::= { genEquipServicesCetSpConfigEntry 19 }

genEquipServicesCetSpConfigCvlanEgressPreserve		OBJECT-TYPE
		SYNTAX 		EnableDisable
		ACCESS		read-write
        STATUS		mandatory
        DESCRIPTION
		"SP Egress attribute - Preserve the C VLAN as it was on the Ingress Service Point."
::= { genEquipServicesCetSpConfigEntry 20 }

genEquipServicesCetSpConfigCvlanCosPreserve		OBJECT-TYPE
		SYNTAX 		EnableDisable
		ACCESS		read-write
        STATUS		mandatory
        DESCRIPTION
		"SP Egress attribute - Preserve the C VLAN CoS as it was on the Ingress Service Point."
::= { genEquipServicesCetSpConfigEntry 21 }

genEquipServicesCetSpConfigMarkingMode		OBJECT-TYPE
		SYNTAX 		EnableDisable
		ACCESS		read-write
        STATUS		mandatory
        DESCRIPTION
		"SP Ingress attribute - Enable / Disable Marking of the incoming packet."
::= { genEquipServicesCetSpConfigEntry 22 }

genEquipServicesCetSpConfigServiceClassId		OBJECT-TYPE
		SYNTAX 		INTEGER (0..63)
		ACCESS		read-write
        STATUS		mandatory
        DESCRIPTION
		"SP Egress attribute - Service Bundle ID."
::= { genEquipServicesCetSpConfigEntry 23 }

genEquipServicesCetSpConfigTcamClassification		OBJECT-TYPE
		SYNTAX 		INTEGER
		ACCESS		read-write
        STATUS		mandatory
        DESCRIPTION
		"TCAM-Classification."
::= { genEquipServicesCetSpConfigEntry 24 }

genEquipServicesCetSpConfigRowStatus		OBJECT-TYPE
		SYNTAX 		RowStatus
		ACCESS		read-write
        STATUS		mandatory
        DESCRIPTION
		"Table Mib Row Status."
::= { genEquipServicesCetSpConfigEntry 30 }

--
-- Switch Application sw-ap-l4-srv-sp-ingress-policer-profile-association-to-cos-table
--

genEquipServicesCetSpPolicerAssociationTable  OBJECT-TYPE
        SYNTAX  SEQUENCE OF GenEquipServicesCetSpPolicerAssociationEntry
        ACCESS  not-accessible
        STATUS mandatory
        DESCRIPTION
        "Service Point and Service Point CoS Policing configuration table."
        ::= { genEquipServicesCet 5 }

genEquipServicesCetSpPolicerAssociationEntry OBJECT-TYPE
        SYNTAX GenEquipServicesCetSpPolicerAssociationEntry
        ACCESS not-accessible
        STATUS mandatory
          DESCRIPTION
        "Service Point and Service Point CoS Policing configuration table."
        INDEX { genEquipServicesCetSpPolicerAssociationServiceIndex,
				genEquipServicesCetSpPolicerAssociationSpIndex }
        ::= { genEquipServicesCetSpPolicerAssociationTable 1 }

GenEquipServicesCetSpPolicerAssociationEntry ::=
		SEQUENCE {
			genEquipServicesCetSpPolicerAssociationServiceIndex
				INTEGER,
			genEquipServicesCetSpPolicerAssociationSpIndex
				INTEGER,
			genEquipServicesCetSpPolicerAssociationSpPolicerAdmin
				EnableDisable,
			genEquipServicesCetSpPolicerAssociationCos0Profile
				INTEGER,
			genEquipServicesCetSpPolicerAssociationCos0Admin
				EnableDisable,
			genEquipServicesCetSpPolicerAssociationCos1Profile
				INTEGER,
			genEquipServicesCetSpPolicerAssociationCos1Admin
				EnableDisable,
			genEquipServicesCetSpPolicerAssociationCos2Profile
				INTEGER,
			genEquipServicesCetSpPolicerAssociationCos2Admin
				INTEGER,
			genEquipServicesCetSpPolicerAssociationCos3Profile
				INTEGER,
			genEquipServicesCetSpPolicerAssociationCos3Admin
				DisableAllowed,
			genEquipServicesCetSpPolicerAssociationCos4Profile
				INTEGER,
			genEquipServicesCetSpPolicerAssociationCos4Admin
				EnableDisable,
			genEquipServicesCetSpPolicerAssociationCos5Profile
				INTEGER,
			genEquipServicesCetSpPolicerAssociationCos5Admin
				EnableDisable,
			genEquipServicesCetSpPolicerAssociationCos6Profile
				INTEGER,
			genEquipServicesCetSpPolicerAssociationCos6Admin
				EnableDisable,
			genEquipServicesCetSpPolicerAssociationCos7Profile
				INTEGER,
			genEquipServicesCetSpPolicerAssociationCos7Admin
				EnableDisable,
			genEquipServicesCetSpPolicerAssociationRowStatus
				RowStatus
}


genEquipServicesCetSpPolicerAssociationServiceIndex		OBJECT-TYPE
		SYNTAX 		INTEGER  (1..1025)
		ACCESS		read-only
        STATUS		mandatory
        DESCRIPTION
		"Service ID."
::= { genEquipServicesCetSpPolicerAssociationEntry 1 }

genEquipServicesCetSpPolicerAssociationSpIndex		OBJECT-TYPE
		SYNTAX 		INTEGER	 (1..32)
		ACCESS		read-only
        STATUS		mandatory
        DESCRIPTION
		"Service Point ID."
::= { genEquipServicesCetSpPolicerAssociationEntry 2 }

genEquipServicesCetSpPolicerAssociationSpPolicerAdmin		OBJECT-TYPE
		SYNTAX 		EnableDisable
		ACCESS		read-write
        STATUS		mandatory
        DESCRIPTION
		"Service Point Policer Admin (enable / disable)."
::= { genEquipServicesCetSpPolicerAssociationEntry 3 }

genEquipServicesCetSpPolicerAssociationCos0Profile		OBJECT-TYPE
		SYNTAX 		INTEGER (1..256)
		ACCESS		read-write
        STATUS		mandatory
        DESCRIPTION
		"CoS 0 Policer attached Profile ID."
::= { genEquipServicesCetSpPolicerAssociationEntry 4 }

genEquipServicesCetSpPolicerAssociationCos0Admin		OBJECT-TYPE
		SYNTAX 		EnableDisable
		ACCESS		read-write
        STATUS		mandatory
        DESCRIPTION
		"CoS 0 Policer Admin (enable / disable)."
::= { genEquipServicesCetSpPolicerAssociationEntry 5 }

genEquipServicesCetSpPolicerAssociationCos1Profile		OBJECT-TYPE
		SYNTAX 		INTEGER (1..256)
		ACCESS		read-write
        STATUS		mandatory
        DESCRIPTION
		"CoS 1 Policer attached Profile ID."
::= { genEquipServicesCetSpPolicerAssociationEntry 6 }

genEquipServicesCetSpPolicerAssociationCos1Admin		OBJECT-TYPE
		SYNTAX 		EnableDisable
		ACCESS		read-write
        STATUS		mandatory
        DESCRIPTION
		"CoS 1 Policer Admin (enable / disable)."
::= { genEquipServicesCetSpPolicerAssociationEntry 7 }

genEquipServicesCetSpPolicerAssociationCos2Profile		OBJECT-TYPE
		SYNTAX 		INTEGER (1..256)
		ACCESS		read-write
        STATUS		mandatory
        DESCRIPTION
		"CoS 2 Policer attached Profile ID."
::= { genEquipServicesCetSpPolicerAssociationEntry 8 }

genEquipServicesCetSpPolicerAssociationCos2Admin		OBJECT-TYPE
		SYNTAX 		EnableDisable
		ACCESS		read-write
        STATUS		mandatory
        DESCRIPTION
		"CoS 2 Policer Admin (enable / disable)."
::= { genEquipServicesCetSpPolicerAssociationEntry 9 }

genEquipServicesCetSpPolicerAssociationCos3Profile		OBJECT-TYPE
		SYNTAX 		INTEGER (1..256)
		ACCESS		read-write
        STATUS		mandatory
        DESCRIPTION
		"CoS 3 Policer attached Profile ID."
::= { genEquipServicesCetSpPolicerAssociationEntry 10 }

genEquipServicesCetSpPolicerAssociationCos3Admin		OBJECT-TYPE
		SYNTAX 		DisableAllowed
		ACCESS		read-write
        STATUS		mandatory
        DESCRIPTION
		"CoS 3 Policer Admin (enable / disable)."
::= { genEquipServicesCetSpPolicerAssociationEntry 11 }

genEquipServicesCetSpPolicerAssociationCos4Profile		OBJECT-TYPE
		SYNTAX 		SPCosMode (1..256)
		ACCESS		read-write
        STATUS		mandatory
        DESCRIPTION
		"CoS 4 Policer attached Profile ID."
::= { genEquipServicesCetSpPolicerAssociationEntry 12 }

genEquipServicesCetSpPolicerAssociationCos4Admin		OBJECT-TYPE
		SYNTAX 		EnableDisable
		ACCESS		read-write
        STATUS		mandatory
        DESCRIPTION
		"CoS 4 Policer Admin (enable / disable)."
::= { genEquipServicesCetSpPolicerAssociationEntry 13 }

genEquipServicesCetSpPolicerAssociationCos5Profile		OBJECT-TYPE
		SYNTAX 		INTEGER (1..256)
		ACCESS		read-write
        STATUS		mandatory
        DESCRIPTION
		"CoS 5 Policer attached Profile ID."
::= { genEquipServicesCetSpPolicerAssociationEntry 14 }

genEquipServicesCetSpPolicerAssociationCos5Admin		OBJECT-TYPE
		SYNTAX 		EnableDisable
		ACCESS		read-write
        STATUS		mandatory
        DESCRIPTION
		"CoS 5 Policer Admin (enable / disable)."
::= { genEquipServicesCetSpPolicerAssociationEntry 15 }

genEquipServicesCetSpPolicerAssociationCos6Profile		OBJECT-TYPE
		SYNTAX 		INTEGER (1..256)
		ACCESS		read-write
        STATUS		mandatory
        DESCRIPTION
		"CoS 6 Policer attached Profile ID."
::= { genEquipServicesCetSpPolicerAssociationEntry 16 }

genEquipServicesCetSpPolicerAssociationCos6Admin		OBJECT-TYPE
		SYNTAX 		EnableDisable
		ACCESS		read-write
        STATUS		mandatory
        DESCRIPTION
		"CoS 6 Policer Admin (enable / disable)."
::= { genEquipServicesCetSpPolicerAssociationEntry 17 }

genEquipServicesCetSpPolicerAssociationCos7Profile		OBJECT-TYPE
		SYNTAX 		INTEGER (1..256)
		ACCESS		read-write
        STATUS		mandatory
        DESCRIPTION
		"CoS 7 Policer attached Profile ID."
::= { genEquipServicesCetSpPolicerAssociationEntry 18 }

genEquipServicesCetSpPolicerAssociationCos7Admin		OBJECT-TYPE
		SYNTAX 		EnableDisable
		ACCESS		read-write
        STATUS		mandatory
        DESCRIPTION
		"CoS 7 Policer Admin (enable / disable)."
::= { genEquipServicesCetSpPolicerAssociationEntry 19 }

genEquipServicesCetSpPolicerAssociationRowStatus		OBJECT-TYPE
		SYNTAX 		RowStatus
		ACCESS		read-write
        STATUS		mandatory
        DESCRIPTION
		"Table Mib Row Status."
::= { genEquipServicesCetSpPolicerAssociationEntry 30 }

--
-- Switch Application sw-ap-l4-srv-sp-vlan-config-table
--

genEquipServicesCetSpVlanMappingTable  OBJECT-TYPE
        SYNTAX  SEQUENCE OF GenEquipServicesCetSpVlanMappingEntry
        ACCESS  not-accessible
        STATUS mandatory
        DESCRIPTION
        "The table holds the VLAN TAG ID that build a single ingress classification of Port+OutterVLAN+InnerVLAN to Service Point."
        ::= { genEquipServicesCet 6 }

genEquipServicesCetSpVlanMappingEntry OBJECT-TYPE
        SYNTAX GenEquipServicesCetSpVlanMappingEntry
        ACCESS not-accessible
        STATUS mandatory
          DESCRIPTION
        "The table holds the VLAN TAG ID that build a single ingress classification of Port+OutterVLAN+InnerVLAN to Service Point."
        INDEX { genEquipServicesCetSpVlanMappingServiceId,
				genEquipServicesCetSpVlanMappingSpId,
				genEquipServicesCetSpVlanMappingSvlanIndex,
				genEquipServicesCetSpVlanMappingCvlanIndex }
        ::= { genEquipServicesCetSpVlanMappingTable 1 }

GenEquipServicesCetSpVlanMappingEntry ::=
		SEQUENCE {
			genEquipServicesCetSpVlanMappingServiceId
				INTEGER,
			genEquipServicesCetSpVlanMappingSpId
				INTEGER,
			genEquipServicesCetSpVlanMappingSvlanIndex
				INTEGER,
			genEquipServicesCetSpVlanMappingCvlanIndex
				INTEGER,
			genEquipServicesCetSpVlanMappingVlanCosOverride
				TrueFalse,
			genEquipServicesCetSpVlanMappingVlanDefCos
				INTEGER,
			genEquipServicesCetSpVlanMappingColor
				GreenYellow,
			genEquipServicesCetSpVlanMappingIfIndex
				INTEGER,
			genEquipServicesCetSpVlanMappingIfSlotIndex
				INTEGER,
			genEquipServicesCetSpVlanMappingIfPortIndex
				INTEGER,
			genEquipServicesCetSpVlanMappingRowStatus
				RowStatus
}


genEquipServicesCetSpVlanMappingServiceId		OBJECT-TYPE
		SYNTAX 		INTEGER  (1..1025)
		ACCESS		read-only
        STATUS		mandatory
        DESCRIPTION
		"Service ID."
::= { genEquipServicesCetSpVlanMappingEntry 1 }

genEquipServicesCetSpVlanMappingSpId		OBJECT-TYPE
		SYNTAX 		INTEGER	 (1..32)
		ACCESS		read-only
        STATUS		mandatory
        DESCRIPTION
		"Service Point ID."
::= { genEquipServicesCetSpVlanMappingEntry 2 }

genEquipServicesCetSpVlanMappingSvlanIndex		OBJECT-TYPE
		SYNTAX 		INTEGER (0..4097)
		ACCESS		read-only
        STATUS		mandatory
        DESCRIPTION
		"S-Vlan Encapsulation."
::= { genEquipServicesCetSpVlanMappingEntry 3 }

genEquipServicesCetSpVlanMappingCvlanIndex		OBJECT-TYPE
		SYNTAX 		INTEGER (0..4097)
		ACCESS		read-only
        STATUS		mandatory
        DESCRIPTION
		"C-Vlan Encapsulation."
::= { genEquipServicesCetSpVlanMappingEntry 4 }

genEquipServicesCetSpVlanMappingVlanCosOverride		OBJECT-TYPE
		SYNTAX 		TrueFalse
		ACCESS		read-write
        STATUS		mandatory
        DESCRIPTION
		"The CoS Value field is valid."
::= { genEquipServicesCetSpVlanMappingEntry 5 }

genEquipServicesCetSpVlanMappingVlanDefCos		OBJECT-TYPE
		SYNTAX 		INTEGER (0..7)
		ACCESS		read-write
        STATUS		mandatory
        DESCRIPTION
		"CoS overwrite value."
::= { genEquipServicesCetSpVlanMappingEntry 6 }

genEquipServicesCetSpVlanMappingColor		OBJECT-TYPE
		SYNTAX 		GreenYellow
		ACCESS		read-write
        STATUS		mandatory
        DESCRIPTION
		"Service Point COLOR."
::= { genEquipServicesCetSpVlanMappingEntry 7 }

genEquipServicesCetSpVlanMappingIfIndex		OBJECT-TYPE
		SYNTAX 		INTEGER
		ACCESS		read-only
        STATUS		mandatory
        DESCRIPTION
		"Ethernet Logical port if-index table key."
::= { genEquipServicesCetSpVlanMappingEntry 8 }

genEquipServicesCetSpVlanMappingIfSlotIndex		OBJECT-TYPE
		SYNTAX 		INTEGER
		ACCESS		read-only
        STATUS		mandatory
        DESCRIPTION
		"Slot index."
::= { genEquipServicesCetSpVlanMappingEntry 9 }

genEquipServicesCetSpVlanMappingIfPortIndex		OBJECT-TYPE
		SYNTAX 		INTEGER (0..10)
		ACCESS		read-only
        STATUS		mandatory
        DESCRIPTION
		"Port index."
::= { genEquipServicesCetSpVlanMappingEntry 10 }

genEquipServicesCetSpVlanMappingRowStatus		OBJECT-TYPE
		SYNTAX 		RowStatus
		ACCESS		read-write
        STATUS		mandatory
        DESCRIPTION
		"Table Mib Row Status."
::= { genEquipServicesCetSpVlanMappingEntry 30 }

--
-- Clear all interface egress queues statistics -  sw-ap-l2-if-logical-egress-clear-all-queues-statistics-table
--

genEquipServicesCETTmPmSpEgressClearAllL2InterfaceQueuesStatisticsTable  OBJECT-TYPE
        SYNTAX  SEQUENCE OF GenEquipServicesCETTmPmSpEgressClearAllL2InterfaceQueuesStatisticsEntry
        ACCESS  not-accessible
        STATUS mandatory
        DESCRIPTION
        "Clear all interface egress queues statistics."
        ::= { genEquipServicesCet 7 }

genEquipServicesCETTmPmSpEgressClearAllL2InterfaceQueuesStatisticsEntry OBJECT-TYPE
        SYNTAX GenEquipServicesCETTmPmSpEgressClearAllL2InterfaceQueuesStatisticsEntry
        ACCESS not-accessible
        STATUS mandatory
          DESCRIPTION
        "Clear all interface egress queues statistics."
        INDEX { genEquipServicesCETTmPmSpEgressClearAllL2InterfaceQueuesStatisticsIfIndex }
        ::= { genEquipServicesCETTmPmSpEgressClearAllL2InterfaceQueuesStatisticsTable 1 }

GenEquipServicesCETTmPmSpEgressClearAllL2InterfaceQueuesStatisticsEntry ::=
		SEQUENCE {
			genEquipServicesCETTmPmSpEgressClearAllL2InterfaceQueuesStatisticsIfIndex
				INTEGER,
			genEquipServicesCETTmPmSpEgressClearAllL2InterfaceQueuesStatisticsClearOnRead
				NoYes
}


genEquipServicesCETTmPmSpEgressClearAllL2InterfaceQueuesStatisticsIfIndex		OBJECT-TYPE
		SYNTAX 		INTEGER
		ACCESS		read-only
        STATUS		mandatory
        DESCRIPTION
		"ifIndex."
::= { genEquipServicesCETTmPmSpEgressClearAllL2InterfaceQueuesStatisticsEntry 1 }

genEquipServicesCETTmPmSpEgressClearAllL2InterfaceQueuesStatisticsClearOnRead		OBJECT-TYPE
		SYNTAX 		NoYes
		ACCESS		read-write
        STATUS		mandatory
        DESCRIPTION
		"Clear all statistics for the specific port."
::= { genEquipServicesCETTmPmSpEgressClearAllL2InterfaceQueuesStatisticsEntry 2 }

--
-- Clear all Service egress queues statistics -  sw-ap-l3-srv-egress-clear-all-queues-statistics-table
--

genEquipServicesCETTmPmSpEgressClearAllL3ServiceQueuesStatisticsTable  OBJECT-TYPE
        SYNTAX  SEQUENCE OF GenEquipServicesCETTmPmSpEgressClearAllL3ServiceQueuesStatisticsEntry
        ACCESS  not-accessible
        STATUS mandatory
        DESCRIPTION
        "Clear all Service egress queues statistics."
        ::= { genEquipServicesCet 8 }

genEquipServicesCETTmPmSpEgressClearAllL3ServiceQueuesStatisticsEntry OBJECT-TYPE
        SYNTAX GenEquipServicesCETTmPmSpEgressClearAllL3ServiceQueuesStatisticsEntry
        ACCESS not-accessible
        STATUS mandatory
          DESCRIPTION
        "Clear all Service egress queues statistics."
        INDEX { genEquipServicesCETTmPmSpEgressClearAllL3ServiceQueuesStatisticsIfIndex,
				genEquipServicesCETTmPmSpEgressClearAllL3ServiceQueuesStatisticsServiceIndex }
        ::= { genEquipServicesCETTmPmSpEgressClearAllL3ServiceQueuesStatisticsTable 1 }

GenEquipServicesCETTmPmSpEgressClearAllL3ServiceQueuesStatisticsEntry ::=
		SEQUENCE {
			genEquipServicesCETTmPmSpEgressClearAllL3ServiceQueuesStatisticsIfIndex
				INTEGER,
			genEquipServicesCETTmPmSpEgressClearAllL3ServiceQueuesStatisticsServiceIndex
				INTEGER,
			genEquipServicesCETTmPmSpEgressClearAllL3ServiceQueuesStatisticsClearOnRead
				NoYes
}


genEquipServicesCETTmPmSpEgressClearAllL3ServiceQueuesStatisticsIfIndex		OBJECT-TYPE
		SYNTAX 		INTEGER
		ACCESS		read-only
        STATUS		mandatory
        DESCRIPTION
		"ifIndex."
::= { genEquipServicesCETTmPmSpEgressClearAllL3ServiceQueuesStatisticsEntry 1 }

genEquipServicesCETTmPmSpEgressClearAllL3ServiceQueuesStatisticsServiceIndex		OBJECT-TYPE
		SYNTAX 		INTEGER (1..63)
		ACCESS		read-only
        STATUS		mandatory
        DESCRIPTION
		"Egress service bundle ID."
::= { genEquipServicesCETTmPmSpEgressClearAllL3ServiceQueuesStatisticsEntry 2 }

genEquipServicesCETTmPmSpEgressClearAllL3ServiceQueuesStatisticsClearOnRead		OBJECT-TYPE
		SYNTAX 		NoYes
		ACCESS		read-write
        STATUS		mandatory
        DESCRIPTION
		"clear on read."
::= { genEquipServicesCETTmPmSpEgressClearAllL3ServiceQueuesStatisticsEntry 3 }


--
-- The following are the Services part of Switch application tables
--
genEquipServicesTM	OBJECT IDENTIFIER ::= {genEquipServices 6}

-- TM Mapping
genEquipTmMapping OBJECT IDENTIFIER ::= {genEquipServicesTM 1}

--
-- Switch Application sw-ap-global-ingress-mapping-802_1ad-up-to-cos-table
--

genEquipTmMappingSVlanPriToCosTable  OBJECT-TYPE
        SYNTAX  SEQUENCE OF GenEquipTmMappingSVlanPriToCosEntry
        ACCESS  not-accessible
        STATUS mandatory
        DESCRIPTION
        "Global 802.1AD classification table to CoS and Color."
        ::= { genEquipTmMapping 1 }

genEquipTmMappingSVlanPriToCosEntry OBJECT-TYPE
        SYNTAX GenEquipTmMappingSVlanPriToCosEntry
        ACCESS not-accessible
        STATUS mandatory
          DESCRIPTION
        "Global 802.1AD classification table to CoS and Color entry."
        INDEX { genEquipTmMappingSVlanPriToCosUpIndex,
				genEquipTmMappingSVlanPriToCosDeiIndex }
        ::= { genEquipTmMappingSVlanPriToCosTable 1 }

GenEquipTmMappingSVlanPriToCosEntry ::=
		SEQUENCE {
			genEquipTmMappingSVlanPriToCosUpIndex
				INTEGER,
			genEquipTmMappingSVlanPriToCosDeiIndex
				INTEGER,
			genEquipTmMappingSVlanPriToCosCos
				INTEGER,
			genEquipTmMappingSVlanPriToCosColor
				GreenYellow
}


genEquipTmMappingSVlanPriToCosUpIndex		OBJECT-TYPE
		SYNTAX 		INTEGER  (0..7)
		ACCESS		read-only
        STATUS		mandatory
        DESCRIPTION
		"User Priority bits - Global 802.1AD User Priority and DEI bits classification table to CoS and Color."
::= { genEquipTmMappingSVlanPriToCosEntry 1 }

genEquipTmMappingSVlanPriToCosDeiIndex		OBJECT-TYPE
		SYNTAX 		INTEGER	 (0..1)
		ACCESS		read-only
        STATUS		mandatory
        DESCRIPTION
		"DEI bit - Global 802.1AD User Priority and DEI bits classification table to CoS and Color."
::= { genEquipTmMappingSVlanPriToCosEntry 2 }

genEquipTmMappingSVlanPriToCosCos		OBJECT-TYPE
		SYNTAX 		INTEGER (0..7)
		ACCESS		read-write
        STATUS		mandatory
        DESCRIPTION
		"CoS bits - Global 802.1AD User Priority and DEI bits classification table to CoS and Color."
::= { genEquipTmMappingSVlanPriToCosEntry 3 }

genEquipTmMappingSVlanPriToCosColor		OBJECT-TYPE
		SYNTAX 		GreenYellow
		ACCESS		read-write
        STATUS		mandatory
        DESCRIPTION
		"Color bit - Global 802.1AD User Priority and DEI bits classification table to CoS and Color."
::= { genEquipTmMappingSVlanPriToCosEntry 4 }

--
-- Switch Application sw-ap-global-ingress-mapping-802_1q-up-to-cos-table
--

genEquipTmMappingCVlanPriToCosTable  OBJECT-TYPE
        SYNTAX  SEQUENCE OF GenEquipTmMappingCVlanPriToCosEntry
        ACCESS  not-accessible
        STATUS mandatory
        DESCRIPTION
        "Global 802.1Q classification table to CoS and Color."
        ::= { genEquipTmMapping 2 }

genEquipTmMappingCVlanPriToCosEntry OBJECT-TYPE
        SYNTAX GenEquipTmMappingCVlanPriToCosEntry
        ACCESS not-accessible
        STATUS mandatory
          DESCRIPTION
        "Global 802.1Q classification table to CoS and Color entry."
        INDEX { genEquipTmMappingCVlanPriToCosUpIndex,
				genEquipTmMappingCVlanPriToCosCfiIndex }
        ::= { genEquipTmMappingCVlanPriToCosTable 1 }

GenEquipTmMappingCVlanPriToCosEntry ::=
		SEQUENCE {
			genEquipTmMappingCVlanPriToCosUpIndex
				INTEGER,
			genEquipTmMappingCVlanPriToCosCfiIndex
				INTEGER,
			genEquipTmMappingCVlanPriToCosCos
				INTEGER,
			genEquipTmMappingCVlanPriToCosColor
				GreenYellow
}


genEquipTmMappingCVlanPriToCosUpIndex		OBJECT-TYPE
		SYNTAX 		INTEGER  (0..7)
		ACCESS		read-only
        STATUS		mandatory
        DESCRIPTION
		"User Priority bits - Global 802.1Q User Priority and CFI bits classification table to CoS and Color."
::= { genEquipTmMappingCVlanPriToCosEntry 1 }

genEquipTmMappingCVlanPriToCosCfiIndex		OBJECT-TYPE
		SYNTAX 		INTEGER	 (0..1)
		ACCESS		read-only
        STATUS		mandatory
        DESCRIPTION
		"CFI bit - Global 802.1Q User Priority and CFI bits classification table to CoS and Color."
::= { genEquipTmMappingCVlanPriToCosEntry 2 }

genEquipTmMappingCVlanPriToCosCos		OBJECT-TYPE
		SYNTAX 		INTEGER (0..7)
		ACCESS		read-write
        STATUS		mandatory
        DESCRIPTION
		"CoS bits - Global 802.1AD User Priority and DEI bits classification table to CoS and Color."
::= { genEquipTmMappingCVlanPriToCosEntry 3 }

genEquipTmMappingCVlanPriToCosColor		OBJECT-TYPE
		SYNTAX 		GreenYellow
		ACCESS		read-write
        STATUS		mandatory
        DESCRIPTION
		"Color bit - Global 802.1Q User Priority and CFI bits classification table to CoS and Color."
::= { genEquipTmMappingCVlanPriToCosEntry 4 }

--
-- Switch Application sw-ap-global-ingress-mapping-dscp-to-cos-table
--

genEquipTmMappingDscpToCosTable  OBJECT-TYPE
        SYNTAX  SEQUENCE OF GenEquipTmMappingDscpToCosEntry
        ACCESS  not-accessible
        STATUS mandatory
        DESCRIPTION
        "Global DSCP bits classification table to CoS and Color."
        ::= { genEquipTmMapping 3 }

genEquipTmMappingDscpToCosEntry OBJECT-TYPE
        SYNTAX GenEquipTmMappingDscpToCosEntry
        ACCESS not-accessible
        STATUS mandatory
          DESCRIPTION
        "Global DSCP bits classification table to CoS and Color entry."
        INDEX { genEquipTmMappingDscpToCosDscpIndex }
        ::= { genEquipTmMappingDscpToCosTable 1 }

GenEquipTmMappingDscpToCosEntry ::=
		SEQUENCE {
			genEquipTmMappingDscpToCosDscpIndex
				INTEGER,
			genEquipTmMappingDscpToCosBinary
				OCTET STRING,
			genEquipTmMappingDscpToCosDescription
				DisplayString,
			genEquipTmMappingDscpToCosCos
				INTEGER,
			genEquipTmMappingDscpToCosColor
				GreenYellow
}


genEquipTmMappingDscpToCosDscpIndex		OBJECT-TYPE
		SYNTAX 		INTEGER  (0..56)
		ACCESS		read-only
        STATUS		mandatory
        DESCRIPTION
		"DSCP bits - Global DSCP bits classification table to CoS and Color."
::= { genEquipTmMappingDscpToCosEntry 1 }

genEquipTmMappingDscpToCosBinary		OBJECT-TYPE
		SYNTAX 		OCTET STRING (SIZE(0..6))
		ACCESS		read-write
        STATUS		mandatory
        DESCRIPTION
		"Global DSCP bits classification table to CoS and Color."
::= { genEquipTmMappingDscpToCosEntry 2 }

genEquipTmMappingDscpToCosDescription		OBJECT-TYPE
		SYNTAX 		DisplayString
		ACCESS		read-write
        STATUS		mandatory
        DESCRIPTION
		"user description field  - Global DSCP bits classification table to CoS and Color."
::= { genEquipTmMappingDscpToCosEntry 3 }

genEquipTmMappingDscpToCosCos		OBJECT-TYPE
		SYNTAX 		INTEGER (0..7)
		ACCESS		read-write
        STATUS		mandatory
        DESCRIPTION
		"CoS bits - Global DSCP bits classification table to CoS and Color."
::= { genEquipTmMappingDscpToCosEntry 4 }

genEquipTmMappingDscpToCosColor		OBJECT-TYPE
		SYNTAX 		GreenYellow
		ACCESS		read-write
        STATUS		mandatory
        DESCRIPTION
		"Color bit - Global DSCP bits classification table to CoS and Color."
::= { genEquipTmMappingDscpToCosEntry 5 }

--
-- Switch Application sw-ap-mapping-mpls-exp-to-cos-color
--

genEquipTmMappingMPLSExpPriToCosTable  OBJECT-TYPE
        SYNTAX  SEQUENCE OF GenEquipTmMappingMPLSExpPriToCosEntry
        ACCESS  not-accessible
        STATUS mandatory
        DESCRIPTION
        "Color bit - Global MPLS EXP bits classification table to CoS and Color."
        ::= { genEquipTmMapping 4 }

genEquipTmMappingMPLSExpPriToCosEntry OBJECT-TYPE
        SYNTAX GenEquipTmMappingMPLSExpPriToCosEntry
        ACCESS not-accessible
        STATUS mandatory
          DESCRIPTION
        "Color bit - Global MPLS EXP bits classification table to CoS and Color entry."
        INDEX { genEquipTmMappingMPLSExpPriToCosMplsExpIndex }
        ::= { genEquipTmMappingMPLSExpPriToCosTable 1 }

GenEquipTmMappingMPLSExpPriToCosEntry ::=
		SEQUENCE {
			genEquipTmMappingMPLSExpPriToCosMplsExpIndex
				INTEGER,
			genEquipTmMappingMPLSExpPriToCosCos
				INTEGER,
			genEquipTmMappingMPLSExpPriToCosColor
				GreenYellow
}


genEquipTmMappingMPLSExpPriToCosMplsExpIndex		OBJECT-TYPE
		SYNTAX 		INTEGER  (0..7)
		ACCESS		read-only
        STATUS		mandatory
        DESCRIPTION
		"Experimental bits - Global MPLS EXP bits classification table to CoS and Color."
::= { genEquipTmMappingMPLSExpPriToCosEntry 1 }


genEquipTmMappingMPLSExpPriToCosCos		OBJECT-TYPE
		SYNTAX 		INTEGER (0..7)
		ACCESS		read-write
        STATUS		mandatory
        DESCRIPTION
		"CoS bit - Global MPLS EXP bits classification table to CoS and Color."
::= { genEquipTmMappingMPLSExpPriToCosEntry 2 }

genEquipTmMappingMPLSExpPriToCosColor		OBJECT-TYPE
		SYNTAX 		GreenYellow
		ACCESS		read-write
        STATUS		mandatory
        DESCRIPTION
		"Color bit - Global MPLS EXP bits classification table to CoS and Color."
::= { genEquipTmMappingMPLSExpPriToCosEntry 3 }

--
-- Switch Application sw-ap-global-egress-marking-802_1ad-table
--

genEquipTmMarkingSVlanPriTable  OBJECT-TYPE
        SYNTAX  SEQUENCE OF GenEquipTmMarkingSVlanPriEntry
        ACCESS  not-accessible
        STATUS mandatory
        DESCRIPTION
        "Global 802.1AD Marking Table User CoS and Color to User Priority bits and DEI."
        ::= { genEquipTmMapping 5 }

genEquipTmMarkingSVlanPriEntry OBJECT-TYPE
        SYNTAX GenEquipTmMarkingSVlanPriEntry
        ACCESS not-accessible
        STATUS mandatory
          DESCRIPTION
        "Global 802.1AD Marking Table User CoS and Color to User Priority bits and DEI entry."
        INDEX { genEquipTmMarkingSVlanPriCosIndex,
				genEquipTmMarkingSVlanPriColorIndex }
        ::= { genEquipTmMarkingSVlanPriTable 1 }

GenEquipTmMarkingSVlanPriEntry ::=
		SEQUENCE {
			genEquipTmMarkingSVlanPriCosIndex
				INTEGER,
			genEquipTmMarkingSVlanPriColorIndex
				GreenYellow,
			genEquipTmMarkingSVlanPriUserPriority
				INTEGER,
			genEquipTmMarkingSVlanPriDEI
				INTEGER
}


genEquipTmMarkingSVlanPriCosIndex		OBJECT-TYPE
		SYNTAX 		INTEGER  (0..7)
		ACCESS		read-only
        STATUS		mandatory
        DESCRIPTION
		"CoS bits - Global 802.1AD Marking Table User CoS and Color to User Priority bits and DEI."
::= { genEquipTmMarkingSVlanPriEntry 1 }

genEquipTmMarkingSVlanPriColorIndex		OBJECT-TYPE
		SYNTAX 		GreenYellow
		ACCESS		read-only
        STATUS		mandatory
        DESCRIPTION
		"Color bit - Global 802.1AD Marking Table User CoS and Color to User Priority bits and DEI."
::= { genEquipTmMarkingSVlanPriEntry 2 }


genEquipTmMarkingSVlanPriUserPriority		OBJECT-TYPE
		SYNTAX 		INTEGER (0..7)
		ACCESS		read-write
        STATUS		mandatory
        DESCRIPTION
		"User Priority bits - Global 802.1AD Marking Table User CoS and Color to User Priority bits and DEI."
::= { genEquipTmMarkingSVlanPriEntry 3 }

genEquipTmMarkingSVlanPriDEI		OBJECT-TYPE
		SYNTAX 		INTEGER (0..1)
		ACCESS		read-write
        STATUS		mandatory
        DESCRIPTION
		"DEI bit - Global 802.1AD Marking Table User CoS and Color to User Priority bits and DEI."
::= { genEquipTmMarkingSVlanPriEntry 4 }

--
-- Switch Application sw-ap-global-egress-marking-802_1q-table
--

genEquipTmMarkingCVlanPriTable  OBJECT-TYPE
        SYNTAX  SEQUENCE OF GenEquipTmMarkingCVlanPriEntry
        ACCESS  not-accessible
        STATUS mandatory
        DESCRIPTION
        "Global 802.1Q Marking Table User CoS and Color to User Priority bits and CFI."
        ::= { genEquipTmMapping 6 }

genEquipTmMarkingCVlanPriEntry OBJECT-TYPE
        SYNTAX GenEquipTmMarkingCVlanPriEntry
        ACCESS not-accessible
        STATUS mandatory
          DESCRIPTION
        "Global 802.1Q Marking Table User CoS and Color to User Priority bits and CFI entry."
        INDEX { genEquipTmMarkingCVlanPriCosIndex,
				genEquipTmMarkingCVlanPriColorIndex }
        ::= { genEquipTmMarkingCVlanPriTable 1 }

GenEquipTmMarkingCVlanPriEntry ::=
		SEQUENCE {
			genEquipTmMarkingCVlanPriCosIndex
				INTEGER,
			genEquipTmMarkingCVlanPriColorIndex
				GreenYellow,
			genEquipTmMarkingCVlanPriUserPriority
				INTEGER,
			genEquipTmMarkingCVlanPriCFI
				INTEGER
}


genEquipTmMarkingCVlanPriCosIndex		OBJECT-TYPE
		SYNTAX 		INTEGER  (0..7)
		ACCESS		read-only
        STATUS		mandatory
        DESCRIPTION
		"CoS bits - Global 802.1Q Marking Table User CoS and Color to User Priority bits and CFI."
::= { genEquipTmMarkingCVlanPriEntry 1 }

genEquipTmMarkingCVlanPriColorIndex		OBJECT-TYPE
		SYNTAX 		GreenYellow
		ACCESS		read-only
        STATUS		mandatory
        DESCRIPTION
		"Color bit - Global 802.1Q Marking Table User CoS and Color to User Priority bits and CFI."
::= { genEquipTmMarkingCVlanPriEntry 2 }


genEquipTmMarkingCVlanPriUserPriority		OBJECT-TYPE
		SYNTAX 		INTEGER (0..7)
		ACCESS		read-write
        STATUS		mandatory
        DESCRIPTION
		"User Priority bits - Global 802.1Q Marking Table User CoS and Color to User Priority bits and CFI."
::= { genEquipTmMarkingCVlanPriEntry 3 }

genEquipTmMarkingCVlanPriCFI		OBJECT-TYPE
		SYNTAX 		INTEGER (0..1)
		ACCESS		read-write
        STATUS		mandatory
        DESCRIPTION
		"CFI bit - Global 802.1Q Marking Table User CoS and Color to User Priority bits and CFI."
::= { genEquipTmMarkingCVlanPriEntry 4 }

-- TM Profiles
genEquipTmProfiles OBJECT IDENTIFIER ::= {genEquipServicesTM 2}

--
-- Switch Application sw-ap-global-ingress-policer-profiles-list-table
--

genEquipProfilesPolicerTable  OBJECT-TYPE
        SYNTAX  SEQUENCE OF GenEquipProfilesPolicerEntry
        ACCESS  not-accessible
        STATUS mandatory
        DESCRIPTION
        "General Policer Profile configuration table."
        ::= { genEquipTmProfiles 1 }

genEquipProfilesPolicerEntry OBJECT-TYPE
        SYNTAX GenEquipProfilesPolicerEntry
        ACCESS not-accessible
        STATUS mandatory
          DESCRIPTION
        "General Policer Profile configuration table entry."
        INDEX { genEquipProfilesPolicerIndex }
        ::= { genEquipProfilesPolicerTable 1 }

GenEquipProfilesPolicerEntry ::=
		SEQUENCE {
			genEquipProfilesPolicerIndex
				INTEGER,
			genEquipProfilesPolicerDescription
				DisplayString,
			genEquipProfilesPolicerPolicerType
				PolicerType,
			genEquipProfilesPolicerCir
				INTEGER,
			genEquipProfilesPolicerCbs
				INTEGER,
			genEquipProfilesPolicerEir
				INTEGER,
			genEquipProfilesPolicerEbs
				INTEGER,
			genEquipProfilesPolicerColorMode
				PolicerColorMode,
			genEquipProfilesPolicerCouplingFlagMode
				EnableDisable,
			genEquipProfilesPolicerDataPlaneId
				INTEGER,
			genEquipProfilesPolicerRowStatus
				RowStatus
}


genEquipProfilesPolicerIndex		OBJECT-TYPE
		SYNTAX 		INTEGER  (1..256)
		ACCESS		read-only
        STATUS		mandatory
        DESCRIPTION
		"User Profile ID number."
::= { genEquipProfilesPolicerEntry 1 }

genEquipProfilesPolicerDescription		OBJECT-TYPE
		SYNTAX 		DisplayString (SIZE (0..21))
		ACCESS		read-write
        STATUS		mandatory
        DESCRIPTION
		"Ingress Policer user Description field."
::= { genEquipProfilesPolicerEntry 2 }


genEquipProfilesPolicerPolicerType		OBJECT-TYPE
		SYNTAX 		PolicerType
		ACCESS		read-only
        STATUS		mandatory
        DESCRIPTION
		"Ingress Policer Type (MEF TrTCM,RFC2697,RFC2698)."
::= { genEquipProfilesPolicerEntry 3 }

genEquipProfilesPolicerCir		OBJECT-TYPE
		SYNTAX 		INTEGER
		ACCESS		read-write
        STATUS		mandatory
        DESCRIPTION
		"Ingress Policer Commited Information Rate (CIR)."
::= { genEquipProfilesPolicerEntry 4 }

genEquipProfilesPolicerCbs		OBJECT-TYPE
		SYNTAX 		INTEGER (0..128)
		ACCESS		read-write
        STATUS		mandatory
        DESCRIPTION
		"Ingress Policer Commited Burst Size (CBS)."
::= { genEquipProfilesPolicerEntry 5 }

genEquipProfilesPolicerEir		OBJECT-TYPE
		SYNTAX 		INTEGER
		ACCESS		read-write
        STATUS		mandatory
        DESCRIPTION
		"Ingress Policer Excess Information Rate (EIR)."
::= { genEquipProfilesPolicerEntry 6 }

genEquipProfilesPolicerEbs		OBJECT-TYPE
		SYNTAX 		INTEGER (0..128)
		ACCESS		read-write
        STATUS		mandatory
        DESCRIPTION
		"Ingress Policer Excess Burst Size (EBS)."
::= { genEquipProfilesPolicerEntry 7 }

genEquipProfilesPolicerColorMode		OBJECT-TYPE
		SYNTAX 		PolicerColorMode
		ACCESS		read-write
        STATUS		mandatory
        DESCRIPTION
		"Ingress Policer Color Mode (Color Aware or Color Blind)."
::= { genEquipProfilesPolicerEntry 8 }

genEquipProfilesPolicerCouplingFlagMode		OBJECT-TYPE
		SYNTAX 		EnableDisable
		ACCESS		read-write
        STATUS		mandatory
        DESCRIPTION
		"Ingress Policer Coupling Flag between Green and Yellow leaky buckets."
::= { genEquipProfilesPolicerEntry 9 }

genEquipProfilesPolicerDataPlaneId		OBJECT-TYPE
		SYNTAX 		INTEGER (0..4096)
		ACCESS		read-only
        STATUS		mandatory
        DESCRIPTION
		"The real policer ID in the dataplan 0 to 10000."
::= { genEquipProfilesPolicerEntry 10 }

genEquipProfilesPolicerRowStatus		OBJECT-TYPE
		SYNTAX 		RowStatus
		ACCESS		read-write
        STATUS		mandatory
        DESCRIPTION
		"Table Mib Row Status."
::= { genEquipProfilesPolicerEntry 30 }

--
-- Switch Application sw-ap-profile-egress-l4-wred-green-max-drop
--

genEquipProfilesL4WredTable  OBJECT-TYPE
        SYNTAX  SEQUENCE OF GenEquipProfilesL4WredEntry
        ACCESS  not-accessible
        STATUS mandatory
        DESCRIPTION
        "Green Curve Maximal Drop Ratio (in percentage)."
        ::= { genEquipTmProfiles 2 }

genEquipProfilesL4WredEntry OBJECT-TYPE
        SYNTAX GenEquipProfilesL4WredEntry
        ACCESS not-accessible
        STATUS mandatory
          DESCRIPTION
        "Green Curve Maximal Drop Ratio (in percentage) entry."
        INDEX { genEquipProfilesL4WredIndex }
        ::= { genEquipProfilesL4WredTable 1 }

GenEquipProfilesL4WredEntry ::=
		SEQUENCE {
			genEquipProfilesL4WredIndex
				INTEGER,
			genEquipProfilesL4WredGreenMinThreshold
				INTEGER,
			genEquipProfilesL4WredGreenMaxThreshold
				INTEGER,
			genEquipProfilesL4WredGreenMaxDrop
				INTEGER,
			genEquipProfilesL4WredYellowMinThreshold
				INTEGER,
			genEquipProfilesL4WredYellowMaxThreshold
				INTEGER,
			genEquipProfilesL4WredYellowMaxDrop
				INTEGER,
			genEquipProfilesL4WredYellowRowStatus
				RowStatus
}


genEquipProfilesL4WredIndex		OBJECT-TYPE
		SYNTAX 		INTEGER  (1..32)
		ACCESS		read-only
        STATUS		mandatory
        DESCRIPTION
		"WRED Curves Profile ID."
::= { genEquipProfilesL4WredEntry 1 }

genEquipProfilesL4WredGreenMinThreshold		OBJECT-TYPE
		SYNTAX 		INTEGER (0..8192)
		ACCESS		read-write
        STATUS		mandatory
        DESCRIPTION
		"Green Curve Minimal occupancy (No drop until this level)."
::= { genEquipProfilesL4WredEntry 2 }

genEquipProfilesL4WredGreenMaxThreshold		OBJECT-TYPE
		SYNTAX 		INTEGER (0..8192)
		ACCESS		read-write
        STATUS		mandatory
        DESCRIPTION
		"Green Curve Maximal occupancy (from this point 100% will be dropped)."
::= { genEquipProfilesL4WredEntry 3 }

genEquipProfilesL4WredGreenMaxDrop		OBJECT-TYPE
		SYNTAX 		INTEGER (1..100)
		ACCESS		read-write
        STATUS		mandatory
        DESCRIPTION
		"Green Curve Maximal Drop Ratio (in percentage)."
::= { genEquipProfilesL4WredEntry 4 }

genEquipProfilesL4WredYellowMinThreshold		OBJECT-TYPE
		SYNTAX 		INTEGER (0..8192)
		ACCESS		read-write
        STATUS		mandatory
        DESCRIPTION
		"Yellow Curve Minimal occupancy (No drop until this level)."
::= { genEquipProfilesL4WredEntry 5 }

genEquipProfilesL4WredYellowMaxThreshold		OBJECT-TYPE
		SYNTAX 		INTEGER (0..8192)
		ACCESS		read-write
        STATUS		mandatory
        DESCRIPTION
		"Yellow Curve Maximal occupancy (from this point 100% will be dropped)."
::= { genEquipProfilesL4WredEntry 6 }

genEquipProfilesL4WredYellowMaxDrop		OBJECT-TYPE
		SYNTAX 		INTEGER (0..8192)
		ACCESS		read-write
        STATUS		mandatory
        DESCRIPTION
		"Yellow Curve Maximal Drop Ratio (in percentage)."
::= { genEquipProfilesL4WredEntry 7 }

genEquipProfilesL4WredYellowRowStatus		OBJECT-TYPE
		SYNTAX 		RowStatus
		ACCESS		read-write
        STATUS		mandatory
        DESCRIPTION
		"Table Mib Row Status."
::= { genEquipProfilesL4WredEntry 30 }

--
-- Switch Application sw-ap-global-egress-scheduler-cos-priority-profiles-list-table
--

genEquipProfilesSchedulerCoSPriTable  OBJECT-TYPE
        SYNTAX  SEQUENCE OF GenEquipProfilesSchedulerCoSPriEntry
        ACCESS  not-accessible
        STATUS mandatory
        DESCRIPTION
        "The table holds  the Egress Scheduler Port priority profile (each profile contain 8 priorities per 8 queues of single port)."
        ::= { genEquipTmProfiles 3 }

genEquipProfilesSchedulerCoSPriEntry OBJECT-TYPE
        SYNTAX GenEquipProfilesSchedulerCoSPriEntry
        ACCESS not-accessible
        STATUS mandatory
          DESCRIPTION
        "The table entry holds  the Egress Scheduler Port priority profile (each profile contain 8 priorities per 8 queues of single port)."
        INDEX { genEquipProfilesSchedulerCoSPriIndex }
        ::= { genEquipProfilesSchedulerCoSPriTable 1 }

GenEquipProfilesSchedulerCoSPriEntry ::=
		SEQUENCE {
			genEquipProfilesSchedulerCoSPriIndex
				INTEGER,
			genEquipProfilesSchedulerCoSPriCos0Description
				DisplayString,
			genEquipProfilesSchedulerCoSPriGreenCos0Priority
				INTEGER,
			genEquipProfilesSchedulerCoSPriCos1description
				DisplayString,
			genEquipProfilesSchedulerCoSPriGreenCos1Priority
				INTEGER,
			genEquipProfilesSchedulerCoSPriCos2Description
				DisplayString,
			genEquipProfilesSchedulerCoSPriGreenCos2Priority
				INTEGER,
			genEquipProfilesSchedulerCoSPriCos3description
				DisplayString,
			genEquipProfilesSchedulerCoSPriGreenCos3Priority
				INTEGER,
			genEquipProfilesSchedulerCoSPriCos4description
				DisplayString,
			genEquipProfilesSchedulerCoSPriGreenCos4Priority
				INTEGER,
			genEquipProfilesSchedulerCoSPriCos5description
				DisplayString,
			genEquipProfilesSchedulerCoSPriGreenCos5Priority
				INTEGER,
			genEquipProfilesSchedulerCoSPriCos6description
				DisplayString,
			genEquipProfilesSchedulerCoSPriGreenCos6Priority
				INTEGER,
			genEquipProfilesSchedulerCoSPriCos7description
				DisplayString,
			genEquipProfilesSchedulerCoSPriGreenCos7Priority
				INTEGER,
			genEquipProfilesSchedulerCoSPriRowStatus
				RowStatus
}


genEquipProfilesSchedulerCoSPriIndex		OBJECT-TYPE
		SYNTAX 		INTEGER  (1..32)
		ACCESS		read-only
        STATUS		mandatory
        DESCRIPTION
		"Profile ID."
::= { genEquipProfilesSchedulerCoSPriEntry 1 }

genEquipProfilesSchedulerCoSPriCos0Description		OBJECT-TYPE
		SYNTAX 		DisplayString (SIZE (0..21))
		ACCESS		read-write
        STATUS		mandatory
        DESCRIPTION
		"CoS 0 Description."
::= { genEquipProfilesSchedulerCoSPriEntry 2 }

genEquipProfilesSchedulerCoSPriGreenCos0Priority		OBJECT-TYPE
		SYNTAX 		INTEGER (1..4)
		ACCESS		read-write
        STATUS		mandatory
        DESCRIPTION
		"Green CoS 0 priority."
::= { genEquipProfilesSchedulerCoSPriEntry 3 }

genEquipProfilesSchedulerCoSPriCos1description		OBJECT-TYPE
		SYNTAX 		DisplayString (SIZE (0..21))
		ACCESS		read-write
        STATUS		mandatory
        DESCRIPTION
		"CoS 1 Description."
::= { genEquipProfilesSchedulerCoSPriEntry 4 }

genEquipProfilesSchedulerCoSPriGreenCos1Priority		OBJECT-TYPE
		SYNTAX 		INTEGER (1..4)
		ACCESS		read-write
        STATUS		mandatory
        DESCRIPTION
		"Green CoS 1 priority."
::= { genEquipProfilesSchedulerCoSPriEntry 5 }

genEquipProfilesSchedulerCoSPriCos2Description		OBJECT-TYPE
		SYNTAX 		DisplayString (SIZE (0..21))
		ACCESS		read-write
        STATUS		mandatory
        DESCRIPTION
		"CoS 2 Description."
::= { genEquipProfilesSchedulerCoSPriEntry 6 }

genEquipProfilesSchedulerCoSPriGreenCos2Priority		OBJECT-TYPE
		SYNTAX 		INTEGER (1..4)
		ACCESS		read-write
        STATUS		mandatory
        DESCRIPTION
		"Green CoS 2 priority."
::= { genEquipProfilesSchedulerCoSPriEntry 7 }

genEquipProfilesSchedulerCoSPriCos3description		OBJECT-TYPE
		SYNTAX 		DisplayString (SIZE (0..21))
		ACCESS		read-write
        STATUS		mandatory
        DESCRIPTION
		"CoS 3 Description."
::= { genEquipProfilesSchedulerCoSPriEntry 8 }

genEquipProfilesSchedulerCoSPriGreenCos3Priority		OBJECT-TYPE
		SYNTAX 		INTEGER (1..4)
		ACCESS		read-write
        STATUS		mandatory
        DESCRIPTION
		"Green CoS 3 priority."
::= { genEquipProfilesSchedulerCoSPriEntry 9 }

genEquipProfilesSchedulerCoSPriCos4description		OBJECT-TYPE
		SYNTAX 		DisplayString (SIZE (0..21))
		ACCESS		read-write
        STATUS		mandatory
        DESCRIPTION
		"CoS 4 Description."
::= { genEquipProfilesSchedulerCoSPriEntry 10 }

genEquipProfilesSchedulerCoSPriGreenCos4Priority		OBJECT-TYPE
		SYNTAX 		INTEGER (1..4)
		ACCESS		read-write
        STATUS		mandatory
        DESCRIPTION
		"Green CoS 4 priority."
::= { genEquipProfilesSchedulerCoSPriEntry 11 }

genEquipProfilesSchedulerCoSPriCos5description		OBJECT-TYPE
		SYNTAX 		DisplayString (SIZE (0..21))
		ACCESS		read-write
        STATUS		mandatory
        DESCRIPTION
		"CoS 5 Description."
::= { genEquipProfilesSchedulerCoSPriEntry 12 }

genEquipProfilesSchedulerCoSPriGreenCos5Priority		OBJECT-TYPE
		SYNTAX 		INTEGER (1..4)
		ACCESS		read-write
        STATUS		mandatory
        DESCRIPTION
		"Green CoS 5 priority."
::= { genEquipProfilesSchedulerCoSPriEntry 13 }

genEquipProfilesSchedulerCoSPriCos6description		OBJECT-TYPE
		SYNTAX 		DisplayString (SIZE (0..21))
		ACCESS		read-write
        STATUS		mandatory
        DESCRIPTION
		"CoS 6 Description."
::= { genEquipProfilesSchedulerCoSPriEntry 14 }

genEquipProfilesSchedulerCoSPriGreenCos6Priority		OBJECT-TYPE
		SYNTAX 		INTEGER (1..4)
		ACCESS		read-write
        STATUS		mandatory
        DESCRIPTION
		"Green CoS 6 priority."
::= { genEquipProfilesSchedulerCoSPriEntry 15 }

genEquipProfilesSchedulerCoSPriCos7description		OBJECT-TYPE
		SYNTAX 		DisplayString (SIZE (0..21))
		ACCESS		read-write
        STATUS		mandatory
        DESCRIPTION
		"CoS 7 Description."
::= { genEquipProfilesSchedulerCoSPriEntry 16 }

genEquipProfilesSchedulerCoSPriGreenCos7Priority		OBJECT-TYPE
		SYNTAX 		INTEGER (1..42)
		ACCESS		read-only
        STATUS		mandatory
        DESCRIPTION
		"Green CoS 7 priority."
::= { genEquipProfilesSchedulerCoSPriEntry 17 }

genEquipProfilesSchedulerCoSPriRowStatus		OBJECT-TYPE
		SYNTAX 		RowStatus
		ACCESS		read-write
        STATUS		mandatory
        DESCRIPTION
		"Table Mib Row Status."
::= { genEquipProfilesSchedulerCoSPriEntry 30 }

--
-- Switch Application sw-ap-global-egress-scheduler-wfq-profiles-list-table
--

genEquipProfilesSchedulerWfqTable  OBJECT-TYPE
        SYNTAX  SEQUENCE OF GenEquipProfilesSchedulerWfqEntry
        ACCESS  not-accessible
        STATUS mandatory
        DESCRIPTION
        "The table holds the Egress Scheduler Port WFQ profiles (each profile contain 8 weights per 8 queues of single port)."
        ::= { genEquipTmProfiles 4 }

genEquipProfilesSchedulerWfqEntry OBJECT-TYPE
        SYNTAX GenEquipProfilesSchedulerWfqEntry
        ACCESS not-accessible
        STATUS mandatory
          DESCRIPTION
        "The table entry holds the Egress Scheduler Port WFQ profiles (each profile contain 8 weights per 8 queues of single port)."
        INDEX { genEquipProfilesSchedulerWfqIndex }
        ::= { genEquipProfilesSchedulerWfqTable 1 }

GenEquipProfilesSchedulerWfqEntry ::=
		SEQUENCE {
			genEquipProfilesSchedulerWfqIndex
				INTEGER,
			genEquipProfilesSchedulerWfqCos0Weight
				INTEGER,
			genEquipProfilesSchedulerWfqCos1Weight
				INTEGER,
			genEquipProfilesSchedulerWfqCos2Weight
				INTEGER,
			genEquipProfilesSchedulerWfqCos3Weight
				INTEGER,
			genEquipProfilesSchedulerWfqCos4Weight
				INTEGER,
			genEquipProfilesSchedulerWfqCos5Weight
				INTEGER,
			genEquipProfilesSchedulerWfqCos6Weight
				INTEGER,
			genEquipProfilesSchedulerWfqCos7Weight
				INTEGER,
			genEquipProfilesSchedulerWfqRowStatus
				RowStatus
}


genEquipProfilesSchedulerWfqIndex		OBJECT-TYPE
		SYNTAX 		INTEGER  (1..7)
		ACCESS		read-only
        STATUS		mandatory
        DESCRIPTION
		"WFQ Profile ID."
::= { genEquipProfilesSchedulerWfqEntry 1 }

genEquipProfilesSchedulerWfqCos0Weight		OBJECT-TYPE
		SYNTAX 		INTEGER (1..256)
		ACCESS		read-write
        STATUS		mandatory
        DESCRIPTION
		"CoS 0 Weight."
::= { genEquipProfilesSchedulerWfqEntry 2 }

genEquipProfilesSchedulerWfqCos1Weight		OBJECT-TYPE
		SYNTAX 		INTEGER (1..256)
		ACCESS		read-write
        STATUS		mandatory
        DESCRIPTION
		"CoS 1 Weight."
::= { genEquipProfilesSchedulerWfqEntry 3 }

genEquipProfilesSchedulerWfqCos2Weight		OBJECT-TYPE
		SYNTAX 		INTEGER (1..256)
		ACCESS		read-write
        STATUS		mandatory
        DESCRIPTION
		"CoS 2 Weight."
::= { genEquipProfilesSchedulerWfqEntry 4 }

genEquipProfilesSchedulerWfqCos3Weight		OBJECT-TYPE
		SYNTAX 		INTEGER (1..256)
		ACCESS		read-write
        STATUS		mandatory
        DESCRIPTION
		"CoS 3 Weight."
::= { genEquipProfilesSchedulerWfqEntry 5 }

genEquipProfilesSchedulerWfqCos4Weight		OBJECT-TYPE
		SYNTAX 		INTEGER
		ACCESS		read-write
        STATUS		mandatory
        DESCRIPTION
		"CoS 4 Weight."
::= { genEquipProfilesSchedulerWfqEntry 6 }

genEquipProfilesSchedulerWfqCos5Weight		OBJECT-TYPE
		SYNTAX 		INTEGER (1..256)
		ACCESS		read-write
        STATUS		mandatory
        DESCRIPTION
		"Green CoS 2 priority."
::= { genEquipProfilesSchedulerWfqEntry 7 }

genEquipProfilesSchedulerWfqCos6Weight		OBJECT-TYPE
		SYNTAX 		INTEGER (1..256)
		ACCESS		read-write
        STATUS		mandatory
        DESCRIPTION
		"CoS 3 Description."
::= { genEquipProfilesSchedulerWfqEntry 8 }

genEquipProfilesSchedulerWfqCos7Weight		OBJECT-TYPE
		SYNTAX 		INTEGER (1..256)
		ACCESS		read-write
        STATUS		mandatory
        DESCRIPTION
		"CoS 7 Weight."
::= { genEquipProfilesSchedulerWfqEntry 9 }

genEquipProfilesSchedulerWfqRowStatus		OBJECT-TYPE
		SYNTAX 		RowStatus
		ACCESS		read-write
        STATUS		mandatory
        DESCRIPTION
		"Table Mib Row Status."
::= { genEquipProfilesSchedulerWfqEntry 30 }

--
-- Switch Application sw-ap-l2-if-logical-profile-egress-shaper-table
--

genEquipProfilesL2ShaperTable  OBJECT-TYPE
        SYNTAX  SEQUENCE OF GenEquipProfilesL2ShaperEntry
        ACCESS  not-accessible
        STATUS mandatory
        DESCRIPTION
        "The table holds the Egress Shaper profiles at port level."
        ::= { genEquipTmProfiles 5 }

genEquipProfilesL2ShaperEntry OBJECT-TYPE
        SYNTAX GenEquipProfilesL2ShaperEntry
        ACCESS not-accessible
        STATUS mandatory
          DESCRIPTION
        "The table entry holds the Egress Shaper profiles at port level."
        INDEX { genEquipProfilesL2ShaperIndex }
        ::= { genEquipProfilesL2ShaperTable 1 }

GenEquipProfilesL2ShaperEntry ::=
		SEQUENCE {
			genEquipProfilesL2ShaperIndex
				INTEGER,
			genEquipProfilesL2ShaperDescription
				DisplayString,
			genEquipProfilesL2ShaperCir
				INTEGER,
			genEquipProfilesL2ShaperCbs
				INTEGER,
			genEquipProfilesL2ShaperBurstType
				BurstType,
			genEquipProfilesL2ShaperRowStatus
				RowStatus
}


genEquipProfilesL2ShaperIndex		OBJECT-TYPE
		SYNTAX 		INTEGER  (1..32)
		ACCESS		read-only
        STATUS		mandatory
        DESCRIPTION
		"Shaper Profile ID."
::= { genEquipProfilesL2ShaperEntry 1 }

genEquipProfilesL2ShaperDescription		OBJECT-TYPE
		SYNTAX 		DisplayString (SIZE (0..21))
		ACCESS		read-write
        STATUS		mandatory
        DESCRIPTION
		"Shaper Description."
::= { genEquipProfilesL2ShaperEntry 2 }

genEquipProfilesL2ShaperCir		OBJECT-TYPE
		SYNTAX 		INTEGER
		ACCESS		read-write
        STATUS		mandatory
        DESCRIPTION
		"Committed Information Rate (in Bits)."
::= { genEquipProfilesL2ShaperEntry 3 }

genEquipProfilesL2ShaperCbs		OBJECT-TYPE
		SYNTAX 		INTEGER (1..2048)
		ACCESS		read-write
        STATUS		mandatory
        DESCRIPTION
		"Committed Burst Size (in Bytes)."
::= { genEquipProfilesL2ShaperEntry 4 }

genEquipProfilesL2ShaperBurstType 	OBJECT-TYPE
		SYNTAX 		BurstType
		ACCESS		read-write
        STATUS		mandatory
        DESCRIPTION
		"CBS burst type - short (minimal) size or long burst (recomanded for long RTT)."
::= { genEquipProfilesL2ShaperEntry 5 }


genEquipProfilesL2ShaperRowStatus		OBJECT-TYPE
		SYNTAX 		RowStatus
		ACCESS		read-write
        STATUS		mandatory
        DESCRIPTION
		"Table Mib Row Status."
::= { genEquipProfilesL2ShaperEntry 30 }

--
-- Switch Application sw-ap-l3-srv-profile-egress-shaper-table
--

genEquipProfilesL3ServiceShaperTable  OBJECT-TYPE
        SYNTAX  SEQUENCE OF GenEquipProfilesL3ServiceShaperEntry
        ACCESS  not-accessible
        STATUS mandatory
        DESCRIPTION
        "The table holds the Egress Shaper profiles at service level."
        ::= { genEquipTmProfiles 6 }

genEquipProfilesL3ServiceShaperEntry OBJECT-TYPE
        SYNTAX GenEquipProfilesL3ServiceShaperEntry
        ACCESS not-accessible
        STATUS mandatory
          DESCRIPTION
        "The table entry holds the Egress Shaper profiles at service level."
        INDEX { genEquipProfilesL3ServiceShaperIndex }
        ::= { genEquipProfilesL3ServiceShaperTable 1 }

GenEquipProfilesL3ServiceShaperEntry ::=
		SEQUENCE {
			genEquipProfilesL3ServiceShaperIndex
				INTEGER,
			genEquipProfilesL3ServiceShaperDescription
				DisplayString,
			genEquipProfilesL3ServiceShaperCir
				INTEGER,
			genEquipProfilesL3ServiceShaperCbs
				INTEGER,
			genEquipProfilesL3ServiceShaperPir
				INTEGER,
			genEquipProfilesL3ServiceShaperPbs
				INTEGER,
			genEquipProfilesL3ServiceShaperBurstType
				BurstType,
			genEquipProfilesL3ServiceShaperRowStatus
				RowStatus
}


genEquipProfilesL3ServiceShaperIndex		OBJECT-TYPE
		SYNTAX 		INTEGER  (1..256)
		ACCESS		read-only
        STATUS		mandatory
        DESCRIPTION
		"Shaper Profile ID."
::= { genEquipProfilesL3ServiceShaperEntry 1 }

genEquipProfilesL3ServiceShaperDescription		OBJECT-TYPE
		SYNTAX 		DisplayString (SIZE (0..21))
		ACCESS		read-write
        STATUS		mandatory
        DESCRIPTION
		"Shaper Description."
::= { genEquipProfilesL3ServiceShaperEntry 2 }

genEquipProfilesL3ServiceShaperCir		OBJECT-TYPE
		SYNTAX 		INTEGER
		ACCESS		read-write
        STATUS		mandatory
        DESCRIPTION
		"Committed Information Rate (in Bits)."
::= { genEquipProfilesL3ServiceShaperEntry 3 }

genEquipProfilesL3ServiceShaperCbs		OBJECT-TYPE
		SYNTAX 		INTEGER (1..1016)
		ACCESS		read-write
        STATUS		mandatory
        DESCRIPTION
		"Committed Burst Size (in Bytes)."
::= { genEquipProfilesL3ServiceShaperEntry 4 }

genEquipProfilesL3ServiceShaperPir		OBJECT-TYPE
		SYNTAX 		INTEGER
		ACCESS		read-write
        STATUS		mandatory
        DESCRIPTION
		"Peak Information Rate (in Bits)."
::= { genEquipProfilesL3ServiceShaperEntry 5 }

genEquipProfilesL3ServiceShaperPbs		OBJECT-TYPE
		SYNTAX 		INTEGER (1..1016)
		ACCESS		read-write
        STATUS		mandatory
        DESCRIPTION
		"Peak Burst size (in Bytes)."
::= { genEquipProfilesL3ServiceShaperEntry 6 }

genEquipProfilesL3ServiceShaperBurstType 	OBJECT-TYPE
		SYNTAX 		BurstType
		ACCESS		read-write
        STATUS		mandatory
        DESCRIPTION
		"CBS and PBS burst type - short (minimal) size or long burst (recomanded for long RTT)."
::= { genEquipProfilesL3ServiceShaperEntry 7 }

genEquipProfilesL3ServiceShaperRowStatus		OBJECT-TYPE
		SYNTAX 		RowStatus
		ACCESS		read-write
        STATUS		mandatory
        DESCRIPTION
		"Table Mib Row Status."
::= { genEquipProfilesL3ServiceShaperEntry 30 }

--
-- Switch Application sw-ap-l4-srv-sp-profile-egress-queue-shaper-table
--

genEquipProfilesEgressL4QueueShaperTable  OBJECT-TYPE
        SYNTAX  SEQUENCE OF GenEquipProfilesEgressL4QueueShaperEntry
        ACCESS  not-accessible
        STATUS mandatory
        DESCRIPTION
        "The table holds the Egress Shaper profiles at Queue level."
        ::= { genEquipTmProfiles 7 }

genEquipProfilesEgressL4QueueShaperEntry OBJECT-TYPE
        SYNTAX GenEquipProfilesEgressL4QueueShaperEntry
        ACCESS not-accessible
        STATUS mandatory
          DESCRIPTION
        "The table entry holds the Egress Shaper profiles at Queue level."
        INDEX { genEquipProfilesEgressL4QueueShaperIndex }
        ::= { genEquipProfilesEgressL4QueueShaperTable 1 }

GenEquipProfilesEgressL4QueueShaperEntry ::=
		SEQUENCE {
			genEquipProfilesEgressL4QueueShaperIndex
				INTEGER,
			genEquipProfilesEgressL4QueueShaperDescription
				DisplayString,
			genEquipProfilesEgressL4QueueShaperCir
				INTEGER,
			genEquipProfilesEgressL4QueueShaperCbs
				INTEGER,
			genEquipProfilesEgressL4QueueShaperBurstType
				BurstType,
			genEquipProfilesEgressL4QueueShaperRowStatus
				RowStatus
}


genEquipProfilesEgressL4QueueShaperIndex		OBJECT-TYPE
		SYNTAX 		INTEGER  (1..32)
		ACCESS		read-only
        STATUS		mandatory
        DESCRIPTION
		"Shaper Profile ID."
::= { genEquipProfilesEgressL4QueueShaperEntry 1 }

genEquipProfilesEgressL4QueueShaperDescription		OBJECT-TYPE
		SYNTAX 		DisplayString (SIZE (0..21))
		ACCESS		read-write
        STATUS		mandatory
        DESCRIPTION
		"Shaper Description."
::= { genEquipProfilesEgressL4QueueShaperEntry 2 }

genEquipProfilesEgressL4QueueShaperCir		OBJECT-TYPE
		SYNTAX 		INTEGER
		ACCESS		read-write
        STATUS		mandatory
        DESCRIPTION
		"Committed Information Rate (in Bits)."
::= { genEquipProfilesEgressL4QueueShaperEntry 3 }

genEquipProfilesEgressL4QueueShaperCbs		OBJECT-TYPE
		SYNTAX 		INTEGER (1..1016)
		ACCESS		read-write
        STATUS		mandatory
        DESCRIPTION
		"Committed Burst Size (in Bytes)."
::= { genEquipProfilesEgressL4QueueShaperEntry 4 }

genEquipProfilesEgressL4QueueShaperBurstType 		OBJECT-TYPE
		SYNTAX 		BurstType
		ACCESS		read-write
        STATUS		mandatory
        DESCRIPTION
		"CBS burst type - short (minimal) size or long burst (recomanded for long RTT)."
::= { genEquipProfilesEgressL4QueueShaperEntry 5 }

genEquipProfilesEgressL4QueueShaperRowStatus		OBJECT-TYPE
		SYNTAX 		RowStatus
		ACCESS		read-write
        STATUS		mandatory
        DESCRIPTION
		"Table Mib Row Status."
::= { genEquipProfilesEgressL4QueueShaperEntry 30 }


-- TM Config
genEquipTmConfig OBJECT IDENTIFIER ::= {genEquipServicesTM 3}

--
-- Switch Application sw-ap-l4-srv-sp-egress-wred-profile-association-queue-table
--

genEquipTmL4WredAssociationTable  OBJECT-TYPE
        SYNTAX  SEQUENCE OF GenEquipTmL4WredAssociationEntry
        ACCESS  not-accessible
        STATUS mandatory
        DESCRIPTION
        "The table holds the user selelcted WRED profile for eac Egress Queue."
        ::= { genEquipTmConfig 1 }

genEquipTmL4WredAssociationEntry OBJECT-TYPE
        SYNTAX GenEquipTmL4WredAssociationEntry
        ACCESS not-accessible
        STATUS mandatory
          DESCRIPTION
        "The table entry holds the user selelcted WRED profile for eac Egress Queue."
        INDEX { genEquipTmL4WredAssociationIfIndex,
				genEquipTmL4WredAssociationServiceIndex,
				genEquipTmL4WredAssociationCosQueueIndex }
        ::= { genEquipTmL4WredAssociationTable 1 }

GenEquipTmL4WredAssociationEntry ::=
		SEQUENCE {
			genEquipTmL4WredAssociationIfIndex
				INTEGER,
			genEquipTmL4WredAssociationServiceIndex
				INTEGER,
			genEquipTmL4WredAssociationCosQueueIndex
				INTEGER,
			genEquipTmL4WredAssociationWredProfileId
				INTEGER
}


genEquipTmL4WredAssociationIfIndex		OBJECT-TYPE
		SYNTAX 		INTEGER
		ACCESS		read-only
        STATUS		mandatory
        DESCRIPTION
		"Ethernet Logical port if-index table key."
::= { genEquipTmL4WredAssociationEntry 1 }

genEquipTmL4WredAssociationServiceIndex		OBJECT-TYPE
		SYNTAX 		INTEGER (1..63)
		ACCESS		read-only
        STATUS		mandatory
        DESCRIPTION
		"Service Bundle ID."
::= { genEquipTmL4WredAssociationEntry 2 }

genEquipTmL4WredAssociationCosQueueIndex		OBJECT-TYPE
		SYNTAX 		INTEGER (0..7)
		ACCESS		read-only
        STATUS		mandatory
        DESCRIPTION
		"CoS Queue ID."
::= { genEquipTmL4WredAssociationEntry 3 }

genEquipTmL4WredAssociationWredProfileId		OBJECT-TYPE
		SYNTAX 		INTEGER (1..32)
		ACCESS		read-write
        STATUS		mandatory
        DESCRIPTION
		"WRED Profile ID."
::= { genEquipTmL4WredAssociationEntry 4 }

--
-- Switch Application sw-ap-l2-if-logical-egress-scheduler-cos-priority-profile-association-to-if-table
--

genEquipTmSchedulerCoSPriAssociationTable  OBJECT-TYPE
        SYNTAX  SEQUENCE OF GenEquipTmSchedulerCoSPriAssociationEntry
        ACCESS  not-accessible
        STATUS mandatory
        DESCRIPTION
        "The table holds the user selected Scheduler Priority Profile for each Egress port."
        ::= { genEquipTmConfig 2 }

genEquipTmSchedulerCoSPriAssociationEntry OBJECT-TYPE
        SYNTAX GenEquipTmSchedulerCoSPriAssociationEntry
        ACCESS not-accessible
        STATUS mandatory
          DESCRIPTION
        "The table entry holds the user selected Scheduler Priority Profile for each Egress port."
        INDEX { genEquipTmSchedulerCoSPriAssociationIfIndex }
        ::= { genEquipTmSchedulerCoSPriAssociationTable 1 }

GenEquipTmSchedulerCoSPriAssociationEntry ::=
		SEQUENCE {
			genEquipTmSchedulerCoSPriAssociationIfIndex
				INTEGER,
			genEquipTmSchedulerCoSPriAssociationAssociatedProfileId
				INTEGER
}


genEquipTmSchedulerCoSPriAssociationIfIndex		OBJECT-TYPE
		SYNTAX 		INTEGER
		ACCESS		read-only
        STATUS		mandatory
        DESCRIPTION
		"Ethernet Logical port if-index table key."
::= { genEquipTmSchedulerCoSPriAssociationEntry 1 }

genEquipTmSchedulerCoSPriAssociationAssociatedProfileId		OBJECT-TYPE
		SYNTAX 		INTEGER (1..9)
		ACCESS		read-write
        STATUS		mandatory
        DESCRIPTION
		"Queue Scheduler Profile ID."
::= { genEquipTmSchedulerCoSPriAssociationEntry 2 }

--
-- Switch Application sw-ap-l3-srv-egress-shaper-profile-association-to-service-bundle-table
--

genEquipTmL3ServiceShaperAssociationTable  OBJECT-TYPE
        SYNTAX  SEQUENCE OF GenEquipTmL3ServiceShaperAssociationEntry
        ACCESS  not-accessible
        STATUS mandatory
        DESCRIPTION
        "The table holds the user selected Shapping profiles for each Service Bundle."
        ::= { genEquipTmConfig 3 }

genEquipTmL3ServiceShaperAssociationEntry OBJECT-TYPE
        SYNTAX GenEquipTmL3ServiceShaperAssociationEntry
        ACCESS not-accessible
        STATUS mandatory
          DESCRIPTION
        "The table entry holds the user selected Shapping profiles for each Service Bundle."
        INDEX { genEquipTmL3ServiceShaperAssociationIfIndex,
				genEquipTmL3ServiceShaperAssociationServiceClassIndex }
        ::= { genEquipTmL3ServiceShaperAssociationTable 1 }

GenEquipTmL3ServiceShaperAssociationEntry ::=
		SEQUENCE {
			genEquipTmL3ServiceShaperAssociationIfIndex
				INTEGER,
			genEquipTmL3ServiceShaperAssociationServiceClassIndex
				INTEGER,
			genEquipTmL3ServiceShaperAssociationShaperProfileId
				INTEGER,
			genEquipTmL3ServiceShaperAssociationShaperAdmin
				EnableDisable,
			genEquipTmL3ServiceShaperAssociationRowStatus
				RowStatus
}


genEquipTmL3ServiceShaperAssociationIfIndex		OBJECT-TYPE
		SYNTAX 		INTEGER
		ACCESS		read-only
        STATUS		mandatory
        DESCRIPTION
		"Ethernet Logical port if-index table key."
::= { genEquipTmL3ServiceShaperAssociationEntry 1 }

genEquipTmL3ServiceShaperAssociationServiceClassIndex		OBJECT-TYPE
		SYNTAX 		INTEGER (1..63)
		ACCESS		read-only
        STATUS		mandatory
        DESCRIPTION
		"Service Bundle ID."
::= { genEquipTmL3ServiceShaperAssociationEntry 2 }

genEquipTmL3ServiceShaperAssociationShaperProfileId		OBJECT-TYPE
		SYNTAX 		INTEGER (1..256)
		ACCESS		read-write
        STATUS		mandatory
        DESCRIPTION
		"Shaper Profile ID."
::= { genEquipTmL3ServiceShaperAssociationEntry 3 }

genEquipTmL3ServiceShaperAssociationShaperAdmin		OBJECT-TYPE
		SYNTAX 		EnableDisable
		ACCESS		read-write
        STATUS		mandatory
        DESCRIPTION
		"Shaper Admin."
::= { genEquipTmL3ServiceShaperAssociationEntry 4 }

genEquipTmL3ServiceShaperAssociationRowStatus		OBJECT-TYPE
		SYNTAX 		RowStatus
		ACCESS		read-write
        STATUS		mandatory
        DESCRIPTION
		"Table Mib Row Status."
::= { genEquipTmL3ServiceShaperAssociationEntry 30 }

--
-- Switch Application sw-ap-l2-if-logical-egress-shaper-profile-association-to-if-table
--

genEquipTmL2ShaperAssociationTable  OBJECT-TYPE
        SYNTAX  SEQUENCE OF GenEquipTmL2ShaperAssociationEntry
        ACCESS  not-accessible
        STATUS mandatory
        DESCRIPTION
        "The table holds the user selected Shapping profiles for each Ethernet Port."
        ::= { genEquipTmConfig 4 }

genEquipTmL2ShaperAssociationEntry OBJECT-TYPE
        SYNTAX GenEquipTmL2ShaperAssociationEntry
        ACCESS not-accessible
        STATUS mandatory
          DESCRIPTION
        "The table entry holds the user selected Shapping profiles for each Ethernet Port."
        INDEX { genEquipTmL2ShaperAssociationIfIndex }
        ::= { genEquipTmL2ShaperAssociationTable 1 }

GenEquipTmL2ShaperAssociationEntry ::=
		SEQUENCE {
			genEquipTmL2ShaperAssociationIfIndex
				INTEGER,
			genEquipTmL2ShaperAssociationProfileId
				INTEGER,
			genEquipTmL2ShaperAssociationAdmin
				EnableDisable,
			genEquipTmL2ShaperAssociationRowStatus
				RowStatus
}


genEquipTmL2ShaperAssociationIfIndex		OBJECT-TYPE
		SYNTAX 		INTEGER
		ACCESS		read-only
        STATUS		mandatory
        DESCRIPTION
		"Ethernet Logical port if-index table key."
::= { genEquipTmL2ShaperAssociationEntry 1 }

genEquipTmL2ShaperAssociationProfileId		OBJECT-TYPE
		SYNTAX 		INTEGER (1..32)
		ACCESS		read-write
        STATUS		mandatory
        DESCRIPTION
		"Port Shaper Profile ID."
::= { genEquipTmL2ShaperAssociationEntry 2 }

genEquipTmL2ShaperAssociationAdmin		OBJECT-TYPE
		SYNTAX 		EnableDisable
		ACCESS		read-write
        STATUS		mandatory
        DESCRIPTION
		"Port Shaper Admin."
::= { genEquipTmL2ShaperAssociationEntry 3 }

genEquipTmL2ShaperAssociationRowStatus		OBJECT-TYPE
		SYNTAX 		RowStatus
		ACCESS		read-write
        STATUS		mandatory
        DESCRIPTION
		"Table Mib Row Status."
::= { genEquipTmL2ShaperAssociationEntry 30 }

--
-- Switch Application sw-ap-l4-srv-sp-egress-queue-shaper-profile-association-to-queue-table
--

genEquipTmL4QueueShaperAssociationTable  OBJECT-TYPE
        SYNTAX  SEQUENCE OF GenEquipTmL4QueueShaperAssociationEntry
        ACCESS  not-accessible
        STATUS mandatory
        DESCRIPTION
        "The table holds the user selected Shapping profiles for each Ethernet PortThe table holds the user selected Shapping profiles for each transmitting Queue."
        ::= { genEquipTmConfig 5 }

genEquipTmL4QueueShaperAssociationEntry OBJECT-TYPE
        SYNTAX GenEquipTmL4QueueShaperAssociationEntry
        ACCESS not-accessible
        STATUS mandatory
          DESCRIPTION
        "The table entry holds the user selected Shapping profiles for each transmitting Queue."
        INDEX { genEquipTmL4QueueShaperAssociationIfIndex,
				genEquipTmL4QueueShaperAssociationServiceIndex,
				genEquipTmL4QueueShaperAssociationCosQueueIndex }
        ::= { genEquipTmL4QueueShaperAssociationTable 1 }

GenEquipTmL4QueueShaperAssociationEntry ::=
		SEQUENCE {
			genEquipTmL4QueueShaperAssociationIfIndex
				INTEGER,
			genEquipTmL4QueueShaperAssociationServiceIndex
				INTEGER,
			genEquipTmL4QueueShaperAssociationCosQueueIndex
				INTEGER,
			genEquipTmL4QueueShaperAssociationShaperProfileId
				INTEGER,
			genEquipTmL4QueueShaperAssociationShaperProfileAdmin
				EnableDisable,
			genEquipTmL4QueueShaperAssociationRowStatus
				RowStatus
}


genEquipTmL4QueueShaperAssociationIfIndex		OBJECT-TYPE
		SYNTAX 		INTEGER
		ACCESS		read-only
        STATUS		mandatory
        DESCRIPTION
		"Ethernet Logical port if-index table key."
::= { genEquipTmL4QueueShaperAssociationEntry 1 }

genEquipTmL4QueueShaperAssociationServiceIndex		OBJECT-TYPE
		SYNTAX 		INTEGER (1..63)
		ACCESS		read-only
        STATUS		mandatory
        DESCRIPTION
		"Service Bundle ID."
::= { genEquipTmL4QueueShaperAssociationEntry 2 }

genEquipTmL4QueueShaperAssociationCosQueueIndex		OBJECT-TYPE
		SYNTAX 		INTEGER (0..7)
		ACCESS		read-only
        STATUS		mandatory
        DESCRIPTION
		"CoS Queue ID."
::= { genEquipTmL4QueueShaperAssociationEntry 3 }

genEquipTmL4QueueShaperAssociationShaperProfileId		OBJECT-TYPE
		SYNTAX 		INTEGER (1..32)
		ACCESS		read-write
        STATUS		mandatory
        DESCRIPTION
		"Queue Shaper Profile ID."
::= { genEquipTmL4QueueShaperAssociationEntry 4 }

genEquipTmL4QueueShaperAssociationShaperProfileAdmin		OBJECT-TYPE
		SYNTAX 		EnableDisable
		ACCESS		read-write
        STATUS		mandatory
        DESCRIPTION
		"Queue Shaper Admin."
::= { genEquipTmL4QueueShaperAssociationEntry 5 }

genEquipTmL4QueueShaperAssociationRowStatus		OBJECT-TYPE
		SYNTAX 		RowStatus
		ACCESS		read-write
        STATUS		mandatory
        DESCRIPTION
		"Table Mib Row Status."
::= { genEquipTmL4QueueShaperAssociationEntry 30 }

--
-- Switch Application sw-ap-l2-if-logical-egress-scheduler-cos-wfq-profile-association-to-if-table
--

genEquipTmSchedulerWfqAssociationTable  OBJECT-TYPE
        SYNTAX  SEQUENCE OF GenEquipTmSchedulerWfqAssociationEntry
        ACCESS  not-accessible
        STATUS mandatory
        DESCRIPTION
        "The table holds the user selected Scheduler WFQ weights Profile for each Egress port."
        ::= { genEquipTmConfig 6 }

genEquipTmSchedulerWfqAssociationEntry OBJECT-TYPE
        SYNTAX GenEquipTmSchedulerWfqAssociationEntry
        ACCESS not-accessible
        STATUS mandatory
          DESCRIPTION
        "The table entry holds the user selected Scheduler WFQ weights Profile for each Egress port."
        INDEX { genEquipTmSchedulerWfqAssociationIfIndex }
        ::= { genEquipTmSchedulerWfqAssociationTable 1 }

GenEquipTmSchedulerWfqAssociationEntry ::=
		SEQUENCE {
			genEquipTmSchedulerWfqAssociationIfIndex
				INTEGER,
			genEquipTmSchedulerWfqAssociationProfileId
				INTEGER
}


genEquipTmSchedulerWfqAssociationIfIndex		OBJECT-TYPE
		SYNTAX 		INTEGER
		ACCESS		read-only
        STATUS		mandatory
        DESCRIPTION
		"Ethernet Logical port if-index table key."
::= { genEquipTmSchedulerWfqAssociationEntry 1 }

genEquipTmSchedulerWfqAssociationProfileId		OBJECT-TYPE
		SYNTAX 		INTEGER (1..7)
		ACCESS		read-write
        STATUS		mandatory
        DESCRIPTION
		"WFQ Scheduler Profile ID"
::= { genEquipTmSchedulerWfqAssociationEntry 2 }


-- The following tables are accessed by its slot, there is no indirect access to this tables through main slot
-- Radio Clock Source
genEquipSynchronizationRadioClkSrcSource		OBJECT-TYPE
		SYNTAX 		INTEGER
		ACCESS		read-write
        STATUS		mandatory
        DESCRIPTION
		"This parameters determines whether the system reference frequency is transported through the radio.
         0 indicates that the outgoing signal takes its clock from an independant local clock.
         channel number indicates that the clock is from that radio-channel reference clock,
         as taken from the synchronization source interface."
::= { genEquipSynchronization 3 }

genEquipSynchronizationSDHClkSrcSource		OBJECT-TYPE
		SYNTAX 		INTEGER
		ACCESS		read-write
        STATUS		mandatory
        DESCRIPTION
		"This parameters determines whether the system reference frequency is transported
         through the interface. if value is 0 it indicates that the outgoing signal takes its
		 clock from an independant local clock.
         system-clock-source indicates that the clock is from the system reference clock,
         as taken from the synchronization source interface."
::= { genEquipSynchronization 4 }

genEquipSynchronizationPDHClkSrcTable  OBJECT-TYPE
        SYNTAX  SEQUENCE OF GenEquipSynchronizationPDHClkSrcEntry
        ACCESS  not-accessible
        STATUS mandatory
        DESCRIPTION
        "Synchronization source table."
        ::= { genEquipSynchronization 5 }

genEquipSynchronizationPDHClkSrcEntry OBJECT-TYPE
        SYNTAX GenEquipSynchronizationPDHClkSrcEntry
        ACCESS not-accessible
        STATUS mandatory
          DESCRIPTION
          "Synchronization source table."
        INDEX { genEquipSynchronizationPDHClkSrcIFNum }
        ::= { genEquipSynchronizationPDHClkSrcTable 1 }

GenEquipSynchronizationPDHClkSrcEntry ::=
		SEQUENCE {
			genEquipSynchronizationPDHClkSrcIFNum
				INTEGER,
			genEquipSynchronizationPDHClkSrcSource
            	INTEGER
}

genEquipSynchronizationPDHClkSrcIFNum		OBJECT-TYPE
		SYNTAX 		INTEGER
		ACCESS		read-write
        STATUS		mandatory
        DESCRIPTION
		"This parameters the interface which is configured to take the system reference clock
        or a local clock in genEquipSynchronizationSDHClkSrcSource.
        The number indicates the E1/DS1 interface being configured (1-32)."
::= { genEquipSynchronizationPDHClkSrcEntry 2 }

genEquipSynchronizationPDHClkSrcSource		OBJECT-TYPE
		SYNTAX 		INTEGER {
				local-clock(0),
				system-clock-source(1)
		}
		ACCESS		read-write
        STATUS		mandatory
        DESCRIPTION
		"This parameters determines whether the system reference frequency is transported
         through the interface defined in genEquipSynchronizationPDHClkSrcIFNum.
         local-clock indicates that the outgoing signal takes its clock from an independant local clock.
         system-clock-source indicates that the clock is from the system reference clock,
         as taken from the synchronization source interface."
::= { genEquipSynchronizationPDHClkSrcEntry 3 }

genEquipSynchronizationPRCRegeneratorMode		OBJECT-TYPE
		SYNTAX EnableDisable
		ACCESS		read-write
        STATUS		mandatory
        DESCRIPTION
		"This parameter sets the IDU to point-to-point PRC quality frequency distribution mode.
		Notice that this is relevant only for smart pipe applications"
::= { genEquipSynchronization 6 }

genEquipSynchronizationPRCRegeneratorDirection OBJECT-TYPE
		SYNTAX INTEGER {
			line-to-radio (0),
			radio-to-line (1)
		}
		ACCESS		read-write
        STATUS		mandatory
        DESCRIPTION
		"This parameter sets the direction in which the frequency signal is transported,
		in the case of electrical GBE interfaces.
		Notice that for optical interfaces, this parameter has no effect."
::= { genEquipSynchronization 7 }


genEquipSynchronizationSrcRevertiveTimer		OBJECT-TYPE
		SYNTAX INTEGER (0..30)
		ACCESS		read-write
        STATUS		mandatory
        DESCRIPTION
		"this parameter sets the timeout (in seconds) for a counter which is set once
    	an interface recovers from a failure; after this timeout the interface will be considered
    	stable and can be used as a synchronization source. A value of zero means no timer."
::= { genEquipSynchronization 8 }

genEquipSynchronizationSrcActiveSyncSourceIndex		OBJECT-TYPE
		SYNTAX INTEGER
		ACCESS		read-only
        STATUS		mandatory
        DESCRIPTION
		"The active synchronization source."
::= { genEquipSynchronization 9 }

genEquipSynchronizationNodeMode		OBJECT-TYPE
		SYNTAX INTEGER {
				automatic (0),
				force (1)
		}
		ACCESS		read-write
        STATUS		mandatory
        DESCRIPTION
		"This parameter allows forcing a certain source as the active source for the system reference clock.
		When forced, the active source is specified by genEquipSynchronizationForceSource.
		In automatic mode, the active source is determined by quality and priority of the relevant interfaces
		(as configured in table genEquipSynchronizationSrcTable)."
::= { genEquipSynchronization 10 }

genEquipSynchronizationForceSource		OBJECT-TYPE
		SYNTAX INTEGER (0..8)
		ACCESS		read-write
        STATUS		mandatory
        DESCRIPTION
		"This parameter determines which source number will be forced as active when  genEquipSynchronizationNodeMode is set to force."
::= { genEquipSynchronization 11 }

genEquipSynchronizationSystemReferenceQuality		OBJECT-TYPE
		SYNTAX INTEGER {
						automatic(0),
						prs(1),
						g811(2),
						transit-node(3),
						ssu-a(4),
						unknown(5),
						stratum2(7),
						ssu-b(8),
						stratum3(10),
						g813-8262(11),
						smc(12),
						stratum3e(13),
						do-not-use (15)
		}
		ACCESS		read-only
        STATUS		mandatory
        DESCRIPTION
		"This parameter shows the current quality of the system reference clock"
::= { genEquipSynchronization 12 }

genEquipSynchronizationRegeneratorSSMAdmin		OBJECT-TYPE
		SYNTAX INTEGER
		ACCESS		read-write
        STATUS		mandatory
        DESCRIPTION
		"This parameter determines whether or not in pipe mode the system generates SSM messages"
::= { genEquipSynchronization 13 }

genEquipSynchronizationPWClkExport 				OBJECT-TYPE
		SYNTAX INTEGER {
					local-clock(0),
					system-clock-source(1)
		}
		ACCESS		read-write
        STATUS		mandatory
        DESCRIPTION
		"This parameter determines whether the system reference clock is exported toward the PWE3 T-Card;
		This reference can be exported towards front panel using ExportClkFrontPannel or used as a common clock for
		PWs using ClockSourceRef. Notice that either this or any single one of the PW T-card TDM interfaces can export the reference clock,
		but not both at the same time."
::= { genEquipSynchronization 14 }


-- Synch Pipe Configurations  - sync-pipe-config-table
--
genEquipSynchronizationPipeTable  OBJECT-TYPE
        SYNTAX  SEQUENCE OF GenEquipSynchronizationPipeEntry
        ACCESS  not-accessible
        STATUS mandatory
        DESCRIPTION
        "The table shows pipe interfaces."
        ::= { genEquipSynchronization 20 }

genEquipSynchronizationPipeEntry OBJECT-TYPE
        SYNTAX GenEquipSynchronizationPipeEntry
        ACCESS not-accessible
        STATUS mandatory
        DESCRIPTION
        "The table entry shows pipe interfaces."
        INDEX { genEquipSynchronizationPipeId }
        ::= { genEquipSynchronizationPipeTable 1 }

GenEquipSynchronizationPipeEntry ::=
		SEQUENCE {
			genEquipSynchronizationPipeId
				INTEGER,
			genEquipSynchronizationPipeInd1
				INTEGER,
			genEquipSynchronizationPipeInd2
				INTEGER,
			genEquipSynchronizationPipeStatus
				INTEGER
}

genEquipSynchronizationPipeId OBJECT-TYPE
        SYNTAX INTEGER
        ACCESS read-only
        STATUS mandatory
        DESCRIPTION
        "Pipe ID."
        ::= { genEquipSynchronizationPipeEntry 1 }


genEquipSynchronizationPipeInd1 OBJECT-TYPE
        SYNTAX INTEGER
        ACCESS read-write
        STATUS mandatory
        DESCRIPTION
        "Sync Interface 1."
        ::= { genEquipSynchronizationPipeEntry 2 }

genEquipSynchronizationPipeInd2 OBJECT-TYPE
        SYNTAX INTEGER
        ACCESS read-write
        STATUS mandatory
        DESCRIPTION
        "Sync Interface 2."
        ::= { genEquipSynchronizationPipeEntry 3 }

genEquipSynchronizationPipeStatus OBJECT-TYPE
        SYNTAX INTEGER
        ACCESS read-write
        STATUS mandatory
        DESCRIPTION
        "Sync Pipe Status."
        ::= { genEquipSynchronizationPipeEntry 4 }

-- PTP (Precision Time Protocol)
genEquipSynchronizationPTP	OBJECT IDENTIFIER ::= {genEquipSynchronization 21}

genEquipSynchronizationPTPTcAdmin OBJECT-TYPE
        SYNTAX INTEGER
        ACCESS read-write
        STATUS mandatory
        DESCRIPTION
        "Transparent Clock (TC) administrative state."
        ::= { genEquipSynchronizationPTP 1 }


-- TC configuartion  - ptp-tc-config-table
--
genEquipSynchronizationPTPTcConfigTable  OBJECT-TYPE
        SYNTAX  SEQUENCE OF GenEquipSynchronizationPTPTcConfigEntry
        ACCESS  not-accessible
        STATUS mandatory
        DESCRIPTION
        "PTP (Precision Time Protocol) TC (Transparent Clock) configuration table."
        ::= { genEquipSynchronizationPTP 10 }

genEquipSynchronizationPTPTcConfigEntry OBJECT-TYPE
        SYNTAX GenEquipSynchronizationPTPTcConfigEntry
        ACCESS not-accessible
        STATUS mandatory
        DESCRIPTION
        "PTP (Precision Time Protocol) TC (Transparent Clock) configuration table entry."
        INDEX { genEquipSynchronizationPTPTcConfigId }
        ::= { genEquipSynchronizationPTPTcConfigTable 1 }

GenEquipSynchronizationPTPTcConfigEntry ::=
		SEQUENCE {
			genEquipSynchronizationPTPTcConfigId
				INTEGER,
			genEquipSynchronizationPTPTcConfigMaster
				INTEGER
}

genEquipSynchronizationPTPTcConfigId OBJECT-TYPE
        SYNTAX INTEGER
        ACCESS read-write
        STATUS mandatory
        DESCRIPTION
        "The interface on which TC function is required."
        ::= { genEquipSynchronizationPTPTcConfigEntry 1 }

genEquipSynchronizationPTPTcConfigMaster OBJECT-TYPE
        SYNTAX INTEGER {
					upstream(0),
					downstream(1)
					}
        ACCESS read-write
        STATUS mandatory
        DESCRIPTION
        "Points whether the interface's direction is upstream or downstream."
        ::= { genEquipSynchronizationPTPTcConfigEntry 2 }


-- TC Status  - ptp-tc-status-table
--
genEquipSynchronizationPTPTcStatusTable  OBJECT-TYPE
        SYNTAX  SEQUENCE OF GenEquipSynchronizationPTPTcStatusEntry
        ACCESS  not-accessible
        STATUS mandatory
        DESCRIPTION
        "PTP (Precision Time Protocol) TC (Transparent Clock) status table."
        ::= { genEquipSynchronizationPTP 11 }

genEquipSynchronizationPTPTcStatusEntry OBJECT-TYPE
        SYNTAX GenEquipSynchronizationPTPTcStatusEntry
        ACCESS not-accessible
        STATUS mandatory
        DESCRIPTION
        "PTP (Precision Time Protocol) TC (Transparent Clock) status table entry."
        INDEX { genEquipSynchronizationPTPTcStatusId }
        ::= { genEquipSynchronizationPTPTcStatusTable 1 }

GenEquipSynchronizationPTPTcStatusEntry ::=
		SEQUENCE {
			genEquipSynchronizationPTPTcStatusId
				INTEGER,
			genEquipSynchronizationPTPTcStatusState
				INTEGER,
			genEquipSynchronizationPTPTcStatusFreqLock
				DownUp
}

genEquipSynchronizationPTPTcStatusId OBJECT-TYPE
        SYNTAX INTEGER
        ACCESS read-only
        STATUS mandatory
        DESCRIPTION
        "The interface on which TC status is required."
        ::= { genEquipSynchronizationPTPTcStatusEntry 1 }


genEquipSynchronizationPTPTcStatusState OBJECT-TYPE
        SYNTAX INTEGER {
					down(0),
					init(1),
					calibrating(2),
					up(3)
		}
        ACCESS read-only
        STATUS mandatory
        DESCRIPTION
        "The status of the TC function that may be: Down, Init, Calibrating or Up."
        ::= { genEquipSynchronizationPTPTcStatusEntry 2 }

genEquipSynchronizationPTPTcStatusFreqLock OBJECT-TYPE
        SYNTAX DownUp
        ACCESS read-only
        STATUS mandatory
        DESCRIPTION
        "The lock status, Up or Down, of the network synchronization frequency that passes through the interface."
        ::= { genEquipSynchronizationPTPTcStatusEntry 3 }


-- Interfaces
genEquipInterfaces	OBJECT IDENTIFIER ::= {genEquip 9}

-- Interfaces - Ethernet
genEquipInterfacesEther	OBJECT IDENTIFIER ::= {genEquipInterfaces 1}

genEquipInterfacesEtherTable  OBJECT-TYPE
        SYNTAX  SEQUENCE OF GenEquipInterfacesEtherEntry
        ACCESS  not-accessible
        STATUS mandatory
        DESCRIPTION
        "Ethernet interface configuration and status table.
        The index of the table is via ifIndex, as well as the operational status and the admin state,
        speed and port connector."
        ::= { genEquipInterfacesEther 1 }

genEquipInterfacesEtherEntry OBJECT-TYPE
        SYNTAX GenEquipInterfacesEtherEntry
        ACCESS not-accessible
        STATUS mandatory
        DESCRIPTION
        "Ethernet interface configuration and status table.
        The index of the table is via ifIndex, as well as the operational status and the admin state,
        speed and port connector."
        INDEX { ifIndex }
        ::= { genEquipInterfacesEtherTable 1 }

GenEquipInterfacesEtherEntry ::=
		SEQUENCE {
			genEquipInterfacesEtherConnType
				INTEGER,
			genEquipInterfacesEtherPortType
				INTEGER,
			genEquipInterfacesEtherAutoNegotiation
				INTEGER,
			genEquipInterfacesEtherDuplex
				HalfFull,
			genEquipInterfacesEtherRate
				RateMbps,
			genEquipInterfacesEtherPortLerningAdmin
				EnableDisable,
			genEquipInterfacesEtherFlowCtrl
				INTEGER,
			genEquipInterfacesEtherLagPortMember
				INTEGER,
			genEquipInterfacesEtherActualDuplex
				HalfFull,
			genEquipInterfacesEtherActualRate
				RateMbps,
			genEquipInterfacesEtherClkSrc
				INTEGER,
			genEquipInterfacesEtherPortServiceType
				INTEGER,
			genEquipInterfacesEtheMACAddress
				MacAddress,
			genEquipInterfacesEtherDefaultVLANId
				INTEGER,
			genEquipInterfacesEtherPortBlockSharedVlans
				EnableDisable
}

genEquipInterfacesEtherConnType OBJECT-TYPE
        SYNTAX INTEGER  {
			not-applicable(-1),
            rj45(0),
		    electricalSFP(1),
		    opticalSFP(2),
		    radio(3),
			sfp100base-fx(4)
        }
        ACCESS read-write
        STATUS mandatory
        DESCRIPTION
        "The physical interface type. For port 8 the only valid value is radio. For ports 3 to 7 the only valid
	     value is rj45."
        ::= { genEquipInterfacesEtherEntry 1 }


genEquipInterfacesEtherPortType OBJECT-TYPE
        SYNTAX INTEGER {
			not-applicable(-1),
			access(0),
			trunk(1),
			hybrid(2),
			cN(3),
			pN(4),
			management(30),
			wayside(31)
		}
        ACCESS read-write
        STATUS mandatory
        DESCRIPTION
        "The type of the port.
        Access - untagged port (in case of managed switch).
        Trunk - C-VID tagged port (in case of managed switch).
        CN - Don't care on the vlan tag (in case of metro switch configuration).
        SN - S-VID is used as the first vlan (in case of metro switch configuration)."
        ::= { genEquipInterfacesEtherEntry 2 }

genEquipInterfacesEtherAutoNegotiation OBJECT-TYPE
        SYNTAX INTEGER {
		  not-applicable(-1),
          off(0),
          on(1)
        }
        ACCESS read-write
        STATUS mandatory
        DESCRIPTION
        "Enable or disable auto-negotiation on the port."
        ::= { genEquipInterfacesEtherEntry 3 }

genEquipInterfacesEtherDuplex OBJECT-TYPE
        SYNTAX HalfFull
        ACCESS read-write
        STATUS mandatory
        DESCRIPTION
        "Half or full duplex."
        ::= { genEquipInterfacesEtherEntry 4 }

genEquipInterfacesEtherRate OBJECT-TYPE
        SYNTAX RateMbps
        ACCESS read-write
        STATUS mandatory
        DESCRIPTION
        "10, 100 OR 1000 Mbps."
        ::= { genEquipInterfacesEtherEntry 5 }

genEquipInterfacesEtherPortLerningAdmin OBJECT-TYPE
       SYNTAX INTEGER {
          not-applicable(-1),
          enable(2),
          disable(3)
        }
        ACCESS read-write
        STATUS mandatory
        DESCRIPTION
        "Enable or disable MAC address learning in the port."
        ::= { genEquipInterfacesEtherEntry 6 }

genEquipInterfacesEtherFlowCtrl OBJECT-TYPE
        SYNTAX INTEGER {
					not-applicable(-1),
					off(0),
					on(1),
					na(2)
		}
        ACCESS read-write
        STATUS mandatory
        DESCRIPTION
        "Enable or disable flow control on the port. Supported only in pipe mode. "
        ::= { genEquipInterfacesEtherEntry 7 }

genEquipInterfacesEtherLagPortMember OBJECT-TYPE
       SYNTAX INTEGER {
		  not-applicable(-1),
          not-aggrigated(0),
          group-1(1),
          group-2(2),
          group-3(3)
        }
        ACCESS read-write
        STATUS mandatory
        DESCRIPTION
        "The syntax is ifIndex, or FFFF for port that is not member in a lag."
        ::= { genEquipInterfacesEtherEntry 8 }

genEquipInterfacesEtherActualDuplex OBJECT-TYPE
        SYNTAX HalfFull
        ACCESS read-only
        STATUS mandatory
        DESCRIPTION
        "Actual duplex (in auto-negotiation, the mode the two ports agreed upon) - Half or full duplex."
        ::= { genEquipInterfacesEtherEntry 9 }

genEquipInterfacesEtherActualRate OBJECT-TYPE
        SYNTAX RateMbps
        ACCESS read-only
        STATUS mandatory
        DESCRIPTION
         "Actual rate (in auto-negotiation, the rate the two ports agreed upon) - 10, 100 OR 1000 Mbps."
        ::= { genEquipInterfacesEtherEntry 10 }

genEquipInterfacesEtherClkSrc OBJECT-TYPE
       SYNTAX INTEGER {
		  not-applicable(-1),
          local-clock(0),
          system-clock-source(1)
        }
        ACCESS read-write
        STATUS mandatory
        DESCRIPTION
        "The source for the outgoing carrier signal clock. Local-clock is an internal independent oscilator.
	   system-clock-source causes the ethernet clock to be derived from the defined system clock source
	   (which can be taken from another interface)
	   Note: changing this parameter per port affect all the Ethernet ports."
        ::= { genEquipInterfacesEtherEntry 11 }

genEquipInterfacesEtherPortServiceType OBJECT-TYPE
        SYNTAX INTEGER {
		  		not-applicable(-1),
				sap(0),
				snp(1)
		}
        ACCESS read-write
        STATUS mandatory
        DESCRIPTION
        "This parameter indicates whether the port is being used as a Service Access Point (SAP)
		or as a Service Network Point (SNP) in a network-wide Ethernet service;
		the parameter has no functionality, but is meant to hold data for the NMS."
        ::= { genEquipInterfacesEtherEntry 12 }

genEquipInterfacesEtheMACAddress
OBJECT-TYPE
        SYNTAX MacAddress
        ACCESS read-only
        STATUS mandatory
        DESCRIPTION
        "The MAC address of the port for CFM or PWE3 addressing purposes."
        ::= { genEquipInterfacesEtherEntry 13 }

genEquipInterfacesEtherDefaultVLANId
OBJECT-TYPE
        SYNTAX  INTEGER  (1..4090)
        ACCESS read-write
        STATUS mandatory
        DESCRIPTION
        "Default VLAN ID of the Ethernet interface."
        ::= { genEquipInterfacesEtherEntry 14 }

genEquipInterfacesEtherPortBlockSharedVlans
OBJECT-TYPE
        SYNTAX  EnableDisable
        ACCESS read-write
        STATUS mandatory
        DESCRIPTION
        "When enabled, this parameter blocks transfer of Ethernet frames to/from other ports
        for which it is enabled, effectively eliminating all shared VLANs."
        ::= { genEquipInterfacesEtherEntry 15 }


---------------
genEquipInterfacesEtherStatePropagation  OBJECT-TYPE
        SYNTAX  INTEGER  {
                none(0) ,
		        lof-loc(1) ,
		        lof-loc-excber(3) ,
		        lof-loc-remote(5) ,
		        lof-loc-excber-remote(7) ,
		        lof(9) ,
		        lof-excber(11) ,
		        lof-remote(13) ,
		        lof-excber-remote(15)
        }
      	ACCESS  read-write
        STATUS mandatory
        DESCRIPTION
        "This parameter configures the behavior of Ethernet ports in single
        pipe mode. When a failure is detected, ports will be automatically shut
        down when the configured conditions take place. The possible choices
        are a combination of the following failures in the local and the remote IDUs:
        radio LOF, Ethernet line LOC, radio excessive ber"
		::= { genEquipInterfacesEther 2 }

genEquipInterfacesEtherPWPort	OBJECT-TYPE
        SYNTAX  INTEGER  (0..7)
      	ACCESS  read-write
        STATUS mandatory
        DESCRIPTION
        "The port in the traffic bridge connected to the PWE3 T-card."
		::= { genEquipInterfacesEther 3 }


-- Interfaces E1/T1
genEquipInterfacesE1T1	OBJECT IDENTIFIER ::= {genEquipInterfaces 2}

genEquipInterfacesE1T1PortGroupTable  OBJECT-TYPE
        SYNTAX  SEQUENCE OF GenEquipInterfacesE1T1PortGroupEntry
        ACCESS  not-accessible
        STATUS mandatory
        DESCRIPTION
        "General parameters for group of E1 or T1 interfaces."
        ::= { genEquipInterfacesE1T1 1 }

genEquipInterfacesE1T1PortGroupEntry OBJECT-TYPE
        SYNTAX GenEquipInterfacesE1T1PortGroupEntry
        ACCESS not-accessible
        STATUS mandatory
          DESCRIPTION
          "General parameters for group of E1 or T1 interfaces."
        INDEX { genEquipInterfacesE1T1PortGroupId }
        ::= { genEquipInterfacesE1T1PortGroupTable 1 }

GenEquipInterfacesE1T1PortGroupEntry ::=
		SEQUENCE {
			genEquipInterfacesE1T1PortGroupId
            	INTEGER,
			genEquipInterfacesE1T1PortGroupLineCode
            	INTEGER,
			genEquipInterfacesE1T1PortGroupExcessiveBERthreshold
            	BerLevel,
			genEquipInterfacesE1T1PortGroupSignalDegradeThreshold
            	INTEGER,
			genEquipInterfacesE1T1PortGroupLineCode1to8
            	INTEGER,
			genEquipInterfacesE1T1PortGroupLineCode9to16
            	INTEGER,
			genEquipInterfacesE1T1PortGroupLineCode17to24
            	INTEGER,
			genEquipInterfacesE1T1PortGroupLineCode25to32
            	INTEGER
}

genEquipInterfacesE1T1PortGroupId OBJECT-TYPE
        SYNTAX INTEGER
        ACCESS read-only
        STATUS mandatory
        DESCRIPTION
        "Group id. the index of this table."
        ::= { genEquipInterfacesE1T1PortGroupEntry 1 }

genEquipInterfacesE1T1PortGroupLineCode OBJECT-TYPE
        SYNTAX INTEGER {
					b8zs(1),
					ami(2),
					hdb3(3)
		}
        ACCESS read-write
        STATUS mandatory
        DESCRIPTION
        "The PDH line coding. b8zs is for T1 and hdb3 for E1.
        ami is only for T1. This parameter is
        relevant only for versions up to 6.6.0.0.1.53 (including)."
        ::= { genEquipInterfacesE1T1PortGroupEntry 2 }

genEquipInterfacesE1T1PortGroupExcessiveBERthreshold OBJECT-TYPE
        SYNTAX BerLevel
        ACCESS read-write
        STATUS mandatory
        DESCRIPTION
        "Excessive BER threshold for the group of E1s/T1s."
        ::= { genEquipInterfacesE1T1PortGroupEntry 3 }

genEquipInterfacesE1T1PortGroupSignalDegradeThreshold OBJECT-TYPE
        SYNTAX INTEGER { n1e-6(3), n1e-7(4), n1e-8(5), n1e-9(6)  }
        ACCESS read-write
        STATUS mandatory
        DESCRIPTION
        "Signal degrade threshold for the group of E1s/T1s."
        ::= { genEquipInterfacesE1T1PortGroupEntry 4 }

genEquipInterfacesE1T1PortGroupLineCode1to8 OBJECT-TYPE
        SYNTAX INTEGER {
					b8zs(1),
					ami(2),
					hdb3(3)
		}
        ACCESS read-write
        STATUS mandatory
        DESCRIPTION
        "The PDH line coding for line interfaces 1 to 8.
        b8zs is for T1 and hdb3 for E1. ami is only for T1."
        ::= { genEquipInterfacesE1T1PortGroupEntry 5 }

genEquipInterfacesE1T1PortGroupLineCode9to16 OBJECT-TYPE
        SYNTAX INTEGER {
					b8zs(1),
					ami(2),
					hdb3(3)
		}
        ACCESS read-write
        STATUS mandatory
        DESCRIPTION
        "The PDH line coding for line interfaces 9 to 16.
        b8zs is for T1 and hdb3 for E1. ami is only for T1."
        ::= { genEquipInterfacesE1T1PortGroupEntry 6 }

genEquipInterfacesE1T1PortGroupLineCode17to24 OBJECT-TYPE
        SYNTAX INTEGER {
					b8zs(1),
					ami(2),
					hdb3(3)
		}
        ACCESS read-write
        STATUS mandatory
        DESCRIPTION
        "The PDH line coding for line interfaces 17 to 24.
        b8zs is for T1 and hdb3 for E1. ami is only for T1."
        ::= { genEquipInterfacesE1T1PortGroupEntry 7 }

genEquipInterfacesE1T1PortGroupLineCode25to32 OBJECT-TYPE
        SYNTAX INTEGER {
					b8zs(1),
					ami(2),
					hdb3(3)
		}
        ACCESS read-write
        STATUS mandatory
        DESCRIPTION
        "The PDH line coding for interfaces 25 to 32.
        b8zs is for T1 and hdb3 for E1. ami is only for T1."
        ::= { genEquipInterfacesE1T1PortGroupEntry 8 }



genEquipInterfacesE1T1Table  OBJECT-TYPE
        SYNTAX  SEQUENCE OF GenEquipInterfacesE1T1Entry
        ACCESS  not-accessible
        STATUS mandatory
        DESCRIPTION
        "E1/T1 interface configuration table."
        ::= { genEquipInterfacesE1T1 2 }

genEquipInterfacesE1T1Entry OBJECT-TYPE
        SYNTAX GenEquipInterfacesE1T1Entry
        ACCESS not-accessible
        STATUS mandatory
          DESCRIPTION
          "E1/T1 interface configuration table."
        INDEX { ifIndex }
        ::= { genEquipInterfacesE1T1Table 1 }

GenEquipInterfacesE1T1Entry ::=
		SEQUENCE {
			genEquipInterfacesE1T1Priority
            	INTEGER,
			genEquipInterfacesE1T1CurrBER
            	BerLevel,
			genEquipInterfacesE1T1Loopback
            	INTEGER,
            genEquipInterfacesE1T1AISSStatus
            	INTEGER,
            genEquipInterfacesE1T1CableLength
            	INTEGER
}

genEquipInterfacesE1T1Priority OBJECT-TYPE
        SYNTAX INTEGER { low(1), high(2) }
        ACCESS read-only
        STATUS mandatory
        DESCRIPTION
        "The ACM priority of the E1/T1.
	   This parameter is relevant only for stand-alone mode.
	   In shelf this parameter is defined in the trail configuration."
        ::= { genEquipInterfacesE1T1Entry 1 }

genEquipInterfacesE1T1CurrBER OBJECT-TYPE
        SYNTAX BerLevel
        ACCESS read-only
        STATUS mandatory
        DESCRIPTION
        "E1/T1 current BER."
        ::= { genEquipInterfacesE1T1Entry 2 }

genEquipInterfacesE1T1Loopback OBJECT-TYPE
        SYNTAX INTEGER {
						off(1),
						towardsLine(2),
						towardsRadio(3)
						}
        ACCESS read-write
        STATUS mandatory
        DESCRIPTION
        "Enable or Disable line loopback on the E1/T1 interface."
        ::= { genEquipInterfacesE1T1Entry 3 }

genEquipInterfacesE1T1AISSStatus OBJECT-TYPE
        SYNTAX INTEGER {
                         detected(0),
                         notDetected(1)
        }
        ACCESS read-only
        STATUS mandatory
        DESCRIPTION
        "Status of the AIS detection, if the AIS detection is activated."
        ::= { genEquipInterfacesE1T1Entry 4 }

genEquipInterfacesE1T1CableLength OBJECT-TYPE
        SYNTAX INTEGER {
                         len-0-133ft-0-41m(1),
                         len-133ft-266ft-41m-81m(2),
                         len-266ft-399ft-81m-122m(3),
                         len-399ft-533ft-122m-162m(4),
                         len-533ft-655ft-162m-200m(5)
        }
        ACCESS read-write
        STATUS mandatory
        DESCRIPTION
        "This parameter is valid only for T1 interfaces, and determines cable length range."
        ::= { genEquipInterfacesE1T1Entry 5 }



genEquipInterfacesAux	OBJECT IDENTIFIER ::= {genEquipInterfaces 3}

-- Interfaces Way Side
genEquipInterfacesAuxWaySide	OBJECT IDENTIFIER ::= {genEquipInterfacesAux 1}

genEquipInterfacesAuxWaySideTable  OBJECT-TYPE
        SYNTAX  SEQUENCE OF GenEquipInterfacesAuxWaySideEntry
        ACCESS  not-accessible
        STATUS mandatory
        DESCRIPTION
        "Way-side interface configuration."
        ::= { genEquipInterfacesAuxWaySide 1 }

genEquipInterfacesAuxWaySideEntry OBJECT-TYPE
        SYNTAX GenEquipInterfacesAuxWaySideEntry
        ACCESS not-accessible
        STATUS mandatory
          DESCRIPTION
          "Way-side interface configuration."
        INDEX { ifIndex }
        ::= { genEquipInterfacesAuxWaySideTable 1 }

GenEquipInterfacesAuxWaySideEntry ::=
		SEQUENCE {
			genEquipInterfacesAuxWaySideAdmin
            	EnableDisable,
			genEquipInterfacesAuxWaySideCapacity
				INTEGER,
			genEquipInterfacesAuxWaySideAutoNegotiation
				OffOn,
			genEquipInterfacesAuxWaySideDuplex
				INTEGER,
			genEquipInterfacesAuxWaySideRate
				RateMbps
}

genEquipInterfacesAuxWaySideAdmin OBJECT-TYPE
        SYNTAX EnableDisable
        ACCESS read-write
        STATUS mandatory
        DESCRIPTION
        "Enable - Set Ethernet port #4 to be a wayside port. Disabling this option will cause the port to behave
	   as a normal traffic Ethernet port."
        ::= { genEquipInterfacesAuxWaySideEntry 1 }


genEquipInterfacesAuxWaySideCapacity OBJECT-TYPE
        SYNTAX INTEGER { narrow(0), wide(1) }
        ACCESS read-write
        STATUS mandatory
        DESCRIPTION
        "Narrow band (64Kbps) or Wide band (2Mbps)"
        ::= { genEquipInterfacesAuxWaySideEntry 2 }


genEquipInterfacesAuxWaySideAutoNegotiation OBJECT-TYPE
        SYNTAX OffOn
        ACCESS read-write
        STATUS mandatory
        DESCRIPTION
        "Wayside port auto negotiation (Off, on)"
        ::= { genEquipInterfacesAuxWaySideEntry 3 }

genEquipInterfacesAuxWaySideDuplex OBJECT-TYPE
        SYNTAX INTEGER {
        		not-applicable(-1),
        		half(0),
        		full(1)
        }
        ACCESS read-write
        STATUS mandatory
        DESCRIPTION
        "Wayside port duplex (Half, Full)"
        ::= { genEquipInterfacesAuxWaySideEntry 4 }

genEquipInterfacesAuxWaySideRate OBJECT-TYPE
        SYNTAX INTEGER {
        		not-applicable(-1),
        		n10(0),
        		n100(1)
        }
        ACCESS read-write
        STATUS mandatory
        DESCRIPTION
        "Wayside interface port rate (10Mbps,100Mbps)"
        ::= { genEquipInterfacesAuxWaySideEntry 5 }




-- Interfaces User channel
genEquipInterfacesAuxUserChanTable  OBJECT-TYPE
        SYNTAX  SEQUENCE OF GenEquipInterfacesAuxUserChanEntry
        ACCESS  not-accessible
        STATUS mandatory
        DESCRIPTION
        "Table of configured user channels."
        ::= { genEquipInterfacesAux 2 }

genEquipInterfacesAuxUserChanEntry OBJECT-TYPE
        SYNTAX GenEquipInterfacesAuxUserChanEntry
        ACCESS not-accessible
        STATUS mandatory
          DESCRIPTION
          "Table of configured user channels."
        INDEX { ifIndex }
        ::= { genEquipInterfacesAuxUserChanTable 1 }

GenEquipInterfacesAuxUserChanEntry ::=
		SEQUENCE {
			genEquipInterfacesAuxUserChanType
				INTEGER
}

genEquipInterfacesAuxUserChanType OBJECT-TYPE
        SYNTAX INTEGER {
				asynchronous-rs232(1),
				asynchronous-v-11(2),
				twin-asynchronous-rs232-and-v-11(3),
				synchronous-v-11-codirectional(4),
				synchronous-v-11-contradirectional(5)
		}
        ACCESS read-write
        STATUS mandatory
        DESCRIPTION
        "User channel type. The asynchronous modes allow two channels, one in each port.
		The twin asynchronous mode uses port 1 for v.11 and port 2 for RS-232.
		The Synchronous modes use two ports each"
        ::= { genEquipInterfacesAuxUserChanEntry 1 }


-- Interfaces Sonet/SDH
genEquipInterfacesSdh	OBJECT IDENTIFIER ::= {genEquipInterfaces 4}

genEquipInterfacesSdhTable  OBJECT-TYPE
        SYNTAX  SEQUENCE OF GenEquipInterfacesSdhEntry
        ACCESS  not-accessible
        STATUS mandatory
        DESCRIPTION
        "STM-1,OC-3 interface configuration and status table. "
        ::= { genEquipInterfacesSdh 1 }

genEquipInterfacesSdhEntry OBJECT-TYPE
        SYNTAX GenEquipInterfacesSdhEntry
        ACCESS not-accessible
        STATUS mandatory
          DESCRIPTION
          "STM-1,OC-3 interface configuration and status table."
        INDEX { ifIndex }
        ::= { genEquipInterfacesSdhTable 1 }

GenEquipInterfacesSdhEntry ::=
		SEQUENCE {
			genEquipInterfacesSdhMuteTx
            	EnableDisableSMI2,
			genEquipInterfacesSdhClockSource
            	INTEGER,
			genEquipInterfacesSdhAISAdmin
            	EnableDisable,
			genEquipInterfacesSdhTraceIdReceived
            	DisplayString,
			genEquipInterfacesSdhTraceIdTransmitted
            	DisplayString,
			genEquipInterfacesSdhTraceIdExpected
            	DisplayString,
			genEquipInterfacesSdhTraceIdStringLength
            	INTEGER,
			genEquipInterfacesSdhExcessiveBer
            	INTEGER,
			genEquipInterfacesSdhSignalDegrade
            	INTEGER,
			genEquipInterfacesSdhLoopback
				INTEGER,
			genEquipInterfacesSdhClockSourceStatus
				INTEGER,
			genEquipInterfacesSdhLineTxProtectionMode
				INTEGER,
			genEquipInterfacesSdhSyncVC
				INTEGER,
			genEquipInterfacesSdhAdmin
				EnableDisableSMI2,
			genEquipInterfacesSdhPdhTimingMode
				PWPDHClockSource,
			genEquipInterfacesSdhSlot
				INTEGER,
			genEquipInterfacesSdhIdleCode
				INTEGER,
			genEquipInterfacesSdhSSMAdmin
				EnableDisableSMI2,
			genEquipInterfacesSdhSSMPattern
				INTEGER,
			genEquipInterfacesSdhTraceIdAdmin
				EnableDisableSMI2,
			genEquipInterfacesSdhVCSignalLabel
				INTEGER,
			genEquipInterfacesSdhVcRdiAdmin
				EnableDisableSMI2
}

genEquipInterfacesSdhMuteTx OBJECT-TYPE
        SYNTAX EnableDisableSMI2
        ACCESS read-write
        STATUS mandatory
        DESCRIPTION
        "Mute Tx option on the interface."
        ::= { genEquipInterfacesSdhEntry 1 }

genEquipInterfacesSdhClockSource OBJECT-TYPE
        SYNTAX INTEGER {
					internal-clock(0),
					loop(1),
					synchronization-vc(2)
		}
        ACCESS read-write
        STATUS mandatory
        DESCRIPTION
        "The source of the clock being used.
        sync-vc option is for future support, to use one of the outgoing TDM VCs as a source."
        ::= { genEquipInterfacesSdhEntry 2 }

genEquipInterfacesSdhAISAdmin OBJECT-TYPE
        SYNTAX EnableDisable
        ACCESS read-write
        STATUS mandatory
        DESCRIPTION
        "Enable, Disable AIS signaling at the V5 byte on the STM-1, OC-3 interface."
        ::= { genEquipInterfacesSdhEntry 3 }

genEquipInterfacesSdhTraceIdReceived OBJECT-TYPE
        SYNTAX DisplayString
        ACCESS read-only
        STATUS mandatory
        DESCRIPTION
        "J0 Trace Identifier signal that was received on the interface."
        ::= { genEquipInterfacesSdhEntry 4 }

genEquipInterfacesSdhTraceIdTransmitted OBJECT-TYPE
        SYNTAX DisplayString
        ACCESS read-write
        STATUS mandatory
        DESCRIPTION
        "J0 Trace Identifier signal that is transmitted on the interface."
        ::= { genEquipInterfacesSdhEntry 5 }

genEquipInterfacesSdhTraceIdExpected OBJECT-TYPE
        SYNTAX DisplayString
        ACCESS read-write
        STATUS mandatory
        DESCRIPTION
        "J0 Trace Identifier signal that is expected to be received on the interface."
        ::= { genEquipInterfacesSdhEntry 6 }

genEquipInterfacesSdhTraceIdStringLength OBJECT-TYPE
        SYNTAX INTEGER {
					len1(0),
					len15(1),
					len62(2)
		}
        ACCESS read-write
        STATUS mandatory
        DESCRIPTION
        "Trace identifier string length. Lengths 0 and 15 are valid for SDH systems. Length 62 is additionally available in SONET systems."
        ::= { genEquipInterfacesSdhEntry 7 }

genEquipInterfacesSdhExcessiveBer OBJECT-TYPE
        SYNTAX INTEGER { n1e-3(0), n1e-4(1), n1e-5(2) }
        ACCESS read-write
        STATUS mandatory
        DESCRIPTION
        "Excessive BER threshold on the interface."
        ::= { genEquipInterfacesSdhEntry 8 }

genEquipInterfacesSdhSignalDegrade OBJECT-TYPE
        SYNTAX INTEGER { n1e-6(3), n1e-7(4), n1e-8(5), n1e-9(6) }
        ACCESS read-write
        STATUS mandatory
        DESCRIPTION
        "Signal degrade threshold on the interface."
        ::= { genEquipInterfacesSdhEntry 9 }

genEquipInterfacesSdhLoopback OBJECT-TYPE
        SYNTAX INTEGER {
        			off(0),
        			loopback-towards-system(1),
        			loopback-towards-line(2)
        }
        ACCESS read-write
        STATUS mandatory
        DESCRIPTION
        "SDH Loopback."
        ::= { genEquipInterfacesSdhEntry 10 }

genEquipInterfacesSdhClockSourceStatus OBJECT-TYPE
        SYNTAX INTEGER {
					internal-clock(0),
					loop(1),
					synchronization-vc(2)
		}
        ACCESS read-only
        STATUS mandatory
        DESCRIPTION
        "The actual source of the clock for the outgoing STM-1/OC-3 signal.
		It may differ from the desired source if the source signal is missing or corrupt"
        ::= { genEquipInterfacesSdhEntry 11 }

genEquipInterfacesSdhLineTxProtectionMode OBJECT-TYPE
        SYNTAX INTEGER {
				normal(1),
				uni-directional-MSP(2)
		}
        ACCESS read-write
        STATUS mandatory
        DESCRIPTION
        "this parameter configures the behavior of the transmitting line in a 1+1 HSB configuration.
		In normal mode the stand-by signal is silenced. In uni-directional MSP both units will transmit"
        ::= { genEquipInterfacesSdhEntry 12 }

genEquipInterfacesSdhSyncVC OBJECT-TYPE
        SYNTAX INTEGER (1..63)
        ACCESS read-write
        STATUS mandatory
        DESCRIPTION
        "The outgoing VC signal to be taken as the STM-1/OC-3 synchronization source if
      	genEquipInterfacesSdhClockSource is set to synchronization-vc"
        ::= { genEquipInterfacesSdhEntry 13 }

genEquipInterfacesSdhAdmin OBJECT-TYPE
        SYNTAX EnableDisableSMI2
        ACCESS read-write
        STATUS mandatory
        DESCRIPTION
        "Administrative status of the STM-1/OC3 port"
        ::= { genEquipInterfacesSdhEntry 14 }

genEquipInterfacesSdhPdhTimingMode OBJECT-TYPE
        SYNTAX EnableDisableSMI2
        ACCESS read-write
        STATUS mandatory
        DESCRIPTION
        "Clock reference for outgoing PDH signals configured in 'absolute clock' mode"
        ::= { genEquipInterfacesSdhEntry 15 }

genEquipInterfacesSdhSlot OBJECT-TYPE
        SYNTAX INTEGER
        ACCESS read-only
        STATUS mandatory
        DESCRIPTION
        "Slot ID"
        ::= { genEquipInterfacesSdhEntry 16 }

genEquipInterfacesSdhIdleCode OBJECT-TYPE
        SYNTAX INTEGER
        ACCESS read-write
        STATUS mandatory
        DESCRIPTION
        "Value to be transmitted at PDH signals inside the STM-1/OC3 when there is no data to transmit"
        ::= { genEquipInterfacesSdhEntry 17 }

genEquipInterfacesSdhSSMAdmin OBJECT-TYPE
        SYNTAX EnableDisableSMI2
        ACCESS read-write
        STATUS mandatory
        DESCRIPTION
        "SSM support admin for this interface"
        ::= { genEquipInterfacesSdhEntry 18 }

genEquipInterfacesSdhSSMPattern OBJECT-TYPE
        SYNTAX INTEGER
        ACCESS read-write
        STATUS mandatory
        DESCRIPTION
        "Indicates the default SSM pattern to be transmitted in case if TCC clock synchronization subsystem doesn't provide SSM pattern value"
        ::= { genEquipInterfacesSdhEntry 19 }

genEquipInterfacesSdhTraceIdAdmin OBJECT-TYPE
        SYNTAX EnableDisableSMI2
        ACCESS read-write
        STATUS mandatory
        DESCRIPTION
        "Enable/disable of  J0  mismatch checking on RX direction"
        ::= { genEquipInterfacesSdhEntry 20 }

genEquipInterfacesSdhVCSignalLabel OBJECT-TYPE
        SYNTAX INTEGER {
				asynchronous(0),
				non-specific-payload(1)
		}
        ACCESS read-write
        STATUS mandatory
        DESCRIPTION
        "Sets the signal label bits to be sent and expected in every VC-11/12;
		use non-specific payload only for backwards compatibility with old equipment"
        ::= { genEquipInterfacesSdhEntry 21 }

genEquipInterfacesSdhVcRdiAdmin OBJECT-TYPE
        SYNTAX EnableDisableSMI2
        ACCESS read-write
        STATUS mandatory
        DESCRIPTION
        "VC-RDI signaling admin status"
        ::= { genEquipInterfacesSdhEntry 22 }


-- LPVC (Low Oreder Path VC)
genEquipInterfacesSdhLpVcTable  OBJECT-TYPE
        SYNTAX  SEQUENCE OF GenEquipInterfacesSdhLpVcEntry
        ACCESS  not-accessible
        STATUS mandatory
        DESCRIPTION
        "This table includes properties for each Low-order path VC (VC-11/12) in the SDH interface. "
        ::= { genEquipInterfacesSdh 2 }

genEquipInterfacesSdhLpVcEntry OBJECT-TYPE
        SYNTAX GenEquipInterfacesSdhLpVcEntry
        ACCESS not-accessible
        STATUS mandatory
          DESCRIPTION
         "This table includes properties for each Low-order path VC (VC-11/12) in the SDH interface. "
        INDEX { ifIndex, genEquipInterfacesSdhLpVcId }
        ::= { genEquipInterfacesSdhLpVcTable 1 }

GenEquipInterfacesSdhLpVcEntry ::=
		SEQUENCE {
			genEquipInterfacesSdhLpVcId
            	INTEGER,
			genEquipInterfacesSdhLpVcAIS
            	INTEGER
}

genEquipInterfacesSdhLpVcId OBJECT-TYPE
        SYNTAX INTEGER   (1..84)
        ACCESS read-only
        STATUS mandatory
        DESCRIPTION
        "VC-11 or VC-12 number; VCs are numbered according to standard KLM order. "
        ::= { genEquipInterfacesSdhLpVcEntry 1 }

genEquipInterfacesSdhLpVcAIS OBJECT-TYPE
        SYNTAX INTEGER {
          aisDetected(0),
		  aisNotDetected(1)
		}
        ACCESS read-only
        STATUS mandatory
        DESCRIPTION
        "Indicates whether incoming AIS is currently detected in the VC's payload. 0 indicates that AIS is detected, 1 that is not detected."
        ::= { genEquipInterfacesSdhLpVcEntry 2 }


-- TDM pw-stm1oc3-status-table
genEquipInterfacesSdhStatusTable  OBJECT-TYPE
        SYNTAX  SEQUENCE OF GenEquipInterfacesSdhStatusEntry
        ACCESS  not-accessible
        STATUS mandatory
        DESCRIPTION
        "SDH Status. "
        ::= { genEquipInterfacesSdh 3 }

genEquipInterfacesSdhStatusEntry OBJECT-TYPE
        SYNTAX GenEquipInterfacesSdhStatusEntry
        ACCESS not-accessible
        STATUS mandatory
          DESCRIPTION
         "SDH Status"
        INDEX { genEquipInterfacesSdhStatusIfIndex }
        ::= { genEquipInterfacesSdhStatusTable 1 }

GenEquipInterfacesSdhStatusEntry ::=
		SEQUENCE {
			genEquipInterfacesSdhStatusIfIndex
				INTEGER,
			genEquipInterfacesSdhStatusLine
            	INTEGER,
			genEquipInterfacesSdhStatusOperState
            	DownUp,
			genEquipInterfacesSdhStatusRegenerator
				INTEGER,
			genEquipInterfacesSdhStatusClockSourceStatus
				PWPDHClockSource,
			genEquipInterfacesSdhStatusPdhClockStatus
				PWPDHClockSource,
			genEquipInterfacesSdhStatusSlotId
				INTEGER,
			genEquipInterfacesSdhStatusLoopback
				INTEGER,
			genEquipInterfacesSdhStatusMultiplexer
				INTEGER,
			genEquipInterfacesSdhStatusSsmRx
				INTEGER,
			genEquipInterfacesSdhStatusSsmTx
				INTEGER
}

genEquipInterfacesSdhStatusIfIndex OBJECT-TYPE
        SYNTAX INTEGER
        ACCESS read-only
        STATUS mandatory
        DESCRIPTION
        "Portnumber"
        ::= { genEquipInterfacesSdhStatusEntry 1 }


genEquipInterfacesSdhStatusLine OBJECT-TYPE
        SYNTAX INTEGER
        ACCESS read-only
        STATUS mandatory
        DESCRIPTION
        "Bitmap field according to the following values: no-defect (1), AIS (2), RDI (4)"
        ::= { genEquipInterfacesSdhStatusEntry 2 }

genEquipInterfacesSdhStatusOperState OBJECT-TYPE
        SYNTAX DownUp
        ACCESS read-only
        STATUS mandatory
        DESCRIPTION
        "Interface operational status"
        ::= { genEquipInterfacesSdhStatusEntry 3 }

genEquipInterfacesSdhStatusRegenerator OBJECT-TYPE
        SYNTAX INTEGER
        ACCESS read-only
        STATUS mandatory
        DESCRIPTION
        "Bitmap field according to the following values: no-defect (1), AIS (2), RDI (4)"
        ::= { genEquipInterfacesSdhStatusEntry 4 }

genEquipInterfacesSdhStatusClockSourceStatus OBJECT-TYPE
        SYNTAX PWPDHClockSource
        ACCESS read-only
        STATUS mandatory
        DESCRIPTION
        "The actual source of the clock for the outgoing STM-1/OC-3 signal.
		It may differ from the desired source if the source signal is missing or corrupt"
        ::= { genEquipInterfacesSdhStatusEntry 5 }

genEquipInterfacesSdhStatusPdhClockStatus OBJECT-TYPE
        SYNTAX PWPDHClockSource
        ACCESS read-only
        STATUS mandatory
        DESCRIPTION
        "PDH clock source status"
        ::= { genEquipInterfacesSdhStatusEntry 6 }

genEquipInterfacesSdhStatusSlotId OBJECT-TYPE
        SYNTAX INTEGER
        ACCESS read-only
        STATUS mandatory
        DESCRIPTION
        "Slot ID"
        ::= { genEquipInterfacesSdhStatusEntry 7 }

genEquipInterfacesSdhStatusLoopback OBJECT-TYPE
        SYNTAX INTEGER {
			off(0),
			towards-system(1),
			towards-line(2)
		}
        ACCESS read-only
        STATUS mandatory
        DESCRIPTION
        "The current state of the loopback for the SONET/SDH interface"
        ::= { genEquipInterfacesSdhStatusEntry 8 }

genEquipInterfacesSdhStatusMultiplexer  OBJECT-TYPE
        SYNTAX INTEGER
        ACCESS read-only
        STATUS mandatory
        DESCRIPTION
        "Bitmask: no-defect (1), STS-LOP(2), STS-AIS(4), STS-RDI(8), unequipped (16), label-mismatch (32)"
        ::= { genEquipInterfacesSdhStatusEntry 9 }

genEquipInterfacesSdhStatusSsmRx OBJECT-TYPE
        SYNTAX INTEGER
        ACCESS read-only
        STATUS mandatory
        DESCRIPTION
        "Indicates the currently received SSM bits "
        ::= { genEquipInterfacesSdhStatusEntry 10 }

genEquipInterfacesSdhStatusSsmTx OBJECT-TYPE
        SYNTAX INTEGER
        ACCESS read-only
        STATUS mandatory
        DESCRIPTION
        "Indicates the currently transmitted SSM bits "
        ::= { genEquipInterfacesSdhStatusEntry 11 }


--
-- TDM pw-stm1oc3-loopback-status-table

genEquipInterfacesSdhLoopbackStatusTable  OBJECT-TYPE
        SYNTAX  SEQUENCE OF GenEquipInterfacesSdhLoopbackStatusEntry
        ACCESS  not-accessible
        STATUS mandatory
        DESCRIPTION
        "SONET/SDH interface loopback status"
        ::= { genEquipInterfacesSdh 4 }

genEquipInterfacesSdhLoopbackStatusEntry OBJECT-TYPE
        SYNTAX GenEquipInterfacesSdhLoopbackStatusEntry
        ACCESS not-accessible
        STATUS mandatory
          DESCRIPTION
         "SONET/SDH interface loopback status entry"
        INDEX { genEquipInterfacesSdhLoopbackStatusIfIndex }
        ::= { genEquipInterfacesSdhLoopbackStatusTable 1 }

GenEquipInterfacesSdhLoopbackStatusEntry ::=
		SEQUENCE {
			genEquipInterfacesSdhLoopbackStatusIfIndex
				INTEGER,
			genEquipInterfacesSdhLoopbackStatusSlotId
            	INTEGER,
			genEquipInterfacesSdhLoopbackStatusType
            	INTEGER,
			genEquipInterfacesSdhLoopbackStatusCounter
				INTEGER
}

genEquipInterfacesSdhLoopbackStatusIfIndex OBJECT-TYPE
        SYNTAX INTEGER
        ACCESS read-only
        STATUS mandatory
        DESCRIPTION
        "Portnumber"
        ::= { genEquipInterfacesSdhLoopbackStatusEntry 1 }


genEquipInterfacesSdhLoopbackStatusSlotId OBJECT-TYPE
        SYNTAX INTEGER
        ACCESS read-only
        STATUS mandatory
        DESCRIPTION
        "Slot ID"
        ::= { genEquipInterfacesSdhLoopbackStatusEntry 2 }

genEquipInterfacesSdhLoopbackStatusType OBJECT-TYPE
        SYNTAX INTEGER {
			off(0),
			towards-system(1),
			towards-line(2)
		}
        ACCESS read-write
        STATUS mandatory
        DESCRIPTION
        "Interface operational status"
        ::= { genEquipInterfacesSdhLoopbackStatusEntry 3 }

genEquipInterfacesSdhLoopbackStatusCounter OBJECT-TYPE
        SYNTAX INTEGER
        ACCESS read-only
        STATUS mandatory
        DESCRIPTION
        "Current value of STM1/OC3 interface Looback Timeout Counter"
        ::= { genEquipInterfacesSdhLoopbackStatusEntry 4 }


-- Interfaces AIS
genEquipInterfacesAIS	OBJECT IDENTIFIER ::= {genEquipInterfaces 5}

genEquipInterfacesAISAdmin OBJECT-TYPE
        SYNTAX EnableDisable
        ACCESS read-write
        STATUS mandatory
        DESCRIPTION
        "Control AIS Detection over all E1/T1/SDH ports."
        ::= { genEquipInterfacesAIS 1 }

-- Automatic State Propagation
genEquipInterfacesASP	OBJECT IDENTIFIER ::= {genEquipInterfaces 6}

genEquipInterfacesASPAdmin OBJECT-TYPE
        SYNTAX EnableDisable
        ACCESS read-write
        STATUS mandatory
        DESCRIPTION
        "Controls the Automatic State Propagation"
        ::= { genEquipInterfacesASP 1 }

genEquipInterfacesASPLocalLOC OBJECT-TYPE
        SYNTAX EnableDisable
        ACCESS read-write
        STATUS mandatory
        DESCRIPTION
        "Enables fault propagation upon detection of local LOC.
        This configuration is relevant only for non-protected single-pipe switch mode only."
        ::= { genEquipInterfacesASP 2 }

genEquipInterfacesASPLocalExcessiveBER  OBJECT-TYPE
        SYNTAX EnableDisable
        ACCESS read-write
        STATUS mandatory
        DESCRIPTION
        "Enables fault propagation to the Ethernet interface upon detection of radio excessive BER.
 	   This configuration is relevant only for non-protected single-pipe switch mode only."

        ::= { genEquipInterfacesASP 3 }

genEquipInterfacesASPACMthreshold OBJECT-TYPE
        SYNTAX INTEGER {
				profile-0(0),
				profile-1(1),
				profile-2(2),
				profile-3(3),
				profile-4(4),
				profile-5(5),
				profile-6(6),
				profile-7(7)
		}
        ACCESS read-write
        STATUS mandatory
        DESCRIPTION
        "Enable or disable the propagation when Radio ACM profile degrades below a defined profile.
         This configuration is relevant only for non-protected single-pipe switch mode only when ACM
	   radio script is running."
        ::= { genEquipInterfacesASP 4 }

genEquipInterfacesASPRemoteFault  OBJECT-TYPE
        SYNTAX EnableDisable
        ACCESS read-write
        STATUS mandatory
        DESCRIPTION
        "This parameter enables/disables automatic state propagation.
	   The following remote faults are propagated to the NE by default:
        - Radio LOF
        - Radio link ID mismatch
        - Ethernet line LOC
        any other remote faults are propagated to the NE only if they are
        enabled at the local NE"
        ::= { genEquipInterfacesASP 5 }

-- NG ASP
genEquipInterfacesNGASP	OBJECT IDENTIFIER ::= {genEquipInterfacesASP 7}

--
-- Automatic state propagation configuration table - asp-config-table
--

genEquipInterfacesNGASPConfigTable  OBJECT-TYPE
        SYNTAX  SEQUENCE OF GenEquipInterfacesNGASPConfigEntry
        ACCESS  not-accessible
        STATUS mandatory
        DESCRIPTION
        "This table configures automatic state propagation functionality."
        ::= { genEquipInterfacesNGASP 1 }

genEquipInterfacesNGASPConfigEntry OBJECT-TYPE
        SYNTAX GenEquipInterfacesNGASPConfigEntry
        ACCESS  not-accessible
        STATUS mandatory
        DESCRIPTION
        "This table configures automatic state propagation functionality entry."
        INDEX { genEquipInterfacesNGASPConfigControlledInterfaceIfindex }
        ::= { genEquipInterfacesNGASPConfigTable 1 }

GenEquipInterfacesNGASPConfigEntry ::=
    SEQUENCE {
		genEquipInterfacesNGASPConfigControlledInterfaceIfindex
			INTEGER,
		genEquipInterfacesNGASPConfigAdmin
			EnableDisable,
	    genEquipInterfacesNGASPConfigMonitoredInterfaceIfindex
			INTEGER,
		genEquipInterfacesNGASPConfigAcmThreshold
			INTEGER,
		genEquipInterfacesNGASPConfigRadioExcessiveBerCriterionAdmin
			EnableDisable,
		genEquipInterfacesNGASPConfigLinkIdMismatchCriterionAdmin
			EnableDisable,
		genEquipInterfacesNGASPConfigRadioLofCriterionAdmin
			EnableDisable,
		genEquipInterfacesNGASPConfigRemoteRadioLofCriterionAdmin
			EnableDisable,
		genEquipInterfacesNGASPConfigRxAcmThresholdCriterionAdmin
			EnableDisable,
		genEquipInterfacesNGASPConfigTxAcmThresholdCriterionAdmin
			EnableDisable,
		genEquipInterfacesNGASPConfigRemoteEthLocCriterionAdmin
			EnableDisable,
		genEquipInterfacesNGASPConfigRemoteFaultTriggerAdmin
			EnableDisable,
		genEquipInterfacesNGASPConfigRemoteRadioExcessiveBerCriterionAdmin
			EnableDisable,
		genEquipInterfacesNGASPConfigMonitoredInterface56
			INTEGER,
		genEquipInterfacesNGASPConfigCsfModeAdmin
			EnableDisable,
		genEquipInterfacesNGASPConfigMonitoredInterface
			INTEGER,
		genEquipInterfacesNGASPConfigDelayTime
			INTEGER,
		genEquipInterfacesNGASPConfigRowStatus
			RowStatus
	}

genEquipInterfacesNGASPConfigControlledInterfaceIfindex OBJECT-TYPE
        SYNTAX  INTEGER
        ACCESS  read-only
        STATUS 	mandatory
        DESCRIPTION
        "Index of the controlled interface.
		This interface will be disabled upon initiation of auto state propagation"
        ::= { genEquipInterfacesNGASPConfigEntry 1 }

genEquipInterfacesNGASPConfigAdmin  OBJECT-TYPE
        SYNTAX 	EnableDisable
        ACCESS  read-write
        STATUS mandatory
        DESCRIPTION
        "Enables/disables automatic state propagation."
        ::= { genEquipInterfacesNGASPConfigEntry 2 }

genEquipInterfacesNGASPConfigMonitoredInterfaceIfindex  OBJECT-TYPE
        SYNTAX  INTEGER
        ACCESS  read-write
        STATUS mandatory
        DESCRIPTION
        "Index to the monitored interface.
		Auto state propagation will act upon detecting a failure indication on this interface."
        ::= { genEquipInterfacesNGASPConfigEntry 3 }

genEquipInterfacesNGASPConfigAcmThreshold OBJECT-TYPE
        SYNTAX  INTEGER
        ACCESS  read-write
        STATUS mandatory
        DESCRIPTION
        "ACM profile threshold for initiating auto state propagation."
        ::= { genEquipInterfacesNGASPConfigEntry 4 }

genEquipInterfacesNGASPConfigRadioExcessiveBerCriterionAdmin OBJECT-TYPE
        SYNTAX 	EnableDisable
        ACCESS  read-write
        STATUS mandatory
        DESCRIPTION
        "Initiate auto state propagation upon local radio excessive BER."
        ::= { genEquipInterfacesNGASPConfigEntry 5 }


genEquipInterfacesNGASPConfigLinkIdMismatchCriterionAdmin OBJECT-TYPE
        SYNTAX 	EnableDisable
        ACCESS  read-write
        STATUS mandatory
        DESCRIPTION
        "Initiate auto state propagation upon local radio link Id mismatch."
        ::= { genEquipInterfacesNGASPConfigEntry 6 }

genEquipInterfacesNGASPConfigRadioLofCriterionAdmin OBJECT-TYPE
        SYNTAX 	EnableDisable
        ACCESS  read-write
        STATUS mandatory
        DESCRIPTION
        "Initiate auto state propagation upon local radio LOF."
        ::= { genEquipInterfacesNGASPConfigEntry 7 }

genEquipInterfacesNGASPConfigRemoteRadioLofCriterionAdmin OBJECT-TYPE
        SYNTAX 	EnableDisable
        ACCESS  read-write
        STATUS mandatory
        DESCRIPTION
        "Initiate auto state propagation upon remote radio LOF."
        ::= { genEquipInterfacesNGASPConfigEntry 8 }

genEquipInterfacesNGASPConfigRxAcmThresholdCriterionAdmin OBJECT-TYPE
        SYNTAX 	EnableDisable
        ACCESS  read-write
        STATUS mandatory
        DESCRIPTION
        "Initiate auto state propagation upon radio ACM RX profile below threshold."
        ::= { genEquipInterfacesNGASPConfigEntry 9 }

genEquipInterfacesNGASPConfigTxAcmThresholdCriterionAdmin OBJECT-TYPE
        SYNTAX 	EnableDisable
        ACCESS  read-write
        STATUS mandatory
        DESCRIPTION
        "Initiate auto state propagation upon radio ACM TX profile below threshold."
        ::= { genEquipInterfacesNGASPConfigEntry 10 }

genEquipInterfacesNGASPConfigRemoteEthLocCriterionAdmin OBJECT-TYPE
        SYNTAX 	EnableDisable
        ACCESS  read-write
        STATUS mandatory
        DESCRIPTION
        "Initiate auto state propagation due to remote ethernet LOC."
        ::= { genEquipInterfacesNGASPConfigEntry 11 }

genEquipInterfacesNGASPConfigRemoteFaultTriggerAdmin OBJECT-TYPE
        SYNTAX 	EnableDisable
        ACCESS  read-write
        STATUS mandatory
        DESCRIPTION
        "Auto state propagation trigger by remote fault."
        ::= { genEquipInterfacesNGASPConfigEntry 12 }

genEquipInterfacesNGASPConfigRemoteRadioExcessiveBerCriterionAdmin OBJECT-TYPE
        SYNTAX 	EnableDisable
        ACCESS  read-write
        STATUS mandatory
        DESCRIPTION
        "Initiate auto state propagation upon remote radio excessive BER."
        ::= { genEquipInterfacesNGASPConfigEntry 13 }

genEquipInterfacesNGASPConfigMonitoredInterface56 OBJECT-TYPE
        SYNTAX 	INTEGER
        ACCESS  read-write
        STATUS mandatory
        DESCRIPTION
        "Index to the monitored interface. Auto state propagation will act upon detecting a failure indication on this interface."
        ::= { genEquipInterfacesNGASPConfigEntry 14 }

genEquipInterfacesNGASPConfigCsfModeAdmin OBJECT-TYPE
        SYNTAX 	EnableDisable
        ACCESS  read-write
        STATUS mandatory
        DESCRIPTION
        "This mode upon failure sends CSF OAM packet instead of shuting down port."
        ::= { genEquipInterfacesNGASPConfigEntry 15 }

genEquipInterfacesNGASPConfigMonitoredInterface OBJECT-TYPE
        SYNTAX 	INTEGER
        ACCESS  read-write
        STATUS mandatory
        DESCRIPTION
        "Index to the monitored interface. Auto state propagation will act upon detecting a failure indication on this interface."
        ::= { genEquipInterfacesNGASPConfigEntry 16 }

genEquipInterfacesNGASPConfigDelayTime  OBJECT-TYPE
        SYNTAX 	INTEGER
        ACCESS  read-write
        STATUS mandatory
        DESCRIPTION
        "Debounce time for ASP (in milliseconds)"
        ::= { genEquipInterfacesNGASPConfigEntry 17 }

genEquipInterfacesNGASPConfigRowStatus OBJECT-TYPE
        SYNTAX  RowStatus
        ACCESS  read-write
        STATUS mandatory
        DESCRIPTION
        "Row status to allow user add entries dynamically."
        ::= { genEquipInterfacesNGASPConfigEntry 30 }



-- PW T-card
genEquipInterfacesPW	OBJECT IDENTIFIER ::= {genEquipInterfaces 7}

genEquipInterfacesPWCardTable  OBJECT-TYPE
        SYNTAX  SEQUENCE OF GenEquipInterfacesPWCardEntry
        ACCESS  not-accessible
        STATUS mandatory
        DESCRIPTION
        "PW-Card configuration table. using the table to configure the system PW-T features."
        ::= { genEquipInterfacesPW 1 }

genEquipInterfacesPWCardEntry OBJECT-TYPE
        SYNTAX GenEquipInterfacesPWCardEntry
        ACCESS not-accessible
        STATUS mandatory
          DESCRIPTION
          "PW-Card configuration table. using the table to configure the system PW-T features."
        INDEX { genEquipInterfacesPWCardSlotNumber }
        ::= { genEquipInterfacesPWCardTable 1 }

GenEquipInterfacesPWCardEntry ::=
		SEQUENCE {
			genEquipInterfacesPWCardSlotNumber
				INTEGER,
			genEquipInterfacesPWCardExportClkSysRef
            	INTEGER,
			genEquipInterfacesPWCardExportClkFrontPannel
                INTEGER,
			genEquipInterfacesPWCardExportClkSysRefCrPort
				INTEGER,
			genEquipInterfacesPWCardExportClkFrontPanelCrPort
				INTEGER,
			genEquipInterfacesPWCardFrontPanelClockSignalInput
				INTEGER,
			genEquipInterfacesPWCardFrontPanelClockSignalOutp
				INTEGER,
			genEquipInterfacesPWCardIpAddrUdpIpTraffic
				IpAddress,
			genEquipInterfacesPWCardIpSubnetUdpIpTraffic
				IpAddress,
			genEquipInterfacesPWCardClkRecoveryMode
				INTEGER,
			genEquipInterfacesPWCardDifferentialClkFrequency
				INTEGER,
			genEquipInterfacesPWCardDifferentialClkSource
				INTEGER
}

genEquipInterfacesPWCardSlotNumber		OBJECT-TYPE
		SYNTAX 		INTEGER (2..12)
		ACCESS		read-write
        STATUS		mandatory
        DESCRIPTION
		"Slot number where the relevant PW card is inserted."
::= { genEquipInterfacesPWCardEntry 1 }

genEquipInterfacesPWCardExportClkSysRef		OBJECT-TYPE
		SYNTAX 		INTEGER {
						none(0),
						frontPanel(1),
						clockRecovery(2)
		}
		ACCESS		read-write
        STATUS		mandatory
        DESCRIPTION
		"Which card clock to provide as source towards system reference clock;
		FrontPanel takes the clock inserted into the front panel interface;
		ClockRecovery takes the clock recovered from the PW service mapped to the TDM port defined in  ExportClkSysRefCrPort."
::= { genEquipInterfacesPWCardEntry 2 }

genEquipInterfacesPWCardExportClkFrontPannel		OBJECT-TYPE
		SYNTAX 		INTEGER {
						none(0),
						sysRefClk(1),
						clockRecovery(2)
		}
		ACCESS		read-only
        STATUS		mandatory
        DESCRIPTION
		"Which clock to export to the front panel clock; SysRefClk exports the system reference clock;
		ClockRecovery exports the clock recovered from the PW service mapped to the TDM port defined in  ExportClkFrontPanelCrPort."

::= { genEquipInterfacesPWCardEntry 3 }

genEquipInterfacesPWCardExportClkSysRefCrPort		OBJECT-TYPE
		SYNTAX 		INTEGER
		ACCESS		read-write
        STATUS		mandatory
        DESCRIPTION
		"TDM port serving as clock recovery reference if ExportClkSysRef is set to ClockRecovery."
::= { genEquipInterfacesPWCardEntry 4 }

genEquipInterfacesPWCardExportClkFrontPanelCrPort		OBJECT-TYPE
		SYNTAX 		INTEGER
		ACCESS		read-write
        STATUS		mandatory
        DESCRIPTION
		"TDM port serving as clock recovery reference if ExportClkFrontPannel is set to ClockRecovery."
::= { genEquipInterfacesPWCardEntry 5 }

genEquipInterfacesPWCardFrontPanelClockSignalInput		OBJECT-TYPE
		SYNTAX 		INTEGER  {
						sync(0),
						e1t1(1)
		}
		ACCESS		read-write
        STATUS		mandatory
        DESCRIPTION
		"Configure the type of input clock signal of the front panel port.
		Sync is 2.048MHz/1.544MHz (differential sine/square 3.3V); e1t1 is a G.823/G.824 signal."
::= { genEquipInterfacesPWCardEntry 6 }

genEquipInterfacesPWCardFrontPanelClockSignalOutp		OBJECT-TYPE
		SYNTAX 		INTEGER  {
						sync(0),
						e1t1(1)
		}
		ACCESS		read-write
        STATUS		mandatory
        DESCRIPTION
		"Configure the type of output clock signal of the front panel port.
		Sync is 2.048MHz/1.544MHz (differential sine/square 3.3V); e1t1 is a G.823/G.824 signal."
::= { genEquipInterfacesPWCardEntry 7 }

genEquipInterfacesPWCardIpAddrUdpIpTraffic		OBJECT-TYPE
		SYNTAX 		IpAddress
		ACCESS		read-write
        STATUS		mandatory
        DESCRIPTION
		"IP Address for UDP/IP encapsulated PWs."
::= { genEquipInterfacesPWCardEntry 8 }

genEquipInterfacesPWCardIpSubnetUdpIpTraffic		OBJECT-TYPE
		SYNTAX 		IpAddress
		ACCESS		read-write
        STATUS		mandatory
        DESCRIPTION
		"IP Subnet for UDP/IP encapsulated PWs."
::= { genEquipInterfacesPWCardEntry 9 }

genEquipInterfacesPWCardClkRecoveryMode		OBJECT-TYPE
		SYNTAX 		INTEGER {
						adaptive(0),
						differential(1)
		}
		ACCESS		read-write
        STATUS		mandatory
        DESCRIPTION
		"Clock recovery mode for the card."
::= { genEquipInterfacesPWCardEntry 10 }

genEquipInterfacesPWCardDifferentialClkFrequency		OBJECT-TYPE
		SYNTAX 		INTEGER {
						none(0),
						n25MHz(1),
						n125MHz(2)
		}
		ACCESS		read-write
        STATUS		mandatory
        DESCRIPTION
		"Frequency for differential clock (none for adaptive)."
::= { genEquipInterfacesPWCardEntry 11 }

genEquipInterfacesPWCardDifferentialClkSource		OBJECT-TYPE
		SYNTAX 		INTEGER {
						none (0),
						sysReference(2),
						frontPanel(3),
						n1588(4)
		}
		ACCESS		read-write
        STATUS		mandatory
        DESCRIPTION
		"Reference clock source for differential clock recovery (none for adaptive)."
::= { genEquipInterfacesPWCardEntry 12 }


-- PW t-card TDM ports  table
genEquipInterfacesServicesPWTDMPortsTable  OBJECT-TYPE
        SYNTAX  SEQUENCE OF GenEquipInterfacesServicesPWTDMPortsEntry
        ACCESS  not-accessible
        STATUS mandatory
        DESCRIPTION
        "This table allows configuration of the 16 internal E1/DS1 ports."
        ::= { genEquipInterfacesPW 2 }

genEquipInterfacesServicesPWTDMPortsEntry OBJECT-TYPE
        SYNTAX GenEquipInterfacesServicesPWTDMPortsEntry
        ACCESS not-accessible
        STATUS mandatory
          DESCRIPTION
          "This table allows configuration of the 16 internal E1/DS1 ports."
        INDEX { ifIndex }
        ::= { genEquipInterfacesServicesPWTDMPortsTable 1 }

GenEquipInterfacesServicesPWTDMPortsEntry ::=
		SEQUENCE {
			genEquipInterfacesServicesPWTDMPortsLineType
				INTEGER,
			genEquipInterfacesServicesPWTDMPortsLineCoding
				INTEGER,
			genEquipInterfacesServicesPWTDMPortsAssigned
				NoYes,
			genEquipInterfacesServicesPWTDMPortsChannelization
				EnableDisable,
			genEquipInterfacesServicesPWTDMPortsTimingMode
				INTEGER,
			genEquipInterfacesServicesPWTDMPortsClockSourceRef
				INTEGER,
			genEquipInterfacesServicesPWTDMPortsClkSrcRefPort
				INTEGER,
			genEquipInterfacesServicesPWTDMPortsClkSrcPWId
				INTEGER,
			genEquipInterfacesServicesPWTDMPortsLoopback
				INTEGER,
			genEquipInterfacesServicesPWTDMPortsTimeout
				INTEGER,
			genEquipInterfacesServicesPWTDMPortsIdleCode
				INTEGER,
			genEquipInterfacesServicesPWTDMPortsCounter
				INTEGER,
			genEquipInterfacesServicesPWTDMPortsLineStatus
				INTEGER
}


genEquipInterfacesServicesPWTDMPortsLineType		OBJECT-TYPE
		SYNTAX 		INTEGER {
						e1Unframed(0),
						e1(1),
						e1Crc(2),
						e1Mf(3),
						e1MfCrc(4),
						ds1Uxnframed(5),
						ds1Sf(6),
						ds1Esf(7)
		}
		ACCESS		read-write
        STATUS		mandatory
        DESCRIPTION
		"Line type of this TDM port. E1 types are for E1 systems and DS1 types for DS1 systems."
::= { genEquipInterfacesServicesPWTDMPortsEntry 1 }

genEquipInterfacesServicesPWTDMPortsLineCoding		OBJECT-TYPE
		SYNTAX 		NoYes
		ACCESS		read-write
        STATUS		mandatory
        DESCRIPTION
		"Line coding for this port. The value hdb3-b8zs means b8zs for T1 and hdb3 for E1.
		Ami is only for T1."
::= { genEquipInterfacesServicesPWTDMPortsEntry 2 }

genEquipInterfacesServicesPWTDMPortsAssigned		OBJECT-TYPE
		SYNTAX 		NoYes
		ACCESS		read-only
        STATUS		mandatory
        DESCRIPTION
		"Indication whether this port is currently assigned to a TDM trail."

::= { genEquipInterfacesServicesPWTDMPortsEntry 3 }

genEquipInterfacesServicesPWTDMPortsChannelization		OBJECT-TYPE
		SYNTAX 		EnableDisable
		ACCESS		read-write
        STATUS		mandatory
        DESCRIPTION
		"TIndication whether this TDM port is channelized into DS0s."
::= { genEquipInterfacesServicesPWTDMPortsEntry 4 }

genEquipInterfacesServicesPWTDMPortsTimingMode		OBJECT-TYPE
		SYNTAX 		INTEGER {
						loop(0),
						absolute(1),
						clockRecovery(2)
		}
		ACCESS		read-write
        STATUS		mandatory
        DESCRIPTION
		"Transmission towards TDM timing mode.
		Loop means transmitting with the received clock from TDM signal.
		Absolute means transmitting with the clock selected by ClockSourceRef.
		ClockRecovery means adaptive clock recovery mode."
::= { genEquipInterfacesServicesPWTDMPortsEntry 5 }

genEquipInterfacesServicesPWTDMPortsClockSourceRef		OBJECT-TYPE
		SYNTAX 		INTEGER  {
						none(0),
						sysRefClk(1),
						frontPanel(2)
		}
		ACCESS		read-write
        STATUS		mandatory
        DESCRIPTION
		"Clock source reference for Absolute clock mode.
		'none' for loop or clock-recovery timing modes."
::= { genEquipInterfacesServicesPWTDMPortsEntry 6 }

genEquipInterfacesServicesPWTDMPortsClkSrcRefPort		OBJECT-TYPE
		SYNTAX 		INTEGER
		ACCESS		read-write
        STATUS		mandatory
        DESCRIPTION
		"TDM port serving as a clock reference for loop or clock-recovery timing modes"
::= { genEquipInterfacesServicesPWTDMPortsEntry 7 }

genEquipInterfacesServicesPWTDMPortsClkSrcPWId		OBJECT-TYPE
		SYNTAX 		INTEGER (0..256)
		ACCESS		read-write
        STATUS		mandatory
        DESCRIPTION
		"PW ID (as defined in genEquipServicesPWServicePWId)  from which clock will be derived
		for this port when TimingMode is ClockRecovery."
::= { genEquipInterfacesServicesPWTDMPortsEntry 8 }

genEquipInterfacesServicesPWTDMPortsLoopback		OBJECT-TYPE
		SYNTAX 		INTEGER {
						off(1),
						towardsLine(2),
						towardsSystem(3)
		}
		ACCESS		read-write
        STATUS		mandatory
        DESCRIPTION
		"Enable or Disable line loopback on the E1/T1 interface."
::= { genEquipInterfacesServicesPWTDMPortsEntry 9 }

genEquipInterfacesServicesPWTDMPortsTimeout		OBJECT-TYPE
		SYNTAX 		INTEGER (0..1440)
		ACCESS		read-write
        STATUS		mandatory
        DESCRIPTION
		"Line loopback timeout, in minutes. 0 means no timer."
::= { genEquipInterfacesServicesPWTDMPortsEntry 10 }

genEquipInterfacesServicesPWTDMPortsIdleCode		OBJECT-TYPE
		SYNTAX 		INTEGER (0..255)
		ACCESS		read-write
        STATUS		mandatory
        DESCRIPTION
		"Value to be transmitted on this TDM port in unused timeslots."
::= { genEquipInterfacesServicesPWTDMPortsEntry 11 }

genEquipInterfacesServicesPWTDMPortsCounter		OBJECT-TYPE
		SYNTAX 		INTEGER
		ACCESS		read-only
        STATUS		mandatory
        DESCRIPTION
		"Loopback time left (in seconds)."
::= { genEquipInterfacesServicesPWTDMPortsEntry 12 }

genEquipInterfacesServicesPWTDMPortsLineStatus		OBJECT-TYPE
		SYNTAX 		INTEGER {
						noAlarm(0),
						rxLof(1),
						txLof(2),
						rxAis(3),
						txAis(4),
						ts16RxLomf(5),
						ts16TxLomf(6),
						loopbackAlarm(7),
						otherFailure(8)

		}
		ACCESS		read-only
        STATUS		mandatory
        DESCRIPTION
		"Line status of this TDM port."
::= { genEquipInterfacesServicesPWTDMPortsEntry 13 }

--
-- NG PW Interfaces
--
genEquipInterfacesNGPW	OBJECT IDENTIFIER ::= {genEquipInterfacesPW 3}

--
-- PW-LIC card configuration table - pw-card-configuration-table
--
genEquipInterfacesNGPWCardTable  OBJECT-TYPE
        SYNTAX  SEQUENCE OF GenEquipInterfacesNGPWCardEntry
        ACCESS  not-accessible
        STATUS mandatory
        DESCRIPTION
        "This table allows configuration of PW-LIC card level parameters."
        ::= { genEquipInterfacesNGPW 1 }

genEquipInterfacesNGPWCardEntry OBJECT-TYPE
        SYNTAX GenEquipInterfacesNGPWCardEntry
        ACCESS not-accessible
        STATUS mandatory
		DESCRIPTION
        "This table entry allows configuration of PW-LIC card level parameters."
        INDEX { genEquipInterfacesNGPWCardSlotID }
        ::= { genEquipInterfacesNGPWCardTable 1 }

GenEquipInterfacesNGPWCardEntry ::=
		SEQUENCE {
			genEquipInterfacesNGPWCardSlotID
				INTEGER,
			genEquipInterfacesNGPWCardExportClkSysRef
            	PWCclockSysRef,
			genEquipInterfacesNGPWCardExportClkSysRefCrPort
                INTEGER,
			genEquipInterfacesNGPWCardIPAddress
				IpAddress,
			genEquipInterfacesNGPWCardIPSubnetMask
				IpAddress,
			genEquipInterfacesNGPWCardClkRecoveryMode
				INTEGER,
			genEquipInterfacesNGPWCardDifferentialClkSource
				PWCDiffClockSrc,
			genEquipInterfacesNGPWCardClockFreq
				INTEGER,
			genEquipInterfacesNGPWCardTDMType
				INTEGER,
			genEquipInterfacesNGPWCardLoopbackTimeout
				INTEGER
}

genEquipInterfacesNGPWCardSlotID		OBJECT-TYPE
		SYNTAX 		INTEGER (2..12)
		ACCESS		read-only
        STATUS		mandatory
        DESCRIPTION
		"Slot where PW-LIC is inserted."
::= { genEquipInterfacesNGPWCardEntry 1 }

genEquipInterfacesNGPWCardExportClkSysRef		OBJECT-TYPE
		SYNTAX 		PWCclockSysRef
		ACCESS		read-write
        STATUS		mandatory
        DESCRIPTION
		"Configures which clock the PW-LIC exports towards the system."
::= { genEquipInterfacesNGPWCardEntry 2 }

genEquipInterfacesNGPWCardExportClkSysRefCrPort		OBJECT-TYPE
		SYNTAX 		INTEGER
		ACCESS		read-write
        STATUS		mandatory
        DESCRIPTION
		"TDM port serving as clock recovery reference towards the system."
::= { genEquipInterfacesNGPWCardEntry 3 }

genEquipInterfacesNGPWCardIPAddress		OBJECT-TYPE
		SYNTAX 		IpAddress
		ACCESS		read-write
        STATUS		mandatory
        DESCRIPTION
		"IP Address for UDP/IP and MPLS encapsulations."
::= { genEquipInterfacesNGPWCardEntry 4 }

genEquipInterfacesNGPWCardIPSubnetMask		OBJECT-TYPE
		SYNTAX 		IpAddress
		ACCESS		read-write
        STATUS		mandatory
        DESCRIPTION
		"IP subnet mask for UDP/IP and MPLS encapsulations."
::= { genEquipInterfacesNGPWCardEntry 5 }

genEquipInterfacesNGPWCardClkRecoveryMode		OBJECT-TYPE
		SYNTAX 		INTEGER {
						adaptive(0),
						differential(1)
					}
		ACCESS		read-write
        STATUS		mandatory
        DESCRIPTION
		"Sets the card either in ACR or differential clock recovery mode."
::= { genEquipInterfacesNGPWCardEntry 6 }

genEquipInterfacesNGPWCardDifferentialClkSource		OBJECT-TYPE
		SYNTAX 		PWCDiffClockSrc
		ACCESS		read-write
        STATUS		mandatory
        DESCRIPTION
		"Reference clock source for differential clock recovery (none for adaptive)."
::= { genEquipInterfacesNGPWCardEntry 7 }

genEquipInterfacesNGPWCardClockFreq		OBJECT-TYPE
		SYNTAX 		INTEGER {
						none(0),
						fr-25(1),
						fr-125(2)
						}
		ACCESS		read-write
        STATUS		mandatory
        DESCRIPTION
		"Frequency for differential clock (none for adaptive)."
::= { genEquipInterfacesNGPWCardEntry 8 }

genEquipInterfacesNGPWCardTDMType		OBJECT-TYPE
		SYNTAX 		INTEGER {
						e1(0),
						ds1(1)
					}
		ACCESS		read-write
        STATUS		mandatory
        DESCRIPTION
		"Type of TDM interfaces (E1, DS1)."
::= { genEquipInterfacesNGPWCardEntry 9 }

genEquipInterfacesNGPWCardLoopbackTimeout		OBJECT-TYPE
		SYNTAX 		INTEGER (0..1440)
		ACCESS		read-write
        STATUS		mandatory
        DESCRIPTION
		"Timeout for TDM ports loopback."
::= { genEquipInterfacesNGPWCardEntry 10 }


-- pwe3-pwc-fp-clock-configuration-table
genEquipInterfacesNGPWClockInterfaceTable  OBJECT-TYPE
        SYNTAX  SEQUENCE OF GenEquipInterfacesNGPWClockInterfaceEntry
        ACCESS  not-accessible
        STATUS mandatory
        DESCRIPTION
        "This table allows configuration of the front panel clock interface in the PW-LIC."
        ::= { genEquipInterfacesNGPW 3 }

genEquipInterfacesNGPWClockInterfaceEntry OBJECT-TYPE
        SYNTAX GenEquipInterfacesNGPWClockInterfaceEntry
        ACCESS not-accessible
        STATUS mandatory
          DESCRIPTION
          "This table entry allows configuration of the front panel clock interface in the PW-LIC."
        INDEX { genEquipInterfacesNGPWClockInterfaceSlotID }
        ::= { genEquipInterfacesNGPWClockInterfaceTable 1 }

GenEquipInterfacesNGPWClockInterfaceEntry ::=
		SEQUENCE {
			genEquipInterfacesNGPWClockInterfaceSlotID
				INTEGER,
			genEquipInterfacesNGPWClockInterfaceIfIndex
				INTEGER,
			genEquipInterfacesNGPWClockInterfaceAdminRx
				EnableDisableSMI2,
			genEquipInterfacesNGPWClockInterfaceAdminTx
				EnableDisableSMI2,
			genEquipInterfacesNGPWClockInterfaceExportClkFrontPannel
				INTEGER,
			genEquipInterfacesNGPWClockInterfaceExportClkFrontPanelCrPort
				INTEGER,
			genEquipInterfacesNGPWClockInterfaceFrontPanelClockSignalInput
				PWfpClockSignal,
			genEquipInterfacesNGPWClockInterfaceFrontPanelClockSignalOutput
				PWfpClockSignal,
			genEquipInterfacesNGPWClockInterfaceSSMAdmin
				EnableDisableSMI2,
			genEquipInterfacesNGPWClockInterfaceSSMBit
				INTEGER,
			genEquipInterfacesNGPWClockInterfaceSSMTxDefault
				INTEGER
}


genEquipInterfacesNGPWClockInterfaceSlotID		OBJECT-TYPE
		SYNTAX 		INTEGER
		ACCESS		read-only
        STATUS		mandatory
        DESCRIPTION
		"Slot where PW-LIC is inserted."
::= { genEquipInterfacesNGPWClockInterfaceEntry 1 }

genEquipInterfacesNGPWClockInterfaceIfIndex		OBJECT-TYPE
		SYNTAX 		INTEGER
		ACCESS		read-write
        STATUS		mandatory
        DESCRIPTION
		"Interface IfIndex."
::= { genEquipInterfacesNGPWClockInterfaceEntry 2 }

genEquipInterfacesNGPWClockInterfaceAdminRx		OBJECT-TYPE
		SYNTAX 		EnableDisableSMI2
		ACCESS		read-only
        STATUS		mandatory
        DESCRIPTION
		"Clock interface administrative state."
::= { genEquipInterfacesNGPWClockInterfaceEntry 3 }

genEquipInterfacesNGPWClockInterfaceAdminTx		OBJECT-TYPE
		SYNTAX 		EnableDisableSMI2
		ACCESS		read-write
        STATUS		mandatory
        DESCRIPTION
		"Clock interface administrative state."
::= { genEquipInterfacesNGPWClockInterfaceEntry 4 }

genEquipInterfacesNGPWClockInterfaceExportClkFrontPannel		OBJECT-TYPE
		SYNTAX 		INTEGER {
						none(0),
						sysRef(1),
						clockRecovery(2)
		}
		ACCESS		read-write
        STATUS		mandatory
        DESCRIPTION
		"Configures which signal the PW-LIC exports to the front panel clock interface."
::= { genEquipInterfacesNGPWClockInterfaceEntry 5 }

genEquipInterfacesNGPWClockInterfaceExportClkFrontPanelCrPort		OBJECT-TYPE
		SYNTAX 		INTEGER  (0..16)
		ACCESS		read-write
        STATUS		mandatory
        DESCRIPTION
		"TDM port serving as clock recovery reference for front panel interface."
::= { genEquipInterfacesNGPWClockInterfaceEntry 6 }

genEquipInterfacesNGPWClockInterfaceFrontPanelClockSignalInput		OBJECT-TYPE
		SYNTAX 		PWfpClockSignal
		ACCESS		read-write
        STATUS		mandatory
        DESCRIPTION
		"Expected input signal type: E1 or differential sine/square 3.3V 2MHz"
::= { genEquipInterfacesNGPWClockInterfaceEntry 7 }

genEquipInterfacesNGPWClockInterfaceFrontPanelClockSignalOutput		OBJECT-TYPE
		SYNTAX 		PWfpClockSignal
		ACCESS		read-write
        STATUS		mandatory
        DESCRIPTION
		"Output signal type: E1 or differential sine/square 3.3V 2MH."
::= { genEquipInterfacesNGPWClockInterfaceEntry 8 }

genEquipInterfacesNGPWClockInterfaceSSMAdmin		OBJECT-TYPE
		SYNTAX 		EnableDisableSMI2
		ACCESS		read-write
        STATUS		mandatory
        DESCRIPTION
		"Enable/disable SSM sending in this interface."
::= { genEquipInterfacesNGPWClockInterfaceEntry 9 }

genEquipInterfacesNGPWClockInterfaceSSMBit		OBJECT-TYPE
		SYNTAX 		INTEGER (4..8)
		ACCESS		read-write
        STATUS		mandatory
        DESCRIPTION
		"Determines which bit in the frame."
::= { genEquipInterfacesNGPWClockInterfaceEntry 10 }

genEquipInterfacesNGPWClockInterfaceSSMTxDefault		OBJECT-TYPE
		SYNTAX 		INTEGER (0..63)
		ACCESS		read-write
        STATUS		mandatory
        DESCRIPTION
		"..."
::= { genEquipInterfacesNGPWClockInterfaceEntry 11 }


-- pw-clock-interface-status-table
genEquipInterfacesNGPWClockInterfaceStatusTable  OBJECT-TYPE
        SYNTAX  SEQUENCE OF GenEquipInterfacesNGPWClockInterfaceStatusEntry
        ACCESS  not-accessible
        STATUS mandatory
        DESCRIPTION
        "This table contains information about current state of the clock interface in the PW-LIC."
        ::= { genEquipInterfacesNGPW 4 }

genEquipInterfacesNGPWClockInterfaceStatusEntry OBJECT-TYPE
        SYNTAX GenEquipInterfacesNGPWClockInterfaceStatusEntry
        ACCESS not-accessible
        STATUS mandatory
          DESCRIPTION
          "This table entry contains information about current state of the clock interface in the PW-LIC."
        INDEX { genEquipInterfacesNGPWClockInterfaceStatusSlotID }
        ::= { genEquipInterfacesNGPWClockInterfaceStatusTable 1 }

GenEquipInterfacesNGPWClockInterfaceStatusEntry ::=
		SEQUENCE {
			genEquipInterfacesNGPWClockInterfaceStatusSlotID
				INTEGER,
			genEquipInterfacesNGPWClockInterfaceStatusIfIndex
				INTEGER,
			genEquipInterfacesNGPWClockInterfaceStatusOperationalState
				DownUp,
			genEquipInterfacesNGPWClockInterfaceStatusSSMTx
				INTEGER,
			genEquipInterfacesNGPWClockInterfaceStatusSSMRx
				INTEGER
}


genEquipInterfacesNGPWClockInterfaceStatusSlotID		OBJECT-TYPE
		SYNTAX 		INTEGER (2..12)
		ACCESS		read-only
        STATUS		mandatory
        DESCRIPTION
		"Slot where PW-LIC is inserted."
::= { genEquipInterfacesNGPWClockInterfaceStatusEntry 1 }

genEquipInterfacesNGPWClockInterfaceStatusIfIndex		OBJECT-TYPE
		SYNTAX 		INTEGER
		ACCESS		read-only
        STATUS		mandatory
        DESCRIPTION
		"Interface IfIndex."
::= { genEquipInterfacesNGPWClockInterfaceStatusEntry 2 }

genEquipInterfacesNGPWClockInterfaceStatusOperationalState		OBJECT-TYPE
		SYNTAX 		DownUp
		ACCESS		read-only
        STATUS		mandatory
        DESCRIPTION
		"Clock interface operational state."
::= { genEquipInterfacesNGPWClockInterfaceStatusEntry 3 }

genEquipInterfacesNGPWClockInterfaceStatusSSMTx		OBJECT-TYPE
		SYNTAX 		INTEGER (0..63)
		ACCESS		read-only
        STATUS		mandatory
        DESCRIPTION
		"Currently transmitted SSM bits."
::= { genEquipInterfacesNGPWClockInterfaceStatusEntry 4 }

genEquipInterfacesNGPWClockInterfaceStatusSSMRx		OBJECT-TYPE
		SYNTAX 		INTEGER (0..63)
		ACCESS		read-only
        STATUS		mandatory
        DESCRIPTION
		"Currently received SSM bits."
::= { genEquipInterfacesNGPWClockInterfaceStatusEntry 5 }


-- pw-eth-port-configuration-table
genEquipInterfacesNGPWEthInterfaceTable  OBJECT-TYPE
        SYNTAX  SEQUENCE OF GenEquipInterfacesNGPWEthInterfaceEntry
        ACCESS  not-accessible
        STATUS mandatory
        DESCRIPTION
        "This table allows enabling/disabling the PW-LIC internal Ethernet port."
        ::= { genEquipInterfacesNGPW 5 }

genEquipInterfacesNGPWEthInterfaceEntry OBJECT-TYPE
        SYNTAX GenEquipInterfacesNGPWEthInterfaceEntry
        ACCESS not-accessible
        STATUS mandatory
          DESCRIPTION
          "This table allows enabling/disabling the PW-LIC internal Ethernet port."
        INDEX { genEquipInterfacesNGPWEthInterfaceSlotID }
        ::= { genEquipInterfacesNGPWEthInterfaceTable 1 }

GenEquipInterfacesNGPWEthInterfaceEntry ::=
		SEQUENCE {
			genEquipInterfacesNGPWEthInterfaceSlotID
				INTEGER,
			genEquipInterfacesNGPWEthInterfaceIfIndex
				INTEGER
}


genEquipInterfacesNGPWEthInterfaceSlotID		OBJECT-TYPE
		SYNTAX 		INTEGER (2..12)
		ACCESS		read-write
        STATUS		mandatory
        DESCRIPTION
		"Slot where PW-LIC is inserted."
::= { genEquipInterfacesNGPWEthInterfaceEntry 1 }

genEquipInterfacesNGPWEthInterfaceIfIndex		OBJECT-TYPE
		SYNTAX 		INTEGER
		ACCESS		read-only
        STATUS		mandatory
        DESCRIPTION
		"Interface IfIndex."
::= { genEquipInterfacesNGPWEthInterfaceEntry 2 }


-- pw-eth-port-status-table
genEquipInterfacesNGPWEthInterfaceStatusTable  OBJECT-TYPE
        SYNTAX  SEQUENCE OF GenEquipInterfacesNGPWEthInterfaceStatusEntry
        ACCESS  not-accessible
        STATUS mandatory
        DESCRIPTION
        "This table contains status and RMON statistics of the internal PW-LIC Ethernet port."
        ::= { genEquipInterfacesNGPW 6 }

genEquipInterfacesNGPWEthInterfaceStatusEntry OBJECT-TYPE
        SYNTAX GenEquipInterfacesNGPWEthInterfaceStatusEntry
        ACCESS not-accessible
        STATUS mandatory
          DESCRIPTION
          "This table enatry contains status and RMON statistics of the internal PW-LIC Ethernet port."
        INDEX { genEquipInterfacesNGPWEthInterfaceStatusIfIndex }
        ::= { genEquipInterfacesNGPWEthInterfaceStatusTable 1 }

GenEquipInterfacesNGPWEthInterfaceStatusEntry ::=
		SEQUENCE {
			genEquipInterfacesNGPWEthInterfaceStatusIfIndex
				INTEGER,
			genEquipInterfacesNGPWEthInterfaceStatusMACAddress
				OCTET STRING,
			genEquipInterfacesNGPWEthInterfaceStatusClearStats
				NoYes,
			genEquipInterfacesNGPWEthInterfaceStatusTxRxFrames64
				Counter64,
			genEquipInterfacesNGPWEthInterfaceStatusTxRxFrames127
				Counter64,
			genEquipInterfacesNGPWEthInterfaceStatusTxRxFrames255
				Counter64,
			genEquipInterfacesNGPWEthInterfaceStatusTxRxFrames511
				Counter64,
			genEquipInterfacesNGPWEthInterfaceStatusTxRxFrames1023
				Counter64,
			genEquipInterfacesNGPWEthInterfaceStatusTxRxFrames1518
				Counter64,
			genEquipInterfacesNGPWEthInterfaceStatusTxRxFrames1522
				Counter64,
			genEquipInterfacesNGPWEthInterfaceStatusRxBytes
				Counter64,
			genEquipInterfacesNGPWEthInterfaceStatusRxPackets
				Counter64,
			genEquipInterfacesNGPWEthInterfaceStatusRxErrFcs
				Counter64,
			genEquipInterfacesNGPWEthInterfaceStatusRxMulticast
				Counter64,
			genEquipInterfacesNGPWEthInterfaceStatusRxBroadcast
				Counter64,
			genEquipInterfacesNGPWEthInterfaceStatusRxMacControl
				Counter64,
			genEquipInterfacesNGPWEthInterfaceStatusRxMacPause
				Counter64,
			genEquipInterfacesNGPWEthInterfaceStatusRxMacUnknown
				Counter64,
			genEquipInterfacesNGPWEthInterfaceStatusRxErrCode
				Counter64,
			genEquipInterfacesNGPWEthInterfaceStatusRxErrFalseCarrier
				Counter64,
			genEquipInterfacesNGPWEthInterfaceStatusRxUndersize
				Counter64,
			genEquipInterfacesNGPWEthInterfaceStatusRxOversize
				Counter64,
			genEquipInterfacesNGPWEthInterfaceStatusRxFragments
				Counter64,
			genEquipInterfacesNGPWEthInterfaceStatusRxJabber
				Counter64,
			genEquipInterfacesNGPWEthInterfaceStatusRxDropped
				Counter64,
			genEquipInterfacesNGPWEthInterfaceStatusTxBytes
				Counter64,
			genEquipInterfacesNGPWEthInterfaceStatusTxPackets
				Counter64,
			genEquipInterfacesNGPWEthInterfaceStatusTxMulticast
				Counter64,
			genEquipInterfacesNGPWEthInterfaceStatusTxBroadcast
				Counter64,
			genEquipInterfacesNGPWEthInterfaceStatusTxMacPause
				Counter64,
			genEquipInterfacesNGPWEthInterfaceStatusTxDefer
				Counter64,
			genEquipInterfacesNGPWEthInterfaceStatusTxExcessDefer
				Counter64,
			genEquipInterfacesNGPWEthInterfaceStatusTxSingleCollision
				Counter64,
			genEquipInterfacesNGPWEthInterfaceStatusTxMultiCollision
				Counter64,
			genEquipInterfacesNGPWEthInterfaceStatusTxLateCollision
				Counter64,
			genEquipInterfacesNGPWEthInterfaceStatusTxExcessCollision
				Counter64,
			genEquipInterfacesNGPWEthInterfaceStatusTxNoCollision
				Counter64,
			genEquipInterfacesNGPWEthInterfaceStatusTxMacPauseHonored
				Counter64,
			genEquipInterfacesNGPWEthInterfaceStatusTxDropped
				Counter64,
			genEquipInterfacesNGPWEthInterfaceStatusTxJabber
				Counter64,
			genEquipInterfacesNGPWEthInterfaceStatusTxErrFcs
				Counter64,
			genEquipInterfacesNGPWEthInterfaceStatusTxControl
				Counter64,
			genEquipInterfacesNGPWEthInterfaceStatusTxOversize
				Counter64,
			genEquipInterfacesNGPWEthInterfaceStatusTxUndersize
				Counter64,
			genEquipInterfacesNGPWEthInterfaceStatusTxFragments
				Counter64,
			genEquipInterfacesNGPWEthInterfaceStatusRxIwFrames
				Counter64,
			genEquipInterfacesNGPWEthInterfaceStatusRxErrFbpUnderrun
				Counter64,
			genEquipInterfacesNGPWEthInterfaceStatusRxErrNonvalidMac
				Counter64,
			genEquipInterfacesNGPWEthInterfaceStatusRxErrMru
				Counter64,
			genEquipInterfacesNGPWEthInterfaceStatusRxErrSdu
				Counter64,
			genEquipInterfacesNGPWEthInterfaceStatusTxErrUnderrun
				Counter64,
			genEquipInterfacesNGPWEthInterfaceStatusRxErrOverrun
				Counter64,
			genEquipInterfacesNGPWEthInterfaceStatusSlotID
				INTEGER
}


genEquipInterfacesNGPWEthInterfaceStatusIfIndex		OBJECT-TYPE
		SYNTAX 		INTEGER
		ACCESS		read-only
        STATUS		mandatory
        DESCRIPTION
		"Interface IfIndex."
::= { genEquipInterfacesNGPWEthInterfaceStatusEntry 2 }

genEquipInterfacesNGPWEthInterfaceStatusMACAddress		OBJECT-TYPE
		SYNTAX 		OCTET STRING (SIZE(6))
		ACCESS		read-only
        STATUS		mandatory
        DESCRIPTION
		"MAC Address to be used in Ethernet and UDP/IP PSN packets"
::= { genEquipInterfacesNGPWEthInterfaceStatusEntry 3 }

genEquipInterfacesNGPWEthInterfaceStatusClearStats		OBJECT-TYPE
		SYNTAX 		NoYes
		ACCESS		write-only
        STATUS		mandatory
        DESCRIPTION
		"Clears internal Ethernet port RMON counters"
::= { genEquipInterfacesNGPWEthInterfaceStatusEntry 4 }

genEquipInterfacesNGPWEthInterfaceStatusTxRxFrames64		OBJECT-TYPE
		SYNTAX 		Counter64
		ACCESS		read-only
        STATUS		mandatory
        DESCRIPTION
		"Unsigned 64-bit modulo counter of good or bad frames transmitted and received that are 64 bytes in length inclusive"
::= { genEquipInterfacesNGPWEthInterfaceStatusEntry 5 }

genEquipInterfacesNGPWEthInterfaceStatusTxRxFrames127		OBJECT-TYPE
		SYNTAX 		Counter64
		ACCESS		read-only
        STATUS		mandatory
        DESCRIPTION
		"Unsigned 64-bit modulo counter of good or bad frames transmitted and received that are 65 to 127 bytes in length inclusive."
::= { genEquipInterfacesNGPWEthInterfaceStatusEntry 6 }

genEquipInterfacesNGPWEthInterfaceStatusTxRxFrames255		OBJECT-TYPE
		SYNTAX 		Counter64
		ACCESS		read-only
        STATUS		mandatory
        DESCRIPTION
		"Unsigned 64-bit modulo counter of good or bad frames transmitted and received that are 128 to 255 bytes in length inclusive."
::= { genEquipInterfacesNGPWEthInterfaceStatusEntry 7 }

genEquipInterfacesNGPWEthInterfaceStatusTxRxFrames511		OBJECT-TYPE
		SYNTAX 		Counter64
		ACCESS		read-only
        STATUS		mandatory
        DESCRIPTION
		"Unsigned 64-bit modulo counter of good or bad frames transmitted and received that are 256 to 511 bytes in length inclusive."
::= { genEquipInterfacesNGPWEthInterfaceStatusEntry 8 }

genEquipInterfacesNGPWEthInterfaceStatusTxRxFrames1023		OBJECT-TYPE
		SYNTAX 		Counter64
		ACCESS		read-only
        STATUS		mandatory
        DESCRIPTION
		"Unsigned 64-bit modulo counter of good or bad frames transmitted and received that are 512 to 1023 bytes in length inclusive."
::= { genEquipInterfacesNGPWEthInterfaceStatusEntry 9 }

genEquipInterfacesNGPWEthInterfaceStatusTxRxFrames1518		OBJECT-TYPE
		SYNTAX 		Counter64
		ACCESS		read-only
        STATUS		mandatory
        DESCRIPTION
		"Unsigned 64-bit modulo counter of good or bad frames transmitted and received that are 1024 to 1518 bytes in length inclusive."
::= { genEquipInterfacesNGPWEthInterfaceStatusEntry 10 }

genEquipInterfacesNGPWEthInterfaceStatusTxRxFrames1522		OBJECT-TYPE
		SYNTAX 		Counter64
		ACCESS		read-only
        STATUS		mandatory
        DESCRIPTION
		"Unsigned 64-bit modulo counter of good or bad frames transmitted and received that are 1519 to 1522 bytes in length inclusive."
::= { genEquipInterfacesNGPWEthInterfaceStatusEntry 11 }

genEquipInterfacesNGPWEthInterfaceStatusRxBytes		OBJECT-TYPE
		SYNTAX 		Counter64
		ACCESS		read-only
        STATUS		mandatory
        DESCRIPTION
		"Unsigned 64-bit modulo counter of byte count of frames received with 0 to 1518 bytes, including those in bad packets."
::= { genEquipInterfacesNGPWEthInterfaceStatusEntry 12 }

genEquipInterfacesNGPWEthInterfaceStatusRxPackets		OBJECT-TYPE
		SYNTAX 		Counter64
		ACCESS		read-only
        STATUS		mandatory
        DESCRIPTION
		"Unsigned 64-bit modulo counter of number of received packets (including bad packets, all Unicast, Broadcast, and Multicast packets)."
::= { genEquipInterfacesNGPWEthInterfaceStatusEntry 13 }

genEquipInterfacesNGPWEthInterfaceStatusRxErrFcs		OBJECT-TYPE
		SYNTAX 		Counter64
		ACCESS		read-only
        STATUS		mandatory
        DESCRIPTION
		"Unsigned 64-bit modulo counter of frames received that have a integral 64 to 1518 byte length and contain a Frame Check Sequence error.."
::= { genEquipInterfacesNGPWEthInterfaceStatusEntry 14 }

genEquipInterfacesNGPWEthInterfaceStatusRxMulticast		OBJECT-TYPE
		SYNTAX 		Counter64
		ACCESS		read-only
        STATUS		mandatory
        DESCRIPTION
		"Unsigned 64-bit modulo counter of number of multicast good frames of length 64 to1518 (non VLAN) or 1522 (VLAN) bytes excluding Broadcast frames."
::= { genEquipInterfacesNGPWEthInterfaceStatusEntry 15 }

genEquipInterfacesNGPWEthInterfaceStatusRxBroadcast		OBJECT-TYPE
		SYNTAX 		Counter64
		ACCESS		read-only
        STATUS		mandatory
        DESCRIPTION
		"Unsigned 64-bit modulo counter of number of broadcast good frames of length 64 to1518 (non VLAN) or 1522 (VLAN) bytes excluding Broadcast frames."
::= { genEquipInterfacesNGPWEthInterfaceStatusEntry 16 }

genEquipInterfacesNGPWEthInterfaceStatusRxMacControl		OBJECT-TYPE
		SYNTAX 		Counter64
		ACCESS		read-only
        STATUS		mandatory
        DESCRIPTION
		"Unsigned 64-bit modulo counter of MAC Control frames received (PAUSE &amp;Unsupported)."
::= { genEquipInterfacesNGPWEthInterfaceStatusEntry 17 }

genEquipInterfacesNGPWEthInterfaceStatusRxMacPause		OBJECT-TYPE
		SYNTAX 		Counter64
		ACCESS		read-only
        STATUS		mandatory
        DESCRIPTION
		"Unsigned 64-bit modulo counter of valid PAUSE MAC Control frames received."
::= { genEquipInterfacesNGPWEthInterfaceStatusEntry 18 }

genEquipInterfacesNGPWEthInterfaceStatusRxMacUnknown		OBJECT-TYPE
		SYNTAX 		Counter64
		ACCESS		read-only
        STATUS		mandatory
        DESCRIPTION
		"Unsigned 64-bit modulo counter of MAC Control Frames received that contain an opcode other than a PAUSE."
::= { genEquipInterfacesNGPWEthInterfaceStatusEntry 19 }

genEquipInterfacesNGPWEthInterfaceStatusRxErrCode		OBJECT-TYPE
		SYNTAX 		Counter64
		ACCESS		read-only
        STATUS		mandatory
        DESCRIPTION
		"Unsigned 64-bit modulo counter of number of instances where a valid carrier was present and at least one invalid data symbol was detected."
::= { genEquipInterfacesNGPWEthInterfaceStatusEntry 20 }

genEquipInterfacesNGPWEthInterfaceStatusRxErrFalseCarrier		OBJECT-TYPE
		SYNTAX 		Counter64
		ACCESS		read-only
        STATUS		mandatory
        DESCRIPTION
		"Unsigned 64-bit modulo counter of number of false carriers detected during idle, as defined by a 1 on RX_ER and an '0xE' on RXD."
::= { genEquipInterfacesNGPWEthInterfaceStatusEntry 21 }

genEquipInterfacesNGPWEthInterfaceStatusRxUndersize		OBJECT-TYPE
		SYNTAX 		Counter64
		ACCESS		read-only
        STATUS		mandatory
        DESCRIPTION
		"Unsigned 64-bit modulo counter of frames received that are less than 64 bytes in length, contain a valid FCS, and were otherwise well formed."
::= { genEquipInterfacesNGPWEthInterfaceStatusEntry 22 }

genEquipInterfacesNGPWEthInterfaceStatusRxOversize		OBJECT-TYPE
		SYNTAX 		Counter64
		ACCESS		read-only
        STATUS		mandatory
        DESCRIPTION
		"Unsigned 64-bit modulo counter of frames received that exceeded maximum bytes in length, contain a valid FCS, and were otherwise well formed."
::= { genEquipInterfacesNGPWEthInterfaceStatusEntry 23 }

genEquipInterfacesNGPWEthInterfaceStatusRxFragments		OBJECT-TYPE
		SYNTAX 		Counter64
		ACCESS		read-only
        STATUS		mandatory
        DESCRIPTION
		"Unsigned 64-bit modulo counter of frames received which are less than 64 bytes in length and contain an invalid FCS."
::= { genEquipInterfacesNGPWEthInterfaceStatusEntry 24 }

genEquipInterfacesNGPWEthInterfaceStatusRxJabber		OBJECT-TYPE
		SYNTAX 		Counter64
		ACCESS		read-only
        STATUS		mandatory
        DESCRIPTION
		"Unsigned 64-bit modulo counter of frames received which exceed maximum length and contain an invalid FCS, including alignment errors."
::= { genEquipInterfacesNGPWEthInterfaceStatusEntry 25 }

genEquipInterfacesNGPWEthInterfaceStatusRxDropped		OBJECT-TYPE
		SYNTAX 		Counter64
		ACCESS		read-only
        STATUS		mandatory
        DESCRIPTION
		"Unsigned 64-bit modulo counter of frames received that are streamed to the system but are later dropped due to lack of system resources."
::= { genEquipInterfacesNGPWEthInterfaceStatusEntry 26 }

genEquipInterfacesNGPWEthInterfaceStatusTxBytes		OBJECT-TYPE
		SYNTAX 		Counter64
		ACCESS		read-only
        STATUS		mandatory
        DESCRIPTION
		"Unsigned 64-bit modulo counter of number of bytes that were put on the wire including fragments of frames that were involved with collisions."
::= { genEquipInterfacesNGPWEthInterfaceStatusEntry 27 }

genEquipInterfacesNGPWEthInterfaceStatusTxPackets		OBJECT-TYPE
		SYNTAX 		Counter64
		ACCESS		read-only
        STATUS		mandatory
        DESCRIPTION
		"Unsigned 64-bit modulo counter of transmitted packets."
::= { genEquipInterfacesNGPWEthInterfaceStatusEntry 28 }

genEquipInterfacesNGPWEthInterfaceStatusTxMulticast		OBJECT-TYPE
		SYNTAX 		Counter64
		ACCESS		read-only
        STATUS		mandatory
        DESCRIPTION
		"Unsigned 64-bit modulo counter of Multicast valid frames transmitted (excluding Broadcast frames)."
::= { genEquipInterfacesNGPWEthInterfaceStatusEntry 29 }

genEquipInterfacesNGPWEthInterfaceStatusTxBroadcast		OBJECT-TYPE
		SYNTAX 		Counter64
		ACCESS		read-only
        STATUS		mandatory
        DESCRIPTION
		"Unsigned 64-bit modulo counter of Broadcast frames transmitted (excluding Multicast frames)."
::= { genEquipInterfacesNGPWEthInterfaceStatusEntry 30 }

genEquipInterfacesNGPWEthInterfaceStatusTxMacPause		OBJECT-TYPE
		SYNTAX 		Counter64
		ACCESS		read-only
        STATUS		mandatory
        DESCRIPTION
		"Unsigned 64-bit modulo counter of valid PAUSE MAC Control frames transmitted."
::= { genEquipInterfacesNGPWEthInterfaceStatusEntry 31 }

genEquipInterfacesNGPWEthInterfaceStatusTxDefer		OBJECT-TYPE
		SYNTAX 		Counter64
		ACCESS		read-only
        STATUS		mandatory
        DESCRIPTION
		"Unsigned 64-bit modulo counter of frames that were deferred upon first transmission attempt. Does not include frames involved in collisions.."
::= { genEquipInterfacesNGPWEthInterfaceStatusEntry 32 }

genEquipInterfacesNGPWEthInterfaceStatusTxExcessDefer		OBJECT-TYPE
		SYNTAX 		Counter64
		ACCESS		read-only
        STATUS		mandatory
        DESCRIPTION
		"Unsigned 64-bit modulo counter of number of frames aborted that were deferred for an excessive period of time (3036 byte times)."
::= { genEquipInterfacesNGPWEthInterfaceStatusEntry 33 }

genEquipInterfacesNGPWEthInterfaceStatusTxSingleCollision		OBJECT-TYPE
		SYNTAX 		Counter64
		ACCESS		read-only
        STATUS		mandatory
        DESCRIPTION
		"Unsigned 64-bit modulo counter of frames transmitted which experienced exactly one collision during transmission."
::= { genEquipInterfacesNGPWEthInterfaceStatusEntry 34 }

genEquipInterfacesNGPWEthInterfaceStatusTxMultiCollision		OBJECT-TYPE
		SYNTAX 		Counter64
		ACCESS		read-only
        STATUS		mandatory
        DESCRIPTION
		"Unsigned 64-bit modulo counter of frames transmitted which experienced 2-15 collisions."
::= { genEquipInterfacesNGPWEthInterfaceStatusEntry 35 }

genEquipInterfacesNGPWEthInterfaceStatusTxLateCollision		OBJECT-TYPE
		SYNTAX 		Counter64
		ACCESS		read-only
        STATUS		mandatory
        DESCRIPTION
		"Unsigned 64-bit modulo counter of frames transmitted that experienced a late collision during a transmission attempt."
::= { genEquipInterfacesNGPWEthInterfaceStatusEntry 36 }

genEquipInterfacesNGPWEthInterfaceStatusTxExcessCollision		OBJECT-TYPE
		SYNTAX 		Counter64
		ACCESS		read-only
        STATUS		mandatory
        DESCRIPTION
		"Unsigned 64-bit modulo counter of frames that experienced 16 collisions during transmission and were aborted."
::= { genEquipInterfacesNGPWEthInterfaceStatusEntry 37 }

genEquipInterfacesNGPWEthInterfaceStatusTxNoCollision		OBJECT-TYPE
		SYNTAX 		Counter64
		ACCESS		read-only
        STATUS		mandatory
        DESCRIPTION
		"Unsigned 64-bit modulo counter of number of frames transmitted that had no collision."
::= { genEquipInterfacesNGPWEthInterfaceStatusEntry 38 }

genEquipInterfacesNGPWEthInterfaceStatusTxMacPauseHonored		OBJECT-TYPE
		SYNTAX 		Counter64
		ACCESS		read-only
        STATUS		mandatory
        DESCRIPTION
		"Unsigned 64-bit modulo counter of number of times a valid PAUSE MAC Control frame was transmitted and honored."
::= { genEquipInterfacesNGPWEthInterfaceStatusEntry 39 }

genEquipInterfacesNGPWEthInterfaceStatusTxDropped		OBJECT-TYPE
		SYNTAX 		Counter64
		ACCESS		read-only
        STATUS		mandatory
        DESCRIPTION
		"Unsigned 64-bit modulo counter of number of times the input PFH is asserted."
::= { genEquipInterfacesNGPWEthInterfaceStatusEntry 40 }

genEquipInterfacesNGPWEthInterfaceStatusTxJabber		OBJECT-TYPE
		SYNTAX 		Counter64
		ACCESS		read-only
        STATUS		mandatory
        DESCRIPTION
		"Unsigned 64-bit modulo counter of oversized transmitted frames with an incorrect FCS value."
::= { genEquipInterfacesNGPWEthInterfaceStatusEntry 41 }

genEquipInterfacesNGPWEthInterfaceStatusTxErrFcs		OBJECT-TYPE
		SYNTAX 		Counter64
		ACCESS		read-only
        STATUS		mandatory
        DESCRIPTION
		"Unsigned 64-bit modulo counter of valid sized packets transmitted with an incorrec tFCS value."
::= { genEquipInterfacesNGPWEthInterfaceStatusEntry 42 }

genEquipInterfacesNGPWEthInterfaceStatusTxControl		OBJECT-TYPE
		SYNTAX 		Counter64
		ACCESS		read-only
        STATUS		mandatory
        DESCRIPTION
		"Unsigned 64-bit modulo counter of valid size frames transmitted with a Type Field signifying a Control frame.."
::= { genEquipInterfacesNGPWEthInterfaceStatusEntry 43 }

genEquipInterfacesNGPWEthInterfaceStatusTxOversize		OBJECT-TYPE
		SYNTAX 		Counter64
		ACCESS		read-only
        STATUS		mandatory
        DESCRIPTION
		"Unsigned 64-bit modulo counter of oversized transmitted frames with a correct."
::= { genEquipInterfacesNGPWEthInterfaceStatusEntry 44 }

genEquipInterfacesNGPWEthInterfaceStatusTxUndersize		OBJECT-TYPE
		SYNTAX 		Counter64
		ACCESS		read-only
        STATUS		mandatory
        DESCRIPTION
		"Unsigned 64-bit modulo counter of transmitted frames less then 64 bytes, with a correctFCS value."
::= { genEquipInterfacesNGPWEthInterfaceStatusEntry 45 }

genEquipInterfacesNGPWEthInterfaceStatusTxFragments		OBJECT-TYPE
		SYNTAX 		Counter64
		ACCESS		read-only
        STATUS		mandatory
        DESCRIPTION
		"Unsigned 64-bit modulo counter of transmitted frames less then 64 bytes, with an incorrect FCS value."
::= { genEquipInterfacesNGPWEthInterfaceStatusEntry 46 }

genEquipInterfacesNGPWEthInterfaceStatusRxIwFrames		OBJECT-TYPE
		SYNTAX 		Counter64
		ACCESS		read-only
        STATUS		mandatory
        DESCRIPTION
		"Unsigned 64-bit modulo counter of the number of received Ethernet Interworking frames that were received and sent to the L3 Interworking module."
::= { genEquipInterfacesNGPWEthInterfaceStatusEntry 47 }

genEquipInterfacesNGPWEthInterfaceStatusRxErrFbpUnderrun		OBJECT-TYPE
		SYNTAX 		Counter64
		ACCESS		read-only
        STATUS		mandatory
        DESCRIPTION
		"Unsigned 64-bit modulo counter of the number of received Ethernet Interworking frames which were dropped due free buffer pool (FBP) Overrun."
::= { genEquipInterfacesNGPWEthInterfaceStatusEntry 48 }

genEquipInterfacesNGPWEthInterfaceStatusRxErrNonvalidMac		OBJECT-TYPE
		SYNTAX 		Counter64
		ACCESS		read-only
        STATUS		mandatory
        DESCRIPTION
		"Unsigned 64-bit modulo counter of the number of received Ethernet frames whose MAC-DA is not valid."
::= { genEquipInterfacesNGPWEthInterfaceStatusEntry 49 }

genEquipInterfacesNGPWEthInterfaceStatusRxErrMru		OBJECT-TYPE
		SYNTAX 		Counter64
		ACCESS		read-only
        STATUS		mandatory
        DESCRIPTION
		"Unsigned 64-bit modulo counter of the number of received Ethernet Interworking frames which were dropped due the Maximum Receive Unit."
::= { genEquipInterfacesNGPWEthInterfaceStatusEntry 50 }

genEquipInterfacesNGPWEthInterfaceStatusRxErrSdu		OBJECT-TYPE
		SYNTAX 		Counter64
		ACCESS		read-only
        STATUS		mandatory
        DESCRIPTION
		"Unsigned 64-bit modulo counter of the number of Ethernet frames which were closed due the maximum frame size has been exceeded."
::= { genEquipInterfacesNGPWEthInterfaceStatusEntry 51 }

genEquipInterfacesNGPWEthInterfaceStatusTxErrUnderrun		OBJECT-TYPE
		SYNTAX 		Counter64
		ACCESS		read-only
        STATUS		mandatory
        DESCRIPTION
		"Unsigned 64-bit modulo counter of number of times Ethernet transmitter underun occurred."
::= { genEquipInterfacesNGPWEthInterfaceStatusEntry 52 }

genEquipInterfacesNGPWEthInterfaceStatusRxErrOverrun		OBJECT-TYPE
		SYNTAX 		Counter64
		ACCESS		read-only
        STATUS		mandatory
        DESCRIPTION
		"Unsigned 64-bit modulo counter of number of received Ethernet frames which were closed or discarded due to a receive buffer overrun event."
::= { genEquipInterfacesNGPWEthInterfaceStatusEntry 53 }

genEquipInterfacesNGPWEthInterfaceStatusSlotID		OBJECT-TYPE
		SYNTAX 		INTEGER
		ACCESS		read-only
        STATUS		mandatory
        DESCRIPTION
		"Slot where PW-LIC is inserted"
::= { genEquipInterfacesNGPWEthInterfaceStatusEntry 54 }


--
-- PW-LIC card staus table - pw-card-status-table
--
genEquipInterfacesNGPWCardStatusTable  OBJECT-TYPE
        SYNTAX  SEQUENCE OF GenEquipInterfacesNGPWCardStatusEntry
        ACCESS  not-accessible
        STATUS mandatory
        DESCRIPTION
        "This table contains information about PW-LIC card level status."
        ::= { genEquipInterfacesNGPW 7 }

genEquipInterfacesNGPWCardStatusEntry OBJECT-TYPE
        SYNTAX GenEquipInterfacesNGPWCardStatusEntry
        ACCESS not-accessible
        STATUS mandatory
		DESCRIPTION
        "This table contains information about PW-LIC card level status."
        INDEX { genEquipInterfacesNGPWCardStatusSlotID }
        ::= { genEquipInterfacesNGPWCardStatusTable 1 }

GenEquipInterfacesNGPWCardStatusEntry ::=
		SEQUENCE {
			genEquipInterfacesNGPWCardStatusSlotID
				INTEGER,
			genEquipInterfacesNGPWCardStatusSWVersion
            	DisplayString
}

genEquipInterfacesNGPWCardStatusSlotID		OBJECT-TYPE
		SYNTAX 		INTEGER (2..12)
		ACCESS		read-only
        STATUS		mandatory
        DESCRIPTION
		"Slot where PW-LIC is inserted."
::= { genEquipInterfacesNGPWCardStatusEntry 1 }

genEquipInterfacesNGPWCardStatusSWVersion		OBJECT-TYPE
		SYNTAX 		DisplayString
		ACCESS		read-only
        STATUS		mandatory
        DESCRIPTION
		"Bundle ID."
::= { genEquipInterfacesNGPWCardStatusEntry 2 }


-- STM-1/OC-3 RST Protection

genEquipInterfacesStm1RstGroupMembersTable  OBJECT-TYPE
        SYNTAX  SEQUENCE OF GenEquipInterfacesStm1RstGroupMembersEntry
        ACCESS  not-accessible
        STATUS mandatory
        DESCRIPTION
        "This table contains the STM-1/OC-3 RST groups members."
        ::= { genEquipInterfacesStm1Rst 4 }

genEquipInterfacesStm1RstGroupMembersEntry OBJECT-TYPE
        SYNTAX GenEquipInterfacesStm1RstGroupMembersEntry
        ACCESS  not-accessible
        STATUS mandatory
        DESCRIPTION
        "This table entry contains the STM-1/OC-3 RST groups members."
        INDEX { genEquipInterfacesStm1RstGroupMembersGroupIfindex }
        ::= { genEquipInterfacesStm1RstGroupMembersTable 1 }

GenEquipInterfacesStm1RstGroupMembersEntry ::=
    SEQUENCE {
		genEquipInterfacesStm1RstGroupMembersGroupIfindex
			INTEGER,
		genEquipInterfacesStm1RstGroupMembersGroupId
			INTEGER,
		genEquipInterfacesStm1RstGroupMembersMem1Ifindex
			INTEGER,
	    genEquipInterfacesStm1RstGroupMembersMem2Ifindex
			INTEGER,
		genEquipInterfacesStm1RstGroupMembersActiveIfindex
			INTEGER,
		genEquipInterfacesStm1RstGroupMembersProtectionCommand
			INTEGER,
		genEquipInterfacesStm1RstGroupMembersStatusLockout
			NoYes,
	    genEquipInterfacesStm1RstGroupMembersRowStatus
			RowStatus
	}

genEquipInterfacesStm1RstGroupMembersGroupIfindex OBJECT-TYPE
        SYNTAX  INTEGER
        ACCESS  read-only
        STATUS 	mandatory
        DESCRIPTION
        "The location of the STM-1/OC-3 RST group."
        ::= { genEquipInterfacesStm1RstGroupMembersEntry 1 }

genEquipInterfacesStm1RstGroupMembersGroupId  OBJECT-TYPE
    SYNTAX 	INTEGER (1..4)
    ACCESS  read-only
    STATUS mandatory
    DESCRIPTION
    "The Id of the STM-1/OC-3 RST protection group."
    ::= { genEquipInterfacesStm1RstGroupMembersEntry 2 }

genEquipInterfacesStm1RstGroupMembersMem1Ifindex  OBJECT-TYPE
        SYNTAX 	INTEGER (1..4)
        ACCESS  read-write
        STATUS mandatory
        DESCRIPTION
        "The STM location of member 1."
        ::= { genEquipInterfacesStm1RstGroupMembersEntry 3 }

genEquipInterfacesStm1RstGroupMembersMem2Ifindex  OBJECT-TYPE
        SYNTAX  INTEGER
        ACCESS  read-write
        STATUS mandatory
        DESCRIPTION
        "The STM location of member 2."
        ::= { genEquipInterfacesStm1RstGroupMembersEntry 4 }

genEquipInterfacesStm1RstGroupMembersActiveIfindex OBJECT-TYPE
        SYNTAX  INTEGER
        ACCESS  read-only
        STATUS 	mandatory
        DESCRIPTION
        "The active stm1 location"
        ::= { genEquipInterfacesStm1RstGroupMembersEntry 5 }

genEquipInterfacesStm1RstGroupMembersProtectionCommand  OBJECT-TYPE
        SYNTAX INTEGER {
				clear(0),
				manual-switch(1),
				force-switch(2),
				lockout(3)
		}
        ACCESS  read-write
        STATUS mandatory
        DESCRIPTION
        "STM-1/OC-3 RST protection user commands for maintenance purposes: force-switch, lockout and manual-switch."
        ::= { genEquipInterfacesStm1RstGroupMembersEntry 6 }

genEquipInterfacesStm1RstGroupMembersStatusLockout  OBJECT-TYPE
		SYNTAX  NoYes
    	ACCESS  read-only
    	STATUS mandatory
    	DESCRIPTION
		"The stm1 location of member 1."
		::= { genEquipInterfacesStm1RstGroupMembersEntry 7 }

genEquipInterfacesStm1RstGroupMembersRowStatus  OBJECT-TYPE
        SYNTAX  RowStatus
        ACCESS  read-write
        STATUS mandatory
        DESCRIPTION
        "Row status to allow user add entries dynamically."
        ::= { genEquipInterfacesStm1RstGroupMembersEntry 30 }


-- Switch Application Branch
genEquipInterfacesCet	OBJECT IDENTIFIER ::= {genEquipInterfaces 8}

genEquipInterfacesCetGeneral	OBJECT IDENTIFIER ::= {genEquipInterfacesCet 1}

genEquipInterfacesCetMru		OBJECT-TYPE
		SYNTAX 		INTEGER (64..9612)
		ACCESS		read-write
        STATUS		mandatory
        DESCRIPTION
		"Maximum Frame Size."
::= { genEquipInterfacesCetGeneral 1 }

--
-- Switch Application if-physical-configuration-table
--

genEquipInterfacesCetPhyConfigTable  OBJECT-TYPE
        SYNTAX  SEQUENCE OF GenEquipInterfacesCetPhyConfigEntry
        ACCESS  not-accessible
        STATUS mandatory
        DESCRIPTION
        "Ethernet physical port configuration table."
        ::= { genEquipInterfacesCet 2 }

genEquipInterfacesCetPhyConfigEntry OBJECT-TYPE
        SYNTAX GenEquipInterfacesCetPhyConfigEntry
        ACCESS not-accessible
        STATUS mandatory
          DESCRIPTION
          "Ethernet physical port configuration table entry."
        INDEX { genEquipInterfacesCetPhyConfigIfIndex }
        ::= { genEquipInterfacesCetPhyConfigTable 1 }

GenEquipInterfacesCetPhyConfigEntry ::=
		SEQUENCE {
			genEquipInterfacesCetPhyConfigIfIndex
				INTEGER,
			genEquipInterfacesCetPhyConfigDescription
				DisplayString,
			genEquipInterfacesCetPhyConfigMediaType
				MediaType,
			genEquipInterfacesCetPhyConfigAdmin
				EnableDisable,
			genEquipInterfacesCetPhyConfigAutoNegotiation
				AutoNegMode,
			genEquipInterfacesCetPhyConfigSpeed
				SpeedDefs,
			genEquipInterfacesCetPhyConfigDuplex
				HalfFull,
			genEquipInterfacesCetPhyConfigMasterSlave
				MasterSalveSetMode,
--			genEquipInterfacesCetPhyConfigFlowControl
--				FlowControl,
			genEquipInterfacesCetPhyConfigIfg
				INTEGER,
			genEquipInterfacesCetPhyConfigPreamble
				INTEGER,
			genEquipInterfacesCetPhyConfigMacAddress
				OCTET STRING,
			genEquipInterfacesCetPhyConfigType
				PortType,
			genEquipInterfacesCetPhyConfigPortPmAdmin
				EnableDisable,
			genEquipInterfacesCetPhyConfigPortPmRxBytesThreshold
				INTEGER,
			genEquipInterfacesCetPhyConfigPortPmTxBytesThreshold
				INTEGER
}


genEquipInterfacesCetPhyConfigIfIndex		OBJECT-TYPE
		SYNTAX 		INTEGER
		ACCESS		read-only
        STATUS		mandatory
        DESCRIPTION
		"Ethernet physical port if-index table key."
::= { genEquipInterfacesCetPhyConfigEntry 1 }

genEquipInterfacesCetPhyConfigDescription		OBJECT-TYPE
		SYNTAX 		DisplayString
		ACCESS		read-write
        STATUS		mandatory
        DESCRIPTION
		"Setting Ethernet physical port user description."
::= { genEquipInterfacesCetPhyConfigEntry 2 }

genEquipInterfacesCetPhyConfigMediaType		OBJECT-TYPE
		SYNTAX 		MediaType
		ACCESS		read-write
        STATUS		mandatory
        DESCRIPTION
		"Setting Ethernet physical port media type."
::= { genEquipInterfacesCetPhyConfigEntry 3 }

genEquipInterfacesCetPhyConfigAdmin		OBJECT-TYPE
		SYNTAX 		EnableDisable
		ACCESS		read-write
        STATUS		mandatory
        DESCRIPTION
		"Setting Ethernet physical port administration."
::= { genEquipInterfacesCetPhyConfigEntry 4 }

genEquipInterfacesCetPhyConfigAutoNegotiation		OBJECT-TYPE
		SYNTAX 		AutoNegMode
		ACCESS		read-write
        STATUS		mandatory
        DESCRIPTION
		"Setting Ethernet physical port auto negotiation state."
::= { genEquipInterfacesCetPhyConfigEntry 5 }

genEquipInterfacesCetPhyConfigSpeed		OBJECT-TYPE
		SYNTAX 		SpeedDefs
		ACCESS		read-write
        STATUS		mandatory
        DESCRIPTION
		"Setting Ethernet physical maximum port speed Affects Auto Neg Capability Advertised Bits."
::= { genEquipInterfacesCetPhyConfigEntry 6 }

genEquipInterfacesCetPhyConfigDuplex		OBJECT-TYPE
		SYNTAX 		HalfFull
		ACCESS		read-write
        STATUS		mandatory
        DESCRIPTION
		"Setting Ethernet physical port duplex Affects Auto Neg Capability Advertised Bits."
::= { genEquipInterfacesCetPhyConfigEntry 7 }

genEquipInterfacesCetPhyConfigMasterSlave		OBJECT-TYPE
		SYNTAX 		MasterSalveSetMode
		ACCESS		read-write
        STATUS		mandatory
        DESCRIPTION
		"Setting Ethernet physical port master slave for 1000BaseT Affects Auto Neg
		Capability Advertised Bits."
::= { genEquipInterfacesCetPhyConfigEntry 8 }

--genEquipInterfacesCetPhyConfigFlowControl		OBJECT-TYPE
--		SYNTAX 		FlowControl
--		ACCESS		read-write
--      STATUS		mandatory
--      DESCRIPTION
--		"Setting Ethernet physical port flow-control Affects Auto Neg Capability Advertised Bits"
--::= { genEquipInterfacesCetPhyConfigEntry 9 }

genEquipInterfacesCetPhyConfigIfg		OBJECT-TYPE
		SYNTAX 		INTEGER (6..15)
		ACCESS		read-write
        STATUS		mandatory
        DESCRIPTION
		"Inter Frame GAP value in bytes."
::= { genEquipInterfacesCetPhyConfigEntry 10 }

genEquipInterfacesCetPhyConfigPreamble		OBJECT-TYPE
		SYNTAX 		INTEGER (6..15)
		ACCESS		read-write
        STATUS		mandatory
        DESCRIPTION
		"port preamble value in bytes."
::= { genEquipInterfacesCetPhyConfigEntry 11 }

genEquipInterfacesCetPhyConfigMacAddress		OBJECT-TYPE
		SYNTAX 		OCTET STRING
		ACCESS		read-write
        STATUS		mandatory
        DESCRIPTION
		"Ethernet physical port mac-address."
::= { genEquipInterfacesCetPhyConfigEntry 12 }

genEquipInterfacesCetPhyConfigType		OBJECT-TYPE
		SYNTAX 		PortType
		ACCESS		read-write
        STATUS		mandatory
        DESCRIPTION
		"Setting Ethernet physical port type."
::= { genEquipInterfacesCetPhyConfigEntry 13 }

genEquipInterfacesCetPhyConfigPortPmAdmin		OBJECT-TYPE
		SYNTAX 		EnableDisable
		ACCESS		read-write
        STATUS		mandatory
        DESCRIPTION
		"Enable/Disable PMs on port level."
::= { genEquipInterfacesCetPhyConfigEntry 14 }

genEquipInterfacesCetPhyConfigPortPmRxBytesThreshold		OBJECT-TYPE
		SYNTAX 		INTEGER
		ACCESS		read-write
        STATUS		mandatory
        DESCRIPTION
		"Threshold of received bytes PM."
::= { genEquipInterfacesCetPhyConfigEntry 15 }

genEquipInterfacesCetPhyConfigPortPmTxBytesThreshold		OBJECT-TYPE
		SYNTAX 		EnableDisable
		ACCESS		read-write
        STATUS		mandatory
        DESCRIPTION
		"Threshold of transmitted bytes PM."
::= { genEquipInterfacesCetPhyConfigEntry 16 }


--
-- Interfaces Switch Application Physical Port Status Table
-- if-physical-status-table
--

genEquipInterfacesCetPhyStatusTable  OBJECT-TYPE
        SYNTAX  SEQUENCE OF GenEquipInterfacesCetPhyStatusEntry
        ACCESS  not-accessible
        STATUS mandatory
        DESCRIPTION
        "Ethernet physical port configuration table."
        ::= { genEquipInterfacesCet 3 }

genEquipInterfacesCetPhyStatusEntry OBJECT-TYPE
        SYNTAX GenEquipInterfacesCetPhyStatusEntry
        ACCESS not-accessible
        STATUS mandatory
          DESCRIPTION
          "This table allows configuration of the 16 internal E1/DS1 ports."
        INDEX { genEquipInterfacesCetPhyStatusIfIndex }
        ::= { genEquipInterfacesCetPhyStatusTable 1 }

GenEquipInterfacesCetPhyStatusEntry ::=
		SEQUENCE {
			genEquipInterfacesCetPhyStatusIfIndex
				INTEGER,
			genEquipInterfacesCetPhyStatusMediaType
				MediaType,
			genEquipInterfacesCetPhyStatusOperationalStatus
				DownUp,
			genEquipInterfacesCetPhystatusAutoNegotiation
				AutoNegMode,
			genEquipInterfacesCetPhyStatusSpeed
				SpeedDefs,
			genEquipInterfacesCetPhyStatusDuplex
				HalfFull,
			genEquipInterfacesCetPhyStatusMasterSlave
				MasterSalveSetMode
}


genEquipInterfacesCetPhyStatusIfIndex		OBJECT-TYPE
		SYNTAX 		INTEGER
		ACCESS		read-only
        STATUS		mandatory
        DESCRIPTION
		"Ethernet physical port if-index table key."
::= { genEquipInterfacesCetPhyStatusEntry 1 }

genEquipInterfacesCetPhyStatusMediaType		OBJECT-TYPE
		SYNTAX 		MediaType
		ACCESS		read-only
        STATUS		mandatory
        DESCRIPTION
		"Setting Ethernet physical port media type."
::= { genEquipInterfacesCetPhyStatusEntry 2 }

genEquipInterfacesCetPhyStatusOperationalStatus		OBJECT-TYPE
		SYNTAX 		DownUp
		ACCESS		read-only
        STATUS		mandatory
        DESCRIPTION
		"Ethernet physical port operational-status."
::= { genEquipInterfacesCetPhyStatusEntry 3 }

genEquipInterfacesCetPhystatusAutoNegotiation		OBJECT-TYPE
		SYNTAX 		AutoNegMode
		ACCESS		read-only
        STATUS		mandatory
        DESCRIPTION
		"Ethernet physical port auto negotiation status."
::= { genEquipInterfacesCetPhyStatusEntry 4 }

genEquipInterfacesCetPhyStatusSpeed		OBJECT-TYPE
		SYNTAX 		SpeedDefs
		ACCESS		read-only
        STATUS		mandatory
        DESCRIPTION
		"Actual Ethernet physical port speed."
::= { genEquipInterfacesCetPhyStatusEntry 5 }

genEquipInterfacesCetPhyStatusDuplex		OBJECT-TYPE
		SYNTAX 		HalfFull
		ACCESS		read-only
        STATUS		mandatory
        DESCRIPTION
		"Actual Ethernet physical port duplex."
::= { genEquipInterfacesCetPhyStatusEntry 6 }

genEquipInterfacesCetPhyStatusMasterSlave		OBJECT-TYPE
		SYNTAX 		MasterSalveSetMode
		ACCESS		read-only
        STATUS		mandatory
        DESCRIPTION
		"Actual Ethernet physical port master slave for 1000BaseT."
::= { genEquipInterfacesCetPhyStatusEntry 7 }

--
-- Switch Application if-logical-configuration-table
--

genEquipInterfacesCetLogicConfigTable  OBJECT-TYPE
        SYNTAX  SEQUENCE OF GenEquipInterfacesCetLogicConfigEntry
        ACCESS  not-accessible
        STATUS mandatory
        DESCRIPTION
        "The table holds the ingress logical port configuration (it is the same point of view for
		single interface or group of ports) ."
        ::= { genEquipInterfacesCet 4 }

genEquipInterfacesCetLogicConfigEntry OBJECT-TYPE
        SYNTAX GenEquipInterfacesCetLogicConfigEntry
        ACCESS not-accessible
        STATUS mandatory
          DESCRIPTION
          "The table entry holds the ingress logical port configuration (it is the same point of
		  view for single interface or group of ports)."
        INDEX { genEquipInterfacesCetLogicConfigIfIndex }
        ::= { genEquipInterfacesCetLogicConfigTable 1 }

GenEquipInterfacesCetLogicConfigEntry ::=
		SEQUENCE {
			genEquipInterfacesCetLogicConfigIfIndex
				INTEGER,
			genEquipInterfacesCetLogicConfigTrafficFlow
				EnableDisable,
			genEquipInterfacesCetLogicConfigEdgePort
				EdgePortType,
			genEquipInterfacesCetLogicConfigIngressTcamClassification
				INTEGER,
			genEquipInterfacesCetLogicConfigDefaultVlanTag
				INTEGER,
			genEquipInterfacesCetLogicConfigInLineCompensation
				INTEGER,
			genEquipInterfacesCetLogicConfigOutLineCompensation
				INTEGER,
			genEquipInterfacesCetLogicConfigPclId
				INTEGER,
			genEquipInterfacesCetLogicConfigDefCos
				INTEGER,
			genEquipInterfacesCetLogicConfigVlanUpToCosTrustMode
				TrustMode,
			genEquipInterfacesCetLogicConfigDscpToCosTrustMode
				TrustMode,
			genEquipInterfacesCetLogicConfigMplsExpToCosTrustMode
				TrustMode,
			genEquipInterfacesCetLogicConfigMacAddress
				OCTET STRING,
			genEquipInterfacesCetLogicConfigLoopbackSwapMacAddressAdmin
				EnableDisable,
			genEquipInterfacesCetLogicConfigLoopbackAdmin
				EnableDisable,
			genEquipInterfacesCetLogicConfigLoopbackDuration
				INTEGER,
			genEquipInterfacesCetLogicConfigInterfaceMode
				INTEGER
}


genEquipInterfacesCetLogicConfigIfIndex		OBJECT-TYPE
		SYNTAX 		INTEGER
		ACCESS		read-only
        STATUS		mandatory
        DESCRIPTION
		"Ethernet Logical port if-index table key."
::= { genEquipInterfacesCetLogicConfigEntry 1 }

genEquipInterfacesCetLogicConfigTrafficFlow		OBJECT-TYPE
		SYNTAX 		EnableDisable
		ACCESS		read-write
        STATUS		mandatory
        DESCRIPTION
		"Control the the traffic via logical port which is connected to physical interface
		(in case of group it control the all interfaces of the group)."
::= { genEquipInterfacesCetLogicConfigEntry 2 }

genEquipInterfacesCetLogicConfigEdgePort		OBJECT-TYPE
		SYNTAX 		EdgePortType
		ACCESS		read-write
        STATUS		mandatory
        DESCRIPTION
		"Port Edge Mode (edge / non-edge)."
::= { genEquipInterfacesCetLogicConfigEntry 3 }

genEquipInterfacesCetLogicConfigIngressTcamClassification		OBJECT-TYPE
		SYNTAX 		INTEGER
		ACCESS		read-only
        STATUS		mandatory
        DESCRIPTION
		"ingress-tcam-classification."
::= { genEquipInterfacesCetLogicConfigEntry 4 }

genEquipInterfacesCetLogicConfigDefaultVlanTag		OBJECT-TYPE
		SYNTAX 		INTEGER
		ACCESS		read-write
        STATUS		mandatory
        DESCRIPTION
		"Default Network Vlan ID."
::= { genEquipInterfacesCetLogicConfigEntry 5 }

genEquipInterfacesCetLogicConfigInLineCompensation		OBJECT-TYPE
		SYNTAX 		INTEGER (0..32)
		ACCESS		read-write
        STATUS		mandatory
        DESCRIPTION
		"Ethernet Layer 1 Ingress Byte Compensation."
::= { genEquipInterfacesCetLogicConfigEntry 6 }

genEquipInterfacesCetLogicConfigOutLineCompensation		OBJECT-TYPE
		SYNTAX 		INTEGER (0..26)
		ACCESS		read-write
        STATUS		mandatory
        DESCRIPTION
		"Ethernet Layer 1 Egress Byte Compensation from the specific logical port."
::= { genEquipInterfacesCetLogicConfigEntry 7 }

genEquipInterfacesCetLogicConfigPclId		OBJECT-TYPE
		SYNTAX 		INTEGER
		ACCESS		read-only
        STATUS		mandatory
        DESCRIPTION
		"...."
::= { genEquipInterfacesCetLogicConfigEntry 8 }

genEquipInterfacesCetLogicConfigDefCos		OBJECT-TYPE
		SYNTAX 		INTEGER (0..7)
		ACCESS		read-write
        STATUS		mandatory
        DESCRIPTION
		"Port Default CoS."
::= { genEquipInterfacesCetLogicConfigEntry 9 }

genEquipInterfacesCetLogicConfigVlanUpToCosTrustMode		OBJECT-TYPE
		SYNTAX 		TrustMode
		ACCESS		read-write
        STATUS		mandatory
        DESCRIPTION
		"Trust VLAN UP bits for classification from the specific logical port."
::= { genEquipInterfacesCetLogicConfigEntry 10 }

genEquipInterfacesCetLogicConfigDscpToCosTrustMode		OBJECT-TYPE
		SYNTAX 		TrustMode
		ACCESS		read-write
        STATUS		mandatory
        DESCRIPTION
		"Trust DSCP for classification from the specific logical port."
::= { genEquipInterfacesCetLogicConfigEntry 11 }

genEquipInterfacesCetLogicConfigMplsExpToCosTrustMode		OBJECT-TYPE
		SYNTAX 		TrustMode
		ACCESS		read-write
        STATUS		mandatory
        DESCRIPTION
		"Trust MPLS EXP bits for classification from the specific logical port."
::= { genEquipInterfacesCetLogicConfigEntry 12 }

genEquipInterfacesCetLogicConfigMacAddress		OBJECT-TYPE
		SYNTAX 		OCTET STRING
		ACCESS		read-only
        STATUS		mandatory
        DESCRIPTION
		"Ethernet logical port mac-address."
::= { genEquipInterfacesCetLogicConfigEntry 13 }

genEquipInterfacesCetLogicConfigLoopbackSwapMacAddressAdmin		OBJECT-TYPE
		SYNTAX 		EnableDisable
		ACCESS		read-write
        STATUS		mandatory
        DESCRIPTION
		"Swap MAC address for Ethernet port loopback."
::= { genEquipInterfacesCetLogicConfigEntry 14 }

genEquipInterfacesCetLogicConfigLoopbackAdmin		OBJECT-TYPE
		SYNTAX 		EnableDisable
		ACCESS		read-write
        STATUS		mandatory
        DESCRIPTION
		"Ethernet loopback admin."
::= { genEquipInterfacesCetLogicConfigEntry 15 }

genEquipInterfacesCetLogicConfigLoopbackDuration		OBJECT-TYPE
		SYNTAX 		INTEGER
		ACCESS		read-write
        STATUS		mandatory
        DESCRIPTION
		"Ethernet loopback duration. Allowed values 1 to 9000 seconds."
::= { genEquipInterfacesCetLogicConfigEntry 16 }

genEquipInterfacesCetLogicConfigInterfaceMode		OBJECT-TYPE
		SYNTAX 		INTEGER {
						none (0),
						lacp (1)
					}
		ACCESS		read-write
        STATUS		mandatory
        DESCRIPTION
		"Interface Mode for line protection."
::= { genEquipInterfacesCetLogicConfigEntry 17 }

--
-- Switch Application if-logical-mgr
--

genEquipInterfacesCetLogicStatusTable  OBJECT-TYPE
        SYNTAX  SEQUENCE OF GenEquipInterfacesCetLogicStatusEntry
        ACCESS  not-accessible
        STATUS mandatory
        DESCRIPTION
        "The table holds the ingress logical port status
		(it is the same point of view for single interface or group of ports)."
        ::= { genEquipInterfacesCet 5 }

genEquipInterfacesCetLogicStatusEntry OBJECT-TYPE
        SYNTAX GenEquipInterfacesCetLogicStatusEntry
        ACCESS not-accessible
        STATUS mandatory
          DESCRIPTION
        "The table entry holds the ingress logical port status
		(it is the same point of view for single interface or group of ports)."
        INDEX { genEquipInterfacesCetLogicStatusIfIndex }
        ::= { genEquipInterfacesCetLogicStatusTable 1 }

GenEquipInterfacesCetLogicStatusEntry ::=
		SEQUENCE {
			genEquipInterfacesCetLogicStatusIfIndex
				INTEGER,
			genEquipInterfacesCetLogicStatusOperationalStatus
				DownUp
}


genEquipInterfacesCetLogicStatusIfIndex		OBJECT-TYPE
		SYNTAX 		INTEGER
		ACCESS		read-only
        STATUS		mandatory
        DESCRIPTION
		"Ethernet Logical port if-index table key."
::= { genEquipInterfacesCetLogicStatusEntry 1 }

genEquipInterfacesCetLogicStatusOperationalStatus		OBJECT-TYPE
		SYNTAX 		DownUp
		ACCESS		read-only
        STATUS		mandatory
        DESCRIPTION
		"Ethernet logical port operational-status (Up or Down)."
::= { genEquipInterfacesCetLogicStatusEntry 2 }


--
-- Switch Application if-logical-broadcast_policing-table
--

genEquipInterfacesCetBcastPolicerAssociationTable  OBJECT-TYPE
        SYNTAX  SEQUENCE OF GenEquipInterfacesCetBcastPolicerAssociationEntry
        ACCESS  not-accessible
        STATUS mandatory
        DESCRIPTION
        "Ethernet Port Broadcast configuration table."
        ::= { genEquipInterfacesCet 6 }

genEquipInterfacesCetBcastPolicerAssociationEntry OBJECT-TYPE
        SYNTAX GenEquipInterfacesCetBcastPolicerAssociationEntry
        ACCESS not-accessible
        STATUS mandatory
          DESCRIPTION
        "Ethernet Port Broadcast configuration table entry."
        INDEX { genEquipInterfacesCetBcastPolicerAssociationIfIndex }
        ::= { genEquipInterfacesCetBcastPolicerAssociationTable 1 }

GenEquipInterfacesCetBcastPolicerAssociationEntry ::=
		SEQUENCE {
			genEquipInterfacesCetBcastPolicerAssociationIfIndex
				INTEGER,
			genEquipInterfacesCetBcastPolicerAssociationAssociatedProfileId
				INTEGER,
			genEquipInterfacesCetBcastPolicerAssociationAssociationAdmin
				EnableDisable,
			genEquipInterfacesCetBcastPolicerAssociationAssociationRowStatus
				RowStatus
}


genEquipInterfacesCetBcastPolicerAssociationIfIndex		OBJECT-TYPE
		SYNTAX 		INTEGER
		ACCESS		read-only
        STATUS		mandatory
        DESCRIPTION
		"Ethernet Logical port if-index table key."
::= { genEquipInterfacesCetBcastPolicerAssociationEntry 1 }

genEquipInterfacesCetBcastPolicerAssociationAssociatedProfileId		OBJECT-TYPE
		SYNTAX 		INTEGER
		ACCESS		read-write
        STATUS		mandatory
        DESCRIPTION
		"Policer Profile."
::= { genEquipInterfacesCetBcastPolicerAssociationEntry 2 }

genEquipInterfacesCetBcastPolicerAssociationAssociationAdmin		OBJECT-TYPE
		SYNTAX 		EnableDisable
		ACCESS		read-write
        STATUS		mandatory
        DESCRIPTION
		"Broadcast Policer Admin (enable / disable)."
::= { genEquipInterfacesCetBcastPolicerAssociationEntry 3 }

genEquipInterfacesCetBcastPolicerAssociationAssociationRowStatus		OBJECT-TYPE
		SYNTAX 		RowStatus
		ACCESS		read-write
        STATUS		mandatory
        DESCRIPTION
		"Table Mib Row Status."
::= { genEquipInterfacesCetBcastPolicerAssociationEntry 30 }



--
-- Switch Application if-logical-ethertype1_policing-table
--

genEquipInterfacesCetEtype1PolicerAssociationTable  OBJECT-TYPE
        SYNTAX  SEQUENCE OF GenEquipInterfacesCetEtype1PolicerAssociationEntry
        ACCESS  not-accessible
        STATUS mandatory
        DESCRIPTION
        "Ethernet Policing of user configuration ethertype type 1 (at port level) table."
        ::= { genEquipInterfacesCet 7 }

genEquipInterfacesCetEtype1PolicerAssociationEntry OBJECT-TYPE
        SYNTAX GenEquipInterfacesCetEtype1PolicerAssociationEntry
        ACCESS not-accessible
        STATUS mandatory
          DESCRIPTION
        "Ethernet Policing of user configuration ethertype type 1 (at port level) table entry."
        INDEX { genEquipInterfacesCetEtype1PolicerAssociationIfIndex }
        ::= { genEquipInterfacesCetEtype1PolicerAssociationTable 1 }

GenEquipInterfacesCetEtype1PolicerAssociationEntry ::=
		SEQUENCE {
			genEquipInterfacesCetEtype1PolicerAssociationIfIndex
				INTEGER,
			genEquipInterfacesCetEtype1PolicerAssociationProfileId
				INTEGER,
			genEquipInterfacesCetEtype1PolicerAssociationEthertype
				INTEGER,
			genEquipInterfacesCetEtype1PolicerAssociationAdmin
				EnableDisable,
			genEquipInterfacesCetEtype1PolicerAssociationRowStatus
				RowStatus
}


genEquipInterfacesCetEtype1PolicerAssociationIfIndex		OBJECT-TYPE
		SYNTAX 		INTEGER
		ACCESS		read-only
        STATUS		mandatory
        DESCRIPTION
		"Ethernet Logical port if-index table key."
::= { genEquipInterfacesCetEtype1PolicerAssociationEntry 1 }

genEquipInterfacesCetEtype1PolicerAssociationProfileId		OBJECT-TYPE
		SYNTAX 		INTEGER (1..256)
		ACCESS		read-write
        STATUS		mandatory
        DESCRIPTION
		"Ingress Policer Profile ID."
::= { genEquipInterfacesCetEtype1PolicerAssociationEntry 2 }

genEquipInterfacesCetEtype1PolicerAssociationEthertype		OBJECT-TYPE
		SYNTAX 		INTEGER (0..65535)
		ACCESS		read-write
        STATUS		mandatory
        DESCRIPTION
		"Ethernet Ethertype 1 user configuration value."
::= { genEquipInterfacesCetEtype1PolicerAssociationEntry 3 }

genEquipInterfacesCetEtype1PolicerAssociationAdmin		OBJECT-TYPE
		SYNTAX 		EnableDisable
		ACCESS		read-write
        STATUS		mandatory
        DESCRIPTION
		"Ingress Ethertype 1 Policer Admin (enable / disable)."
::= { genEquipInterfacesCetEtype1PolicerAssociationEntry 4 }

genEquipInterfacesCetEtype1PolicerAssociationRowStatus		OBJECT-TYPE
		SYNTAX 		RowStatus
		ACCESS		read-write
        STATUS		mandatory
        DESCRIPTION
		"Table Mib Row Status."
::= { genEquipInterfacesCetEtype1PolicerAssociationEntry 30 }


--
-- Switch Application if-logical-ethertype2_policing-table
--

genEquipInterfacesCetEtype2PolicerAssociationTable  OBJECT-TYPE
        SYNTAX  SEQUENCE OF GenEquipInterfacesCetEtype2PolicerAssociationEntry
        ACCESS  not-accessible
        STATUS mandatory
        DESCRIPTION
        "Ethernet Policing of user configuration ethertype type 2 (at port level) table."
        ::= { genEquipInterfacesCet 8 }

genEquipInterfacesCetEtype2PolicerAssociationEntry OBJECT-TYPE
        SYNTAX GenEquipInterfacesCetEtype2PolicerAssociationEntry
        ACCESS not-accessible
        STATUS mandatory
          DESCRIPTION
        "Ethernet Policing of user configuration ethertype type 2 (at port level) table."
        INDEX { genEquipInterfacesCetEtype2PolicerAssociationIfIndex }
        ::= { genEquipInterfacesCetEtype2PolicerAssociationTable 1 }

GenEquipInterfacesCetEtype2PolicerAssociationEntry ::=
		SEQUENCE {
			genEquipInterfacesCetEtype2PolicerAssociationIfIndex
				INTEGER,
			genEquipInterfacesCetEtype2PolicerAssociationAssociatedProfileId
				INTEGER,
			genEquipInterfacesCetEtype2PolicerAssociationEthertype
				INTEGER,
			genEquipInterfacesCetEtype2PolicerAssociationAdmin
				EnableDisable,
			genEquipInterfacesCetEtype2PolicerAssociationRowStatus
				RowStatus
}


genEquipInterfacesCetEtype2PolicerAssociationIfIndex		OBJECT-TYPE
		SYNTAX 		INTEGER
		ACCESS		read-only
        STATUS		mandatory
        DESCRIPTION
		"Ethernet Logical port if-index table key."
::= { genEquipInterfacesCetEtype2PolicerAssociationEntry 1 }

genEquipInterfacesCetEtype2PolicerAssociationAssociatedProfileId		OBJECT-TYPE
		SYNTAX 		INTEGER (1..256)
		ACCESS		read-write
        STATUS		mandatory
        DESCRIPTION
		"Ingress Policer Profile ID."
::= { genEquipInterfacesCetEtype2PolicerAssociationEntry 2 }

genEquipInterfacesCetEtype2PolicerAssociationEthertype		OBJECT-TYPE
		SYNTAX 		INTEGER (0..65535)
		ACCESS		read-write
        STATUS		mandatory
        DESCRIPTION
		"Ethernet Ethertype 2 user configuration value."
::= { genEquipInterfacesCetEtype2PolicerAssociationEntry 3 }

genEquipInterfacesCetEtype2PolicerAssociationAdmin		OBJECT-TYPE
		SYNTAX 		EnableDisable
		ACCESS		read-write
        STATUS		mandatory
        DESCRIPTION
		"Ingress Ethertype 2 Policer Admin (enable / disable)."
::= { genEquipInterfacesCetEtype2PolicerAssociationEntry 4 }

genEquipInterfacesCetEtype2PolicerAssociationRowStatus		OBJECT-TYPE
		SYNTAX 		RowStatus
		ACCESS		read-write
        STATUS		mandatory
        DESCRIPTION
		"Table Mib Row Status."
::= { genEquipInterfacesCetEtype2PolicerAssociationEntry 30 }



--
-- Switch Application if-logical-ethertype3_policing-table
--

genEquipInterfacesCetEtype3PolicerAssociationTable  OBJECT-TYPE
        SYNTAX  SEQUENCE OF GenEquipInterfacesCetEtype3PolicerAssociationEntry
        ACCESS  not-accessible
        STATUS mandatory
        DESCRIPTION
        "Ethernet Policing of user configuration ethertype type 3 (at port level) table."
        ::= { genEquipInterfacesCet 9 }

genEquipInterfacesCetEtype3PolicerAssociationEntry OBJECT-TYPE
        SYNTAX GenEquipInterfacesCetEtype3PolicerAssociationEntry
        ACCESS not-accessible
        STATUS mandatory
          DESCRIPTION
        "Ethernet Policing of user configuration ethertype type 3 (at port level) table entry."
        INDEX { genEquipInterfacesCetEtype3PolicerAssociationIfIndex }
        ::= { genEquipInterfacesCetEtype3PolicerAssociationTable 1 }

GenEquipInterfacesCetEtype3PolicerAssociationEntry ::=
		SEQUENCE {
			genEquipInterfacesCetEtype3PolicerAssociationIfIndex
				INTEGER,
			genEquipInterfacesCetEtype3PolicerAssociationAssociatedProfileId
				INTEGER,
			genEquipInterfacesCetEtype3PolicerAssociationEthertype
				INTEGER,
			genEquipInterfacesCetEtype3PolicerAssociationAdmin
				EnableDisable,
			genEquipInterfacesCetEtype3PolicerAssociationRowStatus
				RowStatus
}


genEquipInterfacesCetEtype3PolicerAssociationIfIndex		OBJECT-TYPE
		SYNTAX 		INTEGER
		ACCESS		read-only
        STATUS		mandatory
        DESCRIPTION
		"Ethernet Logical port if-index table key."
::= { genEquipInterfacesCetEtype3PolicerAssociationEntry 1 }

genEquipInterfacesCetEtype3PolicerAssociationAssociatedProfileId		OBJECT-TYPE
		SYNTAX 		INTEGER (1..256)
		ACCESS		read-write
        STATUS		mandatory
        DESCRIPTION
		"Ingress Policer Profile ID."
::= { genEquipInterfacesCetEtype3PolicerAssociationEntry 2 }

genEquipInterfacesCetEtype3PolicerAssociationEthertype		OBJECT-TYPE
		SYNTAX 		INTEGER (0..65535)
		ACCESS		read-write
        STATUS		mandatory
        DESCRIPTION
		"Ethernet Ethertype 3 user configuration value."
::= { genEquipInterfacesCetEtype3PolicerAssociationEntry 3 }

genEquipInterfacesCetEtype3PolicerAssociationAdmin		OBJECT-TYPE
		SYNTAX 		EnableDisable
		ACCESS		read-write
        STATUS		mandatory
        DESCRIPTION
		"Ingress Ethertype 3 Policer Admin (enable / disable)."
::= { genEquipInterfacesCetEtype3PolicerAssociationEntry 4 }

genEquipInterfacesCetEtype3PolicerAssociationRowStatus		OBJECT-TYPE
		SYNTAX 		RowStatus
		ACCESS		read-write
        STATUS		mandatory
        DESCRIPTION
		"Table Mib Row Status."
::= { genEquipInterfacesCetEtype3PolicerAssociationEntry 30 }


--
-- Switch Application if-logical-multicast_policing-table
--

genEquipInterfacesCetMcastPolicerAssociationTable  OBJECT-TYPE
        SYNTAX  SEQUENCE OF GenEquipInterfacesCetMcastPolicerAssociationEntry
        ACCESS  not-accessible
        STATUS mandatory
        DESCRIPTION
        "Ethernet Port Multicast configuration table."
        ::= { genEquipInterfacesCet 10 }

genEquipInterfacesCetMcastPolicerAssociationEntry OBJECT-TYPE
        SYNTAX GenEquipInterfacesCetMcastPolicerAssociationEntry
        ACCESS not-accessible
        STATUS mandatory
          DESCRIPTION
        "Ethernet Port Multicast configuration table."
        INDEX { genEquipInterfacesCetMcastPolicerAssociationIfIndex }
        ::= { genEquipInterfacesCetMcastPolicerAssociationTable 1 }

GenEquipInterfacesCetMcastPolicerAssociationEntry ::=
		SEQUENCE {
			genEquipInterfacesCetMcastPolicerAssociationIfIndex
				INTEGER,
			genEquipInterfacesCetMcastPolicerAssociationAssociatedProfileId
				INTEGER,
			genEquipInterfacesCetMcastPolicerAssociationAdmin
				EnableDisable,
			genEquipInterfacesCetMcastPolicerAssociationAssociationRowStatus
				RowStatus
}


genEquipInterfacesCetMcastPolicerAssociationIfIndex		OBJECT-TYPE
		SYNTAX 		INTEGER
		ACCESS		read-only
        STATUS		mandatory
        DESCRIPTION
		"Ethernet Logical port if-index table key."
::= { genEquipInterfacesCetMcastPolicerAssociationEntry 1 }

genEquipInterfacesCetMcastPolicerAssociationAssociatedProfileId		OBJECT-TYPE
		SYNTAX 		INTEGER (1..256)
		ACCESS		read-write
        STATUS		mandatory
        DESCRIPTION
		"Ingress Policer Profile ID."
::= { genEquipInterfacesCetMcastPolicerAssociationEntry 2 }

genEquipInterfacesCetMcastPolicerAssociationAdmin		OBJECT-TYPE
		SYNTAX 		EnableDisable
		ACCESS		read-write
        STATUS		mandatory
        DESCRIPTION
		"Ingress Multicast Policer Admin (enable / disable)."
::= { genEquipInterfacesCetMcastPolicerAssociationEntry 3 }

genEquipInterfacesCetMcastPolicerAssociationAssociationRowStatus		OBJECT-TYPE
		SYNTAX 		RowStatus
		ACCESS		read-write
        STATUS		mandatory
        DESCRIPTION
		"Table Mib Row Status."
::= { genEquipInterfacesCetMcastPolicerAssociationEntry 30 }


--
-- Switch Application if-logical-unicast_policing-table
--

genEquipInterfacesCetUcastPolicerAssociationTable  OBJECT-TYPE
        SYNTAX  SEQUENCE OF GenEquipInterfacesCetUcastPolicerAssociationEntry
        ACCESS  not-accessible
        STATUS mandatory
        DESCRIPTION
        "Ethernet Port Multicast configuration table."
        ::= { genEquipInterfacesCet 11 }

genEquipInterfacesCetUcastPolicerAssociationEntry OBJECT-TYPE
        SYNTAX GenEquipInterfacesCetUcastPolicerAssociationEntry
        ACCESS not-accessible
        STATUS mandatory
          DESCRIPTION
        "Ethernet Port Multicast configuration table."
        INDEX { genEquipInterfacesCetUcastPolicerAssociationIfIndex }
        ::= { genEquipInterfacesCetUcastPolicerAssociationTable 1 }

GenEquipInterfacesCetUcastPolicerAssociationEntry ::=
		SEQUENCE {
			genEquipInterfacesCetUcastPolicerAssociationIfIndex
				INTEGER,
			genEquipInterfacesCetUcastPolicerAssociationAssociatedProfileId
				INTEGER,
			genEquipInterfacesCetUcastPolicerAssociationAdmin
				EnableDisable,
			genEquipInterfacesCetUcastPolicerAssociationRowStatus
				RowStatus
}


genEquipInterfacesCetUcastPolicerAssociationIfIndex		OBJECT-TYPE
		SYNTAX 		INTEGER
		ACCESS		read-only
        STATUS		mandatory
        DESCRIPTION
		"Ethernet Logical port if-index table key."
::= { genEquipInterfacesCetUcastPolicerAssociationEntry 1 }

genEquipInterfacesCetUcastPolicerAssociationAssociatedProfileId		OBJECT-TYPE
		SYNTAX 		INTEGER (1..256)
		ACCESS		read-write
        STATUS		mandatory
        DESCRIPTION
		"Ingress Policer Profile ID."
::= { genEquipInterfacesCetUcastPolicerAssociationEntry 2 }

genEquipInterfacesCetUcastPolicerAssociationAdmin		OBJECT-TYPE
		SYNTAX 		EnableDisable
		ACCESS		read-write
        STATUS		mandatory
        DESCRIPTION
		"Ingress Unicast Policer Admin (enable / disable)."
::= { genEquipInterfacesCetUcastPolicerAssociationEntry 3 }

genEquipInterfacesCetUcastPolicerAssociationRowStatus		OBJECT-TYPE
		SYNTAX 		RowStatus
		ACCESS		read-write
        STATUS		mandatory
        DESCRIPTION
		"Table Mib Row Status."
::= { genEquipInterfacesCetUcastPolicerAssociationEntry 30 }

--
-- Switch Application sys-if-logical-mgr-if-logical-lag-table
--

genEquipInterfacesCetLagTable  OBJECT-TYPE
        SYNTAX  SEQUENCE OF GenEquipInterfacesCetLagEntry
        ACCESS  not-accessible
        STATUS mandatory
        DESCRIPTION
        "This table holds the members of a Link Aggregation Group."
        ::= { genEquipInterfacesCet 12 }

genEquipInterfacesCetLagEntry OBJECT-TYPE
        SYNTAX GenEquipInterfacesCetLagEntry
        ACCESS not-accessible
        STATUS mandatory
          DESCRIPTION
        "This table holds the members of a Link Aggregation Group entry."
        INDEX { genEquipInterfacesCetLagIfIndex }
        ::= { genEquipInterfacesCetLagTable 1 }

GenEquipInterfacesCetLagEntry ::=
		SEQUENCE {
			genEquipInterfacesCetLagIfIndex
				INTEGER,
			genEquipInterfacesCetLagMember1IfIndex
				INTEGER,
			genEquipInterfacesCetLagMember2IfIndex
				INTEGER,
			genEquipInterfacesCetLagMember3IfIndex
				INTEGER,
			genEquipInterfacesCetLagMember4IfIndex
				INTEGER,
			genEquipInterfacesCetLagMember5IfIndex
				INTEGER,
			genEquipInterfacesCetLagMember6IfIndex
				INTEGER,
			genEquipInterfacesCetLagMember7IfIndex
				INTEGER,
			genEquipInterfacesCetLagMember8IfIndex
				INTEGER,
			genEquipInterfacesCetLagMember9IfIndex
				INTEGER,
			genEquipInterfacesCetLagMember10IfIndex
				INTEGER,
			genEquipInterfacesCetLagMember11IfIndex
				INTEGER,
			genEquipInterfacesCetLagMember12IfIndex
				INTEGER,
			genEquipInterfacesCetLagMember13IfIndex
				INTEGER,
			genEquipInterfacesCetLagMember14IfIndex
				INTEGER,
			genEquipInterfacesCetLagMember15IfIndex
				INTEGER,
			genEquipInterfacesCetLagMember16IfIndex
				INTEGER,
			genEquipInterfacesCetLagRowStatus
				RowStatus
}


genEquipInterfacesCetLagIfIndex		OBJECT-TYPE
		SYNTAX 		INTEGER
		ACCESS		read-only
        STATUS		mandatory
        DESCRIPTION
		"Link aggregation group IF index."
::= { genEquipInterfacesCetLagEntry 1 }

genEquipInterfacesCetLagMember1IfIndex		OBJECT-TYPE
		SYNTAX 		INTEGER
		ACCESS		read-write
        STATUS		mandatory
        DESCRIPTION
		"Link aggregation member 1 IF index."
::= { genEquipInterfacesCetLagEntry 2 }

genEquipInterfacesCetLagMember2IfIndex		OBJECT-TYPE
		SYNTAX 		INTEGER
		ACCESS		read-write
        STATUS		mandatory
        DESCRIPTION
		"Link aggregation member 2 IF index."
::= { genEquipInterfacesCetLagEntry 3 }

genEquipInterfacesCetLagMember3IfIndex		OBJECT-TYPE
		SYNTAX 		INTEGER
		ACCESS		read-write
        STATUS		mandatory
        DESCRIPTION
		"Link aggregation member 3 IF index."
::= { genEquipInterfacesCetLagEntry 4 }

genEquipInterfacesCetLagMember4IfIndex		OBJECT-TYPE
		SYNTAX 		INTEGER
		ACCESS		read-write
        STATUS		mandatory
        DESCRIPTION
		"Link aggregation member 4 IF index."
::= { genEquipInterfacesCetLagEntry 5 }

genEquipInterfacesCetLagMember5IfIndex		OBJECT-TYPE
		SYNTAX 		INTEGER
		ACCESS		read-write
        STATUS		mandatory
        DESCRIPTION
		"Link aggregation member 5 IF index."
::= { genEquipInterfacesCetLagEntry 6 }

genEquipInterfacesCetLagMember6IfIndex		OBJECT-TYPE
		SYNTAX 		INTEGER
		ACCESS		read-write
        STATUS		mandatory
        DESCRIPTION
		"Link aggregation member 6 IF index."
::= { genEquipInterfacesCetLagEntry 7 }

genEquipInterfacesCetLagMember7IfIndex		OBJECT-TYPE
		SYNTAX 		INTEGER
		ACCESS		read-write
        STATUS		mandatory
        DESCRIPTION
		"Link aggregation member 7 IF index."
::= { genEquipInterfacesCetLagEntry 8 }

genEquipInterfacesCetLagMember8IfIndex		OBJECT-TYPE
		SYNTAX 		INTEGER
		ACCESS		read-write
        STATUS		mandatory
        DESCRIPTION
		"Link aggregation member 8 IF index."
::= { genEquipInterfacesCetLagEntry 9 }

genEquipInterfacesCetLagMember9IfIndex		OBJECT-TYPE
		SYNTAX 		INTEGER
		ACCESS		read-write
        STATUS		mandatory
        DESCRIPTION
		"Link aggregation member 9 IF index."
::= { genEquipInterfacesCetLagEntry 10 }

genEquipInterfacesCetLagMember10IfIndex		OBJECT-TYPE
		SYNTAX 		INTEGER
		ACCESS		read-write
        STATUS		mandatory
        DESCRIPTION
		"Link aggregation member 9 IF index."
::= { genEquipInterfacesCetLagEntry 11 }

genEquipInterfacesCetLagMember11IfIndex		OBJECT-TYPE
		SYNTAX 		INTEGER
		ACCESS		read-write
        STATUS		mandatory
        DESCRIPTION
		"Link aggregation member 11 IF index."
::= { genEquipInterfacesCetLagEntry 12 }

genEquipInterfacesCetLagMember12IfIndex		OBJECT-TYPE
		SYNTAX 		INTEGER
		ACCESS		read-write
        STATUS		mandatory
        DESCRIPTION
		"Link aggregation member 12 IF index."
::= { genEquipInterfacesCetLagEntry 13 }

genEquipInterfacesCetLagMember13IfIndex		OBJECT-TYPE
		SYNTAX 		INTEGER
		ACCESS		read-write
        STATUS		mandatory
        DESCRIPTION
		"Link aggregation member 13 IF index."
::= { genEquipInterfacesCetLagEntry 14 }

genEquipInterfacesCetLagMember14IfIndex		OBJECT-TYPE
		SYNTAX 		INTEGER
		ACCESS		read-write
        STATUS		mandatory
        DESCRIPTION
		"Link aggregation member 14 IF index."
::= { genEquipInterfacesCetLagEntry 15 }

genEquipInterfacesCetLagMember15IfIndex		OBJECT-TYPE
		SYNTAX 		INTEGER
		ACCESS		read-write
        STATUS		mandatory
        DESCRIPTION
		"Link aggregation member 15 IF index."
::= { genEquipInterfacesCetLagEntry 16 }

genEquipInterfacesCetLagMember16IfIndex		OBJECT-TYPE
		SYNTAX 		INTEGER
		ACCESS		read-write
        STATUS		mandatory
        DESCRIPTION
		"Link aggregation member 16 IF index."
::= { genEquipInterfacesCetLagEntry 17 }

genEquipInterfacesCetLagRowStatus		OBJECT-TYPE
		SYNTAX 		RowStatus
		ACCESS		read-write
        STATUS		mandatory
        DESCRIPTION
		"Table Mib Row Status."
::= { genEquipInterfacesCetLagEntry 30 }

--
-- Switch Application sw-ap-service-to-instance-table
--

genEquipServicesCetConfigServiceToInstanceTable  OBJECT-TYPE
        SYNTAX  SEQUENCE OF GenEquipServicesCetConfigServiceToInstanceEntry
        ACCESS  not-accessible
        STATUS mandatory
        DESCRIPTION
        "This table is used for mapping xSTP instance number per service."
        ::= { genEquipInterfacesCet 13 }

genEquipServicesCetConfigServiceToInstanceEntry OBJECT-TYPE
        SYNTAX GenEquipServicesCetConfigServiceToInstanceEntry
        ACCESS not-accessible
        STATUS mandatory
          DESCRIPTION
        "This table entry is used for mapping xSTP instance number per service."
        INDEX { genEquipServicesCetConfigServiceToInstanceServiceIndex }
        ::= { genEquipServicesCetConfigServiceToInstanceTable 1 }

GenEquipServicesCetConfigServiceToInstanceEntry ::=
		SEQUENCE {
			genEquipServicesCetConfigServiceToInstanceServiceIndex
				INTEGER,
			genEquipServicesCetConfigServiceToInstanceInstanceIndex
				INTEGER
}


genEquipServicesCetConfigServiceToInstanceServiceIndex		OBJECT-TYPE
		SYNTAX 		INTEGER
		ACCESS		read-write
        STATUS		mandatory
        DESCRIPTION
		"Service ID."
::= { genEquipServicesCetConfigServiceToInstanceEntry 1 }

genEquipServicesCetConfigServiceToInstanceInstanceIndex		OBJECT-TYPE
		SYNTAX 		INTEGER
		ACCESS		read-write
        STATUS		mandatory
        DESCRIPTION
		"xSTP Instance ID for the specific Service."
::= { genEquipServicesCetConfigServiceToInstanceEntry 2 }

-- IF Manager if-manager-configuration-table
genEquipInterfacesIfManager	OBJECT IDENTIFIER ::= {genEquipInterfaces 9}

genEquipInterfacesIfManagerTable  OBJECT-TYPE
        SYNTAX  SEQUENCE OF GenEquipInterfacesIfManagerEntry
        ACCESS  not-accessible
        STATUS mandatory
        DESCRIPTION
        "This table contains a list of configuration information about the user managed interfaces."
        ::= { genEquipInterfacesIfManager 1 }

genEquipInterfacesIfManagerEntry OBJECT-TYPE
        SYNTAX GenEquipInterfacesIfManagerEntry
        ACCESS not-accessible
        STATUS mandatory
          DESCRIPTION
          "This table entry contains a list of configuration information about the user managed interfaces."
        INDEX { ifIndex }
        ::= { genEquipInterfacesIfManagerTable 1 }

GenEquipInterfacesIfManagerEntry ::=
		SEQUENCE {
			genEquipInterfacesIfManagerifCascading
				IfMgrTrueFalse,
			genEquipInterfacesIfManagerifSecondaryOperStatus
				INTEGER
}


genEquipInterfacesIfManagerifCascading		OBJECT-TYPE
		SYNTAX 		IfMgrTrueFalse
		ACCESS		read-only
        STATUS		mandatory
        DESCRIPTION
		"The cascading state of the interface."
::= { genEquipInterfacesIfManagerEntry 1 }

genEquipInterfacesIfManagerifSecondaryOperStatus OBJECT-TYPE
		SYNTAX 		INTEGER
		ACCESS		read-only
        STATUS		mandatory
        DESCRIPTION
		"An additional information about the current operational state of the interface."
::= { genEquipInterfacesIfManagerEntry 2 }

--
-- IF Cascading if-physical-cascading-port-config-table
genEquipInterfacesCascading	OBJECT IDENTIFIER ::= {genEquipInterfaces 10}

genEquipInterfacesCascadingConfigurationTable  OBJECT-TYPE
        SYNTAX  SEQUENCE OF GenEquipInterfacesCascadingConfigurationEntry
        ACCESS  not-accessible
        STATUS mandatory
        DESCRIPTION
        "Cascading Port Configuration Table."
        ::= { genEquipInterfacesCascading 1 }

genEquipInterfacesCascadingConfigurationEntry OBJECT-TYPE
        SYNTAX GenEquipInterfacesCascadingConfigurationEntry
        ACCESS not-accessible
        STATUS mandatory
          DESCRIPTION
          "Cascading Port Configuration Table entry."
        INDEX { genEquipInterfacesCascadingConfigurationIfindex }
        ::= { genEquipInterfacesCascadingConfigurationTable 1 }

GenEquipInterfacesCascadingConfigurationEntry ::=
		SEQUENCE {
			genEquipInterfacesCascadingConfigurationIfindex
				INTEGER,
			genEquipInterfacesCascadingConfigurationCascading
				MibTrueFalse
}


genEquipInterfacesCascadingConfigurationIfindex		OBJECT-TYPE
		SYNTAX 		INTEGER
		ACCESS		read-only
        STATUS		mandatory
        DESCRIPTION
		"Cascading port if-index table key."
::= { genEquipInterfacesCascadingConfigurationEntry 1 }

genEquipInterfacesCascadingConfigurationCascading OBJECT-TYPE
		SYNTAX 		MibTrueFalse
		ACCESS		read-write
        STATUS		mandatory
        DESCRIPTION
		"Indicates if the port is cascading or not."
::= { genEquipInterfacesCascadingConfigurationEntry 2 }


-- STM-1/OC-3
genEquipInterfacesStm1Rst	OBJECT IDENTIFIER ::= {genEquipInterfaces 11}

-- stm1-config-table
genEquipInterfacesStm1RstConfigTable  OBJECT-TYPE
        SYNTAX  SEQUENCE OF GenEquipInterfacesStm1RstConfigEntry
        ACCESS  not-accessible
        STATUS mandatory
        DESCRIPTION
        "STM-1/OC-3 configuration table."
        ::= { genEquipInterfacesStm1Rst 1 }

genEquipInterfacesStm1RstConfigEntry OBJECT-TYPE
        SYNTAX GenEquipInterfacesStm1RstConfigEntry
        ACCESS not-accessible
        STATUS mandatory
          DESCRIPTION
          "STM-1/OC-3 configuration table entry."
        INDEX { genEquipInterfacesStm1RstConfigIfindex }
        ::= { genEquipInterfacesStm1RstConfigTable 1 }

GenEquipInterfacesStm1RstConfigEntry ::=
		SEQUENCE {
			genEquipInterfacesStm1RstConfigIfindex
				INTEGER,
			genEquipInterfacesStm1RstConfigPort
				INTEGER,
			genEquipInterfacesStm1RstConfigAdmin
				EnableDisableSMI2,
			genEquipInterfacesStm1RstConfigMute
				INTEGER
}


genEquipInterfacesStm1RstConfigIfindex		OBJECT-TYPE
		SYNTAX 		INTEGER
		ACCESS		read-only
        STATUS		mandatory
        DESCRIPTION
		"The interface index of the STM-1/OC-3 interface."
::= { genEquipInterfacesStm1RstConfigEntry 1 }

genEquipInterfacesStm1RstConfigPort OBJECT-TYPE
		SYNTAX 		INTEGER
		ACCESS		read-write
        STATUS		mandatory
        DESCRIPTION
		"The port of the STM-1/OC-3 interface."
::= { genEquipInterfacesStm1RstConfigEntry 2 }

genEquipInterfacesStm1RstConfigAdmin OBJECT-TYPE
		SYNTAX 		EnableDisableSMI2
		ACCESS		read-write
        STATUS		mandatory
        DESCRIPTION
		"The Admin Sate of the STM-1/OC-3 interface."
::= { genEquipInterfacesStm1RstConfigEntry 3 }

genEquipInterfacesStm1RstConfigMute OBJECT-TYPE
		SYNTAX 		INTEGER {
						unmute(0),
						mute(1)
					}
		ACCESS		read-write
        STATUS		mandatory
        DESCRIPTION
		"The SFP Mute config of the STM-1/OC-3 interface."
::= { genEquipInterfacesStm1RstConfigEntry 4 }


--
-- stm1-status-table
genEquipInterfacesStm1RstStatusTable  OBJECT-TYPE
        SYNTAX  SEQUENCE OF GenEquipInterfacesStm1RstStatusEntry
        ACCESS  not-accessible
        STATUS mandatory
        DESCRIPTION
        "STM-1/OC-3 status table."
        ::= { genEquipInterfacesStm1Rst 2 }

genEquipInterfacesStm1RstStatusEntry OBJECT-TYPE
        SYNTAX GenEquipInterfacesStm1RstStatusEntry
        ACCESS not-accessible
        STATUS mandatory
          DESCRIPTION
          "STM-1/OC-3 status table entry."
        INDEX { genEquipInterfacesStm1RstStatusIfindex }
        ::= { genEquipInterfacesStm1RstStatusTable 1 }

GenEquipInterfacesStm1RstStatusEntry ::=
		SEQUENCE {
			genEquipInterfacesStm1RstStatusIfindex
				INTEGER,
			genEquipInterfacesStm1RstStatusLoopbackTimer
				INTEGER,
			genEquipInterfacesStm1RstStatusLoopbackType
				RSTLoopbackType,
			genEquipInterfacesStm1RstStatusOperstatus
				DownUp
}


genEquipInterfacesStm1RstStatusIfindex		OBJECT-TYPE
		SYNTAX 		INTEGER
		ACCESS		read-only
        STATUS		mandatory
        DESCRIPTION
		"The interface index of the STM-1/OC-3 interface."
::= { genEquipInterfacesStm1RstStatusEntry 1 }

genEquipInterfacesStm1RstStatusLoopbackTimer OBJECT-TYPE
		SYNTAX 		INTEGER
		ACCESS		read-write
        STATUS		mandatory
        DESCRIPTION
		"The port of the STM-1/OC-3 interface."
::= { genEquipInterfacesStm1RstStatusEntry 2 }

genEquipInterfacesStm1RstStatusLoopbackType OBJECT-TYPE
		SYNTAX 		RSTLoopbackType
		ACCESS		read-write
        STATUS		mandatory
        DESCRIPTION
		"The loopback type of the STM-1/OC-3 interface."
::= { genEquipInterfacesStm1RstStatusEntry 3 }

genEquipInterfacesStm1RstStatusOperstatus OBJECT-TYPE
		SYNTAX 		DownUp
		ACCESS		read-only
        STATUS		mandatory
        DESCRIPTION
		"The operational status of the STM-1/OC-3 interface."
::= { genEquipInterfacesStm1RstStatusEntry 4 }

-- stm1-status-table only prbs
genEquipInterfacesStm1RstPrbsTable  OBJECT-TYPE
        SYNTAX  SEQUENCE OF GenEquipInterfacesStm1RstPrbsEntry
        ACCESS  not-accessible
        STATUS mandatory
        DESCRIPTION
        "STM-1/OC-3 status table."
        ::= { genEquipInterfacesStm1Rst 3 }

genEquipInterfacesStm1RstPrbsEntry OBJECT-TYPE
        SYNTAX GenEquipInterfacesStm1RstPrbsEntry
        ACCESS not-accessible
        STATUS mandatory
          DESCRIPTION
          "STM-1/OC-3 status table entry."
        INDEX { genEquipInterfacesStm1RstStatusIfindex }
        ::= { genEquipInterfacesStm1RstPrbsTable 1 }

GenEquipInterfacesStm1RstPrbsEntry ::=
		SEQUENCE {
			genEquipInterfacesStm1RstPrbsCheckLineClear
				INTEGER,
			genEquipInterfacesStm1RstPrbsCheckLine
				INTEGER,
			genEquipInterfacesStm1RstPrbsCheckLineInv
				INTEGER,
			genEquipInterfacesStm1RstPrbsCheckLineStatus
				DisplayString,
			genEquipInterfacesStm1RstPrbsCheckLineTotErr
				INTEGER,
			genEquipInterfacesStm1RstPrbsCheckRadioClear
				INTEGER,
			genEquipInterfacesStm1RstPrbsCheckRadio
				INTEGER,
			genEquipInterfacesStm1RstPrbsCheckRadioInv
				INTEGER,
			genEquipInterfacesStm1RstPrbsCheckRadioStatus
				DisplayString,
			genEquipInterfacesStm1RstPrbsCheckRadioTotErr
				INTEGER,
			genEquipInterfacesStm1RstPrbsGenLine
				INTEGER,
			genEquipInterfacesStm1RstPrbsGenLineErrIns
				INTEGER,
			genEquipInterfacesStm1RstPrbsGenLineInv
				INTEGER,
			genEquipInterfacesStm1RstPrbsGenRadio
				INTEGER,
			genEquipInterfacesStm1RstPrbsGenRadioErrIns
				INTEGER,
			genEquipInterfacesStm1RstPrbsGenRadioInv
				INTEGER
}


genEquipInterfacesStm1RstPrbsCheckLineClear OBJECT-TYPE
		SYNTAX 		INTEGER
		ACCESS		read-write
        STATUS		mandatory
        DESCRIPTION
		"The PRBS Checker Line Direction Reset counter of the STM-1/OC-3 interface."
::= { genEquipInterfacesStm1RstPrbsEntry 1 }


genEquipInterfacesStm1RstPrbsCheckLine OBJECT-TYPE
		SYNTAX 		INTEGER
		ACCESS		read-write
        STATUS		mandatory
        DESCRIPTION
		"The PRBS Checker Line Direction of the STM-1/OC-3 interface."
::= { genEquipInterfacesStm1RstPrbsEntry 2 }

genEquipInterfacesStm1RstPrbsCheckLineInv OBJECT-TYPE
		SYNTAX 		INTEGER
		ACCESS		read-write
        STATUS		mandatory
        DESCRIPTION
		"The PRBS Checker Line Direction of the STM-1/OC-3 interface."
::= { genEquipInterfacesStm1RstPrbsEntry 3 }

genEquipInterfacesStm1RstPrbsCheckLineStatus OBJECT-TYPE
		SYNTAX 		DisplayString
		ACCESS		read-write
        STATUS		mandatory
        DESCRIPTION
		"The PRBS Checker Line Direction Status of the STM-1/OC-3 interface."
::= { genEquipInterfacesStm1RstPrbsEntry 4 }

genEquipInterfacesStm1RstPrbsCheckLineTotErr OBJECT-TYPE
		SYNTAX 		INTEGER
		ACCESS		read-write
        STATUS		mandatory
        DESCRIPTION
		"The PRBS Checker Line Direction Total Error counter of the STM-1/OC-3 interface."
::= { genEquipInterfacesStm1RstPrbsEntry 5 }

genEquipInterfacesStm1RstPrbsCheckRadioClear OBJECT-TYPE
		SYNTAX 		INTEGER
		ACCESS		read-write
        STATUS		mandatory
        DESCRIPTION
		"The PRBS Checker Radio Direction Reset counter of the STM-1/OC-3 interface."
::= { genEquipInterfacesStm1RstPrbsEntry 6 }

genEquipInterfacesStm1RstPrbsCheckRadio OBJECT-TYPE
		SYNTAX 		INTEGER
		ACCESS		read-write
        STATUS		mandatory
        DESCRIPTION
		"The PRBS Checker Radio Direction of the STM-1/OC-3 interface."
::= { genEquipInterfacesStm1RstPrbsEntry 7 }

genEquipInterfacesStm1RstPrbsCheckRadioInv OBJECT-TYPE
		SYNTAX 		INTEGER
		ACCESS		read-write
        STATUS		mandatory
        DESCRIPTION
		"The PRBS Checker Radio Direction of the STM-1/OC-3 interface."
::= { genEquipInterfacesStm1RstPrbsEntry 8 }

genEquipInterfacesStm1RstPrbsCheckRadioStatus OBJECT-TYPE
		SYNTAX 		DisplayString
		ACCESS		read-write
        STATUS		mandatory
        DESCRIPTION
		"The PRBS Checker Radio Direction Status of the STM-1/OC-3 interface."
::= { genEquipInterfacesStm1RstPrbsEntry 9 }

genEquipInterfacesStm1RstPrbsCheckRadioTotErr OBJECT-TYPE
		SYNTAX 		INTEGER
		ACCESS		read-write
        STATUS		mandatory
        DESCRIPTION
		"The PRBS Checker Radio Direction Total Error counter of the STM-1/OC-3 interface."
::= { genEquipInterfacesStm1RstPrbsEntry 10 }

genEquipInterfacesStm1RstPrbsGenLine OBJECT-TYPE
		SYNTAX 		INTEGER
		ACCESS		read-write
        STATUS		mandatory
        DESCRIPTION
		"The PRBS Generator Line Direction of the STM-1/OC-3 interface."
::= { genEquipInterfacesStm1RstPrbsEntry 11 }

genEquipInterfacesStm1RstPrbsGenLineErrIns OBJECT-TYPE
		SYNTAX 		INTEGER
		ACCESS		read-write
        STATUS		mandatory
        DESCRIPTION
		"The PRBS Generator Line Direction Error Insert of the STM-1/OC-3 interface."
::= { genEquipInterfacesStm1RstPrbsEntry 12 }

genEquipInterfacesStm1RstPrbsGenLineInv OBJECT-TYPE
		SYNTAX 		INTEGER
		ACCESS		read-write
        STATUS		mandatory
        DESCRIPTION
		"The PRBS Generator Line Direction of the STM-1/OC-3 interface."
::= { genEquipInterfacesStm1RstPrbsEntry 13 }

genEquipInterfacesStm1RstPrbsGenRadio OBJECT-TYPE
		SYNTAX 		INTEGER
		ACCESS		read-write
        STATUS		mandatory
        DESCRIPTION
		"The PRBS Generator Radio Direction of the STM-1/OC-3 interface."
::= { genEquipInterfacesStm1RstPrbsEntry 14 }

genEquipInterfacesStm1RstPrbsGenRadioErrIns OBJECT-TYPE
		SYNTAX 		INTEGER
		ACCESS		read-write
        STATUS		mandatory
        DESCRIPTION
		"The PRBS Generator Radio Direction Error Insert of the STM-1/OC-3 interface."
::= { genEquipInterfacesStm1RstPrbsEntry 15 }

genEquipInterfacesStm1RstPrbsGenRadioInv OBJECT-TYPE
		SYNTAX 		INTEGER
		ACCESS		read-write
        STATUS		mandatory
        DESCRIPTION
		"The PRBS Generator Radio Direction of the STM-1/OC-3 interface."
::= { genEquipInterfacesStm1RstPrbsEntry 16 }


-- ###########################################################
--                 Traps Section
-- ###########################################################

alarmTrap TRAP-TYPE
		ENTERPRISE microwave-radio
		VARIABLES { genEquipCurrentAlarmCounter,
					genEquipCurrentAlarmRaisedTimeT,
					genEquipCurrentAlarmId,
					genEquipCurrentAlarmSlotId,
					genEquipCurrentAlarmInstance,
		            genEquipCurrentAlarmSeverity,
		            genEquipCurrentAlarmIfIndex,
		            genEquipCurrentAlarmModule,
		            genEquipCurrentAlarmDesc,
					genEquipMostSevereAlarm,
					genEquipNetworkAgentIp,
					genEquipCurrentAlarmState,
					genEquipTrapCfgMgrCLLI
		          }
		DESCRIPTION "Alarm network trap"
		::= 1001

eventTrap TRAP-TYPE
		ENTERPRISE microwave-radio
		VARIABLES { genEquipCurrentAlarmCounter,
					genEquipCurrentAlarmRaisedTimeT,
					genEquipCurrentAlarmId,
					genEquipCurrentAlarmSlotId,
					genEquipCurrentAlarmInstance,
		            genEquipCurrentAlarmSeverity,
		            genEquipCurrentAlarmIfIndex,
		            genEquipCurrentAlarmModule,
		            genEquipCurrentAlarmDesc,
					genEquipMostSevereAlarm,
					genEquipNetworkAgentIp,
					genEquipTrapCfgMgrCLLI
		          }
		DESCRIPTION "Event network trap"
		::= 1002


heartbeatTrap TRAP-TYPE
		ENTERPRISE microwave-radio
		VARIABLES { genEquipTrapCfgMgrCLLI
		          }
		DESCRIPTION "The heartbeat trap, sent once per heartbeat period"
		::= 1003

eventTrapSTP TRAP-TYPE        -- STP, RSTP, Ring RSTP trap
       ENTERPRISE microwave-radio
       VARIABLES { genEquipCurrentAlarmCounter,           -- general event parameters
                   genEquipCurrentAlarmRaisedTimeT,
                   genEquipCurrentAlarmId,
                   genEquipCurrentAlarmSlotId,
                   genEquipCurrentAlarmInstance,
                   genEquipCurrentAlarmSeverity,
                   genEquipCurrentAlarmIfIndex,
                   genEquipCurrentAlarmModule,
                   genEquipCurrentAlarmDesc, -- This field shows show the descriptions of the event
                                             -- "STP event - on port: <port>, root id: <root id>, Bridge role: <bridge role>,
                                             --  Role: <Role>, State: <state>"
                   genEquipMostSevereAlarm,
                   genEquipNetworkAgentIp,
                   genEquipTrapCfgMgrCLLI,
                   genEquipEthernetSwitchXSTPParamsEthernetPortsRole,   -- event trigger
                   genEquipEthernetSwitchXSTPParamsEthernetPortsState,       -- event trigger
                   genEquipEthernetSwitchXSTPBridgeRole,
                   genEquipEthernetSwitchXSTPRootID    -- RSTP parameters
                 }
       DESCRIPTION "STP trap.
                    (1) The description field shows show the descriptions of the event
                    STP event - on port: <port>, root id: <root id>, Bridge role: <bridge role>,
                    Role: <Role>, State: <state>
                    In addition to the general trap event var-binds, this trap also adds the STP parameters."

       ::= 1004

genTraps OBJECT IDENTIFIER ::= { microwave-radio 11 }
		generalV3Trap NOTIFICATION-TYPE
		OBJECTS { 	genEquipCurrentAlarmCounter,
					genEquipCurrentAlarmRaisedTimeT,
					genEquipCurrentAlarmId,
					genEquipCurrentAlarmSlotId,
					genEquipCurrentAlarmInstance,
		            genEquipCurrentAlarmSeverity,
		            genEquipCurrentAlarmIfIndex,
		            genEquipCurrentAlarmModule,
		            genEquipCurrentAlarmDesc,
					genEquipMostSevereAlarm,
					genEquipNetworkAgentIp,
					genEquipCurrentAlarmState,
					genEquipTrapCfgMgrCLLI
		          }
		STATUS	current
		DESCRIPTION "General network V3 trap"
		::= { genTraps 1 }

		eventV3Trap NOTIFICATION-TYPE
		OBJECTS { 	genEquipCurrentAlarmCounter,
					genEquipCurrentAlarmRaisedTimeT,
					genEquipCurrentAlarmId,
					genEquipCurrentAlarmSlotId,
					genEquipCurrentAlarmInstance,
		            genEquipCurrentAlarmSeverity,
		            genEquipCurrentAlarmIfIndex,
		            genEquipCurrentAlarmModule,
		            genEquipCurrentAlarmDesc,
					genEquipMostSevereAlarm,
					genEquipNetworkAgentIp,
					genEquipTrapCfgMgrCLLI
		          }
		STATUS	current
		DESCRIPTION "Event network V3 trap"
		::= { genTraps 2 }

		heartbeatV3Trap NOTIFICATION-TYPE
		OBJECTS     {
				genEquipTrapCfgMgrCLLI
					}

             STATUS  current
             DESCRIPTION
				"Heartbeat v3 trap - The heartbeat trap, sent once per heartbeat period"
	 ::= { genTraps 3 }

      eventv3TrapSTP NOTIFICATION-TYPE        -- STP, RSTP, Ring RSTP trap
        OBJECTS    { genEquipCurrentAlarmCounter,           -- general event parameters
                     genEquipCurrentAlarmRaisedTimeT,
                     genEquipCurrentAlarmId,
                     genEquipCurrentAlarmSlotId,
                     genEquipCurrentAlarmInstance,
                     genEquipCurrentAlarmSeverity,
                     genEquipCurrentAlarmIfIndex,
                     genEquipCurrentAlarmModule,
                     genEquipCurrentAlarmDesc, -- This field shows show the descriptions of the event
                                               -- "STP event - on port: <port>, root id: <root id>, Bridge role: <bridge role>,
                                               --  Role: <Role>, State: <state>,
                     genEquipMostSevereAlarm,
                     genEquipNetworkAgentIp,
                     genEquipTrapCfgMgrCLLI,
                     genEquipEthernetSwitchXSTPParamsEthernetPortsRole,   -- event trigger
                     genEquipEthernetSwitchXSTPParamsEthernetPortsState,       -- event trigger
                     genEquipEthernetSwitchXSTPBridgeRole,
                     genEquipEthernetSwitchXSTPRootID    -- RSTP parameters
                   }
                STATUS  current
                DESCRIPTION "STP trap.
                             (1) The description field shows show the descriptions of the event
                             STP event - on port: <port>, root id: <root id>, Bridge role: <bridge role>,
                             Role: <Role>, State: <state>,
                             In addition to the general trap event var-binds, this trap also adds the STP parameters."
     ::= { genTraps 4 }



-- ###########################################################
--                 NG Traps Section
-- ###########################################################

alarmTrap TRAP-TYPE
		ENTERPRISE microwave-radio
		VARIABLES { genEquipCurrentAlarmCounter,
					genEquipCurrentAlarmRaisedTimeT,
					genEquipNetworkAgentIp,
					genEquipCurrentAlarmId,
					genEquipCurrentAlarmDesc,
		            genEquipCurrentAlarmIfIndex,
					genEquipCurrentAlarmInstance,
		            genEquipCurrentAlarmSeverity,
					genEquipCurrentAlarmState,
		            genEquipCurrentAlarmUserText,
					genEquipTrapCfgMgrCLLI,
					genEquipNetworkAgentIpV6
		          }
		DESCRIPTION "NG Alarm network trap"
		::= 2000

heartbeatTrap TRAP-TYPE
		ENTERPRISE microwave-radio
		VARIABLES { genEquipCurrentAlarmCounter,
					genEquipTrapCfgMgrCLLI
		          }
		DESCRIPTION "NG heartbeat trap, sent once per heartbeat period"
		::= 2001


-- ###########################################################
--                 NG Notificatin Section (V2 V3)
-- ###########################################################

		generalNGV3Trap NOTIFICATION-TYPE
		OBJECTS { 	genEquipCurrentAlarmCounter,
					genEquipCurrentAlarmRaisedTimeT,
					genEquipNetworkAgentIp,
					genEquipCurrentAlarmId,
					genEquipCurrentAlarmDesc,
		            genEquipCurrentAlarmIfIndex,
					genEquipCurrentAlarmInstance,
		            genEquipCurrentAlarmSeverity,
					genEquipCurrentAlarmState,
		            genEquipCurrentAlarmUserText,
					genEquipTrapCfgMgrCLLI,
					genEquipNetworkAgentIpV6
		          }
		STATUS	current
		DESCRIPTION "NG General network V3 trap"
		::= { genTraps 2000 }

		heartbeatNGV3Trap NOTIFICATION-TYPE
		OBJECTS   {	genEquipCurrentAlarmCounter,
					genEquipTrapCfgMgrCLLI
				}
	    STATUS  current
        DESCRIPTION "NG Heartbeat v3 trap - The heartbeat trap, sent once per heartbeat period"
	 ::= { genTraps 2001 }

END
