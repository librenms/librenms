-- This file is corresponding to Release 10.2.3.100 from 2018/07/18 00:00:00


-- (C)opyright 2000-2014 bintec elmeg GmbH, All Rights Reserved
-- $RCSfile: mibpppoa,v $
-- $Revision: 1.5 $


BIANCA-BRICK-PPPOA-MIB DEFINITIONS ::= BEGIN

        IMPORTS
            IpAddress, Counter, enterprises
                FROM RFC1155-SMI

            DisplayString
                FROM RFC1158-MIB
 
            OBJECT-TYPE
                FROM RFC-1212;

    bintec 	OBJECT IDENTIFIER ::= { enterprises 272 }
    bibo	OBJECT IDENTIFIER ::= { bintec 4 }
    pppoa	OBJECT IDENTIFIER
	::= { bibo 28 }


    -- PPPoA Group

    -- PPPoA

	pppoaCallTable OBJECT-TYPE
	    SYNTAX  SEQUENCE OF PppoaCallEntry
	    ACCESS  not-accessible
	    STATUS  mandatory
	    DESCRIPTION
		"The pppoaCallTable displays all currently active PPPoA
                calls. Only the system can add or remove entries to this table."

	::= { pppoa 1 }

	pppoaCallEntry OBJECT-TYPE
	    SYNTAX  PppoaCallEntry
	    ACCESS  not-accessible
	    STATUS  mandatory
	    DESCRIPTION
		""
	    INDEX   { pppoaCallId }
	::= { pppoaCallTable 1 }

	PppoaCallEntry ::=
	    SEQUENCE {
		pppoaCallId				INTEGER,
		pppoaCallState				INTEGER,
		pppoaCallReceivedPackets		Counter,
		pppoaCallReceivedOctets			Counter,
		pppoaCallReceivedErrors			Counter,
		pppoaCallTransmitPackets		Counter,
		pppoaCallTransmitOctets			Counter,
		pppoaCallTransmitErrors			Counter,
		pppoaCallInfo                           DisplayString
	    }

	pppoaCallId OBJECT-TYPE
	    SYNTAX  INTEGER
	    ACCESS  read-only
	    STATUS  mandatory

	    DESCRIPTION
		"Identification of the PPPoA call."
	::= { pppoaCallEntry 1 }


	pppoaCallState OBJECT-TYPE
	    SYNTAX  INTEGER { 
		idle(1), established(2), terminated(3)
	    } 
	    ACCESS  read-write
	    STATUS  mandatory

	    DESCRIPTION
		"The state of the PPPoA discovery stage."
	    DEFVAL { idle }
	::= { pppoaCallEntry 2 }

	pppoaCallReceivedPackets OBJECT-TYPE
	    SYNTAX  Counter
	    ACCESS  read-only
	    STATUS  mandatory

	    DESCRIPTION
		"Count of received valid packets."
	::= { pppoaCallEntry 3 }

	pppoaCallReceivedOctets OBJECT-TYPE
	    SYNTAX  Counter
	    ACCESS  read-only
	    STATUS  mandatory

	    DESCRIPTION
		"Count of received valid Octets."
	::= { pppoaCallEntry 4 }

	pppoaCallReceivedErrors OBJECT-TYPE
	    SYNTAX  Counter
	    ACCESS  read-only
	    STATUS  mandatory

	    DESCRIPTION
		"Count of received invalid packets."
	::= { pppoaCallEntry 5 }

	pppoaCallTransmitPackets OBJECT-TYPE
	    SYNTAX  Counter
	    ACCESS  read-only
	    STATUS  mandatory

	    DESCRIPTION
		"Count of transmitted packets."
	::= { pppoaCallEntry 6 }

	pppoaCallTransmitOctets OBJECT-TYPE
	    SYNTAX  Counter
	    ACCESS  read-only
	    STATUS  mandatory

	    DESCRIPTION
		"Count of transmitted Octets."
	::= { pppoaCallEntry 7 }

	pppoaCallTransmitErrors OBJECT-TYPE
	    SYNTAX  Counter
	    ACCESS  read-only
	    STATUS  mandatory

	    DESCRIPTION
		"Count of transmit errors."
	::= { pppoaCallEntry 8 }

        pppoaCallInfo OBJECT-TYPE
	    SYNTAX  DisplayString
	    ACCESS  read-only
            STATUS  mandatory

	    DESCRIPTION
	    "Additional information to identify the PPPoA call"
        ::= { pppoaCallEntry 9 }



END
