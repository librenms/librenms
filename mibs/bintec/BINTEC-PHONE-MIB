-- This file is corresponding to Release 10.2.3.100 from 2018/07/18 00:00:00


-- (C)opyright 1999-2014 bintec elmeg GmbH
-- All Rights Reserved
-- $RCSfile: mib-phone,v $ 
-- $Revision: 1.7 $ 

BINTEC-PHONE-MIB DEFINITIONS ::= BEGIN

IMPORTS
    MODULE-IDENTITY, OBJECT-TYPE, NOTIFICATION-TYPE,
    Integer32, Unsigned32, Counter32, Counter64, IpAddress, TimeTicks,
    mib-2, enterprises
        FROM SNMPv2-SMI

    DisplayString, TimeStamp, TruthValue
        FROM SNMPv2-TC

    bibo, Date, BitValue, HexValue
        FROM BINTEC-MIB

    MODULE-COMPLIANCE, OBJECT-GROUP, NOTIFICATION-GROUP
        FROM SNMPv2-CONF;


phoneMIB MODULE-IDENTITY
    LAST-UPDATED "201211090000Z"
    ORGANIZATION "bintec elmeg GmbH"
    CONTACT-INFO
            "EMail:   info@bintec-elmeg.com
             Web:     www.bintec-elmeg.com
            "
    DESCRIPTION
            "This MIB module contains common definitions for phone interfaces."
    REVISION      "200908010000Z"
    DESCRIPTION
            "First release of this MIB."

        ::= { bibo 15 }

    -- INTERFACES Group

---------------------------------------------------------------------------
-- PHONE OID groups & all tables
---------------------------------------------------------------------------
phone            OBJECT IDENTIFIER ::= { phoneMIB 1 }
                -- phoneIfToneTable             1
                -- phoneIfToneDefinitionTable   2
                -- phoneIfRingTable             3

---------------------------------------------------------------------------
-- PHONE TYPES
---------------------------------------------------------------------------
RingTabIndex            ::= INTEGER             -- table index
ToneTabIndex            ::= INTEGER             -- table index
ToneDefTabIndex         ::= INTEGER             -- table index
ToneFrequency           ::= INTEGER (300..3400) -- value in Hz
CadenceString           ::= DisplayString (SIZE (0..127))


---------------------------------------------------------------------------
-- 1. phoneIfToneTable:  Tone Frequency and Cadence Table
---------------------------------------------------------------------------

    phoneIfToneTable OBJECT-TYPE
        SYNTAX          SEQUENCE OF PhoneIfToneEntry
        MAX-ACCESS      read-write
        STATUS          current
        DESCRIPTION
            "The phoneIfToneTable contains configuration information
            for the various tone signals."
        ::= { phone 1 }

    phoneIfToneEntry OBJECT-TYPE
        SYNTAX          PhoneIfToneEntry
        MAX-ACCESS      read-write
        STATUS          current
        DESCRIPTION
            ""
        INDEX           { phoneIfToneIndex }
        ::= { phoneIfToneTable 1 }

    PhoneIfToneEntry ::=
        SEQUENCE {
            phoneIfToneIndex                    ToneTabIndex,
            phoneIfToneInternDef                ToneDefTabIndex,
            phoneIfToneExternDef                ToneDefTabIndex,
            phoneIfToneCallingDef               ToneDefTabIndex,
            phoneIfToneBusyDef                  ToneDefTabIndex,
            phoneIfToneSpecialDialDef           ToneDefTabIndex,
            phoneIfToneIntrusionDef             ToneDefTabIndex,
            phoneIfTonePositiveAckDef           ToneDefTabIndex,
            phoneIfToneNegativeAckDef           ToneDefTabIndex,
            phoneIfToneContinousDialDef         ToneDefTabIndex,
            phoneIfToneCallWaitingDef           ToneDefTabIndex,
            phoneIfToneNotification1Def         ToneDefTabIndex,
            phoneIfToneNotification2Def         ToneDefTabIndex,
            phoneIfToneNotification3Def         ToneDefTabIndex,
            phoneIfToneRingbackDef              ToneDefTabIndex,
            phoneIfToneFallbackDef              ToneDefTabIndex
        }

    phoneIfToneIndex OBJECT-TYPE
        SYNTAX          ToneTabIndex
        MAX-ACCESS      read-write
        STATUS          current
        DESCRIPTION
            "Index of the set of tone definitions."
        DEFVAL          { -1 }
        ::= { phoneIfToneEntry 1 }

    phoneIfToneInternDef     OBJECT-TYPE
        SYNTAX          ToneDefTabIndex
        MAX-ACCESS      read-write
        STATUS          current
        DESCRIPTION
            "Tone definition table index for the internal dial tone."
        DEFVAL          { -1 }
        ::= { phoneIfToneEntry 2 }

    phoneIfToneExternDef     OBJECT-TYPE
        SYNTAX          ToneDefTabIndex
        MAX-ACCESS      read-write
        STATUS          current
        DESCRIPTION
            "Tone definition table index for the external dial tone."
        DEFVAL          { -1 }
        ::= { phoneIfToneEntry 3 }

    phoneIfToneCallingDef     OBJECT-TYPE
        SYNTAX          ToneDefTabIndex
        MAX-ACCESS      read-write
        STATUS          current
        DESCRIPTION
            "Tone definition table index for the calling tone."
        DEFVAL          { -1 }
        ::= { phoneIfToneEntry 4 }

    phoneIfToneBusyDef     OBJECT-TYPE
        SYNTAX          ToneDefTabIndex
        MAX-ACCESS      read-write
        STATUS          current
        DESCRIPTION
            "Tone definition table index for the busy tone."
        DEFVAL          { -1 }
        ::= { phoneIfToneEntry 5 }

    phoneIfToneSpecialDialDef     OBJECT-TYPE
        SYNTAX          ToneDefTabIndex
        MAX-ACCESS      read-write
        STATUS          current
        DESCRIPTION
            "Tone definition table index for the special dial tone."
        DEFVAL          { -1 }
        ::= { phoneIfToneEntry 6 }

    phoneIfToneIntrusionDef     OBJECT-TYPE
        SYNTAX          ToneDefTabIndex
        MAX-ACCESS      read-write
        STATUS          current
        DESCRIPTION
            "Tone definition table index for the intrusion tone."
        DEFVAL          { -1 }
        ::= { phoneIfToneEntry 7 }

    phoneIfTonePositiveAckDef     OBJECT-TYPE
        SYNTAX          ToneDefTabIndex
        MAX-ACCESS      read-write
        STATUS          current
        DESCRIPTION
            "Tone definition table index for the positive acknowledgement."
        DEFVAL          { -1 }
        ::= { phoneIfToneEntry 8 }

    phoneIfToneNegativeAckDef     OBJECT-TYPE
        SYNTAX          ToneDefTabIndex
        MAX-ACCESS      read-write
        STATUS          current
        DESCRIPTION
            "Tone definition table index for the negative acknowledgement."
        DEFVAL          { -1 }
        ::= { phoneIfToneEntry 9 }

    phoneIfToneContinousDialDef     OBJECT-TYPE
        SYNTAX          ToneDefTabIndex
        MAX-ACCESS      read-write
        STATUS          current
        DESCRIPTION
            "Tone definition table index for the continous dial tone."
        DEFVAL          { -1 }
        ::= { phoneIfToneEntry 10 }

    phoneIfToneCallWaitingDef     OBJECT-TYPE
        SYNTAX          ToneDefTabIndex
        MAX-ACCESS      read-write
        STATUS          current
        DESCRIPTION
            "Tone definition table index for the call waiting tone."
        DEFVAL          { -1 }
        ::= { phoneIfToneEntry 11 }

    phoneIfToneNotification1Def     OBJECT-TYPE
        SYNTAX          ToneDefTabIndex
        MAX-ACCESS      read-write
        STATUS          current
        DESCRIPTION
            "Tone definition table index for the notification tone 1."
        DEFVAL          { -1 }
        ::= { phoneIfToneEntry 12 }

    phoneIfToneNotification2Def     OBJECT-TYPE
        SYNTAX          ToneDefTabIndex
        MAX-ACCESS      read-write
        STATUS          current
        DESCRIPTION
            "Tone definition table index for the notification tone 2."
        DEFVAL          { -1 }
        ::= { phoneIfToneEntry 13 }

    phoneIfToneNotification3Def     OBJECT-TYPE
        SYNTAX          ToneDefTabIndex
        MAX-ACCESS      read-write
        STATUS          current
        DESCRIPTION
            "Tone definition table index for the notification tone 3."
        DEFVAL          { -1 }
        ::= { phoneIfToneEntry 14 }

    phoneIfToneRingbackDef     OBJECT-TYPE
        SYNTAX          ToneDefTabIndex
        MAX-ACCESS      read-write
        STATUS          current
        DESCRIPTION
            "Tone definition table index for the ring back tone."
        DEFVAL          { -1 }
        ::= { phoneIfToneEntry 15 }

    phoneIfToneFallbackDef     OBJECT-TYPE
        SYNTAX          ToneDefTabIndex
        MAX-ACCESS      read-write
        STATUS          current
        DESCRIPTION
            "Tone definition table index for the fall back tone."
        DEFVAL          { -1 }
        ::= { phoneIfToneEntry 16 }


---------------------------------------------------------------------------
-- 2. phoneIfToneDefinitionTable:  Tone Frequency and Cadence Table
---------------------------------------------------------------------------

    phoneIfToneDefinitionTable OBJECT-TYPE
        SYNTAX          SEQUENCE OF PhoneIfToneDefinitionEntry
        MAX-ACCESS      read-write
        STATUS          current
        DESCRIPTION
            "The phoneIfToneTable the contains configuration information
            for several tones on FXO and FXS lines."
        ::= { phone 2 }

    phoneIfToneDefinitionEntry OBJECT-TYPE
        SYNTAX          PhoneIfToneDefinitionEntry
        MAX-ACCESS      read-write
        STATUS          current
        DESCRIPTION
            ""
        INDEX           { phoneIfToneDefinitionIndex }
        ::= { phoneIfToneDefinitionTable 1 }

    PhoneIfToneDefinitionEntry ::=
        SEQUENCE {
            phoneIfToneDefinitionIndex          ToneDefTabIndex,
            phoneIfToneDefinitionType           INTEGER,
            phoneIfToneDefinitionFreq1          ToneFrequency,
            phoneIfToneDefinitionFreq2          ToneFrequency,
            phoneIfToneDefinitionLevel          INTEGER,
            phoneIfToneDefinitionCadence        CadenceString
        }

    phoneIfToneDefinitionIndex OBJECT-TYPE
        SYNTAX          ToneDefTabIndex
        MAX-ACCESS      read-write
        STATUS          current
        DESCRIPTION
            "Index of the set of tone cadences."
        DEFVAL          { 0 }
        ::= { phoneIfToneDefinitionEntry 1 }

    phoneIfToneDefinitionType OBJECT-TYPE
        SYNTAX          INTEGER { single(1), dual(2) }
        MAX-ACCESS      read-write
        STATUS          current
        DESCRIPTION
            "Type of tone:
                single(1)   just one frequency
                dual(2)     mix of two frequencies

             Variables phoneIfToneDefinitionFreq1 and phoneIfToneDefinitionFreq2
             specify frequencies involved as appropriate.

             Default value is single-tone."
        DEFVAL          { single }
        ::= { phoneIfToneDefinitionEntry 2 }

    phoneIfToneDefinitionFreq1 OBJECT-TYPE
        SYNTAX          ToneFrequency
        UNITS           "Hz"
        MAX-ACCESS      read-write
        STATUS          current
        DESCRIPTION
            "Tone frequency 1: only tone (for single-tone type) or first tone
	     of dual-tone signal (type dual-tone)."
        DEFVAL          { 425 }
        ::= { phoneIfToneDefinitionEntry 3 }

    phoneIfToneDefinitionFreq2 OBJECT-TYPE
        SYNTAX          ToneFrequency
        UNITS           "Hz"
        MAX-ACCESS      read-write
        STATUS          current
        DESCRIPTION
            "Tone frequency 2: second tone of dual-tone signal.
             Ignored for single-tone entries."
        DEFVAL          { 425 }
        ::= { phoneIfToneDefinitionEntry 4 }

    phoneIfToneDefinitionLevel OBJECT-TYPE
        SYNTAX          INTEGER (-50..0)
        UNITS           "dB"
        MAX-ACCESS      read-write
        STATUS          current
        DESCRIPTION
            "Tone signal level."
        DEFVAL          { -10 }
        ::= { phoneIfToneDefinitionEntry 5 }

    phoneIfToneDefinitionCadence OBJECT-TYPE
        SYNTAX          CadenceString
        MAX-ACCESS      read-write
        STATUS          current
        DESCRIPTION
            "Cadence string for this single/dual-tone.

             The cadence definition consists of times of activity, times 
             of no activity and some control information. All information
             is concatenated to one string and all times are given in 
             milliseconds.

             Synopsis:
                 [:] active time [:] [passive time] [:]...

             Arguments:
                 active time    a<time value in ms>
                 passive time   p<time value in ms>
                 :              start or end of loop interval
                 ,|-|blank      allowed delimiters for better reading
                                before and behind the timing arguments

             Examples:
                 1) a200,p200,a200
                    => two tones with 200ms pause in between

                 2) a1000 p500 : a200 p200 :
                    => a long pulse at the beginning followed by a
                       continous interval of short pulses

                 3) p2000-a1000
                    => a pulse of one second after two second pause

                 4) :a1000:
                    => definition for an endless active period
            "

        ::= { phoneIfToneDefinitionEntry 6 }


---------------------------------------------------------------------------
-- 3. phoneIfRingTable:  Ring Cadence Table
---------------------------------------------------------------------------

    phoneIfRingTable OBJECT-TYPE
        SYNTAX          SEQUENCE OF PhoneIfRingEntry
        MAX-ACCESS      read-write
        STATUS          current
        DESCRIPTION
            "The phoneIfRingTable the contains configuration information
            for ringing signals."
        ::= { phone 3 }

    phoneIfRingEntry OBJECT-TYPE
        SYNTAX          PhoneIfRingEntry
        MAX-ACCESS      read-write
        STATUS          current
        DESCRIPTION
            ""
        INDEX           { phoneIfRingIndex }
        ::= { phoneIfRingTable 1 }

    PhoneIfRingEntry ::=
        SEQUENCE {
            phoneIfRingIndex                    RingTabIndex,
            phoneIfRingInternCadence            CadenceString,
            phoneIfRingExternCadence            CadenceString,
            phoneIfRingInquiryCadence           CadenceString,
            phoneIfRingInternRecallCadence      CadenceString,
            phoneIfRingExternRecallCadence      CadenceString,
            phoneIfRingInternCallBackCadence    CadenceString,
            phoneIfRingExternCallBackCadence    CadenceString,
            phoneIfRingInternDoorCadence        CadenceString,
            phoneIfRingAlarmCadence             CadenceString,
            phoneIfRingAnnouncementCadence      CadenceString,
            phoneIfRingIntercomCadence          CadenceString,
            phoneIfRingChiefCadence             CadenceString,
            phoneIfRingSecretaryCadence         CadenceString,
            phoneIfRingMwiCadence               CadenceString,
            phoneIfRingWebServiceCadence        CadenceString
        }

    phoneIfRingIndex OBJECT-TYPE
        SYNTAX          RingTabIndex
        MAX-ACCESS      read-write
        STATUS          current
        DESCRIPTION
            "Index of the set of ring cadences."
        DEFVAL          { 0 }
        ::= { phoneIfRingEntry 1 }

    phoneIfRingInternCadence OBJECT-TYPE
        SYNTAX          CadenceString
        MAX-ACCESS      read-write
        STATUS          current
        DESCRIPTION
            "Ring cadence definition string for an internal call. 
             For a description of allowed format refer to 
             phoneIfToneDefinitionCadence."
        ::= { phoneIfRingEntry 2 }

    phoneIfRingExternCadence OBJECT-TYPE
        SYNTAX          CadenceString
        MAX-ACCESS      read-write
        STATUS          current
        DESCRIPTION
            "Ring cadence definition string for an external call. 
             For a description of allowed format refer to 
             phoneIfToneDefinitionCadence."
        ::= { phoneIfRingEntry 3 }

    phoneIfRingInquiryCadence OBJECT-TYPE
        SYNTAX          CadenceString
        MAX-ACCESS      read-write
        STATUS          current
        DESCRIPTION
            "Ring cadence definition string for an inquiry call. 
             For a description of allowed format refer to 
             phoneIfToneDefinitionCadence."
        ::= { phoneIfRingEntry 4 }

    phoneIfRingInternRecallCadence OBJECT-TYPE
        SYNTAX          CadenceString
        MAX-ACCESS      read-write
        STATUS          current
        DESCRIPTION
            "Ring cadence definition string for internal recall. 
             For a description of allowed format refer to 
             phoneIfToneDefinitionCadence."
        ::= { phoneIfRingEntry 5 }

    phoneIfRingExternRecallCadence OBJECT-TYPE
        SYNTAX          CadenceString
        MAX-ACCESS      read-write
        STATUS          current
        DESCRIPTION
            "Ring cadence definition string for external recall. 
             For a description of allowed format refer to 
             phoneIfToneDefinitionCadence."
        ::= { phoneIfRingEntry 6 }

    phoneIfRingInternCallBackCadence OBJECT-TYPE
        SYNTAX          CadenceString
        MAX-ACCESS      read-write
        STATUS          current
        DESCRIPTION
            "Ring cadence definition string for internal call back. 
             For a description of allowed format refer to 
             phoneIfToneDefinitionCadence."
        ::= { phoneIfRingEntry 7 }

    phoneIfRingExternCallBackCadence OBJECT-TYPE
        SYNTAX          CadenceString
        MAX-ACCESS      read-write
        STATUS          current
        DESCRIPTION
            "Ring cadence definition string for external call back. 
             For a description of allowed format refer to 
             phoneIfToneDefinitionCadence."
        ::= { phoneIfRingEntry 8 }

    phoneIfRingInternDoorCadence OBJECT-TYPE
        SYNTAX          CadenceString
        MAX-ACCESS      read-write
        STATUS          current
        DESCRIPTION
            "Ring cadence definition string for an internal door call. 
             For a description of allowed format refer to 
             phoneIfToneDefinitionCadence."
        ::= { phoneIfRingEntry 9 }

    phoneIfRingAlarmCadence OBJECT-TYPE
        SYNTAX          CadenceString
        MAX-ACCESS      read-write
        STATUS          current
        DESCRIPTION
            "Ring cadence definition string for an alarm call. 
             For a description of allowed format refer to 
             phoneIfToneDefinitionCadence."
        ::= { phoneIfRingEntry 10 }

    phoneIfRingAnnouncementCadence OBJECT-TYPE
        SYNTAX          CadenceString
        MAX-ACCESS      read-write
        STATUS          current
        DESCRIPTION
            "Ring cadence definition string for an announcement call. 
             For a description of allowed format refer to 
             phoneIfToneDefinitionCadence."
        ::= { phoneIfRingEntry 11 }

    phoneIfRingIntercomCadence OBJECT-TYPE
        SYNTAX          CadenceString
        MAX-ACCESS      read-write
        STATUS          current
        DESCRIPTION
            "Ring cadence definition string for an intercom call. 
             For a description of allowed format refer to 
             phoneIfToneDefinitionCadence."
        ::= { phoneIfRingEntry 12 }

    phoneIfRingChiefCadence OBJECT-TYPE
        SYNTAX          CadenceString
        MAX-ACCESS      read-write
        STATUS          current
        DESCRIPTION
            "Ring cadence definition string for an chief call. 
             For a description of allowed format refer to 
             phoneIfToneDefinitionCadence."
        ::= { phoneIfRingEntry 13 }

    phoneIfRingSecretaryCadence OBJECT-TYPE
        SYNTAX          CadenceString
        MAX-ACCESS      read-write
        STATUS          current
        DESCRIPTION
            "Ring cadence definition string for an secretary call. 
             For a description of allowed format refer to 
             phoneIfToneDefinitionCadence."
        ::= { phoneIfRingEntry 14 }

    phoneIfRingMwiCadence OBJECT-TYPE
        SYNTAX          CadenceString
        MAX-ACCESS      read-write
        STATUS          current
        DESCRIPTION
            "Ring cadence definition string for a message waiting call. 
             For a description of allowed format refer to 
             phoneIfToneDefinitionCadence."
        ::= { phoneIfRingEntry 15 }

    phoneIfRingWebServiceCadence OBJECT-TYPE
        SYNTAX          CadenceString
        MAX-ACCESS      read-write
        STATUS          current
        DESCRIPTION
            "Ring cadence definition string for a web service call. 
             For a description of allowed format refer to 
             phoneIfToneDefinitionCadence."
        ::= { phoneIfRingEntry 16 }


END
