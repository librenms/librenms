-- This file is corresponding to Release 10.2.3.100 from 2018/07/18 00:00:00


---------------------------------------------------------------------------
-- (C)opyright 2017 bintec elmeg GmbH
-- $RCSfile: mib-gui,v $
-- $Revision: 1.2 $
-- $Date: 2017-03-13 13:44:04 $
---------------------------------------------------------------------------

BINTEC-GUI-MIB DEFINITIONS ::= BEGIN

IMPORTS
    MODULE-IDENTITY, OBJECT-TYPE,
    Integer32, Unsigned32, 
    mib-2, enterprises
        FROM SNMPv2-SMI
    TruthValue
	FROM SNMPv2-TC
    DisplayString
	FROM RFC1158-MIB
    gui
	FROM BINTEC-MIB;

---------------------------------------------------------------------------

guiMIB MODULE-IDENTITY
    LAST-UPDATED "201702010000Z"
    ORGANIZATION "bintec elmeg GmbH"
    CONTACT-INFO
            "EMail:   info@bintec-elmeg.com
             Web:     www.bintec-elmeg.com
            "
    DESCRIPTION
            "The MIB module for GUI data entities.
            "
    REVISION     "201702010000Z"
    DESCRIPTION
            "Initial version."

    ::= { gui 1 }

guiAdmin	OBJECT IDENTIFIER 
::= { guiMIB 1 }

    guiAdmVideoHelpUrl OBJECT-TYPE
        SYNTAX  DisplayString
        MAX-ACCESS  read-write
        STATUS  current
        DESCRIPTION
            "Specifies a URL where video help support is available.
            "
            DEFVAL { "" }
    ::= { guiAdmin 1 }

    guiAdmAutosave OBJECT-TYPE
        SYNTAX          TruthValue
        MAX-ACCESS      read-write
        STATUS          current
        DESCRIPTION
            "This value determines if GUI auto save is enabled (true) or disabled
             (false)."
        DEFVAL { false }
        ::= { guiAdmin 2 }

END
