-- This file is corresponding to Release 10.2.3.100 from 2018/07/18 00:00:00


---------------------------------------------------------------------------
-- (C)opyright 2010-2014 bintec elmeg GmbH
-- $RCSfile: mib-ikev2,v $
-- $Revision: 1.11 $
-- $Date: 2018-03-06 14:47:58 $
---------------------------------------------------------------------------

FEC-IKEV2-MIB DEFINITIONS ::= BEGIN

IMPORTS
    MODULE-IDENTITY, OBJECT-TYPE, NOTIFICATION-TYPE, enterprises, 
    IpAddress, TimeTicks, Counter32, snmpModules, mib-2, Unsigned32, Counter64
        FROM SNMPv2-SMI
    DisplayString, TestAndIncr, TimeStamp
        FROM SNMPv2-TC
    MODULE-COMPLIANCE, OBJECT-GROUP, NOTIFICATION-GROUP
        FROM SNMPv2-CONF
    ipsec, Date, HexValue, BitValue
        FROM BINTEC-MIB
    InetAddressIPv6 
        FROM INET-ADDRESS-MIB;
 
---------------------------------------------------------------------------

---------------------------------------------------------------------------

ikev2MIB MODULE-IDENTITY
    LAST-UPDATED "201803060000Z"
    ORGANIZATION "bintec elmeg GmbH"
    CONTACT-INFO "EMail:   info@bintec-elmeg.com
                  Web:     www.bintec-elmeg.com"
    DESCRIPTION  "Management Information for IKEv2 of IPSec Subsystem"

    ::= { ipsec 252 }

---------------------------------------------------------------------------

-- IKE Security Associations Table

	ikev2SaTable OBJECT-TYPE
            SYNTAX  SEQUENCE OF Ikev2SaEntry
            MAX-ACCESS  not-accessible
            STATUS  current
            DESCRIPTION
		"This table contains the list of currently active IKE security
		 associations, that are created using IKEv2 protocol."
	::= { ipsec 21 }

	ikev2SaEntry OBJECT-TYPE
            SYNTAX  Ikev2SaEntry
            MAX-ACCESS  not-accessible
            STATUS  current
            DESCRIPTION
		"This object contains an IKE security association."
	    INDEX   {
		ikev2SaIndex
	    }
            ::= { ikev2SaTable 1 }

	Ikev2SaEntry ::=
            SEQUENCE {
		ikev2SaIndex			INTEGER,
		ikev2SaState			INTEGER, 
		ikev2SaAuthMethod		INTEGER,
		ikev2SaEncAlg			INTEGER,
		ikev2SaIntegAlg			INTEGER,
		ikev2SaPrfAlg			INTEGER,
		ikev2SaGroup			INTEGER,
		ikev2SaRole			INTEGER, 
		ikev2SaLocalId			DisplayString,
		ikev2SaRemoteId			DisplayString,
		ikev2SaLocalIp			IpAddress,
		ikev2SaRemoteIp			IpAddress,
		ikev2SaSpiI			OCTET STRING,
		ikev2SaSpiR			OCTET STRING,
		ikev2SaCreated			Date,
		ikev2SaLastUsed			Date,
		ikev2SaExpires			Date,
		ikev2SaNumCerts			INTEGER,
		ikev2SaNumNegotiations		INTEGER, 
		ikev2SaBytes			INTEGER, 
		ikev2SaPeerIndex		INTEGER, 
		ikev2SaLocalPort		INTEGER,
		ikev2SaRemotePort		INTEGER,




		ikev2SaRekeys			Date
            }

	ikev2SaIndex OBJECT-TYPE
	    SYNTAX INTEGER
            MAX-ACCESS  read-only
            STATUS  current
            DESCRIPTION
		 "A unique index for this entry."
	::= { ikev2SaEntry 1 }

	ikev2SaState OBJECT-TYPE
	    SYNTAX INTEGER {
		negotiating(1), -- the SA is still being negotiated
		established(2),	-- the SA negotiation is finished
		waiting-for-remove(3), -- the SA is waiting for removal
		delete(7)	       -- mark the SA for deletion
	    }
	    MAX-ACCESS read-write
	    STATUS current
	    DESCRIPTION
		"This object specifies the state of the SA.
		  Possible values:
		   negotiating(1),        -- the SA is still being negotiated
		   established(2),        -- the SA negotiation is finished
		   waiting-for-remove(3), -- the SA is waiting for removal
		   delete(7)	          -- mark the SA for deletion."
	    DEFVAL { negotiating }
	::= { ikev2SaEntry 2 }

	ikev2SaAuthMethod OBJECT-TYPE
	    SYNTAX INTEGER {
		pre-sh-key(1), 	-- Authentication using pre shared keys
		dss-sig(2), 	-- Authentication using DSS signatures
		rsa-sig(3), 	-- Authentication using RSA signatures
		rsa-enc(4), 	-- Authentication using RSA encryption
		rsa-enc-rev(5) 	-- Authentication using revised RSA encryption
	    }
	    MAX-ACCESS read-only
	    STATUS current
	    DESCRIPTION
		"The authentication method used when creating this SA.
		  Possible values:
		   pre-sh-key(1), 	-- Authentication using pre shared keys
		   dss-sig(2), 	  -- Authentication using DSS signatures
		   rsa-sig(3), 	  -- Authentication using RSA signatures
		   rsa-enc(4), 	  -- Authentication using RSA encryption
		   rsa-enc-rev(5) -- Authentication using revised RSA encryption."
	::= { ikev2SaEntry 3 }

	ikev2SaEncAlg OBJECT-TYPE
	    SYNTAX INTEGER {
		des(2),
		des3(3),
		rc5(4),
		idea(5),
		cast(6),
		blowfish(7),
		aes-cbc(12),
		aes-ctr(13)
	    }
	    MAX-ACCESS read-only
	    STATUS current
	    DESCRIPTION
		"The encryption algorithm used for the IKE_SA.
		  Possible values:
		   des(2),
		   des3(3),
	           rc5(4),
		   idea(5),
		   cast(6),
		   blowfish(7),
		   aes-cbc(12),
		   aes-ctr(13)"
	::= { ikev2SaEntry 4 }

	ikev2SaIntegAlg OBJECT-TYPE
	    SYNTAX INTEGER {
		hmac-md5-96(1),		-- The MD5 hash algorithm
		hmac-sha1-96(2),	-- The Secure Hash Algorithm
		hmac-sha2-256(3),	-- SHA2 256 bit
		hmac-sha2-384(4),	-- SHA2 384 bit
		hmac-sha2-512(5)	-- SHA2 512 bit
	    }
	    MAX-ACCESS read-only
	    STATUS current
	    DESCRIPTION
		"The integrity protection algorithm used for the IKE_SA.
		  Possible values:
		   hmac-md5-96(1),
		   hmac-sha1-96(2),
		   hmac-sha2-256(3),
		   hmac-sha2-384(4),
		   hmac-sha2-512(5)"
	::= { ikev2SaEntry 5 }

	ikev2SaPrfAlg OBJECT-TYPE
	    SYNTAX INTEGER {
		hmac-md5(1),		-- The MD5 hash algorithm
		hmac-sha1(2),		-- The Secure Hash Algorithm
		hmac-sha2-256(3),	-- SHA2 256 bit
		hmac-sha2-384(4),	-- SHA2 384 bit
		hmac-sha2-512(5)	-- SHA2 512 bit
	    }
	    MAX-ACCESS read-only
	    STATUS current
	    DESCRIPTION
		"The hash algorithm used for the pseudo random function.
		  Possible values:
		   hmac-md5(1),	
		   hmac-sha1(2),
		   hmac-sha2-256(3),
		   hmac-sha2-384(4),
		   hmac-sha2-512(5)"
	::= { ikev2SaEntry 6 }

	ikev2SaGroup OBJECT-TYPE
	    SYNTAX INTEGER
	    MAX-ACCESS read-only
	    STATUS current
	    DESCRIPTION
		"The Diffie-Hellman group used for the IKE_SA.
		  Possible values:
		   1	- DH-group 768-bit MODP,	
		   2	- DH-group 1024-bit MODP"
	::= { ikev2SaEntry 7 }

	ikev2SaRole OBJECT-TYPE
	    SYNTAX INTEGER {
		initiator(1), 	-- this end initiated the SA negotiation
		responder(2)	-- the remote end initiated the SA negotiation
	    }
	    MAX-ACCESS read-only
	    STATUS current
	    DESCRIPTION
		"This object specifies by which side the SA
		 negotiation was initiated.
		  Possible values:
		   initiator(1), -- this end	initiated the SA negotiation 
		   responder(2)  -- the remote end initiated the SA negotiation."
	::= { ikev2SaEntry 8 }

	ikev2SaLocalId OBJECT-TYPE
	    SYNTAX DisplayString
	    MAX-ACCESS read-only
	    STATUS current
	    DESCRIPTION
		"The local ID used for authentication."
	::= { ikev2SaEntry 9 }

	ikev2SaRemoteId OBJECT-TYPE
	    SYNTAX DisplayString
	    MAX-ACCESS read-only
	    STATUS current
	    DESCRIPTION
		"The remote ID used for authentication."
	::= { ikev2SaEntry 10 }

	ikev2SaLocalIp OBJECT-TYPE
	    SYNTAX IpAddress
	    MAX-ACCESS read-only
	    STATUS current
	    DESCRIPTION
		"The local IP address used in the IKE communication."
	::= { ikev2SaEntry 11 }

	ikev2SaRemoteIp OBJECT-TYPE
	    SYNTAX IpAddress
	    MAX-ACCESS read-only
	    STATUS current
	    DESCRIPTION
		"The remote IP address used in the IKE communication."
	::= { ikev2SaEntry 12 }

	ikev2SaSpiI OBJECT-TYPE
	    SYNTAX OCTET STRING
	    MAX-ACCESS read-only
	    STATUS current
	    DESCRIPTION
		"The SPI of the initiator."
	::= { ikev2SaEntry 13 }

	ikev2SaSpiR OBJECT-TYPE
	    SYNTAX OCTET STRING
	    MAX-ACCESS read-only
	    STATUS current
	    DESCRIPTION
		"The SPI of the responder."
	::= { ikev2SaEntry 14 }

	ikev2SaCreated OBJECT-TYPE
	    SYNTAX  Date 
	    MAX-ACCESS  read-only
	    STATUS  current
	    DESCRIPTION
		"Time the SA was created."
	::= { ikev2SaEntry 15 }

	ikev2SaLastUsed OBJECT-TYPE
	    SYNTAX  Date 
	    MAX-ACCESS  read-only
	    STATUS  current
	    DESCRIPTION
		"Time the SA was used last."
	::= { ikev2SaEntry 16 }

	ikev2SaExpires OBJECT-TYPE
	    SYNTAX  Date 
	    MAX-ACCESS  read-only
	    STATUS  current
	    DESCRIPTION
		"Time the SA will expire."
	::= { ikev2SaEntry 17 }

	ikev2SaNumCerts OBJECT-TYPE
	    SYNTAX INTEGER	
	    MAX-ACCESS read-only
	    STATUS current
	    DESCRIPTION
		"The number of certificates received from the remote
		 side when negotiating this SA."
	::= { ikev2SaEntry 18 }

	ikev2SaNumNegotiations OBJECT-TYPE
	    SYNTAX INTEGER
            MAX-ACCESS  read-only
            STATUS  current
            DESCRIPTION
		 "This object specifies the number of currently active 
		  negotiations for this SA."
	::= { ikev2SaEntry 19 }

	ikev2SaBytes OBJECT-TYPE
	    SYNTAX INTEGER
            MAX-ACCESS  read-only
            STATUS  current
            DESCRIPTION
		 "Number of bytes transmitted using this SA."
	::= { ikev2SaEntry 20 }

	ikev2SaPeerIndex OBJECT-TYPE
	    SYNTAX INTEGER
	    MAX-ACCESS read-only
	    STATUS current
	    DESCRIPTION
		"The index of the peer for which this SA was created."
	::= { ikev2SaEntry 21 }

	ikev2SaLocalPort OBJECT-TYPE
	    SYNTAX INTEGER (0..65535)
            MAX-ACCESS  read-only
            STATUS  current
            DESCRIPTION
		 "Local port currently used for the SA."
	::= { ikev2SaEntry 22 }

	ikev2SaRemotePort OBJECT-TYPE
	    SYNTAX INTEGER (0..65535)
            MAX-ACCESS  read-only
            STATUS  current
            DESCRIPTION
		 "Remote port currently used for the SA."
	::= { ikev2SaEntry 23 }


	ikev2SaRekeys OBJECT-TYPE
	    SYNTAX  Date 
	    MAX-ACCESS  read-only
	    STATUS  current
	    DESCRIPTION
		"Time the SA will rekey."
	::= { ikev2SaEntry 26 }

-- End IKE Security Associations Table


-- IKEv2 Profile Table

	ikev2ProfileTable OBJECT-TYPE
            SYNTAX  SEQUENCE OF Ikev2ProfileEntry
            MAX-ACCESS  not-accessible
            STATUS  current
            DESCRIPTION
		"This table contains the list of IKE_SA profiles.
		 these profiles are neede when using IKEv2 protocol."
	::= { ipsec 22 }

	ikev2ProfileEntry OBJECT-TYPE
            SYNTAX  Ikev2ProfileEntry
            MAX-ACCESS  not-accessible
            STATUS  current
            DESCRIPTION
		"This object contains an IKE_SA profile."
	    INDEX   {
		ikev2PrfIndex
	    }
            ::= { ikev2ProfileTable 1 }

	Ikev2ProfileEntry ::=
	    SEQUENCE {
		ikev2PrfIndex			Unsigned32,
		ikev2PrfDescription		DisplayString,
		ikev2PrfProposal		Unsigned32,
		ikev2PrfBlockTime		INTEGER,
		ikev2PrfNatT			INTEGER,
		ikev2PrfMtuMax			INTEGER,
		ikev2PrfLifeSeconds		Unsigned32,
		ikev2PrfAliveCheck		INTEGER,
		ikev2PrfLifeRekeyPercent	INTEGER
	    }

	ikev2PrfIndex OBJECT-TYPE
	    SYNTAX Unsigned32 (1..4294967295)
	    MAX-ACCESS read-write
	    STATUS current
	    DESCRIPTION
		"A unique index identifying this entry."
	::= { ikev2ProfileEntry 1 }

	ikev2PrfDescription OBJECT-TYPE
	    SYNTAX DisplayString
	    MAX-ACCESS read-write
	    STATUS current
	    DESCRIPTION
		"An optional description for this profile."
	::= { ikev2ProfileEntry 2 }

	ikev2PrfProposal OBJECT-TYPE
	    SYNTAX Unsigned32
	    MAX-ACCESS read-write
	    STATUS current
	    DESCRIPTION
		"The index of the first IKE proposal which may be used
		 for IKE SA negotiation with this profile."
	::= { ikev2ProfileEntry 3 }

	ikev2PrfBlockTime OBJECT-TYPE
	    SYNTAX INTEGER (-1..86400) 
		UNITS "seconds"
	    MAX-ACCESS read-write
	    STATUS current
	    DESCRIPTION
		"This object specifies the time in seconds for which a peer is
		 blocked for any IPSec operations after a phase 1 initiator
		 negotiation failed.
		  Special values:
		   -1: use settings from global profile (do not block by default)
		    0: do not block the peer at all."
	    DEFVAL { -1 }
	::= { ikev2ProfileEntry 4 }

	ikev2PrfNatT OBJECT-TYPE
	    SYNTAX INTEGER {
		enabled(1), 	-- enable Nat-Traversal
		disabled(2),	-- disable Nat-Traversal
		default(3),   	-- use value from default profile 
                                -- (enabled, if this is the default profile)
		delete(4)   	-- mark this entry for deletion 
	    }
	    MAX-ACCESS read-write
	    STATUS current
	    DESCRIPTION
		"This object specifies whether NAT-Traversal is enabled
		  Possible values:
		   enabled(1), 	-- enable Nat-Traversal
		   disabled(2),	-- disable Nat-Traversal
		   default(3)   -- use value from default profile 
                                -- (disabled, if this is the default profile)."
	    DEFVAL { default }
	::= { ikev2ProfileEntry 5 }

	ikev2PrfMtuMax OBJECT-TYPE
	    SYNTAX INTEGER (0..65535)
	    MAX-ACCESS read-write
	    STATUS current
	    DESCRIPTION
		"The maximum MTU value allowed for ipsecPeerMtu.
		 This variable affects only peers with ipsecPeerStatIpVersion 'ipv4'.
		 Zero means use value from global profile, 
		 if this is the global profile, 1418 is assumed.
		 Nonzero values smaller than 214 are reset to the minimum of 214."
	    DEFVAL { 0 }
	::= { ikev2ProfileEntry 6 }

	ikev2PrfLifeSeconds OBJECT-TYPE
	    SYNTAX Unsigned32
		UNITS "seconds"
	    MAX-ACCESS read-write
	    STATUS current
	    DESCRIPTION
		"The time (in seconds) after which an SA will be rekeyed."
	    DEFVAL { 3600 }
	::= { ikev2ProfileEntry 7 }

	ikev2PrfAliveCheck OBJECT-TYPE
	    SYNTAX INTEGER {
		enabled(1), 	-- enable alive check
		disabled(2)	-- disable alive check
	    }
	    MAX-ACCESS read-write
	    STATUS current
	    DESCRIPTION
		"This object specifies if a check is done to see whether the 
		 other endpoint is alive.
		(only for IKEv2)."
	    DEFVAL { enabled }
	::= { ikev2ProfileEntry 8 }


	ikev2PrfLifeRekeyPercent OBJECT-TYPE
	    SYNTAX INTEGER (50..100)
	    MAX-ACCESS read-write
	    STATUS current
	    DESCRIPTION
		"The percentage of the lifetime after which rekeying is started."
	    DEFVAL { 80 }
	::= { ikev2ProfileEntry 10 }

-- End IKE SA Profile Table (IKEv2)


-- IKEv2 Redirect Table

	ikev2RedirectTable OBJECT-TYPE
            SYNTAX  SEQUENCE OF Ikev2RedirectEntry
            MAX-ACCESS  not-accessible
            STATUS  current
            DESCRIPTION
		"This table contains entries created as result of a 
		 gateway-initiated redirect. The maximum count of entries
		 can be configured using ipsecGlobContMaxIkev2RdrEntries."
	::= { ipsec 23 }

	ikev2RedirectEntry OBJECT-TYPE
            SYNTAX  Ikev2RedirectEntry
            MAX-ACCESS  not-accessible
            STATUS  current
            DESCRIPTION
		"This object contains information for redirecting a bundle
		 within an IKE SA."
	    INDEX   {
		ikev2RdrPeerIndex, ikev2RdrNewGW, ikev2RdrTime
	    }
            ::= { ikev2RedirectTable 1 }

	Ikev2RedirectEntry ::=
	    SEQUENCE {
		ikev2RdrPeerIndex            INTEGER,
		ikev2RdrNewGW                DisplayString,
		ikev2RdrTime                 Date,
		ikev2RdrState                INTEGER,
		ikev2RdrLocalAddress         IpAddress,
		ikev2RdrLocalMaskLen         INTEGER,
		ikev2RdrLocalRange           IpAddress,
		ikev2RdrLocalPort            INTEGER,
		ikev2RdrRemoteAddress        IpAddress,
		ikev2RdrRemoteMaskLen        INTEGER,
		ikev2RdrRemoteRange          IpAddress,
		ikev2RdrRemotePort           INTEGER,
	        ikev2RdrIp6LocalAddress      InetAddressIPv6,
	        ikev2RdrIp6LocalMaskLen      INTEGER,
	        ikev2RdrIp6RemoteAddress     InetAddressIPv6,
		ikev2RdrIp6RemoteMaskLen     INTEGER,
		ikev2RdrProto                INTEGER,
		ikev2RdrRedirectedFrom       IpAddress,
		ikev2RdrIp6RedirectedFrom    InetAddressIPv6
 	    }

	ikev2RdrPeerIndex OBJECT-TYPE
	    SYNTAX INTEGER
	    MAX-ACCESS read-only
	    STATUS current
	    DESCRIPTION
		"The index of the peer which is redirected."
	::= { ikev2RedirectEntry 1 }

	ikev2RdrNewGW OBJECT-TYPE
	    SYNTAX DisplayString
	    MAX-ACCESS read-only
	    STATUS current
	    DESCRIPTION
		"The IP-address of the new gateway the peer is redirected to.
		 This object may contain either an IP address or a domain name."
	::= { ikev2RedirectEntry 2 }

	ikev2RdrTime OBJECT-TYPE
	    SYNTAX Date
	    MAX-ACCESS read-only
	    STATUS current
	    DESCRIPTION
		"Time the redirect request was received."
	::= { ikev2RedirectEntry 3 }

	ikev2RdrState OBJECT-TYPE
	    SYNTAX INTEGER {
		new(1), 	-- newly created entry 
		handled(2)	-- already handled entry
	    }
	    MAX-ACCESS read-only
	    STATUS current
	    DESCRIPTION
		"The current state of the received redirect request.
		 Possible values:
                  new(1),	-- The request is newly received and not handled yet.
		  handled(2),	-- The request is already handled."
	    DEFVAL { new }
	::= { ikev2RedirectEntry 4 }

	ikev2RdrLocalAddress OBJECT-TYPE
	    SYNTAX IpAddress
	    MAX-ACCESS read-only
	    STATUS current
	    DESCRIPTION
		"The local address (host or network or range start address)
                 of the traffic selectors,
                 source for outbound, destination for inbound."
	::= { ikev2RedirectEntry 5 }

	ikev2RdrLocalMaskLen OBJECT-TYPE
	    SYNTAX INTEGER
	    MAX-ACCESS read-only
	    STATUS current
	    DESCRIPTION
		"The local network masklen of the traffic selectors,
                 source for outbound, destination for inbound."
	::= { ikev2RedirectEntry 6 }

	ikev2RdrLocalRange OBJECT-TYPE
	    SYNTAX IpAddress
	    MAX-ACCESS read-only
	    STATUS current
	    DESCRIPTION
		"The local address range end address of the traffic selectors,
                 source for outbound, destination for inbound."
	::= { ikev2RedirectEntry 7 }

	ikev2RdrLocalPort OBJECT-TYPE
	    SYNTAX INTEGER
	    MAX-ACCESS read-only
	    STATUS current
	    DESCRIPTION
		"The local port of the traffic selectors,
                 source for outbound, destination for inbound."
	::= { ikev2RedirectEntry 8 }

	ikev2RdrRemoteAddress OBJECT-TYPE
	    SYNTAX IpAddress
	    MAX-ACCESS read-only
	    STATUS current
	    DESCRIPTION
		"The remote address (host or network or range start address)
                 of the traffic selectors
                 source for outbound, destination for inbound."
	::= { ikev2RedirectEntry 9 }

	ikev2RdrRemoteMaskLen OBJECT-TYPE
	    SYNTAX INTEGER
	    MAX-ACCESS read-only
	    STATUS current
	    DESCRIPTION
		"The remote network masklen of the traffic selectors
                 source for outbound, destination for inbound."
	::= { ikev2RedirectEntry 10 }

	ikev2RdrRemoteRange OBJECT-TYPE
	    SYNTAX IpAddress
	    MAX-ACCESS read-only
	    STATUS current
	    DESCRIPTION
		"The remote address range end address of the traffic selectors
                 source for outbound, destination for inbound."
	::= { ikev2RedirectEntry 11 }

	ikev2RdrRemotePort OBJECT-TYPE
	    SYNTAX INTEGER
	    MAX-ACCESS read-only
	    STATUS current
	    DESCRIPTION
		"The remote port of the traffic selectors
                 source for outbound, destination for inbound."
	::= { ikev2RedirectEntry 12 }

	ikev2RdrIp6LocalAddress OBJECT-TYPE
	    SYNTAX InetAddressIPv6
	    MAX-ACCESS read-only
	    STATUS current
	    DESCRIPTION
		"The local IPv6 address (host or network or range start address)
                 of the traffic selectors, source for outbound,
                 destination for inbound."
	::= { ikev2RedirectEntry 13 }

	ikev2RdrIp6LocalMaskLen OBJECT-TYPE
	    SYNTAX INTEGER
	    MAX-ACCESS read-only
	    STATUS current
	    DESCRIPTION
		"Indicates the prefix length associated with the source
                 (local) IPv6 address."
	::= { ikev2RedirectEntry 14 }

	ikev2RdrIp6RemoteAddress OBJECT-TYPE
	    SYNTAX InetAddressIPv6
	    MAX-ACCESS read-only
	    STATUS current
	    DESCRIPTION
		"The remote IPv6 address (host or network or range start
                 address) of the traffic selectors, source for outbound,
                 destination for inbound."
	::= { ikev2RedirectEntry 15 }

	ikev2RdrIp6RemoteMaskLen OBJECT-TYPE
	    SYNTAX INTEGER
	    MAX-ACCESS read-only
	    STATUS current
	    DESCRIPTION
		"Indicates the prefix length associated with the destination
                 (remote) IPv6 address."
	::= { ikev2RedirectEntry 16 }

	ikev2RdrProto OBJECT-TYPE
	    SYNTAX INTEGER {
                icmp(1),
                igmp(2),
                ggp(3),
                ipip(4),
                st(5),
                tcp(6),
                cbt(7),
                egp(8),
                igp(9),
                bbn(10),
                nvp(11),
                pup(12),
                argus(13),
                emcon(14),
                xnet(15),
                chaos(16),
                udp(17),
                mux(18),
                dcn(19),
                hmp(20),
                prm(21),
                xns(22),
                trunk1(23),
                trunk2(24),
                leaf1(25),
                leaf2(26),
                rdp(27),
                irtp(28),
                isotp4(29),
                netblt(30),
                mfe(31),
                merit(32),
                sep(33),
                pc3(34),
                idpr(35),
                xtp(36),
                ddp(37),
                idprc(38),
                tp(39),
                il(40),
                ipv6(41),
                sdrp(42),
                ipv6route(43),
                ipv6frag(44),
                idrp(45),
                rsvp(46),
                gre(47),
                mhrp(48),
                bna(49),
                esp(50),
                ah(51),
                inlsp(52),
                swipe(53),
                narp(54),
                mobile(55),
                tlsp(56),
                skip(57),
                ipv6icmp(58),
                ipv6nonxt(59),
                ipv6opts(60),
                ipproto-61(61),
                cftp(62),
                local(63),
                sat(64),
                kryptolan(65),
                rvd(66),
                ippc(67),
                distfs(68),
                satmon(69),
                visa(70),
                ipcv(71),
                cpnx(72),
                cphb(73),
                wsn(74),
                pvp(75),
                brsatmon(76),
                sunnd(77),
                wbmon(78),
                wbexpak(79),
                isoip(80),
                vmtp(81),
                securevmtp(82),
                vines(83),
                ttp(84),
                nsfnet(85),
                dgp(86),
                tcf(87),
                eigrp(88),
                ospfigp(89),
                sprite(90),
                larp(91),
                mtp(92),
                ax25(93),
                ipwip(94),
                micp(95),
                scc(96),
                etherip(97),
                encap(98),
                encrypt(99),
                gmtp(100),
                ifmp(101),
                pnni(102),
                pim(103),
                aris(104),
                scps(105),
                qnx(106),
                an(107),
                ippcp(108),
                snp(109),
                compaq(110),
                ipxip(111),
                vrrp(112),
                pgm(113),
                hop0(114),
                l2tp(115),
                ipproto-116(116),
                ipproto-117(117),
                ipproto-118(118),
                ipproto-119(119),
                ipproto-120(120),
                ipproto-121(121),
                ipproto-122(122),
                ipproto-123(123),
                ipproto-124(124),
                ipproto-125(125),
                ipproto-126(126),
                ipproto-127(127),
                ipproto-128(128),
                ipproto-129(129),
                ipproto-130(130),
                ipproto-131(131),
                ipproto-132(132),
                ipproto-133(133),
                ipproto-134(134),
                ipproto-135(135),
                ipproto-136(136),
                ipproto-137(137),
                ipproto-138(138),
                ipproto-139(139),
                ipproto-140(140),
                ipproto-141(141),
                ipproto-142(142),
                ipproto-143(143),
                ipproto-144(144),
                ipproto-145(145),
                ipproto-146(146),
                ipproto-147(147),
                ipproto-148(148),
                ipproto-149(149),
                ipproto-150(150),
                ipproto-151(151),
                ipproto-152(152),
                ipproto-153(153),
                ipproto-154(154),
                ipproto-155(155),
                ipproto-156(156),
                ipproto-157(157),
                ipproto-158(158),
                ipproto-159(159),
                ipproto-160(160),
                ipproto-161(161),
                ipproto-162(162),
                ipproto-163(163),
                ipproto-164(164),
                ipproto-165(165),
                ipproto-166(166),
                ipproto-167(167),
                ipproto-168(168),
                ipproto-169(169),
                ipproto-170(170),
                ipproto-171(171),
                ipproto-172(172),
                ipproto-173(173),
                ipproto-174(174),
                ipproto-175(175),
                ipproto-176(176),
                ipproto-177(177),
                ipproto-178(178),
                ipproto-179(179),
                ipproto-180(180),
                ipproto-181(181),
                ipproto-182(182),
                ipproto-183(183),
                ipproto-184(184),
                ipproto-185(185),
                ipproto-186(186),
                ipproto-187(187),
                ipproto-188(188),
                ipproto-189(189),
                ipproto-190(190),
                ipproto-191(191),
                ipproto-192(192),
                ipproto-193(193),
                ipproto-194(194),
                ipproto-195(195),
                ipproto-196(196),
                ipproto-197(197),
                ipproto-198(198),
                ipproto-199(199),
                ipproto-200(200),
                ipproto-201(201),
                ipproto-202(202),
                ipproto-203(203),
                ipproto-204(204),
                ipproto-205(205),
                ipproto-206(206),
                ipproto-207(207),
                ipproto-208(208),
                ipproto-209(209),
                ipproto-210(210),
                ipproto-211(211),
                ipproto-212(212),
                ipproto-213(213),
                ipproto-214(214),
                ipproto-215(215),
                ipproto-216(216),
                ipproto-217(217),
                ipproto-218(218),
                ipproto-219(219),
                ipproto-220(220),
                ipproto-221(221),
                ipproto-222(222),
                ipproto-223(223),
                ipproto-224(224),
                ipproto-225(225),
                ipproto-226(226),
                ipproto-227(227),
                ipproto-228(228),
                ipproto-229(229),
                ipproto-230(230),
                ipproto-231(231),
                ipproto-232(232),
                ipproto-233(233),
                ipproto-234(234),
                ipproto-235(235),
                ipproto-236(236),
                ipproto-237(237),
                ipproto-238(238),
                ipproto-239(239),
                ipproto-240(240),
                ipproto-241(241),
                ipproto-242(242),
                ipproto-243(243),
                ipproto-244(244),
                ipproto-245(245),
                ipproto-246(246),
                ipproto-247(247),
                ipproto-248(248),
                ipproto-249(249),
                ipproto-250(250),
                ipproto-251(251),
                ipproto-252(252),
                ipproto-253(253),
                ipproto-254(254),
                dont-verify(255)
    	        }
	    MAX-ACCESS read-only
	    STATUS current
	    DESCRIPTION
		"The protocol of the traffic selectors."
	::= { ikev2RedirectEntry 17 }

	ikev2RdrRedirectedFrom OBJECT-TYPE
	    SYNTAX      IpAddress
	    MAX-ACCESS  read-only
	    STATUS      current
   	    DESCRIPTION
		"The IP address of the original gateway from which we 
	         got redirected."
	::= { ikev2RedirectEntry 18 }

	ikev2RdrIp6RedirectedFrom OBJECT-TYPE
	    SYNTAX      InetAddressIPv6
    	    MAX-ACCESS  read-only
    	    STATUS      current
    	    DESCRIPTION
		"The IPv6 address of the original gateway from which we 
	         got redirected."
    	::= { ikev2RedirectEntry 19 }

-- End IKEv2 Redirect Table

END
