-- This file is corresponding to Release 10.2.3.100 from 2018/07/18 00:00:00


-- (C)opyright 2005-2014 bintec elmeg Gmbh, All Rights Reserved
-- $RCSfile: mib-voipstat,v $
-- $Revision: 1.2 $

BIANCA-BRICK-VOIPSTAT-MIB DEFINITIONS ::= BEGIN

	IMPORTS
	    MODULE-IDENTITY, OBJECT-TYPE, NOTIFICATION-TYPE,
            Counter64, Counter32, TimeTicks
                FROM SNMPv2-SMI

	    enterprises
		FROM RFC1155-SMI

            TimeStamp, DisplayString
                FROM SNMPv2-TC

            MODULE-COMPLIANCE, OBJECT-GROUP, NOTIFICATION-GROUP
                FROM SNMPv2-CONF
	    
            voip, Date
		FROM BINTEC-MIB;

voipStatMIB    MODULE-IDENTITY
            LAST-UPDATED "201504080000Z"
        
            ORGANIZATION "bintec elmeg GmbH"
        
            CONTACT-INFO "EMail:   info@bintec-elmeg.com
                          Web:     www.bintec-elmeg.com"
        
            DESCRIPTION  "Vendor specific Management Information for VoIP statistics"

            REVISION     "201504080000Z"
            DESCRIPTION  "VoIP statistics as required by TR-069/VoiceService."
        ::= { voip 22 }


        voipStatRtcpHistoryMaxEntries OBJECT-TYPE
	    SYNTAX      INTEGER (0..65535)
	    MAX-ACCESS  read-write
	    STATUS      current

	    DESCRIPTION
		"Maximum number of voipStatRtcpHistory entries in memory."
	    DEFVAL { 20 }
	::= { voipStatMIB 1 }
        
    -- voipStatCallTable

        voipStatCallTable OBJECT-TYPE
	    SYNTAX      SEQUENCE OF VoipStatCallEntry
	    MAX-ACCESS  not-accessible
	    STATUS      current
	    DESCRIPTION
	    "Contains all call related Statistics"
	::= { voipStatMIB 2 }

	voipStatCallEntry OBJECT-TYPE
	    SYNTAX      VoipStatCallEntry
	    MAX-ACCESS  not-accessible
	    STATUS      current
	    DESCRIPTION
		"Describes the call statistics for a SIP account."
	    INDEX { voipStatCallIndex }
	::= { voipStatCallTable 1 }

	VoipStatCallEntry ::=
	    SEQUENCE {
		voipStatCallIndex	        INTEGER,
		voipStatCallProvider	        INTEGER,
		voipStatCallAddress	        INTEGER,
		voipStatCallAction	        INTEGER,
		voipStatCallLastReset	        Date,
		voipStatCallCount	        Counter32,
                voipStatCallOutAttempt	        Counter32,
		voipStatCallOutAnswered	        Counter32,
		voipStatCallOutConnect	        Counter32,
		voipStatCallOutFailed	        Counter32,
		voipStatCallInReceive	        Counter32,
		voipStatCallInAnswered	        Counter32,
		voipStatCallInConnect	        Counter32,
		voipStatCallInFailed	        Counter32,
		voipStatCallDropped	        Counter32,
		voipStatCallTotalConnectTime    INTEGER,
		voipStatCallServerDownTime	INTEGER,
		voipStatCallTxPackets	        Counter64,
		voipStatCallTxBytes	        Counter64,
		voipStatCallRxPackets	        Counter64,
		voipStatCallRxBytes	        Counter64
	   }

      voipStatCallIndex OBJECT-TYPE
       	    SYNTAX      INTEGER 
	    MAX-ACCESS  read-only
	    STATUS      current

	    DESCRIPTION
		"Unique Index value of this Entry"
	::= { voipStatCallEntry 1 }

      voipStatCallProvider OBJECT-TYPE
       	    SYNTAX      INTEGER 
	    MAX-ACCESS  read-only
	    STATUS      current

	    DESCRIPTION
		"Reference to the SIP Account the statistic belongs."
	::= { voipStatCallEntry 2 }

       voipStatCallAddress OBJECT-TYPE
            SYNTAX      INTEGER
	    MAX-ACCESS  read-only
	    STATUS      current

	    DESCRIPTION
		"Reference to the subscriber Number of the
                 concerning SIP Account."
	::= { voipStatCallEntry 3 }

        voipStatCallAction  OBJECT-TYPE
 	    SYNTAX      INTEGER {
                done(1),
                reset(2)
            }
	    MAX-ACCESS  read-write
	    STATUS      current

	    DESCRIPTION
		"Reset all Statistic values to zero.
                    done    - reset executed
                    reset   - reset request
                "
	    DEFVAL { done }
	::= { voipStatCallEntry 4 }

       voipStatCallLastReset   OBJECT-TYPE	   
	    SYNTAX      Date
	    MAX-ACCESS  read-only
	    STATUS      current

	    DESCRIPTION
		"Date and time of last reset"
	::= { voipStatCallEntry 5 }

       voipStatCallCount   OBJECT-TYPE
 	    SYNTAX      Counter32
	    MAX-ACCESS  read-only
	    STATUS      current

	    DESCRIPTION
		"Total number of calls (incoming and outgoing) including
                also not successfully completed calls"
	::= { voipStatCallEntry 6 }

       voipStatCallOutAttempt   OBJECT-TYPE
 	    SYNTAX      Counter32
	    MAX-ACCESS  read-only
	    STATUS      current

	    DESCRIPTION
		"Total attempted outgoing calls."
	::= { voipStatCallEntry 7 }

       voipStatCallOutAnswered	OBJECT-TYPE
            SYNTAX      Counter32
	    MAX-ACCESS  read-only
	    STATUS      current

	    DESCRIPTION
		"Total outgoing calls answered."
	::= { voipStatCallEntry 8 }

        voipStatCallOutConnect  OBJECT-TYPE
            SYNTAX      Counter32
	    MAX-ACCESS  read-only
	    STATUS      current

	    DESCRIPTION
		"Total outgoing successfully completed calls."
	::= { voipStatCallEntry 9 }

        voipStatCallOutFailed   OBJECT-TYPE
            SYNTAX      Counter32
	    MAX-ACCESS  read-only
	    STATUS      current

	    DESCRIPTION
		"Total outgoing not successfully completed calls."
	::= { voipStatCallEntry 10 }

        voipStatCallInReceive   OBJECT-TYPE
            SYNTAX      Counter32
	    MAX-ACCESS  read-only
	    STATUS      current

	    DESCRIPTION
                "Total incoming calls received"
	::= { voipStatCallEntry 11 }

        voipStatCallInAnswered  OBJECT-TYPE
            SYNTAX      Counter32
	    MAX-ACCESS  read-only
	    STATUS      current

	    DESCRIPTION
                "Total incoming calls signalled to the local user."
	::= { voipStatCallEntry 12 }

        voipStatCallInConnect   OBJECT-TYPE
            SYNTAX      Counter32
	    MAX-ACCESS  read-only
	    STATUS      current

	    DESCRIPTION
                "Total incoming calls that successfully completed 
                call setup signaling."
	::= { voipStatCallEntry 13 }

        voipStatCallInFailed    OBJECT-TYPE
            SYNTAX      Counter32
	    MAX-ACCESS  read-only
	    STATUS      current

	    DESCRIPTION
		"Total incoming calls that failed to successfully 
                complete call setup signaling."
	::= { voipStatCallEntry 14 }

        voipStatCallDropped OBJECT-TYPE
            SYNTAX      Counter32
	    MAX-ACCESS  read-only
	    STATUS      current

	    DESCRIPTION
                "Total calls that were successfully connected 
                (incoming or outgoing), but dropped unexpectedly 
                while in progress without explicit user termination."
	::= { voipStatCallEntry 15 }

        voipStatCallTotalConnectTime   OBJECT-TYPE
            SYNTAX      INTEGER
	    UNITS       "seconds"
            MAX-ACCESS  read-only
	    STATUS      current

	    DESCRIPTION
                "Cumulative call connected duration in seconds."
	::= { voipStatCallEntry 16 }

        voipStatCallServerDownTime    OBJECT-TYPE	    
            SYNTAX      INTEGER
	    UNITS       "seconds"
	    MAX-ACCESS  read-only
	    STATUS      current

	    DESCRIPTION
                "The number of seconds the CPE is unable to maintain a connection to the server
                not including time in which overall network connectivity is unavailable.
                Applies only to SIP."
	::= { voipStatCallEntry 17 }

        voipStatCallTxPackets   OBJECT-TYPE	    
            SYNTAX      Counter64
	    MAX-ACCESS  read-only
	    STATUS      current

	    DESCRIPTION
                "Total number of RTP packets sent for this line."
	::= { voipStatCallEntry 18 }

       voipStatCallTxBytes   OBJECT-TYPE	    
            SYNTAX  Counter64
	    MAX-ACCESS  read-only
	    STATUS  current

	    DESCRIPTION
                "Total number of RTP payload bytes sent for this line."
	::= { voipStatCallEntry 19 }

        voipStatCallRxPackets   OBJECT-TYPE	    
            SYNTAX  Counter64
	    MAX-ACCESS  read-only
	    STATUS  current

	    DESCRIPTION
                "Total number of RTP packets received for this line."
	::= { voipStatCallEntry 20 }

       voipStatCallRxBytes   OBJECT-TYPE	    
            SYNTAX  Counter64
	    MAX-ACCESS  read-only
	    STATUS  current

	    DESCRIPTION
                "Total number of RTP payload bytes received for this line."
	::= { voipStatCallEntry 21 }

    -- voipStatRtcpTable

        voipStatRtcpTable OBJECT-TYPE
	    SYNTAX  SEQUENCE OF VoipStatRtcpEntry
	    MAX-ACCESS  not-accessible
	    STATUS  current
	    DESCRIPTION
	        "Contains a current call Statistic"
	::= { voipStatMIB 3 }

	voipStatRtcpEntry OBJECT-TYPE
	    SYNTAX VoipStatRtcpEntry
	    MAX-ACCESS not-accessible
	    STATUS current
	    DESCRIPTION
		"Describes current call specific statistics 
                 calculated from RTCP contents"
	    INDEX { voipStatRtcpIndex }
	::= { voipStatRtcpTable 1 }

	VoipStatRtcpEntry ::=
	    SEQUENCE {
		voipStatRtcpIndex	                INTEGER,
		voipStatRtcpReference	                INTEGER,
		voipStatRtcpDuration	                TimeStamp,
		voipStatRtcpRoundTripDelay              INTEGER,
		voipStatRtcpAvgRoundTripDelay           INTEGER,
                voipStatRtcpLocalIdent                  DisplayString,
		voipStatRtcpLocalInterarrivalJitter     INTEGER,
		voipStatRtcpLocalAvgInterarrivalJitter  INTEGER,
                voipStatRtcpLocalPackets                Counter32,
                voipStatRtcpLocalBytes                  Counter32,
                voipStatRtcpLocalPacketLossRate         INTEGER,
                voipStatRtcpRemoteIdent                 DisplayString,
		voipStatRtcpRemoteInterarrivalJitter    INTEGER,
		voipStatRtcpRemoteAvgInterarrivalJitter INTEGER,
	        voipStatRtcpRemotePackets               Counter32,
                voipStatRtcpRemoteBytes                 Counter32,
                voipStatRtcpRemotePacketLossRate        INTEGER
	   }

        voipStatRtcpIndex OBJECT-TYPE
       	    SYNTAX      INTEGER 
	    MAX-ACCESS  read-only
	    STATUS      current

	    DESCRIPTION
		"Unique Index to reference this call"
	::= { voipStatRtcpEntry 1 }

        voipStatRtcpReference OBJECT-TYPE
       	    SYNTAX      INTEGER 
	    MAX-ACCESS  read-only
	    STATUS      current

	    DESCRIPTION
		"Reference to the Account the local statistic belongs."
	::= { voipStatRtcpEntry 2 }

         voipStatRtcpDuration OBJECT-TYPE
       	    SYNTAX      TimeStamp
	    MAX-ACCESS  read-only
	    STATUS      current

	    DESCRIPTION
		"The Duration of the current call."
	::= { voipStatRtcpEntry 3 }

        voipStatRtcpRoundTripDelay  OBJECT-TYPE
            SYNTAX      INTEGER
            UNITS       "microseconds"
	    MAX-ACCESS  read-only
	    STATUS      current

	    DESCRIPTION
                "Current round trip delay in microseconds calculated as defined in
                [Section6.4/RFC3550]."
	::= { voipStatRtcpEntry 4 }

        voipStatRtcpAvgRoundTripDelay    OBJECT-TYPE
            SYNTAX      INTEGER
            UNITS       "microseconds"
	    MAX-ACCESS  read-only
	    STATUS  current

	    DESCRIPTION
                "Average round trip delay in microseconds since the beginning of the current call.
                Average of the RoundTripDelay statistic accumulated each time the delay is
                calculated.
                "
	::= { voipStatRtcpEntry 5 }

        voipStatRtcpLocalIdent  OBJECT-TYPE
            SYNTAX      DisplayString
	    MAX-ACCESS  read-only
	    STATUS      current

	    DESCRIPTION 
                "Current Local Source Description transfered in SDES defined
                 in [Section6.5/RFC3550]."
	::= { voipStatRtcpEntry 6 }

       voipStatRtcpLocalInterarrivalJitter  OBJECT-TYPE
            SYNTAX      INTEGER
            UNITS       "microseconds"
	    MAX-ACCESS  read-only
	    STATUS      current

	    DESCRIPTION
		"Current receive interarrival jitter in microseconds. Calculated from J(i) as
                defined in [Section6.4/RFC3550], with units converted to microseconds."
	::= { voipStatRtcpEntry 7 }

        voipStatRtcpLocalAvgInterarrivalJitter   OBJECT-TYPE
            SYNTAX      INTEGER
            UNITS       "microseconds"
	    MAX-ACCESS  read-only
	    STATUS      current

	    DESCRIPTION
		"Average receive interarrival jitter in microseconds since the beginning of the
                current call. Calculated as the average of D(i,j) as defined in
                [Section6.4/RFC3550], with units converted to microseconds."
	::= { voipStatRtcpEntry 8 }

        voipStatRtcpLocalPackets  OBJECT-TYPE
            SYNTAX      Counter32
	    MAX-ACCESS  read-only
	    STATUS      current

	    DESCRIPTION
		"Current count of local generated RTP data Packets for this call from DSP."
	::= { voipStatRtcpEntry 9 }

       voipStatRtcpLocalBytes  OBJECT-TYPE
            SYNTAX      Counter32
	    MAX-ACCESS  read-only
	    STATUS      current

	    DESCRIPTION
		"Current count of local generated RTP data bytes for this call from DSP."
	::= { voipStatRtcpEntry 10 }

       voipStatRtcpLocalPacketLossRate  OBJECT-TYPE
            SYNTAX      INTEGER (0..100)
            UNITS       "percent"
	    MAX-ACCESS  read-only
	    STATUS  current

	    DESCRIPTION
                "Current receive packet loss rate in percent, calculated as defined in
                [Section6.4/RFC3550]."
	::= { voipStatRtcpEntry 11 }

        voipStatRtcpRemoteIdent  OBJECT-TYPE
            SYNTAX      DisplayString
	    MAX-ACCESS  read-only
	    STATUS      current

	    DESCRIPTION 
                "Current Source Description defined in [Section6.5/RFC3550]"
	::= { voipStatRtcpEntry 12 }

        voipStatRtcpRemoteInterarrivalJitter  OBJECT-TYPE
            SYNTAX      INTEGER
            UNITS       "microseconds"
	    MAX-ACCESS  read-only
	    STATUS      current

	    DESCRIPTION 
                "Current Interarrival jitter in microseconds as reported from the far-end device via
                RTCP. Calculated from J(i) as defined in [Section64./RFC3550], with units converted
                to microseconds."
	::= { voipStatRtcpEntry 13 }

        voipStatRtcpRemoteAvgInterarrivalJitter   OBJECT-TYPE
            SYNTAX      INTEGER
            UNITS       "microseconds"
	    MAX-ACCESS  read-only
	    STATUS      current

	    DESCRIPTION
                "Average far-end interarrival jitter in microseconds since the beginning of the
                current call. Calculated as the average of the interarrival jitter values reported
                by the far-end, with units converted to microseconds."
	::= { voipStatRtcpEntry 14 }

       voipStatRtcpRemotePackets  OBJECT-TYPE
            SYNTAX      Counter32
	    MAX-ACCESS  read-only
	    STATUS      current

	    DESCRIPTION
		"Current count of far-end generated RTP data Packets for this call from RTCP signalling."
	::= { voipStatRtcpEntry 15 }

       voipStatRtcpRemoteBytes  OBJECT-TYPE
            SYNTAX      Counter32
	    MAX-ACCESS  read-only
	    STATUS      current

	    DESCRIPTION
		"Current count of far-end generated RTP data bytes for this call from RTCP signalling."
	::= { voipStatRtcpEntry 16 }

        voipStatRtcpRemotePacketLossRate  OBJECT-TYPE
            SYNTAX      INTEGER (0..100)
            UNITS       "percent"
	    MAX-ACCESS  read-only
	    STATUS      current

	    DESCRIPTION
                "Current far end receive packet lost rate in percent, calculated as defined in
                [Section6.4/RFC3550]."
	::= { voipStatRtcpEntry 17 }


-- voipStatRtcpHistoryTable

        voipStatRtcpHistoryTable OBJECT-TYPE
	    SYNTAX      SEQUENCE OF VoipStatRtcpHistoryEntry
	    MAX-ACCESS  not-accessible
	    STATUS      current
	    DESCRIPTION
	        "Contains a competed call Statistic"
	::= { voipStatMIB 4 }

	voipStatRtcpHistoryEntry OBJECT-TYPE
	    SYNTAX VoipStatRtcpHistoryEntry
	    MAX-ACCESS not-accessible
	    STATUS current
	    DESCRIPTION
		"Describes completed call specific statistics 
                 calculated from voipStatRtcpEntryTable"
	    INDEX { voipStatRtcpHistoryIndex }
	::= { voipStatRtcpHistoryTable 1 }

	VoipStatRtcpHistoryEntry ::=
	    SEQUENCE {
		voipStatRtcpHistoryIndex	                INTEGER,
		voipStatRtcpHistoryReference	                INTEGER,
		voipStatRtcpHistoryDate	                        Date,
                voipStatRtcpHistoryDuration	                TimeTicks,
		voipStatRtcpHistoryAvgRoundTripDelay            INTEGER,
                voipStatRtcpHistoryLocalIdent                   DisplayString,
                voipStatRtcpHistoryLocalAvgInterarrivalJitter   INTEGER,
                voipStatRtcpHistoryLocalPackets                 INTEGER,
                voipStatRtcpHistoryLocalBytes                   INTEGER,
                voipStatRtcpHistoryLocalPacketLossRate          INTEGER,
                voipStatRtcpHistoryRemoteIdent                  DisplayString,
		voipStatRtcpHistoryRemoteAvgInterarrivalJitter  INTEGER,
	        voipStatRtcpHistoryRemotePackets                INTEGER,
                voipStatRtcpHistoryRemoteBytes                  INTEGER,
                voipStatRtcpHistoryRemotePacketLossRate         INTEGER
	   }

        voipStatRtcpHistoryIndex OBJECT-TYPE
       	    SYNTAX      INTEGER 
	    MAX-ACCESS  read-only
	    STATUS      current

	    DESCRIPTION
		"Unique Index to reference this entry"
	::= { voipStatRtcpHistoryEntry 1 }

        voipStatRtcpHistoryReference OBJECT-TYPE
       	    SYNTAX      INTEGER 
	    MAX-ACCESS  read-only
	    STATUS      current

	    DESCRIPTION
		"Reference to the Account the local statistic belongs."
	::= { voipStatRtcpHistoryEntry 2 }

         voipStatRtcpHistoryDate OBJECT-TYPE
       	    SYNTAX      Date
	    MAX-ACCESS  read-only
	    STATUS      current

	    DESCRIPTION
		"The Starttime and date of the call."
	::= { voipStatRtcpHistoryEntry 3 }

        voipStatRtcpHistoryDuration OBJECT-TYPE
            SYNTAX
       	                TimeTicks
	    MAX-ACCESS  read-only
	    STATUS      current

	    DESCRIPTION
		"The Duration of the call."
	::= { voipStatRtcpHistoryEntry 4 }

        voipStatRtcpHistoryAvgRoundTripDelay    OBJECT-TYPE
            SYNTAX      INTEGER
            UNITS       "microseconds"
	    MAX-ACCESS  read-only
	    STATUS      current

	    DESCRIPTION
                "Average round trip delay in microseconds taken from related voipStatRtcpEntry"
	::= { voipStatRtcpHistoryEntry 5 }

        voipStatRtcpHistoryLocalIdent  OBJECT-TYPE
            SYNTAX      DisplayString
	    MAX-ACCESS  read-only
	    STATUS      current

	    DESCRIPTION 
                "Local Source Description taken from voipStatRtcpEntry."
	::= { voipStatRtcpHistoryEntry 6 }


        voipStatRtcpHistoryLocalAvgInterarrivalJitter   OBJECT-TYPE
            SYNTAX      INTEGER
            UNITS       "microseconds"
	    MAX-ACCESS  read-only
	    STATUS      current

	    DESCRIPTION
		"Average receive interarrival jitter in microseconds taken from related
                voipStatRtcpEntry."
	::= { voipStatRtcpHistoryEntry 7 }

       voipStatRtcpHistoryLocalPackets  OBJECT-TYPE
            SYNTAX      INTEGER
	    MAX-ACCESS  read-only
	    STATUS      current

	    DESCRIPTION
		"Count of local generated RTP data Packets."
	::= { voipStatRtcpHistoryEntry 8 }

       voipStatRtcpHistoryLocalBytes  OBJECT-TYPE
            SYNTAX      INTEGER
	    MAX-ACCESS  read-only
	    STATUS      current

	    DESCRIPTION
		"Count of local generated RTP data bytes."
	::= { voipStatRtcpHistoryEntry 9 }

       voipStatRtcpHistoryLocalPacketLossRate  OBJECT-TYPE
            SYNTAX      INTEGER (0..100)
            UNITS       "percent"
	    MAX-ACCESS  read-only
	    STATUS      current

	    DESCRIPTION
                "Receive packet loss rate in percent taken from related voipStatRtcpEntry."
	::= { voipStatRtcpHistoryEntry 10 }

        voipStatRtcpHistoryRemoteIdent   OBJECT-TYPE
            SYNTAX      DisplayString
	    MAX-ACCESS  read-only
	    STATUS      current

	    DESCRIPTION
                "Far-end Source Description taken from voipStatRtcpEntry."
	::= { voipStatRtcpHistoryEntry 11 }

        voipStatRtcpHistoryRemoteAvgInterarrivalJitter   OBJECT-TYPE
            SYNTAX      INTEGER
            UNITS       "microseconds"
	    MAX-ACCESS  read-only
	    STATUS      current

	    DESCRIPTION
                "Average far-end interarrival jitter in microseconds taken from related
                voipStatRtcpEntry."
	::= { voipStatRtcpHistoryEntry 12 }

       voipStatRtcpHistoryRemotePackets  OBJECT-TYPE
            SYNTAX      INTEGER
	    MAX-ACCESS  read-only
	    STATUS      current

	    DESCRIPTION
		"Count of far-end generated RTP data Packets taken from related voipStatRtcpEntry."
	::= { voipStatRtcpHistoryEntry 13 }

       voipStatRtcpHistoryRemoteBytes  OBJECT-TYPE
            SYNTAX      INTEGER
	    MAX-ACCESS  read-only
	    STATUS      current

	    DESCRIPTION
		"Current count of far-end generated RTP data bytes taken from related voipStatRtcpEntry."
	::= { voipStatRtcpHistoryEntry 14 }

        voipStatRtcpHistoryRemotePacketLossRate  OBJECT-TYPE
            SYNTAX      INTEGER (0..100)
            UNITS       "percent"
	    MAX-ACCESS  read-only
	    STATUS      current

	    DESCRIPTION
                "Far end receive packet lost rate in percent taken from related voipStatRtcpEntry."
	::= { voipStatRtcpHistoryEntry 15 }
---------------------------------------------------------------------------
END
