-- This file is corresponding to Release 10.2.3.100 from 2018/07/18 00:00:00


---------------------------------------------------------------------------
-- (C)opyright 2006-2014 bintec elmeg GmbH
-- $RCSfile: mib-acct,v $
-- $Revision: 1.11 $
-- $Date: 2014-02-07 10:37:49 $
-- Author: stefans
---------------------------------------------------------------------------

BINTEC-ACCTSTORE DEFINITIONS ::= BEGIN

IMPORTS
    MODULE-IDENTITY, OBJECT-TYPE, NOTIFICATION-TYPE,
    Integer32, Unsigned32, Counter32, Counter64, IpAddress, TimeTicks,
    mib-2, enterprises
        FROM SNMPv2-SMI

    DisplayString, TimeStamp
        FROM SNMPv2-TC

    Date, admin-2
	FROM BINTEC-MIB

    MODULE-COMPLIANCE, OBJECT-GROUP, NOTIFICATION-GROUP
        FROM SNMPv2-CONF;

-- This MIB file contains MIBs for accouting store
--  group admin: 
-- 

---------------------------------------------------------------------------
--  acctStore MIB

acctStoreMIB MODULE-IDENTITY
    LAST-UPDATED "200604040000Z"
    ORGANIZATION "bintec elmeg GmbH"
    CONTACT-INFO
            "EMail:   info@bintec-elmeg.de
	     Web:     www.bintec-elmeg.de
	    "
    DESCRIPTION
            "The MIB module for .ccouting store
            "
    REVISION      "200604040000Z"
    DESCRIPTION
            "Initial version." 

    ::= { admin-2 4 }

---------------------------------------------------------------------------
-- acctStore		accouting store configuration
---------------------------------------------------------------------------

acctStore OBJECT IDENTIFIER ::= { acctStoreMIB 1 }

    acctStoreMode  OBJECT-TYPE
	SYNTAX      INTEGER { off(1), ram(2), flash(3) }
	MAX-ACCESS  read-write
	STATUS      current
	DESCRIPTION
	    "This enables the accouting store
	        off  : all new entries in acctStoreTable are deleted at once
		ram  : entries are only kept in table (not saved permanent)
		flash: entries are saved permanent
	    ."
	DEFVAL { flash }
    ::= { acctStore 1 }

    acctStoreSize   OBJECT-TYPE
	SYNTAX      INTEGER (64 .. 8096)
	MAX-ACCESS  read-write
	STATUS      current

	DESCRIPTION
	    "maximum size of accouting store (in kBytes)."
    ::= { acctStore 2 }

    acctStoreUsed  OBJECT-TYPE
	SYNTAX      INTEGER (-1 .. 100)
	MAX-ACCESS  read-only
	STATUS      current
	DESCRIPTION
	    "Current used size of availabe memory (percent).
	     -1: error occured during file creation"
    ::= { acctStore 3 }


---------------------------------------------------------------------------
-- acctStoreTable	accouting store entries
---------------------------------------------------------------------------

acctStoreTable OBJECT-TYPE
    SYNTAX      SEQUENCE OF AcctStoreEntry
    MAX-ACCESS  not-accessible
    STATUS      current
    DESCRIPTION
	    "This tables contains the current entries within the accouting 
	     store.
	     Entries are created by the system.
	     The user may only create a new entry with Type=delete, to
	     delete some or all entries.
	    "
    ::= { acctStoreMIB 2 }

    acctStoreEntry OBJECT-TYPE
	SYNTAX      AcctStoreEntry
	MAX-ACCESS  not-accessible
	STATUS      current
	DESCRIPTION
		"(one entry of acctStoreTable)"
	INDEX   { acctStoreType }
	::= { acctStoreTable 1 }

    AcctStoreEntry ::=
	SEQUENCE {
	    acctStoreType		INTEGER,
	    acctStoreContent		INTEGER,
	    acctStoreDirection		INTEGER,
	    acctStoreId			INTEGER,
	    acctStoreTime		Date,
	    acctStoreInfo		DisplayString
    }

    acctStoreType OBJECT-TYPE
	SYNTAX      INTEGER { volatile(1), permanent(2), delete(3) }
	MAX-ACCESS  read-write
	STATUS      current
	DESCRIPTION
		"Storage type of this entry.
		 volatile : the entry is not saved permanent in flash
		 permanent: the entry is saved permanent in flash
		 delete   : command to delete entries.
		"
	DEFVAL  { volatile }
	::= { acctStoreEntry 1 }

    acctStoreContent OBJECT-TYPE
	SYNTAX      INTEGER { call(1), ifc(2) }
	MAX-ACCESS  read-write
	STATUS      current
	DESCRIPTION
		"Content type of this entry.
		 call : dialup call
		 ifc  : interface traffic summary 
		        the RX/TX-octets of the enabled interfaces are saved 
			automatically each 10 min.
			The storage of appropriate interfaces is enabled 
			with IP-Accouting in ipExtIfTable:Accounting
		"
	::= { acctStoreEntry 2 }

    acctStoreDirection OBJECT-TYPE
	SYNTAX      INTEGER { in(1), out(2), sum(3) }
	MAX-ACCESS  read-write
	STATUS      current
	DESCRIPTION
		"Direction type of this entry.
		 in/out : for content call
		 sum    : summary entry (total call charge, ifc summary)
		"
	::= { acctStoreEntry 3 }

    acctStoreId OBJECT-TYPE
	SYNTAX      INTEGER (0..16777215)	-- 24 Bit
	MAX-ACCESS  read-write
	STATUS      current
	DESCRIPTION
		"Entry-Id of the origin:
		  content call: internal phone-number or UserId
		  content ifc : interface index
		"
	::= { acctStoreEntry 4 }

    acctStoreTime OBJECT-TYPE
	SYNTAX      Date
	MAX-ACCESS  read-write
	STATUS      current
	DESCRIPTION
		"Date and time of this entry creation
		"
	::= { acctStoreEntry 5 }

    acctStoreInfo OBJECT-TYPE
	SYNTAX      DisplayString
	MAX-ACCESS  read-write
	STATUS      current
	DESCRIPTION
		"Accounting string. The fields are separated by ';'
		  The fields are converted to following types:
		     - Integer: 1-8 bytes length
		     - String : must have leading ' ' (max length 15 chars)
		     - BCD num: must have leading '.' (max length 30 digits)
				(e.g. phone number)
		  e.g. 123;;456; Infostr;.091196730;
		"
	::= { acctStoreEntry 6 }


-- end: acctStore
---------------------------------------------------------------------------

END
