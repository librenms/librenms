-- This file is corresponding to Release 10.2.3.100 from 2018/07/18 00:00:00


-- (C)opyright 2003-2014 bintec elmeg GmbH, All Rights Reserved

BIANCA-BRICK-PPPOEAC-MIB DEFINITIONS ::= BEGIN

        IMPORTS
            IpAddress, Counter, enterprises
                FROM RFC1155-SMI

            DisplayString
                FROM RFC1158-MIB
 
            OBJECT-TYPE
                FROM RFC-1212;

    bintec 	OBJECT IDENTIFIER ::= { enterprises 272 }
    bibo	OBJECT IDENTIFIER ::= { bintec 4 }
    pppoe	OBJECT IDENTIFIER
	::= { bibo 24 }


    -- PPPoE Group extensions for PPPoE server mode

    -- pppoeAcTable

	pppoeAcTable OBJECT-TYPE
	    SYNTAX  SEQUENCE OF PppoeAcEntry
	    ACCESS  not-accessible
	    STATUS  mandatory
	    DESCRIPTION
		"The pppoeAcTable is used to enable the PPPoE server
		mode (Access Concentrator) on the associated Ethernet
		interface.

		Creating entries: Entries are added by the user.

                Deleting entries: Entries are removed once the 
                respective variable pppoeAcChkService is
		set to delete(4)."
	::= { pppoe 3 }

	pppoeAcEntry OBJECT-TYPE
	    SYNTAX  PppoeAcEntry
	    ACCESS  not-accessible
	    STATUS  mandatory
	    DESCRIPTION
		""
	    INDEX   { pppoeAcEthIfIndex }
	::= { pppoeAcTable 1 }

	PppoeAcEntry ::=
	    SEQUENCE {
		pppoeAcEthIfIndex			INTEGER,
		pppoeAcChkService			INTEGER,
		pppoeAcName				DisplayString
	    }

	pppoeAcEthIfIndex OBJECT-TYPE
	    SYNTAX  INTEGER
	    ACCESS  read-write
	    STATUS  mandatory

	    DESCRIPTION
                "The interface index (ifIndex) of the associated Ethernet
		interface."
	::= { pppoeAcEntry 1 }
	
	pppoeAcChkService OBJECT-TYPE
	    SYNTAX  INTEGER { 
		accept-all(1),
		accept-from-list(2),
		delete(4)
	    } 
	    ACCESS  read-write
	    STATUS  mandatory

	    DESCRIPTION
		"If set to accept-all(1) this variable determines that
		- regardless of the PPPoE 'SERVICE-NAME' tag (see RFC 2516) -
		all PPPoE Active Discovery Initiation (PADI) packets will
		be accepted and answered with a PPPoE Active Discovery Offer
		(PADO) packet.
		If set to accept-from-list(2) only PADI packets with a
		'SERVICE-NAME' tag matching with one of the services
		specified via the pppoeAcServiceTable will be accepted and
		answered.
		If set to delete(4), this entry will be removed and PADI
		packets received on the associated Ethernet interface
		will be ignored."
		
	    DEFVAL { accept-all }
	::= { pppoeAcEntry 2 }

	pppoeAcName OBJECT-TYPE
	    SYNTAX  DisplayString
	    ACCESS  read-write
	    STATUS  mandatory

	    DESCRIPTION
		"The PPPoE AC-NAME to be used for PPPoE Active Discovery Offer
		(PADO) and PPPoE Active Discovery Session-confirmation (PADS)
		packet. If not specified, the given system name (sysName) will
		be used as fallback."
	::= { pppoeAcEntry 3 }


    -- pppoeAcServiceTable

        pppoeAcServiceTable OBJECT-TYPE
            SYNTAX  SEQUENCE OF PppoeAcServiceEntry
            ACCESS  not-accessible
            STATUS  mandatory
            DESCRIPTION
                "The pppoeAcServiceTable is used to specify the supported
		PPPoE service on the associated Ethernet interface.
		It's only relevant for the PPPoE server mode.

                Creating entries: Entries are added by the user.

                Deleting entries: Entries are removed once the respective
		variable pppoeAcServiceStatus is set to delete(3)."
        ::= { pppoe 4 }

        pppoeAcServiceEntry OBJECT-TYPE
            SYNTAX  PppoeAcServiceEntry
            ACCESS  not-accessible
            STATUS  mandatory
            DESCRIPTION
                ""
            INDEX   { pppoeAcServiceEthIfIndex }
        ::= { pppoeAcServiceTable 1 }

        PppoeAcServiceEntry ::=
            SEQUENCE {
                pppoeAcServiceEthIfIndex		INTEGER,
                pppoeAcServiceName			DisplayString,
                pppoeAcServiceStatus 			INTEGER
            }

        pppoeAcServiceEthIfIndex OBJECT-TYPE
            SYNTAX  INTEGER
            ACCESS  read-write
            STATUS  mandatory

            DESCRIPTION
                "The interface index (ifIndex) of the associated Ethernet
                interface."
        ::= { pppoeAcServiceEntry 1 }

	pppoeAcServiceName OBJECT-TYPE
	    SYNTAX  DisplayString
	    ACCESS  read-write
	    STATUS  mandatory

	    DESCRIPTION
		"The accepted PPPoE SERVICE-NAME for PPPoE Active Discovery Offer
		(PADO) and PPPoE Active Discovery Session-confirmation (PADS)
		packets."
	::= { pppoeAcServiceEntry 2 }

	pppoeAcServiceStatus OBJECT-TYPE
	    SYNTAX  INTEGER { 
		enabled(1),
		disabled(2),
		delete(3)
	    } 
	    ACCESS  read-write
	    STATUS  mandatory

	    DESCRIPTION
		"The administrative and operational status of this entry.
		If set to enabled(1), this entry will be considered for
		the PPPoE SERVICE-NAME check as described for the variable
		pppoeAcChkService.
		If set to disabled(2), this entry will be ignored.
		If set to delete(3), this entry will be removed."
	    DEFVAL { enabled }
	::= { pppoeAcServiceEntry 3 }


END
