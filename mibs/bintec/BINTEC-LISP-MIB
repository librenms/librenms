-- This file is corresponding to Release 10.2.3.100 from 2018/07/18 00:00:00


--
-- (C)opyright 2014 bintec elmeg GmbH, All Rights Reserved
--

BINTEC-LISP-MIB DEFINITIONS ::= BEGIN

IMPORTS
    MODULE-IDENTITY, OBJECT-TYPE,
    Counter32, Unsigned32, Counter64, IpAddress, TimeTicks  FROM SNMPv2-SMI
    DisplayString                                           FROM SNMPv2-TC
    vpn                                                     FROM BINTEC-MIB
    InterfaceIndexOrZero                                    FROM IF-MIB;


--
-- LISP-module
--

lispMIB MODULE-IDENTITY
    LAST-UPDATED    "201604210000Z"
    ORGANIZATION    "bintec elmeg GmbH"
    CONTACT-INFO    "EMail:     info@bintec-elmeg.com
                     Web:       www.bintec-elmeg.com"
    DESCRIPTION     "Locator/ID Separation Protocol (LISP)"
    ::= { vpn 9 }


--
-- Configured LISP-instances
--

lispInstTable OBJECT-TYPE
    SYNTAX      SEQUENCE OF LispInstEntry
    MAX-ACCESS  not-accessible
    STATUS      current
    DESCRIPTION
        "List of configured LISP-instances (see section 5.5 of RFC-6830).
         With each LISP-instance, a corresponding entry is stored in ifTable
         and biboAdmDeviceTable."
    ::= { lispMIB 1 }

lispInstEntry OBJECT-TYPE
    SYNTAX      LispInstEntry
    MAX-ACCESS  not-accessible
    STATUS      current
    DESCRIPTION
        ""
    INDEX       { lispInstId }
    ::= { lispInstTable 1 }

LispInstEntry ::=
    SEQUENCE {
        lispInstId              INTEGER,
        lispInstIndex           InterfaceIndexOrZero,
        lispInstAdminStatus     INTEGER,
        lispInstDescr           DisplayString,
        lispInstMtu             INTEGER,
        lispInstCacheMaxSites   Unsigned32,
        lispInstCacheMaxEtrs    Unsigned32,
        lispInstCacheMaxFrames  Unsigned32,
        lispInstDefaultTtl      Unsigned32,
        lispInstResolvingTtl    Unsigned32,
        lispInstDefTtlMode      INTEGER,
        lispInstProxyEtrAddr    IpAddress
    }

lispInstId OBJECT-TYPE
    SYNTAX      INTEGER (-1..16777215)
    MAX-ACCESS  read-write
    STATUS      current
    DESCRIPTION
        "Identifier for this LISP-instance (see section 5.5 of RFC-6830).
         Special value of -1 identifies default-instance. In this case,
         Instance-ID-field is skipped in related LISP-frames.
         Remark: At most one default-LISP-instance may be specified."
    ::= { lispInstEntry 1 }

lispInstIndex OBJECT-TYPE
    SYNTAX      InterfaceIndexOrZero
    MAX-ACCESS  read-only
    STATUS      current
    DESCRIPTION
        "Automatically selected index of virtual LISP-interface, stored as
         ifIndex in related ifTable-entry and stored as ipExtRtDstIfIndex in
         related ipExtRt-entries.
         Remark: Is set to zero if interface-selection fails."
    ::= { lispInstEntry 2 }

lispInstAdminStatus OBJECT-TYPE
    SYNTAX      INTEGER {
        active(1),
        inactive(2),
        delete(3)
    }
    MAX-ACCESS  read-write
    STATUS      current
    DESCRIPTION
        "Administrative status of LISP-instance.
         Set to delete for killing entry."
    DEFVAL      { active }
    ::= { lispInstEntry 3 }

lispInstDescr OBJECT-TYPE
    SYNTAX      DisplayString (SIZE (0..255))
    MAX-ACCESS  read-write
    STATUS      current
    DESCRIPTION
        "Optional name of LISP-instance, stored as ifDescr in related
         ifTable-entry.
         In case of empty string, ifDesc is set automatically."
    ::= { lispInstEntry 4 }

lispInstMtu OBJECT-TYPE
    SYNTAX      INTEGER (1..8192)
    UNITS       "bytes"
    MAX-ACCESS  read-write
    STATUS      current
    DESCRIPTION
        "Largest datagrams-size, stored as ifMtu in related ifTable-entry."
    DEFVAL      { 1444 }
    ::= { lispInstEntry 5 }

lispInstCacheMaxSites OBJECT-TYPE
    SYNTAX      Unsigned32
    MAX-ACCESS  read-write
    STATUS      current
    DESCRIPTION
        "Maximum number of stored lispCchSite entries for this LISP-instance."
    DEFVAL      { 100 }
    ::= { lispInstEntry 6 }

lispInstCacheMaxEtrs OBJECT-TYPE
    SYNTAX      Unsigned32
    MAX-ACCESS  read-write
    STATUS      current
    DESCRIPTION
        "Maximum number of lispCchEtr entries stored per lispCchSite entry for
         this LISP-instance."
    DEFVAL      { 10 }
    ::= { lispInstEntry 7 }

lispInstCacheMaxFrames OBJECT-TYPE
    SYNTAX      Unsigned32
    MAX-ACCESS  read-write
    STATUS      current
    DESCRIPTION
        "Maximum number of data-frames buffered per to-be-resolved lispCchEtr
         entry for this LISP-instance."
    DEFVAL      { 1 }
    ::= { lispInstEntry 8 }

lispInstDefaultTtl OBJECT-TYPE
    SYNTAX      Unsigned32
    UNITS       "minutes"
    MAX-ACCESS  read-write
    STATUS      current
    DESCRIPTION
        "Default time-to-live in minutes for lispCchSite-entries of this
         LISP-instance. See description of lispInstDefTtlMode-field about when
         this default-value is used instead of the Map-Server-reported one."
    DEFVAL      { 60 }
    ::= { lispInstEntry 9 }

lispInstResolvingTtl OBJECT-TYPE
    SYNTAX      Unsigned32
    UNITS       "minutes"
    MAX-ACCESS  read-write
    STATUS      current
    DESCRIPTION
        "Time-to-live in minutes stored in lispCchSite entries that are still
         in to-be-resolved state for this LISP-instance."
    DEFVAL      { 1 }
    ::= { lispInstEntry 10 }

lispInstDefTtlMode OBJECT-TYPE
    SYNTAX      INTEGER {
        fallback(1),
        fixed(2)
    }
    MAX-ACCESS  read-write
    STATUS      current
    DESCRIPTION
        "Tells if lispInstDefaultTtl-field for this LISP-instance is used only
         as 'fallback' when Map-Server does not specify TTL, or if TTL is
         'fixed' to this default-value (i.e. TTL from Map-Server is ignored)."
    DEFVAL      { fallback }
    ::= { lispInstEntry 11 }

lispInstProxyEtrAddr OBJECT-TYPE
    SYNTAX      IpAddress
    MAX-ACCESS  read-write
    STATUS      current
    DESCRIPTION
        "Optional Proxy-ETR-RLOC for special handling of negative Map-Replies
         with action 'Natively-Forward' (see section 6.1 of RFC-6832 and
         description of 'ACT' field in section 6.1.4 of RFC-6830).
         Per default, current LISP-implementation ignores action-parameter in
         negative Map-Replies and always assumes 'No-Action'. However, if this
         MIB-field is set (i.e. not 0.0.0.0) then it specifies Proxy-ETR-RLOC
         to be used for this LISP-instance for any target-EIDs resolved via
         negative Map-Reply with action 'Natively-Forward'."
    ::= { lispInstEntry 12 }


--
-- Configured remote LISP-sites
--

lispRemSiteTable OBJECT-TYPE
    SYNTAX      SEQUENCE OF LispRemSiteEntry
    MAX-ACCESS  not-accessible
    STATUS      current
    DESCRIPTION
        "List of remote LISP-sites (see section 4.1 of RFC-6833). For each
         pair of remote and local site of same LISP-instance, a corresponding
         entry is stored in ipExtRtTable."
    ::= { lispMIB 2 }

lispRemSiteEntry OBJECT-TYPE
    SYNTAX      LispRemSiteEntry
    MAX-ACCESS  not-accessible
    STATUS      current
    DESCRIPTION
        ""
    INDEX       { lispRemSiteInstId, lispRemSiteAddr, lispRemSiteLen }
    ::= { lispRemSiteTable 1 }

LispRemSiteEntry ::=
    SEQUENCE {
        lispRemSiteInstId       INTEGER,
        lispRemSiteAddr         IpAddress,
        lispRemSiteLen          INTEGER,
        lispRemSiteAligned      IpAddress,
        lispRemSiteAdminStatus  INTEGER
    }

lispRemSiteInstId OBJECT-TYPE
    SYNTAX      INTEGER (-1..16777215)
    MAX-ACCESS  read-write
    STATUS      current
    DESCRIPTION
        "Refers to lispInstId-field of related lispInst-entry."
    ::= { lispRemSiteEntry 1 }

lispRemSiteAddr OBJECT-TYPE
    SYNTAX      IpAddress
    MAX-ACCESS  read-write
    STATUS      current
    DESCRIPTION
        "Together with lispRemSiteLen, specifies EID-prefix of this remote
         LISP-site. Cached EID-prefixes (received via Map-Reply) may (but
         should not) be completely different ones. In such cases, LISP-routing
         considers only such IP-frames that match with both kinds of prefixes,
         administratively configured one and dynamically received ones."
    ::= { lispRemSiteEntry 2 }

lispRemSiteLen OBJECT-TYPE
    SYNTAX      INTEGER (0..32)
    UNITS       "bits"
    MAX-ACCESS  read-write
    STATUS      current
    DESCRIPTION
        "See description of lispRemSiteAddr.
         Converted/stored as ipExtRtDstMask in related ipExtRt-entries."
    ::= { lispRemSiteEntry 3 }

lispRemSiteAligned OBJECT-TYPE
    SYNTAX      IpAddress
    MAX-ACCESS  read-only
    STATUS      current
    DESCRIPTION
        "Prefix-length-aligned read-only-version of lispRemSiteAddr.
         Stored as ipExtRtDstAddr in related ipExtRt-entries"
    ::= { lispRemSiteEntry 4 }

lispRemSiteAdminStatus OBJECT-TYPE
    SYNTAX      INTEGER {
        active(1),
        inactive(2),
        delete(3)
    }
    MAX-ACCESS  read-write
    STATUS      current
    DESCRIPTION
        "Administrative status of remote LISP-site.
         Set to delete for killing entry."
    DEFVAL      { active }
    ::= { lispRemSiteEntry 5 }


--
-- Configured local LISP-sites
--

lispLocSiteTable OBJECT-TYPE
    SYNTAX      SEQUENCE OF LispLocSiteEntry
    MAX-ACCESS  not-accessible
    STATUS      current
    DESCRIPTION
        "List of local LISP-sites (see section 4.2 of RFC-6833). For each pair
         of remote and local site of same LISP-instance, a corresponding entry
         is stored in ipExtRtTable."
    ::= { lispMIB 3 }

lispLocSiteEntry OBJECT-TYPE
    SYNTAX      LispLocSiteEntry
    MAX-ACCESS  not-accessible
    STATUS      current
    DESCRIPTION
        ""
    INDEX       { lispLocSiteInstId, lispLocSiteAddr, lispLocSiteLen }
    ::= { lispLocSiteTable 1 }

LispLocSiteEntry ::=
    SEQUENCE {
        lispLocSiteInstId       INTEGER,
        lispLocSiteAddr         IpAddress,
        lispLocSiteLen          INTEGER,
        lispLocSiteAligned      IpAddress,
        lispLocSiteAdminStatus  INTEGER,
        lispLocSiteTtl          Unsigned32,
        lispLocSiteIfIndex      InterfaceIndexOrZero,
        lispLocSiteMetric1      INTEGER,
        lispLocSiteRlocMode     INTEGER
    }

lispLocSiteInstId OBJECT-TYPE
    SYNTAX      INTEGER (-1..16777215)
    MAX-ACCESS  read-write
    STATUS      current
    DESCRIPTION
        "Refers to lispInstId-field of related lispInst-entry."
    ::= { lispLocSiteEntry 1 }

lispLocSiteAddr OBJECT-TYPE
    SYNTAX      IpAddress
    MAX-ACCESS  read-write
    STATUS      current
    DESCRIPTION
        "Together with lispLocSiteLen, specifies EID-prefix of this local
         LISP-site. Prefix is reported to configured Map-Servers via
         Map-Register."
    ::= { lispLocSiteEntry 2 }

lispLocSiteLen OBJECT-TYPE
    SYNTAX      INTEGER (0..32)
    UNITS       "bits"
    MAX-ACCESS  read-write
    STATUS      current
    DESCRIPTION
        "See description of lispLocSiteAddr.
         Converted/stored as ipExtRtSrcMask in related ipExtRt-entries."
    ::= { lispLocSiteEntry 3 }

lispLocSiteAligned OBJECT-TYPE
    SYNTAX      IpAddress
    MAX-ACCESS  read-only
    STATUS      current
    DESCRIPTION
        "Prefix-length-aligned read-only-version of lispLocSiteAddr.
         Stored as ipExtRtSrcAddr in related ipExtRt-entry."
    ::= { lispLocSiteEntry 4 }

lispLocSiteAdminStatus OBJECT-TYPE
    SYNTAX      INTEGER {
        active(1),
        inactive(2),
        delete(3)
    }
    MAX-ACCESS  read-write
    STATUS      current
    DESCRIPTION
        "Administrative status of local LISP-site.
         Set to delete for killing entry."
    DEFVAL      { active }
    ::= { lispLocSiteEntry 5 }

lispLocSiteTtl OBJECT-TYPE
    SYNTAX      Unsigned32
    UNITS       "minutes"
    MAX-ACCESS  read-write
    STATUS      current
    DESCRIPTION
        "Time-to-live-value in minutes that is reported via Map-Register for
         this local LISP-site."
    DEFVAL      { 60 }
    ::= { lispLocSiteEntry 6 }

lispLocSiteIfIndex OBJECT-TYPE
    SYNTAX      InterfaceIndexOrZero
    MAX-ACCESS  read-write
    STATUS      current
    DESCRIPTION
        "Optional interface-index of this local LISP-site, stored as
         ipExtRtSrcIfIndex in related ipExtRt-entries. At present, it is not
         possible to assign multiple ifindex-values to the same local site.
         Special value of 0 means that interface-index is not specified."
    ::= { lispLocSiteEntry 7 }

lispLocSiteMetric1 OBJECT-TYPE
    SYNTAX      INTEGER
    MAX-ACCESS  read-write
    STATUS      current
    DESCRIPTION
        "Stored as ipExtRtMetric1 in related ipExtRt-entries."
    ::= { lispLocSiteEntry 8 }

lispLocSiteRlocMode OBJECT-TYPE
    SYNTAX      INTEGER {
        negative(1),
        auto(2)
    }
    MAX-ACCESS  read-write
    STATUS      current
    DESCRIPTION
        "Tells how to fill reported ETR-RLOCs-list for this local LISP-site.
         Negative mappings have an empty ETR-RLOCs-list, i.e. matching frames
         cannot be LISP-tunnelled. The reported action-field for such mappings
         is currently hard-coded to 0 (i.e. drop matching frames silently).
         In automatic mode, ETR-RLOCs-list is auto-filled, based on current
         route/address-info.
         At present, ETR-RLOCs cannot be configured manually."
    DEFVAL      { auto }
    ::= { lispLocSiteEntry 9 }


--
-- Configured Map-Servers
--

lispMapSrvTable OBJECT-TYPE
    SYNTAX      SEQUENCE OF LispMapSrvEntry
    MAX-ACCESS  not-accessible
    STATUS      current
    DESCRIPTION
        "List of Map-Servers (see section 4.2 of RFC-6833) to inform about
         configured local LISP-sites."
    ::= { lispMIB 4 }

lispMapSrvEntry OBJECT-TYPE
    SYNTAX      LispMapSrvEntry
    MAX-ACCESS  not-accessible
    STATUS      current
    DESCRIPTION
        ""
    INDEX       { lispMapSrvAddr }
    ::= { lispMapSrvTable 1 }

LispMapSrvEntry ::=
    SEQUENCE {
        lispMapSrvAddr         IpAddress,
        lispMapSrvAdminStatus  INTEGER,
        lispMapSrvPeriod       Unsigned32,
        lispMapSrvNextReg      TimeTicks,
        lispMapSrvKeyId        INTEGER,
        lispMapSrvKeyVal       OCTET STRING,
        lispMapSrvKeyLen       Unsigned32,
        lispMapSrvAuthMode     INTEGER,
        lispMapSrvAuthLen      Unsigned32
    }

lispMapSrvAddr OBJECT-TYPE
    SYNTAX      IpAddress
    MAX-ACCESS  read-write
    STATUS      current
    DESCRIPTION
        "RLOC of this Map-Server."
    ::= { lispMapSrvEntry 1 }

lispMapSrvAdminStatus OBJECT-TYPE
    SYNTAX      INTEGER {
        active(1),
        inactive(2),
        delete(3)
    }
    MAX-ACCESS  read-write
    STATUS      current
    DESCRIPTION
        "Administrative status of Map-Server.
         Set to delete for killing entry."
    DEFVAL      { active }
    ::= { lispMapSrvEntry 2 }

lispMapSrvPeriod OBJECT-TYPE
    SYNTAX      Unsigned32
    UNITS       "seconds"
    MAX-ACCESS  read-write
    STATUS      current
    DESCRIPTION
        "Period in seconds for Map-Register-frames sent to this Map-Server."
    DEFVAL      { 60 }
    ::= { lispMapSrvEntry 3 }

lispMapSrvNextReg OBJECT-TYPE
    SYNTAX
                TimeTicks
    MAX-ACCESS  read-only
    STATUS      current
    DESCRIPTION
        "Count-down for next Map-Register-send-attempt to this Map-Server.
         Relevant only if this entry is active and if there is at least one
         active lispLocSite-entry with related active lispInst-entry."
    ::= { lispMapSrvEntry 4 }

lispMapSrvKeyId OBJECT-TYPE
    SYNTAX      INTEGER {
        none(0),
        hmac-sha1-96(1),
        hmac-sha2-256-128(2)
    }
    MAX-ACCESS  read-write
    STATUS      current
    DESCRIPTION
        "Method and implied key-format used for Map-Register-authentication.
         Authentication can be deactivated by setting this value to none.
         hmac-sha1-96 refers to the specifications in RFC-2404.
         hmac-sha2-256-128 refert to specifications in RFC-4868."
    DEFVAL      { hmac-sha1-96 }
    ::= { lispMapSrvEntry 5 }

lispMapSrvKeyVal OBJECT-TYPE
    SYNTAX      OCTET STRING (SIZE (0..255))
    MAX-ACCESS  read-write
    STATUS      current
    DESCRIPTION
        "Octet-string (value) of secret shared with this Map-Server and used
         for Map-Register-authentication.
         Its length is internally padded/truncated to lispMapSrvKeyLen."
    ::= { lispMapSrvEntry 6 }

lispMapSrvKeyLen OBJECT-TYPE
    SYNTAX      Unsigned32
    UNITS       "bytes"
    MAX-ACCESS  read-only
    STATUS      current
    DESCRIPTION
        "Tells lispMapSrvKeyId-specific length for internally used copy of
         lispMapSrvKeyVal."
    ::= { lispMapSrvEntry 7 }

lispMapSrvAuthMode OBJECT-TYPE
    SYNTAX      INTEGER {
        skip-trunc-if-opt(0),
        do-trunc-if-opt(1)
    }
    MAX-ACCESS  read-write
    STATUS      current
    DESCRIPTION
        "Tells for hmac-sha1-96 if authentication-data shall be stored in full
         160-bits-length (skip-trunc-if-opt) or in truncated 96-bits-length
         (do-trunc-if-opt). RFC-6830 and RFC-2104 leave this choice open but
         some Map-Servers may support only one variant.
         For hmac-sha2-256-128, this setting has no effect because truncation
         to 128-bits-length is mandatory there."
    DEFVAL      { skip-trunc-if-opt }
    ::= { lispMapSrvEntry 8 }

lispMapSrvAuthLen OBJECT-TYPE
    SYNTAX      Unsigned32
    UNITS       "bytes"
    MAX-ACCESS  read-only
    STATUS      current
    DESCRIPTION
        "Tells lispMapSrvKeyId-specific and lispMapSrvAuthMode-specific length
         of authentication-data added to Map-Register-frames."
    ::= { lispMapSrvEntry 9 }


--
-- Configured Map-Resolvers
--

lispMapRsvTable OBJECT-TYPE
    SYNTAX      SEQUENCE OF LispMapRsvEntry
    MAX-ACCESS  not-accessible
    STATUS      current
    DESCRIPTION
        "List of Map-Resolvers (see section 4.1 of RFC-6833) to consult for
         remote EID-RLOC-mappings."
    ::= { lispMIB 5 }

lispMapRsvEntry OBJECT-TYPE
    SYNTAX      LispMapRsvEntry
    MAX-ACCESS  not-accessible
    STATUS      current
    DESCRIPTION
        ""
    INDEX       { lispMapRsvAddr }
    ::= { lispMapRsvTable 1 }

LispMapRsvEntry ::=
    SEQUENCE {
        lispMapRsvAddr         IpAddress,
        lispMapRsvAdminStatus  INTEGER,
        lispMapRsvOperStatus   INTEGER,
        lispMapRsvMinPeriod    Unsigned32,
        lispMapRsvMaxPending   Unsigned32,
        lispMapRsvPendingCnt   Counter32,
        lispMapRsvPendingTime  TimeTicks,
        lispMapRsvMaxDelay     Unsigned32
    }

lispMapRsvAddr OBJECT-TYPE
    SYNTAX      IpAddress
    MAX-ACCESS  read-write
    STATUS      current
    DESCRIPTION
        "RLOC of this Map-Resolver."
    ::= { lispMapRsvEntry 1 }

lispMapRsvAdminStatus OBJECT-TYPE
    SYNTAX      INTEGER {
        active(1),
        inactive(2),
        delete(3)
    }
    MAX-ACCESS  read-write
    STATUS      current
    DESCRIPTION
        "Administrative status of Map-Resolver.
         Set to delete for killing entry."
    DEFVAL      { active }
    ::= { lispMapRsvEntry 2 }

lispMapRsvOperStatus OBJECT-TYPE
    SYNTAX      INTEGER {
        selected(1),
        not-selected(2)
    }
    MAX-ACCESS  read-only
    STATUS      current
    DESCRIPTION
        "Operative status of Map-Resolver."
    DEFVAL      { selected }
    ::= { lispMapRsvEntry 3 }

lispMapRsvMinPeriod OBJECT-TYPE
    SYNTAX      Unsigned32
    UNITS       "seconds"
    MAX-ACCESS  read-write
    STATUS      current
    DESCRIPTION
        "Minimum time-distance in seconds for subsequent Map-Requests that are
         sent to this Map-Resolver for same to-be-resolved EID.
         In current implementation, subsequent Map-Requests are not triggered
         automatically but only by subsequent send-attempts from LISP-hosts."
    DEFVAL      { 1 }
    ::= { lispMapRsvEntry 4 }

lispMapRsvMaxPending OBJECT-TYPE
    SYNTAX      Unsigned32
    MAX-ACCESS  read-write
    STATUS      current
    DESCRIPTION
        "Allowed number of unreplied subsequent Map-Requests before switching
         to next Map-Resolver (if any) is considered. This defines some kind
         of frame-loss-tolerance for the Map-Resolver-switching. Additionally,
         some net-delay-tolerance can be configured via lispMapRsvMaxDelay."
    DEFVAL      { 2 }
    ::= { lispMapRsvEntry 5 }

lispMapRsvPendingCnt OBJECT-TYPE
    SYNTAX      Counter32
    MAX-ACCESS  read-only
    STATUS      current
    DESCRIPTION
        "Current number of unreplied subsequent Map-Requests.
         This field is valid only if lispMapRsvOperStatus is 'selected'."
    ::= { lispMapRsvEntry 6 }

lispMapRsvPendingTime OBJECT-TYPE
    SYNTAX      TimeTicks
    MAX-ACCESS  read-only
    STATUS      current
    DESCRIPTION
        "Send-time of the (lispMapRsvMaxPending + 1)st still pending
         Map-Request.
         This time-stamp is valid only if lispMapRsvOperStatus is 'selected'
         and lispMapRsvPendingCnt is greater than lispMapRsvMaxPending."
    ::= { lispMapRsvEntry 7 }

lispMapRsvMaxDelay OBJECT-TYPE
    SYNTAX      Unsigned32
    UNITS       "seconds"
    MAX-ACCESS  read-write
    STATUS      current
    DESCRIPTION
        "Allowed number of seconds between lispMapRsvPendingTime (if valid)
         and receipt of next valid Map-Reply before switching to next
         Map-Resolver (if any) is considered."
    DEFVAL      { 3 }
    ::= { lispMapRsvEntry 8 }


--
-- Cached remote LISP-sites
--

lispCchSiteTable OBJECT-TYPE
    SYNTAX      SEQUENCE OF LispCchSiteEntry
    MAX-ACCESS  not-accessible
    STATUS      current
    DESCRIPTION
        "List of cached remote LISP-sites (see section 4.1 of RFC-6833)."
    ::= { lispMIB 6 }

lispCchSiteEntry OBJECT-TYPE
    SYNTAX      LispCchSiteEntry
    MAX-ACCESS  not-accessible
    STATUS      current
    DESCRIPTION
        ""
    INDEX       { lispCchSiteInstId, lispCchSiteAddr, lispCchSiteLen }
    ::= { lispCchSiteTable 1 }

LispCchSiteEntry ::=
    SEQUENCE {
        lispCchSiteInstId   INTEGER,
        lispCchSiteAddr     IpAddress,
        lispCchSiteLen      INTEGER,
        lispCchSiteState    INTEGER,
        lispCchSiteTtl      INTEGER,
        lispCchSiteStart    TimeTicks,
        lispCchSiteFlagA    INTEGER,
        lispCchSiteLru      TimeTicks,
        lispCchSiteReqTime  TimeTicks,
        lispCchSiteNonce    Counter64,
        lispCchSiteAction   INTEGER
    }

lispCchSiteInstId OBJECT-TYPE
    SYNTAX      INTEGER (-1..16777215)
    MAX-ACCESS  read-only
    STATUS      current
    DESCRIPTION
        "Refers to lispInstId-field of related lispInst-entry."
    ::= { lispCchSiteEntry 1 }

lispCchSiteAddr OBJECT-TYPE
    SYNTAX      IpAddress
    MAX-ACCESS  read-only
    STATUS      current
    DESCRIPTION
        "Together with lispCchSiteLen, specifies EID-prefix of this cached
         remote LISP-site."
    ::= { lispCchSiteEntry 2 }

lispCchSiteLen OBJECT-TYPE
    SYNTAX      INTEGER (0..32)
    UNITS       "bits"
    MAX-ACCESS  read-only
    STATUS      current
    DESCRIPTION
        "See description of lispCchSiteAddr."
    ::= { lispCchSiteEntry 3 }

lispCchSiteState OBJECT-TYPE
    SYNTAX      INTEGER {
        to-be-resolved(0),
        valid-not-refreshing(1),
        valid-refreshing(2)
    }
    MAX-ACCESS  read-only
    STATUS      current
    DESCRIPTION
        "State of this cache-entry.
         'to-be-resolved' means that entry is not yet valid, and related
         Map-Request is still pending. 'valid-not-refreshing' means that entry
         is valid, and refresh has not yet been triggered. 'valid-refreshing'
         means that entry is valid, and refresh has already been triggered."
    DEFVAL      { to-be-resolved }
    ::= { lispCchSiteEntry 4 }

lispCchSiteTtl OBJECT-TYPE
    SYNTAX      INTEGER (0..4294967295)
    UNITS       "minutes"
    MAX-ACCESS  read-only
    STATUS      current
    DESCRIPTION
        "Time-to-live in minutes of this cache-entry, starting at
         lispCchSiteStart. See 6.1.4 of RFC-6830 for details."
    ::= { lispCchSiteEntry 5 }

lispCchSiteStart OBJECT-TYPE
    SYNTAX      TimeTicks
    MAX-ACCESS  read-only
    STATUS      current
    DESCRIPTION
        "Start of time-to-live period. See lispCchSiteTtl for more details."
    ::= { lispCchSiteEntry 6 }

lispCchSiteFlagA OBJECT-TYPE
    SYNTAX      INTEGER {
        not-authoritative(0),
        authoritative(1)
    }
    MAX-ACCESS  read-only
    STATUS      current
    DESCRIPTION
        "Flag A of this cache-entry. See 6.1.4 of RFC-6830 for details.
         This field is not relevant/valid in state to-be-resolved.
         Current implementation mostly yet ignores this value."
    DEFVAL      { not-authoritative }
    ::= { lispCchSiteEntry 7 }

lispCchSiteLru OBJECT-TYPE
    SYNTAX      TimeTicks
    MAX-ACCESS  read-only
    STATUS      current
    DESCRIPTION
        "Time-stamp of latest use (LRU) of this cache-entry."
    ::= { lispCchSiteEntry 8 }

lispCchSiteReqTime OBJECT-TYPE
    SYNTAX      TimeTicks
    MAX-ACCESS  read-only
    STATUS      current
    DESCRIPTION
        "Time-stamp of latest Map-Request sent for resolving (in state
         to-be-resolved) or updating (in state valid-refreshing) this
         cache-entry.
         This field is not relevant/valid in state valid-not-refreshing."
    ::= { lispCchSiteEntry 9 }

lispCchSiteNonce OBJECT-TYPE
    SYNTAX      Counter64
    MAX-ACCESS  read-only
    STATUS      current
    DESCRIPTION
        "Nonce-value of latest Map-Request sent for resolving (in state
         to-be-resolved) or updating (in state valid-refreshing) this
         cache-entry.
         This field is not relevant/valid in state valid-not-refreshing."
    ::= { lispCchSiteEntry 10 }

lispCchSiteAction OBJECT-TYPE
    SYNTAX      INTEGER {
        no-action(0),
        natively-forward(1),
        send-map-request(2),
        drop(3)
    }
    MAX-ACCESS  read-only
    STATUS      current
    DESCRIPTION
        "Requested action for negative Map-Replies (i.e. no cached ETRs,
         see description of 'ACT' field in section 6.1.4 of RFC-6830).
         This field is not relevant/valid for positive Map-Replies
         (and in state to-be-resolved).
         Current code supports only 'no-action' and special variant of
         'natively-forward' (see 'lispInstProxyEtrAddr' for details)."
    DEFVAL      { no-action }
    ::= { lispCchSiteEntry 11 }


--
-- Cached ETRs for remote LISP-sites
--

lispCchEtrTable OBJECT-TYPE
    SYNTAX      SEQUENCE OF LispCchEtrEntry
    MAX-ACCESS  not-accessible
    STATUS      current
    DESCRIPTION
        "List of cached ETRs for remote LISP-sites (see section 4.1 of
         RFC-6833 and section 4.1.4 of RFC-6830). In current implementation,
         support of multiple ETRs is rather restricted (no load-balancing,
         no reachability-checks)."
    ::= { lispMIB 7 }

lispCchEtrEntry OBJECT-TYPE
    SYNTAX      LispCchEtrEntry
    MAX-ACCESS  not-accessible
    STATUS      current
    DESCRIPTION
        ""
    INDEX       { lispCchEtrInstId, lispCchEtrSiteAddr,
                  lispCchEtrSiteLen, lispCchEtrAddr }
    ::= { lispCchEtrTable 1 }

LispCchEtrEntry ::=
    SEQUENCE {
        lispCchEtrInstId    INTEGER,
        lispCchEtrSiteAddr  IpAddress,
        lispCchEtrSiteLen   INTEGER,
        lispCchEtrAddr      IpAddress,
        lispCchEtrPrio      INTEGER,
        lispCchEtrWeight    INTEGER,
        lispCchEtrFlagL     INTEGER,
        lispCchEtrFlagR     INTEGER
    }

lispCchEtrInstId OBJECT-TYPE
    SYNTAX      INTEGER (-1..16777215)
    MAX-ACCESS  read-only
    STATUS      current
    DESCRIPTION
        "Refers to lispInstId-field of related lispCchSite-entry."
    ::= { lispCchEtrEntry 1 }

lispCchEtrSiteAddr OBJECT-TYPE
    SYNTAX      IpAddress
    MAX-ACCESS  read-only
    STATUS      current
    DESCRIPTION
        "Refers to lispCchSiteAddr-field of related lispCchSite-entry."
    ::= { lispCchEtrEntry 2 }

lispCchEtrSiteLen OBJECT-TYPE
    SYNTAX      INTEGER (0..32)
    UNITS       "bits"
    MAX-ACCESS  read-only
    STATUS      current
    DESCRIPTION
        "Refers to lispCchSiteLen-field of related lispCchSite-entry."
    ::= { lispCchEtrEntry 3 }

lispCchEtrAddr OBJECT-TYPE
    SYNTAX      IpAddress
    MAX-ACCESS  read-only
    STATUS      current
    DESCRIPTION
        "RLOC of this cached remote ETR."
    ::= { lispCchEtrEntry 4 }

lispCchEtrPrio OBJECT-TYPE
    SYNTAX      INTEGER (0..255)
    MAX-ACCESS  read-only
    STATUS      current
    DESCRIPTION
        "Prio of this cached remote ETR. See 6.1.4 of RFC-6830 for details."
    ::= { lispCchEtrEntry 5 }

lispCchEtrWeight OBJECT-TYPE
    SYNTAX      INTEGER (0..255)
    MAX-ACCESS  read-only
    STATUS      current
    DESCRIPTION
        "Weight of this cached remote ETR. See 6.1.4 of RFC-6830 for details.
         Current implementation mostly yet ignores this value."
    ::= { lispCchEtrEntry 6 }

lispCchEtrFlagL OBJECT-TYPE
    SYNTAX      INTEGER {
        not-local(0),
        local(1)
    }
    MAX-ACCESS  read-only
    STATUS      current
    DESCRIPTION
        "Flag L of this cached remote ETR. See 6.1.4 of RFC-6830 for details.
         Current implementation mostly yet ignores this value."
    DEFVAL      { not-local }
    ::= { lispCchEtrEntry 7 }

lispCchEtrFlagR OBJECT-TYPE
    SYNTAX      INTEGER {
        has-no-route(0),
        has-route(1)
    }
    MAX-ACCESS  read-only
    STATUS      current
    DESCRIPTION
        "Flag R of this cached remote ETR. See 6.1.4 of RFC-6830 for details.
         Current implementation mostly yet ignores this value."
    DEFVAL      { has-no-route }
    ::= { lispCchEtrEntry 8 }


END
