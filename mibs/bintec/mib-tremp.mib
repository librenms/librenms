-- This file is corresponding to Release 10.2.3.100 from 2018/07/18 00:00:00


---------------------------------------------------------------------------
-- (C)opyright 2011-2015 bintec elmeg GmbH
-- $RCSfile: mib-tremp,v $
-- $Revision: 1.4 $
-- $Date: 2015-12-08 13:42:43 $
-- Author: hsommerf
---------------------------------------------------------------------------

BINTEC-TREMP-MIB DEFINITIONS ::= BEGIN

        IMPORTS
        enterprises
                FROM RFC1155-SMI
        IpAddress, enterprises
                FROM RFC1155-SMI
        MacAddress, DisplayString, TimeStamp, TruthValue
                FROM SNMPv2-TC
        bibo, Date, BitValue
                FROM BINTEC-MIB
        MODULE-IDENTITY, OBJECT-TYPE, NOTIFICATION-TYPE, Counter32, Counter64, TimeTicks
                FROM SNMPv2-SMI
        TRAP-TYPE
                FROM RFC-1215
        TruthValue
                FROM SNMPv2-TC
        ifIndex
                FROM IF-MIB
        OBJECT-TYPE
                FROM RFC-1212
        MODULE-COMPLIANCE, OBJECT-GROUP, NOTIFICATION-GROUP
                FROM SNMPv2-CONF
        InetAddressType, InetAddress
                FROM INET-ADDRESS-MIB;


trempMIB MODULE-IDENTITY
    LAST-UPDATED "201512080000Z"
    ORGANIZATION "bintec elmeg GmbH"
    CONTACT-INFO
	    "EMail:   info@bintec-elmeg.com
	     Web:     www.bintec-elmeg.com
	    "
    DESCRIPTION
            "The MIB module for TREMP (Teldat REst Management Protocol) configuration."
    REVISION      "201504070000Z"
    DESCRIPTION
            "Initial version." 
    ::= { bibo 99 }

    tremp  OBJECT IDENTIFIER
    ::= { trempMIB 1 }


-- **********************************************************************
-- *    trempAdminTable TABLE
-- **********************************************************************
trempAdmin OBJECT IDENTIFIER
    ::= { tremp 1 }

    trempAdminStatus OBJECT-TYPE
        SYNTAX INTEGER { enabled(1), disabled(2) }
        MAX-ACCESS read-write
        STATUS current
        DESCRIPTION
            "Activate or deactivate the TREMP client."
        DEFVAL { disabled }
    ::= { trempAdmin 1 }

    trempAdminOperStatus OBJECT-TYPE
        SYNTAX INTEGER { enabled(1), disabled(2), managed(3), idle(4), startup(5) }
        MAX-ACCESS read-only
        STATUS current
        DESCRIPTION
            "Operational status of the TREMP client."
        DEFVAL { disabled }
    ::= { trempAdmin 2 }

    trempAdminServer OBJECT-TYPE
        SYNTAX DisplayString
        MAX-ACCESS read-write
        STATUS current
        DESCRIPTION
            "The address of the TREMP server.
             This object can start with the scheme 'http://' or 'https://'.
             The address may contain either an IP address or a domain name
             and can be followed by the port separated by a colon."
    ::= { trempAdmin 3 }

    trempAdminQueryInterval OBJECT-TYPE
        SYNTAX INTEGER (5..3600)
        MAX-ACCESS read-write
        STATUS current
        DESCRIPTION
            "The interval in seconds to query the TREMP server for new tasks."
        DEFVAL { 30 }
    ::= { trempAdmin 4 }

    trempAdminPurgeSecurity OBJECT-TYPE
        SYNTAX INTEGER { enabled(1), disabled(2) }
        MAX-ACCESS read-write
        STATUS current
        DESCRIPTION
            "Removes security information from the system."
        DEFVAL { disabled }
    ::= { trempAdmin 5 }

    trempAdminDebugLevel OBJECT-TYPE
        SYNTAX INTEGER { normal(1), verbose(2), quiet(3) }
        MAX-ACCESS read-write
        STATUS current
        DESCRIPTION
            "Defines the verbosity of the debugging utility for this daemon.
             The 'verbose' level shows the maximum amount of debugging 
             information that can be generated by the daemon."
        DEFVAL { normal }
    ::= { trempAdmin 6 }

    trempAdminStartupTimer OBJECT-TYPE
        SYNTAX INTEGER (0..3600)
        MAX-ACCESS read-write
        STATUS current
        DESCRIPTION
            "Defines the amount of time that the daemon will wait on startup 
             before running."
        DEFVAL { 60 }
    ::= { trempAdmin 7 }

-- **********************************************************************
-- *    trempPersistTable TABLE
-- **********************************************************************
trempPersist OBJECT IDENTIFIER
    ::= { tremp 2 }

    trempPersistMonitoringInterval OBJECT-TYPE
        SYNTAX INTEGER (5..3600)
        MAX-ACCESS read-only
        STATUS current
        DESCRIPTION
            "The interval in seconds to send to the TREMP server the monitoring events."
        DEFVAL { 30 }
    ::= { trempPersist 1 }

    trempPersistCertIndex OBJECT-TYPE
        SYNTAX INTEGER
        ACCESS read-only
        STATUS current
        DESCRIPTION
            "Index of certificate entry in certTable which is to be used as
             client certificate for REST transport."
        DEFVAL { 0 } 
    ::= { trempPersist 2 }

    trempPersistHMAC OBJECT-TYPE
        SYNTAX OCTET STRING (SIZE (20))
        ACCESS read-only
        STATUS current
        DESCRIPTION
            "Current HMAC key for non 'https' connections."
        DEFVAL { '4e976c8d20ae65926e9b629f728c68e031c736cd'h }
    ::= { trempPersist 3 }

    trempPersistHMACTimestamp OBJECT-TYPE
        SYNTAX INTEGER
        ACCESS read-only
        STATUS current
        DESCRIPTION
            "Timestamp that define the HMAC valid lifetime"
        DEFVAL { 0 } 
    ::= { trempPersist 4 }

END
