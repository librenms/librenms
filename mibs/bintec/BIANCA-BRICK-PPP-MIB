-- This file is corresponding to Release 10.2.3.100 from 2018/07/18 00:00:00


-- (C)opyright 2007-2015 bintec elmeg GmbH, All Rights Reserved
--  $RCSfile: mibppp,v $ 
-- $Revision: 1.156 $ 

BIANCA-BRICK-PPP-MIB DEFINITIONS ::= BEGIN

        IMPORTS
            IpAddress, Counter, enterprises
                FROM RFC1155-SMI

            DisplayString
                FROM RFC1158-MIB
       
            Date, BitValue
                FROM BINTEC-MIB
 
            OBJECT-TYPE
                FROM RFC-1212;

    bintec 	OBJECT IDENTIFIER ::= { enterprises 272 }
    bibo	OBJECT IDENTIFIER ::= { bintec 4 }
    ppp		OBJECT IDENTIFIER
	::= { bibo 3 }
    dialmap	OBJECT IDENTIFIER 
	::= { bibo 4 }

    -- PPP Group

    -- Configuration of PPP

	biboPPPTable OBJECT-TYPE
	    SYNTAX  SEQUENCE OF BiboPPPEntry
	    ACCESS  not-accessible
	    STATUS  mandatory
	    DESCRIPTION
		"The biboPPPTable contains configuration information
                for the PPP interfaces. Each time a new entry is made
                here, a corresponding entry is made in the ifTable.

                Creating entries: Entries are created by assigning a
                value to the biboPPPType object.

                Deleting entries: Entries are removed by setting an
                entry's biboPPPEncapsulation object to 'delete'."
	::= { ppp 1 }

	biboPPPEntry OBJECT-TYPE
	    SYNTAX  BiboPPPEntry
	    ACCESS  not-accessible
	    STATUS  mandatory
	    DESCRIPTION
		""
	    INDEX   { biboPPPType }
	::= { biboPPPTable 1 }

	BiboPPPEntry ::=
	    SEQUENCE {
		biboPPPIfIndex				INTEGER,
		biboPPPType				INTEGER,
		biboPPPEncapsulation			INTEGER,
		biboPPPKeepalive			INTEGER,
		biboPPPTimeout				INTEGER,
		biboPPPCompression	  		INTEGER,
		biboPPPAuthentication			INTEGER,
		biboPPPAuthIdent			DisplayString,
		biboPPPAuthSecret			DisplayString,
 		biboPPPCallback				INTEGER,
 		biboPPPIpAddress			INTEGER,
 --		biboPPPIpHeader				INTEGER,
		biboPPPRetryTime			INTEGER,
		biboPPPBlockTime			INTEGER,
		biboPPPMaxRetries			INTEGER,
		biboPPPShortHold			INTEGER,
		biboPPPInitConn				INTEGER,
		biboPPPMaxConn				INTEGER,
		biboPPPMinConn				INTEGER,
		biboPPPLayer1Protocol			INTEGER,
                biboPPPLoginString                      DisplayString,
                biboPPPVJHeaderComp                     INTEGER,
		biboPPPLayer2Mode			INTEGER,
                biboPPPDynShortHold                     INTEGER,
                biboPPPLocalIdent                       DisplayString,
                biboPPPDNSNegotiation                   INTEGER,
                biboPPPEncryption                       INTEGER,
                biboPPPLQMonitoring                     INTEGER,
		biboPPPIpPoolId				INTEGER,
		biboPPPSessionTimeout			INTEGER,
		biboPPPLayer1DiscDelay 			INTEGER,
		biboPPPAuthDomain			DisplayString,
		biboPPPAliveCheck			INTEGER
	    }

	biboPPPIfIndex OBJECT-TYPE
	    SYNTAX  INTEGER 
	    ACCESS  read-only
	    STATUS  mandatory

	    DESCRIPTION
		"Correlating PPP interface index. This value is 
                assigned automatically by the system."
	::= { biboPPPEntry 1 }

	biboPPPType OBJECT-TYPE
	    SYNTAX  INTEGER { 
		isdn-dialup(1), 
		leased(2),
		isdn-dialin-only(3),
--		dialout-only(4),
		multiuser(5)
	    } 
	    ACCESS  read-write
	    STATUS  mandatory

	    DESCRIPTION
                "The type of the PPP multiprotocol interface. A new dialup
		interface is created when this field is set to the value
		isdn-dialup(1), isdn-dialin-only(3) or multiuser(5).

                A leased line interface cannot be created by setting this
                field to leased(2), but is automatically established
		if there is a corresponding leased line configuration
		(for example in the IsdnChTable, x21IfTable, serialIfTable).

		Setting this object to isdn-dialin-only(3) only incoming
		connections will be accepted, outgoing connection attempts
		are blocked.

		Setting this object to multiuser(5), up to biboPPPMaxConn
		matching incoming connections (see biboPPPAuthentication,
		biboPPPAuthSecret, biboPPPAuthIdent) from different dialin
		partners will be accepted.

		In all cases, a new entry in the biboPPPTable creates
                corresponding entries in the ifTable (a new interface) 
                and in the biboPPPStatTable (PPP statistics)."
	    DEFVAL { isdn-dialup }
	::= { biboPPPEntry 2 }

	biboPPPEncapsulation OBJECT-TYPE
	    SYNTAX  INTEGER { 
		ppp(1), 
		x25(2),
--		x25-ppp(3),
		ip-lapb(4),
		delete(5),
		ip-hdlc(6),
		mpr-lapb(7),
		mpr-hdlc(8),
		frame-relay(9),
--		x31-bchan(10),
                x75-ppp(11),
--                x75btx-ppp(12),
--		x25-nosig(13),
--		x25-ppp-opt(14),
--		x25-pad(15),
--                x25-noconfig(16),
--                x25-noconfig-nosig(17),
--		ipoa(18),
		v120-ppp(19)
	    } 
	    ACCESS  read-write
	    STATUS  mandatory

	    DESCRIPTION
		"The layer 2 encapsulation of the link. The use of
                ppp(1) as described in RFC 1661 is the preferred 
                encapsulation for point-to-point links. The encapsulation 
                is set to x25(2) for X.25-only links and to x25-ppp(3) for 
                concurrent use of X.25 and PPP.

		Mpr-lapb(7) and mpr-hdlc(8) are popular proprietary
		encapsulations. They both use the ethertype number
		for protocol multiplexing. The former is used when
		error correction or data compression (v42bis) is desired.
		The latter (mpr-hdlc) is compatible to Cisco's HDLC
		encapsulation.

		On IP-only links it is also possible to use the
		ISO LAPB protocol (ip-lapb(4)), also known as X.75,
		or raw hdlc framing (ip-hdlc(6)).

                The x75-ppp encapsulation provides PPP over X.75 (LAPB)
		framing,  x75btx-ppp provides PPP over T.70 and LAPB framing
		including a BTX protocol header.

		The x25-nosig(13) encapsulation is used to establish X.25
		connections over dialup links without specific signalling
		on the D-channel (pure data call).

                The x25-ppp-opt encapsulation provides a special kind of the
                x25-ppp encapsulation. Dialin partner will be authenticated
                either outband to establish an X.25 connection via ISDN or
                optional inband by using the point-to-point protocol (PPP).
                Concurrent use of X.25 and PPP encapsulation is excluded.

		The x25-noconfig(16) and x25-noconfig-nosig(17) encapsulations
		provide a solution for establishing X.25 connections via ISDN.
		The dial number will be derived from X.25 destination address
		by using special rules. 

		V42bis data compression can be enabled on LAPB links only, 
		because v42bis requires an error free connection.

		The v120-ppp(19) enables a GSM HSCSD connect. Data Rates up 
		to 57KBps are possible.

		Dialup links can be removed by setting this field
                to delete(5). This has no effect on permanent links."
	    DEFVAL { ppp }
	::= { biboPPPEntry 3 }

	biboPPPKeepalive OBJECT-TYPE
	    SYNTAX  INTEGER { 
		on(1), 
		off(2) 
	    } 
	    ACCESS  read-write
	    STATUS  obsolete

	    DESCRIPTION
		 "When set to on(1), keepalive packets are sent in 
                regular intervals during the connection. Keepalive packets
                can not be sent using the ip-lapb or x25 encapsulation."
	    DEFVAL { off }
	::= { biboPPPEntry 4 }

	biboPPPTimeout OBJECT-TYPE
	    SYNTAX  INTEGER  (500..10000)
	    ACCESS  read-write
	    STATUS  mandatory

	    DESCRIPTION
		"The number of milliseconds waiting before 
		 retransmitting a PPP configure packet."
	    DEFVAL { 3000 }
	::= { biboPPPEntry 5 }

	biboPPPCompression OBJECT-TYPE
	    SYNTAX  INTEGER { 
		none(1), 
		v42bis(2),
		stac(3),
                ms-stac(4),
                mppc(5)
	    } 
	    ACCESS  read-write
	    STATUS  mandatory

	    DESCRIPTION
		 "The throughput can be enhanced up to factor three
		  using the V42bis compression method or the Stac LZS
                  compression algorithm. V42bis is currently supported
                  with the ip-lapb and mpr-lapb encapsulation. Stac LZS
                  compression algorithm is provided using PPP encapsulated
                  links, stac(3) indicates support of Sequence checking,
                  ms-stac(4) indicates support of Extended mode which is
                  prefered by Microsoft. Both check modes are implemented 
                  according RFC 1974.
                  When set to mppc(5), the Microsoft Point-to-Point
                  Compression (MPPC) Protocol according RFC 2118 is
                  negotiated. MPPC uses an LZ based algorithm with a
                  sliding window history buffer."
	    DEFVAL { none }
	::= { biboPPPEntry 6 }

	biboPPPAuthentication OBJECT-TYPE
	    SYNTAX  INTEGER { 
		none(1), 
		pap(2), 
		chap(3), 
		both(4),
		radius(5),
                ms-chap(6),
                all(7),
                ms-chapv2(8)
	    } 
	    ACCESS  read-write
	    STATUS  mandatory

	    DESCRIPTION
		"The type of authentication used on the point-to-point
                link as described in RFC 1334. The authentication
                protocol supports pap(2) (Password Authentication Protocol),
                chap(3) (Challenge Handshake Authentication Protocol),
                or both(4). When set to both(4), the link must be 
                successfully authenticated by either CHAP or PAP. The type
                ms-chap(6) and ms-chapv2(8) are Microsofts proprietary CHAP
		authentication procedures (using MD4 and DES encryption
		instead of MD5 encryption algorithm), all(7) includes PAP,
		CHAP adn MS-CHAP Version 1 and 2.

		Another way to authenticate dial-in users is by using
		RADIUS (remote authentication dial in user service).
		Users can authenticate themselves either using PAP, CHAP or
                MS-CHAP Version 1 and 2. In general the system creates PPP
                interfaces with this authentication itself, but it's also
                possible to take advance of the RADIUS dial-in services 
                with pre-configured interfaces. See biboAdmRadiusServer for
                further details."
	    DEFVAL { none }
	::= { biboPPPEntry 7 }

	biboPPPAuthIdent OBJECT-TYPE
	    SYNTAX  DisplayString (SIZE (0..255))
	    ACCESS  read-write
	    STATUS  mandatory

	    DESCRIPTION
		"The remote authentication identification string. The
                local authentication identification string is taken from the
                contents of the variable biboPPPLocalIdent."
	::= { biboPPPEntry 8 }

	biboPPPAuthSecret OBJECT-TYPE
	    SYNTAX  DisplayString (SIZE (0..255))
	    ACCESS  read-write
	    STATUS  mandatory

	    DESCRIPTION
		"The authentication secret, which is used symmetrically
		 for both local and remote sides of the PPP link."
	::= { biboPPPEntry 9 }

	biboPPPIpAddress OBJECT-TYPE
	    SYNTAX  INTEGER { 
		static(1), 
		dynamic-server(2),
		dynamic-client(3)
	    } 
	    ACCESS  read-write
	    STATUS  mandatory

	    DESCRIPTION
		"The IP control protocol as described in RFC1332
		 has a means of negotiating IP-addresses. When this
		 option is set to dynamic-server(2), an available
		 IP-address found in biboPPPIpAddrTable is assigned
		 as the remote IP-address and a temporary route is
		 created during the uptime of the interface.

		 When set to dynamic-client(3), the remote system is
		 asked to tell us our own IP-address. A host route 
		 will be created during the uptime of the interface.
		 In most cases this option will be set automatically
		 by the network address translation option.

		 In static(1) mode, address-negotiation is not forced."
	    DEFVAL { static }
	::= { biboPPPEntry 10 }

	biboPPPRetryTime OBJECT-TYPE
	    SYNTAX  INTEGER (0..3600)
	    ACCESS  read-write
	    STATUS  mandatory

	    DESCRIPTION
		"Time in seconds to wait before retrying an ISDN call
		 or PPTP control connection.

		 This value is also used as timeout for the delayed callback
		 (see biboPPPCallback_delayed)."
	    DEFVAL { 4 }
	::= { biboPPPEntry 11 }

	biboPPPBlockTime OBJECT-TYPE
	    SYNTAX  INTEGER (0..2147483647)
	    ACCESS  read-write
	    STATUS  mandatory

	    DESCRIPTION
		"Time in seconds to wait after a connection failure
		 (e.g. the number of biboPPPMaxRetries calls failed).
                 When set to zero, the interface state is never set to
                 blocked."
	    DEFVAL { 300 }
	::= { biboPPPEntry 12 }

	biboPPPMaxRetries OBJECT-TYPE
	    SYNTAX  INTEGER (0..100)
	    ACCESS  read-write
	    STATUS  mandatory

	    DESCRIPTION
		"The number of dialup retries before changing to
		 the blocked state."
	    DEFVAL { 5 }
	::= { biboPPPEntry 13 }

	biboPPPShortHold OBJECT-TYPE
	    SYNTAX  INTEGER (-1..3600)
	    ACCESS  read-write
	    STATUS  mandatory

	    DESCRIPTION
		"The time in seconds to wait, once the channel is silent,
		(that is, no data is being received or transmitted) before
		terminating the link. When set to zero the short hold
		mode is disabled, when set to -1 the short hold mode is
		disabled and the link will be reconnected when connection
		was lost."
	    DEFVAL { 20 }
	::= { biboPPPEntry 14 }

	biboPPPInitConn OBJECT-TYPE
	    SYNTAX  INTEGER (1..250)
	    ACCESS  read-write
	    STATUS  mandatory

	    DESCRIPTION
		" The number of channels to initially set up for this 
                interface."
	    DEFVAL { 1 }
	::= { biboPPPEntry 15 }

	biboPPPMaxConn OBJECT-TYPE
	    SYNTAX  INTEGER (0..250)
	    ACCESS  read-write
	    STATUS  mandatory

	    DESCRIPTION
		"The maximum number of channels bundled for this interface."
	    DEFVAL { 1 }
	::= { biboPPPEntry 16 }

	biboPPPMinConn OBJECT-TYPE
	    SYNTAX  INTEGER (0..250)
	    ACCESS  read-write
	    STATUS  mandatory

	    DESCRIPTION
		"The minimum number of channels bundled for this interface."
	    DEFVAL { 1 }
	::= { biboPPPEntry 17 }

	biboPPPCallback OBJECT-TYPE
	    SYNTAX  INTEGER { 
		enabled(1),
		disabled(2),
		expected(3),
                ppp-offered(4),
                delayed(5),
                ppp-callback-optional(6),
                vpn(7),
		expected-cbcp(8)
	    } 
	    ACCESS  read-write
	    STATUS  mandatory

	    DESCRIPTION
		"If this object is enabled(1), and the call is recognized by
                the dialed number then calls are never accepted, and a
                callback is forced for incoming calls at once. The callback
                can be delayed for biboPPPRetryTime seconds by setting this
                entry to delayed(5).
                If the call is recognized by inband authentication (PAP or
                CHAP) then the actual connection is closed and a callback is
                performed at once.
                Setting this value to ppp-offered(4) allows a called peer to
                call back the calling site if offered by PPP negotiation. For
                PABX dialout a dialprefix is added to the number, if offered
                by the calling site (see isdnStkTable).

                If this object is set to expected(3), only one initial
                outgoing call is made expecting a callback.

                If this object is set to ppp-callback-optional(6), the CBCP
                option 'no callback' is also offered to the Windows client
                so that the user can decide wether he wants to be called back
                or not.

                Setting this value to vpn(7) a callback will be performed
                either via PPTP (if biboPPPLayer1Protocol is set to
                pptp-pns(20) or pptp-pac(23)) or via ipsec.

		Setting this value to expected_cbcp(8), callback is requested
		by using the Callback Control Protocol (CBCP) - same procedure
		as done by Windows Clients."
	    DEFVAL { disabled }
	::= { biboPPPEntry 18 }

	biboPPPLayer1Protocol OBJECT-TYPE
	    SYNTAX INTEGER {
		data-64k(1),
		data-56k(2),
		modem(3),
		dovb(4),
		v110-1200(5),
		v110-2400(6),
		v110-4800(7),
		v110-9600(8),
		v110-14400(9),
		v110-19200(10),
		v110-38400(11),
                modem-profile-1(12),
                modem-profile-2(13),
                modem-profile-3(14),
                modem-profile-4(15),
                modem-profile-5(16),
                modem-profile-6(17),
                modem-profile-7(18),
                modem-profile-8(19),
                pptp-pns(20),
                pppoe(21),
                aodi(22),
		pptp-pac(23),
		pppoa(24),
                l2tp-lns(25),
                l2tp-lac(26),
                pppox25(27),
                dovb-64k(28),
		gprs(29),
		eth-emu(30)
	    }
	    ACCESS  read-write
	    STATUS  mandatory

	    DESCRIPTION
		"This entry is used to select the layer 1 protocol settings
		 for this partner. Normally the correct entry is hdlc-64."
	    DEFVAL { data-64k }
	::= { biboPPPEntry 19 }

	biboPPPLoginString OBJECT-TYPE
	    SYNTAX  DisplayString (SIZE (0..255))
	    ACCESS  read-write
	    STATUS  mandatory

	    DESCRIPTION
		"A textual string containing a login sequence (script)
                 composed of fields in the format [expect send], comparable
                 to chat scripts commonly used on other sytems. This 
                 script is required i.e. to establish an asynchronus PPP
                 dialup connection to CompuServe."
	::= { biboPPPEntry 20 }

	biboPPPVJHeaderComp OBJECT-TYPE
	    SYNTAX  INTEGER { 
		enabled(1),
		disabled(2)
	    } 
	    ACCESS  read-write
	    STATUS  mandatory

	    DESCRIPTION
		"This entry is used to enable Van Jacobsen TCP/IP header
		 compression, which reduces the size of TCP/IP packet
		 headers and increases the efficiency of line utilization."
	    DEFVAL { disabled }
	::= { biboPPPEntry 21 }

	biboPPPLayer2Mode OBJECT-TYPE
	    SYNTAX  INTEGER { 
		auto(1),
		dte(2),
		dce(3)
	    } 
	    ACCESS  read-write
	    STATUS  mandatory

	    DESCRIPTION
		"This object specifies the layer 2 mode to be used for a
		 connection. It is only relevant, if the Encapsulation
		 involves an LAPB protocol. This is the case for 
                 x25, x25-ppp, ip-lapb, lapb, x31-bchan, x75-ppp, x75btx-ppp,
                 x25-nosig, v120-ppp. The Default value of this object is auto.
		 For dialup connection, the layer 2 mode will than be DTE,
		 on the calling side and DCE on the called side. For
		 permanent connections, the layer 2 mode is set at lower
		 layers (for example isdnChType in the isdnChTable).


		 When this object is set to dte or dce, the layer 2 mode
		 will always be DTE or DCE, regardless of the call direction
		 or the settings at the lower layer."
	    DEFVAL { auto }
	::= { biboPPPEntry 22 }

	biboPPPDynShortHold OBJECT-TYPE
	    SYNTAX  INTEGER (0..100)
	    ACCESS  read-write
	    STATUS  mandatory

	    DESCRIPTION
		 "Optimizes idle time disconnects depending on the charging
                  information received during the connection. This value
                  specifies the minimum inactivity time (channel is silent)
                  in percents of the current charging interval length and is
                  only used for outgoing connections. Incoming connections
                  are disconnected after idle time according to the value
                  biboPPPShortHold.
                  Please note that this only works if your ISDN port has the
                  AOCD service enabled (advice of charging during the call).
                  For instance in Germany this is an extra paid service.
                  (Even the 'Komfortanschluss' does only include AOCE
                  [advice of charge at the end of the call], so AOCD has to
                  be ordered and paid extra.)"
	    DEFVAL { 0 }
	::= { biboPPPEntry 23 }

	biboPPPLocalIdent OBJECT-TYPE
	    SYNTAX  DisplayString (SIZE (0..255))
	    ACCESS  read-write
	    STATUS  mandatory

	    DESCRIPTION	
	         "This is the local identification string used for PPP
                  authentication(PAP/CHAP/MS-CHAP)."
	::= { biboPPPEntry 24 }

	biboPPPDNSNegotiation OBJECT-TYPE
	    SYNTAX  INTEGER { 
		disabled(1),
		enabled(2),
                dynamic-client(3),
                dynamic-server(4),
                dynamic-client-with-wins(5)
	    } 
	    ACCESS  read-write
	    STATUS  mandatory

	    DESCRIPTION
		"The IP control protocol extensions as described in
                 RFC 1877 has a means of negotiating primary and
                 secondary Domain Name System (DNS) server addresses.

                 When this option is disabled(1), no DNS negotiation
                 will be performed.
                 If enabled(2), DNS negotiation behavier depends on
                 biboPPPIpAddress switch (client or server mode).
                 Setting to dynamic-client(3), the remote system is asked
                 to tell us the IP-address(es) of primary and/or secondary
                 DNS. In dynamic-client-with-wins mode it is also asked for
                 the IP-addresses of the primary and secondary WINS.
                 Setting to dynamic_server(4), primary and/or secondary
                 DNS IP-address(es) found in ipDynAdddrPoolDnsServer1 and
                 ipDynAddrPoolDnsServer2 (or if empty biboAdmNameServer 
                 and/or biboAdmNameServ2), if asked, will be send to remote."
            DEFVAL { enabled }
	::= { biboPPPEntry 25 }

	biboPPPEncryption OBJECT-TYPE
	    SYNTAX  INTEGER { 
		none(1), 
		mppe-40(2),
		mppe-128(3),
		des-56(4),
		triple-des-168(5),
		blowfish-168(6),
		mppe-56(7),
		mppev2-40(8),
		mppev2-56(9),
		mppev2-128(10),
		blowfish-56(11),
		mppev2-40-rfc3078(12),
		mppev2-56-rfc3078(13),
		mppev2-128-rfc3078(14),
		mppev1-40-fixed(15),
		mppev1-56-fixed(16),
		mppev1-128-fixed(17),
		mppev1-128-ms-compat(18),
		mppev2-128-ms-compat(19)
	    } 
	    ACCESS  read-write
	    STATUS  mandatory

	    DESCRIPTION
                 "This field specifies the data encryption scheme for
                  en(de)crypting PPP encapsulated multi-protocol datagrams.
                  Setting to mppe-40(2), mppe-128(3) or mppe-56(7) the
		  Microsoft Point to Point Encryption Protocol (MPPE) will be
		  enabled, using a 40 bit, 128 bit respectively 56 bit session
		  key for initializing encryption tables.
                  Setting to mppev2-40(8), mppev2-56(9) or mppev2-128(10) the
		  old-style Microsoft Point to Point Encryption Protocol (MPPE)
		  'stateless mode' will be enabled, using a 40 bit, 56 bit
		  respectively 128 bit session key.
                  Setting to mppev2-40-rfc3078(12), mppev2-56-rfc3078(13) or
		  mppev2-128-rfc3078(14) the Microsoft Point to Point Encryption
		  Protocol (MPPE) 'stateless mode' in conformance with RFC 3078
		  will be enabled, using a 40 bit, 56 bit respectively 128 bit
		  session key.
		  Setting to mppev1-40-fixed(15), mppev1-56-fixed(16) or
		  mppev1=128-fixed(17) only the 'old' MPPE V1 (stateful) mode
		  will be negotiated and used.
		  Setting to mppev1-128-ms-compat(18) 'old' MPPE V1 (stateful)
		  128 bit mode negotiation will be enforced and MS-CHAP V1
		  NT password hashing non-conform to RFC 3079 but compatible
		  with Microsoft and Cisco products will be used.
		  Setting to mppev2-128-ms-compat(19) 'old' MPPE V2 (stateless)
		  128 bit mode will be offered first and MS-CHAP V1 NT hash
		  non-conform to RFC 3079 but compatible with Microsoft and
		  Cisco products will be used."
	    DEFVAL { none }
	::= { biboPPPEntry 26 }

	biboPPPLQMonitoring OBJECT-TYPE
	    SYNTAX  INTEGER { 
                off(1), 
                on(2)
	    } 
	    ACCESS  read-write
	    STATUS  mandatory

	    DESCRIPTION
                 "This parameter enables (2) or disables (1) PPP Link Quality
                  Monitoring (LQM) according RFC 1989. When set to on(2) LQM
                  is added to the list of parameters used in LCP negotiation.
                  If LQM is acknowledged by peer link quality reports will be
                  generated and send periodically."
	    DEFVAL { off }
	::= { biboPPPEntry 27 }

	biboPPPIpPoolId OBJECT-TYPE
	    SYNTAX  INTEGER
	    ACCESS  read-write
	    STATUS  mandatory

	    DESCRIPTION
		 "Pool ID value to select an IP address pool for dynamic IP
		  address assignment via IPCP. See also PPPIpPoolTable
		  for further details."
	    DEFVAL { 0 }
	::= { biboPPPEntry 28 }

	biboPPPSessionTimeout OBJECT-TYPE
	    SYNTAX  INTEGER
	    ACCESS  read-write
	    STATUS  mandatory

	    DESCRIPTION
		 "Maximum number of seconds before termination the established
		  PPP session, regardless there is any data throughput on the
		  corresponding link(s). When set to 0, there no limit for the
		  duration of the PPP session."
	    DEFVAL { 0 }
	::= { biboPPPEntry 29 }

	biboPPPLayer1DiscDelay OBJECT-TYPE
	    SYNTAX  INTEGER {
                enabled(1), 
                disabled(2)
	    } 
	    ACCESS  read-write
	    STATUS  mandatory

	    DESCRIPTION
		 "This parameter specifies wether the link (layer 1) should be
		  disconnected immediately (after receiving a layer 2 disconnect)
		  or delayed (after expiration of biboPPPShortHold seconds).
		  It is only relevant for X.25 encapsulations over dialup links.
		  If enabled(2), biboPPPShortHold specifies the time interval to be
		  expired after receiving a layer 2 disconnect before disconnecting
		  the link. If set to disabled(2), the layer 2 disconnect leads to
		  the immediate disconnect of the layer 1."
	    DEFVAL { enabled }
	::= { biboPPPEntry 30 }

    biboPPPAuthDomain OBJECT-TYPE
	    SYNTAX  DisplayString (SIZE (0..255))
	    ACCESS  read-write
	    STATUS  mandatory

	    DESCRIPTION
		"The authentication domain, which is used 
		 for authenticating via MS-CHAP with enabled DomainName."
	::= { biboPPPEntry 31 }

	biboPPPAliveCheck OBJECT-TYPE
	    SYNTAX  INTEGER { 
		enabled(1), 
		disabled(2) 
	    } 
	    ACCESS  read-write
	    STATUS  mandatory

	    DESCRIPTION
		 "When set to enabled(1), LCP Echo Request (in case of
		  encapsulation PPP) or Cisco-HDLC keepalive messages
		  (in case of encapsulation cisco-hdlc) are sent in 
                  regular intervals during the connection. Note that for
		  ip-lapb or x25 encapsulation the liveliness check is done
		  within the X.75 layer (independent of this setting)."
	    DEFVAL { enabled }
	::= { biboPPPEntry 32 }

    -- PPP statistics

	biboPPPStatTable OBJECT-TYPE
	    SYNTAX  SEQUENCE OF BiboPPPStatEntry
	    ACCESS  not-accessible
	    STATUS  mandatory
	    DESCRIPTION
		"The biboPPPStatTable contains statistical connection-
                specific information. Only the system can add or delete
                entries to this table.

                Creating entries: Entries are created by the system
                each time a new PPP interface is created in the 
                biboPPPTable.

                Deleting entries: Entries are removed by the system
                when the corresponding PPP interface is removed."
	::= { ppp 2 }

	biboPPPStatEntry OBJECT-TYPE
	    SYNTAX  BiboPPPStatEntry
	    ACCESS  not-accessible
	    STATUS  mandatory
	    DESCRIPTION
		""
	    INDEX   { biboPPPConnIfIndex }
	::= { biboPPPStatTable 1 }

	BiboPPPStatEntry ::=
	    SEQUENCE {
		biboPPPConnIfIndex			INTEGER,
		biboPPPConnActive			INTEGER,
		biboPPPConnProtocols			INTEGER,
		biboPPPConnState			INTEGER,
		biboPPPConnDuration			INTEGER,
		biboPPPConnUnits			Counter,
		biboPPPConnTransmitOctets		Counter,
		biboPPPConnReceivedOctets		Counter,
		biboPPPConnOutgoingCalls		Counter,
		biboPPPConnOutgoingFails		Counter,
		biboPPPConnIncomingCalls		Counter,
		biboPPPConnIncomingFails		Counter,
		biboPPPTotalDuration			INTEGER,
		biboPPPTotalUnits			Counter,
		biboPPPTotalTransmitOctets		Counter,
		biboPPPTotalReceivedOctets		Counter,
		biboPPPTotalOutgoingCalls		Counter,
		biboPPPTotalOutgoingFails		Counter,
		biboPPPTotalIncomingCalls		Counter,
		biboPPPTotalIncomingFails		Counter,
		biboPPPThroughput			INTEGER,
--		biboPPPCompressionMode                  INTEGER,
		biboPPPChargeInterval                   INTEGER,
		biboPPPIdleTime                         INTEGER,
		biboPPPConnCharge			Counter,
		biboPPPTotalCharge			Counter,
		biboPPPLastConnDuration			INTEGER,
		biboPPPLastConnIdle			INTEGER
	    }

	biboPPPConnIfIndex OBJECT-TYPE
	    SYNTAX  INTEGER 
	    ACCESS  read-only
	    STATUS  mandatory

	    DESCRIPTION
		"Correlating PPP interface index."
	::= { biboPPPStatEntry 1 }

	biboPPPConnActive OBJECT-TYPE
	    SYNTAX  INTEGER (1..250)
	    ACCESS  read-only
	    STATUS  mandatory

	    DESCRIPTION
		"The actual number of bundled channels."
	::= { biboPPPStatEntry 2 }

	biboPPPConnProtocols OBJECT-TYPE
	    SYNTAX  INTEGER 
	    ACCESS  read-only
	    STATUS  mandatory

	    DESCRIPTION
		"The bitwise ORed protocols successfully negotiated on
		 this connection; currently the following protocols are
		 supported: tcp/ip(1), ipx(2), bridge(4), bpdu(8), x25(16).
		 These protocol values are most likely to change in
		 future software releases."
	::= { biboPPPStatEntry 3 }

	biboPPPConnState OBJECT-TYPE
	    SYNTAX  INTEGER { 
		idle(1), 
		incoming(2), 
		outgoing(3), 
		connected(4), 
		dataxfer(5), 
		disconnect(6),
		authentication-failed(7), 
		authentication-successful(8) 
	    } 
	    ACCESS  read-only
	    STATUS  mandatory

	    DESCRIPTION
		"The physical state of the link. This field is obsolete
		 and will not be supported in a future release."
	    DEFVAL { idle }
	::= { biboPPPStatEntry 4 }

	biboPPPConnDuration OBJECT-TYPE
	    SYNTAX  INTEGER 
	    ACCESS  read-only
	    STATUS  mandatory

	    DESCRIPTION
		"The current link duration on this interface in seconds."
	::= { biboPPPStatEntry 5 }

	biboPPPConnUnits OBJECT-TYPE
	    SYNTAX  Counter 
	    ACCESS  read-only
	    STATUS  mandatory

	    DESCRIPTION
		"The current costs on this interface for all member links."
	::= { biboPPPStatEntry 6 }

	biboPPPConnTransmitOctets OBJECT-TYPE
	    SYNTAX  Counter 
	    ACCESS  read-only
	    STATUS  mandatory

	    DESCRIPTION
		"The octets transmitted on this interface since its last
		 change to the 'up' state."
	::= { biboPPPStatEntry 7 }

	biboPPPConnReceivedOctets OBJECT-TYPE
	    SYNTAX  Counter 
	    ACCESS  read-only
	    STATUS  mandatory

	    DESCRIPTION
		"The octets received since its last change to the `up'
                state."
	::= { biboPPPStatEntry 8 }

	biboPPPConnOutgoingCalls OBJECT-TYPE
	    SYNTAX  Counter 
	    ACCESS  read-only
	    STATUS  mandatory

	    DESCRIPTION
		"The number of outgoing calls on this interface since
		 its last change to the 'up' state."
	::= { biboPPPStatEntry 9 }

	biboPPPConnOutgoingFails OBJECT-TYPE
	    SYNTAX  Counter 
	    ACCESS  read-only
	    STATUS  mandatory

	    DESCRIPTION
		"The number of outgoing call failures on this interface
		 since its last change to the 'up' state."
	::= { biboPPPStatEntry 10 }

	biboPPPConnIncomingCalls OBJECT-TYPE
	    SYNTAX  Counter 
	    ACCESS  read-only
	    STATUS  mandatory

	    DESCRIPTION
		"The number of incoming calls on this interface since
		 its last change to the up state."
	::= { biboPPPStatEntry 11 }

	biboPPPConnIncomingFails OBJECT-TYPE
	    SYNTAX  Counter 
	    ACCESS  read-only
	    STATUS  mandatory

	    DESCRIPTION
		"The number of incoming call failures on this interface since
		 its last change to the up state."
	::= { biboPPPStatEntry 12 }

	biboPPPTotalDuration OBJECT-TYPE
	    SYNTAX  INTEGER 
	    ACCESS  read-only
	    STATUS  mandatory

	    DESCRIPTION
		"The total link duration in seconds."
	::= { biboPPPStatEntry 13 }

	biboPPPTotalUnits OBJECT-TYPE
	    SYNTAX  Counter 
	    ACCESS  read-only
	    STATUS  mandatory

	    DESCRIPTION
		"The total costs on this interface for all member links."
	::= { biboPPPStatEntry 14 }

	biboPPPTotalTransmitOctets OBJECT-TYPE
	    SYNTAX  Counter 
	    ACCESS  read-only
	    STATUS  mandatory

	    DESCRIPTION
		"The total amount of octets transmitted."
	::= { biboPPPStatEntry 15 }

	biboPPPTotalReceivedOctets OBJECT-TYPE
	    SYNTAX  Counter 
	    ACCESS  read-only
	    STATUS  mandatory

	    DESCRIPTION
		"The total amount of octets received."
	::= { biboPPPStatEntry 16 }

	biboPPPTotalOutgoingCalls OBJECT-TYPE
	    SYNTAX  Counter 
	    ACCESS  read-only
	    STATUS  mandatory

	    DESCRIPTION
		"The total number of outgoing calls."
	::= { biboPPPStatEntry 17 }

	biboPPPTotalOutgoingFails OBJECT-TYPE
	    SYNTAX  Counter 
	    ACCESS  read-only
	    STATUS  mandatory

	    DESCRIPTION
		"The total number of outgoing call failures."
	::= { biboPPPStatEntry 18 }

	biboPPPTotalIncomingCalls OBJECT-TYPE
	    SYNTAX  Counter 
	    ACCESS  read-only
	    STATUS  mandatory

	    DESCRIPTION
		"The total number of incoming calls."
	::= { biboPPPStatEntry 19 }

	biboPPPTotalIncomingFails OBJECT-TYPE
	    SYNTAX  Counter 
	    ACCESS  read-only
	    STATUS  mandatory

	    DESCRIPTION
		"The total number of incoming call failures."
	::= { biboPPPStatEntry 20 }

	biboPPPThroughput OBJECT-TYPE
	    SYNTAX  Counter 
	    ACCESS  read-only
	    STATUS  mandatory

	    DESCRIPTION
		"The actual throughput of the interface; updated every
                 5 seconds. Note that only the actual maximum of the
		 both directions (send / receive) is considered."
	::= { biboPPPStatEntry 21 }

--	biboPPPCompressionMode OBJECT-TYPE
--	    SYNTAX  INTEGER { 
--		inactive(1), 
--		active(2) 
--	    } 
--	    ACCESS  read-only
--	    STATUS  mandatory
--	    DESCRIPTION
--		"This object describes wether data compression is active
--		 for this interface. 42bis or Stac LZS compression
--               algorithm can be enabled in the biboPPPTable."
--	    DEFVAL { inactive }
--	::= { biboPPPStatEntry 22 }
--
	biboPPPChargeInterval OBJECT-TYPE
	    SYNTAX  INTEGER (0..3600)
	    ACCESS  read-only
	    STATUS  mandatory

	    DESCRIPTION
		"Describes the measured interval between charging info
                 elements received from the ISDN network."
	    DEFVAL { 0 }
	::= { biboPPPStatEntry 23 }

	biboPPPIdleTime OBJECT-TYPE
	    SYNTAX  INTEGER (0..3600)
	    ACCESS  read-only
	    STATUS  mandatory

	    DESCRIPTION
		"The currently measured connection inactivity time
                 (channel is silent)."
	    DEFVAL { 0 }
	::= { biboPPPStatEntry 24 }

	biboPPPConnCharge OBJECT-TYPE
	    SYNTAX  Counter 
	    ACCESS  read-only
	    STATUS  mandatory

	    DESCRIPTION
		"The current charge on this interface as 1/1000 of the
		respective currency."
	::= { biboPPPStatEntry 25 }

	biboPPPTotalCharge OBJECT-TYPE
	    SYNTAX  Counter 
	    ACCESS  read-only
	    STATUS  mandatory

	    DESCRIPTION
		"The total charge on this interface as 1/1000 of the
		respective currency."
	::= { biboPPPStatEntry 26 }

	biboPPPLastConnDuration OBJECT-TYPE
	    SYNTAX  INTEGER 
	    ACCESS  read-only
	    STATUS  mandatory

	    DESCRIPTION
		"The duration of the last connection on this interface
		 in seconds."
	::= { biboPPPStatEntry 27 }

	biboPPPLastConnIdle OBJECT-TYPE
	    SYNTAX  INTEGER 
	    ACCESS  read-only
	    STATUS  mandatory

	    DESCRIPTION
		"The inactivity time of the last connection on this interface
		 in seconds."
	::= { biboPPPStatEntry 28 }


    -- PPP-specific statistics

	pppSessionTable OBJECT-TYPE
	    SYNTAX  SEQUENCE OF PppSessionEntry
	    ACCESS  not-accessible
	    STATUS  mandatory
	    DESCRIPTION
		"The pppSessionTable contains statistical information
                for the PPP protocol. Only the system can add or delete
                entries to this table.

                Creating entries: Entries are created by the system
                each time a new PPP connection is created.

                Deleting entries: Entries are removed by the system
                when the corresponding PPP connection is terminated."
	::= { ppp 10 }

	pppSessionEntry OBJECT-TYPE
	    SYNTAX  PppSessionEntry
	    ACCESS  not-accessible
	    STATUS  mandatory
	    DESCRIPTION
		""
	    INDEX   { pppSessionIfIndex }
	::= { pppSessionTable 1 }

	PppSessionEntry ::=
	    SEQUENCE {
		pppSessionIfIndex		INTEGER,
		pppSessionMlp			INTEGER,
		pppSessionMru			Counter,
		pppSessionLcpCallback		INTEGER,
		pppSessionAuthProt		INTEGER,
		pppSessionCompression		INTEGER,
		pppSessionEncryption		INTEGER,
		pppSessionCbcpMode		INTEGER,
		pppSessionCbcpDelay		Counter,
		pppSessionLocIpAddr		IpAddress,
		pppSessionRemIpAddr		IpAddress,
		pppSessionDNS1			IpAddress,
		pppSessionDNS2			IpAddress,
		pppSessionWINS1			IpAddress,
		pppSessionWINS2			IpAddress,
		pppSessionVJHeaderComp		INTEGER,
--		pppSessionIpxcpNodeNumber	OCTET STRING (SIZE(6)),
		pppSessionBacpFavoredPeer	INTEGER,
		pppSessionIpcpStatus		INTEGER






	    }

	pppSessionIfIndex OBJECT-TYPE
	    SYNTAX  INTEGER 
	    ACCESS  read-only
	    STATUS  mandatory

	    DESCRIPTION
		"Correlating PPP interface index."
	::= { pppSessionEntry 1 }

	pppSessionMlp OBJECT-TYPE
	    SYNTAX  INTEGER { 
		none(1), 
		negotiated(2) 
	    } 
	    ACCESS  read-only
	    STATUS  mandatory

	    DESCRIPTION
		"Indicates negotiation of Multilink PPP."
	::= { pppSessionEntry 2 }

	pppSessionMru OBJECT-TYPE
	    SYNTAX  Counter 
	    ACCESS  read-only
	    STATUS  mandatory

	    DESCRIPTION
		"Peer's MRU/MRRU LCP option."
	::= { pppSessionEntry 3 }

	pppSessionLcpCallback OBJECT-TYPE
	    SYNTAX  INTEGER { 
		none(1), 
		lcp(2), 
		cbcp(3) 
	    } 
	    ACCESS  read-only
	    STATUS  mandatory

	    DESCRIPTION
		"Callback option inside LCP negotiation."
	::= { pppSessionEntry 4 }

	pppSessionAuthProt OBJECT-TYPE
	    SYNTAX  INTEGER { 
		none(1), 
		pap(2), 
		chap(3), 
		ms-chapv1(4), 
		ms-chapv2(5) 
	    } 
	    ACCESS  read-only
	    STATUS  mandatory

	    DESCRIPTION
		"The negotiated PPP authentication protocol."
	::= { pppSessionEntry 5 }

	pppSessionCompression OBJECT-TYPE
	    SYNTAX  INTEGER { 
		none(1), 
		stac(2), 
		ms-stac(3), 
		mppc(4) 
	    } 
	    ACCESS  read-only
	    STATUS  mandatory

	    DESCRIPTION
		"The negotiated CCP compression mode."
	::= { pppSessionEntry 6 }

	pppSessionEncryption OBJECT-TYPE
	    SYNTAX  INTEGER { 
		none(1), 
		mppe-40(2), 
		mppe-128(3),
		des-56(4),
		triple-des-168(5),
		blowfish-168(6),
		mppe-56(7),
		mppev2-40(8),
		mppev2-56(9),
		mppev2-128(10),
		blowfish-56(11),
		mppev2-40-rfc3078(12),
		mppev2-56-rfc3078(13),
		mppev2-128-rfc3078(14)
	    } 
	    ACCESS  read-only
	    STATUS  mandatory

	    DESCRIPTION
		"The negotiated CCP encryption mode."
	::= { pppSessionEntry 7 }

	pppSessionCbcpMode OBJECT-TYPE
	    SYNTAX  INTEGER { 
		none(1), 
		no-callback(2), 
		user-specified(3), 
		pre-specified(4) 
	    } 
	    ACCESS  read-only
	    STATUS  mandatory

	    DESCRIPTION
		"The negotiated Callback Control Protocol (CBCP) mode."
	::= { pppSessionEntry 8 }

	pppSessionCbcpDelay OBJECT-TYPE
	    SYNTAX  INTEGER (0..60)
	    ACCESS  read-only
	    STATUS  mandatory

	    DESCRIPTION
		"The negotiated (CBCP) callback delay in seconds."
	::= { pppSessionEntry 9 }

	pppSessionLocIpAddr OBJECT-TYPE
	    SYNTAX  IpAddress 
	    ACCESS  read-only
	    STATUS  mandatory

	    DESCRIPTION
		"The negotiated local IP Address."
	::= { pppSessionEntry 10 }

	pppSessionRemIpAddr OBJECT-TYPE
	    SYNTAX  IpAddress 
	    ACCESS  read-only
	    STATUS  mandatory

	    DESCRIPTION
		"The negotiated remote IP Address."
	::= { pppSessionEntry 11 }

	pppSessionDNS1 OBJECT-TYPE
	    SYNTAX  IpAddress 
	    ACCESS  read-only
	    STATUS  mandatory

	    DESCRIPTION
		"The negotiated first name server IP address."
	::= { pppSessionEntry 12 }

	pppSessionDNS2 OBJECT-TYPE
	    SYNTAX  IpAddress 
	    ACCESS  read-only
	    STATUS  mandatory

	    DESCRIPTION
		"The negotiated second name server IP address."
	::= { pppSessionEntry 13 }

	pppSessionWINS1 OBJECT-TYPE
	    SYNTAX  IpAddress 
	    ACCESS  read-only
	    STATUS  mandatory

	    DESCRIPTION
		"The negotiated first NetBIOS name server (WINS)
                 IP address."
	::= { pppSessionEntry 14 }

	pppSessionWINS2 OBJECT-TYPE
	    SYNTAX  IpAddress 
	    ACCESS  read-only
	    STATUS  mandatory

	    DESCRIPTION
		"The negotiated second NetBIOS name server (WINS)
                 IP address."
	::= { pppSessionEntry 15 }

	pppSessionVJHeaderComp OBJECT-TYPE
	    SYNTAX  INTEGER { 
		none(1),
		negotiated(2)
	    } 
	    ACCESS  read-only
	    STATUS  mandatory

	    DESCRIPTION
		"The negotiation of Van Jacobsen TCP/IP header compression
                 option (IPCP)."
	::= { pppSessionEntry 16 }

--	pppSessionIpxcpNodeNumber OBJECT-TYPE
--	    SYNTAX  OCTET STRING (SIZE(6)) 
--	    ACCESS  read-only
--	    STATUS  mandatory
--
--	    DESCRIPTION
--		"Unique IPX Node Id dynamically assigned the client."
--	::= { pppSessionEntry 17 }

	pppSessionBacpFavoredPeer OBJECT-TYPE
	    SYNTAX  INTEGER { 
		none(1),
		local(2),
		remote(3)
	    } 
	    ACCESS  read-only
	    STATUS  mandatory

	    DESCRIPTION
		"The result of the BACP Favored-Peer negotiation."
	    DEFVAL { none }
	::= { pppSessionEntry 18 }

	pppSessionIpcpStatus OBJECT-TYPE
	    SYNTAX  INTEGER { 
		initial(1),
		starting(2),
		closed(3),
		stopped(4),
		closing(5),
		stopping(6),
		reqsent(7),
		ackrcvd(8),
		acksent(9),
		opened(10)
	    } 
	    ACCESS  read-only
	    STATUS  mandatory

	    DESCRIPTION
		"IPCP FSM status according RFC 1548." 
	::= { pppSessionEntry 19 }



        mlpppStatTable OBJECT-TYPE
            SYNTAX  SEQUENCE OF MlpppStatEntry
            ACCESS  not-accessible
            STATUS  mandatory
            DESCRIPTION
                "The mlpppStatTable contains statistical multilink
                specific information. Only the system can add or delete
                entries to this table.
 
                Creating entries: Entries are created by the system
                each time a new multilink PPP interface is negotiated.
 
                Deleting entries: Entries are removed by the system
                when the multilink feature is disabled."
	::= { ppp 16 }
 
        mlpppStatEntry OBJECT-TYPE
            SYNTAX  MlpppStatEntry
            ACCESS  not-accessible
            STATUS  mandatory
            DESCRIPTION
                ""
            INDEX   { mlpppIfIndex }
        ::= { mlpppStatTable 1 }

        MlpppStatEntry ::=
            SEQUENCE {
                mlpppIfIndex			INTEGER,
        	mlpppNextTxSeqno		INTEGER,
        	mlpppLastRxSeqno		INTEGER,
		mlpppMaxFragCount		INTEGER,
		mlpppMaxFragLifeTime		INTEGER,
		mlpppFragsRcvd			Counter,
		mlpppFragsQueued		Counter,
		mlpppFragsDropped		Counter,
		mlpppPktsReassembled		Counter,
		mlpppBeginOfQueue		INTEGER,
		mlpppEndOfQueue			INTEGER,
		mlpppBFragsQueued		INTEGER,
		mlpppEFragsQueued		INTEGER,
		mlpppMFragsQueued		INTEGER,
		mlpppCFragsQueued		INTEGER,
		mlpppAgeDrops			Counter,
		mlpppOutOfSyncDrops		Counter,
		mlpppOverFlowDrops		Counter,
		mlpppDuplicateDrops		Counter,
		mlpppForwardDeviation		INTEGER,
		mlpppBackwardDeviation		INTEGER,
		mlpppNextReasSeqNo		INTEGER,
		mlpppOutOfOrderWaits		INTEGER,
		mlpppMaxReasBurst		INTEGER,
                mlpppCleanupDrops               Counter 
            }
 
        mlpppIfIndex OBJECT-TYPE
            SYNTAX  INTEGER
            ACCESS  read-only
            STATUS  mandatory
 
            DESCRIPTION
                "Correlating PPP interface index."
        ::= { mlpppStatEntry 1 }
 
        mlpppNextTxSeqno OBJECT-TYPE
	    SYNTAX  INTEGER (0..16777215)
            ACCESS  read-only
            STATUS  mandatory
 
            DESCRIPTION
                ""
        ::= { mlpppStatEntry 2 }
 
        mlpppLastRxSeqno OBJECT-TYPE
	    SYNTAX  INTEGER (0..16777215)
            ACCESS  read-only
            STATUS  mandatory
 
            DESCRIPTION
                ""
        ::= { mlpppStatEntry 3 }
 
        mlpppMaxFragCount OBJECT-TYPE
	    SYNTAX  INTEGER (0..10000)
            ACCESS  read-only
            STATUS  mandatory
 
            DESCRIPTION
                "Maximum size (number of Fragments) of MLPPP reassembling area."
        ::= { mlpppStatEntry 4 }
 
        mlpppMaxFragLifeTime OBJECT-TYPE
	    SYNTAX  INTEGER (0..10)
            ACCESS  read-only
            STATUS  mandatory
 
            DESCRIPTION
                "Maximum lifetime of fragments stored in MLPPP reassembling
		 area."
        ::= { mlpppStatEntry 5 }

        mlpppFragsRcvd OBJECT-TYPE
	    SYNTAX  Counter
            ACCESS  read-only
            STATUS  mandatory
 
            DESCRIPTION
                "Total number of MLPPP fragments received since interface is
		 in operational 'up' status."
        ::= { mlpppStatEntry 6 }

        mlpppFragsQueued OBJECT-TYPE
	    SYNTAX  Counter
            ACCESS  read-only
            STATUS  mandatory
 
            DESCRIPTION
                "Current number of MLPPP fragments stored in MLPPP
		 reassembling area."
        ::= { mlpppStatEntry 7 }

        mlpppFragsDropped OBJECT-TYPE
	    SYNTAX  Counter
            ACCESS  read-only
            STATUS  mandatory
 
            DESCRIPTION
                "Total number of MLPPP fragments dropped since interface is
		 in operational 'up' status."
        ::= { mlpppStatEntry 8 }

        mlpppPktsReassembled OBJECT-TYPE
	    SYNTAX  Counter
            ACCESS  read-only
            STATUS  mandatory
 
            DESCRIPTION
                "Total number pakets reassembled since interface is in
		 operational 'up' status."
        ::= { mlpppStatEntry 9 }

        mlpppBeginOfQueue OBJECT-TYPE
	    SYNTAX  INTEGER (0..16777215)
            ACCESS  read-only
            STATUS  mandatory
 
            DESCRIPTION
                "Sequence Number of first fragment stored in MLPPP
		 reassembling area."
        ::= { mlpppStatEntry 10 }

        mlpppEndOfQueue OBJECT-TYPE
	    SYNTAX  INTEGER (0..16777215)
            ACCESS  read-only
            STATUS  mandatory
 
            DESCRIPTION
                "Sequence Number of last fragment stored in MLPPP
		 reassembling area."
        ::= { mlpppStatEntry 11 }

        mlpppBFragsQueued OBJECT-TYPE
	    SYNTAX  INTEGER (0..10000)
            ACCESS  read-only
            STATUS  mandatory
 
            DESCRIPTION
                "Current number (begin-)fragments stored in MLPPP
		 reassembling area."
        ::= { mlpppStatEntry 12 }

        mlpppEFragsQueued OBJECT-TYPE
	    SYNTAX  INTEGER (0..10000)
            ACCESS  read-only
            STATUS  mandatory
 
            DESCRIPTION
                "Current number (end-)fragments stored in MLPPP
		 reassembling area."
        ::= { mlpppStatEntry 13 }

        mlpppMFragsQueued OBJECT-TYPE
	    SYNTAX  INTEGER (0..10000)
            ACCESS  read-only
            STATUS  mandatory
 
            DESCRIPTION
                "Current number (middle-)fragments stored in MLPPP
		 reassembling area."
        ::= { mlpppStatEntry 14 }

        mlpppCFragsQueued OBJECT-TYPE
	    SYNTAX  INTEGER (0..10000)
            ACCESS  read-only
            STATUS  mandatory
 
            DESCRIPTION
                "Current number (complete-)fragments stored in MLPPP
		 reassembling area."
        ::= { mlpppStatEntry 15 }

        mlpppAgeDrops OBJECT-TYPE
	    SYNTAX  Counter
            ACCESS  read-only
            STATUS  mandatory
 
            DESCRIPTION
                "Total number fragments dropped due to exceeded lifetime, see
		 also mlpppMaxFragLifeTime."
        ::= { mlpppStatEntry 16 }

        mlpppOutOfSyncDrops OBJECT-TYPE
	    SYNTAX  Counter
            ACCESS  read-only
            STATUS  mandatory
 
            DESCRIPTION
                "Total number fragments dropped due to a 'out of sync'
		 condition."
        ::= { mlpppStatEntry 17 }

        mlpppOverFlowDrops OBJECT-TYPE
	    SYNTAX  Counter
            ACCESS  read-only
            STATUS  mandatory
 
            DESCRIPTION
                "Total number fragments dropped due to a MLPPP reassembling
		 area 'overflow' condition, see also mlpppMaxFragCount."
        ::= { mlpppStatEntry 18 }

        mlpppDuplicateDrops OBJECT-TYPE
	    SYNTAX  Counter
            ACCESS  read-only
            STATUS  mandatory
 
            DESCRIPTION
                "Total number duplicate fragments dropped."
        ::= { mlpppStatEntry 19 }

        mlpppForwardDeviation OBJECT-TYPE
	    SYNTAX  INTEGER (0..10000)
            ACCESS  read-only
            STATUS  mandatory
 
            DESCRIPTION
                "Maximum deviation of current received sequence number compared
		 with the end of the reassembling queue in forward direction."
        ::= { mlpppStatEntry 20 }

        mlpppBackwardDeviation OBJECT-TYPE
	    SYNTAX  INTEGER (0..10000)
            ACCESS  read-only
            STATUS  mandatory
 
            DESCRIPTION
                "Maximum deviation of current received sequence number compared
		 with the begin of the reassembling queue in backward direction."
        ::= { mlpppStatEntry 21 }

        mlpppNextReasSeqNo OBJECT-TYPE
	    SYNTAX  INTEGER (0..16777215)
            ACCESS  read-only
            STATUS  mandatory
 
            DESCRIPTION
                "Awaited first sequence number of next the fragment chain
		 or packet ready to be distributed to the upper layer."
        ::= { mlpppStatEntry 22 }

        mlpppOutOfOrderWaits OBJECT-TYPE
	    SYNTAX  INTEGER
            ACCESS  read-only
            STATUS  mandatory
 
            DESCRIPTION
                "Number of cycles already reassembled packets are retained
		 due to the expected mlpppNextReasSeqNo value."
        ::= { mlpppStatEntry 23 }

        mlpppMaxReasBurst OBJECT-TYPE
	    SYNTAX  INTEGER (0..16777215)
            ACCESS  read-only
            STATUS  mandatory
 
            DESCRIPTION
                "Maximum number of reassembled packets sended to the upper
		 layer within one cycle."
        ::= { mlpppStatEntry 24 }

        mlpppCleanupDrops OBJECT-TYPE
	    SYNTAX  Counter
            ACCESS  read-only
            STATUS  mandatory
 
            DESCRIPTION
                "Number of fragments dropped cause they were still in
                 in the queue when interface went down." 
        ::= { mlpppStatEntry 25 }


    -- Statistics of PPP links

	biboPPPLinkTable OBJECT-TYPE
	    SYNTAX  SEQUENCE OF BiboPPPLinkEntry
	    ACCESS  not-accessible
	    STATUS  mandatory
	    DESCRIPTION
		"The biboPPPLinkTable contains statistical information
                for each current PPP link on the system. Only the system
                can add or delete entries to this table.

                Creating entries: Entries are created by the system
                each time a new PPP interface is created in the
                biboPPPTable.

                Deleting entries: Entries are removed by the system
                when the corresponding PPP interface is removed."
	::= { ppp 3 }

	biboPPPLinkEntry OBJECT-TYPE
	    SYNTAX  BiboPPPLinkEntry
	    ACCESS  not-accessible
	    STATUS  mandatory
	    DESCRIPTION
		""
	    INDEX   { biboPPPLinkIfIndex }
	::= { biboPPPLinkTable 1 }

	BiboPPPLinkEntry ::=
	    SEQUENCE {
		biboPPPLinkIfIndex			INTEGER,
		biboPPPLinkEstablished			Date,
		biboPPPLinkDirection			INTEGER,
		biboPPPLinkProtocols			INTEGER,
		biboPPPLinkState			INTEGER,
		biboPPPLinkUnits			Counter,
		biboPPPLinkRetries			Counter,
		biboPPPLinkKeepaliveSent		Counter,
		biboPPPLinkKeepalivePending		Counter,
		biboPPPLinkDeviceIndex			INTEGER,
		biboPPPLinkSpeed			INTEGER,
		biboPPPLinkStkNumber			INTEGER,
		biboPPPLinkCallType			INTEGER,
		biboPPPLinkCallReference		INTEGER,
		biboPPPLinkCharge			Counter,
		biboPPPLinkAccm				OCTET STRING (SIZE(4)),
		biboPPPLinkLqm				INTEGER,
		biboPPPLinkLcpComp			INTEGER,
		biboPPPLinkLocDiscr			OCTET STRING (SIZE(6)),
		biboPPPLinkRemDiscr			OCTET STRING (SIZE(20)),
		biboPPPLinkL1Protocol			INTEGER,
		biboPPPLinkLocAuth			INTEGER,
		biboPPPLinkRemAuth			INTEGER,
		biboPPPLinkNRxDesc			INTEGER,
		biboPPPLinkNTxDesc			INTEGER
	    }

	biboPPPLinkIfIndex OBJECT-TYPE
	    SYNTAX  INTEGER 
	    ACCESS  read-only
	    STATUS  mandatory

	    DESCRIPTION
		"Correlating PPP interface index."
	::= { biboPPPLinkEntry 1 }

	biboPPPLinkEstablished OBJECT-TYPE
	    SYNTAX  Date 
	    ACCESS  read-only
	    STATUS  mandatory

	    DESCRIPTION
		"Time when the link was established."
	::= { biboPPPLinkEntry 2 }

	biboPPPLinkDirection OBJECT-TYPE
	    SYNTAX  INTEGER { 
		incoming-dce(1), 
		outgoing-dte(2)
	    } 
	    ACCESS  read-only
	    STATUS  mandatory

	    DESCRIPTION
		"Direction of link, incoming(1) or outgoing(2). In case
		 of permanent links, the meaning is dce(1) or dte(2)."
	    DEFVAL { incoming-dce }
	::= { biboPPPLinkEntry 3 }

	biboPPPLinkProtocols OBJECT-TYPE
	    SYNTAX  INTEGER 
	    ACCESS  read-only
	    STATUS  mandatory

	    DESCRIPTION
		"The bitwise ORed protocols successfully negotiated on
		 this link; currently the following protocols are
		 supported: tcp/ip(1), ipx(2), bridge(4), bpdu(8), x25(16).
		 These protocol values are most likely to change in
		 future software releases."
	::= { biboPPPLinkEntry 4 }

	biboPPPLinkState OBJECT-TYPE
	    SYNTAX  INTEGER { 
		up(1), 
		down(2), 
		starting(3), 
		loopbacked(4),
		dialing(5),
		retry-wait(6)
	    } 
	    ACCESS  read-only
	    STATUS  mandatory

	    DESCRIPTION
		"The actual state of each link in a bundle. The link is
		fully operational in the up(1) state, and not operational
		in the down(2) state. The starting(3) state is an inter-
		mediate state when the link is physically established but
		PPP or other link negotation has not finished yet.
		The loopbacked(4) state is entered when the PPP keepalive
		mechanism detects a loopbacked link.
		The dialing(5) state shows that a dialup link is in its
		link establishment phase, dialing. If there is no answer
		to the call, the link enters the retry-wait(6) state for
		biboPPPRetryTime seconds.
		After waiting that time either a call retry will occur, or
		the ifOperStatus will enter the blocked state, depending
		on the amount of retries already done (biboPPPLinkRetries)
		and the value of the biboPPPMaxRetries field."
	    DEFVAL { down }
	::= { biboPPPLinkEntry 5 }

	biboPPPLinkUnits OBJECT-TYPE
	    SYNTAX  Counter 
	    ACCESS  read-only
	    STATUS  mandatory

	    DESCRIPTION
		"The costs for this link in units."
	::= { biboPPPLinkEntry 6 }

	biboPPPLinkRetries OBJECT-TYPE
	    SYNTAX  Counter 
	    ACCESS  read-only
	    STATUS  mandatory

	    DESCRIPTION
		"The amount of retries taken to establish the link."
	::= { biboPPPLinkEntry 7 }

	biboPPPLinkKeepaliveSent OBJECT-TYPE
	    SYNTAX  Counter 
	    ACCESS  read-only
	    STATUS  mandatory

	    DESCRIPTION
		"The amount of keepalive packets sent on the link."
	::= { biboPPPLinkEntry 8 }

	biboPPPLinkKeepalivePending OBJECT-TYPE
	    SYNTAX  Counter 
	    ACCESS  read-only
	    STATUS  mandatory

	    DESCRIPTION
		"The amount of keepalive answer packets waiting for
		 since the last occurance of an echo reply packet."
	::= { biboPPPLinkEntry 9 }

	biboPPPLinkDeviceIndex OBJECT-TYPE
	    SYNTAX  INTEGER
	    ACCESS  read-only
	    STATUS  mandatory

	    DESCRIPTION
		"The underlying link device index."
	::= { biboPPPLinkEntry 10 }

	biboPPPLinkSpeed OBJECT-TYPE
	    SYNTAX  INTEGER
	    ACCESS  read-only
	    STATUS  mandatory

	    DESCRIPTION
		"The speed of the link."
	::= { biboPPPLinkEntry 11 }

	biboPPPLinkStkNumber OBJECT-TYPE
	    SYNTAX  INTEGER (0..31)
	    ACCESS  read-only
	    STATUS  mandatory

	    DESCRIPTION
		"The stack number of the dialup link, correlating to
		 the isdnCallStkNumber field in the isdnCallTable."
	::= { biboPPPLinkEntry 13 }

	biboPPPLinkCallType OBJECT-TYPE
	    SYNTAX  INTEGER { 
		incoming(1), outgoing(2), undef(3)
	    } 
	    ACCESS  read-only
	    STATUS  mandatory

	    DESCRIPTION
		"The call type of the dialup link, correlating to
		 the isdnCallType field in the isdnCallTable."
	    DEFVAL { outgoing }
	::= { biboPPPLinkEntry 14 }

	biboPPPLinkCallReference OBJECT-TYPE
	    SYNTAX  INTEGER
	    ACCESS  read-only
	    STATUS  mandatory

	    DESCRIPTION
		"The call reference of the dialup link, correlating to
		 the isdnCallReference field in the isdnCallTable."
	::= { biboPPPLinkEntry 15 }

	biboPPPLinkCharge OBJECT-TYPE
	    SYNTAX  Counter 
	    ACCESS  read-only
	    STATUS  mandatory

	    DESCRIPTION
		"The costs for this link as 1/1000 of the respective currency."
	::= { biboPPPLinkEntry 16 }

	biboPPPLinkAccm OBJECT-TYPE
	    SYNTAX  OCTET STRING (SIZE(4))
	    ACCESS  read-only
	    STATUS  mandatory

	    DESCRIPTION
		"The Asynchronous Control Character Map (ACCM) according
		 RFC 1662."
	::= { biboPPPLinkEntry 17 }

	biboPPPLinkLqm OBJECT-TYPE
	    SYNTAX  INTEGER { 
		none(1), 
		negotiated(2) 
	    } 
	    ACCESS  read-only
	    STATUS  mandatory

	    DESCRIPTION
		"Indicates the successful negotiation of the Link Quality
                 Protocol (LQM)."
	::= { biboPPPLinkEntry 18 }

	biboPPPLinkLcpComp OBJECT-TYPE
	    SYNTAX  INTEGER { 
		none(1), 
		addr(2), 
		prot(3), 
		both(4) 
	    } 
	    ACCESS  read-only
	    STATUS  mandatory

	    DESCRIPTION
		"Address- and Protocol-Field compression."
	::= { biboPPPLinkEntry 19 }

	biboPPPLinkLocDiscr OBJECT-TYPE
	    SYNTAX  OCTET STRING (SIZE(6)) 
	    ACCESS  read-only
	    STATUS  mandatory

	    DESCRIPTION
		"Local LCP multilink endpoint discriminator."
	::= { biboPPPLinkEntry 20 }

	biboPPPLinkRemDiscr OBJECT-TYPE
	    SYNTAX  OCTET STRING (SIZE(20)) 
	    ACCESS  read-only
	    STATUS  mandatory

	    DESCRIPTION
		"Peer's LCP multilink endpoint discriminator."
	::= { biboPPPLinkEntry 21 }

	biboPPPLinkL1Protocol OBJECT-TYPE
	    SYNTAX INTEGER {
		data-64k(1),
		data-56k(2),
		modem(3),
		dovb(4),
		v110-1200(5),
		v110-2400(6),
		v110-4800(7),
		v110-9600(8),
		v110-14400(9),
		v110-19200(10),
		v110-38400(11),
                modem-profile-1(12),
                modem-profile-2(13),
                modem-profile-3(14),
                modem-profile-4(15),
                modem-profile-5(16),
                modem-profile-6(17),
                modem-profile-7(18),
                modem-profile-8(19),
                pptp-pns(20),
                pppoe(21),
                pppox25(22),
		pptp-pac(23),
		pppoa(24),
                l2tp-lns(25),
		l2tp-lac(26),
		dovb-64k(28)
	    }
	    ACCESS  read-only
	    STATUS  mandatory

	    DESCRIPTION
		"The layer 1 protocol of this link."
	::= { biboPPPLinkEntry 22 }

	biboPPPLinkLocAuth OBJECT-TYPE
	    SYNTAX  INTEGER { 
		none(1), 
		successful(2),
		failed(3),
		timeout(4),
		prot-rejected(5)
	    } 
	    ACCESS  read-only
	    STATUS  mandatory

	    DESCRIPTION
		"The result of the PPP authentication procedure performed
		 locally."
	::= { biboPPPLinkEntry 23 }

	biboPPPLinkRemAuth OBJECT-TYPE
	    SYNTAX  INTEGER { 
		none(1), 
		successful(2),
		failed(3),
		timeout(4),
		prot-rejected(5)
	    } 
	    ACCESS  read-only
	    STATUS  mandatory

	    DESCRIPTION
		"The result of the PPP authentication procedure performed
		 on remote."
	::= { biboPPPLinkEntry 24 }

	biboPPPLinkNRxDesc OBJECT-TYPE
	    SYNTAX  INTEGER (0..2048) 
	    ACCESS  read-only
	    STATUS  mandatory

	    DESCRIPTION
		"This variable contains the number of receive descriptors used
		 by the interface driver of the respective link."
	::= { biboPPPLinkEntry 25 }

	biboPPPLinkNTxDesc OBJECT-TYPE
	    SYNTAX  INTEGER (0..2048) 
	    ACCESS  read-only
	    STATUS  mandatory

	    DESCRIPTION
		"This variable contains the number of transmit descriptors used
		 by the interface driver of the respective link."
	::= { biboPPPLinkEntry 26 }



	pppLqmTable OBJECT-TYPE
	    SYNTAX  SEQUENCE OF PppLqmEntry
	    ACCESS  not-accessible
	    STATUS  mandatory
	    DESCRIPTION
		"The pppLqmTable contains statistical information
                for each current PPP link on the system. Only the system
                can add or delete entries to this table.

                Creating entries: Entries are created by the system
                each time a new PPP link was established and LQM negotiated
                successful.

                Deleting entries: Entries are removed by the system
                when the corresponding PPP link is disconnected."
	::= { ppp 6 }

	pppLqmEntry OBJECT-TYPE
	    SYNTAX  PppLqmEntry
	    ACCESS  not-accessible
	    STATUS  mandatory
	    DESCRIPTION
		""
	    INDEX   { pppLqmIfIndex }
	::= { pppLqmTable 1 }

	PppLqmEntry ::=
	    SEQUENCE {
		pppLqmIfIndex				INTEGER,
		pppLqmCallReference			INTEGER,
                pppLqmReportingPeriod                   INTEGER,
                pppLqmOutLQRs                           Counter,
                pppLqmOutPackets                        Counter,
                pppLqmOutOctets                         Counter,
                pppLqmInLQRs                            Counter,
                pppLqmInPackets                         Counter,
                pppLqmInOctets                          Counter,
                pppLqmInDiscards                        Counter,
                pppLqmInErrors                          Counter,
                pppLqmPeerOutLQRs                       Counter,
                pppLqmPeerOutPackets                    Counter,
                pppLqmPeerOutOctets                     Counter,
                pppLqmPeerInLQRs                        Counter,
                pppLqmPeerInPackets                     Counter,
                pppLqmPeerInOctets                      Counter,
                pppLqmPeerInDiscards                    Counter,
                pppLqmPeerInErrors                      Counter,
                pppLqmLostOutLQRs			Counter,
                pppLqmLostOutPackets			Counter,
                pppLqmLostOutOctets			Counter,
                pppLqmLostPeerOutLQRs			Counter,
                pppLqmLostPeerOutPkts			Counter,
                pppLqmLostPeerOutOcts			Counter
	    }

	pppLqmIfIndex OBJECT-TYPE
	    SYNTAX  INTEGER 
	    ACCESS  read-only
	    STATUS  mandatory

	    DESCRIPTION
		"Correlating PPP interface index."
	::= { pppLqmEntry 1 }

	pppLqmCallReference OBJECT-TYPE
	    SYNTAX  INTEGER
	    ACCESS  read-only
	    STATUS  mandatory

	    DESCRIPTION
		"The call reference of the dialup link, correlating to
		 the isdnCallReference field in the isdnCallTable."
	::= { pppLqmEntry 2 }


	pppLqmReportingPeriod OBJECT-TYPE
	    SYNTAX  INTEGER
	    ACCESS  read-only
	    STATUS  mandatory

	    DESCRIPTION
		"The LQMReportingPeriod field indicates the maximum time in
                 hundredths of seconds between transmission of Link Quality
                 Reports (LQR). The peer may transmit packets at a faster
                 rate than that which was negotiated."
	::= { pppLqmEntry 3 }

	pppLqmOutLQRs OBJECT-TYPE
	    SYNTAX  Counter 
	    ACCESS  read-only
	    STATUS  mandatory

	    DESCRIPTION
		"Number of transmitted Link Quality Reports (LQR) on this
                 link."
	::= { pppLqmEntry 4 }

	pppLqmOutPackets OBJECT-TYPE
	    SYNTAX  Counter 
	    ACCESS  read-only
	    STATUS  mandatory

	    DESCRIPTION
		"Number of transmitted Packets on this link."
	::= { pppLqmEntry 5 }

	pppLqmOutOctets OBJECT-TYPE
	    SYNTAX  Counter 
	    ACCESS  read-only
	    STATUS  mandatory

	    DESCRIPTION
		"Number of transmitted Octets on this link, including framing
                 data."
	::= { pppLqmEntry 6 }

	pppLqmInLQRs OBJECT-TYPE
	    SYNTAX  Counter 
	    ACCESS  read-only
	    STATUS  mandatory

	    DESCRIPTION
		"Number of Link Quality Reports (LQR) received on this link."
	::= { pppLqmEntry 7 }

	pppLqmInPackets OBJECT-TYPE
	    SYNTAX  Counter 
	    ACCESS  read-only
	    STATUS  mandatory

	    DESCRIPTION
		"Number of Packets reveived on this link."
	::= { pppLqmEntry 8 }

	pppLqmInOctets OBJECT-TYPE
	    SYNTAX  Counter 
	    ACCESS  read-only
	    STATUS  mandatory

	    DESCRIPTION
		"Number of Octets reveived on this link, including framing
                 data."
	::= { pppLqmEntry 9 }

	pppLqmInDiscards OBJECT-TYPE
	    SYNTAX  Counter 
	    ACCESS  read-only
	    STATUS  mandatory

	    DESCRIPTION
		"Number of Packets received on this link, but discarded."
	::= { pppLqmEntry 10 }

	pppLqmInErrors OBJECT-TYPE
	    SYNTAX  Counter 
	    ACCESS  read-only
	    STATUS  mandatory

	    DESCRIPTION
		"Number of errorneous Packets received on this link."
	::= { pppLqmEntry 11 }

	pppLqmPeerOutLQRs OBJECT-TYPE
	    SYNTAX  Counter 
	    ACCESS  read-only
	    STATUS  mandatory

	    DESCRIPTION
		"Number of Link Quality Reports (LQR) transmitted by remote
                 on this link."
	::= { pppLqmEntry 12 }

	pppLqmPeerOutPackets OBJECT-TYPE
	    SYNTAX  Counter 
	    ACCESS  read-only
	    STATUS  mandatory

	    DESCRIPTION
		"Number of Packets transmitted by remote on this link."
	::= { pppLqmEntry 13 }

	pppLqmPeerOutOctets OBJECT-TYPE
	    SYNTAX  Counter 
	    ACCESS  read-only
	    STATUS  mandatory

	    DESCRIPTION
		"Number of Octets transmitted by remote on this link,
                 including framing data."
	::= { pppLqmEntry 14 }

	pppLqmPeerInLQRs OBJECT-TYPE
	    SYNTAX  Counter 
	    ACCESS  read-only
	    STATUS  mandatory

	    DESCRIPTION
		"Number of Link Quality Reports (LQR) received by remote
                 on this link."
	::= { pppLqmEntry 15 }

	pppLqmPeerInPackets OBJECT-TYPE
	    SYNTAX  Counter 
	    ACCESS  read-only
	    STATUS  mandatory

	    DESCRIPTION
		"Number of Packets reveived by remote on this link."
	::= { pppLqmEntry 16 }

	pppLqmPeerInOctets OBJECT-TYPE
	    SYNTAX  Counter 
	    ACCESS  read-only
	    STATUS  mandatory

	    DESCRIPTION
		"Number of Octets reveived by remote on this link, including
                 framing data."
	::= { pppLqmEntry 17 }

	pppLqmPeerInDiscards OBJECT-TYPE
	    SYNTAX  Counter 
	    ACCESS  read-only
	    STATUS  mandatory

	    DESCRIPTION
		"Number of Packets received by remote on this link, but
                 discarded."
	::= { pppLqmEntry 18 }

	pppLqmPeerInErrors OBJECT-TYPE
	    SYNTAX  Counter 
	    ACCESS  read-only
	    STATUS  mandatory

	    DESCRIPTION
		"Number of errorneous Packets received by remote on this
                 link."
	::= { pppLqmEntry 19 }

	pppLqmLostOutLQRs OBJECT-TYPE
	    SYNTAX  Counter 
	    ACCESS  read-only
	    STATUS  mandatory

	    DESCRIPTION
		"Number of lost Link Quality Reports (LQR) transmitted on
                 this link."
	::= { pppLqmEntry 20 }

	pppLqmLostOutPackets OBJECT-TYPE
	    SYNTAX  Counter 
	    ACCESS  read-only
	    STATUS  mandatory

	    DESCRIPTION
		"Number of lost Packets transmitted on this link."
	::= { pppLqmEntry 21 }

	pppLqmLostOutOctets OBJECT-TYPE
	    SYNTAX  Counter 
	    ACCESS  read-only
	    STATUS  mandatory

	    DESCRIPTION
		"Number of lost Octets transmitted on this link."
	::= { pppLqmEntry 22 }

	pppLqmLostPeerOutLQRs OBJECT-TYPE
	    SYNTAX  Counter 
	    ACCESS  read-only
	    STATUS  mandatory

	    DESCRIPTION
		"Number of lost Link Quality Reports (LQR) transmitted by
                 remote on this link."
	::= { pppLqmEntry 23 }

	pppLqmLostPeerOutPkts OBJECT-TYPE
	    SYNTAX  Counter 
	    ACCESS  read-only
	    STATUS  mandatory

	    DESCRIPTION
		"Number of lost Packets transmitted by remote on this
                 link."
	::= { pppLqmEntry 24 }

	pppLqmLostPeerOutOcts OBJECT-TYPE
	    SYNTAX  Counter 
	    ACCESS  read-only
	    STATUS  mandatory

	    DESCRIPTION
		"Number of lost Octets transmitted by remote on this link."
	::= { pppLqmEntry 25 }


	pppLinkHistoryTable OBJECT-TYPE
	    SYNTAX  SEQUENCE OF PPPLinkHistoryEntry
	    ACCESS  not-accessible
	    STATUS  mandatory
	    DESCRIPTION
		"The pppLinkHistoryTable contains statistical information
                for each closed PPP link on the system. Only the system
                can add or delete entries to this table.

                Creating entries: Entries are created by the system
                each time a PPP link is closed.

                Deleting entries: Entries are removed by the system
                either the maximum number of entries is reached or
		when the corresponding PPP interface is removed."
	::= { ppp 13 }

	pppLinkHistoryEntry OBJECT-TYPE
	    SYNTAX  PPPLinkHistoryEntry
	    ACCESS  not-accessible
	    STATUS  mandatory
	    DESCRIPTION
		""
	    INDEX   { pppLinkHistIfIndex, pppLinkHistId }
	::= { pppLinkHistoryTable 1 }

	PPPLinkHistoryEntry ::=
	    SEQUENCE {
		pppLinkHistIfIndex			INTEGER,
		pppLinkHistId				INTEGER,
		pppLinkHistCreated			Date,
		pppLinkHistDirection			INTEGER,
--		pppLinkHistLcpEchoReqSent		Counter,
--		pppLinkHistLcpEchoRepSent		Counter,
--		pppLinkHistLcpEchoReqRcvd		Counter,
--		pppLinkHistLcpEchoRepRcvd		Counter,
		pppLinkHistAccm				OCTET STRING (SIZE(4)),
		pppLinkHistLqm				INTEGER,
		pppLinkHistLcpComp			INTEGER,
		pppLinkHistLocDiscr			OCTET STRING (SIZE(6)),
		pppLinkHistRemDiscr			OCTET STRING (SIZE(20)),
		pppLinkHistLocAuth			INTEGER,
		pppLinkHistRemAuth			INTEGER,
--		pppLinkHistDiscCause			INTEGER,
		pppLinkHistL1Protocol			INTEGER
	    }

	pppLinkHistIfIndex OBJECT-TYPE
	    SYNTAX  INTEGER 
	    ACCESS  read-only
	    STATUS  mandatory

	    DESCRIPTION
		"Correlating PPP interface index."
	::= { pppLinkHistoryEntry 1 }

	pppLinkHistId OBJECT-TYPE
	    SYNTAX  INTEGER 
	    ACCESS  read-only
	    STATUS  mandatory

	    DESCRIPTION
		"Unique ID for this entry."
	::= { pppLinkHistoryEntry 2 }

	pppLinkHistCreated OBJECT-TYPE
	    SYNTAX  Date 
	    ACCESS  read-only
	    STATUS  mandatory

	    DESCRIPTION
		"Time when this entry was created."
	::= { pppLinkHistoryEntry 3 }

	pppLinkHistDirection OBJECT-TYPE
	    SYNTAX  INTEGER { 
		incoming-dce(1), 
		outgoing-dte(2)
	    } 
	    ACCESS  read-only
	    STATUS  mandatory

	    DESCRIPTION
		"Direction of link, incoming(1) or outgoing(2). In case
		 of permanent links, the meaning is dce(1) or dte(2)."
	    DEFVAL { incoming-dce }
	::= { pppLinkHistoryEntry 4 }

--	pppLinkHistLcpEchoReqSent OBJECT-TYPE
--	    SYNTAX  Counter 
--	    ACCESS  read-only
--	    STATUS  mandatory
--	    DESCRIPTION
--		"The number of LCP Echo Request packets sent on the link."
--	::= { pppLinkHistoryEntry 5 }
--
--	pppLinkHistLcpEchoRepSent OBJECT-TYPE
--	    SYNTAX  Counter 
--	    ACCESS  read-only
--	    STATUS  mandatory
--
--	    DESCRIPTION
--		"The number of LCP Echo Reply packets sent on the link."
--	::= { pppLinkHistoryEntry 6 }
--
--	pppLinkHistLcpEchoReqRcvd OBJECT-TYPE
--	    SYNTAX  Counter 
--	    ACCESS  read-only
--	    STATUS  mandatory
--
--	    DESCRIPTION
--		"The number of LCP Echo Request packets received on the link."
--	::= { pppLinkHistoryEntry 7 }
--
--	pppLinkHistLcpEchoRepRcvd OBJECT-TYPE
--	    SYNTAX  Counter 
--	    ACCESS  read-only
--	    STATUS  mandatory
--
--	    DESCRIPTION
--		"The number of LCP Echo Reply packets received on the link."
--	::= { pppLinkHistoryEntry 8 }
--
	pppLinkHistAccm OBJECT-TYPE
	    SYNTAX  OCTET STRING (SIZE(4))
	    ACCESS  read-only
	    STATUS  mandatory

	    DESCRIPTION
		"The Asynchronous Control Character Map (ACCM) according
		 RFC 1662."
	::= { pppLinkHistoryEntry 9 }

	pppLinkHistLqm OBJECT-TYPE
	    SYNTAX  INTEGER { 
		none(1), 
		negotiated(2) 
	    } 
	    ACCESS  read-only
	    STATUS  mandatory

	    DESCRIPTION
		"Indicates the successful negotiation of the Link Quality
                 Protocol (LQM)."
	::= { pppLinkHistoryEntry 10 }

	pppLinkHistLcpComp OBJECT-TYPE
	    SYNTAX  INTEGER { 
		none(1), 
		addr(2), 
		prot(3), 
		both(4) 
	    } 
	    ACCESS  read-only
	    STATUS  mandatory

	    DESCRIPTION
		"Address- and Protocol-Field compression."
	::= { pppLinkHistoryEntry 11 }
	
	pppLinkHistLocDiscr OBJECT-TYPE
	    SYNTAX  OCTET STRING (SIZE(6)) 
	    ACCESS  read-only
	    STATUS  mandatory

	    DESCRIPTION
		"Local LCP multilink endpoint discriminator."
	::= { pppLinkHistoryEntry 12 }

	pppLinkHistRemDiscr OBJECT-TYPE
	    SYNTAX  OCTET STRING (SIZE(20)) 
	    ACCESS  read-only
	    STATUS  mandatory

	    DESCRIPTION
		"Peer's LCP multilink endpoint discriminator."
	::= { pppLinkHistoryEntry 13 }

	pppLinkHistLocAuth OBJECT-TYPE
	    SYNTAX  INTEGER { 
		none(1), 
		successful(2),
		failed(3),
		timeout(4),
		prot-rejected(5)
	    } 
	    ACCESS  read-only
	    STATUS  mandatory

	    DESCRIPTION
		"The result of the PPP authentication procedure performed
		 locally."
	::= { pppLinkHistoryEntry 14 }

	pppLinkHistRemAuth OBJECT-TYPE
	    SYNTAX  INTEGER { 
		none(1), 
		successful(2),
		failed(3),
		timeout(4),
		prot-rejected(5)
	    } 
	    ACCESS  read-only
	    STATUS  mandatory

	    DESCRIPTION
		"The result of the PPP authentication procedure performed
		 on remote."
	::= { pppLinkHistoryEntry 15 }

--	pppLinkHistDiscCause OBJECT-TYPE
--	    SYNTAX  INTEGER { 
--		unknown(1), 
--		local(2),
--		remote(3),
--		layer1(4)
--	    } 
--	    ACCESS  read-only
--	    STATUS  mandatory
--
--	    DESCRIPTION
--		"The detected cause of the disconnect."
--	::= { pppLinkHistoryEntry 16 }
--
	pppLinkHistL1Protocol OBJECT-TYPE
	    SYNTAX INTEGER {
		data-64k(1),
		data-56k(2),
		modem(3),
		dovb(4),
                v110-1200(5),
                v110-2400(6),
                v110-4800(7),
                v110-9600(8),
                v110-14400(9),
                v110-19200(10),
                v110-38400(11), 
                modem-profile-1(12),
                modem-profile-2(13),
                modem-profile-3(14),
                modem-profile-4(15),
                modem-profile-5(16),
                modem-profile-6(17),
                modem-profile-7(18),
                modem-profile-8(19),
                pptp-pns(20),
                pppoe(21),
                pppx25(22),
                pptp-pac(23),
                l2tp-lns(24),
                l2tp-lac(25),
                dovb-64k(26),
		all(31)
	    }
	    ACCESS  read-only
	    STATUS  mandatory

	    DESCRIPTION
		"The layer 1 protocol of this link."
	::= { pppLinkHistoryEntry 17 }


        pppLinkHistoryMaxEntries OBJECT-TYPE
            SYNTAX  INTEGER (0..255)
            ACCESS  read-write
            STATUS  mandatory
 
            DESCRIPTION
                "Maximum number of pppLinkHistory entries in memory."
            DEFVAL { 20 }
        ::= { ppp 14 }


    -- Old IP Address pool for dynamic assignment

    biboPPPIpAssignTable OBJECT-TYPE
        SYNTAX  SEQUENCE OF BiboPPPIpAssignEntry
        ACCESS  not-accessible
        STATUS  mandatory
        DESCRIPTION
        "The biboPPPIpAssignTable contains IP addresses used
                when dynamically assigning IP addresses; i.e. when the
                biboPPPIpAddress field is set to `dynamic'.

                Creating entries: Entries are created by assigning a
                value (IP address) to the biboPPPIpAssignAddress object.

                Deleting entries: An entry (address) can be removed
                by assigning the value `delete' to its biboPPPIpAssignState."
    ::= { ppp 4 }

    biboPPPIpAssignEntry OBJECT-TYPE
        SYNTAX  BiboPPPIpAssignEntry
        ACCESS  not-accessible
        STATUS  mandatory
        DESCRIPTION
        "Pool of IP addresses for dynamic IP address assignment via IPCP.
        See the biboPPPIpAddress field for further explanation."
        INDEX   { biboPPPIpAssignAddress }
    ::= { biboPPPIpAssignTable 1 }

    BiboPPPIpAssignEntry ::=
        SEQUENCE {
        biboPPPIpAssignAddress      IpAddress,
        biboPPPIpAssignState        INTEGER,
        biboPPPIpAssignPoolId       INTEGER,
        biboPPPIpAssignRange        INTEGER,
        biboPPPIpAssignDescription  DisplayString
        }

    biboPPPIpAssignAddress OBJECT-TYPE
        SYNTAX  IpAddress 
        ACCESS  read-write
        STATUS  mandatory

        DESCRIPTION
        "First IP address of this range."
    ::= { biboPPPIpAssignEntry 1 }

    biboPPPIpAssignState OBJECT-TYPE
        SYNTAX  INTEGER {
        unused(1), 
        assigned(2), 
        delete(3)
        }
        ACCESS  read-write
        STATUS  mandatory

        DESCRIPTION
        "If an entry is currently in use, the state is set to as-
                signed(1). Otherwise it is set to unused(2). You may also
                delete this entry by changing it to delete(3)."
        DEFVAL { unused }
    ::= { biboPPPIpAssignEntry 2 }

    biboPPPIpAssignPoolId OBJECT-TYPE
        SYNTAX  INTEGER 
        ACCESS  read-write
        STATUS  mandatory

        DESCRIPTION
        "Pool ID value."
        DEFVAL { 0 }
    ::= { biboPPPIpAssignEntry 3 }

    biboPPPIpAssignRange OBJECT-TYPE
        SYNTAX  INTEGER 
        ACCESS  read-write
        STATUS  mandatory

        DESCRIPTION
        "Number of IP addresses that will be assigned starting
         from biboPPPIpAssignAddress. A range of 0 will disable
         this entry"
        DEFVAL { 0 }
    ::= { biboPPPIpAssignEntry 4 }

    biboPPPIpAssignDescription OBJECT-TYPE
        SYNTAX  DisplayString (SIZE (0..255))
        ACCESS  read-write
        STATUS  mandatory

        DESCRIPTION
        "Optional IP pool description."
    ::= { biboPPPIpAssignEntry 5 }


    -- IP Address pool for dynamic assignment

	biboPPPIpPoolTable OBJECT-TYPE
	    SYNTAX  SEQUENCE OF BiboPPPIpPoolEntry
	    ACCESS  not-accessible
	    STATUS  mandatory
	    DESCRIPTION
		"The biboPPPIpPoolTable contains IP addresses used
                when dynamically assigning IP addresses; i.e. when the
                biboPPPIpAddress field is set to `dynamic'.

                Creating entries: Entries are created by assigning a
                value (IP address) to the biboPPPIpPoolAddress object.

                Deleting entries: An entry (address) can be removed
                by assigning the value `delete' to its biboPPPIpPoolState."
	::= { ppp 17 }

	biboPPPIpPoolEntry OBJECT-TYPE
	    SYNTAX  BiboPPPIpPoolEntry
	    ACCESS  not-accessible
	    STATUS  mandatory
	    DESCRIPTION
		"Pool of IP addresses for dynamic IP address assignment via IPCP.
		See the biboPPPIpAddress field for further explanation."
	    INDEX   { biboPPPIpPoolIdentifier }
	::= { biboPPPIpPoolTable 1 }

	BiboPPPIpPoolEntry ::=
	    SEQUENCE {
		biboPPPIpPoolIdentifier      	INTEGER,
		biboPPPIpPoolAdminStatus	    INTEGER,
		biboPPPIpPoolMode		        INTEGER
	    }

	biboPPPIpPoolIdentifier OBJECT-TYPE
	    SYNTAX  INTEGER 
	    ACCESS  read-write
	    STATUS  mandatory

	    DESCRIPTION
		"The ID of the responding dynamic pool."
	::= { biboPPPIpPoolEntry 1 }

	biboPPPIpPoolAdminStatus OBJECT-TYPE
	    SYNTAX  INTEGER {
		enabled(1), 
		disabled(2), 
		delete(3)
	    }
	    ACCESS  read-write
	    STATUS  mandatory

	    DESCRIPTION
		"If the AdminStatus is set to enabled(1) this entry will be used.
         Setting it to disabled(2) this entry won't be used . You may also
         delete this entry by changing it to delete(3)."
	    DEFVAL { enabled }
	::= { biboPPPIpPoolEntry 2 }

	biboPPPIpPoolMode OBJECT-TYPE
	    SYNTAX  INTEGER {
		recover(1), 
		random(2)
	    }
	    ACCESS  read-write
	    STATUS  mandatory

	    DESCRIPTION
		"The IpPoolMode tries to reassign the IP Address a client had before
         if it is in recover(1) Mode. Otherwise (2) an unassigned IP Address
         of the PPP dynamic IP Pool is assigned to the client no matter which
         Address he had before.  
        "
	    DEFVAL { recover }
	::= { biboPPPIpPoolEntry 3 }


    -- PPP dialin profile (defaults)

	biboPPPProfileTable OBJECT-TYPE
	    SYNTAX  SEQUENCE OF BiboPPPProfileEntry
	    ACCESS  not-accessible
	    STATUS  mandatory
	    DESCRIPTION
		"The biboPPPProfileTable contains PPP default parameters
                 used for PPP negotiation with unknown dialin partners.
                 For PPP connections, PPP profiles are asigned to incoming
                 connections via the isdnDispatchTable.
                 Currently no entries can be created or deleted by user."
		::= { ppp 5 }

	biboPPPProfileEntry OBJECT-TYPE
	    SYNTAX  BiboPPPProfileEntry
	    ACCESS  not-accessible
	    STATUS  mandatory
	    DESCRIPTION
		""
	    INDEX   { biboPPPProfileName }
	::= { biboPPPProfileTable 1 }

	BiboPPPProfileEntry ::=
	    SEQUENCE {
		biboPPPProfileName			INTEGER,
		biboPPPProfileAuthProtocol		INTEGER,
		biboPPPProfileAuthRadius		INTEGER,
                biboPPPProfileLQMonitoring       	INTEGER,
		biboPPPProfilePPPoEDevIfIndex           INTEGER,
 --		biboPPPProfileLayer1Protocol		INTEGER,
		biboPPPProfileCallbackNegotiation       INTEGER
	    }

	biboPPPProfileName OBJECT-TYPE
	    SYNTAX  INTEGER {
		profile-1(1), profile-2(2), profile-3(3)
	    } 
	    ACCESS  read-only
	    STATUS  mandatory

	    DESCRIPTION
		"The name of the PPP profile. Three profiles are available."
	    DEFVAL { profile-1 }
	::= { biboPPPProfileEntry 1 }

	biboPPPProfileAuthProtocol OBJECT-TYPE
	    SYNTAX  INTEGER { 
		none(1), 
		pap(2), 
		chap(3), 
		both(4),
--		radius(5),
                ms-chap(6),
                all(7),
                ms-chapv2(8)
	    } 
	    ACCESS  read-write
	    STATUS  mandatory

	    DESCRIPTION
		"The type of authentication used on the point-to-point
                link as described in RFC 1334. See biboPPPAuthentication
                for further details."
	    DEFVAL { all }
	::= { biboPPPProfileEntry 2 }

	biboPPPProfileAuthRadius OBJECT-TYPE
	    SYNTAX  INTEGER { 
		none(1), 
		inband(2), 
		outband(3), 
		both(4),
		radius-only(5)
	    } 
	    ACCESS  read-write
	    STATUS  mandatory

	    DESCRIPTION
		"This entry is used to configure possible RADIUS
		 authentication on incoming calls. The default value is
                 inband(2), only inband RADIUS requests (PAP, CHAP) are sent
                 to the defined RADIUS server.
		 Outband requests (CALLERID) are sent in outband(3) mode.
		 If set to both(3), both requests are sent. To disable
                 RADIUS requests in the profile set this value to none(1).
		 To disable authentication attempts via the local data base
		 set this value to radius-only(5)."
	    DEFVAL { inband }
	::= { biboPPPProfileEntry 3 }

	biboPPPProfileLQMonitoring OBJECT-TYPE
	    SYNTAX  INTEGER { 
                off(1), 
                on(2)
	    } 
	    ACCESS  read-write
	    STATUS  mandatory

	    DESCRIPTION
                 "This parameter enables (2) or disables (1) PPP Link Quality
                  Monitoring (LQM) according RFC 1989. When set to on(2) LQM
                  is added to the list of parameters acknowledged in LCP
                  negotiation. Link quality reports (LQR) will be generated
                  and send periodically."
	    DEFVAL { off }
	::= { biboPPPProfileEntry 4 }

	biboPPPProfilePPPoEDevIfIndex OBJECT-TYPE
	    SYNTAX  INTEGER 
	    ACCESS  read-write
	    STATUS  mandatory

	    DESCRIPTION
		"Specifies the device to be used for PPP over Ethernet (PPPoE)
                 according RFC 2516."
	::= { biboPPPProfileEntry 5 }

--	biboPPPProfileLayer1Protocol OBJECT-TYPE
--	    SYNTAX  INTEGER { 
--	    } 
--	    ACCESS  read-write
--	    STATUS  mandatory
--
--	    DESCRIPTION
--		"."
--	::= { biboPPPProfileEntry 6 }

	biboPPPProfileCallbackNegotiation OBJECT-TYPE
	    SYNTAX  INTEGER { 
                disabled(1), 
                enabled(2), 
                cbcp-optional(3)
	    } 
	    ACCESS  read-write
	    STATUS  mandatory

	    DESCRIPTION
		"Specifies wether callback negotiation (LCP/CBCP) is
		 allowed or not. If set to disabled(1), no callback
		 negotiation will be performed or accepted. If set
		 to enabled(2), PPP callback negotation will be accepted
		 on demand.
		 If this object is set to cbcp-optional(3), the CBCP
                 option 'no callback' is also offered to the Windows client
                 so that the user can decide wether he wants to be called
		 back or not."
	    DEFVAL { enabled }
	::= { biboPPPProfileEntry 7 }

    -- extended PPP configuration

	pppExtIfTable OBJECT-TYPE
	    SYNTAX  SEQUENCE OF PppExtIfEntry
	    ACCESS  not-accessible
	    STATUS  mandatory
	    DESCRIPTION
		"The pppExtIfTable contains extended configuration and
		 information related to the PPP interfaces on the system.

                 Entries are created and deleted due to the existence of
		 associated biboPPPTable entries."
	::= { ppp 9 }

	pppExtIfEntry OBJECT-TYPE
	    SYNTAX  PppExtIfEntry
	    ACCESS  not-accessible
	    STATUS  mandatory
	    DESCRIPTION
		""
	    INDEX   { pppExtIfIndex }
	::= { pppExtIfTable 1 }

	PppExtIfEntry ::=
	    SEQUENCE {
		pppExtIfIndex			INTEGER,
		pppExtIfBodMode			INTEGER,
		pppExtIfAlgorithm		INTEGER,
		pppExtIfInterval		INTEGER,
		pppExtIfLoad			INTEGER,
		pppExtIfMlpFragmentation	INTEGER,
		pppExtIfMlpFragSize		INTEGER,
		pppExtIfPPPoEService		DisplayString,
		pppExtIfPPPoEAcServer		DisplayString,
		pppExtIfEncKeyNegotiation	INTEGER,
		pppExtIfEncTxKey		OCTET STRING,
		pppExtIfEncRxKey		OCTET STRING,
		pppExtIfGearUpThreshold		INTEGER,
		pppExtIfGearDownThreshold	INTEGER,
		pppExtIfAodiDChanQlen		INTEGER,
		pppExtIfAodiGearDownTxRate	INTEGER,
		pppExtIfGearUpPersistance	INTEGER,
		pppExtIfGearDownPersistance	INTEGER,
		pppExtIfL1Speed			INTEGER,
		pppExtIfCurrentRetryTime	INTEGER,
		pppExtIfMaxRetryTime		INTEGER,
		pppExtIfMtu			INTEGER,
		pppExtIfMru			INTEGER,
		pppExtIfAuthMutual		INTEGER,
--		pppExtIfAuthRestart		INTEGER,
		pppExtIfDialProfileIndex	INTEGER,
		pppExtIfDialinL1Protocol	INTEGER,
		pppExtIfpppoeEthIfIndex		INTEGER,
		pppExtIfpppoaPvcIfIndex		INTEGER,
		pppExtIfRadiusMarkAcct		INTEGER,
		pppExtIfRadiusGroupId		INTEGER,
		pppExtIfpppoeFallbackVlanId	INTEGER
	    }

	pppExtIfIndex OBJECT-TYPE
	    SYNTAX  INTEGER 
	    ACCESS  read-only
	    STATUS  mandatory

	    DESCRIPTION
		"Correlating PPP interface index."
	::= { pppExtIfEntry 1 }

	pppExtIfBodMode OBJECT-TYPE
	    SYNTAX  INTEGER { 
                disabled(1),
		backup(2), 
		bod-active(3),
		bod-passive(4),
		bap-active(5),
		bap-passive(6),
--		delete(7),
		bap-both(8),
		bap-first(9),
		bap-client(10),
		bap-server(11),
                bod-reduce-incoming(12)
	    } 
	    ACCESS  read-write
	    STATUS  mandatory

	    DESCRIPTION
		"Enables bandwidth on demand (BOD) mode for leased line and
		 dialup interfaces when setting to bod-active (3) respectively
                 bod-passive (4) or backup only mode for leased line
		 connections like X.21. bod-reduce-incoming (12) reduces the number
                 of links on incoming connections if needed/wanted.
                 When set to disabled (1), neither bandwidth
                 on demand (as specified by the pppExtIfTable) or
		 backup mode is enabled. Four modes (bap-active (5),
		 bap-passive (6), bap-both(7) and bap-first (8)) are available
 		 for BAP (Bandwidth Allocation Protocol) support to specify
		 wether BAP Call-Requests and BAP Callback-Requests should be
		 initiated and/or accepted."
	    DEFVAL { disabled }
	::= { pppExtIfEntry 2 }

	pppExtIfAlgorithm OBJECT-TYPE
	    SYNTAX  INTEGER { 
		equal(1), 
		proportional(2)
	    } 
	    ACCESS  read-write
	    STATUS  mandatory

	    DESCRIPTION
		"The algorithm to use for weighting line utilization.
		 Line utilization is determined by calculating the average
		 load for each interface. When set to equal (1) all samples
		 taken over the time interval (defined in pppExtIfInterval)
		 will be given equal weight, when set to proportional (2)
		 the weighting disproportional to the age of the sample."
	    DEFVAL { equal }
	::= { pppExtIfEntry 3 }

	pppExtIfInterval OBJECT-TYPE
	    SYNTAX  INTEGER (5..300)
	    ACCESS  read-write
	    STATUS  mandatory

	    DESCRIPTION
		"The time interval (in seconds) to use for sampling and
		 calculating of the average throughput of the interface.
		 See also: pppExtIfLoad."
	    DEFVAL { 5 }
	::= { pppExtIfEntry 4 }

	pppExtIfLoad OBJECT-TYPE
	    SYNTAX  INTEGER (0..100)
	    ACCESS  read-only
	    STATUS  mandatory

	    DESCRIPTION
		"The actual throughput (in percent) of the total bandwidth
                 of this interface (load). This value is updated once every
                 second and based on the amount of traffic during the last
		 sampling interval. Note that only the actual maximum of the
		 both directions (send / receive) is considered."
	    DEFVAL { 0 }
	::= { pppExtIfEntry 5 }

	pppExtIfMlpFragmentation OBJECT-TYPE
	    SYNTAX  INTEGER {
		proportional(1), 
		equal(2),
		interleave(3)
	    } 
	    ACCESS  read-write
	    STATUS  mandatory

	    DESCRIPTION
		"The multilink PPP fragmentation mode. When set to
                 proportional (1) packets will be divided into fragments
		 proportional to the transmission rate of each link,
		 when set to equal (2) packets will be divided into multiple
		 equal fragments (equal to MlpFragSize) such that the number
		 sent on each link is proportional to the transmission rate.
		 When set to interleave (3), large datagrams will be
		 fragmentated (maximum size determined by MlpFragSize) to
		 reduce transmission delay of high-priority traffic on
		 slower links."
	    DEFVAL { proportional }
	::= { pppExtIfEntry 6 }

	pppExtIfMlpFragSize OBJECT-TYPE
	    SYNTAX  INTEGER (30..1500)
	    ACCESS  read-write
	    STATUS  mandatory

	    DESCRIPTION
		"The multilink PPP fragment size. If MlpFragmentation is set
		 to proportional (1) this value specifies the minimum size
		 of the fragment in bytes. If MlpFragmentation is set to
		 equal (2) this value specifies the maximum fragment size
		 in bytes."
	    DEFVAL { 100 }
	::= { pppExtIfEntry 7 }

	pppExtIfPPPoEService OBJECT-TYPE
	    SYNTAX  DisplayString (SIZE (0..63))
	    ACCESS  read-write
	    STATUS  mandatory

	    DESCRIPTION
		"The PPPoE (PPP over Ethernet, RFC 2516) service name which
                 indicates the requested service during PPPoE discovery stage.
                 Examples of the use of the service name are to indicate an
                 ISP name or a class or a quality of service."
	::= { pppExtIfEntry 8 }

	pppExtIfPPPoEAcServer OBJECT-TYPE
	    SYNTAX  DisplayString (SIZE (0..63))
	    ACCESS  read-write
	    STATUS  mandatory

	    DESCRIPTION
		"The PPPoE (PPP over Ethernet, RFC 2516) AC-Server name which
                 determines the access concentrator during PPPoE discovery
		 stage."
	::= { pppExtIfEntry 9 }

	pppExtIfEncKeyNegotiation OBJECT-TYPE
	    SYNTAX  INTEGER {
		static(1), 
		authentication(2)
	    } 
	    ACCESS  read-write
	    STATUS  mandatory

	    DESCRIPTION
		"This variable defines the specification of shared secrets
		 (encryption keys) between the sender and receiver of
		 encrypted data. If set to static (1), the keys specified in
		 'pppExtIfEncTxKey' and 'pppExtIfEncRxKey' will be used, if
		 set to authentication (2), the key derivation is based on
		 PPP authentication via CHAP or MS-CHAP."
	    DEFVAL { authentication }
	::= { pppExtIfEntry 10 }

	pppExtIfEncTxKey OBJECT-TYPE
	    SYNTAX  OCTET STRING
	    ACCESS  read-write
	    STATUS  mandatory

	    DESCRIPTION
		"Static (encryption) key used for transmission of encrypted
		 data via PPP. It's size depends on the used encryption 
		 algorithm and the corresponding key length, e.g. 'des_56'
		 or 'blowfish_168'."
	::= { pppExtIfEntry 11 }

	pppExtIfEncRxKey OBJECT-TYPE
	    SYNTAX  OCTET STRING
	    ACCESS  read-write
	    STATUS  mandatory

	    DESCRIPTION
		"Static (decryption) key used for decryption of encrypted
		 data received on PPP connections. It's size depends on the
		 used encryption algorithm and the corresponding key length,
		 e.g. 'des_56' or 'blowfish_168'."
	::= { pppExtIfEntry 12 }

	pppExtIfGearUpThreshold OBJECT-TYPE
	    SYNTAX  INTEGER (0..100)
	    ACCESS  read-write
	    STATUS  mandatory

	    DESCRIPTION
		"Gear up threshold for invoking current bandwidth. The
		 measured throughput (in percent of the total bandwidth) of
		 this interface (see pppExtIfLoad) is compared with this value
		 once per second. If exceeded longer than 5 seconds an
		 additional B-channel will be requested."
	    DEFVAL { 90 }
	::= { pppExtIfEntry 13 }

	pppExtIfGearDownThreshold OBJECT-TYPE
	    SYNTAX  INTEGER (0..100)
	    ACCESS  read-write
	    STATUS  mandatory

	    DESCRIPTION
		"Gear down threshold for decreasing current bandwidth. The
		 expected throughput (in percent of the total bandwidth) of
		 this interface (see pppExtIfLoad) after dropping a B-channel
		 is compared with this threshold value once per second. If the
		 needed bandwidth falls below this threshold longer than 10
		 seconds, exactly one B-channel will be dropped."
	    DEFVAL { 80 }
	::= { pppExtIfEntry 14 }

	pppExtIfAodiDChanQlen OBJECT-TYPE
	    SYNTAX  INTEGER
	    ACCESS  read-write
	    STATUS  mandatory

	    DESCRIPTION
		"Upper threshold for the amount of data (in octets) waiting
		 to be sent across the 9.6Kbit/sec D-channel. If exceeded,
		 additional bandwidth will be invoked at once."
	    DEFVAL { 7500 }
	::= { pppExtIfEntry 15 }

	pppExtIfAodiGearDownTxRate OBJECT-TYPE
	    SYNTAX  INTEGER
	    ACCESS  read-write
	    STATUS  mandatory

	    DESCRIPTION
		"Lower threshold for the amount of data in bits per second
		 to be sent across the 64Kbit/sec B-channel. If the measured
		 throughput becomes smaller than this value over a period of
		 pppExtIfGearDownPersistance seconds, the remaining B-channel
		 will be dropped."
	    DEFVAL { 9600 }
	::= { pppExtIfEntry 16 }

	pppExtIfGearUpPersistance OBJECT-TYPE
	    SYNTAX  INTEGER (0..100)
	    ACCESS  read-write
	    STATUS  mandatory

	    DESCRIPTION
		"Gear up persistence interval for invoking current bandwidth.
		 The measured throughput (in percent of the total bandwidth)
		 of this interface (see pppExtIfLoad) is compared with the
		 current value of the variable pppExtIfGearUpThreshold once
		 per second. If exceeded longer than pppExtIfGearUpPersistance
		 seconds an additional B-channel will be requested."
	    DEFVAL { 5 }
	::= { pppExtIfEntry 17 }

	pppExtIfGearDownPersistance OBJECT-TYPE
	    SYNTAX  INTEGER (0..100)
	    ACCESS  read-write
	    STATUS  mandatory

	    DESCRIPTION
		"Gear down persistence interval for decreasing current
		 bandwidth. The measured throughput (in percent of the total
		 bandwidth) of this interface (see pppExtIfLoad) is compared
		 with the current value of pppExtIfGearDownThreshold once per
		 second. If exceeded longer than pppExtIfGearDownPersistance
		 seconds, exactly one B-channel will be dropped."
	    DEFVAL { 10 }
	::= { pppExtIfEntry 18 }

	pppExtIfL1Speed OBJECT-TYPE
	    SYNTAX  INTEGER
	    ACCESS  read-write
	    STATUS  mandatory

	    DESCRIPTION
		"This object contains the interface's nominal bandwidth
                 in bits per second. Please note that this parameter may
		 not represent the real available transmission rate. The
		 current purpose is only informational for example for PPTP
		 or PPPoE interfaces where no accurate information from
		 the underlaying network is available."
	    DEFVAL { 0 }
	::= { pppExtIfEntry 19 }

	pppExtIfCurrentRetryTime OBJECT-TYPE
	    SYNTAX  INTEGER (0..36000)
	    ACCESS  read-write
	    STATUS  mandatory

	    DESCRIPTION
		"Current time in seconds to wait before retrying a call when
	         the smart retry algorithm is implemented."
	    DEFVAL { 4 }
	::= { pppExtIfEntry 20 }

	pppExtIfMaxRetryTime OBJECT-TYPE
	    SYNTAX  INTEGER (0..36000)
	    ACCESS  read-write
	    STATUS  mandatory

	    DESCRIPTION
		"Maximum time in seconds to wait before retrying a call when
		 the smart retry algorithm is implemented. When set to zero
		 this algorithm is disabled."
	    DEFVAL { 0 }
	::= { pppExtIfEntry 21 }

	pppExtIfMtu OBJECT-TYPE
	    SYNTAX  INTEGER (0..8192)
	    ACCESS  read-write
	    STATUS  mandatory

	    DESCRIPTION
                "Determines size of the largest datagram which can be
	         sent on the interface, specified in octets (see ifMtu).
		 When set to zero (default), the value of the variable
		 ifMtu depends on the received LCP MRU/MRRU option."
	    DEFVAL { 0 }
	::= { pppExtIfEntry 22 }

	pppExtIfMru OBJECT-TYPE
	    SYNTAX  INTEGER (0..8192)
	    ACCESS  read-write
	    STATUS  mandatory

	    DESCRIPTION
		"The maximum length for the PPP information field, including
		 padding, but not including the protocol field, is termed
		 the Maximum Receive Unit (MRU)."
	    DEFVAL { 1524 }
	::= { pppExtIfEntry 23 }

	pppExtIfAuthMutual OBJECT-TYPE
	    SYNTAX  INTEGER {
		disabled(1), 
		enabled(2)
	    } 
	    ACCESS  read-write
	    STATUS  mandatory

	    DESCRIPTION
		"This object enables mutual PPP authentication between the
		 peers."
	    DEFVAL { disabled }
	::= { pppExtIfEntry 24 }

--	pppExtIfAuthRestart OBJECT-TYPE
--	    SYNTAX  INTEGER {
--		disabled(1), 
--		enabled(2)
--	    } 
--	    ACCESS  read-write
--	    STATUS  obsolete
--
--	    DESCRIPTION
--		"This object enables a two-phase PPP authentication scheme
--		 where an initial PPP authentication procedure is partially
--		 handled by a proxy and finally relayed to the target server
--		 which restarts a full LCP negociation."
--	    DEFVAL { disabled }
--	::= { pppExtIfEntry 25 }
--
	pppExtIfDialProfileIndex OBJECT-TYPE
	    SYNTAX  INTEGER
	    ACCESS  read-write
	    STATUS  mandatory

            DESCRIPTION
		 "References the associated dial profile."
	::= { pppExtIfEntry 26 }

	pppExtIfDialinL1Protocol OBJECT-TYPE
	    SYNTAX INTEGER {
                data-64k(1),
                data-56k(2),
                modem(3),
                dovb(4),
                v110-1200(5),
                v110-2400(6),
                v110-4800(7),
                v110-9600(8),
                v110-14400(9),
                v110-19200(10),
                v110-38400(11), 
                modem-profile-1(12),
                modem-profile-2(13),
                modem-profile-3(14),
                modem-profile-4(15),
                modem-profile-5(16),
                modem-profile-6(17),
                modem-profile-7(18),
                modem-profile-8(19),
                pptp-pns(20),
                pppoe(21),
                pppx25(22),
                pptp-pac(23),
                l2tp-lns(24),
                l2tp-lac(25),
                dovb-64k(26),
		all(31)
	    }
	    ACCESS  read-write
	    STATUS  mandatory

            DESCRIPTION
		 "This variable determines the permitted layer 1 protocol
		 for incoming calls. If set to all(31) there is no specific
		 restriction. In all other cases incoming calls are either
		 rejected (when identified via CLID) or terminated after
		 identification via PPP authentication (inband authentication)
		 if the used layer 1 protocol doesn't match. Note that this
		 check will be also performed for any initial call used to
		 initiate a callback."
	    DEFVAL { all }
	::= { pppExtIfEntry 27 }

	pppExtIfpppoeEthIfIndex	OBJECT-TYPE
	    SYNTAX  INTEGER 
	    ACCESS  read-write
	    STATUS  mandatory

	    DESCRIPTION
                "Determines the Ethernet interface to be used for
		 PPP over Ethernet (PPPoE) according RFC 2516. If not
		 specified here the value in biboPPPProfilePPPoEDevIfIndex
		 will be used as fallback (backward compatiblity)."
	::= { pppExtIfEntry 28 }

	pppExtIfpppoaPvcIfIndex	OBJECT-TYPE
	    SYNTAX  INTEGER 
	    ACCESS  read-write
	    STATUS  mandatory

	    DESCRIPTION
                "Determines the ATM PVC to be used for PPP over Ethernet (PPPoA)
		 according RFC 2364 - PPPoA on demand mode. If not specified
		 here the first ATM PVC configured for PPPoA on demand
		 (see pppoaPvcTable) will be used as fallback."
	::= { pppExtIfEntry 29 }

	pppExtIfRadiusMarkAcct OBJECT-TYPE
	    SYNTAX INTEGER {
                disabled(1),
                enabled(2),
		trigger-on(3),
		trigger-off(4)
	    }
	    ACCESS  read-write
	    STATUS  mandatory

	    DESCRIPTION
                "Determines wether start or stop of RADIUS accounting should
		 be marked (via Accounting-On/Accounting-Off) for the logical
		 RADIUS server group specified by pppExtIfRadiusGroupId.
		 RADIUS 'Accounting-On' is send either if set to trigger-on
		 (3) or once the associated IPCP layer reaches the operational
		 'up' statuis. RADIUS 'Accounting-Off' is send either if set to
		 trigger-off (4) or once the associated IPCP layer reaches the
		 operational 'down' status."
	    DEFVAL { disabled }
	::= { pppExtIfEntry 30 }

	pppExtIfRadiusGroupId OBJECT-TYPE
	    SYNTAX  INTEGER (0..9) 
	    ACCESS  read-write
	    STATUS  mandatory

	    DESCRIPTION
                "Determines the logical RADIUS server group to be addressed
		 for sending the RADIUS Accounting-On/Accounting-Off messages.
		 See also radiusSrvPriority."
	    DEFVAL { 0 }
	::= { pppExtIfEntry 31 }

	pppExtIfpppoeFallbackVlanId OBJECT-TYPE
	    SYNTAX  INTEGER (-1..4094)
	    MAX-ACCESS  read-write
	    STATUS      current

	    DESCRIPTION
		"In case of PPPoE this variable specifies the VLAN-Tag-Id
		 to be used as fallback (VLAN-ID probing). If set to '-1'
		 this variable has no effect (fallback disabled)."
	    DEFVAL { -1 }
	::= { pppExtIfEntry 32 }

    -- PPP dial profile

	pppDialProfileTable OBJECT-TYPE
	    SYNTAX  SEQUENCE OF PppDialProfileEntry
	    ACCESS  not-accessible
	    STATUS  mandatory
	    DESCRIPTION
		"The pppDialProfileTable contains default parameters
                 used for establishing dialout connections in cases
                 where there is no partner specific configuration available
                 (see biboDialTable).

                Creating entries: Entries are created by assigning a
                value to the pppDialProfileType object.

                Deleting entries: An entry can be removed by assigning
                the value `delete' to its pppDialProfileType object."
		::= { ppp 11 }

	pppDialProfileEntry OBJECT-TYPE
	    SYNTAX  PppDialProfileEntry
	    ACCESS  not-accessible
	    STATUS  mandatory
	    DESCRIPTION
		""
	    INDEX   { pppDialProfileBapLkType }
	::= { pppDialProfileTable 1 }

	PppDialProfileEntry ::=
	    SEQUENCE {
		pppDialProfileIndex			INTEGER,
		pppDialProfileDescr			DisplayString,
		pppDialProfileBapNumber			DisplayString,
		pppDialProfileBapSubAddress		DisplayString,
		pppDialProfileBapLkType			INTEGER,
		pppDialProfileStkMask			INTEGER,
		pppDialProfileCallbackL1Prot		INTEGER
	    }

	pppDialProfileIndex OBJECT-TYPE
	    SYNTAX  INTEGER
	    ACCESS  read-only
	    STATUS  mandatory

	    DESCRIPTION
		"This object uniquely references this dialout profile.
		 The index value is generated automatically."
	::= { pppDialProfileEntry 1 } 
	
	pppDialProfileDescr OBJECT-TYPE
	    SYNTAX  DisplayString (SIZE (0..255))
	    ACCESS  read-write
	    STATUS  mandatory

	    DESCRIPTION
		"A textual string describing this dialout profile."
	::= { pppDialProfileEntry 2 } 

	pppDialProfileBapNumber OBJECT-TYPE
	    SYNTAX  DisplayString (SIZE (0..63))
	    ACCESS  read-write
	    STATUS  mandatory

	    DESCRIPTION
		"This object decribes the phone delta to use in a BAP
		 Call-Response or Callback-Request according RFC 2125."
	::= { pppDialProfileEntry 3 }

	pppDialProfileBapSubAddress OBJECT-TYPE
	    SYNTAX  DisplayString (SIZE (0..63))
	    ACCESS  read-write
	    STATUS  mandatory

	    DESCRIPTION
		"This object decribes the subaddress to use in a BAP
		 Call-Response or Callback-Request according RFC 2125."
	::= { pppDialProfileEntry 4 }

	pppDialProfileBapLkType OBJECT-TYPE
	    SYNTAX  INTEGER { 
		isdn(1), 
		x25(2),
		analog(3),
--		switched-digital(4),
		isdn-dovb(5),
		delete(8)
	    } 
	    ACCESS  read-write
	    STATUS  mandatory

	    DESCRIPTION
		"This object describes the link type to use in a BAP
		 Call-Response or Callback-Request according RFC 2125."
	    DEFVAL { isdn }
	::= { pppDialProfileEntry 5 }

	pppDialProfileStkMask OBJECT-TYPE
	    SYNTAX  BitValue 
	    ACCESS  read-write
	    STATUS  mandatory

	    DESCRIPTION
                "This binary number defines the ISDN stack(s) to use. Each 
                 bit corresponds to one entry (stack) in the isdnStkTable, 
                 the rightmost bit selects entry 0, the next bit selects 
                 entry 1, and so forth. For example, StkMask=0b1101 means: 
                 Allow to use ISDN stacks 0, 2and 3.
                 A mask of 0 disables dialup completely, while a mask of 
                 -1 enables dialup on all available ISDN stacks."
	    -- DEFVAL { 'ffffffff'H }
	    DEFVAL { 4294967295 }
	::= { pppDialProfileEntry 6 }

	pppDialProfileCallbackL1Prot OBJECT-TYPE
	    SYNTAX INTEGER {
		initial(1),
		data-64k(2),
		data-56k(3),
		modem(4),
		dovb(5),
		v110-1200(6),
		v110-2400(7),
		v110-4800(8),
		v110-9600(9),
		v110-14400(10),
		v110-19200(11),
		v110-38400(12),
		modem-profile-1(13),
		modem-profile-2(14),
		modem-profile-3(15),
		modem-profile-4(16),
		modem-profile-5(17),
		modem-profile-6(18),
		modem-profile-7(19),
		modem-profile-8(20),
		pptp-pns(21),
		pppoe(22),
		aodi(23),
		pptp-pac(24),
		pppoa(25),
                l2tp-lac(26),
                pppox25(27),
		dovb-64k(29),
                gprs(30)
	    }
	    ACCESS  read-write
	    STATUS  mandatory

	    DESCRIPTION
		"This entry is used to select the layer 1 protocol settings
		 for callback. if set to initial(1), the selected layer 1
		 protocol of the initial call will be used to perform the
		 callback."
	    DEFVAL { initial }
	::= { pppDialProfileEntry 7 }


    -- DIAL Group

    -- Configuration of Dial Strings

	biboDialTable OBJECT-TYPE
	    SYNTAX  SEQUENCE OF BiboDialEntry
	    ACCESS  not-accessible
	    STATUS  mandatory
	    DESCRIPTION
		"The biboDialTable contains configuration information
                for incoming and outgoing ISDN telephone numbers.

                Creating entries: Entries are created by assigning a
                value to the biboDialIfIndex object.

                Deleting entries: An entry can be removed by assigning
                the value `delete' to its biboDialType object."
	::= { dialmap 1 }

	biboDialEntry OBJECT-TYPE
	    SYNTAX  BiboDialEntry
	    ACCESS  not-accessible
	    STATUS  mandatory
	    DESCRIPTION
		""
	    INDEX   { biboDialIfIndex }
	::= { biboDialTable 1 }

	BiboDialEntry ::=
	    SEQUENCE {
		biboDialIfIndex				INTEGER,
		biboDialType				INTEGER,
		biboDialDirection			INTEGER,
		biboDialNumber				DisplayString,
		biboDialSubaddress			OCTET STRING,
		biboDialClosedUserGroup			INTEGER,
		biboDialStkMask				BitValue,
		biboDialScreening			INTEGER,
		biboDialCallingSubaddress		OCTET STRING,
		biboDialTypeOfCallingSubAdd		INTEGER,
		biboDialTypeOfCalledSubAdd		INTEGER,
		biboDialLocalNumber			DisplayString,
		biboDialTypeOfLocalNumber		INTEGER,
		biboDialOutNumTranslation		INTEGER
	    }

	biboDialIfIndex OBJECT-TYPE
	    SYNTAX  INTEGER 
	    ACCESS  read-write
	    STATUS  mandatory

	    DESCRIPTION
		"The correlating PPP interface index."
	::= { biboDialEntry 1 }

	biboDialType OBJECT-TYPE
	    SYNTAX  INTEGER { 
		isdn(1), 
		isdn-spv(2), 
		delete(3),
                ppp-callback(4),
                ppp-negotiated(5),
                x25-dialout(6),
		ip(7),
		x25(8)
	    } 
	    ACCESS  read-write
	    STATUS  mandatory

	    DESCRIPTION
		"The dialup type can be set to plain isdn(1),
		 isdn-spv(2) semi-permanent links used by the German
		 1TR6 D-channel protocol, or to delete(3) to delete
		 a biboDialTable entry. The types ppp-callback(4) and 
                 ppp-negotiated(5) are used for the LCP callback option."
	    DEFVAL { isdn }
	::= { biboDialEntry 2 }

	biboDialDirection OBJECT-TYPE
	    SYNTAX  INTEGER { 
		incoming(1), 
		outgoing(2), 
		both(3)
--		callback(4)
	    } 
	    ACCESS  read-write
	    STATUS  mandatory

	    DESCRIPTION
		"The allowed dial direction is either incoming(1), 
                outgoing(2), or both(3) calls. No call is ever set up when set
                to incoming(1). Incoming calls will not be identified
                when set to outoing(2). Furthermore, once PPP 
                authentication succeeds and there is at least one incoming
                number defined but for which none matches, the call will
                not be accepted for security reasons."
	    DEFVAL { both }
	::= { biboDialEntry 3 }

	biboDialNumber OBJECT-TYPE
	    SYNTAX  DisplayString (SIZE (0..63))
	    ACCESS  read-write
	    STATUS  mandatory

	    DESCRIPTION
		"The defined dialing number. Used for either dialing
		 or comparing to incoming calls or both, depending on
		 the content of the biboDialDirection field. The
		 wildcards '*', '?', '[', ']', '{', '}' may be used."
	::= { biboDialEntry 4 }

	biboDialSubaddress OBJECT-TYPE
	    SYNTAX  OCTET STRING
	    ACCESS  read-write
	    STATUS  mandatory

	    DESCRIPTION
		"The defined dial subaddress, if any. Also, see the 
                biboDialNumber field."
	::= { biboDialEntry 5 }

	biboDialClosedUserGroup OBJECT-TYPE
	    SYNTAX  INTEGER (0..9999) 
	    ACCESS  read-write
	    STATUS  mandatory

	    DESCRIPTION
		"The defined closed user group, if any. Also, see the 
                biboDialNumber field."
	::= { biboDialEntry 6 }

	biboDialStkMask OBJECT-TYPE
	    SYNTAX  BitValue 
	    ACCESS  read-write
	    STATUS  mandatory

	    DESCRIPTION
		"The defined stack mask. Each value of IsdnStkNumber 
		 represents a bit in this bitmask. A mask of 0 disables dialup
		 completely, while a mask of -1 enables dialup on all
		 available ISDN stacks."
	    -- DEFVAL { 'ffffffff'H }
	    DEFVAL { 4294967295 }
	::= { biboDialEntry 7 }

        biboDialScreening OBJECT-TYPE
            SYNTAX  INTEGER { 
                user(1), user-verified(2), user-failed(3), network(4),
                dont-care(5)
            } 
            ACCESS  read-write
            STATUS  mandatory
 
            DESCRIPTION
                "The screening indicator of the biboDialNumber. The 
		biboDialScreening field can be used to gauge the 
                `trustworthiness' of the biboDialNumber field.
		(See isdnCallScreening)
                Indicators are ordered from highest to lowest as follows:
      
                indicator:        CPN assigned:   verification:   
                `network'         by network      none
                `user-verified'   by user         verification successful
                `user'            by user         none
                `user-failed'     by user         verification failed
      
                Set this field to `dont-care' to accept all calls.
                Otherwise calls are accepted only if the screening
                indicator matches or is higher than the set value."
            DEFVAL { dont-care }
        ::= { biboDialEntry 8 }

	biboDialCallingSubaddress OBJECT-TYPE
	    SYNTAX  OCTET STRING
	    ACCESS  read-write
	    STATUS  mandatory

	    DESCRIPTION
		"The defined calling dial subaddress, if any. Also, see the 
                biboDialNumber field."
	::= { biboDialEntry 9 }

        biboDialTypeOfCallingSubAdd OBJECT-TYPE
            SYNTAX  INTEGER { 
                nsap(1), user-specified(2), reserved(3)
            } 
            ACCESS  read-write
            STATUS  mandatory
 
            DESCRIPTION
                "The type of calling party subaddress."
            DEFVAL { reserved }
        ::= { biboDialEntry 10 }

        biboDialTypeOfCalledSubAdd OBJECT-TYPE
            SYNTAX  INTEGER { 
                nsap(1), user-specified(2), reserved(3)
            } 
            ACCESS  read-write
            STATUS  mandatory
 
            DESCRIPTION
                "The type of called party subaddress."
            DEFVAL { reserved }
        ::= { biboDialEntry 11 }

	biboDialLocalNumber OBJECT-TYPE
	    SYNTAX  DisplayString (SIZE (0..63))
	    ACCESS  read-write
	    STATUS  mandatory

	    DESCRIPTION
		"The defined local dialing number. Used as originator address
         in the case of an outgoing calling and is checked against the 
         destination address in the case of an incoming call. The 
		 wildcards '*', '?', '[', ']', '{', '}' may be used."
	::= { biboDialEntry 12 }
	
        biboDialTypeOfLocalNumber OBJECT-TYPE
            SYNTAX  INTEGER { 
                unknown(1),
		international-number(2),
		national-number(3),
		network-specific-number(4),
		subscriber-number(5)
            } 
            ACCESS  read-write
            STATUS  mandatory
 
            DESCRIPTION
                "The type of local number (biboDialLocalNumber) upon outgoing
		 calls according to ETS 300 102-1.

		 Possible values are:
		     unknown(1),
		     international-number(2),
		     national-number(3),
		     network-specific-number(4),
		     subscriber-number(5)

		 Default value is unknown."
            DEFVAL { unknown }
        ::= { biboDialEntry 13 }

--      biboDialInNumTranslation ::= { biboDialEntry 13 } reserved

	biboDialOutNumTranslation OBJECT-TYPE
	    SYNTAX  INTEGER { 
	    	enabled(1), 
		disabled(2)
	    } 
	    ACCESS  read-write
	    STATUS  mandatory

	    DESCRIPTION
		"If DialOutNumTranslation is disabled, the number will
		 be passed to the lower layers without modification."
	    DEFVAL { enabled }
	::= { biboDialEntry 14 }

    -- pppPppoeEthDevTable

	pppPppoeEthDevTable OBJECT-TYPE
	    SYNTAX  SEQUENCE OF PppPppoeEthDevEntry
	    ACCESS  not-accessible
	    STATUS  mandatory
	    DESCRIPTION
		"."
	::= { ppp 15 }

	pppPppoeEthDevEntry OBJECT-TYPE
	    SYNTAX  PppPppoeEthDevEntry
	    ACCESS  not-accessible
	    STATUS  mandatory
	    DESCRIPTION
		""
	    INDEX   { pppPppoeEthDevIfIndex, pppPppoeEthDevIndex }
	::= { pppPppoeEthDevTable 1 }

	PppPppoeEthDevEntry ::=
	    SEQUENCE {
		pppPppoeEthDevIfIndex			INTEGER,
		pppPppoeEthDevAdminStatus		INTEGER,
		pppPppoeEthDevIndex			INTEGER,
		pppPppoeEthDevOperStatus		INTEGER,
		pppPppoeEthDevResidualBlockTime		INTEGER,
		pppPppoeEthDevMaxTxRate			INTEGER
	    }

	pppPppoeEthDevIfIndex OBJECT-TYPE
	    SYNTAX  INTEGER
	    ACCESS  read-write
	    STATUS  mandatory

	    DESCRIPTION
                "The associated interface index of this entry."
	::= { pppPppoeEthDevEntry 1 }
	
	pppPppoeEthDevAdminStatus OBJECT-TYPE
	    SYNTAX  INTEGER {
	        enabled(1),
		disabled(2),
		delete(3)
	    }
	    ACCESS  read-write
	    STATUS  mandatory

	    DESCRIPTION
                "The administrative this entry."
	    DEFVAL { enabled }
	::= { pppPppoeEthDevEntry 2 }

	pppPppoeEthDevIndex OBJECT-TYPE
	    SYNTAX  INTEGER
	    ACCESS  read-write
	    STATUS  mandatory

	    DESCRIPTION
                "Specifies the first device to be used for PPP over Ethernet
		 (PPPoE) according RFC 2516."
	::= { pppPppoeEthDevEntry 3 }
	
	pppPppoeEthDevMaxTxRate OBJECT-TYPE
	    SYNTAX  INTEGER (0..10000000)
	    ACCESS  read-write
	    STATUS  mandatory

	    DESCRIPTION
                "Administrative transmit rate limitation needed in order
		 to support scenarios with external XDSL modems. If specified
		 this value will be adopted in associated biboPPPLinkSpeed
		 value. If set to '0' biboPPPLineSpeed is set according the
		 ifSpeed value of the associated Ethernet Device."
	    DEFVAL { 0 }
	::= { pppPppoeEthDevEntry 4 }
	
	pppPppoeEthDevOperStatus OBJECT-TYPE
	    SYNTAX  INTEGER {
	        dormant(1),	-- device not yet used for PPPoE connect
		connecting(2),	-- asociated PPPoE not yet connected
		up(3),		-- asociated PPPoE connection established
		blocked(4)	-- device usage blocked due to connect failure
	    }
	    ACCESS  read-only
	    STATUS  mandatory

	    DESCRIPTION
                "The PPP-internal operational status of the first device to be
		 used for PPP over Ethernet (PPPoE) according RFC 2516."
	    DEFVAL { dormant }
	::= { pppPppoeEthDevEntry 10 }
	
	pppPppoeEthDevResidualBlockTime OBJECT-TYPE
	    SYNTAX  INTEGER (0..2147483647)
	    ACCESS  read-only
	    STATUS  mandatory

	    DESCRIPTION
                "The remaining time interval till the associated
		 pppPppoeEthDevOperStatus will be changed from blocked(4)
		 to dormant(1) again."
	::= { pppPppoeEthDevEntry 11 }
	

        -- pppPppoaPvcDevTable

	pppPppoaPvcDevTable OBJECT-TYPE
	    SYNTAX  SEQUENCE OF PppPppoaPvcDevEntry
	    ACCESS  not-accessible
	    STATUS  mandatory
	    DESCRIPTION
		"."
	::= { ppp 18 }

	pppPppoaPvcDevEntry OBJECT-TYPE
	    SYNTAX  PppPppoaPvcDevEntry
	    ACCESS  not-accessible
	    STATUS  mandatory
	    DESCRIPTION
		""
	    INDEX   { pppPppoaPvcDevIfIndex, pppPppoaPvcDevIndex }
	::= { pppPppoaPvcDevTable 1 }

	PppPppoaPvcDevEntry ::=
	    SEQUENCE {
		pppPppoaPvcDevIfIndex			INTEGER,
		pppPppoaPvcDevAdminStatus		INTEGER,
		pppPppoaPvcDevIndex			INTEGER,
		pppPppoaPvcDevOperStatus		INTEGER,
		pppPppoaPvcDevResidualBlockTime		INTEGER
	    }

	pppPppoaPvcDevIfIndex OBJECT-TYPE
	    SYNTAX  INTEGER
	    ACCESS  read-write
	    STATUS  mandatory

	    DESCRIPTION
                "The associated interface index of this entry."
	::= { pppPppoaPvcDevEntry 1 }
	
	pppPppoaPvcDevAdminStatus OBJECT-TYPE
	    SYNTAX  INTEGER {
	        enabled(1),
		disabled(2),
		delete(3)
	    }
	    ACCESS  read-write
	    STATUS  mandatory

	    DESCRIPTION
                "The administrative this entry."
	    DEFVAL { enabled }
	::= { pppPppoaPvcDevEntry 2 }

	pppPppoaPvcDevIndex OBJECT-TYPE
	    SYNTAX  INTEGER
	    ACCESS  read-write
	    STATUS  mandatory

	    DESCRIPTION
                "Specifies the first device to be used for PPP over ATM 
		 (PPPoA) according RFC 2364."
	::= { pppPppoaPvcDevEntry 3 }
	
	pppPppoaPvcDevOperStatus OBJECT-TYPE
	    SYNTAX  INTEGER {
	        dormant(1),	-- device not yet used for PPPoA connect
		connecting(2),	-- asociated PPPoA not yet connected
		up(3),		-- asociated PPPoA connection established
		blocked(4)	-- device usage blocked due to connect failure
	    }
	    ACCESS  read-only
	    STATUS  mandatory

	    DESCRIPTION
                "The PPP-internal operational status of the first device to be
		 used for PPP over ATM (PPPoA) according RFC 2364."
	    DEFVAL { dormant }
	::= { pppPppoaPvcDevEntry 10 }
	
	pppPppoaPvcDevResidualBlockTime OBJECT-TYPE
	    SYNTAX  INTEGER (0..2147483647)
	    ACCESS  read-only
	    STATUS  mandatory

	    DESCRIPTION
                "The remaining time interval till the associated
		 pppPppoaPvcDevOperStatus will be changed from blocked(4)
		 to dormant(1) again."
	::= { pppPppoaPvcDevEntry 11 }
	
END
