-- This file is corresponding to Release 10.2.3.100 from 2018/07/18 00:00:00


-- $RCSfile: mib-adsl,v $
-- $Revision: 1.15 $

-- (C)opyright 2007-2014 bintec elmeg GmbH, All Rights Reserved

BIANCA-BRICK-ADSL-MIB DEFINITIONS ::= BEGIN

        IMPORTS
            Counter32, enterprises, OBJECT-TYPE, MODULE-IDENTITY
                FROM SNMPv2-SMI
             DisplayString
                FROM SNMPv2-TC
            TRAP-TYPE
                FROM RFC-1215
	    adsl
		FROM BINTEC-MIB;

--	AdslPerfTimeElapsed ::= INTEGER
--         "The number of seconds that have elapsed since
--          the beginning of the current measurement period.
--          If, for some reason, such as an adjustment in the
--          system's time-of-day clock, the current interval
--          exceeds the maximum value, the agent will return
--          the maximum value."
--	AdslPerfCurrDayCount ::= INTEGER
--         "A counter associated with interface performance
--          measurements in a current 1-day (24 hour) measurement
--          interval.
--          
--          The value of this counter starts at zero at the
--          beginning of an interval and is increased when
--          associated events occur, until the end of the
--          1-day interval.  At that time the value of the
--          counter is stored in the previous 1-day history
--          interval, if available, and the current interval
--          counter is restarted at zero.
--          
--          In the case where the agent has no valid data available
--          for this interval the corresponding object
--          instance is not available and upon a retrieval
--          request a corresponding error message shall be
--          returned to indicate that this instance does
--          not exist (for example, a noSuchName error for
--          SNMPv1 and a noSuchInstance for SNMPv2 GET
--          operation)."
--	AdslPerfPrevDayCount ::= INTEGER
--         "A counter associated with interface performance
--          measurements during the most previous 1-day (24 hour)
--          measurement interval.  The value of this counter is
--          equal to the value of the current day counter at
--          the end of its most recent interval.
--          
--          In the case where the agent has no valid data available
--          for this interval the corresponding object
--          instance is not available and upon a retrieval
--          request a corresponding error message shall be
--          returned to indicate that this instance does
--          not exist (for example, a noSuchName error for
--          SNMPv1 and a noSuchInstance for SNMPv2 GET
--          operation)."
---------------------------------------------------------------------------
    adslMIB MODULE-IDENTITY
	    LAST-UPDATED "200908210000Z"
	    ORGANIZATION
	        "bintec elmeg GmbH"
	    CONTACT-INFO
		"EMail:   info@bintec-elmeg.com
		 Web:     www.bintec-elmeg.com
		"
	    DESCRIPTION
               "The MIB module defining objects for the management of a pair of
                ADSL modems at each end of the ADSL line.  Each such line has
                an entry in an ifTable which may include multiple modem lines.
                An agent may reside at either end of the ADSL line however the
                MIB is designed to require no management communication between
                them beyond that inherent in the low-level ADSL line protocol.
                The agent may monitor and control this protocol for its needs.
                
                ADSL lines may support optional Fast or Interleaved channels.
                If these are supported, additional entries corresponding to the
                supported channels must be created in the ifTable. Thus an ADSL
                line that supports both channels will have three entries in the
                ifTable, one for each physical, fast, and interleaved, whose
                ifType values are equal to adsl(94), fast(125), and
                interleaved(124), respectively. The ifStackTable is used to
                represent the relationship between the entries.
                
                Naming Conventions:
                          Atuc - (ATUC) modem at near (Central) end of line
                          Atur - (ATUR) modem at Remote end of line
                          Curr - mandatory
                          Prev - Previous
                          Atn - Attenuation
                          ES  - Errored Second.
                          LCS - Line Code Specific
                          Lof - Loss of Frame
                          Lol - Loss of Link
                          Los - Loss of Signal
                          Lpr - Loss of Power
                          xxxs- interval of Seconds in which xxx occurs
                                 (e.g., xxx=Lof, Los, Lpr)
                          Max - Maximum
                          Mgn - Margin
                          Min - Minimum
                          Psd - Power Spectral Density
                          Snr - Signal to Noise Ratio
                          Tx  - Transmit
                          Blks- Blocks, a data unit, see
                                 adslAtuXChanCrcBlockLength
                  
              Build from Initial Version, published as RFC 2662"
		
	    REVISION     "200908210000Z"
	    DESCRIPTION
	        "First version conforming to SMIv2."
	    ::= { adsl 250 }
---------------------------------------------------------------------------

    adslLineMib OBJECT IDENTIFIER ::= { adsl 1 }
    adslMibObjects OBJECT IDENTIFIER ::= { adslLineMib 1 }

    adslLineTable OBJECT-TYPE
	SYNTAX      SEQUENCE OF AdslLineEntry
	MAX-ACCESS  not-accessible
	STATUS      current
	DESCRIPTION 
	    "This table includes common attributes describing
	     far end (ATU-R) of the line.  It is required for all ADSL
	     physical interfaces.  ADSL physical interfaces are
	     those ifEntries where ifType is equal to adsl(94)."
	::= { adslMibObjects 1 }

    adslLineEntry OBJECT-TYPE
	SYNTAX      AdslLineEntry
	MAX-ACCESS  not-accessible
	STATUS      current
	DESCRIPTION 
	    "An entry in adslLineTable."
	INDEX       { adslLineIfIndex  }
	::= { adslLineTable 1 }

    AdslLineEntry ::= SEQUENCE {
	adslLineIfIndex		INTEGER,
	adslLineCoding		INTEGER,
	adslLineOpenMode	INTEGER,
	adslLineOperationalMode	INTEGER,
	adslLineTxGainOffset    INTEGER,
	adslLineRxGainOffset    INTEGER,
	adslLineType		INTEGER,
	adslLineMarginThreshold	INTEGER,
	adslLineAnnexType	INTEGER,
	adslLineDyingGasp	INTEGER,
	adslLineBitSwapping	BITS,
	adslLineProfile         INTEGER,
	adslLineCodingGainOffset INTEGER,
	adslLineModemCapabilities BITS,
	adslLineGHSCarrierSets	 BITS
    }

    adslLineIfIndex OBJECT-TYPE
	SYNTAX      INTEGER
	MAX-ACCESS  read-only
	STATUS      current
	DESCRIPTION 
	    "Specifies the ADSL interface index used on this line."
	::= { adslLineEntry 1 }

    adslLineCoding OBJECT-TYPE
	SYNTAX      INTEGER { other(1), dmt(2), cap(3), qam(4) }
	MAX-ACCESS  read-only
	STATUS      current
	DESCRIPTION 
	    "Specifies the ADSL coding type used on this line."
	::= { adslLineEntry 2 }

    adslLineOpenMode OBJECT-TYPE
	SYNTAX      INTEGER {open(3), ansiT1dot413(5), gdmt(6), gliteg992dot2(7), multimode(8), adsl2(9), adsl2delt(10),
	                     adsl2plus(11), adsl2plusdelt(12), readsl2(13), readsl2delt(14), 
			     multimodeM(15), adsl2plusAnnexM(16), vdsl2(17), multimodeVdsl(18)}
	MAX-ACCESS  read-write
	STATUS      current
	DESCRIPTION 
	    "Specifies the ADSL opening mode used on this line. Possible values:
	    open   (3): do not use adsl line,
	    ansiT1dot413 (5): ANSI T1.413,
	    gdmt (6): ADSL classic, G.DMT, ITU-T G.992.1
	    gliteg992dot2 (7): Splitterless ADSL, G.Lite, ITU-T G.992.2,
	    multimode (8),
	    adsl2 (9): ADSL2, G.DMT.Bis, ITU-T G.992.3,
	    adsl2delt (10: ADSL2 Double Ended Line Test,
	    adsl2plus (11): ADSL2 Plus, ITU-T G.992.5,
	    adsl2plusdelt (12): ADSL2 Plus Double Ended Line Test,
	    readsl2 (13): Reach Extended ADSL2,
	    readsl2delt (14): Reach Extended ADSL2 Double Ended Line Test,
	    multimodeM (15): multimode including ADSL2(+) Annex M,
	    adsl2plusAnnexM (16): ITU-T G.992.5 Annex M,
	    vdsl2 (17): VDSL2, ITU-T G.993.2,
	    multimodeVdsl (18): contains multimode (8) and vdsl2 (17)"

	DEFVAL      { multimode }
	::= { adslLineEntry 3 }

    adslLineOperationalMode OBJECT-TYPE
	SYNTAX      INTEGER {unknown(1), ansiT1dot413(2), itug992dot1(3), itug992dot2(4), adsl2(5), adsl2delt(6),
	                     adsl2plus(7), adsl2plusdelt(8), readsl2(9), readsl2delt(10), 
			     adsl2AnnexM(11), adsl2plusAnnexM(12), vdsl2(13),
			     adsl2AnnexJ(14), adsl2plusAnnexJ(15),
			     adsl2AnnexI(16), adsl2plusAnnexI(17) }
	MAX-ACCESS  read-only
	STATUS      current
	DESCRIPTION 
	    "Current operational mode :
	    unknown (1),
	    ansiT1dot413 (2): ANSI T1.413,
	    itug992dot1 (3): ADSL classic, G.DMT, ITU-T G.992.1,
	    itug992dot2 (4): Splitterless ADSL, ITU-T G.992.2,
	    adsl2 (5): G.DMT.Bis ITU-T G.992.3,
	    adsl2delt (6): ADSL2 Double Ended Line Test,
	    adsl2plus (7): ADSL2 Plus, ITU-T G.992.5,
	    adsl2plusdelt (8): ADSL2 Plus Double Ended Line Test,
	    readsl2 (9): Reach Extended ADSL2,
	    readsl2delt (10): Reach Extended ADSL2 Double Ended Line Test,
	    adsl2AnnexM (11): ADSL2 ITU-T G.992.3 Annex M, 
	    adsl2plusAnnexM (12): ADSL2+ ITU-T G.992.5 Annex M,
	    vdsl2 (13): VDSL2, ITU-T G.993.2
	    adsl2AnnexJ(14): ADSL2 ITU-T G.992.3 J,
	    adsl2plusAnnexJ(15): ADSL2+ ITU-T G.992.5 J,
	    adsl2AnnexI(16): ADSL2 ITU-T G.992.3 I,
	    adsl2plusAnnexI(17): ADSL2+ ITU-T G.992.5 I"
	::= { adslLineEntry 4 }

    adslLineTxGainOffset OBJECT-TYPE
	SYNTAX      INTEGER (-100..30)
	MAX-ACCESS  read-write
	STATUS      current
	DESCRIPTION 
	    "This parameter allows the user to add an offset to the Tx gain
	     of the CPE of the modem. 
	     The offset range is limited between -10dB and +3dB. 
	     It is expressed in tenth dB with a granularity of 0.5dB.
	     The default value is 0 dB."
	DEFVAL      { 0 }
	::= { adslLineEntry 5 }

    adslLineRxGainOffset OBJECT-TYPE
	SYNTAX      INTEGER (-50..50)
	MAX-ACCESS  read-write
	STATUS      current
	DESCRIPTION 
	    "This parameter allows the user to add an offset to the Rx gain
	     of the CPE of the modem. 
	     The offset range is limited between -5dB and +5dB. 
	     The default value is 0 dB."
	DEFVAL      { 0 }
	::= { adslLineEntry 6 }

    adslLineType OBJECT-TYPE
	SYNTAX      INTEGER (0..255)
	MAX-ACCESS  read-write
	STATUS      current
	DESCRIPTION 
	    "This parameter indicates the adsl line type."
	DEFVAL      { 0 }
	::= { adslLineEntry 7 }

    adslLineMarginThreshold OBJECT-TYPE
	SYNTAX      INTEGER (-320..315)
	MAX-ACCESS  read-write
	STATUS      current
	DESCRIPTION 
	    "This parameter allows the user to specify a threshold
	     for triggering a retrain, if the downstream margin drops
	     below the threshold.
	     The offset range is between -32dB and +31.5dB. 
	     It is expressed in tenth dB with a granularity of 0.5dB.
	     The default value is 6 dB."
	DEFVAL      { 60 }
	::= { adslLineEntry 8 }
    
    adslLineAnnexType OBJECT-TYPE
	SYNTAX	    INTEGER { annexA(1), annexB(2) }
	MAX-ACCESS  read-write
	STATUS      current
	DESCRIPTION
	    "This parameter allows the user to specify the used ADSL Annex type.
	    annexA (1): use annex A for related adsl interface,
	    annexB (2): use annex B for related adsl interface."
	DEFVAL       { 2 }
	::= { adslLineEntry 9 }

    adslLineDyingGasp OBJECT-TYPE
	SYNTAX      INTEGER { disable(1), enable(2) }
	MAX-ACCESS  read-write
	STATUS      current
	DESCRIPTION
	    "This parameter controls the behavior when the dying gasp condition
	     is detected. The dying gasp condition is detected when the power
	     input falls below a certain voltage level, eg. this happens when
	     the ATUR is switched off.
	     If dying gasp is enabled in this case the ATUR signals the dying gasp
	     indication to the ATUC, so the ATUC could ingore subsequent line
	     failures (if instructed to do so) because they are consequence of
	     the switched off power.
	     If dying gasp is disabled nothing is signalled to the ATUC."
	 DEFVAL      { 1 }
	::= { adslLineEntry 10 }

    adslLineBitSwapping OBJECT-TYPE
	SYNTAX      BITS { upstream(0), downstream(1) }
	MAX-ACCESS  read-write
	STATUS      current
	DESCRIPTION
	    "This parameter controls the behavior of up- and downstream bit swapping.
	     Setting the bit enables the bit swapping in the corresponding direction."
	 DEFVAL      { { upstream, downstream } }
	::= { adslLineEntry 11 }
    
    adslLineProfile OBJECT-TYPE
	SYNTAX      INTEGER
	MAX-ACCESS  read-write
	STATUS      current
	DESCRIPTION 
	    "This parameter adapts the training behaviour, to comply with some
	    special configurations used on some ADSL lines or during approval 
	    tests of their respective ADSL providers.
	    The following values are common on all devices:
	    0	this parameter is not supported by hardware, do not modify it.
	    1	Tiscali UK
	    2	France Telecom
	    3	Deutsche Telekom
	    4	standard behaviour - no special settings
	    5	Vodafone Germany
	    6	Telekom Austria
	    7	British Telecom
	    8	Telefonica Spain

	    The other values are only for debugging purpose and their
	    meaning depends on the hardware and on the BOSS version."
	DEFVAL      { 0 }
	::= { adslLineEntry 13 }

--    adslLineCodingGain OBJECT-TYPE
--	SYNTAX      INTEGER (-1..7)
--	MAX-ACCESS  read-write
--	STATUS      current
--	::= { adslLineEntry 14 }

    adslLineCodingGainOffset OBJECT-TYPE
	SYNTAX      INTEGER (-1..7)
	MAX-ACCESS  read-write
	STATUS      current
	DESCRIPTION 
	    "This parameter allows the user to control the Coding Gain 
	     of the CPE of the modem. 
	     The coding gain range is limited between 0dB and 7dB, a value
	     of -1 lets the CPE choose the coding gain itself.
	     The coding gain is expressed in entire dBs. The default value is -1."
	DEFVAL      { -1 }
	::= { adslLineEntry 19 }

    adslLineModemCapabilities OBJECT-TYPE
	SYNTAX  BITS {
		annexA(0),
		annexB(1),
		multimodeM(2),
		vdsl2(3),
		multimodeVdsl(4)
	}
	MAX-ACCESS  read-only
	STATUS  current
	DESCRIPTION
	    "This bitfield describes which open modes ADSL modem supports:
		    annexA          : The modem supports ADSL Annex A modes
		    annexB          : The modem supports ADSL Annex B modes
		    multimodeM      : To allow additional open modes like
		    			Annex I, J, M for a bigger
		    			upstream bandwidth use multimodeM
		    vdsl2           : Modem supports VDSL
		    multimodeVdsl   : Modem detects automatically ADSL and VDSL
	     ."
	::= { adslLineEntry 20 }

    adslLineGHSCarrierSets OBJECT-TYPE
	SYNTAX  BITS {
		b43(0),
		a43(1),
		v43(2),
		v43P(3),
		v43I(4),
		c43(5),
		j43(6),
		b43C(7),
		a43C(8)
	}
	MAX-ACCESS  read-write
	STATUS  current
	DESCRIPTION
	    "Specifies the G.994.1 handshake carrier sets used on this line.
	    Possible values:
	    b43   :  ADSL Annex B
	    a43   :  ADSL Annex A
	    v43   :  VDSL
	    v43P  :  VDSL Annex C pots
	    v43I  :  VDSL Annex C ISDN
	    c43   :  ADSL Annnex C
	    j43   :  ADSL2+ Annex J/M
	    b43C  :  ADSL Annex B
	    a43C  :  ADSL Annex A
	    "
	::= { adslLineEntry 21 }



    adslAtucPhysTable OBJECT-TYPE
	SYNTAX      SEQUENCE OF AdslAtucPhysEntry
	MAX-ACCESS  not-accessible
	STATUS      current
	DESCRIPTION 
	    "This table provides one row for each ATUC.
	     Each row contains the Physical Layer Parameters
	     table for that ATUC. ADSL physical interfaces are
	     those ifEntries where ifType is equal to adsl(94)."
	::= { adslMibObjects 2 }

    adslAtucPhysEntry OBJECT-TYPE
	SYNTAX      AdslAtucPhysEntry
	MAX-ACCESS  not-accessible
	STATUS      current
	DESCRIPTION 
	    "An entry in the adslAtucPhysTable."
	INDEX       { adslAtucIfIndex }
	::= { adslAtucPhysTable 1 }

    AdslAtucPhysEntry ::= SEQUENCE {
	adslAtucIfIndex		INTEGER,
	adslAtucInvVendorID         DisplayString,
	adslAtucInvVersionNumber    DisplayString,
	adslAtucCurrStatus          INTEGER,
	adslAtucCurrOutputPwr       INTEGER,
	adslAtucCurrAttainableRate  INTEGER,
	adslAtucCurrSnrMgn          INTEGER,
	adslAtucCurrAtn             INTEGER,
	adslAtucCurrPowercutback    INTEGER
    }

    adslAtucIfIndex OBJECT-TYPE
	SYNTAX      INTEGER
	MAX-ACCESS  read-only
	STATUS      current
	DESCRIPTION 
	    "Specifies the ADSL interface index."
	::= { adslAtucPhysEntry 1 }

    adslAtucInvVendorID OBJECT-TYPE
	SYNTAX      DisplayString (SIZE(0..16))
	MAX-ACCESS  read-only
	STATUS      current
	DESCRIPTION 
	    "The vendor ID code is a copy of the binary
	     vendor identification field defined by the
	     PHY[10] and expressed as readable characters."
    --     REFERENCE   
    --         "ANSI T1.413[10]"
	::= { adslAtucPhysEntry 2 }

    adslAtucInvVersionNumber OBJECT-TYPE
	SYNTAX      DisplayString (SIZE(0..16))
	MAX-ACCESS  read-only
	STATUS      current
	DESCRIPTION 
	    "The vendor specific version number sent by this ATU
	     as part of the initialization messages.  It is a copy
	     of the binary version number field defined by the
	     PHY[10] and expressed as readable characters."
    --     REFERENCE   
    --         "ANSI T1.413[10]"
	::= { adslAtucPhysEntry 3 }

    adslAtucCurrStatus OBJECT-TYPE
	SYNTAX      INTEGER 
			{	noDefect(1), 
				lossOfFraming(2), 
				lossOfSignal(3), 
				lossOfPower(4), 
				lossOfSignalQuality(5), 
				lossOfLink(6), 
				dataInitFailure(7), 
				configInitFailure(8), 
				protocolInitFailure(9), 
				noPeerAtuPresent(10),
				lossOfCellDelineation(11)
			}

	MAX-ACCESS  read-only
	STATUS      current
	DESCRIPTION 
	    "Indicates mandatory state of the ATUC line, i.e. the state of the line
	     as seen by ATUC. This is a bit-map of possible conditions.  The various bit
	     positions are:
         
	     1      noDefect             There no defects on the line
         
	     2      lossOfFraming        ATUC failure due to not
				  receiving valid frame.
         
	     3      lossOfSignal         ATUC failure due to not
				  receiving signal.
         
	     4      lossOfPower          ATUC failure due to loss of
				  power.
				  Note: the Agent may still
				  function.
         
	     5      lossOfSignalQuality  Loss of Signal Quality is
				  declared when the Noise Margin
				  falls below the Minimum Noise
				  Margin, or the bit-error-rate
				  exceeds 10^-7.
         
	     6      lossOfLink           ATUC failure due to inability
				  to link with ATUR.
         
	     7      dataInitFailure      ATUC failure during
				  initialization due to bit
				  errors corrupting startup
				  exchange data.
         
	     8      configInitFailure    ATUC failure during
				  initialization due to peer
				  ATU not able to support
				  requested configuration
         
	     9      protocolInitFailure  ATUC failure during
				  initialization due to
				  incompatible protocol used by
				  the peer ATU.
         
	     10      noPeerAtuPresent     ATUC failure during
				  initialization due to no
				  activation sequence detected
				  from peer ATU.
	     11      lossOfCellDelineation      ATUC failure due
				  loss of Cell Delineation in interleaved
				  and non-interleaved mode.
         
	     This is intended to supplement ifOperStatus."
	::= { adslAtucPhysEntry 4 }

    adslAtucCurrOutputPwr OBJECT-TYPE
	SYNTAX      INTEGER (-310..310)
	MAX-ACCESS  read-only
	STATUS      current
	DESCRIPTION 
	    "Measured total output power transmitted by this ATU.
	     This is the measurement that was reported during
	     the last activation sequence in tenth dB."
	::= { adslAtucPhysEntry 5 }

    adslAtucCurrAttainableRate OBJECT-TYPE
	SYNTAX      INTEGER
	MAX-ACCESS  read-only
	STATUS      current
	DESCRIPTION 
	    "Indicates the maximum mandatoryly attainable data rate
	     by the ATU.  This value will be equal or greater than
	     the mandatory line rate."
	::= { adslAtucPhysEntry 6 }

    adslAtucCurrSnrMgn OBJECT-TYPE
	SYNTAX      INTEGER (-640..640)
	MAX-ACCESS  read-only
	STATUS      current
	DESCRIPTION 
	    "Noise Margin as seen by this ATU with respect to its
	     received signal in tenth dB."
	::= { adslAtucPhysEntry 7 }

    adslAtucCurrAtn OBJECT-TYPE
	SYNTAX      INTEGER (0..630)
	MAX-ACCESS  read-only
	STATUS      current
	DESCRIPTION 
	    "Measured difference between the total power transmitted by
	     the peer ATU and the total power received by this ATU
	     in tenth dB."
	::= { adslAtucPhysEntry 8 }

    adslAtucCurrPowercutback OBJECT-TYPE
	SYNTAX      INTEGER
	MAX-ACCESS  read-only
	STATUS      current
	DESCRIPTION
	    "Indicates the powercutback by the ATU in tenth dB."
	::= { adslAtucPhysEntry 9 }

    adslAturPhysTable OBJECT-TYPE
	SYNTAX      SEQUENCE OF AdslAturPhysEntry
	MAX-ACCESS  not-accessible
	STATUS      current
	DESCRIPTION 
	    "This table provides one row for each ATUR
	     Each row contains the Physical Layer Parameters
	     table for that ATUR. ADSL physical interfaces are
	     those ifEntries where ifType is equal to adsl(94)."
	::= { adslMibObjects 3 }

    adslAturPhysEntry OBJECT-TYPE
	SYNTAX      AdslAturPhysEntry
	MAX-ACCESS  not-accessible
	STATUS      current
	DESCRIPTION 
	    "An entry in the adslAturPhysTable."
	INDEX       { adslAturIfIndex }
	::= { adslAturPhysTable 1 }

    AdslAturPhysEntry ::= SEQUENCE {
	adslAturIfIndex		INTEGER,
	adslAturInvSerialNumber     DisplayString,
	adslAturInvVendorID         DisplayString,
	adslAturInvVersionNumber    DisplayString,
	adslAturCurrSnrMgn          INTEGER,
	adslAturCurrAtn             INTEGER,
	adslAturCurrStatus          INTEGER,
	adslAturCurrOutputPwr       INTEGER,
	adslAturCurrAttainableRate  INTEGER,
	adslAturCurrPowercutback    INTEGER,
	adslAturCurrLinkStatus      INTEGER	
    }

    adslAturIfIndex OBJECT-TYPE
	SYNTAX      INTEGER
	MAX-ACCESS  read-only
	STATUS      current
	DESCRIPTION 
	    "Specifies the ADSL interface index."
	::= { adslAturPhysEntry 1 }

    adslAturInvSerialNumber OBJECT-TYPE
	SYNTAX      DisplayString (SIZE(0..32))
	MAX-ACCESS  read-only
	STATUS      current
	DESCRIPTION 
	    "The vendor specific string that identifies the
	     vendor equipment."
	::= { adslAturPhysEntry 2 }

    adslAturInvVendorID OBJECT-TYPE
	SYNTAX      DisplayString (SIZE(0..16))
	MAX-ACCESS  read-only
	STATUS      current
	DESCRIPTION 
	    "The vendor ID code is a copy of the binary
	     vendor identification field defined by the
	     PHY[10] and expressed as readable characters."
    --     REFERENCE   
    --         "ANSI T1.413"
	::= { adslAturPhysEntry 3 }

    adslAturInvVersionNumber OBJECT-TYPE
	SYNTAX      DisplayString (SIZE(0..16))
	MAX-ACCESS  read-only
	STATUS      current
	DESCRIPTION 
	    "The vendor specific version number sent by this ATU
	     as part of the initialization messages.  It is a copy
	     of the binary version number field defined by the
	     PHY[10] and expressed as readable characters."
    --     REFERENCE   
    --         "ANSI T1.413"
	::= { adslAturPhysEntry 4 }

    adslAturCurrSnrMgn OBJECT-TYPE
	SYNTAX      INTEGER (-640..640)
	MAX-ACCESS  read-only
	STATUS      current
	DESCRIPTION 
	    "Noise Margin as seen by this ATU with respect to its
	     received signal in tenth dB."
	::= { adslAturPhysEntry 5 }

    adslAturCurrAtn OBJECT-TYPE
	SYNTAX      INTEGER (0..630)
	MAX-ACCESS  read-only
	STATUS      current
	DESCRIPTION 
	    "Measured difference between the total power transmitted by
	     the peer ATU and the total power received by this ATU
	     in tenth dB."
	::= { adslAturPhysEntry 6 }

    adslAturCurrStatus OBJECT-TYPE
	SYNTAX      INTEGER
			{	noDefect(1), 
				lossOfFraming(2), 
				lossOfSignal(3), 
				lossOfPower(4), 
				lossOfSignalQuality(5), 
				lossOfCellDelineation(6)
			 }
	MAX-ACCESS  read-only
	STATUS      current
	DESCRIPTION 
	    "Indicates mandatory state of the ATUR line, i.e. the state
	     of the line as seen by ATUR. 
	     This is a bit-map of possible conditions.  Due to the isolation
	     of the ATUR when line problems occur, many state
	     conditions like loss of power, loss of quality signal,
	     and initialization errors,  can not be determined.
	     While trouble shooting ATUR, also use object,
	     adslAtucCurrStatus.  The various bit positions are:
         
	     1      noDefect             There no defects on the line
         
	     2      lossOfFraming        ATUR failure due to not
				  receiving valid frame
         
	     3      lossOfSignal         ATUR failure due to not
				  receiving signal
         
	     4      lossOfPower          ATUR failure due to loss of
				  power
         
	     5      lossOfSignalQuality  Loss of Signal Quality is
				  declared when the Noise Margin
				  falls below the Minimum Noise
				  Margin, or the
				  bit-error-rate exceeds 10^-7.
         
	     6      lossOfCellDelineation      ATUR failure due
				  loss of Cell Delineation in interleaved
				  and non-interleaved mode.
         
	     This is intended to supplement ifOperStatus."
	::= { adslAturPhysEntry 7 }

    adslAturCurrOutputPwr OBJECT-TYPE
	SYNTAX      INTEGER (-310..310)
	MAX-ACCESS  read-only
	STATUS      current
	DESCRIPTION 
	    "Measured total output power transmitted by this ATU.
	     This is the measurement that was reported during
	     the last activation sequence in tenth dB."
	::= { adslAturPhysEntry 8 }

    adslAturCurrAttainableRate OBJECT-TYPE
	SYNTAX      INTEGER 
	MAX-ACCESS  read-only
	STATUS      current
	DESCRIPTION 
	    "Indicates the maximum mandatoryly attainable data rate
	     by the ATU.  This value will be equal or greater than
	     the mandatory line rate."
	::= { adslAturPhysEntry 9 }

    adslAturCurrPowercutback OBJECT-TYPE
	SYNTAX      INTEGER
	MAX-ACCESS  read-only
	STATUS      current
	DESCRIPTION
	    "Indicates the powercutback by the ATU in tenth dB."
	::= { adslAturPhysEntry 10 }
    
    adslAturCurrLinkStatus OBJECT-TYPE
	SYNTAX      INTEGER
			{	up(1), 
				initializing(2), 
				establishingLink(3), 
				noSignal(4), 
				disabled(5), 
				error(6)
			 }
	MAX-ACCESS  read-only
	STATUS      current
	DESCRIPTION
	    "Status of the DSL physical link."
	DEFVAL      { initializing }
	::= { adslAturPhysEntry 11 }
    
    adslAtucChanTable OBJECT-TYPE
	SYNTAX      SEQUENCE OF AdslAtucChanEntry
	MAX-ACCESS  not-accessible
	STATUS      current
	DESCRIPTION 
	    "This table provides one row for each ATUC channel.
	     ADSL channel interfaces are those ifEntries
	     where ifType is equal to adslInterleave(124)
	     or adslFast(125)."
	::= { adslMibObjects 4 }

    adslAtucChanEntry OBJECT-TYPE
	SYNTAX      AdslAtucChanEntry
	MAX-ACCESS  not-accessible
	STATUS      current
	DESCRIPTION 
	    "An entry in the adslAtucChanTable."
	INDEX       { adslAtucChanIfIndex }
	::= { adslAtucChanTable 1 }

    AdslAtucChanEntry ::= SEQUENCE {
	adslAtucChanIfIndex		    INTEGER,
	adslAtucChanInterleaveDelay     INTEGER,
	adslAtucChanCurrTxRate          INTEGER,
	adslAtucChanPrevTxRate          INTEGER,
	adslAtucChanInterleaveDepth     INTEGER
    }

    adslAtucChanIfIndex OBJECT-TYPE
	SYNTAX      INTEGER
	MAX-ACCESS  read-only
	STATUS      current
	DESCRIPTION 
	    "Specifies the ADSL interface index."
	::= { adslAtucChanEntry 1 }

    adslAtucChanInterleaveDelay OBJECT-TYPE
	SYNTAX      INTEGER
	MAX-ACCESS  read-only
	STATUS      current
	DESCRIPTION 
	    "Interleave Delay for this channel.
         
	     Interleave delay applies only to the
	     interleave channel and defines the mapping
	     (relative spacing) between subsequent input
	     bytes at the interleaver input and their placement
	     in the bit stream at the interleaver output.
	     Larger numbers provide greater separation between
	     consecutive input bytes in the output bit stream
	     allowing for improved impulse noise immunity at
	     the expense of payload latency.
         
	     In the case where the ifType is Fast(125), use
	     noSuchObject."
	::= { adslAtucChanEntry 2 }

    adslAtucChanCurrTxRate OBJECT-TYPE
	SYNTAX      INTEGER
	MAX-ACCESS  read-only
	STATUS      current
	DESCRIPTION 
	    "Actual transmit rate on this channel."
	::= { adslAtucChanEntry 3 }

    adslAtucChanPrevTxRate OBJECT-TYPE
	SYNTAX      INTEGER
	MAX-ACCESS  read-only
	STATUS      current
	DESCRIPTION 
	    "The rate at the time of the last
	     adslAtucRateChangeTrap event. It is also set at
	     initialization to prevent a trap being sent.
         
	     Rate changes less than adslAtucThresh(*)RateDown
	     or less than adslAtucThresh(*)RateUp will not
	     cause a trap or cause this object to change.
	     (*) == Fast or Interleave.
	     See AdslLineAlarmConfProfileEntry."
	::= { adslAtucChanEntry 4 }
    
    adslAtucChanInterleaveDepth OBJECT-TYPE
	SYNTAX        INTEGER
	MAX-ACCESS   read-only
	STATUS       current
	DESCRIPTION
	    "The interleaver depth."
	::= { adslAtucChanEntry 5 }
	    
    adslAturChanTable OBJECT-TYPE
	SYNTAX      SEQUENCE OF AdslAturChanEntry
	MAX-ACCESS  not-accessible
	STATUS      current
	DESCRIPTION 
	    "This table provides one row for each ATUR channel.
	     ADSL channel interfaces are those ifEntries
	     where ifType is equal to adslInterleave(124)
	     or adslFast(125)."
	::= { adslMibObjects 5 }

    adslAturChanEntry OBJECT-TYPE
	SYNTAX      AdslAturChanEntry
	MAX-ACCESS  not-accessible
	STATUS      current
	DESCRIPTION 
	    "An entry in the adslAturChanTable."
	INDEX       { adslAturChanIfIndex }
	::= { adslAturChanTable 1 }

    AdslAturChanEntry ::= SEQUENCE {
	adslAturChanIfIndex		    INTEGER,
	adslAturChanInterleaveDelay     INTEGER,
	adslAturChanCurrTxRate          INTEGER,
	adslAturChanPrevTxRate          INTEGER,
	adslAturChanCrcBlockLength      INTEGER,
	adslAturChanInterleaveDepth     INTEGER
    }

   adslAturChanIfIndex OBJECT-TYPE
	SYNTAX      INTEGER
	MAX-ACCESS  read-only
	STATUS      current
	DESCRIPTION 
	    "Specifies the ADSL interface index."
	::= { adslAturChanEntry 1 }


    adslAturChanInterleaveDelay OBJECT-TYPE
	SYNTAX      INTEGER
	MAX-ACCESS  read-only
	STATUS      current
	DESCRIPTION 
	    "Interleave Delay for this channel.
         
	     Interleave delay applies only to the
	     interleave channel and defines the mapping
	     (relative spacing) between subsequent input
	     bytes at the interleaver input and their placement
	     in the bit stream at the interleaver output.
	     Larger numbers provide greater separation between
	     consecutive input bytes in the output bit stream
	     allowing for improved impulse noise immunity at
	     the expense of payload latency.
         
	     In the case where the ifType is Fast(125), use
	     noSuchObject."
	::= { adslAturChanEntry 2 }

    adslAturChanCurrTxRate OBJECT-TYPE
	SYNTAX      INTEGER
	MAX-ACCESS  read-only
	STATUS      current
	DESCRIPTION 
	    "Actual transmit rate on this channel."
	::= { adslAturChanEntry 3 }

    adslAturChanPrevTxRate OBJECT-TYPE
	SYNTAX      INTEGER
	MAX-ACCESS  read-only
	STATUS      current
	DESCRIPTION 
	    "The rate at the time of the last
	     adslAturRateChangeTrap event. It is also set at
	     initialization to prevent a trap being sent.
	     Rate changes less than adslAturThresh(*)RateDown
	     or less than adslAturThresh(*)RateUp will not
	     cause a trap or cause this object to change.
	     (*) == Fast or Interleave.
	     See AdslLineAlarmConfProfileEntry."
	::= { adslAturChanEntry 4 }

    adslAturChanCrcBlockLength OBJECT-TYPE
	SYNTAX      INTEGER
	MAX-ACCESS  read-only
	STATUS      current
	DESCRIPTION 
	    "Indicates the length of the channel data-block
	     on which the CRC operates.  Refer to Line Code
	     Specific MIBs, [11] and [12] for more
	     information."
	::= { adslAturChanEntry 5 }

    adslAturChanInterleaveDepth OBJECT-TYPE
	SYNTAX       INTEGER
	MAX-ACCESS   read-only
	STATUS       current
	DESCRIPTION
	    "The interleaver depth."
	::= { adslAturChanEntry 6 }

    
    adslAturPerfDataTable OBJECT-TYPE
	SYNTAX      SEQUENCE OF AdslAturPerfDataEntry
	MAX-ACCESS  not-accessible
	STATUS      current
	DESCRIPTION 
	    "This table provides one row for each ATUR.
	     ADSL physical interfaces are
	     those ifEntries where ifType is equal to adsl(94)."
	::= { adslMibObjects 7 }

    adslAturPerfDataEntry OBJECT-TYPE
	SYNTAX      AdslAturPerfDataEntry
	MAX-ACCESS  not-accessible
	STATUS      current
	DESCRIPTION 
	    "An entry in adslAturPerfDataTable."
	INDEX       { adslAturPerfIfIndex }
	::= { adslAturPerfDataTable 1 }

    AdslAturPerfDataEntry ::= SEQUENCE {
	adslAturPerfIfIndex		    INTEGER,
	adslAturPerfLofs                    INTEGER,
	adslAturPerfLoss                    INTEGER,
	adslAturPerfLprs                    INTEGER,
	adslAturPerfESs                     INTEGER,
	adslAturPerfValidIntervals          INTEGER,
	adslAturPerfInvalidIntervals        INTEGER,
	adslAturPerfCurr15MinTimeElapsed    INTEGER,
	adslAturPerfCurr15MinLofs           INTEGER,
	adslAturPerfCurr15MinLoss           INTEGER,
	adslAturPerfCurr15MinLprs           INTEGER,
	adslAturPerfCurr15MinESs            INTEGER,
	adslAturPerfCurr1DayTimeElapsed     INTEGER,
	adslAturPerfCurr1DayLofs            INTEGER,
	adslAturPerfCurr1DayLoss            INTEGER,
	adslAturPerfCurr1DayLprs            INTEGER,
	adslAturPerfCurr1DayESs             INTEGER,
	adslAturPerfPrev1DayMoniSecs        INTEGER,
	adslAturPerfPrev1DayLofs            INTEGER,
	adslAturPerfPrev1DayLoss            INTEGER,
	adslAturPerfPrev1DayLprs            INTEGER,
	adslAturPerfPrev1DayESs             INTEGER
    }

    adslAturPerfIfIndex OBJECT-TYPE
	SYNTAX      INTEGER
	MAX-ACCESS  read-only
	STATUS      current
	DESCRIPTION 
	    "Specifies the ADSL interface index."
	::= { adslAturPerfDataEntry 1 }

    adslAturPerfLofs OBJECT-TYPE
	SYNTAX      INTEGER
	MAX-ACCESS  read-only
	STATUS      current
	DESCRIPTION 
	    "Count of the number of Loss of Framing failures since
	     agent reset."
	::= { adslAturPerfDataEntry 2 }

    adslAturPerfLoss OBJECT-TYPE
	SYNTAX      INTEGER
	MAX-ACCESS  read-only
	STATUS      current
	DESCRIPTION 
	    "Count of the number of Loss of Signal failures since
	     agent reset."
	::= { adslAturPerfDataEntry 3 }

    adslAturPerfLprs OBJECT-TYPE
	SYNTAX      INTEGER
	MAX-ACCESS  read-only
	STATUS      current
	DESCRIPTION 
	    "Count of the number of Loss of Power failures since
	     agent reset."
	::= { adslAturPerfDataEntry 4 }

    adslAturPerfESs OBJECT-TYPE
	SYNTAX      INTEGER
	MAX-ACCESS  read-only
	STATUS      current
	DESCRIPTION 
	    "Count of the number of Errored Seconds since agent
	     reset.  The errored second parameter is a count of
	     one-second intervals containing one or more crc
	     anomalies, or one or more los or sef defects."
	::= { adslAturPerfDataEntry 5 }

    adslAturPerfValidIntervals OBJECT-TYPE
	SYNTAX      INTEGER (0..96)
	MAX-ACCESS  read-only
	STATUS      current
	DESCRIPTION 
	    "The number of previous 15-minute intervals in the
	     interval table for which data was collected.  Given
	     that <n> is the maximum # of intervals supported.
	     The value will be <n> unless the measurement was
	     (re-)started within the last (<n>*15) minutes, in which
	     case the value will be the number of complete 15
	     minute intervals for which the agent has at least
	     some data. In certain cases (e.g., in the case
	     where the agent is a proxy) it is possible that some
	     intervals are unavailable.  In this case, this
	     interval is the maximum interval number for
	     which data is available."
	::= { adslAturPerfDataEntry 6 }

    adslAturPerfInvalidIntervals OBJECT-TYPE
	SYNTAX      INTEGER (0..96)
	MAX-ACCESS  read-only
	STATUS      current
	DESCRIPTION 
	    "The number of intervals in the range from
	     0 to the value of adslAturPerfValidIntervals
	     for which no data is available. This object
	     will typically be zero except in cases where
	     the data for some intervals are not available
	     (e.g., in proxy situations)."
	::= { adslAturPerfDataEntry 7 }

    adslAturPerfCurr15MinTimeElapsed OBJECT-TYPE
	SYNTAX      INTEGER (0..899)
	MAX-ACCESS  read-only
	STATUS      current
	DESCRIPTION 
	    "Total elapsed seconds in this interval."
	::= { adslAturPerfDataEntry 8 }

    adslAturPerfCurr15MinLofs OBJECT-TYPE
	SYNTAX      INTEGER
	MAX-ACCESS  read-only
	STATUS      current
	DESCRIPTION 
	    "Count of seconds in the mandatory 15 minute interval
	     when there was Loss of Framing."
	::= { adslAturPerfDataEntry 9 }

    adslAturPerfCurr15MinLoss OBJECT-TYPE
	SYNTAX      INTEGER
	MAX-ACCESS  read-only
	STATUS      current
	DESCRIPTION 
	    "Count of seconds in the mandatory 15 minute interval
	     when there was Loss of Signal."
	::= { adslAturPerfDataEntry 10 }

    adslAturPerfCurr15MinLprs OBJECT-TYPE
	SYNTAX      INTEGER
	MAX-ACCESS  read-only
	STATUS      current
	DESCRIPTION 
	    "Count of seconds in the mandatory 15 minute interval
	     when there was Loss of Power."
	::= { adslAturPerfDataEntry 11 }

    adslAturPerfCurr15MinESs OBJECT-TYPE
	SYNTAX      INTEGER
	MAX-ACCESS  read-only
	STATUS      current
	DESCRIPTION 
	    "Count of Errored Seconds in the mandatory 15 minute
	     interval.  The errored second parameter is a count of
	     one-second intervals containing one or more crc
	     anomalies, or one or more los or sef defects."
	::= { adslAturPerfDataEntry 12 }

    adslAturPerfCurr1DayTimeElapsed OBJECT-TYPE
	SYNTAX      INTEGER (0..86399)
	MAX-ACCESS  read-only
	STATUS      current
	DESCRIPTION 
	    "Number of seconds that have elapsed since the
	     beginning of the mandatory 1-day interval."
	::= { adslAturPerfDataEntry 13 }

    adslAturPerfCurr1DayLofs OBJECT-TYPE
	SYNTAX      INTEGER
	MAX-ACCESS  read-only
	STATUS      current
	DESCRIPTION 
	    "Count of the number of seconds when there was Loss
	     of Framing during the mandatory day as measured by
	     adslAturPerfCurr1DayTimeElapsed."
	::= { adslAturPerfDataEntry 14 }

    adslAturPerfCurr1DayLoss OBJECT-TYPE
	SYNTAX      INTEGER
	MAX-ACCESS  read-only
	STATUS      current
	DESCRIPTION 
	    "Count of the number of seconds when there was Loss
	     of Signal during the mandatory day as measured by
	     adslAturPerfCurr1DayTimeElapsed."
	::= { adslAturPerfDataEntry 15 }

    adslAturPerfCurr1DayLprs OBJECT-TYPE
	SYNTAX      INTEGER
	MAX-ACCESS  read-only
	STATUS      current
	DESCRIPTION 
	    "Count of the number of seconds when there was Loss
	     of Power during the mandatory day as measured by
	     adslAturPerfCurr1DayTimeElapsed."
	::= { adslAturPerfDataEntry 16 }

    adslAturPerfCurr1DayESs OBJECT-TYPE
	SYNTAX      INTEGER
	MAX-ACCESS  read-only
	STATUS      current
	DESCRIPTION 
	    "Count of Errored Seconds during the mandatory day as
	     measured by adslAturPerfCurr1DayTimeElapsed.
	     The errored second parameter is a count of
	     one-second intervals containing one or more crc
	     anomalies, or one or more los or sef defects."
	::= { adslAturPerfDataEntry 17 }

    adslAturPerfPrev1DayMoniSecs OBJECT-TYPE
	SYNTAX      INTEGER (0..86400)
	MAX-ACCESS  read-only
	STATUS      current
	DESCRIPTION 
	    "The amount of time in the previous 1-day interval
	     over which the performance monitoring information
	     is actually counted. This value will be the same as
	     the interval duration except in a situation where
	     performance monitoring data could not be collected
	     for any reason."
	::= { adslAturPerfDataEntry 18 }

    adslAturPerfPrev1DayLofs OBJECT-TYPE
	SYNTAX      INTEGER
	MAX-ACCESS  read-only
	STATUS      current
	DESCRIPTION 
	    "Count of seconds in the interval when there was
	     Loss of Framing within the most recent previous
	     1-day period."
	::= { adslAturPerfDataEntry 19 }

    adslAturPerfPrev1DayLoss OBJECT-TYPE
	SYNTAX      INTEGER
	MAX-ACCESS  read-only
	STATUS      current
	DESCRIPTION 
	    "Count of seconds in the interval when there was
	     Loss of Signal within the most recent previous
	     1-day period."
	::= { adslAturPerfDataEntry 20 }

    adslAturPerfPrev1DayLprs OBJECT-TYPE
	SYNTAX      INTEGER
	MAX-ACCESS  read-only
	STATUS      current
	DESCRIPTION 
	    "Count of seconds in the interval when there was
	     Loss of Power within the most recent previous
	     1-day period."
	::= { adslAturPerfDataEntry 21 }

    adslAturPerfPrev1DayESs OBJECT-TYPE
	SYNTAX      INTEGER
	MAX-ACCESS  read-only
	STATUS      current
	DESCRIPTION 
	    "Count of Errored Seconds within the most recent
	     previous 1-day period. The errored second parameter is
	     a count of one-second intervals containing one or more
	     crc anomalies, or one or more los or sef defects."
	::= { adslAturPerfDataEntry 22 }


    adslAturChanPerfDataTable OBJECT-TYPE
	SYNTAX      SEQUENCE OF AdslAturChanPerfDataEntry
	MAX-ACCESS  not-accessible
	STATUS      current
	DESCRIPTION 
	    "This table provides one row for each ATUR channel.
	     ADSL channel interfaces are those ifEntries
	     where ifType is equal to adslInterleave(124)
	     or adslFast(125)."
	::= { adslMibObjects 11 }

    adslAturChanPerfDataEntry OBJECT-TYPE
	SYNTAX      AdslAturChanPerfDataEntry
	MAX-ACCESS  not-accessible
	STATUS      current
	DESCRIPTION 
	    "An entry in adslAturChanPerfDataTable."
	INDEX       { adslAturChanPerfIfIndex }
	::= { adslAturChanPerfDataTable 1 }

    AdslAturChanPerfDataEntry ::= SEQUENCE {
	adslAturChanPerfIfIndex				INTEGER,
	adslAturChanReceivedBlks                    INTEGER,
	adslAturChanTransmittedBlks                 INTEGER,
	adslAturChanCorrectedBlks                   INTEGER,
	adslAturChanUncorrectBlks                   INTEGER,
	adslAturChanPerfValidIntervals              INTEGER,
	adslAturChanPerfInvalidIntervals            INTEGER,
	adslAturChanPerfCurr15MinTimeElapsed        INTEGER,
	adslAturChanPerfCurr15MinReceivedBlks       INTEGER,
	adslAturChanPerfCurr15MinTransmittedBlks    INTEGER,
	adslAturChanPerfCurr15MinCorrectedBlks      INTEGER,
	adslAturChanPerfCurr15MinUncorrectBlks      INTEGER,
	adslAturChanPerfCurr1DayTimeElapsed         INTEGER,
	adslAturChanPerfCurr1DayReceivedBlks        INTEGER,
	adslAturChanPerfCurr1DayTransmittedBlks     INTEGER,
	adslAturChanPerfCurr1DayCorrectedBlks       INTEGER,
	adslAturChanPerfCurr1DayUncorrectBlks       INTEGER,
	adslAturChanPerfPrev1DayMoniSecs            INTEGER,
	adslAturChanPerfPrev1DayReceivedBlks        INTEGER,
	adslAturChanPerfPrev1DayTransmittedBlks     INTEGER,
	adslAturChanPerfPrev1DayCorrectedBlks       INTEGER,
	adslAturChanPerfPrev1DayUncorrectBlks       INTEGER,
	adslAturChanPerfCurrShowtimeCorrectedBlks   INTEGER,
	adslAturChanPerfCurrShowtimeUncorrectBlks   INTEGER,
	adslAturChanReceivedBytes                   INTEGER,
	adslAturChanTransmittedBytes                INTEGER
    }

    adslAturChanPerfIfIndex OBJECT-TYPE
	SYNTAX      INTEGER
	MAX-ACCESS  read-only
	STATUS      current
	DESCRIPTION 
	    "Specifies the ADSL interface index."
	::= { adslAturChanPerfDataEntry 1 }

    adslAturChanReceivedBlks OBJECT-TYPE
	SYNTAX      INTEGER
	MAX-ACCESS  read-only
	STATUS      current
	DESCRIPTION 
	    "Count of all encoded blocks received on this channel
	     since agent reset."
	::= { adslAturChanPerfDataEntry 2 }

    adslAturChanTransmittedBlks OBJECT-TYPE
	SYNTAX      INTEGER
	MAX-ACCESS  read-only
	STATUS      current
	DESCRIPTION 
	    "Count of all encoded blocks transmitted on this
	     channel since agent reset."
	::= { adslAturChanPerfDataEntry 3 }

    adslAturChanCorrectedBlks OBJECT-TYPE
	SYNTAX      INTEGER
	MAX-ACCESS  read-only
	STATUS      current
	DESCRIPTION 
	    "Count of all blocks received with errors that were
	     corrected since agent reset.  These blocks are passed
	     on as good data."
	::= { adslAturChanPerfDataEntry 4 }

    adslAturChanUncorrectBlks OBJECT-TYPE
	SYNTAX      INTEGER
	MAX-ACCESS  read-only
	STATUS      current
	DESCRIPTION 
	    "Count of all blocks received with uncorrectable
	     errors since agent reset."
	::= { adslAturChanPerfDataEntry 5 }

    adslAturChanPerfValidIntervals OBJECT-TYPE
	SYNTAX      INTEGER (0..96)
	MAX-ACCESS  read-only
	STATUS      current
	DESCRIPTION 
	    "The number of previous 15-minute intervals in the
	     interval table for which data was collected.  Given
	     that <n> is the maximum # of intervals supported.
	     The value will be <n> unless the measurement was
	     (re-)started within the last (<n>*15) minutes, in which
	     case the value will be the number of complete 15
	     minute intervals for which the agent has at least
	     some data. In certain cases (e.g., in the case
	     where the agent is a proxy) it is possible that some
	     intervals are unavailable.  In this case, this
	     interval is the maximum interval number for
	     which data is available."
	::= { adslAturChanPerfDataEntry 6 }

    adslAturChanPerfInvalidIntervals OBJECT-TYPE
	SYNTAX      INTEGER (0..96)
	MAX-ACCESS  read-only
	STATUS      current
	DESCRIPTION 
	    "The number of intervals in the range from
	     0 to the value of adslAturChanPerfValidIntervals
	     for which no data is available. This object
	     will typically be zero except in cases where
	     the data for some intervals are not available
	     (e.g., in proxy situations)."
	::= { adslAturChanPerfDataEntry 7 }

    adslAturChanPerfCurr15MinTimeElapsed OBJECT-TYPE
	SYNTAX      INTEGER (0..899)
	MAX-ACCESS  read-only
	STATUS      current
	DESCRIPTION 
	    "Total elapsed seconds in this interval.
	     A full interval is 900 seconds."
	::= { adslAturChanPerfDataEntry 8 }

    adslAturChanPerfCurr15MinReceivedBlks OBJECT-TYPE
	SYNTAX      INTEGER
	MAX-ACCESS  read-only
	STATUS      current
	DESCRIPTION 
	    "Count of all encoded blocks received on this
	     channel within the mandatory 15 minute interval."
	::= { adslAturChanPerfDataEntry 9 }

    adslAturChanPerfCurr15MinTransmittedBlks OBJECT-TYPE
	SYNTAX      INTEGER
	MAX-ACCESS  read-only
	STATUS      current
	DESCRIPTION 
	    "Count of all encoded blocks transmitted on this
	     channel within the mandatory 15 minute interval."
	::= { adslAturChanPerfDataEntry 10 }

    adslAturChanPerfCurr15MinCorrectedBlks OBJECT-TYPE
	SYNTAX      INTEGER
	MAX-ACCESS  read-only
	STATUS      current
	DESCRIPTION 
	    "Count of all blocks received with errors that were
	     corrected on this channel within the mandatory 15 minute
	     interval."
	::= { adslAturChanPerfDataEntry 11 }

    adslAturChanPerfCurr15MinUncorrectBlks OBJECT-TYPE
	SYNTAX      INTEGER
	MAX-ACCESS  read-only
	STATUS      current
	DESCRIPTION 
	    "Count of all blocks received with uncorrectable
	     errors on this channel within the mandatory 15 minute
	     interval."
	::= { adslAturChanPerfDataEntry 12 }

    adslAturChanPerfCurr1DayTimeElapsed OBJECT-TYPE
	SYNTAX      INTEGER (0..86399)
	MAX-ACCESS  read-only
	STATUS      current
	DESCRIPTION 
	    "Number of seconds that have elapsed since the
	     beginning of the mandatory 1-day interval."
	::= { adslAturChanPerfDataEntry 13 }

    adslAturChanPerfCurr1DayReceivedBlks OBJECT-TYPE
	SYNTAX      INTEGER
	MAX-ACCESS  read-only
	STATUS      current
	DESCRIPTION 
	    "Count of all encoded blocks received on this
	     channel during the mandatory day as measured by
	     adslAturChanPerfCurr1DayTimeElapsed."
	::= { adslAturChanPerfDataEntry 14 }

    adslAturChanPerfCurr1DayTransmittedBlks OBJECT-TYPE
	SYNTAX      INTEGER
	MAX-ACCESS  read-only
	STATUS      current
	DESCRIPTION 
	    "Count of all encoded blocks transmitted on this
	     channel during the mandatory day as measured by
	     adslAturChanPerfCurr1DayTimeElapsed."
	::= { adslAturChanPerfDataEntry 15 }

    adslAturChanPerfCurr1DayCorrectedBlks OBJECT-TYPE
	SYNTAX      INTEGER
	MAX-ACCESS  read-only
	STATUS      current
	DESCRIPTION 
	    "Count of all blocks received with errors that were
	     corrected on this channel during the mandatory day as
	     measured by adslAturChanPerfCurr1DayTimeElapsed."
	::= { adslAturChanPerfDataEntry 16 }

    adslAturChanPerfCurr1DayUncorrectBlks OBJECT-TYPE
	SYNTAX      INTEGER
	MAX-ACCESS  read-only
	STATUS      current
	DESCRIPTION 
	    "Count of all blocks received with uncorrectable
	     errors on this channel during the mandatory day as
	     measured by adslAturChanPerfCurr1DayTimeElapsed."
	::= { adslAturChanPerfDataEntry 17 }

    adslAturChanPerfPrev1DayMoniSecs OBJECT-TYPE
	SYNTAX      INTEGER (0..86400)
	MAX-ACCESS  read-only
	STATUS      current
	DESCRIPTION 
	    "The amount of time in the previous 1-day interval
	     over which the performance monitoring information
	     is actually counted. This value will be the same as
	     the interval duration except in a situation where
	     performance monitoring data could not be collected
	     for any reason."
	::= { adslAturChanPerfDataEntry 18 }

    adslAturChanPerfPrev1DayReceivedBlks OBJECT-TYPE
	SYNTAX      INTEGER
	MAX-ACCESS  read-only
	STATUS      current
	DESCRIPTION 
	    "Count of all encoded blocks received on this
	     channel within the most recent previous 1-day
	     period."
	::= { adslAturChanPerfDataEntry 19 }

    adslAturChanPerfPrev1DayTransmittedBlks OBJECT-TYPE
	SYNTAX      INTEGER
	MAX-ACCESS  read-only
	STATUS      current
	DESCRIPTION 
	    "Count of all encoded blocks transmitted on this
	     channel within the most recent previous 1-day
	     period."
	::= { adslAturChanPerfDataEntry 20 }

    adslAturChanPerfPrev1DayCorrectedBlks OBJECT-TYPE
	SYNTAX      INTEGER
	MAX-ACCESS  read-only
	STATUS      current
	DESCRIPTION 
	    "Count of all blocks received with errors that were
	     corrected on this channel within the most recent
	     previous 1-day period."
	::= { adslAturChanPerfDataEntry 21 }

    adslAturChanPerfPrev1DayUncorrectBlks OBJECT-TYPE
	SYNTAX      INTEGER
	MAX-ACCESS  read-only
	STATUS      current
	DESCRIPTION 
	    "Count of all blocks received with uncorrectable
	     errors on this channel within the most recent previous
	     1-day period."
	::= { adslAturChanPerfDataEntry 22 }

    adslAturChanPerfCurrShowtimeCorrectedBlks OBJECT-TYPE
	SYNTAX      INTEGER
	MAX-ACCESS  read-only
	STATUS      current
	DESCRIPTION 
	    "Count of all blocks received with errors that were
	     corrected on this channel since the most recent
	     DSL Showtime."
	::= { adslAturChanPerfDataEntry 23 }

    adslAturChanPerfCurrShowtimeUncorrectBlks OBJECT-TYPE
	SYNTAX      INTEGER
	MAX-ACCESS  read-only
	STATUS      current
	DESCRIPTION 
	    "Count of all blocks received with uncorrectable
	     errors on this channel since the most recent
	     DSL Showtime."
	::= { adslAturChanPerfDataEntry 24 }

    adslAturChanReceivedBytes OBJECT-TYPE
	SYNTAX      INTEGER
	MAX-ACCESS  read-only
	STATUS      current
	DESCRIPTION 
	    "Count of Bytes received on this channel."
	::= { adslAturChanPerfDataEntry 25 }

    adslAturChanTransmittedBytes OBJECT-TYPE
	SYNTAX      INTEGER
	MAX-ACCESS  read-only
	STATUS      current
	DESCRIPTION 
	    "Count of Bytes transmitted on this channel."
	::= { adslAturChanPerfDataEntry 26 }


---
--- ADSL ATUC Performance Data Table
---
    
    adslAtucPerfDataTable OBJECT-TYPE
	SYNTAX      SEQUENCE OF AdslAtucPerfDataEntry
	MAX-ACCESS  not-accessible
	STATUS      current
	DESCRIPTION 
	    "This table provides one row for each ATUC.
	     ADSL physical interfaces are
	     those ifEntries where ifType is equal to adsl(94)."
	::= { adslMibObjects 12 }

    adslAtucPerfDataEntry OBJECT-TYPE
	SYNTAX      AdslAtucPerfDataEntry
	MAX-ACCESS  not-accessible
	STATUS      current
	DESCRIPTION 
	    "An entry in adslAtucPerfDataTable."
	INDEX       { adslAtucPerfIfIndex }
	::= { adslAtucPerfDataTable 1 }

    AdslAtucPerfDataEntry ::= SEQUENCE {
	adslAtucPerfIfIndex		    INTEGER,
	adslAtucPerfLofs                    INTEGER,
	adslAtucPerfLoss                    INTEGER,
	adslAtucPerfLprs                    INTEGER,
	adslAtucPerfESs                     INTEGER,
	adslAtucPerfValidIntervals          INTEGER,
	adslAtucPerfInvalidIntervals        INTEGER,
	adslAtucPerfCurr15MinTimeElapsed    INTEGER,
	adslAtucPerfCurr15MinLofs           INTEGER,
	adslAtucPerfCurr15MinLoss           INTEGER,
	adslAtucPerfCurr15MinLprs           INTEGER,
	adslAtucPerfCurr15MinESs            INTEGER,
	adslAtucPerfCurr1DayTimeElapsed     INTEGER,
	adslAtucPerfCurr1DayLofs            INTEGER,
	adslAtucPerfCurr1DayLoss            INTEGER,
	adslAtucPerfCurr1DayLprs            INTEGER,
	adslAtucPerfCurr1DayESs             INTEGER,
	adslAtucPerfPrev1DayMoniSecs        INTEGER,
	adslAtucPerfPrev1DayLofs            INTEGER,
	adslAtucPerfPrev1DayLoss            INTEGER,
	adslAtucPerfPrev1DayLprs            INTEGER,
	adslAtucPerfPrev1DayESs             INTEGER
    }

    adslAtucPerfIfIndex OBJECT-TYPE
	SYNTAX      INTEGER
	MAX-ACCESS  read-only
	STATUS      current
	DESCRIPTION 
	    "Specifies the ADSL interface index."
	::= { adslAtucPerfDataEntry 1 }

    adslAtucPerfLofs OBJECT-TYPE
	SYNTAX      INTEGER
	MAX-ACCESS  read-only
	STATUS      current
	DESCRIPTION 
	    "Count of the number of Loss of Framing failures since
	     agent reset."
	::= { adslAtucPerfDataEntry 2 }

    adslAtucPerfLoss OBJECT-TYPE
	SYNTAX      INTEGER
	MAX-ACCESS  read-only
	STATUS      current
	DESCRIPTION 
	    "Count of the number of Loss of Signal failures since
	     agent reset."
	::= { adslAtucPerfDataEntry 3 }

    adslAtucPerfLprs OBJECT-TYPE
	SYNTAX      INTEGER
	MAX-ACCESS  read-only
	STATUS      current
	DESCRIPTION 
	    "Count of the number of Loss of Power failures since
	     agent reset."
	::= { adslAtucPerfDataEntry 4 }

    adslAtucPerfESs OBJECT-TYPE
	SYNTAX      INTEGER
	MAX-ACCESS  read-only
	STATUS      current
	DESCRIPTION 
	    "Count of the number of Errored Seconds since agent
	     reset.  The errored second parameter is a count of
	     one-second intervals containing one or more crc
	     anomalies, or one or more los or sef defects."
	::= { adslAtucPerfDataEntry 5 }

    adslAtucPerfValidIntervals OBJECT-TYPE
	SYNTAX      INTEGER (0..96)
	MAX-ACCESS  read-only
	STATUS      current
	DESCRIPTION 
	    "The number of previous 15-minute intervals in the
	     interval table for which data was collected.  Given
	     that <n> is the maximum # of intervals supported.
	     The value will be <n> unless the measurement was
	     (re-)started within the last (<n>*15) minutes, in which
	     case the value will be the number of complete 15
	     minute intervals for which the agent has at least
	     some data. In certain cases (e.g., in the case
	     where the agent is a proxy) it is possible that some
	     intervals are unavailable.  In this case, this
	     interval is the maximum interval number for
	     which data is available."
	::= { adslAtucPerfDataEntry 6 }

    adslAtucPerfInvalidIntervals OBJECT-TYPE
	SYNTAX      INTEGER (0..96)
	MAX-ACCESS  read-only
	STATUS      current
	DESCRIPTION 
	    "The number of intervals in the range from
	     0 to the value of adslAtucPerfValidIntervals
	     for which no data is available. This object
	     will typically be zero except in cases where
	     the data for some intervals are not available
	     (e.g., in proxy situations)."
	::= { adslAtucPerfDataEntry 7 }

    adslAtucPerfCurr15MinTimeElapsed OBJECT-TYPE
	SYNTAX      INTEGER (0..899)
	MAX-ACCESS  read-only
	STATUS      current
	DESCRIPTION 
	    "Total elapsed seconds in this interval."
	::= { adslAtucPerfDataEntry 8 }

    adslAtucPerfCurr15MinLofs OBJECT-TYPE
	SYNTAX      INTEGER
	MAX-ACCESS  read-only
	STATUS      current
	DESCRIPTION 
	    "Count of seconds in the mandatory 15 minute interval
	     when there was Loss of Framing."
	::= { adslAtucPerfDataEntry 9 }

    adslAtucPerfCurr15MinLoss OBJECT-TYPE
	SYNTAX      INTEGER
	MAX-ACCESS  read-only
	STATUS      current
	DESCRIPTION 
	    "Count of seconds in the mandatory 15 minute interval
	     when there was Loss of Signal."
	::= { adslAtucPerfDataEntry 10 }

    adslAtucPerfCurr15MinLprs OBJECT-TYPE
	SYNTAX      INTEGER
	MAX-ACCESS  read-only
	STATUS      current
	DESCRIPTION 
	    "Count of seconds in the mandatory 15 minute interval
	     when there was Loss of Power."
	::= { adslAtucPerfDataEntry 11 }

    adslAtucPerfCurr15MinESs OBJECT-TYPE
	SYNTAX      INTEGER
	MAX-ACCESS  read-only
	STATUS      current
	DESCRIPTION 
	    "Count of Errored Seconds in the mandatory 15 minute
	     interval.  The errored second parameter is a count of
	     one-second intervals containing one or more crc
	     anomalies, or one or more los or sef defects."
	::= { adslAtucPerfDataEntry 12 }

    adslAtucPerfCurr1DayTimeElapsed OBJECT-TYPE
	SYNTAX      INTEGER (0..86399)
	MAX-ACCESS  read-only
	STATUS      current
	DESCRIPTION 
	    "Number of seconds that have elapsed since the
	     beginning of the mandatory 1-day interval."
	::= { adslAtucPerfDataEntry 13 }

    adslAtucPerfCurr1DayLofs OBJECT-TYPE
	SYNTAX      INTEGER
	MAX-ACCESS  read-only
	STATUS      current
	DESCRIPTION 
	    "Count of the number of seconds when there was Loss
	     of Framing during the mandatory day as measured by
	     adslAtucPerfCurr1DayTimeElapsed."
	::= { adslAtucPerfDataEntry 14 }

    adslAtucPerfCurr1DayLoss OBJECT-TYPE
	SYNTAX      INTEGER
	MAX-ACCESS  read-only
	STATUS      current
	DESCRIPTION 
	    "Count of the number of seconds when there was Loss
	     of Signal during the mandatory day as measured by
	     adslAtucPerfCurr1DayTimeElapsed."
	::= { adslAtucPerfDataEntry 15 }

    adslAtucPerfCurr1DayLprs OBJECT-TYPE
	SYNTAX      INTEGER
	MAX-ACCESS  read-only
	STATUS      current
	DESCRIPTION 
	    "Count of the number of seconds when there was Loss
	     of Power during the mandatory day as measured by
	     adslAtucPerfCurr1DayTimeElapsed."
	::= { adslAtucPerfDataEntry 16 }

    adslAtucPerfCurr1DayESs OBJECT-TYPE
	SYNTAX      INTEGER
	MAX-ACCESS  read-only
	STATUS      current
	DESCRIPTION 
	    "Count of Errored Seconds during the mandatory day as
	     measured by adslAtucPerfCurr1DayTimeElapsed.
	     The errored second parameter is a count of
	     one-second intervals containing one or more crc
	     anomalies, or one or more los or sef defects."
	::= { adslAtucPerfDataEntry 17 }

    adslAtucPerfPrev1DayMoniSecs OBJECT-TYPE
	SYNTAX      INTEGER (0..86400)
	MAX-ACCESS  read-only
	STATUS      current
	DESCRIPTION 
	    "The amount of time in the previous 1-day interval
	     over which the performance monitoring information
	     is actually counted. This value will be the same as
	     the interval duration except in a situation where
	     performance monitoring data could not be collected
	     for any reason."
	::= { adslAtucPerfDataEntry 18 }

    adslAtucPerfPrev1DayLofs OBJECT-TYPE
	SYNTAX      INTEGER
	MAX-ACCESS  read-only
	STATUS      current
	DESCRIPTION 
	    "Count of seconds in the interval when there was
	     Loss of Framing within the most recent previous
	     1-day period."
	::= { adslAtucPerfDataEntry 19 }

    adslAtucPerfPrev1DayLoss OBJECT-TYPE
	SYNTAX      INTEGER
	MAX-ACCESS  read-only
	STATUS      current
	DESCRIPTION 
	    "Count of seconds in the interval when there was
	     Loss of Signal within the most recent previous
	     1-day period."
	::= { adslAtucPerfDataEntry 20 }

    adslAtucPerfPrev1DayLprs OBJECT-TYPE
	SYNTAX      INTEGER
	MAX-ACCESS  read-only
	STATUS      current
	DESCRIPTION 
	    "Count of seconds in the interval when there was
	     Loss of Power within the most recent previous
	     1-day period."
	::= { adslAtucPerfDataEntry 21 }

    adslAtucPerfPrev1DayESs OBJECT-TYPE
	SYNTAX      INTEGER
	MAX-ACCESS  read-only
	STATUS      current
	DESCRIPTION 
	    "Count of Errored Seconds within the most recent
	     previous 1-day period. The errored second parameter is
	     a count of one-second intervals containing one or more
	     crc anomalies, or one or more los or sef defects."
	::= { adslAtucPerfDataEntry 22 }


---
--- ADSL ATUC Channel Performance Data Table
---
    
    adslAtucChanPerfDataTable OBJECT-TYPE
	SYNTAX      SEQUENCE OF AdslAtucChanPerfDataEntry
	MAX-ACCESS  not-accessible
	STATUS      current
	DESCRIPTION 
	    "This table provides one row for each ATUR channel.
	     ADSL channel interfaces are those ifEntries
	     where ifType is equal to adslInterleave(124)
	     or adslFast(125)."
	::= { adslMibObjects 13 }

    adslAtucChanPerfDataEntry OBJECT-TYPE
	SYNTAX      AdslAtucChanPerfDataEntry
	MAX-ACCESS  not-accessible
	STATUS      current
	DESCRIPTION 
	    "An entry in adslAtucChanPerfDataTable."
	INDEX       { adslAtucChanPerfIfIndex }
	::= { adslAtucChanPerfDataTable 1 }

    AdslAtucChanPerfDataEntry ::= SEQUENCE {
	adslAtucChanPerfIfIndex                     INTEGER,
	adslAtucChanReceivedBlks                    INTEGER,
	adslAtucChanTransmittedBlks                 INTEGER,
	adslAtucChanCorrectedBlks                   INTEGER,
	adslAtucChanUncorrectBlks                   INTEGER,
	adslAtucChanPerfValidIntervals              INTEGER,
	adslAtucChanPerfInvalidIntervals            INTEGER,
	adslAtucChanPerfCurr15MinTimeElapsed        INTEGER,
	adslAtucChanPerfCurr15MinReceivedBlks       INTEGER,
	adslAtucChanPerfCurr15MinTransmittedBlks    INTEGER,
	adslAtucChanPerfCurr15MinCorrectedBlks      INTEGER,
	adslAtucChanPerfCurr15MinUncorrectBlks      INTEGER,
	adslAtucChanPerfCurr1DayTimeElapsed         INTEGER,
	adslAtucChanPerfCurr1DayReceivedBlks        INTEGER,
	adslAtucChanPerfCurr1DayTransmittedBlks     INTEGER,
	adslAtucChanPerfCurr1DayCorrectedBlks       INTEGER,
	adslAtucChanPerfCurr1DayUncorrectBlks       INTEGER,
	adslAtucChanPerfPrev1DayMoniSecs            INTEGER,
	adslAtucChanPerfPrev1DayReceivedBlks        INTEGER,
	adslAtucChanPerfPrev1DayTransmittedBlks     INTEGER,
	adslAtucChanPerfPrev1DayCorrectedBlks       INTEGER,
	adslAtucChanPerfPrev1DayUncorrectBlks       INTEGER,
	adslAtucChanPerfCurrShowtimeCorrectedBlks   INTEGER,
	adslAtucChanPerfCurrShowtimeUncorrectBlks   INTEGER
    }

    adslAtucChanPerfIfIndex OBJECT-TYPE
	SYNTAX      INTEGER
	MAX-ACCESS  read-only
	STATUS      current
	DESCRIPTION 
	    "Specifies the ADSL interface index."
	::= { adslAtucChanPerfDataEntry 1 }

    adslAtucChanReceivedBlks OBJECT-TYPE
	SYNTAX      INTEGER
	MAX-ACCESS  read-only
	STATUS      current
	DESCRIPTION 
	    "Count of all encoded blocks received on this channel
	     since agent reset."
	::= { adslAtucChanPerfDataEntry 2 }

    adslAtucChanTransmittedBlks OBJECT-TYPE
	SYNTAX      INTEGER
	MAX-ACCESS  read-only
	STATUS      current
	DESCRIPTION 
	    "Count of all encoded blocks transmitted on this
	     channel since agent reset."
	::= { adslAtucChanPerfDataEntry 3 }

    adslAtucChanCorrectedBlks OBJECT-TYPE
	SYNTAX      INTEGER
	MAX-ACCESS  read-only
	STATUS      current
	DESCRIPTION 
	    "Count of all blocks received with errors that were
	     corrected since agent reset.  These blocks are passed
	     on as good data."
	::= { adslAtucChanPerfDataEntry 4 }

    adslAtucChanUncorrectBlks OBJECT-TYPE
	SYNTAX      INTEGER
	MAX-ACCESS  read-only
	STATUS      current
	DESCRIPTION 
	    "Count of all blocks received with uncorrectable
	     errors since agent reset."
	::= { adslAtucChanPerfDataEntry 5 }

    adslAtucChanPerfValidIntervals OBJECT-TYPE
	SYNTAX      INTEGER (0..96)
	MAX-ACCESS  read-only
	STATUS      current
	DESCRIPTION 
	    "The number of previous 15-minute intervals in the
	     interval table for which data was collected.  Given
	     that <n> is the maximum # of intervals supported.
	     The value will be <n> unless the measurement was
	     (re-)started within the last (<n>*15) minutes, in which
	     case the value will be the number of complete 15
	     minute intervals for which the agent has at least
	     some data. In certain cases (e.g., in the case
	     where the agent is a proxy) it is possible that some
	     intervals are unavailable.  In this case, this
	     interval is the maximum interval number for
	     which data is available."
	::= { adslAtucChanPerfDataEntry 6 }

    adslAtucChanPerfInvalidIntervals OBJECT-TYPE
	SYNTAX      INTEGER (0..96)
	MAX-ACCESS  read-only
	STATUS      current
	DESCRIPTION 
	    "The number of intervals in the range from
	     0 to the value of adslAtucChanPerfValidIntervals
	     for which no data is available. This object
	     will typically be zero except in cases where
	     the data for some intervals are not available
	     (e.g., in proxy situations)."
	::= { adslAtucChanPerfDataEntry 7 }

    adslAtucChanPerfCurr15MinTimeElapsed OBJECT-TYPE
	SYNTAX      INTEGER (0..899)
	MAX-ACCESS  read-only
	STATUS      current
	DESCRIPTION 
	    "Total elapsed seconds in this interval.
	     A full interval is 900 seconds."
	::= { adslAtucChanPerfDataEntry 8 }

    adslAtucChanPerfCurr15MinReceivedBlks OBJECT-TYPE
	SYNTAX      INTEGER
	MAX-ACCESS  read-only
	STATUS      current
	DESCRIPTION 
	    "Count of all encoded blocks received on this
	     channel within the mandatory 15 minute interval."
	::= { adslAtucChanPerfDataEntry 9 }

    adslAtucChanPerfCurr15MinTransmittedBlks OBJECT-TYPE
	SYNTAX      INTEGER
	MAX-ACCESS  read-only
	STATUS      current
	DESCRIPTION 
	    "Count of all encoded blocks transmitted on this
	     channel within the mandatory 15 minute interval."
	::= { adslAtucChanPerfDataEntry 10 }

    adslAtucChanPerfCurr15MinCorrectedBlks OBJECT-TYPE
	SYNTAX      INTEGER
	MAX-ACCESS  read-only
	STATUS      current
	DESCRIPTION 
	    "Count of all blocks received with errors that were
	     corrected on this channel within the mandatory 15 minute
	     interval."
	::= { adslAtucChanPerfDataEntry 11 }

    adslAtucChanPerfCurr15MinUncorrectBlks OBJECT-TYPE
	SYNTAX      INTEGER
	MAX-ACCESS  read-only
	STATUS      current
	DESCRIPTION 
	    "Count of all blocks received with uncorrectable
	     errors on this channel within the mandatory 15 minute
	     interval."
	::= { adslAtucChanPerfDataEntry 12 }

    adslAtucChanPerfCurr1DayTimeElapsed OBJECT-TYPE
	SYNTAX      INTEGER (0..86399)
	MAX-ACCESS  read-only
	STATUS      current
	DESCRIPTION 
	    "Number of seconds that have elapsed since the
	     beginning of the mandatory 1-day interval."
	::= { adslAtucChanPerfDataEntry 13 }

    adslAtucChanPerfCurr1DayReceivedBlks OBJECT-TYPE
	SYNTAX      INTEGER
	MAX-ACCESS  read-only
	STATUS      current
	DESCRIPTION 
	    "Count of all encoded blocks received on this
	     channel during the mandatory day as measured by
	     adslAtucChanPerfCurr1DayTimeElapsed."
	::= { adslAtucChanPerfDataEntry 14 }

    adslAtucChanPerfCurr1DayTransmittedBlks OBJECT-TYPE
	SYNTAX      INTEGER
	MAX-ACCESS  read-only
	STATUS      current
	DESCRIPTION 
	    "Count of all encoded blocks transmitted on this
	     channel during the mandatory day as measured by
	     adslAtucChanPerfCurr1DayTimeElapsed."
	::= { adslAtucChanPerfDataEntry 15 }

    adslAtucChanPerfCurr1DayCorrectedBlks OBJECT-TYPE
	SYNTAX      INTEGER
	MAX-ACCESS  read-only
	STATUS      current
	DESCRIPTION 
	    "Count of all blocks received with errors that were
	     corrected on this channel during the mandatory day as
	     measured by adslAtucChanPerfCurr1DayTimeElapsed."
	::= { adslAtucChanPerfDataEntry 16 }

    adslAtucChanPerfCurr1DayUncorrectBlks OBJECT-TYPE
	SYNTAX      INTEGER
	MAX-ACCESS  read-only
	STATUS      current
	DESCRIPTION 
	    "Count of all blocks received with uncorrectable
	     errors on this channel during the mandatory day as
	     measured by adslAtucChanPerfCurr1DayTimeElapsed."
	::= { adslAtucChanPerfDataEntry 17 }

    adslAtucChanPerfPrev1DayMoniSecs OBJECT-TYPE
	SYNTAX      INTEGER (0..86400)
	MAX-ACCESS  read-only
	STATUS      current
	DESCRIPTION 
	    "The amount of time in the previous 1-day interval
	     over which the performance monitoring information
	     is actually counted. This value will be the same as
	     the interval duration except in a situation where
	     performance monitoring data could not be collected
	     for any reason."
	::= { adslAtucChanPerfDataEntry 18 }

    adslAtucChanPerfPrev1DayReceivedBlks OBJECT-TYPE
	SYNTAX      INTEGER
	MAX-ACCESS  read-only
	STATUS      current
	DESCRIPTION 
	    "Count of all encoded blocks received on this
	     channel within the most recent previous 1-day
	     period."
	::= { adslAtucChanPerfDataEntry 19 }

    adslAtucChanPerfPrev1DayTransmittedBlks OBJECT-TYPE
	SYNTAX      INTEGER
	MAX-ACCESS  read-only
	STATUS      current
	DESCRIPTION 
	    "Count of all encoded blocks transmitted on this
	     channel within the most recent previous 1-day
	     period."
	::= { adslAtucChanPerfDataEntry 20 }

    adslAtucChanPerfPrev1DayCorrectedBlks OBJECT-TYPE
	SYNTAX      INTEGER
	MAX-ACCESS  read-only
	STATUS      current
	DESCRIPTION 
	    "Count of all blocks received with errors that were
	     corrected on this channel within the most recent
	     previous 1-day period."
	::= { adslAtucChanPerfDataEntry 21 }

    adslAtucChanPerfPrev1DayUncorrectBlks OBJECT-TYPE
	SYNTAX      INTEGER
	MAX-ACCESS  read-only
	STATUS      current
	DESCRIPTION 
	    "Count of all blocks received with uncorrectable
	     errors on this channel within the most recent previous
	     1-day period."
	::= { adslAtucChanPerfDataEntry 22 }
    
    adslAtucChanPerfCurrShowtimeCorrectedBlks OBJECT-TYPE
	SYNTAX      INTEGER
	MAX-ACCESS  read-only
	STATUS      current
	DESCRIPTION 
	    "Count of all blocks received with errors that were
	     corrected on this channel since the most recent
	     DSL Showtime."
	::= { adslAtucChanPerfDataEntry 23 }

    adslAtucChanPerfCurrShowtimeUncorrectBlks OBJECT-TYPE
	SYNTAX      INTEGER
	MAX-ACCESS  read-only
	STATUS      current
	DESCRIPTION 
	    "Count of all blocks received with uncorrectable
	     errors on this channel since the most recent
	     DSL Showtime."
	::= { adslAtucChanPerfDataEntry 24 }
    
END
