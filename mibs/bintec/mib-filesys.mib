-- This file is corresponding to Release 10.2.3.100 from 2018/07/18 00:00:00


---------------------------------------------------------------------------
-- (C)opyright 2008-2014 bintec elmeg GmbH
-- $RCSfile: mib-filesys,v $
-- $Revision: 1.6 $
-- $Date: 2014-02-07 10:37:49 $
-- Author: stefans
---------------------------------------------------------------------------

BINTEC-FILESYS DEFINITIONS ::= BEGIN

IMPORTS
    MODULE-IDENTITY, OBJECT-TYPE, NOTIFICATION-TYPE,
    Unsigned32, mib-2, enterprises
        FROM SNMPv2-SMI

    DisplayString, TimeStamp
        FROM SNMPv2-TC

    admin-2, Date
	FROM BINTEC-MIB

    MODULE-COMPLIANCE, OBJECT-GROUP, NOTIFICATION-GROUP
        FROM SNMPv2-CONF;

---------------------------------------------------------------------------
--  filesystem MIB

fsMIB MODULE-IDENTITY
    LAST-UPDATED "201102170000Z"
    ORGANIZATION "bintec elmeg GmbH"
    CONTACT-INFO
            "EMail:   info@bintec-elmeg.com
	     Web:     www.bintec-elmeg.com
	    "
    DESCRIPTION
            "The MIB module for file system
            "
    REVISION      "201102170000Z"
    DESCRIPTION
            "Initial version." 

    ::= { admin-2 7 }

---------------------------------------------------------------------------
-- fsDisk		file system disk
---------------------------------------------------------------------------

fsDiskTable OBJECT-TYPE
    SYNTAX      SEQUENCE OF FsDiskEntry
    MAX-ACCESS  not-accessible
    STATUS      current
    DESCRIPTION
	    "This tables contains the current file system entries. 
	     Entries are created by the system.
	    "
    ::= { fsMIB 1 }

    fsDiskEntry OBJECT-TYPE
	SYNTAX      FsDiskEntry
	MAX-ACCESS  not-accessible
	STATUS      current
	DESCRIPTION
		"(one entry of fsDiskTable)"
	INDEX   { fsDiskId }
	::= { fsDiskTable 1 }

    FsDiskEntry ::=
	SEQUENCE {
	    fsDiskId			INTEGER,
	    fsDiskDevName		DisplayString,
	    fsDiskDevInfo		DisplayString,
	    fsDiskStatus		BITS,
	    fsDiskCommand		INTEGER,
	    fsDiskFsType		INTEGER,
	    fsDiskSize			Unsigned32,
	    fsDiskBlocks		Unsigned32,
	    fsDiskFreeBlocks		Unsigned32,
	    fsDiskInfoMsg		DisplayString
    }

    fsDiskId        OBJECT-TYPE
	SYNTAX      INTEGER (0..255)
	MAX-ACCESS  read-only
	STATUS      current
	DESCRIPTION
		"Disk partition number.
		 Directory path is /disk0..n
		"
	::= { fsDiskEntry 1 }

    fsDiskDevName   OBJECT-TYPE
	SYNTAX      DisplayString (SIZE (0..32))
	MAX-ACCESS  read-only
	STATUS      current
	DESCRIPTION
		"Diskname and the alternative directory path.
		 format: driver-devicenumber-partitionnumber
		         e.g.  ifl-0-0   (for internal flash device)
		"
	::= { fsDiskEntry 2 }

    fsDiskDevInfo   OBJECT-TYPE
	SYNTAX      DisplayString (SIZE (0..255))
	MAX-ACCESS  read-only
	STATUS      current
	DESCRIPTION
		"Device hardware information. 
		   e.g. IN28F032
		"
	::= { fsDiskEntry 3 }

    fsDiskStatus    OBJECT-TYPE
	SYNTAX      BITS { inserted(0), mounted(1), readonly(2), error(7) }
	MAX-ACCESS  read-only
	STATUS      current
	DESCRIPTION
		"Disk status flags
		"
	::= { fsDiskEntry 4 }
	
    fsDiskCommand   OBJECT-TYPE
	SYNTAX      INTEGER    { none(0), mount(1), umount(2), format(3) }
	MAX-ACCESS  read-write
	STATUS      current
	DESCRIPTION
		"Execute disk command
		   mount:  mount disk 
		   umount: umount disk to eject
		   format: format whole disk (set together with FsType/Version)
		"
	DEFVAL { none }
	::= { fsDiskEntry 5 }


    fsDiskFsType    OBJECT-TYPE
	SYNTAX      INTEGER { unkown(0), fat12(1), fat16(2), fat32(3) }
	MAX-ACCESS  read-write
	STATUS      current
	DESCRIPTION
		"Disk filesystem type.
		 fat12 : FAT12
		 fat16 : FAT16
		 fat32 : FAT32
		"
	DEFVAL  { unkown }
	::= { fsDiskEntry 6 }

    fsDiskSize OBJECT-TYPE
	SYNTAX      Unsigned32 
	MAX-ACCESS  read-only
	STATUS      current
	DESCRIPTION
		"Total disk size in kBytes.
		"
	::= { fsDiskEntry 8 }

    fsDiskBlocks OBJECT-TYPE
	SYNTAX      Unsigned32 
	MAX-ACCESS  read-only
	STATUS      current
	DESCRIPTION
		"Number of disk/partition blocks (blocksize 512 bytes).
		"
	::= { fsDiskEntry 9 }

--  fsDiskUsedBlocks OBJECT-TYPE ::= { fsDiskEntry 10 }

    fsDiskFreeBlocks OBJECT-TYPE
	SYNTAX      Unsigned32 
	MAX-ACCESS  read-only
	STATUS      current
	DESCRIPTION
		"Number of free blocks.
		"
	::= { fsDiskEntry 11 }

--  fsDiskBadBlocks OBJECT-TYPE ::= { fsDiskEntry 12 }

    fsDiskInfoMsg   OBJECT-TYPE
	SYNTAX      DisplayString
	MAX-ACCESS  read-only
	STATUS      current
	DESCRIPTION
		"Last informational message.
		 E.g. performed cmd message or occured error.
		"
	::= { fsDiskEntry 13 }

-- end: fsDiskTable
---------------------------------------------------------------------------

END
