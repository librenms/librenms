-- This file is corresponding to Release 10.2.3.100 from 2018/07/18 00:00:00


-- $RCSfile: mib-vdsl,v $
-- $Revision: 1.1 $

-- (C)opyright 2007-2017 bintec elmeg GmbH, All Rights Reserved

BIANCA-BRICK-VDSL-MIB DEFINITIONS ::= BEGIN

        IMPORTS
            Counter64, enterprises, OBJECT-TYPE, MODULE-IDENTITY
                FROM SNMPv2-SMI
             DisplayString
                FROM SNMPv2-TC
            TRAP-TYPE
                FROM RFC-1215
	    adsl
		FROM BINTEC-MIB;



    vdslMibObjects OBJECT IDENTIFIER ::= { adsl 2 }

    efmStatsTable OBJECT-TYPE
	SYNTAX      SEQUENCE OF EfmStatsEntry
	MAX-ACCESS  not-accessible
	STATUS      current
	DESCRIPTION 
	    "This table includes common attributes describing
	     far end (ATU-R) of the line.  It is required for all ADSL
	     physical interfaces.  ADSL physical interfaces are
	     those ifEntries where ifType is equal to adsl(94)."
	::= { vdslMibObjects 1 }

    efmStatsEntry OBJECT-TYPE
	SYNTAX      EfmStatsEntry
	MAX-ACCESS  not-accessible
	STATUS      current
	DESCRIPTION 
	    "An entry in efmStatsTable."
	INDEX       { efmStatsIfIndex, efmStatsChannel }
	::= { efmStatsTable 1 }

    EfmStatsEntry ::= SEQUENCE {
	efmStatsIfIndex		INTEGER,
	efmStatsChannel		INTEGER,
	efmStatsInPkts		Counter64,
	efmStatsOutPkts		Counter64,
	efmStatsInOctets	Counter64,
	efmStatsOutOctets	Counter64,
	efmStatsInDiscards	Counter64,
	efmStatsOutDiscards	Counter64,
	efmStatsInErrors	Counter64
    }

    efmStatsIfIndex OBJECT-TYPE
	SYNTAX      INTEGER
	MAX-ACCESS  read-only
	STATUS      current
	DESCRIPTION 
	    "Specifies the DSL interface index used on this line."
	::= { efmStatsEntry 1 }

    efmStatsChannel OBJECT-TYPE
	SYNTAX      INTEGER 
	MAX-ACCESS  read-only
	STATUS      current
	DESCRIPTION 
	    "Specifies the QOS channel that is described in this entry."
	DEFVAL       { 0 }
	::= { efmStatsEntry 2 }

    efmStatsInPkts OBJECT-TYPE
	SYNTAX      Counter64
	MAX-ACCESS  read-only
	STATUS      current
	DESCRIPTION
	    "The number of reassembled received packets."
    ::= { efmStatsEntry 3 }

    efmStatsOutPkts OBJECT-TYPE
	SYNTAX      Counter64
	MAX-ACCESS  read-only
	STATUS      current
	DESCRIPTION
	    "This number of transmitted packets."
    ::= { efmStatsEntry 4 }

    efmStatsInOctets OBJECT-TYPE
	SYNTAX      Counter64
	MAX-ACCESS  read-only
	STATUS      current
	DESCRIPTION
	    "The total number of octets received on the interface,
	     including framing characters."
    ::= { efmStatsEntry 5 }

    efmStatsOutOctets OBJECT-TYPE 
	SYNTAX      Counter64
	MAX-ACCESS  read-only
	STATUS      current
	DESCRIPTION
	    "The total number of octets transmitted out of the interface,
	     including framing characters."
    ::= { efmStatsEntry 6 }
    
    efmStatsInDiscards OBJECT-TYPE
	SYNTAX      Counter64
	MAX-ACCESS  read-only
	STATUS      current
	DESCRIPTION
	    "The number of inbound packets which were chosen to be
	     discarded even though no errors had been detected to prevent
	     their being deliverable to a higher-layer protocol. One
	     possible reason for discarding such a packet could be to
	     free up buffer space."
    ::= { efmStatsEntry 7 }

    efmStatsOutDiscards OBJECT-TYPE
	SYNTAX      Counter64
	MAX-ACCESS  read-only
	STATUS      current
	DESCRIPTION
	    "The number of outbound packets which were chosen to be
	     discarded even though no errors had been detected to prevent
	     their being transmitted.  One possible reason for discarding
	     such a packet could be to free up buffer space."
    ::= { efmStatsEntry 8 }

    efmStatsInErrors OBJECT-TYPE
	SYNTAX      Counter64
	MAX-ACCESS  read-only
	STATUS      current
	DESCRIPTION
	    "The number of inbound packets that contained errors preventing
	     them from being deliverable to a higher-layer protocol."
    ::= { efmStatsEntry 9 }


END
