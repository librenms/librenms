-- This file is corresponding to Release 10.2.3.100 from 2018/07/18 00:00:00


-- (C)opyright 2003-2014 bintec elmeg GmbH, All Rights Reserved
-- $RCSfile: mibl2tp,v $ 
-- $Revision: 1.14 $ 
-- $Id: mibl2tp,v 1.14 2015-09-16 08:43:42 harry Exp $"

BIANCA-BRICK-L2TP-MIB DEFINITIONS ::= BEGIN

        IMPORTS
            IpAddress, Counter, enterprises
                FROM RFC1155-SMI

            DisplayString
                FROM RFC1158-MIB
 
            OBJECT-TYPE
                FROM RFC-1212

            vpn
                FROM BINTEC-MIB;

    -- L2TP

    l2tp	OBJECT IDENTIFIER
	::= { vpn 8 }

    -- L2TP static table for global parameters

	l2tpGlobals OBJECT IDENTIFIER
	::= { l2tp 10 }

	l2tpGlobUdpPort OBJECT-TYPE
	    SYNTAX INTEGER(1..65535)
            ACCESS  read-write
            STATUS  mandatory
            DESCRIPTION
		"The UDP port which is monitored by L2TP for tunnel
		establishment requests received from remote hosts."
	    DEFVAL { 1701 }
	::= { l2tpGlobals 10 }

	l2tpGlobPortUsage OBJECT-TYPE
	    SYNTAX INTEGER {
		single(1), 	-- L2TP uses the UDP port defined by l2tpGlobUdpPort
				-- to send messages to the remote equipment.
		floating(2)	-- L2TP allocates a new port to send messages to
				-- the remote equipment (default).
	    }
            ACCESS  read-write
            STATUS  mandatory
	    DESCRIPTION
		"This object specifies whether L2TP uses only one UDP port (which
		 number is defined by l2tpGlobUdpPort), or if it allocates a new 
		 available port, to send messages to the remote equipment. Choosing
		 'single' makes it sometimes easier to process L2TP through NAT
		 since L2TP traffic can be classified based on the UDP port number.
		 Choosing 'floating' selects the behavior which is recommended in 
		 RFC2331.
		 Possible values:
		 single(1), 	-- L2TP uses the UDP port defined by l2tpGlobUdpPort
				-- to send messages to the remote equipment.
		 floating(2)	-- L2TP allocates a new port to send messages to
				-- the remote equipment (default)."
	    DEFVAL { floating }
	::= { l2tpGlobals 20 }



    -- L2TP tunnel profile table

	l2tpTunnelProfileTable OBJECT-TYPE
	    SYNTAX  SEQUENCE OF L2tpTunnelProfileEntry
	    ACCESS  not-accessible
	    STATUS  mandatory
	    DESCRIPTION
		"This table contains profile information for L2TP tunnels."
	::= { l2tp 20 }

	l2tpTunnelProfileEntry OBJECT-TYPE
	    SYNTAX  L2tpTunnelProfileEntry
	    ACCESS  not-accessible
	    STATUS  mandatory
	    DESCRIPTION
		"An entry in the l2tpTunnelProfileTable."
	    INDEX   { l2tpTunnelProfileIndex }
	::= { l2tpTunnelProfileTable 10 }

	L2tpTunnelProfileEntry ::=
	    SEQUENCE {
		l2tpTunnelProfileIndex			INTEGER,
		l2tpTunnelProfileName			DisplayString,
		l2tpTunnelProfileRemoteIpAddress	IpAddress,
		l2tpTunnelProfileRemoteIpAddressBackup	IpAddress,
		l2tpTunnelProfileRemoteUdpPort		INTEGER,
		l2tpTunnelProfileRemoteHostname		DisplayString,
		l2tpTunnelProfileLocalIpAddress		IpAddress,
		l2tpTunnelProfileLocalUdpPort		INTEGER,
		l2tpTunnelProfileLocalHostname		DisplayString,
		l2tpTunnelProfilePassword		DisplayString,
		l2tpTunnelProfileReceiveWindowSize	INTEGER,
		l2tpTunnelProfileHelloInterval		INTEGER,
		l2tpTunnelProfileSessionDataSequencing	INTEGER,
		l2tpTunnelProfileMinRetryTime		INTEGER,
		l2tpTunnelProfileMaxRetryTime		INTEGER,
		l2tpTunnelProfileMaxRetries		INTEGER,
		l2tpTunnelProfileRadiusAssignment	INTEGER,
		l2tpTunnelProfileRadiusGroupId		INTEGER
	}

	l2tpTunnelProfileIndex OBJECT-TYPE
	    SYNTAX  INTEGER
	    ACCESS  read-write
	    STATUS  mandatory
	    DESCRIPTION
		"The unique index for this entry."
	    DEFVAL  { 0 }
	::= { l2tpTunnelProfileEntry 10 }

	l2tpTunnelProfileName OBJECT-TYPE
            SYNTAX  DisplayString (SIZE (0..255))
	    ACCESS  read-write
	    STATUS  mandatory
	    DESCRIPTION
		"The friendly name for this entry."
	    DEFVAL  { "" }
	::= { l2tpTunnelProfileEntry 15 }

	l2tpTunnelProfileRemoteIpAddress OBJECT-TYPE
	    SYNTAX  IpAddress
	    ACCESS  read-write
	    STATUS  mandatory
	    DESCRIPTION
		"The main remote IP address for the tunnel. Only 
		meaningful in LAC mode. If l2tpTunnelProfileRadiusAssignment
		is set to 'enabled', this object is ignored and the L2TP 
		daemon will ask the Radius daemon to send a request for the 
		main and backup remote IP addresses."
	::= { l2tpTunnelProfileEntry 20 }

	l2tpTunnelProfileRemoteIpAddressBackup OBJECT-TYPE
	    SYNTAX  IpAddress
	    ACCESS  read-write
	    STATUS  mandatory
	    DESCRIPTION
		"The backup remote IP address for the tunnel. Only 
		meaningful in LAC mode. If l2tpTunnelProfileRadiusAssignment
		is set to 'enabled', this object is ignored and the L2TP 
		daemon will ask the Radius daemon to send a request for the 
		main and backup remote IP addresses."
	::= { l2tpTunnelProfileEntry 25 }

	l2tpTunnelProfileRemoteUdpPort OBJECT-TYPE
	    SYNTAX  INTEGER(0..65535)
	    ACCESS  read-write
	    STATUS  mandatory
	    DESCRIPTION
		"The remote UDP port number for the tunnel. 
		Only meaningful in LAC mode."
	    DEFVAL  { 1701 }
	::= { l2tpTunnelProfileEntry 30 }

	l2tpTunnelProfileRemoteHostname OBJECT-TYPE
            SYNTAX  DisplayString (SIZE (0..255))
	    ACCESS  read-write
	    STATUS  mandatory
	    DESCRIPTION
		"The name of the remote host. Use an empty string for
		default profile."
	    DEFVAL  { "" }
	::= { l2tpTunnelProfileEntry 40 }

	l2tpTunnelProfileLocalIpAddress OBJECT-TYPE
	    SYNTAX  IpAddress
	    ACCESS  read-write
	    STATUS  mandatory
	    DESCRIPTION
		"The local IP address for the tunnel. If this value
		is set to 0, the IP address of the egress interface
		will be used in outgoing L2TP packets."
	::= { l2tpTunnelProfileEntry 50 }

	l2tpTunnelProfileLocalUdpPort OBJECT-TYPE
	    SYNTAX  INTEGER(0..65535)
	    ACCESS  read-write
	    STATUS  mandatory
	    DESCRIPTION
		"The local UDP port number for the tunnel. 
		Only meaningful in LAC mode. If this 
		value is set to 0 (zero), the port number
		is allocated dynamically."
	    DEFVAL  { 0 }
	::= { l2tpTunnelProfileEntry 60 }

	l2tpTunnelProfileLocalHostname OBJECT-TYPE
            SYNTAX  DisplayString (SIZE (0..255))
	    ACCESS  read-write
	    STATUS  mandatory
	    DESCRIPTION
		"The name of the local host."
	    DEFVAL  { "" }
	::= { l2tpTunnelProfileEntry 70 }

	l2tpTunnelProfilePassword OBJECT-TYPE
            SYNTAX  DisplayString (SIZE (0..255))
	    ACCESS  read-write
	    STATUS  mandatory
	    DESCRIPTION
		"The password used for tunnel authentication."
	    DEFVAL  { "" }
	::= { l2tpTunnelProfileEntry 80 }

	l2tpTunnelProfileReceiveWindowSize OBJECT-TYPE
--	    SYNTAX  INTEGER(1..255)
	    SYNTAX  INTEGER(1..1)
	    ACCESS  read-write
	    STATUS  mandatory
	    DESCRIPTION
		"The received window size used by L2TP on the local 
		 side of this tunnel. Currently, the only supported 
		 value is 1."
--	    DEFVAL { 4 }
	    DEFVAL { 1 }
	::= { l2tpTunnelProfileEntry 90 }

	l2tpTunnelProfileHelloInterval OBJECT-TYPE
	    SYNTAX  INTEGER(0..255)
	    ACCESS  read-write
	    STATUS  mandatory
	    DESCRIPTION
		"The interval in seconds between two consecutive hello 
		 requests sent by L2TP during the tunnel life. If this 
		 object is set to 0 (zero), no hello requests are sent 
		 by L2TP on this tunnel."
	    DEFVAL { 30 }
	::= { l2tpTunnelProfileEntry 100 }

	l2tpTunnelProfileSessionDataSequencing OBJECT-TYPE
	    SYNTAX INTEGER {
		delete(1),
		disabled(2),
		enabled(3)
	    }
            ACCESS  read-write
            STATUS  mandatory
	    DESCRIPTION
		"This object specifies if sequence numbers are used on
		 the data channel of sessions supported by this tunnel.
		 Additionally, if this object is set to delete (1), the
		 entry is marked for discard."
	    DEFVAL { disabled }
	::= { l2tpTunnelProfileEntry 110 }

	l2tpTunnelProfileMinRetryTime OBJECT-TYPE
	    SYNTAX  INTEGER(1..255)
	    ACCESS  read-write
	    STATUS  mandatory
	    DESCRIPTION
		"The initial interval in seconds between two consecutive 
		 attempts to send an L2TP control packet. The value of 
		 this interval is doubled with each new attempt, until 
		 the maximum value defined in l2tpTunnelProfileMaxRetryTime 
		 is reached."
	    DEFVAL { 1 }
	::= { l2tpTunnelProfileEntry 120 }

	l2tpTunnelProfileMaxRetryTime OBJECT-TYPE
	    SYNTAX  INTEGER(8..255)
	    ACCESS  read-write
	    STATUS  mandatory
	    DESCRIPTION
		"The maximum interval in seconds between two consecutive 
		 attempts to send an L2TP control packet."
	    DEFVAL { 16 }
	::= { l2tpTunnelProfileEntry 130 }

	l2tpTunnelProfileMaxRetries OBJECT-TYPE
	    SYNTAX  INTEGER(1..255)
	    ACCESS  read-write
	    STATUS  mandatory
	    DESCRIPTION
		"The maximum number of retries to send an L2TP control 
		 packet. The total number of attempts will be one more 
		 than this value."
	    DEFVAL { 5 }
	::= { l2tpTunnelProfileEntry 140 }

	l2tpTunnelProfileRadiusAssignment OBJECT-TYPE
	    SYNTAX INTEGER {
		disabled(1),	-- disable option
		enabled(2)	-- enable option
	    }
            ACCESS  read-write
            STATUS  mandatory
            DESCRIPTION
		"This object enables/disables the use of Radius for
		 requesting main and backup remote IP addresses. Only 
		 meaningful in LAC mode."
            DEFVAL { disabled }
	::= { l2tpTunnelProfileEntry 150 }

	l2tpTunnelProfileRadiusGroupId OBJECT-TYPE
	    SYNTAX  INTEGER (0..9)
	    ACCESS  read-write
	    STATUS  mandatory

	    DESCRIPTION
		"Determines the logical RADIUS server group to be addressed 
		 for sending the RADIUS Access-Request messages. Only 
		 meaningful in LAC mode. See also radiusSrvGroupId."
	    DEFVAL { 0 }
	::= { l2tpTunnelProfileEntry 160 }


    -- L2TP tunnel table

	l2tpTunnelTable OBJECT-TYPE
	    SYNTAX  SEQUENCE OF L2tpTunnelEntry
	    ACCESS  not-accessible
	    STATUS  mandatory
	    DESCRIPTION
		"This table contains information for L2TP tunnels."
	::= { l2tp 30 }

	l2tpTunnelEntry OBJECT-TYPE
	    SYNTAX  L2tpTunnelEntry
	    ACCESS  not-accessible
	    STATUS  mandatory
	    DESCRIPTION
		"Entries in this table are created by the system."
	    INDEX   { l2tpTunnelLocalTunnelId }
	::= { l2tpTunnelTable 10 }

	L2tpTunnelEntry ::=
	    SEQUENCE {
		l2tpTunnelRemoteIpAddress		IpAddress,
		l2tpTunnelRemoteUdpPort			INTEGER,
		l2tpTunnelRemoteTunnelId		INTEGER,
		l2tpTunnelRemoteReceiveWindowSize	INTEGER,
		l2tpTunnelRemoteHostname		DisplayString,
		l2tpTunnelRemoteVendorName		DisplayString,
		l2tpTunnelLocalIpAddress		IpAddress,
		l2tpTunnelLocalUdpPort			INTEGER,
		l2tpTunnelLocalTunnelId			INTEGER,
		l2tpTunnelLocalReceiveWindowSize	INTEGER,
		l2tpTunnelLocalHostname			DisplayString,
		l2tpTunnelPassword			DisplayString,
		l2tpTunnelHelloInterval			INTEGER,
		l2tpTunnelSessionDataSequencing		INTEGER,
		l2tpTunnelMinRetryTime			INTEGER,
		l2tpTunnelMaxRetryTime			INTEGER,
		l2tpTunnelMaxRetries			INTEGER,
		l2tpTunnelState				INTEGER
	}

	l2tpTunnelRemoteIpAddress OBJECT-TYPE
	    SYNTAX  IpAddress
	    ACCESS  read-only
	    STATUS  mandatory
	    DESCRIPTION
		"The remote IP address for the tunnel."
	::= { l2tpTunnelEntry 10 }

	l2tpTunnelRemoteUdpPort OBJECT-TYPE
	    SYNTAX  INTEGER(0..65535)
	    ACCESS  read-only
	    STATUS  mandatory
	    DESCRIPTION
		"The remote UDP port number for the tunnel."
	    DEFVAL  { 0 }
	::= { l2tpTunnelEntry 20 }

	l2tpTunnelRemoteTunnelId OBJECT-TYPE
	    SYNTAX  INTEGER(0..65535)
	    ACCESS  read-only
	    STATUS  mandatory
	    DESCRIPTION
		"The ID used by the remote end for the tunnel."
	    DEFVAL  { 0 }
	::= { l2tpTunnelEntry 30 }

	l2tpTunnelRemoteReceiveWindowSize OBJECT-TYPE
	    SYNTAX  INTEGER(1..65535)
	    ACCESS  read-only
	    STATUS  mandatory
	    DESCRIPTION
		"The receive window size used by L2TP on the remote 
		 side of this tunnel."
	    DEFVAL { 4 }
	::= { l2tpTunnelEntry 35 }

	l2tpTunnelRemoteHostname OBJECT-TYPE
            SYNTAX  DisplayString (SIZE (0..255))
	    ACCESS  read-only
	    STATUS  mandatory
	    DESCRIPTION
		"The name of the remote host."
	    DEFVAL  { "" }
	::= { l2tpTunnelEntry 40 }

	l2tpTunnelRemoteVendorName OBJECT-TYPE
            SYNTAX  DisplayString (SIZE (0..255))
	    ACCESS  read-only
	    STATUS  mandatory
	    DESCRIPTION
		"The vendor name of the remote host L2TP layer."
	    DEFVAL  { "" }
	::= { l2tpTunnelEntry 50 }

	l2tpTunnelLocalIpAddress OBJECT-TYPE
	    SYNTAX  IpAddress
	    ACCESS  read-only
	    STATUS  mandatory
	    DESCRIPTION
		"The local IP address for the tunnel."
	::= { l2tpTunnelEntry 60 }

	l2tpTunnelLocalUdpPort OBJECT-TYPE
	    SYNTAX  INTEGER(0..65535)
	    ACCESS  read-only
	    STATUS  mandatory
	    DESCRIPTION
		"The local UDP port number for the tunnel."
	    DEFVAL  { 0 }
	::= { l2tpTunnelEntry 70 }

	l2tpTunnelLocalTunnelId OBJECT-TYPE
	    SYNTAX  INTEGER(0..65535)
	    ACCESS  read-only
	    STATUS  mandatory
	    DESCRIPTION
		"The ID used by the local end for the tunnel."
	    DEFVAL  { 0 }
	::= { l2tpTunnelEntry 80 }

	l2tpTunnelLocalReceiveWindowSize OBJECT-TYPE
--	    SYNTAX  INTEGER(1..65535)
	    SYNTAX  INTEGER(1..1)
	    ACCESS  read-only
	    STATUS  mandatory
	    DESCRIPTION
		"The receive window size used by L2TP on the local 
		 side of this tunnel. Currently, the only supported 
		 value is 1."
--	    DEFVAL { 4 }
	    DEFVAL { 1 }
	::= { l2tpTunnelEntry 85 }

	l2tpTunnelLocalHostname OBJECT-TYPE
            SYNTAX  DisplayString (SIZE (0..255))
	    ACCESS  read-only
	    STATUS  mandatory
	    DESCRIPTION
		"The name of the local host."
	    DEFVAL  { "" }
	::= { l2tpTunnelEntry 90 }

	l2tpTunnelPassword OBJECT-TYPE
            SYNTAX  DisplayString (SIZE (0..255))
	    ACCESS  read-only
	    STATUS  mandatory
	    DESCRIPTION
		"The password used for tunnel authentication."
	    DEFVAL  { "" }
	::= { l2tpTunnelEntry 100 }

	l2tpTunnelHelloInterval OBJECT-TYPE
	    SYNTAX  INTEGER(0..255)
	    ACCESS  read-write
	    STATUS  mandatory
	    DESCRIPTION
		"The interval in seconds between two consecutive hello 
		 requests sent by L2TP during the tunnel life. If this 
		 object is set to 0 (zero), no hello requests are sent 
		 by L2TP on this tunnel."
	    DEFVAL { 60 }
	::= { l2tpTunnelEntry 120 }

	l2tpTunnelSessionDataSequencing OBJECT-TYPE
	    SYNTAX INTEGER {
		disabled(2),
		enabled(3)
	    }
            ACCESS  read-write
            STATUS  mandatory
	    DESCRIPTION
		"This object specifies if sequence numbers are used on
		 the data channel of sessions supported by this tunnel."
	    DEFVAL { disabled }
	::= { l2tpTunnelEntry 130 }

	l2tpTunnelMinRetryTime OBJECT-TYPE
	    SYNTAX  INTEGER(1..255)
	    ACCESS  read-write
	    STATUS  mandatory
	    DESCRIPTION
		"The initial interval in seconds between two consecutive 
		 attempts to send an L2TP control packet. The value of 
		 this interval is doubled with each new attempt, until 
		 the maximum value defined in l2tpTunnelProfileMaxRetryTime 
		 is reached."
	    DEFVAL { 1 }
	::= { l2tpTunnelEntry 140 }

	l2tpTunnelMaxRetryTime OBJECT-TYPE
	    SYNTAX  INTEGER(8..255)
	    ACCESS  read-write
	    STATUS  mandatory
	    DESCRIPTION
		"The maximum interval in seconds between two consecutive 
		 attempts to send an L2TP control packet."
	    DEFVAL { 16 }
	::= { l2tpTunnelEntry 150 }

	l2tpTunnelMaxRetries OBJECT-TYPE
	    SYNTAX  INTEGER(1..255)
	    ACCESS  read-write
	    STATUS  mandatory
	    DESCRIPTION
		"The maximum number of retries to send an L2TP control 
		 packet. The total number of attempts will be one more 
		 than this value."
	    DEFVAL { 5 }
	::= { l2tpTunnelEntry 160 }

	l2tpTunnelState OBJECT-TYPE
	    SYNTAX INTEGER {
		idle(1),
		waitctlreply(2),
		waitctlconn(3),
		established(4),
		shutdown(5)
	    }
            ACCESS  read-write
            STATUS  mandatory
	    DESCRIPTION
		"The current state of the tunnel as specified in
		 RFC2661. Selecting shutdown(5) value results in tunnel
		 hangup. Any other value is ignored."
	    DEFVAL { idle }
	::= { l2tpTunnelEntry 170 }



    -- L2TP session table

	l2tpSessionTable OBJECT-TYPE
	    SYNTAX  SEQUENCE OF L2tpSessionEntry
	    ACCESS  not-accessible
	    STATUS  mandatory
	    DESCRIPTION
		"This Table contains information for L2TP sessions."
	::= { l2tp 40 }

	l2tpSessionEntry OBJECT-TYPE
	    SYNTAX  L2tpSessionEntry
	    ACCESS  not-accessible
	    STATUS  mandatory
	    DESCRIPTION
		"Entries in this table are created by the system."
	    INDEX   { l2tpSessionLocalSessionId }
	::= { l2tpSessionTable 10 }

	L2tpSessionEntry ::=
	    SEQUENCE {
		l2tpSessionRemoteIpAddress		IpAddress,
		l2tpSessionRemoteUdpPort		INTEGER,
		l2tpSessionRemoteTunnelId		INTEGER,
		l2tpSessionRemoteSessionId		INTEGER,
		l2tpSessionRemoteHostname		DisplayString,
		l2tpSessionLocalIpAddress		IpAddress,
		l2tpSessionLocalUdpPort			INTEGER,
		l2tpSessionLocalTunnelId		INTEGER,
		l2tpSessionLocalSessionId		INTEGER,
		l2tpSessionLocalHostname		DisplayString,
		l2tpSessionCallSerialNumber		INTEGER,
		l2tpSessionDataSequencing		INTEGER,
		l2tpSessionState			INTEGER,
		l2tpSessionInfo				DisplayString,
		l2tpSessionClientPPPCrcErrors		INTEGER,
		l2tpSessionClientPPPFramingErrors	INTEGER,
		l2tpSessionClientPPPHardwareOverruns	INTEGER,
		l2tpSessionClientPPPBufferOverruns	INTEGER,
		l2tpSessionClientPPPTimeoutErrors	INTEGER,
		l2tpSessionClientPPPAlignmentErrors	INTEGER
	}

	l2tpSessionRemoteIpAddress OBJECT-TYPE
	    SYNTAX  IpAddress
	    ACCESS  read-only
	    STATUS  mandatory
	    DESCRIPTION
		"The remote IP address for the tunnel."
	::= { l2tpSessionEntry 10 }

	l2tpSessionRemoteUdpPort OBJECT-TYPE
	    SYNTAX  INTEGER(0..65535)
	    ACCESS  read-only
	    STATUS  mandatory
	    DESCRIPTION
		"The remote UDP port number for the tunnel."
	    DEFVAL  { 0 }
	::= { l2tpSessionEntry 20 }

	l2tpSessionRemoteTunnelId OBJECT-TYPE
	    SYNTAX  INTEGER(0..65535)
	    ACCESS  read-only
	    STATUS  mandatory
	    DESCRIPTION
		"The ID used by the remote end for the tunnel."
	    DEFVAL  { 0 }
	::= { l2tpSessionEntry 30 }

	l2tpSessionRemoteSessionId OBJECT-TYPE
	    SYNTAX  INTEGER(0..65535)
	    ACCESS  read-only
	    STATUS  mandatory
	    DESCRIPTION
		"The ID used by the remote end for the session."
	    DEFVAL  { 0 }
	::= { l2tpSessionEntry 40 }

	l2tpSessionRemoteHostname OBJECT-TYPE
            SYNTAX  DisplayString (SIZE (0..255))
	    ACCESS  read-only
	    STATUS  mandatory
	    DESCRIPTION
		"The name of the remote host."
	    DEFVAL  { "" }
	::= { l2tpSessionEntry 50 }

	l2tpSessionLocalIpAddress OBJECT-TYPE
	    SYNTAX  IpAddress
	    ACCESS  read-only
	    STATUS  mandatory
	    DESCRIPTION
		"The local IP address for the tunnel."
	::= { l2tpSessionEntry 60 }

	l2tpSessionLocalUdpPort OBJECT-TYPE
	    SYNTAX  INTEGER(0..65535)
	    ACCESS  read-only
	    STATUS  mandatory
	    DESCRIPTION
		"The local UDP port number for the tunnel."
	    DEFVAL  { 0 }
	::= { l2tpSessionEntry 70 }

	l2tpSessionLocalTunnelId OBJECT-TYPE
	    SYNTAX  INTEGER(0..65535)
	    ACCESS  read-only
	    STATUS  mandatory
	    DESCRIPTION
		"The ID used by the local end for the tunnel."
	    DEFVAL  { 0 }
	::= { l2tpSessionEntry 80 }

	l2tpSessionLocalSessionId OBJECT-TYPE
	    SYNTAX  INTEGER(0..65535)
	    ACCESS  read-only
	    STATUS  mandatory
	    DESCRIPTION
		"The ID used by the local end for the session."
	    DEFVAL  { 0 }
	::= { l2tpSessionEntry 90 }

	l2tpSessionLocalHostname OBJECT-TYPE
            SYNTAX  DisplayString (SIZE (0..255))
	    ACCESS  read-only
	    STATUS  mandatory
	    DESCRIPTION
		"The name of the local host."
	    DEFVAL  { "" }
	::= { l2tpSessionEntry 100 }

	l2tpSessionCallSerialNumber OBJECT-TYPE
	    SYNTAX  INTEGER
	    ACCESS  read-only
	    STATUS  mandatory
	    DESCRIPTION
		"The call serial number for the session."
	    DEFVAL  { 0 }
	::= { l2tpSessionEntry 110 }

	l2tpSessionDataSequencing OBJECT-TYPE
	    SYNTAX INTEGER {
		disabled(2),
		enabled(3)
	    }
            ACCESS  read-write
            STATUS  mandatory
	    DESCRIPTION
		"This object specifies if sequence numbers are used on
		 the data channel of the session."
	    DEFVAL { disabled }
	::= { l2tpSessionEntry 120 }

	l2tpSessionState OBJECT-TYPE
	    SYNTAX INTEGER {
		idle(1),
		waittunnel(2),
		waitcsanswer(3),
		waitreply(4),
		waitconnect(5),
		established(6),
		shutdown(7)
	    }
            ACCESS  read-write
            STATUS  mandatory
	    DESCRIPTION
		"The current state of the session as specified in
		 RFC2661. Selecting shutdown(7) value results in session
		 hangup. Any other value is ignored."
	    DEFVAL { idle }
	::= { l2tpSessionEntry 130 }

	l2tpSessionInfo OBJECT-TYPE
            SYNTAX  DisplayString (SIZE (0..255))
	    ACCESS  read-only
	    STATUS  mandatory
	    DESCRIPTION
		"Info on the state of the session."
	    DEFVAL  { "" }
	::= { l2tpSessionEntry 140 }

	l2tpSessionClientPPPCrcErrors OBJECT-TYPE
	    SYNTAX  INTEGER
	    ACCESS  read-only
	    STATUS  mandatory
	    DESCRIPTION
		"The number of PPP CRC errors detected by the LAC 
		while communicating with the PPP client. This value 
		is only significant in L2TP-LNS mode."
	    DEFVAL  { 0 }
	::= { l2tpSessionEntry 150 }

	l2tpSessionClientPPPFramingErrors OBJECT-TYPE
	    SYNTAX  INTEGER
	    ACCESS  read-only
	    STATUS  mandatory
	    DESCRIPTION
		"The number of PPP framing errors detected by the LAC 
		while communicating with the PPP client. This value 
		is only significant in L2TP-LNS mode."
	    DEFVAL  { 0 }
	::= { l2tpSessionEntry 160 }

	l2tpSessionClientPPPHardwareOverruns OBJECT-TYPE
	    SYNTAX  INTEGER
	    ACCESS  read-only
	    STATUS  mandatory
	    DESCRIPTION
		"The number of PPP hardware overruns detected by the LAC 
		while communicating with the PPP client. This value 
		is only significant in L2TP-LNS mode."
	    DEFVAL  { 0 }
	::= { l2tpSessionEntry 170 }

	l2tpSessionClientPPPBufferOverruns OBJECT-TYPE
	    SYNTAX  INTEGER
	    ACCESS  read-only
	    STATUS  mandatory
	    DESCRIPTION
		"The number of PPP buffer overruns detected by the LAC 
		while communicating with the PPP client. This value 
		is only significant in L2TP-LNS mode."
	    DEFVAL  { 0 }
	::= { l2tpSessionEntry 180 }

	l2tpSessionClientPPPTimeoutErrors OBJECT-TYPE
	    SYNTAX  INTEGER
	    ACCESS  read-only
	    STATUS  mandatory
	    DESCRIPTION
		"The number of PPP timeout errors detected by the LAC 
		while communicating with the PPP client. This value 
		is only significant in L2TP-LNS mode."
	    DEFVAL  { 0 }
	::= { l2tpSessionEntry 190 }

	l2tpSessionClientPPPAlignmentErrors OBJECT-TYPE
	    SYNTAX  INTEGER
	    ACCESS  read-only
	    STATUS  mandatory
	    DESCRIPTION
		"The number of PPP alignment errors detected by the LAC 
		while communicating with the PPP client. This value 
		is only significant in L2TP-LNS mode."
	    DEFVAL  { 0 }
	::= { l2tpSessionEntry 200 }

END
