-- This file is corresponding to Release 10.2.3.100 from 2018/07/18 00:00:00


-- (C)opyright 1991-2015 bintec elmeg GmbH, All Rights Reserved
-- $Revision: 1.25 $ 

BIANCA-VIF-MIB DEFINITIONS ::= BEGIN


	IMPORTS
	    IpAddress, Counter, Gauge, TimeTicks, enterprises
		FROM RFC1155-SMI

	    OBJECT-TYPE
		FROM RFC-1212
	     
	    RowStatus, PhysAddress, DisplayString
	        FROM SNMPv2-TC

	    bibo, vif
		FROM BINTEC-MIB;

	--  This MIB module uses the extended OBJECT-TYPE macro as
	--  defined in [14];


---------------------------------------------------------------------------

virtIfMIB MODULE-IDENTITY
    LAST-UPDATED "201607040000Z"
    ORGANIZATION "bintec elmeg GmbH"
    CONTACT-INFO "EMail:   info@bintec-elmeg.com
                  Web:     www.bintec-elmeg.com"
    DESCRIPTION  "Management Information for virtual interface definitions"

    ::= { bibo 67 }

---------------------------------------------------------------------------

    -- Management Information for non-standard interface settings of
    -- BIANCA/BRICK


	virtIfDefinitionTable OBJECT-TYPE
	    SYNTAX  SEQUENCE OF VirtIfDefinitionEntry
	    MAX-ACCESS  not-accessible
	    STATUS  current
	    DESCRIPTION
		"The virtIfDefinitionTable contains information about the
		 physical interface address (MAC-Address) used on the
		 virtual interface and the ifIndex of the corresponding
		 physical interface defined by Slot/Unit/Channel."
	::= { vif 1 }

	virtIfDefinitionEntry OBJECT-TYPE
	    SYNTAX  VirtIfDefinitionEntry
	    MAX-ACCESS  not-accessible
	    STATUS      current

	    DESCRIPTION
		"Each entry contains a unique virtIfIndex and the physical
		 address used. The corresponding IP-Address musr be taken
		 from the ipAddressTable."
	    INDEX   { virtIfBaseSlot, virtIfBaseUnit, virtIfVirtChannel }
	::= { virtIfDefinitionTable 1 }

	VirtIfDefinitionEntry ::=
	    SEQUENCE {
		virtIfBaseSlot		INTEGER,
		virtIfBaseUnit		INTEGER,
		virtIfVirtChannel	INTEGER,
		virtIfPhysAddr		PhysAddress,
		virtIfAdminStatus	INTEGER,
		virtIfVlanId		INTEGER,
		virtIfOperMode		INTEGER,
		virtIfOrigPhysAddr	PhysAddress,
		virtIfBridgeIndex	INTEGER,
		virtIfUntaggedFrames	INTEGER,
		virtIfNonMemberFrames	INTEGER,
		virtIfAdminOverride	INTEGER,
		virtIfStatus		RowStatus,
		virtIfAutoPhysAddr	INTEGER,
		virtIfUsedPhysAddr	PhysAddress,
		virtIfRcvAllFrames	INTEGER,
		virtIfTransmitVlanId	INTEGER
	    }

	virtIfBaseSlot OBJECT-TYPE
	    SYNTAX  INTEGER (0..511)
	    MAX-ACCESS  read-write
	    STATUS      current

	    DESCRIPTION
		"The slot # the virtual interface is assigned to."
	::= { virtIfDefinitionEntry 1 }

	virtIfBaseUnit OBJECT-TYPE



	    SYNTAX  INTEGER (0..9)

	    MAX-ACCESS  read-write
	    STATUS      current

	    DESCRIPTION
		"The unit # the virtual interface is assigned to."
	::= { virtIfDefinitionEntry 2 }

	virtIfVirtChannel OBJECT-TYPE





	    SYNTAX  INTEGER (0..24)

	    MAX-ACCESS  read-write
	    STATUS      current

	    DESCRIPTION
		"The channel # the virtual interface is assigned to."
	::= { virtIfDefinitionEntry 3 }

	virtIfPhysAddr OBJECT-TYPE
	    SYNTAX  PhysAddress
	    MAX-ACCESS  read-write
	    STATUS      current

	    DESCRIPTION
		"Configured MAC-Address for the virtual interface. If
		 this is empty virtIfOrigPhysAddr will be used."
	::= { virtIfDefinitionEntry 4 }

	virtIfAdminStatus OBJECT-TYPE
	    SYNTAX  INTEGER {
		up(1),		-- virtual interface in use
		down(2),	-- virtual interface disabled
		delete(3)
	    }
	    MAX-ACCESS  read-write
	    STATUS      current

	    DESCRIPTION
		"Optional enable/disable of virtual interface operation.
		 This is useful for interfaces which are controlled by
		 special daemons like the BRRP daemon. The AdminStatus
		 of the interface is set according to the logical state
		 to the used protocol (like BRRP)."
	    DEFVAL { down }
	::= { virtIfDefinitionEntry 5 }

	virtIfVlanId OBJECT-TYPE
	    SYNTAX  INTEGER (-1..4094)
	    MAX-ACCESS  read-write
	    STATUS      current

	    DESCRIPTION
		"The VLAN-Tag-Id used for the virtual interface. 
		 "
	::= { virtIfDefinitionEntry 6 }

	virtIfOperMode OBJECT-TYPE
	    SYNTAX  INTEGER {
		manual(1),	-- set initial ifAdminStatus from ifTable
		vlan(2),	-- set initial ifAdminStatus from ifTable
		brrp(3),	-- set initial      "     from virtIfAdminStatus
		brrpOverVlan(4)
	    }
	    MAX-ACCESS  read-write
	    STATUS      current

	    DESCRIPTION
		"The intended operation mode of the interface. For use
		 with BRRP, the driver ignores the last saved ifAdminStatus
		 in the ifTable and sets the ifAdminStatus from the
		 virtIfAdminStatus defined above. The other currently defined
		 operation modes uses the saved ifAdminStatus."
	    DEFVAL { manual }
	::= { virtIfDefinitionEntry 7 }

	virtIfOrigPhysAddr OBJECT-TYPE
              SYNTAX  PhysAddress
              MAX-ACCESS  read-only
              STATUS      current
              DESCRIPTION
		    "The interface's factory MAC address."
	::= { virtIfDefinitionEntry 8 }

	virtIfBridgeIndex OBJECT-TYPE
	    SYNTAX  INTEGER
	    MAX-ACCESS  read-write
	    STATUS      current

	    DESCRIPTION
		"The BridgeIndex is used for assigning the virtual interface. 
		 to a specific bridge; -1 means, not connected to a bridge,
		 but used for routing."
	    DEFVAL { -1 }
	::= { virtIfDefinitionEntry 9 }

	virtIfUntaggedFrames OBJECT-TYPE
	    SYNTAX  INTEGER { drop(1), forward(2) }
	    MAX-ACCESS  read-write
	    STATUS      current

	    DESCRIPTION
		"Select for interfaces in Bridge Mode whether untagged
                 frames are dropped or forwarded."
	    DEFVAL { forward }
	::= { virtIfDefinitionEntry 10 }

	virtIfNonMemberFrames OBJECT-TYPE
	    SYNTAX  INTEGER { drop(1), forward(2) }
	    MAX-ACCESS  read-write
	    STATUS      current

	    DESCRIPTION
		"Select for interfaces in Bridge Mode whether non member
                 frames are dropped or forwarded."
	    DEFVAL { forward }
	::= { virtIfDefinitionEntry 11 }

	virtIfAdminOverride OBJECT-TYPE
	    SYNTAX  INTEGER {
	        off(1),
		up(2),
		down(3)
	    }
	    MAX-ACCESS  read-write
	    STATUS      current

	    DESCRIPTION
		"For use with BRRP; if value is off during configuation 
		 load ifAdminStatus of the interfaces is taken from saved
		 config, otherwise this OID ovrrides the saved ifAdminStatus."
	    DEFVAL { off }
	::= { virtIfDefinitionEntry 12 }

	virtIfStatus OBJECT-TYPE
	    SYNTAX  RowStatus
	    MAX-ACCESS  read-write
	    STATUS      current

	    DESCRIPTION
		"Status of this entry."
	::= { virtIfDefinitionEntry 13 }

	virtIfAutoPhysAddr OBJECT-TYPE
	    SYNTAX  INTEGER { enabled(1), disabled(2) }
	    MAX-ACCESS  read-write
	    STATUS      current

	    DESCRIPTION
		"Create a unique mac address for this interface. This
                 will make virtIfPhysAddr/virtIfOrigPhysAddr inactive.
                 The created MAC will show up in virtIfUsedPhysAddr."
	    DEFVAL { disabled }
	::= { virtIfDefinitionEntry 15 }
	
	virtIfUsedPhysAddr OBJECT-TYPE
	    SYNTAX  PhysAddress
	    MAX-ACCESS  read-only
	    STATUS      current

	    DESCRIPTION
		"MAC-Address used for the virtual interface. If
		 virtIfCreatePhysAddr is enabled a unique MAC
		 address will be created by the system. Otherwise
		 virtIfPhysAddr is used, or if it is empty virtIfOrigPhysAddr."
	::= { virtIfDefinitionEntry 25 }

	virtIfRcvAllFrames OBJECT-TYPE
	    SYNTAX  INTEGER { enabled(1), disabled(2) }
	    MAX-ACCESS  read-write
	    STATUS      current

	    DESCRIPTION
		"Select for interfaces in Routing Mode whether non member
                 frames are dropped (disabled) or forwarded (enabled)
		 For internal use only."
	    DEFVAL { disabled }
	::= { virtIfDefinitionEntry 16 }
	
	virtIfTransmitVlanId OBJECT-TYPE
	    SYNTAX  INTEGER (-1..4094)
	    MAX-ACCESS  read-write
	    STATUS      current

	    DESCRIPTION
		"VlanId used for transmitting frames. If this OID is -1
		 virtIfVlanId is used as VLAN-Tag-Id."
	    DEFVAL { -1 }
	::= { virtIfDefinitionEntry 17 }

	vlanTable OBJECT-TYPE
	    SYNTAX  SEQUENCE OF VlanEntry
	    MAX-ACCESS  not-accessible
	    STATUS  current
	    DESCRIPTION
		"The vlabTable contains information existing VLANs."
	::= { vif 2 }

	vlanEntry OBJECT-TYPE
	    SYNTAX  VlanEntry
	    MAX-ACCESS  not-accessible
	    STATUS      current

	    DESCRIPTION
		"Each entry contains a unique virtIfIndex and the physical
		 address used. The corresponding IP-Address musr be taken
		 from the ipAddressTable."
	    INDEX { vlanId }
	::= { vlanTable 1 }

	VlanEntry ::=
	    SEQUENCE {
		vlanId	        	INTEGER,
		vlanDescr		DisplayString,
		vlanStatus              RowStatus
	    }

	vlanId OBJECT-TYPE
	    SYNTAX  INTEGER (0..4095)
	    MAX-ACCESS  read-write
	    STATUS      current

	    DESCRIPTION
		"VLAN Id."
	::= { vlanEntry 1 }

	vlanDescr OBJECT-TYPE
	    SYNTAX  DisplayString (SIZE (0..32))
	    MAX-ACCESS  read-write
	    STATUS      current

	    DESCRIPTION
		"Description of the VLAN."
	::= { vlanEntry 2 }

	vlanStatus OBJECT-TYPE
	    SYNTAX      RowStatus
	    MAX-ACCESS  read-write
	    STATUS      current

	    DESCRIPTION
		"Status of this entry."
	::= { vlanEntry 3 }

	vlanMemberTable OBJECT-TYPE
	    SYNTAX  SEQUENCE OF VlanMemberEntry
	    MAX-ACCESS  not-accessible
	    STATUS  current
	    DESCRIPTION
		"The vlabMemberTable contains all members and configuration
		 of a VLAN defined in vlanTable."
	::= { vif 3 }

	vlanMemberEntry OBJECT-TYPE
	    SYNTAX  VlanMemberEntry
	    MAX-ACCESS  not-accessible
	    STATUS      current

	    DESCRIPTION
		"Each entry contains a unique virtIfIndex and the physical
		 address used. The corresponding IP-Address musr be taken
		 from the ipAddressTable."
	    INDEX { vlanMemberIfIndex, vlanMemberVlanId }
	::= { vlanMemberTable 1 }

	VlanMemberEntry ::=
	    SEQUENCE {
	        vlanMemberIfIndex       INTEGER,
		vlanMemberVlanId	INTEGER,
		vlanMemberEgress	INTEGER,
		vlanMemberStatus        RowStatus
	    }

	vlanMemberIfIndex OBJECT-TYPE
	    SYNTAX      INTEGER
	    MAX-ACCESS  read-write
	    STATUS      current

	    DESCRIPTION
		"Interface Index of the VLAN Member."
	::= { vlanMemberEntry 1 }
	
	vlanMemberVlanId OBJECT-TYPE
	    SYNTAX      INTEGER (0..4095)
	    MAX-ACCESS  read-write
	    STATUS      current

	    DESCRIPTION
		"VLAN Id of the VLAN member."
	::= { vlanMemberEntry 2 }

	vlanMemberEgress OBJECT-TYPE
	    SYNTAX      INTEGER { untagged(1), tagged(2), drop(3)}
	    MAX-ACCESS  read-write
	    STATUS      current

	    DESCRIPTION
		"Selects how frames will egress the interface."
	    DEFVAL { untagged }
	::= { vlanMemberEntry 3 }

	vlanMemberStatus OBJECT-TYPE
	    SYNTAX      RowStatus
	    MAX-ACCESS  read-write
	    STATUS      current

	    DESCRIPTION
		"Status of this entry."
	::= { vlanMemberEntry 4 }
	
END
