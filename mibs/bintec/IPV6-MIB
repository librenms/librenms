-- This file is corresponding to Release 10.2.3.100 from 2018/07/18 00:00:00


-- extracted from rfc2465.txt
-- at Mon Nov 15 17:11:40 1999

    IPV6-MIB DEFINITIONS ::= BEGIN

    IMPORTS
        MODULE-IDENTITY, OBJECT-TYPE, NOTIFICATION-TYPE, mib-2, Counter32,
        Unsigned32, Integer32, Gauge32
            FROM SNMPv2-SMI
        DisplayString, PhysAddress, TruthValue, TimeStamp, VariablePointer,
        RowPointer
            FROM SNMPv2-TC
        MODULE-COMPLIANCE, OBJECT-GROUP, NOTIFICATION-GROUP
            FROM SNMPv2-CONF
        InterfaceIndexOrZero, InterfaceIndex
            FROM IF-MIB
        InetAddressType, InetAddressIPv6, InetAddressIPv4, InetAddress
            FROM INET-ADDRESS-MIB
        IANAipRouteProtocol
            FROM IANA-RTPROTO-MIB
        IANAifType
            FROM IANAifType-MIB
        biboip
            FROM BINTEC-MIB;

    ip6MIB MODULE-IDENTITY
        LAST-UPDATED "201801100000Z"
        ORGANIZATION "bintec elmeg GmbH"
        CONTACT-INFO "EMail: info@bintec-elmeg.com
                      Web:   www.bintec-elmeg.com"
        DESCRIPTION
            "MIB module for bintec elmeg specific definitions used by entities
             implementing the IPv6 protocol."
        ::= { biboip 100 }

    ip6Config OBJECT IDENTIFIER ::= { ip6MIB 1 }
    ip6Stats  OBJECT IDENTIFIER ::= { ip6MIB 2 }
    ip6Debug  OBJECT IDENTIFIER ::= { ip6MIB 3 }


-- Start: Administrative: Global IPv6-settings

    ip6CfgGlobals OBJECT IDENTIFIER ::= { ip6Config 1 }

    ip6UniqueLocal OBJECT-TYPE
        SYNTAX      InetAddressIPv6
        MAX-ACCESS  read-write
        STATUS      current
        DESCRIPTION
            "The Locally Assigned Global Id for the locally assigned Prefix."
    ::= { ip6CfgGlobals 1 }

    ip6UniqueDUID OBJECT-TYPE
        SYNTAX      OCTET STRING
        MAX-ACCESS  read-only
        STATUS      current
        DESCRIPTION
            "The locally unique DUID used by internal DHCPv6-client and server
             (see 9, 22.2, 22.3 of RFC-3315)."
    ::= { ip6CfgGlobals 2 }

-- End: Administrative: Global IPv6-settings


-- Start: Administrative: IPv6-interfaces

   ip6AdmIfTable OBJECT-TYPE
        SYNTAX      SEQUENCE OF Ip6AdmIfEntry
        MAX-ACCESS  not-accessible
        STATUS      current
        DESCRIPTION
            "The IPv6 Interfaces table contains information
            on the entity's internetwork-layer interfaces.
            An IPv6 interface constitutes a logical network
            layer attachment to the layer immediately below
            IPv6 including internet layer 'tunnels', such as
            tunnels over IPv4 or IPv6 itself."
    ::= { ip6Config 2 }

    ip6AdmIfEntry OBJECT-TYPE
        SYNTAX      Ip6AdmIfEntry
        MAX-ACCESS  not-accessible
        STATUS      current
        DESCRIPTION
            "An interface entry containing objects
             about a particular IPv6 interface."
        INDEX   { ip6AdmIfIndex }
    ::= { ip6AdmIfTable 1 }

    Ip6AdmIfEntry ::= SEQUENCE {
        ip6AdmIfIndex               InterfaceIndex,
        ip6AdmIfIdentifier          InetAddressIPv6,
        ip6AdmIfAdvertise           INTEGER,
        ip6AdmIfPolicy              INTEGER,
        ip6AdmIfLifetime            INTEGER,
        ip6AdmIfPreference          INTEGER,
        ip6AdmIfAdminStatus         INTEGER,
        ip6AdmIfValidLifetime       INTEGER,
        ip6AdmIfMtu                 INTEGER,
        ip6AdmIfReachableTime       INTEGER,
        ip6AdmIfRetransTimer        Unsigned32,
        ip6AdmIfDhcpMode            INTEGER,
        ip6AdmIfAdvCurrHopLimit     INTEGER,
        ip6AdmIfMldMode             INTEGER,
        ip6AdmIfDhcpOffer           BITS,
        ip6AdmIfDnsAssign           INTEGER,
        ip6AdmIfAdvInterval         INTEGER,
        ip6AdmIfDhcpAddrMode        INTEGER
    }

    ip6AdmIfIndex OBJECT-TYPE
        SYNTAX      InterfaceIndex
        MAX-ACCESS  read-create
        STATUS      current
        DESCRIPTION
            "A unique non-zero value identifying the particular IPv6 interface."
    ::= { ip6AdmIfEntry 1 }

    ip6AdmIfIdentifier OBJECT-TYPE
        SYNTAX      InetAddressIPv6
        MAX-ACCESS  read-create
        STATUS      current
        DESCRIPTION
            "The interface's address at its protocol sub-layer.  For
             example, for an 802.x interface, this object normally
             contains a MAC address.  The interface's media-specific MIB
             must define the bit and byte ordering and the format of the
             value of this object.  For interfaces which do not have such
             an address (e.g., a serial line), this object should contain
             an octet string of zero length."
    ::= { ip6AdmIfEntry 2 }

    ip6AdmIfAdvertise OBJECT-TYPE
        SYNTAX      INTEGER {
            accept(1),
            publish(2),
            ignore(3)
        }
        MAX-ACCESS  read-create
        STATUS      current
        DESCRIPTION
            "The handling of router advertisments.
             accept  = accept routes
             publish = server mode, send advertisements
             ignore  = do not handle router advertisements"
        DEFVAL { ignore }
    ::= { ip6AdmIfEntry 3 }

    ip6AdmIfPolicy OBJECT-TYPE
        SYNTAX      INTEGER {
            untrusted(1),
            trusted(2)
        }
        MAX-ACCESS  read-create
        STATUS      current
        DESCRIPTION
            "The kind of connection.
             trusted    = Secure, filtering deactivated
             untrusted  = not secure (WAN) filter activated"
        DEFVAL { untrusted }
    ::= { ip6AdmIfEntry 4 }

    ip6AdmIfLifetime OBJECT-TYPE
        SYNTAX      INTEGER (0..65535)
        UNITS       "seconds"
        MAX-ACCESS  read-create
        STATUS      obsolete
        DESCRIPTION
            "Obsoleted: Replaced by new variable ip6AdmIfAdvInterval."
        DEFVAL { 600 }
    ::= { ip6AdmIfEntry 5 }

    ip6AdmIfPreference OBJECT-TYPE
        SYNTAX      INTEGER {
            high(1),
            medium(2),
            low(3)
        }
        MAX-ACCESS read-create
        STATUS     current
        DESCRIPTION
            "Priority of the router according RFC 2461."
        DEFVAL { medium }
    ::= { ip6AdmIfEntry 6 }

    ip6AdmIfAdminStatus OBJECT-TYPE
        SYNTAX      INTEGER {
            enable(1),
            disable(2),
            delete(3)
        }
        MAX-ACCESS  read-create
        STATUS      current
        DESCRIPTION
            "The Administration state of the entry."
        DEFVAL { enable }
    ::= { ip6AdmIfEntry 7 }

    ip6AdmIfValidLifetime OBJECT-TYPE
        SYNTAX      INTEGER (0..65535)
        UNITS       "seconds"
        MAX-ACCESS  read-create
        STATUS      current
        DESCRIPTION
            "Advertised router-lifetime in seconds for this interface.
             Relevant only if ip6AdmIfAdvertise is set to 'publish'.
             Typically, lifetime is NOT set here (zero value) but derived from
             ip6AdmIfAdvInterval instead (see AdvDefaultLifetime in RFC-4861)."
        DEFVAL { 0 }
    ::= { ip6AdmIfEntry 8 }

    ip6AdmIfMtu OBJECT-TYPE
        SYNTAX      INTEGER (0..4096)
        MAX-ACCESS  read-create
        STATUS      current
        DESCRIPTION
            "Normally 0. If set this MTU will be used instead of standard MTU."
        DEFVAL { 0 }
    ::= { ip6AdmIfEntry 9 }

    ip6AdmIfReachableTime OBJECT-TYPE
        SYNTAX      INTEGER (0..3600000)
        MAX-ACCESS  read-create
        STATUS      current
        DESCRIPTION
            "Defines the Value in mS of the Reachable Time
             field in the Router Advertisement (RA) message.
             0 is default and means unspecified."
        DEFVAL { 0 }
    ::= { ip6AdmIfEntry 10 }

    ip6AdmIfRetransTimer OBJECT-TYPE
        SYNTAX      Unsigned32
        MAX-ACCESS  read-create
        STATUS      current
        DESCRIPTION
            "Defines the Value in mS of the Retrans Timer
             field in the Router Advertisement (RA) message.
             0 is default and means unspecified."
        DEFVAL { 0 }
    ::= { ip6AdmIfEntry 11 }

    ip6AdmIfDhcpMode OBJECT-TYPE
        SYNTAX      INTEGER {
            off(1),
            client(2),
            server(3)
        }
        MAX-ACCESS  read-create
        STATUS      current
        DESCRIPTION
            "Defines DHCPv6-related behaviour on this interface."
        DEFVAL { client }
    ::= { ip6AdmIfEntry 12 }

   ip6AdmIfAdvCurrHopLimit OBJECT-TYPE
        SYNTAX      INTEGER {
            enable(1),
            disable(2)
        }
        MAX-ACCESS  read-create
        STATUS      current
        DESCRIPTION
            "Enable or disable transfer of default
             Hop Limit in Router Advertisement (RA)."
        DEFVAL { enable }
    ::= { ip6AdmIfEntry 13 }

    ip6AdmIfMldMode OBJECT-TYPE
        SYNTAX      INTEGER {
            off(1),
            auto(2),
            downstream(3),
            upstream(4)
        }
        MAX-ACCESS  read-create
        STATUS      current
        DESCRIPTION
            "Set the Mld Proxy Mode for this interface
                 off         disable all Mld Action
                 auto        use downstream to Link Prefix
                             upstream otherwise
                 dowstream   interface is downstream link
                 upstream    interface is upstream link"
        DEFVAL { off }
    ::= { ip6AdmIfEntry 14 }

    ip6AdmIfDhcpOffer OBJECT-TYPE
        SYNTAX      BITS {
            other(0),
            managed(1)
        }
        MAX-ACCESS  read-create
        STATUS      current
        DESCRIPTION
            "'Default-values' for 'ip6IfDhcpOffer' (see further description
             there). Processing depends on current value of ip6AdmIfAdvertise.
             - accept:
                 When ip6IfOperStatus goes up, 'ip6IfDhcpOffer' bits are
                 initialised to false and later updated to M/O-flags for
                 each received router-advertisement. However, if initial
                 solicitation for router-advertisements times-out, these
                 default-values are copied to ip6IfDhcpOffer as a substitute.
             - ignore/publish:
                 When ip6IfOperStatus goes up, 'ip6IfDhcpOffer' bits are
                 initialised to these default-values."
    ::= { ip6AdmIfEntry 15 }

    ip6AdmIfDnsAssign OBJECT-TYPE
        SYNTAX      INTEGER {
            off(1),
            self(2),
            other-ns(3)
        }
        MAX-ACCESS  read-create
        STATUS      current
        DESCRIPTION
            "Specifies DNS-propagation-policy via RA for this interface.
             For DHCPv6-case, if no 'ip6DhcpDnsServerOpt' entries match,
             this setting also applies as fall-back.
                 off       - Disable DNS-propagation
                 self      - Propagate own (prefix-associated) address
                 other_ns  - Propagate learned or configured name-servers"
        DEFVAL { off }
    ::= { ip6AdmIfEntry 16 }

    ip6AdmIfAdvInterval OBJECT-TYPE
        SYNTAX      INTEGER (0..65535)
        UNITS       "seconds"
        MAX-ACCESS  read-create
        STATUS      current
        DESCRIPTION
            "Time in seconds between unsolicited Router Advertisements
             (see MaxRtrAdvInterval in RFC-4861).
             Relevant only if ip6AdmIfAdvertise is set to 'publish'.
             Used also for calculating advertised router-lifetime unless
             explicitly specified by ip6AdmIfValidLifetime."
        DEFVAL { 600 }
    ::= { ip6AdmIfEntry 17 }

    ip6AdmIfDhcpAddrMode OBJECT-TYPE
        SYNTAX      INTEGER {
            auto(1),
            never(2),
            always(3)
        }
        MAX-ACCESS  read-create
        STATUS      current
        DESCRIPTION
            "Specifies how DHCPv6-client decides whether to request own
             IPv6-address for DHCPv6-server or not.
             - auto (default) : Request if managed bit of ip6IfDhcpOffer is set.
             - never : Never request own address.
             - always : Always request own address.
             This field is relevant only if ip6AdmIfDhcpMode is client."
        DEFVAL { auto }
    ::= { ip6AdmIfEntry 18 }

-- End: Administrative: IPv6-interfaces


-- Start: Administrative: Static IPv6-addresses

    ip6AdmAddrTable OBJECT-TYPE
        SYNTAX      SEQUENCE OF Ip6AdmAddrEntry
        MAX-ACCESS  not-accessible
        STATUS      current
        DESCRIPTION
            "This table contains administratively configured
             (static) IPv6-unicast-addresses."
    ::= { ip6Config 3 }

    ip6AdmAddrEntry OBJECT-TYPE
        SYNTAX      Ip6AdmAddrEntry
        MAX-ACCESS  not-accessible
        STATUS      current
        DESCRIPTION
            "A static address entry."
        INDEX   { ip6AdmAddrAddress,
                  ip6AdmAddrLength,
                  ip6AdmAddrIfIndex }
    ::= { ip6AdmAddrTable 1 }

    Ip6AdmAddrEntry ::= SEQUENCE {
        ip6AdmAddrAddress       InetAddressIPv6,
        ip6AdmAddrLength        INTEGER,
        ip6AdmAddrIfIndex       InterfaceIndex,
        ip6AdmAddrAdminStatus   INTEGER,
        ip6AdmAddrLkPrefixId    INTEGER
    }

    ip6AdmAddrAddress OBJECT-TYPE
        SYNTAX     InetAddressIPv6
        MAX-ACCESS read-write
        STATUS     current
        DESCRIPTION
            "The destination IPv6 address of this route.
             This object may not take a multicast address value."
    ::= { ip6AdmAddrEntry 1 }

    ip6AdmAddrLength OBJECT-TYPE
        SYNTAX      INTEGER (1..128)
        MAX-ACCESS  read-write
        STATUS      current
        DESCRIPTION
            "Indicates the prefix length of the address."
    ::= { ip6AdmAddrEntry 2 }

    ip6AdmAddrIfIndex OBJECT-TYPE
        SYNTAX      InterfaceIndex
        MAX-ACCESS  read-write
        STATUS      current
        DESCRIPTION
            "Indicates the Interface the address belongs to."
    ::= { ip6AdmAddrEntry 3 }

    ip6AdmAddrAdminStatus OBJECT-TYPE
        SYNTAX      INTEGER {
            enable(1),
            disable(2),
            delete(3)
        }
        MAX-ACCESS  read-write
        STATUS      current
        DESCRIPTION
            "The Administration state of the address entry."
        DEFVAL { enable }
    ::= { ip6AdmAddrEntry 4 }

    ip6AdmAddrLkPrefixId OBJECT-TYPE
        SYNTAX      INTEGER
        MAX-ACCESS  read-write
        STATUS      current
        DESCRIPTION
            "Referenece to ipLinkPrefixTable entries, used in order to merge
             the static (host) part of this address with the associated
             (probably dynamic) link prefix."
    ::= { ip6AdmAddrEntry 5 }

-- End: Administrative: Static IPv6-addresses


-- Start: Administrative: IPv6-prefixes

    ip6AdmPrefixTable OBJECT-TYPE
        SYNTAX  SEQUENCE OF Ip6AdmPrefixEntry
        MAX-ACCESS  not-accessible
        STATUS      current
        DESCRIPTION
            "The list of administratively configured IPv6-address-prefixes."
    ::= { ip6Config 4 }

    ip6AdmPrefixEntry OBJECT-TYPE
        SYNTAX      Ip6AdmPrefixEntry
        MAX-ACCESS  not-accessible
        STATUS      current
        DESCRIPTION
            "An interface entry containing objects of
             a particular IPv6 address prefix."
        INDEX   { ip6AdmPrefixId }
    ::= { ip6AdmPrefixTable 1 }

    Ip6AdmPrefixEntry ::= SEQUENCE {
         ip6AdmPrefixId             Unsigned32,
         ip6AdmPrefixIfIndex        InterfaceIndexOrZero,
         ip6AdmPrefixAdminStatus    INTEGER,
         ip6AdmPrefixType           INTEGER,
         ip6AdmPrefixPrefix         InetAddressIPv6,
         ip6AdmPrefixLength         INTEGER,
         ip6AdmPrefixNextHop        InetAddressIPv6,
         ip6AdmPrefixSlaac          INTEGER,
         ip6AdmPrefixDescr          DisplayString
    }

    ip6AdmPrefixId OBJECT-TYPE
        SYNTAX      Unsigned32
        MAX-ACCESS  read-create
        STATUS      current
        DESCRIPTION
            "A unique non-zero value identifying the particular IPv6 prefix."
        DEFVAL { 0 }
    ::= { ip6AdmPrefixEntry 1 }

    ip6AdmPrefixIfIndex OBJECT-TYPE
        SYNTAX      InterfaceIndexOrZero
        MAX-ACCESS  read-create
        STATUS      current
        DESCRIPTION
            "A unique non-zero value identifying
             the particular IPv6 interface or relay."
    ::= { ip6AdmPrefixEntry 2 }

    ip6AdmPrefixAdminStatus OBJECT-TYPE
        SYNTAX      INTEGER {
            enable(1),
            disable(2),
            delete(3)
        }
        MAX-ACCESS  read-create
        STATUS      current
        DESCRIPTION
            "The administrative status of this entry."
        DEFVAL { enable }
    ::= { ip6AdmPrefixEntry 3 }

    ip6AdmPrefixType OBJECT-TYPE
        SYNTAX      INTEGER {
            dynamic(1),
            static(2)
        }
        MAX-ACCESS  read-create
        STATUS      current
        DESCRIPTION
            "The type of the prefix associated with the this interface."
        DEFVAL { static }
    ::= { ip6AdmPrefixEntry 4 }

    ip6AdmPrefixPrefix OBJECT-TYPE
        SYNTAX      InetAddressIPv6
        MAX-ACCESS  read-create
        STATUS      current
        DESCRIPTION
            "The prefix associated with the this interface."
    ::= { ip6AdmPrefixEntry 5 }

    ip6AdmPrefixLength OBJECT-TYPE
        SYNTAX      INTEGER (0..128)
        MAX-ACCESS  read-create
        STATUS      current
        DESCRIPTION
            "The length of the prefix (in bits)."
        DEFVAL { 64 }
    ::= { ip6AdmPrefixEntry 6 }

    ip6AdmPrefixNextHop OBJECT-TYPE
        SYNTAX      InetAddressIPv6
        MAX-ACCESS  read-create
        STATUS      current
        DESCRIPTION
            "The next hop associated with this prefix."
    ::= { ip6AdmPrefixEntry 7 }

    ip6AdmPrefixSlaac OBJECT-TYPE
        SYNTAX  INTEGER {
            eui64(1),
--          privacyy-ext(2),
            disabled(3)
        }
        MAX-ACCESS  read-create
        STATUS      current
        DESCRIPTION
            "SLAAC method, this setting determines the address format which
             should be the result of the address autoconfiguration procedure
                 eui64          EUI-64-Identifier according RFC 4291
                 privacy-ext    Privacy Extensions according RFC 4941
                 disabled       no SLAAC"
        DEFVAL { disabled }
    ::= { ip6AdmPrefixEntry 8 }

    ip6AdmPrefixDescr OBJECT-TYPE
        SYNTAX      DisplayString
        MAX-ACCESS  read-create
        STATUS      current
        DESCRIPTION
            "User defined description of this prefix entry"
    ::= { ip6AdmPrefixEntry 9 }

-- End: Administrative: IPv6-prefixes


-- Start: Administrative: Static IPv6-routes

    ip6AdmRouteTable OBJECT-TYPE
        SYNTAX      SEQUENCE OF Ip6AdmRouteEntry
        MAX-ACCESS  not-accessible
        STATUS      current
        DESCRIPTION
            "IPv6 Routing table. This table contains an entry
             for each valid IPv6 unicast route that can be
             used for packet forwarding determination."
    ::= { ip6Config 5 }

    ip6AdmRouteEntry OBJECT-TYPE
        SYNTAX      Ip6AdmRouteEntry
        MAX-ACCESS  not-accessible
        STATUS      current
        DESCRIPTION
            "A administrative routing entry."
        INDEX   { ip6AdmRouteTarget,
                  ip6AdmRouteTargetLen,
                  ip6AdmRouteSource,
                  ip6AdmRouteSourceLen,
                  ip6AdmRoutePriority }
    ::= { ip6AdmRouteTable 1 }

    Ip6AdmRouteEntry ::= SEQUENCE {
        ip6AdmRouteTarget       InetAddressIPv6,
        ip6AdmRouteTargetLen    INTEGER,
        ip6AdmRouteSource       InetAddressIPv6,
        ip6AdmRouteSourceLen    INTEGER,
        ip6AdmRouteIfIndex      InterfaceIndex,
        ip6AdmRouteAdminStatus  INTEGER,
        ip6AdmRouteNextHop      InetAddressIPv6,
        ip6AdmRoutePriority     INTEGER,
        ip6AdmRouteDescr        DisplayString
    }

    ip6AdmRouteTarget OBJECT-TYPE
        SYNTAX      InetAddressIPv6
        MAX-ACCESS  read-write
        STATUS      current
        DESCRIPTION
            "The destination IPv6 address of this route.
             This object may not take a Multicast address value."
    ::= { ip6AdmRouteEntry 1 }

    ip6AdmRouteTargetLen OBJECT-TYPE
        SYNTAX      INTEGER(0..128)
        MAX-ACCESS  read-write
        STATUS      current
        DESCRIPTION
            "Indicates the prefix length of the destination address."
    ::= { ip6AdmRouteEntry 2 }

    ip6AdmRouteSource OBJECT-TYPE
        SYNTAX      InetAddressIPv6
        MAX-ACCESS  read-write
        STATUS      current
        DESCRIPTION
            "The Source IPv6 address of this route.
             This object may not take a Multicast address value."
    ::= { ip6AdmRouteEntry 3 }

    ip6AdmRouteSourceLen OBJECT-TYPE
        SYNTAX      INTEGER(0..128)
        MAX-ACCESS  read-write
        STATUS      current
        DESCRIPTION
            "Indicates the prefix length of the source address."
        DEFVAL { 64 }
    ::= { ip6AdmRouteEntry 4 }

    ip6AdmRouteIfIndex OBJECT-TYPE
        SYNTAX      InterfaceIndex
        MAX-ACCESS  read-write
        STATUS      current
        DESCRIPTION
            "The index value which uniquely identifies the local
             interface through which the next hop of this
             route should be reached.  The interface identified
             by a particular value of this index is the same
             interface as identified by the same value of
             ip6DeviceIfIndex. For routes of the discard type this
             value can be zero."
    ::= { ip6AdmRouteEntry 5 }

    ip6AdmRouteNextHop OBJECT-TYPE
        SYNTAX      InetAddressIPv6
        MAX-ACCESS  read-write
        STATUS      current
        DESCRIPTION
            "On remote routes, the address of the next hop, otherwise set to ::"
    ::= { ip6AdmRouteEntry 6 }

    ip6AdmRouteAdminStatus OBJECT-TYPE
        SYNTAX      INTEGER {
            enable(1),
            disable(2),
            delete(3)
        }
        MAX-ACCESS  read-write
        STATUS      current
        DESCRIPTION
            "The administrative status of this routing entry."
        DEFVAL { enable }
    ::= { ip6AdmRouteEntry 7 }

    ip6AdmRoutePriority OBJECT-TYPE
        SYNTAX      INTEGER (0..16)
        MAX-ACCESS  read-write
        STATUS      current
        DESCRIPTION
            "The routing priority for this route,
             a value of 0 means highest priority,
             a value of 16 lowest priority."
        DEFVAL { 8 }
    ::= { ip6AdmRouteEntry 8 }

    ip6AdmRouteDescr OBJECT-TYPE
        SYNTAX      DisplayString
        MAX-ACCESS  read-write
        STATUS      current
        DESCRIPTION
            "User defined description of this routing entry"
    ::= { ip6AdmRouteEntry 9 }

-- End: Administrative: Static IPv6-routes


-- Start: Administrative/Operative: IPv6-link-prefixes

    ip6LinkPrefixTable OBJECT-TYPE
        SYNTAX      SEQUENCE OF Ip6LinkPrefixEntry
        MAX-ACCESS  not-accessible
        STATUS      current
        DESCRIPTION
            "This table lists the administratively configured
             downstream-link-prefixes"
    ::= { ip6Config 6 }

    ip6LinkPrefixEntry OBJECT-TYPE
        SYNTAX      Ip6LinkPrefixEntry
        MAX-ACCESS  not-accessible
        STATUS      current
        DESCRIPTION
            "A link prefix entry."
        INDEX   { ip6LinkPrefixIfIndex,
                  ip6LinkPrefixId }
    ::= { ip6LinkPrefixTable 1 }

    Ip6LinkPrefixEntry ::= SEQUENCE {
        ip6LinkPrefixIfIndex                InterfaceIndex,
        ip6LinkPrefixPrefixId               INTEGER,
        ip6LinkPrefixAdminStatus            INTEGER,
        ip6LinkPrefixSiteLevelValue         Unsigned32,
        ip6LinkPrefixLength                 INTEGER,
        ip6LinkPrefixOnLinkFlag             INTEGER,
        ip6LinkPrefixAutonomousFlag         INTEGER,
        ip6LinkPrefixAdvValidLifetime       Unsigned32,
        ip6LinkPrefixAdvPreferredLifetime   Unsigned32,
        ip6LinkPrefixPrefix                 InetAddressIPv6,
        ip6LinkPrefixOperStatus             INTEGER,
        ip6LinkPrefixId                     INTEGER,
        ip6LinkPrefixSlaac                  INTEGER,
        ip6LinkPrefixAdvertise              INTEGER,
        ip6LinkPrefixDescr                  DisplayString,
        ip6LinkPrefixAdmPrefix              InetAddressIPv6,
        ip6LinkPrefixDhcpOptionSetId        INTEGER,
        ip6LinkPrefixOpValidLifetime        Unsigned32,
        ip6LinkPrefixOpPreferredLifetime    Unsigned32
    }

    ip6LinkPrefixIfIndex OBJECT-TYPE
        SYNTAX      InterfaceIndex
        MAX-ACCESS  read-write
        STATUS      current
        DESCRIPTION
            "Interface on which the prefix will published."
    ::= { ip6LinkPrefixEntry 1 }

    ip6LinkPrefixPrefixId OBJECT-TYPE
        SYNTAX      INTEGER
        MAX-ACCESS  read-write
        STATUS      current
        DESCRIPTION
            "Ident of the associated administrative prefix,
             see ip6AdmPrefixEntryTable."
    ::= { ip6LinkPrefixEntry 2 }

    ip6LinkPrefixAdminStatus OBJECT-TYPE
        SYNTAX      INTEGER {
            enable(1),
            disable(2),
            delete(3)
        }
        MAX-ACCESS  read-write
        STATUS      current
        DESCRIPTION
            "Administrative status of this entry."
        DEFVAL { enable }
    ::= { ip6LinkPrefixEntry 3 }

    ip6LinkPrefixSiteLevelValue OBJECT-TYPE
        SYNTAX      Unsigned32
        MAX-ACCESS  read-write
        STATUS      current
        DESCRIPTION
            "SiteLevel Identifier SLA."
        DEFVAL { 0 }
    ::= { ip6LinkPrefixEntry 4 }

    ip6LinkPrefixLength OBJECT-TYPE
        SYNTAX      INTEGER (48..64)
        MAX-ACCESS  read-write
        STATUS      current
        DESCRIPTION
            "The Length of the new generated prefix,"
        DEFVAL { 64 }
    ::= { ip6LinkPrefixEntry 5 }

    ip6LinkPrefixOnLinkFlag OBJECT-TYPE
        SYNTAX      INTEGER {
            true(1),
            false(2)
        }
        MAX-ACCESS  read-write
        STATUS      current
        DESCRIPTION
            "true: prefix can be used for on-link determination"
        DEFVAL { false }
    ::= { ip6LinkPrefixEntry 6 }

    ip6LinkPrefixAutonomousFlag OBJECT-TYPE
        SYNTAX      INTEGER {
            true(1),
            false(2)
        }
        MAX-ACCESS  read-write
        STATUS      current
        DESCRIPTION
            "Determines whether the Autonomous address configuration flag
             within the Router Advertisement Message (RFC 4861) should be set
             or not.
             true:  set the flag - stateless configuration possible
             false: don't set the flag - no autoconfiguration possible"
        DEFVAL { true }
    ::= { ip6LinkPrefixEntry 7 }

    ip6LinkPrefixAdvValidLifetime OBJECT-TYPE
        SYNTAX      Unsigned32
        UNITS       "seconds"
        MAX-ACCESS  read-write
        STATUS      current
        DESCRIPTION
            "Configured maximum 'valid lifetime'. More details are
             described for field 'ip6LinkPrefixOpValidLifetime'."
        DEFVAL { 2592000 }
    ::= { ip6LinkPrefixEntry 8 }

    ip6LinkPrefixAdvPreferredLifetime OBJECT-TYPE
        SYNTAX      Unsigned32
        UNITS       "seconds"
        MAX-ACCESS  read-write
        STATUS      current
        DESCRIPTION
            "Configured maximum 'prefered lifetime'. More details are
             described for field 'ip6LinkPrefixOpPreferredLifetime'."
        DEFVAL { 604800 }
    ::= { ip6LinkPrefixEntry 9 }

    ip6LinkPrefixPrefix OBJECT-TYPE
        SYNTAX      InetAddressIPv6
        MAX-ACCESS  read-only
        STATUS      current
        DESCRIPTION
            "The current used prefix for this link."
    ::= { ip6LinkPrefixEntry 10 }

    ip6LinkPrefixOperStatus OBJECT-TYPE
        SYNTAX      INTEGER {
            up(1),
            down(2)
        }
        MAX-ACCESS  read-only
        STATUS      current
        DESCRIPTION
            "The operational status."
        DEFVAL { down }
    ::= { ip6LinkPrefixEntry 11 }

    ip6LinkPrefixId OBJECT-TYPE
        SYNTAX      INTEGER
        MAX-ACCESS  read-write
        STATUS      current
        DESCRIPTION
            "Unique ID of this table-entry."
    ::= { ip6LinkPrefixEntry 12 }

    ip6LinkPrefixSlaac OBJECT-TYPE
        SYNTAX      INTEGER {
            eui64(1),
--          privacy-ext(2),
            disabled(3)
        }
        MAX-ACCESS  read-write
        STATUS      current
        DESCRIPTION
            "SLAAC method, this setting determines the address format which
             should be the result of the address autoconfiguration procedure
                 eui64          EUI-64-Identifier according RFC 4291
                 privacy-ext    Privacy Extensions according RFC 4941
                 disabled       no SLAAC"
        DEFVAL { eui64 }
    ::= { ip6LinkPrefixEntry 13 }

    ip6LinkPrefixAdvertise OBJECT-TYPE
        SYNTAX      INTEGER {
            enabled(1),
            disabled(2)
        }
        MAX-ACCESS  read-write
        STATUS      current
        DESCRIPTION
            "Specifies the propagation policy for this entry when sending
             a Router Advertisement (RA) via the associated interface
                 enabled        include prefix in RA
                 disabled       ignore this prefix when sending RA's"
        DEFVAL { enabled }
    ::= { ip6LinkPrefixEntry 14 }

    ip6LinkPrefixDescr OBJECT-TYPE
        SYNTAX      DisplayString
        MAX-ACCESS  read-write
        STATUS      current
        DESCRIPTION
            "User defined description of this link prefix entry"
    ::= { ip6LinkPrefixEntry 15 }

   ip6LinkPrefixAdmPrefix OBJECT-TYPE
        SYNTAX      InetAddressIPv6
        MAX-ACCESS  read-write
        STATUS      current
        DESCRIPTION
            "The configured prefix for this link - without any reference
             to a general prefix."
    ::= { ip6LinkPrefixEntry 16 }

    ip6LinkPrefixDhcpOptionSetId OBJECT-TYPE
        SYNTAX      INTEGER (0..65535)
        MAX-ACCESS  read-write
        STATUS      current
        DESCRIPTION
            "If not set to 0 and if 'ip6DhcpOptionSet' entry with matching 'Id'
             value exists then internal DHCPv6-server uses this prefix for
             building requested IA_NA options (see 22.4 and 22.6 of RFC-3315).
             In this case, 'ip6LinkPrefixOnLinkFlag' must be set to 'true' and
             'ip6LinkPrefixAutonomousFlag' must be set to 'false' for proper
             configuration."
    ::= { ip6LinkPrefixEntry 17 }

    ip6LinkPrefixOpValidLifetime OBJECT-TYPE
        SYNTAX      Unsigned32
        UNITS       "seconds"
        MAX-ACCESS  read-only
        STATUS      current
        DESCRIPTION
            "'Operative' valid lifetime. If 'ip6LinkPrefixPrefixId'
             does NOT refer to valid 'ip6Prefix' then lifetime is set
             to configured 'ip6LinkPrefixAdvValidLifetime'. Otherwise,
             it is set to minimum of configured value and inherited
             'ip6PrefixAdvValidLifetime'."
    ::= { ip6LinkPrefixEntry 18 }

    ip6LinkPrefixOpPreferredLifetime OBJECT-TYPE
        SYNTAX      Unsigned32
        UNITS       "seconds"
        MAX-ACCESS  read-only
        STATUS      current
        DESCRIPTION
            "'Operative' preferred lifetime. If 'ip6LinkPrefixPrefixId'
             does NOT refer to valid 'ip6Prefix' then lifetime is set
             to configured 'ip6LinkPrefixAdvPreferredLifetime'. Otherwise,
             it is set to minimum of configured value and inherited
             'ip6PrefixAdvPreferredLifetime'."
    ::= { ip6LinkPrefixEntry 19 }

-- End: Administrative/Operative: IPv6-link-prefixes


-- Start: Administrative/Operative: 6to4-relay-interfaces

    ip6RelayTable OBJECT-TYPE
        SYNTAX      SEQUENCE OF Ip6RelayEntry
        MAX-ACCESS  not-accessible
        STATUS      current
        DESCRIPTION
            "IPv6 to v4 tunnel configuration table."
    ::= { ip6Config 7 }

    ip6RelayEntry OBJECT-TYPE
        SYNTAX      Ip6RelayEntry
        MAX-ACCESS  not-accessible
        STATUS      current
        DESCRIPTION
            "Each entry contains one IPv6 address to `physical'
             address equivalence."
        INDEX   { ip6RelayIfIndexV6 }
    ::= { ip6RelayTable 1 }

    Ip6RelayEntry ::= SEQUENCE {
        ip6RelayIfIndexV6           InterfaceIndexOrZero,
        ip6RelayDescr               DisplayString,
        ip6RelayIfIndexV4           InterfaceIndexOrZero,
        ip6RelayType                INTEGER,
        ip6RelayLocalAddress        InetAddressIPv6,
        ip6RelayRemoteAddress       InetAddressIPv6,
        ip6RelayMtu                 INTEGER,
        ip6RelayPOP                 InetAddressIPv4,
        ip6RelayInterval            INTEGER,
        ip6RelaySecret              DisplayString,
        ip6RelayTICUser             DisplayString,
        ip6RelayTICSecret           DisplayString,
        ip6RelayTICTunnel           DisplayString,
        ip6RelayTICHost             DisplayString,
        ip6RelayUsedLocalAddress    InetAddressIPv6,
        ip6RelayUsedRemoteAddress   InetAddressIPv6,
        ip6RelayUsedMtu             INTEGER,
        ip6RelayUsedPOP             InetAddressIPv4,
        ip6RelayUsedSrc             InetAddressIPv4,
        ip6RelayUsedInterval        INTEGER,
        ip6RelayUsedSecret          DisplayString,
        ip6RelayOperStatus          INTEGER
    }

    ip6RelayIfIndexV6 OBJECT-TYPE
        SYNTAX      InterfaceIndexOrZero
        MAX-ACCESS  read-create
        STATUS      current
        DESCRIPTION
            "Unique Identifier for this entry"
    ::= { ip6RelayEntry 1 }

    ip6RelayDescr OBJECT-TYPE
        SYNTAX      DisplayString
        MAX-ACCESS  read-create
        STATUS      current
        DESCRIPTION
            "Description or name of this entry."
    ::= { ip6RelayEntry 2 }

    ip6RelayIfIndexV4 OBJECT-TYPE
        SYNTAX      InterfaceIndexOrZero
        MAX-ACCESS  read-create
        STATUS      current
        DESCRIPTION
            "Specifies the associated IPv4 interface for this relay."
    ::= { ip6RelayEntry 3 }

    ip6RelayType OBJECT-TYPE
        SYNTAX      INTEGER {
            stf(1),
            stf-tic(2),
            stf-he(3),
            delete(16)
        }
        MAX-ACCESS  read-create
        STATUS      current
        DESCRIPTION
            "Type of the tunnel."
        DEFVAL { stf }
    ::= { ip6RelayEntry 4 }

    ip6RelayLocalAddress OBJECT-TYPE
        SYNTAX      InetAddressIPv6
        MAX-ACCESS  read-create
        STATUS      current
        DESCRIPTION
            "Assigned local IPv6 endpoint address"
    ::= { ip6RelayEntry 5 }

    ip6RelayRemoteAddress OBJECT-TYPE
        SYNTAX      InetAddressIPv6
        MAX-ACCESS  read-create
        STATUS      current
        DESCRIPTION
            "Remote IPv6 endpoint address"
    ::= { ip6RelayEntry 6 }

    ip6RelayMtu OBJECT-TYPE
        SYNTAX      INTEGER (1280..4095)
        MAX-ACCESS  read-create
        STATUS      current
        DESCRIPTION
            "Mtu value for this tunnel."
        DEFVAL { 1280 }
    ::= { ip6RelayEntry 7 }

    ip6RelayPOP OBJECT-TYPE
        SYNTAX      InetAddressIPv4
        MAX-ACCESS  read-create
        STATUS      current
        DESCRIPTION
            "IPv4 address for the relay gateway."
    ::= { ip6RelayEntry 8 }

    ip6RelayInterval OBJECT-TYPE
        SYNTAX      INTEGER
        MAX-ACCESS  read-create
        STATUS      current
        DESCRIPTION
            "Schedule interval for heartbeats."
        DEFVAL { 60 }
    ::= { ip6RelayEntry 9 }

    ip6RelaySecret OBJECT-TYPE
        SYNTAX      DisplayString
        MAX-ACCESS  read-create
        STATUS      current
        DESCRIPTION
            "Password or authentication phrase for heartbeats."
        DEFVAL { "" }
    ::= { ip6RelayEntry 10 }

    ip6RelayTICUser OBJECT-TYPE
        SYNTAX      DisplayString
        MAX-ACCESS  read-create
        STATUS      current
        DESCRIPTION
            "TIC protocol user name."
        DEFVAL { "" }
    ::= { ip6RelayEntry 11 }

    ip6RelayTICSecret OBJECT-TYPE
        SYNTAX      DisplayString
        MAX-ACCESS  read-create
        STATUS      current
        DESCRIPTION
            "TIC protocol password."
        DEFVAL { "" }
    ::= { ip6RelayEntry 12 }

    ip6RelayTICTunnel OBJECT-TYPE
        SYNTAX      DisplayString
        MAX-ACCESS  read-create
        STATUS      current
        DESCRIPTION
            "TIC tunnel ID."
        DEFVAL { "" }
    ::= { ip6RelayEntry 13 }

    ip6RelayTICHost OBJECT-TYPE
        SYNTAX      DisplayString
        MAX-ACCESS  read-create
        STATUS      current
        DESCRIPTION
            "TIC server address."
        DEFVAL { "" }
    ::= { ip6RelayEntry 14 }

    ip6RelayUsedLocalAddress OBJECT-TYPE
        SYNTAX      InetAddressIPv6
        MAX-ACCESS  read-only
        STATUS      current
        DESCRIPTION
            "Assigned local IPv6 address."
    ::= { ip6RelayEntry 15 }

    ip6RelayUsedRemoteAddress OBJECT-TYPE
        SYNTAX      InetAddressIPv6
        MAX-ACCESS  read-only
        STATUS      current
        DESCRIPTION
            "Assigned remote IPv6 address."
    ::= { ip6RelayEntry 16 }

    ip6RelayUsedMtu OBJECT-TYPE
        SYNTAX      INTEGER (1280..4095)
        MAX-ACCESS  read-only
        STATUS      current
        DESCRIPTION
            "Mtu value for this tunnel."
        DEFVAL { 1280 }
    ::= { ip6RelayEntry 17 }

    ip6RelayUsedPOP OBJECT-TYPE
        SYNTAX      InetAddressIPv4
        MAX-ACCESS  read-only
        STATUS      current
        DESCRIPTION
            "IPv4 address of the associated relay gateway."
    ::= { ip6RelayEntry 18 }

    ip6RelayUsedSrc OBJECT-TYPE
        SYNTAX      InetAddressIPv4
        MAX-ACCESS  read-only
        STATUS      current
        DESCRIPTION
            "The local IPv4 address used for this tunnel."
    ::= { ip6RelayEntry 19 }

    ip6RelayUsedInterval OBJECT-TYPE
        SYNTAX      INTEGER (0..3600)
        MAX-ACCESS  read-only
        STATUS      current
        DESCRIPTION
            "Schedule interval for the heartbeats."
        DEFVAL { 60 }
    ::= { ip6RelayEntry 20 }

    ip6RelayUsedSecret OBJECT-TYPE
        SYNTAX      DisplayString
        MAX-ACCESS  read-only
        STATUS      current
        DESCRIPTION
            "TIC server address."
        DEFVAL { "" }
    ::= { ip6RelayEntry 21 }

    ip6RelayOperStatus OBJECT-TYPE
        SYNTAX      INTEGER {
            up(1),
            down(2),
            update(3),
            authenticate(4),
            failed(5)
        }
        MAX-ACCESS  read-only
        STATUS      current
        DESCRIPTION
            "The current operational status of this tunnel."
        DEFVAL { down }
    ::= { ip6RelayEntry 22 }

-- End: Administrative/Operative: 6to4-relay-interfaces


-- Start: Administrative: IPv6-SIF/firewall-rules

    ip6SifAliasTable OBJECT-TYPE
        SYNTAX      SEQUENCE OF Ip6SifAliasEntry
        ACCESS      not-accessible
        STATUS      mandatory
        DESCRIPTION
            "Contains a IPv6 'Stateful Inspection Firewall' (SIF) policy."
    ::= { ip6Config 8 }

    ip6SifAliasEntry OBJECT-TYPE
        SYNTAX      Ip6SifAliasEntry
        ACCESS      not-accessible
        STATUS      mandatory
        DESCRIPTION
            ""
        INDEX   { ip6SifAliasOrder }
    ::= { ip6SifAliasTable 1 }

    Ip6SifAliasEntry ::= SEQUENCE {
        ip6SifAliasOrder        INTEGER,
        ip6SifAliasSource       INTEGER,
        ip6SifAliasDestination  INTEGER,
        ip6SifAliasService      INTEGER,
        ip6SifAliasAction       INTEGER,
        ip6SifAliasStatus       INTEGER,
        ip6SifAliasPriority     INTEGER,
        ip6SifAliasClassId      INTEGER,
        ip6SifAliasDscp         INTEGER
    }

    ip6SifAliasOrder OBJECT-TYPE
        SYNTAX      INTEGER
        ACCESS      read-write
        STATUS      mandatory
        DESCRIPTION
            "The configured order (implict priority) for this
             'Stateful Inspection Firewall' (SIF) rule."
    ::= { ip6SifAliasEntry 1 }

    ip6SifAliasSource OBJECT-TYPE
        SYNTAX      INTEGER
        ACCESS      read-write
        STATUS      mandatory
        DESCRIPTION
            "The source index associated with this rule."
    ::= { ip6SifAliasEntry 2 }

    ip6SifAliasDestination OBJECT-TYPE
        SYNTAX      INTEGER
        ACCESS      read-write
        STATUS      mandatory
        DESCRIPTION
            "The destination index associated with this rule."
    ::= { ip6SifAliasEntry 3 }

    ip6SifAliasService OBJECT-TYPE
        SYNTAX      INTEGER
        ACCESS      read-write
        STATUS      mandatory
        DESCRIPTION
            "The protocol/service associated with this rule."
    ::= { ip6SifAliasEntry 4 }

    ip6SifAliasAction OBJECT-TYPE
        SYNTAX      INTEGER {
            access(1),
            deny(2),
            reject(3),
            delete(255)
        }
        ACCESS      read-write
        STATUS      mandatory
        DESCRIPTION
            "The policy associated with this rule."
        DEFVAL { access }
    ::= { ip6SifAliasEntry 5 }

    ip6SifAliasStatus OBJECT-TYPE
        SYNTAX      INTEGER {
            enabled(1),
            disabled(2)
        }
        ACCESS      read-write
        STATUS      mandatory
        DESCRIPTION
            "Defines the administrative status of this rule."
        DEFVAL { enabled }
    ::= { ip6SifAliasEntry 6 }

    ip6SifAliasPriority OBJECT-TYPE
        SYNTAX      INTEGER {
            default(1),
            low-latency(2),
            high(3),
            medium(4),
            low(5)
        }
        ACCESS      read-write
        STATUS      mandatory
        DESCRIPTION
            "Defines the QoS priority associated with this rule."
        DEFVAL { default }
    ::= { ip6SifAliasEntry 7 }

    ip6SifAliasClassId OBJECT-TYPE
        SYNTAX      INTEGER  (0..255)
        ACCESS      read-write
        STATUS      mandatory
        DESCRIPTION
            "Internal ID for SIF policy to QoS policy mapping"
    ::= { ip6SifAliasEntry 8 }

    ip6SifAliasDscp OBJECT-TYPE
        SYNTAX      INTEGER  (0..63)
        ACCESS      read-write
        STATUS      mandatory
        DESCRIPTION
            "DSCP value to be set for signalling"
    ::= { ip6SifAliasEntry 9 }

-- End: Administrative: IPv6-SIF/firewall-rules


-- Start: Administrative/Operative: Dual Stack Lite (DsLite, 4in6) interfaces

    ip6DsLiteTable OBJECT-TYPE
        SYNTAX      SEQUENCE OF Ip6DsLiteEntry
        ACCESS      not-accessible
        STATUS      mandatory
        DESCRIPTION
            "Contains a DsLite (4in6) configuration."
    ::= { ip6Config 9 }

    ip6DsLiteEntry OBJECT-TYPE
        SYNTAX      Ip6DsLiteEntry
        ACCESS      not-accessible
        STATUS      mandatory
        DESCRIPTION
            ""
        INDEX   { ip6DsLiteIfIndexV4,
                  ip6DsLiteIfIndexV6 }
    ::= { ip6DsLiteTable 1 }

    Ip6DsLiteEntry ::= SEQUENCE {
        ip6DsLiteIfIndexV4          InterfaceIndexOrZero,
        ip6DsLiteIfIndexV6          InterfaceIndex,
        ip6DsLiteDescr              DisplayString,
        ip6DsLiteConfigMode         INTEGER,
        ip6DsLiteEncapsulation      INTEGER,
        ip6DsLiteLocalAddress       InetAddressIPv6,
        ip6DsLiteRemoteAddress      InetAddressIPv6,
        ip6DsLiteUsedLocalAddress   InetAddressIPv6,
        ip6DsLiteUsedRemoteAddress  InetAddressIPv6,
        ip6DsLiteAftrFqdn           DisplayString
    }

    ip6DsLiteIfIndexV4 OBJECT-TYPE
        SYNTAX      InterfaceIndexOrZero
        ACCESS      read-write
        STATUS      mandatory
        DESCRIPTION
            "Unique Identifier for this entry"
    ::= { ip6DsLiteEntry 1 }

    ip6DsLiteIfIndexV6 OBJECT-TYPE
        SYNTAX      InterfaceIndex
        ACCESS      read-write
        STATUS      mandatory
        DESCRIPTION
            "Specifies the associated IPv6 interface for this entry."
    ::= { ip6DsLiteEntry 2 }

    ip6DsLiteDescr OBJECT-TYPE
        SYNTAX      DisplayString
        ACCESS      read-write
        STATUS      mandatory
        DESCRIPTION
            "Description for the DsLite connection"
    ::= { ip6DsLiteEntry 3 }

    ip6DsLiteConfigMode OBJECT-TYPE
        SYNTAX      INTEGER {
            static(1),
            dhcp(2),
            delete(8)
        }
        ACCESS      read-write
        STATUS      mandatory
        DESCRIPTION
            "Configuration mode of the tunnel addresse."
        DEFVAL { static }
    ::= { ip6DsLiteEntry 4 }

    ip6DsLiteEncapsulation OBJECT-TYPE
        SYNTAX      INTEGER {
            ipip(1),
            none(16)
        }
        ACCESS      read-write
        STATUS      mandatory
        DESCRIPTION
            "The encapsulation used for this tunnel."
        DEFVAL { ipip }
    ::= { ip6DsLiteEntry 5 }

    ip6DsLiteLocalAddress OBJECT-TYPE
        SYNTAX      InetAddressIPv6
        ACCESS      read-write
        STATUS      mandatory
        DESCRIPTION
            "Static configured local IPv6 address of ithis tunnel."
    ::= { ip6DsLiteEntry 6 }

    ip6DsLiteRemoteAddress OBJECT-TYPE
        SYNTAX      InetAddressIPv6
        ACCESS      read-write
        STATUS      mandatory
        DESCRIPTION
            "DsLite tunnel endpoint IPv6 address."
    ::= { ip6DsLiteEntry 7 }

    ip6DsLiteUsedLocalAddress OBJECT-TYPE
        SYNTAX      InetAddressIPv6
        ACCESS      read-only
        STATUS      mandatory
        DESCRIPTION
            "Used local IPv6 address of this tunnel."
    ::= { ip6DsLiteEntry 8 }

    ip6DsLiteUsedRemoteAddress OBJECT-TYPE
        SYNTAX      InetAddressIPv6
        ACCESS      read-only
        STATUS      mandatory
        DESCRIPTION
            "Used tunnel endpoint IPv6 address of this tunnel."
    ::= { ip6DsLiteEntry 9 }

    ip6DsLiteAftrFqdn OBJECT-TYPE
        SYNTAX DisplayString
        ACCESS read-write
        STATUS mandatory
        DESCRIPTION
            "FQDN of the associated Address Family Transition Router (AFTR).
             Will be used and resolved as long as there is no static AFTR
             address (ip6DsLiteRemoteAddress) given."
    ::= { ip6DsLiteEntry 10 }

-- End: Administrative/Operative: Dual Stack Lite (DsLite, 4in6) interfaces


-- Start: Operative: IPv6-interfaces

    ip6IfTable OBJECT-TYPE
        SYNTAX      SEQUENCE OF Ip6IfEntry
        MAX-ACCESS  not-accessible
        STATUS      current
        DESCRIPTION
            "A list of interface entries.  The number of entries is
             given by the value of ifNumber."
    ::= { ip6Stats 2 }

    ip6IfEntry OBJECT-TYPE
        SYNTAX      Ip6IfEntry
        MAX-ACCESS  not-accessible
        STATUS      current
        DESCRIPTION
            "An entry containing management information applicable to a
             particular interface."
        INDEX   { ip6IfIndex }
    ::= { ip6IfTable 1 }

    Ip6IfEntry ::= SEQUENCE {
        ip6IfIndex              InterfaceIndex,
        ip6IfDescr              DisplayString,
        ip6IfIdentifier         InetAddressIPv6,
        ip6IfHopLimit           INTEGER,
        ip6IfLifetime           INTEGER,
        ip6IfPreference         INTEGER,
        ip6IfDhcpOffer          BITS,
        ip6IfMtu                INTEGER,
        ip6IfOperStatus         INTEGER,
        ip6IfLastChange         TimeStamp,
        ip6IfMldOperMode        INTEGER,
        ip6IfDnsAssign          INTEGER,
        ip6IfSlaacStatus        INTEGER,
        ip6IfDhcpClientStatus   INTEGER,
        ip6IfDhcpClientTxCount  INTEGER
    }

    ip6IfIndex OBJECT-TYPE
        SYNTAX      InterfaceIndex
        MAX-ACCESS  read-only
        STATUS      current
        DESCRIPTION
            "A unique value, greater than zero, for each interface.  It
             is recommended that values are assigned contiguously
             starting from 1.  The value for each interface sub-layer
             must remain constant at least from one re-initialization of
             the entity's network management system to the next re-
             initialization."
    ::= { ip6IfEntry 1 }

    ip6IfDescr OBJECT-TYPE
        SYNTAX      DisplayString
        MAX-ACCESS  read-only
        STATUS      current
        DESCRIPTION
            "The description or name of the interface."
    ::= { ip6IfEntry 2 }

    ip6IfIdentifier OBJECT-TYPE
        SYNTAX      InetAddressIPv6
        MAX-ACCESS  read-only
        STATUS      current
        DESCRIPTION
            "The interface's address at its protocol sub-layer.  For
             example, for an 802.x interface, this object normally
             contains a MAC address.  The interface's media-specific MIB
             must define the bit and byte ordering and the format of the
             value of this object.  For interfaces which do not have such
             an address (e.g., a serial line), this object should contain
             an octet string of zero length."
    ::= { ip6IfEntry 3 }

    ip6IfHopLimit OBJECT-TYPE
        SYNTAX      INTEGER(0..255)
        MAX-ACCESS  read-only
        STATUS      current
        DESCRIPTION
            "The default value inserted into the Hop Limit
             field of the IPv6 header of datagrams originated
             at this entity, whenever a Hop Limit value is not
             supplied by the transport layer protocol."
        DEFVAL  { 64 }
    ::= { ip6IfEntry 4 }

    ip6IfLifetime OBJECT-TYPE
        SYNTAX      INTEGER (0..65535)
        UNITS       "seconds"
        MAX-ACCESS  read-only
        STATUS      current
        DESCRIPTION
            "Depending on value of ip6AdmIfAdvertise, tells learned or
             advertised default-router-lifetime in seconds for this link."
        DEFVAL { 1800 }
    ::= { ip6IfEntry 5 }

    ip6IfPreference OBJECT-TYPE
        SYNTAX      INTEGER {
            high(1),
            medium(2),
            low(3)
        }
        MAX-ACCESS  read-only
        STATUS      current
        DESCRIPTION
            "Priority of router."
        DEFVAL { medium }
    ::= { ip6IfEntry 6 }

    ip6IfDhcpOffer OBJECT-TYPE
        SYNTAX      BITS {
            other(0),
            managed(1)
        }
        MAX-ACCESS  read-only
        STATUS      current
        DESCRIPTION
            "DHCPv6-services offered on this interface
             (see O and M bits in 4.2 of RFC-4861).
             - other:   'Stateless' info like DNS-servers.
             - managed: 'Stateful'  info like IPv6-addresses.
             Current value is copied from received router-advertisement
             or from default-values in ip6AdmIfDhcpOffer (see further
             description there).
             If internal DHCPv6-client is activated for this interface via
             ip6AdmIfDhcpMode then it checks these bits for deciding whether
             to send DHCPv6-messages on this interface or not.
             If sending of router-advertisements is activated for this
             interface via ip6AdmIfAdvertise then the included M/O-flags
             are taken from this field."
    ::= { ip6IfEntry 7 }

    ip6IfMtu OBJECT-TYPE
        SYNTAX      INTEGER (0..4095)
        MAX-ACCESS  read-only
        STATUS      current
        DESCRIPTION
            "The size of the largest packet which can be sent/received
             on the interface, specified in octets. For interfaces that
             are used for transmitting network datagrams, this is the
             size of the largest network datagram that can be sent on the
             interface."
        DEFVAL { 1492 }
    ::= { ip6IfEntry 8 }

    ip6IfOperStatus OBJECT-TYPE
        SYNTAX      INTEGER {
            down(9),
            dormant(10),
            dialup(11),
            noSAP(12),
            noAddr(13),
            up(14)
        }
        MAX-ACCESS  read-only
        STATUS      current
        DESCRIPTION
            "The current operational status of the interface.
             - down:
                 Lower layers of this interface are not yet ready and
                 cannot be triggered vie IPv6-routing.
             - dormant:
                 Lower layers of this interface are not yet ready but
                 can be triggered via IPv6-routing.
             - dialup:
                 Lower layers of this interface are not yet ready but
                 have already been triggered via IPv6-routing.
             - noSAP:
                 Lower layers of this interface are ready but IPv6-service
                 has not yet been activated.
             - noAddr:
                 IPv6-service has been activated on this interface but
                 valid link-local address not yet available (usually means
                 that duplicate-address-detection yet pending).
             - up:
                 IPv6-service has been activated on this interface and
                 valid link-local address is available."
        DEFVAL { down }
    ::= { ip6IfEntry 9 }

    ip6IfLastChange OBJECT-TYPE
        SYNTAX      TimeStamp
        MAX-ACCESS  read-only
        STATUS      current
        DESCRIPTION
            "The value of sysUpTime at the time the interface entered
             its current operational state. If the current state was
             entered prior to the last re-initialization of the local
             network management subsystem, then this object contains a
             zero value."
    ::= { ip6IfEntry 10 }

    ip6IfMldOperMode OBJECT-TYPE
        SYNTAX      INTEGER {
            off(1),
            downstream(3),
            upstream(4)
        }
        MAX-ACCESS  read-only
        STATUS      current
        DESCRIPTION
            "Shows the current 'Mld Proxy Mode' for this interface
                 off         no Mld functionality
                 dowstream   interface is downstream link
                 upstream    interface is upstream link"
        DEFVAL { off }
    ::= { ip6IfEntry 11 }

    ip6IfDnsAssign OBJECT-TYPE
        SYNTAX      INTEGER {
            off(1),
            self(2),
            other-ns(3)
        }
        MAX-ACCESS  read-only
        STATUS      current
        DESCRIPTION
            "Specifies DNS-propagation-policy via RA for this interface.
             For DHCPv6-case, if no 'ip6DhcpDnsServerOpt' entries match,
             this setting also applies as fall-back.
                 off       - Disable DNS-propagation
                 self      - Propagate own (prefix-associated) address
                 other_ns  - Propagate learned or configured name-servers"
        DEFVAL { off }
    ::= { ip6IfEntry 12 }

    ip6IfSlaacStatus OBJECT-TYPE
        SYNTAX      INTEGER {
            disabled(1),
            wait-ifc(2),
            solicit-ra(3),
            wait-periodic-ra(4)
        }
        MAX-ACCESS  read-only
        STATUS      current
        DESCRIPTION
            "Current operation-status of stateless address-auto-configuration
             (see RFC-4862) for this interface.
             - disabled:
                 Administratively disabled
                 (ip6AdmIfAdvertise != accept).
             - wait_ifc:
                 Waiting (maybe endlessly) for interface to get up
                 (ip6IfOperStatus != up).
             - solicit_ra:
                 Sending (limited number of) router-solicitations,
                 waiting for answering router-advertisements.
             - wait_periodic_ra:
                 Waiting for periodic router-advertisements
                 (stopped sending router-solitations)."
        DEFVAL { disabled }
    ::= { ip6IfEntry 13 }

    ip6IfDhcpClientStatus OBJECT-TYPE
        SYNTAX      INTEGER {
            disabled(1),
            wait-ifc(2),
            wait-changed-mo(3),
            solicit(4),
            request(5),
            idle(6),
            release(7),
            decline(8),
            renew(9),
            rebind(10)
        }
        MAX-ACCESS  read-only
        STATUS      current
        DESCRIPTION
            "Current operation-status of DHCPv6-client (see RFC-3315) for this
             interface.
             - disabled:
                 Administratively disabled
                 (ip6AdmIfDhcpMode != client).
             - wait_ifc:
                 Waiting (maybe endlessly) for interface to get up
                 (ip6IfOperStatus != up).
             - wait_changed_mo:
                 Waiting for the M or O flag in ip6IfDhcpOffer (both 'false')
                 to be updated to 'true', indicating that DHCPv6-service is
                 available (again) on this interface.
             - solicit:
                 Sending DHCPv6-solicit messages.
             - request:
                 Sending DHCPv6-request messages.
             - idle:
                 Not sending any messages, waiting for idle-timer to expire
                 (T1 in stateful case, proprietary update-period otherwise).
             - release:
                 Sending DHCPv6-release messages.
             - decline:
                 Sending DHCPv6-decline messages.
             - renew:
                 Sending DHCPv6-renew messages.
             - rebind:
                 Sending DHCPv6-rebind messages."
        DEFVAL { disabled }
    ::= { ip6IfEntry 14 }

    ip6IfDhcpClientTxCount OBJECT-TYPE
        SYNTAX      INTEGER
        MAX-ACCESS  read-only
        STATUS      current
        DESCRIPTION
            "Counts number of sent DHCPv6-frames.
             Is reset to 0 whenever ip6IfDhcpClientStatus changes.
             Frame-type depends on current ip6IfDhcpClientStatus:
             - disabled, wait_ifc, wait_changed_mo, idle:
                 No frames are counted. Value is always 0.
             - solicit:
                 DHCPv6-solicit frames are counted.
             - request:
                 DHCPv6-request frames are counted."
    ::= { ip6IfEntry 15 }

-- End: Operative: IPv6-interfaces


-- Start: Operative: IPv6-prefixes

    ip6PrefixTable OBJECT-TYPE
        SYNTAX      SEQUENCE OF Ip6PrefixEntry
        MAX-ACCESS  not-accessible
        STATUS      current
        DESCRIPTION
            "The list of IPv6 address prefixes of IPv6 interfaces."
    ::= { ip6Stats 3 }

    ip6PrefixEntry OBJECT-TYPE
        SYNTAX      Ip6PrefixEntry
        MAX-ACCESS  not-accessible
        STATUS      current
        DESCRIPTION
            "An interface entry containing objects of
             a particular IPv6 address prefix."
        INDEX   { ip6PrefixId }
    ::= { ip6PrefixTable 1 }

    Ip6PrefixEntry ::= SEQUENCE {
        ip6PrefixId                     Unsigned32,
        ip6PrefixIfIndex                InterfaceIndexOrZero,
        ip6PrefixPrefix                 InetAddressIPv6,
        ip6PrefixLength                 INTEGER,
        ip6PrefixOnLinkFlag             INTEGER,
        ip6PrefixAutonomousFlag         INTEGER,
        ip6PrefixAdvValidLifetime       Unsigned32,
        ip6PrefixAdvPreferredLifetime   Unsigned32,
        ip6PrefixNextHop                InetAddressIPv6,
        ip6PrefixType                   INTEGER,
        ip6PrefixAge                    TimeStamp,
        ip6PrefixOperStatus             INTEGER,
        ip6PrefixSlaac                  INTEGER
    }

    ip6PrefixId OBJECT-TYPE
        SYNTAX      Unsigned32
        MAX-ACCESS  read-only
        STATUS      current
        DESCRIPTION
            "A unique non-zero value identifying the particular IPv6 prefix."
        DEFVAL { 0 }
    ::= { ip6PrefixEntry 1 }

    ip6PrefixIfIndex OBJECT-TYPE
        SYNTAX      InterfaceIndexOrZero
        MAX-ACCESS  read-only
        STATUS      current
        DESCRIPTION
            "A unique non-zero value identifying
             the particular IPv6 interface (or relay) index."
    ::= { ip6PrefixEntry 2 }

    ip6PrefixPrefix OBJECT-TYPE
        SYNTAX      InetAddressIPv6
        MAX-ACCESS  read-only
        STATUS      current
        DESCRIPTION
            "The prefix associated with the this interface."
    ::= { ip6PrefixEntry 3 }

    ip6PrefixLength OBJECT-TYPE
        SYNTAX      INTEGER (0..128)
        MAX-ACCESS  read-only
        STATUS      current
        DESCRIPTION
            "The length of the prefix (in bits)."
    ::= { ip6PrefixEntry 4 }

    ip6PrefixOnLinkFlag OBJECT-TYPE
        SYNTAX      INTEGER {
            true(1),
            false(2)
        }
        MAX-ACCESS  read-only
        STATUS      current
        DESCRIPTION
            "true: Prefix can be used for on-link determination"
        DEFVAL { false }
    ::= { ip6PrefixEntry 5 }

    ip6PrefixAutonomousFlag OBJECT-TYPE
        SYNTAX      INTEGER {
            true(1),
            false(2)
        }
        MAX-ACCESS  read-only
        STATUS      current
        DESCRIPTION
            "true:  stateless configuration possible
             false: no autoconfiguration possible"
        DEFVAL { true }
    ::= { ip6PrefixEntry 6 }

    ip6PrefixAdvValidLifetime OBJECT-TYPE
        SYNTAX      Unsigned32
        UNITS       "seconds"
        MAX-ACCESS  read-only
        STATUS      current
        DESCRIPTION
            "The value in seconds the prefix will remain valid."
    ::= { ip6PrefixEntry 7 }

    ip6PrefixAdvPreferredLifetime OBJECT-TYPE
        SYNTAX      Unsigned32
        UNITS       "seconds"
        MAX-ACCESS  read-only
        STATUS      current
        DESCRIPTION
            "The length in seconds the prefix will remain preferred."
    ::= { ip6PrefixEntry 8 }

    ip6PrefixNextHop OBJECT-TYPE
        SYNTAX      InetAddressIPv6
        MAX-ACCESS  read-only
        STATUS      current
        DESCRIPTION
            "The prefix associated with the this interface."
    ::= { ip6PrefixEntry 9 }

    ip6PrefixType OBJECT-TYPE
        SYNTAX      INTEGER {
            dynamic(1),
            static(2)
        }
        MAX-ACCESS  read-only
        STATUS      current
        DESCRIPTION
            "The working mode of the prefix."
        DEFVAL { static }
    ::= { ip6PrefixEntry 10 }

    ip6PrefixAge OBJECT-TYPE
        SYNTAX      TimeStamp
        MAX-ACCESS  read-only
        STATUS      current
        DESCRIPTION
            "The timestamp of last update of the prefix. "
    ::= { ip6PrefixEntry 11 }

    ip6PrefixOperStatus OBJECT-TYPE
        SYNTAX      INTEGER  {
            up(1),
            down(2)
        }
        MAX-ACCESS  read-only
        STATUS      current
        DESCRIPTION
            "The current status of the prefix
                 up         prefix is valid
                 down       prefix is not valid"
        DEFVAL { down }
    ::= { ip6PrefixEntry 12 }

    ip6PrefixSlaac OBJECT-TYPE
        SYNTAX      INTEGER  {
            eui64(1),
            privacy-ext(2),
            none(3)
        }
        MAX-ACCESS  read-only
        STATUS      current
        DESCRIPTION
            "SLAAC method, in conjunction with the ip6PrefixAutonomousFlag this
             setting determines the address format which should be the result of
             the address autoconfiguration procedure
                 eui64          EUI-64-Identifier according RFC 4291
                 privacy-ext    Privacy Extensions according RFC 4941
                 none           no SLAAC will be performed"
        DEFVAL { none }
    ::= { ip6PrefixEntry 13 }

-- End: Operative: IPv6-prefixes


-- Start: Operative: IPv6-addresses

    ip6AddrTable OBJECT-TYPE
        SYNTAX      SEQUENCE OF Ip6AddrEntry
        MAX-ACCESS  not-accessible
        STATUS      current
        DESCRIPTION
            "List of own interface-addresses currently used by this node."
    ::= { ip6Stats 4 }

    ip6AddrEntry OBJECT-TYPE
        SYNTAX      Ip6AddrEntry
        MAX-ACCESS  not-accessible
        STATUS      current
        DESCRIPTION
            ""
        INDEX   { ip6AddrIfIndex, ip6AddrAddress }
    ::= { ip6AddrTable 1 }

    Ip6AddrEntry ::= SEQUENCE {
        ip6AddrIfIndex      InterfaceIndex,
        ip6AddrPrefix       Unsigned32,
        ip6AddrLength       INTEGER,
        ip6AddrAddress      InetAddressIPv6,
        ip6AddrScope        INTEGER,
        ip6AddrType         INTEGER,
        ip6AddrLkPrefix     Unsigned32
    }

    ip6AddrIfIndex OBJECT-TYPE
        SYNTAX      InterfaceIndex
        MAX-ACCESS  read-create
        STATUS      current
        DESCRIPTION
            "ip6IfIndex of related interface."
    ::= { ip6AddrEntry 1 }

    ip6AddrPrefix OBJECT-TYPE
        SYNTAX      Unsigned32
        MAX-ACCESS  read-only
        STATUS      current
        DESCRIPTION
            "ip6PrefixId of related ip6Prefix-entry, if any, else 0."
    ::= { ip6AddrEntry 2 }

    ip6AddrLength OBJECT-TYPE
        SYNTAX      INTEGER (1..128)
        MAX-ACCESS  read-only
        STATUS      current
        DESCRIPTION
            "Length of related prefix."
        DEFVAL { 64 }
    ::= { ip6AddrEntry 3 }

    ip6AddrAddress OBJECT-TYPE
        SYNTAX      InetAddressIPv6
        MAX-ACCESS  read-only
        STATUS      current
        DESCRIPTION
            "Address-value."
    ::= { ip6AddrEntry 4 }

    ip6AddrScope OBJECT-TYPE
        SYNTAX     INTEGER {
            linklocal(2),
            global(14)
        }
        MAX-ACCESS  read-only
        STATUS      current
        DESCRIPTION
            "Scope of this address."
        DEFVAL { linklocal }
    ::= { ip6AddrEntry 5 }

    ip6AddrType OBJECT-TYPE
        SYNTAX      INTEGER {
            stateless(1),
            stateful(2),
            static(3),
            anycast(4),
            unknown(5)
        }
        MAX-ACCESS  read-only
        STATUS      current
        DESCRIPTION
            "'Type' of this address.
                 stateless(1) - Auto-configured (see RFC-4862).
                 stateful(2)  - Learned from DHCPv6-server.
                 static(3)    - Configured via ip6AdmAddr-entry.
                 anycast(4)   - Dummy-entry for anycast-receipt.
                 unknown(5)   - Used for debugging only."
        DEFVAL { unknown }
    ::= { ip6AddrEntry 6 }

    ip6AddrLkPrefix OBJECT-TYPE
        SYNTAX      Unsigned32
        MAX-ACCESS  read-only
        STATUS      current
        DESCRIPTION
            "ip6LinkPrefixId of related ip6LinkPrefix-entry, if any, else 0."
    ::= { ip6AddrEntry 7 }

-- End: Operative: IPv6-addresses


-- Start: Operative: IPv6-routes

    ip6RouteTable OBJECT-TYPE
        SYNTAX      SEQUENCE OF Ip6RouteEntry
        MAX-ACCESS  not-accessible
        STATUS      current
        DESCRIPTION
            "IPv6 Routing table. This table contains
             an entry for each valid IPv6 unicast route
             that can be used for packet forwarding
             determination."
    ::= { ip6Stats 5 }

    ip6RouteEntry OBJECT-TYPE
        SYNTAX      Ip6RouteEntry
        MAX-ACCESS  not-accessible
        STATUS      current
        DESCRIPTION
            "A routing entry."
        INDEX   { ip6RouteSource,
                  ip6RouteSourceLen,
                  ip6RouteTarget,
                  ip6RouteTargetLen,
                  ip6RouteMetric }
    ::= { ip6RouteTable 1 }

    Ip6RouteEntry ::= SEQUENCE {
        ip6RouteTarget      InetAddressIPv6,
        ip6RouteTargetLen   INTEGER,
        ip6RouteSource      InetAddressIPv6,
        ip6RouteSourceLen   INTEGER,
        ip6RouteNextHop     InetAddressIPv6,
        ip6RouteIfIndex     InterfaceIndexOrZero,
        ip6RouteProtocol    INTEGER,
        ip6RouteMetric      Unsigned32,
        ip6RouteLifetime    Unsigned32,
        ip6RoutePrefix      Integer32,
        ip6RouteAge         TimeStamp
    }

    ip6RouteTarget OBJECT-TYPE
        SYNTAX      InetAddressIPv6
        MAX-ACCESS  read-only
        STATUS      current
        DESCRIPTION
            "The destination IPv6 address of this route.
             This object may not take a multicast address value."
    ::= { ip6RouteEntry 1 }

    ip6RouteTargetLen OBJECT-TYPE
        SYNTAX      INTEGER(0..128)
        MAX-ACCESS  read-only
        STATUS      current
        DESCRIPTION
            "Indicates the prefix length of the destination address."
    ::= { ip6RouteEntry 2 }

   ip6RouteSource OBJECT-TYPE
        SYNTAX      InetAddressIPv6
        MAX-ACCESS  read-only
        STATUS      current
        DESCRIPTION
            "The Source IPv6 address of this route.
             This object may not take a multicast address value."
    ::= { ip6RouteEntry 3 }

    ip6RouteSourceLen OBJECT-TYPE
        SYNTAX      INTEGER(0..128)
        MAX-ACCESS  read-only
        STATUS      current
        DESCRIPTION
            "Indicates the prefix length of the source address."
    ::= { ip6RouteEntry 4 }

    ip6RouteIfIndex OBJECT-TYPE
        SYNTAX      InterfaceIndexOrZero
        MAX-ACCESS  read-only
        STATUS      current
        DESCRIPTION
            "The index value which uniquely identifies the local
             interface through which the next hop of this
             route should be reached.  The interface identified
             by a particular value of this index is the same
             interface as identified by the same value of
             ip6AdmIfIfIndex.  For routes of the discard type this
             value can be zero."
    ::= { ip6RouteEntry 5 }

    ip6RouteNextHop OBJECT-TYPE
        SYNTAX      InetAddressIPv6
        MAX-ACCESS  read-only
        STATUS      current
        DESCRIPTION
            "On remote routes, the address of the next hop of this routing
             entry, set to ::  otherwise."
    ::= { ip6RouteEntry 6 }

    ip6RouteProtocol OBJECT-TYPE
        SYNTAX      INTEGER {
            static(1),  -- adminuistrative configured entry

            netmgmt(2), -- routes generated by system

                        -- obtained via Neighbor
                        -- Discovery protocol,
            ndisc(3),   -- e.g., result of Redirect

                        -- the following are all
                        -- dynamic routing protocols
            rip(4),     -- RIPng
            ospf(5),    -- Open Shortest Path First
            bgp(6),     -- Border Gateway Protocol
            idrp(7),    -- InterDomain Routing Protocol
            dhcp-pd(8)  -- DHCPv6-prefix-delegation
        }
        MAX-ACCESS  read-only
        STATUS      current
        DESCRIPTION
            "The routing mechanism via which this route was learned."
        DEFVAL { netmgmt }
    ::= { ip6RouteEntry 7 }

    ip6RouteMetric OBJECT-TYPE
        SYNTAX      Unsigned32
        MAX-ACCESS  read-only
        STATUS      current
        DESCRIPTION
            "The routing metric for this route. The
             semantics of this metric are determined by the
             routing protocol specified in the route's
             ip6RouteProtocol value.  When this is unknown
             or not relevant to the protocol indicated by
             ip6RouteProtocol, the object value should be
             set to its maximum value (4,294,967,295)."
    ::= { ip6RouteEntry 8 }

    ip6RouteLifetime OBJECT-TYPE
        SYNTAX      Unsigned32
        UNITS       "seconds"
        MAX-ACCESS  read-only
        STATUS      current
        DESCRIPTION
            "The number of seconds the routing entry is valid"
    ::= { ip6RouteEntry 9 }

    ip6RoutePrefix OBJECT-TYPE
        SYNTAX      Integer32
        MAX-ACCESS  read-only
        STATUS      current
        DESCRIPTION
            "The value which identifies the global prefix
             of the source address using this route."
    ::= { ip6RouteEntry 10 }

    ip6RouteAge OBJECT-TYPE
        SYNTAX      TimeStamp
        MAX-ACCESS  read-only
        STATUS      current
        DESCRIPTION
            "The number of seconds since this route was last
             updated or otherwise determined to be correct.
             Note that no semantics of `too old' can be implied
             except through knowledge of the routing protocol
             by which the route was learned."
    ::= { ip6RouteEntry 11 }

-- End: Operative: IPv6-routes


-- Start: Operative: TCP-over-IPv6-connections

    ip6TcpConnTable OBJECT-TYPE
        SYNTAX      SEQUENCE OF Ip6TcpConnEntry
        MAX-ACCESS  not-accessible
        STATUS      current
        DESCRIPTION
            "This table contains info on TCP-connections where endpoints
             have IPv6-addresses.
             For IPv4-endpoints, info is stored in tcpConnTable instead."
    ::= { ip6Stats 6 }

    ip6TcpConnEntry OBJECT-TYPE
        SYNTAX      Ip6TcpConnEntry
        MAX-ACCESS  not-accessible
        STATUS      current
        DESCRIPTION
            "A conceptual row of the ip6TcpConnTable containing
             information about a particular current TCP connection.
             Each row of this table is transient, in that it ceases to
             exist when (or soon after) the connection makes the transition
             to the CLOSED state.
             Note that conceptual rows in this table require an additional
             index object compared to tcpConnTable, since IPv6 addresses
             are not guaranteed to be unique on the managed node."
        INDEX   { ip6TcpConnLocalAddress,
                  ip6TcpConnLocalPort,
                  ip6TcpConnRemAddress,
                  ip6TcpConnRemPort,
                  ip6TcpConnIfIndex }
    ::= { ip6TcpConnTable 1 }

    Ip6TcpConnEntry ::= SEQUENCE {
        ip6TcpConnLocalAddress  InetAddressIPv6,
        ip6TcpConnLocalPort     INTEGER (0..65535),
        ip6TcpConnRemAddress    InetAddressIPv6,
        ip6TcpConnRemPort       INTEGER (0..65535),
        ip6TcpConnIfIndex       InterfaceIndexOrZero,
        ip6TcpConnState         INTEGER
    }

    ip6TcpConnLocalAddress OBJECT-TYPE
        SYNTAX      InetAddressIPv6
        MAX-ACCESS  read-only
        STATUS      current
        DESCRIPTION
            "The local IPv6 address for this TCP connection. In
             the case of a connection in the listen state which
             is willing to accept connections for any IPv6 address
             associated with the managed node, the value ::0 is used."
    ::= { ip6TcpConnEntry 1 }

    ip6TcpConnLocalPort OBJECT-TYPE
        SYNTAX      INTEGER (0..65535)
        MAX-ACCESS  read-only
        STATUS      current
        DESCRIPTION
            "The local port number for this TCP connection."
    ::= { ip6TcpConnEntry 2 }

    ip6TcpConnRemAddress OBJECT-TYPE
        SYNTAX      InetAddressIPv6
        MAX-ACCESS  read-only
        STATUS      current
        DESCRIPTION
            "The remote IPv6 address for this TCP connection."
    ::= { ip6TcpConnEntry 3 }

    ip6TcpConnRemPort OBJECT-TYPE
        SYNTAX      INTEGER (0..65535)
        MAX-ACCESS  read-only
        STATUS      current
        DESCRIPTION
            "The remote port number for this TCP connection."
    ::= { ip6TcpConnEntry 4 }

    ip6TcpConnIfIndex OBJECT-TYPE
        SYNTAX      InterfaceIndexOrZero
        MAX-ACCESS  read-only
        STATUS      current
        DESCRIPTION
            "This index disambiguates the conceptual rows of this table,
             since the connection-4-tuple may not be unique.
             If the connection's remote-address (ip6TcpConnRemAddress)
             is a link-local address and the connection's local address
             (ip6TcpConnLocalAddress) is not a link-local address, this
             object identifies a local interface on the same link as
             the connection's remote link-local address.
             Otherwise, this object identifies the local interface that
             is associated with the ip6TcpConnLocalAddress for this
             TCP connection.
             If such a local interface cannot be determined, this object
             should take on the value 0. (A possible example would be if
             the value of ip6TcpConnLocalAddress is ::0.)
             The interface identified by a particular non-0 value of this
             index is the same interface as identified by the same value
             of ip6IfIndex.
             The value of this object must remain constant during the life
             of the TCP connection."
    ::= { ip6TcpConnEntry 5 }

    ip6TcpConnState OBJECT-TYPE
        SYNTAX      INTEGER {
            closed(1),
            listen(2),
            synSent(3),
            synReceived(4),
            established(5),
            finWait1(6),
            finWait2(7),
            closeWait(8),
            lastAck(9),
            closing(10),
            timeWait(11),
            deleteTCB(12)
        }
        MAX-ACCESS  read-write
        STATUS      current
        DESCRIPTION
            "The state of this TCP connection.
             The only value which may be set by a management station is
             deleteTCB(12).  Accordingly, it is appropriate for an agent
             to return an error response (`badValue' for SNMPv1, 'wrongValue'
             for SNMPv2) if a management station attempts to set this
             object to any other value.
             If a management station sets this object to the value
             deleteTCB(12), then this has the effect of deleting the TCB
             (as defined in RFC 793) of the corresponding connection on
             the managed node, resulting in immediate termination of the
             connection.
             As an implementation-specific option, a RST segment may be
             sent from the managed node to the other TCP endpoint (note
             however that RST segments are not sent reliably)."
             DEFVAL { closed }
    ::= { ip6TcpConnEntry 6 }

-- End: Operative: TCP-over-IPv6-connections


-- Start: Operative: IPv6-net-to-media-cache

    ip6NetToMediaTable OBJECT-TYPE
        SYNTAX      SEQUENCE OF Ip6NetToMediaEntry
        MAX-ACCESS  not-accessible
        STATUS      current
        DESCRIPTION
            "The IPv6 Address Translation table used for mapping from
             IPv6-addresses to physical addresses.
             The IPv6-address translation-table contains the InetAddressIPv6
             to 'physical' address-equivalencies.
             Some interfaces do not use translation tables for determining
             address-equivalencies; if all interfaces are of this type, then
             the Address Translation table is empty, i.e., has zero entries."
    ::= { ip6Stats 7 }

    ip6NetToMediaEntry OBJECT-TYPE
        SYNTAX      Ip6NetToMediaEntry
        MAX-ACCESS  not-accessible
        STATUS      current
        DESCRIPTION
            "Each entry contains one IPv6 address to `physical'
             address equivalence."
        INDEX   { ip6NetToMediaIfIndex,
                  ip6NetToMediaNetAddress }
    ::= { ip6NetToMediaTable 1 }

    Ip6NetToMediaEntry ::= SEQUENCE {
        ip6NetToMediaIfIndex        InterfaceIndex,
        ip6NetToMediaNetAddress     InetAddressIPv6,
        ip6NetToMediaPhysAddress    PhysAddress,
        ip6NetToMediaType           INTEGER,
        ip6NetToMediaState          INTEGER,
        ip6NetToMediaLastUpdated    TimeStamp
    }

    ip6NetToMediaIfIndex OBJECT-TYPE
        SYNTAX      InterfaceIndex
        MAX-ACCESS  read-create
        STATUS      current
        DESCRIPTION
            "A unique non-zero value identifying
             the particular IPv6 interface."
    ::= { ip6NetToMediaEntry 1 }

    ip6NetToMediaNetAddress OBJECT-TYPE
        SYNTAX      InetAddressIPv6
        MAX-ACCESS  read-only
        STATUS      current
        DESCRIPTION
            "The IPv6 Address corresponding to
             the media-dependent `physical' address."
    ::= { ip6NetToMediaEntry 2 }

    ip6NetToMediaPhysAddress OBJECT-TYPE
        SYNTAX      PhysAddress
        MAX-ACCESS  read-only
        STATUS      current
        DESCRIPTION
            "The media-dependent `physical' address."
    ::= { ip6NetToMediaEntry 3 }

    ip6NetToMediaType OBJECT-TYPE
        SYNTAX      INTEGER {
            dynamic(1),     -- dynamically resolved
            static(2),      -- statically configured
            local(3)        -- local interface
        }
        MAX-ACCESS  read-only
        STATUS      current
        DESCRIPTION
            "The type of the mapping. The 'dynamic(2)' type
             indicates that the IPv6 address to physical
             addresses mapping has been dynamically
             resolved using the IPv6 Neighbor Discovery
             protocol. The static(3)' types indicates that
             the mapping has been statically configured.
             The local(4) indicates that the mapping is
             provided for an entity's own interface address."
        DEFVAL { dynamic }
    ::= { ip6NetToMediaEntry 4 }

    ip6NetToMediaState OBJECT-TYPE
        SYNTAX      INTEGER {
            incomplete(1),  -- discover in progress

            reachable(2),   -- confirmed reachability

            stale(3),       -- unconfirmed reachability

            delay(4),       -- waiting for reachability-confirmation before
                            -- entering the probe state

            probe(5),       -- actively probing

            invalid(6),     -- an invalidated mapping

            unknown(7)      -- state can not be determined for some reason.
        }
        MAX-ACCESS  read-only
        STATUS      current
        DESCRIPTION
            "The Neighbor Unreachability Detection [8] state for the
             interface when the address mapping in this entry is used."
        DEFVAL { unknown }
    ::= { ip6NetToMediaEntry 5 }

    ip6NetToMediaLastUpdated OBJECT-TYPE
        SYNTAX      TimeStamp
        MAX-ACCESS  read-only
        STATUS      current
        DESCRIPTION
            "The value of sysUpTime at the time this entry was last updated.
             If this entry was updated prior to the last re-initialization
             of the local network management subsystem, then this object
             contains a zero value."
    ::= { ip6NetToMediaEntry 6 }

-- End: Operative: IPv6-net-to-media-cache


-- Start: Operative: MLD-proxy-cache

    ip6MldListenTable OBJECT-TYPE
        SYNTAX      SEQUENCE OF Ip6MldListenEntry
        MAX-ACCESS  not-accessible
        STATUS      current
        DESCRIPTION
            "The list of IPv6 address prefixes associated with IPv6 interfaces."
    ::= { ip6Stats 8 }

    ip6MldListenEntry OBJECT-TYPE
        SYNTAX      Ip6MldListenEntry
        MAX-ACCESS  not-accessible
        STATUS      current
        DESCRIPTION
            "A Mld 'Listen Entry' used by multicast routing."
        INDEX   { ip6MldListenIfIndex,
                  ip6MldListenGroup }
    ::= { ip6MldListenTable 1 }

    Ip6MldListenEntry ::= SEQUENCE {
        ip6MldListenIfIndex     InterfaceIndex,
        ip6MldListenGroup       InetAddressIPv6,
        ip6MldListenAge         TimeStamp,
        ip6MldListenProto       BITS
    }

    ip6MldListenIfIndex OBJECT-TYPE
        SYNTAX      InterfaceIndex
        MAX-ACCESS  read-only
        STATUS      current
        DESCRIPTION
            "Indicates the interface associoted with this Mld 'Listen Entry'."
    ::= { ip6MldListenEntry 1 }

    ip6MldListenGroup OBJECT-TYPE
        SYNTAX      InetAddressIPv6
        MAX-ACCESS  read-only
        STATUS      current
        DESCRIPTION
            "The listeners 'Multicast Group Address'."
    ::= { ip6MldListenEntry 2 }

   ip6MldListenAge OBJECT-TYPE
        SYNTAX      TimeStamp
        MAX-ACCESS  read-only
        STATUS      current
        DESCRIPTION
            "Shows the age of the last active 'Listen Report' inititated
             by a client."
    ::= { ip6MldListenEntry 3 }

    ip6MldListenProto OBJECT-TYPE
        SYNTAX      BITS {
            local(0),
            mld(1)
        }
        MAX-ACCESS  read-only
        STATUS      current
        DESCRIPTION
            "The listeners 'Protocol'."
    ::= { ip6MldListenEntry 4 }

-- End: Operative: MLD-proxy-cache


-- Start: Operative: IPv6-routes learned by other protocols

    ip6DynRouteTable OBJECT-TYPE
        SYNTAX      SEQUENCE OF Ip6DynRouteEntry
        MAX-ACCESS  not-accessible
        STATUS      current
        DESCRIPTION
            "IPv6-dynamic-routing-table. This table contains routing-entries
             learned via DHCPv6 or any other (routing) protocol."
    ::= { ip6Stats 9 }

    ip6DynRouteEntry OBJECT-TYPE
        SYNTAX      Ip6DynRouteEntry
        MAX-ACCESS  not-accessible
        STATUS      current
        DESCRIPTION
            "A dynamically created routing entry."
        INDEX   { ip6DynRouteTarget,
                  ip6DynRouteTargetLen,
                  ip6DynRouteSource,
                  ip6DynRouteSourceLen,
                  ip6DynRoutePriority }
    ::= { ip6DynRouteTable 1 }

    Ip6DynRouteEntry ::= SEQUENCE {
        ip6DynRouteCreator      INTEGER,
        ip6DynRouteTarget       InetAddressIPv6,
        ip6DynRouteTargetLen    INTEGER,
        ip6DynRouteSource       InetAddressIPv6,
        ip6DynRouteSourceLen    INTEGER,
        ip6DynRouteIfIndex      InterfaceIndex,
        ip6DynRouteNextHop      InetAddressIPv6,
        ip6DynRoutePriority     INTEGER
    }

    ip6DynRouteCreator OBJECT-TYPE
        SYNTAX      INTEGER {
            netmgmt(2), -- routes generated by system
            rip(4),     -- RIPng
            ospf(5),    -- Open Shortest Path First
            bgp(6),     -- Border Gateway Protocol
            idrp(7),    -- InterDomain Routing Protocol
            dhcp-pd(8)  -- DHCPv6-prefix-delegation
        }
        MAX-ACCESS  read-only
        STATUS      current
        DESCRIPTION
            "The creator of the dynamic routing-entry,
             can be DHCPv6 or any other (routing-)protocol."
        DEFVAL { netmgmt }
    ::= { ip6DynRouteEntry 1 }

    ip6DynRouteTarget OBJECT-TYPE
        SYNTAX      InetAddressIPv6
        MAX-ACCESS  read-only
        STATUS      current
        DESCRIPTION
            "The destination IPv6 address of this route.
             This object may not take a multicast address value."
    ::= { ip6DynRouteEntry 2 }

    ip6DynRouteTargetLen OBJECT-TYPE
        SYNTAX      INTEGER(0..128)
        MAX-ACCESS  read-only
        STATUS      current
        DESCRIPTION
            "Indicates the prefix length of the destination address."
    ::= { ip6DynRouteEntry 3 }

    ip6DynRouteSource OBJECT-TYPE
        SYNTAX      InetAddressIPv6
        MAX-ACCESS  read-only
        STATUS      current
        DESCRIPTION
            "The Source IPv6 address of this route.
             This object may not take a multicast address value."
    ::= { ip6DynRouteEntry 4 }

    ip6DynRouteSourceLen OBJECT-TYPE
        SYNTAX      INTEGER(0..128)
        MAX-ACCESS  read-only
        STATUS      current
        DESCRIPTION
            "Indicates the prefix length of the source address."
        DEFVAL { 64 }
    ::= { ip6DynRouteEntry 5 }

    ip6DynRouteIfIndex OBJECT-TYPE
        SYNTAX      InterfaceIndex
        MAX-ACCESS  read-only
        STATUS      current
        DESCRIPTION
            "The index value which uniquely identifies the local
             interface through which the next hop of this
             route should be reached. The interface identified
             by a particular value of this index is the same
             interface as identified by the same value of
             ip6DeviceIfIndex. For routes of the discard type this
             value can be zero."
    ::= { ip6DynRouteEntry 6 }

    ip6DynRouteNextHop OBJECT-TYPE
        SYNTAX      InetAddressIPv6
        MAX-ACCESS  read-only
        STATUS      current
        DESCRIPTION
            "On remote routes, the address of the next hop of this routing
             entry, set to ::  otherwise."
    ::= { ip6DynRouteEntry 7 }

    ip6DynRoutePriority OBJECT-TYPE
        SYNTAX      INTEGER (0..16)
        MAX-ACCESS  read-only
        STATUS      current
        DESCRIPTION
            "The routing priority for this route,
             a value of 0 means highest priority,
             a value of 16 lowest priority."
        DEFVAL { 8 }
    ::= { ip6DynRouteEntry 8 }

-- End: Operative: IPv6-routes learned by other protocols


-- Start: Administrative/Operative: Global IPv6-debug-settings/info

    ip6DbgGlobals OBJECT IDENTIFIER ::= { ip6Debug 1 }

    ip6DebugOptions OBJECT-TYPE
        SYNTAX      BITS {
            context(0),
            trusted(1),
            ndisc(2)
        }
        MAX-ACCESS  read-write
        STATUS      current
        DESCRIPTION
            "Various debugging modes."
    ::= { ip6DbgGlobals 1 }

    ip6RejectsLimit OBJECT-TYPE
        SYNTAX      INTEGER
        MAX-ACCESS  read-write
        STATUS      current
        DESCRIPTION
            "Various debugging modes."
        DEFVAL { 5000 }
    ::= { ip6DbgGlobals 2 }

    ip6MemoryUsage OBJECT-TYPE
        SYNTAX      INTEGER
        MAX-ACCESS  read-only
        STATUS      current
        DESCRIPTION
            "The subsystems current memory usage."
    ::= { ip6DbgGlobals 3 }

    ip6ContextCount OBJECT-TYPE
        SYNTAX      INTEGER
        MAX-ACCESS  read-only
        STATUS      current
        DESCRIPTION
            "The current number of context entries."
    ::= { ip6DbgGlobals 4 }

    ip6RejectCount OBJECT-TYPE
        SYNTAX      INTEGER
        MAX-ACCESS  read-only
        STATUS      current
        DESCRIPTION
            "The current number of context reject entries."
    ::= { ip6DbgGlobals 5 }

    ip6PktsInUse OBJECT-TYPE
        SYNTAX      Counter32
        MAX-ACCESS  read-only
        STATUS      current
        DESCRIPTION
            "Current number IPv6 packet wrappers allocated by the subsystem."
    ::= { ip6DbgGlobals 6 }

-- End: Administrative/Operative: Global IPv6-debug-settings/info


-- Start: Operative: Debug-info for IPv6-session-contexts

    ip6ContextTable OBJECT-TYPE
        SYNTAX      SEQUENCE OF Ip6ContextEntry
        ACCESS      not-accessible
        STATUS      mandatory
        DESCRIPTION
            "Contains a IPv6 Stateful Inspection Firewall (SIF) policy."
    ::= { ip6Debug 2 }

    ip6ContextEntry OBJECT-TYPE
        SYNTAX      Ip6ContextEntry
        ACCESS      not-accessible
        STATUS      mandatory
        DESCRIPTION
            ""
        INDEX   { ip6ContextIdent }
    ::= { ip6ContextTable 1 }

    Ip6ContextEntry ::= SEQUENCE {
        ip6ContextIdent             INTEGER,
        ip6ContextProtocol          INTEGER,
        ip6ContextInitiatorIfIndex  InterfaceIndexOrZero,
        ip6ContextInitiatorAddress  InetAddressIPv6,
        ip6ContextInitiatorPort     INTEGER,
        ip6ContextResponderIfIndex  InterfaceIndexOrZero,
        ip6ContextResponderAddress  InetAddressIPv6,
        ip6ContextResponderPort     INTEGER,
        ip6ContextRouteFlags        BITS,
        ip6ContextLifetime          INTEGER,
        ip6ContextAge               TimeStamp
    }

    ip6ContextIdent OBJECT-TYPE
        SYNTAX      INTEGER
        ACCESS      read-only
        STATUS      mandatory
        DESCRIPTION
            "Internal ID for the context entry."
    ::= { ip6ContextEntry 1 }

    ip6ContextProtocol OBJECT-TYPE
        SYNTAX      INTEGER {
            icmp(1),
            igmp(2),
            ggp(3),
            ip(4),
            tcp(6),
            egp(8),
            igp(9),
            pup(12),
            chaos(16),
            udp(17),
            hmp(20),
            xns-idp(22),
            rdp(27),
            ipv6(41),
            rsvp(46),
            gre(47),
            esp(50),
            ah(51),
            tlsp(56),
            skip(57),
            icmpv6(58),
            kryptolan(65),
            iso-ip(80),
            igrp(88),
            ospf(89),
            ipip(94),
            pim(103),
            ipx-in-ip(111),
            vrrp(112),
            l2tp(115)
        }
        ACCESS      read-only
        STATUS      mandatory
        DESCRIPTION
            "IP protocol associated with this context."
        DEFVAL { ip }
    ::= { ip6ContextEntry 2 }

    ip6ContextInitiatorIfIndex OBJECT-TYPE
        SYNTAX      InterfaceIndexOrZero
        ACCESS      read-only
        STATUS      mandatory
        DESCRIPTION
            "Initiators interface index."
    ::= { ip6ContextEntry 3 }

    ip6ContextInitiatorAddress OBJECT-TYPE
        SYNTAX      InetAddressIPv6
        ACCESS      read-only
        STATUS      mandatory
        DESCRIPTION
            "Initiators IPv6 address."
    ::= { ip6ContextEntry 4 }

    ip6ContextInitiatorPort OBJECT-TYPE
        SYNTAX      INTEGER (0..65535)
        ACCESS      read-only
        STATUS      mandatory
        DESCRIPTION
            "Initiators TCP/UDP port number."
    ::= { ip6ContextEntry 5 }

    ip6ContextResponderIfIndex OBJECT-TYPE
        SYNTAX      InterfaceIndexOrZero
        ACCESS      read-only
        STATUS      mandatory
        DESCRIPTION
            "Responders interface index."
    ::= { ip6ContextEntry 6 }

    ip6ContextResponderAddress OBJECT-TYPE
        SYNTAX      InetAddressIPv6
        ACCESS      read-only
        STATUS      mandatory
        DESCRIPTION
            "Responders IPv6 address."
    ::= { ip6ContextEntry 7 }

    ip6ContextResponderPort OBJECT-TYPE
        SYNTAX      INTEGER (0..65535)
        ACCESS      read-only
        STATUS      mandatory
        DESCRIPTION
            "Responders TCP/UDP port number."
    ::= { ip6ContextEntry 8 }

    ip6ContextRouteFlags OBJECT-TYPE
        SYNTAX      BITS {
            local(0),
            direct(1),
            deny(2),
            reject(3),
            blocked(4)
        }
        ACCESS      read-only
        STATUS      mandatory
        DESCRIPTION
            "various routing flags:
                 local:     Source or target is local
                 direct:    Source or target direct routing
                 deny:      drop rule or firewall blocked
                 reject:    icmp answer by no route or firewall blocked
                 blocked:   set by firewall rule deny or reject"
    ::= { ip6ContextEntry 9 }

    ip6ContextLifetime OBJECT-TYPE
        SYNTAX      INTEGER
        UNITS       "seconds"
        ACCESS      read-only
        STATUS      mandatory
        DESCRIPTION
            "The 'Lifetime' of this context in seconds."
    ::= { ip6ContextEntry 10 }

    ip6ContextAge OBJECT-TYPE
        SYNTAX      TimeStamp
        ACCESS      read-only
        STATUS      mandatory
        DESCRIPTION
            "The age of this context in seconds."
    ::= { ip6ContextEntry 11 }

-- End: Operative: Debug-info for IPv6-session-contexts

END
