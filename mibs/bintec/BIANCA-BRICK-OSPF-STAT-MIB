-- This file is corresponding to Release 10.2.3.100 from 2018/07/18 00:00:00


-- (C)opyright 1991-2014 bintec elmeg GmbH, All Rights Reserved
--  $RCSfile: mibbospf,v $ 
-- $Revision: 1.8 $ 

BIANCA-BRICK-OSPF-STAT-MIB DEFINITIONS ::= BEGIN
 
        IMPORTS
            IpAddress, Counter, enterprises
                FROM RFC1155-SMI
 
            OBJECT-TYPE
                FROM RFC-1212;

    bintec 	OBJECT IDENTIFIER ::= { enterprises 272 }
    bibo	OBJECT IDENTIFIER ::= { bintec 4 }
    biboip      OBJECT IDENTIFIER ::= { bibo 5 }
    ospfStat	OBJECT IDENTIFIER
	::= { biboip 10 }

-- OSPF MIB

	ospfStatHelloRecv OBJECT-TYPE
	    SYNTAX Counter
	    ACCESS read-only
	    STATUS mandatory
	    DESCRIPTION
		"Counts the number of Hello packets received."
	::= { ospfStat 1 }

	ospfStatHelloSent OBJECT-TYPE
	    SYNTAX Counter
	    ACCESS read-only
	    STATUS mandatory
	    DESCRIPTION
		"Counts the number of Hello packets sent."
	::= { ospfStat 2 }

	ospfStatDdRecv OBJECT-TYPE
	    SYNTAX Counter
	    ACCESS read-only
	    STATUS mandatory
	    DESCRIPTION
		"Counts the number of Database Description packets received."
	::= { ospfStat 3 }

	ospfStatDdSent OBJECT-TYPE
	    SYNTAX Counter
	    ACCESS read-only
	    STATUS mandatory
	    DESCRIPTION
		"Counts the number of Database Description packets sent."
	::= { ospfStat 4 }

	ospfStatLsackRecv OBJECT-TYPE
	    SYNTAX Counter
	    ACCESS read-only
	    STATUS mandatory
	    DESCRIPTION
		"Counts the number of Link State Acknowledge packets received."
	::= { ospfStat 5 }

	ospfStatLsackSent OBJECT-TYPE
	    SYNTAX Counter
	    ACCESS read-only
	    STATUS mandatory
	    DESCRIPTION
		"Counts the number of Link State Acknowledge packets sent."
	::= { ospfStat 6 }

	ospfStatLsreqRecv OBJECT-TYPE
	    SYNTAX Counter
	    ACCESS read-only
	    STATUS mandatory
	    DESCRIPTION
		"Counts the number of Link State Request packets received."
	::= { ospfStat 7 }

	ospfStatLsreqSent OBJECT-TYPE
	    SYNTAX Counter
	    ACCESS read-only
	    STATUS mandatory
	    DESCRIPTION
		"Counts the number of Link State Request packets sent"
	::= { ospfStat 8 }

	ospfStatLsupdRecv OBJECT-TYPE
	    SYNTAX Counter
	    ACCESS read-only
	    STATUS mandatory
	    DESCRIPTION
		"Counts the number of Link State Update packets received."
	::= { ospfStat 9 }

	ospfStatLsupdSent OBJECT-TYPE
	    SYNTAX Counter
	    ACCESS read-only
	    STATUS mandatory
	    DESCRIPTION
		"Counts the number of Link State Update packets sent."
	::= { ospfStat 10 }

	ospfStatSummaryIncUpd OBJECT-TYPE
	    SYNTAX Counter
	    ACCESS read-only
	    STATUS mandatory
	    DESCRIPTION
		"Counts the number of incremental routing table updates 
		 performed due to reception of new Summary Links Advertisments."
	::= { ospfStat 11 }

	ospfStatExternalIncUpd OBJECT-TYPE
	    SYNTAX Counter
	    ACCESS read-only
	    STATUS mandatory
	    DESCRIPTION
		"Counts the number of incremental routing table updates 
		 performed due to reception of new External Advertisments."
	::= { ospfStat 12 }
END



BIANCA-BRICK-OSPF-ERR-MIB DEFINITIONS ::= BEGIN
 
        IMPORTS
            IpAddress, Counter, enterprises
                FROM RFC1155-SMI
 
            OBJECT-TYPE
                FROM RFC-1212;

    bintec 	OBJECT IDENTIFIER ::= { enterprises 272 }
    bibo	OBJECT IDENTIFIER ::= { bintec 4 } 
    biboip      OBJECT IDENTIFIER ::= { bibo 5 }
    ospfErr	OBJECT IDENTIFIER
	
	::= { biboip 11 }

-- OSPF MIB
	ospfErrOspfBadVersion OBJECT-TYPE
	    SYNTAX Counter
	    ACCESS read-only
	    STATUS mandatory
	    DESCRIPTION
		"Counts the number of OSPF packets received with bad
                 version number."
	::= { ospfErr 1 }

	ospfErrOspfBadPacketType OBJECT-TYPE
	    SYNTAX Counter
	    ACCESS read-only
	    STATUS mandatory
	    DESCRIPTION
		"Counts the number of OSPF packets received with bad
	         packet type."
	::= { ospfErr 2 }

	ospfErrOspfBadChecksum OBJECT-TYPE
	    SYNTAX Counter
	    ACCESS read-only
	    STATUS mandatory
	    DESCRIPTION
		"Counts the number of OSPF packets received with bad checksum."
	::= { ospfErr 3 }

	ospfErrIpBadDestination OBJECT-TYPE
	    SYNTAX Counter
	    ACCESS read-only
	    STATUS mandatory
	    DESCRIPTION
		"Counts the number of OSPF packets received with bad
	         destination IP address."
	::= { ospfErr 4 }

	ospfErrOspfBadAreaId OBJECT-TYPE
	    SYNTAX Counter
	    ACCESS read-only
	    STATUS mandatory
	    DESCRIPTION
		"Counts the number of OSPF packets with the wrong area field."
	::= { ospfErr 5 }

	ospfErrOspfAuthenticationFailed OBJECT-TYPE
	    SYNTAX Counter
	    ACCESS read-only
	    STATUS mandatory
	    DESCRIPTION
		"Counts the number of OSPF packets with wrong authentication."
	::= { ospfErr 6 }

	ospfErrOspfUnknownNeighbor OBJECT-TYPE
	    SYNTAX Counter
	    ACCESS read-only
	    STATUS mandatory
	    DESCRIPTION
		"Counts the number of OSPF packets received from an unknown
	         neighbor."
	::= { ospfErr 7 }

	ospfErrHelloNetmaskMismatch OBJECT-TYPE
	    SYNTAX Counter
	    ACCESS read-only
	    STATUS mandatory
	    DESCRIPTION
		"Counts the number of Hello packets received with wrong network
                 mask."
	::= { ospfErr 8 }

	ospfErrHelloDeadTimerMismatch OBJECT-TYPE
	    SYNTAX Counter
	    ACCESS read-only
	    STATUS mandatory
	    DESCRIPTION
		"Counts the number of OSPF Hello packets where the DeadTimer
	         was not equal to the DeadTimer of the associated interface."
	::= { ospfErr 9 }

	ospfErrHelloTimerMismatch OBJECT-TYPE
	    SYNTAX Counter
	    ACCESS read-only
	    STATUS mandatory
	    DESCRIPTION
		"Counts the number of OSPF Hello packets where the HelloTimer
	         was not equal to the DeadTimer of the associated interface."
	::= { ospfErr 10 }

	ospfErrHelloOptionMismatch OBJECT-TYPE
	    SYNTAX Counter
	    ACCESS read-only
	    STATUS mandatory
	    DESCRIPTION
		"Counts the number of OSPF Hello packets with bad options."
	::= { ospfErr 11 }

	ospfErrOspfRouterIdConfusion OBJECT-TYPE
	    SYNTAX Counter
	    ACCESS read-only
	    STATUS mandatory
	    DESCRIPTION
		"Counts the number of packets received that used 
 	         our own router id."
	::= { ospfErr 12 }

	ospfErrOspfUnknownLsaType OBJECT-TYPE
	    SYNTAX Counter
	    ACCESS read-only
	    STATUS mandatory
	    DESCRIPTION
		"Counts the number of unknown LSAs received."
	::= { ospfErr 13 }

	ospfErrDdOptionMismatch OBJECT-TYPE
	    SYNTAX Counter
	    ACCESS read-only
	    STATUS mandatory
	    DESCRIPTION
		"Counts the number of OSPF DD packets with bad options."
	::= { ospfErr 14 }

	ospfErrDdNeighborStateLow OBJECT-TYPE
	    SYNTAX Counter
	    ACCESS read-only
	    STATUS mandatory
	    DESCRIPTION
		"Counts the number of OSPF DD packets received then the
	         neighbor was in the wrong state."
	::= { ospfErr 15 }

	ospfErrLsackBadAck OBJECT-TYPE
	    SYNTAX Counter
	    ACCESS read-only
	    STATUS mandatory
	    DESCRIPTION
		"Counts the number of OSPF LS Acknowledge packets received
                 that were not exactly found on the retransmission list of 
                 that neighbor, i.e. with the wrong sequence number or
                 checksum."
	::= { ospfErr 16 }

	ospfErrLsackDuplicateAck OBJECT-TYPE
	    SYNTAX Counter
	    ACCESS read-only
	    STATUS mandatory
	    DESCRIPTION
		"Counts the number of OSPF LS Acknowledge packets received
                 that were not found on the retransmission list of 
                 that neighbor."
	::= { ospfErr 17 }

	ospfErrLsreqBadRequest OBJECT-TYPE
	    SYNTAX Counter
	    ACCESS read-only
	    STATUS mandatory
	    DESCRIPTION
		"Counts the number of requests for LSAs that were not found
                 in the database."
	::= { ospfErr 18 }

	ospfErrLsreqNeighborStateLow OBJECT-TYPE
	    SYNTAX Counter
	    ACCESS read-only
	    STATUS mandatory
	    DESCRIPTION
		"Counts the number of OSPF LS Request packets received then the 
	         neighbor was in the wrong state."
	::= { ospfErr 19 }

	ospfErrLsupdNeighborStateLow OBJECT-TYPE
	    SYNTAX Counter
	    ACCESS read-only
	    STATUS mandatory
	    DESCRIPTION
		"Counts the number of OSPF LS Update packets received then the 
	         neighbor was in the wrong state."
	::= { ospfErr 20 }

	ospfErrLsupdBadLsaChecksum OBJECT-TYPE
	    SYNTAX Counter
	    ACCESS read-only
	    STATUS mandatory
	    DESCRIPTION
		"Counts the number of OSPF LS Update packets with bad checksum."
	::= { ospfErr 21 }

	ospfErrLsupdNewerSelfgenLsa OBJECT-TYPE
	    SYNTAX Counter
	    ACCESS read-only
	    STATUS mandatory
	    DESCRIPTION
		"The router received an instance of one of its self-originated
 	         advertisements that is considered to be more recent."
	::= { ospfErr 22 }

	ospfErrLsupdLessRecentLsa OBJECT-TYPE
	    SYNTAX Counter
	    ACCESS read-only
	    STATUS mandatory
	    DESCRIPTION
		"The router received an instance of an advertisement that 
	         is considered to be less recent than the database copy."
	::= { ospfErr 23 }

END
