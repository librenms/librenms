-- SiteBoss 550 MIB

-- v 4.66 Mar 8 2019

-- Copyright (c) 2019 by Asentria Corporation.  All rights reserved.


SITEBOSS-550-STD-MIB DEFINITIONS ::= BEGIN

IMPORTS
 DisplayString
    FROM SNMPv2-TC
 IpAddress, TimeTicks, Integer32,
 MODULE-IDENTITY, NOTIFICATION-TYPE, OBJECT-TYPE
    FROM SNMPv2-SMI
 asentria
    FROM ASENTRIA-ROOT-MIB;

--***************************************************************************************
--MODULE IDENTITY
--***************************************************************************************

  s550 MODULE-IDENTITY
    LAST-UPDATED "201903081530Z"
    ORGANIZATION "Asentria Corporation"
    CONTACT-INFO
     "Phone:  206-344-8800
      Fax:    206-344-2116
      Email:  support@asentria.com"
    DESCRIPTION
      "MIB module for managing Asentria SiteBoss 550"

    REVISION      "201903081530Z"
    DESCRIPTION
      "-v4.66
       -Add objects for Power Meter line-to-line voltage (OMX-2143) and modified OID numbering for ACMON.
       -Applicable since unit version 2.11.760."


    REVISION      "201902111345Z"
    DESCRIPTION
      "-v4.65
       -Added objects for Site Security (OMX-2021).
       -Applicable since unit version 2.11.760."
 
    REVISION      "201710311049Z"
    DESCRIPTION
      "-v4.64
       -Added objects for Bard HVAC controller (OMX-1852).
       -Applicable since unit version 2.11.550."
  
    REVISION      "201705251028Z"
    DESCRIPTION
      "-v4.63
       -Added trap 545 and 548 to the mibs
       -Applicable since unit version 2.11.500."

    REVISION      "201704260945Z"
    DESCRIPTION
      "-v4.62
       -Added ACMON Alarm datetime to the mibs
       -Applicable since unit version 2.11.490."

    REVISION      "201603160850Z"
    DESCRIPTION
      "-v4.61
       -Fixed missing IP Camera trap notifications
       -Applicable since unit version 2.11.210."
   
    REVISION      "201603150500Z"
    DESCRIPTION
      "-v4.60
       -Replace existing sensor .type setting with new system .group
       -Added Objects espcCCGroup, espcTempGroup, espcHumidGroup, 
        espcAIGroup espcOutputGroup
       -Applicable since unit version 2.11.210."
  
  
    REVISION      "201601070459Z"
    DESCRIPTION
      "-v4.59
       -Added Event Sensor Alias and Class OID for event states.
       -Added Fuel Sensor Fuel Type.
       -Applicable since unit version 2.11.140."
  
  
    REVISION      "201510290458Z"
    DESCRIPTION
      "-v4.58
       -Allow read access for battery backup - percent charge and running
        status.
       -Add trap for power up/down or running on battery/main
       -Applicable since unit version 2.10.930."

    REVISION      "201504030457Z"
    DESCRIPTION
      "-v4.57
       -Allow read access for serial number, product name, software version
       -Add trap for General Sensor Unresponsive (OMX-1257)
       -Applicable since unit version 2.10.700."

    REVISION      "201503200456Z"
    DESCRIPTION
      "-v4.56
       -Removed non-essential Bard settings (OMX-1203).
       -Removed wirelessPIN and scSecret objects (OMX-1064).
       -Added HVAC status and settings objects.
       -Added ACDM wiegand point object.
       -Applicable since unit version 2.10.670."

    REVISION      "201412110455Z"
    DESCRIPTION
      "-v4.55
       -Changed analog-input fuel sensor objects from Integer32 to DisplayString (OMX-1177).
       -Added missing ipv6DefaultRouter object (OMX-1175).
       -Applicable since unit version 2.10.580."

    REVISION      "201410160454Z"
    DESCRIPTION
      "-v4.54
       -Added espcAIDisplayFormat object (OMX-1112).
       -Removed espcAIPolarity, espcAIConvHighSign, espcAIConvLowSign objects (OMX-1113).
       -Applicable since unit version 2.10.460."

    REVISION      "201410030453Z"
    DESCRIPTION
      "-v4.53
       -Changed analog input objects from Integer32 to DisplayString.
       -Applicable since unit version 2.10.460."

    REVISION      "201409100452Z"
    DESCRIPTION
      "-v4.52
       -Added dnp3 and telemetry branches (OMX-454).
       -Applicable since unit version 2.10.460."

    REVISION      "201408140451Z"
    DESCRIPTION
      "-v4.51
       -Fixed description for wirelessConnIP objects (OMX-1061).
       -Applicable since unit version 2.10.390."

    REVISION      "201407030450Z"
    DESCRIPTION
      "-v4.50
       -Fixed wirelessIdleTimeout (OMX-1037).
       -Fixed CPE status objects (OMX-1036).
       -Applicable since unit version 2.10.390."

    REVISION      "201406240449Z"
    DESCRIPTION
      "-v4.49
       -Fixed CPE status objects.
       -Applicable since unit version 2.10.340."

    REVISION      "201406170448Z"
    DESCRIPTION
      "-v4.48
       -Added various missing objects (OMX-751).
       -Added CPE objects (OMX-162).
       -Added ACDM objects (OMX-683).
       -Applicable since unit version 2.10.340."

    REVISION      "201404110447Z"
    DESCRIPTION
      "-v4.47
       -Clarified relay and power output function and documentation (OMX-926).
       -Applicable since unit version 2.10.300."

    REVISION      "201401170146Z"
    DESCRIPTION
      "-v4.46
       -Added IPv6 objects (OMX-705).
       -Added power distribution objects (powerDistributionStatus branch) (OMX-708).
       -Fixed ipRestrictionMask wrong type (OMX-743).
       -Added ftpPushPermissions (OMX-737).
       -Added snmpProxy objects (OMX-747).
       -Applicable since unit version 2.10.150."

    REVISION      "201312160445Z"
    DESCRIPTION
      "-v4.45
       -Changed evHVACStatus branch OIDs (OMX-702).
       -Applicable since unit version 2.10.130."

    REVISION      "201312040444Z"
    DESCRIPTION
      "-v4.44
       -Added fsGenEnable (OMX-661).
       -Applicable since unit version 2.10.110."

    REVISION      "201310300443Z"
    DESCRIPTION
      "-v4.43
       -Added genSetRelayTable for multiple genset ignition relays (OMX-577).
       -Added genSetCCDelay object (OMX-589).
       -Added webXMLProxy branch (OMX-629).
       -Applicable since unit version 2.09.625."

    REVISION      "201310040442Z"
    DESCRIPTION
      "-v4.42
       -Added objects for Emerson Vortex Power System (OMX-578).
       -Applicable since unit version 2.09.624."

    REVISION      "201309260441Z"
    DESCRIPTION
      "-v4.41
       -Added objects for Bard HVAC controller (OMX-563).
       -Applicable since unit version 2.09.623."

    REVISION      "201308010440Z"
    DESCRIPTION
      "-v4.40
       -Added missing trapEventTypeNumber available values in description (OMX-437).
       -Applicable since unit version 2.09.560."

    REVISION      "201307170439Z"
    DESCRIPTION
      "-v4.39
       -Corrected snmpPBufferAllPeriod object.
       -Applicable since unit version 2.09.560."

    REVISION      "201307020438Z"
    DESCRIPTION
      "-v4.38
       -Added snmpPoll objects (OMX-394).
       -Applicable since unit version 2.09.560."

    REVISION      "201306120437Z"
    DESCRIPTION
      "-v4.37
       -Renamed EX10 to Ethernet Expansion (OMX-364)
       -Applicable since unit version 2.09.510."

    REVISION      "201305280436Z"
    DESCRIPTION
      "-v4.36
       -Fixed incorrect SYNTAX for sysCharMask (OMX-328).
       -Added evGlobal branch (OMX-228).
       -Applicable since unit version 2.09.500."

    REVISION      "201305100435Z"
    DESCRIPTION
      "-v4.35
       -Fixed incorrect SYNTAX statements for various objects (OMX-314).
       -Applicable since unit version 2.09.380."

    REVISION      "201304100434Z"
    DESCRIPTION
      "-v4.34
       -Added non-weekly job scheduling objects (OMX-252).
       -Applicable since unit version 2.09.310."

    REVISION      "201303150433Z"
    DESCRIPTION
      "-v4.33
       -Renamed sysLocation branch to sysLoc (OMX-198).
       -Applicable since unit version 2.09.240."

    REVISION      "201303140432Z"
    DESCRIPTION
      "-v4.32
       -Added snmpProxy branch (OMX-190).
       -Applicable since unit version 2.09.280."

    REVISION      "201302060431Z"
    DESCRIPTION
      "-v4.31
       -Added ex10 branch.
       -Renamed telnet* objects.
       -Applicable since unit version 2.09.240."

    REVISION      "201301140430Z"
    DESCRIPTION
      "-v4.30
       -Added evReset branch and associated notification (OMX-83).
       -Applicable since unit version 2.09.220."

    REVISION      "201211190429Z"
    DESCRIPTION
      "-v4.29
       -Added sysFileTransfer and sysUpdate objects. (BN 4632)
       -Fixed backwards pppRoutingEnable/ethRoutingEnable comments.  (BN 4620)
       -Applicable since unit version 2.09.120."

    REVISION      "201208220428Z"
    DESCRIPTION
      "-v4.28
       -Added additional AC power monitor items."

    REVISION      "201208020427Z"
    DESCRIPTION
      "-v4.27
       -Removed non-weekly job schedule objects."

    REVISION      "201206120425Z"
    DESCRIPTION
      "-v4.25
       -Removed user credentials objects."

    REVISION      "201205010424Z"
    DESCRIPTION
      "-v4.24
       -Added object for location.
       -Fixed objects for Generator Exercising Non-Start event."

    REVISION      "201204300423Z"
    DESCRIPTION
      "-v4.23
       -Added objects for fuel sensor sudden/slow change."

    REVISION      "201204120422Z"
    DESCRIPTION
      "-v4.22
       -Added objects for job scheduling and generator exercising."

    REVISION      "201204090421Z"
    DESCRIPTION
      "-v4.21
       -Added eth2WanRoutingEnable object."

    REVISION      "201204050420Z"
    DESCRIPTION
      "-v4.20
       -Added combined eventsensor status objects."

    REVISION      "201203060419Z"
    DESCRIPTION
      "-v4.19
       -Added objects and trap definitions for fuel sensor and AC power monitor."

    REVISION      "201201160902Z"
    DESCRIPTION
      "-v4.18
       -Jumped to 4.xx Asentria version series.  The version 4
       series officially may improve compatibility with certain
       NMS installations by grouping all notifications in a
       dedicated branch.
       -Added stockScriptTrap notification definition."

    REVISION      "201109150900Z"
    DESCRIPTION
      "-v1.17
       -Moved notification definitions to dedicated branch."

    REVISION      "201108080900Z"
    DESCRIPTION
      "-v1.16
       -Added s550StockOutputTrap notification definition."

    REVISION      "201108010900Z"
    DESCRIPTION
      "-v1.15
       -Added evMgmtReprocess object."

    REVISION      "201107080900Z"
    DESCRIPTION
      "-v1.14
       -Added wirelessModemStatus branch."

    REVISION      "201101050900Z"
    DESCRIPTION
      "-v1.13
       -Added espcCCNormalThreshold object."

    REVISION      "201011030900Z"
    DESCRIPTION
      "-v1.12
       -Changed deadband, threshold, and current values for temperature
       sensors from integer to floating-point type.  This means the
       SNMP object type for the temperature settings (deadbands and
       thresholds) changed from Integer32 to DisplayString.
       -Fixed bug where SNMP integer range defined in the MIB for
       trapIncludedValue was 16-bit instead of 32-bit."

    REVISION      "201008240900Z"
    DESCRIPTION
      "-v1.11
       -Fixed bug where some stock traps had too few varbinds declared.
       -Removed useless trap definitions."

    REVISION      "201003160900Z"
    DESCRIPTION
      "-v1.10
       -Removed useless objects consoleInlineHsk, consoleBaud, consoleFormat, consoleHsk."

    REVISION      "201001190900Z"
    DESCRIPTION
      "-v1.09
       -Increased range for esPointValueInt"

    REVISION      "200811210900Z"
    DESCRIPTION
      "-v1.08
       -Added scripting variable objects."

    REVISION      "200811120900Z"
    DESCRIPTION
      "-v1.07
       -Corrected comments for stock trap definitions."

    REVISION      "200806090900Z"
    DESCRIPTION
      "-v1.06
       -Added sysLocation branch.
       -Updated phone numbers in contact info block."

    REVISION      "200806021100Z"
    DESCRIPTION
      "-v1.05
       -Added SitePath CPE routing authorization requested stock trap."

    REVISION      "200805151500Z"
    DESCRIPTION
      "-v1.04
       -Added pager settings"

    REVISION      "200805081426Z"
    DESCRIPTION
      "-v1.03
       -Fixed issue where commented OIDs used wrong module identity number"

    REVISION      "200804221652Z"
    DESCRIPTION
      "-v1.02
       -Added missing wireless objects
       -Removed wirelessBaud object which broke mib walk
       -Fixed issue where snmpNotificationTx branch was defined wrong."

    REVISION      "200803211650Z"
    DESCRIPTION
      "-v1.01
       -Added missing CPEDown/VPNGDow notification definitions"

    REVISION      "200712070030Z"
    DESCRIPTION
      "-v1.00
       -Branched new MIB off of SiteBoss 570 MIB"

    ::= { asentria 10 }
    --1.3.6.1.4.1.3052.10


--***************************************************************************************
--Concise MIB View: Top Level Branches
--***************************************************************************************

--  status                                 .1
--    eventSensorStatus                    .1.1
--      esPointTable                       .1.1.1
--    dataEventStatus                      .1.2
--      deStatusTable                      .1.2.1
--    modemStatus                          .1.3
--    modemCLIDLogTable                    .1.4
--    powerDistributionStatus              .1.5
--    fuelSensorStatus                     .1.6
--      fsStatusTable                      .1.6.1
--    wirelessModemStatus                  .1.7
--    acPowerMonitorStatus                 .1.8
--      acpmStatusTable                    .1.8.1
--    evHVACStatus                         .1.11
--      evHVACStatusBard                   .1.11.2
--      evHVACStatusAsentria               .1.11.3
--      evHVACStatusAirsys                 .1.11.4
--    backupBattStatus                     .1.12
--      liBattStatus                       .1.12.1
--  config                                 .2
--    eventSensorBasics                    .2.1
--      esNumberEventSensors               .2.1.1
--      esTable                            .2.1.2
--        esNewSensors                     .2.1.3
--    eventSensorPointConfig               .2.2
--      esPointConfigTempTable             .2.2.1
--      esPointConfigCCTable               .2.2.2
--      esPointConfigHumidTable            .2.2.3
--      esPointConfigAITable               .2.2.5
--      esPointConfigOutputTable           .2.2.6
--    serialPorts                          .2.3
--      numberPorts                        .2.3.1
--      portConfigTable                    .2.3.2
--    network                              .2.4
--      interface                          .2.4.1
--      defaultRouter                      .2.4.2
--      dnsTable                           .2.4.3
--      hostname                           .2.4.4
--      hostTable                          .2.4.5
--      ncpDuplex                          .2.4.6
--      ncpTimeout                         .2.4.7
--      snmp                               .2.4.8
--      ftpPush                            .2.4.9
--      ppp                                .2.4.10
--      routing                            .2.4.11
--      netSecurity                        .2.4.12
--      rts                                .2.4.13
--      trap                               .2.4.14
--      routeTest                          .2.4.15
--      gprs                               .2.4.16
--      email                              .2.4.17
--      netAdvanced                        .2.4.18
--      web                                .2.4.19
--      ethExpan                           .2.4.20
--      ipv6                               .2.4.21
--      cpe                                .2.4.22
--      dnp3                               .2.4.23
--    modem                                .2.5
--    time                                 .2.8
--      clock                              .2.8.1
--    console                              .2.10
--    unitSecurity                         .2.11
--      secCore                            .2.11.1
--      secUserTable                       .2.11.2
--      secFactory                         .2.11.3
--      secSSH                             .2.11.4
--      secVPN                             .2.11.5
--    event                                .2.12
--      evCore                             .2.12.1
--      evData                             .2.12.2
--      evNoData1                          .2.12.3
--      evNoData2                          .2.12.4
--      evSched1                           .2.12.5
--      evSched2                           .2.12.6
--      evShskLowTable                     .2.12.7
--      evShskHighTable                    .2.12.8
--      evNoSensor                         .2.12.9
--      fuelSensor                         .2.12.11
--        fuelSensorGeneralTable           .2.12.11.1
--        fuelSensorTankTable              .2.12.11.2
--        fuelSensorCustomTankTable        .2.12.11.3
--        fuelSensorVolumeTable            .2.12.11.4
--        fuelSensorDisconnectTable        .2.12.11.5
--        fuelSensorSuddenChangeTable      .2.12.11.6
--        fuelSensorSlowChangeTable        .2.12.11.7
--      acPowerMonitor                     .2.12.12
--      evReset                            .2.12.16
--      evGlobal                           .2.12.18
--      evHVAC                             .2.12.19
--        evHVACGeneral                    .2.12.19.1
--        evHVACBard                       .2.12.19.2
--        evHVACAsentria                   .2.12.19.3
--        evHVACAirsys                     .2.12.19.4
--      evEvps                             .2.12.20
--      accessControl                      .2.12.21
--      telemetry                          .2.12.22
--      siteSecurity                       .2.12.23          
--    action                               .2.14
--      actionCallNumberTable              .2.14.1
--      actionPagerTable                   .2.14.2
--      actionSched                        .2.14.3
--      actionAsentria                     .2.14.4
--      actionHostTable                    .2.14.6
--      actionEmailTable                   .2.14.7
--      actionParseError                   .2.14.8
--    sys                                  .2.16
--      sysTime                            .2.16.1
--      sysPT                              .2.16.2
--      sysMTU                             .2.16.3
--      sysAnswerString                    .2.16.4
--      sysEventFileID                     .2.16.6
--      sysEscapeCharacter                 .2.16.7
--      sysTimeStamp                       .2.16.8
--      sysLog                             .2.16.9
--      sysCRDB                            .2.16.10
--      sysCharMask                        .2.16.11
--      sysPrompt                          .2.16.12
--      sysBootStatus                      .2.16.13
--      sysLoc                             .2.16.14
--      sysAssetMgmt                       .2.16.15
--      sysFileTransfer                    .2.16.17
--      sysUpdate                          .2.16.18
--    auditLog                             .2.17
--    scripting                            .2.18
--      scrGlobalEnable                    .2.18.1
--      scrDTRCtrlPortEnableTable          .2.18.2
--      scrTable                           .2.18.3
--      scrVolatileStringTable             .2.18.4
--      scrVolatileIntTable                .2.18.5
--      scrNonVolatileStringTable          .2.18.6
--      scrNonVolatileIntTable             .2.18.7
--    generator                            .2.19
--      genSet                             .2.19.1
--        genSetRelay                      .2.19.1.2
--        genSetCc                         .2.19.1.3
--      genRun                             .2.19.2
--        genRunNonstartEvent              .2.19.2.7
--    calendar                             .2.20
--  productIds                             .3
--    siteName                              3.1
--    thisProduct                          .3.2
--    stockTrapString                      .3.3
--    trapEventTypeNumber                  .3.4
--    trapEventTypeName                    .3.5
--    trapIncludedValue                    .3.6
--    trapIncludedString                   .3.7
--    trapTypeString                       .3.8
--    trapEventClassNumber                 .3.9
--    trapEventClassName                   .3.10
--  keyInterface                           .4.0

--***************************************************************************************
--Complete MIB View: All Objects
--***************************************************************************************

--  status                                           .1
--    eventSensorStatus                              .1.1
--      esPointTable                                 .1.1.1
--        esPointEntry                               .1.1.1.1
--          esIndexES                                .1.1.1.1.1
--          esIndexPC                                .1.1.1.1.2
--          esIndexPoint                             .1.1.1.1.3
--          esPointName                              .1.1.1.1.4
--          esPointInEventState                      .1.1.1.1.5
--          esPointValueInt                          .1.1.1.1.6
--          esPointValueStr                          .1.1.1.1.7
--          esPointTimeLastChange                    .1.1.1.1.8
--          esPointTimetickLastChange                .1.1.1.1.9
--          esPointAliasValueStr                     .1.1.1.1.10
--          esPointClassValueStr                     .1.1.1.1.11
--    dataEventStatus                                .1.2
--      deStatusTable                                .1.2.1
--        deStatusEntry                              .1.2.1.1
--          deStatusIndex                            .1.2.1.1.1
--          deStatusName                             .1.2.1.1.2
--          deStatusCounter                          .1.2.1.1.3
--          deStatusThreshold                        .1.2.1.1.4
--    modemStatus                                    .1.3
--    modemCLIDLogTable                              .1.4
--      modemCLIDLogEntry                            .1.4.1
--        modemCLIDLogIndex                          .1.4.1.1
--        modemCLIDLogNumber                         .1.4.1.2
--    powerDistributionStatus                        .1.5
--      pdConfig                                     .1.5.1
--      pdNextGen                                    .1.5.4
--        pdnTable                                   .1.5.4.1
--          pdnEntry                                 .1.5.4.1.1
--            pdnIndexPD                             .1.5.4.1.1.1
--            pdnIndexOutput                         .1.5.4.1.1.2
--            pdnConfig                              .1.5.4.1.1.3
--            pdnMainCurrentInEventState             .1.5.4.1.1.4
--            pdnMainCurrentValue                    .1.5.4.1.1.5
--            pdnMainCurrentValueStr                 .1.5.4.1.1.6
--            pdnMainCurrentDeadband                 .1.5.4.1.1.7
--            pdnMainCurrentVHighCurrent             .1.5.4.1.1.8
--            pdnMainCurrentHighCurrent              .1.5.4.1.1.9
--            pdnMainCurrentLowCurrent               .1.5.4.1.1.10
--            pdnMainCurrentVLowCurrent              .1.5.4.1.1.11
--            pdnMainVoltageInEventState             .1.5.4.1.1.12
--            pdnMainVoltageValue                    .1.5.4.1.1.13
--            pdnMainVoltageValueStr                 .1.5.4.1.1.14
--            pdnMainVoltageDeadband                 .1.5.4.1.1.15
--            pdnMainVoltageVHighVoltage             .1.5.4.1.1.16
--            pdnMainVoltageHighVoltage              .1.5.4.1.1.17
--            pdnMainVoltageLowVoltage               .1.5.4.1.1.18
--            pdnMainVoltageVLowVoltage              .1.5.4.1.1.19
--            pdnMainPowerValue                      .1.5.4.1.1.20
--            pdnMainPowerValueStr                   .1.5.4.1.1.21
--            pdnOutputCurrentInEventState           .1.5.4.1.1.22
--            pdnOutputCurrentValue                  .1.5.4.1.1.23
--            pdnOutputCurrentValueStr               .1.5.4.1.1.24
--            pdnOutputCurrentDeadband               .1.5.4.1.1.25
--            pdnOutputCurrentVHighCurrent           .1.5.4.1.1.26
--            pdnOutputCurrentHighCurrent            .1.5.4.1.1.27
--            pdnOutputCurrentLowCurrent             .1.5.4.1.1.28
--            pdnOutputCurrentVLowCurrent            .1.5.4.1.1.29
--            pdnOutputFuseInEventState              .1.5.4.1.1.30
--            pdnOutputFuseValueStr                  .1.5.4.1.1.31
--            pdnMainCombinedStatus                  .1.5.4.1.1.32
--            pdnOutputCombinedStatusBlock1          .1.5.4.1.1.33
--            pdnOutputCombinedStatusBlock2          .1.5.4.1.1.34
--            pdnDeviceCurrentValue                  .1.5.4.1.1.35
--            pdnDeviceCurrentValueStr               .1.5.4.1.1.36
--      pdSystem                                     .1.5.5
--        pdSystemCurrent                            .1.5.5.1
--        pdSystemPower                              .1.5.5.2
--    fuelSensorStatus                               .1.6
--      fsStatusTable                                .1.6.1
--        fsStatusEntry                              .1.6.1.1
--          fsStatusIndex                            .1.6.1.1.1
--          fsStatusName                             .1.6.1.1.2
--          fsStatusDeviceState                      .1.6.1.1.3
--          fsStatusVolumeValueString                .1.6.1.1.4
--          fsStatusVolumePercentLevel               .1.6.1.1.7
--          fsStatusVolumeInEventState               .1.6.1.1.8
--          fsStatusCombined                         .1.6.1.1.9
--    wirelessModemStatus                            .1.7
--      wmsStatus                                    .1.7.1
--      wmsSignal                                    .1.7.2
--      wmsRSSI                                      .1.7.3
--      wmsBER                                       .1.7.4
--      wmsUpdated                                   .1.7.5
--      wmsRegistration                              .1.7.6
--      wmsLAC                                       .1.7.7
--      wmsCellID                                    .1.7.8
--      wmsIMSI                                      .1.7.9
--      wmsPhnum                                     .1.7.10
--      wmsLocalIP                                   .1.7.11
--      wmsMgfID                                     .1.7.12
--      wmsModelID                                   .1.7.13
--      wmsIMEI                                      .1.7.14
--      wmsRevID                                     .1.7.15
--      wmsNetName                                   .1.7.16
--      wmsGPRSStatus                                .1.7.17
--      wmsBand                                      .1.7.18
--      wmsChannel                                   .1.7.19
--      wmsCountryCode                               .1.7.20
--      wmsNetCode                                   .1.7.21
--      wmsPLMNColor                                 .1.7.22
--      wmsBScolor                                   .1.7.23
--      wmsMpRACH                                    .1.7.24
--      wmsMinRxLevel                                .1.7.25
--      wmsBaseCoeff                                 .1.7.26
--      wmsSIMStatus                                 .1.7.27
--      wmsICCID                                     .1.7.28
--      wmsModemType                                 .1.7.29
--    acPowerMonitorStatus                           .1.8
--      acpmStatusTable                              .1.8.1
--        acpmStatusEntry                            .1.8.1.1
--          acpmsIndex                               .1.8.1.1.1
--          acpmsName                                .1.8.1.1.2
--          acpmsAvgVoltageValueStr                  .1.8.1.1.3
--          acpmsAvgVoltageMinStr                    .1.8.1.1.4
--          acpmsAvgVoltageMaxStr                    .1.8.1.1.5
--          acpmsAvgVoltageAvgStr                    .1.8.1.1.6
--          acpmsAvgVoltageInEventState              .1.8.1.1.7
--          acpmsVoltagePhaseAValueStr               .1.8.1.1.8
--          acpmsVoltagePhaseBValueStr               .1.8.1.1.9
--          acpmsVoltagePhaseCValueStr               .1.8.1.1.10
--          acpmsVoltageL1L2Value                    .1.8.1.1.11
--          acpmsVoltageL2L3Value                    .1.8.1.1.12
--          acpmsVoltageL3L1Value                    .1.8.1.1.13
--          acpmsAvgCurrentValueStr                  .1.8.1.1.14
--          acpmsAvgCurrentMinStr                    .1.8.1.1.15
--          acpmsAvgCurrentMaxStr                    .1.8.1.1.16
--          acpmsAvgCurrentAvgStr                    .1.8.1.1.17
--          acpmsAvgCurrentInEventState              .1.8.1.1.18
--          acpmsCurrentPhaseAValueStr               .1.8.1.1.19
--          acpmsCurrentPhaseBValueStr               .1.8.1.1.20
--          acpmsCurrentPhaseCValueStr               .1.8.1.1.21
--          acpmsFreqValueStr                        .1.8.1.1.22
--          acpmsFreqMinStr                          .1.8.1.1.23
--          acpmsFreqMaxStr                          .1.8.1.1.24
--          acpmsFreqAvgStr                          .1.8.1.1.25
--          acpmsFreqInEventState                    .1.8.1.1.26
--          acpmsTRPValueStr                         .1.8.1.1.27
--          acpmsTRPMinStr                           .1.8.1.1.28
--          acpmsTRPMaxStr                           .1.8.1.1.29
--          acpmsTRPAvgStr                           .1.8.1.1.30
--          acpmsTRPInEventState                     .1.8.1.1.31
--          acpmsRPPhaseAValueStr                    .1.8.1.1.32
--          acpmsRPPhaseBValueStr                    .1.8.1.1.33
--          acpmsRPPhaseCValueStr                    .1.8.1.1.34
--          acpmsCombined                            .1.8.1.1.35
--          acpmsTPFValueStr                         .1.8.1.1.36
--          acpmsTPFMinStr                           .1.8.1.1.37
--          acpmsTPFMaxStr                           .1.8.1.1.38
--          acpmsTPFAvgStr                           .1.8.1.1.39
--          acpmsTPFInEventState                     .1.8.1.1.40
--          acpmsPFPhaseAValueStr                    .1.8.1.1.41
--          acpmsPFPhaseBValueStr                    .1.8.1.1.42
--          acpmsPFPhaseCValueStr                    .1.8.1.1.43
--          acpmsTRcPValueStr                        .1.8.1.1.44
--          acpmsTRcPMinStr                          .1.8.1.1.45
--          acpmsTRcPMaxStr                          .1.8.1.1.46
--          acpmsTRcPAvgStr                          .1.8.1.1.47
--          acpmsRcPPhaseAValueStr                   .1.8.1.1.48
--          acpmsRcPPhaseBValueStr                   .1.8.1.1.49
--          acpmsRcPPhaseCValueStr                   .1.8.1.1.50
--          acpmsTAPValueStr                         .1.8.1.1.51
--          acpmsTAPMinStr                           .1.8.1.1.52
--          acpmsTAPMaxStr                           .1.8.1.1.53
--          acpmsTAPAvgStr                           .1.8.1.1.54
--          acpmsAPPhaseAValueStr                    .1.8.1.1.55
--          acpmsAPPhaseBValueStr                    .1.8.1.1.56
--          acpmsAPPhaseCValueStr                    .1.8.1.1.57
--          acpmsTotalEnergyWh                       .1.8.1.1.58
--          acpmsTotalEnergyVAR                      .1.8.1.1.59
--          acpmsTotalEnergyVA                       .1.8.1.1.60
--          acmpsAvgVoltageAlarmDatetime             .1.8.1.1.61
--          acmpsAvgCurrentAlarmDatetime             .1.8.1.1.62
--          acmpsFreqAlarmDatetime                   .1.8.1.1.63
--          acmpsRealPowerAlarmDatetime              .1.8.1.1.64
--          acmpsPowerFactorAlarmDatetime            .1.8.1.1.65
--    evHVACStatus                                   .1.11
--      evHVACStatusBard                             .1.11.2
--        evHVACStatusBardSystem1                    .1.11.2.1
--          evHVACStatusBardSystem1Stage1            .1.11.2.1.1
--            evHVACStatusBardSystem1Stage1Cooling   .1.11.2.1.1.1
--          evHVACStatusBardSystem1Stage2            .1.11.2.1.2
--            evHVACStatusBardSystem1Stage2Cooling   .1.11.2.1.2.1
--          evHVACStatusBardSystem1Blower            .1.11.2.1.3
--          evHVACStatusBardSystem1Heating           .1.11.2.1.4
--          evHVACStatusBardSystem1Economizer        .1.11.2.1.5
--        evHVACStatusBardSystem2                    .1.11.2.2
--          evHVACStatusBardSystem2Stage1            .1.11.2.2.1
--            evHVACStatusBardSystem2Stage1Cooling   .1.11.2.2.1.1
--          evHVACStatusBardSystem2Stage2            .1.11.2.2.2
--            evHVACStatusBardSystem2Stage2Cooling   .1.11.2.2.2.1
--          evHVACStatusBardSystem2Blower            .1.11.2.2.3
--          evHVACStatusBardSystem2Heating           .1.11.2.2.4
--          evHVACStatusBardSystem2Economizer        .1.11.2.2.5
--        evHVACStatusBardTempAvg                    .1.11.2.3
--        evHVACStatusBardTempLocal                  .1.11.2.4
--        evHVACStatusBardTempRemote                 .1.11.2.5
--          evHVACStatusBardTempRemote1              .1.11.2.5.1
--          evHVACStatusBardTempRemote2              .1.11.2.5.2
--        evHVACStatusBardDehumidification           .1.11.2.6
--        evHVACStatusBardLEDs                       .1.11.2.7
--          evHVACStatusBardLEDsCooling              .1.11.2.7.1
--            evHVACStatusBardLEDsCooling1           .1.11.2.7.1.1
--            evHVACStatusBardLEDsCooling2           .1.11.2.7.1.2
--            evHVACStatusBardLEDsCooling3           .1.11.2.7.1.3
--            evHVACStatusBardLEDsCooling4           .1.11.2.7.1.4
--          evHVACStatusBardLEDsHeating              .1.11.2.7.2
--            evHVACStatusBardLEDsHeating1           .1.11.2.7.2.1
--            evHVACStatusBardLEDsHeating2           .1.11.2.7.2.2
--            evHVACStatusBardLEDsHeating3           .1.11.2.7.2.3
--            evHVACStatusBardLEDsHeating4           .1.11.2.7.2.4
--          evHVACStatusBardLEDsDeHumid              .1.11.2.7.3
--            evHVACStatusBardLEDsDeHumid1           .1.11.2.7.3.1
--        evHVACStatusBardGenerator                  .1.11.2.8
--        evHVACStatusBardAlarmBoardState            .1.11.2.9
--        evHVACStatusBardAlarmStatus                .1.11.2.10
--          evHVACStatusBardASSystem1                .1.11.2.10.1
--            evHVACStatusBardASSystem1PowerLoss     .1.11.2.10.1.1
--            evHVACStatusBardASSystem1Lockout       .1.11.2.10.1.2
--          evHVACStatusBardASSystem2                .1.11.2.10.2
--            evHVACStatusBardASSystem2PowerLoss     .1.11.2.10.2.1
--            evHVACStatusBardASSystem2Lockout       .1.11.2.10.2.2
--          evHVACStatusBardASFire                   .1.11.2.10.3
--          evHVACStatusBardASTemp                   .1.11.2.10.4
--            evHVACStatusBardASTempLowAlarm         .1.11.2.10.4.1
--            evHVACStatusBardASTempHighAlarm        .1.11.2.10.4.2
--            evHVACStatusBardASTempVHighAlarm       .1.11.2.10.4.3
--          evHVACStatusBardASFailure                .1.11.2.10.5
--        evHVACStatusBardConnState                  .1.11.2.11
--      evHVACStatusAsentria                         .1.11.3
--        evHVACStatusAsentriaSequenceTable          .1.11.3.1
--          evHVACStatusAsentriaSequenceEntry        .1.11.3.1.1
--            evHVACStatusAsentriaSequenceIndex      .1.11.3.1.1.1
--            evHVACStatusAsentriaSeqVentTime        .1.11.3.1.1.2
--            evHVACStatusAsentriaSeqCoolTime        .1.11.3.1.1.3
--            evHVACStatusAsentriaSeqHeatTime        .1.11.3.1.1.4
--            evHVACStatusAsentriaSeqIdleTime        .1.11.3.1.1.5
--        evHVACStatusAsentriaUnitTable              .1.11.3.2
--          evHVACStatusAsentriaUnitEntry            .1.11.3.2.1
--            evHVACStatusAsentriaUnitIndex          .1.11.3.2.1.1
--            evHVACStatusAsentriaUnitState          .1.11.3.2.1.2
--            evHVACStatusAsentriaUnitVentTime       .1.11.3.2.1.3
--            evHVACStatusAsentriaUnitCoolTime       .1.11.3.2.1.4
--            evHVACStatusAsentriaUnitHeatTime       .1.11.3.2.1.5
--            evHVACStatusAsentriaUnitIdleTime       .1.11.3.2.1.6
--        evHVACStatusAsentriaBackupEvent            .1.11.3.3
--        evHVACStatusAsentriaFireEvent              .1.11.3.4
--        evHVACStatusAsentriaTemp                   .1.11.3.5
--          evHVACStatusAsentriaTempOut              .1.11.3.5.1
--          evHVACStatusAsentriaTempIn               .1.11.3.5.2
--        evHVACStatusAsentriaHumid                  .1.11.3.6
--          evHVACStatusAsentriaHumidOut             .1.11.3.6.1
--          evHVACStatusAsentriaHumidIn              .1.11.3.6.2
--      evHVACStatusAirsys                           .1.11.4
--        evHVACStatusAirsysAlarm                    .1.11.4.1
--          evHVACStatusAirsysAlarmUnitTable         .1.11.4.1.1
--            evHVACStatusAirsysAlarmUnitEntry       .1.11.4.1.1.1
--              evHVACStatusAirsysAlarmUnitIndex     .1.11.4.1.1.1.1
--              evHVACStatusAirsysAlarmUnitLowPress  .1.11.4.1.1.1.2
--              evHVACStatusAirsysAlarmUnitHighPress .1.11.4.1.1.1.3
--              evHVACStatusAirsysAlarmUnitEvapFan   .1.11.4.1.1.1.4
--              evHVACStatusAirsysAlarmUnitDirty     .1.11.4.1.1.1.5
--              evHVACStatusAirsysAlarmUnitDamper    .1.11.4.1.1.1.6
--              evHVACStatusAirsysAlarmUnitSupProbe  .1.11.4.1.1.1.7
--          evHVACStatusAirsysAlarmSmokeFire         .1.11.4.1.2
--          evHVACStatusAirsysAlarmLowRoomTemp       .1.11.4.1.3
--          evHVACStatusAirsysAlarmHighRoomTemp      .1.11.4.1.4
--          evHVACStatusAirsysAlarmPower             .1.11.4.1.5
--          evHVACStatusAirsysAlarmpLAN              .1.11.4.1.6
--          evHVACStatusAirsysAlarmClock             .1.11.4.1.7
--          evHVACStatusAirsysAlarmHumidProbe        .1.11.4.1.8
--          evHVACStatusAirsysAlarmOutProbe          .1.11.4.1.9
--          evHVACStatusAirsysAlarmBothCompress      .1.11.4.1.10
--          evHVACStatusAirsysAlarmGenerator         .1.11.4.1.11
--          evHVACStatusAirsysAlarmConnection        .1.11.4.1.12
--          evHVACStatusAirsysAlarmInProbe1          .1.11.4.1.13
--          evHVACStatusAirsysAlarmInProbe2          .1.11.4.1.14
--        evHVACStatusAirsysTempOut                  .1.11.4.2
--        evHVACStatusAirsysTempIn                   .1.11.4.3
--        evHVACStatusAirsysTempInBackup             .1.11.4.4
--        evHVACStatusAirsysHumidIn                  .1.11.4.5
--        evHVACStatusAirsysUnitTable                .1.11.4.6
--          evHVACStatusAirsysUnitEntry              .1.11.4.6.1
--            evHVACStatusAirsysUnitIndex            .1.11.4.6.1.1
--            evHVACStatusAirsysUnitTempSupply       .1.11.4.6.1.2
--            evHVACStatusAirsysUnitFanspeed         .1.11.4.6.1.3
--            evHVACStatusAirsysUnitFreeOpening      .1.11.4.6.1.4
--            evHVACStatusAirsysUnitStatus           .1.11.4.6.1.5
--            evHVACStatusAirsysUnitLocked           .1.11.4.6.1.6
--            evHVACStatusAirsysUnitCompressor       .1.11.4.6.1.7
--            evHVACStatusAirsysUnitHeater           .1.11.4.6.1.8
--            evHVACStatusAirsysURuntimeSupplyFan    .1.11.4.6.1.9
--            evHVACStatusAirsysURuntimeCompressor   .1.11.4.6.1.10
--            evHVACStatusAirsysURuntimeHeat         .1.11.4.6.1.11
--            evHVACStatusAirsysURuntimeFreeCooling  .1.11.4.6.1.12
--            evHVACStatusAirsysUCountSupplyFan      .1.11.4.6.1.13
--            evHVACStatusAirsysUCountCompressor     .1.11.4.6.1.14
--            evHVACStatusAirsysUCountHeat           .1.11.4.6.1.15
--            evHVACStatusAirsysUCountFreeCooling    .1.11.4.6.1.16
--        evHVACStatusAirsysDay                      .1.11.4.7
--        evHVACStatusAirsysDate                     .1.11.4.8
--        evHVACStatusAirsysTime                     .1.11.4.9
--        evHVACStatusAirsysVersion                  .1.11.4.10
--    backupBattStatus                               .1.12
--      liBattStatus                                 .1.12.1
--        liBattPercentCharge                          .1.12.1.1
--        liBattRunning                                .1.12.1.2
--  config                                           .2
--    eventSensorBasics                              .2.1
--      esNumberEventSensors                         .2.1.1
--      esTable                                      .2.1.2
--        esEntry                                    .2.1.2.1
--          esIndex                                  .2.1.2.1.1
--          esName                                   .2.1.2.1.2
--          esID                                     .2.1.2.1.3
--          esNumberTempSensors                      .2.1.2.1.4
--          esTempReportingMode                      .2.1.2.1.5
--          esNumberCCs                              .2.1.2.1.6
--          esCCReportingMode                        .2.1.2.1.7
--          esNumberHumidSensors                     .2.1.2.1.8
--          esHumidReportingMode                     .2.1.2.1.9
--          esNumberNoiseSensors                     .2.1.2.1.10
--          esNoiseReportingMode                     .2.1.2.1.11
--          esNumberAirflowSensors                   .2.1.2.1.12
--          esAirflowReportingMode                   .2.1.2.1.13
--          esNumberAnalog                           .2.1.2.1.14
--          esAnalogReportingMode                    .2.1.2.1.15
--          esNumberOutputs                          .2.1.2.1.16
--          esOutputReportingMode                    .2.1.2.1.17
--          esTempCombinedStatus                     .2.1.2.1.18
--          esCCCombinedStatusBlock1                 .2.1.2.1.19
--          esCCCombinedStatusBlock2                 .2.1.2.1.20
--          esCCCombinedStatusBlock3                 .2.1.2.1.21
--          esCCCombinedStatusBlock4                 .2.1.2.1.22
--          esCCCombinedStatusBlock5                 .2.1.2.1.23
--          esCCCombinedStatusBlock6                 .2.1.2.1.24
--          esCCCombinedStatusBlock7                 .2.1.2.1.25
--          esCCCombinedStatusBlock8                 .2.1.2.1.26
--          esHumidCombinedStatus                    .2.1.2.1.27
--          esAnalogCombinedStatusBlock1             .2.1.2.1.28
--          esAnalogCombinedStatusBlock2             .2.1.2.1.29
--          esAnalogCombinedStatusBlock3             .2.1.2.1.30
--          esAnalogCombinedStatusBlock4             .2.1.2.1.31
--          esAnalogCombinedStatusBlock5             .2.1.2.1.32
--          esAnalogCombinedStatusBlock6             .2.1.2.1.33
--          esOutputCombinedStatusBlock1             .2.1.2.1.34
--          esOutputCombinedStatusBlock2             .2.1.2.1.35
--        esNewSensors                               .2.1.3
--    eventSensorPointConfig                         .2.2
--      esPointConfigTempTable                       .2.2.1
--        esPointConfigTempEntry                     .2.2.1.1
--          espcTempIndexES                          .2.2.1.1.1
--          espcTempIndexPoint                       .2.2.1.1.2
--          espcTempEnable                           .2.2.1.1.3
--          espcTempScale                            .2.2.1.1.4
--          espcTempDeadband                         .2.2.1.1.5
--          espcTempVHighTemp                        .2.2.1.1.6
--          espcTempVHighActions                     .2.2.1.1.7
--          espcTempVHighTrapnum                     .2.2.1.1.8
--          espcTempVHighClass                       .2.2.1.1.9
--          espcTempHighTemp                         .2.2.1.1.10
--          espcTempHighActions                      .2.2.1.1.11
--          espcTempHighTrapnum                      .2.2.1.1.12
--          espcTempHighClass                        .2.2.1.1.13
--          espcTempNormalActions                    .2.2.1.1.14
--          espcTempNormalTrapnum                    .2.2.1.1.15
--          espcTempNormalClass                      .2.2.1.1.16
--          espcTempLowTemp                          .2.2.1.1.17
--          espcTempLowActions                       .2.2.1.1.18
--          espcTempLowTrapnum                       .2.2.1.1.19
--          espcTempLowClass                         .2.2.1.1.20
--          espcTempVLowTemp                         .2.2.1.1.21
--          espcTempVLowActions                      .2.2.1.1.22
--          espcTempVLowTrapnum                      .2.2.1.1.23
--          espcTempVLowClass                        .2.2.1.1.24
--          espcTempGroup                            .2.2.1.1.25
--      esPointConfigCCTable                         .2.2.2
--        esPointConfigCCEntry                       .2.2.2.1
--          espcCCIndexES                            .2.2.2.1.1
--          espcCCIndexPoint                         .2.2.2.1.2
--          espcCCEnable                             .2.2.2.1.3
--          espcCCName                               .2.2.2.1.4
--          espcCCEventState                         .2.2.2.1.5
--          espcCCThreshold                          .2.2.2.1.6
--          espcCCEventActions                       .2.2.2.1.7
--          espcCCEventTrapnum                       .2.2.2.1.8
--          espcCCEventClass                         .2.2.2.1.9
--          espcCCNormalActions                      .2.2.2.1.10
--          espcCCNormalTrapnum                      .2.2.2.1.11
--          espcCCNormalClass                        .2.2.2.1.12
--          espcCCAlarmAlias                         .2.2.2.1.13
--          espcCCNormalAlias                        .2.2.2.1.14
--          espcCCNormalThreshold                    .2.2.2.1.15
--          espcCCOverrideGlobalReminder             .2.2.2.1.16
--          espcCCReminderInterval                   .2.2.2.1.17
--          espcCCGroup                              .2.2.2.1.18
--      esPointConfigHumidTable                      .2.2.3
--        esPointConfigHumidEntry                    .2.2.3.1
--          espcHumidIndexES                         .2.2.3.1.1
--          espcHumidIndexPoint                      .2.2.3.1.2
--          espcHumidEnable                          .2.2.3.1.3
--          espcHumidDeadband                        .2.2.3.1.4
--          espcHumidVHighHumid                      .2.2.3.1.5
--          espcHumidVHighActions                    .2.2.3.1.6
--          espcHumidVHighTrapnum                    .2.2.3.1.7
--          espcHumidVHighClass                      .2.2.3.1.8
--          espcHumidHighHumid                       .2.2.3.1.9
--          espcHumidHighActions                     .2.2.3.1.10
--          espcHumidHighTrapnum                     .2.2.3.1.11
--          espcHumidHighClass                       .2.2.3.1.12
--          espcHumidNormalActions                   .2.2.3.1.13
--          espcHumidNormalTrapnum                   .2.2.3.1.14
--          espcHumidNormalClass                     .2.2.3.1.15
--          espcHumidLowHumid                        .2.2.3.1.16
--          espcHumidLowActions                      .2.2.3.1.17
--          espcHumidLowTrapnum                      .2.2.3.1.18
--          espcHumidLowClass                        .2.2.3.1.19
--          espcHumidVLowHumid                       .2.2.3.1.20
--          espcHumidVLowActions                     .2.2.3.1.21
--          espcHumidVLowTrapnum                     .2.2.3.1.22
--          espcHumidVLowClass                       .2.2.3.1.23
--          espcHumidGroup                           .2.2.3.1.24
--      esPointConfigAITable                         .2.2.5
--        esPointConfigAIEntry                       .2.2.5.1
--          espcAIIndexES                            .2.2.5.1.1
--          espcAIIndexPoint                         .2.2.5.1.2
--          espcAIEnable                             .2.2.5.1.3
--          espcAIDeadband                           .2.2.5.1.5
--          espcAIVhighValue                         .2.2.5.1.6
--          espcAIVhighActions                       .2.2.5.1.7
--          espcAIVhighTrapnum                       .2.2.5.1.8
--          espcAIVhighClass                         .2.2.5.1.9
--          espcAIHighValue                          .2.2.5.1.10
--          espcAIHighActions                        .2.2.5.1.11
--          espcAIHighTrapnum                        .2.2.5.1.12
--          espcAIHighClass                          .2.2.5.1.13
--          espcAINormalActions                      .2.2.5.1.14
--          espcAINormalTrapnum                      .2.2.5.1.15
--          espcAINormalClass                        .2.2.5.1.16
--          espcAILowValue                           .2.2.5.1.17
--          espcAILowActions                         .2.2.5.1.18
--          espcAILowTrapnum                         .2.2.5.1.19
--          espcAILowClass                           .2.2.5.1.20
--          espcAIVlowValue                          .2.2.5.1.21
--          espcAIVlowActions                        .2.2.5.1.22
--          espcAIVlowTrapnum                        .2.2.5.1.23
--          espcAIVlowClass                          .2.2.5.1.24
--          espcAIConvUnitName                       .2.2.5.1.25
--          espcAIConvHighValue                      .2.2.5.1.26
--          espcAIConvHighUnit                       .2.2.5.1.27
--          espcAIConvLowValue                       .2.2.5.1.29
--          espcAIConvLowUnit                        .2.2.5.1.30
--          espcAIDisplayFormat                      .2.2.5.1.32
--          espcAIGroup                              .2.2.5.1.33
--      esPointConfigOutputTable                     .2.2.6
--        esPointConfigOutputEntry                   .2.2.6.1
--          espcOutputIndexES                        .2.2.6.1.1
--          espcOutputIndexPoint                     .2.2.6.1.2
--          espcOutputEnable                         .2.2.6.1.3
--          espcOutputActiveState                    .2.2.6.1.4
--          espcOutputType                           .2.2.6.1.5
--          espcOutputAliasValue                     .2.2.6.1.6
--          espcOutputAliasColor                     .2.2.6.1.7
--          espcOutputActiveAlias                    .2.2.6.1.10
--          espcOutputActiveColor                    .2.2.6.1.11
--          espcOutputActiveActions                  .2.2.6.1.12
--          espcOutputActiveTrapnum                  .2.2.6.1.13
--          espcOutputActiveClass                    .2.2.6.1.14
--          espcOutputInactiveAlias                  .2.2.6.1.20
--          espcOutputInactiveColor                  .2.2.6.1.21
--          espcOutputInactiveActions                .2.2.6.1.22
--          espcOutputInactiveTrapnum                .2.2.6.1.23
--          espcOutputInactiveClass                  .2.2.6.1.24
--          espcOutputGroup                          .2.2.6.1.25
--    serialPorts                                    .2.3
--      numberPorts                                  .2.3.1
--      portConfigTable                              .2.3.2
--        portConfigEntry                            .2.3.2.1
--          portConfigIndex                          .2.3.2.1.1
--          portConfigBaud                           .2.3.2.1.2
--          portConfigDataFormat                     .2.3.2.1.3
--          portConfigStripPtOutputLfs               .2.3.2.1.4
--          portConfigStripPtInputLfs                .2.3.2.1.5
--          portConfigMaskEnable                     .2.3.2.1.7
--          portConfigDAEnable                       .2.3.2.1.8
--          portConfigStoreAlarmsDPT                 .2.3.2.1.9
--          portConfigRecordTimeout                  .2.3.2.1.10
--          portConfigDataType                       .2.3.2.1.11
--          portConfigEtxToCRLF                      .2.3.2.1.12
--          portConfigMLREnable                      .2.3.2.1.13
--          portConfigMLRStartField1Pos              .2.3.2.1.14
--          portConfigMLRStartField1Text             .2.3.2.1.15
--          portConfigMLRStartField2Pos              .2.3.2.1.16
--          portConfigMLRStartField2Text             .2.3.2.1.17
--          portConfigMLRNumLinesBefore              .2.3.2.1.18
--          portConfigMLREndDetection                .2.3.2.1.19
--          portConfigMLRLineCount                   .2.3.2.1.20
--          portConfigMLREndField1Pos                .2.3.2.1.21
--          portConfigMLREndField1Text               .2.3.2.1.22
--          portConfigMLREndField2Pos                .2.3.2.1.23
--          portConfigMLREndField2Text               .2.3.2.1.24
--          portConfigMLRUseComplexRules             .2.3.2.1.25
--          portConfigBufferPT                       .2.3.2.1.26
--          portConfigId                             .2.3.2.1.27
--          portConfigMode                           .2.3.2.1.28
--          portConfigHsk                            .2.3.2.1.29
--    network                                        .2.4
--      interface                                    .2.4.1
--        ethernet                                   .2.4.1.1
--          ethernet1                                .2.4.1.1.1
--            eth1Mode                               .2.4.1.1.1.1
--            eth1Address                            .2.4.1.1.1.2
--            eth1SubnetMask                         .2.4.1.1.1.3
--            eth1Router                             .2.4.1.1.1.4
--            eth1VLAN                               .2.4.1.1.1.5
--              eth1VLAN1                            .2.4.1.1.1.5.1
--                eth1VLAN1ID                        .2.4.1.1.1.5.1.1
--                eth1VLAN1Priority                  .2.4.1.1.1.5.1.2
--                eth1VLAN1Address                   .2.4.1.1.1.5.1.3
--                eth1VLAN1SubnetMask                .2.4.1.1.1.5.1.4
--                eth1VLAN1Router                    .2.4.1.1.1.5.1.5
--              eth1VLAN2                            .2.4.1.1.1.5.2
--                eth1VLAN2ID                        .2.4.1.1.1.5.2.1
--                eth1VLAN2Priority                  .2.4.1.1.1.5.2.2
--                eth1VLAN2Address                   .2.4.1.1.1.5.2.3
--                eth1VLAN2SubnetMask                .2.4.1.1.1.5.2.4
--                eth1VLAN2Router                    .2.4.1.1.1.5.2.5
--              eth1VLAN3                            .2.4.1.1.1.5.3
--                eth1VLAN3ID                        .2.4.1.1.1.5.3.1
--                eth1VLAN3Priority                  .2.4.1.1.1.5.3.2
--                eth1VLAN3Address                   .2.4.1.1.1.5.3.3
--                eth1VLAN3SubnetMask                .2.4.1.1.1.5.3.4
--                eth1VLAN3Router                    .2.4.1.1.1.5.3.5
--              eth1VLAN4                            .2.4.1.1.1.5.4
--                eth1VLAN4ID                        .2.4.1.1.1.5.4.1
--                eth1VLAN4Priority                  .2.4.1.1.1.5.4.2
--                eth1VLAN4Address                   .2.4.1.1.1.5.4.3
--                eth1VLAN4SubnetMask                .2.4.1.1.1.5.4.4
--                eth1VLAN4Router                    .2.4.1.1.1.5.4.5
--              eth1VLAN5                            .2.4.1.1.1.5.5
--                eth1VLAN5ID                        .2.4.1.1.1.5.5.1
--                eth1VLAN5Priority                  .2.4.1.1.1.5.5.2
--                eth1VLAN5Address                   .2.4.1.1.1.5.5.3
--                eth1VLAN5SubnetMask                .2.4.1.1.1.5.5.4
--                eth1VLAN5Router                    .2.4.1.1.1.5.5.5
--              eth1VLAN6                            .2.4.1.1.1.5.6
--                eth1VLAN6ID                        .2.4.1.1.1.5.6.1
--                eth1VLAN6Priority                  .2.4.1.1.1.5.6.2
--                eth1VLAN6Address                   .2.4.1.1.1.5.6.3
--                eth1VLAN6SubnetMask                .2.4.1.1.1.5.6.4
--                eth1VLAN6Router                    .2.4.1.1.1.5.6.5
--              eth1MAC                              .2.4.1.1.1.6
--            eth1IPv6                               .2.4.1.1.1.7
--              eth1IPv6Mode                         .2.4.1.1.1.7.1
--              eth1IPv6Static                       .2.4.1.1.1.7.2
--                eth1IPv6StaticAddress              .2.4.1.1.1.7.2.1
--                eth1IPv6StaticRouter               .2.4.1.1.1.7.2.2
--              eth1IPv6Auto                         .2.4.1.1.1.7.3
--                eth1IPv6AutoAddress1               .2.4.1.1.1.7.3.1
--                eth1IPv6AutoAddress2               .2.4.1.1.1.7.3.2
--                eth1IPv6AutoAddress3               .2.4.1.1.1.7.3.3
--                eth1IPv6AutoAddress4               .2.4.1.1.1.7.3.4
--              eth1IPv6LinkLocalAddress             .2.4.1.1.1.7.4
--          ethernet2                                .2.4.1.1.2
--            eth2Mode                               .2.4.1.1.2.1
--            eth2Address                            .2.4.1.1.2.2
--            eth2SubnetMask                         .2.4.1.1.2.3
--            eth2Router                             .2.4.1.1.2.4
--            eth2VLAN                               .2.4.1.1.2.5
--              eth2VLAN1                            .2.4.1.1.2.5.1
--                eth2VLAN1ID                        .2.4.1.1.2.5.1.1
--                eth2VLAN1Priority                  .2.4.1.1.2.5.1.2
--                eth2VLAN1Address                   .2.4.1.1.2.5.1.3
--                eth2VLAN1SubnetMask                .2.4.1.1.2.5.1.4
--                eth2VLAN1Router                    .2.4.1.1.2.5.1.5
--              eth2VLAN2                            .2.4.1.1.2.5.2
--                eth2VLAN2ID                        .2.4.1.1.2.5.2.1
--                eth2VLAN2Priority                  .2.4.1.1.2.5.2.2
--                eth2VLAN2Address                   .2.4.1.1.2.5.2.3
--                eth2VLAN2SubnetMask                .2.4.1.1.2.5.2.4
--                eth2VLAN2Router                    .2.4.1.1.2.5.2.5
--              eth2VLAN3                            .2.4.1.1.2.5.3
--                eth2VLAN3ID                        .2.4.1.1.2.5.3.1
--                eth2VLAN3Priority                  .2.4.1.1.2.5.3.2
--                eth2VLAN3Address                   .2.4.1.1.2.5.3.3
--                eth2VLAN3SubnetMask                .2.4.1.1.2.5.3.4
--                eth2VLAN3Router                    .2.4.1.1.2.5.3.5
--              eth2VLAN4                            .2.4.1.1.2.5.4
--                eth2VLAN4ID                        .2.4.1.1.2.5.4.1
--                eth2VLAN4Priority                  .2.4.1.1.2.5.4.2
--                eth2VLAN4Address                   .2.4.1.1.2.5.4.3
--                eth2VLAN4SubnetMask                .2.4.1.1.2.5.4.4
--                eth2VLAN4Router                    .2.4.1.1.2.5.4.5
--              eth2VLAN5                            .2.4.1.1.2.5.5
--                eth2VLAN5ID                        .2.4.1.1.2.5.5.1
--                eth2VLAN5Priority                  .2.4.1.1.2.5.5.2
--                eth2VLAN5Address                   .2.4.1.1.2.5.5.3
--                eth2VLAN5SubnetMask                .2.4.1.1.2.5.5.4
--                eth2VLAN5Router                    .2.4.1.1.2.5.5.5
--              eth2VLAN6                            .2.4.1.1.2.5.6
--                eth2VLAN6ID                        .2.4.1.1.2.5.6.1
--                eth2VLAN6Priority                  .2.4.1.1.2.5.6.2
--                eth2VLAN6Address                   .2.4.1.1.2.5.6.3
--                eth2VLAN6SubnetMask                .2.4.1.1.2.5.6.4
--                eth2VLAN6Router                    .2.4.1.1.2.5.6.5
--              eth2MAC                              .2.4.1.1.2.6
--            eth2IPv6                               .2.4.1.1.2.7
--              eth2IPv6Mode                         .2.4.1.1.2.7.1
--              eth2IPv6Static                       .2.4.1.1.2.7.2
--                eth2IPv6StaticAddress              .2.4.1.1.2.7.2.1
--                eth2IPv6StaticRouter               .2.4.1.1.2.7.2.2
--              eth2IPv6Auto                         .2.4.1.1.2.7.3
--                eth2IPv6AutoAddress1               .2.4.1.1.2.7.3.1
--                eth2IPv6AutoAddress2               .2.4.1.1.2.7.3.2
--                eth2IPv6AutoAddress3               .2.4.1.1.2.7.3.3
--                eth2IPv6AutoAddress4               .2.4.1.1.2.7.3.4
--              eth2IPv6LinkLocalAddress             .2.4.1.1.2.7.4
--      defaultRouter                                .2.4.2
--      dnsTable                                     .2.4.3
--        dnsEntry                                   .2.4.3.1
--          dnsIndex                                 .2.4.3.1.1
--          dnsAddress                               .2.4.3.1.2
--      hostname                                     .2.4.4
--      hostTable                                    .2.4.5
--        hostEntry                                  .2.4.5.1
--          hostIndex                                .2.4.5.1.1
--          hostDeclaration                          .2.4.5.1.2
--      ncpDuplex                                    .2.4.6
--      ncpTimeout                                   .2.4.7
--      snmp                                         .2.4.8
--        snmpAgentEnable                            .2.4.8.1
--        snmpNotificationCaptureEnable              .2.4.8.5
--        snmpNotificationCaptureFile                .2.4.8.6
--        snmpNotificationTx                         .2.4.8.7
--          snmpNtfnAttempts                         .2.4.8.7.1
--          snmpNtfnTimeout                          .2.4.8.7.2
--          snmpNtfnCycles                           .2.4.8.7.3
--          snmpNtfnSnooze                           .2.4.8.7.4
--        snmpProxy                                  .2.4.8.8
--          snmpProxyTable                           .2.4.8.8.1
--            snmpProxyEntry                         .2.4.8.8.1.1
--              snmpProxyIndex                       .2.4.8.8.1.1.1
--              snmpProxyEgressOIDBranch             .2.4.8.8.1.1.2
--              snmpProxyIP                          .2.4.8.8.1.1.3
--              snmpProxyPort                        .2.4.8.8.1.1.4
--              snmpProxyIngressOIDBranch            .2.4.8.8.1.1.5
--              snmpProxyName                        .2.4.8.8.1.1.6
--        snmpPoll                                   .2.4.8.9
--          snmpPMode                                .2.4.8.9.1
--          snmpPBufferFile                          .2.4.8.9.2
--          snmpPBufferAllPeriod                     .2.4.8.9.3
--          snmpPRequestTable                        .2.4.8.9.4
--            snmpPRequestEntry                      .2.4.8.9.4.1
--              snmpPRequestIndex                    .2.4.8.9.4.1.1
--              snmpPRequestDescription              .2.4.8.9.4.1.2
--              snmpPRequestAgent                    .2.4.8.9.4.1.3
--              snmpPRequestReadcom                  .2.4.8.9.4.1.4
--              snmpPRequestOID                      .2.4.8.9.4.1.5
--              snmpPRequestPeriod                   .2.4.8.9.4.1.6
--              snmpPRequestID                       .2.4.8.9.4.1.7
--              snmpPRequestThreshold                .2.4.8.9.4.1.8
--              snmpPRequestResultStatus             .2.4.8.9.4.1.10
--              snmpPRequestResultValue              .2.4.8.9.4.1.11
--              snmpPRequestResultTime               .2.4.8.9.4.1.12
--              snmpPRequestResultType               .2.4.8.9.4.1.13
--      ftpPush                                      .2.4.9
--        ftpPushEnable                              .2.4.9.1
--        ftpPushServer                              .2.4.9.2
--        ftpPushAccount                             .2.4.9.5
--        ftpPushDirectory                           .2.4.9.6
--        ftpPushperiod                              .2.4.9.7
--        ftpPushPushFileTable                       .2.4.9.8
--          ftpPushPushFileEntry                     .2.4.9.8.1
--            ftpPushPushFileIndex                   .2.4.9.8.1.1
--            ftpPushPushFile                        .2.4.9.8.1.2
--        ftpPushPushAudit                           .2.4.9.9
--        ftpPushPushAlarms                          .2.4.9.10
--        ftpPushRemoteFileTable                     .2.4.9.11
--          ftpPushRemoteFileEntry                   .2.4.9.11.1
--            ftpPushRemoteFileIndex                 .2.4.9.11.1.1
--            ftpPushRemoteFileName                  .2.4.9.11.1.2
--        ftpPushRemoteAlarmName                     .2.4.9.12
--        ftpPushPassive                             .2.4.9.13
--        ftpPushIncludeDate                         .2.4.9.14
--        ftpPushIncludeTime                         .2.4.9.15
--        ftpPushIncludeSeq                          .2.4.9.16
--        ftpPushPermissions                         .2.4.9.17
--      ppp                                          .2.4.10
--        pppDial                                    .2.4.10.1
--          pppDialEnable                            .2.4.10.1.1
--          pppDialNumber                            .2.4.10.1.2
--          pppDialIdleTimeout                       .2.4.10.1.5
--          pppDialRetries                           .2.4.10.1.6
--          pppDialCDTimeout                         .2.4.10.1.7
--          pppDialLoginTimeout                      .2.4.10.1.8
--          pppDialMdmInit                           .2.4.10.1.9
--          pppDialSuggestIP                         .2.4.10.1.10
--          pppDialPlainLogin                        .2.4.10.1.11
--        pppHost                                    .2.4.10.2
--          pppHostEnable                            .2.4.10.2.1
--          pppHostIdleTimeout                       .2.4.10.2.2
--          pppHostLocalIP                           .2.4.10.2.3
--          pppHostRemoteIP                          .2.4.10.2.4
--      routing                                      .2.4.11
--        pppRoutingEnable                           .2.4.11.1
--        ethRoutingEnable                           .2.4.11.2
--        ethRoutingNATEnable                        .2.4.11.3
--        routingInterface                           .2.4.11.4
--        eth2WanRoutingEnable                       .2.4.11.5
--      netSecurity                                  .2.4.12
--        ipRestriction                              .2.4.12.1
--          ipRestrictionTable                       .2.4.12.1.1
--            ipRestrictionEntry                     .2.4.12.1.1.1
--              ipRestrictionIndex                   .2.4.12.1.1.1.1
--              ipRestrictionEnable                  .2.4.12.1.1.1.2
--              ipRestrictionMask                    .2.4.12.1.1.1.3
--      rts                                          .2.4.13
--        rtsFileTable                               .2.4.13.1
--          rtsFileEntry                             .2.4.13.1.1
--            rtsFileIndex                           .2.4.13.1.1.1
--            rtsFileMode                            .2.4.13.1.1.2
--            rtsFileShowAnswer                      .2.4.13.1.1.3
--            rtsFileReqXON                          .2.4.13.1.1.4
--            rtsFileTimeout                         .2.4.13.1.1.5
--            rtsFileEmptyClose                      .2.4.13.1.1.6
--            rtsFilePushHost                        .2.4.13.1.1.7
--            rtsFilePushPort                        .2.4.13.1.1.8
--            rtsFilePushRetryTimer                  .2.4.13.1.1.9
--        rtsAlarms                                  .2.4.13.2
--          rtsAlarmsMode                            .2.4.13.2.1
--          rtsAlarmsShowAnswer                      .2.4.13.2.2
--          rtsAlarmsReqXON                          .2.4.13.2.3
--          rtsAlarmsTimeout                         .2.4.13.2.4
--          rtsAlarmsEmptyClose                      .2.4.13.2.5
--          rtsAlarmsPushHost                        .2.4.13.2.6
--          rtsAlarmsPushPort                        .2.4.13.2.7
--          rtsAlarmsPushRetryTimer                  .2.4.13.2.8
--      trap                                         .2.4.14
--        trapInclude                                .2.4.14.1
--          trapIncludeDateTime                      .2.4.14.1.1
--          trapIncludeSiteName                      .2.4.14.1.2
--          trapIncludeSensorID                      .2.4.14.1.3
--          trapIncludeUDName                        .2.4.14.1.4
--          trapIncludeUDState                       .2.4.14.1.5
--          trapIncludeSourceAddress                 .2.4.14.1.6
--        trapAuthFailEnable                         .2.4.14.2
--      routeTest                                    .2.4.15
--        routeTestEnable                            .2.4.15.1
--        routeTestPeriod                            .2.4.15.2
--        routeTestAddressTable                      .2.4.15.3
--          routeTestAddressEntry                    .2.4.15.3.1
--            routeTestAddressIndex                  .2.4.15.3.1.1
--            routeTestAddress                       .2.4.15.3.1.2
--      wireless                                     .2.4.16
--        wirelessMode                               .2.4.16.1
--        wirelessAPN                                .2.4.16.2
--        wirelessIdleTimeout                        .2.4.16.3
--        wirelessDRE                                .2.4.16.9
--        wirelessPPPUsername                        .2.4.16.10
--        wirelessFirewall                           .2.4.16.11
--        wirelessKeepaliveThreshold                 .2.4.16.12
--        wirelessPPPDebug                           .2.4.16.13
--        wirelessConnectivity                       .2.4.16.20
--          wirelessConnEnable                       .2.4.16.20.1
--          wirelessConnCheckInterval                .2.4.16.20.2
--          wirelessConnFailThreshold                .2.4.16.20.3
--          wirelessConnIP1                          .2.4.16.20.10
--          wirelessConnIP2                          .2.4.16.20.11
--      email                                        .2.4.17
--        emailServer                                .2.4.17.1
--        emailDomain                                .2.4.17.2
--        emailAuthEnable                            .2.4.17.3
--      netAdvanced                                  .2.4.18
--        arpFilter                                  .2.4.18.1
--      web                                          .2.4.19
--        webEnable                                  .2.4.19.1
--        webPort                                    .2.4.19.2
--        webTimeout                                 .2.4.19.3
--        webXMLProxy                                .2.4.19.4
--          wxpEnable                                .2.4.19.4.1
--          wxpDeviceTable                           .2.4.19.4.2
--            wxpDeviceEntry                         .2.4.19.4.2.1
--              wxpDeviceIndex                       .2.4.19.4.2.1.1
--              wxpDeviceEnable                      .2.4.19.4.2.1.2
--              wxpDeviceIPAddress                   .2.4.19.4.2.1.3
--              wxpDevicePort                        .2.4.19.4.2.1.4
--              wxpDeviceRemoteFile                  .2.4.19.4.2.1.5
--              wxpDeviceLocalFile                   .2.4.19.4.2.1.6
--              wxpDeviceTimeout                     .2.4.19.4.2.1.7
--              wxpDeviceTimestamp                   .2.4.19.4.2.1.8
--      ethExpan                                     .2.4.20
--        ethExpanIp                                 .2.4.20.1
--        ethExpanMask                               .2.4.20.2
--        ethExpanCardTable                          .2.4.20.3
--          ethExpanCardEntry                        .2.4.20.3.1
--            ethExpanCardIndex                      .2.4.20.3.1.1
--            ethExpanCardMAC                        .2.4.20.3.1.2
--        ethExpanDHCP                               .2.4.20.6
--          ethExpanDHCPStartIp                      .2.4.20.6.1
--          ethExpanDHCPLeaseTime                    .2.4.20.6.2
--      ipv6                                         .2.4.21
--        ipv6DefaultRouter                          .2.4.21.1
--      cpe                                          .2.4.22
--        cpeTable                                   .2.4.22.1
--          cpeEntry                                 .2.4.22.1.1
--            cpeIndex                               .2.4.22.1.1.1
--            cpeHost                                .2.4.22.1.1.2
--            cpeName                                .2.4.22.1.1.3
--            cpeDescription                         .2.4.22.1.1.4
--            cpeKeepalive                           .2.4.22.1.1.5
--            cpeThreshold                           .2.4.22.1.1.6
--            cpeEventReminderInterval               .2.4.22.1.1.7
--            cpeKeepaliveTicks                      .2.4.22.1.1.20
--            cpePingSize                            .2.4.22.1.1.21
--            cpeInfoReset                           .2.4.22.1.1.30
--            cpeInfoNumReq                          .2.4.22.1.1.31
--            cpeInfoNumGoodResp                     .2.4.22.1.1.32
--            cpeInfoNumBadResp                      .2.4.22.1.1.33
--            cpeInfoNumLostResp                     .2.4.22.1.1.34
--            cpeInfoPercentLoss                     .2.4.22.1.1.35
--            cpeInfoPercentBad                      .2.4.22.1.1.36
--      dnp3                                         .2.4.23
--        dnp3General                                .2.4.23.1
--          dnp3Mode                                 .2.4.23.1.1
--          dnp3SelfAddressEnable                    .2.4.23.1.2
--          dnp3KeepaliveTimeout                     .2.4.23.1.3
--          dnp3MaxRXFragmentSize                    .2.4.23.1.4
--          dnp3MaxTXFragmentSize                    .2.4.23.1.5
--          dnp3UnsolResponseEnable                  .2.4.23.1.6
--          dnp3UnsolResponseTimeout                 .2.4.23.1.7
--          dnp3UnsolResponseRetries                 .2.4.23.1.8
--          dnp3LogFilter                            .2.4.23.1.9
--        dnp3Outstation                             .2.4.23.2
--          dnp3OutstationTCPPort                    .2.4.23.2.1
--          dnp3OutstationDNP3Address                .2.4.23.2.2
--          dnp3OutstationMasterIPAddress            .2.4.23.2.3
--          dnp3OutstationMasterDNP3Address          .2.4.23.2.4
--          dnp3OutstationUnsolResponseDNP3Address   .2.4.23.2.5
--        dnp3Master                                 .2.4.23.3
--        dnp3Error                                  .2.4.23.4
--          dnp3DuplicateFragmentCount               .2.4.23.4.1
--          dnp3CollidingFragmentCount               .2.4.23.4.2
--          dnp3UnsolResponseCfmFailCount            .2.4.23.4.3
--          dnp3SolCfmFailCount                      .2.4.23.4.4
--          dnp3ObjParseErrorCount                   .2.4.23.4.5
--          dnp3FrameParseErrorCount                 .2.4.23.4.6
--          dnp3DiscardedFrameCount                  .2.4.23.4.7
--          dnp3BadBlockCount                        .2.4.23.4.8
--          dnp3UnsolResponseRetryCount              .2.4.23.4.9
--          dnp3UnsupportedFrameCount                .2.4.23.4.10
--        dnp3Status                                 .2.4.23.5
--          dnp3OutstationCount                      .2.4.23.5.1
--          dnp3ConnPeer                             .2.4.23.5.2
--          dnp3StartTime                            .2.4.23.5.3
--          dnp3EventAwaitingSolCfmCount             .2.4.23.5.4
--          dnp3EventAwaitingUnsolCfmCount           .2.4.23.5.5
--          dnp3EventCount                           .2.4.23.5.6
--          dnp3EventClass1Count                     .2.4.23.5.7
--          dnp3EventClass2Count                     .2.4.23.5.8
--          dnp3EventClass3Count                     .2.4.23.5.9
--          dnp3RxFragmentTime                       .2.4.23.5.10
--          dnp3TxFragmentTime                       .2.4.23.5.11
--          dnp3TxCachedResponseCount                .2.4.23.5.12
--          dnp3TxUnsolResponseCount                 .2.4.23.5.13
--          dnp3TxSolResponseCount                   .2.4.23.5.14
--          dnp3TxFragmentReqCfmCount                .2.4.23.5.15
--          dnp3RxUnsolResponseCfmCount              .2.4.23.5.16
--          dnp3RxSolResponseCfmCount                .2.4.23.5.17
--          dnp3RxFunctionCount                      .2.4.23.5.18
--          dnp3RxReadFunctionCount                  .2.4.23.5.19
--          dnp3RxWriteFunctionCount                 .2.4.23.5.20
--          dnp3RxDirOpFunctionCount                 .2.4.23.5.21
--          dnp3RxEnableURCount                      .2.4.23.5.22
--          dnp3RxDisableURCount                     .2.4.23.5.23
--          dnp3RxSolObjectCount                     .2.4.23.5.40
--          dnp3TxSolObjectCount                     .2.4.23.5.41
--          dnp3RxFrameTime                          .2.4.23.5.42
--          dnp3TxFrameTime                          .2.4.23.5.43
--          dnp3TxFrameCount                         .2.4.23.5.44
--          dnp3RxAcceptedFrameCount                 .2.4.23.5.45
--          dnp3RxSupportedFrameCount                .2.4.23.5.46
--    modem                                          .2.5
--      modemFormat                                  .2.5.1
--      modemInitString                              .2.5.2
--      modemCallAttempts                            .2.5.4
--      modemCallDelay                               .2.5.5
--      modemCmdTimout                               .2.5.6
--      modemGoto                                    .2.5.7
--      modemClid                                    .2.5.8
--        modemCLIDEnable                            .2.5.8.1
--        modemCLIDNumberTable                       .2.5.8.2
--          modemCLIDNumberEntry                     .2.5.8.2.1
--            modemCLIDNumberIndex                   .2.5.8.2.1.1
--            modemCLIDNumber                        .2.5.8.2.1.2
--      modemTAPInitString                           .2.5.9
--      modemTAP8N1                                  .2.5.10
--    time                                           .2.8
--      clock                                        .2.8.1
--    console                                        .2.10
--      consoleDuplex                                .2.10.1
--      consoleTimeout                               .2.10.2
--      consoleConfirm                               .2.10.7
--    unitSecurity                                   .2.11
--      secCore                                      .2.11.1
--        scShowPasswordPrompt                       .2.11.1.1
--        scConsoleLoginRequired                     .2.11.1.2
--        scModemLoginRequired                       .2.11.1.3
--        scTelnetLoginRequired                      .2.11.1.4
--        scTelnetPTLoginRequired                    .2.11.1.5
--        scRTSLoginRequired                         .2.11.1.6
--        scAuthMode                                 .2.11.1.7
--        scRightsGroup                              .2.11.1.8
--      secUserTable                                 .2.11.2
--        secUserEntry                               .2.11.2.1
--          secUserIndex                             .2.11.2.1.1
--          secUserEnable                            .2.11.2.1.2
--          secUserConnectVia                        .2.11.2.1.5
--          secUserLoginTo                           .2.11.2.1.6
--          secUserAccessFile                        .2.11.2.1.7
--          secUserPTEscapeTo                        .2.11.2.1.9
--          secUserPPPType                           .2.11.2.1.10
--          secUserRights                            .2.11.2.1.11
--          secUserEventsReadAccess                  .2.11.2.1.13
--          secUserAuditReadAccess                   .2.11.2.1.14
--          secUserEventsWriteAccess                 .2.11.2.1.16
--          secUserAuditWriteAccess                  .2.11.2.1.17
--          secUserExpiration                        .2.11.2.1.18
--          secUserCallbackNumber1                   .2.11.2.1.19
--          secUserCallbackNumber2                   .2.11.2.1.20
--          secUserCallbackNumber3                   .2.11.2.1.21
--          secUserChallengeTelnetMode               .2.11.2.1.22
--          secUserChallengeModemMode                .2.11.2.1.23
--          secUserChallengeConsoleMode              .2.11.2.1.24
--          secUserChallengeTelnetSendTo             .2.11.2.1.25
--          secUserChallengeModemSendTo              .2.11.2.1.26
--          secUserChallengeExpiration               .2.11.2.1.27
--      secFactory                                   .2.11.3
--        sfEnable                                   .2.11.3.1
--        sfSecret                                   .2.11.3.2
--      secSSH                                       .2.11.4
--      secVPN                                       .2.11.5
--    event                                          .2.12
--      evCore                                       .2.12.1
--        evClassNameTable                           .2.12.1.1
--          evClassNameEntry                         .2.12.1.1.1
--            evClassNameIndex                       .2.12.1.1.1.1
--            evClassName                            .2.12.1.1.1.2
--        evReminderInterval                         .2.12.1.2
--        evLog                                      .2.12.1.3
--          evLogEnable                              .2.12.1.3.1
--          evLogStoreAlarm                          .2.12.1.3.2
--          evLogMaxSize                             .2.12.1.3.3
--          evLogStoreSensor                         .2.12.1.3.4
--          evLogTimeStampAlarms                     .2.12.1.3.5
--          evLogPrependName                         .2.12.1.3.6
--        evMgmt                                     .2.12.1.4
--          evMgmtReprocess                          .2.12.1.4.3
--      evData                                       .2.12.2
--        evdCore                                    .2.12.2.1
--          evdExitOnTrue                            .2.12.2.1.1
--          evdFilterAction                          .2.12.2.1.2
--          evdWildCardChar                          .2.12.2.1.3
--        evdTable                                   .2.12.2.2
--          evdEntry                                 .2.12.2.2.1
--            evdIndex                               .2.12.2.2.1.1
--            evdEnable                              .2.12.2.2.1.2
--            evdName                                .2.12.2.2.1.3
--            evdEquation                            .2.12.2.2.1.4
--            evdThreshold                           .2.12.2.2.1.5
--            evdAutoclear                           .2.12.2.2.1.6
--            evdClearInterval                       .2.12.2.2.1.7
--            evdClearTime                           .2.12.2.2.1.8
--            evdActions                             .2.12.2.2.1.9
--            evdClass                               .2.12.2.2.1.10
--            evdTrapNum                             .2.12.2.2.1.11
--            evdMode                                .2.12.2.2.1.12
--        evdFieldTable                              .2.12.2.3
--          evdFieldEntry                            .2.12.2.3.1
--            evdFieldIndex                          .2.12.2.3.1.1
--            evdFieldStart                          .2.12.2.3.1.2
--            evdFieldLength                         .2.12.2.3.1.3
--            evdFieldName                           .2.12.2.3.1.4
--            evdFieldLine                           .2.12.2.3.1.5
--            evdFieldType                           .2.12.2.3.1.6
--        evdMacroTable                              .2.12.2.4
--          evdMacroEntry                            .2.12.2.4.1
--            evdMacroIndex                          .2.12.2.4.1.1
--            evdMacroName                           .2.12.2.4.1.2
--            evdMacroEquation                       .2.12.2.4.1.3
--      evNoData1                                    .2.12.3
--        evNoData1Enable                            .2.12.3.1
--        evNoData1Actions                           .2.12.3.2
--        evNoData1Message                           .2.12.3.3
--        evNoData1TrapNum                           .2.12.3.4
--        evNoData1Class                             .2.12.3.5
--        evNoData1Sched1Begin                       .2.12.3.6
--        evNoData1Sched1End                         .2.12.3.7
--        evNoData1Sched1Duration                    .2.12.3.8
--        evNoData1Sched2Begin                       .2.12.3.9
--        evNoData1Sched2End                         .2.12.3.10
--        evNoData1Sched2Duration                    .2.12.3.11
--        evNoData1PortEnableTable                   .2.12.3.12
--          evNoData1PortEnableEntry                 .2.12.3.12.1
--            evNoData1PortEnableIndex               .2.12.3.12.1.1
--            evNoData1PortEnable                    .2.12.3.12.1.2
--        evNoData1Exclusions                        .2.12.3.13
--        evNoData1Days                              .2.12.3.14
--      evNoData2                                    .2.12.4
--        evNoData2Enable                            .2.12.4.1
--        evNoData2Actions                           .2.12.4.2
--        evNoData2Message                           .2.12.4.3
--        evNoData2TrapNum                           .2.12.4.4
--        evNoData2Class                             .2.12.4.5
--        evNoData2Sched1Begin                       .2.12.4.6
--        evNoData2Sched1End                         .2.12.4.7
--        evNoData2Sched1Duration                    .2.12.4.8
--        evNoData2Sched2Begin                       .2.12.4.9
--        evNoData2Sched2End                         .2.12.4.10
--        evNoData2Sched2Duration                    .2.12.4.11
--        evNoData2PortEnableTable                   .2.12.4.12
--          evNoData2PortEnableEntry                 .2.12.4.12.1
--            evNoData2PortEnableIndex               .2.12.4.12.1.1
--            evNoData2PortEnable                    .2.12.4.12.1.2
--        evNoData2Exclusions                        .2.12.4.13
--        evNoData2Days                              .2.12.4.14
--      evSched1                                     .2.12.5
--        evSched1Enable                             .2.12.5.1
--        evSched1Actions                            .2.12.5.2
--        evSched1Message                            .2.12.5.3
--        evSched1TrapNum                            .2.12.5.4
--        evSched1Class                              .2.12.5.5
--        evSched1Sunday                             .2.12.5.6
--        evSched1Monday                             .2.12.5.7
--        evSched1Tuesday                            .2.12.5.8
--        evSched1Wednesday                          .2.12.5.9
--        evSched1Thursday                           .2.12.5.10
--        evSched1Friday                             .2.12.5.11
--        evSched1Saturday                           .2.12.5.12
--        evSched1Exclusions                         .2.12.5.13
--      evSched2                                     .2.12.6
--        evSched2Enable                             .2.12.6.1
--        evSched2Actions                            .2.12.6.2
--        evSched2Message                            .2.12.6.3
--        evSched2TrapNum                            .2.12.6.4
--        evSched2Class                              .2.12.6.5
--        evSched2Sunday                             .2.12.6.6
--        evSched2Monday                             .2.12.6.7
--        evSched2Tuesday                            .2.12.6.8
--        evSched2Wednesday                          .2.12.6.9
--        evSched2Thursday                           .2.12.6.10
--        evSched2Friday                             .2.12.6.11
--        evSched2Saturday                           .2.12.6.12
--        evSched2Exclusions                         .2.12.6.13
--      evShskLowTable                               .2.12.7
--        evShskLowEntry                             .2.12.7.1
--          evShskLowIndex                           .2.12.7.1.1
--          evShskLowEnable                          .2.12.7.1.2
--          evShskLowActions                         .2.12.7.1.3
--          evShskLowMessage                         .2.12.7.1.4
--          evShskLowClass                           .2.12.7.1.5
--          evShskLowTrapNum                         .2.12.7.1.6
--      evShskHighTable                              .2.12.8
--        evShskHighEntry                            .2.12.8.1
--          evShskHighIndex                          .2.12.8.1.1
--          evShskHighEnable                         .2.12.8.1.2
--          evShskHighActions                        .2.12.8.1.3
--          evShskHighMessage                        .2.12.8.1.4
--          evShskHighClass                          .2.12.8.1.5
--          evShskHighTrapNum                        .2.12.8.1.6
--      evNoSensor                                   .2.12.9
--        evNoSensorTimeout                          .2.12.9.1
--        evNoSensorActions                          .2.12.9.2
--        evNoSensorTrapNum                          .2.12.9.3
--        evNoSensorClass                            .2.12.9.4
--      fuelSensor                                   .2.12.11
--        fuelSensorGeneralTable                     .2.12.11.1
--          fsGenEntry                               .2.12.11.1.1
--            fsGenIndex                             .2.12.11.1.1.1
--            fsGenName                              .2.12.11.1.1.2
--            fsGenSensorType                        .2.12.11.1.1.3
--            fsGenDistanceUnit                      .2.12.11.1.1.4
--            fsGenRawValueTop                       .2.12.11.1.1.5
--            fsGenTopOffset                         .2.12.11.1.1.6
--            fsGenRawValueBottom                    .2.12.11.1.1.7
--            fsGenBottomOffset                      .2.12.11.1.1.8
--            fsGenInputES                           .2.12.11.1.1.9
--            fsGenInputPoint                        .2.12.11.1.1.10
--            fsGenFilterAveraging                   .2.12.11.1.1.11
--            fsGenSysrepEnable                      .2.12.11.1.1.12
--            fsGenSysrepThreshold                   .2.12.11.1.1.13
--            fsGenSysrepLimit                       .2.12.11.1.1.14
--            fsGenSysrepPackage                     .2.12.11.1.1.15
--            fsGenGroup                             .2.12.11.1.1.16
--            fsGenEnable                            .2.12.11.1.1.17
--            fsGenFuelType                          .2.12.11.1.1.18
--        fuelSensorTankTable                        .2.12.11.2
--          fsTankEntry                              .2.12.11.2.1
--            fsTankIndex                            .2.12.11.2.1.1
--            fsTankHeight                           .2.12.11.2.1.2
--            fsTankDimA                             .2.12.11.2.1.3
--            fsTankDimB                             .2.12.11.2.1.4
--            fsTankVolume                           .2.12.11.2.1.5
--            fsTankVolumeUnit                       .2.12.11.2.1.6
--            fsTankShape                            .2.12.11.2.1.7
--        fuelSensorCustomTankTable                  .2.12.11.3
--          fsCustomTankEntry                        .2.12.11.3.1
--            fsCustomTankIndexFS                    .2.12.11.3.1.1
--            fsCustomTankIndexDatum                 .2.12.11.3.1.2
--            fsCustomTankHeight                     .2.12.11.3.1.3
--            fsCustomTankVolume                     .2.12.11.3.1.4
--        fuelSensorVolumeTable                      .2.12.11.4
--          fsVolumeEntry                            .2.12.11.4.1
--            fsVolumeIndex                          .2.12.11.4.1.1
--            fsVolumeEnable                         .2.12.11.4.1.2
--            fsVolumeDeadband                       .2.12.11.4.1.3
--            fsVolumeVHighValue                     .2.12.11.4.1.4
--            fsVolumeVHighActions                   .2.12.11.4.1.5
--            fsVolumeVHighTrapNum                   .2.12.11.4.1.6
--            fsVolumeVHighClass                     .2.12.11.4.1.7
--            fsVolumeHighValue                      .2.12.11.4.1.8
--            fsVolumeHighActions                    .2.12.11.4.1.9
--            fsVolumeHighTrapNum                    .2.12.11.4.1.10
--            fsVolumeHighClass                      .2.12.11.4.1.11
--            fsVolumeNormalActions                  .2.12.11.4.1.12
--            fsVolumeNormalTrapNum                  .2.12.11.4.1.13
--            fsVolumeNormalClass                    .2.12.11.4.1.14
--            fsVolumeLowValue                       .2.12.11.4.1.15
--            fsVolumeLowActions                     .2.12.11.4.1.16
--            fsVolumeLowTrapNum                     .2.12.11.4.1.17
--            fsVolumeLowClass                       .2.12.11.4.1.18
--            fsVolumeVLowValue                      .2.12.11.4.1.19
--            fsVolumeVLowActions                    .2.12.11.4.1.20
--            fsVolumeVLowTrapNum                    .2.12.11.4.1.21
--            fsVolumeVLowClass                      .2.12.11.4.1.22
--        fuelSensorDisconnectTable                  .2.12.11.5
--          fsDiscEntry                              .2.12.11.5.1
--            fsDiscIndex                            .2.12.11.5.1.1
--            fsDiscEnable                           .2.12.11.5.1.2
--            fsDiscHighValue                        .2.12.11.5.1.3
--            fsDiscLowValue                         .2.12.11.5.1.4
--            fsDiscActions                          .2.12.11.5.1.5
--            fsDiscTrapNum                          .2.12.11.5.1.6
--            fsDiscClass                            .2.12.11.5.1.7
--            fsDiscNormalActions                    .2.12.11.5.1.8
--            fsDiscNormalTrapNum                    .2.12.11.5.1.9
--            fsDiscNormalClass                      .2.12.11.5.1.10
--        fuelSensorSuddenChangeTable                .2.12.11.6
--          fsSuddenChangeEntry                      .2.12.11.6.1
--            fsSuddenChangeIndex                    .2.12.11.6.1.1
--            fsSuddenChangeEnable                   .2.12.11.6.1.2
--            fsSuddenChangeTime                     .2.12.11.6.1.3
--            fsSuddenChangeAmplitude                .2.12.11.6.1.4
--            fsSuddenChangeActions                  .2.12.11.6.1.5
--            fsSuddenChangeTrapNum                  .2.12.11.6.1.6
--            fsSuddenChangeClass                    .2.12.11.6.1.7
--        fuelSensorSlowChangeTable                  .2.12.11.7
--          fuelSensorSlowChangeEntry                .2.12.11.7.1
--            fsSlowChangeIndex                      .2.12.11.7.1.1
--            fsSlowChangeEnable                     .2.12.11.7.1.2
--            fsSlowChangeTime                       .2.12.11.7.1.3
--            fsSlowChangeAmplitude                  .2.12.11.7.1.4
--            fsSlowChangeActions                    .2.12.11.7.1.5
--            fsSlowChangeTrapNum                    .2.12.11.7.1.6
--            fsSlowChangeClass                      .2.12.11.7.1.7
--      acPowerMonitor                               .2.12.12
--        acpmGeneralTable                           .2.12.12.1
--          acpmGenEntry                             .2.12.12.1.1
--            acpmGenIndex                           .2.12.12.1.1.1
--            acpmGenDevice                          .2.12.12.1.1.2
--            acpmGenName                            .2.12.12.1.1.3
--            acpmGenAddress                         .2.12.12.1.1.4
--            acpmGenPtRatio                         .2.12.12.1.1.5
--            acpmGenCtRatio                         .2.12.12.1.1.6
--            acpmGenPowerType                       .2.12.12.1.1.7
--            acpmGenSysrepPackage                   .2.12.12.1.1.8
--            acpmGenGroup                           .2.12.12.1.1.9
--            acpmGenEnable                          .2.12.12.1.1.10
--        acpmAvgVoltageTable                        .2.12.12.2
--          acpmAvgVoltageEntry                      .2.12.12.2.1
--            acpmAvgVoltageIndex                    .2.12.12.2.1.1
--            acpmAvgVoltageEnable                   .2.12.12.2.1.2
--            acpmAvgVoltageDeadband                 .2.12.12.2.1.3
--            acpmAvgVoltageVHighValue               .2.12.12.2.1.4
--            acpmAvgVoltageVHighActions             .2.12.12.2.1.5
--            acpmAvgVoltageVHighTrapNum             .2.12.12.2.1.6
--            acpmAvgVoltageVHighClass               .2.12.12.2.1.7
--            acpmAvgVoltageHighValue                .2.12.12.2.1.8
--            acpmAvgVoltageHighActions              .2.12.12.2.1.9
--            acpmAvgVoltageHighTrapNum              .2.12.12.2.1.10
--            acpmAvgVoltageHighClass                .2.12.12.2.1.11
--            acpmAvgVoltageNormalActions            .2.12.12.2.1.12
--            acpmAvgVoltageNormalTrapNum            .2.12.12.2.1.13
--            acpmAvgVoltageNormalClass              .2.12.12.2.1.14
--            acpmAvgVoltageLowValue                 .2.12.12.2.1.15
--            acpmAvgVoltageLowActions               .2.12.12.2.1.16
--            acpmAvgVoltageLowTrapNum               .2.12.12.2.1.17
--            acpmAvgVoltageLowClass                 .2.12.12.2.1.18
--            acpmAvgVoltageVLowValue                .2.12.12.2.1.19
--            acpmAvgVoltageVLowActions              .2.12.12.2.1.20
--            acpmAvgVoltageVLowTrapNum              .2.12.12.2.1.21
--            acpmAvgVoltageVLowClass                .2.12.12.2.1.22
--            acpmAvgVoltageSysrepEnable             .2.12.12.2.1.23
--            acpmAvgVoltageSysrepThreshold          .2.12.12.2.1.24
--            acpmAvgVoltageSysrepLimit              .2.12.12.2.1.25
--        acpmAvgCurrentTable                        .2.12.12.3
--          acpmAvgCurrentEntry                      .2.12.12.3.1
--            acpmAvgCurrentIndex                    .2.12.12.3.1.1
--            acpmAvgCurrentEnable                   .2.12.12.3.1.2
--            acpmAvgCurrentDeadband                 .2.12.12.3.1.3
--            acpmAvgCurrentVHighValue               .2.12.12.3.1.4
--            acpmAvgCurrentVHighActions             .2.12.12.3.1.5
--            acpmAvgCurrentVHighTrapNum             .2.12.12.3.1.6
--            acpmAvgCurrentVHighClass               .2.12.12.3.1.7
--            acpmAvgCurrentHighValue                .2.12.12.3.1.8
--            acpmAvgCurrentHighActions              .2.12.12.3.1.9
--            acpmAvgCurrentHighTrapNum              .2.12.12.3.1.10
--            acpmAvgCurrentHighClass                .2.12.12.3.1.11
--            acpmAvgCurrentNormalActions            .2.12.12.3.1.12
--            acpmAvgCurrentNormalTrapNum            .2.12.12.3.1.13
--            acpmAvgCurrentNormalClass              .2.12.12.3.1.14
--            acpmAvgCurrentLowValue                 .2.12.12.3.1.15
--            acpmAvgCurrentLowActions               .2.12.12.3.1.16
--            acpmAvgCurrentLowTrapNum               .2.12.12.3.1.17
--            acpmAvgCurrentLowClass                 .2.12.12.3.1.18
--            acpmAvgCurrentVLowValue                .2.12.12.3.1.19
--            acpmAvgCurrentVLowActions              .2.12.12.3.1.20
--            acpmAvgCurrentVLowTrapNum              .2.12.12.3.1.21
--            acpmAvgCurrentVLowClass                .2.12.12.3.1.22
--            acpmAvgCurrentSysrepEnable             .2.12.12.3.1.23
--            acpmAvgCurrentSysrepThreshold          .2.12.12.3.1.24
--            acpmAvgCurrentSysrepLimit              .2.12.12.3.1.25
--        acpmFreqTable                              .2.12.12.4
--          acpmFreqEntry                            .2.12.12.4.1
--            acpmFreqIndex                          .2.12.12.4.1.1
--            acpmFreqEnable                         .2.12.12.4.1.2
--            acpmFreqDeadband                       .2.12.12.4.1.3
--            acpmFreqVHighValue                     .2.12.12.4.1.4
--            acpmFreqVHighActions                   .2.12.12.4.1.5
--            acpmFreqVHighTrapNum                   .2.12.12.4.1.6
--            acpmFreqVHighClass                     .2.12.12.4.1.7
--            acpmFreqHighValue                      .2.12.12.4.1.8
--            acpmFreqHighActions                    .2.12.12.4.1.9
--            acpmFreqHighTrapNum                    .2.12.12.4.1.10
--            acpmFreqHighClass                      .2.12.12.4.1.11
--            acpmFreqNormalActions                  .2.12.12.4.1.12
--            acpmFreqNormalTrapNum                  .2.12.12.4.1.13
--            acpmFreqNormalClass                    .2.12.12.4.1.14
--            acpmFreqLowValue                       .2.12.12.4.1.15
--            acpmFreqLowActions                     .2.12.12.4.1.16
--            acpmFreqLowTrapNum                     .2.12.12.4.1.17
--            acpmFreqLowClass                       .2.12.12.4.1.18
--            acpmFreqVLowValue                      .2.12.12.4.1.19
--            acpmFreqVLowActions                    .2.12.12.4.1.20
--            acpmFreqVLowTrapNum                    .2.12.12.4.1.21
--            acpmFreqVLowClass                      .2.12.12.4.1.22
--            acpmFreqSysrepEnable                   .2.12.12.4.1.23
--            acpmFreqSysrepThreshold                .2.12.12.4.1.24
--            acpmFreqSysrepLimit                    .2.12.12.4.1.25
--        acpmTotalRealPowerTable                    .2.12.12.5
--          acpmTRPEntry                             .2.12.12.5.1
--            acpmTRPIndex                           .2.12.12.5.1.1
--            acpmTRPEnable                          .2.12.12.5.1.2
--            acpmTRPDeadband                        .2.12.12.5.1.3
--            acpmTRPVHighValue                      .2.12.12.5.1.4
--            acpmTRPVHighActions                    .2.12.12.5.1.5
--            acpmTRPVHighTrapNum                    .2.12.12.5.1.6
--            acpmTRPVHighClass                      .2.12.12.5.1.7
--            acpmTRPHighValue                       .2.12.12.5.1.8
--            acpmTRPHighActions                     .2.12.12.5.1.9
--            acpmTRPHighTrapNum                     .2.12.12.5.1.10
--            acpmTRPHighClass                       .2.12.12.5.1.11
--            acpmTRPNormalActions                   .2.12.12.5.1.12
--            acpmTRPNormalTrapNum                   .2.12.12.5.1.13
--            acpmTRPNormalClass                     .2.12.12.5.1.14
--            acpmTRPLowValue                        .2.12.12.5.1.15
--            acpmTRPLowActions                      .2.12.12.5.1.16
--            acpmTRPLowTrapNum                      .2.12.12.5.1.17
--            acpmTRPLowClass                        .2.12.12.5.1.18
--            acpmTRPVLowValue                       .2.12.12.5.1.19
--            acpmTRPVLowActions                     .2.12.12.5.1.20
--            acpmTRPVLowTrapNum                     .2.12.12.5.1.21
--            acpmTRPVLowClass                       .2.12.12.5.1.22
--            acpmTRPSysrepEnable                    .2.12.12.5.1.23
--            acpmTRPSysrepThreshold                 .2.12.12.5.1.24
--            acpmTRPSysrepLimit                     .2.12.12.5.1.25
--        acpmDisconnectTable                        .2.12.12.6
--          acpmDisconnectEntry                      .2.12.12.6.1
--            acpmDisconnectIndex                    .2.12.12.6.1.1
--            acpmDisconnectEnable                   .2.12.12.6.1.2
--            acpmDisconnectActions                  .2.12.12.6.1.3
--            acpmDisconnectTrapNum                  .2.12.12.6.1.4
--            acpmDisconnectClass                    .2.12.12.6.1.5
--            acpmDisconnectNormalActions            .2.12.12.6.1.6
--            acpmDisconnectNormalTrapNum            .2.12.12.6.1.7
--            acpmDisconnectNormalClass              .2.12.12.6.1.8
--        acpmTotalPowerFactorTable                  .2.12.12.7
--          acpmTPFEntry                             .2.12.12.7.1
--            acpmTPFIndex                           .2.12.12.7.1.1
--            acpmTPFEnable                          .2.12.12.7.1.2
--            acpmTPFDeadband                        .2.12.12.7.1.3
--            acpmTPFNormalActions                   .2.12.12.7.1.4
--            acpmTPFNormalTrapNum                   .2.12.12.7.1.5
--            acpmTPFNormalClass                     .2.12.12.7.1.6
--            acpmTPFLowValue                        .2.12.12.7.1.7
--            acpmTPFLowActions                      .2.12.12.7.1.8
--            acpmTPFLowTrapNum                      .2.12.12.7.1.9
--            acpmTPFLowClass                        .2.12.12.7.1.10
--            acpmTPFVLowValue                       .2.12.12.7.1.11
--            acpmTPFVLowActions                     .2.12.12.7.1.12
--            acpmTPFVLowTrapNum                     .2.12.12.7.1.13
--            acpmTPFVLowClass                       .2.12.12.7.1.14
--            acpmTPFSysrepEnable                    .2.12.12.7.1.15
--            acpmTPFSysrepThreshold                 .2.12.12.7.1.16
--            acpmTPFSysrepLimit                     .2.12.12.7.1.17
--      evReset                                      .2.12.16
--        evResetEnable                              .2.12.16.1
--        evResetDelay                               .2.12.16.2
--        evResetActions                             .2.12.16.3
--        evResetMessage                             .2.12.16.4
--        evResetTrapnum                             .2.12.16.5
--        evResetClass                               .2.12.16.6
--      evGlobal                                     .2.12.18
--        evGlobalActions                            .2.12.18.1
--        evGlobalTrapnum                            .2.12.18.2
--      evHVAC                                       .2.12.19
--        evHVACGeneral                              .2.12.19.1
--        evHVACBard                                 .2.12.19.2
--          evHVACBardLocal                          .2.12.19.2.1
--            evHVACBardIPAddress                    .2.12.19.2.1.1
--            evHVACBardPort                         .2.12.19.2.1.2
--            evHVACBardTimeout                      .2.12.19.2.1.3
--            evHVACBardXMLStatus                    .2.12.19.2.1.4
--            evHVACBardXMLSettings                  .2.12.19.2.1.5
--            evHVACBardWebSettingsHTML              .2.12.19.2.1.6
--            evHVACBardAlarm                        .2.12.19.2.1.7
--              evHVACBardAlarmEnable                .2.12.19.2.1.7.1
--              evHVACBardAlarmActions               .2.12.19.2.1.7.2
--              evHVACBardAlarmTrapnum               .2.12.19.2.1.7.3
--              evHVACBardAlarmClass                 .2.12.19.2.1.7.4
--              evHVACBardAlarmNormalActions         .2.12.19.2.1.7.5
--              evHVACBardAlarmNormalTrapnum         .2.12.19.2.1.7.6
--              evHVACBardAlarmNormalClass           .2.12.19.2.1.7.7
--            evHVACBardReset                        .2.12.19.2.1.8
--            evHVACBardDefault                      .2.12.19.2.1.9 
--          evHVACBardSynchronized                   .2.12.19.2.2
--            evHVACBardTempScale                    .2.12.19.2.2.1
--            evHVACBardCoolThreshold                .2.12.19.2.2.2
--            evHVACBardCoolThresholdState           .2.12.19.2.2.3
--            evHVACBardHeatThreshold                .2.12.19.2.2.4
--            evHVACBardHeatDiff                     .2.12.19.2.2.5
--            evHVACBardHeatDiffState                .2.12.19.2.2.6
--            evHVACBardBlower                       .2.12.19.2.2.7
--            evHVACBardBlowerState                  .2.12.19.2.2.8
--            evHVACBardAlternate                    .2.12.19.2.2.9
--            evHVACBardAlternateState               .2.12.19.2.2.10
--            evHVACBardChangeover                   .2.12.19.2.2.11
--            evHVACBardChangeoverState              .2.12.19.2.2.12
--            evHVACBardBlowDiff                     .2.12.19.2.2.13
--            evHVACBardBlowDiffState                .2.12.19.2.2.14
--            evHVACBardOffDelay                     .2.12.19.2.2.15
--            evHVACBardOffDelayState                .2.12.19.2.2.16
--            evHVACBardRunMin                       .2.12.19.2.2.17
--            evHVACBardRunMinState                  .2.12.19.2.2.18
--            evHVACBardDiff                         .2.12.19.2.2.19
--              evHVACBardStage1Diff                 .2.12.19.2.2.19.1
--              evHVACBardStage1DiffState            .2.12.19.2.2.19.2
--              evHVACBardStage2Diff                 .2.12.19.2.2.19.3
--              evHVACBardStage2DiffState            .2.12.19.2.2.19.4
--              evHVACBardStage3Diff                 .2.12.19.2.2.19.5
--              evHVACBardStage3DiffState            .2.12.19.2.2.19.6
--            evHVACBardCoolDisableDb                .2.12.19.2.2.20
--            evHVACBardCoolDisableDbState           .2.12.19.2.2.21
--            evHVACBardCoolEnableDb                 .2.12.19.2.2.22
--            evHVACBardCoolEnableDbState            .2.12.19.2.2.23
--            evHVACBardHeatDb                       .2.12.19.2.2.24
--            evHVACBardHeatDbState                  .2.12.19.2.2.25
--            evHVACBardHeatPump                     .2.12.19.2.2.26
--            evHVACBardHeatPumpState                .2.12.19.2.2.27
--            evHVACBardCompressors                  .2.12.19.2.2.28
--            evHVACBardCompressorsState             .2.12.19.2.2.29
--            evHVACBardEconomizer                   .2.12.19.2.2.30
--            evHVACBardEconomizerState              .2.12.19.2.2.31
--            evHVACBardTemp                         .2.12.19.2.2.32
--              evHVACBardTempLowValue               .2.12.19.2.2.32.1
--              evHVACBardTempLowValueState          .2.12.19.2.2.32.2
--              evHVACBardTempHighValue              .2.12.19.2.2.32.3
--              evHVACBardTempHighValueState         .2.12.19.2.2.32.4
--              evHVACBardTempVHighValue             .2.12.19.2.2.32.5
--              evHVACBardTempVHighValueState        .2.12.19.2.2.32.6
--            evHVACBardOverride                     .2.12.19.2.2.33
--            evHVACBardOverrideState                .2.12.19.2.2.34
--            evHVACBardLock                         .2.12.19.2.2.35
--            evHVACBardLockState                    .2.12.19.2.2.36
--            evHVACBardLeadUnit                     .2.12.19.2.2.37
--            evHVACBardLeadUnitState                .2.12.19.2.2.38
--            evHVACBardComfort                      .2.12.19.2.2.39
--            evHVACBardComfortState                 .2.12.19.2.2.40
--        evHVACAsentria                             .2.12.19.3
--          evHVACAsentriaSensorListTable            .2.12.19.3.1
--            evHVACAsentriaSensorListEntry          .2.12.19.3.1.1
--              evHVACAsentriaSensorListIndex        .2.12.19.3.1.1.1
--              evHVACAsentriaSensorListES           .2.12.19.3.1.1.2
--              evHVACAsentriaSensorListPT           .2.12.19.3.1.1.3
--              evHVACAsentriaSensorListType         .2.12.19.3.1.1.4
--              evHVACAsentriaSensorListLoc          .2.12.19.3.1.1.5
--          evHVACAsentriaOverride                   .2.12.19.3.2
--          evHVACAsentriaSchedule                   .2.12.19.3.3
--          evHVACAsentriaPrimary                    .2.12.19.3.4
--          evHVACAsentriaMethod                     .2.12.19.3.5
--          evHVACAsentriaAlarm                      .2.12.19.3.6
--            evHVACAsentriaAlarmLagNormEnable       .2.12.19.3.6.1
--            evHVACAsentriaAlarmLagNormActions      .2.12.19.3.6.2
--            evHVACAsentriaAlarmLagNormTrapNum      .2.12.19.3.6.3
--            evHVACAsentriaAlarmLagNormClass        .2.12.19.3.6.4
--            evHVACAsentriaAlarmLagVentEnable       .2.12.19.3.6.5
--            evHVACAsentriaAlarmLagVentActions      .2.12.19.3.6.6
--            evHVACAsentriaAlarmLagVentTrapNum      .2.12.19.3.6.7
--            evHVACAsentriaAlarmLagVentClass        .2.12.19.3.6.8
--            evHVACAsentriaAlarmLagCoolEnable       .2.12.19.3.6.9
--            evHVACAsentriaAlarmLagCoolActions      .2.12.19.3.6.10
--            evHVACAsentriaAlarmLagCoolTrapNum      .2.12.19.3.6.11
--            evHVACAsentriaAlarmLagCoolClass        .2.12.19.3.6.12
--            evHVACAsentriaAlarmLagHeatEnable       .2.12.19.3.6.13
--            evHVACAsentriaAlarmLagHeatActions      .2.12.19.3.6.14
--            evHVACAsentriaAlarmLagHeatTrapNum      .2.12.19.3.6.15
--            evHVACAsentriaAlarmLagHeatClass        .2.12.19.3.6.16
--          evHVACAsentriaFire                       .2.12.19.3.7
--            evHVACAsentriaFireES                   .2.12.19.3.7.1
--            evHVACAsentriaFirePT                   .2.12.19.3.7.2
--            evHVACAsentriaFireActions              .2.12.19.3.7.3
--            evHVACAsentriaFireTrapNum              .2.12.19.3.7.4
--            evHVACAsentriaFireClass                .2.12.19.3.7.5
--            evHVACAsentriaFireNormActions          .2.12.19.3.7.6
--            evHVACAsentriaFireNormTrapNum          .2.12.19.3.7.7
--            evHVACAsentriaFireNormClass            .2.12.19.3.7.8
--          evHVACAsentriaUnitTable                  .2.12.19.3.8
--            evHVACAsentriaUnitEntry                .2.12.19.3.8.1
--              evHVACAsentriaUnitIndex              .2.12.19.3.8.1.1
--              evHVACAsentriaUnitEnable             .2.12.19.3.8.1.2
--              evHVACAsentriaUnitFanRelayES         .2.12.19.3.8.1.3
--              evHVACAsentriaUnitFanRelayPT         .2.12.19.3.8.1.4
--              evHVACAsentriaUnitVentRelayES        .2.12.19.3.8.1.5
--              evHVACAsentriaUnitVentRelayPT        .2.12.19.3.8.1.6
--              evHVACAsentriaUnitTimereset          .2.12.19.3.8.1.7
--              evHVACAsentriaSeqTimereset           .2.12.19.3.8.1.8
--              evHVACAsentriaUnitStage1CoolES       .2.12.19.3.8.1.20
--              evHVACAsentriaUnitStage1CoolPT       .2.12.19.3.8.1.21
--              evHVACAsentriaUnitStage1HeatES       .2.12.19.3.8.1.22
--              evHVACAsentriaUnitStage1HeatPT       .2.12.19.3.8.1.23
--              evHVACAsentriaUnitStage2CoolES       .2.12.19.3.8.1.30
--              evHVACAsentriaUnitStage2CoolPT       .2.12.19.3.8.1.31
--              evHVACAsentriaUnitStage2HeatES       .2.12.19.3.8.1.32
--              evHVACAsentriaUnitStage2HeatPT       .2.12.19.3.8.1.33
--          evHVACAsentriaTemp                       .2.12.19.3.9
--            evHVACAsentriaTempScale                .2.12.19.3.9.1
--            evHVACAsentriaTempCoolThresh           .2.12.19.3.9.2
--            evHVACAsentriaTempHeatThresh           .2.12.19.3.9.3
--            evHVACAsentriaTempEnable               .2.12.19.3.9.4
--            evHVACAsentriaTempEventDeadband        .2.12.19.3.9.5
--            evHVACAsentriaTempVLowValue            .2.12.19.3.9.6
--            evHVACAsentriaTempVLowActions          .2.12.19.3.9.7
--            evHVACAsentriaTempVLowTrapNum          .2.12.19.3.9.8
--            evHVACAsentriaTempVLowClass            .2.12.19.3.9.9
--            evHVACAsentriaTempLowValue             .2.12.19.3.9.10
--            evHVACAsentriaTempLowActions           .2.12.19.3.9.11
--            evHVACAsentriaTempLowTrapNum           .2.12.19.3.9.12
--            evHVACAsentriaTempLowClass             .2.12.19.3.9.13
--            evHVACAsentriaTempNormalActions        .2.12.19.3.9.14
--            evHVACAsentriaTempNormalTrapNum        .2.12.19.3.9.15
--            evHVACAsentriaTempNormalClass          .2.12.19.3.9.16
--            evHVACAsentriaTempHighValue            .2.12.19.3.9.17
--            evHVACAsentriaTempHighActions          .2.12.19.3.9.18
--            evHVACAsentriaTempHighTrapNum          .2.12.19.3.9.19
--            evHVACAsentriaTempHighClass            .2.12.19.3.9.20
--            evHVACAsentriaTempVHighValue           .2.12.19.3.9.21
--            evHVACAsentriaTempVHighActions         .2.12.19.3.9.22
--            evHVACAsentriaTempVHighTrapNum         .2.12.19.3.9.23
--            evHVACAsentriaTempVHighClass           .2.12.19.3.9.24
--            evHVACAsentriaTempDeadband             .2.12.19.3.9.25
--            evHVACAsentriaTempDifference           .2.12.19.3.9.26
--          evHVACAsentriaHumid                      .2.12.19.3.10
--            evHVACAsentriaHumidInThresh            .2.12.19.3.10.2
--            evHVACAsentriaHumidOutThresh           .2.12.19.3.10.3
--            evHVACAsentriaHumidEnable              .2.12.19.3.10.4
--            evHVACAsentriaHumidEventDeadband       .2.12.19.3.10.5
--            evHVACAsentriaHumidVLowValue           .2.12.19.3.10.6
--            evHVACAsentriaHumidVLowActions         .2.12.19.3.10.7
--            evHVACAsentriaHumidVLowTrapNum         .2.12.19.3.10.8
--            evHVACAsentriaHumidVLowClass           .2.12.19.3.10.9
--            evHVACAsentriaHumidLowValue            .2.12.19.3.10.10
--            evHVACAsentriaHumidLowActions          .2.12.19.3.10.11
--            evHVACAsentriaHumidLowTrapNum          .2.12.19.3.10.12
--            evHVACAsentriaHumidLowClass            .2.12.19.3.10.13
--            evHVACAsentriaHumidNormalActions       .2.12.19.3.10.14
--            evHVACAsentriaHumidNormalTrapNum       .2.12.19.3.10.15
--            evHVACAsentriaHumidNormalClass         .2.12.19.3.10.16
--            evHVACAsentriaHumidHighValue           .2.12.19.3.10.17
--            evHVACAsentriaHumidHighActions         .2.12.19.3.10.18
--            evHVACAsentriaHumidHighTrapNum         .2.12.19.3.10.19
--            evHVACAsentriaHumidHighClass           .2.12.19.3.10.20
--            evHVACAsentriaHumidVHighValue          .2.12.19.3.10.21
--            evHVACAsentriaHumidVHighActions        .2.12.19.3.10.22
--            evHVACAsentriaHumidVHighTrapNum        .2.12.19.3.10.23
--            evHVACAsentriaHumidVHighClass          .2.12.19.3.10.24
--            evHVACAsentriaHumidDeadband            .2.12.19.3.10.25
--            evHVACAsentriaHumidDifference          .2.12.19.3.10.26
--        evHVACAirsys                               .2.12.19.4
--          evHVACAirsysGeneral                      .2.12.19.4.1
--            evHVACAirsysGeneratorLogic             .2.12.19.4.1.1
--            evHVACAirsysFreeMode                   .2.12.19.4.1.2
--            evHVACAirsysRemoteEnable               .2.12.19.4.1.3
--            evHVACAirsysHVACRotation               .2.12.19.4.1.4
--            evHVACAirsysRotationRuntime            .2.12.19.4.1.5
--          evHVACAirsysAlarm                        .2.12.19.4.2
--            evHVACAirsysUnitTable                  .2.12.19.4.2.1
--              evHVACAirsysUnitEntry                .2.12.19.4.2.1.1
--                evHVACAirsysUnitIndex              .2.12.19.4.2.1.1.1
--                evHVACAirsysULowPEnable            .2.12.19.4.2.1.1.2
--                evHVACAirsysULowPActions           .2.12.19.4.2.1.1.3
--                evHVACAirsysULowPClass             .2.12.19.4.2.1.1.4
--                evHVACAirsysULowPTrapNum           .2.12.19.4.2.1.1.5
--                evHVACAirsysULowPNormActions       .2.12.19.4.2.1.1.6
--                evHVACAirsysULowPNormClass         .2.12.19.4.2.1.1.7
--                evHVACAirsysULowPNormTrapNum       .2.12.19.4.2.1.1.8
--                evHVACAirsysUHighPEnable           .2.12.19.4.2.1.1.9
--                evHVACAirsysUHighPActions          .2.12.19.4.2.1.1.10
--                evHVACAirsysUHighPClass            .2.12.19.4.2.1.1.11
--                evHVACAirsysUHighPTrapNum          .2.12.19.4.2.1.1.12
--                evHVACAirsysUHighPNormActions      .2.12.19.4.2.1.1.13
--                evHVACAirsysUHighPNormClass        .2.12.19.4.2.1.1.14
--                evHVACAirsysUHighPNormTrapNum      .2.12.19.4.2.1.1.15
--                evHVACAirsysUEvapFanEnable         .2.12.19.4.2.1.1.16
--                evHVACAirsysUEvapFanActions        .2.12.19.4.2.1.1.17
--                evHVACAirsysUEvapFanClass          .2.12.19.4.2.1.1.18
--                evHVACAirsysUEvapFanTrapNum        .2.12.19.4.2.1.1.19
--                evHVACAirsysUEvapFanNormActions    .2.12.19.4.2.1.1.20
--                evHVACAirsysUEvapFanNormClass      .2.12.19.4.2.1.1.21
--                evHVACAirsysUEvapFanNormTrapNum    .2.12.19.4.2.1.1.22
--                evHVACAirsysUDirtyEnable           .2.12.19.4.2.1.1.23
--                evHVACAirsysUDirtyActions          .2.12.19.4.2.1.1.24
--                evHVACAirsysUDirtyClass            .2.12.19.4.2.1.1.25
--                evHVACAirsysUDirtyTrapNum          .2.12.19.4.2.1.1.26
--                evHVACAirsysUDirtyNormActions      .2.12.19.4.2.1.1.27
--                evHVACAirsysUDirtyNormClass        .2.12.19.4.2.1.1.28
--                evHVACAirsysUDirtyNormTrapNum      .2.12.19.4.2.1.1.29
--                evHVACAirsysUInProbeEnable         .2.12.19.4.2.1.1.30
--                evHVACAirsysUInProbeActions        .2.12.19.4.2.1.1.31
--                evHVACAirsysUInProbeClass          .2.12.19.4.2.1.1.32
--                evHVACAirsysUInProbeTrapNum        .2.12.19.4.2.1.1.33
--                evHVACAirsysUInProbeNormActions    .2.12.19.4.2.1.1.34
--                evHVACAirsysUInProbeNormClass      .2.12.19.4.2.1.1.35
--                evHVACAirsysUInProbeNormTrapNum    .2.12.19.4.2.1.1.36
--                evHVACAirsysUDamperEnable          .2.12.19.4.2.1.1.37
--                evHVACAirsysUDamperActions         .2.12.19.4.2.1.1.38
--                evHVACAirsysUDamperClass           .2.12.19.4.2.1.1.39
--                evHVACAirsysUDamperTrapNum         .2.12.19.4.2.1.1.40
--                evHVACAirsysUDamperNormActions     .2.12.19.4.2.1.1.41
--                evHVACAirsysUDamperNormClass       .2.12.19.4.2.1.1.42
--                evHVACAirsysUDamperNormTrapNum     .2.12.19.4.2.1.1.43
--                evHVACAirsysUSupProbeEnable        .2.12.19.4.2.1.1.44
--                evHVACAirsysUSupProbeActions       .2.12.19.4.2.1.1.45
--                evHVACAirsysUSupProbeClass         .2.12.19.4.2.1.1.46
--                evHVACAirsysUSupProbeTrapNum       .2.12.19.4.2.1.1.47
--                evHVACAirsysUSupProbeNormActions   .2.12.19.4.2.1.1.48
--                evHVACAirsysUSupProbeNormClass     .2.12.19.4.2.1.1.49
--                evHVACAirsysUSupProbeNormTrapNum   .2.12.19.4.2.1.1.50
--            evHVACAirsysSmokeFireEnable            .2.12.19.4.2.2
--            evHVACAirsysSmokeFireAction            .2.12.19.4.2.3
--            evHVACAirsysSmokeFireClass             .2.12.19.4.2.4
--            evHVACAirsysSmokeFireTrapNum           .2.12.19.4.2.5
--            evHVACAirsysSmokeFireNormAction        .2.12.19.4.2.6
--            evHVACAirsysSmokeFireNormClass         .2.12.19.4.2.7
--            evHVACAirsysSmokeFireNormTrapNum       .2.12.19.4.2.8
--            evHVACAirsysLowRoomTempEnable          .2.12.19.4.2.9
--            evHVACAirsysLowRoomTempAction          .2.12.19.4.2.10
--            evHVACAirsysLowRoomTempClass           .2.12.19.4.2.11
--            evHVACAirsysLowRoomTempTrapNum         .2.12.19.4.2.12
--            evHVACAirsysLowRoomTempNormAction      .2.12.19.4.2.13
--            evHVACAirsysLowRoomTempNormClass       .2.12.19.4.2.14
--            evHVACAirsysLowRoomTempNormTrapNum     .2.12.19.4.2.15
--            evHVACAirsysHighRoomTempEnable         .2.12.19.4.2.16
--            evHVACAirsysHighRoomTempAction         .2.12.19.4.2.17
--            evHVACAirsysHighRoomTempClass          .2.12.19.4.2.18
--            evHVACAirsysHighRoomTempTrapNum        .2.12.19.4.2.19
--            evHVACAirsysHighRoomTempNormAction     .2.12.19.4.2.20
--            evHVACAirsysHighRoomTempNormClass      .2.12.19.4.2.21
--            evHVACAirsysHighRoomTempNormTrapNum    .2.12.19.4.2.22
--            evHVACAirsysPowerEnable                .2.12.19.4.2.23
--            evHVACAirsysPowerAction                .2.12.19.4.2.24
--            evHVACAirsysPowerClass                 .2.12.19.4.2.25
--            evHVACAirsysPowerTrapNum               .2.12.19.4.2.26
--            evHVACAirsysPowerNormAction            .2.12.19.4.2.27
--            evHVACAirsysPowerNormClass             .2.12.19.4.2.28
--            evHVACAirsysPowerNormTrapNum           .2.12.19.4.2.29
--            evHVACAirsyspLANEnable                 .2.12.19.4.2.30
--            evHVACAirsyspLANAction                 .2.12.19.4.2.31
--            evHVACAirsyspLANClass                  .2.12.19.4.2.32
--            evHVACAirsyspLANTrapNum                .2.12.19.4.2.33
--            evHVACAirsyspLANNormAction             .2.12.19.4.2.34
--            evHVACAirsyspLANNormClass              .2.12.19.4.2.35
--            evHVACAirsyspLANNormTrapNum            .2.12.19.4.2.36
--            evHVACAirsysClockEnable                .2.12.19.4.2.37
--            evHVACAirsysClockAction                .2.12.19.4.2.38
--            evHVACAirsysClockClass                 .2.12.19.4.2.39
--            evHVACAirsysClockTrapNum               .2.12.19.4.2.40
--            evHVACAirsysClockNormAction            .2.12.19.4.2.41
--            evHVACAirsysClockNormClass             .2.12.19.4.2.42
--            evHVACAirsysClockNormTrapNum           .2.12.19.4.2.43
--            evHVACAirsysHumidProbeEnable           .2.12.19.4.2.44
--            evHVACAirsysHumidProbeAction           .2.12.19.4.2.45
--            evHVACAirsysHumidProbeClass            .2.12.19.4.2.46
--            evHVACAirsysHumidProbeTrapNum          .2.12.19.4.2.47
--            evHVACAirsysHumidProbeNormAction       .2.12.19.4.2.48
--            evHVACAirsysHumidProbeNormClass        .2.12.19.4.2.49
--            evHVACAirsysHumidProbeNormTrapNum      .2.12.19.4.2.50
--            evHVACAirsysOutProbeEnable             .2.12.19.4.2.51
--            evHVACAirsysOutProbeAction             .2.12.19.4.2.52
--            evHVACAirsysOutProbeClass              .2.12.19.4.2.53
--            evHVACAirsysOutProbeTrapNum            .2.12.19.4.2.54
--            evHVACAirsysOutProbeNormAction         .2.12.19.4.2.55
--            evHVACAirsysOutProbeNormClass          .2.12.19.4.2.56
--            evHVACAirsysOutProbeNormTrapNum        .2.12.19.4.2.57
--            evHVACAirsysBothCompressEnable         .2.12.19.4.2.58
--            evHVACAirsysBothCompressAction         .2.12.19.4.2.59
--            evHVACAirsysBothCompressClass          .2.12.19.4.2.60
--            evHVACAirsysBothCompressTrapNum        .2.12.19.4.2.61
--            evHVACAirsysBothCompressNormAction     .2.12.19.4.2.62
--            evHVACAirsysBothCompressNormClass      .2.12.19.4.2.63
--            evHVACAirsysBothCompressNormTrapNum    .2.12.19.4.2.64
--            evHVACAirsysGeneratorEnable            .2.12.19.4.2.65
--            evHVACAirsysGeneratorAction            .2.12.19.4.2.66
--            evHVACAirsysGeneratorClass             .2.12.19.4.2.67
--            evHVACAirsysGeneratorTrapNum           .2.12.19.4.2.68
--            evHVACAirsysGeneratorNormAction        .2.12.19.4.2.69
--            evHVACAirsysGeneratorNormClass         .2.12.19.4.2.70
--            evHVACAirsysGeneratorNormTrapNum       .2.12.19.4.2.71
--            evHVACAirsysConnectionEnable           .2.12.19.4.2.72
--            evHVACAirsysConnectionAction           .2.12.19.4.2.73
--            evHVACAirsysConnectionClass            .2.12.19.4.2.74
--            evHVACAirsysConnectionTrapNum          .2.12.19.4.2.75
--            evHVACAirsysConnectionNormAction       .2.12.19.4.2.76
--            evHVACAirsysConnectionNormClass        .2.12.19.4.2.77
--            evHVACAirsysConnectionNormTrapNum      .2.12.19.4.2.78
--          evHVACAirsysTemp                         .2.12.19.4.3
--            evHVACAirsysTempBaseThresh             .2.12.19.4.3.1
--            evHVACAirsysTempCoolDeadband           .2.12.19.4.3.2
--            evHVACAirsysTempHeatDeadband           .2.12.19.4.3.3
--            evHVACAirsysTempHighValue              .2.12.19.4.3.4
--            evHVACAirsysTempLowValue               .2.12.19.4.3.5
--          evHVACAirsysHumid                        .2.12.19.4.4
--            evHVACAirsysHumidMaxFree               .2.12.19.4.4.1
--            evHVACAirsysHumidDeadband              .2.12.19.4.4.2
--      evEvps                                       .2.12.20
--        evpsEnable                                 .2.12.20.1
--        evpsIPAddress                              .2.12.20.2
--        evpsPort                                   .2.12.20.3
--        evpsTimeout                                .2.12.20.4
--      accessControl                                .2.12.21
--        acActions                                  .2.12.21.2
--        acTrapnum                                  .2.12.21.3
--        acClass                                    .2.12.21.4
--        accessControlDeviceTable                   .2.12.21.10
--          accessControlDeviceEntry                 .2.12.21.10.1
--            acdIndex                               .2.12.21.10.1.1
--            acdEnable                              .2.12.21.10.1.2
--            acdName                                .2.12.21.10.1.3
--            acdReader                              .2.12.21.10.1.4
--            acdWiegandES                           .2.12.21.10.1.5
--            acdWiegandPoint                        .2.12.21.10.1.6
--            acdRelayType                           .2.12.21.10.1.7
--            acdRelayES                             .2.12.21.10.1.8
--            acdRelayPoint                          .2.12.21.10.1.9
--            acdOpenTime                            .2.12.21.10.1.10
--            acdUserGroup                           .2.12.21.10.1.11
--        accessControlUserTable                     .2.12.21.11
--          accessControlUserEntry                   .2.12.21.11.1
--            acuIndexUserGroup                      .2.12.21.11.1.1
--            acuIndexUser                           .2.12.21.11.1.2
--            acuEnable                              .2.12.21.11.1.3
--            acuName                                .2.12.21.11.1.4
--            acuSn                                  .2.12.21.11.1.5
--            acuSunBegin                            .2.12.21.11.1.6
--            acuSunEnd                              .2.12.21.11.1.7
--            acuMonBegin                            .2.12.21.11.1.8
--            acuMonEnd                              .2.12.21.11.1.9
--            acuTueBegin                            .2.12.21.11.1.10
--            acuTueEnd                              .2.12.21.11.1.11
--            acuWedBegin                            .2.12.21.11.1.12
--            acuWedEnd                              .2.12.21.11.1.13
--            acuThuBegin                            .2.12.21.11.1.14
--            acuThuEnd                              .2.12.21.11.1.15
--            acuFriBegin                            .2.12.21.11.1.16
--            acuFriEnd                              .2.12.21.11.1.17
--            acuSatBegin                            .2.12.21.11.1.18
--            acuSatEnd                              .2.12.21.11.1.19
--      telemetry                                    .2.12.22
--        telemetryTable                             .2.12.22.1
--          telemetryTableEntry                      .2.12.22.1.1
--            telemetryPointIndex                    .2.12.22.1.1.1
--            telemetryPointName                     .2.12.22.1.1.2
--            telemetryPointKey                      .2.12.22.1.1.3
--            telemetryPointType                     .2.12.22.1.1.4
--            telemetryPointClass                    .2.12.22.1.1.5
--            telemetryPointDeadband                 .2.12.22.1.1.6
--            telemetryPointShortcode                .2.12.22.1.1.7
--      siteSecurity                                 .2.12.23
--            siteSecIntrusionTable                  .2.12.23.1
--                siteSecEnable                          .2.12.23.1.1 
--                siteSecDisarmed                        .2.12.23.1.2
--                siteSecName                            .2.12.23.1.3
--                siteSecState                           .2.12.23.1.4 
--                siteSecSensorES                        .2.12.23.1.5 
--                siteSecSensorPoint                     .2.12.23.1.6 
--                siteSecIntrusionThreshold              .2.12.23.1.7 
--                siteSecReader                          .2.12.23.1.8
--                siteSecReaderThreshold                 .2.12.23.1.9
--                siteSecButtonEnable                    .2.12.23.1.10
--                siteSecButtonES                        .2.12.23.1.11
--                siteSecButtonPoint                     .2.12.23.1.12
--                siteSecButtonType                      .2.12.23.1.13
--                siteSecButtonThresholdArm              .2.12.23.1.14
--                siteSecButtonThresholdDisarm           .2.12.23.1.15
--                siteSecSirenEnable                     .2.12.23.1.16
--                siteSecSirenES                         .2.12.23.1.17
--                siteSecSirenPoint                      .2.12.23.1.18
--                siteSecRearmDelay                      .2.12.23.1.19
--            siteSecMotionTable                     .2.12.23.2
--                siteSecMotionES                        .2.12.23.2.1 
--                siteSecMotionPoint                     .2.12.23.2.2
--                siteSecMotionEnable                    .2.12.23.2.3 
--                siteSecMotionName                      .2.12.23.2.4
--                siteSecMotionThresholdRearm            .2.12.23.2.5
--            siteSecDoorAjarTable                   .2.12.23.3
--                siteSecDoorAjarEnable                  .2.12.23.3.1  
--                siteSecDoorAjarName                    .2.12.23.3.2  
--                siteSecDoorAjarES                      .2.12.23.3.3 
--                siteSecDoorAjarPoint                   .2.12.23.3.4 
--                siteSecDoorAjarThresholdNormal         .2.12.23.3.5  
--                siteSecDoorAjarThresholdExtraTime      .2.12.23.3.6  
--    action                                         .2.
--      actionCallNumberTable                        .2.14.1
--        actionCallNumberEntry                      .2.14.1.1
--          actionCallNumberIndex                    .2.14.1.1.1
--          actionCallNumber                         .2.14.1.1.2
--      actionPagerTable                             .2.14.2
--        actionPagerEntry                           .2.14.2.1
--          actionPagerIndex                         .2.14.2.1.1
--          actionPagerType                          .2.14.2.1.2
--          actionPagerNumber                        .2.14.2.1.3
--          actionPagerID                            .2.14.2.1.4
--          actionPagerMessage                       .2.14.2.1.5
--          actionPagerPostCalloutDelay              .2.14.2.1.6
--          actionPagerPostIDDelay                   .2.14.2.1.7
--      actionSched                                  .2.14.3
--        actionSchedEnable                          .2.14.3.1
--        actionSchedBegin                           .2.14.3.2
--        actionSchedEnd                             .2.14.3.3
--        actionSchedWeekdaysOnly                    .2.14.3.4
--      actionAsentria                               .2.14.4
--        actionAsentriaRequireAck                   .2.14.4.1
--        actionAsentriaVersion                      .2.14.4.2
--        actionAsentriaTCPPort                      .2.14.4.3
--      actionHostTable                              .2.14.6
--        actionHostEntry                            .2.14.6.1
--          actionHostIndex                          .2.14.6.1.1
--          actionHost                               .2.14.6.1.2
--      actionEmailTable                             .2.14.7
--        actionEmailEntry                           .2.14.7.1
--          actionEmailIndex                         .2.14.7.1.1
--          actionEmail                              .2.14.7.1.2
--      actionParseError                             .2.14.8
--    sys                                            .2.16
--      sysTime                                      .2.16.1
--        sysTimeAutoDST                             .2.16.1.1
--        sysTimeGMTOffset                           .2.16.1.2
--        sysTimeGMTDirection                        .2.16.1.3
--        sysTimeNet                                 .2.16.1.4
--          sysTimeNetEnable                         .2.16.1.4.1
--          sysTimeNetHostTable                      .2.16.1.4.2
--            sysTimeNetHostEntry                    .2.16.1.4.2.1
--              sysTimeNetHostIndex                  .2.16.1.4.2.1.1
--              sysTimeNetHost                       .2.16.1.4.2.1.2
--      sysPT                                        .2.16.2
--        sysPTTimeout                               .2.16.2.1
--        sysPTEndPause                              .2.16.2.2
--        sysPTJoinable                              .2.16.2.3
--      sysMTU                                       .2.16.3
--      sysAnswerString                              .2.16.4
--      sysEventFileID                               .2.16.6
--      sysEscapeCharacter                           .2.16.7
--      sysTimeStamp                                 .2.16.8
--        sysTimeStampTimeFormat                     .2.16.8.1
--        sysTimeStampDateFormat                     .2.16.8.2
--        sysTimeStampSpaceAfter                     .2.16.8.3
--      sysLog                                       .2.16.9
--        sysLogMode                                 .2.16.9.1
--        sysLoghost                                 .2.16.9.2
--        sysLogFilter                               .2.16.9.3
--        sysLogFileSize                             .2.16.9.4
--        sysLogFileCount                            .2.16.9.5
--        sysLogListenPort                           .2.16.9.6
--      sysCRDB                                      .2.16.10
--        sysCRDBCapacity                            .2.16.10.1
--        sysCRDBPercentFull                         .2.16.10.2
--        sysCRDBFileIDTable                         .2.16.10.3
--          sysCRDBFileIDEntry                       .2.16.10.3.1
--            sysCRDBFileIDIndex                     .2.16.10.3.1.1
--            sysCRDBFileID                          .2.16.10.3.1.2
--        sysCRDBFileEnforceMinTable                 .2.16.10.4
--          sysCRDBFileEnforceMinEntry               .2.16.10.4.1
--            sysCRDBFileEnforceMinIndex             .2.16.10.4.1.1
--            sysCRDBFileEnforceMin                  .2.16.10.4.1.2
--      sysCharMask                                  .2.16.11
--      sysPrompt                                    .2.16.12
--      sysBootStatus                                .2.16.13
--      sysLoc                                       .2.16.14
--        sysLocLatitude                             .2.16.14.1
--        sysLocLongitude                            .2.16.14.2
--        sysLocXOffset                              .2.16.14.3
--        sysLocYOffset                              .2.16.14.4
--        sysLocAngle                                .2.16.14.5
--        sysLocAltitude                             .2.16.14.6
--      sysAssetMgmt                                 .2.16.15
--        sysAMManufacturer                          .2.16.15.1
--        sysAMProduct                               .2.16.15.2
--        sysAMSerialNumber                          .2.16.15.3
--        sysAMHardwareOptions                       .2.16.15.4
--        sysAMSoftwareVersion                       .2.16.15.5
--        sysAMSiteName                              .2.16.15.6
--      sysFileTransfer                              .2.16.17
--        sysFileTransferStatus                      .2.16.17.1
--        sysFileTransferURL                         .2.16.17.2
--        sysFileTransferUsername                    .2.16.17.3
--        sysFileTransferPassword                    .2.16.17.4
--      sysUpdate                                    .2.16.18
--        sysUpdateStatus                            .2.16.18.1
--    auditLog                                       .2.17
--      auditLogEnable                               .2.17.1
--      auditLogStoreResets                          .2.17.2
--      auditLogStoreCommands                        .2.17.3
--      auditLogStoreOutputs                         .2.17.4
--      auditLogStoreAlarmActions                    .2.17.5
--      auditLogStorePwdFailures                     .2.17.6
--      auditLogStoreLogins                          .2.17.7
--      auditLogStoreSHSK                            .2.17.8
--      auditLogStorePassthrough                     .2.17.9
--      auditLogStoreInactivity                      .2.17.10
--      auditLogStorePolling                         .2.17.11
--      auditLogMaxSize                              .2.17.12
--    scripting                                      .2.18
--      scrGlobalEnable                              .2.18.1
--      scrDTRCtrlPortEnableTable                    .2.18.2
--        scrDTRCtrlPortEnableEnabletry              .2.18.2.1
--          scrDTRCtrlPortEnableIndex                .2.18.2.1.1
--          scrDTRCtrlPortEnable                     .2.18.2.1.2
--      scrTable                                     .2.18.3
--        scrEntry                                   .2.18.3.1
--          scrIndex                                 .2.18.3.1.1
--          scrEnable                                .2.18.3.1.2
--          scrName                                  .2.18.3.1.3
--          scrFilename                              .2.18.3.1.4
--          scrRunAlways                             .2.18.3.1.5
--          scrRunAtStartup                          .2.18.3.1.6
--          scrRunScheduled                          .2.18.3.1.7
--          scrScheduleTime                          .2.18.3.1.8
--          scrArguments                             .2.18.3.1.9
--          scrRepeatInterval                        .2.18.3.1.10
--      scrVolatileStringTable                       .2.18.4
--        scrVolatileStringEntry                     .2.18.4.1
--          scrVolatileStringIndex                   .2.18.4.1.1
--          scrVolatileString                        .2.18.4.1.2
--      scrVolatileIntTable                          .2.18.5
--        scrVolatileIntEntry                        .2.18.5.1
--          scrVolatileIntIndex                      .2.18.5.1.1
--          scrVolatileInt                           .2.18.5.1.2
--      scrNonVolatileStringTable                    .2.18.6
--        scrNonVolatileStringEntry                  .2.18.6.1
--          scrNonVolatileStringIndex                .2.18.6.1.1
--          scrNonVolatileString                     .2.18.6.1.2
--      scrNonVolatileIntTable                       .2.18.7
--        scrNonVolatileIntEntry                     .2.18.7.1
--          scrNonVolatileIntIndex                   .2.18.7.1.1
--          scrNonVolatileInt                        .2.18.7.1.2
--    generator                                      .2.19
--      genSet                                       .2.19.1
--        genSetEnable                               .2.19.1.1
--        genSetRelay                                .2.19.1.2
--          genSetRelayEs                            .2.19.1.2.1
--          genSetRelayPoint                         .2.19.1.2.2
--          genSetRelayRunningstate                  .2.19.1.2.3
--          genSetRelayTable                         .2.19.1.2.5
--            genSetRelayTableEntry                  .2.19.1.2.5.1
--              genSetRelayTableIndex                .2.19.1.2.5.1.1
--              genSetRelayTableEnable               .2.19.1.2.5.1.2
--              genSetRelayTableEs                   .2.19.1.2.5.1.3
--              genSetRelayTablePoint                .2.19.1.2.5.1.4
--              genSetRelayTableRunningstate         .2.19.1.2.5.1.5
--        genSetCc                                   .2.19.1.3
--          genSetCcEnable                           .2.19.1.3.1
--          genSetCcEs                               .2.19.1.3.2
--          genSetCcPoint                            .2.19.1.3.3
--          genSetCcRunningstate                     .2.19.1.3.4
--          genSetCCDelay                            .2.19.1.3.5
--      genRun                                       .2.19.2
--        genRunMode                                 .2.19.2.1
--        genRunSched                                .2.19.2.2
--        genRunDuration                             .2.19.2.3
--        genRunForce                                .2.19.2.4
--        genRunReqasm                               .2.19.2.5
--        genRunStatus                               .2.19.2.6
--        genRunNonstartEvent                        .2.19.2.7
--          genRunNonstartEventEnable                .2.19.2.7.1
--          genRunNonstartEventActions               .2.19.2.7.2
--          genRunNonstartEventTrap                  .2.19.2.7.3
--          genRunNonstartEventClass                 .2.19.2.7.4
--    calendar                                       .2.20
--      schedTable                                   .2.20.1
--        schedEntry                                 .2.20.1.1
--          schedIndex                               .2.20.1.1.1
--          schedEnable                              .2.20.1.1.2
--          schedStart                               .2.20.1.1.3
--          schedRepeatMode                          .2.20.1.1.4
--          schedRepeatFreq                          .2.20.1.1.5
--          schedRepeatEndMode                       .2.20.1.1.6
--          schedRepeatEndAfter                      .2.20.1.1.7
--          schedRepeatEndOn                         .2.20.1.1.8
--          schedRepeatWeeklySun                     .2.20.1.1.9
--          schedRepeatWeeklyMon                     .2.20.1.1.10
--          schedRepeatWeeklyTue                     .2.20.1.1.11
--          schedRepeatWeeklyWed                     .2.20.1.1.12
--          schedRepeatWeeklyThu                     .2.20.1.1.13
--          schedRepeatWeeklyFri                     .2.20.1.1.14
--          schedRepeatWeeklySat                     .2.20.1.1.15
--          schedRepeatMonthlyMode                   .2.20.1.1.16
--          schedRepeatMonthlyDates                  .2.20.1.1.17
--          schedRepeatMonthlyOnThe                  .2.20.1.1.18
--          schedRepeatMonthlyOnDay                  .2.20.1.1.19
--          schedRepeatYearlyJan                     .2.20.1.1.20
--          schedRepeatYearlyFeb                     .2.20.1.1.21
--          schedRepeatYearlyMar                     .2.20.1.1.22
--          schedRepeatYearlyApr                     .2.20.1.1.23
--          schedRepeatYearlyMay                     .2.20.1.1.24
--          schedRepeatYearlyJun                     .2.20.1.1.25
--          schedRepeatYearlyJul                     .2.20.1.1.26
--          schedRepeatYearlyAug                     .2.20.1.1.27
--          schedRepeatYearlySep                     .2.20.1.1.28
--          schedRepeatYearlyOct                     .2.20.1.1.29
--          schedRepeatYearlyNov                     .2.20.1.1.30
--          schedRepeatYearlyDec                     .2.20.1.1.31
--          schedRepeatYearlyOnThe                   .2.20.1.1.32
--          schedRepeatYearlyOnDay                   .2.20.1.1.33
--          schedNextTrigger                         .2.20.1.1.34

--  productIds                                       .3
--    siteName                                        3.1
--    thisProduct                                    .3.2
--    stockTrapString                                .3.3
--    trapEventTypeNumber                            .3.4
--    trapEventTypeName                              .3.5
--    trapIncludedValue                              .3.6
--    trapIncludedString                             .3.7
--    trapTypeString                                 .3.8
--    trapEventClassNumber                           .3.9
--    trapEventClassName                             .3.10

--  keyInterface                                     .4.0


--***************************************************************************************
--TOP-LEVEL OBJECT IDENTIFIERS
--***************************************************************************************

s550notifications OBJECT IDENTIFIER ::= { s550 0 }
    --1.3.6.1.4.1.3052.10.0

    status OBJECT IDENTIFIER ::= { s550 1 }
    --1.3.6.1.4.1.3052.10.1

        eventSensorStatus OBJECT IDENTIFIER ::= { status 1 }
        --1.3.6.1.4.1.3052.10.1.1

        dataEventStatus OBJECT IDENTIFIER ::= { status 2 }
        --1.3.6.1.4.1.3052.10.1.2

        powerDistributionStatus OBJECT IDENTIFIER ::= { status 5 }
        --1.3.6.1.4.1.3052.10.1.5

            pdNextGen OBJECT IDENTIFIER ::= { powerDistributionStatus 4 }
            --1.3.6.1.4.1.3052.10.1.5.4

            pdSystem OBJECT IDENTIFIER ::= { powerDistributionStatus 5 }
            --1.3.6.1.4.1.3052.10.1.5.5

        fuelSensorStatus OBJECT IDENTIFIER ::= { status 6 }
        --1.3.6.1.4.1.3052.10.1.6

        wirelessModemStatus OBJECT IDENTIFIER ::= { status 7 }
        --1.3.6.1.4.1.3052.10.1.7

        acPowerMonitorStatus OBJECT IDENTIFIER ::= { status 8 }
        --1.3.6.1.4.1.3052.10.1.8

        evHVACStatus OBJECT IDENTIFIER ::= { status 11 }
        --1.3.6.1.4.1.3052.10.1.11

            evHVACStatusBard OBJECT IDENTIFIER ::= { evHVACStatus 2 }
            --1.3.6.1.4.1.3052.10.1.11.2

                evHVACStatusBardSystem1 OBJECT IDENTIFIER ::= { evHVACStatusBard 1 }
                --1.3.6.1.4.1.3052.10.1.11.2.1

                    evHVACStatusBardSystem1Stage1 OBJECT IDENTIFIER ::= { evHVACStatusBardSystem1 1 }
                    --1.3.6.1.4.1.3052.10.1.11.2.1.1

                    evHVACStatusBardSystem1Stage2 OBJECT IDENTIFIER ::= { evHVACStatusBardSystem1 2 }
                    --1.3.6.1.4.1.3052.10.1.11.2.1.2

                evHVACStatusBardSystem2 OBJECT IDENTIFIER ::= { evHVACStatusBard 2 }
                --1.3.6.1.4.1.3052.10.1.11.2.2

                    evHVACStatusBardSystem2Stage1 OBJECT IDENTIFIER ::= { evHVACStatusBardSystem2 1 }
                    --1.3.6.1.4.1.3052.10.1.11.2.2.1

                    evHVACStatusBardSystem2Stage2 OBJECT IDENTIFIER ::= { evHVACStatusBardSystem2 2 }
                    --1.3.6.1.4.1.3052.10.1.11.2.2.2

                evHVACStatusBardTempRemote OBJECT IDENTIFIER ::= { evHVACStatusBard 5 }
                --1.3.6.1.4.1.3052.10.1.11.2.5

                evHVACStatusBardLEDs OBJECT IDENTIFIER ::= { evHVACStatusBard 7 }
                --1.3.6.1.4.1.3052.10.1.11.2.7.1

                    evHVACStatusBardLEDsCooling OBJECT IDENTIFIER ::= { evHVACStatusBardLEDs 1 }
                    --1.3.6.1.4.1.3052.10.1.11.2.7.1

                    evHVACStatusBardLEDsHeating OBJECT IDENTIFIER ::= { evHVACStatusBardLEDs 2 }
                    --1.3.6.1.4.1.3052.10.1.11.2.7.2

                    evHVACStatusBardLEDsDeHumid OBJECT IDENTIFIER ::= { evHVACStatusBardLEDs 3 }
                    --1.3.6.1.4.1.3052.10.1.11.2.7.3

                evHVACStatusBardAlarmStatus OBJECT IDENTIFIER ::= { evHVACStatusBard 10 }
                --1.3.6.1.4.1.3052.10.1.11.2.10

                    evHVACStatusBardASSystem1 OBJECT IDENTIFIER ::= { evHVACStatusBardAlarmStatus 1 }
                    --1.3.6.1.4.1.3052.10.1.11.2.10.1

                    evHVACStatusBardASSystem2 OBJECT IDENTIFIER ::= { evHVACStatusBardAlarmStatus 2 }
                    --1.3.6.1.4.1.3052.10.1.11.2.10.2

                    evHVACStatusBardASTemp OBJECT IDENTIFIER ::= { evHVACStatusBardAlarmStatus 4 }
                    --1.3.6.1.4.1.3052.10.1.11.2.10.4

            evHVACStatusAsentria OBJECT IDENTIFIER ::= { evHVACStatus 3 }
            --1.3.6.1.4.1.3052.10.1.11.3

                evHVACStatusAsentriaTemp OBJECT IDENTIFIER ::= { evHVACStatusAsentria 5 }
                --1.3.6.1.4.1.3052.10.1.11.3.5

                evHVACStatusAsentriaHumid OBJECT IDENTIFIER ::= { evHVACStatusAsentria 6 }
                --1.3.6.1.4.1.3052.10.1.11.3.6

            evHVACStatusAirsys OBJECT IDENTIFIER ::= { evHVACStatus 4 }
            --1.3.6.1.4.1.3052.10.1.11.4

                evHVACStatusAirsysAlarm OBJECT IDENTIFIER ::= { evHVACStatusAirsys 1 }
                --1.3.6.1.4.1.3052.10.1.11.4.1

        backupBattStatus OBJECT IDENTIFIER ::= { status 12 }
        --1.3.6.1.4.1.3052.10.1.12

              liBattStatus OBJECT IDENTIFIER ::= { backupBattStatus 1 }
              --1.3.6.1.4.1.3052.10.1.12.1
    config OBJECT IDENTIFIER ::= { s550 2 }
    --1.3.6.1.4.1.3052.10.2

        eventSensorBasics OBJECT IDENTIFIER ::= { config 1 }
        --1.3.6.1.4.1.3052.10.2.1

        eventSensorPointConfig OBJECT IDENTIFIER ::= { config 2 }
        --1.3.6.1.4.1.3052.10.2.2

        serialPorts OBJECT IDENTIFIER ::= { config 3 }
        --1.3.6.1.4.1.3052.10.2.3

        network OBJECT IDENTIFIER ::= { config 4 }
        --1.3.6.1.4.1.3052.10.2.4

            interface OBJECT IDENTIFIER ::= { network 1 }
            --1.3.6.1.4.1.3052.10.2.4

                ethernet OBJECT IDENTIFIER ::= { interface 1 }
                --1.3.6.1.4.1.3052.10.2.4.1

                    ethernet1 OBJECT IDENTIFIER ::= { ethernet 1 }
                    --1.3.6.1.4.1.3052.10.2.4.1.1

                        eth1VLAN OBJECT IDENTIFIER ::= { ethernet1 5 }
                        --1.3.6.1.4.1.3052.10.2.4.1.1.5

                            eth1VLAN1 OBJECT IDENTIFIER ::= { eth1VLAN 1 }
                            --1.3.6.1.4.1.3052.10.2.4.1.1.5.1

                            eth1VLAN2 OBJECT IDENTIFIER ::= { eth1VLAN 2 }
                            --1.3.6.1.4.1.3052.10.2.4.1.1.5.2

                            eth1VLAN3 OBJECT IDENTIFIER ::= { eth1VLAN 3 }
                            --1.3.6.1.4.1.3052.10.2.4.1.1.5.3

                            eth1VLAN4 OBJECT IDENTIFIER ::= { eth1VLAN 4 }
                            --1.3.6.1.4.1.3052.10.2.4.1.1.5.4

                            eth1VLAN5 OBJECT IDENTIFIER ::= { eth1VLAN 5 }
                            --1.3.6.1.4.1.3052.10.2.4.1.1.5.5

                            eth1VLAN6 OBJECT IDENTIFIER ::= { eth1VLAN 6 }
                            --1.3.6.1.4.1.3052.10.2.4.1.1.5.6

                        eth1IPv6 OBJECT IDENTIFIER ::= { ethernet1 7 }
                        --1.3.6.1.4.1.3052.10.2.4.1.1.7

                            eth1IPv6Static OBJECT IDENTIFIER ::= { eth1IPv6 2 }
                            --1.3.6.1.4.1.3052.10.2.4.1.1.7.2

                            eth1IPv6Auto OBJECT IDENTIFIER ::= { eth1IPv6 3 }
                            --1.3.6.1.4.1.3052.10.2.4.1.1.7.3

                    ethernet2 OBJECT IDENTIFIER ::= { ethernet 2 }
                    --1.3.6.1.4.1.3052.10.2.4.1.2

                        eth2VLAN OBJECT IDENTIFIER ::= { ethernet2 5 }
                        --1.3.6.1.4.1.3052.10.2.4.1.2.5

                            eth2VLAN1 OBJECT IDENTIFIER ::= { eth2VLAN 1 }
                            --1.3.6.1.4.1.3052.10.2.4.1.2.5.1

                            eth2VLAN2 OBJECT IDENTIFIER ::= { eth2VLAN 2 }
                            --1.3.6.1.4.1.3052.10.2.4.1.2.5.2

                            eth2VLAN3 OBJECT IDENTIFIER ::= { eth2VLAN 3 }
                            --1.3.6.1.4.1.3052.10.2.4.1.2.5.3

                            eth2VLAN4 OBJECT IDENTIFIER ::= { eth2VLAN 4 }
                            --1.3.6.1.4.1.3052.10.2.4.1.2.5.4

                            eth2VLAN5 OBJECT IDENTIFIER ::= { eth2VLAN 5 }
                            --1.3.6.1.4.1.3052.10.2.4.1.2.5.5

                            eth2VLAN6 OBJECT IDENTIFIER ::= { eth2VLAN 6 }
                            --1.3.6.1.4.1.3052.10.2.4.1.2.5.6

                        eth2IPv6 OBJECT IDENTIFIER ::= { ethernet2 7 }
                        --1.3.6.1.4.1.3052.10.2.4.1.2.7

                            eth2IPv6Static OBJECT IDENTIFIER ::= { eth2IPv6 2 }
                            --1.3.6.1.4.1.3052.10.2.4.1.2.7.2

                            eth2IPv6Auto OBJECT IDENTIFIER ::= { eth2IPv6 3 }
                            --1.3.6.1.4.1.3052.10.2.4.1.2.7.3

            snmp OBJECT IDENTIFIER ::= { network 8 }
            --1.3.6.1.4.1.3052.10.2.4.8

                snmpNotificationTx OBJECT IDENTIFIER ::= { snmp 7 }
                --1.3.6.1.4.1.3052.10.2.4.8.7

                snmpProxy OBJECT IDENTIFIER ::= { snmp 8 }
                --1.3.6.1.4.1.3052.10.2.4.8.8

                snmpPoll OBJECT IDENTIFIER ::= { snmp 9 }
                --1.3.6.1.4.1.3052.10.2.4.8.9

            ftpPush OBJECT IDENTIFIER ::= { network 9 }
            --1.3.6.1.4.1.3052.10.2.4.9

            ppp OBJECT IDENTIFIER ::= { network 10 }
            --1.3.6.1.4.1.3052.10.2.4.10

                pppDial OBJECT IDENTIFIER ::= { ppp 1 }
                --1.3.6.1.4.1.3052.10.2.4.10.1

                pppHost OBJECT IDENTIFIER ::= { ppp 2 }
                --1.3.6.1.4.1.3052.10.2.4.10.2

            routing OBJECT IDENTIFIER ::= { network 11 }
            --1.3.6.1.4.1.3052.10.2.4.11

            netSecurity OBJECT IDENTIFIER ::= { network 12 }
            --1.3.6.1.4.1.3052.10.2.4.12

                ipRestriction OBJECT IDENTIFIER ::= { netSecurity 1 }
                --1.3.6.1.4.1.3052.10.2.4.12.1

            rts OBJECT IDENTIFIER ::= { network 13 }
            --1.3.6.1.4.1.3052.10.2.4.13

                rtsAlarms OBJECT IDENTIFIER ::= { rts 2 }
                --1.3.6.1.4.1.3052.10.2.4.13.2

            trap OBJECT IDENTIFIER ::= { network 14 }
            --1.3.6.1.4.1.3052.10.2.4.14

                trapInclude OBJECT IDENTIFIER ::= { trap 1}
                --1.3.6.1.4.1.3052.10.2.4.14.1

            routeTest OBJECT IDENTIFIER ::= { network 15 }
            --1.3.6.1.4.1.3052.10.2.4.15

            wireless OBJECT IDENTIFIER ::= { network 16 }
            --1.3.6.1.4.1.3052.10.2.4.16

                wirelessConnectivity OBJECT IDENTIFIER ::= { wireless 20 }
                --1.3.6.1.4.1.3052.10.2.4.16.20

            email OBJECT IDENTIFIER ::= { network 17 }
            --1.3.6.1.4.1.3052.10.2.4.17

            netAdvanced OBJECT IDENTIFIER ::= { network 18 }
            --1.3.6.1.4.1.3052.10.2.4.18

            web OBJECT IDENTIFIER ::= { network 19 }
            --1.3.6.1.4.1.3052.10.2.4.19

                webXMLProxy OBJECT IDENTIFIER ::= { web 4 }
                --1.3.6.1.4.1.3052.10.2.4.19.4

            ethExpan OBJECT IDENTIFIER ::= { network 20 }
            --1.3.6.1.4.1.3052.10.2.4.20

              ethExpanDHCP OBJECT IDENTIFIER ::= { ethExpan 6 }
              --1.3.6.1.4.1.3052.10.2.4.20.6

            ipv6 OBJECT IDENTIFIER ::= { network 21 }
            --1.3.6.1.4.1.3052.10.2.4.21

            cpe OBJECT IDENTIFIER ::= { network 22 }
            --1.3.6.1.4.1.3052.10.2.4.22

            dnp3 OBJECT IDENTIFIER ::= { network 23 }
            --1.3.6.1.4.1.3052.10.2.4.23

                dnp3General OBJECT IDENTIFIER ::= { dnp3 1 }
                --1.3.6.1.4.1.3052.10.2.4.23.1

                dnp3Outstation OBJECT IDENTIFIER ::= { dnp3 2 }
                --1.3.6.1.4.1.3052.10.2.4.23.2

                dnp3Master OBJECT IDENTIFIER ::= { dnp3 3 }
                --1.3.6.1.4.1.3052.10.2.4.23.3

                dnp3Error OBJECT IDENTIFIER ::= { dnp3 4 }
                --1.3.6.1.4.1.3052.10.2.4.23.4

                dnp3Status OBJECT IDENTIFIER ::= { dnp3 5 }
                --1.3.6.1.4.1.3052.10.2.4.23.5

        modem OBJECT IDENTIFIER ::= { config 5 }
        --1.3.6.1.4.1.3052.10.2.5

            modemClid OBJECT IDENTIFIER ::= { modem 8 }
            --1.3.6.1.4.1.3052.10.2.5.7

        time OBJECT IDENTIFIER ::= { config 8 }
        --1.3.6.1.4.1.3052.10.2.8

        console OBJECT IDENTIFIER ::= { config 10 }
        --1.3.6.1.4.1.3052.10.2.10

        unitSecurity OBJECT IDENTIFIER ::= { config 11 }
        --1.3.6.1.4.1.3052.10.2.11

            secCore OBJECT IDENTIFIER ::= { unitSecurity 1 }
            --1.3.6.1.4.1.3052.10.2.11.1

            secFactory OBJECT IDENTIFIER ::= { unitSecurity 3 }
            --1.3.6.1.4.1.3052.10.2.11.3

            secSSH OBJECT IDENTIFIER ::= { unitSecurity 4 }
            --1.3.6.1.4.1.3052.10.2.11.4

            secVPN OBJECT IDENTIFIER ::= { unitSecurity 5 }
            --1.3.6.1.4.1.3052.10.2.11.5

        event OBJECT IDENTIFIER ::= { config 12 }
        --1.3.6.1.4.1.3052.10.2.12

            evCore OBJECT IDENTIFIER ::= { event 1 }
            --1.3.6.1.4.1.3052.10.2.12.1

                evLog OBJECT IDENTIFIER ::= { evCore 3 }
                --1.3.6.1.4.1.3052.10.2.12.1.3

                evMgmt OBJECT IDENTIFIER ::= { evCore 4 }
                --1.3.6.1.4.1.3052.10.2.12.1.4

            evData OBJECT IDENTIFIER ::= { event 2 }
            --1.3.6.1.4.1.3052.10.2.12.1

                evdCore OBJECT IDENTIFIER ::= { evData 1 }
                --1.3.6.1.4.1.3052.10.2.12.2.1

            evNoData1 OBJECT IDENTIFIER ::= { event 3 }
            --1.3.6.1.4.1.3052.10.2.12.3

            evNoData2 OBJECT IDENTIFIER ::= { event 4 }
            --1.3.6.1.4.1.3052.10.2.12.4

            evSched1 OBJECT IDENTIFIER ::= { event 5 }
            --1.3.6.1.4.1.3052.10.2.12.5

            evSched2 OBJECT IDENTIFIER ::= { event 6 }
            --1.3.6.1.4.1.3052.10.2.12.6

            evNoSensor OBJECT IDENTIFIER ::= { event 9 }
            --1.3.6.1.4.1.3052.10.2.12.9

            fuelSensor OBJECT IDENTIFIER ::= { event 11 }
            --1.3.6.1.4.1.3052.10.2.12.11

            acPowerMonitor OBJECT IDENTIFIER ::= { event 12 }
            --1.3.6.1.4.1.3052.10.2.12.12

            evReset OBJECT IDENTIFIER ::= { event 16 }
            --1.3.6.1.4.1.3052.10.2.12.16

            evGlobal OBJECT IDENTIFIER ::= { event 18 }
            --1.3.6.1.4.1.3052.10.2.12.18

            evHVAC OBJECT IDENTIFIER ::= { event 19 }
            --1.3.6.1.4.1.3052.10.2.12.19

                evHVACBard OBJECT IDENTIFIER ::= { evHVAC 2 }
                --1.3.6.1.4.1.3052.10.2.12.19.2

                    evHVACBardLocal OBJECT IDENTIFIER ::= { evHVACBard 1 }
                    --1.3.6.1.4.1.3052.10.2.12.19.2.1

                    evHVACBardAlarm OBJECT IDENTIFIER ::= { evHVACBardLocal 7 }
                        --1.3.6.1.4.1.3052.10.2.12.19.2.1.7

                    evHVACBardSynchronized OBJECT IDENTIFIER ::= { evHVACBard 2 }
                    --1.3.6.1.4.1.3052.10.2.12.19.2.2

                        evHVACBardDiff OBJECT IDENTIFIER ::= { evHVACBardSynchronized 19 }
                        --1.3.6.1.4.1.3052.10.2.12.19.2.2.19

                        evHVACBardTemp OBJECT IDENTIFIER ::= { evHVACBardSynchronized 32 }
                        --1.3.6.1.4.1.3052.10.2.12.19.2.2.32

                evHVACAsentria OBJECT IDENTIFIER ::= { evHVAC 3 }
                --1.3.6.1.4.1.3052.10.2.12.19.3

                    evHVACAsentriaAlarm OBJECT IDENTIFIER ::= { evHVACAsentria 6 }
                    --1.3.6.1.4.1.3052.10.2.12.19.3.6

                    evHVACAsentriaFire OBJECT IDENTIFIER ::= { evHVACAsentria 7 }
                    --1.3.6.1.4.1.3052.10.2.12.19.3.7

                    evHVACAsentriaTemp OBJECT IDENTIFIER ::= { evHVACAsentria 9 }
                    --1.3.6.1.4.1.3052.10.2.12.19.3.9

                    evHVACAsentriaHumid OBJECT IDENTIFIER ::= { evHVACAsentria 10 }
                    --1.3.6.1.4.1.3052.10.2.12.19.3.10
                    
                evHVACAirsys OBJECT IDENTIFIER ::= { evHVAC 4 }
                --1.3.6.1.4.1.3052.10.2.12.19.4

                    evHVACAirsysGeneral OBJECT IDENTIFIER ::= { evHVACAirsys 1 }
                    --1.3.6.1.4.1.3052.10.2.12.19.4.1

                    evHVACAirsysAlarm OBJECT IDENTIFIER ::= { evHVACAirsys 2 }
                    --1.3.6.1.4.1.3052.10.2.12.19.4.2

                    evHVACAirsysTemp OBJECT IDENTIFIER ::= { evHVACAirsys 3 }
                    --1.3.6.1.4.1.3052.10.2.12.19.4.3

                    evHVACAirsysHumid OBJECT IDENTIFIER ::= { evHVACAirsys 4 }
                    --1.3.6.1.4.1.3052.10.2.12.19.4.4

            evEvps OBJECT IDENTIFIER ::= { event 20 }
            --1.3.6.1.4.1.3052.10.2.12.20

            accessControl OBJECT IDENTIFIER ::= { event 21 }
            --1.3.6.1.4.1.3052.10.2.12.21

            telemetry OBJECT IDENTIFIER ::= { event 22 }
            --1.3.6.1.4.1.3052.10.2.12.22

            siteSecurity OBJECT IDENTIFIER ::= { event 23 }
            --1.3.6.1.4.1.3052.10.2.12.23


        action OBJECT IDENTIFIER ::= { config 14 }
        --1.3.6.1.4.1.3052.10.2.14

            actionSched OBJECT IDENTIFIER ::= { action 3 }
            --1.3.6.1.4.1.3052.10.2.14.3

            actionAsentria OBJECT IDENTIFIER ::= { action 4 }
            --1.3.6.1.4.1.3052.10.2.14.4

        sys OBJECT IDENTIFIER ::= { config 16 }
        --1.3.6.1.4.1.3052.10.2.16

            sysTime OBJECT IDENTIFIER ::= { sys 1 }
            --1.3.6.1.4.1.3052.10.2.16.1

                sysTimeNet OBJECT IDENTIFIER ::= { sysTime 4 }
                --1.3.6.1.4.1.3052.10.2.16.1.4

            sysPT OBJECT IDENTIFIER ::= { sys 2 }
            --1.3.6.1.4.1.3052.10.2.16.2

            sysTimeStamp OBJECT IDENTIFIER ::= { sys 8 }
            --1.3.6.1.4.1.3052.10.2.16.8

            sysLog OBJECT IDENTIFIER ::= { sys 9 }
            --1.3.6.1.4.1.3052.10.2.16.9

            sysCRDB OBJECT IDENTIFIER ::= { sys 10 }
            --1.3.6.1.4.1.3052.10.2.16.10

            sysLoc OBJECT IDENTIFIER ::= { sys 14 }
            --1.3.6.1.4.1.3052.10.2.16.14

            sysAssetMgmt OBJECT IDENTIFIER ::= { sys 15 }
            --1.3.6.1.4.1.3052.10.2.16.15

            sysFileTransfer OBJECT IDENTIFIER ::= { sys 17 }
            --1.3.6.1.4.1.3052.10.2.16.17

            sysUpdate OBJECT IDENTIFIER ::= { sys 18 }
            --1.3.6.1.4.1.3052.10.2.16.18

        auditLog OBJECT IDENTIFIER ::= { config 17 }
        --1.3.6.1.4.1.3052.10.2.17

        scripting OBJECT IDENTIFIER ::= { config 18 }
        --1.3.6.1.4.1.3052.10.2.18

        generator OBJECT IDENTIFIER ::= { config 19 }
        --1.3.6.1.4.1.3052.10.2.19

          genSet OBJECT IDENTIFIER ::= { generator 1 }
          --1.3.6.1.4.1.3052.10.2.19.1

            genSetRelay OBJECT IDENTIFIER ::= { genSet 2 }
            --1.3.6.1.4.1.3052.10.2.19.1.2

            genSetCC OBJECT IDENTIFIER ::= { genSet 3 }
            --1.3.6.1.4.1.3052.10.2.19.1.3

          genRun OBJECT IDENTIFIER ::= { generator 2 }
          --1.3.6.1.4.1.3052.10.2.19.2

            genRunNonstartEvent OBJECT IDENTIFIER ::= { genRun 7 }
            --1.3.6.1.4.1.3052.10.2.19.2.7

        calendar OBJECT IDENTIFIER ::= { config 20 }
        --1.3.6.1.4.1.3052.10.2.20

    productIds OBJECT IDENTIFIER ::= { s550 3 }
    --1.3.6.1.4.1.3052.10.3

--***************************************************************************************
--OBJECT DEFINITIONS
--***************************************************************************************

--***************************************************************************************
--EventSensor Status Section    1.1
--***************************************************************************************

esPointTable OBJECT-TYPE
    SYNTAX SEQUENCE OF ESPoint
    MAX-ACCESS not-accessible
    STATUS current
    DESCRIPTION
        "
        This table organizes 4 basic attributes of points.  A point
        is a particular sensor on an EventSensor (e.g., temperature,
        humidity, contact closure 2, output 5, etc.).  The 4 point
        attributes are its name, whether it's in its event state,
        the point's value as a number and its value as a string.

        Points are referenced by a point index.  The point index
        is a string of 3 numbers separated by periods.
        It contains all the information necessary for getting a piece
        of data off an event sensor; namely, which EventSensor,
        point class, and which-sensor-of-that-class (a.k.a. point).
        "
    ::= { eventSensorStatus 1 }
    --1.3.6.1.4.1.3052.10.1.1.1

esPointEntry OBJECT-TYPE
    SYNTAX ESPoint
    MAX-ACCESS not-accessible
    STATUS current
    DESCRIPTION
        "Entry for EventSensor point table"
    INDEX { esIndexES, esIndexPC, esIndexPoint }
    ::= { esPointTable 1 }
    --1.3.6.1.4.1.3052.10.1.1.1.1

esIndexES OBJECT-TYPE
    SYNTAX Integer32 (1..200)
    MAX-ACCESS read-only
    STATUS current
    DESCRIPTION
        "The part of the point index that refers to an
        EventSensor.

        The point index is a string of 3 numbers separated
        by periods.  It contains all the information
        necessary for getting a piece of data off an event
        sensor; namely, which EventSensor, point class,
        and which-sensor-of-that-class (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointEntry 1 }
    --1.3.6.1.4.1.3052.10.1.1.1.1.1

esIndexPC OBJECT-TYPE
    SYNTAX Integer32 (1..6)
    MAX-ACCESS read-only
    STATUS current
    DESCRIPTION
        "The part of the point index that refers to point class.

        The point index is a string of 3 numbers separated by periods.
        It contains all the information necessary for getting a piece
        of data off an event sensor; namely, which EventSensor,
        point class, and which-sensor-of-that-class (a.k.a. point).

        The values for this object are:
        1=temperature sensor
        2=contact closure
        3=humidity sensor
        4=noise sensor
        5=analog input
        6=output (relay output or power output)
        "
    ::= { esPointEntry 2 }
    --1.3.6.1.4.1.3052.10.1.1.1.1.2

esIndexPoint OBJECT-TYPE
    SYNTAX Integer32 (1..64)
    MAX-ACCESS read-only
    STATUS current
    DESCRIPTION
        "The part of the point index that delineates which
        sensor on the EventSensor.

        So this combined with esIndexPC (Point Class or type)
        and esIndexES (which EventSensor) uniquely defines each
        point (sensor or output) attached to a unit.  For
        example, if esIndexES is 3, esIndexPC is 1 and
        esIndexPoint is 4 then this is the Fourth Temperature
        Sensor on EventSensor number 3."
    ::= { esPointEntry 3 }
    --1.3.6.1.4.1.3052.10.1.1.1.1.3

esPointName OBJECT-TYPE
    SYNTAX DisplayString
    MAX-ACCESS read-write
    STATUS current
    DESCRIPTION
        "The name of the point on an EventSensor. For example,
        'AC temp' (in the case of the temperature sensor on an
        EventSensor).

        There can be multiple points of the same point class on an
        EventSensor (e.g., 8 contact closures) and multiple sensor
        classes on an EventSensor (e.g., temperature, contact closure,
        humidity).

        If the point referenced by a given point index is solitary
        (e.g., temperature sensor, because there can be only one on
        an EventSensor), then this object reads as '<EventSensor
        name>'.  Setting this object for solitary point indices sets
        the EventSensor name only.

        On the other hand, if a given point is among other points of
        the same point class on an EventSensor, then this object reads
        as '<Sensor name>'.  Setting this object for these NON-
        solitary point indices sets the sensor name only - not the
        EventSensor name."
    ::= { esPointEntry 4 }
    --1.3.6.1.4.1.3052.10.1.1.1.1.4

esPointInEventState OBJECT-TYPE
    SYNTAX Integer32
    MAX-ACCESS read-write
    STATUS current
    DESCRIPTION
        "A number referring to the event state of a point
        on an EventSensor.  This number can have different
        meanings depending on the point class.

        If the point class is temperature, humidity, or
        analog input, then the values of this object are:
        1=very low
        2=low
        3=normal
        4=high
        5=very high

        For contact closures the values of this object are:
        1=point in event state
        2=point in normal state

        For outputs the values of this object is the numeric
        code for the logical state of the output: 1 or 2.  The
        logical state of the output is either active/inactive for
        relay outputs or on/off for power outputs.  The logical
        state of the output has different nomenclature depending
        on the type of the output (relay output or power output):

        1=active (for relay output) or on (for power output)
        2=inactive (for relay output) or off (for power output)

        This is not necessarily representative of physical state
        of the output.  Physical state is energized/de-energized,
        for both relay and power outputs.  For relay outputs,
        the active logical state corresponds to either the energized
        physical state or the de-energized physical state depending
        on how the relay output is configured.  For power outputs,
        the on logical state always corresponds to the energized
        physical state.

        For any point class and any point, if the event
        state is undefined, then the value of this object
        is 0.

        For any point class except output, this object is read-only.
        For outputs, setting this object to 1 puts the output into
        its active logical state.

        Setting this object to 2 puts the output into its inactive
        logical state.

        Setting this object to any value greater than 2 puts the
        output into its active logical state for that many seconds
        (up to 3600), after which time it puts the output into its
        inactive logical state.
        "
    ::= { esPointEntry 5 }
    --1.3.6.1.4.1.3052.10.1.1.1.1.5

esPointValueInt OBJECT-TYPE
    SYNTAX Integer32 (-2147483648..2147483647)
    MAX-ACCESS read-write
    STATUS current
    DESCRIPTION
        "A read-only number referring to the value of a
        point on an EventSensor.

        If the point class is temperature, then this object
        is the temperature in its configured scale (default
        is Fahrenheit).

        If the point class is contact closure, then
        this object is either 0 (open) or 1 (closed).

        If the point class is humidity, then this object
        is the percent relative humidity.

        If the point class is analog input, then this
        object is the signed input value in tenths of the
        configured units.

        If the point class is an output, then this object is
        the numeric code for the physical state of the output.
        0=de-energized
        1=energized

        This object cannot be used to control the output, i.e,
        change its logical or physical state (instead use
        the esPointInEventState object).
        "
    ::= { esPointEntry 6 }
    --1.3.6.1.4.1.3052.10.1.1.1.1.6

esPointValueStr OBJECT-TYPE
    SYNTAX DisplayString
    MAX-ACCESS read-only
    STATUS current
    DESCRIPTION
        "A string referring to the value of a point on an
        EventSensor.

        For contact closures this object is either 'Open'
        or 'Closed'.

        For outputs this object is a concatenation of the
        logical state and physical state, separated by '/'.

        For a relay output this object can be one of the
        following 4 possible values:

        Active/Energized
        Inactive/Energized
        Active/De-energized
        Inactve/De-energized

        For a power output this object can be one of the
        following 2 possible values:

        On/Energized
        Off/De-energized

        For temperature and humidity point classes, this
        object is the string representation of the
        esPointValueInt object.  For temperature, 'C' or
        'F' is including in the string to indicate scale.

        For analog inputs, this object is the string
        representation of the plus/minus input in the
        configured units appended with the unit name.
        "
    ::= { esPointEntry 7 }
    --1.3.6.1.4.1.3052.10.1.1.1.1.7

esPointTimeLastChange OBJECT-TYPE
    SYNTAX DisplayString
    MAX-ACCESS read-only
    STATUS current
    DESCRIPTION
        "The time of the last time an event was
        triggerred for a point on an EventSensor in
        MM/DD/YY HH:MM:SS format.

        For contact closures, the possible events are
        Active and Inactive.  For temperature, humidity,
        and analog inputs, the possible events are Normal,
        High, Very High, Low, and Very Low.

        For outputs, this object is a null string."
    ::= { esPointEntry 8 }
    --1.3.6.1.4.1.3052.10.1.1.1.1.8

esPointTimetickLastChange OBJECT-TYPE
    SYNTAX TimeTicks
    MAX-ACCESS read-only
    STATUS current
    DESCRIPTION
        "The time of the last time an event was
        triggerred for a point on an EventSensor in
        100ths of seconds since reset.

        For contact closures, the possible events are
        Active and Inactive.  For temperature, humidity,
        and analog inputs, the possible events are Normal,
        High, Very High, Low, and Very Low.

        For outputs, this object is 0."
    ::= { esPointEntry 9 }
    --1.3.6.1.4.1.3052.10.1.1.1.1.9

esPointAliasValueStr OBJECT-TYPE
    SYNTAX DisplayString
    MAX-ACCESS read-only
    STATUS current
    DESCRIPTION
        "For CC inputs, this is the CC active/inactive alias setting
         setting value that currently corresponds to the event state.
         So if the CC input is in the event state, then this object
         is the active alias setting value.  If the CC input is in the
         normal state, then this object is the inactive alias setting
         value.

         For relay/power outputs, this is the output active/inactive
         alias setting value that currently corresponds to the output
         state.  So if the output is in the active state, then this
         object is the active alias setting value.  If the output is
         in hte inactive state, then this object is the inactive alias
         setting value.

         For non-CC and non-output sensors, this is the same as the
         esPointValueStr object."
    ::= { esPointEntry 10 }
    --1.3.6.1.4.1.3052.10.1.1.1.1.10



esPointClassValueStr OBJECT-TYPE
    SYNTAX DisplayString
    MAX-ACCESS read-only
    STATUS current
    DESCRIPTION
        "For CC inputs, this is the CC active/inactive class setting
         setting value that currently corresponds to the event state.
         So if the CC input is in the event state, then this object
         is the active class setting value.  If the CC input is in the
         normal state, then this object is the inactive class setting
         value.

         For relay/power, analog and temp outputs, this is the output 
         class string given the event (Very High, High, Normal, Low and
         Very Low).  The class string is based upon the chosen string in
         the class table for e.g. Info, Minor, Major, Minor, Critical etc.
         If the given event is High, the chosen Class string for this event
         is what returned.
         "
    ::= { esPointEntry 11 }
    --1.3.6.1.4.1.3052.10.1.1.1.1.11

--***************************************************************************************
--Data Event Status Section 1.2
--***************************************************************************************

deStatusTable OBJECT-TYPE
    SYNTAX SEQUENCE OF DEStatus
    MAX-ACCESS not-accessible
    STATUS current
    DESCRIPTION
        "Data Event Status Table"
    ::= { dataEventStatus 1 }
    --1.3.6.1.4.1.3052.10.1.2.1

deStatusEntry OBJECT-TYPE
    SYNTAX DEStatus
    MAX-ACCESS not-accessible
    STATUS current
    DESCRIPTION
        "EventSensor status entry"
    INDEX { deStatusIndex }
    ::= { deStatusTable 1 }
    --1.3.6.1.4.1.3052.10.1.2.1.1

deStatusIndex OBJECT-TYPE
    SYNTAX Integer32 (1..100)
    MAX-ACCESS read-only
    STATUS current
    DESCRIPTION
        "Index for Data Events"
    ::= { deStatusEntry 1 }
    --1.3.6.1.4.1.3052.10.1.2.1.1.1

deStatusName OBJECT-TYPE
    SYNTAX DisplayString
    MAX-ACCESS read-only
    STATUS current
    DESCRIPTION
        "Data Event name"
    ::= { deStatusEntry 2 }
    --1.3.6.1.4.1.3052.10.1.2.1.1.2

deStatusCounter OBJECT-TYPE
    SYNTAX Integer32
    MAX-ACCESS read-only
    STATUS current
    DESCRIPTION
        "Number of times a data record has matched this
        event's equation.
        Range: 1-999999999"
    ::= { deStatusEntry 3 }
    --1.3.6.1.4.1.3052.10.1.2.1.1.3

deStatusThreshold OBJECT-TYPE
    SYNTAX Integer32
    MAX-ACCESS read-only
    STATUS current
    DESCRIPTION
        "Number of times the equation is matched before
        an event is triggered.
        Range: 1-999999999"
    ::= { deStatusEntry 4 }
    --1.3.6.1.4.1.3052.10.1.2.1.1.4

modemStatus OBJECT-TYPE
    SYNTAX DisplayString
    MAX-ACCESS read-only
    STATUS current
    DESCRIPTION
        "status of modem (idle, dialing, connected, etc.)"
    ::= { status 3 }
    --1.3.6.1.4.1.3052.10.1.3

modemCLIDLogTable OBJECT-TYPE
    SYNTAX SEQUENCE OF ModemCLIDLogConfig
    MAX-ACCESS not-accessible
    STATUS current
    DESCRIPTION
        "Table of numbers of recent dialing parties"
    ::= { status 4 }
    --1.3.6.1.4.1.3052.10.1.4

modemCLIDLogEntry OBJECT-TYPE
    SYNTAX ModemCLIDLogConfig
    MAX-ACCESS not-accessible
    STATUS current
    DESCRIPTION
        "Entry for table of CLID log entries"
    INDEX { modemCLIDLogIndex }
    ::= { modemCLIDLogTable 1 }
    --1.3.6.1.4.1.3052.10.1.4.1

modemCLIDLogIndex OBJECT-TYPE
    SYNTAX Integer32 (1..8)
    MAX-ACCESS read-only
    STATUS current
    DESCRIPTION
        "Index for table of CLID log entries"
    ::= { modemCLIDLogEntry 1 }
    --1.3.6.1.4.1.3052.10.1.4.1.1

modemCLIDLogNumber OBJECT-TYPE
    SYNTAX DisplayString
    MAX-ACCESS read-write
    STATUS current
    DESCRIPTION
        "recently logged number of dialing party"
    ::= { modemCLIDLogEntry 2 }
    --1.3.6.1.4.1.3052.10.1.4.1.2

--***************************************************************************************
--Power Distribution Status Section 1.5
--***************************************************************************************

pdConfig OBJECT-TYPE
    SYNTAX DisplayString
    MAX-ACCESS read-only
    STATUS current
    DESCRIPTION
        "Power Distribution output configuration"
    ::= { powerDistributionStatus 1 }
    --1.3.6.1.4.1.3052.10.1.5.1

PowerDistribNextGen ::=
    SEQUENCE {
        pdnIndexPD
            Integer32,
        pdnIndexOutput
            Integer32,
        pdnConfig
            DisplayString,
        pdnMainCurrentInEventState
            DisplayString,
        pdnMainCurrentValue
            Integer32,
        pdnMainCurrentValueStr
            DisplayString,
        pdnMainCurrentDeadband
            Integer32,
        pdnMainCurrentVHighCurrent
            Integer32,
        pdnMainCurrentHighCurrent
            Integer32,
        pdnMainCurrentLowCurrent
            Integer32,
        pdnMainCurrentVLowCurrent
            Integer32,
        pdnMainVoltageInEventState
            DisplayString,
        pdnMainVoltageValue
            Integer32,
        pdnMainVoltageValueStr
            DisplayString,
        pdnMainVoltageDeadband
            Integer32,
        pdnMainVoltageVHighVoltage
            Integer32,
        pdnMainVoltageHighVoltage
            Integer32,
        pdnMainVoltageLowVoltage
            Integer32,
        pdnMainVoltageVLowVoltage
            Integer32,
        pdnMainPowerValue
            Integer32,
        pdnMainPowerValueStr
            DisplayString,
        pdnOutputCurrentInEventState
            DisplayString,
        pdnOutputCurrentValue
            Integer32,
        pdnOutputCurrentValueStr
            DisplayString,
        pdnOutputCurrentDeadband
            Integer32,
        pdnOutputCurrentVHighCurrent
            Integer32,
        pdnOutputCurrentHighCurrent
            Integer32,
        pdnOutputCurrentLowCurrent
            Integer32,
        pdnOutputCurrentVLowCurrent
            Integer32,
        pdnOutputFuseInEventState
            DisplayString,
        pdnOutputFuseValueStr
            DisplayString,
        pdnMainCombinedStatus
            DisplayString,
        pdnOutputCombinedStatusBlock1
            DisplayString,
        pdnOutputCombinedStatusBlock2
            DisplayString,
        pdnDeviceCurrentValue
            Integer32,
        pdnDeviceCurrentValueStr
            DisplayString
}

pdnTable OBJECT-TYPE
    SYNTAX SEQUENCE OF PowerDistribNextGen
    MAX-ACCESS not-accessible
    STATUS current
    DESCRIPTION
        "Table of power distribution objects arranged according
        to next-generation methodology (i.e., using multiple PowerBoss
        power distributors in addition to the on-board power
        distributor)."
    ::= { pdNextGen 1 }
    --1.3.6.1.4.1.3052.10.1.5.4.1

pdnEntry OBJECT-TYPE
    SYNTAX PowerDistribNextGen
    MAX-ACCESS not-accessible
    STATUS current
    DESCRIPTION
        "Entry for table of power distribution objects arranged according
        to next-generation methodology (i.e., using multiple PowerBoss
        power distributors in addition to the on-board power
        distributor)."
    INDEX { pdnIndexPD, pdnIndexOutput }
    ::= { pdnTable 1 }
    --1.3.6.1.4.1.3052.10.1.5.4.1.1

pdnIndexPD OBJECT-TYPE
    SYNTAX Integer32 (1..200)
    MAX-ACCESS read-only
    STATUS current
    DESCRIPTION
        "Index for table of power distribution objects, specifically the
        index that refers to which power distributor.  A value of 200 means
        the internal power distributor.  A value from 1 to 16 refers to an
        external power distributor (PowerBoss), and is the same value as esIndexES,
        which refers to the PowerBoss as an EventSensor in the eventSensorStatus
        object table.  In other words, pdnIndexPD is the same as esIndexES:
        esIndexES is used to refer to the PowerBoss as an eventsensor (i.e., control
        outputs), while pdnIndexPD is used to refer to the PowerBoss when used for
        power distribution monitoring (i.e., to alarm on output
        current/voltage/fuse status)."
    ::= { pdnEntry 1 }
    --1.3.6.1.4.1.3052.10.1.5.4.1.1.1

pdnIndexOutput OBJECT-TYPE
    SYNTAX Integer32 (1..12)
    MAX-ACCESS read-only
    STATUS current
    DESCRIPTION
        "Index for table of power distribution objects, specifically the
        index that refers to which output on the power distributor specified
        by pdnIndexPD.  For objects where the output is irrelevant, this index
        should be 1."
    ::= { pdnEntry 2 }
    --1.3.6.1.4.1.3052.10.1.5.4.1.1.2

pdnConfig OBJECT-TYPE
    SYNTAX DisplayString
    MAX-ACCESS read-only
    STATUS current
    DESCRIPTION
        "The number of outputs on the power distributor specified by pdnIndexPD.
        pdnIndexOutput should be 1 for this object."
    ::= { pdnEntry 3 }
    --1.3.6.1.4.1.3052.10.1.5.4.1.1.3

pdnMainCurrentInEventState OBJECT-TYPE
    SYNTAX DisplayString
    MAX-ACCESS read-only
    STATUS current
    DESCRIPTION
        "The event state of the current (i.e. Amps) event of the power distributor
        specified by pdnIndexPD.  pdnIndexOutput should be 1 for this object.
        Possible values for this object are: 'Very Low', 'Low', 'Normal', 'High',
        'Very High'."
    ::= { pdnEntry 4 }
    --1.3.6.1.4.1.3052.10.1.5.4.1.1.4

pdnMainCurrentValue OBJECT-TYPE
    SYNTAX Integer32
    MAX-ACCESS read-only
    STATUS current
    DESCRIPTION
        "The current drawn, in mA, for the power distributor specified by pdnIndexPD.
        If pdnIndexPD is 1-16 then this is an external power distributor (PowerBoss)
        and refers to the current drawn by that PowerBoss and all equipment powered
        by that PowerBoss.  pdnIndexOutput should be 1 for this object."
    ::= { pdnEntry 5 }
    --1.3.6.1.4.1.3052.10.1.5.4.1.1.5

pdnMainCurrentValueStr OBJECT-TYPE
    SYNTAX DisplayString
    MAX-ACCESS read-only
    STATUS current
    DESCRIPTION
        "Essentially pdnMainCurrentValue formatted as a string in units of Amps, with
        3 decimal places.  pdnIndexOutput should be 1 for this object."
    ::= { pdnEntry 6 }
    --1.3.6.1.4.1.3052.10.1.5.4.1.1.6

pdnMainCurrentDeadband OBJECT-TYPE
    SYNTAX Integer32
    MAX-ACCESS read-only
    STATUS current
    DESCRIPTION
        "The deadband, in mA, for the main current sensor for the power distributor
        specified by pdIndexPD.  pdnIndexOutput should be 1 for this object."
    ::= { pdnEntry 7 }
    --1.3.6.1.4.1.3052.10.1.5.4.1.1.7

pdnMainCurrentVHighCurrent OBJECT-TYPE
    SYNTAX Integer32
    MAX-ACCESS read-only
    STATUS current
    DESCRIPTION
        "The current, in mA, for the main current sensor's Very High event threshold,
        for the power distributor specified by pdIndexPD.  pdnIndexOutput should be 1
        for this object."
    ::= { pdnEntry 8 }
    --1.3.6.1.4.1.3052.10.1.5.4.1.1.8

pdnMainCurrentHighCurrent OBJECT-TYPE
    SYNTAX Integer32
    MAX-ACCESS read-only
    STATUS current
    DESCRIPTION
        "The current, in mA, for the main current sensor's High event threshold,
        for the power distributor specified by pdIndexPD.  pdnIndexOutput should be 1
        for this object."
    ::= { pdnEntry 9 }
    --1.3.6.1.4.1.3052.10.1.5.4.1.1.9

pdnMainCurrentLowCurrent OBJECT-TYPE
    SYNTAX Integer32
    MAX-ACCESS read-only
    STATUS current
    DESCRIPTION
        "The current, in mA, for the main current sensor's Low event threshold,
        for the power distributor specified by pdIndexPD.  pdnIndexOutput should be 1
        for this object."
    ::= { pdnEntry 10 }
    --1.3.6.1.4.1.3052.10.1.5.4.1.1.10

pdnMainCurrentVLowCurrent OBJECT-TYPE
    SYNTAX Integer32
    MAX-ACCESS read-only
    STATUS current
    DESCRIPTION
        "The current, in mA, for the main current sensor's Very Low event threshold,
        for the power distributor specified by pdIndexPD.  pdnIndexOutput should be 1
        for this object."
    ::= { pdnEntry 11 }
    --1.3.6.1.4.1.3052.10.1.5.4.1.1.11

pdnMainVoltageInEventState OBJECT-TYPE
    SYNTAX DisplayString
    MAX-ACCESS read-only
    STATUS current
    DESCRIPTION
        "The event state of the voltage event of the power distributor
        specified by pdnIndexPD.  pdnIndexOutput should be 1 for this object.
        Possible values for this object are: 'Very Low', 'Low', 'Normal', 'High',
        'Very High'."
    ::= { pdnEntry 12 }
    --1.3.6.1.4.1.3052.10.1.5.4.1.1.12

pdnMainVoltageValue OBJECT-TYPE
    SYNTAX Integer32
    MAX-ACCESS read-only
    STATUS current
    DESCRIPTION
        "The voltage, in mV, at the power distributor specified by pdnIndexPD.
        If pdnIndexPD is 1-16 then this is an external power distributor (PowerBoss)
        and refers to the voltage at that PowerBoss and all equipment powered by that
        PowerBoss.  pdnIndexOutput should be 1 for this object."
    ::= { pdnEntry 13 }
    --1.3.6.1.4.1.3052.10.1.5.4.1.1.13

pdnMainVoltageValueStr OBJECT-TYPE
    SYNTAX DisplayString
    MAX-ACCESS read-only
    STATUS current
    DESCRIPTION
        "Essentially pdnMainVoltageValue formatted as a string in units of Volts, with
        3 decimal places.  pdnIndexOutput should be 1 for this object."
    ::= { pdnEntry 14 }
    --1.3.6.1.4.1.3052.10.1.5.4.1.1.14

pdnMainVoltageDeadband OBJECT-TYPE
    SYNTAX Integer32
    MAX-ACCESS read-only
    STATUS current
    DESCRIPTION
        "The deadband, in mV, for the main voltage sensor for the power distributor
        specified by pdIndexPD.  pdnIndexOutput should be 1 for this object."
    ::= { pdnEntry 15 }
    --1.3.6.1.4.1.3052.10.1.5.4.1.1.15

pdnMainVoltageVHighVoltage OBJECT-TYPE
    SYNTAX Integer32
    MAX-ACCESS read-only
    STATUS current
    DESCRIPTION
        "The voltage, in mA, for the main voltage sensor's Very High event threshold,
        for the power distributor specified by pdIndexPD.  pdnIndexOutput should be 1
        for this object."
    ::= { pdnEntry 16 }
    --1.3.6.1.4.1.3052.10.1.5.4.1.1.16

pdnMainVoltageHighVoltage OBJECT-TYPE
    SYNTAX Integer32
    MAX-ACCESS read-only
    STATUS current
    DESCRIPTION
        "The voltage, in mV, for the main voltage sensor's High event threshold,
        for the power distributor specified by pdIndexPD.  pdnIndexOutput should be 1
        for this object."
    ::= { pdnEntry 17 }
    --1.3.6.1.4.1.3052.10.1.5.4.1.1.17

pdnMainVoltageLowVoltage OBJECT-TYPE
    SYNTAX Integer32
    MAX-ACCESS read-only
    STATUS current
    DESCRIPTION
        "The voltage, in mV, for the main voltage sensor's Low event threshold,
        for the power distributor specified by pdIndexPD.  pdnIndexOutput should be 1
        for this object."
    ::= { pdnEntry 18 }
    --1.3.6.1.4.1.3052.10.1.5.4.1.1.18

pdnMainVoltageVLowVoltage OBJECT-TYPE
    SYNTAX Integer32
    MAX-ACCESS read-only
    STATUS current
    DESCRIPTION
        "The voltage, in mV, for the main voltage sensor's Very Low event threshold,
        for the power distributor specified by pdIndexPD.  pdnIndexOutput should be 1
        for this object."
    ::= { pdnEntry 19 }
    --1.3.6.1.4.1.3052.10.1.5.4.1.1.19

pdnMainPowerValue OBJECT-TYPE
    SYNTAX Integer32
    MAX-ACCESS read-only
    STATUS current
    DESCRIPTION
        "The power, in Watts, for the power distributor specified by pdIndexPD.
        pdnIndexOutput should be 1 for this object."
    ::= { pdnEntry 20 }
    --1.3.6.1.4.1.3052.10.1.5.4.1.1.20

pdnMainPowerValueStr OBJECT-TYPE
    SYNTAX DisplayString
    MAX-ACCESS read-only
    STATUS current
    DESCRIPTION
        "The power, in Watts, for the power distributor specified by pdIndexPD,
        formatted as a string with the unit name 'Watts'.  pdnIndexOutput should be 1
        for this object."
    ::= { pdnEntry 21 }
    --1.3.6.1.4.1.3052.10.1.5.4.1.1.21

pdnOutputCurrentInEventState OBJECT-TYPE
    SYNTAX DisplayString
    MAX-ACCESS read-only
    STATUS current
    DESCRIPTION
        "The event state of the current (i.e. Amps) event of the power distributor
        output specified by pdnIndexPD and pdnIndexOutput.  E.g., for pdnIndexPD=200
        and pdnIndexOutput=2, this refers to power output #2 of the internal power
        distributor. Possible values for this object are: 'Very Low', 'Low', 'Normal',
        'High', 'Very High'."
    ::= { pdnEntry 22 }
    --1.3.6.1.4.1.3052.10.1.5.4.1.1.22

pdnOutputCurrentValue OBJECT-TYPE
    SYNTAX Integer32
    MAX-ACCESS read-only
    STATUS current
    DESCRIPTION
        "The current drawn, in mA, for the power distributor output specified by
        pdnIndexPD and pdIndexOutput.  E.g., if pdIndexPD is 3 then this is an external
        power distributor (PowerBoss) identified as 'power distributor 3' and refers to
        the current drawn by a specific power output on that PowerBoss.  The specific
        power output is specified by pdIndexOutput."
    ::= { pdnEntry 23 }
    --1.3.6.1.4.1.3052.10.1.5.4.1.1.23

pdnOutputCurrentValueStr OBJECT-TYPE
    SYNTAX DisplayString
    MAX-ACCESS read-only
    STATUS current
    DESCRIPTION
        "Essentially pdnOutputCurrentValue formatted as a string in units of Amps, with
        3 decimal places."
    ::= { pdnEntry 24 }
    --1.3.6.1.4.1.3052.10.1.5.4.1.1.24

pdnOutputCurrentDeadband OBJECT-TYPE
    SYNTAX Integer32
    MAX-ACCESS read-only
    STATUS current
    DESCRIPTION
        "The deadband, in mA, for the main current sensor for the power distributor
        specified by pdIndexPD.  The power output is specified by pdnIndexOutput."
    ::= { pdnEntry 25 }
    --1.3.6.1.4.1.3052.10.1.5.4.1.1.25

pdnOutputCurrentVHighCurrent OBJECT-TYPE
    SYNTAX Integer32
    MAX-ACCESS read-only
    STATUS current
    DESCRIPTION
        "The current, in mA, for a specific power output's current sensor Very High
        event threshold, for the power distributor specified by pdIndexPD.  The power
        output is specified by pdnIndexOutput."
    ::= { pdnEntry 26 }
    --1.3.6.1.4.1.3052.10.1.5.4.1.1.26

pdnOutputCurrentHighCurrent OBJECT-TYPE
    SYNTAX Integer32
    MAX-ACCESS read-only
    STATUS current
    DESCRIPTION
        "The current, in mA, for a specific power output's current sensor High event
        threshold, for the power distributor specified by pdIndexPD.  The power output
        is specified by pdnIndexOutput for this object."
    ::= { pdnEntry 27 }
    --1.3.6.1.4.1.3052.10.1.5.4.1.1.27

pdnOutputCurrentLowCurrent OBJECT-TYPE
    SYNTAX Integer32
    MAX-ACCESS read-only
    STATUS current
    DESCRIPTION
        "The current, in mA, for a specific power output's current sensor Low event
        threshold, for the power distributor specified by pdIndexPD.  The power output
        is specified by pdnIndexOutput for this object."
    ::= { pdnEntry 28 }
    --1.3.6.1.4.1.3052.10.1.5.4.1.1.28

pdnOutputCurrentVLowCurrent OBJECT-TYPE
    SYNTAX Integer32
    MAX-ACCESS read-only
    STATUS current
    DESCRIPTION
        "The current, in mA, for a specific power output's current sensor Very Low
        event threshold, for the power distributor specified by pdIndexPD.  The power
        output is specified by pdnIndexOutput for this object."
    ::= { pdnEntry 29 }
    --1.3.6.1.4.1.3052.10.1.5.4.1.1.29

pdnOutputFuseInEventState OBJECT-TYPE
    SYNTAX DisplayString
    MAX-ACCESS read-only
    STATUS current
    DESCRIPTION
        "The event state of the fuse event of the power distributor output specified
        by pdnIndexPD and pdnIndexOutput.  E.g., for pdnIndexPD=14 and pdnIndexOutput=2,
        this refers to power output #2 of the external power distributor (PowerBoss),
        identified as 'power distributor 14'. Possible values for this object are:
        'Very Low', 'Low', 'Normal', 'High', 'Very High'.  This object exists only for
        power distributors with fuse monitoring support."
    ::= { pdnEntry 30 }
    --1.3.6.1.4.1.3052.10.1.5.4.1.1.30

pdnOutputFuseValueStr OBJECT-TYPE
    SYNTAX DisplayString
    MAX-ACCESS read-only
    STATUS current
    DESCRIPTION
        "The state of the fuse of the power distributor output specified
        by pdnIndexPD and pdnIndexOutput.  Possible values for this object are:
        'BLOWN' and 'OK'.  This object exists only for power distributors with fuse
        monitoring support."
    ::= { pdnEntry 31 }
    --1.3.6.1.4.1.3052.10.1.5.4.1.1.31

pdnMainCombinedStatus OBJECT-TYPE
    SYNTAX DisplayString
    MAX-ACCESS read-only
    STATUS current
    DESCRIPTION
        "Combined status string intended to be parsed by NMS:
        format: voltageColorCode`voltageEventState`voltageValue`mainCurrentColorCode`mainCurrentEventState`mainCurrentValue`deviceCurrentValue`mainPowerValue"
    ::= { pdnEntry 32 }
    --1.3.6.1.4.1.3052.10.1.5.4.1.1.32

pdnOutputCombinedStatusBlock1 OBJECT-TYPE
    SYNTAX DisplayString
    MAX-ACCESS read-only
    STATUS current
    DESCRIPTION
        "Combined status string intended to be parsed by NMS:
        format: numInBlock~outputCurrentColorCode1`outputCurrentEventState1`outputCurrentValue1`fuseColorCode1`fuseValue1~..."
    ::= { pdnEntry 33 }
    --1.3.6.1.4.1.3052.10.1.5.4.1.1.33

pdnOutputCombinedStatusBlock2 OBJECT-TYPE
    SYNTAX DisplayString
    MAX-ACCESS read-only
    STATUS current
    DESCRIPTION
        "Combined status string intended to be parsed by NMS:
        format: numInBlock~outputCurrentColorCode1`outputCurrentEventState1`outputCurrentValue1`fuseColorCode1`fuseValue1~..."
    ::= { pdnEntry 34 }
    --1.3.6.1.4.1.3052.10.1.5.4.1.1.34

pdnDeviceCurrentValue OBJECT-TYPE
    SYNTAX Integer32
    MAX-ACCESS read-only
    STATUS current
    DESCRIPTION
        "Current drawn by device in mA.  For the internal power distributor device,
        this is the current drawn by the SiteBoss 571.  For an external power
        distributor device (PowerBoss), this is the current drawn by the
        PowerBoss.  This object exists only for power distributors with device
        current monitoring support."
    ::= { pdnEntry 35 }
    --1.3.6.1.4.1.3052.10.1.5.4.1.1.35

pdnDeviceCurrentValueStr OBJECT-TYPE
    SYNTAX DisplayString
    MAX-ACCESS read-only
    STATUS current
    DESCRIPTION
        "Current drawn by device as a string with units (Amps).  For the internal
        power distributor device, this is the current drawn by the SiteBoss 571.
        For an external power distributor device (PowerBoss), this is the
        current drawn by the PowerBoss.  This object exists only for power
        distributors with device current monitoring support."
    ::= { pdnEntry 36 }
    --1.3.6.1.4.1.3052.10.1.5.4.1.1.36

pdSystemCurrent OBJECT-TYPE
    SYNTAX DisplayString
    MAX-ACCESS read-only
    STATUS current
    DESCRIPTION
        "Total current drawn by all power distributors in system; that is, the
        sum of all pdnMainCurrentValue objects for all connected power
        distributors: internal and external."
    ::= { pdSystem 1 }
    --1.3.6.1.4.1.3052.10.1.5.5.1

pdSystemPower OBJECT-TYPE
    SYNTAX DisplayString
    MAX-ACCESS read-only
    STATUS current
    DESCRIPTION
        "Total power used by all power distributors in system; that is, the
        sum of all pdnMainPowerValue objects for all connected power
        distributors: internal and external."
    ::= { pdSystem 2 }
    --1.3.6.1.4.1.3052.10.1.5.5.2


--***************************************************************************************
--Fuel Sensor 1.6
--***************************************************************************************

fsStatusTable OBJECT-TYPE
    SYNTAX SEQUENCE OF FSStatus
    MAX-ACCESS not-accessible
    STATUS current
    DESCRIPTION
        "Fuel sensor status table"
    ::= { fuelSensorStatus 1 }
    --1.3.6.1.4.1.3052.10.1.6.1

fsStatusEntry OBJECT-TYPE
    SYNTAX FSStatus
    MAX-ACCESS not-accessible
    STATUS current
    DESCRIPTION
        "Fuel sensor status table entry"
    INDEX { fsStatusIndex }
    ::= { fsStatusTable 1 }
    --1.3.6.1.4.1.3052.10.1.6.1.1

fsStatusIndex OBJECT-TYPE
    SYNTAX Integer32 (1..3)
    MAX-ACCESS read-only
    STATUS current
    DESCRIPTION
        "Index for fuel sensors"
    ::= { fsStatusEntry 1 }
    --1.3.6.1.4.1.3052.10.1.6.1.1.1

fsStatusName OBJECT-TYPE
    SYNTAX DisplayString
    MAX-ACCESS read-only
    STATUS current
    DESCRIPTION
        "Fuel sensor name"
    ::= { fsStatusEntry 2 }
    --1.3.6.1.4.1.3052.10.1.6.1.1.2

fsStatusDeviceState OBJECT-TYPE
    SYNTAX DisplayString
    MAX-ACCESS read-only
    STATUS current
    DESCRIPTION
        "Fuel sensor device state"
    ::= { fsStatusEntry 3 }
    --1.3.6.1.4.1.3052.10.1.6.1.1.3

fsStatusVolumeValueString OBJECT-TYPE
    SYNTAX DisplayString
    MAX-ACCESS read-only
    STATUS current
    DESCRIPTION
        "Fuel volume. Range is -2,147,483,648 to 2,147,483,647. This value reads
         -999 when the fuel sensor is disconnected"
    ::= { fsStatusEntry 4 }
    --1.3.6.1.4.1.3052.10.1.6.1.1.4

fsStatusVolumePercentLevel OBJECT-TYPE
    SYNTAX DisplayString
    MAX-ACCESS read-only
    STATUS current
    DESCRIPTION
        "Height of the fluid in the tank expressed as a percentage of the tank
         height, in hundredths of a percent."
    ::= { fsStatusEntry 7 }
    --1.3.6.1.4.1.3052.10.1.6.1.1.7

fsStatusVolumeInEventState OBJECT-TYPE
    SYNTAX DisplayString
    MAX-ACCESS read-only
    STATUS current
    DESCRIPTION
        "Current event status of the fuel sensor."
    ::= { fsStatusEntry 8 }
    --1.3.6.1.4.1.3052.10.1.6.1.1.8

fsStatusCombined OBJECT-TYPE
    SYNTAX DisplayString
    MAX-ACCESS read-only
    STATUS current
    DESCRIPTION
        "Combined status string intended to be parsed by NMS:
        deviceState`deviceStateColorCode`percentRounded`valueAsFloat`volumeEventState`volumeEventStateColorCode`capacity`units`name"
    ::= { fsStatusEntry 9 }
    --1.3.6.1.4.1.3052.10.1.6.1.1.9

--***************************************************************************************
--Wireless Modem Status Section  1.7
--***************************************************************************************

wmsStatus OBJECT-TYPE
    SYNTAX DisplayString
    MAX-ACCESS read-only
    STATUS current
    DESCRIPTION
        "Wireless modem status"
    ::= { wirelessModemStatus 1 }
    --1.3.6.1.4.1.3052.10.1.7.1

wmsSignal OBJECT-TYPE
    SYNTAX DisplayString
    MAX-ACCESS read-only
    STATUS current
    DESCRIPTION
        "Wireless modem Signal strength"
    ::= { wirelessModemStatus 2 }
    --1.3.6.1.4.1.3052.10.1.7.2

wmsRSSI OBJECT-TYPE
    SYNTAX DisplayString
    MAX-ACCESS read-only
    STATUS current
    DESCRIPTION
        "Wireless modem Signal strength (RSSI)"
    ::= { wirelessModemStatus 3 }
    --1.3.6.1.4.1.3052.10.1.7.3

wmsBER OBJECT-TYPE
    SYNTAX DisplayString
    MAX-ACCESS read-only
    STATUS current
    DESCRIPTION
        "Wireless modem Bit Error Rate"
    ::= { wirelessModemStatus 4 }
    --1.3.6.1.4.1.3052.10.1.7.4

wmsUpdated OBJECT-TYPE
    SYNTAX DisplayString
    MAX-ACCESS read-only
    STATUS current
    DESCRIPTION
        "Wireless modem info last update time"
    ::= { wirelessModemStatus 5 }
    --1.3.6.1.4.1.3052.10.1.7.5

wmsRegistration OBJECT-TYPE
    SYNTAX DisplayString
    MAX-ACCESS read-only
    STATUS current
    DESCRIPTION
        "Wireless modem registration status"
    ::= { wirelessModemStatus 6 }
    --1.3.6.1.4.1.3052.10.1.7.6

wmsLAC OBJECT-TYPE
    SYNTAX DisplayString
    MAX-ACCESS read-only
    STATUS current
    DESCRIPTION
        "Wireless modem Location Area Code"
    ::= { wirelessModemStatus 7 }
    --1.3.6.1.4.1.3052.10.1.7.7

wmsCellID OBJECT-TYPE
    SYNTAX DisplayString
    MAX-ACCESS read-only
    STATUS current
    DESCRIPTION
        "Wireless modem Cell ID"
    ::= { wirelessModemStatus 8 }
    --1.3.6.1.4.1.3052.10.1.7.8

wmsIMSI OBJECT-TYPE
    SYNTAX DisplayString
    MAX-ACCESS read-only
    STATUS current
    DESCRIPTION
        "Wireless modem Internation Mobile Subscriber Identity number"
    ::= { wirelessModemStatus 9 }
    --1.3.6.1.4.1.3052.10.1.7.9

wmsPhnum OBJECT-TYPE
    SYNTAX DisplayString
    MAX-ACCESS read-only
    STATUS current
    DESCRIPTION
        "Wireless modem phone number"
    ::= { wirelessModemStatus 10 }
    --1.3.6.1.4.1.3052.10.1.7.10

wmsLocalIP OBJECT-TYPE
    SYNTAX DisplayString
    MAX-ACCESS read-only
    STATUS current
    DESCRIPTION
        "Local IP address of modem on wireless network"
    ::= { wirelessModemStatus 11 }
    --1.3.6.1.4.1.3052.10.1.7.11

wmsMgfID OBJECT-TYPE
    SYNTAX DisplayString
    MAX-ACCESS read-only
    STATUS current
    DESCRIPTION
        "Wireless modem manufacturer ID"
    ::= { wirelessModemStatus 12 }
    --1.3.6.1.4.1.3052.10.1.7.12

wmsModelID OBJECT-TYPE
    SYNTAX DisplayString
    MAX-ACCESS read-only
    STATUS current
    DESCRIPTION
        "Wireless modem model ID"
    ::= { wirelessModemStatus 13 }
    --1.3.6.1.4.1.3052.10.1.7.13

wmsIMEI OBJECT-TYPE
    SYNTAX DisplayString
    MAX-ACCESS read-only
    STATUS current
    DESCRIPTION
        "Wireless modem International Mobile Equipment Identity number"
    ::= { wirelessModemStatus 14 }
    --1.3.6.1.4.1.3052.10.1.7.14

wmsRevID OBJECT-TYPE
    SYNTAX DisplayString
    MAX-ACCESS read-only
    STATUS current
    DESCRIPTION
        "Wireless modem revision ID"
    ::= { wirelessModemStatus 15 }
    --1.3.6.1.4.1.3052.10.1.7.15

wmsNetName OBJECT-TYPE
    SYNTAX DisplayString
    MAX-ACCESS read-only
    STATUS current
    DESCRIPTION
        "Wireless modem network name"
    ::= { wirelessModemStatus 16 }
    --1.3.6.1.4.1.3052.10.1.7.16

wmsGPRSStatus OBJECT-TYPE
    SYNTAX DisplayString
    MAX-ACCESS read-only
    STATUS current
    DESCRIPTION
        "Wireless modem (E)GPRS status"
    ::= { wirelessModemStatus 17 }
    --1.3.6.1.4.1.3052.10.1.7.17

wmsBand OBJECT-TYPE
    SYNTAX DisplayString
    MAX-ACCESS read-only
    STATUS current
    DESCRIPTION
        "Wireless modem band"
    ::= { wirelessModemStatus 18 }
    --1.3.6.1.4.1.3052.10.1.7.18

wmsChannel OBJECT-TYPE
    SYNTAX DisplayString
    MAX-ACCESS read-only
    STATUS current
    DESCRIPTION
        "Wireless modem channel"
    ::= { wirelessModemStatus 19 }
    --1.3.6.1.4.1.3052.10.1.7.19

wmsCountryCode OBJECT-TYPE
    SYNTAX DisplayString
    MAX-ACCESS read-only
    STATUS current
    DESCRIPTION
        "Wireless modem country code"
    ::= { wirelessModemStatus 20 }
    --1.3.6.1.4.1.3052.10.1.7.20

wmsNetCode OBJECT-TYPE
    SYNTAX DisplayString
    MAX-ACCESS read-only
    STATUS current
    DESCRIPTION
        "Wireless modem network code"
    ::= { wirelessModemStatus 21 }
    --1.3.6.1.4.1.3052.10.1.7.21

wmsPLMNColor OBJECT-TYPE
    SYNTAX DisplayString
    MAX-ACCESS read-only
    STATUS current
    DESCRIPTION
        "Wireless modem PLMN color"
    ::= { wirelessModemStatus 22 }
    --1.3.6.1.4.1.3052.10.1.7.22

wmsBScolor OBJECT-TYPE
    SYNTAX DisplayString
    MAX-ACCESS read-only
    STATUS current
    DESCRIPTION
        "Wireless modem BS color"
    ::= { wirelessModemStatus 23 }
    --1.3.6.1.4.1.3052.10.1.7.23

wmsMpRACH OBJECT-TYPE
    SYNTAX DisplayString
    MAX-ACCESS read-only
    STATUS current
    DESCRIPTION
        "Wireless modem max power RACH"
    ::= { wirelessModemStatus 24 }
    --1.3.6.1.4.1.3052.10.1.7.24

wmsMinRxLevel OBJECT-TYPE
    SYNTAX DisplayString
    MAX-ACCESS read-only
    STATUS current
    DESCRIPTION
        "Wireless modem minimum receive level"
    ::= { wirelessModemStatus 25 }
    --1.3.6.1.4.1.3052.10.1.7.25

wmsBaseCoeff OBJECT-TYPE
    SYNTAX DisplayString
    MAX-ACCESS read-only
    STATUS current
    DESCRIPTION
        "Wireless modem base coefficient"
    ::= { wirelessModemStatus 26 }
    --1.3.6.1.4.1.3052.10.1.7.26

wmsSIMStatus OBJECT-TYPE
    SYNTAX DisplayString
    MAX-ACCESS read-only
    STATUS current
    DESCRIPTION
        "WWireless modem SIM status"
    ::= { wirelessModemStatus 27 }
    --1.3.6.1.4.1.3052.10.1.7.27

wmsICCID OBJECT-TYPE
    SYNTAX DisplayString
    MAX-ACCESS read-only
    STATUS current
    DESCRIPTION
        "Wireless modem SIM ICCID"
    ::= { wirelessModemStatus 28 }
    --1.3.6.1.4.1.3052.10.1.7.28

wmsModemType OBJECT-TYPE
    SYNTAX DisplayString
    MAX-ACCESS read-only
    STATUS current
    DESCRIPTION
        "Wireless modem type"
    ::= { wirelessModemStatus 29 }
    --1.3.6.1.4.1.3052.10.1.7.29


--***************************************************************************************
--AC Power Monitor Section 1.8
--***************************************************************************************

acpmStatusTable OBJECT-TYPE
    SYNTAX SEQUENCE OF ACPMStatus
    MAX-ACCESS not-accessible
    STATUS current
    DESCRIPTION
        "AC power monitor status table"
    ::= { acPowerMonitorStatus 1 }
    --1.3.6.1.4.1.3052.10.1.8.1

acpmStatusEntry OBJECT-TYPE
    SYNTAX ACPMStatus
    MAX-ACCESS not-accessible
    STATUS current
    DESCRIPTION
        "AC power monitor status table entry"
    INDEX { acpmsIndex }
    ::= { acpmStatusTable 1 }
    --1.3.6.1.4.1.3052.10.1.8.1.1

acpmsIndex OBJECT-TYPE
    SYNTAX Integer32 (1..6)
    MAX-ACCESS read-only
    STATUS current
    DESCRIPTION
        "Index for AC power monitors"
    ::= { acpmStatusEntry 1 }
    --1.3.6.1.4.1.3052.10.1.8.1.1.1

acpmsName OBJECT-TYPE
    SYNTAX DisplayString
    MAX-ACCESS read-only
    STATUS current
    DESCRIPTION
        "Name for the AC power monitor device."
    ::= { acpmStatusEntry 2 }
    --1.3.6.1.4.1.3052.10.1.8.1.1.2

acpmsAvgVoltageValueStr OBJECT-TYPE
    SYNTAX DisplayString
    MAX-ACCESS read-only
    STATUS current
    DESCRIPTION
        "Average voltage, in volts. This is calculated using the formula
        (register * PT ratio * 0.1). This could be either the average of
        the phase voltages, or the sum of the phase voltages, depending
        on device configuration."
    ::= { acpmStatusEntry 3 }
    --1.3.6.1.4.1.3052.10.1.8.1.1.3

acpmsAvgVoltageMinStr OBJECT-TYPE
    SYNTAX DisplayString
    MAX-ACCESS read-only
    STATUS current
    DESCRIPTION
        "Minimum average voltage value since last reset, in volts."
    ::= { acpmStatusEntry 4 }
    --1.3.6.1.4.1.3052.10.1.8.1.1.4

acpmsAvgVoltageMaxStr OBJECT-TYPE
    SYNTAX DisplayString
    MAX-ACCESS read-only
    STATUS current
    DESCRIPTION
        "Maximum average voltage value since last reset, in volts."
    ::= { acpmStatusEntry 5 }
    --1.3.6.1.4.1.3052.10.1.8.1.1.5

acpmsAvgVoltageAvgStr OBJECT-TYPE
    SYNTAX DisplayString
    MAX-ACCESS read-only
    STATUS current
    DESCRIPTION
        "Average average voltage value since last reset, in volts.  This is
        the unit's average of its measurements of the average voltage
        reported by the AC power monitor device."
    ::= { acpmStatusEntry 6 }
    --1.3.6.1.4.1.3052.10.1.8.1.1.6

acpmsAvgVoltageInEventState OBJECT-TYPE
    SYNTAX DisplayString
    MAX-ACCESS read-only
    STATUS current
    DESCRIPTION
        "Event state of this AC power monitor voltage (Low, Normal, High, etc.)."
    ::= { acpmStatusEntry 7 }
    --1.3.6.1.4.1.3052.10.1.8.1.1.7

acpmsVoltagePhaseAValueStr OBJECT-TYPE
    SYNTAX DisplayString
    MAX-ACCESS read-only
    STATUS current
    DESCRIPTION
        "Phase A voltage, in volts. This is calculated using the formula
        (register * PT ratio * 0.1)."
    ::= { acpmStatusEntry 8 }
    --1.3.6.1.4.1.3052.10.1.8.1.1.8

acpmsVoltagePhaseBValueStr OBJECT-TYPE
    SYNTAX DisplayString
    MAX-ACCESS read-only
    STATUS current
    DESCRIPTION
        "Phase B voltage, in volts. This is calculated using the formula
        (register * PT ratio * 0.1)."
    ::= { acpmStatusEntry 9 }
    --1.3.6.1.4.1.3052.10.1.8.1.1.9

acpmsVoltagePhaseCValueStr OBJECT-TYPE
    SYNTAX DisplayString
    MAX-ACCESS read-only
    STATUS current
    DESCRIPTION
        "Phase C voltage, in volts. This is calculated using the formula
        (register * PT ratio * 0.1)."
    ::= { acpmStatusEntry 10 }
    --1.3.6.1.4.1.3052.10.1.8.1.1.10

acpmsVoltageL1L2Value OBJECT-TYPE
    SYNTAX DisplayString
    MAX-ACCESS read-only
    STATUS current
    DESCRIPTION
        "Line 1 to Line 2 voltage"
    ::= { acpmStatusEntry 11 }
    --1.3.6.1.4.1.3052.10.1.8.1.1.11

acpmsVoltageL2L3Value OBJECT-TYPE
    SYNTAX DisplayString
    MAX-ACCESS read-only
    STATUS current
    DESCRIPTION
        "Line 2 to Line 3 voltage"
    ::= { acpmStatusEntry 12 }
    --1.3.6.1.4.1.3052.10.1.8.1.1.12

acpmsVoltageL3L1Value OBJECT-TYPE
    SYNTAX DisplayString
    MAX-ACCESS read-only
    STATUS current
    DESCRIPTION
        "Line 3 to Line 1 voltage"
    ::= { acpmStatusEntry 13 }
    --1.3.6.1.4.1.3052.10.1.8.1.1.13


acpmsAvgCurrentValueStr OBJECT-TYPE
    SYNTAX DisplayString
    MAX-ACCESS read-only
    STATUS current
    DESCRIPTION
        "Average current, in amps. This is calculated using the formula
        (register * CT ratio * 0.001). This could be either the average of
        the phase currents, or the sum of the phase currents, depending on
        device configuration."
    ::= { acpmStatusEntry 14 }
    --1.3.6.1.4.1.3052.10.1.8.1.1.14

acpmsAvgCurrentMinStr OBJECT-TYPE
    SYNTAX DisplayString
    MAX-ACCESS read-only
    STATUS current
    DESCRIPTION
        "Minimum average current value since last reset, in amps."
    ::= { acpmStatusEntry 15 }
    --1.3.6.1.4.1.3052.10.1.8.1.1.15

acpmsAvgCurrentMaxStr OBJECT-TYPE
    SYNTAX DisplayString
    MAX-ACCESS read-only
    STATUS current
    DESCRIPTION
        "Maximum average current value since last reset, in amps."
    ::= { acpmStatusEntry 16 }
    --1.3.6.1.4.1.3052.10.1.8.1.1.16

acpmsAvgCurrentAvgStr OBJECT-TYPE
    SYNTAX DisplayString
    MAX-ACCESS read-only
    STATUS current
    DESCRIPTION
        "Average average current value since last reset, in amps.  This is
        the unit's average of its measurements of the average current reported
        by the AC power monitor device."
    ::= { acpmStatusEntry 17 }
    --1.3.6.1.4.1.3052.10.1.8.1.1.17

acpmsAvgCurrentInEventState OBJECT-TYPE
    SYNTAX DisplayString
    MAX-ACCESS read-only
    STATUS current
    DESCRIPTION
        "Event state of this AC power monitor current (Low, Normal, High, etc.)."
    ::= { acpmStatusEntry 18 }
    --1.3.6.1.4.1.3052.10.1.8.1.1.18

acpmsCurrentPhaseAValueStr OBJECT-TYPE
    SYNTAX DisplayString
    MAX-ACCESS read-only
    STATUS current
    DESCRIPTION
        "Phase A current, in amps. This is calculated using the formula
        (register * CT ratio * 0.001)."
    ::= { acpmStatusEntry 19 }
    --1.3.6.1.4.1.3052.10.1.8.1.1.19

acpmsCurrentPhaseBValueStr OBJECT-TYPE
    SYNTAX DisplayString
    MAX-ACCESS read-only
    STATUS current
    DESCRIPTION
        "Phase B current, in amps. This is calculated using the formula
        (register * CT ratio * 0.001)."
    ::= { acpmStatusEntry 20 }
    --1.3.6.1.4.1.3052.10.1.8.1.1.20

acpmsCurrentPhaseCValueStr OBJECT-TYPE
    SYNTAX DisplayString
    MAX-ACCESS read-only
    STATUS current
    DESCRIPTION
        "Phase C current, in amps. This is calculated using the formula
        (register * CT ratio * 0.001)."
    ::= { acpmStatusEntry 21 }
    --1.3.6.1.4.1.3052.10.1.8.1.1.21

acpmsAvgFreqValueStr OBJECT-TYPE
    SYNTAX DisplayString
    MAX-ACCESS read-only
    STATUS current
    DESCRIPTION
        "Frequency, in hertz. On the YD2010, this is calculated using the
        formula (register * 0.00106813). On the WattsOn, this is calculated
        using the formula (register * 0.1)."
    ::= { acpmStatusEntry 22 }
    --1.3.6.1.4.1.3052.10.1.8.1.1.22

acpmsAvgFreqMinStr OBJECT-TYPE
    SYNTAX DisplayString
    MAX-ACCESS read-only
    STATUS current
    DESCRIPTION
        "Minimum frequency value since last reset, in hertz."
    ::= { acpmStatusEntry 23 }
    --1.3.6.1.4.1.3052.10.1.8.1.1.23

acpmsAvgFreqMaxStr OBJECT-TYPE
    SYNTAX DisplayString
    MAX-ACCESS read-only
    STATUS current
    DESCRIPTION
        "Maximum frequency value since last reset, in hertz."
    ::= { acpmStatusEntry 24 }
    --1.3.6.1.4.1.3052.10.1.8.1.1.24

acpmsAvgFreqAvgStr OBJECT-TYPE
    SYNTAX DisplayString
    MAX-ACCESS read-only
    STATUS current
    DESCRIPTION
        "Average frequency value since last reset, in hertz.  This is the
        unit's average of its measurements of the average frequency reported
        by the AC power monitor device."
    ::= { acpmStatusEntry 25 }
    --1.3.6.1.4.1.3052.10.1.8.1.1.25

acpmsAvgFreqInEventState OBJECT-TYPE
    SYNTAX DisplayString
    MAX-ACCESS read-only
    STATUS current
    DESCRIPTION
        "Event state of this AC power monitor frequency (Low, Normal, High, etc.)."
    ::= { acpmStatusEntry 26 }
    --1.3.6.1.4.1.3052.10.1.8.1.1.26

acpmsTRPValueStr OBJECT-TYPE
    SYNTAX DisplayString
    MAX-ACCESS read-only
    STATUS current
    DESCRIPTION
        "Total real power, in watts. On the YD2010, this is calculated using
        the formula (register * PT ratio * CT ratio * Urg * 0.4), where Urg is
        the voltage range taken from register 0x30A. On the WattsOn models,
        this is calculated using the formula (register * PT * CT)."
    ::= { acpmStatusEntry 27 }
    --1.3.6.1.4.1.3052.10.1.8.1.1.27

acpmsTRPMinStr OBJECT-TYPE
    SYNTAX DisplayString
    MAX-ACCESS read-only
    STATUS current
    DESCRIPTION
        "Minimum total real power value since last reset, in watts."
    ::= { acpmStatusEntry 28 }
    --1.3.6.1.4.1.3052.10.1.8.1.1.28

acpmsTRPMaxStr OBJECT-TYPE
    SYNTAX DisplayString
    MAX-ACCESS read-only
    STATUS current
    DESCRIPTION
        "Maximum total real power value since last reset, in watts."
    ::= { acpmStatusEntry 29 }
    --1.3.6.1.4.1.3052.10.1.8.1.1.29

acpmsTRPAvgStr OBJECT-TYPE
    SYNTAX DisplayString
    MAX-ACCESS read-only
    STATUS current
    DESCRIPTION
        "Average total real power value since last reset, in watts.  This is
        the unit's average of its measurements of the average total real power
        reported by the AC power monitor device."
    ::= { acpmStatusEntry 30 }
    --1.3.6.1.4.1.3052.10.1.8.1.1.30

acpmsTRPInEventState OBJECT-TYPE
    SYNTAX DisplayString
    MAX-ACCESS read-only
    STATUS current
    DESCRIPTION
        "Event state of this AC power monitor total real power (Low, Normal,
        High, etc.)."
    ::= { acpmStatusEntry 31 }
    --1.3.6.1.4.1.3052.10.1.8.1.1.31

acpmsRPPhaseAValueStr OBJECT-TYPE
    SYNTAX DisplayString
    MAX-ACCESS read-only
    STATUS current
    DESCRIPTION
        "Phase A real power, in watts. On the YD2010, this is calculated using
        the formula (register * PT ratio * CT ratio * Urg * 0.4), where Urg is
        the voltage range taken from register 0x30A. On the WattsOn, this is
        calculated using the formula (register * PT * CT)."
    ::= { acpmStatusEntry 32 }
    --1.3.6.1.4.1.3052.10.1.8.1.1.32

acpmsRPPhaseBValueStr OBJECT-TYPE
    SYNTAX DisplayString
    MAX-ACCESS read-only
    STATUS current
    DESCRIPTION
        "Phase B real power, in watts. On the YD2010, this is calculated using
        the formula (register * PT ratio * CT ratio * Urg * 0.4), where Urg is
        the voltage range taken from register 0x30A. On the WattsOn, this is
        calculated using the formula (register * PT * CT)."
    ::= { acpmStatusEntry 33 }
    --1.3.6.1.4.1.3052.10.1.8.1.1.33

acpmsRPPhaseCValueStr OBJECT-TYPE
    SYNTAX DisplayString
    MAX-ACCESS read-only
    STATUS current
    DESCRIPTION
        "Phase C real power, in watts. On the YD2010, this is calculated using
        the formula (register * PT ratio * CT ratio * Urg * 0.4), where Urg is
        the voltage range taken from register 0x30A. On the WattsOn, this is
        calculated using the formula (register * PT * CT)."
    ::= { acpmStatusEntry 34 }
    --1.3.6.1.4.1.3052.10.1.8.1.1.34

acpmsCombined OBJECT-TYPE
    SYNTAX DisplayString
    MAX-ACCESS read-only
    STATUS current
    DESCRIPTION
        "Combined status string intended to be parsed by NMS:
        name`deviceState`deviceStateColorCode`voltage`current`frequency`power~voltageEventState`voltageColorCode`currentEventState`currentColorCode`frequencyEventState`freuencyColorCode`powerEventState`powerColorCode"
    ::= { acpmStatusEntry 35 }
    --1.3.6.1.4.1.3052.10.1.8.1.1.35

acpmsTPFValueStr OBJECT-TYPE
    SYNTAX DisplayString
    MAX-ACCESS read-only
    STATUS current
    DESCRIPTION
        "Total power factor."
    ::= { acpmStatusEntry 36 }
    --1.3.6.1.4.1.3052.10.1.8.1.1.36

acpmsTPFMinStr OBJECT-TYPE
    SYNTAX DisplayString
    MAX-ACCESS read-only
    STATUS current
    DESCRIPTION
        "Total power factor minimum value since last reset."
    ::= { acpmStatusEntry 37 }
    --1.3.6.1.4.1.3052.10.1.8.1.1.37

acpmsTPFMaxStr OBJECT-TYPE
    SYNTAX DisplayString
    MAX-ACCESS read-only
    STATUS current
    DESCRIPTION
        "Total power factor maximum value since last reset."
    ::= { acpmStatusEntry 38 }
    --1.3.6.1.4.1.3052.10.1.8.1.1.38

acpmsTPFAvgStr OBJECT-TYPE
    SYNTAX DisplayString
    MAX-ACCESS read-only
    STATUS current
    DESCRIPTION
        "Total power factor average value since last reset."
    ::= { acpmStatusEntry 39 }
    --1.3.6.1.4.1.3052.10.1.8.1.1.39

acpmsTPFInEventState OBJECT-TYPE
    SYNTAX DisplayString
    MAX-ACCESS read-only
    STATUS current
    DESCRIPTION
        "Total power factor event state."
    ::= { acpmStatusEntry 40 }
    --1.3.6.1.4.1.3052.10.1.8.1.1.40

acpmsPFPhaseAValueStr OBJECT-TYPE
    SYNTAX DisplayString
    MAX-ACCESS read-only
    STATUS current
    DESCRIPTION
        "Phase A power factor."
    ::= { acpmStatusEntry 41 }
    --1.3.6.1.4.1.3052.10.1.8.1.1.41

acpmsPFPhaseBValueStr OBJECT-TYPE
    SYNTAX DisplayString
    MAX-ACCESS read-only
    STATUS current
    DESCRIPTION
        "Phase B power factor."
    ::= { acpmStatusEntry 42 }
    --1.3.6.1.4.1.3052.10.1.8.1.1.42

acpmsPFPhaseCValueStr OBJECT-TYPE
    SYNTAX DisplayString
    MAX-ACCESS read-only
    STATUS current
    DESCRIPTION
        "Phase C power factor."
    ::= { acpmStatusEntry 43 }
    --1.3.6.1.4.1.3052.10.1.8.1.1.43

acpmsTRcPValueStr OBJECT-TYPE
    SYNTAX DisplayString
    MAX-ACCESS read-only
    STATUS current
    DESCRIPTION
        "Total reactive power, in VAR."
    ::= { acpmStatusEntry 44 }
    --1.3.6.1.4.1.3052.10.1.8.1.1.44

acpmsTRcPMinStr OBJECT-TYPE
    SYNTAX DisplayString
    MAX-ACCESS read-only
    STATUS current
    DESCRIPTION
        "Total reactive power minimum value since last reset, in VAR."
    ::= { acpmStatusEntry 45 }
    --1.3.6.1.4.1.3052.10.1.8.1.1.45

acpmsTRcPMaxStr OBJECT-TYPE
    SYNTAX DisplayString
    MAX-ACCESS read-only
    STATUS current
    DESCRIPTION
        "Total reactive power maximum value since last reset, in VAR."
    ::= { acpmStatusEntry 46 }
    --1.3.6.1.4.1.3052.10.1.8.1.1.46

acpmsTRcPAvgStr OBJECT-TYPE
    SYNTAX DisplayString
    MAX-ACCESS read-only
    STATUS current
    DESCRIPTION
        "Total reactive power average value since last reset, in VAR."
    ::= { acpmStatusEntry 47 }
    --1.3.6.1.4.1.3052.10.1.8.1.1.47

acpmsRcPPhaseAValueStr OBJECT-TYPE
    SYNTAX DisplayString
    MAX-ACCESS read-only
    STATUS current
    DESCRIPTION
        "Phase A reactive power, in VAR."
    ::= { acpmStatusEntry 48 }
    --1.3.6.1.4.1.3052.10.1.8.1.1.48

acpmsRcPPhaseBValueStr OBJECT-TYPE
    SYNTAX DisplayString
    MAX-ACCESS read-only
    STATUS current
    DESCRIPTION
        "Phase B reactive power, in VAR."
    ::= { acpmStatusEntry 49 }
    --1.3.6.1.4.1.3052.10.1.8.1.1.49

acpmsRcPPhaseCValueStr OBJECT-TYPE
    SYNTAX DisplayString
    MAX-ACCESS read-only
    STATUS current
    DESCRIPTION
        "Phase C reactive power, in VAR."
    ::= { acpmStatusEntry 50 }
    --1.3.6.1.4.1.3052.10.1.8.1.1.50

acpmsTAPValueStr OBJECT-TYPE
    SYNTAX DisplayString
    MAX-ACCESS read-only
    STATUS current
    DESCRIPTION
        "Total apparent power, in VA."
    ::= { acpmStatusEntry 51 }
    --1.3.6.1.4.1.3052.10.1.8.1.1.51

acpmsTAPMinStr OBJECT-TYPE
    SYNTAX DisplayString
    MAX-ACCESS read-only
    STATUS current
    DESCRIPTION
        "Total apparent power minimum value since last reset, in VA."
    ::= { acpmStatusEntry 52 }
    --1.3.6.1.4.1.3052.10.1.8.1.1.52

acpmsTAPMaxStr OBJECT-TYPE
    SYNTAX DisplayString
    MAX-ACCESS read-only
    STATUS current
    DESCRIPTION
        "Total apparent power maximum value since last reset, in VA."
    ::= { acpmStatusEntry 53 }
    --1.3.6.1.4.1.3052.10.1.8.1.1.53

acpmsTAPAvgStr OBJECT-TYPE
    SYNTAX DisplayString
    MAX-ACCESS read-only
    STATUS current
    DESCRIPTION
        "Total apparent power average value since last reset, in VA."
    ::= { acpmStatusEntry 54 }
    --1.3.6.1.4.1.3052.10.1.8.1.1.54

acpmsAPPhaseAValueStr OBJECT-TYPE
    SYNTAX DisplayString
    MAX-ACCESS read-only
    STATUS current
    DESCRIPTION
        "Phase A apparent power, in VA."
    ::= { acpmStatusEntry 55 }
    --1.3.6.1.4.1.3052.10.1.8.1.1.55

acpmsAPPhaseBValueStr OBJECT-TYPE
    SYNTAX DisplayString
    MAX-ACCESS read-only
    STATUS current
    DESCRIPTION
        "Phase B apparent power, in VA."
    ::= { acpmStatusEntry 56 }
    --1.3.6.1.4.1.3052.10.1.8.1.1.56

acpmsAPPhaseCValueStr OBJECT-TYPE
    SYNTAX DisplayString
    MAX-ACCESS read-only
    STATUS current
    DESCRIPTION
        "Phase C apparent power, in VA."
    ::= { acpmStatusEntry 57 }
    --1.3.6.1.4.1.3052.10.1.8.1.1.57

acpmsTotalEnergyWh OBJECT-TYPE
    SYNTAX Integer32
    MAX-ACCESS read-only
    STATUS current
    DESCRIPTION
        "Total energy, in Wh."
    ::= { acpmStatusEntry 58 }
    --1.3.6.1.4.1.3052.10.1.8.1.1.58

acpmsTotalEnergyVAR OBJECT-TYPE
    SYNTAX Integer32
    MAX-ACCESS read-only
    STATUS current
    DESCRIPTION
        "Total reactive energy, in VAR."
    ::= { acpmStatusEntry 59 }
    --1.3.6.1.4.1.3052.10.1.8.1.1.59

acpmsTotalEnergyVA OBJECT-TYPE
    SYNTAX Integer32
    MAX-ACCESS read-only
    STATUS current
    DESCRIPTION
        "Total apparent energy, in VA."
    ::= { acpmStatusEntry 60 }
    --1.3.6.1.4.1.3052.10.1.8.1.1.60

acmpsAvgVoltageAlarmDatetime OBJECT-TYPE
    SYNTAX DisplayString
    MAX-ACCESS read-only
    STATUS current
    DESCRIPTION
        "The time of the last Average Voltage alarm
        triggerred in the AC monitor
        MM/DD/YY HH:MM:SS format.

        The possible events are High, Very High, 
        Low, and Very Low.

        For outputs, this object is a null string."
    ::= { acpmStatusEntry 61 }
    --1.3.6.1.4.1.3052.10.1.8.1.1.61
    
acmpsAvgCurrentAlarmDatetime OBJECT-TYPE
    SYNTAX DisplayString
    MAX-ACCESS read-only
    STATUS current
    DESCRIPTION
        "The time of the last Average Current alarm
        triggerred in the AC monitor
        MM/DD/YY HH:MM:SS format.

        The possible events are High, Very High, 
        Low, and Very Low.

        For outputs, this object is a null string."
    ::= { acpmStatusEntry 62 }
    --1.3.6.1.4.1.3052.10.1.8.1.1.62
    
acmpsFreqAlarmDatetime OBJECT-TYPE
    SYNTAX DisplayString
    MAX-ACCESS read-only
    STATUS current
    DESCRIPTION
        "The time of the last Frequency alarm
        triggerred in the AC monitor
        MM/DD/YY HH:MM:SS format.

        The possible events are High, Very High, 
        Low, and Very Low.

        For outputs, this object is a null string."
    ::= { acpmStatusEntry 63 }
    --1.3.6.1.4.1.3052.10.1.8.1.1.63

acmpsRealPowerAlarmDatetime OBJECT-TYPE
    SYNTAX DisplayString
    MAX-ACCESS read-only
    STATUS current
    DESCRIPTION
        "The time of the last Real Power alarm
        triggerred in the AC monitor
        MM/DD/YY HH:MM:SS format.

        The possible events are High, Very High, 
        Low, and Very Low.

        For outputs, this object is a null string."
    ::= { acpmStatusEntry 64 }
    --1.3.6.1.4.1.3052.10.1.8.1.1.64
    
acmpsPowerFactorAlarmDatetime OBJECT-TYPE
    SYNTAX DisplayString
    MAX-ACCESS read-only
    STATUS current
    DESCRIPTION
        "The time of the last Power Factor alarm
        triggerred in the AC monitor
        MM/DD/YY HH:MM:SS format.

        The possible events are Low, and Very Low.

        For outputs, this object is a null string."
    ::= { acpmStatusEntry 65 }
    --1.3.6.1.4.1.3052.10.1.8.1.1.66








































--***************************************************************************************
--HVAC Status Section 1.11
--***************************************************************************************
--***************************************************************************************
--Asentria HVAC Status Section 1.11.2
--***************************************************************************************

evHVACStatusBardSystem1Stage1Cooling OBJECT-TYPE
    SYNTAX DisplayString
    MAX-ACCESS read-only
    STATUS current
    DESCRIPTION
        "Bard HVAC: System 1 stage 1 cooling status."
    ::= { evHVACStatusBardSystem1Stage1 1 }
    --1.3.6.1.4.1.3052.10.1.11.2.1.1.1

evHVACStatusBardSystem1Stage2Cooling OBJECT-TYPE
    SYNTAX DisplayString
    MAX-ACCESS read-only
    STATUS current
    DESCRIPTION
        "Bard HVAC: System 1 stage 2 cooling status."
    ::= { evHVACStatusBardSystem1Stage2 1 }
    --1.3.6.1.4.1.3052.10.1.11.2.1.2.1

evHVACStatusBardSystem1Blower OBJECT-TYPE
    SYNTAX DisplayString
    MAX-ACCESS read-only
    STATUS current
    DESCRIPTION
        "Bard HVAC: System 1 blower status."
    ::= { evHVACStatusBardSystem1 3 }
    --1.3.6.1.4.1.3052.10.1.11.2.1.3

evHVACStatusBardSystem1Heating OBJECT-TYPE
    SYNTAX DisplayString
    MAX-ACCESS read-only
    STATUS current
    DESCRIPTION
        "Bard HVAC: System 1 heating status."
    ::= { evHVACStatusBardSystem1 4 }
    --1.3.6.1.4.1.3052.10.1.11.2.1.4

evHVACStatusBardSystem1Economizer OBJECT-TYPE
    SYNTAX DisplayString
    MAX-ACCESS read-only
    STATUS current
    DESCRIPTION
        "Bard HVAC: System 1 heating status."
    ::= { evHVACStatusBardSystem1 5 }
    --1.3.6.1.4.1.3052.10.1.11.2.1.5

evHVACStatusBardSystem2Stage1Cooling OBJECT-TYPE
    SYNTAX DisplayString
    MAX-ACCESS read-only
    STATUS current
    DESCRIPTION
        "Bard HVAC: System 2 stage 1 cooling status."
    ::= { evHVACStatusBardSystem2Stage1 1 }
    --1.3.6.1.4.1.3052.10.1.11.2.2.1.1

evHVACStatusBardSystem2Stage2Cooling OBJECT-TYPE
    SYNTAX DisplayString
    MAX-ACCESS read-only
    STATUS current
    DESCRIPTION
        "Bard HVAC: System 2 stage 2 cooling status."
    ::= { evHVACStatusBardSystem2Stage2 1 }
    --1.3.6.1.4.1.3052.10.1.11.2.2.2.1

evHVACStatusBardSystem2Blower OBJECT-TYPE
    SYNTAX DisplayString
    MAX-ACCESS read-only
    STATUS current
    DESCRIPTION
        "Bard HVAC: System 2 blower status."
    ::= { evHVACStatusBardSystem2 3 }
    --1.3.6.1.4.1.3052.10.1.11.2.2.3

evHVACStatusBardSystem2Heating OBJECT-TYPE
    SYNTAX DisplayString
    MAX-ACCESS read-only
    STATUS current
    DESCRIPTION
        "Bard HVAC: System 2 heating status."
    ::= { evHVACStatusBardSystem2 4 }
    --1.3.6.1.4.1.3052.10.1.11.2.2.4

evHVACStatusBardSystem2Economizer OBJECT-TYPE
    SYNTAX DisplayString
    MAX-ACCESS read-only
    STATUS current
    DESCRIPTION
        "Bard HVAC: System 2 heating status."
    ::= { evHVACStatusBardSystem2 5 }
    --1.3.6.1.4.1.3052.10.1.11.2.2.5

evHVACStatusBardTempAvg OBJECT-TYPE
    SYNTAX DisplayString
    MAX-ACCESS read-only
    STATUS current
    DESCRIPTION
        "Bard HVAC: Average temperature."
    ::= { evHVACStatusBard 3 }
    --1.3.6.1.4.1.3052.10.1.11.2.3

evHVACStatusBardTempLocal OBJECT-TYPE
    SYNTAX DisplayString
    MAX-ACCESS read-only
    STATUS current
    DESCRIPTION
        "Bard HVAC: Local temperature."
    ::= { evHVACStatusBard 4 }
    --1.3.6.1.4.1.3052.10.1.11.2.4

evHVACStatusBardTempRemote1 OBJECT-TYPE
    SYNTAX DisplayString
    MAX-ACCESS read-only
    STATUS current
    DESCRIPTION
        "Bard HVAC: Remote 1 temperature."
    ::= { evHVACStatusBardTempRemote 1 }
    --1.3.6.1.4.1.3052.10.1.11.2.5.1

evHVACStatusBardTempRemote2 OBJECT-TYPE
    SYNTAX DisplayString
    MAX-ACCESS read-only
    STATUS current
    DESCRIPTION
        "Bard HVAC: Remote 2 temperature."
    ::= { evHVACStatusBardTempRemote 2 }
    --1.3.6.1.4.1.3052.10.1.11.2.5.2

evHVACStatusBardDehumidification OBJECT-TYPE
    SYNTAX DisplayString
    MAX-ACCESS read-only
    STATUS current
    DESCRIPTION
        "Bard HVAC: Dehumidification status."
    ::= { evHVACStatusBard 6 }
    --1.3.6.1.4.1.3052.10.1.11.2.6

evHVACStatusBardLEDsCooling1 OBJECT-TYPE
    SYNTAX DisplayString
    MAX-ACCESS read-only
    STATUS current
    DESCRIPTION
        "Bard HVAC: Cooling LED 1."
    ::= { evHVACStatusBardLEDsCooling 1 }
    --1.3.6.1.4.1.3052.10.1.11.2.7.1.1

evHVACStatusBardLEDsCooling2 OBJECT-TYPE
    SYNTAX DisplayString
    MAX-ACCESS read-only
    STATUS current
    DESCRIPTION
        "Bard HVAC: Cooling LED 2."
    ::= { evHVACStatusBardLEDsCooling 2 }
    --1.3.6.1.4.1.3052.10.1.11.2.7.1.2

evHVACStatusBardLEDsCooling3 OBJECT-TYPE
    SYNTAX DisplayString
    MAX-ACCESS read-only
    STATUS current
    DESCRIPTION
        "Bard HVAC: Cooling LED 3."
    ::= { evHVACStatusBardLEDsCooling 3 }
    --1.3.6.1.4.1.3052.10.1.11.2.7.1.3

evHVACStatusBardLEDsCooling4 OBJECT-TYPE
    SYNTAX DisplayString
    MAX-ACCESS read-only
    STATUS current
    DESCRIPTION
        "Bard HVAC: Cooling LED 4."
    ::= { evHVACStatusBardLEDsCooling 4 }
    --1.3.6.1.4.1.3052.10.1.11.2.7.1.4

evHVACStatusBardLEDsHeating1 OBJECT-TYPE
    SYNTAX DisplayString
    MAX-ACCESS read-only
    STATUS current
    DESCRIPTION
        "Bard HVAC: Heating LED 1."
    ::= { evHVACStatusBardLEDsHeating 1 }
    --1.3.6.1.4.1.3052.10.1.11.2.7.2.1

evHVACStatusBardLEDsHeating2 OBJECT-TYPE
    SYNTAX DisplayString
    MAX-ACCESS read-only
    STATUS current
    DESCRIPTION
        "Bard HVAC: Heating LED 2."
    ::= { evHVACStatusBardLEDsHeating 2 }
    --1.3.6.1.4.1.3052.10.1.11.2.7.2.2

evHVACStatusBardLEDsHeating3 OBJECT-TYPE
    SYNTAX DisplayString
    MAX-ACCESS read-only
    STATUS current
    DESCRIPTION
        "Bard HVAC: Heating LED 3."
    ::= { evHVACStatusBardLEDsHeating 3 }
    --1.3.6.1.4.1.3052.10.1.11.2.7.2.3

evHVACStatusBardLEDsHeating4 OBJECT-TYPE
    SYNTAX DisplayString
    MAX-ACCESS read-only
    STATUS current
    DESCRIPTION
        "Bard HVAC: Heating LED 4."
    ::= { evHVACStatusBardLEDsHeating 4 }
    --1.3.6.1.4.1.3052.10.1.11.2.7.2.4

evHVACStatusBardLEDsDeHumid1 OBJECT-TYPE
    SYNTAX DisplayString
    MAX-ACCESS read-only
    STATUS current
    DESCRIPTION
        "Bard HVAC: Dehumidification LED 1."
    ::= { evHVACStatusBardLEDsDeHumid 1 }
    --1.3.6.1.4.1.3052.10.1.11.2.7.3.1

evHVACStatusBardGenerator OBJECT-TYPE
    SYNTAX DisplayString
    MAX-ACCESS read-only
    STATUS current
    DESCRIPTION
        "Bard HVAC: Backup generator status."
    ::= { evHVACStatusBard 7 }
    --1.3.6.1.4.1.3052.10.1.11.2.8

evHVACStatusBardAlarmBoardState OBJECT-TYPE
    SYNTAX DisplayString
    MAX-ACCESS read-only
    STATUS current
    DESCRIPTION
        "Bard HVAC: Alarm board state."
    ::= { evHVACStatusBard 8 }
    --1.3.6.1.4.1.3052.10.1.11.2.9

evHVACStatusBardASSystem1PowerLoss OBJECT-TYPE
    SYNTAX DisplayString
    MAX-ACCESS read-only
    STATUS current
    DESCRIPTION
        "Bard HVAC Alarm Status: System 1 power loss."
    ::= { evHVACStatusBardASSystem1 1 }
    --1.3.6.1.4.1.3052.10.1.11.2.10.1.1

evHVACStatusBardASSystem1Lockout OBJECT-TYPE
    SYNTAX DisplayString
    MAX-ACCESS read-only
    STATUS current
    DESCRIPTION
        "Bard HVAC Alarm Status: System 1 ref. lockout."
    ::= { evHVACStatusBardASSystem1 2 }
    --1.3.6.1.4.1.3052.10.1.11.2.10.1.2

evHVACStatusBardASSystem2PowerLoss OBJECT-TYPE
    SYNTAX DisplayString
    MAX-ACCESS read-only
    STATUS current
    DESCRIPTION
        "Bard HVAC Alarm Status: System 2 power loss."
    ::= { evHVACStatusBardASSystem2 1 }
    --1.3.6.1.4.1.3052.10.1.11.2.10.2.1

evHVACStatusBardASSystem2Lockout OBJECT-TYPE
    SYNTAX DisplayString
    MAX-ACCESS read-only
    STATUS current
    DESCRIPTION
        "Bard HVAC Alarm Status: System 2 ref. lockout."
    ::= { evHVACStatusBardASSystem2 2 }
    --1.3.6.1.4.1.3052.10.1.11.2.10.2.2

evHVACStatusBardASFire OBJECT-TYPE
    SYNTAX DisplayString
    MAX-ACCESS read-only
    STATUS current
    DESCRIPTION
        "Bard HVAC Alarm Status: Fire / smoke."
    ::= { evHVACStatusBardAlarmStatus 3 }
    --1.3.6.1.4.1.3052.10.1.11.2.10.3

evHVACStatusBardASTempLowAlarm OBJECT-TYPE
    SYNTAX DisplayString
    MAX-ACCESS read-only
    STATUS current
    DESCRIPTION
        "Bard HVAC Alarm Status: Low temperature."
    ::= { evHVACStatusBardASTemp 1 }
    --1.3.6.1.4.1.3052.10.1.11.2.10.4.1

evHVACStatusBardASTempHighAlarm OBJECT-TYPE
    SYNTAX DisplayString
    MAX-ACCESS read-only
    STATUS current
    DESCRIPTION
        "Bard HVAC Alarm Status: High temperature."
    ::= { evHVACStatusBardASTemp 2 }
    --1.3.6.1.4.1.3052.10.1.11.2.10.4.2

evHVACStatusBardASTempVHighAlarm OBJECT-TYPE
    SYNTAX DisplayString
    MAX-ACCESS read-only
    STATUS current
    DESCRIPTION
        "Bard HVAC Alarm Status: Very high temperature."
    ::= { evHVACStatusBardASTemp 3 }
    --1.3.6.1.4.1.3052.10.1.11.2.10.4.3

evHVACStatusBardASFailure OBJECT-TYPE
    SYNTAX DisplayString
    MAX-ACCESS read-only
    STATUS current
    DESCRIPTION
        "Bard HVAC Alarm Status: Controller failure."
    ::= { evHVACStatusBardAlarmStatus 5 }
    --1.3.6.1.4.1.3052.10.1.11.2.10.5

evHVACStatusBardConnState OBJECT-TYPE
    SYNTAX Integer32
    MAX-ACCESS read-only
    STATUS current
    DESCRIPTION
        "Connectivity state: 1 means unit has good connectivity to the
        Bard HVAC controller, 0 otherwise."
    ::= { evHVACStatusBard 11 }
    --1.3.6.1.4.1.3052.10.1.11.2.11

--***************************************************************************************
--Asentria HVAC Status Section 1.11.3
--***************************************************************************************

evHVACStatusAsentriaSequenceTable OBJECT-TYPE
    SYNTAX SEQUENCE OF HVACStatusAsentriaSequence
    MAX-ACCESS not-accessible
    STATUS current
    DESCRIPTION
        "Asentria HVAC sequence status table"
    ::= { evHVACStatusAsentria 1 }
    --1.3.6.1.4.1.3052.10.1.11.3.1

evHVACStatusAsentriaSequenceEntry OBJECT-TYPE
    SYNTAX HVACStatusAsentriaSequence
    MAX-ACCESS not-accessible
    STATUS current
    DESCRIPTION
        "Asentria HVAC sequence status table entry"
    INDEX { evHVACStatusAsentriaSequenceIndex }
    ::= { evHVACStatusAsentriaSequenceTable 1 }
    --1.3.6.1.4.1.3052.10.1.11.3.1.1

evHVACStatusAsentriaSequenceIndex OBJECT-TYPE
    SYNTAX Integer32 (1..2)
    MAX-ACCESS read-only
    STATUS current
    DESCRIPTION
        "Index for Asentria HVAC sequence"
    ::= { evHVACStatusAsentriaSequenceEntry 1 }
    --1.3.6.1.4.1.3052.10.1.11.3.1.1.1

evHVACStatusAsentriaSeqVentTime OBJECT-TYPE
    SYNTAX DisplayString
    MAX-ACCESS read-only
    STATUS current
    DESCRIPTION
        "Asentria HVAC sequence time spent venting"
    ::= { evHVACStatusAsentriaSequenceEntry 2 }
    --1.3.6.1.4.1.3052.10.1.11.3.1.1.2

evHVACStatusAsentriaSeqCoolTime OBJECT-TYPE
    SYNTAX DisplayString
    MAX-ACCESS read-only
    STATUS current
    DESCRIPTION
        "Asentria HVAC sequence time spent cooling"
    ::= { evHVACStatusAsentriaSequenceEntry 3 }
    --1.3.6.1.4.1.3052.10.1.11.3.1.1.3

evHVACStatusAsentriaSeqHeatTime OBJECT-TYPE
    SYNTAX DisplayString
    MAX-ACCESS read-only
    STATUS current
    DESCRIPTION
        "Asentria HVAC sequence time spent heating"
    ::= { evHVACStatusAsentriaSequenceEntry 4 }
    --1.3.6.1.4.1.3052.10.1.11.3.1.1.4

evHVACStatusAsentriaSeqIdleTime OBJECT-TYPE
    SYNTAX DisplayString
    MAX-ACCESS read-only
    STATUS current
    DESCRIPTION
        "Asentria HVAC sequence time spent idling"
    ::= { evHVACStatusAsentriaSequenceEntry 5 }
    --1.3.6.1.4.1.3052.10.1.11.3.1.1.5

evHVACStatusAsentriaUnitTable OBJECT-TYPE
    SYNTAX SEQUENCE OF HVACStatusAsentriaUnit
    MAX-ACCESS not-accessible
    STATUS current
    DESCRIPTION
        "Asentria HVAC unit status table"
    ::= { evHVACStatusAsentria 2 }
    --1.3.6.1.4.1.3052.10.1.11.3.2

evHVACStatusAsentriaUnitEntry OBJECT-TYPE
    SYNTAX HVACStatusAsentriaUnit
    MAX-ACCESS not-accessible
    STATUS current
    DESCRIPTION
        "Asentria HVAC unit status table entry"
    INDEX { evHVACStatusAsentriaUnitIndex }
    ::= { evHVACStatusAsentriaUnitTable 1 }
    --1.3.6.1.4.1.3052.10.1.11.3.2.1

evHVACStatusAsentriaUnitIndex OBJECT-TYPE
    SYNTAX Integer32 (1..2)
    MAX-ACCESS read-only
    STATUS current
    DESCRIPTION
        "Index for Asentria HVAC unit"
    ::= { evHVACStatusAsentriaUnitEntry 1 }
    --1.3.6.1.4.1.3052.10.1.11.3.2.1.1

evHVACStatusAsentriaUnitState OBJECT-TYPE
    SYNTAX DisplayString
    MAX-ACCESS read-only
    STATUS current
    DESCRIPTION
        "Asentria HVAC unit status"
    ::= { evHVACStatusAsentriaUnitEntry 2 }
    --1.3.6.1.4.1.3052.10.1.11.3.2.1.2

evHVACStatusAsentriaUnitVentTime OBJECT-TYPE
    SYNTAX DisplayString
    MAX-ACCESS read-only
    STATUS current
    DESCRIPTION
        "Asentria HVAC unit time spent venting"
    ::= { evHVACStatusAsentriaUnitEntry 3 }
    --1.3.6.1.4.1.3052.10.1.11.3.2.1.3

evHVACStatusAsentriaUnitCoolTime OBJECT-TYPE
    SYNTAX DisplayString
    MAX-ACCESS read-only
    STATUS current
    DESCRIPTION
        "Asentria HVAC unit time spent cooling"
    ::= { evHVACStatusAsentriaUnitEntry 4 }
    --1.3.6.1.4.1.3052.10.1.11.3.2.1.4

evHVACStatusAsentriaUnitHeatTime OBJECT-TYPE
    SYNTAX DisplayString
    MAX-ACCESS read-only
    STATUS current
    DESCRIPTION
        "Asentria HVAC unit time spent heating"
    ::= { evHVACStatusAsentriaUnitEntry 5 }
    --1.3.6.1.4.1.3052.10.1.11.3.2.1.5

evHVACStatusAsentriaUnitIdleTime OBJECT-TYPE
    SYNTAX DisplayString
    MAX-ACCESS read-only
    STATUS current
    DESCRIPTION
        "Asentria HVAC unit time spent idling"
    ::= { evHVACStatusAsentriaUnitEntry 6 }
    --1.3.6.1.4.1.3052.10.1.11.3.2.1.6

evHVACStatusAsentriaBackupEvent OBJECT-TYPE
    SYNTAX DisplayString
    MAX-ACCESS read-only
    STATUS current
    DESCRIPTION
        "Asentria HVAC backup event"
    ::= { evHVACStatusAsentria 3 }
    --1.3.6.1.4.1.3052.10.1.11.3.3

evHVACStatusAsentriaFireEvent OBJECT-TYPE
    SYNTAX DisplayString
    MAX-ACCESS read-only
    STATUS current
    DESCRIPTION
        "Asentria HVAC smoke/fire event"
    ::= { evHVACStatusAsentria 4 }
    --1.3.6.1.4.1.3052.10.1.11.3.4

evHVACStatusAsentriaTempOut OBJECT-TYPE
    SYNTAX DisplayString
    MAX-ACCESS read-only
    STATUS current
    DESCRIPTION
        "Asentria HVAC temperature outside"
    ::= { evHVACStatusAsentriaTemp 1 }
    --1.3.6.1.4.1.3052.10.1.11.3.5.1

evHVACStatusAsentriaTempIn OBJECT-TYPE
    SYNTAX DisplayString
    MAX-ACCESS read-only
    STATUS current
    DESCRIPTION
        "Asentria HVAC temperature inside"
    ::= { evHVACStatusAsentriaTemp 2 }
    --1.3.6.1.4.1.3052.10.1.11.3.5.2
    
evHVACStatusAsentriaHumidOut OBJECT-TYPE
    SYNTAX DisplayString
    MAX-ACCESS read-only
    STATUS current
    DESCRIPTION
        "Asentria HVAC humidity outside"
    ::= { evHVACStatusAsentriaHumid 1 }
    --1.3.6.1.4.1.3052.10.1.11.3.6.1

evHVACStatusAsentriaHumidIn OBJECT-TYPE
    SYNTAX DisplayString
    MAX-ACCESS read-only
    STATUS current
    DESCRIPTION
        "Asentria HVAC humidity inside"
    ::= { evHVACStatusAsentriaHumid 2 }
    --1.3.6.1.4.1.3052.10.1.11.3.6.2


--***************************************************************************************
--Airsys HVAC Status Section 1.11.4
--***************************************************************************************

evHVACStatusAirsysAlarmUnitTable OBJECT-TYPE
    SYNTAX SEQUENCE OF HVACStatusAirsysAlarmUnit
    MAX-ACCESS not-accessible
    STATUS current
    DESCRIPTION
        "Airsys HVAC unit alarm status table"
    ::= { evHVACStatusAirsysAlarm 1 }
    --1.3.6.1.4.1.3052.10.1.11.4.1.1

evHVACStatusAirsysAlarmUnitEntry OBJECT-TYPE
    SYNTAX HVACStatusAirsysAlarmUnit
    MAX-ACCESS not-accessible
    STATUS current
    DESCRIPTION
        "Airsys HVAC unit alarm status table entry"
    INDEX { evHVACStatusAirsysAlarmUnitIndex }
    ::= { evHVACStatusAirsysAlarmUnitTable 1 }
    --1.3.6.1.4.1.3052.10.1.11.4.1.1.1

evHVACStatusAirsysAlarmUnitIndex OBJECT-TYPE
    SYNTAX Integer32 (1..2)
    MAX-ACCESS read-only
    STATUS current
    DESCRIPTION
        "Index for Airsys HVAC unit alarms"
    ::= { evHVACStatusAirsysAlarmUnitEntry 1 }
    --1.3.6.1.4.1.3052.10.1.11.4.1.1.1.1

evHVACStatusAirsysAlarmUnitLowPress OBJECT-TYPE
    SYNTAX DisplayString
    MAX-ACCESS read-only
    STATUS current
    DESCRIPTION
        "Airsys HVAC unit low pressure event"
    ::= { evHVACStatusAirsysAlarmUnitEntry 2 }
    --1.3.6.1.4.1.3052.10.1.11.4.1.1.1.2

evHVACStatusAirsysAlarmUnitHighPress OBJECT-TYPE
    SYNTAX DisplayString
    MAX-ACCESS read-only
    STATUS current
    DESCRIPTION
        "Airsys HVAC unit high pressure event"
    ::= { evHVACStatusAirsysAlarmUnitEntry 3 }
    --1.3.6.1.4.1.3052.10.1.11.4.1.1.1.3

evHVACStatusAirsysAlarmUnitEvapFan OBJECT-TYPE
    SYNTAX DisplayString
    MAX-ACCESS read-only
    STATUS current
    DESCRIPTION
        "Airsys HVAC unit AC power/evaporator fan overload event"
    ::= { evHVACStatusAirsysAlarmUnitEntry 4 }
    --1.3.6.1.4.1.3052.10.1.11.4.1.1.1.4

evHVACStatusAirsysAlarmUnitDirty OBJECT-TYPE
    SYNTAX DisplayString
    MAX-ACCESS read-only
    STATUS current
    DESCRIPTION
        "Airsys HVAC unit dirty filter event"
    ::= { evHVACStatusAirsysAlarmUnitEntry 5 }
    --1.3.6.1.4.1.3052.10.1.11.4.1.1.1.5

evHVACStatusAirsysAlarmUnitDamper OBJECT-TYPE
    SYNTAX DisplayString
    MAX-ACCESS read-only
    STATUS current
    DESCRIPTION
        "Airsys HVAC unit damper event"
    ::= { evHVACStatusAirsysAlarmUnitEntry 6 }
    --1.3.6.1.4.1.3052.10.1.11.4.1.1.1.6

evHVACStatusAirsysAlarmUnitSupProbe OBJECT-TYPE
    SYNTAX DisplayString
    MAX-ACCESS read-only
    STATUS current
    DESCRIPTION
        "Airsys HVAC unit supply probe broken event"
    ::= { evHVACStatusAirsysAlarmUnitEntry 7 }
    --1.3.6.1.4.1.3052.10.1.11.4.1.1.1.7

evHVACStatusAirsysAlarmSmokeFire OBJECT-TYPE
    SYNTAX DisplayString
    MAX-ACCESS read-only
    STATUS current
    DESCRIPTION
        "Airsys HVAC smoke/fire event"
    ::= { evHVACStatusAirsysAlarm 2 }
    --1.3.6.1.4.1.3052.10.1.11.4.1.2

evHVACStatusAirsysAlarmLowRoomTemp OBJECT-TYPE
    SYNTAX DisplayString
    MAX-ACCESS read-only
    STATUS current
    DESCRIPTION
        "Airsys HVAC low temperature event"
    ::= { evHVACStatusAirsysAlarm 3 }
    --1.3.6.1.4.1.3052.10.1.11.4.1.3

evHVACStatusAirsysAlarmHighRoomTemp OBJECT-TYPE
    SYNTAX DisplayString
    MAX-ACCESS read-only
    STATUS current
    DESCRIPTION
        "Airsys HVAC high temperature event"
    ::= { evHVACStatusAirsysAlarm 4 }
    --1.3.6.1.4.1.3052.10.1.11.4.1.4

evHVACStatusAirsysAlarmPower OBJECT-TYPE
    SYNTAX DisplayString
    MAX-ACCESS read-only
    STATUS current
    DESCRIPTION
        "Airsys HVAC power failure event"
    ::= { evHVACStatusAirsysAlarm 5 }
    --1.3.6.1.4.1.3052.10.1.11.4.1.5

evHVACStatusAirsysAlarmpLAN OBJECT-TYPE
    SYNTAX DisplayString
    MAX-ACCESS read-only
    STATUS current
    DESCRIPTION
        "Airsys HVAC pLAN event"
    ::= { evHVACStatusAirsysAlarm 6 }
    --1.3.6.1.4.1.3052.10.1.11.4.1.6

evHVACStatusAirsysAlarmClock OBJECT-TYPE
    SYNTAX DisplayString
    MAX-ACCESS read-only
    STATUS current
    DESCRIPTION
        "Airsys HVAC clock card event"
    ::= { evHVACStatusAirsysAlarm 7 }
    --1.3.6.1.4.1.3052.10.1.11.4.1.7

evHVACStatusAirsysAlarmHumidProbe OBJECT-TYPE
    SYNTAX DisplayString
    MAX-ACCESS read-only
    STATUS current
    DESCRIPTION
        "Airsys HVAC humidity probe broken event"
    ::= { evHVACStatusAirsysAlarm 8 }
    --1.3.6.1.4.1.3052.10.1.11.4.1.8

evHVACStatusAirsysAlarmOutProbe OBJECT-TYPE
    SYNTAX DisplayString
    MAX-ACCESS read-only
    STATUS current
    DESCRIPTION
        "Airsys HVAC outdoor probe broken event"
    ::= { evHVACStatusAirsysAlarm 9 }
    --1.3.6.1.4.1.3052.10.1.11.4.1.9

evHVACStatusAirsysAlarmBothCompress OBJECT-TYPE
    SYNTAX DisplayString
    MAX-ACCESS read-only
    STATUS current
    DESCRIPTION
        "Airsys HVAC both compressors running event"
    ::= { evHVACStatusAirsysAlarm 10 }
    --1.3.6.1.4.1.3052.10.1.11.4.1.10

evHVACStatusAirsysAlarmGenerator OBJECT-TYPE
    SYNTAX DisplayString
    MAX-ACCESS read-only
    STATUS current
    DESCRIPTION
        "Airsys HVAC generator running event"
    ::= { evHVACStatusAirsysAlarm 11 }
    --1.3.6.1.4.1.3052.10.1.11.4.1.11

evHVACStatusAirsysAlarmConnection OBJECT-TYPE
    SYNTAX DisplayString
    MAX-ACCESS read-only
    STATUS current
    DESCRIPTION
        "Airsys HVAC controller connection event"
    ::= { evHVACStatusAirsysAlarm 12 }
    --1.3.6.1.4.1.3052.10.1.11.4.1.12

evHVACStatusAirsysAlarmInProbe1 OBJECT-TYPE
    SYNTAX DisplayString
    MAX-ACCESS read-only
    STATUS current
    DESCRIPTION
        "Airsys HVAC indoor probe broken event"
    ::= { evHVACStatusAirsysAlarm 13 }
    --1.3.6.1.4.1.3052.10.1.11.4.1.13

evHVACStatusAirsysAlarmInProbe2 OBJECT-TYPE
    SYNTAX DisplayString
    MAX-ACCESS read-only
    STATUS current
    DESCRIPTION
        "Airsys HVAC backup indoor probe broken event"
    ::= { evHVACStatusAirsysAlarm 14 }
    --1.3.6.1.4.1.3052.10.1.11.4.1.14

evHVACStatusAirsysTempOut OBJECT-TYPE
    SYNTAX DisplayString
    MAX-ACCESS read-only
    STATUS current
    DESCRIPTION
        "Airsys HVAC outdoor temperature"
    ::= { evHVACStatusAirsys 2 }
    --1.3.6.1.4.1.3052.10.1.11.4.2

evHVACStatusAirsysTempIn OBJECT-TYPE
    SYNTAX DisplayString
    MAX-ACCESS read-only
    STATUS current
    DESCRIPTION
        "Airsys HVAC indoor temperature"
    ::= { evHVACStatusAirsys 3 }
    --1.3.6.1.4.1.3052.10.1.11.4.3

evHVACStatusAirsysTempInBackup OBJECT-TYPE
    SYNTAX DisplayString
    MAX-ACCESS read-only
    STATUS current
    DESCRIPTION
        "Airsys HVAC backup indoor temperature"
    ::= { evHVACStatusAirsys 4 }
    --1.3.6.1.4.1.3052.10.1.11.4.4

evHVACStatusAirsysHumidIn OBJECT-TYPE
    SYNTAX DisplayString
    MAX-ACCESS read-only
    STATUS current
    DESCRIPTION
        "Airsys HVAC indoor humidity"
    ::= { evHVACStatusAirsys 5 }
    --1.3.6.1.4.1.3052.10.1.11.4.5

evHVACStatusAirsysUnitTable OBJECT-TYPE
    SYNTAX SEQUENCE OF HVACStatusAirsysUnit
    MAX-ACCESS not-accessible
    STATUS current
    DESCRIPTION
        "Airsys HVAC unit alarm status table"
    ::= { evHVACStatusAirsys 6 }
    --1.3.6.1.4.1.3052.10.1.11.4.6

evHVACStatusAirsysUnitEntry OBJECT-TYPE
    SYNTAX HVACStatusAirsysUnit
    MAX-ACCESS not-accessible
    STATUS current
    DESCRIPTION
        "Airsys HVAC unit alarm status table entry"
    INDEX { evHVACStatusAirsysUnitIndex }
    ::= { evHVACStatusAirsysUnitTable 1 }
    --1.3.6.1.4.1.3052.10.1.11.4.6.1

evHVACStatusAirsysUnitIndex OBJECT-TYPE
    SYNTAX Integer32 (1..2)
    MAX-ACCESS read-only
    STATUS current
    DESCRIPTION
        "Index for Airsys HVAC unit"
    ::= { evHVACStatusAirsysUnitEntry 1 }
    --1.3.6.1.4.1.3052.10.1.11.4.6.1.1
    
evHVACStatusAirsysUnitTempSupply OBJECT-TYPE
    SYNTAX DisplayString
    MAX-ACCESS read-only
    STATUS current
    DESCRIPTION
        "Airsys HVAC unit supply temperature"
    ::= { evHVACStatusAirsysUnitEntry 2 }
    --1.3.6.1.4.1.3052.10.1.11.4.6.1.2

evHVACStatusAirsysUnitFanspeed OBJECT-TYPE
    SYNTAX DisplayString
    MAX-ACCESS read-only
    STATUS current
    DESCRIPTION
        "Airsys HVAC unit fan speed"
    ::= { evHVACStatusAirsysUnitEntry 3 }
    --1.3.6.1.4.1.3052.10.1.11.4.6.1.3

evHVACStatusAirsysUnitFreeOpening OBJECT-TYPE
    SYNTAX DisplayString
    MAX-ACCESS read-only
    STATUS current
    DESCRIPTION
        "Airsys HVAC unit free cooling vent opening percentage"
    ::= { evHVACStatusAirsysUnitEntry 4 }
    --1.3.6.1.4.1.3052.10.1.11.4.6.1.4

evHVACStatusAirsysUnitStatus OBJECT-TYPE
    SYNTAX DisplayString
    MAX-ACCESS read-only
    STATUS current
    DESCRIPTION
        "Airsys HVAC unit running status"
    ::= { evHVACStatusAirsysUnitEntry 5 }
    --1.3.6.1.4.1.3052.10.1.11.4.6.1.5

evHVACStatusAirsysUnitLocked OBJECT-TYPE
    SYNTAX DisplayString
    MAX-ACCESS read-only
    STATUS current
    DESCRIPTION
        "Airsys HVAC unit locked status"
    ::= { evHVACStatusAirsysUnitEntry 6 }
    --1.3.6.1.4.1.3052.10.1.11.4.6.1.6

evHVACStatusAirsysUnitCompressor OBJECT-TYPE
    SYNTAX DisplayString
    MAX-ACCESS read-only
    STATUS current
    DESCRIPTION
        "Airsys HVAC unit state of compressor"
    ::= { evHVACStatusAirsysUnitEntry 7 }
    --1.3.6.1.4.1.3052.10.1.11.4.6.1.7

evHVACStatusAirsysUnitHeater OBJECT-TYPE
    SYNTAX DisplayString
    MAX-ACCESS read-only
    STATUS current
    DESCRIPTION
        "Airsys HVAC unit state of heater"
    ::= { evHVACStatusAirsysUnitEntry 8 }
    --1.3.6.1.4.1.3052.10.1.11.4.6.1.8

evHVACStatusAirsysURuntimeSupplyFan OBJECT-TYPE
    SYNTAX DisplayString
    MAX-ACCESS read-only
    STATUS current
    DESCRIPTION
        "Airsys HVAC unit run time of supply fan in hours"
    ::= { evHVACStatusAirsysUnitEntry 9 }
    --1.3.6.1.4.1.3052.10.1.11.4.6.1.9

evHVACStatusAirsysURuntimeCompressor OBJECT-TYPE
    SYNTAX DisplayString
    MAX-ACCESS read-only
    STATUS current
    DESCRIPTION
        "Airsys HVAC unit run time of compressor in hours"
    ::= { evHVACStatusAirsysUnitEntry 10 }
    --1.3.6.1.4.1.3052.10.1.11.4.6.1.10

evHVACStatusAirsysURuntimeHeat OBJECT-TYPE
    SYNTAX DisplayString
    MAX-ACCESS read-only
    STATUS current
    DESCRIPTION
        "Airsys HVAC unit run time of heating in hours"
    ::= { evHVACStatusAirsysUnitEntry 11 }
    --1.3.6.1.4.1.3052.10.1.11.4.6.1.11

evHVACStatusAirsysURuntimeFreeCooling OBJECT-TYPE
    SYNTAX DisplayString
    MAX-ACCESS read-only
    STATUS current
    DESCRIPTION
        "Airsys HVAC unit run time of free cooling in hours"
    ::= { evHVACStatusAirsysUnitEntry 12 }
    --1.3.6.1.4.1.3052.10.1.11.4.6.1.12

evHVACStatusAirsysUCountSupplyFan OBJECT-TYPE
    SYNTAX DisplayString
    MAX-ACCESS read-only
    STATUS current
    DESCRIPTION
        "Airsys HVAC unit number of times supply fan has started"
    ::= { evHVACStatusAirsysUnitEntry 13 }
    --1.3.6.1.4.1.3052.10.1.11.4.6.1.13

evHVACStatusAirsysUCountCompressor OBJECT-TYPE
    SYNTAX DisplayString
    MAX-ACCESS read-only
    STATUS current
    DESCRIPTION
        "Airsys HVAC unit number of times compressor has started"
    ::= { evHVACStatusAirsysUnitEntry 14 }
    --1.3.6.1.4.1.3052.10.1.11.4.6.1.14

evHVACStatusAirsysUCountHeat OBJECT-TYPE
    SYNTAX DisplayString
    MAX-ACCESS read-only
    STATUS current
    DESCRIPTION
        "Airsys HVAC unit number of times heating has started"
    ::= { evHVACStatusAirsysUnitEntry 15 }
    --1.3.6.1.4.1.3052.10.1.11.4.6.1.15

evHVACStatusAirsysUCountFreeCooling OBJECT-TYPE
    SYNTAX DisplayString
    MAX-ACCESS read-only
    STATUS current
    DESCRIPTION
        "Airsys HVAC unit number of times free cooling has started"
    ::= { evHVACStatusAirsysUnitEntry 16 }
    --1.3.6.1.4.1.3052.10.1.11.4.6.1.16

evHVACStatusAirsysDay OBJECT-TYPE
    SYNTAX DisplayString
    MAX-ACCESS read-only
    STATUS current
    DESCRIPTION
        "Airsys HVAC controller day"
    ::= { evHVACStatusAirsys 7 }
    --1.3.6.1.4.1.3052.10.1.11.4.7

evHVACStatusAirsysDate OBJECT-TYPE
    SYNTAX DisplayString
    MAX-ACCESS read-only
    STATUS current
    DESCRIPTION
        "Airsys HVAC controller date"
    ::= { evHVACStatusAirsys 8 }
    --1.3.6.1.4.1.3052.10.1.11.4.8

evHVACStatusAirsysTime OBJECT-TYPE
    SYNTAX DisplayString
    MAX-ACCESS read-only
    STATUS current
    DESCRIPTION
        "Airsys HVAC controller time"
    ::= { evHVACStatusAirsys 9 }
    --1.3.6.1.4.1.3052.10.1.11.4.9

evHVACStatusAirsysVersion OBJECT-TYPE
    SYNTAX DisplayString
    MAX-ACCESS read-only
    STATUS current
    DESCRIPTION
        "Airsys HVAC controller software version"
    ::= { evHVACStatusAirsys 10 }
    --1.3.6.1.4.1.3052.10.1.11.4.10

--***************************************************************************************
--Battery Backup Status Section 1.12
--***************************************************************************************
liBattPercentCharge OBJECT-TYPE
    SYNTAX Integer32 (1..100)
    MAX-ACCESS read-only
    STATUS current
    DESCRIPTION
        "Lithium Battery State Charge in Percent (0% to 100%)"
    ::= { liBattStatus 1 }
    --1.3.6.1.4.1.3052.10.1.12.1.1

liBattRunning OBJECT-TYPE
    SYNTAX Integer32 (0..1)
    MAX-ACCESS read-only
    STATUS current
    DESCRIPTION
        "Is the unit running on battery backup: (TRUE/FALSE) or (1/0)"
    ::= { liBattStatus 2 }
    --1.3.6.1.4.1.3052.10.1.12.1.2

--***************************************************************************************
--EventSensor Basics Section    2.1
--***************************************************************************************

esNumberEventSensors OBJECT-TYPE
    SYNTAX Integer32
    MAX-ACCESS read-only
    STATUS current
    DESCRIPTION
        "The number of EventSensors recognized by the unit,
        including the internal EventSensor.
        Range: 1-17"
    ::= { eventSensorBasics 1 }
    --1.3.6.1.4.1.3052.10.2.1.1

esTable OBJECT-TYPE
    SYNTAX SEQUENCE OF ESExist
    MAX-ACCESS not-accessible
    STATUS current
    DESCRIPTION
        "The table of what EventSensors are attached to the unit,
        including the internal EventSensor"
    ::= { eventSensorBasics 2 }
    --1.3.6.1.4.1.3052.10.2.1.2

esEntry OBJECT-TYPE
    SYNTAX ESExist
    MAX-ACCESS not-accessible
    STATUS current
    DESCRIPTION
        "Table entry for EventSensor table"
    INDEX { esIndex }
    ::= { esTable 1 }
    --1.3.6.1.4.1.3052.10.2.1.2.1

esIndex OBJECT-TYPE
    SYNTAX Integer32 (1..200)
    MAX-ACCESS read-only
    STATUS current
    DESCRIPTION
        "This number refers to an EventSensor; it has the
        same meaning as the esIndexES object (see above),
        except that this object is used only within the
        esTable branch.

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndex=2
        will now refer to that particular EventSensor.
        "
    ::= { esEntry 1 }
    --1.3.6.1.4.1.3052.10.2.1.2.1.1

esName  OBJECT-TYPE
    SYNTAX DisplayString
    MAX-ACCESS read-only
    STATUS current
    DESCRIPTION
        "The name of the EventSensor"
    ::= { esEntry 2 }
    --1.3.6.1.4.1.3052.10.2.1.2.1.2

esID    OBJECT-TYPE
    SYNTAX DisplayString
    MAX-ACCESS read-only
    STATUS current
    DESCRIPTION
        "The factory-assigned ID of the EventSensor"
    ::= { esEntry 3 }
    --1.3.6.1.4.1.3052.10.2.1.2.1.3

esNumberTempSensors OBJECT-TYPE
    SYNTAX Integer32
    MAX-ACCESS read-only
    STATUS current
    DESCRIPTION
        "The number of temperature sensors on the EventSensor"
    ::= { esEntry 4 }
    --1.3.6.1.4.1.3052.10.2.1.2.1.4

esTempReportingMode OBJECT-TYPE
    SYNTAX DisplayString
    MAX-ACCESS read-only
    STATUS current
    DESCRIPTION
        "Description of how temperature values should
        be interpreted."
    ::= { esEntry 5 }
    --1.3.6.1.4.1.3052.10.2.1.2.1.5

esNumberCCs OBJECT-TYPE
    SYNTAX Integer32
    MAX-ACCESS read-only
    STATUS current
    DESCRIPTION
        "The number of contact closures on the EventSensor."
    ::= { esEntry 6 }
    --1.3.6.1.4.1.3052.10.2.1.2.1.6

esCCReportingMode OBJECT-TYPE
    SYNTAX DisplayString
    MAX-ACCESS read-only
    STATUS current
    DESCRIPTION
        "Description of how CC values should be interpreted."
    ::= { esEntry 7 }
    --1.3.6.1.4.1.3052.10.2.1.2.1.7

esNumberHumidSensors OBJECT-TYPE
    SYNTAX Integer32
    MAX-ACCESS read-only
    STATUS current
    DESCRIPTION
        "The number of humidity sensors on the EventSensor."
    ::= { esEntry 8 }
    --1.3.6.1.4.1.3052.10.2.1.2.1.8

esHumidReportingMode OBJECT-TYPE
    SYNTAX DisplayString
    MAX-ACCESS read-only
    STATUS current
    DESCRIPTION
        "Description of how humidity sensor values should be
        interpreted."
    ::= { esEntry 9 }
    --1.3.6.1.4.1.3052.10.2.1.2.1.9

esNumberNoiseSensors OBJECT-TYPE
    SYNTAX Integer32
    MAX-ACCESS read-only
    STATUS current
    DESCRIPTION
        "The number of noise sensors on the EventSensor."
    ::= { esEntry 10 }
    --1.3.6.1.4.1.3052.10.2.1.2.1.10

esNoiseReportingMode OBJECT-TYPE
    SYNTAX DisplayString
    MAX-ACCESS read-only
    STATUS current
    DESCRIPTION
        "Description of how noise sensor values should be
        interpreted."
    ::= { esEntry 11 }
    --1.3.6.1.4.1.3052.10.2.1.2.1.11

esNumberAirflowSensors OBJECT-TYPE
    SYNTAX Integer32
    MAX-ACCESS read-only
    STATUS current
    DESCRIPTION
        "The number of airflow sensors on the EventSensor."
    ::= { esEntry 12 }
    --1.3.6.1.4.1.3052.10.2.1.2.1.12

esAirflowReportingMode OBJECT-TYPE
    SYNTAX DisplayString
    MAX-ACCESS read-only
    STATUS current
    DESCRIPTION
        "Description of how airflow sensor values should be
        interpreted."
    ::= { esEntry 13 }
    --1.3.6.1.4.1.3052.10.2.1.2.1.13

esNumberAnalog OBJECT-TYPE
    SYNTAX Integer32
    MAX-ACCESS read-only
    STATUS current
    DESCRIPTION
        "The number of analog inputs on the EventSensor."
    ::= { esEntry 14 }
    --1.3.6.1.4.1.3052.10.2.1.2.1.14

esAnalogReportingMode OBJECT-TYPE
    SYNTAX DisplayString
    MAX-ACCESS read-only
    STATUS current
    DESCRIPTION
        "Description of how analog input values should be
        interpreted."
    ::= { esEntry 15 }
    --1.3.6.1.4.1.3052.10.2.1.2.1.15

esNumberOutputs OBJECT-TYPE
    SYNTAX Integer32
    MAX-ACCESS read-only
    STATUS current
    DESCRIPTION
        "The number of outputs (relay or power) on the EventSensor"
    ::= { esEntry 16 }
    --1.3.6.1.4.1.3052.10.2.1.2.1.16

esOutputReportingMode OBJECT-TYPE
    SYNTAX DisplayString
    MAX-ACCESS read-only
    STATUS current
    DESCRIPTION
        "Description of how output values should be interpreted."
    ::= { esEntry 17 }
    --1.3.6.1.4.1.3052.10.2.1.2.1.17

esTempCombinedStatus OBJECT-TYPE
    SYNTAX DisplayString
    MAX-ACCESS read-only
    STATUS current
    DESCRIPTION
        "Combined status string intended to be parsed by NMS:
        name`value`scale`eventState`eventColorCode"
    ::= { esEntry 18 }
    --1.3.6.1.4.1.3052.10.2.1.2.1.18

esCCCombinedStatusBlock1 OBJECT-TYPE
    SYNTAX DisplayString
    MAX-ACCESS read-only
    STATUS current
    DESCRIPTION
        "Combined status string intended to be parsed by NMS:
        numInBlock~name1`value1`eventColorCode1`alias1~name2`value2`eventColorCode2`alias2~...name8`value8`eventColorCode8`alias8"
    ::= { esEntry 19 }
    --1.3.6.1.4.1.3052.10.2.1.2.1.19

esCCCombinedStatusBlock2 OBJECT-TYPE
    SYNTAX DisplayString
    MAX-ACCESS read-only
    STATUS current
    DESCRIPTION
        "Combined status string intended to be parsed by NMS:
        numInBlock~name9`value9`eventColorCode9`alias9~name10`value10`eventColorCode10`alias10~...name16`value16`eventColorCode16`alias16"
    ::= { esEntry 20 }
    --1.3.6.1.4.1.3052.10.2.1.2.1.20

esCCCombinedStatusBlock3 OBJECT-TYPE
    SYNTAX DisplayString
    MAX-ACCESS read-only
    STATUS current
    DESCRIPTION
        "Combined status string intended to be parsed by NMS:
        numInBlock~name17`value17`eventColorCode17`alias17~name18`value18`eventColorCode18`alias18~...name24`value24`eventColorCode24`alias24"
    ::= { esEntry 21 }
    --1.3.6.1.4.1.3052.10.2.1.2.1.21

esCCCombinedStatusBlock4 OBJECT-TYPE
    SYNTAX DisplayString
    MAX-ACCESS read-only
    STATUS current
    DESCRIPTION
        "Combined status string intended to be parsed by NMS:
        numInBlock~name25`value25`eventColorCode25`alias25~name26`value26`eventColorCode26`alias26~...name32`value32`eventColorCode32`alias32"
    ::= { esEntry 22 }
    --1.3.6.1.4.1.3052.10.2.1.2.1.22

esCCCombinedStatusBlock5 OBJECT-TYPE
    SYNTAX DisplayString
    MAX-ACCESS read-only
    STATUS current
    DESCRIPTION
        "Combined status string intended to be parsed by NMS:
        numInBlock~name33`value33`eventColorCode33`alias33~name34`value34`eventColorCode34`alias35~...name40`value40`eventColorCode40`alias40"
    ::= { esEntry 23 }
    --1.3.6.1.4.1.3052.10.2.1.2.1.23

esCCCombinedStatusBlock6 OBJECT-TYPE
    SYNTAX DisplayString
    MAX-ACCESS read-only
    STATUS current
    DESCRIPTION
        "Combined status string intended to be parsed by NMS:
        numInBlock~name41`value41`eventColorCode41`alias41~name42`value42`eventColorCode42`alias43~...name48`value48`eventColorCode48`alias48"
    ::= { esEntry 24 }
    --1.3.6.1.4.1.3052.10.2.1.2.1.24

esCCCombinedStatusBlock7 OBJECT-TYPE
    SYNTAX DisplayString
    MAX-ACCESS read-only
    STATUS current
    DESCRIPTION
        "Combined status string intended to be parsed by NMS:
        numInBlock~name49`value49`eventColorCode49`alias49~name50`value50`eventColorCode50`alias50~...name56`value56`eventColorCode56`alias56"
    ::= { esEntry 25 }
    --1.3.6.1.4.1.3052.10.2.1.2.1.25

esCCCombinedStatusBlock8 OBJECT-TYPE
    SYNTAX DisplayString
    MAX-ACCESS read-only
    STATUS current
    DESCRIPTION
        "Combined status string intended to be parsed by NMS:
        numInBlock~name57`value57`eventColorCode57`alias57~name57`value57`eventColorCode564`alias57~...name64`value64`eventColorCode64`alias64"
    ::= { esEntry 26 }
    --1.3.6.1.4.1.3052.10.2.1.2.1.26

esHumidCombinedStatus OBJECT-TYPE
    SYNTAX DisplayString
    MAX-ACCESS read-only
    STATUS current
    DESCRIPTION
        "Combined status string intended to be parsed by NMS:
        name`value`eventState`eventColorCode"
    ::= { esEntry 27 }
    --1.3.6.1.4.1.3052.10.2.1.2.1.27

esAnalogCombinedStatusBlock1 OBJECT-TYPE
    SYNTAX DisplayString
    MAX-ACCESS read-only
    STATUS current
    DESCRIPTION
        "Combined status string intended to be parsed by NMS:
        numInBlock~name1`value1`units1`eventState`eventColorCode1~name2`value2`units2`eventState`eventColorCode2~..."
    ::= { esEntry 28 }
    --1.3.6.1.4.1.3052.10.2.1.2.1.28

esAnalogCombinedStatusBlock2 OBJECT-TYPE
    SYNTAX DisplayString
    MAX-ACCESS read-only
    STATUS current
    DESCRIPTION
        "Combined status string intended to be parsed by NMS:
        numInBlock~name9`value9`units9`eventState9`eventColorCode9~..."
    ::= { esEntry 29 }
    --1.3.6.1.4.1.3052.10.2.1.2.1.29

esAnalogCombinedStatusBlock3 OBJECT-TYPE
    SYNTAX DisplayString
    MAX-ACCESS read-only
    STATUS current
    DESCRIPTION
        "Combined status string intended to be parsed by NMS:
        numInBlock~namex`valuex`unitsx`eventStatex`eventColorCodex~..."
    ::= { esEntry 30 }
    --1.3.6.1.4.1.3052.10.2.1.2.1.31

esAnalogCombinedStatusBlock4 OBJECT-TYPE
    SYNTAX DisplayString
    MAX-ACCESS read-only
    STATUS current
    DESCRIPTION
        "Combined status string intended to be parsed by NMS:
        numInBlock~namex`valuex`unitsx`eventStatex`eventColorCodex~..."
    ::= { esEntry 31 }
    --1.3.6.1.4.1.3052.10.2.1.2.1.31

esAnalogCombinedStatusBlock5 OBJECT-TYPE
    SYNTAX DisplayString
    MAX-ACCESS read-only
    STATUS current
    DESCRIPTION
        "Combined status string intended to be parsed by NMS:
        numInBlock~namex`valuex`unitsx`eventStatex`eventColorCodex~..."
    ::= { esEntry 32 }
    --1.3.6.1.4.1.3052.10.2.1.2.1.32

esAnalogCombinedStatusBlock6 OBJECT-TYPE
    SYNTAX DisplayString
    MAX-ACCESS read-only
    STATUS current
    DESCRIPTION
        "Combined status string intended to be parsed by NMS:
        numInBlock~namex`valuex`unitsx`eventStatex`eventColorCodex~..."
    ::= { esEntry 33 }
    --1.3.6.1.4.1.3052.10.2.1.2.1.33

esOutputCombinedStatusBlock1 OBJECT-TYPE
    SYNTAX DisplayString
    MAX-ACCESS read-only
    STATUS current
    DESCRIPTION
        "Combined status string intended to be parsed by NMS:
        numInBlock~namex`valuex`unitsx`eventStatex`eventColorCodex~..."
    ::= { esEntry 34 }
    --1.3.6.1.4.1.3052.10.2.1.2.1.34

esOutputCombinedStatusBlock2 OBJECT-TYPE
    SYNTAX DisplayString
    MAX-ACCESS read-only
    STATUS current
    DESCRIPTION
        "Combined status string intended to be parsed by NMS:
        numInBlock`namex`valuex`aliasx~namey`valuey`aliasy~...namez`valuez`aliasz"
    ::= { esEntry 35 }
    --1.3.6.1.4.1.3052.10.2.1.2.1.35

esNewSensors OBJECT-TYPE
    SYNTAX DisplayString
    MAX-ACCESS read-only
    STATUS current
    DESCRIPTION
        "String representing the number of new (attached but unconfigured) EventSensors"
    ::= { eventSensorBasics 3 }
    --1.3.6.1.4.1.3052.10.2.1.3


--***************************************************************************************
--EventSensor Point Config Section   2.2
--***************************************************************************************



esPointConfigTempTable OBJECT-TYPE
    SYNTAX SEQUENCE OF ESPointConfigTemp
    MAX-ACCESS not-accessible
    STATUS current
    DESCRIPTION
        "This table organizes 3 basic attributes of temperature
        sensor points.  A point is a particular sensor on an
        EventSensor.  The 3 point attributes organizes in this table
        are:
        1. the configuration item (e.g., enable, name, etc.)
        2. the eventsensor on which this point resides
        3. the point number (always 1 for temp sensors)

        Points are referenced by a point config index.  The point
        config index is a string of 2 numbers separated by periods.
        It contains all the information necessary for getting a
        piece of data off an event sensor within the context of this
        emperature point config table ; namely, which EventSensor,
        and which sensor (a.k.a. point) (always 1 for temperature
        sensors).
        "
    ::= { eventSensorPointConfig 1 }
    --1.3.6.1.4.1.3052.10.2.2.1

esPointConfigTempEntry OBJECT-TYPE
    SYNTAX ESPointConfigTemp
    MAX-ACCESS not-accessible
    STATUS current
    DESCRIPTION
        "Entry for EventSensor point config temperature table"
    INDEX { espcTempIndexES, espcTempIndexPoint }
    ::= { esPointConfigTempTable 1 }
    --1.3.6.1.4.1.3052.10.2.2.1.1

espcTempIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config temperature table; namely, which EventSensor,
        and which sensor (a.k.a. point).

        This object's allowable values are 1 through 16,
        and 200.  200 always refers to the EventSensor
        inside the unit.  1 through 16 refer to additional
        attached EventSensors.

        The number corresponding to an EventSensor is
        determined by the user at the initial configuration
        time.  If there is an internal sensor in the unit,
        it will always be the first item in the Sensor
        Events setup menu.

        For example, if a new EventSensor is configured as
        the 2nd entry AFTER the internal EventSensor (if
        one exists) in the Sensor Events Setup Menu, then
        that EventSensor will be known from then on as
        EventSensor 2.  All point indeces with esIndexES=2
        will now refer to that particular EventSensor.
        "
    ::= { esPointConfigTempEntry 1 }
    --1.3.6.1.4.1.3052.10.2.2.1.1.1

espcTempIndexPoint OBJECT-TYPE
    SYNTAX Integer32 (1..64)
    MAX-ACCESS read-only
    STATUS current
    DESCRIPTION
        "The part of the point index that delineates which
        sensor on the EventSensor.

        So this combined with espcTempIndexES (which EventSensor)
        uniquely defines each point attached to a unit within the
        context of temperature point configuration."
    ::= { esPointConfigTempEntry 2 }
    --1.3.6.1.4.1.3052.10.2.2.1.1.2

espcTempEnable OBJECT-TYPE
    SYNTAX DisplayString
    MAX-ACCESS read-write
    STATUS current
    DESCRIPTION
        "ON/OFF enable this temperature sensor"
    ::= { esPointConfigTempEntry 3 }
    --1.3.6.1.4.1.3052.10.2.2.1.1.3

espcTempScale OBJECT-TYPE
    SYNTAX DisplayString
    MAX-ACCESS read-write
    STATUS current
    DESCRIPTION
        "Scale (C/F) for this temperature sensor"
    ::= { esPointConfigTempEntry 4 }
    --1.3.6.1.4.1.3052.10.2.2.1.1.4

espcTempDeadband OBJECT-TYPE
    SYNTAX DisplayString
    MAX-ACCESS read-write
    STATUS current
    DESCRIPTION
        "Deadband for this temperature sensor (in floating-point format)"
    ::= { esPointConfigTempEntry 5 }
    --1.3.6.1.4.1.3052.10.2.2.1.1.5

espcTempVHighTemp OBJECT-TYPE
    SYNTAX DisplayString
    MAX-ACCESS read-write
    STATUS current
    DESCRIPTION
        "Very high temperature event threshold for this temperature
        sensor (in floating-point format)"
    ::= { esPointConfigTempEntry 6 }
    --1.3.6.1.4.1.3052.10.2.2.1.1.6

espcTempVHighActions OBJECT-TYPE
    SYNTAX DisplayString
    MAX-ACCESS read-write
    STATUS current
    DESCRIPTION
        "Very high temperature event actions for this temperature
        sensor"
    ::= { esPointConfigTempEntry 7 }
    --1.3.6.1.4.1.3052.10.2.2.1.1.7

espcTempVHighTrapnum OBJECT-TYPE
    SYNTAX Integer32
    MAX-ACCESS read-write
    STATUS current
    DESCRIPTION
        "Very high temperature event trap number for this
        temperature sensor"
    ::= { esPointConfigTempEntry 8 }
    --1.3.6.1.4.1.3052.10.2.2.1.1.8

espcTempVHighClass OBJECT-TYPE
    SYNTAX DisplayString
    MAX-ACCESS read-write
    STATUS current
    DESCRIPTION
        "Very high temperature event class for this temperature
        sensor"
    ::= { esPointConfigTempEntry 9 }
    --1.3.6.1.4.1.3052.10.2.2.1.1.9

espcTempHighTemp OBJECT-TYPE
    SYNTAX DisplayString
    MAX-ACCESS read-write
    STATUS current
    DESCRIPTION
        "High temperature event threshold for this temperature
        sensor (in floating-point format)"
    ::= { esPointConfigTempEntry 10 }
    --1.3.6.1.4.1.3052.10.2.2.1.1.10

espcTempHighActions OBJECT-TYPE
    SYNTAX DisplayString
    MAX-ACCESS read-write
    STATUS current
    DESCRIPTION
        "High temperature event actions for this temperature sensor"
    ::= { esPointConfigTempEntry 11 }
    --1.3.6.1.4.1.3052.10.2.2.1.1.11

espcTempHighTrapnum OBJECT-TYPE
    SYNTAX Integer32
    MAX-ACCESS read-write
    STATUS current
    DESCRIPTION
        "High temperature event trap number for this temperature
        sensor"
    ::= { esPointConfigTempEntry 12 }
    --1.3.6.1.4.1.3052.10.2.2.1.1.12

espcTempHighClass OBJECT-TYPE
    SYNTAX DisplayString
    MAX-ACCESS read-write
    STATUS current
    DESCRIPTION
        "High temperature event class for this temperature sensor"
    ::= { esPointConfigTempEntry 13 }
    --1.3.6.1.4.1.3052.10.2.2.1.1.13

espcTempNormalActions OBJECT-TYPE
    SYNTAX DisplayString
    MAX-ACCESS read-write
    STATUS current
    DESCRIPTION
        "Return-to-normal event actions for this temperature sensor"
    ::= { esPointConfigTempEntry 14 }
    --1.3.6.1.4.1.3052.10.2.2.1.1.14

espcTempNormalTrapnum OBJECT-TYPE
    SYNTAX Integer32
    MAX-ACCESS read-write
    STATUS current
    DESCRIPTION
        "Return-to-normal event trap number for this temperature
        sensor"
    ::= { esPointConfigTempEntry 15 }
    --1.3.6.1.4.1.3052.10.2.2.1.1.15

espcTempNormalClass OBJECT-TYPE
    SYNTAX DisplayString
    MAX-ACCESS read-write
    STATUS current
    DESCRIPTION
        "Return-to-normal event class for this temperature sensor"
    ::= { esPointConfigTempEntry 16 }
    --1.3.6.1.4.1.3052.10.2.2.1.1.16

espcTempLowTemp OBJECT-TYPE
    SYNTAX DisplayString
    MAX-ACCESS read-write
    STATUS current
    DESCRIPTION
        "Low temperature event threshold for this temperature sensor
        (in floating-point format)"
    ::= { esPointConfigTempEntry 17 }
    --1.3.6.1.4.1.3052.10.2.2.1.1.17

espcTempLowActions OBJECT-TYPE
    SYNTAX DisplayString
    MAX-ACCESS read-write
    STATUS current
    DESCRIPTION
        "Low temperature event actions for this temperature sensor"
    ::= { esPointConfigTempEntry 18 }
    --1.3.6.1.4.1.3052.10.2.2.1.1.18

espcTempLowTrapnum OBJECT-TYPE
    SYNTAX Integer32
    MAX-ACCESS read-write
    STATUS current
    DESCRIPTION
        "Low temperature event trap number for this temperature
        sensor"
    ::= { esPointConfigTempEntry 19 }
    --1.3.6.1.4.1.3052.10.2.2.1.1.19

espcTempLowClass OBJECT-TYPE
    SYNTAX DisplayString
    MAX-ACCESS read-write
    STATUS current
    DESCRIPTION
        "Low temperature event class for this temperature sensor"
    ::= { esPointConfigTempEntry 20 }
    --1.3.6.1.4.1.3052.10.2.2.1.1.20

espcTempVLowTemp OBJECT-TYPE
    SYNTAX DisplayString
    MAX-ACCESS read-write
    STATUS current
    DESCRIPTION
        "Very Low temperature event threshold for this temperature
        sensor (in floating-point format)"
    ::= { esPointConfigTempEntry 21 }
    --1.3.6.1.4.1.3052.10.2.2.1.1.21

espcTempVLowActions OBJECT-TYPE
    SYNTAX DisplayString
    MAX-ACCESS read-write
    STATUS current
    DESCRIPTION
        "Very Low temperature event actions for this temperature
        sensor"
    ::= { esPointConfigTempEntry 22 }
    --1.3.6.1.4.1.3052.10.2.2.1.1.22

espcTempVLowTrapnum OBJECT-TYPE
    SYNTAX Integer32
    MAX-ACCESS read-write
    STATUS current
    DESCRIPTION
        "Very Low temperature event trap number for this temperature
        sensor"
    ::= { esPointConfigTempEntry 23 }
    --1.3.6.1.4.1.3052.10.2.2.1.1.23

espcTempVLowClass OBJECT-TYPE
    SYNTAX DisplayString
    MAX-ACCESS read-write
    STATUS current
    DESCRIPTION
        "Very Low temperature event class for this temperature sensor"
    ::= { esPointConfigTempEntry 24 }
    --1.3.6.1.4.1.3052.10.2.2.1.1.24

espcTempGroup OBJECT-TYPE
    SYNTAX DisplayString
    MAX-ACCESS read-write
    STATUS current
    DESCRIPTION
        "Name for this temperature sensor group"
    ::= { esPointConfigTempEntry 25 }
    --1.3.6.1.4.1.3052.10.2.2.1.1.25

esPointConfigCCTable OBJECT-TYPE
    SYNTAX SEQUENCE OF ESPointConfigCC
    MAX-ACCESS not-accessible
    STATUS current
    DESCRIPTION
        "This table organizes 3 basic attributes of contact closure
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a piece
        of data off an event sensor within the context of this
        contact closure point config table ; namely, which
        EventSensor and which sensor.
        "
    ::= { eventSensorPointConfig 2 }
    --1.3.6.1.4.1.3052.10.2.2.2

esPointConfigCCEntry OBJECT-TYPE
    SYNTAX ESPointConfigCC
    MAX-ACCESS not-accessible
    STATUS current
    DESCRIPTION
        "Entry for EventSensor point config contact closure table"
    INDEX { espcCCIndexES, espcCCIndexPoint }
    ::= { esPointConfigCCTable 1 }
    --1.3.6.1.4.1.3052.10.2.2.2.1

espcCCIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigCCEntry 1 }
    --1.3.6.1.4.1.3052.10.2.2.2.1.1

espcCCIndexPoint OBJECT-TYPE
    SYNTAX Integer32 (1..64)
    MAX-ACCESS read-only
    STATUS current
    DESCRIPTION
        "The part of the point index that delineates which
        sensor on the EventSensor.

        So this combined with espcCCIndexES (which EventSensor)
        uniquely defines each point attached to a unit within the
        context of contact closure point configuration."
    ::= { esPointConfigCCEntry 2 }
    --1.3.6.1.4.1.3052.10.2.2.2.1.2

espcCCEnable OBJECT-TYPE
    SYNTAX DisplayString
    MAX-ACCESS read-write
    STATUS current
    DESCRIPTION
        "ON/OFF enable for this contact closure"
    ::= { esPointConfigCCEntry 3 }
    --1.3.6.1.4.1.3052.10.2.2.2.1.3

espcCCName OBJECT-TYPE
    SYNTAX DisplayString
    MAX-ACCESS read-write
    STATUS current
    DESCRIPTION
        "Name for this contact closure"
    ::= { esPointConfigCCEntry 4 }
    --1.3.6.1.4.1.3052.10.2.2.2.1.4

espcCCEventState OBJECT-TYPE
    SYNTAX DisplayString
    MAX-ACCESS read-write
    STATUS current
    DESCRIPTION
        "Event state for this contact closure"
    ::= { esPointConfigCCEntry 5 }
    --1.3.6.1.4.1.3052.10.2.2.2.1.5

espcCCThreshold OBJECT-TYPE
    SYNTAX Integer32 (0..65535)
    MAX-ACCESS read-write
    STATUS current
    DESCRIPTION
        "Event threshold (seconds) for this contact closure"
    ::= { esPointConfigCCEntry 6 }
    --1.3.6.1.4.1.3052.10.2.2.2.1.6

espcCCEventActions OBJECT-TYPE
    SYNTAX DisplayString
    MAX-ACCESS read-write
    STATUS current
    DESCRIPTION
        "Event actions for this contact closure"
    ::= { esPointConfigCCEntry 7 }
    --1.3.6.1.4.1.3052.10.2.2.2.1.7

espcCCEventTrapnum OBJECT-TYPE
    SYNTAX Integer32
    MAX-ACCESS read-write
    STATUS current
    DESCRIPTION
        "Event trap number for this contact closure"
    ::= { esPointConfigCCEntry 8 }
    --1.3.6.1.4.1.3052.10.2.2.2.1.8

espcCCEventClass OBJECT-TYPE
    SYNTAX DisplayString
    MAX-ACCESS read-write
    STATUS current
    DESCRIPTION
        "Event class for this contact closure"
    ::= { esPointConfigCCEntry 9 }
    --1.3.6.1.4.1.3052.10.2.2.2.1.9

espcCCNormalActions OBJECT-TYPE
    SYNTAX DisplayString
    MAX-ACCESS read-write
    STATUS current
    DESCRIPTION
        "Return-to-normal actions for this contact closure"
    ::= { esPointConfigCCEntry 10 }
    --1.3.6.1.4.1.3052.10.2.2.2.1.10

espcCCNormalTrapnum OBJECT-TYPE
    SYNTAX Integer32
    MAX-ACCESS read-write
    STATUS current
    DESCRIPTION
        "Return-to-normal trap number for this contact closure"
    ::= { esPointConfigCCEntry 11 }
    --1.3.6.1.4.1.3052.10.2.2.2.1.11

espcCCNormalClass OBJECT-TYPE
    SYNTAX DisplayString
    MAX-ACCESS read-write
    STATUS current
    DESCRIPTION
        "Return-to-normal class for this contact closure"
    ::= { esPointConfigCCEntry 12 }
    --1.3.6.1.4.1.3052.10.2.2.2.1.12

espcCCAlarmAlias OBJECT-TYPE
    SYNTAX DisplayString
    MAX-ACCESS read-write
    STATUS current
    DESCRIPTION
        "Event alias for this contact closure"
    ::= { esPointConfigCCEntry 13 }
    --1.3.6.1.4.1.3052.10.2.2.2.1.13

espcCCNormalAlias OBJECT-TYPE
    SYNTAX DisplayString
    MAX-ACCESS read-write
    STATUS current
    DESCRIPTION
        "Return-to-normal alias for this contact closure"
    ::= { esPointConfigCCEntry 14 }
    --1.3.6.1.4.1.3052.10.2.2.2.1.14

espcCCNormalThreshold OBJECT-TYPE
    SYNTAX Integer32 (0..65535)
    MAX-ACCESS read-write
    STATUS current
    DESCRIPTION
        "Event threshold (seconds) for this contact closure to return to normal"
    ::= { esPointConfigCCEntry 15 }
    --1.3.6.1.4.1.3052.10.2.2.2.1.15

espcCCOverrideGlobalReminder OBJECT-TYPE
    SYNTAX DisplayString
    MAX-ACCESS read-write
    STATUS current
    DESCRIPTION
        "Override global reminder interval (evReminderInterval) for this CC."
    ::= { esPointConfigCCEntry 16 }
    --1.3.6.1.4.1.3052.10.2.2.2.1.16

espcCCReminderInterval OBJECT-TYPE
    SYNTAX Integer32
    MAX-ACCESS read-write
    STATUS current
    DESCRIPTION
        "Individual reminder interval for this CC, applicable when the global
        reminder is overriden."
    ::= { esPointConfigCCEntry 17 }
    --1.3.6.1.4.1.3052.10.2.2.2.1.17

espcCCGroup OBJECT-TYPE
    SYNTAX DisplayString
    MAX-ACCESS read-write
    STATUS current
    DESCRIPTION
        "Name for this contact closure group"
    ::= { esPointConfigCCEntry 18 }
    --1.3.6.1.4.1.3052.10.2.2.2.1.18

esPointConfigHumidTable OBJECT-TYPE
    SYNTAX SEQUENCE OF ESPointConfigHumid
    MAX-ACCESS not-accessible
    STATUS current
    DESCRIPTION
        "This table organizes 3 basic attributes of humidity points.
        A point is a particular sensor on an EventSensor.  The 3
        point attributes organizes in this table are:
        1. the configuration item (e.g., enable, name, etc.)
        2. the eventsensor on which this point resides
        3. the point number (always 1 for humidity sensors)

        Points are referenced by a point config index.  The point
        config index is a string of 2 numbers separated by a period.
        It contains all the information necessary for getting a piece
        of data off an event sensor within the context of this
        humidity point config table ; namely, which EventSensor and
        which sensor.
        "
    ::= { eventSensorPointConfig 3 }
    --1.3.6.1.4.1.3052.10.2.2.3

esPointConfigHumidEntry OBJECT-TYPE
    SYNTAX ESPointConfigHumid
    MAX-ACCESS not-accessible
    STATUS current
    DESCRIPTION
        "Entry for EventSensor point config humidity table"
    INDEX { espcHumidIndexES, espcHumidIndexPoint }
    ::= { esPointConfigHumidTable 1 }
    --1.3.6.1.4.1.3052.10.2.2.3.1

espcHumidIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigHumidEntry 1 }
    --1.3.6.1.4.1.3052.10.2.2.3.1.1

espcHumidIndexPoint OBJECT-TYPE
    SYNTAX Integer32 (1..64)
    MAX-ACCESS read-only
    STATUS current
    DESCRIPTION
        "The part of the point index that delineates which
        sensor on the EventSensor.

        So this combined with espcHumidIndexES (which EventSensor)
        uniquely defines each point attached to a unit within the
        context of contact closure point configuration."
    ::= { esPointConfigHumidEntry 2 }
    --1.3.6.1.4.1.3052.10.2.2.3.1.2

espcHumidEnable OBJECT-TYPE
    SYNTAX DisplayString
    MAX-ACCESS read-write
    STATUS current
    DESCRIPTION
        "ON/OFF enable for this humidity sensor"
    ::= { esPointConfigHumidEntry 3 }
    --1.3.6.1.4.1.3052.10.2.2.3.1.3

espcHumidDeadband OBJECT-TYPE
    SYNTAX Integer32
    MAX-ACCESS read-write
    STATUS current
    DESCRIPTION
        "Deadband for this humidity sensor"
    ::= { esPointConfigHumidEntry 4 }
    --1.3.6.1.4.1.3052.10.2.2.3.1.4

espcHumidVHighHumid OBJECT-TYPE
    SYNTAX Integer32
    MAX-ACCESS read-write
    STATUS current
    DESCRIPTION
        "Very high event threshold for this humidity sensor"
    ::= { esPointConfigHumidEntry 5 }
    --1.3.6.1.4.1.3052.10.2.2.3.1.5

espcHumidVHighActions OBJECT-TYPE
    SYNTAX DisplayString
    MAX-ACCESS read-write
    STATUS current
    DESCRIPTION
        "Very high event actions for this humidity sensor"
    ::= { esPointConfigHumidEntry 6 }
    --1.3.6.1.4.1.3052.10.2.2.3.1.6

espcHumidVHighTrapnum OBJECT-TYPE
    SYNTAX Integer32
    MAX-ACCESS read-write
    STATUS current
    DESCRIPTION
        "Very high event trap number for this humidity sensor"
    ::= { esPointConfigHumidEntry 7 }
    --1.3.6.1.4.1.3052.10.2.2.3.1.7

espcHumidVHighClass OBJECT-TYPE
    SYNTAX DisplayString
    MAX-ACCESS read-write
    STATUS current
    DESCRIPTION
        "Very high event class for this humidity sensor"
    ::= { esPointConfigHumidEntry 8 }
    --1.3.6.1.4.1.3052.10.2.2.3.1.8

espcHumidHighHumid OBJECT-TYPE
    SYNTAX Integer32
    MAX-ACCESS read-write
    STATUS current
    DESCRIPTION
        "High event threshold for this humidity sensor"
    ::= { esPointConfigHumidEntry 9 }
    --1.3.6.1.4.1.3052.10.2.2.3.1.9

espcHumidHighActions OBJECT-TYPE
    SYNTAX DisplayString
    MAX-ACCESS read-write
    STATUS current
    DESCRIPTION
        "High event actions for this humidity sensor"
    ::= { esPointConfigHumidEntry 10 }
    --1.3.6.1.4.1.3052.10.2.2.3.1.10

espcHumidHighTrapnum OBJECT-TYPE
    SYNTAX Integer32
    MAX-ACCESS read-write
    STATUS current
    DESCRIPTION
        "High event trap number for this humidity sensor"
    ::= { esPointConfigHumidEntry 11 }
    --1.3.6.1.4.1.3052.10.2.2.3.1.11

espcHumidHighClass OBJECT-TYPE
    SYNTAX DisplayString
    MAX-ACCESS read-write
    STATUS current
    DESCRIPTION
        "High event class for this humidity sensor"
    ::= { esPointConfigHumidEntry 12 }
    --1.3.6.1.4.1.3052.10.2.2.3.1.12

espcHumidNormalActions OBJECT-TYPE
    SYNTAX DisplayString
    MAX-ACCESS read-write
    STATUS current
    DESCRIPTION
        "Return-to-normal actions for this humidity sensor"
    ::= { esPointConfigHumidEntry 13 }
    --1.3.6.1.4.1.3052.10.2.2.3.1.13

espcHumidNormalTrapnum OBJECT-TYPE
    SYNTAX Integer32
    MAX-ACCESS read-write
    STATUS current
    DESCRIPTION
        "Return-to-normal trap number for this humidity sensor"
    ::= { esPointConfigHumidEntry 14 }
    --1.3.6.1.4.1.3052.10.2.2.3.1.14

espcHumidNormalClass OBJECT-TYPE
    SYNTAX DisplayString
    MAX-ACCESS read-write
    STATUS current
    DESCRIPTION
        "Return-to-normal class for this humidity sensor"
    ::= { esPointConfigHumidEntry 15 }
    --1.3.6.1.4.1.3052.10.2.2.3.1.15

espcHumidLowHumid OBJECT-TYPE
    SYNTAX Integer32
    MAX-ACCESS read-write
    STATUS current
    DESCRIPTION
        "Low event threshold for this humidity sensor"
    ::= { esPointConfigHumidEntry 16 }
    --1.3.6.1.4.1.3052.10.2.2.3.1.16

espcHumidLowActions OBJECT-TYPE
    SYNTAX DisplayString
    MAX-ACCESS read-write
    STATUS current
    DESCRIPTION
        "Low event actions for this humidity sensor"
    ::= { esPointConfigHumidEntry 17 }
    --1.3.6.1.4.1.3052.10.2.2.3.1.17

espcHumidLowTrapnum OBJECT-TYPE
    SYNTAX Integer32
    MAX-ACCESS read-write
    STATUS current
    DESCRIPTION
        "Low event trap number for this humidity sensor"
    ::= { esPointConfigHumidEntry 18 }
    --1.3.6.1.4.1.3052.10.2.2.3.1.18

espcHumidLowClass OBJECT-TYPE
    SYNTAX DisplayString
    MAX-ACCESS read-write
    STATUS current
    DESCRIPTION
        "Low event class for this humidity sensor"
    ::= { esPointConfigHumidEntry 19 }
    --1.3.6.1.4.1.3052.10.2.2.3.1.19

espcHumidVLowHumid OBJECT-TYPE
    SYNTAX Integer32
    MAX-ACCESS read-write
    STATUS current
    DESCRIPTION
        "Very low event threshold for this humidity sensor"
    ::= { esPointConfigHumidEntry 20 }
    --1.3.6.1.4.1.3052.10.2.2.3.1.20

espcHumidVLowActions OBJECT-TYPE
    SYNTAX DisplayString
    MAX-ACCESS read-write
    STATUS current
    DESCRIPTION
        "Very low event actions for this humidity sensor"
    ::= { esPointConfigHumidEntry 21 }
    --1.3.6.1.4.1.3052.10.2.2.3.1.21

espcHumidVLowTrapnum OBJECT-TYPE
    SYNTAX Integer32
    MAX-ACCESS read-write
    STATUS current
    DESCRIPTION
        "Very low event trap number for this humidity sensor"
    ::= { esPointConfigHumidEntry 22 }
    --1.3.6.1.4.1.3052.10.2.2.3.1.22

espcHumidVLowClass OBJECT-TYPE
    SYNTAX DisplayString
    MAX-ACCESS read-write
    STATUS current
    DESCRIPTION
        "Very low event class for this humidity sensor"
    ::= { esPointConfigHumidEntry 23 }
    --1.3.6.1.4.1.3052.10.2.2.3.1.23

espcHumidGroup OBJECT-TYPE
    SYNTAX DisplayString
    MAX-ACCESS read-write
    STATUS current
    DESCRIPTION
        "Name for this humidity sensor group"
    ::= { esPointConfigHumidEntry 24 }
    --1.3.6.1.4.1.3052.10.2.2.3.1.24

esPointConfigAITable OBJECT-TYPE
    SYNTAX SEQUENCE OF ESPointConfigAnalogInput
    MAX-ACCESS not-accessible
    STATUS current
    DESCRIPTION
        "This table organizes 3 basic attributes of analog input
        points.  A point is a particular sensor on an EventSensor.
        The 3 point attributes organizes in this table are:
        1. the configuration item (e.g., enable, name, etc.)
        2. the eventsensor on which this point resides
        3. the point number

        Points are referenced by a point config index.  The point
        config index is a string of 2 numbers separated by a period.
        It contains all the information necessary for getting a
        piece of data off an event sensor within the context of this
        analog input point config table ; namely, which EventSensor
        and which sensor.
        "
    ::= { eventSensorPointConfig 5 }
    --1.3.6.1.4.1.3052.10.2.2.5

esPointConfigAIEntry OBJECT-TYPE
    SYNTAX ESPointConfigAnalogInput
    MAX-ACCESS not-accessible
    STATUS current
    DESCRIPTION
        "Entry for EventSensor point config analog input table"
    INDEX { espcHumidIndexES, espcHumidIndexPoint }
    ::= { esPointConfigAITable 1 }
    --1.3.6.1.4.1.3052.10.2.2.5.1

espcAIIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigAIEntry 1 }
    --1.3.6.1.4.1.3052.10.2.2.5.1.1

espcAIIndexPoint OBJECT-TYPE
    SYNTAX Integer32 (1..64)
    MAX-ACCESS read-only
    STATUS current
    DESCRIPTION
        "The part of the point index that delineates which
        sensor on the EventSensor.

        So this combined with espcAIIndexES (which EventSensor)
        uniquely defines each point attached to a unit within the
        context of contact closure point configuration."
    ::= { esPointConfigAIEntry 2 }
    --1.3.6.1.4.1.3052.10.2.2.5.1.2

espcAIEnable OBJECT-TYPE
    SYNTAX DisplayString
    MAX-ACCESS read-write
    STATUS current
    DESCRIPTION
        "ON/OFF for this analog input sensor"
    ::= { esPointConfigAIEntry 3 }
    --1.3.6.1.4.1.3052.10.2.2.5.1.3

espcAIDeadband OBJECT-TYPE
    SYNTAX DisplayString
    MAX-ACCESS read-write
    STATUS current
    DESCRIPTION
        "Deadband for this analog input sensor"
    ::= { esPointConfigAIEntry 5 }
    --1.3.6.1.4.1.3052.10.2.2.5.1.5

espcAIVhighValue OBJECT-TYPE
    SYNTAX DisplayString
    MAX-ACCESS read-write
    STATUS current
    DESCRIPTION
        "Very high event threshold (decivolts or tenths of
        milliamps) for this analog input sensor"
    ::= { esPointConfigAIEntry 6 }
    --1.3.6.1.4.1.3052.10.2.2.5.1.6

espcAIVhighActions OBJECT-TYPE
    SYNTAX DisplayString
    MAX-ACCESS read-write
    STATUS current
    DESCRIPTION
        "Very high event actions for this analog input sensor"
    ::= { esPointConfigAIEntry 7 }
    --1.3.6.1.4.1.3052.10.2.2.5.1.7

espcAIVhighTrapnum OBJECT-TYPE
    SYNTAX Integer32
    MAX-ACCESS read-write
    STATUS current
    DESCRIPTION
        "Very high event trap number for this analog input sensor"
    ::= { esPointConfigAIEntry 8 }
    --1.3.6.1.4.1.3052.10.2.2.5.1.8

espcAIVhighClass OBJECT-TYPE
    SYNTAX DisplayString
    MAX-ACCESS read-write
    STATUS current
    DESCRIPTION
        "Very high event class for this analog input sensor"
    ::= { esPointConfigAIEntry 9 }
    --1.3.6.1.4.1.3052.10.2.2.5.1.9

espcAIHighValue OBJECT-TYPE
    SYNTAX DisplayString
    MAX-ACCESS read-write
    STATUS current
    DESCRIPTION
        "High event threshold (decivolts or tenths of milliamps) for
        this analog input sensor"
    ::= { esPointConfigAIEntry 10 }
    --1.3.6.1.4.1.3052.10.2.2.5.1.10

espcAIHighActions OBJECT-TYPE
    SYNTAX DisplayString
    MAX-ACCESS read-write
    STATUS current
    DESCRIPTION
        "High event actions for this analog input sensor"
    ::= { esPointConfigAIEntry 11 }
    --1.3.6.1.4.1.3052.10.2.2.5.1.11

espcAIHighTrapnum OBJECT-TYPE
    SYNTAX Integer32
    MAX-ACCESS read-write
    STATUS current
    DESCRIPTION
        "High event trap number for this analog input sensor"
    ::= { esPointConfigAIEntry 12 }
    --1.3.6.1.4.1.3052.10.2.2.5.1.12

espcAIHighClass OBJECT-TYPE
    SYNTAX DisplayString
    MAX-ACCESS read-write
    STATUS current
    DESCRIPTION
        "High event class for this analog input sensor"
    ::= { esPointConfigAIEntry 13 }
    --1.3.6.1.4.1.3052.10.2.2.5.1.13

espcAINormalActions OBJECT-TYPE
    SYNTAX DisplayString
    MAX-ACCESS read-write
    STATUS current
    DESCRIPTION
        "Return-to-normal actions for this analog input sensor"
    ::= { esPointConfigAIEntry 14 }
    --1.3.6.1.4.1.3052.10.2.2.5.1.14

espcAINormalTrapnum OBJECT-TYPE
    SYNTAX Integer32
    MAX-ACCESS read-write
    STATUS current
    DESCRIPTION
        "Return-to-normal trap number for this analog input sensor"
    ::= { esPointConfigAIEntry 15 }
    --1.3.6.1.4.1.3052.10.2.2.5.1.15

espcAINormalClass OBJECT-TYPE
    SYNTAX DisplayString
    MAX-ACCESS read-write
    STATUS current
    DESCRIPTION
        "Return-to-normal class for this analog input sensor"
    ::= { esPointConfigAIEntry 16 }
    --1.3.6.1.4.1.3052.10.2.2.5.1.16

espcAILowValue OBJECT-TYPE
    SYNTAX DisplayString
    MAX-ACCESS read-write
    STATUS current
    DESCRIPTION
        "Low event threshold (decivolts or tenths of milliamps) for
        this analog input sensor"
    ::= { esPointConfigAIEntry 17 }
    --1.3.6.1.4.1.3052.10.2.2.5.1.17

espcAILowActions OBJECT-TYPE
    SYNTAX DisplayString
    MAX-ACCESS read-write
    STATUS current
    DESCRIPTION
        "Low event actions for this analog input sensor"
    ::= { esPointConfigAIEntry 18 }
    --1.3.6.1.4.1.3052.10.2.2.5.1.18

espcAILowTrapnum OBJECT-TYPE
    SYNTAX Integer32
    MAX-ACCESS read-write
    STATUS current
    DESCRIPTION
        "Low event trap number for this analog input sensor"
    ::= { esPointConfigAIEntry 19 }
    --1.3.6.1.4.1.3052.10.2.2.5.1.19

espcAILowClass OBJECT-TYPE
    SYNTAX DisplayString
    MAX-ACCESS read-write
    STATUS current
    DESCRIPTION
        "Low event class for this analog input sensor"
    ::= { esPointConfigAIEntry 20 }
    --1.3.6.1.4.1.3052.10.2.2.5.1.20

espcAIVlowValue OBJECT-TYPE
    SYNTAX DisplayString
    MAX-ACCESS read-write
    STATUS current
    DESCRIPTION
        "Very low event threshold (decivolts or tenths of milliamps)
        for this analog input sensor"
    ::= { esPointConfigAIEntry 21 }
    --1.3.6.1.4.1.3052.10.2.2.5.1.21

espcAIVlowActions OBJECT-TYPE
    SYNTAX DisplayString
    MAX-ACCESS read-write
    STATUS current
    DESCRIPTION
        "Very low event actions for this analog input sensor"
    ::= { esPointConfigAIEntry 22 }
    --1.3.6.1.4.1.3052.10.2.2.5.1.22

espcAIVlowTrapnum OBJECT-TYPE
    SYNTAX Integer32
    MAX-ACCESS read-write
    STATUS current
    DESCRIPTION
        "Very low event actions for this analog input sensor"
    ::= { esPointConfigAIEntry 23 }
    --1.3.6.1.4.1.3052.10.2.2.5.1.23

espcAIVlowClass OBJECT-TYPE
    SYNTAX DisplayString
    MAX-ACCESS read-write
    STATUS current
    DESCRIPTION
        "Very low event class for this analog input sensor"
    ::= { esPointConfigAIEntry 24 }
    --1.3.6.1.4.1.3052.10.2.2.5.1.24

espcAIConvUnitName OBJECT-TYPE
    SYNTAX DisplayString
    MAX-ACCESS read-write
    STATUS current
    DESCRIPTION
        "Converstion unit name for this analog input sensor"
    ::= { esPointConfigAIEntry 25 }
    --1.3.6.1.4.1.3052.10.2.2.5.1.25

espcAIConvHighValue OBJECT-TYPE
    SYNTAX DisplayString
    MAX-ACCESS read-write
    STATUS current
    DESCRIPTION
        "Conversion high value for this analog input sensor"
    ::= { esPointConfigAIEntry 26 }
    --1.3.6.1.4.1.3052.10.2.2.5.1.26

espcAIConvHighUnit OBJECT-TYPE
    SYNTAX DisplayString
    MAX-ACCESS read-write
    STATUS current
    DESCRIPTION
        "Conversion high unit value for this analog input sensor"
    ::= { esPointConfigAIEntry 27 }
    --1.3.6.1.4.1.3052.10.2.2.5.1.27

espcAIConvLowValue OBJECT-TYPE
    SYNTAX DisplayString
    MAX-ACCESS read-write
    STATUS current
    DESCRIPTION
        "Conversion low value for this analog input sensor"
    ::= { esPointConfigAIEntry 29 }
    --1.3.6.1.4.1.3052.10.2.2.5.1.29

espcAIConvLowUnit OBJECT-TYPE
    SYNTAX DisplayString
    MAX-ACCESS read-write
    STATUS current
    DESCRIPTION
        "Conversion unit low unit value for this analog input sensor"
    ::= { esPointConfigAIEntry 30 }
    --1.3.6.1.4.1.3052.10.2.2.5.1.30

espcAIDisplayFormat OBJECT-TYPE
    SYNTAX DisplayString
    MAX-ACCESS read-write
    STATUS current
    DESCRIPTION
        "Analog input display format"
    ::= { esPointConfigAIEntry 32 }
    --1.3.6.1.4.1.3052.10.2.2.5.1.32

espcAIGroup OBJECT-TYPE
    SYNTAX DisplayString
    MAX-ACCESS read-write
    STATUS current
    DESCRIPTION
        "Name for this Analog input group"
    ::= { esPointConfigAIEntry 33 }
    --1.3.6.1.4.1.3052.10.2.2.5.1.33

esPointConfigOutputTable OBJECT-TYPE
    SYNTAX SEQUENCE OF ESPointConfigOutput
    MAX-ACCESS not-accessible
    STATUS current
    DESCRIPTION
        "This table organizes configuration items for output
        points.  A point is a particular sensor on an EventSensor.
        The 3 point attributes organized in this table are:
        1. the configuration item (e.g., enable, name, etc.)
        2. the eventsensor on which this point resides
        3. the point number

        Points are referenced by a point config index.  The point
        config index is a string of 2 numbers separated by a period.
        It contains all the information necessary for getting a
        piece of data off an event sensor within the context of this
        output config table ; namely, which EventSensor
        and which sensor.
        "
    ::= { eventSensorPointConfig 6 }
    --1.3.6.1.4.1.3052.10.2.2.6

esPointConfigOutputEntry OBJECT-TYPE
    SYNTAX ESPointConfigOutput
    MAX-ACCESS not-accessible
    STATUS current
    DESCRIPTION
        "Entry for EventSensor point config output table"
    INDEX { espcOutputIndexES, espcOutputIndexPoint }
    ::= { esPointConfigOutputTable 1 }
    --1.3.6.1.4.1.3052.10.2.2.6.1

espcOutputIndexES OBJECT-TYPE
    SYNTAX Integer32 (1..200)
    MAX-ACCESS read-only
    STATUS current
    DESCRIPTION
        "The part of the point index that refers to an
        EventSensor.

        The point config index is a string of 2 numbers separated
        by a period.  It contains all the information
        necessary for getting a piece of data off an event
        sensor within the the context of the eventsensor point
        config contact closure table; namely, which EventSensor
        and which sensor (a.k.a. point).

        This object's allowable values are 1 through 16,
        and 200.  200 always refers to the EventSensor
        inside the unit.  1 through 16 refer to additional
        attached EventSensors.
        "
    ::= { esPointConfigOutputEntry 1 }
    --1.3.6.1.4.1.3052.10.2.2.6.1.1

espcOutputIndexPoint OBJECT-TYPE
    SYNTAX Integer32 (1..64)
    MAX-ACCESS read-only
    STATUS current
    DESCRIPTION
        "The part of the point index that delineates which
        sensor on the EventSensor.

        So this combined with espcOutputIndexES (which EventSensor)
        uniquely defines each point attached to a unit within the
        context of output point configuration."
    ::= { esPointConfigOutputEntry 2 }
    --1.3.6.1.4.1.3052.10.2.2.6.1.2

espcOutputEnable OBJECT-TYPE
    SYNTAX DisplayString
    MAX-ACCESS read-write
    STATUS current
    DESCRIPTION
        "Enables the output event for this output.  This has no effect
        on whether the relay changes state, only on whether a state change
        triggers an event."
    ::= { esPointConfigOutputEntry 3 }
    --1.3.6.1.4.1.3052.10.2.2.6.1.3

espcOutputActiveState OBJECT-TYPE
    SYNTAX DisplayString
    MAX-ACCESS read-write
    STATUS current
    DESCRIPTION
        "Which state is considered the active state: energized/de-energized."
    ::= { esPointConfigOutputEntry 4 }
    --1.3.6.1.4.1.3052.10.2.2.6.1.4

espcOutputType OBJECT-TYPE
    SYNTAX DisplayString
    MAX-ACCESS read-only
    STATUS current
    DESCRIPTION
        "Output type: RELAY, POWER, SSR, TTL."
    ::= { esPointConfigOutputEntry 5 }
    --1.3.6.1.4.1.3052.10.2.2.6.1.5

espcOutputAliasValue OBJECT-TYPE
    SYNTAX DisplayString
    MAX-ACCESS read-only
    STATUS current
    DESCRIPTION
        "Output alias corresponding to its event state."
    ::= { esPointConfigOutputEntry 6 }
    --1.3.6.1.4.1.3052.10.2.2.6.1.6

espcOutputAliasColor OBJECT-TYPE
    SYNTAX DisplayString
    MAX-ACCESS read-only
    STATUS current
    DESCRIPTION
        "Output color corresponding to its event state."
    ::= { esPointConfigOutputEntry 7 }
    --1.3.6.1.4.1.3052.10.2.2.6.1.7

espcOutputActiveAlias OBJECT-TYPE
    SYNTAX DisplayString
    MAX-ACCESS read-write
    STATUS current
    DESCRIPTION
        "Alias for the output active state."
    ::= { esPointConfigOutputEntry 10 }
    --1.3.6.1.4.1.3052.10.2.2.6.1.10

espcOutputActiveColor OBJECT-TYPE
    SYNTAX DisplayString
    MAX-ACCESS read-write
    STATUS current
    DESCRIPTION
        "Output color (as rendered in the web UI, in RGB hex format) corresponding
        to the output active state."
    ::= { esPointConfigOutputEntry 11 }
    --1.3.6.1.4.1.3052.10.2.2.6.1.11

espcOutputActiveActions OBJECT-TYPE
    SYNTAX DisplayString
    MAX-ACCESS read-write
    STATUS current
    DESCRIPTION
        "Actions for the output active event."
    ::= { esPointConfigOutputEntry 12 }
    --1.3.6.1.4.1.3052.10.2.2.6.1.12

espcOutputActiveTrapnum OBJECT-TYPE
    SYNTAX Integer32 (150..1199)
    MAX-ACCESS read-write
    STATUS current
    DESCRIPTION
        "Actions for the output active event."
    ::= { esPointConfigOutputEntry 13 }
    --1.3.6.1.4.1.3052.10.2.2.6.1.13

espcOutputActiveClass OBJECT-TYPE
    SYNTAX DisplayString
    MAX-ACCESS read-write
    STATUS current
    DESCRIPTION
        "Class (severity) for the output active event."
    ::= { esPointConfigOutputEntry 14 }
    --1.3.6.1.4.1.3052.10.2.2.6.1.14

espcOutputInactiveAlias OBJECT-TYPE
    SYNTAX DisplayString
    MAX-ACCESS read-write
    STATUS current
    DESCRIPTION
        "Alias for the output inactive state."
    ::= { esPointConfigOutputEntry 20 }
    --1.3.6.1.4.1.3052.10.2.2.6.1.20

espcOutputInactiveColor OBJECT-TYPE
    SYNTAX DisplayString
    MAX-ACCESS read-write
    STATUS current
    DESCRIPTION
        "Output color (as rendered in the web UI, in RGB hex format) corresponding
        to the output inactive state."
    ::= { esPointConfigOutputEntry 21 }
    --1.3.6.1.4.1.3052.10.2.2.6.1.21

espcOutputInactiveActions OBJECT-TYPE
    SYNTAX DisplayString
    MAX-ACCESS read-write
    STATUS current
    DESCRIPTION
        "Actions for the output inactive event."
    ::= { esPointConfigOutputEntry 22 }
    --1.3.6.1.4.1.3052.10.2.2.6.1.22

espcOutputInactiveTrapnum OBJECT-TYPE
    SYNTAX Integer32 (150..1199)
    MAX-ACCESS read-write
    STATUS current
    DESCRIPTION
        "Actions for the output inactive event."
    ::= { esPointConfigOutputEntry 23 }
    --1.3.6.1.4.1.3052.10.2.2.6.1.23

espcOutputInactiveClass OBJECT-TYPE
    SYNTAX DisplayString
    MAX-ACCESS read-write
    STATUS current
    DESCRIPTION
        "Class (severity) for the output inactive event."
    ::= { esPointConfigOutputEntry 24 }
    --1.3.6.1.4.1.3052.10.2.2.6.1.24

espcOutputGroup OBJECT-TYPE
    SYNTAX DisplayString
    MAX-ACCESS read-write
    STATUS current
    DESCRIPTION
        "Name for this Ouput Group"
    ::= { esPointConfigOutputEntry 25 }
    --1.3.6.1.4.1.3052.10.2.2.6.1.25

--***************************************************************************************
--Serial Port Section       2.3
--***************************************************************************************

numberPorts OBJECT-TYPE
    SYNTAX Integer32
    MAX-ACCESS read-only
    STATUS current
    DESCRIPTION
        "Number of RS-232 ports found.
        Range: 2 or 4"
    ::= { serialPorts 1 }
    --1.3.6.1.4.1.3052.10.2.3.1

portConfigTable OBJECT-TYPE
    SYNTAX SEQUENCE OF PortConfig
    MAX-ACCESS not-accessible
    STATUS current
    DESCRIPTION
        "Port config table"
    ::= { serialPorts 2 }
    --1.3.6.1.4.1.3052.10.2.3.2

portConfigEntry OBJECT-TYPE
    SYNTAX PortConfig
    MAX-ACCESS not-accessible
    STATUS current
    DESCRIPTION
        "Port config entry"
    INDEX { portConfigIndex }
    ::= { portConfigTable 1 }
    --1.3.6.1.4.1.3052.10.2.3.2.1

portConfigIndex OBJECT-TYPE
    SYNTAX Integer32 (1..16)
    MAX-ACCESS read-only
    STATUS current
    DESCRIPTION
        "Index for ports"
    ::= { portConfigEntry 1 }
    --1.3.6.1.4.1.3052.10.2.3.2.1.1

portConfigBaud OBJECT-TYPE
    SYNTAX Integer32
    MAX-ACCESS read-write
    STATUS current
    DESCRIPTION
        "Baud rate, 19200, 9600, etc."
    ::= { portConfigEntry 2 }
    --1.3.6.1.4.1.3052.10.2.3.2.1.2

portConfigDataFormat OBJECT-TYPE
    SYNTAX Integer32
    MAX-ACCESS read-write
    STATUS current
    DESCRIPTION
        "Value representing word length, parity, and
        stop bits: 0=8N1, 1=7E1, 2=7O1, 3=7N1, 4=8O2"
    ::= { portConfigEntry 3 }
    --1.3.6.1.4.1.3052.10.2.3.2.1.3

portConfigStripPtOutputLfs OBJECT-TYPE
    SYNTAX Integer32
    MAX-ACCESS read-write
    STATUS current
    DESCRIPTION
        "Strip passthrough LFs sent to device on this port:
        1=yes, 0=no."
    ::= { portConfigEntry 4 }
    --1.3.6.1.4.1.3052.10.2.3.2.1.4

portConfigStripPtInputLfs OBJECT-TYPE
    SYNTAX Integer32
    MAX-ACCESS read-write
    STATUS current
    DESCRIPTION
        "Strip passthrough LFs received from device on this
        port: 1=yes, 0=no."
    ::= { portConfigEntry 5 }
    --1.3.6.1.4.1.3052.10.2.3.2.1.5

portConfigMaskEnable OBJECT-TYPE
    SYNTAX Integer32
    MAX-ACCESS read-write
    STATUS current
    DESCRIPTION
        "1=Use the character mask on this port.  0=Do
        not use the mask.  When the mask is enabled,
        the following ASCII characters are ignored
        on the port:
        0, 1, 4-9, 11, 12, 14-31, 128-255.
        When the mask is disabled, all characters are
        accepted on the port."
    ::= { portConfigEntry 7 }
    --1.3.6.1.4.1.3052.10.2.3.2.1.7

portConfigDAEnable OBJECT-TYPE
    SYNTAX Integer32
    MAX-ACCESS read-write
    STATUS current
    DESCRIPTION
        "1=Enable the Data Alarm Evaluator for data
        on this port.  0=Do not evaluate data on this
        port."
    ::= { portConfigEntry 8 }
    --1.3.6.1.4.1.3052.10.2.3.2.1.8

portConfigStoreAlarmsDPT OBJECT-TYPE
    SYNTAX DisplayString
    MAX-ACCESS read-write
    STATUS current
    DESCRIPTION
        "ON/OFF: store alarms received during passthrough"
    ::= { portConfigEntry 9 }
    --1.3.6.1.4.1.3052.10.2.3.2.1.9

portConfigRecordTimeout OBJECT-TYPE
    SYNTAX Integer32
    MAX-ACCESS read-write
    STATUS current
    DESCRIPTION
        "Timeout after last unterminated data received upon
        which data collected so far is stored as a record."
    ::= { portConfigEntry 10 }
    --1.3.6.1.4.1.3052.10.2.3.2.1.10

portConfigDataType OBJECT-TYPE
    SYNTAX DisplayString
    MAX-ACCESS read-write
    STATUS current
    DESCRIPTION
        "How the port interprets incoming data: ASCII/BINARY"
    ::= { portConfigEntry 11 }
    --1.3.6.1.4.1.3052.10.2.3.2.1.11

portConfigEtxToCRLF OBJECT-TYPE
    SYNTAX DisplayString
    MAX-ACCESS read-write
    STATUS current
    DESCRIPTION
        "ON/OFF whether the port translates incoming ETX to CRLF"
    ::= { portConfigEntry 12 }
    --1.3.6.1.4.1.3052.10.2.3.2.1.12

portConfigMLREnable OBJECT-TYPE
    SYNTAX DisplayString
    MAX-ACCESS read-write
    STATUS current
    DESCRIPTION
        "ON/OFF Whether Multiline Records are collected on this port."
    ::= { portConfigEntry 13 }
    --1.3.6.1.4.1.3052.10.2.3.2.1.13

portConfigMLRStartField1Pos OBJECT-TYPE
    SYNTAX Integer32
    MAX-ACCESS read-write
    STATUS current
    DESCRIPTION
        "Position of MLR start field 1"
    ::= { portConfigEntry 14 }
    --1.3.6.1.4.1.3052.10.2.3.2.1.14

portConfigMLRStartField1Text OBJECT-TYPE
    SYNTAX DisplayString
    MAX-ACCESS read-write
    STATUS current
    DESCRIPTION
        "Text to match MLR start field 1"
    ::= { portConfigEntry 15 }
    --1.3.6.1.4.1.3052.10.2.3.2.1.15

portConfigMLRStartField2Pos OBJECT-TYPE
    SYNTAX Integer32
    MAX-ACCESS read-write
    STATUS current
    DESCRIPTION
        "Position of MLR start field 2"
    ::= { portConfigEntry 16 }
    --1.3.6.1.4.1.3052.10.2.3.2.1.16

portConfigMLRStartField2Text OBJECT-TYPE
    SYNTAX DisplayString
    MAX-ACCESS read-write
    STATUS current
    DESCRIPTION
        "Text to match MLR start field 2"
    ::= { portConfigEntry 17 }
    --1.3.6.1.4.1.3052.10.2.3.2.1.17

portConfigMLRNumLinesBefore OBJECT-TYPE
    SYNTAX Integer32
    MAX-ACCESS read-write
    STATUS current
    DESCRIPTION
        "Number of lines before the starting line which should
        be included in the MLR"
    ::= { portConfigEntry 18 }
    --1.3.6.1.4.1.3052.10.2.3.2.1.18

portConfigMLREndDetection OBJECT-TYPE
    SYNTAX DisplayString
    MAX-ACCESS read-write
    STATUS current
    DESCRIPTION
        "How the MLR parser determines what ends an MLR: by FORMULA,
        number of lines received so far (COUNT), or number of blank
        lines received so far (BLANKS)"
    ::= { portConfigEntry 19 }
    --1.3.6.1.4.1.3052.10.2.3.2.1.19

portConfigMLRLineCount OBJECT-TYPE
    SYNTAX Integer32
    MAX-ACCESS read-write
    STATUS current
    DESCRIPTION
        "Number of lines in the MLR (used by the end detection mode)"
    ::= { portConfigEntry 20 }
    --1.3.6.1.4.1.3052.10.2.3.2.1.20

portConfigMLREndField1Pos OBJECT-TYPE
    SYNTAX Integer32
    MAX-ACCESS read-write
    STATUS current
    DESCRIPTION
        "Position of MLR end field 1"
    ::= { portConfigEntry 21 }
    --1.3.6.1.4.1.3052.10.2.3.2.1.21

portConfigMLREndField1Text OBJECT-TYPE
    SYNTAX DisplayString
    MAX-ACCESS read-write
    STATUS current
    DESCRIPTION
        "Text to match MLR end field 1"
    ::= { portConfigEntry 22 }
    --1.3.6.1.4.1.3052.10.2.3.2.1.22

portConfigMLREndField2Pos OBJECT-TYPE
    SYNTAX Integer32
    MAX-ACCESS read-write
    STATUS current
    DESCRIPTION
        "Position of MLR end field 2"
    ::= { portConfigEntry 23 }
    --1.3.6.1.4.1.3052.10.2.3.2.1.23

portConfigMLREndField2Text OBJECT-TYPE
    SYNTAX DisplayString
    MAX-ACCESS read-write
    STATUS current
    DESCRIPTION
        "Text to match MLR end field 2"
    ::= { portConfigEntry 24 }
    --1.3.6.1.4.1.3052.10.2.3.2.1.24

portConfigMLRUseComplexRules OBJECT-TYPE
    SYNTAX DisplayString
    MAX-ACCESS read-write
    STATUS current
    DESCRIPTION
        "ON/OFF MLR parser uses complex rules (field possitions/
        formulas, etc.)"
    ::= { portConfigEntry 25 }
    --1.3.6.1.4.1.3052.10.2.3.2.1.25

portConfigBufferPT OBJECT-TYPE
    SYNTAX DisplayString
    MAX-ACCESS read-write
    STATUS current
    DESCRIPTION
        "ON/OFF records received during passthrough mode are
        buffered/stored in the database"
    ::= { portConfigEntry 26 }
    --1.3.6.1.4.1.3052.10.2.3.2.1.26

portConfigId OBJECT-TYPE
    SYNTAX DisplayString
    MAX-ACCESS read-write
    STATUS current
    DESCRIPTION
        "The text identifer for the port"
    ::= { portConfigEntry 27 }
    --1.3.6.1.4.1.3052.10.2.3.2.1.27

portConfigMode OBJECT-TYPE
    SYNTAX DisplayString
    MAX-ACCESS read-write
    STATUS current
    DESCRIPTION
        "Mode of the serial port."
    ::= { portConfigEntry 28 }
    --1.3.6.1.4.1.3052.10.2.3.2.1.28

portConfigHsk OBJECT-TYPE
    SYNTAX DisplayString
    MAX-ACCESS read-write
    STATUS current
    DESCRIPTION
        "Handshaking mode of the serial port."
    ::= { portConfigEntry 29 }
    --1.3.6.1.4.1.3052.10.2.3.2.1.29


--***************************************************************************************
--Network Section   2.4
--***************************************************************************************

eth1Mode OBJECT-TYPE
    SYNTAX DisplayString
    MAX-ACCESS read-only
    STATUS current
    DESCRIPTION
         "Mode of the Ethernet1 interface: STATIC,DHCP,VLAN"
    ::= { ethernet1 1 }
    --1.3.6.1.4.1.3052.10.2.4.1.1.1.1

eth1Address OBJECT-TYPE
    SYNTAX IpAddress
    MAX-ACCESS read-write
    STATUS current
    DESCRIPTION
        "Ethernet1 IP address"
    ::= { ethernet1 2 }
    --1.3.6.1.4.1.3052.10.2.4.1.1.1.2

eth1SubnetMask OBJECT-TYPE
    SYNTAX IpAddress
    MAX-ACCESS read-write
    STATUS current
    DESCRIPTION
        "Ethernet1 subnet mask"
    ::= { ethernet1 3 }
    --1.3.6.1.4.1.3052.10.2.4.1.1.1.3

eth1Router OBJECT-TYPE
    SYNTAX IpAddress
    MAX-ACCESS read-write
    STATUS current
    DESCRIPTION
        "Ethernet1 router"
    ::= { ethernet1 4 }
    --1.3.6.1.4.1.3052.10.2.4.1.1.1.4

-- Ethernet1 VLAN1

eth1VLAN1ID OBJECT-TYPE
    SYNTAX Integer32
    MAX-ACCESS read-write
    STATUS current
    DESCRIPTION
        "Ethernet1 VLAN1 ID"
    ::= { eth1VLAN1 1 }
    --1.3.6.1.4.1.3052.10.2.4.1.1.1.5.1.1

eth1VLAN1Priority OBJECT-TYPE
    SYNTAX Integer32
    MAX-ACCESS read-write
    STATUS current
    DESCRIPTION
        "Ethernet1 VLAN1 priority"
    ::= { eth1VLAN1 2 }
    --1.3.6.1.4.1.3052.10.2.4.1.1.1.5.1.2

eth1VLAN1Address OBJECT-TYPE
    SYNTAX IpAddress
    MAX-ACCESS read-write
    STATUS current
    DESCRIPTION
        "Ethernet1 VLAN1 IP address"
    ::= { eth1VLAN1 3 }
    --1.3.6.1.4.1.3052.10.2.4.1.1.1.5.1.3

eth1VLAN1SubnetMask OBJECT-TYPE
    SYNTAX IpAddress
    MAX-ACCESS read-write
    STATUS current
    DESCRIPTION
        "Ethernet1 VLAN1 subnet mask"
    ::= { eth1VLAN1 4 }
    --1.3.6.1.4.1.3052.10.2.4.1.1.1.5.1.4

eth1VLAN1Router OBJECT-TYPE
    SYNTAX IpAddress
    MAX-ACCESS read-write
    STATUS current
    DESCRIPTION
        "Ethernet1 VLAN1 router"
    ::= { eth1VLAN1 5 }
    --1.3.6.1.4.1.3052.10.2.4.1.1.1.5.1.5

-- Ethernet1 VLAN2

eth1VLAN2ID OBJECT-TYPE
    SYNTAX Integer32
    MAX-ACCESS read-write
    STATUS current
    DESCRIPTION
        "Ethernet1 VLAN2 ID"
    ::= { eth1VLAN2 1 }
    --1.3.6.1.4.1.3052.10.2.4.1.1.1.5.2.1

eth1VLAN2Priority OBJECT-TYPE
    SYNTAX Integer32
    MAX-ACCESS read-write
    STATUS current
    DESCRIPTION
        "Ethernet1 VLAN2 priority"
    ::= { eth1VLAN2 2 }
    --1.3.6.1.4.1.3052.10.2.4.1.1.1.5.2.2

eth1VLAN2Address OBJECT-TYPE
    SYNTAX IpAddress
    MAX-ACCESS read-write
    STATUS current
    DESCRIPTION
        "Ethernet1 VLAN2 IP address"
    ::= { eth1VLAN2 3 }
    --1.3.6.1.4.1.3052.10.2.4.1.1.1.5.2.3

eth1VLAN2SubnetMask OBJECT-TYPE
    SYNTAX IpAddress
    MAX-ACCESS read-write
    STATUS current
    DESCRIPTION
        "Ethernet1 VLAN2 subnet mask"
    ::= { eth1VLAN2 4 }
    --1.3.6.1.4.1.3052.10.2.4.1.1.1.5.2.4

eth1VLAN2Router OBJECT-TYPE
    SYNTAX IpAddress
    MAX-ACCESS read-write
    STATUS current
    DESCRIPTION
        "Ethernet1 VLAN2 router"
    ::= { eth1VLAN2 5 }
    --1.3.6.1.4.1.3052.10.2.4.1.1.1.5.2.5

-- Ethernet1 VLAN3

eth1VLAN3ID OBJECT-TYPE
    SYNTAX Integer32
    MAX-ACCESS read-write
    STATUS current
    DESCRIPTION
        "Ethernet1 VLAN3 ID"
    ::= { eth1VLAN3 1 }
    --1.3.6.1.4.1.3052.10.2.4.1.1.1.5.3.1

eth1VLAN3Priority OBJECT-TYPE
    SYNTAX Integer32
    MAX-ACCESS read-write
    STATUS current
    DESCRIPTION
        "Ethernet1 VLAN3 priority"
    ::= { eth1VLAN3 2 }
    --1.3.6.1.4.1.3052.10.2.4.1.1.1.5.3.2

eth1VLAN3Address OBJECT-TYPE
    SYNTAX IpAddress
    MAX-ACCESS read-write
    STATUS current
    DESCRIPTION
        "Ethernet1 VLAN3 IP address"
    ::= { eth1VLAN3 3 }
    --1.3.6.1.4.1.3052.10.2.4.1.1.1.5.3.3

eth1VLAN3SubnetMask OBJECT-TYPE
    SYNTAX IpAddress
    MAX-ACCESS read-write
    STATUS current
    DESCRIPTION
        "Ethernet1 VLAN3 subnet mask"
    ::= { eth1VLAN3 4 }
    --1.3.6.1.4.1.3052.10.2.4.1.1.1.5.3.4

eth1VLAN3Router OBJECT-TYPE
    SYNTAX IpAddress
    MAX-ACCESS read-write
    STATUS current
    DESCRIPTION
        "Ethernet1 VLAN3 router"
    ::= { eth1VLAN3 5 }
    --1.3.6.1.4.1.3052.10.2.4.1.1.1.5.3.5

-- Ethernet1 VLAN4

eth1VLAN4ID OBJECT-TYPE
    SYNTAX Integer32
    MAX-ACCESS read-write
    STATUS current
    DESCRIPTION
        "Ethernet1 VLAN4 ID"
    ::= { eth1VLAN4 1 }
    --1.3.6.1.4.1.3052.10.2.4.1.1.1.5.4.1

eth1VLAN4Priority OBJECT-TYPE
    SYNTAX Integer32
    MAX-ACCESS read-write
    STATUS current
    DESCRIPTION
        "Ethernet1 VLAN4 priority"
    ::= { eth1VLAN4 2 }
    --1.3.6.1.4.1.3052.10.2.4.1.1.1.5.4.2

eth1VLAN4Address OBJECT-TYPE
    SYNTAX IpAddress
    MAX-ACCESS read-write
    STATUS current
    DESCRIPTION
        "Ethernet1 VLAN4 IP address"
    ::= { eth1VLAN4 3 }
    --1.3.6.1.4.1.3052.10.2.4.1.1.1.5.4.3

eth1VLAN4SubnetMask OBJECT-TYPE
    SYNTAX IpAddress
    MAX-ACCESS read-write
    STATUS current
    DESCRIPTION
        "Ethernet1 VLAN4 subnet mask"
    ::= { eth1VLAN4 4 }
    --1.3.6.1.4.1.3052.10.2.4.1.1.1.5.4.4

eth1VLAN4Router OBJECT-TYPE
    SYNTAX IpAddress
    MAX-ACCESS read-write
    STATUS current
    DESCRIPTION
        "Ethernet1 VLAN4 router"
    ::= { eth1VLAN4 5 }
    --1.3.6.1.4.1.3052.10.2.4.1.1.1.5.4.5

-- Ethernet1 VLAN5

eth1VLAN5ID OBJECT-TYPE
    SYNTAX Integer32
    MAX-ACCESS read-write
    STATUS current
    DESCRIPTION
        "Ethernet1 VLAN5 ID"
    ::= { eth1VLAN5 1 }
    --1.3.6.1.4.1.3052.10.2.4.1.1.1.5.5.1

eth1VLAN5Priority OBJECT-TYPE
    SYNTAX Integer32
    MAX-ACCESS read-write
    STATUS current
    DESCRIPTION
        "Ethernet1 VLAN5 priority"
    ::= { eth1VLAN5 2 }
    --1.3.6.1.4.1.3052.10.2.4.1.1.1.5.5.2

eth1VLAN5Address OBJECT-TYPE
    SYNTAX IpAddress
    MAX-ACCESS read-write
    STATUS current
    DESCRIPTION
        "Ethernet1 VLAN5 IP address"
    ::= { eth1VLAN5 3 }
    --1.3.6.1.4.1.3052.10.2.4.1.1.1.5.5.3

eth1VLAN5SubnetMask OBJECT-TYPE
    SYNTAX IpAddress
    MAX-ACCESS read-write
    STATUS current
    DESCRIPTION
        "Ethernet1 VLAN5 subnet mask"
    ::= { eth1VLAN5 4 }
    --1.3.6.1.4.1.3052.10.2.4.1.1.1.5.5.4

eth1VLAN5Router OBJECT-TYPE
    SYNTAX IpAddress
    MAX-ACCESS read-write
    STATUS current
    DESCRIPTION
        "Ethernet1 VLAN5 router"
    ::= { eth1VLAN5 5 }
    --1.3.6.1.4.1.3052.10.2.4.1.1.1.5.5.5

-- Ethernet1 VLAN6

eth1VLAN6ID OBJECT-TYPE
    SYNTAX Integer32
    MAX-ACCESS read-write
    STATUS current
    DESCRIPTION
        "Ethernet1 VLAN6 ID"
    ::= { eth1VLAN6 1 }
    --1.3.6.1.4.1.3052.10.2.4.1.1.1.5.6.1

eth1VLAN6Priority OBJECT-TYPE
    SYNTAX Integer32
    MAX-ACCESS read-write
    STATUS current
    DESCRIPTION
        "Ethernet1 VLAN6 priority"
    ::= { eth1VLAN6 2 }
    --1.3.6.1.4.1.3052.10.2.4.1.1.1.5.6.2

eth1VLAN6Address OBJECT-TYPE
    SYNTAX IpAddress
    MAX-ACCESS read-write
    STATUS current
    DESCRIPTION
        "Ethernet1 VLAN6 IP address"
    ::= { eth1VLAN6 3 }
    --1.3.6.1.4.1.3052.10.2.4.1.1.1.5.6.3

eth1VLAN6SubnetMask OBJECT-TYPE
    SYNTAX IpAddress
    MAX-ACCESS read-write
    STATUS current
    DESCRIPTION
        "Ethernet1 VLAN6 subnet mask"
    ::= { eth1VLAN6 4 }
    --1.3.6.1.4.1.3052.10.2.4.1.1.1.5.6.4

eth1VLAN6Router OBJECT-TYPE
    SYNTAX IpAddress
    MAX-ACCESS read-write
    STATUS current
    DESCRIPTION
        "Ethernet1 VLAN6 router"
    ::= { eth1VLAN6 5 }
    --1.3.6.1.4.1.3052.10.2.4.1.1.1.5.6.5

eth1MAC OBJECT-TYPE
    SYNTAX DisplayString
    MAX-ACCESS read-only
    STATUS current
    DESCRIPTION
        "Ethernet1 MAC"
    ::= { ethernet1 6 }
    --1.3.6.1.4.1.3052.10.2.4.1.1.1.6

eth1IPv6Mode OBJECT-TYPE
    SYNTAX DisplayString
    MAX-ACCESS read-write
    STATUS current
    DESCRIPTION
        "Controls IPv6 operation for this Ethernet interface."
    ::= { eth1IPv6 1 }
    --1.3.6.1.4.1.3052.10.2.4.1.1.1.7.1

eth1IPv6StaticAddress OBJECT-TYPE
    SYNTAX DisplayString
    MAX-ACCESS read-write
    STATUS current
    DESCRIPTION
        "he static IPv6 address to use for this interface when in
        operating in STATIC mode."
    ::= { eth1IPv6Static 1 }
    --1.3.6.1.4.1.3052.10.2.4.1.1.1.7.2.1

eth1IPv6StaticRouter OBJECT-TYPE
    SYNTAX DisplayString
    MAX-ACCESS read-write
    STATUS current
    DESCRIPTION
        "The IPv6 router to engage as the default router when this
        interface operates in STATIC mode."
    ::= { eth1IPv6Static 2 }
    --1.3.6.1.4.1.3052.10.2.4.1.1.1.7.2.1

eth1IPv6AutoAddress1 OBJECT-TYPE
    SYNTAX DisplayString
    MAX-ACCESS read-only
    STATUS current
    DESCRIPTION
        "One of the automatically-acquired IPv6 addresses."
    ::= { eth1IPv6Auto 1 }
    --1.3.6.1.4.1.3052.10.2.4.1.1.1.7.3.1

eth1IPv6AutoAddress2 OBJECT-TYPE
    SYNTAX DisplayString
    MAX-ACCESS read-only
    STATUS current
    DESCRIPTION
        "One of the automatically-acquired IPv6 addresses."
    ::= { eth1IPv6Auto 2 }
    --1.3.6.1.4.1.3052.10.2.4.1.1.1.7.3.2

eth1IPv6AutoAddress3 OBJECT-TYPE
    SYNTAX DisplayString
    MAX-ACCESS read-only
    STATUS current
    DESCRIPTION
        "One of the automatically-acquired IPv6 addresses."
    ::= { eth1IPv6Auto 3 }
    --1.3.6.1.4.1.3052.10.2.4.1.1.1.7.3.3

eth1IPv6AutoAddress4 OBJECT-TYPE
    SYNTAX DisplayString
    MAX-ACCESS read-only
    STATUS current
    DESCRIPTION
        "One of the automatically-acquired IPv6 addresses."
    ::= { eth1IPv6Auto 4 }
    --1.3.6.1.4.1.3052.10.2.4.1.1.1.7.3.4

eth1IPv6LinkLocalAddress OBJECT-TYPE
    SYNTAX DisplayString
    MAX-ACCESS read-only
    STATUS current
    DESCRIPTION
        "The link local IPv6 address for this interface. This is
        present when the IPv6 mode is not OFF."
    ::= { eth1IPv6 4 }
    --1.3.6.1.4.1.3052.10.2.4.1.1.1.7.4



eth2Mode OBJECT-TYPE
    SYNTAX DisplayString
    MAX-ACCESS read-only
    STATUS current
    DESCRIPTION
         "Mode of the Ethernet2 interface: STATIC,DHCP,VLAN"
    ::= { ethernet2 1 }
    --1.3.6.1.4.1.3052.10.2.4.1.1.2.1

eth2Address OBJECT-TYPE
    SYNTAX IpAddress
    MAX-ACCESS read-write
    STATUS current
    DESCRIPTION
        "Ethernet2 IP address"
    ::= { ethernet2 2 }
    --1.3.6.1.4.1.3052.10.2.4.1.1.2.2

eth2SubnetMask OBJECT-TYPE
    SYNTAX IpAddress
    MAX-ACCESS read-write
    STATUS current
    DESCRIPTION
        "Ethernet2 subnet mask"
    ::= { ethernet2 3 }
    --1.3.6.1.4.1.3052.10.2.4.1.1.2.3

eth2Router OBJECT-TYPE
    SYNTAX IpAddress
    MAX-ACCESS read-write
    STATUS current
    DESCRIPTION
        "Ethernet2 router"
    ::= { ethernet2 4 }
    --1.3.6.1.4.1.3052.10.2.4.1.1.2.4


-- Ethernet2 VLAN1

eth2VLAN1ID OBJECT-TYPE
    SYNTAX Integer32
    MAX-ACCESS read-write
    STATUS current
    DESCRIPTION
        "Ethernet2 VLAN1 ID"
    ::= { eth2VLAN1 1 }
    --1.3.6.1.4.1.3052.10.2.4.1.1.2.5.1.1

eth2VLAN1Priority OBJECT-TYPE
    SYNTAX Integer32
    MAX-ACCESS read-write
    STATUS current
    DESCRIPTION
        "Ethernet2 VLAN1 priority"
    ::= { eth2VLAN1 2 }
    --1.3.6.1.4.1.3052.10.2.4.1.1.2.5.1.2

eth2VLAN1Address OBJECT-TYPE
    SYNTAX IpAddress
    MAX-ACCESS read-write
    STATUS current
    DESCRIPTION
        "Ethernet2 VLAN1 IP address"
    ::= { eth2VLAN1 3 }
    --1.3.6.1.4.1.3052.10.2.4.1.1.2.5.1.3

eth2VLAN1SubnetMask OBJECT-TYPE
    SYNTAX IpAddress
    MAX-ACCESS read-write
    STATUS current
    DESCRIPTION
        "Ethernet2 VLAN1 subnet mask"
    ::= { eth2VLAN1 4 }
    --1.3.6.1.4.1.3052.10.2.4.1.1.2.5.1.4

eth2VLAN1Router OBJECT-TYPE
    SYNTAX IpAddress
    MAX-ACCESS read-write
    STATUS current
    DESCRIPTION
        "Ethernet2 VLAN1 router"
    ::= { eth2VLAN1 5 }
    --1.3.6.1.4.1.3052.10.2.4.1.1.2.5.1.5

-- Ethernet2 VLAN2

eth2VLAN2ID OBJECT-TYPE
    SYNTAX Integer32
    MAX-ACCESS read-write
    STATUS current
    DESCRIPTION
        "Ethernet2 VLAN2 ID"
    ::= { eth2VLAN2 1 }
    --1.3.6.1.4.1.3052.10.2.4.1.1.2.5.2.1

eth2VLAN2Priority OBJECT-TYPE
    SYNTAX Integer32
    MAX-ACCESS read-write
    STATUS current
    DESCRIPTION
        "Ethernet2 VLAN2 priority"
    ::= { eth2VLAN2 2 }
    --1.3.6.1.4.1.3052.10.2.4.1.1.2.5.2.2

eth2VLAN2Address OBJECT-TYPE
    SYNTAX IpAddress
    MAX-ACCESS read-write
    STATUS current
    DESCRIPTION
        "Ethernet2 VLAN2 IP address"
    ::= { eth2VLAN2 3 }
    --1.3.6.1.4.1.3052.10.2.4.1.1.2.5.2.3

eth2VLAN2SubnetMask OBJECT-TYPE
    SYNTAX IpAddress
    MAX-ACCESS read-write
    STATUS current
    DESCRIPTION
        "Ethernet2 VLAN2 subnet mask"
    ::= { eth2VLAN2 4 }
    --1.3.6.1.4.1.3052.10.2.4.1.1.2.5.2.4

eth2VLAN2Router OBJECT-TYPE
    SYNTAX IpAddress
    MAX-ACCESS read-write
    STATUS current
    DESCRIPTION
        "Ethernet2 VLAN2 router"
    ::= { eth2VLAN2 5 }
    --1.3.6.1.4.1.3052.10.2.4.1.1.2.5.2.5

-- Ethernet2 VLAN3

eth2VLAN3ID OBJECT-TYPE
    SYNTAX Integer32
    MAX-ACCESS read-write
    STATUS current
    DESCRIPTION
        "Ethernet2 VLAN3 ID"
    ::= { eth2VLAN3 1 }
    --1.3.6.1.4.1.3052.10.2.4.1.1.2.5.3.1

eth2VLAN3Priority OBJECT-TYPE
    SYNTAX Integer32
    MAX-ACCESS read-write
    STATUS current
    DESCRIPTION
        "Ethernet2 VLAN3 priority"
    ::= { eth2VLAN3 2 }
    --1.3.6.1.4.1.3052.10.2.4.1.1.2.5.3.2

eth2VLAN3Address OBJECT-TYPE
    SYNTAX IpAddress
    MAX-ACCESS read-write
    STATUS current
    DESCRIPTION
        "Ethernet2 VLAN3 IP address"
    ::= { eth2VLAN3 3 }
    --1.3.6.1.4.1.3052.10.2.4.1.1.2.5.3.3

eth2VLAN3SubnetMask OBJECT-TYPE
    SYNTAX IpAddress
    MAX-ACCESS read-write
    STATUS current
    DESCRIPTION
        "Ethernet2 VLAN3 subnet mask"
    ::= { eth2VLAN3 4 }
    --1.3.6.1.4.1.3052.10.2.4.1.1.2.5.3.4

eth2VLAN3Router OBJECT-TYPE
    SYNTAX IpAddress
    MAX-ACCESS read-write
    STATUS current
    DESCRIPTION
        "Ethernet2 VLAN3 router"
    ::= { eth2VLAN3 5 }
    --1.3.6.1.4.1.3052.10.2.4.1.1.2.5.3.5

-- Ethernet2 VLAN4

eth2VLAN4ID OBJECT-TYPE
    SYNTAX Integer32
    MAX-ACCESS read-write
    STATUS current
    DESCRIPTION
        "Ethernet2 VLAN4 ID"
    ::= { eth2VLAN4 1 }
    --1.3.6.1.4.1.3052.10.2.4.1.1.2.5.4.1

eth2VLAN4Priority OBJECT-TYPE
    SYNTAX Integer32
    MAX-ACCESS read-write
    STATUS current
    DESCRIPTION
        "Ethernet2 VLAN4 priority"
    ::= { eth2VLAN4 2 }
    --1.3.6.1.4.1.3052.10.2.4.1.1.2.5.4.2

eth2VLAN4Address OBJECT-TYPE
    SYNTAX IpAddress
    MAX-ACCESS read-write
    STATUS current
    DESCRIPTION
        "Ethernet2 VLAN4 IP address"
    ::= { eth2VLAN4 3 }
    --1.3.6.1.4.1.3052.10.2.4.1.1.2.5.4.3

eth2VLAN4SubnetMask OBJECT-TYPE
    SYNTAX IpAddress
    MAX-ACCESS read-write
    STATUS current
    DESCRIPTION
        "Ethernet2 VLAN4 subnet mask"
    ::= { eth2VLAN4 4 }
    --1.3.6.1.4.1.3052.10.2.4.1.1.2.5.4.4

eth2VLAN4Router OBJECT-TYPE
    SYNTAX IpAddress
    MAX-ACCESS read-write
    STATUS current
    DESCRIPTION
        "Ethernet2 VLAN4 router"
    ::= { eth2VLAN4 5 }
    --1.3.6.1.4.1.3052.10.2.4.1.1.2.5.4.5

-- Ethernet2 VLAN5

eth2VLAN5ID OBJECT-TYPE
    SYNTAX Integer32
    MAX-ACCESS read-write
    STATUS current
    DESCRIPTION
        "Ethernet2 VLAN5 ID"
    ::= { eth2VLAN5 1 }
    --1.3.6.1.4.1.3052.10.2.4.1.1.2.5.5.1

eth2VLAN5Priority OBJECT-TYPE
    SYNTAX Integer32
    MAX-ACCESS read-write
    STATUS current
    DESCRIPTION
        "Ethernet2 VLAN5 priority"
    ::= { eth2VLAN5 2 }
    --1.3.6.1.4.1.3052.10.2.4.1.1.2.5.5.2

eth2VLAN5Address OBJECT-TYPE
    SYNTAX IpAddress
    MAX-ACCESS read-write
    STATUS current
    DESCRIPTION
        "Ethernet2 VLAN5 IP address"
    ::= { eth2VLAN5 3 }
    --1.3.6.1.4.1.3052.10.2.4.1.1.2.5.5.3

eth2VLAN5SubnetMask OBJECT-TYPE
    SYNTAX IpAddress
    MAX-ACCESS read-write
    STATUS current
    DESCRIPTION
        "Ethernet2 VLAN5 subnet mask"
    ::= { eth2VLAN5 4 }
    --1.3.6.1.4.1.3052.10.2.4.1.1.2.5.5.4

eth2VLAN5Router OBJECT-TYPE
    SYNTAX IpAddress
    MAX-ACCESS read-write
    STATUS current
    DESCRIPTION
        "Ethernet2 VLAN5 router"
    ::= { eth2VLAN5 5 }
    --1.3.6.1.4.1.3052.10.2.4.1.1.2.5.5.5

-- Ethernet2 VLAN6

eth2VLAN6ID OBJECT-TYPE
    SYNTAX Integer32
    MAX-ACCESS read-write
    STATUS current
    DESCRIPTION
        "Ethernet2 VLAN6 ID"
    ::= { eth2VLAN6 1 }
    --1.3.6.1.4.1.3052.10.2.4.1.1.2.5.6.1

eth2VLAN6Priority OBJECT-TYPE
    SYNTAX Integer32
    MAX-ACCESS read-write
    STATUS current
    DESCRIPTION
        "Ethernet2 VLAN6 priority"
    ::= { eth2VLAN6 2 }
    --1.3.6.1.4.1.3052.10.2.4.1.1.2.5.6.2

eth2VLAN6Address OBJECT-TYPE
    SYNTAX IpAddress
    MAX-ACCESS read-write
    STATUS current
    DESCRIPTION
        "Ethernet2 VLAN6 IP address"
    ::= { eth2VLAN6 3 }
    --1.3.6.1.4.1.3052.10.2.4.1.1.2.5.6.3

eth2VLAN6SubnetMask OBJECT-TYPE
    SYNTAX IpAddress
    MAX-ACCESS read-write
    STATUS current
    DESCRIPTION
        "Ethernet2 VLAN6 subnet mask"
    ::= { eth2VLAN6 4 }
    --1.3.6.1.4.1.3052.10.2.4.1.1.2.5.6.4

eth2VLAN6Router OBJECT-TYPE
    SYNTAX IpAddress
    MAX-ACCESS read-write
    STATUS current
    DESCRIPTION
        "Ethernet2 VLAN6 router"
    ::= { eth2VLAN6 5 }
    --1.3.6.1.4.1.3052.10.2.4.1.1.2.5.6.5

eth2MAC OBJECT-TYPE
    SYNTAX DisplayString
    MAX-ACCESS read-only
    STATUS current
    DESCRIPTION
        "Ethernet2 MAC"
    ::= { ethernet2 6 }
    --1.3.6.1.4.1.3052.10.2.4.1.1.2.6

eth2IPv6Mode OBJECT-TYPE
    SYNTAX DisplayString
    MAX-ACCESS read-write
    STATUS current
    DESCRIPTION
        "Controls IPv6 operation for this Ethernet interface."
    ::= { eth2IPv6 1 }
    --1.3.6.1.4.1.3052.10.2.4.1.1.2.7.1

eth2IPv6StaticAddress OBJECT-TYPE
    SYNTAX DisplayString
    MAX-ACCESS read-write
    STATUS current
    DESCRIPTION
        "he static IPv6 address to use for this interface when in
        operating in STATIC mode."
    ::= { eth2IPv6Static 1 }
    --1.3.6.1.4.1.3052.10.2.4.1.1.2.7.2.1

eth2IPv6StaticRouter OBJECT-TYPE
    SYNTAX DisplayString
    MAX-ACCESS read-write
    STATUS current
    DESCRIPTION
        "The IPv6 router to engage as the default router when this
        interface operates in STATIC mode."
    ::= { eth2IPv6Static 2 }
    --1.3.6.1.4.1.3052.10.2.4.1.1.2.7.2.1

eth2IPv6AutoAddress1 OBJECT-TYPE
    SYNTAX DisplayString
    MAX-ACCESS read-only
    STATUS current
    DESCRIPTION
        "One of the automatically-acquired IPv6 addresses."
    ::= { eth2IPv6Auto 1 }
    --1.3.6.1.4.1.3052.10.2.4.1.1.2.7.3.1

eth2IPv6AutoAddress2 OBJECT-TYPE
    SYNTAX DisplayString
    MAX-ACCESS read-only
    STATUS current
    DESCRIPTION
        "One of the automatically-acquired IPv6 addresses."
    ::= { eth2IPv6Auto 2 }
    --1.3.6.1.4.1.3052.10.2.4.1.1.2.7.3.2

eth2IPv6AutoAddress3 OBJECT-TYPE
    SYNTAX DisplayString
    MAX-ACCESS read-only
    STATUS current
    DESCRIPTION
        "One of the automatically-acquired IPv6 addresses."
    ::= { eth2IPv6Auto 3 }
    --1.3.6.1.4.1.3052.10.2.4.1.1.2.7.3.3

eth2IPv6AutoAddress4 OBJECT-TYPE
    SYNTAX DisplayString
    MAX-ACCESS read-only
    STATUS current
    DESCRIPTION
        "One of the automatically-acquired IPv6 addresses."
    ::= { eth2IPv6Auto 4 }
    --1.3.6.1.4.1.3052.10.2.4.1.1.2.7.3.4

eth2IPv6LinkLocalAddress OBJECT-TYPE
    SYNTAX DisplayString
    MAX-ACCESS read-only
    STATUS current
    DESCRIPTION
        "The link local IPv6 address for this interface. This is
        present when the IPv6 mode is not OFF."
    ::= { eth2IPv6 4 }
    --1.3.6.1.4.1.3052.10.2.4.1.1.2.7.4



defaultRouter OBJECT-TYPE
    SYNTAX DisplayString
    MAX-ACCESS read-write
    STATUS current
    DESCRIPTION
        "The default router/gateway"
    ::= { network 2 }
    --1.3.6.1.4.1.3052.10.2.4.2

-- DNS

dnsTable OBJECT-TYPE
    SYNTAX SEQUENCE OF DNSConfig
    MAX-ACCESS not-accessible
    STATUS current
    DESCRIPTION
        "DNS server address table"
    ::= { network 3 }
    --1.3.6.1.4.1.3052.10.2.4.3

dnsEntry OBJECT-TYPE
    SYNTAX DNSConfig
    MAX-ACCESS not-accessible
    STATUS current
    DESCRIPTION
        "DNS server address entry"
    INDEX { dnsIndex }
    ::= { dnsTable 1 }
    --1.3.6.1.4.1.3052.10.2.4.3.1

dnsIndex OBJECT-TYPE
    SYNTAX Integer32 (1..2)
    MAX-ACCESS read-only
    STATUS current
    DESCRIPTION
        "Index for DNS server address"
    ::= { dnsEntry 1 }
    --1.3.6.1.4.1.3052.10.2.4.3.1.1

dnsAddress OBJECT-TYPE
    SYNTAX IpAddress
    MAX-ACCESS read-write
    STATUS current
    DESCRIPTION
        "DNS server address"
    ::= { dnsEntry 2 }
    --1.3.6.1.4.1.3052.10.2.4.3.1.2

hostname OBJECT-TYPE
    SYNTAX DisplayString
    MAX-ACCESS read-write
    STATUS current
    DESCRIPTION
        "The hostname of the unit"
    ::= { network 4 }
    --1.3.6.1.4.1.3052.10.2.4.4

hostTable OBJECT-TYPE
    SYNTAX SEQUENCE OF HostConfig
    MAX-ACCESS not-accessible
    STATUS current
    DESCRIPTION
        "Static host table"
    ::= { network 5 }
    --1.3.6.1.4.1.3052.10.2.4.5

hostEntry OBJECT-TYPE
    SYNTAX HostConfig
    MAX-ACCESS not-accessible
    STATUS current
    DESCRIPTION
        "Static host entry"
    INDEX { hostIndex }
    ::= { hostTable 1 }
    --1.3.6.1.4.1.3052.10.2.4.5.1

hostIndex OBJECT-TYPE
    SYNTAX Integer32 (1..2)
    MAX-ACCESS read-only
    STATUS current
    DESCRIPTION
        "Index for static host"
    ::= { hostEntry 1 }
    --1.3.6.1.4.1.3052.10.2.4.5.1.1

hostDeclaration OBJECT-TYPE
    SYNTAX DisplayString
    MAX-ACCESS read-write
    STATUS current
    DESCRIPTION
        "Static host declaration string (i.e. 'address hostname')"
    ::= { hostEntry 2 }
    --1.3.6.1.4.1.3052.10.2.4.5.1.2

-- Network Command Processor

ncpDuplex OBJECT-TYPE
    SYNTAX Integer32
    MAX-ACCESS read-write
    STATUS current
    DESCRIPTION
        "For network command processor: 1=Input characters are echoed; 0=no echo."
    ::= { network 6 }
    --1.3.6.1.4.1.3052.10.2.4.6

ncpTimeout OBJECT-TYPE
    SYNTAX Integer32
    MAX-ACCESS read-write
    STATUS current
    DESCRIPTION
        "Network command processor inactivity timeout"
    ::= { network 7 }
    --1.3.6.1.4.1.3052.10.2.4.7

-- SNMP

snmpAgentEnable OBJECT-TYPE
    SYNTAX DisplayString
    MAX-ACCESS read-write
    STATUS current
    DESCRIPTION
        "ON/OFF for snmp agent"
    ::= { snmp 1 }
    --1.3.6.1.4.1.3052.10.2.4.8.1

snmpNotificationCaptureEnable OBJECT-TYPE
    SYNTAX DisplayString
    MAX-ACCESS read-write
    STATUS current
    DESCRIPTION
        "ON/OFF unit receives and stores SNMP traps/informs"
    ::= { snmp 5 }
    --1.3.6.1.4.1.3052.10.2.4.8.5

snmpNotificationCaptureFile OBJECT-TYPE
    SYNTAX DisplayString
    MAX-ACCESS read-write
    STATUS current
    DESCRIPTION
        "File to which unit stores received SNMP traps/informs"
    ::= { snmp 6 }
    --1.3.6.1.4.1.3052.10.2.4.8.6

snmpNtfnAttempts OBJECT-TYPE
    SYNTAX Integer32
    MAX-ACCESS read-write
    STATUS current
    DESCRIPTION
        "Maximum of times the unit attempts to send a notification
        (trap/inform) in 1 cycle"
    ::= { snmpNotificationTx 1 }
    --1.3.6.1.4.1.3052.10.2.4.8.7.1

snmpNtfnTimeout OBJECT-TYPE
    SYNTAX Integer32
    MAX-ACCESS read-write
    STATUS current
    DESCRIPTION
        "Number of seconds between retries of sending a notification"
    ::= { snmpNotificationTx 2 }
    --1.3.6.1.4.1.3052.10.2.4.8.7.2

snmpNtfnCycles OBJECT-TYPE
    SYNTAX Integer32
    MAX-ACCESS read-write
    STATUS current
    DESCRIPTION
        "Number of times the unit attempts a group of attempts to send
        a notification (a cycle)"
    ::= { snmpNotificationTx 3 }
    --1.3.6.1.4.1.3052.10.2.4.8.7.3

snmpNtfnSnooze OBJECT-TYPE
    SYNTAX Integer32
    MAX-ACCESS read-write
    STATUS current
    DESCRIPTION
        "Minutes between cycles"
    ::= { snmpNotificationTx 4 }
    --1.3.6.1.4.1.3052.10.2.4.8.7.4

-- SNMP proxy

snmpProxyTable OBJECT-TYPE
    SYNTAX SEQUENCE OF SNMPProxyTable
    MAX-ACCESS not-accessible
    STATUS current
    DESCRIPTION
        "Table of SNMP proxy entries"
    ::= { snmpProxy 1 }
    --1.3.6.1.4.1.3052.10.2.4.8.8.1

snmpProxyEntry OBJECT-TYPE
    SYNTAX SNMPProxyTable
    MAX-ACCESS not-accessible
    STATUS current
    DESCRIPTION
        "Entry for SNMP proxy table"
    INDEX { snmpProxyIndex }
    ::= { snmpProxyTable 1 }
    --1.3.6.1.4.1.3052.10.2.4.8.8.1.1

snmpProxyIndex OBJECT-TYPE
    SYNTAX Integer32 (1..8)
    MAX-ACCESS read-only
    STATUS current
    DESCRIPTION
        "Index for SNMP proxy table"
    ::= { snmpProxyEntry 1 }
    --1.3.6.1.4.1.3052.10.2.4.8.8.1.1.1

snmpProxyEgressOIDBranch OBJECT-TYPE
    SYNTAX DisplayString
    MAX-ACCESS read-write
    STATUS current
    DESCRIPTION
        "The OID branch to trigger the proxy function.  This should cover
        the device to proxy.  If blank then this proxy entry is disabled."
    ::= { snmpProxyEntry 2 }
    --1.3.6.1.4.1.3052.10.2.4.8.8.1.1.2

snmpProxyIP OBJECT-TYPE
    SYNTAX DisplayString
    MAX-ACCESS read-write
    STATUS current
    DESCRIPTION
        "The IP address of the device to proxy."
    ::= { snmpProxyEntry 3 }
    --1.3.6.1.4.1.3052.10.2.4.8.8.1.1.3

snmpProxyPort OBJECT-TYPE
    SYNTAX Integer32 (1..65535)
    MAX-ACCESS read-write
    STATUS current
    DESCRIPTION
        "The UDP port on which the device to proxy listens."
    ::= { snmpProxyEntry 4 }
    --1.3.6.1.4.1.3052.10.2.4.8.8.1.1.4

snmpProxyIngressOIDBranch OBJECT-TYPE
    SYNTAX DisplayString
    MAX-ACCESS read-write
    STATUS current
    DESCRIPTION
        "The OID branch to be remapped to egress OID branch to trigger the
        proxy function.  If blank then the egress OID branch is proxied
        without remapping."
    ::= { snmpProxyEntry 5 }
    --1.3.6.1.4.1.3052.10.2.4.8.8.1.1.5

snmpProxyName OBJECT-TYPE
    SYNTAX DisplayString
    MAX-ACCESS read-write
    STATUS current
    DESCRIPTION
        "Name of this proxy entry."
    ::= { snmpProxyEntry 6 }
    --1.3.6.1.4.1.3052.10.2.4.8.8.1.1.6

-- SNMP Poll

snmpPMode OBJECT-TYPE
    SYNTAX DisplayString
    MAX-ACCESS read-write
    STATUS current
    DESCRIPTION
        "Mode of poll operation: OFF, POLL ONLY (just make the results
        available to view), or POLL BUFFER (store the results)."
    ::= { snmpPoll 1 }
    --1.3.6.1.4.1.3052.10.2.4.8.9.1

snmpPBufferFile OBJECT-TYPE
    SYNTAX DisplayString
    MAX-ACCESS read-write
    STATUS current
    DESCRIPTION
        "CRDB file in which data is stored."
    ::= { snmpPoll 2 }
    --1.3.6.1.4.1.3052.10.2.4.8.9.2

snmpPBufferAllPeriod OBJECT-TYPE
    SYNTAX Integer32
    MAX-ACCESS read-write
    STATUS current
    DESCRIPTION
        "Period (in seconds) that, if non-zero, all results are buffered
        in the CRDB regardless of the threshold."
    ::= { snmpPoll 3 }
    --1.3.6.1.4.1.3052.10.2.4.8.9.3

snmpPRequestTable OBJECT-TYPE
    SYNTAX SEQUENCE OF SNMPPollRequestConfig
    MAX-ACCESS not-accessible
    STATUS current
    DESCRIPTION
        "Table of SNMP Poll requests."
    ::= { snmpPoll 4 }
    --1.3.6.1.4.1.3052.10.2.4.8.9.4

snmpPRequestEntry OBJECT-TYPE
    SYNTAX SNMPPollRequestConfig
    MAX-ACCESS not-accessible
    STATUS current
    DESCRIPTION
        "Entry for table pf SNMP Poll requests."
    INDEX { snmpPRequestIndex }
    ::= { snmpPRequestTable 1 }
    --1.3.6.1.4.1.3052.10.2.4.8.9.4.1

snmpPRequestIndex OBJECT-TYPE
    SYNTAX Integer32 (1..64)
    MAX-ACCESS read-only
    STATUS current
    DESCRIPTION
        "Index for table of SNMP Poll requests."
    ::= { snmpPRequestEntry 1 }
    --1.3.6.1.4.1.3052.10.2.4.8.9.4.1.1

snmpPRequestDescription OBJECT-TYPE
    SYNTAX DisplayString
    MAX-ACCESS read-write
    STATUS current
    DESCRIPTION
        "A description for this single telemetry request; no functional effect."
    ::= { snmpPRequestEntry 2 }
    --1.3.6.1.4.1.3052.10.2.4.8.9.4.1.2

snmpPRequestAgent OBJECT-TYPE
    SYNTAX DisplayString
    MAX-ACCESS read-write
    STATUS current
    DESCRIPTION
        "SNMP Agent IP address or hostname for this single telemetry request."
    ::= { snmpPRequestEntry 3 }
    --1.3.6.1.4.1.3052.10.2.4.8.9.4.1.3

snmpPRequestReadcom OBJECT-TYPE
    SYNTAX DisplayString
    MAX-ACCESS read-write
    STATUS current
    DESCRIPTION
        "SNMP read community for this single telemetry request."
    ::= { snmpPRequestEntry 4 }
    --1.3.6.1.4.1.3052.10.2.4.8.9.4.1.4

snmpPRequestOID OBJECT-TYPE
    SYNTAX DisplayString
    MAX-ACCESS read-write
    STATUS current
    DESCRIPTION
        "SNMP object identifier for this single telemetry request."
    ::= { snmpPRequestEntry 5 }
    --1.3.6.1.4.1.3052.10.2.4.8.9.4.1.5

snmpPRequestPeriod OBJECT-TYPE
    SYNTAX Integer32 (1..255)
    MAX-ACCESS read-write
    STATUS current
    DESCRIPTION
        "How many seconds between periodic SNMP polls of this
        single telemetry request."
    ::= { snmpPRequestEntry 6 }
    --1.3.6.1.4.1.3052.10.2.4.8.9.4.1.6

snmpPRequestID OBJECT-TYPE
    SYNTAX DisplayString
    MAX-ACCESS read-write
    STATUS current
    DESCRIPTION
        "A textual field that is part of the record containing
        the telemetry result."
    ::= { snmpPRequestEntry 7 }
    --1.3.6.1.4.1.3052.10.2.4.8.9.4.1.7

snmpPRequestThreshold OBJECT-TYPE
    SYNTAX DisplayString
    MAX-ACCESS read-write
    STATUS current
    DESCRIPTION
        "Controls when new data is stored upon a successful
        telemetry request."
    ::= { snmpPRequestEntry 8 }
    --1.3.6.1.4.1.3052.10.2.4.8.9.4.1.8

snmpPRequestResultStatus OBJECT-TYPE
    SYNTAX DisplayString
    MAX-ACCESS read-only
    STATUS current
    DESCRIPTION
        "Status of the last attempt for this telemetry request."
    ::= { snmpPRequestEntry 10 }
    --1.3.6.1.4.1.3052.10.2.4.8.9.4.1.10

snmpPRequestResultValue OBJECT-TYPE
    SYNTAX DisplayString
    MAX-ACCESS read-only
    STATUS current
    DESCRIPTION
        "The telemetry value if the last request was successful."
    ::= { snmpPRequestEntry 11 }
    --1.3.6.1.4.1.3052.10.2.4.8.9.4.1.11

snmpPRequestResultTime OBJECT-TYPE
    SYNTAX DisplayString
    MAX-ACCESS read-only
    STATUS current
    DESCRIPTION
        "The timestamp of the last telemetry request."
    ::= { snmpPRequestEntry 12 }
    --1.3.6.1.4.1.3052.10.2.4.8.9.4.1.12

snmpPRequestResultType OBJECT-TYPE
    SYNTAX DisplayString
    MAX-ACCESS read-only
    STATUS current
    DESCRIPTION
        "The type of the telemetry as reported by the agent."
    ::= { snmpPRequestEntry 13 }
    --1.3.6.1.4.1.3052.10.2.4.8.9.4.1.13


-- FTP

ftpPushEnable OBJECT-TYPE
    SYNTAX DisplayString
    MAX-ACCESS read-write
    STATUS current
    DESCRIPTION
        "Enable FTP push for REGULAR (protocol: FTP) or SECURE (protocol:
        SFTP) operation, or disable it (OFF)"
    ::= { ftpPush 1 }
    --1.3.6.1.4.1.3052.10.2.4.9.1

ftpPushServer OBJECT-TYPE
    SYNTAX DisplayString
    MAX-ACCESS read-write
    STATUS current
    DESCRIPTION
        "FTP server to which data should be pushed"
    ::= { ftpPush 2 }
    --1.3.6.1.4.1.3052.10.2.4.9.2

ftpPushAccount OBJECT-TYPE
    SYNTAX DisplayString
    MAX-ACCESS read-write
    STATUS current
    DESCRIPTION
        "FTP push account"
    ::= { ftpPush 5 }
    --1.3.6.1.4.1.3052.10.2.4.9.5

ftpPushDirectory OBJECT-TYPE
    SYNTAX DisplayString
    MAX-ACCESS read-write
    STATUS current
    DESCRIPTION
        "FTP push directory"
    ::= { ftpPush 6 }
    --1.3.6.1.4.1.3052.10.2.4.9.6

ftpPushperiod OBJECT-TYPE
    SYNTAX Integer32
    MAX-ACCESS read-write
    STATUS current
    DESCRIPTION
        "Minutes between pushes"
    ::= { ftpPush 7 }
    --1.3.6.1.4.1.3052.10.2.4.9.7

ftpPushPushFileTable OBJECT-TYPE
    SYNTAX SEQUENCE OF FTPPushPushFileConfig
    MAX-ACCESS not-accessible
    STATUS current
    DESCRIPTION
        "Table of files to push"
    ::= { ftpPush 8 }
    --1.3.6.1.4.1.3052.10.2.4.9.8

ftpPushPushFileEntry OBJECT-TYPE
    SYNTAX FTPPushPushFileConfig
    MAX-ACCESS not-accessible
    STATUS current
    DESCRIPTION
        "Entry for table of files to push"
    INDEX { ftpPushPushFileIndex }
    ::= { ftpPushPushFileTable 1 }
    --1.3.6.1.4.1.3052.10.2.4.9.8.1

ftpPushPushFileIndex OBJECT-TYPE
    SYNTAX Integer32 (1..16)
    MAX-ACCESS read-only
    STATUS current
    DESCRIPTION
        "Index for table of files to push"
    ::= { ftpPushPushFileEntry 1 }
    --1.3.6.1.4.1.3052.10.2.4.9.8.1.1

ftpPushPushFile OBJECT-TYPE
    SYNTAX DisplayString
    MAX-ACCESS read-write
    STATUS current
    DESCRIPTION
        "ON/OFF push this local FILEx"
    ::= { ftpPushPushFileEntry 2 }
    --1.3.6.1.4.1.3052.10.2.4.9.8.1.2

ftpPushPushAudit OBJECT-TYPE
    SYNTAX DisplayString
    MAX-ACCESS read-write
    STATUS current
    DESCRIPTION
        "ON/OFF push the audit log"
    ::= { ftpPush 9 }
    --1.3.6.1.4.1.3052.10.2.4.9.9

ftpPushPushAlarms OBJECT-TYPE
    SYNTAX DisplayString
    MAX-ACCESS read-write
    STATUS current
    DESCRIPTION
        "ON/OFF push the alarms/events file"
    ::= { ftpPush 10 }
    --1.3.6.1.4.1.3052.10.2.4.9.10

ftpPushRemoteFileTable OBJECT-TYPE
    SYNTAX SEQUENCE OF FTPPushRemoteFileConfig
    MAX-ACCESS not-accessible
    STATUS current
    DESCRIPTION
        "Table of remote names of files to push"
    ::= { ftpPush 11 }
    --1.3.6.1.4.1.3052.10.2.4.9.11

ftpPushRemoteFileEntry OBJECT-TYPE
    SYNTAX FTPPushRemoteFileConfig
    MAX-ACCESS not-accessible
    STATUS current
    DESCRIPTION
        "Entry for table of remote names of files to push"
    INDEX { ftpPushRemoteFileIndex }
    ::= { ftpPushRemoteFileTable 1 }
    --1.3.6.1.4.1.3052.10.2.4.9.11.1

ftpPushRemoteFileIndex OBJECT-TYPE
    SYNTAX Integer32 (1..16)
    MAX-ACCESS read-only
    STATUS current
    DESCRIPTION
        "Index for table of remote names of files to push"
    ::= { ftpPushRemoteFileEntry 1 }
    --1.3.6.1.4.1.3052.10.2.4.9.11.1

ftpPushRemoteFileName OBJECT-TYPE
    SYNTAX DisplayString
    MAX-ACCESS read-write
    STATUS current
    DESCRIPTION
        "remote name of pushed FILEx (name on server)"
    ::= { ftpPushRemoteFileEntry 2 }
    --1.3.6.1.4.1.3052.10.2.4.9.11.2

ftpPushRemoteAlarmName OBJECT-TYPE
    SYNTAX DisplayString
    MAX-ACCESS read-write
    STATUS current
    DESCRIPTION
        "Filename on server for alarms"
    ::= { ftpPush 12 }
    --1.3.6.1.4.1.3052.10.2.4.9.12

ftpPushPassive OBJECT-TYPE
    SYNTAX DisplayString
    MAX-ACCESS read-write
    STATUS current
    DESCRIPTION
        "ON/OFF use ftp passive mode"
    ::= { ftpPush 13 }
    --1.3.6.1.4.1.3052.10.2.4.9.13

ftpPushIncludeDate OBJECT-TYPE
    SYNTAX DisplayString
    MAX-ACCESS read-write
    STATUS current
    DESCRIPTION
        "ON/OFF include the date in the name of the pushed file"
    ::= { ftpPush 14 }
    --1.3.6.1.4.1.3052.10.2.4.9.14

ftpPushIncludeTime OBJECT-TYPE
    SYNTAX DisplayString
    MAX-ACCESS read-write
    STATUS current
    DESCRIPTION
        "ON/OFF include the time in the name of the pushed file"
    ::= { ftpPush 15 }
    --1.3.6.1.4.1.3052.10.2.4.9.15

ftpPushIncludeSeq OBJECT-TYPE
    SYNTAX DisplayString
    MAX-ACCESS read-write
    STATUS current
    DESCRIPTION
        "ON/OFF include a sequence number in the name of the pushed file"
    ::= { ftpPush 16 }
    --1.3.6.1.4.1.3052.10.2.4.9.16

ftpPushPermissions OBJECT-TYPE
    SYNTAX DisplayString
    MAX-ACCESS read-write
    STATUS current
    DESCRIPTION
        "Unix permissions to apply to pushed files (octal notation)."
    ::= { ftpPush 17 }
    --1.3.6.1.4.1.3052.10.2.4.9.17


pppDialEnable OBJECT-TYPE
    SYNTAX DisplayString
    MAX-ACCESS read-write
    STATUS current
    DESCRIPTION
        "ON/OFF PPP dialout enabled"
    ::= { pppDial 1 }
    --1.3.6.1.4.1.3052.10.2.4.10.1.1

pppDialNumber OBJECT-TYPE
    SYNTAX DisplayString
    MAX-ACCESS read-write
    STATUS current
    DESCRIPTION
        "phone number to dial"
    ::= { pppDial 2 }
    --1.3.6.1.4.1.3052.10.2.4.10.1.2

pppDialIdleTimeout OBJECT-TYPE
    SYNTAX Integer32
    MAX-ACCESS read-write
    STATUS current
    DESCRIPTION
        "Seconds of inactivity after which the unit disconnects"
    ::= { pppDial 5 }
    --1.3.6.1.4.1.3052.10.2.4.10.1.5

pppDialRetries OBJECT-TYPE
    SYNTAX Integer32
    MAX-ACCESS read-write
    STATUS current
    DESCRIPTION
        "Number of dialing retries for PPP"
    ::= { pppDial 6 }
    --1.3.6.1.4.1.3052.10.2.4.10.1.6

pppDialCDTimeout OBJECT-TYPE
    SYNTAX Integer32
    MAX-ACCESS read-write
    STATUS current
    DESCRIPTION
        "Number of seconds to wait after dialing for CD before
        giving up"
    ::= { pppDial 7 }
    --1.3.6.1.4.1.3052.10.2.4.10.1.7

pppDialLoginTimeout OBJECT-TYPE
    SYNTAX Integer32
    MAX-ACCESS read-write
    STATUS current
    DESCRIPTION
        "Seconds to wait to negotiate PPP after connecting"
    ::= { pppDial 8 }
    --1.3.6.1.4.1.3052.10.2.4.10.1.8

pppDialMdmInit OBJECT-TYPE
    SYNTAX DisplayString
    MAX-ACCESS read-write
    STATUS current
    DESCRIPTION
        "Modem init string to use when dialing PPP"
    ::= { pppDial 9 }
    --1.3.6.1.4.1.3052.10.2.4.10.1.9

pppDialSuggestIP OBJECT-TYPE
    SYNTAX IpAddress
    MAX-ACCESS read-write
    STATUS current
    DESCRIPTION
        "IP address to suggest as the unit's end (local end) of the
        PPP link"
    ::= { pppDial 10 }
    --1.3.6.1.4.1.3052.10.2.4.10.1.10

pppDialPlainLogin OBJECT-TYPE
    SYNTAX DisplayString
    MAX-ACCESS read-write
    STATUS current
    DESCRIPTION
        "ON/OFF look for login/password prompt before negotiating
        PPP"
    ::= { pppDial 11 }
    --1.3.6.1.4.1.3052.10.2.4.10.1.11

pppHostEnable OBJECT-TYPE
    SYNTAX DisplayString
    MAX-ACCESS read-write
    STATUS current
    DESCRIPTION
        "ON/OFF Unit accepts PPP negotiation"
    ::= { pppHost 1 }
    --1.3.6.1.4.1.3052.10.2.4.10.2.1

pppHostIdleTimeout OBJECT-TYPE
    SYNTAX Integer32
    MAX-ACCESS read-write
    STATUS current
    DESCRIPTION
        "Seconds of inactivity after which PPP-hosted link will
        terminate"
    ::= { pppHost 2 }
    --1.3.6.1.4.1.3052.10.2.4.10.2.2

pppHostLocalIP OBJECT-TYPE
    SYNTAX IpAddress
    MAX-ACCESS read-write
    STATUS current
    DESCRIPTION
        "Local IP address to negotiate"
    ::= { pppHost 3 }
    --1.3.6.1.4.1.3052.10.2.4.10.2.3

pppHostRemoteIP OBJECT-TYPE
    SYNTAX IpAddress
    MAX-ACCESS read-write
    STATUS current
    DESCRIPTION
        "Remote IP address to hand out to PPP peer"
    ::= { pppHost 4 }
    --1.3.6.1.4.1.3052.10.2.4.10.2.4

-- Routing

pppRoutingEnable OBJECT-TYPE
    SYNTAX DisplayString
    MAX-ACCESS read-write
    STATUS current
    DESCRIPTION
        "ON/OFF unit routes IP traffic from PPP/Wireless to Ethernet"
    ::= { routing 1 }
    --1.3.6.1.4.1.3052.10.2.4.11.1

ethRoutingEnable OBJECT-TYPE
    SYNTAX DisplayString
    MAX-ACCESS read-write
    STATUS current
    DESCRIPTION
        "ON/OFF unit routes IP traffic from Ethernet to PPP/Wireless"
    ::= { routing 2 }
    --1.3.6.1.4.1.3052.10.2.4.11.2

ethRoutingNATEnable OBJECT-TYPE
    SYNTAX DisplayString
    MAX-ACCESS read-write
    STATUS current
    DESCRIPTION
        "ON/OFF unit applies NAT on routed IP frames egressing the
        unit on its PPP interface"
    ::= { routing 3 }
    --1.3.6.1.4.1.3052.10.2.4.11.3

routingInterface OBJECT-TYPE
    SYNTAX DisplayString
    MAX-ACCESS read-write
    STATUS current
    DESCRIPTION
        "When Ethernet routing is enabled (routing.1), this is the
        Ethernet interface to which IP frames received on PPP are
        routed"
    ::= { routing 4 }
    --1.3.6.1.4.1.3052.10.2.4.11.4

eth2WanRoutingEnable OBJECT-TYPE
    SYNTAX DisplayString
    MAX-ACCESS read-write
    STATUS current
    DESCRIPTION
        "Make ETH2 operate as a WAN port to route outbound traffic
        arriving on ETH1."
    ::= { routing 5 }
    --1.3.6.1.4.1.3052.10.2.4.11.5

-- IP Restrictions

ipRestrictionTable OBJECT-TYPE
    SYNTAX SEQUENCE OF IPRestrictionConfig
    MAX-ACCESS not-accessible
    STATUS current
    DESCRIPTION
        "Table of IP restrictions"
    ::= { ipRestriction 1 }
    --1.3.6.1.4.1.3052.10.2.4.12.1.1

ipRestrictionEntry OBJECT-TYPE
    SYNTAX IPRestrictionConfig
    MAX-ACCESS not-accessible
    STATUS current
    DESCRIPTION
        "Entry for table of IP restrictions"
    INDEX { ipRestrictionIndex }
    ::= { ipRestrictionTable 1 }
    --1.3.6.1.4.1.3052.10.2.4.12.1.1

ipRestrictionIndex OBJECT-TYPE
    SYNTAX Integer32 (1..8)
    MAX-ACCESS read-only
    STATUS current
    DESCRIPTION
        "Index for table of IP restrictions"
    ::= { ipRestrictionEntry 1 }
    --1.3.6.1.4.1.3052.10.2.4.12.1.1.1.1

ipRestrictionEnable OBJECT-TYPE
    SYNTAX DisplayString
    MAX-ACCESS read-write
    STATUS current
    DESCRIPTION
        "ON/OFF enable this IP restriction"
    ::= { ipRestrictionEntry 2 }
    --1.3.6.1.4.1.3052.10.2.4.12.1.1.1.2

ipRestrictionMask OBJECT-TYPE
    SYNTAX DisplayString
    MAX-ACCESS read-write
    STATUS current
    DESCRIPTION
        "IP restriction mask"
    ::= { ipRestrictionEntry 3 }
    --1.3.6.1.4.1.3052.10.2.4.12.1.1.1.3


-- RTS


rtsFileTable OBJECT-TYPE
    SYNTAX SEQUENCE OF RTSFileConfig
    MAX-ACCESS not-accessible
    STATUS current
    DESCRIPTION
        "Table of RTS files"
    ::= { rts 1 }
    --1.3.6.1.4.1.3052.10.2.4.13.1

rtsFileEntry OBJECT-TYPE
    SYNTAX RTSFileConfig
    MAX-ACCESS not-accessible
    STATUS current
    DESCRIPTION
        "Entry for table of RTS files"
    INDEX { rtsFileIndex }
    ::= { rtsFileTable 1 }
    --1.3.6.1.4.1.3052.10.2.4.13.1

rtsFileIndex OBJECT-TYPE
    SYNTAX Integer32 (1..16)
    MAX-ACCESS read-only
    STATUS current
    DESCRIPTION
        "Index for table of RTS files"
    ::= { rtsFileEntry 1 }
    --1.3.6.1.4.1.3052.10.2.4.13.1.1.1

rtsFileMode OBJECT-TYPE
    SYNTAX DisplayString
    MAX-ACCESS read-write
    STATUS current
    DESCRIPTION
        "RTS mode (OFF,LISTEN,PUSH) for FILEx"
    ::= { rtsFileEntry 2 }
    --1.3.6.1.4.1.3052.10.2.4.13.1.1.2

rtsFileShowAnswer OBJECT-TYPE
    SYNTAX DisplayString
    MAX-ACCESS read-write
    STATUS current
    DESCRIPTION
        "Show answer string upon RTS connect for FILEx"
    ::= { rtsFileEntry 3 }
    --1.3.6.1.4.1.3052.10.2.4.13.1.1.3

rtsFileReqXON OBJECT-TYPE
    SYNTAX DisplayString
    MAX-ACCESS read-write
    STATUS current
    DESCRIPTION
        "ON/OFF require XON to start flow for FILEx"
    ::= { rtsFileEntry 4 }
    --1.3.6.1.4.1.3052.10.2.4.13.1.1.4

rtsFileTimeout OBJECT-TYPE
    SYNTAX Integer32
    MAX-ACCESS read-write
    STATUS current
    DESCRIPTION
        "Idle connection close timer (0 means no timeout) for FILEx"
    ::= { rtsFileEntry 5 }
    --1.3.6.1.4.1.3052.10.2.4.13.1.1.5

rtsFileEmptyClose OBJECT-TYPE
    SYNTAX DisplayString
    MAX-ACCESS read-write
    STATUS current
    DESCRIPTION
        "ON/OFF close the socket when FILEx is empty"
    ::= { rtsFileEntry 6 }
    --1.3.6.1.4.1.3052.10.2.4.13.1.1.6

rtsFilePushHost OBJECT-TYPE
    SYNTAX DisplayString
    MAX-ACCESS read-write
    STATUS current
    DESCRIPTION
        "Host to which FILEx should be pushed via RTS"
    ::= { rtsFileEntry 7 }
    --1.3.6.1.4.1.3052.10.2.4.13.1.1.7

rtsFilePushPort OBJECT-TYPE
    SYNTAX Integer32
    MAX-ACCESS read-write
    STATUS current
    DESCRIPTION
        "TCP port to which FILEx should be pushed via RTS"
    ::= { rtsFileEntry 8 }
    --1.3.6.1.4.1.3052.10.2.4.13.1.1.8

rtsFilePushRetryTimer OBJECT-TYPE
    SYNTAX Integer32
    MAX-ACCESS read-write
    STATUS current
    DESCRIPTION
        "Retry timer (seconds) for retrying failed RTS push connect
        attempts"
    ::= { rtsFileEntry 9 }
    --1.3.6.1.4.1.3052.10.2.4.13.1.1.9

-- RTS Alarms

rtsAlarmsMode OBJECT-TYPE
    SYNTAX DisplayString
    MAX-ACCESS read-write
    STATUS current
    DESCRIPTION
        "RTS mode (OFF,LISTEN,PUSH) for alarms file"
    ::= { rtsAlarms 1 }
    --1.3.6.1.4.1.3052.10.2.4.13.2.1

rtsAlarmsShowAnswer OBJECT-TYPE
    SYNTAX DisplayString
    MAX-ACCESS read-write
    STATUS current
    DESCRIPTION
        "Show answer string upon RTS connect for alarms file"
    ::= { rtsAlarms 2 }
    --1.3.6.1.4.1.3052.10.2.4.13.2.2

rtsAlarmsReqXON OBJECT-TYPE
    SYNTAX DisplayString
    MAX-ACCESS read-write
    STATUS current
    DESCRIPTION
        "ON/OFF require XON to start flow for alarms file"
    ::= { rtsAlarms 3 }
    --1.3.6.1.4.1.3052.10.2.4.13.2.3

rtsAlarmsTimeout OBJECT-TYPE
    SYNTAX Integer32
    MAX-ACCESS read-write
    STATUS current
    DESCRIPTION
        "Idle connection close timer (0 means no timeout) for alarms
        file"
    ::= { rtsAlarms 4 }
    --1.3.6.1.4.1.3052.10.2.4.13.2.4

rtsAlarmsEmptyClose OBJECT-TYPE
    SYNTAX DisplayString
    MAX-ACCESS read-write
    STATUS current
    DESCRIPTION
        "ON/OFF close the socket when this file is empty for alarms
        file"
    ::= { rtsAlarms 5 }
    --1.3.6.1.4.1.3052.10.2.4.13.2.5

rtsAlarmsPushHost OBJECT-TYPE
    SYNTAX DisplayString
    MAX-ACCESS read-write
    STATUS current
    DESCRIPTION
        "Host to which alarms file should be pushed via RTS"
    ::= { rtsAlarms 6 }
    --1.3.6.1.4.1.3052.10.2.4.13.2.6

rtsAlarmsPushPort OBJECT-TYPE
    SYNTAX Integer32
    MAX-ACCESS read-write
    STATUS current
    DESCRIPTION
        "TCP port to which alarms file should be pushed via RTS"
    ::= { rtsAlarms 7 }
    --1.3.6.1.4.1.3052.10.2.4.13.2.7

rtsAlarmsPushRetryTimer OBJECT-TYPE
    SYNTAX Integer32
    MAX-ACCESS read-write
    STATUS current
    DESCRIPTION
        "Retry timer (seconds) for retrying failed RTS push connect
        attempts"
    ::= { rtsAlarms 8 }
    --1.3.6.1.4.1.3052.10.2.4.13.2.8

-- Traps

trapIncludeDateTime OBJECT-TYPE
    SYNTAX DisplayString
    MAX-ACCESS read-write
    STATUS current
    DESCRIPTION
        "ON/OFF include date and time in stock trap message"
    ::= { trapInclude 1 }
    --1.3.6.1.4.1.3052.10.2.4.14.1.1

trapIncludeSiteName OBJECT-TYPE
    SYNTAX DisplayString
    MAX-ACCESS read-write
    STATUS current
    DESCRIPTION
        "ON/OFF include site name in stock trap message"
    ::= { trapInclude 2 }
    --1.3.6.1.4.1.3052.10.2.4.14.1.2

trapIncludeSensorID OBJECT-TYPE
    SYNTAX DisplayString
    MAX-ACCESS read-write
    STATUS current
    DESCRIPTION
        "ON/OFF include sensor ID in stock trap message"
    ::= { trapInclude 3 }
    --1.3.6.1.4.1.3052.10.2.4.14.1.3

trapIncludeUDName OBJECT-TYPE
    SYNTAX DisplayString
    MAX-ACCESS read-write
    STATUS current
    DESCRIPTION
        "ON/OFF include user defined name in stock trap message"
    ::= { trapInclude 4 }
    --1.3.6.1.4.1.3052.10.2.4.14.1.4

trapIncludeUDState OBJECT-TYPE
    SYNTAX DisplayString
    MAX-ACCESS read-write
    STATUS current
    DESCRIPTION
        "ON/OFF include user defined state in stock trap message"
    ::= { trapInclude 5 }
    --1.3.6.1.4.1.3052.10.2.4.14.1.5

trapIncludeSourceAddress OBJECT-TYPE
    SYNTAX IpAddress
    MAX-ACCESS read-write
    STATUS current
    DESCRIPTION
        "ON/OFF include source IP address in stock trap message"
    ::= { trapInclude 6 }
    --1.3.6.1.4.1.3052.10.2.4.14.1.6

trapAuthFailEnable OBJECT-TYPE
    SYNTAX DisplayString
    MAX-ACCESS read-write
    STATUS current
    DESCRIPTION
        "ON/OFF enable trap sent upon SNMP authentication failure"
    ::= { trap 2 }
    --1.3.6.1.4.1.3052.10.2.4.14.2

-- Route testing

routeTestEnable OBJECT-TYPE
    SYNTAX DisplayString
    MAX-ACCESS read-write
    STATUS current
    DESCRIPTION
        "ON/OFF enable route testing"
    ::= { routeTest 1 }
    --1.3.6.1.4.1.3052.10.2.4.15.1


routeTestPeriod OBJECT-TYPE
    SYNTAX Integer32
    MAX-ACCESS read-write
    STATUS current
    DESCRIPTION
        "The period which a route is considered valid"
    ::= { routeTest 2 }
    --1.3.6.1.4.1.3052.10.2.4.15.2

routeTestAddressTable OBJECT-TYPE
    SYNTAX SEQUENCE OF RouteTestConfig
    MAX-ACCESS not-accessible
    STATUS current
    DESCRIPTION
        "Table of route testing addresses"
    ::= { routeTest 3 }
    --1.3.6.1.4.1.3052.10.2.4.15.3

routeTestAddressEntry OBJECT-TYPE
    SYNTAX RouteTestConfig
    MAX-ACCESS not-accessible
    STATUS current
    DESCRIPTION
        "Entry for table of RTS files"
    INDEX { routeTestAddressIndex }
    ::= { routeTestAddressTable 1 }
    --1.3.6.1.4.1.3052.10.2.4.15.3.1

routeTestAddressIndex OBJECT-TYPE
    SYNTAX Integer32 (1..3)
    MAX-ACCESS read-only
    STATUS current
    DESCRIPTION
        "Index for table of RTS files"
    ::= { routeTestAddressEntry 1 }
    --1.3.6.1.4.1.3052.10.2.4.15.3.1.1

routeTestAddress OBJECT-TYPE
    SYNTAX DisplayString
    MAX-ACCESS read-write
    STATUS current
    DESCRIPTION
        "Address to ping to see if the route to it is valid"
    ::= { routeTestAddressEntry 2 }
    --1.3.6.1.4.1.3052.10.2.4.15.3.1.2


-- Wireless


wirelessMode OBJECT-TYPE
    SYNTAX DisplayString
    MAX-ACCESS read-write
    STATUS current
    DESCRIPTION
        "Wireless mode (OFF,PERMANENT-EDGE)"
    ::= { wireless 1 }
    --1.3.6.1.4.1.3052.10.2.4.16.1

wirelessAPN OBJECT-TYPE
    SYNTAX DisplayString
    MAX-ACCESS read-write
    STATUS current
    DESCRIPTION
        "Wireless access point name"
    ::= { wireless 2 }
    --1.3.6.1.4.1.3052.10.2.4.16.2

wirelessIdleTimeout OBJECT-TYPE
    SYNTAX Integer32
    MAX-ACCESS read-write
    STATUS current
    DESCRIPTION
        "Wireless idle timeout"
    ::= { wireless 3 }
    --1.3.6.1.4.1.3052.10.2.4.16.3

wirelessDRE OBJECT-TYPE
    SYNTAX DisplayString
    MAX-ACCESS read-write
    STATUS current
    DESCRIPTION
        "Default route enable for wireless network interface.
         When this is ON, the wireless link, if up, becomes
         the default route, overriding the default route setting
         (defaultRouter object).  When OFF, the default route
         setting controls the default route and the wireless link
         does not become the default route."
    ::= { wireless 9 }
    --1.3.6.1.4.1.3052.10.2.4.16.9

wirelessPPPUsername OBJECT-TYPE
    SYNTAX DisplayString
    MAX-ACCESS read-write
    STATUS current
    DESCRIPTION
        "Username for PPP-based wireless modem connections."
    ::= { wireless 10 }
    --1.3.6.1.4.1.3052.10.2.4.16.10

wirelessFirewall OBJECT-TYPE
    SYNTAX DisplayString
    MAX-ACCESS read-write
    STATUS current
    DESCRIPTION
        "Enable wireless modem firewall."
    ::= { wireless 11 }
    --1.3.6.1.4.1.3052.10.2.4.16.11

wirelessKeepaliveThreshold OBJECT-TYPE
    SYNTAX Integer32
    MAX-ACCESS read-write
    STATUS current
    DESCRIPTION
        "Minutes of no RX activity before sending keep-alive."
    ::= { wireless 12 }
    --1.3.6.1.4.1.3052.10.2.4.16.12

wirelessPPPDebug OBJECT-TYPE
    SYNTAX DisplayString
    MAX-ACCESS read-write
    STATUS current
    DESCRIPTION
        "Enable wireless modem PPP debug."
    ::= { wireless 13 }
    --1.3.6.1.4.1.3052.10.2.4.16.13

wirelessConnEnable OBJECT-TYPE
    SYNTAX DisplayString
    MAX-ACCESS read-write
    STATUS current
    DESCRIPTION
        "Enable wireless modem connectivity check."
    ::= { wirelessConnectivity 1 }
    --1.3.6.1.4.1.3052.10.2.4.16.20.1

wirelessConnCheckInterval OBJECT-TYPE
    SYNTAX Integer32
    MAX-ACCESS read-write
    STATUS current
    DESCRIPTION
        "Wireless connectivity check interval in minutes."
    ::= { wirelessConnectivity 2 }
    --1.3.6.1.4.1.3052.10.2.4.16.20.2

wirelessConnFailThreshold OBJECT-TYPE
    SYNTAX Integer32
    MAX-ACCESS read-write
    STATUS current
    DESCRIPTION
        "Wireless connectivity fail threshold."
    ::= { wirelessConnectivity 3 }
    --1.3.6.1.4.1.3052.10.2.4.16.20.3

wirelessConnIP1 OBJECT-TYPE
    SYNTAX IpAddress
    MAX-ACCESS read-write
    STATUS current
    DESCRIPTION
        "Wireless connectivity check IP address 1."
    ::= { wirelessConnectivity 10 }
    --1.3.6.1.4.1.3052.10.2.4.16.20.10

wirelessConnIP2 OBJECT-TYPE
    SYNTAX IpAddress
    MAX-ACCESS read-write
    STATUS current
    DESCRIPTION
        "Wireless connectivity check IP address 2."
    ::= { wirelessConnectivity 11 }
    --1.3.6.1.4.1.3052.10.2.4.16.20.11


-- Email


emailServer OBJECT-TYPE
    SYNTAX DisplayString
    MAX-ACCESS read-write
    STATUS current
    DESCRIPTION
        "SMTP server to which the unit sends email"
    ::= { email 1 }
    --1.3.6.1.4.1.3052.10.2.4.17.1

emailDomain OBJECT-TYPE
    SYNTAX DisplayString
    MAX-ACCESS read-write
    STATUS current
    DESCRIPTION
        "Domain to use in recipient address"
    ::= { email 2 }
    --1.3.6.1.4.1.3052.10.2.4.17.2

emailAuthEnable OBJECT-TYPE
    SYNTAX DisplayString
    MAX-ACCESS read-write
    STATUS current
    DESCRIPTION
        "ON/OFF enable SMTP authentication"
    ::= { email 3 }
    --1.3.6.1.4.1.3052.10.2.4.17.3

-- Advanced network config

arpFilter OBJECT-TYPE
    SYNTAX Integer32
    MAX-ACCESS read-write
    STATUS current
    DESCRIPTION
        "ARP filter code"
    ::= { netAdvanced 1 }
    --1.3.6.1.4.1.3052.10.2.4.18.1


-- Web interface

webEnable OBJECT-TYPE
    SYNTAX DisplayString
    MAX-ACCESS read-write
    STATUS current
    DESCRIPTION
        "ON/OFF for the web interface"
    ::= { web 1 }
    --1.3.6.1.4.1.3052.10.2.4.19.1

webPort OBJECT-TYPE
    SYNTAX Integer32
    MAX-ACCESS read-write
    STATUS current
    DESCRIPTION
        "TCP port on which web interface listens"
    ::= { web 2 }
    --1.3.6.1.4.1.3052.10.2.4.19.2

webTimeout OBJECT-TYPE
    SYNTAX Integer32
    MAX-ACCESS read-write
    STATUS current
    DESCRIPTION
        "Web interface session timeout (seconds)"
    ::= { web 3 }
    --1.3.6.1.4.1.3052.10.2.4.19.3


-- XML Proxy

wxpEnable OBJECT-TYPE
    SYNTAX DisplayString
    MAX-ACCESS read-write
    STATUS current
    DESCRIPTION
        "Globally enables/disables the XML Proxy feature.  This feature
        is not available in the STD software build."
    ::= { webXMLProxy 1 }
    --1.3.6.1.4.1.3052.10.2.4.19.4.1

wxpDeviceTable OBJECT-TYPE
    SYNTAX SEQUENCE OF WebXMLProxyDeviceConfig
    MAX-ACCESS not-accessible
    STATUS current
    DESCRIPTION
        "Table of XML Proxy devices."
    ::= { webXMLProxy 2 }
    --1.3.6.1.4.1.3052.10.2.4.19.4.2

wxpDeviceEntry OBJECT-TYPE
    SYNTAX WebXMLProxyDeviceConfig
    MAX-ACCESS not-accessible
    STATUS current
    DESCRIPTION
        "Entry for table of XML Proxy devices."
    INDEX { wxpDeviceIndex }
    ::= { wxpDeviceTable 1 }
    --1.3.6.1.4.1.3052.10.2.4.19.4.2.1

wxpDeviceIndex OBJECT-TYPE
    SYNTAX Integer32 (1..16)
    MAX-ACCESS read-only
    STATUS current
    DESCRIPTION
        "Index for table of XML Proxy devices."
    ::= { wxpDeviceEntry 1 }
    --1.3.6.1.4.1.3052.10.2.4.19.4.2.1.1

wxpDeviceEnable OBJECT-TYPE
    SYNTAX DisplayString
    MAX-ACCESS read-write
    STATUS current
    DESCRIPTION
        "Enables/disables this particular XML device configuration."
    ::= { wxpDeviceEntry 2 }
    --1.3.6.1.4.1.3052.10.2.4.19.4.2.1.2

wxpDeviceIPAddress OBJECT-TYPE
    SYNTAX IpAddress
    MAX-ACCESS read-write
    STATUS current
    DESCRIPTION
        "IP address for device."
    ::= { wxpDeviceEntry 3 }
    --1.3.6.1.4.1.3052.10.2.4.19.4.2.1.3

wxpDevicePort OBJECT-TYPE
    SYNTAX Integer32 (0..65535)
    MAX-ACCESS read-write
    STATUS current
    DESCRIPTION
        "TCP port on which to connect via HTTP to fetch the XML file."
    ::= { wxpDeviceEntry 4 }
    --1.3.6.1.4.1.3052.10.2.4.19.4.2.1.4

wxpDeviceRemoteFile OBJECT-TYPE
    SYNTAX DisplayString
    MAX-ACCESS read-write
    STATUS current
    DESCRIPTION
        "Path and name of the XML file on the remote device.  E.g.,
        'xml/telemetry.xml' if the URL for the XML is
        'http://<remote device address>/xml/telemetry.xml'."
    ::= { wxpDeviceEntry 5 }
    --1.3.6.1.4.1.3052.10.2.4.19.4.2.1.5

wxpDeviceLocalFile OBJECT-TYPE
    SYNTAX DisplayString
    MAX-ACCESS read-write
    STATUS current
    DESCRIPTION
        "Name of file in which the remote file content will be cached
        on the unit.  E.g., 'alpha-telemetry.xml' if the URL for the
        unit-cached XML is intended to be
        'http://<unit address>/xmlproxy/alpha-telemetry.xml'."
    ::= { wxpDeviceEntry 6 }
    --1.3.6.1.4.1.3052.10.2.4.19.4.2.1.6

wxpDeviceTimeout OBJECT-TYPE
    SYNTAX Integer32 (1..255)
    MAX-ACCESS read-write
    STATUS current
    DESCRIPTION
        "How long in seconds to wait for the device to serve the
        remote file before cancelling the fetch operation."
    ::= { wxpDeviceEntry 7 }
    --1.3.6.1.4.1.3052.10.2.4.19.4.2.1.7

wxpDeviceTimestamp OBJECT-TYPE
    SYNTAX DisplayString
    MAX-ACCESS read-write
    STATUS current
    DESCRIPTION
        "Timestamp of last successful XML file fetch/cache operation.
        If blank then either the device is not configured or there
        was a fetch error. If not blank, but not updating, then this
        indicates that the fetch succeeded at one point but then
        encountered an error."
    ::= { wxpDeviceEntry 8 }
    --1.3.6.1.4.1.3052.10.2.4.19.4.2.1.8


-- Ethernet Expansion

ethExpanIp OBJECT-TYPE
    SYNTAX IpAddress
    MAX-ACCESS read-write
    STATUS current
    DESCRIPTION
        "IPv4 address of the unit reachable by nodes on the network interface
        consisting of the Ethernet Expansion Card(s). If this is default
        (0.0.0.0), then each card will still convey Ethernet traffic
        (acting as Ethernet switch) among its nodes but those nodes will not
        be able to communicate with the unit."
    ::= { ethExpan 1 }
    --1.3.6.1.4.1.3052.10.2.4.20.1

ethExpanMask OBJECT-TYPE
    SYNTAX IpAddress
    MAX-ACCESS read-write
    STATUS current
    DESCRIPTION
        "IPv4 subnet mask for the Ethernet Expansion network interface."
    ::= { ethExpan 2 }
    --1.3.6.1.4.1.3052.10.2.4.20.2

ethExpanCardTable OBJECT-TYPE
    SYNTAX SEQUENCE OF EthernetExpansionCardConfig
    MAX-ACCESS not-accessible
    STATUS current
    DESCRIPTION
        "Table of Ethernet Expansion cards"
    ::= { ethExpan 3 }
    --1.3.6.1.4.1.3052.10.2.4.20.3

ethExpanCardEntry OBJECT-TYPE
    SYNTAX EthernetExpansionCardConfig
    MAX-ACCESS not-accessible
    STATUS current
    DESCRIPTION
        "Entry for table of Ethernet Expansion cards"
    INDEX { ethExpanCardIndex }
    ::= { ethExpanCardTable 1 }
    --1.3.6.1.4.1.3052.10.2.4.20.3.1

ethExpanCardIndex OBJECT-TYPE
    SYNTAX Integer32 (1..2)
    MAX-ACCESS read-only
    STATUS current
    DESCRIPTION
        "Index for table of Ethernet Expansion cards"
    ::= { ethExpanCardEntry 1 }
    --1.3.6.1.4.1.3052.10.2.4.20.3.1.1

ethExpanCardMAC OBJECT-TYPE
    SYNTAX DisplayString
    MAX-ACCESS read-only
    STATUS current
    DESCRIPTION
        "MAC address for each Ethernet Expansion Card that is bridged
        together to form the Ethernet Expansion network interface."
    ::= { ethExpanCardEntry 2 }
    --1.3.6.1.4.1.3052.10.2.4.20.3.1.2

ethExpanDHCPStartIp OBJECT-TYPE
    SYNTAX IpAddress
    MAX-ACCESS read-write
    STATUS current
    DESCRIPTION
        "Starting IP address for serving DHCP addresses on the Ethernet
        Expansion network interface. If this is default (0.0.0.0) then
        the unit will not run DHCP to serve addresses."
    ::= { ethExpanDHCP 1 }
    --1.3.6.1.4.1.3052.10.2.4.20.6.1

ethExpanDHCPLeaseTime OBJECT-TYPE
    SYNTAX Integer32
    MAX-ACCESS read-write
    STATUS current
    DESCRIPTION
        "Lease time for Ethernet Expansion DHCP clients in minutes."
    ::= { ethExpanDHCP 2 }
    --1.3.6.1.4.1.3052.10.2.4.20.6.2



-- IPv6

ipv6DefaultRouter OBJECT-TYPE
    SYNTAX DisplayString
    MAX-ACCESS read-write
    STATUS current
    DESCRIPTION
        "The IPv6 default router in use."
    ::= { ipv6 1 }
    --1.3.6.1.4.1.3052.10.2.4.21.1



-- CPE table

cpeTable OBJECT-TYPE
    SYNTAX SEQUENCE OF CPEConfig
    MAX-ACCESS not-accessible
    STATUS current
    DESCRIPTION
        "Table of CPEs"
    ::= { cpe 1 }
    --1.3.6.1.4.1.3052.10.2.4.22.1

cpeEntry OBJECT-TYPE
    SYNTAX CPEConfig
    MAX-ACCESS not-accessible
    STATUS current
    DESCRIPTION
        "Entry for table of CPEs"
    INDEX { cpeIndex }
    ::= { cpeTable 1 }
    --1.3.6.1.4.1.3052.10.2.4.22.1.1

cpeIndex OBJECT-TYPE
    SYNTAX Integer32 (1..16)
    MAX-ACCESS read-only
    STATUS current
    DESCRIPTION
        "Index for table of CPEs"
    ::= { cpeEntry 1 }
    --1.3.6.1.4.1.3052.10.2.4.22.1.1.1

cpeHost OBJECT-TYPE
    SYNTAX DisplayString
    MAX-ACCESS read-write
    STATUS current
    DESCRIPTION
        "CPE host (IP address or DNS name)"
    ::= { cpeEntry 2 }
    --1.3.6.1.4.1.3052.10.2.4.22.1.1.2

cpeName OBJECT-TYPE
    SYNTAX DisplayString
    MAX-ACCESS read-write
    STATUS current
    DESCRIPTION
        "CPE name, informational only"
    ::= { cpeEntry 3 }
    --1.3.6.1.4.1.3052.10.2.4.22.1.1.3

cpeDescription OBJECT-TYPE
    SYNTAX DisplayString
    MAX-ACCESS read-write
    STATUS current
    DESCRIPTION
        "CPE description, informational only"
    ::= { cpeEntry 4 }
    --1.3.6.1.4.1.3052.10.2.4.22.1.1.4

cpeKeepalive OBJECT-TYPE
    SYNTAX Integer32
    MAX-ACCESS read-write
    STATUS current
    DESCRIPTION
        "Number of seconds between each successful ping request."
    ::= { cpeEntry 5 }
    --1.3.6.1.4.1.3052.10.2.4.22.1.1.5

cpeThreshold OBJECT-TYPE
    SYNTAX Integer32
    MAX-ACCESS read-write
    STATUS current
    DESCRIPTION
        "Number of unsuccessful pings that triggers the CPE event."
    ::= { cpeEntry 6 }
    --1.3.6.1.4.1.3052.10.2.4.22.1.1.6

cpeEventReminderInterval OBJECT-TYPE
    SYNTAX Integer32
    MAX-ACCESS read-write
    STATUS current
    DESCRIPTION
        "CPE event reminder interval (minutes)."
    ::= { cpeEntry 7 }
    --1.3.6.1.4.1.3052.10.2.4.22.1.1.7

cpeKeepaliveTicks OBJECT-TYPE
    SYNTAX Integer32
    MAX-ACCESS read-write
    STATUS current
    DESCRIPTION
        "CPE ping period in 16ths of a second (nonzero overrides keepalive)."
    ::= { cpeEntry 20 }
    --1.3.6.1.4.1.3052.10.2.4.22.1.1.20

cpePingSize OBJECT-TYPE
    SYNTAX Integer32
    MAX-ACCESS read-write
    STATUS current
    DESCRIPTION
        "Number of bytes in CPE ping payload"
    ::= { cpeEntry 21 }
    --1.3.6.1.4.1.3052.10.2.4.22.1.11

cpeInfoReset OBJECT-TYPE
    SYNTAX Integer32
    MAX-ACCESS read-only
    STATUS current
    DESCRIPTION
        "Set any number to reset CPE ping stats."
    ::= { cpeEntry 30 }
    --1.3.6.1.4.1.3052.10.2.4.22.1.1.30

cpeInfoNumReq OBJECT-TYPE
    SYNTAX Integer32
    MAX-ACCESS read-only
    STATUS current
    DESCRIPTION
        "Total number of requests transmitted."
    ::= { cpeEntry 31 }
    --1.3.6.1.4.1.3052.10.2.4.22.1.1.31

cpeInfoNumGoodResp OBJECT-TYPE
    SYNTAX Integer32
    MAX-ACCESS read-only
    STATUS current
    DESCRIPTION
        "Total number of non-corrupt responses."
    ::= { cpeEntry 32 }
    --1.3.6.1.4.1.3052.10.2.4.22.1.1.32

cpeInfoNumBadResp OBJECT-TYPE
    SYNTAX Integer32
    MAX-ACCESS read-only
    STATUS current
    DESCRIPTION
        "Total number of corrupt responses."
    ::= { cpeEntry 33 }
    --1.3.6.1.4.1.3052.10.2.4.22.1.1.33

cpeInfoNumLostResp OBJECT-TYPE
    SYNTAX Integer32
    MAX-ACCESS read-only
    STATUS current
    DESCRIPTION
        "Total number of requests with no response."
    ::= { cpeEntry 34 }
    --1.3.6.1.4.1.3052.10.2.4.22.1.1.34

cpeInfoPercentLoss OBJECT-TYPE
    SYNTAX DisplayString
    MAX-ACCESS read-only
    STATUS current
    DESCRIPTION
        "Percent loss (missing responses / total requests)."
    ::= { cpeEntry 35 }
    --1.3.6.1.4.1.3052.10.2.4.22.1.1.35

cpeInfoPercentBad OBJECT-TYPE
    SYNTAX DisplayString
    MAX-ACCESS read-only
    STATUS current
    DESCRIPTION
        "Percent corrupt (corrupt responses / total requests)."
    ::= { cpeEntry 36 }
    --1.3.6.1.4.1.3052.10.2.4.22.1.1.36


-- DNP3

dnp3Mode OBJECT-TYPE
    SYNTAX DisplayString
    MAX-ACCESS read-write
    STATUS current
    DESCRIPTION
        "DNP3 operating mode."
    ::= { dnp3General 1 }
    --1.3.6.1.4.1.3052.10.2.4.23.1.1

dnp3SelfAddressEnable OBJECT-TYPE
    SYNTAX DisplayString
    MAX-ACCESS read-write
    STATUS current
    DESCRIPTION
        "DNP3 self-address enabled."
    ::= { dnp3General 2 }
    --1.3.6.1.4.1.3052.10.2.4.23.1.2

dnp3KeepaliveTimeout OBJECT-TYPE
    SYNTAX Integer32
    MAX-ACCESS read-write
    STATUS current
    DESCRIPTION
        "Keepalive timeout in seconds."
    ::= { dnp3General 3 }
    --1.3.6.1.4.1.3052.10.2.4.23.1.3

dnp3MaxRXFragmentSize OBJECT-TYPE
    SYNTAX Integer32
    MAX-ACCESS read-write
    STATUS current
    DESCRIPTION
        "Maximum size of a received fragment in bytes."
    ::= { dnp3General 4 }
    --1.3.6.1.4.1.3052.10.2.4.23.1.4

dnp3MaxTXFragmentSize OBJECT-TYPE
    SYNTAX Integer32
    MAX-ACCESS read-write
    STATUS current
    DESCRIPTION
        "Maximum size of a transmitted fragment in bytes."
    ::= { dnp3General 5 }
    --1.3.6.1.4.1.3052.10.2.4.23.1.5

dnp3UnsolResponseEnable OBJECT-TYPE
    SYNTAX DisplayString
    MAX-ACCESS read-write
    STATUS current
    DESCRIPTION
        "Enable unsolicited responses."
    ::= { dnp3General 6 }
    --1.3.6.1.4.1.3052.10.2.4.23.1.6

dnp3UnsolResponseTimeout OBJECT-TYPE
    SYNTAX Integer32
    MAX-ACCESS read-write
    STATUS current
    DESCRIPTION
        "Unsolicited response confirmation timeout in seconds."
    ::= { dnp3General 7 }
    --1.3.6.1.4.1.3052.10.2.4.23.1.7

dnp3UnsolResponseRetries OBJECT-TYPE
    SYNTAX Integer32
    MAX-ACCESS read-write
    STATUS current
    DESCRIPTION
        "Unsolicited response confirmation timeout retries."
    ::= { dnp3General 8 }
    --1.3.6.1.4.1.3052.10.2.4.23.1.8

dnp3LogFilter OBJECT-TYPE
    SYNTAX Integer32
    MAX-ACCESS read-write
    STATUS current
    DESCRIPTION
        "Numeric code to describe what gets logged (for support/troubleshooting analysis only)."
    ::= { dnp3General 9 }
    --1.3.6.1.4.1.3052.10.2.4.23.1.9

dnp3OutstationTCPPort OBJECT-TYPE
    SYNTAX Integer32
    MAX-ACCESS read-write
    STATUS current
    DESCRIPTION
        "TCP port on which to listen for connections."
    ::= { dnp3Outstation 1 }
    --1.3.6.1.4.1.3052.10.2.4.23.2.1

dnp3OutstationDNP3Address OBJECT-TYPE
    SYNTAX Integer32
    MAX-ACCESS read-write
    STATUS current
    DESCRIPTION
        "DNP3 address of the outstation. "
    ::= { dnp3Outstation 2 }
    --1.3.6.1.4.1.3052.10.2.4.23.2.2

dnp3OutstationMasterIPAddress OBJECT-TYPE
    SYNTAX DisplayString
    MAX-ACCESS read-write
    STATUS current
    DESCRIPTION
        "IP (v4 or v6) address (non-resolved) of the intended master. Default blank.
        If non-blank then the outstation drops connections from TCP clients not at this address."
    ::= { dnp3Outstation 3 }
    --1.3.6.1.4.1.3052.10.2.4.23.2.3

dnp3OutstationMasterDNP3Address OBJECT-TYPE
    SYNTAX Integer32
    MAX-ACCESS read-write
    STATUS current
    DESCRIPTION
        "DNP3 address of the intended master upon connection. Range 0 - 65520, default 65520.
        If set to 0 - 65519 then the outstation discards DNP3 data link frames not from this
        address. 65520 is not a valid DNP3 address; if set to 65520 then it means the
        outstation accepts frames from any address."
    ::= { dnp3Outstation 4 }
    --1.3.6.1.4.1.3052.10.2.4.23.2.4

dnp3OutstationUnsolResponseDNP3Address OBJECT-TYPE
    SYNTAX Integer32
    MAX-ACCESS read-write
    STATUS current
    DESCRIPTION
        "DNP3 destination address of unsolicited responses. Range 0 - 65520, default 65520.
        If set to 65520 then it means the outstation addresses data link frames of
        unsolicited responses to the source address of the last accepted frame received
        from the master."
    ::= { dnp3Outstation 5 }
    --1.3.6.1.4.1.3052.10.2.4.23.2.5



dnp3DuplicateFragmentCount OBJECT-TYPE
    SYNTAX Integer32
    MAX-ACCESS read-only
    STATUS current
    DESCRIPTION
        "Count of duplicate fragments received."
    ::= { dnp3Error 1 }
    --1.3.6.1.4.1.3052.10.2.4.23.4.1

dnp3CollidingFragmentCount OBJECT-TYPE
    SYNTAX Integer32
    MAX-ACCESS read-only
    STATUS current
    DESCRIPTION
        "Count of colliding fragments received."
    ::= { dnp3Error 2 }
    --1.3.6.1.4.1.3052.10.2.4.23.4.2

dnp3UnsolResponseCfmFailCount OBJECT-TYPE
    SYNTAX Integer32
    MAX-ACCESS read-only
    STATUS current
    DESCRIPTION
        "Count of unsolicited response confirmation failures."
    ::= { dnp3Error 3 }
    --1.3.6.1.4.1.3052.10.2.4.23.4.3

dnp3SolCfmFailCount OBJECT-TYPE
    SYNTAX Integer32
    MAX-ACCESS read-only
    STATUS current
    DESCRIPTION
        "Count of solicited response confirmation failures."
    ::= { dnp3Error 4 }
    --1.3.6.1.4.1.3052.10.2.4.23.4.4

dnp3ObjParseErrorCount OBJECT-TYPE
    SYNTAX Integer32
    MAX-ACCESS read-only
    STATUS current
    DESCRIPTION
        "Count of received data object parse errors."
    ::= { dnp3Error 5 }
    --1.3.6.1.4.1.3052.10.2.4.23.4.5

dnp3FrameParseErrorCount OBJECT-TYPE
    SYNTAX Integer32
    MAX-ACCESS read-only
    STATUS current
    DESCRIPTION
        "Count of received frame parse errors."
    ::= { dnp3Error 6 }
    --1.3.6.1.4.1.3052.10.2.4.23.4.6

dnp3DiscardedFrameCount OBJECT-TYPE
    SYNTAX Integer32
    MAX-ACCESS read-only
    STATUS current
    DESCRIPTION
        "Count of received frames discarded."
    ::= { dnp3Error 7 }
    --1.3.6.1.4.1.3052.10.2.4.23.4.7

dnp3BadBlockCount OBJECT-TYPE
    SYNTAX Integer32
    MAX-ACCESS read-only
    STATUS current
    DESCRIPTION
        "Count of received frame blocks with bad CRC."
    ::= { dnp3Error 8 }
    --1.3.6.1.4.1.3052.10.2.4.23.4.8

dnp3UnsolResponseRetryCount OBJECT-TYPE
    SYNTAX Integer32
    MAX-ACCESS read-only
    STATUS current
    DESCRIPTION
        "Count of retried unsolicited responses."
    ::= { dnp3Error 9 }
    --1.3.6.1.4.1.3052.10.2.4.23.4.9

dnp3UnsupportedFrameCount OBJECT-TYPE
    SYNTAX Integer32
    MAX-ACCESS read-only
    STATUS current
    DESCRIPTION
        "Count of received frames accepted (good CRC and addressed to
        the outstation) with an unsupported data link function code."
    ::= { dnp3Error 10 }
    --1.3.6.1.4.1.3052.10.2.4.23.4.10


dnp3OutstationCount OBJECT-TYPE
    SYNTAX Integer32
    MAX-ACCESS read-only
    STATUS current
    DESCRIPTION
        "Count of running outstation instances."
    ::= { dnp3Status 1 }
    --1.3.6.1.4.1.3052.10.2.4.23.5.1

dnp3ConnPeer OBJECT-TYPE
    SYNTAX DisplayString
    MAX-ACCESS read-only
    STATUS current
    DESCRIPTION
        "Description of the connected peer (the TCP socket endpoint of the master)."
    ::= { dnp3Status 2 }
    --1.3.6.1.4.1.3052.10.2.4.23.5.2

dnp3StartTime OBJECT-TYPE
    SYNTAX DisplayString
    MAX-ACCESS read-only
    STATUS current
    DESCRIPTION
        "When the outstation instance started."
    ::= { dnp3Status 3 }
    --1.3.6.1.4.1.3052.10.2.4.23.5.3

dnp3EventAwaitingSolCfmCount OBJECT-TYPE
    SYNTAX Integer32
    MAX-ACCESS read-only
    STATUS current
    DESCRIPTION
        "Number of events reported and awaiting solicited confirmation; usually 0."
    ::= { dnp3Status 4 }
    --1.3.6.1.4.1.3052.10.2.4.23.5.4

dnp3EventAwaitingUnsolCfmCount OBJECT-TYPE
    SYNTAX Integer32
    MAX-ACCESS read-only
    STATUS current
    DESCRIPTION
        "Number of events reported and awaiting unsolicited confirmation; usually 0."
    ::= { dnp3Status 5 }
    --1.3.6.1.4.1.3052.10.2.4.23.5.5

dnp3EventCount OBJECT-TYPE
    SYNTAX Integer32
    MAX-ACCESS read-only
    STATUS current
    DESCRIPTION
        "Number of total events buffered (that is, existing, maybe reported, but not confirmed)."
    ::= { dnp3Status 6 }
    --1.3.6.1.4.1.3052.10.2.4.23.5.6

dnp3EventClass1Count OBJECT-TYPE
    SYNTAX Integer32
    MAX-ACCESS read-only
    STATUS current
    DESCRIPTION
        "Portion of the total events buffered that are class 1 events."
    ::= { dnp3Status 7 }
    --1.3.6.1.4.1.3052.10.2.4.23.5.7

dnp3EventClass2Count OBJECT-TYPE
    SYNTAX Integer32
    MAX-ACCESS read-only
    STATUS current
    DESCRIPTION
        "Portion of the total events buffered that are class 2 events."
    ::= { dnp3Status 8 }
    --1.3.6.1.4.1.3052.10.2.4.23.5.8

dnp3EventClass3Count OBJECT-TYPE
    SYNTAX Integer32
    MAX-ACCESS read-only
    STATUS current
    DESCRIPTION
        "Portion of the total events buffered that are class 3 events."
    ::= { dnp3Status 9 }
    --1.3.6.1.4.1.3052.10.2.4.23.5.9

dnp3RxFragmentTime OBJECT-TYPE
    SYNTAX DisplayString
    MAX-ACCESS read-only
    STATUS current
    DESCRIPTION
        "Time of the last fragment received."
    ::= { dnp3Status 10 }
    --1.3.6.1.4.1.3052.10.2.4.23.5.10

dnp3TxFragmentTime OBJECT-TYPE
    SYNTAX DisplayString
    MAX-ACCESS read-only
    STATUS current
    DESCRIPTION
        "Time of the last fragment transmitted."
    ::= { dnp3Status 11 }
    --1.3.6.1.4.1.3052.10.2.4.23.5.11

dnp3TxCachedResponseCount OBJECT-TYPE
    SYNTAX Integer32
    MAX-ACCESS read-only
    STATUS current
    DESCRIPTION
        "Count of cached responses transmitted."
    ::= { dnp3Status 12 }
    --1.3.6.1.4.1.3052.10.2.4.23.5.12

dnp3TxUnsolResponseCount OBJECT-TYPE
    SYNTAX Integer32
    MAX-ACCESS read-only
    STATUS current
    DESCRIPTION
        "Count of unsolicited responses transmitted."
    ::= { dnp3Status 13 }
    --1.3.6.1.4.1.3052.10.2.4.23.5.13

dnp3TxSolResponseCount OBJECT-TYPE
    SYNTAX Integer32
    MAX-ACCESS read-only
    STATUS current
    DESCRIPTION
        "Count of solicited responses transmitted."
    ::= { dnp3Status 14 }
    --1.3.6.1.4.1.3052.10.2.4.23.5.14

dnp3TxFragmentReqCfmCount OBJECT-TYPE
    SYNTAX Integer32
    MAX-ACCESS read-only
    STATUS current
    DESCRIPTION
        "Count of fragments transmitted that required confirmation."
    ::= { dnp3Status 15 }
    --1.3.6.1.4.1.3052.10.2.4.23.5.15

dnp3RxUnsolResponseCfmCount OBJECT-TYPE
    SYNTAX Integer32
    MAX-ACCESS read-only
    STATUS current
    DESCRIPTION
        "Count of unsolicited response confirmations received."
    ::= { dnp3Status 16 }
    --1.3.6.1.4.1.3052.10.2.4.23.5.16

dnp3RxSolResponseCfmCount OBJECT-TYPE
    SYNTAX Integer32
    MAX-ACCESS read-only
    STATUS current
    DESCRIPTION
        "Count of solicited response confirmations received."
    ::= { dnp3Status 17 }
    --1.3.6.1.4.1.3052.10.2.4.23.5.17

dnp3RxFunctionCount OBJECT-TYPE
    SYNTAX Integer32
    MAX-ACCESS read-only
    STATUS current
    DESCRIPTION
        "Count of total application function codes received."
    ::= { dnp3Status 18 }
    --1.3.6.1.4.1.3052.10.2.4.23.5.18

dnp3RxReadFunctionCount OBJECT-TYPE
    SYNTAX Integer32
    MAX-ACCESS read-only
    STATUS current
    DESCRIPTION
        "Count of read application function codes received."
    ::= { dnp3Status 19 }
    --1.3.6.1.4.1.3052.10.2.4.23.5.19

dnp3RxWriteFunctionCount OBJECT-TYPE
    SYNTAX Integer32
    MAX-ACCESS read-only
    STATUS current
    DESCRIPTION
        "Count of write application function codes received."
    ::= { dnp3Status 20 }
    --1.3.6.1.4.1.3052.10.2.4.23.5.20

dnp3RxDirOpFunctionCount OBJECT-TYPE
    SYNTAX Integer32
    MAX-ACCESS read-only
    STATUS current
    DESCRIPTION
        "Count of direct operate application function codes received."
    ::= { dnp3Status 21 }
    --1.3.6.1.4.1.3052.10.2.4.23.5.21

dnp3RxEnableURCount OBJECT-TYPE
    SYNTAX Integer32
    MAX-ACCESS read-only
    STATUS current
    DESCRIPTION
        "Count of enable unsolicited application function codes received."
    ::= { dnp3Status 22 }
    --1.3.6.1.4.1.3052.10.2.4.23.5.22

dnp3RxDisableURCount OBJECT-TYPE
    SYNTAX Integer32
    MAX-ACCESS read-only
    STATUS current
    DESCRIPTION
        "Count of disabled unsolicited application function codes received."
    ::= { dnp3Status 23 }
    --1.3.6.1.4.1.3052.10.2.4.23.5.23

dnp3RxSolObjectCount OBJECT-TYPE
    SYNTAX Integer32
    MAX-ACCESS read-only
    STATUS current
    DESCRIPTION
        "Count of data objects received in solicited requests."
    ::= { dnp3Status 40 }
    --1.3.6.1.4.1.3052.10.2.4.23.5.40

dnp3TxSolObjectCount OBJECT-TYPE
    SYNTAX Integer32
    MAX-ACCESS read-only
    STATUS current
    DESCRIPTION
        "Count of data objects transmitted in solicted responses."
    ::= { dnp3Status 41 }
    --1.3.6.1.4.1.3052.10.2.4.23.5.41

dnp3RxFrameTime OBJECT-TYPE
    SYNTAX DisplayString
    MAX-ACCESS read-only
    STATUS current
    DESCRIPTION
        "Time of the last frame received."
    ::= { dnp3Status 42 }
    --1.3.6.1.4.1.3052.10.2.4.23.5.42

dnp3TxFrameTime OBJECT-TYPE
    SYNTAX DisplayString
    MAX-ACCESS read-only
    STATUS current
    DESCRIPTION
        "Time of the last frame transmitted."
    ::= { dnp3Status 43 }
    --1.3.6.1.4.1.3052.10.2.4.23.5.43

dnp3TxFrameCount OBJECT-TYPE
    SYNTAX Integer32
    MAX-ACCESS read-only
    STATUS current
    DESCRIPTION
        "Count of total frames transmitted."
    ::= { dnp3Status 44 }
    --1.3.6.1.4.1.3052.10.2.4.23.5.44

dnp3RxAcceptedFrameCount OBJECT-TYPE
    SYNTAX Integer32
    MAX-ACCESS read-only
    STATUS current
    DESCRIPTION
        "Count of total frames accepted."
    ::= { dnp3Status 45 }
    --1.3.6.1.4.1.3052.10.2.4.23.5.45

dnp3RxSupportedFrameCount OBJECT-TYPE
    SYNTAX Integer32
    MAX-ACCESS read-only
    STATUS current
    DESCRIPTION
        "Count of total frames accepted with a supported data link function code."
    ::= { dnp3Status 46 }
    --1.3.6.1.4.1.3052.10.2.4.23.5.46


--***************************************************************************************
--Modem Section  2.5
--***************************************************************************************





modemFormat OBJECT-TYPE
    SYNTAX DisplayString
    MAX-ACCESS read-write
    STATUS current
    DESCRIPTION
        "Modem data format (8N1,7E1,7O1,7N1)"
    ::= { modem 1 }
    --1.3.6.1.4.1.3052.10.2.5.1

modemInitString OBJECT-TYPE
    SYNTAX DisplayString
    MAX-ACCESS read-write
    STATUS current
    DESCRIPTION
        "Init string for modem"
    ::= { modem 2 }
    --1.3.6.1.4.1.3052.10.2.5.2


modemCallAttempts OBJECT-TYPE
    SYNTAX Integer32
    MAX-ACCESS read-write
    STATUS current
    DESCRIPTION
        "Max mumber of times the modem should try to call out until
        successful connect"
    ::= { modem 4 }
    --1.3.6.1.4.1.3052.10.2.5.4

modemCallDelay OBJECT-TYPE
    SYNTAX Integer32
    MAX-ACCESS read-write
    STATUS current
    DESCRIPTION
        "Minimum delay (seconds) between callouts"
    ::= { modem 5 }
    --1.3.6.1.4.1.3052.10.2.5.6


modemCmdTimout OBJECT-TYPE
    SYNTAX Integer32
    MAX-ACCESS read-write
    STATUS current
    DESCRIPTION
        "Number of minutes after which an idle command session via
        modem is terminated"
    ::= { modem 6 }
    --1.3.6.1.4.1.3052.10.2.5.6

modemGoto OBJECT-TYPE
    SYNTAX DisplayString
    MAX-ACCESS read-write
    STATUS current
    DESCRIPTION
        "When a user connects, where that user is routed (command
        session, passthrough to port 1, passthrough to port 2, etc.)"
    ::= { modem 7 }
    --1.3.6.1.4.1.3052.10.2.5.7


modemCLIDEnable OBJECT-TYPE
    SYNTAX DisplayString
    MAX-ACCESS read-write
    STATUS current
    DESCRIPTION
        "ON/OFF Calling Line Identification security"
    ::= { modemClid 1 }
    --1.3.6.1.4.1.3052.10.2.5.8.1


modemCLIDNumberTable OBJECT-TYPE
    SYNTAX SEQUENCE OF ModemCLIDNumberConfig
    MAX-ACCESS not-accessible
    STATUS current
    DESCRIPTION
        "Table of authorized callers identified by phone number"
    ::= { modemClid 2 }
    --1.3.6.1.4.1.3052.10.2.5.8.2

modemCLIDNumberEntry OBJECT-TYPE
    SYNTAX ModemCLIDNumberConfig
    MAX-ACCESS not-accessible
    STATUS current
    DESCRIPTION
        "Entry for table of CLID numbers"
    INDEX { modemCLIDNumberIndex }
    ::= { modemCLIDNumberTable 1 }
    --1.3.6.1.4.1.3052.10.2.5.8.2.1

modemCLIDNumberIndex OBJECT-TYPE
    SYNTAX Integer32 (1..20)
    MAX-ACCESS read-only
    STATUS current
    DESCRIPTION
        "Index for table of CLID numbers"
    ::= { modemCLIDNumberEntry 1 }
    --1.3.6.1.4.1.3052.10.2.5.8.2.1.1

modemCLIDNumber OBJECT-TYPE
    SYNTAX DisplayString
    MAX-ACCESS read-write
    STATUS current
    DESCRIPTION
        "auhorized CLID number"
    ::= { modemCLIDNumberEntry 2 }
    --1.3.6.1.4.1.3052.10.2.5.8.2.1.2

modemTAPInitString OBJECT-TYPE
    SYNTAX DisplayString
    MAX-ACCESS read-write
    STATUS current
    DESCRIPTION
        "Init string to use for TAP (pager) connections"
    ::= { modem 9 }
    --1.3.6.1.4.1.3052.10.2.5.9

modemTAP8N1 OBJECT-TYPE
    SYNTAX DisplayString
    MAX-ACCESS read-write
    STATUS current
    DESCRIPTION
        "ON/OFF: use 8N1 data/parity/stop for TAP connections"
    ::= { modem 10 }
    --1.3.6.1.4.1.3052.10.2.5.10


--***************************************************************************************
--Time Section  2.8
--***************************************************************************************

clock OBJECT-TYPE
    SYNTAX DisplayString
    MAX-ACCESS read-write
    STATUS current
    DESCRIPTION
        "Text string for date and time;
        e.g. 'SUN 01/02/98 12:34:27'.  When setting
        this object, only the date and time are
        required; the unit will ignore a specified
        day of week because it is calculated from
        the date and time.  When this object is included
        in a notification as a varbind, it represents
        the time that the triggering event occurred."
    ::= { time 1 }
    --1.3.6.1.4.1.3052.10.2.8.1

--***************************************************************************************
--Console Section  2.10
--***************************************************************************************


consoleDuplex OBJECT-TYPE
    SYNTAX DisplayString
    MAX-ACCESS read-write
    STATUS current
    DESCRIPTION
        "ON/OFF characters echoed on telnet command session"
    ::= { console 1 }
    --1.3.6.1.4.1.3052.10.2.10.1

consoleTimeout OBJECT-TYPE
    SYNTAX Integer32
    MAX-ACCESS read-write
    STATUS current
    DESCRIPTION
        "Minutes of inactivity after which telnet command session is terminated"
    ::= { console 2 }
    --1.3.6.1.4.1.3052.10.2.10.2

consoleConfirm OBJECT-TYPE
    SYNTAX DisplayString
    MAX-ACCESS read-write
    STATUS current
    DESCRIPTION
        "ON/OFF Prompt to confirm certain actions"
    ::= { console 7 }
    --1.3.6.1.4.1.3052.10.2.10.7

--***************************************************************************************
--Core Security Section 2.11.1
--***************************************************************************************

scShowPasswordPrompt OBJECT-TYPE
    SYNTAX DisplayString
    MAX-ACCESS read-write
    STATUS current
    DESCRIPTION
        "ON/OFF show password prompt upon login"
    ::= { secCore 1 }
    --1.3.6.1.4.1.3052.10.2.11.1.1

scConsoleLoginRequired  OBJECT-TYPE
    SYNTAX DisplayString
    MAX-ACCESS read-write
    STATUS current
    DESCRIPTION
        "ON/OFF login required upon connecting via console"
    ::= { secCore 2 }
    --1.3.6.1.4.1.3052.10.2.11.1.2

scModemLoginRequired OBJECT-TYPE
    SYNTAX DisplayString
    MAX-ACCESS read-write
    STATUS current
    DESCRIPTION
        "ON/OFF login required upon connecting via modem"
    ::= { secCore 3 }
    --1.3.6.1.4.1.3052.10.2.11.1.3

scTelnetLoginRequired OBJECT-TYPE
    SYNTAX DisplayString
    MAX-ACCESS read-write
    STATUS current
    DESCRIPTION
        "ON/OFF login required upon connecting via Telnet"
    ::= { secCore 4 }
    --1.3.6.1.4.1.3052.10.2.11.1.4

scTelnetPTLoginRequired OBJECT-TYPE
    SYNTAX DisplayString
    MAX-ACCESS read-write
    STATUS current
    DESCRIPTION
        "ON/OFF login required upon connecting via Telnet to pass-
        through ports (TCP ports 210x)"
    ::= { secCore 5 }
    --1.3.6.1.4.1.3052.10.2.11.1.5

scRTSLoginRequired OBJECT-TYPE
    SYNTAX DisplayString
    MAX-ACCESS read-write
    STATUS current
    DESCRIPTION
        "ON/OFF login required upon connecting to RTS (TCP ports 220x)"
    ::= { secCore 6 }
    --1.3.6.1.4.1.3052.10.2.11.1.6

scAuthMode OBJECT-TYPE
    SYNTAX DisplayString
    MAX-ACCESS read-write
    STATUS current
    DESCRIPTION
        "Authentication mode (USERNAME/PW,PW/USERNAME,PASSWORD ONLY)"
    ::= { secCore 7 }
    --1.3.6.1.4.1.3052.10.2.11.1.7

scRightsGroup OBJECT-TYPE
    SYNTAX DisplayString
    MAX-ACCESS read-write
    STATUS current
    DESCRIPTION
        "The set of aliases used for the 8 available rights levels"
    ::= { secCore 8 }
    --1.3.6.1.4.1.3052.10.2.11.1.8


--***************************************************************************************
--User Security Section 2.11.2
--***************************************************************************************


secUserTable OBJECT-TYPE
    SYNTAX SEQUENCE OF SecUserConfig
    MAX-ACCESS not-accessible
    STATUS current
    DESCRIPTION
        "Table of users"
    ::= { unitSecurity 2 }
    --1.3.6.1.4.1.3052.10.2.11.2

secUserEntry OBJECT-TYPE
    SYNTAX SecUserConfig
    MAX-ACCESS not-accessible
    STATUS current
    DESCRIPTION
        "Entry for table of users"
    INDEX { secUserIndex }
    ::= { secUserTable 1 }
    --1.3.6.1.4.1.3052.10.2.11.2.1

secUserIndex OBJECT-TYPE
    SYNTAX Integer32 (1..12)
    MAX-ACCESS read-only
    STATUS current
    DESCRIPTION
        "Index for table of users"
    ::= { secUserEntry 1 }
    --1.3.6.1.4.1.3052.10.2.11.2.1.1

secUserEnable OBJECT-TYPE
    SYNTAX DisplayString
    MAX-ACCESS read-write
    STATUS current
    DESCRIPTION
        "ON/OFF enable user"
    ::= { secUserEntry 2 }
    --1.3.6.1.4.1.3052.10.2.11.2.1.2

secUserConnectVia OBJECT-TYPE
    SYNTAX DisplayString
    MAX-ACCESS read-write
    STATUS current
    DESCRIPTION
        "Methods by which user is allowed to connect:
        L=local (console)
        T=Telnet
        M=modem
        F=FTP
        R=RTS
        S=SSH
        "
    ::= { secUserEntry 5 }
    --1.3.6.1.4.1.3052.10.2.11.2.1.5

secUserLoginTo OBJECT-TYPE
    SYNTAX DisplayString
    MAX-ACCESS read-write
    STATUS current
    DESCRIPTION
        "The function presented to the user upon login (COMMAND,
        PASSTHROUGH,MENU)"
    ::= { secUserEntry 6 }
    --1.3.6.1.4.1.3052.10.2.11.2.1.6

secUserAccessFile OBJECT-TYPE
    SYNTAX DisplayString
    MAX-ACCESS read-write
    STATUS current
    DESCRIPTION
        "The default access file associated with the user"
    ::= { secUserEntry 7 }
    --1.3.6.1.4.1.3052.10.2.11.2.1.7

secUserPTEscapeTo OBJECT-TYPE
    SYNTAX DisplayString
    MAX-ACCESS read-write
    STATUS current
    DESCRIPTION
        "The function presented to the user upon escaping pass-
        through: currently only MENU"
    ::= { secUserEntry 9 }
    --1.3.6.1.4.1.3052.10.2.11.2.1.9

secUserPPPType OBJECT-TYPE
    SYNTAX DisplayString
    MAX-ACCESS read-write
    STATUS current
    DESCRIPTION
        "The kind of PPP access allowed to this user cannot connect
        via PPP (NONE), can connect but only to the unit (LOCAL), or
        can connect and route to Ethernet (ROUTING)"
    ::= { secUserEntry 10 }
    --1.3.6.1.4.1.3052.10.2.11.2.1.10

secUserRights OBJECT-TYPE
    SYNTAX DisplayString
    MAX-ACCESS read-write
    STATUS current
    DESCRIPTION
        "The rights level granted to this user"
    ::= { secUserEntry 11 }
    --1.3.6.1.4.1.3052.10.2.11.2.1.11

secUserEventsReadAccess OBJECT-TYPE
    SYNTAX DisplayString
    MAX-ACCESS read-write
    STATUS current
    DESCRIPTION
        "DENY/ALLOW user to read the events/alarms file"
    ::= { secUserEntry 13 }
    --1.3.6.1.4.1.3052.10.2.11.2.1.13

secUserAuditReadAccess OBJECT-TYPE
    SYNTAX DisplayString
    MAX-ACCESS read-write
    STATUS current
    DESCRIPTION
        "DENY/ALLOW user to read the audit log"
    ::= { secUserEntry 14 }
    --1.3.6.1.4.1.3052.10.2.11.2.1.14

secUserEventsWriteAccess OBJECT-TYPE
    SYNTAX DisplayString
    MAX-ACCESS read-write
    STATUS current
    DESCRIPTION
        "DENY/ALLOW user to delete the events file"
    ::= { secUserEntry 16 }
    --1.3.6.1.4.1.3052.10.2.11.2.1.16

secUserAuditWriteAccess OBJECT-TYPE
    SYNTAX DisplayString
    MAX-ACCESS read-write
    STATUS current
    DESCRIPTION
        "DENY/ALLOW user to write to the audit log"
    ::= { secUserEntry 17 }
    --1.3.6.1.4.1.3052.10.2.11.2.1.17

secUserExpiration OBJECT-TYPE
    SYNTAX DisplayString
    MAX-ACCESS read-write
    STATUS current
    DESCRIPTION
        "Expiration date/time of this user"
    ::= { secUserEntry 18 }
    --1.3.6.1.4.1.3052.10.2.11.2.1.18

secUserCallbackNumber1 OBJECT-TYPE
    SYNTAX DisplayString
    MAX-ACCESS read-write
    STATUS current
    DESCRIPTION
        "Number slot 1 the unit calls for dialback"
    ::= { secUserEntry 19 }
    --1.3.6.1.4.1.3052.10.2.11.2.1.19

secUserCallbackNumber2 OBJECT-TYPE
    SYNTAX DisplayString
    MAX-ACCESS read-write
    STATUS current
    DESCRIPTION
        "Number slot 2 the unit calls for dialback"
    ::= { secUserEntry 20 }
    --1.3.6.1.4.1.3052.10.2.11.2.1.20

secUserCallbackNumber3 OBJECT-TYPE
    SYNTAX DisplayString
    MAX-ACCESS read-write
    STATUS current
    DESCRIPTION
        "Number slot 3 the unit calls for dialback"
    ::= { secUserEntry 21 }
    --1.3.6.1.4.1.3052.10.2.11.2.1.21

secUserChallengeTelnetMode OBJECT-TYPE
    SYNTAX DisplayString
    MAX-ACCESS read-write
    STATUS current
    DESCRIPTION
        "Telnet challenge mode: when user logs in via telnet, unit
        allows access (OFF), presents a challenge (CHALLENGE), or
        unit sends a one-time-password (SEND PASSWORD) to a
        destination configured by secUserChallengeTelnetSendTo"
    ::= { secUserEntry 22 }
    --1.3.6.1.4.1.3052.10.2.11.2.1.22

secUserChallengeModemMode OBJECT-TYPE
    SYNTAX DisplayString
    MAX-ACCESS read-write
    STATUS current
    DESCRIPTION
        "Modem challenge mode: when user logs in via modem, unit
        allows access (OFF), presents a challenge (CHALLENGE), sends
        a one-time-password (SEND PASSWORD) to a destination
        configured by secUserChallengeTelnetSendTo, or dials a
        number (CALLBACK) configured with secUserCallbackNumberx"
    ::= { secUserEntry 23 }
    --1.3.6.1.4.1.3052.10.2.11.2.1.23

secUserChallengeConsoleMode OBJECT-TYPE
    SYNTAX DisplayString
    MAX-ACCESS read-write
    STATUS current
    DESCRIPTION
        "Console challenge mode: when user logs in via console, unit
        allows access (OFF), or presents a challenge (CHALLENGE)"
    ::= { secUserEntry 24 }
    --1.3.6.1.4.1.3052.10.2.11.2.1.24

secUserChallengeTelnetSendTo OBJECT-TYPE
    SYNTAX DisplayString
    MAX-ACCESS read-write
    STATUS current
    DESCRIPTION
        "Email action used as the destination address for one-time-
        password when a user logs in with a challenge mode of
        SEND PASSWORD"
    ::= { secUserEntry 25 }
    --1.3.6.1.4.1.3052.10.2.11.2.1.25

secUserChallengeModemSendTo OBJECT-TYPE
    SYNTAX DisplayString
    MAX-ACCESS read-write
    STATUS current
    DESCRIPTION
        "Modem action used as the destination phone number for one-
        time-password when a user logs in with a challenge mode of
        SEND PASSWORD"
    ::= { secUserEntry 26 }
    --1.3.6.1.4.1.3052.10.2.11.2.1.26

secUserChallengeExpiration OBJECT-TYPE
    SYNTAX Integer32 (0..180)
    MAX-ACCESS read-write
    STATUS current
    DESCRIPTION
        "Time (in minutes) after which a one-time-password is sent
        that it can be used to log in"
    ::= { secUserEntry 27 }
    --1.3.6.1.4.1.3052.10.2.11.2.1.27


--***************************************************************************************
--Factory Security Section 2.11.3
--***************************************************************************************

sfEnable OBJECT-TYPE
    SYNTAX DisplayString
    MAX-ACCESS read-write
    STATUS current
    DESCRIPTION
        "ON/OFF enable factory access"
    ::= { secFactory 1 }
    --1.3.6.1.4.1.3052.10.2.11.3.1

sfSecret OBJECT-TYPE
    SYNTAX DisplayString
    MAX-ACCESS read-write
    STATUS current
    DESCRIPTION
        "Secret used for factory access"
    ::= { secFactory 2 }
    --1.3.6.1.4.1.3052.10.2.11.3.2


--***************************************************************************************
--SSH Security Section 2.11.3
--***************************************************************************************

--***************************************************************************************
--Event Section   2.12
--***************************************************************************************

--***************************************************************************************
--Event Core Section   2.12.1
--***************************************************************************************


evClassNameTable OBJECT-TYPE
    SYNTAX SEQUENCE OF EventClassConfig
    MAX-ACCESS not-accessible
    STATUS current
    DESCRIPTION
        "Table of classes"
    ::= { evCore 1 }
    --1.3.6.1.4.1.3052.10.2.12.1.1

evClassNameEntry OBJECT-TYPE
    SYNTAX EventClassConfig
    MAX-ACCESS not-accessible
    STATUS current
    DESCRIPTION
        "Entry for table of classes"
    INDEX { evClassNameIndex }
    ::= { evClassNameTable 1 }
    --1.3.6.1.4.1.3052.10.2.12.1.1.1

evClassNameIndex OBJECT-TYPE
    SYNTAX Integer32 (1..12)
    MAX-ACCESS read-only
    STATUS current
    DESCRIPTION
        "Index for table of classes"
    ::= { evClassNameEntry 1 }
    --1.3.6.1.4.1.3052.10.2.12.1.1.1.1

evClassName OBJECT-TYPE
    SYNTAX DisplayString
    MAX-ACCESS read-write
    STATUS current
    DESCRIPTION
        "Class name for this slot"
    ::= { evClassNameEntry 2 }
    --1.3.6.1.4.1.3052.10.2.12.1.1.1.2

evReminderInterval OBJECT-TYPE
    SYNTAX Integer32 (0..65535)
    MAX-ACCESS read-write
    STATUS current
    DESCRIPTION
        "Interval (minutes) between EventSensor reminder events"
    ::= { evCore 2 }
    --1.3.6.1.4.1.3052.10.2.12.1.2

evLogEnable OBJECT-TYPE
    SYNTAX DisplayString
    MAX-ACCESS read-write
    STATUS current
    DESCRIPTION
        "ON/OFF enable event log"
    ::= { evLog 1 }
    --1.3.6.1.4.1.3052.10.2.12.1.3.1

evLogStoreAlarm OBJECT-TYPE
    SYNTAX DisplayString
    MAX-ACCESS read-write
    STATUS current
    DESCRIPTION
        "ON/OFF store data alarms in event log"
    ::= { evLog 2 }
    --1.3.6.1.4.1.3052.10.2.12.1.3.2

evLogMaxSize OBJECT-TYPE
    SYNTAX Integer32
    MAX-ACCESS read-write
    STATUS current
    DESCRIPTION
        "max size (in KB) of event log"
    ::= { evLog 3 }
    --1.3.6.1.4.1.3052.10.2.12.1.3.3

evLogStoreSensor OBJECT-TYPE
    SYNTAX DisplayString
    MAX-ACCESS read-write
    STATUS current
    DESCRIPTION
        "ON/OFF store EventSensor events in event log"
    ::= { evLog 4 }
    --1.3.6.1.4.1.3052.10.2.12.1.3.4

evLogTimeStampAlarms OBJECT-TYPE
    SYNTAX DisplayString
    MAX-ACCESS read-write
    STATUS current
    DESCRIPTION
        "ON/OFF put timestamps on event log entries"
    ::= { evLog 5 }
    --1.3.6.1.4.1.3052.10.2.12.1.3.5

evLogPrependName OBJECT-TYPE
    SYNTAX DisplayString
    MAX-ACCESS read-write
    STATUS current
    DESCRIPTION
        "ON/OFF prepend data event name to data alarm records in event
        log"
    ::= { evLog 6 }
    --1.3.6.1.4.1.3052.10.2.12.1.3.6


evMgmtReprocess OBJECT-TYPE
    SYNTAX DisplayString
    MAX-ACCESS read-write
    STATUS current
    DESCRIPTION
        "Number of sensors that have generated events since reset.
        Write this to reprocess each sensor's last generated event
        since reset.  The value to write determines what kind of
        events should be reprocessed:
                'all': all sensor events
                 'cc': cc events
        'temperature': temperature events
           'humidity': humidity events
             'analog': analog input events"
    ::= { evMgmt 3 }
    --1.3.6.1.4.1.3052.10.2.12.1.4.3



--***************************************************************************************
--Data event section 2.12.2
--***************************************************************************************

evdExitOnTrue OBJECT-TYPE
    SYNTAX DisplayString
    MAX-ACCESS read-write
    STATUS current
    DESCRIPTION
        "ON/OFF: Data alarm evaluator stops checking record against
        alarm equations when it finds an equation that matches"
    ::= { evdCore 1 }
    --1.3.6.1.4.1.3052.10.2.12.2.1.1.1

evdFilterAction OBJECT-TYPE
    SYNTAX DisplayString
    MAX-ACCESS read-write
    STATUS current
    DESCRIPTION
        "What happens to a record that matches an equation:
        REJECT/ACCEPT"
    ::= { evdCore 2 }
    --1.3.6.1.4.1.3052.10.2.12.2.1.1.2

evdWildCardChar OBJECT-TYPE
    SYNTAX Integer32
    MAX-ACCESS read-write
    STATUS current
    DESCRIPTION
        "Character (in decimal ASCII code format) used to indicate
        wildcards in data alarm equation"
    ::= { evdCore 3 }
    --1.3.6.1.4.1.3052.10.2.12.2.1.1.3


evdTable OBJECT-TYPE
    SYNTAX SEQUENCE OF DataEventConfig
    MAX-ACCESS not-accessible
    STATUS current
    DESCRIPTION
        "Table of data events"
    ::= { evData 2 }
    --1.3.6.1.4.1.3052.10.2.12.2.2

evdEntry OBJECT-TYPE
    SYNTAX DataEventConfig
    MAX-ACCESS not-accessible
    STATUS current
    DESCRIPTION
        "Entry for table of data events"
    INDEX { evdIndex }
    ::= { evdTable 1 }
    --1.3.6.1.4.1.3052.10.2.12.2.2.1

evdIndex OBJECT-TYPE
    SYNTAX Integer32 (1..1000)
    MAX-ACCESS read-only
    STATUS current
    DESCRIPTION
        "Index for table of data events"
    ::= { evdEntry 1 }
    --1.3.6.1.4.1.3052.10.2.12.2.2.1.1

evdEnable OBJECT-TYPE
    SYNTAX DisplayString
    MAX-ACCESS read-write
    STATUS current
    DESCRIPTION
        "ON/OFF enable this data event"
    ::= { evdEntry 2 }
    --1.3.6.1.4.1.3052.10.2.12.2.2.1.2

evdName OBJECT-TYPE
    SYNTAX DisplayString
    MAX-ACCESS read-write
    STATUS current
    DESCRIPTION
        "Name for this data event"
    ::= { evdEntry 3 }
    --1.3.6.1.4.1.3052.10.2.12.2.2.1.3

evdEquation OBJECT-TYPE
    SYNTAX DisplayString
    MAX-ACCESS read-write
    STATUS current
    DESCRIPTION
        "Equation for this data event"
    ::= { evdEntry 4 }
    --1.3.6.1.4.1.3052.10.2.12.2.2.1.4

evdThreshold OBJECT-TYPE
    SYNTAX Integer32
    MAX-ACCESS read-write
    STATUS current
    DESCRIPTION
        "Number of equation matches that must happen to trigger this
        data event"
    ::= { evdEntry 5 }
    --1.3.6.1.4.1.3052.10.2.12.2.2.1.5

evdAutoClear OBJECT-TYPE
    SYNTAX DisplayString
    MAX-ACCESS read-write
    STATUS current
    DESCRIPTION
        "ON/OFF this data alarm is automatically cleared (re-armed)
        upon reaching the threshold number of matches"
    ::= { evdEntry 6 }
    --1.3.6.1.4.1.3052.10.2.12.2.2.1.6

evdClearInterval OBJECT-TYPE
    SYNTAX DisplayString
    MAX-ACCESS read-write
    STATUS current
    DESCRIPTION
        "Interval at which this alarm is automatically cleared (no
        bearing with evdAutoClear)"
    ::= { evdEntry 7 }
    --1.3.6.1.4.1.3052.10.2.12.2.2.1.7

evdClearTime OBJECT-TYPE
    SYNTAX DisplayString
    MAX-ACCESS read-write
    STATUS current
    DESCRIPTION
        "Tie of day (HH:MM) at which this data alarm is cleared (no
        bearing with evdAutoClear)"
    ::= { evdEntry 8 }
    --1.3.6.1.4.1.3052.10.2.12.2.2.1.8

evdActions OBJECT-TYPE
    SYNTAX DisplayString
    MAX-ACCESS read-write
    STATUS current
    DESCRIPTION
        "Actions for this data event"
    ::= { evdEntry 9 }
    --1.3.6.1.4.1.3052.10.2.12.2.2.1.9

evdClass OBJECT-TYPE
    SYNTAX DisplayString
    MAX-ACCESS read-write
    STATUS current
    DESCRIPTION
        "Class for this data event"
    ::= { evdEntry 10 }
    --1.3.6.1.4.1.3052.10.2.12.2.2.1.10

evdTrapNum OBJECT-TYPE
    SYNTAX Integer32
    MAX-ACCESS read-write
    STATUS current
    DESCRIPTION
        "Trap number for this event"
    ::= { evdEntry 11 }
    --1.3.6.1.4.1.3052.10.2.12.2.2.1.11

evdMode OBJECT-TYPE
    SYNTAX DisplayString
    MAX-ACCESS read-write
    STATUS current
    DESCRIPTION
        "ALARM/FILTER: what is happens when this data event
        triggers: either generate actions (mode=ALARM) )or
        ACCEPT/REJECT (via evdFilterAction) the record
        (mode=FILTER)"
    ::= { evdEntry 12 }
    --1.3.6.1.4.1.3052.10.2.12.2.2.1.12

evdFieldTable OBJECT-TYPE
    SYNTAX SEQUENCE OF DataEventFieldConfig
    MAX-ACCESS not-accessible
    STATUS current
    DESCRIPTION
        "Table of data event fields"
    ::= { evData 3 }
    --1.3.6.1.4.1.3052.10.2.12.2.3

evdFieldEntry OBJECT-TYPE
    SYNTAX DataEventFieldConfig
    MAX-ACCESS not-accessible
    STATUS current
    DESCRIPTION
        "Entry for table of data event fields"
    INDEX { evdFieldIndex }
    ::= { evdFieldTable 1 }
    --1.3.6.1.4.1.3052.10.2.12.2.3.1

evdFieldIndex OBJECT-TYPE
    SYNTAX Integer32 (1..16)
    MAX-ACCESS read-only
    STATUS current
    DESCRIPTION
        "Index for table of data event fields"
    ::= { evdFieldEntry 1 }
    --1.3.6.1.4.1.3052.10.2.12.2.3.1.1

evdFieldStart OBJECT-TYPE
    SYNTAX Integer32
    MAX-ACCESS read-write
    STATUS current
    DESCRIPTION
        "Start position (1-based) for this data event field"
    ::= { evdFieldEntry 2 }
    --1.3.6.1.4.1.3052.10.2.12.2.3.1.2

evdFieldLength OBJECT-TYPE
    SYNTAX Integer32
    MAX-ACCESS read-write
    STATUS current
    DESCRIPTION
        "Number of characters this data event field occupies"
    ::= { evdFieldEntry 3 }
    --1.3.6.1.4.1.3052.10.2.12.2.3.1.3

evdFieldName OBJECT-TYPE
    SYNTAX DisplayString
    MAX-ACCESS read-write
    STATUS current
    DESCRIPTION
        "Start position (1-based) for this data event field"
    ::= { evdFieldEntry 4 }
    --1.3.6.1.4.1.3052.10.2.12.2.3.1.4

evdFieldLine OBJECT-TYPE
    SYNTAX Integer32
    MAX-ACCESS read-write
    STATUS current
    DESCRIPTION
        "Line number (1-based, for multiline records) for this data
        event field"
    ::= { evdFieldEntry 5 }
    --1.3.6.1.4.1.3052.10.2.12.2.3.1.5

evdFieldType OBJECT-TYPE
    SYNTAX DisplayString
    MAX-ACCESS read-write
    STATUS current
    DESCRIPTION
        "Alpha/Numeric type for this data event field"
    ::= { evdFieldEntry 6 }
    --1.3.6.1.4.1.3052.10.2.12.2.3.1.6

evdMacroTable OBJECT-TYPE
    SYNTAX SEQUENCE OF DataEventMacroConfig
    MAX-ACCESS not-accessible
    STATUS current
    DESCRIPTION
        "Table of data event macros"
    ::= { evData 4 }
    --1.3.6.1.4.1.3052.10.2.12.2.4

evdMacroEntry OBJECT-TYPE
    SYNTAX DataEventMacroConfig
    MAX-ACCESS not-accessible
    STATUS current
    DESCRIPTION
        "Entry for table of data event macros"
    INDEX { evdMacroIndex }
    ::= { evdMacroTable 1 }
    --1.3.6.1.4.1.3052.10.2.12.2.4.1

evdMacroIndex OBJECT-TYPE
    SYNTAX Integer32 (1..100)
    MAX-ACCESS read-only
    STATUS current
    DESCRIPTION
        "Index for table of data event macros"
    ::= { evdMacroEntry 1 }
    --1.3.6.1.4.1.3052.10.2.12.2.4.1.1

evdMacroName OBJECT-TYPE
    SYNTAX DisplayString
    MAX-ACCESS read-write
    STATUS current
    DESCRIPTION
        "Name of this macro for use in data event equations"
    ::= { evdMacroEntry 2 }
    --1.3.6.1.4.1.3052.10.2.12.2.4.1.2

evdMacroEquation OBJECT-TYPE
    SYNTAX DisplayString
    MAX-ACCESS read-write
    STATUS current
    DESCRIPTION
        "Equation for this data event macro"
    ::= { evdMacroEntry 3 }
    --1.3.6.1.4.1.3052.10.2.12.2.4.1.3

--***************************************************************************************
--No data event 1 Section 2.12.3
--***************************************************************************************

evNoData1Enable OBJECT-TYPE
    SYNTAX DisplayString
    MAX-ACCESS read-write
    STATUS current
    DESCRIPTION
        "ON/OFF enable this no data event"
    ::= { evNoData1 1 }
    --1.3.6.1.4.1.3052.10.2.12.3.1

evNoData1Actions OBJECT-TYPE
    SYNTAX DisplayString
    MAX-ACCESS read-write
    STATUS current
    DESCRIPTION
        "Actions for this no data event"
    ::= { evNoData1 2 }
    --1.3.6.1.4.1.3052.10.2.12.3.2

evNoData1Message OBJECT-TYPE
    SYNTAX DisplayString
    MAX-ACCESS read-write
    STATUS current
    DESCRIPTION
        "Message for this no data event"
    ::= { evNoData1 3 }
    --1.3.6.1.4.1.3052.10.2.12.3.3

evNoData1TrapNum OBJECT-TYPE
    SYNTAX Integer32 (505..1199)
    MAX-ACCESS read-write
    STATUS current
    DESCRIPTION
        "Trap number for this no data event"
    ::= { evNoData1 4 }
    --1.3.6.1.4.1.3052.10.2.12.3.4

evNoData1Class OBJECT-TYPE
    SYNTAX DisplayString
    MAX-ACCESS read-write
    STATUS current
    DESCRIPTION
        "Class for this no data event"
    ::= { evNoData1 5 }
    --1.3.6.1.4.1.3052.10.2.12.3.5

evNoData1Sched1Begin OBJECT-TYPE
    SYNTAX DisplayString
    MAX-ACCESS read-write
    STATUS current
    DESCRIPTION
        "Schedule 1 begin time (HH:MM) for this no data event"
    ::= { evNoData1 6 }
    --1.3.6.1.4.1.3052.10.2.12.3.6

evNoData1Sched1End OBJECT-TYPE
    SYNTAX DisplayString
    MAX-ACCESS read-write
    STATUS current
    DESCRIPTION
        "Schedule 1 end time (HH:MM) for this no data event"
    ::= { evNoData1 7 }
    --1.3.6.1.4.1.3052.10.2.12.3.7

evNoData1Sched1Duration OBJECT-TYPE
    SYNTAX Integer32 (0..65535)
    MAX-ACCESS read-write
    STATUS current
    DESCRIPTION
        "Duration (minutes) for schedule 1 of this no data event"
    ::= { evNoData1 8 }
    --1.3.6.1.4.1.3052.10.2.12.3.8

evNoData1Sched2Begin OBJECT-TYPE
    SYNTAX DisplayString
    MAX-ACCESS read-write
    STATUS current
    DESCRIPTION
        "Schedule 2 begin time (HH:MM) for this no data event"
    ::= { evNoData1 9 }
    --1.3.6.1.4.1.3052.10.2.12.3.9

evNoData1Sched2End OBJECT-TYPE
    SYNTAX DisplayString
    MAX-ACCESS read-write
    STATUS current
    DESCRIPTION
        "Schedule 2 end time (HH:MM) for this no data event"
    ::= { evNoData1 10 }
    --1.3.6.1.4.1.3052.10.2.12.3.10

evNoData1Sched2Duration OBJECT-TYPE
    SYNTAX Integer32 (0..65535)
    MAX-ACCESS read-write
    STATUS current
    DESCRIPTION
        "Duration (minutes) for schedule 2 of this no data event"
    ::= { evNoData1 11 }
    --1.3.6.1.4.1.3052.10.2.12.3.11

evNoData1PortEnableTable OBJECT-TYPE
    SYNTAX SEQUENCE OF NoDataEvent1PortEnableConfig
    MAX-ACCESS not-accessible
    STATUS current
    DESCRIPTION
        "Table of no data event 1 port enables"
    ::= { evNoData1 12 }
    --1.3.6.1.4.1.3052.10.2.12.3.12

evNoData1PortEnableEntry OBJECT-TYPE
    SYNTAX NoDataEvent1PortEnableConfig
    MAX-ACCESS not-accessible
    STATUS current
    DESCRIPTION
        "Entry for table of no data event 1 port enables"
    INDEX { evNoData1PortEnableIndex }
    ::= { evNoData1PortEnableTable 1 }
    --1.3.6.1.4.1.3052.10.2.12.3.12.1

evNoData1PortEnableIndex OBJECT-TYPE
    SYNTAX Integer32 (1..16)
    MAX-ACCESS read-only
    STATUS current
    DESCRIPTION
        "Index for table of no data event 1 port enables"
    ::= { evNoData1PortEnableEntry 1 }
    --1.3.6.1.4.1.3052.10.2.12.3.12.1.1

evNoData1PortEnable OBJECT-TYPE
    SYNTAX DisplayString
    MAX-ACCESS read-write
    STATUS current
    DESCRIPTION
        "ON/OFF: no data event 1 observes this port"
    ::= { evNoData1PortEnableEntry 2 }
    --1.3.6.1.4.1.3052.10.2.12.3.12.1.2

evNoData1Exclusions OBJECT-TYPE
    SYNTAX DisplayString
    MAX-ACCESS read-write
    STATUS current
    DESCRIPTION
        "Exclusions (space-separated MM/DD-formatted dates) for this
        no data event"
    ::= { evNoData1 13 }
    --1.3.6.1.4.1.3052.10.2.12.3.13

evNoData1Days OBJECT-TYPE
    SYNTAX DisplayString
    MAX-ACCESS read-write
    STATUS current
    DESCRIPTION
        "Days of the week on which this no event is active"
    ::= { evNoData1 14 }
    --1.3.6.1.4.1.3052.10.2.12.3.14

--***************************************************************************************
--No data event 2 Section 2.12.4
--***************************************************************************************

evNoData2Enable OBJECT-TYPE
    SYNTAX DisplayString
    MAX-ACCESS read-write
    STATUS current
    DESCRIPTION
        "ON/OFF enable this no data event"
    ::= { evNoData2 1 }
    --1.3.6.1.4.1.3052.10.2.12.4.1

evNoData2Actions OBJECT-TYPE
    SYNTAX DisplayString
    MAX-ACCESS read-write
    STATUS current
    DESCRIPTION
        "Actions for this no data event"
    ::= { evNoData2 2 }
    --1.3.6.1.4.1.3052.10.2.12.4.2

evNoData2Message OBJECT-TYPE
    SYNTAX DisplayString
    MAX-ACCESS read-write
    STATUS current
    DESCRIPTION
        "Message for this no data event"
    ::= { evNoData2 3 }
    --1.3.6.1.4.1.3052.10.2.12.4.3

evNoData2TrapNum OBJECT-TYPE
    SYNTAX Integer32 (505..1199)
    MAX-ACCESS read-write
    STATUS current
    DESCRIPTION
        "Trap number for this no data event"
    ::= { evNoData2 4 }
    --1.3.6.1.4.1.3052.10.2.12.4.4

evNoData2Class OBJECT-TYPE
    SYNTAX DisplayString
    MAX-ACCESS read-write
    STATUS current
    DESCRIPTION
        "Class for this no data event"
    ::= { evNoData2 5 }
    --1.3.6.1.4.1.3052.10.2.12.4.5

evNoData2Sched1Begin OBJECT-TYPE
    SYNTAX DisplayString
    MAX-ACCESS read-write
    STATUS current
    DESCRIPTION
        "Schedule 1 begin time (HH:MM) for this no data event"
    ::= { evNoData2 6 }
    --1.3.6.1.4.1.3052.10.2.12.4.6

evNoData2Sched1End OBJECT-TYPE
    SYNTAX DisplayString
    MAX-ACCESS read-write
    STATUS current
    DESCRIPTION
        "Schedule 1 end time (HH:MM) for this no data event"
    ::= { evNoData2 7 }
    --1.3.6.1.4.1.3052.10.2.12.4.7

evNoData2Sched1Duration OBJECT-TYPE
    SYNTAX Integer32 (0..65535)
    MAX-ACCESS read-write
    STATUS current
    DESCRIPTION
        "Duration (minutes) for schedule 1 of this no data event"
    ::= { evNoData2 8 }
    --1.3.6.1.4.1.3052.10.2.12.4.8

evNoData2Sched2Begin OBJECT-TYPE
    SYNTAX DisplayString
    MAX-ACCESS read-write
    STATUS current
    DESCRIPTION
        "Schedule 2 begin time (HH:MM) for this no data event"
    ::= { evNoData2 9 }
    --1.3.6.1.4.1.3052.10.2.12.4.9

evNoData2Sched2End OBJECT-TYPE
    SYNTAX DisplayString
    MAX-ACCESS read-write
    STATUS current
    DESCRIPTION
        "Schedule 2 end time (HH:MM) for this no data event"
    ::= { evNoData2 10 }
    --1.3.6.1.4.1.3052.10.2.12.4.10

evNoData2Sched2Duration OBJECT-TYPE
    SYNTAX Integer32 (0..65535)
    MAX-ACCESS read-write
    STATUS current
    DESCRIPTION
        "Duration (minutes) for schedule 2 of this no data event"
    ::= { evNoData2 11 }
    --1.3.6.1.4.1.3052.10.2.12.4.11

evNoData2PortEnableTable OBJECT-TYPE
    SYNTAX SEQUENCE OF NoDataEvent2PortEnableConfig
    MAX-ACCESS not-accessible
    STATUS current
    DESCRIPTION
        "Table of no data event 2 port enables"
    ::= { evNoData2 12 }
    --1.3.6.1.4.1.3052.10.2.12.4.12

evNoData2PortEnableEntry OBJECT-TYPE
    SYNTAX NoDataEvent2PortEnableConfig
    MAX-ACCESS not-accessible
    STATUS current
    DESCRIPTION
        "Entry for table of no data event 2 port enables"
    INDEX { evNoData2PortEnableIndex }
    ::= { evNoData2PortEnableTable 1 }
    --1.3.6.1.4.1.3052.10.2.12.4.12.1

evNoData2PortEnableIndex OBJECT-TYPE
    SYNTAX Integer32 (1..16)
    MAX-ACCESS read-only
    STATUS current
    DESCRIPTION
        "Index for table of no data event 2 port enables"
    ::= { evNoData2PortEnableEntry 1 }
    --1.3.6.1.4.1.3052.10.2.12.4.12.1.1

evNoData2PortEnable OBJECT-TYPE
    SYNTAX DisplayString
    MAX-ACCESS read-write
    STATUS current
    DESCRIPTION
        "ON/OFF: no data event 2 observes this port"
    ::= { evNoData2PortEnableEntry 2 }
    --1.3.6.1.4.1.3052.10.2.12.4.12.1.2

evNoData2Exclusions OBJECT-TYPE
    SYNTAX DisplayString
    MAX-ACCESS read-write
    STATUS current
    DESCRIPTION
        "Exclusions (space-separated MM/DD-formatted dates) for this
        no data event"
    ::= { evNoData2 13 }
    --1.3.6.1.4.1.3052.10.2.12.4.13

evNoData2Days OBJECT-TYPE
    SYNTAX DisplayString
    MAX-ACCESS read-write
    STATUS current
    DESCRIPTION
        "Days of the week on which this no event is active"
    ::= { evNoData2 14 }
    --1.3.6.1.4.1.3052.10.2.12.4.14

--***************************************************************************************
--Scheduled Event 1 Section 2.12.5
--***************************************************************************************

evSched1Enable OBJECT-TYPE
    SYNTAX DisplayString
    MAX-ACCESS read-write
    STATUS current
    DESCRIPTION
        "ON/OFF enable this scheduled event"
    ::= { evSched1 1 }
    --1.3.6.1.4.1.3052.10.2.12.5.1

evSched1Actions OBJECT-TYPE
    SYNTAX DisplayString
    MAX-ACCESS read-write
    STATUS current
    DESCRIPTION
        "Actions for this scheduled event"
    ::= { evSched1 2 }
    --1.3.6.1.4.1.3052.10.2.12.5.2

evSched1Message OBJECT-TYPE
    SYNTAX DisplayString
    MAX-ACCESS read-write
    STATUS current
    DESCRIPTION
        "Message for this scheduled event"
    ::= { evSched1 3 }
    --1.3.6.1.4.1.3052.10.2.12.5.3

evSched1TrapNum OBJECT-TYPE
    SYNTAX Integer32
    MAX-ACCESS read-write
    STATUS current
    DESCRIPTION
        "Trap number for this scheduled event"
    ::= { evSched1 4 }
    --1.3.6.1.4.1.3052.10.2.12.5.4

evSched1Class OBJECT-TYPE
    SYNTAX DisplayString
    MAX-ACCESS read-write
    STATUS current
    DESCRIPTION
        "Class for this scheduled event"
    ::= { evSched1 5 }
    --1.3.6.1.4.1.3052.10.2.12.5.5

evSched1Sunday OBJECT-TYPE
    SYNTAX DisplayString
    MAX-ACCESS read-write
    STATUS current
    DESCRIPTION
        "Time on Sunday (HH:MM) when this scheduled event triggers"
    ::= { evSched1 6 }
    --1.3.6.1.4.1.3052.10.2.12.5.6

evSched1Monday OBJECT-TYPE
    SYNTAX DisplayString
    MAX-ACCESS read-write
    STATUS current
    DESCRIPTION
        "Time on Monday (HH:MM) when this scheduled event triggers"
    ::= { evSched1 7 }
    --1.3.6.1.4.1.3052.10.2.12.5.7

evSched1Tuesday OBJECT-TYPE
    SYNTAX DisplayString
    MAX-ACCESS read-write
    STATUS current
    DESCRIPTION
        "Time on Tuesday (HH:MM) when this scheduled event triggers"
    ::= { evSched1 8 }
    --1.3.6.1.4.1.3052.10.2.12.5.8

evSched1Wednesday OBJECT-TYPE
    SYNTAX DisplayString
    MAX-ACCESS read-write
    STATUS current
    DESCRIPTION
        "Time on Wednesday (HH:MM) when this scheduled event triggers"
    ::= { evSched1 9 }
    --1.3.6.1.4.1.3052.10.2.12.5.9

evSched1Thursday OBJECT-TYPE
    SYNTAX DisplayString
    MAX-ACCESS read-write
    STATUS current
    DESCRIPTION
        "Time on Thursday (HH:MM) when this scheduled event triggers"
    ::= { evSched1 10 }
    --1.3.6.1.4.1.3052.10.2.12.5.10

evSched1Friday OBJECT-TYPE
    SYNTAX DisplayString
    MAX-ACCESS read-write
    STATUS current
    DESCRIPTION
        "Time on Friday (HH:MM) when this scheduled event triggers"
    ::= { evSched1 11 }
    --1.3.6.1.4.1.3052.10.2.12.5.11

evSched1Saturday OBJECT-TYPE
    SYNTAX DisplayString
    MAX-ACCESS read-write
    STATUS current
    DESCRIPTION
        "Time on Saturday (HH:MM) when this scheduled event triggers"
    ::= { evSched1 12 }
    --1.3.6.1.4.1.3052.10.2.12.5.12

evSched1Exclusions OBJECT-TYPE
    SYNTAX DisplayString
    MAX-ACCESS read-write
    STATUS current
    DESCRIPTION
        "Exclusions (space-separated MM/DD-formatted dates) for this
        scheduled event"
    ::= { evSched1 13 }
    --1.3.6.1.4.1.3052.10.2.12.5.13


--***************************************************************************************
--Scheduled Event 2 Section 2.12.6
--***************************************************************************************

evSched2Enable OBJECT-TYPE
    SYNTAX DisplayString
    MAX-ACCESS read-write
    STATUS current
    DESCRIPTION
        "ON/OFF enable this scheduled event"
    ::= { evSched2 1 }
    --1.3.6.1.4.1.3052.10.2.12.6.1

evSched2Actions OBJECT-TYPE
    SYNTAX DisplayString
    MAX-ACCESS read-write
    STATUS current
    DESCRIPTION
        "Actions for this scheduled event"
    ::= { evSched2 2 }
    --1.3.6.1.4.1.3052.10.2.12.6.2

evSched2Message OBJECT-TYPE
    SYNTAX DisplayString
    MAX-ACCESS read-write
    STATUS current
    DESCRIPTION
        "Message for this scheduled event"
    ::= { evSched2 3 }
    --1.3.6.1.4.1.3052.10.2.12.6.3

evSched2TrapNum OBJECT-TYPE
    SYNTAX Integer32
    MAX-ACCESS read-write
    STATUS current
    DESCRIPTION
        "Trap number for this scheduled event"
    ::= { evSched2 4 }
    --1.3.6.1.4.1.3052.10.2.12.6.4

evSched2Class OBJECT-TYPE
    SYNTAX DisplayString
    MAX-ACCESS read-write
    STATUS current
    DESCRIPTION
        "Class for this scheduled event"
    ::= { evSched2 5 }
    --1.3.6.1.4.1.3052.10.2.12.6.5

evSched2Sunday OBJECT-TYPE
    SYNTAX DisplayString
    MAX-ACCESS read-write
    STATUS current
    DESCRIPTION
        "Time on Sunday (HH:MM) when this scheduled event triggers"
    ::= { evSched2 6 }
    --1.3.6.1.4.1.3052.10.2.12.6.6

evSched2Monday OBJECT-TYPE
    SYNTAX DisplayString
    MAX-ACCESS read-write
    STATUS current
    DESCRIPTION
        "Time on Monday (HH:MM) when this scheduled event triggers"
    ::= { evSched2 7 }
    --1.3.6.1.4.1.3052.10.2.12.6.7

evSched2Tuesday OBJECT-TYPE
    SYNTAX DisplayString
    MAX-ACCESS read-write
    STATUS current
    DESCRIPTION
        "Time on Tuesday (HH:MM) when this scheduled event triggers"
    ::= { evSched2 8 }
    --1.3.6.1.4.1.3052.10.2.12.6.8

evSched2Wednesday OBJECT-TYPE
    SYNTAX DisplayString
    MAX-ACCESS read-write
    STATUS current
    DESCRIPTION
        "Time on Wednesday (HH:MM) when this scheduled event triggers"
    ::= { evSched2 9 }
    --1.3.6.1.4.1.3052.10.2.12.6.9

evSched2Thursday OBJECT-TYPE
    SYNTAX DisplayString
    MAX-ACCESS read-write
    STATUS current
    DESCRIPTION
        "Time on Thursday (HH:MM) when this scheduled event triggers"
    ::= { evSched2 10 }
    --1.3.6.1.4.1.3052.10.2.12.6.10

evSched2Friday OBJECT-TYPE
    SYNTAX DisplayString
    MAX-ACCESS read-write
    STATUS current
    DESCRIPTION
        "Time on Friday (HH:MM) when this scheduled event triggers"
    ::= { evSched2 11 }
    --1.3.6.1.4.1.3052.10.2.12.6.11

evSched2Saturday OBJECT-TYPE
    SYNTAX DisplayString
    MAX-ACCESS read-write
    STATUS current
    DESCRIPTION
        "Time on Saturday (HH:MM) when this scheduled event triggers"
    ::= { evSched2 12 }
    --1.3.6.1.4.1.3052.10.2.12.6.12

evSched2Exclusions OBJECT-TYPE
    SYNTAX DisplayString
    MAX-ACCESS read-write
    STATUS current
    DESCRIPTION
        "Exclusions (space-separated MM/DD-formatted dates) for this
        scheduled event"
    ::= { evSched2 13 }
    --1.3.6.1.4.1.3052.10.2.12.6.13

--***************************************************************************************
--Serial Handshaking Low Section 2.12.7
--***************************************************************************************

evShskLowTable OBJECT-TYPE
    SYNTAX SEQUENCE OF SerialHandshakingLowEventConfig
    MAX-ACCESS not-accessible
    STATUS current
    DESCRIPTION
        "Table of serial handshaking low events"
    ::= { event 7 }
    --1.3.6.1.4.1.3052.10.2.12.7

evShskLowEntry OBJECT-TYPE
    SYNTAX SerialHandshakingLowEventConfig
    MAX-ACCESS not-accessible
    STATUS current
    DESCRIPTION
        "Entry for table of serial handshaking low events"
    INDEX { evShskLowIndex }
    ::= { evShskLowTable 1 }
    --1.3.6.1.4.1.3052.10.2.12.7.1

evShskLowIndex OBJECT-TYPE
    SYNTAX Integer32 (1..16)
    MAX-ACCESS read-only
    STATUS current
    DESCRIPTION
        "Index for table of serial handshaking low events"
    ::= { evShskLowEntry 1 }
    --1.3.6.1.4.1.3052.10.2.12.7.1.1

evShskLowEnable OBJECT-TYPE
    SYNTAX DisplayString
    MAX-ACCESS read-write
    STATUS current
    DESCRIPTION
        "ON/OFF: enable the serial handshaking low event for this port"
    ::= { evShskLowEntry 2 }
    --1.3.6.1.4.1.3052.10.2.12.7.1.2

evShskLowActions OBJECT-TYPE
    SYNTAX DisplayString
    MAX-ACCESS read-write
    STATUS current
    DESCRIPTION
        "Actions for the serial handshaking low event for this port"
    ::= { evShskLowEntry 3 }
    --1.3.6.1.4.1.3052.10.2.12.7.1.3

evShskLowMessage OBJECT-TYPE
    SYNTAX DisplayString
    MAX-ACCESS read-write
    STATUS current
    DESCRIPTION
        "Message for the serial handshaking low event for this port"
    ::= { evShskLowEntry 4 }
    --1.3.6.1.4.1.3052.10.2.12.7.1.4

evShskLowClass OBJECT-TYPE
    SYNTAX DisplayString
    MAX-ACCESS read-write
    STATUS current
    DESCRIPTION
        "Class for the serial handshaking low event for this port"
    ::= { evShskLowEntry 5 }
    --1.3.6.1.4.1.3052.10.2.12.7.1.5

evShskLowTrapNum OBJECT-TYPE
    SYNTAX Integer32
    MAX-ACCESS read-write
    STATUS current
    DESCRIPTION
        "Trap number for the serial handshaking low event for this port"
    ::= { evShskLowEntry 6 }
    --1.3.6.1.4.1.3052.10.2.12.7.1.6


--***************************************************************************************
--Serial Handshaking High Section 2.12.8
--***************************************************************************************

evShskHighTable OBJECT-TYPE
    SYNTAX SEQUENCE OF SerialHandshakingHighEventConfig
    MAX-ACCESS not-accessible
    STATUS current
    DESCRIPTION
        "Table of serial handshaking high events"
    ::= { event 8 }
    --1.3.6.1.4.1.3052.10.2.12.8

evShskHighEntry OBJECT-TYPE
    SYNTAX SerialHandshakingHighEventConfig
    MAX-ACCESS not-accessible
    STATUS current
    DESCRIPTION
        "Entry for table of serial handshaking high events"
    INDEX { evShskHighIndex }
    ::= { evShskHighTable 1 }
    --1.3.6.1.4.1.3052.10.2.12.8.1

evShskHighIndex OBJECT-TYPE
    SYNTAX Integer32 (1..16)
    MAX-ACCESS read-only
    STATUS current
    DESCRIPTION
        "Index for table of serial handshaking high events"
    ::= { evShskHighEntry 1 }
    --1.3.6.1.4.1.3052.10.2.12.8.1.1

evShskHighEnable OBJECT-TYPE
    SYNTAX DisplayString
    MAX-ACCESS read-write
    STATUS current
    DESCRIPTION
        "ON/OFF: enable the serial handshaking high event for this
        port"
    ::= { evShskHighEntry 2 }
    --1.3.6.1.4.1.3052.10.2.12.8.1.2

evShskHighActions OBJECT-TYPE
    SYNTAX DisplayString
    MAX-ACCESS read-write
    STATUS current
    DESCRIPTION
        "Actions for the serial handshaking high event for this port"
    ::= { evShskHighEntry 3 }
    --1.3.6.1.4.1.3052.10.2.12.8.1.3

evShskHighMessage OBJECT-TYPE
    SYNTAX DisplayString
    MAX-ACCESS read-write
    STATUS current
    DESCRIPTION
        "Message for the serial handshaking high event for this port"
    ::= { evShskHighEntry 4 }
    --1.3.6.1.4.1.3052.10.2.12.8.1.4

evShskHighClass OBJECT-TYPE
    SYNTAX DisplayString
    MAX-ACCESS read-write
    STATUS current
    DESCRIPTION
        "Class for the serial handshaking high event for this port"
    ::= { evShskHighEntry 5 }
    --1.3.6.1.4.1.3052.10.2.12.8.1.5

evShskHighTrapNum OBJECT-TYPE
    SYNTAX Integer32
    MAX-ACCESS read-write
    STATUS current
    DESCRIPTION
        "Trap number for the serial handshaking high event for this
        port"
    ::= { evShskHighEntry 6 }
    --1.3.6.1.4.1.3052.10.2.12.8.1.6



--***************************************************************************************
--No Sensor Event Section 2.12.9
--***************************************************************************************

evNoSensorTimeout OBJECT-TYPE
    SYNTAX Integer32
    MAX-ACCESS read-write
    STATUS current
    DESCRIPTION
        "Timeout (seconds) after which an EventSensor becomes
        unresponsive that this event is triggered"
    ::= { evNoSensor 1 }
    --1.3.6.1.4.1.3052.10.2.12.9.1

evNoSensorActions OBJECT-TYPE
    SYNTAX DisplayString
    MAX-ACCESS read-write
    STATUS current
    DESCRIPTION
        "Actions for no sensor event"
    ::= { evNoSensor 2 }
    --1.3.6.1.4.1.3052.10.2.12.9.2

evNoSensorTrapNum OBJECT-TYPE
    SYNTAX Integer32
    MAX-ACCESS read-write
    STATUS current
    DESCRIPTION
        "Trap number for no sensor event"
    ::= { evNoSensor 3 }
    --1.3.6.1.4.1.3052.10.2.12.9.3

evNoSensorClass OBJECT-TYPE
    SYNTAX DisplayString
    MAX-ACCESS read-write
    STATUS current
    DESCRIPTION
        "Class for no sensor event"
    ::= { evNoSensor 4 }
    --1.3.6.1.4.1.3052.10.2.12.9.4



--***************************************************************************************
--Fuel Sensor Config Section       2.12.11
--***************************************************************************************


fuelSensorGeneralTable OBJECT-TYPE
    SYNTAX SEQUENCE OF FuelSensorConfigGeneral
    MAX-ACCESS not-accessible
    STATUS current
    DESCRIPTION
        "This table organizes general fuel sensor attributes."
    ::= { fuelSensor 1 }
    --1.3.6.1.4.1.3052.10.2.12.11.1

fsGenEntry OBJECT-TYPE
    SYNTAX FuelSensorConfigGeneral
    MAX-ACCESS not-accessible
    STATUS current
    DESCRIPTION
        "Entry for fuel sensor general config table."
    INDEX { fsGenIndex }
    ::= { fuelSensorGeneralTable 1 }
    --1.3.6.1.4.1.3052.10.2.12.11.1.1

fsGenIndex OBJECT-TYPE
    SYNTAX Integer32 (1..3)
    MAX-ACCESS read-only
    STATUS current
    DESCRIPTION
        "Which fuel sensor in the fuel sensor general config table."
    ::= { fsGenEntry 1 }
    --1.3.6.1.4.1.3052.10.2.12.11.1.1.1

fsGenName OBJECT-TYPE
    SYNTAX DisplayString
    MAX-ACCESS read-write
    STATUS current
    DESCRIPTION
        "Fuel sensor name."
    ::= { fsGenEntry 2 }
    --1.3.6.1.4.1.3052.10.2.12.11.1.1.2

fsGenSensorType OBJECT-TYPE
    SYNTAX DisplayString
    MAX-ACCESS read-write
    STATUS current
    DESCRIPTION
        "Type of fuel sensor in use; NONE disables the fuel sensor."
    ::= { fsGenEntry 3 }
    --1.3.6.1.4.1.3052.10.2.12.11.1.1.3

fsGenDistanceUnit OBJECT-TYPE
    SYNTAX DisplayString
    MAX-ACCESS read-write
    STATUS current
    DESCRIPTION
        "Distance units in use when setting and indicating tank dimensions."
    ::= { fsGenEntry 4 }
    --1.3.6.1.4.1.3052.10.2.12.11.1.1.4

fsGenRawValueTop OBJECT-TYPE
    SYNTAX DisplayString
    MAX-ACCESS read-write
    STATUS current
    DESCRIPTION
        "Analog input reading corresponding to the SENSOR FULL point."
    ::= { fsGenEntry 5 }
    --1.3.6.1.4.1.3052.10.2.12.11.1.1.5

fsGenTopOffset OBJECT-TYPE
    SYNTAX DisplayString
    MAX-ACCESS read-write
    STATUS current
    DESCRIPTION
        "Distance, in the specified distance unit, between the SENSOR FULL
        point and the TANK FULL point.  The value is positive if the
        SENSOR FULL point is above the TANK FULL point, and negative if it is
        below."
    ::= { fsGenEntry 6 }
    --1.3.6.1.4.1.3052.10.2.12.11.1.1.6

fsGenRawValueBottom OBJECT-TYPE
    SYNTAX DisplayString
    MAX-ACCESS read-write
    STATUS current
    DESCRIPTION
        "Analog input reading corresponding to the minimum fluid height
        measurable by the fuel sensor."
    ::= { fsGenEntry 7 }
    --1.3.6.1.4.1.3052.10.2.12.11.1.1.7

fsGenBottomOffset OBJECT-TYPE
    SYNTAX DisplayString
    MAX-ACCESS read-write
    STATUS current
    DESCRIPTION
        "Distance, in the specified distance unit, between the SENSOR EMPTY
        point and the TANK EMPTY point.  The value is positive if the
        SENSOR EMPTY point is above the TANK EMPTY point, and negative if it
        is below."
    ::= { fsGenEntry 8 }
    --1.3.6.1.4.1.3052.10.2.12.11.1.1.8

fsGenInputES OBJECT-TYPE
    SYNTAX Integer32 (1..200)
    MAX-ACCESS read-write
    STATUS current
    DESCRIPTION
        "Which eventsensor contains the analog input associated with this fuel
        sensor. Allowed values are 200 (for internal ES), or 1-16."
    ::= { fsGenEntry 9 }
    --1.3.6.1.4.1.3052.10.2.12.11.1.1.9

fsGenInputPoint OBJECT-TYPE
    SYNTAX Integer32 (1..16)
    MAX-ACCESS read-write
    STATUS current
    DESCRIPTION
        "Which analog input point, on the specified eventsensor, that is
        associated with the fuel sensor."
    ::= { fsGenEntry 10 }
    --1.3.6.1.4.1.3052.10.2.12.11.1.1.10

fsGenFilterAveraging OBJECT-TYPE
    SYNTAX Integer32
    MAX-ACCESS read-write
    STATUS current
    DESCRIPTION
        "Fuel sensor filter averaging factor."
    ::= { fsGenEntry 11 }
    --1.3.6.1.4.1.3052.10.2.12.11.1.1.11

fsGenSysrepEnable OBJECT-TYPE
    SYNTAX DisplayString
    MAX-ACCESS read-write
    STATUS current
    DESCRIPTION
        "Fuel sensor System Reporting enable."
    ::= { fsGenEntry 12 }
    --1.3.6.1.4.1.3052.10.2.12.11.1.1.12

fsGenSysrepThreshold OBJECT-TYPE
    SYNTAX DisplayString
    MAX-ACCESS read-write
    STATUS current
    DESCRIPTION
        "Fuel sensor System Reporting threshold (floating point value)."
    ::= { fsGenEntry 13 }
    --1.3.6.1.4.1.3052.10.2.12.11.1.1.13

fsGenSysrepLimit OBJECT-TYPE
    SYNTAX Integer32
    MAX-ACCESS read-write
    STATUS current
    DESCRIPTION
        "Fuel sensor System Reporting limit."
    ::= { fsGenEntry 14 }
    --1.3.6.1.4.1.3052.10.2.12.11.1.1.14

fsGenSysrepPackage OBJECT-TYPE
    SYNTAX Integer32 (0..10)
    MAX-ACCESS read-write
    STATUS current
    DESCRIPTION
        "Fuel sensor System Reporting package number."
    ::= { fsGenEntry 15 }
    --1.3.6.1.4.1.3052.10.2.12.11.1.1.15

fsGenGroup OBJECT-TYPE
    SYNTAX DisplayString
    MAX-ACCESS read-write
    STATUS current
    DESCRIPTION
        "Fuel sensor ASM profile type."
    ::= { fsGenEntry 16 }
    --1.3.6.1.4.1.3052.10.2.12.11.1.1.16

fsGenEnable OBJECT-TYPE
    SYNTAX DisplayString
    MAX-ACCESS read-write
    STATUS current
    DESCRIPTION
        "Fuel sensor enable."
    ::= { fsGenEntry 17 }
    --1.3.6.1.4.1.3052.10.2.12.11.1.1.17

fsGenFuelType OBJECT-TYPE
    SYNTAX DisplayString
    MAX-ACCESS read-write
    STATUS current
    DESCRIPTION
        "Type of fuel being measured: DIESEL, PROPANE,
        NATURAL GAS, HYDROGEN, GASOLINE, OTHER."
    ::= { fsGenEntry 18 }
    --1.3.6.1.4.1.3052.10.2.12.11.1.1.18

fuelSensorTankTable OBJECT-TYPE
    SYNTAX SEQUENCE OF FuelSensorConfigTank
    MAX-ACCESS not-accessible
    STATUS current
    DESCRIPTION
        "This table organizes tank-specific fuel sensor attributes."
    ::= { fuelSensor 2 }
    --1.3.6.1.4.1.3052.10.2.12.11.2

fsTankEntry OBJECT-TYPE
    SYNTAX FuelSensorConfigTank
    MAX-ACCESS not-accessible
    STATUS current
    DESCRIPTION
        "Entry for fuel sensor tank config table."
    INDEX { fsTankIndex }
    ::= { fuelSensorTankTable 1 }
    --1.3.6.1.4.1.3052.10.2.12.11.2.1

fsTankIndex OBJECT-TYPE
    SYNTAX Integer32 (1..3)
    MAX-ACCESS read-only
    STATUS current
    DESCRIPTION
        "Which fuel sensor in the fuel sensor tank config table."
    ::= { fsTankEntry 1 }
    --1.3.6.1.4.1.3052.10.2.12.11.2.1.1

fsTankHeight OBJECT-TYPE
    SYNTAX DisplayString
    MAX-ACCESS read-write
    STATUS current
    DESCRIPTION
        "Height of the tank, from the TANK EMPTY point to the TANK FULL point,
        in the specified distance unit (i.e. TANK HEIGHT).  This is a
        floating point value."
    ::= { fsTankEntry 2 }
    --1.3.6.1.4.1.3052.10.2.12.11.2.1.2

fsTankDimA OBJECT-TYPE
    SYNTAX DisplayString
    MAX-ACCESS read-write
    STATUS current
    DESCRIPTION
        "Tank dimension measurement A for certain tank profiles. For
        HORIZ OVAL, this is the length of the straight section.  This is a
        floating point value."
    ::= { fsTankEntry 3 }
    --1.3.6.1.4.1.3052.10.2.12.11.2.1.3

fsTankDimB OBJECT-TYPE
    SYNTAX DisplayString
    MAX-ACCESS read-write
    STATUS current
    DESCRIPTION
        "Tank dimension measurement B for certain tank profiles. For
        HORIZ OVAL, this is the radius of the curved section.  This is a
        floating point value."
    ::= { fsTankEntry 4 }
    --1.3.6.1.4.1.3052.10.2.12.11.2.1.4

fsTankVolume OBJECT-TYPE
    SYNTAX DisplayString
    MAX-ACCESS read-write
    STATUS current
    DESCRIPTION
        "How many volume units the tank contains, when full.  This is a
        floating point value."
    ::= { fsTankEntry 5 }
    --1.3.6.1.4.1.3052.10.2.12.11.2.1.5

fsTankVolumeUnit OBJECT-TYPE
    SYNTAX DisplayString
    MAX-ACCESS read-write
    STATUS current
    DESCRIPTION
        "Name of the unit representing fluid volume in the tank. This is only
        used for display purposes; it does not affect the volume calculation."
    ::= { fsTankEntry 6 }
    --1.3.6.1.4.1.3052.10.2.12.11.2.1.6

fsTankShape OBJECT-TYPE
    SYNTAX DisplayString
    MAX-ACCESS read-write
    STATUS current
    DESCRIPTION
        "The shape of the fuel tank.  A value of LINEAR produces a fluid
        volume reading that is directly proportional to fluid height.  The
        HORIZ CYL and HORIZ OVAL settings use a hard-coded formula to
        calculate the volume.  The CUSTOM setting uses a strapping table that
        must be configured as well (see fuelSensorCustomTankTable)."
    ::= { fsTankEntry 7 }
    --1.3.6.1.4.1.3052.10.2.12.11.2.1.7


fuelSensorCustomTankTable OBJECT-TYPE
    SYNTAX SEQUENCE OF FuelSensorConfigCustomTankStrapping
    MAX-ACCESS not-accessible
    STATUS current
    DESCRIPTION
        "This table organizes the custom tank strapping table.  Each fuel
        sensor has a table of height/volume pairs in service only when the tank
        shape (fsTankShape) in CUSTOM.  This allows the unit to calculate
        volumes for nonstandard tank shapes, to the degree that accurate
        height/volume measurements can be configured.  This SNMP table has two
        indexes: the first for which fuel sensor and the second for which
        height/volume pair."
    ::= { fuelSensor 3 }
    --1.3.6.1.4.1.3052.10.2.12.11.3

fsCustomTankEntry OBJECT-TYPE
    SYNTAX FuelSensorConfigCustomTankStrapping
    MAX-ACCESS not-accessible
    STATUS current
    DESCRIPTION
        "Entry for fuel sensor custom tank config table."
    INDEX { fsCustomTankIndexFS, fsCustomTankIndexDatum }
    ::= { fuelSensorCustomTankTable 1 }
    --1.3.6.1.4.1.3052.10.2.12.11.3.1

fsCustomTankIndexFS OBJECT-TYPE
    SYNTAX Integer32 (1..3)
    MAX-ACCESS read-only
    STATUS current
    DESCRIPTION
        "Which fuel sensor in the fuel sensor tank config table.  This is the
        first of two indexes for this SNMP table."
    ::= { fsCustomTankEntry 1 }
    --1.3.6.1.4.1.3052.10.2.12.11.3.1.1

fsCustomTankIndexDatum OBJECT-TYPE
    SYNTAX Integer32 (1..32)
    MAX-ACCESS read-only
    STATUS current
    DESCRIPTION
        "Which hight/volume pair: there are 32 pairs per fuel sensor.  This is
        the second of two indexes for this SNMP table."
    ::= { fsCustomTankEntry 2 }
    --1.3.6.1.4.1.3052.10.2.12.11.3.1.2

fsCustomTankHeight OBJECT-TYPE
    SYNTAX DisplayString
    MAX-ACCESS read-write
    STATUS current
    DESCRIPTION
        "Height of custom tank height/volume pair.  This is a floating point
        value."
    ::= { fsCustomTankEntry 3 }
    --1.3.6.1.4.1.3052.10.2.12.11.3.1.3

fsCustomTankVolume OBJECT-TYPE
    SYNTAX DisplayString
    MAX-ACCESS read-write
    STATUS current
    DESCRIPTION
        "Volume of custom tank height/volume pair.  This is a floating point
        value."
    ::= { fsCustomTankEntry 4 }
    --1.3.6.1.4.1.3052.10.2.12.11.3.1.4


fuelSensorVolumeTable OBJECT-TYPE
    SYNTAX SEQUENCE OF FuelSensorConfigVolume
    MAX-ACCESS not-accessible
    STATUS current
    DESCRIPTION
        "This table organizes volume-event-specific fuel sensor attributes."
    ::= { fuelSensor 4 }
    --1.3.6.1.4.1.3052.10.2.12.11.4

fsVolumeEntry OBJECT-TYPE
    SYNTAX FuelSensorConfigVolume
    MAX-ACCESS not-accessible
    STATUS current
    DESCRIPTION
        "Entry for fuel sensor volume event config table."
    INDEX { fsVolumeIndex }
    ::= { fuelSensorVolumeTable 1 }
    --1.3.6.1.4.1.3052.10.2.12.11.4.1

fsVolumeIndex OBJECT-TYPE
    SYNTAX Integer32 (1..3)
    MAX-ACCESS read-only
    STATUS current
    DESCRIPTION
        "Which fuel sensor in the fuel sensor volume event config table."
    ::= { fsVolumeEntry 1 }
    --1.3.6.1.4.1.3052.10.2.12.11.4.1.1

fsVolumeEnable OBJECT-TYPE
    SYNTAX DisplayString
    MAX-ACCESS read-write
    STATUS current
    DESCRIPTION
        "Enable fuel sensor volume events."
    ::= { fsVolumeEntry 2 }
    --1.3.6.1.4.1.3052.10.2.12.11.4.1.2

fsVolumeDeadband OBJECT-TYPE
    SYNTAX DisplayString
    MAX-ACCESS read-write
    STATUS current
    DESCRIPTION
        "Fuel sensor deadband (hysteresis).  This is a floating point value."
    ::= { fsVolumeEntry 3 }
    --1.3.6.1.4.1.3052.10.2.12.11.4.1.3

fsVolumeVHighValue OBJECT-TYPE
    SYNTAX DisplayString
    MAX-ACCESS read-write
    STATUS current
    DESCRIPTION
        "Fuel sensor volume very high event threshold value.  This is a
        floating point value."
    ::= { fsVolumeEntry 4 }
    --1.3.6.1.4.1.3052.10.2.12.11.4.1.4

fsVolumeVHighActions OBJECT-TYPE
    SYNTAX DisplayString
    MAX-ACCESS read-write
    STATUS current
    DESCRIPTION
        "Fuel sensor volume very high event threshold actions."
    ::= { fsVolumeEntry 5 }
    --1.3.6.1.4.1.3052.10.2.12.11.4.1.5

fsVolumeVHighTrapNum OBJECT-TYPE
    SYNTAX Integer32 (519..1199)
    MAX-ACCESS read-write
    STATUS current
    DESCRIPTION
        "Fuel sensor volume very high event threshold trap number."
    ::= { fsVolumeEntry 6 }
    --1.3.6.1.4.1.3052.10.2.12.11.4.1.6

fsVolumeVHighClass OBJECT-TYPE
    SYNTAX DisplayString
    MAX-ACCESS read-write
    STATUS current
    DESCRIPTION
        "Fuel sensor volume very high event threshold class (severity)."
    ::= { fsVolumeEntry 7 }
    --1.3.6.1.4.1.3052.10.2.12.11.4.1.7

fsVolumeHighValue OBJECT-TYPE
    SYNTAX DisplayString
    MAX-ACCESS read-write
    STATUS current
    DESCRIPTION
        "Fuel sensor volume high event threshold value.  This is a floating
        point value."
    ::= { fsVolumeEntry 8 }
    --1.3.6.1.4.1.3052.10.2.12.11.4.1.8

fsVolumeHighActions OBJECT-TYPE
    SYNTAX DisplayString
    MAX-ACCESS read-write
    STATUS current
    DESCRIPTION
        "Fuel sensor volume high event threshold actions."
    ::= { fsVolumeEntry 9 }
    --1.3.6.1.4.1.3052.10.2.12.11.4.1.9

fsVolumeHighTrapNum OBJECT-TYPE
    SYNTAX Integer32 (519..1199)
    MAX-ACCESS read-write
    STATUS current
    DESCRIPTION
        "Fuel sensor volume high event threshold trap number."
    ::= { fsVolumeEntry 10 }
    --1.3.6.1.4.1.3052.10.2.12.11.4.1.10

fsVolumeHighClass OBJECT-TYPE
    SYNTAX DisplayString
    MAX-ACCESS read-write
    STATUS current
    DESCRIPTION
        "Fuel sensor volume high event threshold class (severity)."
    ::= { fsVolumeEntry 11 }
    --1.3.6.1.4.1.3052.10.2.12.11.4.1.11

fsVolumeNormalActions OBJECT-TYPE
    SYNTAX DisplayString
    MAX-ACCESS read-write
    STATUS current
    DESCRIPTION
        "Fuel sensor volume return to normal actions."
    ::= { fsVolumeEntry 12 }
    --1.3.6.1.4.1.3052.10.2.12.11.4.1.12

fsVolumeNormalTrapNum OBJECT-TYPE
    SYNTAX Integer32 (519..1199)
    MAX-ACCESS read-write
    STATUS current
    DESCRIPTION
        "Fuel sensor volume return to normal trap number."
    ::= { fsVolumeEntry 13 }
    --1.3.6.1.4.1.3052.10.2.12.11.4.1.13

fsVolumeNormalClass OBJECT-TYPE
    SYNTAX DisplayString
    MAX-ACCESS read-write
    STATUS current
    DESCRIPTION
        "Fuel sensor volume return to normal class (severity)."
    ::= { fsVolumeEntry 14 }
    --1.3.6.1.4.1.3052.10.2.12.11.4.1.14

fsVolumeLowValue OBJECT-TYPE
    SYNTAX DisplayString
    MAX-ACCESS read-write
    STATUS current
    DESCRIPTION
        "Fuel sensor volume low event threshold value.  This is a floating
        point value."
    ::= { fsVolumeEntry 15 }
    --1.3.6.1.4.1.3052.10.2.12.11.4.1.15

fsVolumeLowActions OBJECT-TYPE
    SYNTAX DisplayString
    MAX-ACCESS read-write
    STATUS current
    DESCRIPTION
        "Fuel sensor volume low event threshold actions."
    ::= { fsVolumeEntry 16 }
    --1.3.6.1.4.1.3052.10.2.12.11.4.1.16

fsVolumeLowTrapNum OBJECT-TYPE
    SYNTAX Integer32 (519..1199)
    MAX-ACCESS read-write
    STATUS current
    DESCRIPTION
        "Fuel sensor volume low event threshold trap number."
    ::= { fsVolumeEntry 17 }
    --1.3.6.1.4.1.3052.10.2.12.11.4.1.17

fsVolumeLowClass OBJECT-TYPE
    SYNTAX DisplayString
    MAX-ACCESS read-write
    STATUS current
    DESCRIPTION
        "Fuel sensor volume low event threshold class (severity)."
    ::= { fsVolumeEntry 18 }
    --1.3.6.1.4.1.3052.10.2.12.11.4.1.18

fsVolumeVLowValue OBJECT-TYPE
    SYNTAX DisplayString
    MAX-ACCESS read-write
    STATUS current
    DESCRIPTION
        "Fuel sensor volume very low event threshold value.  This is a
        floating point value."
    ::= { fsVolumeEntry 19 }
    --1.3.6.1.4.1.3052.10.2.12.11.4.1.19

fsVolumeVLowActions OBJECT-TYPE
    SYNTAX DisplayString
    MAX-ACCESS read-write
    STATUS current
    DESCRIPTION
        "Fuel sensor volume very low event threshold actions."
    ::= { fsVolumeEntry 20 }
    --1.3.6.1.4.1.3052.10.2.12.11.4.1.20

fsVolumeVLowTrapNum OBJECT-TYPE
    SYNTAX Integer32 (519..1199)
    MAX-ACCESS read-write
    STATUS current
    DESCRIPTION
        "Fuel sensor volume very low event threshold trap number."
    ::= { fsVolumeEntry 21 }
    --1.3.6.1.4.1.3052.10.2.12.11.4.1.21

fsVolumeVLowClass OBJECT-TYPE
    SYNTAX DisplayString
    MAX-ACCESS read-write
    STATUS current
    DESCRIPTION
        "Fuel sensor volume very low event threshold class (severity)."
    ::= { fsVolumeEntry 22 }
    --1.3.6.1.4.1.3052.10.2.12.11.4.1.22



fuelSensorDisconnectTable OBJECT-TYPE
    SYNTAX SEQUENCE OF FuelSensorConfigDisconnect
    MAX-ACCESS not-accessible
    STATUS current
    DESCRIPTION
        "This table organizes disconnect-event-specific fuel sensor attributes."
    ::= { fuelSensor 5 }
    --1.3.6.1.4.1.3052.10.2.12.11.5

fsDiscEntry OBJECT-TYPE
    SYNTAX FuelSensorConfigDisconnect
    MAX-ACCESS not-accessible
    STATUS current
    DESCRIPTION
        "Entry for fuel sensor disconnect event config table."
    INDEX { fsDiscIndex }
    ::= { fuelSensorDisconnectTable 1 }
    --1.3.6.1.4.1.3052.10.2.12.11.5.1

fsDiscIndex OBJECT-TYPE
    SYNTAX Integer32 (1..3)
    MAX-ACCESS read-only
    STATUS current
    DESCRIPTION
        "Which fuel sensor in the fuel sensor disconnect event config table."
    ::= { fsDiscEntry 1 }
    --1.3.6.1.4.1.3052.10.2.12.11.5.1.1

fsDiscEnable OBJECT-TYPE
    SYNTAX DisplayString
    MAX-ACCESS read-write
    STATUS current
    DESCRIPTION
        "Fuel sensor disconnect event enable."
    ::= { fsDiscEntry 2 }
    --1.3.6.1.4.1.3052.10.2.12.11.5.1.2

fsDiscHighValue OBJECT-TYPE
    SYNTAX DisplayString
    MAX-ACCESS read-write
    STATUS current
    DESCRIPTION
        "High end of input value range when fuel sensor is disconnected.  This
        is in the units of the analog input value."
    ::= { fsDiscEntry 3 }
    --1.3.6.1.4.1.3052.10.2.12.11.5.1.3

fsDiscLowValue OBJECT-TYPE
    SYNTAX DisplayString
    MAX-ACCESS read-write
    STATUS current
    DESCRIPTION
        "Low end of input value range when fuel sensor is disconnected.  This
        is in the units of the analog input value."
    ::= { fsDiscEntry 4 }
    --1.3.6.1.4.1.3052.10.2.12.11.5.1.4

fsDiscActions OBJECT-TYPE
    SYNTAX DisplayString
    MAX-ACCESS read-write
    STATUS current
    DESCRIPTION
        "Fuel sensor disconnect event actions."
    ::= { fsDiscEntry 5 }
    --1.3.6.1.4.1.3052.10.2.12.11.5.1.5

fsDiscTrapNum OBJECT-TYPE
    SYNTAX Integer32 (515..1199)
    MAX-ACCESS read-write
    STATUS current
    DESCRIPTION
        "Fuel sensor disconnect event trap number."
    ::= { fsDiscEntry 6 }
    --1.3.6.1.4.1.3052.10.2.12.11.5.1.6

fsDiscClass OBJECT-TYPE
    SYNTAX DisplayString
    MAX-ACCESS read-write
    STATUS current
    DESCRIPTION
        "Fuel sensor disconnect event class (severity)."
    ::= { fsDiscEntry 7 }
    --1.3.6.1.4.1.3052.10.2.12.11.5.1.7

fsDiscNormalActions OBJECT-TYPE
    SYNTAX DisplayString
    MAX-ACCESS read-write
    STATUS current
    DESCRIPTION
        "Fuel sensor disconnect return to normal actions."
    ::= { fsDiscEntry 8 }
    --1.3.6.1.4.1.3052.10.2.12.11.5.1.8

fsDiscNormalTrapNum OBJECT-TYPE
    SYNTAX Integer32 (515..1199)
    MAX-ACCESS read-write
    STATUS current
    DESCRIPTION
        "Fuel sensor disconnect return to normal trap number."
    ::= { fsDiscEntry 9 }
    --1.3.6.1.4.1.3052.10.2.12.11.5.1.9

fsDiscNormalClass OBJECT-TYPE
    SYNTAX DisplayString
    MAX-ACCESS read-write
    STATUS current
    DESCRIPTION
        "Fuel sensor disconnect return to normal class (severity)."
    ::= { fsDiscEntry 10 }
    --1.3.6.1.4.1.3052.10.2.12.11.5.1.10


fuelSensorSuddenChangeTable OBJECT-TYPE
    SYNTAX SEQUENCE OF FuelSensorConfigSuddenChange
    MAX-ACCESS not-accessible
    STATUS current
    DESCRIPTION
        "This table organizes sudden-change-event-specific fuel sensor
        attributes."
    ::= { fuelSensor 6 }
    --1.3.6.1.4.1.3052.10.2.12.11.6

fsSuddenChangeEntry OBJECT-TYPE
    SYNTAX FuelSensorConfigSuddenChange
    MAX-ACCESS not-accessible
    STATUS current
    DESCRIPTION
        "Entry for fuel sensor sudden change event config table."
    INDEX { fsSuddenChangeIndex }
    ::= { fuelSensorSuddenChangeTable 1 }
    --1.3.6.1.4.1.3052.10.2.12.11.6.1

fsSuddenChangeIndex OBJECT-TYPE
    SYNTAX Integer32 (1..3)
    MAX-ACCESS read-only
    STATUS current
    DESCRIPTION
        "Which fuel sensor in the fuel sensor sudden change event
        config table."
    ::= { fsSuddenChangeEntry 1 }
    --1.3.6.1.4.1.3052.10.2.12.11.6.1.1

fsSuddenChangeEnable OBJECT-TYPE
    SYNTAX DisplayString
    MAX-ACCESS read-write
    STATUS current
    DESCRIPTION
        "Fuel volume sudden change event enable."
    ::= { fsSuddenChangeEntry 2 }
    --1.3.6.1.4.1.3052.10.2.12.11.6.1.2

fsSuddenChangeTime OBJECT-TYPE
    SYNTAX Integer32 (5..360)
    MAX-ACCESS read-write
    STATUS current
    DESCRIPTION
        "Fuel volume sudden change event time (minutes): what duration defines
        'sudden'."
    ::= { fsSuddenChangeEntry 3 }
    --1.3.6.1.4.1.3052.10.2.12.11.6.1.3

fsSuddenChangeAmplitude OBJECT-TYPE
    SYNTAX DisplayString
    MAX-ACCESS read-write
    STATUS current
    DESCRIPTION
        "Fuel volume sudden change event amplitude: what amount (in fuel
        volume units) over the duration (fsSuddenChangeTime) defines enough
        change."
    ::= { fsSuddenChangeEntry 4 }
    --1.3.6.1.4.1.3052.10.2.12.11.6.1.4

fsSuddenChangeActions OBJECT-TYPE
    SYNTAX DisplayString
    MAX-ACCESS read-write
    STATUS current
    DESCRIPTION
        "Fuel volume sudden change event actions."
    ::= { fsSuddenChangeEntry 5 }
    --1.3.6.1.4.1.3052.10.2.12.11.6.1.5

fsSuddenChangeTrapNum OBJECT-TYPE
    SYNTAX Integer32 (527..1199)
    MAX-ACCESS read-write
    STATUS current
    DESCRIPTION
        "Fuel volume sudden change event trap number."
    ::= { fsSuddenChangeEntry 6 }
    --1.3.6.1.4.1.3052.10.2.12.11.6.1.6

fsSuddenChangeClass OBJECT-TYPE
    SYNTAX DisplayString
    MAX-ACCESS read-write
    STATUS current
    DESCRIPTION
        "Fuel volume sudden change event class (severity)."
    ::= { fsSuddenChangeEntry 7 }
    --1.3.6.1.4.1.3052.10.2.12.11.6.1.7


fuelSensorSlowChangeTable OBJECT-TYPE
    SYNTAX SEQUENCE OF FuelSensorConfigSlowChange
    MAX-ACCESS not-accessible
    STATUS current
    DESCRIPTION
        "This table organizes slow-change-event-specific fuel sensor attributes."
    ::= { fuelSensor 7 }
    --1.3.6.1.4.1.3052.10.2.12.11.7

fsSlowChangeEntry OBJECT-TYPE
    SYNTAX FuelSensorConfigSlowChange
    MAX-ACCESS not-accessible
    STATUS current
    DESCRIPTION
        "Entry for fuel sensor slow change event config table."
    INDEX { fsSlowChangeIndex }
    ::= { fuelSensorSlowChangeTable 1 }
    --1.3.6.1.4.1.3052.10.2.12.11.7.1

fsSlowChangeIndex OBJECT-TYPE
    SYNTAX Integer32 (1..3)
    MAX-ACCESS read-only
    STATUS current
    DESCRIPTION
        "Which fuel sensor in the fuel sensor slow change event
        config table."
    ::= { fsSlowChangeEntry 1 }
    --1.3.6.1.4.1.3052.10.2.12.11.7.1.1

fsSlowChangeEnable OBJECT-TYPE
    SYNTAX DisplayString
    MAX-ACCESS read-write
    STATUS current
    DESCRIPTION
        "Fuel volume slow change event enable."
    ::= { fsSlowChangeEntry 2 }
    --1.3.6.1.4.1.3052.10.2.12.11.7.1.2

fsSlowChangeTime OBJECT-TYPE
    SYNTAX Integer32 (1..168)
    MAX-ACCESS read-write
    STATUS current
    DESCRIPTION
        "Fuel volume slow change event time (minutes): what duration defines
        'slow'."
    ::= { fsSlowChangeEntry 3 }
    --1.3.6.1.4.1.3052.10.2.12.11.7.1.3

fsSlowChangeAmplitude OBJECT-TYPE
    SYNTAX DisplayString
    MAX-ACCESS read-write
    STATUS current
    DESCRIPTION
        "Fuel volume slow change event amplitude: what amount (in fuel volume
        units) over the duration (fsSlowChangeTime) defines enough change."
    ::= { fsSlowChangeEntry 4 }
    --1.3.6.1.4.1.3052.10.2.12.11.7.1.4

fsSlowChangeActions OBJECT-TYPE
    SYNTAX DisplayString
    MAX-ACCESS read-write
    STATUS current
    DESCRIPTION
        "Fuel volume slow change event actions."
    ::= { fsSlowChangeEntry 5 }
    --1.3.6.1.4.1.3052.10.2.12.11.7.1.5

fsSlowChangeTrapNum OBJECT-TYPE
    SYNTAX Integer32 (528..1199)
    MAX-ACCESS read-write
    STATUS current
    DESCRIPTION
        "Fuel volume slow change event trap number."
    ::= { fsSlowChangeEntry 6 }
    --1.3.6.1.4.1.3052.10.2.12.11.7.1.6

fsSlowChangeClass OBJECT-TYPE
    SYNTAX DisplayString
    MAX-ACCESS read-write
    STATUS current
    DESCRIPTION
        "Fuel volume slow change event class (severity)."
    ::= { fsSlowChangeEntry 7 }
    --1.3.6.1.4.1.3052.10.2.12.11.7.1.7


--***************************************************************************************
--AC Power Monitor Config Section       2.12.12
--***************************************************************************************

acpmGeneralTable OBJECT-TYPE
    SYNTAX SEQUENCE OF ACPMConfigGeneral
    MAX-ACCESS not-accessible
    STATUS current
    DESCRIPTION
        "This table organizes general AC power monitor attributes."
    ::= { acPowerMonitor 1 }
    --1.3.6.1.4.1.3052.10.2.12.12.1

acpmGenEntry OBJECT-TYPE
    SYNTAX ACPMConfigGeneral
    MAX-ACCESS not-accessible
    STATUS current
    DESCRIPTION
        "Entry for AC power monitor general config table."
    INDEX { acpmGenIndex }
    ::= { acpmGeneralTable 1 }
    --1.3.6.1.4.1.3052.10.2.12.12.1.1

acpmGenIndex OBJECT-TYPE
    SYNTAX Integer32 (1..6)
    MAX-ACCESS read-only
    STATUS current
    DESCRIPTION
        "Which AC power monitor in the AC power monitor general config table."
    ::= { acpmGenEntry 1 }
    --1.3.6.1.4.1.3052.10.2.12.12.1.1.1

acpmGenDevice OBJECT-TYPE
    SYNTAX DisplayString
    MAX-ACCESS read-write
    STATUS current
    DESCRIPTION
        "Model of the AC power monitor device. The unit needs this setting to
        know which registers to poll for the various data items, among other
        things."
    ::= { acpmGenEntry 2 }
    --1.3.6.1.4.1.3052.10.2.12.12.1.1.2

acpmGenName OBJECT-TYPE
    SYNTAX DisplayString
    MAX-ACCESS read-write
    STATUS current
    DESCRIPTION
        "Name for the AC power monitor device."
    ::= { acpmGenEntry 3 }
    --1.3.6.1.4.1.3052.10.2.12.12.1.1.3

acpmGenAddress OBJECT-TYPE
    SYNTAX Integer32 (1..247)
    MAX-ACCESS read-write
    STATUS current
    DESCRIPTION
        "Modbus address of the AC power monitor device."
    ::= { acpmGenEntry 4 }
    --1.3.6.1.4.1.3052.10.2.12.12.1.1.4

acpmGenPtRatio OBJECT-TYPE
    SYNTAX Integer32 (1..10000)
    MAX-ACCESS read-write
    STATUS current
    DESCRIPTION
        "Ratio of secondary turns to primary turns on potential transformers
        (PT)."
    ::= { acpmGenEntry 5 }
    --1.3.6.1.4.1.3052.10.2.12.12.1.1.5

acpmGenCtRatio OBJECT-TYPE
    SYNTAX Integer32 (1..10000)
    MAX-ACCESS read-write
    STATUS current
    DESCRIPTION
        "Ratio of secondary turns to primary turns on current transformers
        (CT)."
    ::= { acpmGenEntry 6 }
    --1.3.6.1.4.1.3052.10.2.12.12.1.1.6

acpmGenPowerType OBJECT-TYPE
    SYNTAX DisplayString
    MAX-ACCESS read-write
    STATUS current
    DESCRIPTION
        "Type of power being monitored."
    ::= { acpmGenEntry 7 }
    --1.3.6.1.4.1.3052.10.2.12.12.1.1.7

acpmGenSysrepPackage OBJECT-TYPE
    SYNTAX Integer32 (0..10)
    MAX-ACCESS read-write
    STATUS current
    DESCRIPTION
        "System reporting package number."
    ::= { acpmGenEntry 8 }
    --1.3.6.1.4.1.3052.10.2.12.12.1.1.8

acpmGenGroup OBJECT-TYPE
    SYNTAX DisplayString
    MAX-ACCESS read-write
    STATUS current
    DESCRIPTION
        "ASM profile group."
    ::= { acpmGenEntry 9 }
    --1.3.6.1.4.1.3052.10.2.12.12.1.1.9

acpmGenEnable OBJECT-TYPE
    SYNTAX DisplayString
    MAX-ACCESS read-write
    STATUS current
    DESCRIPTION
        "AC power monitor enable."
    ::= { acpmGenEntry 10 }
    --1.3.6.1.4.1.3052.10.2.12.12.1.1.10


acpmAvgVoltageTable OBJECT-TYPE
    SYNTAX SEQUENCE OF ACPMConfigAvgVoltage
    MAX-ACCESS not-accessible
    STATUS current
    DESCRIPTION
        "This table organizes AC power monitor average voltage attributes."
    ::= { acPowerMonitor 2 }
    --1.3.6.1.4.1.3052.10.2.12.12.2

acpmAvgVoltageEntry OBJECT-TYPE
    SYNTAX ACPMConfigAvgVoltage
    MAX-ACCESS not-accessible
    STATUS current
    DESCRIPTION
        "Entry for AC power monitor average voltage config table."
    INDEX { acpmAvgVoltageIndex }
    ::= { acpmAvgVoltageTable 1 }
    --1.3.6.1.4.1.3052.10.2.12.12.2.1

acpmAvgVoltageIndex OBJECT-TYPE
    SYNTAX Integer32 (1..6)
    MAX-ACCESS read-only
    STATUS current
    DESCRIPTION
        "Which AC power monitor in the AC power monitor average voltage config
        table."
    ::= { acpmAvgVoltageEntry 1 }
    --1.3.6.1.4.1.3052.10.2.12.12.2.1.1

acpmAvgVoltageEnable OBJECT-TYPE
    SYNTAX DisplayString
    MAX-ACCESS read-write
    STATUS current
    DESCRIPTION
        "Enable AC power monitor average voltage events."
    ::= { acpmAvgVoltageEntry 2 }
    --1.3.6.1.4.1.3052.10.2.12.12.2.1.2

acpmAvgVoltageDeadband OBJECT-TYPE
    SYNTAX DisplayString
    MAX-ACCESS read-write
    STATUS current
    DESCRIPTION
        "Deadband (hysteresis) for average voltage event.  This is a floating
        point value."
    ::= { acpmAvgVoltageEntry 3 }
    --1.3.6.1.4.1.3052.10.2.12.12.2.1.3

acpmAvgVoltageVHighValue OBJECT-TYPE
    SYNTAX DisplayString
    MAX-ACCESS read-write
    STATUS current
    DESCRIPTION
        "Very high event threshold.  This is a floating point value."
    ::= { acpmAvgVoltageEntry 4 }
    --1.3.6.1.4.1.3052.10.2.12.12.2.1.4

acpmAvgVoltageVHighActions OBJECT-TYPE
    SYNTAX DisplayString
    MAX-ACCESS read-write
    STATUS current
    DESCRIPTION
        "Very high event actions."
    ::= { acpmAvgVoltageEntry 5 }
    --1.3.6.1.4.1.3052.10.2.12.12.2.1.5

acpmAvgVoltageVHighTrapNum OBJECT-TYPE
    SYNTAX Integer32 (520..1199)
    MAX-ACCESS read-write
    STATUS current
    DESCRIPTION
        "Very high event trap number."
    ::= { acpmAvgVoltageEntry 6 }
    --1.3.6.1.4.1.3052.10.2.12.12.2.1.6

acpmAvgVoltageVHighClass OBJECT-TYPE
    SYNTAX DisplayString
    MAX-ACCESS read-write
    STATUS current
    DESCRIPTION
        "Very high event class."
    ::= { acpmAvgVoltageEntry 7 }
    --1.3.6.1.4.1.3052.10.2.12.12.2.1.7

acpmAvgVoltageHighValue OBJECT-TYPE
    SYNTAX DisplayString
    MAX-ACCESS read-write
    STATUS current
    DESCRIPTION
        "High event threshold.  This is a floating point value."
    ::= { acpmAvgVoltageEntry 8 }
    --1.3.6.1.4.1.3052.10.2.12.12.2.1.8

acpmAvgVoltageHighActions OBJECT-TYPE
    SYNTAX DisplayString
    MAX-ACCESS read-write
    STATUS current
    DESCRIPTION
        "High event actions."
    ::= { acpmAvgVoltageEntry 9 }
    --1.3.6.1.4.1.3052.10.2.12.12.2.1.9

acpmAvgVoltageHighTrapNum OBJECT-TYPE
    SYNTAX Integer32 (520..1199)
    MAX-ACCESS read-write
    STATUS current
    DESCRIPTION
        "High event trap number."
    ::= { acpmAvgVoltageEntry 10 }
    --1.3.6.1.4.1.3052.10.2.12.12.2.1.10

acpmAvgVoltageHighClass OBJECT-TYPE
    SYNTAX DisplayString
    MAX-ACCESS read-write
    STATUS current
    DESCRIPTION
        "High event class."
    ::= { acpmAvgVoltageEntry 11 }
    --1.3.6.1.4.1.3052.10.2.12.12.2.1.11

acpmAvgVoltageNormalActions OBJECT-TYPE
    SYNTAX DisplayString
    MAX-ACCESS read-write
    STATUS current
    DESCRIPTION
        "Return to normal actions."
    ::= { acpmAvgVoltageEntry 12 }
    --1.3.6.1.4.1.3052.10.2.12.12.2.1.12

acpmAvgVoltageNormalTrapNum OBJECT-TYPE
    SYNTAX Integer32 (520..1199)
    MAX-ACCESS read-write
    STATUS current
    DESCRIPTION
        "Return to normal trap number."
    ::= { acpmAvgVoltageEntry 13 }
    --1.3.6.1.4.1.3052.10.2.12.12.2.1.13

acpmAvgVoltageNormalClass OBJECT-TYPE
    SYNTAX DisplayString
    MAX-ACCESS read-write
    STATUS current
    DESCRIPTION
        "Return to normal class."
    ::= { acpmAvgVoltageEntry 14 }
    --1.3.6.1.4.1.3052.10.2.12.12.2.1.14

acpmAvgVoltageLowValue OBJECT-TYPE
    SYNTAX DisplayString
    MAX-ACCESS read-write
    STATUS current
    DESCRIPTION
        "Low event threshold.  This is a floating point value."
    ::= { acpmAvgVoltageEntry 15 }
    --1.3.6.1.4.1.3052.10.2.12.12.2.1.15

acpmAvgVoltageLowActions OBJECT-TYPE
    SYNTAX DisplayString
    MAX-ACCESS read-write
    STATUS current
    DESCRIPTION
        "Low event actions."
    ::= { acpmAvgVoltageEntry 16 }
    --1.3.6.1.4.1.3052.10.2.12.12.2.1.16

acpmAvgVoltageLowTrapNum OBJECT-TYPE
    SYNTAX Integer32 (520..1199)
    MAX-ACCESS read-write
    STATUS current
    DESCRIPTION
        "Low event trap number."
    ::= { acpmAvgVoltageEntry 17 }
    --1.3.6.1.4.1.3052.10.2.12.12.2.1.17

acpmAvgVoltageLowClass OBJECT-TYPE
    SYNTAX DisplayString
    MAX-ACCESS read-write
    STATUS current
    DESCRIPTION
        "Low event class."
    ::= { acpmAvgVoltageEntry 18 }
    --1.3.6.1.4.1.3052.10.2.12.12.2.1.18

acpmAvgVoltageVLowValue OBJECT-TYPE
    SYNTAX DisplayString
    MAX-ACCESS read-write
    STATUS current
    DESCRIPTION
        "Very low event threshold.  This is a floating point value."
    ::= { acpmAvgVoltageEntry 19 }
    --1.3.6.1.4.1.3052.10.2.12.12.2.1.19

acpmAvgVoltageVLowActions OBJECT-TYPE
    SYNTAX DisplayString
    MAX-ACCESS read-write
    STATUS current
    DESCRIPTION
        "Very low event actions."
    ::= { acpmAvgVoltageEntry 20 }
    --1.3.6.1.4.1.3052.10.2.12.12.2.1.20

acpmAvgVoltageVLowTrapNum OBJECT-TYPE
    SYNTAX Integer32 (520..1199)
    MAX-ACCESS read-write
    STATUS current
    DESCRIPTION
        "Very low event trap number."
    ::= { acpmAvgVoltageEntry 21 }
    --1.3.6.1.4.1.3052.10.2.12.12.2.1.21

acpmAvgVoltageVLowClass OBJECT-TYPE
    SYNTAX DisplayString
    MAX-ACCESS read-write
    STATUS current
    DESCRIPTION
        "Very low event class."
    ::= { acpmAvgVoltageEntry 22 }
    --1.3.6.1.4.1.3052.10.2.12.12.2.1.22

acpmAvgVoltageSysrepEnable OBJECT-TYPE
    SYNTAX DisplayString
    MAX-ACCESS read-write
    STATUS current
    DESCRIPTION
        "System reporting enable for average voltage telemetry."
    ::= { acpmAvgVoltageEntry 23 }
    --1.3.6.1.4.1.3052.10.2.12.12.2.1.23

acpmAvgVoltageSysrepThreshold OBJECT-TYPE
    SYNTAX DisplayString
    MAX-ACCESS read-write
    STATUS current
    DESCRIPTION
        "System reporting threshold for average voltage telemetry.  This is a
        floating point value."
    ::= { acpmAvgVoltageEntry 24 }
    --1.3.6.1.4.1.3052.10.2.12.12.2.1.24

acpmAvgVoltageSysrepLimit OBJECT-TYPE
    SYNTAX Integer32
    MAX-ACCESS read-write
    STATUS current
    DESCRIPTION
        "System reporting limit for average voltage telemetry."
    ::= { acpmAvgVoltageEntry 25 }
    --1.3.6.1.4.1.3052.10.2.12.12.2.1.25


acpmAvgCurrentTable OBJECT-TYPE
    SYNTAX SEQUENCE OF ACPMConfigAvgCurrent
    MAX-ACCESS not-accessible
    STATUS current
    DESCRIPTION
        "This table organizes AC power monitor average current attributes."
    ::= { acPowerMonitor 3 }
    --1.3.6.1.4.1.3052.10.2.12.12.3

acpmAvgCurrentEntry OBJECT-TYPE
    SYNTAX ACPMConfigAvgCurrent
    MAX-ACCESS not-accessible
    STATUS current
    DESCRIPTION
        "Entry for AC power monitor average current config table."
    INDEX { acpmAvgCurrentIndex }
    ::= { acpmAvgCurrentTable 1 }
    --1.3.6.1.4.1.3052.10.2.12.12.3.1

acpmAvgCurrentIndex OBJECT-TYPE
    SYNTAX Integer32 (1..6)
    MAX-ACCESS read-only
    STATUS current
    DESCRIPTION
        "Which AC power monitor in the AC power monitor average current config
        table."
    ::= { acpmAvgCurrentEntry 1 }
    --1.3.6.1.4.1.3052.10.2.12.12.3.1.1

acpmAvgCurrentEnable OBJECT-TYPE
    SYNTAX DisplayString
    MAX-ACCESS read-write
    STATUS current
    DESCRIPTION
        "Enable AC power monitor average current events."
    ::= { acpmAvgCurrentEntry 2 }
    --1.3.6.1.4.1.3052.10.2.12.12.3.1.2

acpmAvgCurrentDeadband OBJECT-TYPE
    SYNTAX DisplayString
    MAX-ACCESS read-write
    STATUS current
    DESCRIPTION
        "Deadband (hysteresis) for average current event.  This is a floating
        point value."
    ::= { acpmAvgCurrentEntry 3 }
    --1.3.6.1.4.1.3052.10.2.12.12.3.1.3

acpmAvgCurrentVHighValue OBJECT-TYPE
    SYNTAX DisplayString
    MAX-ACCESS read-write
    STATUS current
    DESCRIPTION
        "Very high event threshold.  This is a floating point value."
    ::= { acpmAvgCurrentEntry 4 }
    --1.3.6.1.4.1.3052.10.2.12.12.3.1.4

acpmAvgCurrentVHighActions OBJECT-TYPE
    SYNTAX DisplayString
    MAX-ACCESS read-write
    STATUS current
    DESCRIPTION
        "Very high event actions."
    ::= { acpmAvgCurrentEntry 5 }
    --1.3.6.1.4.1.3052.10.2.12.12.3.1.5

acpmAvgCurrentVHighTrapNum OBJECT-TYPE
    SYNTAX Integer32 (521..1199)
    MAX-ACCESS read-write
    STATUS current
    DESCRIPTION
        "Very high event trap number."
    ::= { acpmAvgCurrentEntry 6 }
    --1.3.6.1.4.1.3052.10.2.12.12.3.1.6

acpmAvgCurrentVHighClass OBJECT-TYPE
    SYNTAX DisplayString
    MAX-ACCESS read-write
    STATUS current
    DESCRIPTION
        "Very high event class."
    ::= { acpmAvgCurrentEntry 7 }
    --1.3.6.1.4.1.3052.10.2.12.12.3.1.7

acpmAvgCurrentHighValue OBJECT-TYPE
    SYNTAX DisplayString
    MAX-ACCESS read-write
    STATUS current
    DESCRIPTION
        "High event threshold.  This is a floating point value."
    ::= { acpmAvgCurrentEntry 8 }
    --1.3.6.1.4.1.3052.10.2.12.12.3.1.8

acpmAvgCurrentHighActions OBJECT-TYPE
    SYNTAX DisplayString
    MAX-ACCESS read-write
    STATUS current
    DESCRIPTION
        "High event actions."
    ::= { acpmAvgCurrentEntry 9 }
    --1.3.6.1.4.1.3052.10.2.12.12.3.1.9

acpmAvgCurrentHighTrapNum OBJECT-TYPE
    SYNTAX Integer32 (521..1199)
    MAX-ACCESS read-write
    STATUS current
    DESCRIPTION
        "High event trap number."
    ::= { acpmAvgCurrentEntry 10 }
    --1.3.6.1.4.1.3052.10.2.12.12.3.1.10

acpmAvgCurrentHighClass OBJECT-TYPE
    SYNTAX DisplayString
    MAX-ACCESS read-write
    STATUS current
    DESCRIPTION
        "High event class."
    ::= { acpmAvgCurrentEntry 11 }
    --1.3.6.1.4.1.3052.10.2.12.12.3.1.11

acpmAvgCurrentNormalActions OBJECT-TYPE
    SYNTAX DisplayString
    MAX-ACCESS read-write
    STATUS current
    DESCRIPTION
        "Return to normal actions."
    ::= { acpmAvgCurrentEntry 12 }
    --1.3.6.1.4.1.3052.10.2.12.12.3.1.12

acpmAvgCurrentNormalTrapNum OBJECT-TYPE
    SYNTAX Integer32 (521..1199)
    MAX-ACCESS read-write
    STATUS current
    DESCRIPTION
        "Return to normal trap number."
    ::= { acpmAvgCurrentEntry 13 }
    --1.3.6.1.4.1.3052.10.2.12.12.3.1.13

acpmAvgCurrentNormalClass OBJECT-TYPE
    SYNTAX DisplayString
    MAX-ACCESS read-write
    STATUS current
    DESCRIPTION
        "Return to normal class."
    ::= { acpmAvgCurrentEntry 14 }
    --1.3.6.1.4.1.3052.10.2.12.12.3.1.14

acpmAvgCurrentLowValue OBJECT-TYPE
    SYNTAX DisplayString
    MAX-ACCESS read-write
    STATUS current
    DESCRIPTION
        "Low event threshold.  This is a floating point value."
    ::= { acpmAvgCurrentEntry 15 }
    --1.3.6.1.4.1.3052.10.2.12.12.3.1.15

acpmAvgCurrentLowActions OBJECT-TYPE
    SYNTAX DisplayString
    MAX-ACCESS read-write
    STATUS current
    DESCRIPTION
        "Low event actions."
    ::= { acpmAvgCurrentEntry 16 }
    --1.3.6.1.4.1.3052.10.2.12.12.3.1.16

acpmAvgCurrentLowTrapNum OBJECT-TYPE
    SYNTAX Integer32 (521..1199)
    MAX-ACCESS read-write
    STATUS current
    DESCRIPTION
        "Low event trap number."
    ::= { acpmAvgCurrentEntry 17 }
    --1.3.6.1.4.1.3052.10.2.12.12.3.1.17

acpmAvgCurrentLowClass OBJECT-TYPE
    SYNTAX DisplayString
    MAX-ACCESS read-write
    STATUS current
    DESCRIPTION
        "Low event class."
    ::= { acpmAvgCurrentEntry 18 }
    --1.3.6.1.4.1.3052.10.2.12.12.3.1.18

acpmAvgCurrentVLowValue OBJECT-TYPE
    SYNTAX DisplayString
    MAX-ACCESS read-write
    STATUS current
    DESCRIPTION
        "Very low event threshold.  This is a floating point value."
    ::= { acpmAvgCurrentEntry 19 }
    --1.3.6.1.4.1.3052.10.2.12.12.3.1.19

acpmAvgCurrentVLowActions OBJECT-TYPE
    SYNTAX DisplayString
    MAX-ACCESS read-write
    STATUS current
    DESCRIPTION
        "Very low event actions."
    ::= { acpmAvgCurrentEntry 20 }
    --1.3.6.1.4.1.3052.10.2.12.12.3.1.20

acpmAvgCurrentVLowTrapNum OBJECT-TYPE
    SYNTAX Integer32 (521..1199)
    MAX-ACCESS read-write
    STATUS current
    DESCRIPTION
        "Very low event trap number."
    ::= { acpmAvgCurrentEntry 21 }
    --1.3.6.1.4.1.3052.10.2.12.12.3.1.21

acpmAvgCurrentVLowClass OBJECT-TYPE
    SYNTAX DisplayString
    MAX-ACCESS read-write
    STATUS current
    DESCRIPTION
        "Very low event class."
    ::= { acpmAvgCurrentEntry 22 }
    --1.3.6.1.4.1.3052.10.2.12.12.3.1.22

acpmAvgCurrentSysrepEnable OBJECT-TYPE
    SYNTAX DisplayString
    MAX-ACCESS read-write
    STATUS current
    DESCRIPTION
        "System reporting enable for average current telemetry."
    ::= { acpmAvgCurrentEntry 23 }
    --1.3.6.1.4.1.3052.10.2.12.12.3.1.23

acpmAvgCurrentSysrepThreshold OBJECT-TYPE
    SYNTAX DisplayString
    MAX-ACCESS read-write
    STATUS current
    DESCRIPTION
        "System reporting threshold for average current telemetry.  This is
        a floating point value."
    ::= { acpmAvgCurrentEntry 24 }
    --1.3.6.1.4.1.3052.10.2.12.12.3.1.24

acpmAvgCurrentSysrepLimit OBJECT-TYPE
    SYNTAX Integer32
    MAX-ACCESS read-write
    STATUS current
    DESCRIPTION
        "System reporting limit for average current telemetry."
    ::= { acpmAvgCurrentEntry 25 }
    --1.3.6.1.4.1.3052.10.2.12.12.3.1.25


acpmFreqTable OBJECT-TYPE
    SYNTAX SEQUENCE OF ACPMConfigFreq
    MAX-ACCESS not-accessible
    STATUS current
    DESCRIPTION
        "This table organizes AC power monitor frequency attributes."
    ::= { acPowerMonitor 4 }
    --1.3.6.1.4.1.3052.10.2.12.12.4

acpmFreqEntry OBJECT-TYPE
    SYNTAX ACPMConfigFreq
    MAX-ACCESS not-accessible
    STATUS current
    DESCRIPTION
        "Entry for AC power monitor frequency config table."
    INDEX { acpmFreqIndex }
    ::= { acpmFreqTable 1 }
    --1.3.6.1.4.1.3052.10.2.12.12.4.1

acpmFreqIndex OBJECT-TYPE
    SYNTAX Integer32 (1..6)
    MAX-ACCESS read-only
    STATUS current
    DESCRIPTION
        "Which AC power monitor in the AC power monitor frequency config table."
    ::= { acpmFreqEntry 1 }
    --1.3.6.1.4.1.3052.10.2.12.12.4.1.1

acpmFreqEnable OBJECT-TYPE
    SYNTAX DisplayString
    MAX-ACCESS read-write
    STATUS current
    DESCRIPTION
        "Enable AC power monitor frequency events."
    ::= { acpmFreqEntry 2 }
    --1.3.6.1.4.1.3052.10.2.12.12.4.1.2

acpmFreqDeadband OBJECT-TYPE
    SYNTAX DisplayString
    MAX-ACCESS read-write
    STATUS current
    DESCRIPTION
        "Deadband (hysteresis) for frequency event.  This is a floating point
        value."
    ::= { acpmFreqEntry 3 }
    --1.3.6.1.4.1.3052.10.2.12.12.4.1.3

acpmFreqVHighValue OBJECT-TYPE
    SYNTAX DisplayString
    MAX-ACCESS read-write
    STATUS current
    DESCRIPTION
        "Very high event threshold.  This is a floating point value."
    ::= { acpmFreqEntry 4 }
    --1.3.6.1.4.1.3052.10.2.12.12.4.1.4

acpmFreqVHighActions OBJECT-TYPE
    SYNTAX DisplayString
    MAX-ACCESS read-write
    STATUS current
    DESCRIPTION
        "Very high event actions."
    ::= { acpmFreqEntry 5 }
    --1.3.6.1.4.1.3052.10.2.12.12.4.1.5

acpmFreqVHighTrapNum OBJECT-TYPE
    SYNTAX Integer32 (522..1199)
    MAX-ACCESS read-write
    STATUS current
    DESCRIPTION
        "Very high event trap number."
    ::= { acpmFreqEntry 6 }
    --1.3.6.1.4.1.3052.10.2.12.12.4.1.6

acpmFreqVHighClass OBJECT-TYPE
    SYNTAX DisplayString
    MAX-ACCESS read-write
    STATUS current
    DESCRIPTION
        "Very high event class."
    ::= { acpmFreqEntry 7 }
    --1.3.6.1.4.1.3052.10.2.12.12.4.1.7

acpmFreqHighValue OBJECT-TYPE
    SYNTAX DisplayString
    MAX-ACCESS read-write
    STATUS current
    DESCRIPTION
        "High event threshold.  This is a floating point value."
    ::= { acpmFreqEntry 8 }
    --1.3.6.1.4.1.3052.10.2.12.12.4.1.8

acpmFreqHighActions OBJECT-TYPE
    SYNTAX DisplayString
    MAX-ACCESS read-write
    STATUS current
    DESCRIPTION
        "High event actions."
    ::= { acpmFreqEntry 9 }
    --1.3.6.1.4.1.3052.10.2.12.12.4.1.9

acpmFreqHighTrapNum OBJECT-TYPE
    SYNTAX Integer32 (522..1199)
    MAX-ACCESS read-write
    STATUS current
    DESCRIPTION
        "High event trap number."
    ::= { acpmFreqEntry 10 }
    --1.3.6.1.4.1.3052.10.2.12.12.4.1.10

acpmFreqHighClass OBJECT-TYPE
    SYNTAX DisplayString
    MAX-ACCESS read-write
    STATUS current
    DESCRIPTION
        "High event class."
    ::= { acpmFreqEntry 11 }
    --1.3.6.1.4.1.3052.10.2.12.12.4.1.11

acpmFreqNormalActions OBJECT-TYPE
    SYNTAX DisplayString
    MAX-ACCESS read-write
    STATUS current
    DESCRIPTION
        "Return to normal actions."
    ::= { acpmFreqEntry 12 }
    --1.3.6.1.4.1.3052.10.2.12.12.4.1.12

acpmFreqNormalTrapNum OBJECT-TYPE
    SYNTAX Integer32 (522..1199)
    MAX-ACCESS read-write
    STATUS current
    DESCRIPTION
        "Return to normal trap number."
    ::= { acpmFreqEntry 13 }
    --1.3.6.1.4.1.3052.10.2.12.12.4.1.13

acpmFreqNormalClass OBJECT-TYPE
    SYNTAX DisplayString
    MAX-ACCESS read-write
    STATUS current
    DESCRIPTION
        "Return to normal class."
    ::= { acpmFreqEntry 14 }
    --1.3.6.1.4.1.3052.10.2.12.12.4.1.14

acpmFreqLowValue OBJECT-TYPE
    SYNTAX DisplayString
    MAX-ACCESS read-write
    STATUS current
    DESCRIPTION
        "Low event threshold.  This is a floating point value."
    ::= { acpmFreqEntry 15 }
    --1.3.6.1.4.1.3052.10.2.12.12.4.1.15

acpmFreqLowActions OBJECT-TYPE
    SYNTAX DisplayString
    MAX-ACCESS read-write
    STATUS current
    DESCRIPTION
        "Low event actions."
    ::= { acpmFreqEntry 16 }
    --1.3.6.1.4.1.3052.10.2.12.12.4.1.16

acpmFreqLowTrapNum OBJECT-TYPE
    SYNTAX Integer32 (522..1199)
    MAX-ACCESS read-write
    STATUS current
    DESCRIPTION
        "Low event trap number."
    ::= { acpmFreqEntry 17 }
    --1.3.6.1.4.1.3052.10.2.12.12.4.1.17

acpmFreqLowClass OBJECT-TYPE
    SYNTAX DisplayString
    MAX-ACCESS read-write
    STATUS current
    DESCRIPTION
        "Low event class."
    ::= { acpmFreqEntry 18 }
    --1.3.6.1.4.1.3052.10.2.12.12.4.1.18

acpmFreqVLowValue OBJECT-TYPE
    SYNTAX DisplayString
    MAX-ACCESS read-write
    STATUS current
    DESCRIPTION
        "Very low event threshold.  This is a floating point value."
    ::= { acpmFreqEntry 19 }
    --1.3.6.1.4.1.3052.10.2.12.12.4.1.19

acpmFreqVLowActions OBJECT-TYPE
    SYNTAX DisplayString
    MAX-ACCESS read-write
    STATUS current
    DESCRIPTION
        "Very low event actions."
    ::= { acpmFreqEntry 20 }
    --1.3.6.1.4.1.3052.10.2.12.12.4.1.20

acpmFreqVLowTrapNum OBJECT-TYPE
    SYNTAX Integer32 (522..1199)
    MAX-ACCESS read-write
    STATUS current
    DESCRIPTION
        "Very low event trap number."
    ::= { acpmFreqEntry 21 }
    --1.3.6.1.4.1.3052.10.2.12.12.4.1.21

acpmFreqVLowClass OBJECT-TYPE
    SYNTAX DisplayString
    MAX-ACCESS read-write
    STATUS current
    DESCRIPTION
        "Very low event class."
    ::= { acpmFreqEntry 22 }
    --1.3.6.1.4.1.3052.10.2.12.12.4.1.22

acpmFreqSysrepEnable OBJECT-TYPE
    SYNTAX DisplayString
    MAX-ACCESS read-write
    STATUS current
    DESCRIPTION
        "System reporting enable for frequency telemetry."
    ::= { acpmFreqEntry 23 }
    --1.3.6.1.4.1.3052.10.2.12.12.4.1.23

acpmFreqSysrepThreshold OBJECT-TYPE
    SYNTAX DisplayString
    MAX-ACCESS read-write
    STATUS current
    DESCRIPTION
        "System reporting threshold for frequency telemetry.  This is a
        floating point value."
    ::= { acpmFreqEntry 24 }
    --1.3.6.1.4.1.3052.10.2.12.12.4.1.24

acpmFreqSysrepLimit OBJECT-TYPE
    SYNTAX Integer32
    MAX-ACCESS read-write
    STATUS current
    DESCRIPTION
        "System reporting limit for frequency telemetry."
    ::= { acpmFreqEntry 25 }
    --1.3.6.1.4.1.3052.10.2.12.12.4.1.25


acpmTotalRealPowerTable OBJECT-TYPE
    SYNTAX SEQUENCE OF ACPMConfigTRP
    MAX-ACCESS not-accessible
    STATUS current
    DESCRIPTION
        "This table organizes AC power monitor total real power attributes."
    ::= { acPowerMonitor 5 }
    --1.3.6.1.4.1.3052.10.2.12.12.5

acpmTRPEntry OBJECT-TYPE
    SYNTAX ACPMConfigTRP
    MAX-ACCESS not-accessible
    STATUS current
    DESCRIPTION
        "Entry for AC power monitor total real power config table."
    INDEX { acpmTRPIndex }
    ::= { acpmTotalRealPowerTable 1 }
    --1.3.6.1.4.1.3052.10.2.12.12.5.1

acpmTRPIndex OBJECT-TYPE
    SYNTAX Integer32 (1..6)
    MAX-ACCESS read-only
    STATUS current
    DESCRIPTION
        "Which AC power monitor in the AC power monitor total real power
        config table."
    ::= { acpmTRPEntry 1 }
    --1.3.6.1.4.1.3052.10.2.12.12.5.1.1

acpmTRPEnable OBJECT-TYPE
    SYNTAX DisplayString
    MAX-ACCESS read-write
    STATUS current
    DESCRIPTION
        "Enable AC power monitor total real power events."
    ::= { acpmTRPEntry 2 }
    --1.3.6.1.4.1.3052.10.2.12.12.5.1.2

acpmTRPDeadband OBJECT-TYPE
    SYNTAX DisplayString
    MAX-ACCESS read-write
    STATUS current
    DESCRIPTION
        "Deadband (hysteresis) for total real power event.  This is a
        floating point value."
    ::= { acpmTRPEntry 3 }
    --1.3.6.1.4.1.3052.10.2.12.12.5.1.3

acpmTRPVHighValue OBJECT-TYPE
    SYNTAX DisplayString
    MAX-ACCESS read-write
    STATUS current
    DESCRIPTION
        "Very high event threshold.  This is a floating point value."
    ::= { acpmTRPEntry 4 }
    --1.3.6.1.4.1.3052.10.2.12.12.5.1.4

acpmTRPVHighActions OBJECT-TYPE
    SYNTAX DisplayString
    MAX-ACCESS read-write
    STATUS current
    DESCRIPTION
        "Very high event actions."
    ::= { acpmTRPEntry 5 }
    --1.3.6.1.4.1.3052.10.2.12.12.5.1.5

acpmTRPVHighTrapNum OBJECT-TYPE
    SYNTAX Integer32 (523..1199)
    MAX-ACCESS read-write
    STATUS current
    DESCRIPTION
        "Very high event trap number."
    ::= { acpmTRPEntry 6 }
    --1.3.6.1.4.1.3052.10.2.12.12.5.1.6

acpmTRPVHighClass OBJECT-TYPE
    SYNTAX DisplayString
    MAX-ACCESS read-write
    STATUS current
    DESCRIPTION
        "Very high event class."
    ::= { acpmTRPEntry 7 }
    --1.3.6.1.4.1.3052.10.2.12.12.5.1.7

acpmTRPHighValue OBJECT-TYPE
    SYNTAX DisplayString
    MAX-ACCESS read-write
    STATUS current
    DESCRIPTION
        "High event threshold.  This is a floating point value."
    ::= { acpmTRPEntry 8 }
    --1.3.6.1.4.1.3052.10.2.12.12.5.1.8

acpmTRPHighActions OBJECT-TYPE
    SYNTAX DisplayString
    MAX-ACCESS read-write
    STATUS current
    DESCRIPTION
        "High event actions."
    ::= { acpmTRPEntry 9 }
    --1.3.6.1.4.1.3052.10.2.12.12.5.1.9

acpmTRPHighTrapNum OBJECT-TYPE
    SYNTAX Integer32 (523..1199)
    MAX-ACCESS read-write
    STATUS current
    DESCRIPTION
        "High event trap number."
    ::= { acpmTRPEntry 10 }
    --1.3.6.1.4.1.3052.10.2.12.12.5.1.10

acpmTRPHighClass OBJECT-TYPE
    SYNTAX DisplayString
    MAX-ACCESS read-write
    STATUS current
    DESCRIPTION
        "High event class."
    ::= { acpmTRPEntry 11 }
    --1.3.6.1.4.1.3052.10.2.12.12.5.1.11

acpmTRPNormalActions OBJECT-TYPE
    SYNTAX DisplayString
    MAX-ACCESS read-write
    STATUS current
    DESCRIPTION
        "Return to normal actions."
    ::= { acpmTRPEntry 12 }
    --1.3.6.1.4.1.3052.10.2.12.12.5.1.12

acpmTRPNormalTrapNum OBJECT-TYPE
    SYNTAX Integer32 (523..1199)
    MAX-ACCESS read-write
    STATUS current
    DESCRIPTION
        "Return to normal trap number."
    ::= { acpmTRPEntry 13 }
    --1.3.6.1.4.1.3052.10.2.12.12.5.1.13

acpmTRPNormalClass OBJECT-TYPE
    SYNTAX DisplayString
    MAX-ACCESS read-write
    STATUS current
    DESCRIPTION
        "Return to normal class."
    ::= { acpmTRPEntry 14 }
    --1.3.6.1.4.1.3052.10.2.12.12.5.1.14

acpmTRPLowValue OBJECT-TYPE
    SYNTAX DisplayString
    MAX-ACCESS read-write
    STATUS current
    DESCRIPTION
        "Low event threshold.  This is a floating point value."
    ::= { acpmTRPEntry 15 }
    --1.3.6.1.4.1.3052.10.2.12.12.5.1.15

acpmTRPLowActions OBJECT-TYPE
    SYNTAX DisplayString
    MAX-ACCESS read-write
    STATUS current
    DESCRIPTION
        "Low event actions."
    ::= { acpmTRPEntry 16 }
    --1.3.6.1.4.1.3052.10.2.12.12.5.1.16

acpmTRPLowTrapNum OBJECT-TYPE
    SYNTAX Integer32 (523..1199)
    MAX-ACCESS read-write
    STATUS current
    DESCRIPTION
        "Low event trap number."
    ::= { acpmTRPEntry 17 }
    --1.3.6.1.4.1.3052.10.2.12.12.5.1.17

acpmTRPLowClass OBJECT-TYPE
    SYNTAX DisplayString
    MAX-ACCESS read-write
    STATUS current
    DESCRIPTION
        "Low event class."
    ::= { acpmTRPEntry 18 }
    --1.3.6.1.4.1.3052.10.2.12.12.5.1.18

acpmTRPVLowValue OBJECT-TYPE
    SYNTAX DisplayString
    MAX-ACCESS read-write
    STATUS current
    DESCRIPTION
        "Very low event threshold.  This is a floating point value."
    ::= { acpmTRPEntry 19 }
    --1.3.6.1.4.1.3052.10.2.12.12.5.1.19

acpmTRPVLowActions OBJECT-TYPE
    SYNTAX DisplayString
    MAX-ACCESS read-write
    STATUS current
    DESCRIPTION
        "Very low event actions."
    ::= { acpmTRPEntry 20 }
    --1.3.6.1.4.1.3052.10.2.12.12.5.1.20

acpmTRPVLowTrapNum OBJECT-TYPE
    SYNTAX Integer32 (523..1199)
    MAX-ACCESS read-write
    STATUS current
    DESCRIPTION
        "Very low event trap number."
    ::= { acpmTRPEntry 21 }
    --1.3.6.1.4.1.3052.10.2.12.12.5.1.21

acpmTRPVLowClass OBJECT-TYPE
    SYNTAX DisplayString
    MAX-ACCESS read-write
    STATUS current
    DESCRIPTION
        "Very low event class."
    ::= { acpmTRPEntry 22 }
    --1.3.6.1.4.1.3052.10.2.12.12.5.1.22

acpmTRPSysrepEnable OBJECT-TYPE
    SYNTAX DisplayString
    MAX-ACCESS read-write
    STATUS current
    DESCRIPTION
        "System reporting enable for total real power telemetry."
    ::= { acpmTRPEntry 23 }
    --1.3.6.1.4.1.3052.10.2.12.12.5.1.23

acpmTRPSysrepThreshold OBJECT-TYPE
    SYNTAX DisplayString
    MAX-ACCESS read-write
    STATUS current
    DESCRIPTION
        "System reporting threshold for total real power telemetry.  This is a
        floating point value."
    ::= { acpmTRPEntry 24 }
    --1.3.6.1.4.1.3052.10.2.12.12.5.1.24

acpmTRPSysrepLimit OBJECT-TYPE
    SYNTAX Integer32
    MAX-ACCESS read-write
    STATUS current
    DESCRIPTION
        "System reporting limit for total real power telemetry."
    ::= { acpmTRPEntry 25 }
    --1.3.6.1.4.1.3052.10.2.12.12.5.1.25


acpmDisconnectTable OBJECT-TYPE
    SYNTAX SEQUENCE OF ACPMConfigDisconnect
    MAX-ACCESS not-accessible
    STATUS current
    DESCRIPTION
        "This table organizes AC power monitor device disconnect event
        attributes."
    ::= { acPowerMonitor 6 }
    --1.3.6.1.4.1.3052.10.2.12.12.6

acpmDisconnectEntry OBJECT-TYPE
    SYNTAX ACPMConfigDisconnect
    MAX-ACCESS not-accessible
    STATUS current
    DESCRIPTION
        "Entry for AC power monitor device disconnect event config table."
    INDEX { acpmDisconnectIndex }
    ::= { acpmDisconnectTable 1 }
    --1.3.6.1.4.1.3052.10.2.12.12.6.1

acpmDisconnectIndex OBJECT-TYPE
    SYNTAX Integer32 (1..6)
    MAX-ACCESS read-only
    STATUS current
    DESCRIPTION
        "Which AC power monitor in the AC power monitor device disconnect event
        config table."
    ::= { acpmDisconnectEntry 1 }
    --1.3.6.1.4.1.3052.10.2.12.12.6.1.1

acpmDisconnectEnable OBJECT-TYPE
    SYNTAX DisplayString
    MAX-ACCESS read-write
    STATUS current
    DESCRIPTION
        "Enable AC power monitor device disconnect event."
    ::= { acpmDisconnectEntry 2 }
    --1.3.6.1.4.1.3052.10.2.12.12.6.1.2

acpmDisconnectActions OBJECT-TYPE
    SYNTAX DisplayString
    MAX-ACCESS read-write
    STATUS current
    DESCRIPTION
        "Actions for disconnect event."
    ::= { acpmDisconnectEntry 3 }
    --1.3.6.1.4.1.3052.10.2.12.12.6.1.3

acpmDisconnectTrapNum OBJECT-TYPE
    SYNTAX Integer32 (524..1199)
    MAX-ACCESS read-write
    STATUS current
    DESCRIPTION
        "Trap number for disconnect event."
    ::= { acpmDisconnectEntry 4 }
    --1.3.6.1.4.1.3052.10.2.12.12.6.1.4

acpmDisconnectClass OBJECT-TYPE
    SYNTAX DisplayString
    MAX-ACCESS read-write
    STATUS current
    DESCRIPTION
        "Class for disconnect event."
    ::= { acpmDisconnectEntry 5 }
    --1.3.6.1.4.1.3052.10.2.12.12.6.1.5

acpmDisconnectNormalActions OBJECT-TYPE
    SYNTAX DisplayString
    MAX-ACCESS read-write
    STATUS current
    DESCRIPTION
        "Actions for disconnect return to normal event."
    ::= { acpmDisconnectEntry 6 }
    --1.3.6.1.4.1.3052.10.2.12.12.6.1.6

acpmDisconnectNormalTrapNum OBJECT-TYPE
    SYNTAX Integer32 (524..1199)
    MAX-ACCESS read-write
    STATUS current
    DESCRIPTION
        "Trap number for disconnect return to normal event."
    ::= { acpmDisconnectEntry 7 }
    --1.3.6.1.4.1.3052.10.2.12.12.6.1.7

acpmDisconnectNormalClass OBJECT-TYPE
    SYNTAX DisplayString
    MAX-ACCESS read-write
    STATUS current
    DESCRIPTION
        "Class for disconnect return to normal event."
    ::= { acpmDisconnectEntry 8 }
    --1.3.6.1.4.1.3052.10.2.12.12.6.1.8

acpmTotalPowerFactorTable OBJECT-TYPE
    SYNTAX SEQUENCE OF ACPMConfigTotalPowerFactor
    MAX-ACCESS not-accessible
    STATUS current
    DESCRIPTION
        "This table organizes AC power monitor device total power factor
        event attributes."
    ::= { acPowerMonitor 7 }
    --1.3.6.1.4.1.3052.10.2.12.12.7

acpmTPFEntry OBJECT-TYPE
    SYNTAX ACPMConfigTotalPowerFactor
    MAX-ACCESS not-accessible
    STATUS current
    DESCRIPTION
        "Entry for AC power monitor device total power factor event config
        table."
    INDEX { acpmTPFIndex }
    ::= { acpmTotalPowerFactorTable 1 }
    --1.3.6.1.4.1.3052.10.2.12.12.7.1

acpmTPFIndex OBJECT-TYPE
    SYNTAX Integer32 (1..6)
    MAX-ACCESS read-only
    STATUS current
    DESCRIPTION
        "Which AC power monitor in the AC power monitor device disconnect
        event config table."
    ::= { acpmTPFEntry 1 }
    --1.3.6.1.4.1.3052.10.2.12.12.7.1.1

acpmTPFEnable OBJECT-TYPE
    SYNTAX DisplayString
    MAX-ACCESS read-write
    STATUS current
    DESCRIPTION
        "Enable AC power monitor device disconnect event."
    ::= { acpmTPFEntry 2 }
    --1.3.6.1.4.1.3052.10.2.12.12.7.1.2

acpmTPFDeadband OBJECT-TYPE
    SYNTAX DisplayString
    MAX-ACCESS read-write
    STATUS current
    DESCRIPTION
        "Deadband (hysteresis)."
    ::= { acpmTPFEntry 3 }
    --1.3.6.1.4.1.3052.10.2.12.12.7.1.3

acpmTPFNormalActions OBJECT-TYPE
    SYNTAX DisplayString
    MAX-ACCESS read-write
    STATUS current
    DESCRIPTION
        "Normal actions."
    ::= { acpmTPFEntry 4 }
    --1.3.6.1.4.1.3052.10.2.12.12.7.1.4

acpmTPFNormalTrapNum OBJECT-TYPE
    SYNTAX Integer32
    MAX-ACCESS read-write
    STATUS current
    DESCRIPTION
        "Normal trap number."
    ::= { acpmTPFEntry 5 }
    --1.3.6.1.4.1.3052.10.2.12.12.7.1.5

acpmTPFNormalClass OBJECT-TYPE
    SYNTAX DisplayString
    MAX-ACCESS read-write
    STATUS current
    DESCRIPTION
        "Normal class."
    ::= { acpmTPFEntry 6 }
    --1.3.6.1.4.1.3052.10.2.12.12.7.1.6

acpmTPFLowValue OBJECT-TYPE
    SYNTAX DisplayString
    MAX-ACCESS read-write
    STATUS current
    DESCRIPTION
        "Low threshold."
    ::= { acpmTPFEntry 7 }
    --1.3.6.1.4.1.3052.10.2.12.12.7.1.7

acpmTPFLowActions OBJECT-TYPE
    SYNTAX DisplayString
    MAX-ACCESS read-write
    STATUS current
    DESCRIPTION
        "Low actions."
    ::= { acpmTPFEntry 8 }
    --1.3.6.1.4.1.3052.10.2.12.12.7.1.8

acpmTPFLowTrapNum OBJECT-TYPE
    SYNTAX Integer32
    MAX-ACCESS read-write
    STATUS current
    DESCRIPTION
        "Low trap number."
    ::= { acpmTPFEntry 9 }
    --1.3.6.1.4.1.3052.10.2.12.12.7.1.9

acpmTPFLowClass OBJECT-TYPE
    SYNTAX DisplayString
    MAX-ACCESS read-write
    STATUS current
    DESCRIPTION
        "Low class."
    ::= { acpmTPFEntry 10 }
    --1.3.6.1.4.1.3052.10.2.12.12.7.1.10

acpmTPFVLowValue OBJECT-TYPE
    SYNTAX DisplayString
    MAX-ACCESS read-write
    STATUS current
    DESCRIPTION
        "Very Low threshold."
    ::= { acpmTPFEntry 11 }
    --1.3.6.1.4.1.3052.10.2.12.12.7.1.11

acpmTPFVLowActions OBJECT-TYPE
    SYNTAX DisplayString
    MAX-ACCESS read-write
    STATUS current
    DESCRIPTION
        "Very Low actions."
    ::= { acpmTPFEntry 12 }
    --1.3.6.1.4.1.3052.10.2.12.12.7.1.12

acpmTPFVLowTrapNum OBJECT-TYPE
    SYNTAX Integer32
    MAX-ACCESS read-write
    STATUS current
    DESCRIPTION
        "Very Low trap number."
    ::= { acpmTPFEntry 13 }
    --1.3.6.1.4.1.3052.10.2.12.12.7.1.13

acpmTPFVLowClass OBJECT-TYPE
    SYNTAX DisplayString
    MAX-ACCESS read-write
    STATUS current
    DESCRIPTION
        "Very Low class."
    ::= { acpmTPFEntry 14 }
    --1.3.6.1.4.1.3052.10.2.12.12.7.1.14

acpmTPFSysrepEnable OBJECT-TYPE
    SYNTAX DisplayString
    MAX-ACCESS read-write
    STATUS current
    DESCRIPTION
        "System reporting enable."
    ::= { acpmTPFEntry 15 }
    --1.3.6.1.4.1.3052.10.2.12.12.7.1.15

acpmTPFSysrepThreshold OBJECT-TYPE
    SYNTAX DisplayString
    MAX-ACCESS read-write
    STATUS current
    DESCRIPTION
        "System reporting threshold."
    ::= { acpmTPFEntry 16 }
    --1.3.6.1.4.1.3052.10.2.12.12.7.1.16

acpmTPFSysrepLimit OBJECT-TYPE
    SYNTAX Integer32
    MAX-ACCESS read-write
    STATUS current
    DESCRIPTION
        "System reporting limit."
    ::= { acpmTPFEntry 17 }
    --1.3.6.1.4.1.3052.10.2.12.12.7.1.17



--***************************************************************************************
--Reset Event Section   2.12.16
--***************************************************************************************


evResetEnable OBJECT-TYPE
    SYNTAX DisplayString
    MAX-ACCESS read-write
    STATUS current
    DESCRIPTION
        "Enable/disable reset event.  This event is triggered when the unit
        finishes booting."
    ::= { evReset 1 }
    --1.3.6.1.4.1.3052.10.2.12.16.1

evResetDelay OBJECT-TYPE
    SYNTAX Integer32 (0..3600)
    MAX-ACCESS read-write
    STATUS current
    DESCRIPTION
        "Number of seconds to wait after unit finishes booting before triggering
        the reset event."
    ::= { evReset 2 }
    --1.3.6.1.4.1.3052.10.2.12.16.2

evResetActions OBJECT-TYPE
    SYNTAX DisplayString
    MAX-ACCESS read-write
    STATUS current
    DESCRIPTION
        "Actions for reset event."
    ::= { evReset 3 }
    --1.3.6.1.4.1.3052.10.2.12.16.3

evResetMessage OBJECT-TYPE
    SYNTAX DisplayString
    MAX-ACCESS read-write
    STATUS current
    DESCRIPTION
        "Message for reset event."
    ::= { evReset 4 }
    --1.3.6.1.4.1.3052.10.2.12.16.4

evResetTrapnum OBJECT-TYPE
    SYNTAX Integer32 (543..1199)
    MAX-ACCESS read-write
    STATUS current
    DESCRIPTION
        "Trap number for reset event."
    ::= { evReset 5 }
    --1.3.6.1.4.1.3052.10.2.12.16.5

evResetClass OBJECT-TYPE
    SYNTAX DisplayString
    MAX-ACCESS read-write
    STATUS current
    DESCRIPTION
        "Class (severity) for reset event."
    ::= { evReset 6 }
    --1.3.6.1.4.1.3052.10.2.12.16.6


--***************************************************************************************
--Global Event Section   2.12.18
--***************************************************************************************

evGlobalActions OBJECT-TYPE
    SYNTAX DisplayString
    MAX-ACCESS read-write
    STATUS current
    DESCRIPTION
        "Global event actions."
    ::= { evGlobal 2 }
    --1.3.6.1.4.1.3052.10.2.12.18.2

evGlobalTrapnum OBJECT-TYPE
    SYNTAX Integer32 (0..1199)
    MAX-ACCESS read-write
    STATUS current
    DESCRIPTION
        "Global trap number."
    ::= { evGlobal 3 }
    --1.3.6.1.4.1.3052.10.2.12.18.3


--***************************************************************************************
--HVAC Configuration Section   2.12.19
--***************************************************************************************
--***************************************************************************************
--BARD HVAC Configuration Section   2.12.19.2
--***************************************************************************************

evHVACBardIPAddress OBJECT-TYPE
    SYNTAX IpAddress
    MAX-ACCESS read-write
    STATUS current
    DESCRIPTION
        "IP address of the Bard HVAC controller."
    ::= { evHVACBardLocal 1 }
    --1.3.6.1.4.1.3052.10.2.12.19.2.1.1

evHVACBardPort OBJECT-TYPE
    SYNTAX Integer32
    MAX-ACCESS read-write
    STATUS current
    DESCRIPTION
        "TCP port of the Bard HVAC controller interface."
    ::= { evHVACBardLocal 2 }
    --1.3.6.1.4.1.3052.10.2.12.19.2.1.2

evHVACBardTimeout OBJECT-TYPE
    SYNTAX Integer32
    MAX-ACCESS read-write
    STATUS current
    DESCRIPTION
        "Seconds to wait for a response from the Bard HVAC controller."
    ::= { evHVACBardLocal 3 }
    --1.3.6.1.4.1.3052.10.2.12.19.2.1.3

evHVACBardXMLStatus OBJECT-TYPE
    SYNTAX DisplayString
    MAX-ACCESS read-write
    STATUS current
    DESCRIPTION
        "XML status page of the Bard HVAC controller."
    ::= { evHVACBardLocal 4 }
    --1.3.6.1.4.1.3052.10.2.12.19.2.1.4

evHVACBardXMLSettings OBJECT-TYPE
    SYNTAX DisplayString
    MAX-ACCESS read-write
    STATUS current
    DESCRIPTION
        "XML settings page of the Bard HVAC controller."
    ::= { evHVACBardLocal 5 }
    --1.3.6.1.4.1.3052.10.2.12.19.2.1.5

evHVACBardWebSettingsHTML OBJECT-TYPE
    SYNTAX DisplayString
    MAX-ACCESS read-write
    STATUS current
    DESCRIPTION
        "Web settings page of the Bard HVAC controller."
    ::= { evHVACBardLocal 6 }
    --1.3.6.1.4.1.3052.10.2.12.19.2.1.6

evHVACBardAlarmEnable OBJECT-TYPE
    SYNTAX DisplayString
    MAX-ACCESS read-write
    STATUS current
    DESCRIPTION
        "Enable/disable the Bard HVAC Alarm event."
    ::= { evHVACBardAlarm 1 }
    --1.3.6.1.4.1.3052.10.2.12.19.2.1.7.1

evHVACBardAlarmActions OBJECT-TYPE
    SYNTAX DisplayString
    MAX-ACCESS read-write
    STATUS current
    DESCRIPTION
        "Actions for the Bard HVAC Alarm event."
    ::= { evHVACBardAlarm 2 }
    --1.3.6.1.4.1.3052.10.2.12.19.2.1.7.2

evHVACBardAlarmTrapnum OBJECT-TYPE
    SYNTAX Integer32
    MAX-ACCESS read-write
    STATUS current
    DESCRIPTION
        "Trap number for the Bard HVAC Alarm event."
    ::= { evHVACBardAlarm 3 }
    --1.3.6.1.4.1.3052.10.2.12.19.2.1.7.3

evHVACBardAlarmClass OBJECT-TYPE
    SYNTAX DisplayString
    MAX-ACCESS read-write
    STATUS current
    DESCRIPTION
        "Class (severity) for the Bard HVAC Alarm event."
    ::= { evHVACBardAlarm 4 }
    --1.3.6.1.4.1.3052.10.2.12.19.2.1.7.4

evHVACBardAlarmNormalActions OBJECT-TYPE
    SYNTAX DisplayString
    MAX-ACCESS read-write
    STATUS current
    DESCRIPTION
        "Actions for the Bard HVAC Alarm Return to Normal event."
    ::= { evHVACBardAlarm 5 }
    --1.3.6.1.4.1.3052.10.2.12.19.2.1.7.5

evHVACBardAlarmNormalTrapnum OBJECT-TYPE
    SYNTAX Integer32
    MAX-ACCESS read-write
    STATUS current
    DESCRIPTION
        "Trap number for the Bard HVAC Alarm Return to Normal event."
    ::= { evHVACBardAlarm 6 }
    --1.3.6.1.4.1.3052.10.2.12.19.2.1.7.6

evHVACBardAlarmNormalClass OBJECT-TYPE
    SYNTAX DisplayString
    MAX-ACCESS read-write
    STATUS current
    DESCRIPTION
        "Class (severity) for the Bard HVAC Alarm Return to Normal event."
    ::= { evHVACBardAlarm 7 }
    --1.3.6.1.4.1.3052.10.2.12.19.2.1.7.7

evHVACBardReset OBJECT-TYPE
    SYNTAX Integer32
    MAX-ACCESS read-write
    STATUS current
    DESCRIPTION
        "Set to any value to reset the Bard HVAC controller. Always reads zero."
    ::= { evHVACBardLocal 8 }
    --1.3.6.1.4.1.3052.10.2.12.19.2.1.8

evHVACBardDefault OBJECT-TYPE
    SYNTAX Integer32
    MAX-ACCESS read-write
    STATUS current
    DESCRIPTION
        "Set to any value to restore default settings on the Bard HVAC controller. Always reads zero."
    ::= { evHVACBardLocal 9 }
    --1.3.6.1.4.1.3052.10.2.12.19.2.1.9 

evHVACBardTempScale OBJECT-TYPE
    SYNTAX DisplayString
    MAX-ACCESS read-write
    STATUS current
    DESCRIPTION
        "Scale used, Celsius or Fahrenheit (C or F)."
    ::= { evHVACBardSynchronized 1 }
    --1.3.6.1.4.1.3052.10.2.12.19.2.2.1

evHVACBardCoolThreshold OBJECT-TYPE
    SYNTAX DisplayString
    MAX-ACCESS read-write
    STATUS current
    DESCRIPTION
        "Cooling threshold to turn on HVAC cooling elements (economizer/compressor)."
    ::= { evHVACBardSynchronized 2 }
    --1.3.6.1.4.1.3052.10.2.12.19.2.2.2

evHVACBardCoolThresholdState OBJECT-TYPE
    SYNTAX DisplayString
    MAX-ACCESS read-only
    STATUS current
    DESCRIPTION
        "Synchronization status of previous object: ERROR (with possible description), PENDING, or OK."
    ::= { evHVACBardSynchronized 3 }
    --1.3.6.1.4.1.3052.10.2.12.19.2.2.3

evHVACBardHeatThreshold OBJECT-TYPE
    SYNTAX DisplayString
    MAX-ACCESS read-write
    STATUS current
    DESCRIPTION
        "Heating threshold to turn on HVAC heating elements (economizer/compressor)."
    ::= { evHVACBardSynchronized 4 }
    --1.3.6.1.4.1.3052.10.2.12.19.2.2.4

evHVACBardHeatDiff OBJECT-TYPE
    SYNTAX DisplayString
    MAX-ACCESS read-write
    STATUS current
    DESCRIPTION
        "Heating differential to turn on HVAC heating elements. The heating threshold
        is calculated by subtracting this number from the current cool threshold."
    ::= { evHVACBardSynchronized 5 }
    --1.3.6.1.4.1.3052.10.2.12.19.2.2.5

evHVACBardHeatDiffState OBJECT-TYPE
    SYNTAX DisplayString
    MAX-ACCESS read-only
    STATUS current
    DESCRIPTION
        "Synchronization status of previous object: ERROR (with possible description), PENDING, or OK."
    ::= { evHVACBardSynchronized 6 }
    --1.3.6.1.4.1.3052.10.2.12.19.2.2.6

evHVACBardBlower OBJECT-TYPE
    SYNTAX DisplayString
    MAX-ACCESS read-write
    STATUS current
    DESCRIPTION
        "Continuous blower operation enable."
    ::= { evHVACBardSynchronized 7 }
    --1.3.6.1.4.1.3052.10.2.12.19.2.2.7

evHVACBardBlowerState OBJECT-TYPE
    SYNTAX DisplayString
    MAX-ACCESS read-only
    STATUS current
    DESCRIPTION
        "Synchronization status of previous object: ERROR (with possible description), PENDING, or OK."
    ::= { evHVACBardSynchronized 8 }
    --1.3.6.1.4.1.3052.10.2.12.19.2.2.8

evHVACBardAlternate OBJECT-TYPE
    SYNTAX DisplayString
    MAX-ACCESS read-write
    STATUS current
    DESCRIPTION
        "Alternate lead-lag sequence for the economizer."
    ::= { evHVACBardSynchronized 9 }
    --1.3.6.1.4.1.3052.10.2.12.19.2.2.9

evHVACBardAlternateState OBJECT-TYPE
    SYNTAX DisplayString
    MAX-ACCESS read-only
    STATUS current
    DESCRIPTION
        "Synchronization status of previous object: ERROR (with possible description), PENDING, or OK."
    ::= { evHVACBardSynchronized 10 }
    --1.3.6.1.4.1.3052.10.2.12.19.2.2.10

evHVACBardChangeover OBJECT-TYPE
    SYNTAX DisplayString
    MAX-ACCESS read-write
    STATUS current
    DESCRIPTION
        "Lead-lag changeover time in days."
    ::= { evHVACBardSynchronized 11 }
    --1.3.6.1.4.1.3052.10.2.12.19.2.2.11

evHVACBardChangeoverState OBJECT-TYPE
    SYNTAX DisplayString
    MAX-ACCESS read-only
    STATUS current
    DESCRIPTION
        "Synchronization status of previous object: ERROR (with possible description), PENDING, or OK."
    ::= { evHVACBardSynchronized 12 }
    --1.3.6.1.4.1.3052.10.2.12.19.2.2.12

evHVACBardBlowDiff OBJECT-TYPE
    SYNTAX DisplayString
    MAX-ACCESS read-write
    STATUS current
    DESCRIPTION
        "Enable to run blowers if two sensors have a difference of 5 F or greater."
    ::= { evHVACBardSynchronized 13 }
    --1.3.6.1.4.1.3052.10.2.12.19.2.2.13

evHVACBardBlowDiffState OBJECT-TYPE
    SYNTAX DisplayString
    MAX-ACCESS read-only
    STATUS current
    DESCRIPTION
        "Synchronization status of previous object: ERROR (with possible description), PENDING, or OK."
    ::= { evHVACBardSynchronized 14 }
    --1.3.6.1.4.1.3052.10.2.12.19.2.2.14

evHVACBardOffDelay OBJECT-TYPE
    SYNTAX DisplayString
    MAX-ACCESS read-write
    STATUS current
    DESCRIPTION
        "3 minute lead/4 minute lag unit off delay enable."
    ::= { evHVACBardSynchronized 15 }
    --1.3.6.1.4.1.3052.10.2.12.19.2.2.15

evHVACBardOffDelayState OBJECT-TYPE
    SYNTAX DisplayString
    MAX-ACCESS read-only
    STATUS current
    DESCRIPTION
        "Synchronization status of previous object: ERROR (with possible description), PENDING, or OK."
    ::= { evHVACBardSynchronized 16 }
    --1.3.6.1.4.1.3052.10.2.12.19.2.2.16

evHVACBardRunMin OBJECT-TYPE
    SYNTAX DisplayString
    MAX-ACCESS read-write
    STATUS current
    DESCRIPTION
        "Run the compressor for at least 3 minutes before shutting off enable."
    ::= { evHVACBardSynchronized 17 }
    --1.3.6.1.4.1.3052.10.2.12.19.2.2.17

evHVACBardRunMinState OBJECT-TYPE
    SYNTAX DisplayString
    MAX-ACCESS read-only
    STATUS current
    DESCRIPTION
        "Synchronization status of previous object: ERROR (with possible description), PENDING, or OK."
    ::= { evHVACBardSynchronized 18 }
    --1.3.6.1.4.1.3052.10.2.12.19.2.2.18

evHVACBardStage1Diff OBJECT-TYPE
    SYNTAX DisplayString
    MAX-ACCESS read-write
    STATUS current
    DESCRIPTION
        "Temperature differential between stages 1 and 2."
    ::= { evHVACBardDiff 1 }
    --1.3.6.1.4.1.3052.10.2.12.19.2.2.19.1

evHVACBardStage1DiffState OBJECT-TYPE
    SYNTAX DisplayString
    MAX-ACCESS read-only
    STATUS current
    DESCRIPTION
        "Synchronization status of previous object: ERROR (with possible description), PENDING, or OK."
    ::= { evHVACBardDiff 2 }
    --1.3.6.1.4.1.3052.10.2.12.19.2.2.19.2

evHVACBardStage2Diff OBJECT-TYPE
    SYNTAX DisplayString
    MAX-ACCESS read-write
    STATUS current
    DESCRIPTION
        "Temperature differential between stages 2 and 3."
    ::= { evHVACBardDiff 3 }
    --1.3.6.1.4.1.3052.10.2.12.19.2.2.19.3

evHVACBardStage2DiffState OBJECT-TYPE
    SYNTAX DisplayString
    MAX-ACCESS read-only
    STATUS current
    DESCRIPTION
        "Synchronization status of previous object: ERROR (with possible description), PENDING, or OK."
    ::= { evHVACBardDiff 4 }
    --1.3.6.1.4.1.3052.10.2.12.19.2.2.19.4

evHVACBardStage3Diff OBJECT-TYPE
    SYNTAX DisplayString
    MAX-ACCESS read-write
    STATUS current
    DESCRIPTION
        "Temperature differential between stages 3 and 4."
    ::= { evHVACBardDiff 5 }
    --1.3.6.1.4.1.3052.10.2.12.19.2.2.19.5

evHVACBardStage3DiffState OBJECT-TYPE
    SYNTAX DisplayString
    MAX-ACCESS read-only
    STATUS current
    DESCRIPTION
        "Synchronization status of previous object: ERROR (with possible description), PENDING, or OK."
    ::= { evHVACBardDiff 6 }
    --1.3.6.1.4.1.3052.10.2.12.19.2.2.19.6

evHVACBardCoolDisableDb OBJECT-TYPE
    SYNTAX DisplayString
    MAX-ACCESS read-write
    STATUS current
    DESCRIPTION
        "Cooling disable deadband."
    ::= { evHVACBardSynchronized 20 }
    --1.3.6.1.4.1.3052.10.2.12.19.2.2.20

evHVACBardCoolDisableDbState OBJECT-TYPE
    SYNTAX DisplayString
    MAX-ACCESS read-only
    STATUS current
    DESCRIPTION
        "Synchronization status of previous object: ERROR (with possible description), PENDING, or OK."
    ::= { evHVACBardSynchronized 21 }
    --1.3.6.1.4.1.3052.10.2.12.19.2.2.21

evHVACBardCoolEnableDb OBJECT-TYPE
    SYNTAX DisplayString
    MAX-ACCESS read-write
    STATUS current
    DESCRIPTION
        "Cooling enable deadband."
    ::= { evHVACBardSynchronized 22 }
    --1.3.6.1.4.1.3052.10.2.12.19.2.2.22

evHVACBardCoolEnableDbState OBJECT-TYPE
    SYNTAX DisplayString
    MAX-ACCESS read-only
    STATUS current
    DESCRIPTION
        "Synchronization status of previous object: ERROR (with possible description), PENDING, or OK."
    ::= { evHVACBardSynchronized 23 }
    --1.3.6.1.4.1.3052.10.2.12.19.2.2.23

evHVACBardHeatDb OBJECT-TYPE
    SYNTAX DisplayString
    MAX-ACCESS read-write
    STATUS current
    DESCRIPTION
        "Heating deadband."
    ::= { evHVACBardSynchronized 24 }
    --1.3.6.1.4.1.3052.10.2.12.19.2.2.24

evHVACBardHeatDbState OBJECT-TYPE
    SYNTAX DisplayString
    MAX-ACCESS read-only
    STATUS current
    DESCRIPTION
        "Synchronization status of previous object: ERROR (with possible description), PENDING, or OK."
    ::= { evHVACBardSynchronized 25 }
    --1.3.6.1.4.1.3052.10.2.12.19.2.2.25

evHVACBardHeatPump OBJECT-TYPE
    SYNTAX DisplayString
    MAX-ACCESS read-write
    STATUS current
    DESCRIPTION
        "Heat pump logic enable."
    ::= { evHVACBardSynchronized 26 }
    --1.3.6.1.4.1.3052.10.2.12.19.2.2.26

evHVACBardHeatPumpState OBJECT-TYPE
    SYNTAX DisplayString
    MAX-ACCESS read-only
    STATUS current
    DESCRIPTION
        "Synchronization status of previous object: ERROR (with possible description), PENDING, or OK."
    ::= { evHVACBardSynchronized 27 }
    --1.3.6.1.4.1.3052.10.2.12.19.2.2.27

evHVACBardCompressors OBJECT-TYPE
    SYNTAX DisplayString
    MAX-ACCESS read-write
    STATUS current
    DESCRIPTION
        "Synchronization status of previous object: ERROR (with possible description), PENDING, or OK."
    ::= { evHVACBardSynchronized 28 }
    --1.3.6.1.4.1.3052.10.2.12.19.2.2.28

evHVACBardCompressorsState OBJECT-TYPE
    SYNTAX DisplayString
    MAX-ACCESS read-only
    STATUS current
    DESCRIPTION
        "Synchronization status of previous object: ERROR (with possible description), PENDING, or OK."
    ::= { evHVACBardSynchronized 29 }
    --1.3.6.1.4.1.3052.10.2.12.19.2.2.29

evHVACBardEconomizer OBJECT-TYPE
    SYNTAX DisplayString
    MAX-ACCESS read-write
    STATUS current
    DESCRIPTION
        "Synchronization status of previous object: ERROR (with possible description), PENDING, or OK."
    ::= { evHVACBardSynchronized 30 }
    --1.3.6.1.4.1.3052.10.2.12.19.2.2.30

evHVACBardEconomizerState OBJECT-TYPE
    SYNTAX DisplayString
    MAX-ACCESS read-only
    STATUS current
    DESCRIPTION
        "Synchronization status of previous object: ERROR (with possible description), PENDING, or OK."
    ::= { evHVACBardSynchronized 31 }
    --1.3.6.1.4.1.3052.10.2.12.19.2.2.31

evHVACBardTempLowValue OBJECT-TYPE
    SYNTAX DisplayString
    MAX-ACCESS read-write
    STATUS current
    DESCRIPTION
        "Low alarm for temperature."
    ::= { evHVACBardTemp 1 }
    --1.3.6.1.4.1.3052.10.2.12.19.2.2.32.1

evHVACBardTempLowValueState OBJECT-TYPE
    SYNTAX DisplayString
    MAX-ACCESS read-only
    STATUS current
    DESCRIPTION
        "Synchronization status of previous object: ERROR (with possible description), PENDING, or OK."
    ::= { evHVACBardTemp 2 }
    --1.3.6.1.4.1.3052.10.2.12.19.2.2.32.2

evHVACBardTempHighValue OBJECT-TYPE
    SYNTAX DisplayString
    MAX-ACCESS read-write
    STATUS current
    DESCRIPTION
        "High alarm for temperature."
    ::= { evHVACBardTemp 3 }
    --1.3.6.1.4.1.3052.10.2.12.19.2.2.32.3

evHVACBardTempHighValueState OBJECT-TYPE
    SYNTAX DisplayString
    MAX-ACCESS read-only
    STATUS current
    DESCRIPTION
        "Synchronization status of previous object: ERROR (with possible description), PENDING, or OK."
    ::= { evHVACBardTemp 4 }
    --1.3.6.1.4.1.3052.10.2.12.19.2.2.32.4

evHVACBardTempVHighValue OBJECT-TYPE
    SYNTAX DisplayString
    MAX-ACCESS read-write
    STATUS current
    DESCRIPTION
        "Very high alarm for temperature."
    ::= { evHVACBardTemp 5 }
    --1.3.6.1.4.1.3052.10.2.12.19.2.2.32.5

evHVACBardTempVHighValueState OBJECT-TYPE
    SYNTAX DisplayString
    MAX-ACCESS read-only
    STATUS current
    DESCRIPTION
        "Synchronization status of previous object: ERROR (with possible description), PENDING, or OK."
    ::= { evHVACBardTemp 6 }
    --1.3.6.1.4.1.3052.10.2.12.19.2.2.32.6

evHVACBardOverride OBJECT-TYPE
    SYNTAX DisplayString
    MAX-ACCESS read-write
    STATUS current
    DESCRIPTION
        "The HVAC controller override."
    ::= { evHVACBardSynchronized 33 }
    --1.3.6.1.4.1.3052.10.2.12.19.2.2.33

evHVACBardOverrideState OBJECT-TYPE
    SYNTAX DisplayString
    MAX-ACCESS read-only
    STATUS current
    DESCRIPTION
        "Synchronization status of previous object: ERROR (with possible description), PENDING, or OK."
    ::= { evHVACBardSynchronized 34 }
    --1.3.6.1.4.1.3052.10.2.12.19.2.2.34

evHVACBardLock OBJECT-TYPE
    SYNTAX DisplayString
    MAX-ACCESS read-write
    STATUS current
    DESCRIPTION
        "Enable the external controller lock."
    ::= { evHVACBardSynchronized 35 }
    --1.3.6.1.4.1.3052.10.2.12.19.2.2.35

evHVACBardLockState OBJECT-TYPE
    SYNTAX DisplayString
    MAX-ACCESS read-only
    STATUS current
    DESCRIPTION
        "Synchronization status of previous object: ERROR (with possible description), PENDING, or OK."
    ::= { evHVACBardSynchronized 36 }
    --1.3.6.1.4.1.3052.10.2.12.19.2.2.36

evHVACBardLeadUnit OBJECT-TYPE
    SYNTAX DisplayString
    MAX-ACCESS read-write
    STATUS current
    DESCRIPTION
        "Which HVAC unit is currently the lead unit."
    ::= { evHVACBardSynchronized 37 }
    --1.3.6.1.4.1.3052.10.2.12.19.2.2.37

evHVACBardLeadUnitState OBJECT-TYPE
    SYNTAX DisplayString
    MAX-ACCESS read-only
    STATUS current
    DESCRIPTION
        "Synchronization status of previous object: ERROR (with possible description), PENDING, or OK."
    ::= { evHVACBardSynchronized 38 }
    --1.3.6.1.4.1.3052.10.2.12.19.2.2.38

evHVACBardComfort OBJECT-TYPE
    SYNTAX DisplayString
    MAX-ACCESS read-write
    STATUS current
    DESCRIPTION
        "Enable comfort mode."
    ::= { evHVACBardSynchronized 39 }
    --1.3.6.1.4.1.3052.10.2.12.19.2.2.39

evHVACBardComfortState OBJECT-TYPE
    SYNTAX DisplayString
    MAX-ACCESS read-only
    STATUS current
    DESCRIPTION
        "Synchronization status of previous object: ERROR (with possible description), PENDING, or OK."
    ::= { evHVACBardSynchronized 40 }
    --1.3.6.1.4.1.3052.10.2.12.19.2.2.40


--***************************************************************************************
--Asentria HVAC Configuration Section   2.12.19.3
--***************************************************************************************

evHVACAsentriaSensorListTable OBJECT-TYPE
    SYNTAX SEQUENCE OF HVACAsentriaSensorList
    MAX-ACCESS not-accessible
    STATUS current
    DESCRIPTION
        "Asentria HVAC temperature/humidity sensor list table"
    ::= { evHVACAsentria 1 }
    --1.3.6.1.4.1.3052.10.2.12.19.3.1

evHVACAsentriaSensorListEntry OBJECT-TYPE
    SYNTAX HVACAsentriaSensorList
    MAX-ACCESS not-accessible
    STATUS current
    DESCRIPTION
        "Asentria HVAC temperature/humidity sensor list table entry"
    INDEX { evHVACAsentriaSensorListIndex }
    ::= { evHVACAsentriaSensorListTable 1 }
    --1.3.6.1.4.1.3052.10.2.12.19.3.1.1

evHVACAsentriaSensorListIndex OBJECT-TYPE
    SYNTAX Integer32 (1..12)
    MAX-ACCESS read-only
    STATUS current
    DESCRIPTION
        "Index for Asentria HVAC temperature/humidity sensor"
    ::= { evHVACAsentriaSensorListEntry 1 }
    --1.3.6.1.4.1.3052.10.2.12.19.3.1.1.1

evHVACAsentriaSensorListES OBJECT-TYPE
    SYNTAX DisplayString
    MAX-ACCESS read-write
    STATUS current
    DESCRIPTION
        "Asentria HVAC temperature/humidity sensor EventSensor number"
    ::= { evHVACAsentriaSensorListEntry 2 }
    --1.3.6.1.4.1.3052.10.2.12.19.3.1.1.2

evHVACAsentriaSensorListPT OBJECT-TYPE
    SYNTAX Integer32 (1..64)
    MAX-ACCESS read-write
    STATUS current
    DESCRIPTION
        "Asentria HVAC temperature/humidity sensor point"
    ::= { evHVACAsentriaSensorListEntry 3 }
    --1.3.6.1.4.1.3052.10.2.12.19.3.1.1.3

evHVACAsentriaSensorListType OBJECT-TYPE
    SYNTAX DisplayString
    MAX-ACCESS read-write
    STATUS current
    DESCRIPTION
        "Asentria HVAC temperature/humidity sensor type"
    ::= { evHVACAsentriaSensorListEntry 4 }
    --1.3.6.1.4.1.3052.10.2.12.19.3.1.1.4

evHVACAsentriaSensorListLoc OBJECT-TYPE
    SYNTAX DisplayString
    MAX-ACCESS read-write
    STATUS current
    DESCRIPTION
        "Asentria HVAC temperature/humidity sensor location"
    ::= { evHVACAsentriaSensorListEntry 5 }
    --1.3.6.1.4.1.3052.10.2.12.19.3.1.1.5

evHVACAsentriaOverride OBJECT-TYPE
    SYNTAX DisplayString
    MAX-ACCESS read-write
    STATUS current
    DESCRIPTION
        "Asentria HVAC controller override"
    ::= { evHVACAsentria 2 }
    --1.3.6.1.4.1.3052.10.2.12.19.3.2

evHVACAsentriaSchedule OBJECT-TYPE
    SYNTAX DisplayString
    MAX-ACCESS read-write
    STATUS current
    DESCRIPTION
        "Asentria HVAC unit primary/lead swap schedule"
    ::= { evHVACAsentria 3 }
    --1.3.6.1.4.1.3052.10.2.12.19.3.3

evHVACAsentriaPrimary OBJECT-TYPE
    SYNTAX Integer32
    MAX-ACCESS read-write
    STATUS current
    DESCRIPTION
        "Asentria HVAC primary/lead unit to operate"
    ::= { evHVACAsentria 4 }
    --1.3.6.1.4.1.3052.10.2.12.19.3.4

evHVACAsentriaMethod OBJECT-TYPE
    SYNTAX DisplayString
    MAX-ACCESS read-write
    STATUS current
    DESCRIPTION
        "Asentria HVAC controller temperature/humidity calculation 
        method"
    ::= { evHVACAsentria 5 }
    --1.3.6.1.4.1.3052.10.2.12.19.3.5

evHVACAsentriaAlarmLagNormEnable OBJECT-TYPE
    SYNTAX DisplayString
    MAX-ACCESS read-write
    STATUS current
    DESCRIPTION
        "Asentria HVAC enable for normal/idle alarm notification on 
        lag unit"
    ::= { evHVACAsentriaAlarm 1 }
    --1.3.6.1.4.1.3052.10.2.12.19.3.6.1

evHVACAsentriaAlarmLagNormActions OBJECT-TYPE
    SYNTAX DisplayString
    MAX-ACCESS read-write
    STATUS current
    DESCRIPTION
        "Asentria HVAC actions to perform for normal/idle alarm 
        notification on lag unit"
    ::= { evHVACAsentriaAlarm 2 }
    --1.3.6.1.4.1.3052.10.2.12.19.3.6.2

evHVACAsentriaAlarmLagNormTrapNum OBJECT-TYPE
    SYNTAX Integer32 (545..1199)
    MAX-ACCESS read-write
    STATUS current
    DESCRIPTION
        "Asentria HVAC trap number for normal/idle alarm notification 
        on lag unit"
    ::= { evHVACAsentriaAlarm 3 }
    --1.3.6.1.4.1.3052.10.2.12.19.3.6.3

evHVACAsentriaAlarmLagNormClass OBJECT-TYPE
    SYNTAX DisplayString
    MAX-ACCESS read-write
    STATUS current
    DESCRIPTION
        "Asentria HVAC alarm class for normal/idle alarm notification 
        on lag unit"
    ::= { evHVACAsentriaAlarm 4 }
    --1.3.6.1.4.1.3052.10.2.12.19.3.6.4

evHVACAsentriaAlarmLagVentEnable OBJECT-TYPE
    SYNTAX DisplayString
    MAX-ACCESS read-write
    STATUS current
    DESCRIPTION
        "Asentria HVAC enable for venting alarm notification on lag 
        unit"
    ::= { evHVACAsentriaAlarm 5 }
    --1.3.6.1.4.1.3052.10.2.12.19.3.6.5

evHVACAsentriaAlarmLagVentActions OBJECT-TYPE
    SYNTAX DisplayString
    MAX-ACCESS read-write
    STATUS current
    DESCRIPTION
        "Asentria HVAC actions to perform for venting alarm 
        notification on lag unit"
    ::= { evHVACAsentriaAlarm 6 }
    --1.3.6.1.4.1.3052.10.2.12.19.3.6.6

evHVACAsentriaAlarmLagVentTrapNum OBJECT-TYPE
    SYNTAX Integer32 (545..1199)
    MAX-ACCESS read-write
    STATUS current
    DESCRIPTION
        "Asentria HVAC trap number for venting alarm notification on 
        lag unit"
    ::= { evHVACAsentriaAlarm 7 }
    --1.3.6.1.4.1.3052.10.2.12.19.3.6.7

evHVACAsentriaAlarmLagVentClass OBJECT-TYPE
    SYNTAX DisplayString
    MAX-ACCESS read-write
    STATUS current
    DESCRIPTION
        "Asentria HVAC alarm class for venting alarm notification on 
        lag unit"
    ::= { evHVACAsentriaAlarm 8 }
    --1.3.6.1.4.1.3052.10.2.12.19.3.6.8

evHVACAsentriaAlarmLagCoolEnable OBJECT-TYPE
    SYNTAX DisplayString
    MAX-ACCESS read-write
    STATUS current
    DESCRIPTION
        "Asentria HVAC enable for cooling alarm notification on lag 
        unit"
    ::= { evHVACAsentriaAlarm 9 }
    --1.3.6.1.4.1.3052.10.2.12.19.3.6.9

evHVACAsentriaAlarmLagCoolActions OBJECT-TYPE
    SYNTAX DisplayString
    MAX-ACCESS read-write
    STATUS current
    DESCRIPTION
        "Asentria HVAC actions to perform for cooling alarm 
        notification on lag unit"
    ::= { evHVACAsentriaAlarm 10 }
    --1.3.6.1.4.1.3052.10.2.12.19.3.6.10

evHVACAsentriaAlarmLagCoolTrapNum OBJECT-TYPE
    SYNTAX Integer32 (545..1199)
    MAX-ACCESS read-write
    STATUS current
    DESCRIPTION
        "Asentria HVAC trap number for cooling alarm notification on 
        lag unit"
    ::= { evHVACAsentriaAlarm 11 }
    --1.3.6.1.4.1.3052.10.2.12.19.3.6.11

evHVACAsentriaAlarmLagCoolClass OBJECT-TYPE
    SYNTAX DisplayString
    MAX-ACCESS read-write
    STATUS current
    DESCRIPTION
        "Asentria HVAC alarm class for cooling alarm notification on 
        lag unit"
    ::= { evHVACAsentriaAlarm 12 }
    --1.3.6.1.4.1.3052.10.2.12.19.3.6.12

evHVACAsentriaAlarmLagHeatEnable OBJECT-TYPE
    SYNTAX DisplayString
    MAX-ACCESS read-write
    STATUS current
    DESCRIPTION
        "Asentria HVAC enable for heating alarm notification on lag 
        unit"
    ::= { evHVACAsentriaAlarm 13 }
    --1.3.6.1.4.1.3052.10.2.12.19.3.6.13

evHVACAsentriaAlarmLagHeatActions OBJECT-TYPE
    SYNTAX DisplayString
    MAX-ACCESS read-write
    STATUS current
    DESCRIPTION
        "Asentria HVAC actions to perform for heating alarm 
        notification on lag unit"
    ::= { evHVACAsentriaAlarm 14 }
    --1.3.6.1.4.1.3052.10.2.12.19.3.6.14

evHVACAsentriaAlarmLagHeatTrapNum OBJECT-TYPE
    SYNTAX Integer32 (545..1199)
    MAX-ACCESS read-write
    STATUS current
    DESCRIPTION
        "Asentria HVAC trap number for heating alarm notification on 
        lag unit"
    ::= { evHVACAsentriaAlarm 15 }
    --1.3.6.1.4.1.3052.10.2.12.19.3.6.15

evHVACAsentriaAlarmLagHeatClass OBJECT-TYPE
    SYNTAX DisplayString
    MAX-ACCESS read-write
    STATUS current
    DESCRIPTION
        "Asentria HVAC alarm class for heating alarm notification on 
        lag unit"
    ::= { evHVACAsentriaAlarm 16 }
    --1.3.6.1.4.1.3052.10.2.12.19.3.6.16

evHVACAsentriaFireES OBJECT-TYPE
    SYNTAX DisplayString
    MAX-ACCESS read-write
    STATUS current
    DESCRIPTION
        "Asentria HVAC fire/smoke alarm EventSensor number"
    ::= { evHVACAsentriaFire 1 }
    --1.3.6.1.4.1.3052.10.2.12.19.3.7.1

evHVACAsentriaFirePT OBJECT-TYPE
    SYNTAX Integer32 (1..64)
    MAX-ACCESS read-write
    STATUS current
    DESCRIPTION
        "Asentria HVAC fire/smoke alarm point number"
    ::= { evHVACAsentriaFire 2 }
    --1.3.6.1.4.1.3052.10.2.12.19.3.7.2

evHVACAsentriaFireActions OBJECT-TYPE
    SYNTAX DisplayString
    MAX-ACCESS read-write
    STATUS current
    DESCRIPTION
        "Asentria HVAC actions to perform for fire/smoke alarm 
        notification"
    ::= { evHVACAsentriaFire 3 }
    --1.3.6.1.4.1.3052.10.2.12.19.3.7.3

evHVACAsentriaFireTrapnum OBJECT-TYPE
    SYNTAX Integer32 (545..1199)
    MAX-ACCESS read-write
    STATUS current
    DESCRIPTION
        "Asentria HVAC trap number for fire/smoke alarm notification"
    ::= { evHVACAsentriaFire 4 }
    --1.3.6.1.4.1.3052.10.2.12.19.3.7.4

evHVACAsentriaFireClass OBJECT-TYPE
    SYNTAX DisplayString
    MAX-ACCESS read-write
    STATUS current
    DESCRIPTION
        "Asentria HVAC alarm class for fire/smoke alarm notification"
    ::= { evHVACAsentriaFire 5 }
    --1.3.6.1.4.1.3052.10.2.12.19.3.7.5

evHVACAsentriaFireNormActions OBJECT-TYPE
    SYNTAX DisplayString
    MAX-ACCESS read-write
    STATUS current
    DESCRIPTION
        "Asentria HVAC return to normal actions to perform for 
        fire/smoke alarm notification"
    ::= { evHVACAsentriaFire 6 }
    --1.3.6.1.4.1.3052.10.2.12.19.3.7.6

evHVACAsentriaFireNormTrapNum OBJECT-TYPE
    SYNTAX Integer32 (545..1199)
    MAX-ACCESS read-write
    STATUS current
    DESCRIPTION
        "Asentria HVAC return to normal trap number for fire/smoke 
        alarm notification"
    ::= { evHVACAsentriaFire 7 }
    --1.3.6.1.4.1.3052.10.2.12.19.3.7.7

evHVACAsentriaFireNormClass OBJECT-TYPE
    SYNTAX DisplayString
    MAX-ACCESS read-write
    STATUS current
    DESCRIPTION
        "Asentria HVAC return to normal class for fire/smoke alarm 
        notification"
    ::= { evHVACAsentriaFire 8 }
    --1.3.6.1.4.1.3052.10.2.12.19.3.7.8

evHVACAsentriaUnitTable OBJECT-TYPE
    SYNTAX SEQUENCE OF HVACAsentriaUnit
    MAX-ACCESS not-accessible
    STATUS current
    DESCRIPTION
        "Asentria HVAC unit table"
    ::= { evHVACAsentria 8 }
    --1.3.6.1.4.1.3052.10.2.12.19.3.8

evHVACAsentriaUnitEntry OBJECT-TYPE
    SYNTAX HVACAsentriaUnit
    MAX-ACCESS not-accessible
    STATUS current
    DESCRIPTION
        "Asentria HVAC unit table entry"
    INDEX { evHVACAsentriaUnitIndex }
    ::= { evHVACAsentriaUnitTable 1 }
    --1.3.6.1.4.1.3052.10.2.12.19.3.8.1

evHVACAsentriaUnitIndex OBJECT-TYPE
    SYNTAX Integer32 (1..2)
    MAX-ACCESS read-only
    STATUS current
    DESCRIPTION
        "Index for Asentria HVAC unit"
    ::= { evHVACAsentriaUnitEntry 1 }
    --1.3.6.1.4.1.3052.10.2.12.19.3.8.1.1

evHVACAsentriaUnitEnable OBJECT-TYPE
    SYNTAX DisplayString
    MAX-ACCESS read-write
    STATUS current
    DESCRIPTION
        "Asentria HVAC unit enable"
    ::= { evHVACAsentriaUnitEntry 2 }
    --1.3.6.1.4.1.3052.10.2.12.19.3.8.1.2

evHVACAsentriaUnitFanRelayES OBJECT-TYPE
    SYNTAX DisplayString
    MAX-ACCESS read-write
    STATUS current
    DESCRIPTION
        "EventSensor number of relay to control the fan on Asentria
        HVAC controller"
    ::= { evHVACAsentriaUnitEntry 3 }
    --1.3.6.1.4.1.3052.10.2.12.19.3.8.1.3

evHVACAsentriaUnitFanRelayPT OBJECT-TYPE
    SYNTAX Integer32 (1..16)
    MAX-ACCESS read-write
    STATUS current
    DESCRIPTION
        "Point number of relay to control the fan on Asentria HVAC 
        controller"
    ::= { evHVACAsentriaUnitEntry 4 }
    --1.3.6.1.4.1.3052.10.2.12.19.3.8.1.4

evHVACAsentriaUnitVentRelayES OBJECT-TYPE
    SYNTAX DisplayString
    MAX-ACCESS read-write
    STATUS current
    DESCRIPTION
        "EventSensor number of relay to control the vent on Asentria
        HVAC controller"
    ::= { evHVACAsentriaUnitEntry 5 }
    --1.3.6.1.4.1.3052.10.2.12.19.3.8.1.5

evHVACAsentriaUnitVentRelayPT OBJECT-TYPE
    SYNTAX Integer32 (1..16)
    MAX-ACCESS read-write
    STATUS current
    DESCRIPTION
        "Point number of relay to control the vent on Asentria HVAC 
        controller"
    ::= { evHVACAsentriaUnitEntry 6 }
    --1.3.6.1.4.1.3052.10.2.12.19.3.8.1.6

evHVACAsentriaUnitTimereset OBJECT-TYPE
    SYNTAX Integer32
    MAX-ACCESS read-write
    STATUS current
    DESCRIPTION
        "Resets the time counter for Asentria HVAC unit"
    ::= { evHVACAsentriaUnitEntry 7 }
    --1.3.6.1.4.1.3052.10.2.12.19.3.8.1.7

evHVACAsentriaSeqTimereset OBJECT-TYPE
    SYNTAX Integer32
    MAX-ACCESS read-write
    STATUS current
    DESCRIPTION
        "Resets the time counter for Asentria HVAC sequence number"
    ::= { evHVACAsentriaUnitEntry 8 }
    --1.3.6.1.4.1.3052.10.2.12.19.3.8.1.8

evHVACAsentriaUnitStage1CoolES OBJECT-TYPE
    SYNTAX DisplayString
    MAX-ACCESS read-write
    STATUS current
    DESCRIPTION
        "EventSensor number of relay to control compressor stage 1 on 
        Asentria HVAC controller"
    ::= { evHVACAsentriaUnitEntry 20 }
    --1.3.6.1.4.1.3052.10.2.12.19.3.8.1.20

evHVACAsentriaUnitStage1CoolPT OBJECT-TYPE
    SYNTAX Integer32 (1..16)
    MAX-ACCESS read-write
    STATUS current
    DESCRIPTION
        "Point number of relay to control compressor stage 1 on 
        Asentria HVAC controller"
    ::= { evHVACAsentriaUnitEntry 21 }
    --1.3.6.1.4.1.3052.10.2.12.19.3.8.1.21

evHVACAsentriaUnitStage1HeatES OBJECT-TYPE
    SYNTAX DisplayString
    MAX-ACCESS read-write
    STATUS current
    DESCRIPTION
        "EventSensor number of relay to control heater stage 1 on 
        Asentria HVAC controller"
    ::= { evHVACAsentriaUnitEntry 22 }
    --1.3.6.1.4.1.3052.10.2.12.19.3.8.1.22

evHVACAsentriaUnitStage1HeatPT OBJECT-TYPE
    SYNTAX Integer32 (1..16)
    MAX-ACCESS read-write
    STATUS current
    DESCRIPTION
        "Point number of relay to control heater stage 1 on 
        Asentria HVAC controller"
    ::= { evHVACAsentriaUnitEntry 23 }
    --1.3.6.1.4.1.3052.10.2.12.19.3.8.1.23

evHVACAsentriaUnitStage2CoolES OBJECT-TYPE
    SYNTAX DisplayString
    MAX-ACCESS read-write
    STATUS current
    DESCRIPTION
        "EventSensor number of relay to control compressor stage 2 on 
        Asentria HVAC controller"
    ::= { evHVACAsentriaUnitEntry 30 }
    --1.3.6.1.4.1.3052.10.2.12.19.3.8.1.30

evHVACAsentriaUnitStage2CoolPT OBJECT-TYPE
    SYNTAX Integer32 (1..16)
    MAX-ACCESS read-write
    STATUS current
    DESCRIPTION
        "Point number of relay to control compressor stage 2 on 
        Asentria HVAC controller"
    ::= { evHVACAsentriaUnitEntry 31 }
    --1.3.6.1.4.1.3052.10.2.12.19.3.8.1.31

evHVACAsentriaUnitStage2HeatES OBJECT-TYPE
    SYNTAX DisplayString
    MAX-ACCESS read-write
    STATUS current
    DESCRIPTION
        "EventSensor number of relay to control heater stage 2 on 
        Asentria HVAC controller"
    ::= { evHVACAsentriaUnitEntry 32 }
    --1.3.6.1.4.1.3052.10.2.12.19.3.8.1.32

evHVACAsentriaUnitStage2HeatPT OBJECT-TYPE
    SYNTAX Integer32 (1..16)
    MAX-ACCESS read-write
    STATUS current
    DESCRIPTION
        "Point number of relay to control heater stage 2 on 
        Asentria HVAC controller"
    ::= { evHVACAsentriaUnitEntry 33 }
    --1.3.6.1.4.1.3052.10.2.12.19.3.8.1.33

evHVACAsentriaTempScale OBJECT-TYPE
    SYNTAX DisplayString
    MAX-ACCESS read-write
    STATUS current
    DESCRIPTION
        "Asentria HVAC controller temperature scale"
    ::= { evHVACAsentriaTemp 1 }
    --1.3.6.1.4.1.3052.10.2.12.19.3.9.1

evHVACAsentriaTempCoolThresh OBJECT-TYPE
    SYNTAX DisplayString
    MAX-ACCESS read-write
    STATUS current
    DESCRIPTION
        "Temperature above this threshold before cooling via Asentria 
        HVAC controller"
    ::= { evHVACAsentriaTemp 2 }
    --1.3.6.1.4.1.3052.10.2.12.19.3.9.2

evHVACAsentriaTempHeatThresh OBJECT-TYPE
    SYNTAX DisplayString
    MAX-ACCESS read-write
    STATUS current
    DESCRIPTION
        "Temperature below this threshold before heating via Asentria 
        HVAC controller"
    ::= { evHVACAsentriaTemp 3 }
    --1.3.6.1.4.1.3052.10.2.12.19.3.9.3

evHVACAsentriaTempEnable OBJECT-TYPE
    SYNTAX DisplayString
    MAX-ACCESS read-write
    STATUS current
    DESCRIPTION
        "Asentria HVAC temperature alarm enable"
    ::= { evHVACAsentriaTemp 4 }
    --1.3.6.1.4.1.3052.10.2.12.19.3.9.4

evHVACAsentriaTempEventDeadband OBJECT-TYPE
    SYNTAX DisplayString
    MAX-ACCESS read-write
    STATUS current
    DESCRIPTION
        "Asentria HVAC temperature alarm event deadband"
    ::= { evHVACAsentriaTemp 5 }
    --1.3.6.1.4.1.3052.10.2.12.19.3.9.5

evHVACAsentriaTempVLowValue OBJECT-TYPE
    SYNTAX DisplayString
    MAX-ACCESS read-write
    STATUS current
    DESCRIPTION
        "Asentria HVAC temperature alarm event very low value"
    ::= { evHVACAsentriaTemp 6 }
    --1.3.6.1.4.1.3052.10.2.12.19.3.9.6

evHVACAsentriaTempVLowActions OBJECT-TYPE
    SYNTAX DisplayString
    MAX-ACCESS read-write
    STATUS current
    DESCRIPTION
        "Asentria HVAC temperature alarm event very low actions"
    ::= { evHVACAsentriaTemp 7 }
    --1.3.6.1.4.1.3052.10.2.12.19.3.9.7

evHVACAsentriaTempVLowTrapNum OBJECT-TYPE
    SYNTAX Integer32 (545..1199)
    MAX-ACCESS read-write
    STATUS current
    DESCRIPTION
        "Asentria HVAC temperature alarm event very low trap number"
    ::= { evHVACAsentriaTemp 8 }
    --1.3.6.1.4.1.3052.10.2.12.19.3.9.8

evHVACAsentriaTempVLowClass OBJECT-TYPE
    SYNTAX DisplayString
    MAX-ACCESS read-write
    STATUS current
    DESCRIPTION
        "Asentria HVAC temperature alarm event very low class"
    ::= { evHVACAsentriaTemp 9 }
    --1.3.6.1.4.1.3052.10.2.12.19.3.9.9

evHVACAsentriaTempLowValue OBJECT-TYPE
    SYNTAX DisplayString
    MAX-ACCESS read-write
    STATUS current
    DESCRIPTION
        "Asentria HVAC temperature alarm event low value"
    ::= { evHVACAsentriaTemp 10 }
    --1.3.6.1.4.1.3052.10.2.12.19.3.9.10

evHVACAsentriaTempLowActions OBJECT-TYPE
    SYNTAX DisplayString
    MAX-ACCESS read-write
    STATUS current
    DESCRIPTION
        "Asentria HVAC temperature alarm event low actions"
    ::= { evHVACAsentriaTemp 11 }
    --1.3.6.1.4.1.3052.10.2.12.19.3.9.11

evHVACAsentriaTempLowTrapNum OBJECT-TYPE
    SYNTAX Integer32 (545..1199)
    MAX-ACCESS read-write
    STATUS current
    DESCRIPTION
        "Asentria HVAC temperature alarm event low trap number"
    ::= { evHVACAsentriaTemp 12 }
    --1.3.6.1.4.1.3052.10.2.12.19.3.9.12

evHVACAsentriaTempLowClass OBJECT-TYPE
    SYNTAX DisplayString
    MAX-ACCESS read-write
    STATUS current
    DESCRIPTION
        "Asentria HVAC temperature alarm event low class"
    ::= { evHVACAsentriaTemp 13 }
    --1.3.6.1.4.1.3052.10.2.12.19.3.9.13

evHVACAsentriaTempNormalActions OBJECT-TYPE
    SYNTAX DisplayString
    MAX-ACCESS read-write
    STATUS current
    DESCRIPTION
        "Asentria HVAC temperature alarm event return to normal 
        actions"
    ::= { evHVACAsentriaTemp 14 }
    --1.3.6.1.4.1.3052.10.2.12.19.3.9.14

evHVACAsentriaTempNormalTrapNum OBJECT-TYPE
    SYNTAX Integer32 (545..1199)
    MAX-ACCESS read-write
    STATUS current
    DESCRIPTION
        "Asentria HVAC temperature alarm event return to normal trap 
        number"
    ::= { evHVACAsentriaTemp 15 }
    --1.3.6.1.4.1.3052.10.2.12.19.3.9.15

evHVACAsentriaTempNormalClass OBJECT-TYPE
    SYNTAX DisplayString
    MAX-ACCESS read-write
    STATUS current
    DESCRIPTION
        "Asentria HVAC temperature alarm event return to normal class"
    ::= { evHVACAsentriaTemp 16 }
    --1.3.6.1.4.1.3052.10.2.12.19.3.9.16

evHVACAsentriaTempHighValue OBJECT-TYPE
    SYNTAX DisplayString
    MAX-ACCESS read-write
    STATUS current
    DESCRIPTION
        "Asentria HVAC temperature alarm event high value"
    ::= { evHVACAsentriaTemp 17 }
    --1.3.6.1.4.1.3052.10.2.12.19.3.9.17

evHVACAsentriaTempHighActions OBJECT-TYPE
    SYNTAX DisplayString
    MAX-ACCESS read-write
    STATUS current
    DESCRIPTION
        "Asentria HVAC temperature alarm event high actions"
    ::= { evHVACAsentriaTemp 18 }
    --1.3.6.1.4.1.3052.10.2.12.19.3.9.18

evHVACAsentriaTempHighTrapNum OBJECT-TYPE
    SYNTAX Integer32 (545..1199)
    MAX-ACCESS read-write
    STATUS current
    DESCRIPTION
        "Asentria HVAC temperature alarm event high trap number"
    ::= { evHVACAsentriaTemp 19 }
    --1.3.6.1.4.1.3052.10.2.12.19.3.9.19

evHVACAsentriaTempHighClass OBJECT-TYPE
    SYNTAX DisplayString
    MAX-ACCESS read-write
    STATUS current
    DESCRIPTION
        "Asentria HVAC temperature alarm event high class"
    ::= { evHVACAsentriaTemp 20 }
    --1.3.6.1.4.1.3052.10.2.12.19.3.9.20

evHVACAsentriaTempVHighValue OBJECT-TYPE
    SYNTAX DisplayString
    MAX-ACCESS read-write
    STATUS current
    DESCRIPTION
        "Asentria HVAC temperature alarm event very high value"
    ::= { evHVACAsentriaTemp 21 }
    --1.3.6.1.4.1.3052.10.2.12.19.3.9.21

evHVACAsentriaTempVHighActions OBJECT-TYPE
    SYNTAX DisplayString
    MAX-ACCESS read-write
    STATUS current
    DESCRIPTION
        "Asentria HVAC temperature alarm event very high actions"
    ::= { evHVACAsentriaTemp 22 }
    --1.3.6.1.4.1.3052.10.2.12.19.3.9.22

evHVACAsentriaTempVHighTrapNum OBJECT-TYPE
    SYNTAX Integer32 (545..1199)
    MAX-ACCESS read-write
    STATUS current
    DESCRIPTION
        "Asentria HVAC temperature alarm event very high trap number"
    ::= { evHVACAsentriaTemp 23 }
    --1.3.6.1.4.1.3052.10.2.12.19.3.9.23

evHVACAsentriaTempVHighClass OBJECT-TYPE
    SYNTAX DisplayString
    MAX-ACCESS read-write
    STATUS current
    DESCRIPTION
        "Asentria HVAC temperature alarm event very high class"
    ::= { evHVACAsentriaTemp 24 }
    --1.3.6.1.4.1.3052.10.2.12.19.3.9.24

evHVACAsentriaTempDeadband OBJECT-TYPE
    SYNTAX DisplayString
    MAX-ACCESS read-write
    STATUS current
    DESCRIPTION
        "Asentria HVAC temperature deadband before stopping current 
        state"
    ::= { evHVACAsentriaTemp 25 }
    --1.3.6.1.4.1.3052.10.2.12.19.3.9.25

evHVACAsentriaTempDifference OBJECT-TYPE
    SYNTAX DisplayString
    MAX-ACCESS read-write
    STATUS current
    DESCRIPTION
        "Asentria HVAC temperature step before changing states"
    ::= { evHVACAsentriaTemp 26 }
    --1.3.6.1.4.1.3052.10.2.12.19.3.9.26

evHVACAsentriaHumidInThresh OBJECT-TYPE
    SYNTAX Integer32 (0..100)
    MAX-ACCESS read-write
    STATUS current
    DESCRIPTION
        "Humidity above this threshold before cooling via Asentria 
        HVAC controller"
    ::= { evHVACAsentriaHumid 2 }
    --1.3.6.1.4.1.3052.10.2.12.19.3.9.2

evHVACAsentriaHumidOutThresh OBJECT-TYPE
    SYNTAX Integer32 (0..100)
    MAX-ACCESS read-write
    STATUS current
    DESCRIPTION
        "Humidity above this threshold before not allowing venting via 
        Asentria HVAC controller"
    ::= { evHVACAsentriaHumid 3 }
    --1.3.6.1.4.1.3052.10.2.12.19.3.9.3

evHVACAsentriaHumidEnable OBJECT-TYPE
    SYNTAX DisplayString
    MAX-ACCESS read-write
    STATUS current
    DESCRIPTION
        "Asentria HVAC humidity alarm enable"
    ::= { evHVACAsentriaHumid 4 }
    --1.3.6.1.4.1.3052.10.2.12.19.3.9.4

evHVACAsentriaHumidEventDeadband OBJECT-TYPE
    SYNTAX Integer32 (1..100)
    MAX-ACCESS read-write
    STATUS current
    DESCRIPTION
        "Asentria HVAC humidity alarm event deadband"
    ::= { evHVACAsentriaHumid 5 }
    --1.3.6.1.4.1.3052.10.2.12.19.3.9.5

evHVACAsentriaHumidVLowValue OBJECT-TYPE
    SYNTAX Integer32 (0..100)
    MAX-ACCESS read-write
    STATUS current
    DESCRIPTION
        "Asentria HVAC humidity alarm event very low value"
    ::= { evHVACAsentriaHumid 6 }
    --1.3.6.1.4.1.3052.10.2.12.19.3.9.6

evHVACAsentriaHumidVLowActions OBJECT-TYPE
    SYNTAX DisplayString
    MAX-ACCESS read-write
    STATUS current
    DESCRIPTION
        "Asentria HVAC humidity alarm event very low actions"
    ::= { evHVACAsentriaHumid 7 }
    --1.3.6.1.4.1.3052.10.2.12.19.3.9.7

evHVACAsentriaHumidVLowTrapNum OBJECT-TYPE
    SYNTAX Integer32 (545..1199)
    MAX-ACCESS read-write
    STATUS current
    DESCRIPTION
        "Asentria HVAC humidity alarm event very low trap number"
    ::= { evHVACAsentriaHumid 8 }
    --1.3.6.1.4.1.3052.10.2.12.19.3.9.8

evHVACAsentriaHumidVLowClass OBJECT-TYPE
    SYNTAX DisplayString
    MAX-ACCESS read-write
    STATUS current
    DESCRIPTION
        "Asentria HVAC humidity alarm event very low class"
    ::= { evHVACAsentriaHumid 9 }
    --1.3.6.1.4.1.3052.10.2.12.19.3.9.9

evHVACAsentriaHumidLowValue OBJECT-TYPE
    SYNTAX Integer32 (0..100)
    MAX-ACCESS read-write
    STATUS current
    DESCRIPTION
        "Asentria HVAC humidity alarm event low value"
    ::= { evHVACAsentriaHumid 10 }
    --1.3.6.1.4.1.3052.10.2.12.19.3.9.10

evHVACAsentriaHumidLowActions OBJECT-TYPE
    SYNTAX DisplayString
    MAX-ACCESS read-write
    STATUS current
    DESCRIPTION
        "Asentria HVAC humidity alarm event low actions"
    ::= { evHVACAsentriaHumid 11 }
    --1.3.6.1.4.1.3052.10.2.12.19.3.9.11

evHVACAsentriaHumidLowTrapNum OBJECT-TYPE
    SYNTAX Integer32 (545..1199)
    MAX-ACCESS read-write
    STATUS current
    DESCRIPTION
        "Asentria HVAC humidity alarm event low trap number"
    ::= { evHVACAsentriaHumid 12 }
    --1.3.6.1.4.1.3052.10.2.12.19.3.9.12

evHVACAsentriaHumidLowClass OBJECT-TYPE
    SYNTAX DisplayString
    MAX-ACCESS read-write
    STATUS current
    DESCRIPTION
        "Asentria HVAC humidity alarm event low class"
    ::= { evHVACAsentriaHumid 13 }
    --1.3.6.1.4.1.3052.10.2.12.19.3.9.13

evHVACAsentriaHumidNormalActions OBJECT-TYPE
    SYNTAX DisplayString
    MAX-ACCESS read-write
    STATUS current
    DESCRIPTION
        "Asentria HVAC humidity alarm event return to normal 
        actions"
    ::= { evHVACAsentriaHumid 14 }
    --1.3.6.1.4.1.3052.10.2.12.19.3.9.14

evHVACAsentriaHumidNormalTrapNum OBJECT-TYPE
    SYNTAX Integer32 (545..1199)
    MAX-ACCESS read-write
    STATUS current
    DESCRIPTION
        "Asentria HVAC humidity alarm event return to normal trap 
        number"
    ::= { evHVACAsentriaHumid 15 }
    --1.3.6.1.4.1.3052.10.2.12.19.3.9.15

evHVACAsentriaHumidNormalClass OBJECT-TYPE
    SYNTAX DisplayString
    MAX-ACCESS read-write
    STATUS current
    DESCRIPTION
        "Asentria HVAC humidity alarm event return to normal class"
    ::= { evHVACAsentriaHumid 16 }
    --1.3.6.1.4.1.3052.10.2.12.19.3.9.16

evHVACAsentriaHumidHighValue OBJECT-TYPE
    SYNTAX Integer32 (0..100)
    MAX-ACCESS read-write
    STATUS current
    DESCRIPTION
        "Asentria HVAC humidity alarm event high value"
    ::= { evHVACAsentriaHumid 17 }
    --1.3.6.1.4.1.3052.10.2.12.19.3.9.17

evHVACAsentriaHumidHighActions OBJECT-TYPE
    SYNTAX DisplayString
    MAX-ACCESS read-write
    STATUS current
    DESCRIPTION
        "Asentria HVAC humidity alarm event high actions"
    ::= { evHVACAsentriaHumid 18 }
    --1.3.6.1.4.1.3052.10.2.12.19.3.9.18

evHVACAsentriaHumidHighTrapNum OBJECT-TYPE
    SYNTAX Integer32 (545..1199)
    MAX-ACCESS read-write
    STATUS current
    DESCRIPTION
        "Asentria HVAC humidity alarm event high trap number"
    ::= { evHVACAsentriaHumid 19 }
    --1.3.6.1.4.1.3052.10.2.12.19.3.9.19

evHVACAsentriaHumidHighClass OBJECT-TYPE
    SYNTAX DisplayString
    MAX-ACCESS read-write
    STATUS current
    DESCRIPTION
        "Asentria HVAC humidity alarm event high class"
    ::= { evHVACAsentriaHumid 20 }
    --1.3.6.1.4.1.3052.10.2.12.19.3.9.20

evHVACAsentriaHumidVHighValue OBJECT-TYPE
    SYNTAX Integer32 (0..100)
    MAX-ACCESS read-write
    STATUS current
    DESCRIPTION
        "Asentria HVAC humidity alarm event very high value"
    ::= { evHVACAsentriaHumid 21 }
    --1.3.6.1.4.1.3052.10.2.12.19.3.9.21

evHVACAsentriaHumidVHighActions OBJECT-TYPE
    SYNTAX DisplayString
    MAX-ACCESS read-write
    STATUS current
    DESCRIPTION
        "Asentria HVAC humidity alarm event very high actions"
    ::= { evHVACAsentriaHumid 22 }
    --1.3.6.1.4.1.3052.10.2.12.19.3.9.22

evHVACAsentriaHumidVHighTrapNum OBJECT-TYPE
    SYNTAX Integer32 (545..1199)
    MAX-ACCESS read-write
    STATUS current
    DESCRIPTION
        "Asentria HVAC humidity alarm event very high trap number"
    ::= { evHVACAsentriaHumid 23 }
    --1.3.6.1.4.1.3052.10.2.12.19.3.9.23

evHVACAsentriaHumidVHighClass OBJECT-TYPE
    SYNTAX DisplayString
    MAX-ACCESS read-write
    STATUS current
    DESCRIPTION
        "Asentria HVAC humidity alarm event very high class"
    ::= { evHVACAsentriaHumid 24 }
    --1.3.6.1.4.1.3052.10.2.12.19.3.9.24

evHVACAsentriaHumidDeadband OBJECT-TYPE
    SYNTAX Integer32 (1..10)
    MAX-ACCESS read-write
    STATUS current
    DESCRIPTION
        "Asentria HVAC humidity deadband before stopping current 
        state"
    ::= { evHVACAsentriaHumid 25 }
    --1.3.6.1.4.1.3052.10.2.12.19.3.9.25

evHVACAsentriaHumidDifference OBJECT-TYPE
    SYNTAX Integer32 (1..10)
    MAX-ACCESS read-write
    STATUS current
    DESCRIPTION
        "Asentria HVAC humidity step before changing states"
    ::= { evHVACAsentriaHumid 26 }
    --1.3.6.1.4.1.3052.10.2.12.19.3.9.26


--***************************************************************************************
--Airsys HVAC Configuration Section   2.12.19.4
--***************************************************************************************

evHVACAirsysGeneratorLogic OBJECT-TYPE
    SYNTAX DisplayString
    MAX-ACCESS read-write
    STATUS current
    DESCRIPTION
        "Airsys HVAC generator logic"
    ::= { evHVACAirsysGeneral 1 }
    --1.3.6.1.4.1.3052.10.2.12.19.4.1.1

evHVACAirsysFreeMode OBJECT-TYPE
    SYNTAX DisplayString
    MAX-ACCESS read-write
    STATUS current
    DESCRIPTION
        "Airsys HVAC free mode"
    ::= { evHVACAirsysGeneral 2 }
    --1.3.6.1.4.1.3052.10.2.12.19.4.1.2

evHVACAirsysRemoteEnable OBJECT-TYPE
    SYNTAX DisplayString
    MAX-ACCESS read-write
    STATUS current
    DESCRIPTION
        "Airsys HVAC remote control enable"
    ::= { evHVACAirsysGeneral 3 }
    --1.3.6.1.4.1.3052.10.2.12.19.4.1.3

evHVACAirsysHVACRotation OBJECT-TYPE
    SYNTAX DisplayString
    MAX-ACCESS read-write
    STATUS current
    DESCRIPTION
        "Airsys HVAC rotate unit lead/lag"
    ::= { evHVACAirsysGeneral 4 }
    --1.3.6.1.4.1.3052.10.2.12.19.4.1.4

evHVACAirsysRotationRuntime OBJECT-TYPE
    SYNTAX Integer32
    MAX-ACCESS read-write
    STATUS current
    DESCRIPTION
        "Airsys HVAC rotation runtime period"
    ::= { evHVACAirsysGeneral 5 }
    --1.3.6.1.4.1.3052.10.2.12.19.4.1.5

evHVACAirsysUnitTable OBJECT-TYPE
    SYNTAX SEQUENCE OF HVACAirsysUnit
    MAX-ACCESS not-accessible
    STATUS current
    DESCRIPTION
        "Airsys HVAC unit table"
    ::= { evHVACAirsysAlarm 1 }
    --1.3.6.1.4.1.3052.10.2.12.19.4.2.1

evHVACAirsysUnitEntry OBJECT-TYPE
    SYNTAX HVACAirsysUnit
    MAX-ACCESS not-accessible
    STATUS current
    DESCRIPTION
        "Airsys HVAC unit table entry"
    INDEX { evHVACAirsysUnitIndex }
    ::= { evHVACAirsysUnitTable 1 }
    --1.3.6.1.4.1.3052.10.2.12.19.4.2.1.1

evHVACAirsysUnitIndex OBJECT-TYPE
    SYNTAX Integer32 (1..2)
    MAX-ACCESS read-only
    STATUS current
    DESCRIPTION
        "Index for Airsys HVAC unit"
    ::= { evHVACAirsysUnitEntry 1 }
    --1.3.6.1.4.1.3052.10.2.12.19.4.2.1.1.1

evHVACAirsysULowPEnable OBJECT-TYPE
    SYNTAX DisplayString
    MAX-ACCESS read-write
    STATUS current
    DESCRIPTION
        "Airsys HVAC unit low pressure alarm enable"
    ::= { evHVACAirsysUnitEntry 2 }
    --1.3.6.1.4.1.3052.10.2.12.19.4.2.1.1.2

evHVACAirsysULowPActions OBJECT-TYPE
    SYNTAX DisplayString
    MAX-ACCESS read-write
    STATUS current
    DESCRIPTION
        "Airsys HVAC actions to perform for low pressure alarm 
        notification"
    ::= { evHVACAirsysUnitEntry 3 }
    --1.3.6.1.4.1.3052.10.2.12.19.4.2.1.1.3

evHVACAirsysULowPTrapnum OBJECT-TYPE
    SYNTAX Integer32 (548..1199)
    MAX-ACCESS read-write
    STATUS current
    DESCRIPTION
        "Airsys HVAC trap number for low pressure alarm notification"
    ::= { evHVACAirsysUnitEntry 4 }
    --1.3.6.1.4.1.3052.10.2.12.19.4.2.1.1.4

evHVACAirsysULowPClass OBJECT-TYPE
    SYNTAX DisplayString
    MAX-ACCESS read-write
    STATUS current
    DESCRIPTION
        "Airsys HVAC alarm class for low pressure alarm notification"
    ::= { evHVACAirsysUnitEntry 5 }
    --1.3.6.1.4.1.3052.10.2.12.19.4.2.1.1.5

evHVACAirsysULowPNormActions OBJECT-TYPE
    SYNTAX DisplayString
    MAX-ACCESS read-write
    STATUS current
    DESCRIPTION
        "Airsys HVAC return to normal actions to perform for 
        low pressure alarm notification"
    ::= { evHVACAirsysUnitEntry 6 }
    --1.3.6.1.4.1.3052.10.2.12.19.4.2.1.1.6

evHVACAirsysULowPNormTrapNum OBJECT-TYPE
    SYNTAX Integer32 (548..1199)
    MAX-ACCESS read-write
    STATUS current
    DESCRIPTION
        "Airsys HVAC return to normal trap number for low pressure 
        alarm notification"
    ::= { evHVACAirsysUnitEntry 7 }
    --1.3.6.1.4.1.3052.10.2.12.19.4.2.1.1.7

evHVACAirsysULowPNormClass OBJECT-TYPE
    SYNTAX DisplayString
    MAX-ACCESS read-write
    STATUS current
    DESCRIPTION
        "Airsys HVAC return to normal class for low pressure alarm 
        notification"
    ::= { evHVACAirsysUnitEntry 8 }
    --1.3.6.1.4.1.3052.10.2.12.19.4.2.1.1.8

evHVACAirsysUHighPEnable OBJECT-TYPE
    SYNTAX DisplayString
    MAX-ACCESS read-write
    STATUS current
    DESCRIPTION
        "Airsys HVAC unit high pressure alarm enable"
    ::= { evHVACAirsysUnitEntry 9 }
    --1.3.6.1.4.1.3052.10.2.12.19.4.2.1.1.9

evHVACAirsysUHighPActions OBJECT-TYPE
    SYNTAX DisplayString
    MAX-ACCESS read-write
    STATUS current
    DESCRIPTION
        "Airsys HVAC actions to perform for high pressure alarm 
        notification"
    ::= { evHVACAirsysUnitEntry 10 }
    --1.3.6.1.4.1.3052.10.2.12.19.4.2.1.1.10

evHVACAirsysUHighPTrapnum OBJECT-TYPE
    SYNTAX Integer32 (548..1199)
    MAX-ACCESS read-write
    STATUS current
    DESCRIPTION
        "Airsys HVAC trap number for high pressure alarm notification"
    ::= { evHVACAirsysUnitEntry 11 }
    --1.3.6.1.4.1.3052.10.2.12.19.4.2.1.1.11

evHVACAirsysUHighPClass OBJECT-TYPE
    SYNTAX DisplayString
    MAX-ACCESS read-write
    STATUS current
    DESCRIPTION
        "Airsys HVAC alarm class for high pressure alarm notification"
    ::= { evHVACAirsysUnitEntry 12 }
    --1.3.6.1.4.1.3052.10.2.12.19.4.2.1.1.12

evHVACAirsysUHighPNormActions OBJECT-TYPE
    SYNTAX DisplayString
    MAX-ACCESS read-write
    STATUS current
    DESCRIPTION
        "Airsys HVAC return to normal actions to perform for 
        high pressure alarm notification"
    ::= { evHVACAirsysUnitEntry 13 }
    --1.3.6.1.4.1.3052.10.2.12.19.4.2.1.1.13

evHVACAirsysUHighPNormTrapNum OBJECT-TYPE
    SYNTAX Integer32 (548..1199)
    MAX-ACCESS read-write
    STATUS current
    DESCRIPTION
        "Airsys HVAC return to normal trap number for high pressure 
        alarm notification"
    ::= { evHVACAirsysUnitEntry 14 }
    --1.3.6.1.4.1.3052.10.2.12.19.4.2.1.1.14

evHVACAirsysUHighPNormClass OBJECT-TYPE
    SYNTAX DisplayString
    MAX-ACCESS read-write
    STATUS current
    DESCRIPTION
        "Airsys HVAC return to normal class for high pressure alarm 
        notification"
    ::= { evHVACAirsysUnitEntry 15 }
    --1.3.6.1.4.1.3052.10.2.12.19.4.2.1.1.15

evHVACAirsysUEvapFanEnable OBJECT-TYPE
    SYNTAX DisplayString
    MAX-ACCESS read-write
    STATUS current
    DESCRIPTION
        "Airsys HVAC unit evaporator fan alarm enable"
    ::= { evHVACAirsysUnitEntry 16 }
    --1.3.6.1.4.1.3052.10.2.12.19.4.2.1.1.16

evHVACAirsysUEvapFanActions OBJECT-TYPE
    SYNTAX DisplayString
    MAX-ACCESS read-write
    STATUS current
    DESCRIPTION
        "Airsys HVAC actions to perform for evaporator fan alarm 
        notification"
    ::= { evHVACAirsysUnitEntry 17 }
    --1.3.6.1.4.1.3052.10.2.12.19.4.2.1.1.17

evHVACAirsysUEvapFanTrapnum OBJECT-TYPE
    SYNTAX Integer32 (548..1199)
    MAX-ACCESS read-write
    STATUS current
    DESCRIPTION
        "Airsys HVAC trap number for evaporator fan alarm notification"
    ::= { evHVACAirsysUnitEntry 18 }
    --1.3.6.1.4.1.3052.10.2.12.19.4.2.1.1.18

evHVACAirsysUEvapFanClass OBJECT-TYPE
    SYNTAX DisplayString
    MAX-ACCESS read-write
    STATUS current
    DESCRIPTION
        "Airsys HVAC alarm class for evaporator fan alarm notification"
    ::= { evHVACAirsysUnitEntry 19 }
    --1.3.6.1.4.1.3052.10.2.12.19.4.2.1.1.19

evHVACAirsysUEvapFanNormActions OBJECT-TYPE
    SYNTAX DisplayString
    MAX-ACCESS read-write
    STATUS current
    DESCRIPTION
        "Airsys HVAC return to normal actions to perform for 
        evaporator fan alarm notification"
    ::= { evHVACAirsysUnitEntry 20 }
    --1.3.6.1.4.1.3052.10.2.12.19.4.2.1.1.20

evHVACAirsysUEvapFanNormTrapNum OBJECT-TYPE
    SYNTAX Integer32 (548..1199)
    MAX-ACCESS read-write
    STATUS current
    DESCRIPTION
        "Airsys HVAC return to normal trap number for evaporator fan 
        alarm notification"
    ::= { evHVACAirsysUnitEntry 21 }
    --1.3.6.1.4.1.3052.10.2.12.19.4.2.1.1.21

evHVACAirsysUEvapFanNormClass OBJECT-TYPE
    SYNTAX DisplayString
    MAX-ACCESS read-write
    STATUS current
    DESCRIPTION
        "Airsys HVAC return to normal class for evaporator fan alarm 
        notification"
    ::= { evHVACAirsysUnitEntry 22 }
    --1.3.6.1.4.1.3052.10.2.12.19.4.2.1.1.22

evHVACAirsysUDirtyEnable OBJECT-TYPE
    SYNTAX DisplayString
    MAX-ACCESS read-write
    STATUS current
    DESCRIPTION
        "Airsys HVAC unit dirty filter alarm enable"
    ::= { evHVACAirsysUnitEntry 23 }
    --1.3.6.1.4.1.3052.10.2.12.19.4.2.1.1.23

evHVACAirsysUDirtyActions OBJECT-TYPE
    SYNTAX DisplayString
    MAX-ACCESS read-write
    STATUS current
    DESCRIPTION
        "Airsys HVAC actions to perform for dirty filter alarm 
        notification"
    ::= { evHVACAirsysUnitEntry 24 }
    --1.3.6.1.4.1.3052.10.2.12.19.4.2.1.1.24

evHVACAirsysUDirtyTrapnum OBJECT-TYPE
    SYNTAX Integer32 (548..1199)
    MAX-ACCESS read-write
    STATUS current
    DESCRIPTION
        "Airsys HVAC trap number for dirty filter alarm notification"
    ::= { evHVACAirsysUnitEntry 25 }
    --1.3.6.1.4.1.3052.10.2.12.19.4.2.1.1.25

evHVACAirsysUDirtyClass OBJECT-TYPE
    SYNTAX DisplayString
    MAX-ACCESS read-write
    STATUS current
    DESCRIPTION
        "Airsys HVAC alarm class for dirty filter alarm notification"
    ::= { evHVACAirsysUnitEntry 26 }
    --1.3.6.1.4.1.3052.10.2.12.19.4.2.1.1.26

evHVACAirsysUDirtyNormActions OBJECT-TYPE
    SYNTAX DisplayString
    MAX-ACCESS read-write
    STATUS current
    DESCRIPTION
        "Airsys HVAC return to normal actions to perform for 
        dirty filter alarm notification"
    ::= { evHVACAirsysUnitEntry 27 }
    --1.3.6.1.4.1.3052.10.2.12.19.4.2.1.1.27

evHVACAirsysUDirtyNormTrapNum OBJECT-TYPE
    SYNTAX Integer32 (548..1199)
    MAX-ACCESS read-write
    STATUS current
    DESCRIPTION
        "Airsys HVAC return to normal trap number for dirty filter 
        alarm notification"
    ::= { evHVACAirsysUnitEntry 28 }
    --1.3.6.1.4.1.3052.10.2.12.19.4.2.1.1.28

evHVACAirsysUDirtyNormClass OBJECT-TYPE
    SYNTAX DisplayString
    MAX-ACCESS read-write
    STATUS current
    DESCRIPTION
        "Airsys HVAC return to normal class for dirty filter alarm 
        notification"
    ::= { evHVACAirsysUnitEntry 29 }
    --1.3.6.1.4.1.3052.10.2.12.19.4.2.1.1.29

evHVACAirsysUInProbeEnable OBJECT-TYPE
    SYNTAX DisplayString
    MAX-ACCESS read-write
    STATUS current
    DESCRIPTION
        "Airsys HVAC unit indoor probe broken alarm enable"
    ::= { evHVACAirsysUnitEntry 30 }
    --1.3.6.1.4.1.3052.10.2.12.19.4.2.1.1.30

evHVACAirsysUInProbeActions OBJECT-TYPE
    SYNTAX DisplayString
    MAX-ACCESS read-write
    STATUS current
    DESCRIPTION
        "Airsys HVAC actions to perform for indoor probe broken 
        alarm notification"
    ::= { evHVACAirsysUnitEntry 31 }
    --1.3.6.1.4.1.3052.10.2.12.19.4.2.1.1.31

evHVACAirsysUInProbeTrapnum OBJECT-TYPE
    SYNTAX Integer32 (548..1199)
    MAX-ACCESS read-write
    STATUS current
    DESCRIPTION
        "Airsys HVAC trap number for indoor probe broken alarm 
        notification"
    ::= { evHVACAirsysUnitEntry 32 }
    --1.3.6.1.4.1.3052.10.2.12.19.4.2.1.1.32

evHVACAirsysUInProbeClass OBJECT-TYPE
    SYNTAX DisplayString
    MAX-ACCESS read-write
    STATUS current
    DESCRIPTION
        "Airsys HVAC alarm class for indoor probe broken alarm 
        notification"
    ::= { evHVACAirsysUnitEntry 33 }
    --1.3.6.1.4.1.3052.10.2.12.19.4.2.1.1.33

evHVACAirsysUInProbeNormActions OBJECT-TYPE
    SYNTAX DisplayString
    MAX-ACCESS read-write
    STATUS current
    DESCRIPTION
        "Airsys HVAC return to normal actions to perform for 
        indoor probe broken alarm notification"
    ::= { evHVACAirsysUnitEntry 34 }
    --1.3.6.1.4.1.3052.10.2.12.19.4.2.1.1.34

evHVACAirsysUInProbeNormTrapNum OBJECT-TYPE
    SYNTAX Integer32 (548..1199)
    MAX-ACCESS read-write
    STATUS current
    DESCRIPTION
        "Airsys HVAC return to normal trap number for indoor probe 
        broken alarm notification"
    ::= { evHVACAirsysUnitEntry 35 }
    --1.3.6.1.4.1.3052.10.2.12.19.4.2.1.1.35

evHVACAirsysUInProbeNormClass OBJECT-TYPE
    SYNTAX DisplayString
    MAX-ACCESS read-write
    STATUS current
    DESCRIPTION
        "Airsys HVAC return to normal class for indoor probe broken 
        alarm notification"
    ::= { evHVACAirsysUnitEntry 36 }
    --1.3.6.1.4.1.3052.10.2.12.19.4.2.1.1.36

evHVACAirsysUDamperEnable OBJECT-TYPE
    SYNTAX DisplayString
    MAX-ACCESS read-write
    STATUS current
    DESCRIPTION
        "Airsys HVAC unit high pressure alarm enable"
    ::= { evHVACAirsysUnitEntry 37 }
    --1.3.6.1.4.1.3052.10.2.12.19.4.2.1.1.37

evHVACAirsysUDamperActions OBJECT-TYPE
    SYNTAX DisplayString
    MAX-ACCESS read-write
    STATUS current
    DESCRIPTION
        "Airsys HVAC actions to perform for high pressure alarm 
        notification"
    ::= { evHVACAirsysUnitEntry 38 }
    --1.3.6.1.4.1.3052.10.2.12.19.4.2.1.1.38

evHVACAirsysUDamperTrapnum OBJECT-TYPE
    SYNTAX Integer32 (548..1199)
    MAX-ACCESS read-write
    STATUS current
    DESCRIPTION
        "Airsys HVAC trap number for high pressure alarm notification"
    ::= { evHVACAirsysUnitEntry 39 }
    --1.3.6.1.4.1.3052.10.2.12.19.4.2.1.1.39

evHVACAirsysUDamperClass OBJECT-TYPE
    SYNTAX DisplayString
    MAX-ACCESS read-write
    STATUS current
    DESCRIPTION
        "Airsys HVAC alarm class for high pressure alarm notification"
    ::= { evHVACAirsysUnitEntry 40 }
    --1.3.6.1.4.1.3052.10.2.12.19.4.2.1.1.40

evHVACAirsysUDamperNormActions OBJECT-TYPE
    SYNTAX DisplayString
    MAX-ACCESS read-write
    STATUS current
    DESCRIPTION
        "Airsys HVAC return to normal actions to perform for 
        high pressure alarm notification"
    ::= { evHVACAirsysUnitEntry 41 }
    --1.3.6.1.4.1.3052.10.2.12.19.4.2.1.1.41

evHVACAirsysUDamperNormTrapNum OBJECT-TYPE
    SYNTAX Integer32 (548..1199)
    MAX-ACCESS read-write
    STATUS current
    DESCRIPTION
        "Airsys HVAC return to normal trap number for high pressure 
        alarm notification"
    ::= { evHVACAirsysUnitEntry 42 }
    --1.3.6.1.4.1.3052.10.2.12.19.4.2.1.1.42

evHVACAirsysUDamperNormClass OBJECT-TYPE
    SYNTAX DisplayString
    MAX-ACCESS read-write
    STATUS current
    DESCRIPTION
        "Airsys HVAC return to normal class for high pressure alarm 
        notification"
    ::= { evHVACAirsysUnitEntry 43 }
    --1.3.6.1.4.1.3052.10.2.12.19.4.2.1.1.43

evHVACAirsysUSupProbeEnable OBJECT-TYPE
    SYNTAX DisplayString
    MAX-ACCESS read-write
    STATUS current
    DESCRIPTION
        "Airsys HVAC unit supply probe broken alarm enable"
    ::= { evHVACAirsysUnitEntry 44 }
    --1.3.6.1.4.1.3052.10.2.12.19.4.2.1.1.44

evHVACAirsysUSupProbeActions OBJECT-TYPE
    SYNTAX DisplayString
    MAX-ACCESS read-write
    STATUS current
    DESCRIPTION
        "Airsys HVAC actions to perform for supply probe broken 
        alarm notification"
    ::= { evHVACAirsysUnitEntry 45 }
    --1.3.6.1.4.1.3052.10.2.12.19.4.2.1.1.45

evHVACAirsysUSupProbeTrapnum OBJECT-TYPE
    SYNTAX Integer32 (548..1199)
    MAX-ACCESS read-write
    STATUS current
    DESCRIPTION
        "Airsys HVAC trap number for supply probe broken alarm 
        notification"
    ::= { evHVACAirsysUnitEntry 46 }
    --1.3.6.1.4.1.3052.10.2.12.19.4.2.1.1.46

evHVACAirsysUSupProbeClass OBJECT-TYPE
    SYNTAX DisplayString
    MAX-ACCESS read-write
    STATUS current
    DESCRIPTION
        "Airsys HVAC alarm class for supply probe broken alarm 
        notification"
    ::= { evHVACAirsysUnitEntry 47 }
    --1.3.6.1.4.1.3052.10.2.12.19.4.2.1.1.47

evHVACAirsysUSupProbeNormActions OBJECT-TYPE
    SYNTAX DisplayString
    MAX-ACCESS read-write
    STATUS current
    DESCRIPTION
        "Airsys HVAC return to normal actions to perform for 
        supply probe broken alarm notification"
    ::= { evHVACAirsysUnitEntry 48 }
    --1.3.6.1.4.1.3052.10.2.12.19.4.2.1.1.48

evHVACAirsysUSupProbeNormTrapNum OBJECT-TYPE
    SYNTAX Integer32 (548..1199)
    MAX-ACCESS read-write
    STATUS current
    DESCRIPTION
        "Airsys HVAC return to normal trap number for supply probe 
        broken alarm notification"
    ::= { evHVACAirsysUnitEntry 49 }
    --1.3.6.1.4.1.3052.10.2.12.19.4.2.1.1.49

evHVACAirsysUSupProbeNormClass OBJECT-TYPE
    SYNTAX DisplayString
    MAX-ACCESS read-write
    STATUS current
    DESCRIPTION
        "Airsys HVAC return to normal class for supply probe broken 
        alarm notification"
    ::= { evHVACAirsysUnitEntry 50 }
    --1.3.6.1.4.1.3052.10.2.12.19.4.2.1.1.50

evHVACAirsysSmokeFireEnable OBJECT-TYPE
    SYNTAX DisplayString
    MAX-ACCESS read-write
    STATUS current
    DESCRIPTION
        "Airsys HVAC unit smoke/fire alarm enable"
    ::= { evHVACAirsysAlarm 2 }
    --1.3.6.1.4.1.3052.10.2.12.19.4.2.2

evHVACAirsysSmokeFireActions OBJECT-TYPE
    SYNTAX DisplayString
    MAX-ACCESS read-write
    STATUS current
    DESCRIPTION
        "Airsys HVAC actions to perform for smoke/fire alarm 
        notification"
    ::= { evHVACAirsysAlarm 3 }
    --1.3.6.1.4.1.3052.10.2.12.19.4.2.3

evHVACAirsysSmokeFireTrapnum OBJECT-TYPE
    SYNTAX Integer32 (548..1199)
    MAX-ACCESS read-write
    STATUS current
    DESCRIPTION
        "Airsys HVAC trap number for smoke/fire alarm notification"
    ::= { evHVACAirsysAlarm 4 }
    --1.3.6.1.4.1.3052.10.2.12.19.4.2.4

evHVACAirsysSmokeFireClass OBJECT-TYPE
    SYNTAX DisplayString
    MAX-ACCESS read-write
    STATUS current
    DESCRIPTION
        "Airsys HVAC alarm class for smoke/fire alarm notification"
    ::= { evHVACAirsysAlarm 5 }
    --1.3.6.1.4.1.3052.10.2.12.19.4.2.5

evHVACAirsysSmokeFireNormActions OBJECT-TYPE
    SYNTAX DisplayString
    MAX-ACCESS read-write
    STATUS current
    DESCRIPTION
        "Airsys HVAC return to normal actions to perform for 
        smoke/fire alarm notification"
    ::= { evHVACAirsysAlarm 6 }
    --1.3.6.1.4.1.3052.10.2.12.19.4.2.6

evHVACAirsysSmokeFireNormTrapNum OBJECT-TYPE
    SYNTAX Integer32 (548..1199)
    MAX-ACCESS read-write
    STATUS current
    DESCRIPTION
        "Airsys HVAC return to normal trap number for smoke/fire 
        alarm notification"
    ::= { evHVACAirsysAlarm 7 }
    --1.3.6.1.4.1.3052.10.2.12.19.4.2.7

evHVACAirsysSmokeFireNormClass OBJECT-TYPE
    SYNTAX DisplayString
    MAX-ACCESS read-write
    STATUS current
    DESCRIPTION
        "Airsys HVAC return to normal class for smoke/fire alarm 
        notification"
    ::= { evHVACAirsysAlarm 8 }
    --1.3.6.1.4.1.3052.10.2.12.19.4.2.8

evHVACAirsysLowRoomTempEnable OBJECT-TYPE
    SYNTAX DisplayString
    MAX-ACCESS read-write
    STATUS current
    DESCRIPTION
        "Airsys HVAC unit low room temperature alarm enable"
    ::= { evHVACAirsysAlarm 9 }
    --1.3.6.1.4.1.3052.10.2.12.19.4.2.9

evHVACAirsysLowRoomTempActions OBJECT-TYPE
    SYNTAX DisplayString
    MAX-ACCESS read-write
    STATUS current
    DESCRIPTION
        "Airsys HVAC actions to perform for low room temperature 
        alarm notification"
    ::= { evHVACAirsysAlarm 10 }
    --1.3.6.1.4.1.3052.10.2.12.19.4.2.10

evHVACAirsysLowRoomTempTrapnum OBJECT-TYPE
    SYNTAX Integer32 (548..1199)
    MAX-ACCESS read-write
    STATUS current
    DESCRIPTION
        "Airsys HVAC trap number for low room temperature alarm 
        notification"
    ::= { evHVACAirsysAlarm 11 }
    --1.3.6.1.4.1.3052.10.2.12.19.4.2.11

evHVACAirsysLowRoomTempClass OBJECT-TYPE
    SYNTAX DisplayString
    MAX-ACCESS read-write
    STATUS current
    DESCRIPTION
        "Airsys HVAC alarm class for low room temperature alarm 
        notification"
    ::= { evHVACAirsysAlarm 12 }
    --1.3.6.1.4.1.3052.10.2.12.19.4.2.12

evHVACAirsysLowRoomTempNormActions OBJECT-TYPE
    SYNTAX DisplayString
    MAX-ACCESS read-write
    STATUS current
    DESCRIPTION
        "Airsys HVAC return to normal actions to perform for low 
        room temperature alarm notification"
    ::= { evHVACAirsysAlarm 13 }
    --1.3.6.1.4.1.3052.10.2.12.19.4.2.13

evHVACAirsysLowRoomTempNormTrapNum OBJECT-TYPE
    SYNTAX Integer32 (548..1199)
    MAX-ACCESS read-write
    STATUS current
    DESCRIPTION
        "Airsys HVAC return to normal trap number for low room 
        temperature alarm notification"
    ::= { evHVACAirsysAlarm 14 }
    --1.3.6.1.4.1.3052.10.2.12.19.4.2.14

evHVACAirsysLowRoomTempNormClass OBJECT-TYPE
    SYNTAX DisplayString
    MAX-ACCESS read-write
    STATUS current
    DESCRIPTION
        "Airsys HVAC return to normal class for low room temperature 
        alarm notification"
    ::= { evHVACAirsysAlarm 15 }
    --1.3.6.1.4.1.3052.10.2.12.19.4.2.15

evHVACAirsysHighRoomTempEnable OBJECT-TYPE
    SYNTAX DisplayString
    MAX-ACCESS read-write
    STATUS current
    DESCRIPTION
        "Airsys HVAC unit high room temperature alarm enable"
    ::= { evHVACAirsysAlarm 16 }
    --1.3.6.1.4.1.3052.10.2.12.19.4.2.16

evHVACAirsysHighRoomTempActions OBJECT-TYPE
    SYNTAX DisplayString
    MAX-ACCESS read-write
    STATUS current
    DESCRIPTION
        "Airsys HVAC actions to perform for high room temperature 
        alarm notification"
    ::= { evHVACAirsysAlarm 17 }
    --1.3.6.1.4.1.3052.10.2.12.19.4.2.17

evHVACAirsysHighRoomTempTrapnum OBJECT-TYPE
    SYNTAX Integer32 (548..1199)
    MAX-ACCESS read-write
    STATUS current
    DESCRIPTION
        "Airsys HVAC trap number for high room temperature alarm 
        notification"
    ::= { evHVACAirsysAlarm 18 }
    --1.3.6.1.4.1.3052.10.2.12.19.4.2.18

evHVACAirsysHighRoomTempClass OBJECT-TYPE
    SYNTAX DisplayString
    MAX-ACCESS read-write
    STATUS current
    DESCRIPTION
        "Airsys HVAC alarm class for high room temperature alarm 
        notification"
    ::= { evHVACAirsysAlarm 19 }
    --1.3.6.1.4.1.3052.10.2.12.19.4.2.19

evHVACAirsysHighRoomTempNormActions OBJECT-TYPE
    SYNTAX DisplayString
    MAX-ACCESS read-write
    STATUS current
    DESCRIPTION
        "Airsys HVAC return to normal actions to perform for high 
        room temperature alarm notification"
    ::= { evHVACAirsysAlarm 20 }
    --1.3.6.1.4.1.3052.10.2.12.19.4.2.20

evHVACAirsysHighRoomTempNormTrapNum OBJECT-TYPE
    SYNTAX Integer32 (548..1199)
    MAX-ACCESS read-write
    STATUS current
    DESCRIPTION
        "Airsys HVAC return to normal trap number for high room 
        temperature alarm notification"
    ::= { evHVACAirsysAlarm 21 }
    --1.3.6.1.4.1.3052.10.2.12.19.4.2.21

evHVACAirsysHighRoomTempNormClass OBJECT-TYPE
    SYNTAX DisplayString
    MAX-ACCESS read-write
    STATUS current
    DESCRIPTION
        "Airsys HVAC return to normal class for high room 
        temperature alarm notification"
    ::= { evHVACAirsysAlarm 22 }
    --1.3.6.1.4.1.3052.10.2.12.19.4.2.22

evHVACAirsysPowerEnable OBJECT-TYPE
    SYNTAX DisplayString
    MAX-ACCESS read-write
    STATUS current
    DESCRIPTION
        "Airsys HVAC unit power failure alarm enable"
    ::= { evHVACAirsysAlarm 23 }
    --1.3.6.1.4.1.3052.10.2.12.19.4.2.23

evHVACAirsysPowerActions OBJECT-TYPE
    SYNTAX DisplayString
    MAX-ACCESS read-write
    STATUS current
    DESCRIPTION
        "Airsys HVAC actions to perform for power failure alarm 
        notification"
    ::= { evHVACAirsysAlarm 24 }
    --1.3.6.1.4.1.3052.10.2.12.19.4.2.24

evHVACAirsysPowerTrapnum OBJECT-TYPE
    SYNTAX Integer32 (548..1199)
    MAX-ACCESS read-write
    STATUS current
    DESCRIPTION
        "Airsys HVAC trap number for power failure alarm 
        notification"
    ::= { evHVACAirsysAlarm 25 }
    --1.3.6.1.4.1.3052.10.2.12.19.4.2.25

evHVACAirsysPowerClass OBJECT-TYPE
    SYNTAX DisplayString
    MAX-ACCESS read-write
    STATUS current
    DESCRIPTION
        "Airsys HVAC alarm class for power failure alarm 
        notification"
    ::= { evHVACAirsysAlarm 26 }
    --1.3.6.1.4.1.3052.10.2.12.19.4.2.26

evHVACAirsysPowerNormActions OBJECT-TYPE
    SYNTAX DisplayString
    MAX-ACCESS read-write
    STATUS current
    DESCRIPTION
        "Airsys HVAC return to normal actions to perform for power 
        failure alarm notification"
    ::= { evHVACAirsysAlarm 27 }
    --1.3.6.1.4.1.3052.10.2.12.19.4.2.27

evHVACAirsysPowerNormTrapNum OBJECT-TYPE
    SYNTAX Integer32 (548..1199)
    MAX-ACCESS read-write
    STATUS current
    DESCRIPTION
        "Airsys HVAC return to normal trap number for power failure 
        alarm notification"
    ::= { evHVACAirsysAlarm 28 }
    --1.3.6.1.4.1.3052.10.2.12.19.4.2.28

evHVACAirsysPowerNormClass OBJECT-TYPE
    SYNTAX DisplayString
    MAX-ACCESS read-write
    STATUS current
    DESCRIPTION
        "Airsys HVAC return to normal class for power failure alarm 
        notification"
    ::= { evHVACAirsysAlarm 29 }
    --1.3.6.1.4.1.3052.10.2.12.19.4.2.29

evHVACAirsyspLANEnable OBJECT-TYPE
    SYNTAX DisplayString
    MAX-ACCESS read-write
    STATUS current
    DESCRIPTION
        "Airsys HVAC unit pLAN alarm enable"
    ::= { evHVACAirsysAlarm 30 }
    --1.3.6.1.4.1.3052.10.2.12.19.4.2.30

evHVACAirsyspLANActions OBJECT-TYPE
    SYNTAX DisplayString
    MAX-ACCESS read-write
    STATUS current
    DESCRIPTION
        "Airsys HVAC actions to perform for pLAN 
        alarm notification"
    ::= { evHVACAirsysAlarm 31 }
    --1.3.6.1.4.1.3052.10.2.12.19.4.2.31

evHVACAirsyspLANTrapnum OBJECT-TYPE
    SYNTAX Integer32 (548..1199)
    MAX-ACCESS read-write
    STATUS current
    DESCRIPTION
        "Airsys HVAC trap number for pLAN alarm notification"
    ::= { evHVACAirsysAlarm 32 }
    --1.3.6.1.4.1.3052.10.2.12.19.4.2.32

evHVACAirsyspLANClass OBJECT-TYPE
    SYNTAX DisplayString
    MAX-ACCESS read-write
    STATUS current
    DESCRIPTION
        "Airsys HVAC alarm class for pLAN alarm notification"
    ::= { evHVACAirsysAlarm 33 }
    --1.3.6.1.4.1.3052.10.2.12.19.4.2.33

evHVACAirsyspLANNormActions OBJECT-TYPE
    SYNTAX DisplayString
    MAX-ACCESS read-write
    STATUS current
    DESCRIPTION
        "Airsys HVAC return to normal actions to perform for pLAN 
        alarm notification"
    ::= { evHVACAirsysAlarm 34 }
    --1.3.6.1.4.1.3052.10.2.12.19.4.2.34

evHVACAirsyspLANNormTrapNum OBJECT-TYPE
    SYNTAX Integer32 (548..1199)
    MAX-ACCESS read-write
    STATUS current
    DESCRIPTION
        "Airsys HVAC return to normal trap number for pLAN alarm 
        notification"
    ::= { evHVACAirsysAlarm 35 }
    --1.3.6.1.4.1.3052.10.2.12.19.4.2.35

evHVACAirsyspLANNormClass OBJECT-TYPE
    SYNTAX DisplayString
    MAX-ACCESS read-write
    STATUS current
    DESCRIPTION
        "Airsys HVAC return to normal class for pLAN alarm 
        notification"
    ::= { evHVACAirsysAlarm 36 }
    --1.3.6.1.4.1.3052.10.2.12.19.4.2.36

evHVACAirsysClockEnable OBJECT-TYPE
    SYNTAX DisplayString
    MAX-ACCESS read-write
    STATUS current
    DESCRIPTION
        "Airsys HVAC unit clock alarm enable"
    ::= { evHVACAirsysAlarm 37 }
    --1.3.6.1.4.1.3052.10.2.12.19.4.2.37

evHVACAirsysClockActions OBJECT-TYPE
    SYNTAX DisplayString
    MAX-ACCESS read-write
    STATUS current
    DESCRIPTION
        "Airsys HVAC actions to perform for clock alarm notification"
    ::= { evHVACAirsysAlarm 38 }
    --1.3.6.1.4.1.3052.10.2.12.19.4.2.38

evHVACAirsysClockTrapnum OBJECT-TYPE
    SYNTAX Integer32 (548..1199)
    MAX-ACCESS read-write
    STATUS current
    DESCRIPTION
        "Airsys HVAC trap number for clock alarm notification"
    ::= { evHVACAirsysAlarm 39 }
    --1.3.6.1.4.1.3052.10.2.12.19.4.2.39

evHVACAirsysClockClass OBJECT-TYPE
    SYNTAX DisplayString
    MAX-ACCESS read-write
    STATUS current
    DESCRIPTION
        "Airsys HVAC alarm class for clock alarm notification"
    ::= { evHVACAirsysAlarm 40 }
    --1.3.6.1.4.1.3052.10.2.12.19.4.2.40

evHVACAirsysClockNormActions OBJECT-TYPE
    SYNTAX DisplayString
    MAX-ACCESS read-write
    STATUS current
    DESCRIPTION
        "Airsys HVAC return to normal actions to perform for clock 
        alarm notification"
    ::= { evHVACAirsysAlarm 41 }
    --1.3.6.1.4.1.3052.10.2.12.19.4.2.41

evHVACAirsysClockNormTrapNum OBJECT-TYPE
    SYNTAX Integer32 (548..1199)
    MAX-ACCESS read-write
    STATUS current
    DESCRIPTION
        "Airsys HVAC return to normal trap number for clock alarm 
        notification"
    ::= { evHVACAirsysAlarm 42 }
    --1.3.6.1.4.1.3052.10.2.12.19.4.2.42

evHVACAirsysClockNormClass OBJECT-TYPE
    SYNTAX DisplayString
    MAX-ACCESS read-write
    STATUS current
    DESCRIPTION
        "Airsys HVAC return to normal class for clock alarm 
        notification"
    ::= { evHVACAirsysAlarm 43 }
    --1.3.6.1.4.1.3052.10.2.12.19.4.2.43

evHVACAirsysHumidProbeEnable OBJECT-TYPE
    SYNTAX DisplayString
    MAX-ACCESS read-write
    STATUS current
    DESCRIPTION
        "Airsys HVAC unit humidity probe broken alarm enable"
    ::= { evHVACAirsysAlarm 44 }
    --1.3.6.1.4.1.3052.10.2.12.19.4.2.44

evHVACAirsysHumidProbeActions OBJECT-TYPE
    SYNTAX DisplayString
    MAX-ACCESS read-write
    STATUS current
    DESCRIPTION
        "Airsys HVAC actions to perform for humidity probe broken 
        alarm notification"
    ::= { evHVACAirsysAlarm 45 }
    --1.3.6.1.4.1.3052.10.2.12.19.4.2.45

evHVACAirsysHumidProbeTrapnum OBJECT-TYPE
    SYNTAX Integer32 (548..1199)
    MAX-ACCESS read-write
    STATUS current
    DESCRIPTION
        "Airsys HVAC trap number for humidity probe broken alarm 
        notification"
    ::= { evHVACAirsysAlarm 46 }
    --1.3.6.1.4.1.3052.10.2.12.19.4.2.46

evHVACAirsysHumidProbeClass OBJECT-TYPE
    SYNTAX DisplayString
    MAX-ACCESS read-write
    STATUS current
    DESCRIPTION
        "Airsys HVAC alarm class for humidity probe broken alarm 
        notification"
    ::= { evHVACAirsysAlarm 47 }
    --1.3.6.1.4.1.3052.10.2.12.19.4.2.47

evHVACAirsysHumidProbeNormActions OBJECT-TYPE
    SYNTAX DisplayString
    MAX-ACCESS read-write
    STATUS current
    DESCRIPTION
        "Airsys HVAC return to normal actions to perform for 
        humidity probe broken alarm notification"
    ::= { evHVACAirsysAlarm 48 }
    --1.3.6.1.4.1.3052.10.2.12.19.4.2.48

evHVACAirsysHumidProbeNormTrapNum OBJECT-TYPE
    SYNTAX Integer32 (548..1199)
    MAX-ACCESS read-write
    STATUS current
    DESCRIPTION
        "Airsys HVAC return to normal trap number for humidity probe 
        broken alarm notification"
    ::= { evHVACAirsysAlarm 49 }
    --1.3.6.1.4.1.3052.10.2.12.19.4.2.49

evHVACAirsysHumidProbeNormClass OBJECT-TYPE
    SYNTAX DisplayString
    MAX-ACCESS read-write
    STATUS current
    DESCRIPTION
        "Airsys HVAC return to normal class for humidity probe broken 
        alarm notification"
    ::= { evHVACAirsysAlarm 50 }
    --1.3.6.1.4.1.3052.10.2.12.19.4.2.50

evHVACAirsysOutProbeEnable OBJECT-TYPE
    SYNTAX DisplayString
    MAX-ACCESS read-write
    STATUS current
    DESCRIPTION
        "Airsys HVAC unit outdoor probe broken alarm enable"
    ::= { evHVACAirsysAlarm 51 }
    --1.3.6.1.4.1.3052.10.2.12.19.4.2.51

evHVACAirsysOutProbeActions OBJECT-TYPE
    SYNTAX DisplayString
    MAX-ACCESS read-write
    STATUS current
    DESCRIPTION
        "Airsys HVAC actions to perform for outdoor probe broken 
        alarm notification"
    ::= { evHVACAirsysAlarm 52 }
    --1.3.6.1.4.1.3052.10.2.12.19.4.2.52

evHVACAirsysOutProbeTrapnum OBJECT-TYPE
    SYNTAX Integer32 (548..1199)
    MAX-ACCESS read-write
    STATUS current
    DESCRIPTION
        "Airsys HVAC trap number for outdoor probe broken alarm 
        notification"
    ::= { evHVACAirsysAlarm 53 }
    --1.3.6.1.4.1.3052.10.2.12.19.4.2.53

evHVACAirsysOutProbeClass OBJECT-TYPE
    SYNTAX DisplayString
    MAX-ACCESS read-write
    STATUS current
    DESCRIPTION
        "Airsys HVAC alarm class for outdoor probe broken alarm 
        notification"
    ::= { evHVACAirsysAlarm 54 }
    --1.3.6.1.4.1.3052.10.2.12.19.4.2.54

evHVACAirsysOutProbeNormActions OBJECT-TYPE
    SYNTAX DisplayString
    MAX-ACCESS read-write
    STATUS current
    DESCRIPTION
        "Airsys HVAC return to normal actions to perform for 
        outdoor probe broken alarm notification"
    ::= { evHVACAirsysAlarm 55 }
    --1.3.6.1.4.1.3052.10.2.12.19.4.2.55

evHVACAirsysOutProbeNormTrapNum OBJECT-TYPE
    SYNTAX Integer32 (548..1199)
    MAX-ACCESS read-write
    STATUS current
    DESCRIPTION
        "Airsys HVAC return to normal trap number for outdoor probe 
        broken alarm notification"
    ::= { evHVACAirsysAlarm 56 }
    --1.3.6.1.4.1.3052.10.2.12.19.4.2.56

evHVACAirsysOutProbeNormClass OBJECT-TYPE
    SYNTAX DisplayString
    MAX-ACCESS read-write
    STATUS current
    DESCRIPTION
        "Airsys HVAC return to normal class for outdoor probe broken 
        alarm notification"
    ::= { evHVACAirsysAlarm 57 }
    --1.3.6.1.4.1.3052.10.2.12.19.4.2.57

evHVACAirsysBothCompressEnable OBJECT-TYPE
    SYNTAX DisplayString
    MAX-ACCESS read-write
    STATUS current
    DESCRIPTION
        "Airsys HVAC unit both compressors on alarm enable"
    ::= { evHVACAirsysAlarm 58 }
    --1.3.6.1.4.1.3052.10.2.12.19.4.2.58

evHVACAirsysBothCompressActions OBJECT-TYPE
    SYNTAX DisplayString
    MAX-ACCESS read-write
    STATUS current
    DESCRIPTION
        "Airsys HVAC actions to perform for both compressors on 
        alarm notification"
    ::= { evHVACAirsysAlarm 59 }
    --1.3.6.1.4.1.3052.10.2.12.19.4.2.59

evHVACAirsysBothCompressTrapnum OBJECT-TYPE
    SYNTAX Integer32 (548..1199)
    MAX-ACCESS read-write
    STATUS current
    DESCRIPTION
        "Airsys HVAC trap number for both compressors on alarm 
        notification"
    ::= { evHVACAirsysAlarm 60 }
    --1.3.6.1.4.1.3052.10.2.12.19.4.2.60

evHVACAirsysBothCompressClass OBJECT-TYPE
    SYNTAX DisplayString
    MAX-ACCESS read-write
    STATUS current
    DESCRIPTION
        "Airsys HVAC alarm class for both compressors on alarm 
        notification"
    ::= { evHVACAirsysAlarm 61 }
    --1.3.6.1.4.1.3052.10.2.12.19.4.2.61

evHVACAirsysBothCompressNormActions OBJECT-TYPE
    SYNTAX DisplayString
    MAX-ACCESS read-write
    STATUS current
    DESCRIPTION
        "Airsys HVAC return to normal actions to perform for 
        both compressors on alarm notification"
    ::= { evHVACAirsysAlarm 62 }
    --1.3.6.1.4.1.3052.10.2.12.19.4.2.62

evHVACAirsysBothCompressNormTrapNum OBJECT-TYPE
    SYNTAX Integer32 (548..1199)
    MAX-ACCESS read-write
    STATUS current
    DESCRIPTION
        "Airsys HVAC return to normal trap number for both 
        compressors on alarm notification"
    ::= { evHVACAirsysAlarm 63 }
    --1.3.6.1.4.1.3052.10.2.12.19.4.2.63

evHVACAirsysBothCompressNormClass OBJECT-TYPE
    SYNTAX DisplayString
    MAX-ACCESS read-write
    STATUS current
    DESCRIPTION
        "Airsys HVAC return to normal class for both compressors on 
        alarm notification"
    ::= { evHVACAirsysAlarm 64 }
    --1.3.6.1.4.1.3052.10.2.12.19.4.2.64

evHVACAirsysGeneratorEnable OBJECT-TYPE
    SYNTAX DisplayString
    MAX-ACCESS read-write
    STATUS current
    DESCRIPTION
        "Airsys HVAC unit generator running alarm enable"
    ::= { evHVACAirsysAlarm 65 }
    --1.3.6.1.4.1.3052.10.2.12.19.4.2.65

evHVACAirsysGeneratorActions OBJECT-TYPE
    SYNTAX DisplayString
    MAX-ACCESS read-write
    STATUS current
    DESCRIPTION
        "Airsys HVAC actions to perform for generator running 
        alarm notification"
    ::= { evHVACAirsysAlarm 66 }
    --1.3.6.1.4.1.3052.10.2.12.19.4.2.66

evHVACAirsysGeneratorTrapnum OBJECT-TYPE
    SYNTAX Integer32 (548..1199)
    MAX-ACCESS read-write
    STATUS current
    DESCRIPTION
        "Airsys HVAC trap number for generator running alarm 
        notification"
    ::= { evHVACAirsysAlarm 67 }
    --1.3.6.1.4.1.3052.10.2.12.19.4.2.67

evHVACAirsysGeneratorClass OBJECT-TYPE
    SYNTAX DisplayString
    MAX-ACCESS read-write
    STATUS current
    DESCRIPTION
        "Airsys HVAC alarm class for generator running alarm 
        notification"
    ::= { evHVACAirsysAlarm 68 }
    --1.3.6.1.4.1.3052.10.2.12.19.4.2.68

evHVACAirsysGeneratorNormActions OBJECT-TYPE
    SYNTAX DisplayString
    MAX-ACCESS read-write
    STATUS current
    DESCRIPTION
        "Airsys HVAC return to normal actions to perform for 
        generator running alarm notification"
    ::= { evHVACAirsysAlarm 69 }
    --1.3.6.1.4.1.3052.10.2.12.19.4.2.69

evHVACAirsysGeneratorNormTrapNum OBJECT-TYPE
    SYNTAX Integer32 (548..1199)
    MAX-ACCESS read-write
    STATUS current
    DESCRIPTION
        "Airsys HVAC return to normal trap number for generator 
        running alarm notification"
    ::= { evHVACAirsysAlarm 70 }
    --1.3.6.1.4.1.3052.10.2.12.19.4.2.70

evHVACAirsysGeneratorNormClass OBJECT-TYPE
    SYNTAX DisplayString
    MAX-ACCESS read-write
    STATUS current
    DESCRIPTION
        "Airsys HVAC return to normal class for generator running 
        alarm notification"
    ::= { evHVACAirsysAlarm 71 }
    --1.3.6.1.4.1.3052.10.2.12.19.4.2.71

evHVACAirsysConnectionEnable OBJECT-TYPE
    SYNTAX DisplayString
    MAX-ACCESS read-write
    STATUS current
    DESCRIPTION
        "Airsys HVAC unit lost connection alarm enable"
    ::= { evHVACAirsysAlarm 72 }
    --1.3.6.1.4.1.3052.10.2.12.19.4.2.72

evHVACAirsysConnectionActions OBJECT-TYPE
    SYNTAX DisplayString
    MAX-ACCESS read-write
    STATUS current
    DESCRIPTION
        "Airsys HVAC actions to perform for lost connection 
        alarm notification"
    ::= { evHVACAirsysAlarm 73 }
    --1.3.6.1.4.1.3052.10.2.12.19.4.2.73

evHVACAirsysConnectionTrapnum OBJECT-TYPE
    SYNTAX Integer32 (548..1199)
    MAX-ACCESS read-write
    STATUS current
    DESCRIPTION
        "Airsys HVAC trap number for lost connection alarm 
        notification"
    ::= { evHVACAirsysAlarm 74 }
    --1.3.6.1.4.1.3052.10.2.12.19.4.2.74

evHVACAirsysConnectionClass OBJECT-TYPE
    SYNTAX DisplayString
    MAX-ACCESS read-write
    STATUS current
    DESCRIPTION
        "Airsys HVAC alarm class for lost connection alarm 
        notification"
    ::= { evHVACAirsysAlarm 75 }
    --1.3.6.1.4.1.3052.10.2.12.19.4.2.75

evHVACAirsysConnectionNormActions OBJECT-TYPE
    SYNTAX DisplayString
    MAX-ACCESS read-write
    STATUS current
    DESCRIPTION
        "Airsys HVAC return to normal actions to perform for 
        lost connection alarm notification"
    ::= { evHVACAirsysAlarm 76 }
    --1.3.6.1.4.1.3052.10.2.12.19.4.2.76

evHVACAirsysConnectionNormTrapNum OBJECT-TYPE
    SYNTAX Integer32 (548..1199)
    MAX-ACCESS read-write
    STATUS current
    DESCRIPTION
        "Airsys HVAC return to normal trap number for lost 
        connection alarm notification"
    ::= { evHVACAirsysAlarm 77 }
    --1.3.6.1.4.1.3052.10.2.12.19.4.2.77

evHVACAirsysConnectionNormClass OBJECT-TYPE
    SYNTAX DisplayString
    MAX-ACCESS read-write
    STATUS current
    DESCRIPTION
        "Airsys HVAC return to normal class for lost connection 
        alarm notification"
    ::= { evHVACAirsysAlarm 78 }
    --1.3.6.1.4.1.3052.10.2.12.19.4.2.78

evHVACAirsysTempBaseThresh OBJECT-TYPE
    SYNTAX DisplayString
    MAX-ACCESS read-write
    STATUS current
    DESCRIPTION
        "Airsys HVAC temperature base threshold"
    ::= { evHVACAirsysTemp 1 }
    --1.3.6.1.4.1.3052.10.2.12.19.4.3.1

evHVACAirsysTempCoolDeadband OBJECT-TYPE
    SYNTAX DisplayString
    MAX-ACCESS read-write
    STATUS current
    DESCRIPTION
        "Airsys HVAC temperature cool deadband"
    ::= { evHVACAirsysTemp 2 }
    --1.3.6.1.4.1.3052.10.2.12.19.4.3.2

evHVACAirsysTempHeatDeadband OBJECT-TYPE
    SYNTAX DisplayString
    MAX-ACCESS read-write
    STATUS current
    DESCRIPTION
        "Airsys HVAC temperature heat deadband"
    ::= { evHVACAirsysTemp 3 }
    --1.3.6.1.4.1.3052.10.2.12.19.4.3.3

evHVACAirsysTempHighValue OBJECT-TYPE
    SYNTAX DisplayString
    MAX-ACCESS read-write
    STATUS current
    DESCRIPTION
        "Airsys HVAC high temperature alarm value"
    ::= { evHVACAirsysTemp 4 }
    --1.3.6.1.4.1.3052.10.2.12.19.4.3.4

evHVACAirsysTempLowValue OBJECT-TYPE
    SYNTAX DisplayString
    MAX-ACCESS read-write
    STATUS current
    DESCRIPTION
        "Airsys HVAC low temperature alarm value"
    ::= { evHVACAirsysTemp 5 }
    --1.3.6.1.4.1.3052.10.2.12.19.4.3.5

evHVACAirsysHumidMaxFree OBJECT-TYPE
    SYNTAX Integer32 (0..99)
    MAX-ACCESS read-write
    STATUS current
    DESCRIPTION
        "Airsys HVAC return to normal class for lost connection 
        alarm notification"
    ::= { evHVACAirsysHumid 1 }
    --1.3.6.1.4.1.3052.10.2.12.19.4.4.1

evHVACAirsysHumidDeadband OBJECT-TYPE
    SYNTAX Integer32 (0..99)
    MAX-ACCESS read-write
    STATUS current
    DESCRIPTION
        "Airsys HVAC return to normal class for lost connection 
        alarm notification"
    ::= { evHVACAirsysHumid 2 }
    --1.3.6.1.4.1.3052.10.2.12.19.4.4.2


--***************************************************************************************
--EVPS Section   2.12.20
--***************************************************************************************

evpsEnable OBJECT-TYPE
    SYNTAX DisplayString
    MAX-ACCESS read-write
    STATUS current
    DESCRIPTION
        "EVPS (Emerson Vortex Power System) enable."
    ::= { evEvps 1 }
    --1.3.6.1.4.1.3052.10.2.12.20.1

evpsIPAddress OBJECT-TYPE
    SYNTAX IpAddress
    MAX-ACCESS read-write
    STATUS current
    DESCRIPTION
        "EVPS IP address."
    ::= { evEvps 2 }
    --1.3.6.1.4.1.3052.10.2.12.20.2

evpsPort OBJECT-TYPE
    SYNTAX Integer32
    MAX-ACCESS read-write
    STATUS current
    DESCRIPTION
        "EVPS IP web port."
    ::= { evEvps 3 }
    --1.3.6.1.4.1.3052.10.2.12.20.3

evpsTimeout OBJECT-TYPE
    SYNTAX Integer32
    MAX-ACCESS read-write
    STATUS current
    DESCRIPTION
        "EVPS IP timeout."
    ::= { evEvps 4 }
    --1.3.6.1.4.1.3052.10.2.12.20.4


--***************************************************************************************
--Access Control Device Management Section   2.12.21
--***************************************************************************************

acActions OBJECT-TYPE
    SYNTAX DisplayString
    MAX-ACCESS read-write
    STATUS current
    DESCRIPTION
        "Actions for the access control event."
    ::= { accessControl 2 }
    --1.3.6.1.4.1.3052.10.2.12.21.2

acTrapnum OBJECT-TYPE
    SYNTAX Integer32
    MAX-ACCESS read-write
    STATUS current
    DESCRIPTION
        "Trap number for the access control event."
    ::= { accessControl 3 }
    --1.3.6.1.4.1.3052.10.2.12.21.3

acClass OBJECT-TYPE
    SYNTAX DisplayString
    MAX-ACCESS read-write
    STATUS current
    DESCRIPTION
        "Class (severity) for the access control event."
    ::= { accessControl 4 }
    --1.3.6.1.4.1.3052.10.2.12.21.4

accessControlDeviceTable OBJECT-TYPE
    SYNTAX SEQUENCE OF AccessControlDevice
    MAX-ACCESS not-accessible
    STATUS current
    DESCRIPTION
        "Table of access control devices for Access Control Device Management."
    ::= { accessControl 10 }
    --1.3.6.1.4.1.3052.10.2.12.21.10

accessControlDeviceEntry OBJECT-TYPE
    SYNTAX AccessControlDevice
    MAX-ACCESS not-accessible
    STATUS current
    DESCRIPTION
        "Entry for table of access control devices for Access Control Device Management."
    INDEX { acdIndex }
    ::= { accessControlDeviceTable 1 }
    --1.3.6.1.4.1.3052.10.2.12.21.10.1

acdIndex OBJECT-TYPE
    SYNTAX Integer32 (1..3)
    MAX-ACCESS read-only
    STATUS current
    DESCRIPTION
        "Index for table of access control devices for Access Control Device Management."
    ::= { accessControlDeviceEntry 1 }
    --1.3.6.1.4.1.3052.10.2.12.21.10.1.1

acdEnable OBJECT-TYPE
    SYNTAX DisplayString
    MAX-ACCESS read-write
    STATUS current
    DESCRIPTION
        "Enable management for this access control device."
    ::= { accessControlDeviceEntry 2 }
    --1.3.6.1.4.1.3052.10.2.12.21.10.1.2

acdName OBJECT-TYPE
    SYNTAX DisplayString
    MAX-ACCESS read-write
    STATUS current
    DESCRIPTION
        "The name of the access control device for informational purpose only."
    ::= { accessControlDeviceEntry 3 }
    --1.3.6.1.4.1.3052.10.2.12.21.10.1.3

acdReader OBJECT-TYPE
    SYNTAX DisplayString
    MAX-ACCESS read-write
    STATUS current
    DESCRIPTION
        "The kind of access control device."
    ::= { accessControlDeviceEntry 4 }
    --1.3.6.1.4.1.3052.10.2.12.21.10.1.4

acdWiegandES OBJECT-TYPE
    SYNTAX Integer32
    MAX-ACCESS read-write
    STATUS current
    DESCRIPTION
        "Index of the Wiegand interface hardware instance allocated as the access control device."
    ::= { accessControlDeviceEntry 5 }
    --1.3.6.1.4.1.3052.10.2.12.21.10.1.5

acdWiegandPoint OBJECT-TYPE
    SYNTAX Integer32 (1..2)
    MAX-ACCESS read-write
    STATUS current
    DESCRIPTION
        "Which wiegand on the wiegand EventSensor to use for as the access control device."
    ::= { accessControlDeviceEntry 6 }
    --1.3.6.1.4.1.3052.10.2.12.21.10.1.6

acdRelayType OBJECT-TYPE
    SYNTAX DisplayString
    MAX-ACCESS read-write
    STATUS current
    DESCRIPTION
        "Type of relay which activates the door strike."
    ::= { accessControlDeviceEntry 7 }
    --1.3.6.1.4.1.3052.10.2.12.21.10.1.7

acdRelayES OBJECT-TYPE
    SYNTAX Integer32
    MAX-ACCESS read-write
    STATUS current
    DESCRIPTION
        "Which relay EventSensor is connected to the door strike."
    ::= { accessControlDeviceEntry 8 }
    --1.3.6.1.4.1.3052.10.2.12.21.10.1.8

acdRelayPoint OBJECT-TYPE
    SYNTAX Integer32
    MAX-ACCESS read-write
    STATUS current
    DESCRIPTION
        "Which relay on the relay EventSensor is connected to the door strike."
    ::= { accessControlDeviceEntry 9 }
    --1.3.6.1.4.1.3052.10.2.12.21.10.1.9

acdOpenTime OBJECT-TYPE
    SYNTAX Integer32 (1..25)
    MAX-ACCESS read-write
    STATUS current
    DESCRIPTION
        ""
    ::= { accessControlDeviceEntry 10 }
    --1.3.6.1.4.1.3052.10.2.12.21.10.1.10

acdUserGroup OBJECT-TYPE
    SYNTAX Integer32 (1..2)
    MAX-ACCESS read-write
    STATUS current
    DESCRIPTION
        "User group to which this access control device applies."
    ::= { accessControlDeviceEntry 11 }
    --1.3.6.1.4.1.3052.10.2.12.21.10.1.11

accessControlUserTable OBJECT-TYPE
    SYNTAX SEQUENCE OF AccessControlUser
    MAX-ACCESS not-accessible
    STATUS current
    DESCRIPTION
        "Table of access control users for Access Control Device Management."
    ::= { accessControl 11 }
    --1.3.6.1.4.1.3052.10.2.12.21.11

accessControlUserEntry OBJECT-TYPE
    SYNTAX AccessControlUser
    MAX-ACCESS not-accessible
    STATUS current
    DESCRIPTION
        "Entry for table of access control users for Access Control Device Management."
    INDEX { acuIndexUserGroup, acuIndexUser }
    ::= { accessControlUserTable 1 }
    --1.3.6.1.4.1.3052.10.2.12.21.11.1

acuIndexUserGroup OBJECT-TYPE
    SYNTAX Integer32 (1..2)
    MAX-ACCESS read-only
    STATUS current
    DESCRIPTION
        "Index for table of access control devices for Access Control Device Management
        which corresponds to the user group containing the user."
    ::= { accessControlUserEntry 1 }
    --1.3.6.1.4.1.3052.10.2.12.21.10.1.1

acuIndexUser OBJECT-TYPE
    SYNTAX Integer32 (1..50)
    MAX-ACCESS read-only
    STATUS current
    DESCRIPTION
        "Index for table of access control devices for Access Control Device Management
        which corresponds to the user within the user group."
    ::= { accessControlUserEntry 2 }
    --1.3.6.1.4.1.3052.10.2.12.21.10.1.2

acuEnable OBJECT-TYPE
    SYNTAX DisplayString
    MAX-ACCESS read-write
    STATUS current
    DESCRIPTION
        "Enable this access control user."
    ::= { accessControlUserEntry 3 }
    --1.3.6.1.4.1.3052.10.2.12.21.10.1.3

acuName OBJECT-TYPE
    SYNTAX DisplayString
    MAX-ACCESS read-write
    STATUS current
    DESCRIPTION
        "Name for this access control user."
    ::= { accessControlUserEntry 4 }
    --1.3.6.1.4.1.3052.10.2.12.21.10.1.4

acuSn OBJECT-TYPE
    SYNTAX DisplayString
    MAX-ACCESS read-write
    STATUS current
    DESCRIPTION
        "Serial number of the card associated with the user."
    ::= { accessControlUserEntry 5 }
    --1.3.6.1.4.1.3052.10.2.12.21.10.1.5

acuSunBegin OBJECT-TYPE
    SYNTAX DisplayString
    MAX-ACCESS read-write
    STATUS current
    DESCRIPTION
        "Time of day (HH:MM) on Sundays when this user should be granted access."
    ::= { accessControlUserEntry 6 }
    --1.3.6.1.4.1.3052.10.2.12.21.10.1.6

acuSunEnd OBJECT-TYPE
    SYNTAX DisplayString
    MAX-ACCESS read-write
    STATUS current
    DESCRIPTION
        "Time of day (HH:MM) on Sundays when this user should be forbidden access."
    ::= { accessControlUserEntry 7 }
    --1.3.6.1.4.1.3052.10.2.12.21.10.1.7

acuMonBegin OBJECT-TYPE
    SYNTAX DisplayString
    MAX-ACCESS read-write
    STATUS current
    DESCRIPTION
        "Time of day (HH:MM) on Mondays when this user should be granted access."
    ::= { accessControlUserEntry 8 }
    --1.3.6.1.4.1.3052.10.2.12.21.10.1.8

acuMonEnd OBJECT-TYPE
    SYNTAX DisplayString
    MAX-ACCESS read-write
    STATUS current
    DESCRIPTION
        "Time of day (HH:MM) on Mondays when this user should be forbidden access."
    ::= { accessControlUserEntry 9 }
    --1.3.6.1.4.1.3052.10.2.12.21.10.1.9

acuTueBegin OBJECT-TYPE
    SYNTAX DisplayString
    MAX-ACCESS read-write
    STATUS current
    DESCRIPTION
        "Time of day (HH:MM) on Tuesdays when this user should be granted access."
    ::= { accessControlUserEntry 10 }
    --1.3.6.1.4.1.3052.10.2.12.21.10.1.10

acuTueEnd OBJECT-TYPE
    SYNTAX DisplayString
    MAX-ACCESS read-write
    STATUS current
    DESCRIPTION
        "Time of day (HH:MM) on Tuesdays when this user should be forbidden access."
    ::= { accessControlUserEntry 11 }
    --1.3.6.1.4.1.3052.10.2.12.21.10.1.11

acuWedBegin OBJECT-TYPE
    SYNTAX DisplayString
    MAX-ACCESS read-write
    STATUS current
    DESCRIPTION
        "Time of day (HH:MM) on Wednesdays when this user should be granted access."
    ::= { accessControlUserEntry 12 }
    --1.3.6.1.4.1.3052.10.2.12.21.10.1.12

acuWedEnd OBJECT-TYPE
    SYNTAX DisplayString
    MAX-ACCESS read-write
    STATUS current
    DESCRIPTION
        "Time of day (HH:MM) on Wednesdays when this user should be forbidden access."
    ::= { accessControlUserEntry 13 }
    --1.3.6.1.4.1.3052.10.2.12.21.10.1.13

acuThuBegin OBJECT-TYPE
    SYNTAX DisplayString
    MAX-ACCESS read-write
    STATUS current
    DESCRIPTION
        "Time of day (HH:MM) on Thursdays when this user should be granted access."
    ::= { accessControlUserEntry 14 }
    --1.3.6.1.4.1.3052.10.2.12.21.10.1.14

acuThuEnd OBJECT-TYPE
    SYNTAX DisplayString
    MAX-ACCESS read-write
    STATUS current
    DESCRIPTION
        "Time of day (HH:MM) on Thursdays when this user should be forbidden access."
    ::= { accessControlUserEntry 15 }
    --1.3.6.1.4.1.3052.10.2.12.21.10.1.15

acuFriBegin OBJECT-TYPE
    SYNTAX DisplayString
    MAX-ACCESS read-write
    STATUS current
    DESCRIPTION
        "Time of day (HH:MM) on Fridays when this user should be granted access."
    ::= { accessControlUserEntry 16 }
    --1.3.6.1.4.1.3052.10.2.12.21.10.1.16

acuFriEnd OBJECT-TYPE
    SYNTAX DisplayString
    MAX-ACCESS read-write
    STATUS current
    DESCRIPTION
        "Time of day (HH:MM) on Fridays when this user should be forbidden access."
    ::= { accessControlUserEntry 17 }
    --1.3.6.1.4.1.3052.10.2.12.21.10.1.17

acuSatBegin OBJECT-TYPE
    SYNTAX DisplayString
    MAX-ACCESS read-write
    STATUS current
    DESCRIPTION
        "Time of day (HH:MM) on Saturdays when this user should be granted access."
    ::= { accessControlUserEntry 18 }
    --1.3.6.1.4.1.3052.10.2.12.21.10.1.18

acuSatEnd OBJECT-TYPE
    SYNTAX DisplayString
    MAX-ACCESS read-write
    STATUS current
    DESCRIPTION
        "Time of day (HH:MM) on Saturdays when this user should be forbidden access."
    ::= { accessControlUserEntry 19 }
    --1.3.6.1.4.1.3052.10.2.12.21.10.1.19



--***************************************************************************************
--Telemetry Section 2.12.22
--***************************************************************************************

telemetryTable OBJECT-TYPE
    SYNTAX SEQUENCE OF TelemetryPoint
    MAX-ACCESS not-accessible
    STATUS current
    DESCRIPTION
        ""
    ::= { telemetry 1 }
    --1.3.6.1.4.1.3052.10.2.12.22.1

telemetryEntry OBJECT-TYPE
    SYNTAX TelemetryPoint
    MAX-ACCESS not-accessible
    STATUS current
    DESCRIPTION
        "Entry for table of telemetry points"
    INDEX { telemetryPointIndex }
    ::= { telemetryTable 1 }
    --1.3.6.1.4.1.3052.10.2.12.22.1.1

telemetryPointIndex OBJECT-TYPE
    SYNTAX Integer32 (1..256)
    MAX-ACCESS read-only
    STATUS current
    DESCRIPTION
        "Index for table of telemetry points."
    ::= { telemetryEntry 1 }
    --1.3.6.1.4.1.3052.10.2.12.22.1.1.1

telemetryPointName OBJECT-TYPE
    SYNTAX DisplayString
    MAX-ACCESS read-write
    STATUS current
    DESCRIPTION
        "Name of telemetry point for information purpose only."
    ::= { telemetryEntry 2 }
    --1.3.6.1.4.1.3052.10.2.12.22.1.1.2

telemetryPointKey OBJECT-TYPE
    SYNTAX DisplayString
    MAX-ACCESS read-write
    STATUS current
    DESCRIPTION
        "Key for telemetry point that specifies the telemetry data source."
    ::= { telemetryEntry 3 }
    --1.3.6.1.4.1.3052.10.2.12.22.1.1.3

telemetryPointType OBJECT-TYPE
    SYNTAX DisplayString
    MAX-ACCESS read-write
    STATUS current
    DESCRIPTION
        "DNP3 type for telemetry point"
    ::= { telemetryEntry 4 }
    --1.3.6.1.4.1.3052.10.2.12.22.1.1.4

telemetryPointClass OBJECT-TYPE
    SYNTAX DisplayString
    MAX-ACCESS read-write
    STATUS current
    DESCRIPTION
        "DNP3 class for telemetry point"
    ::= { telemetryEntry 5 }
    --1.3.6.1.4.1.3052.10.2.12.22.1.1.5

telemetryPointDeadband OBJECT-TYPE
    SYNTAX DisplayString
    MAX-ACCESS read-write
    STATUS current
    DESCRIPTION
        "Deadband for telemetry point"
    ::= { telemetryEntry 6 }
    --1.3.6.1.4.1.3052.10.2.12.22.1.1.6

telemetryPointShortcode OBJECT-TYPE
    SYNTAX DisplayString
    MAX-ACCESS read-write
    STATUS current
    DESCRIPTION
        "Shortcode for telemetry point"
    ::= { telemetryEntry 7 }
    --1.3.6.1.4.1.3052.10.2.12.22.1.1.7

--***************************************************************************************
--Site Security Section   2.12.23
--***************************************************************************************

siteSecIntrusionTable OBJECT-TYPE
    SYNTAX SEQUENCE OF SiteSecIntrusion
    MAX-ACCESS not-accessible
    STATUS current
    DESCRIPTION
        "Table of for Site Security"
    ::= { siteSecurity 1 }
    --1.3.6.1.4.1.3052.10.2.12.23.1

siteSecEnable OBJECT-TYPE
    SYNTAX DisplayString
    MAX-ACCESS read-write
    STATUS current
    DESCRIPTION
       "Security zone 1 to 10 is ON or OFF stating that a zone is configured properly"
    ::= { siteSecIntrusionTable 1 }
    --1.3.6.1.4.1.3052.10.2.12.23.1.1

siteSecDisarmed OBJECT-TYPE 
    SYNTAX DisplayString
    MAX-ACCESS read-write
    STATUS current
    DESCRIPTION
       "ON or OFF if ON the zone will not detect intrusion because it is disarmed, OFF arms the zone to detect intrusion"
    ::= { siteSecIntrusionTable 2 }
    --1.3.6.1.4.1.3052.10.2.12.23.1.2


siteSecName OBJECT-TYPE 
    SYNTAX DisplayString
    MAX-ACCESS read-write
    STATUS current
    DESCRIPTION
       "The name given to the zone"
    ::= { siteSecIntrusionTable 3 }
    --1.3.6.1.4.1.3052.10.2.12.23.1.3


siteSecState OBJECT-TYPE      
    SYNTAX DisplayString
    MAX-ACCESS read-write
    STATUS current
    DESCRIPTION
       "ALARM/DISARMED/DISABLED/INTRUDER/REARMING one of five states the zone is in"
    ::= { siteSecIntrusionTable 4 }
    --1.3.6.1.4.1.3052.10.2.12.23.1.4


siteSecSensorES OBJECT-TYPE 
    SYNTAX Integer32
    MAX-ACCESS read-write
    STATUS current
    DESCRIPTION
       "The Event Sensors related to a particular zone"
    ::= { siteSecIntrusionTable 5 }
    --1.3.6.1.4.1.3052.10.2.12.23.1.5


siteSecSensorPoint OBJECT-TYPE 
    SYNTAX Integer32
    MAX-ACCESS read-write
    STATUS current
    DESCRIPTION
       "The point in conjunction with event-sensor and zone"
    ::= { siteSecIntrusionTable 6 }
    --1.3.6.1.4.1.3052.10.2.12.23.1.6


siteSecIntrusionThreshold OBJECT-TYPE 
    SYNTAX Integer32 (0..255)
    MAX-ACCESS read-write
    STATUS current
    DESCRIPTION
       "Seconds to wait for a disarm event"
    ::= { siteSecIntrusionTable 7 }
    --1.3.6.1.4.1.3052.10.2.12.23.1.7


siteSecReader OBJECT-TYPE 
    SYNTAX DisplayString
    MAX-ACCESS read-write
    STATUS current
    DESCRIPTION
       "Comma separated string of readers that disarms a zone"
    ::= { siteSecIntrusionTable 8 }
    --1.3.6.1.4.1.3052.10.2.12.23.1.8


siteSecReaderThreshold OBJECT-TYPE 
    SYNTAX Integer32 (0..255)
    MAX-ACCESS read-write
    STATUS current
    DESCRIPTION
       "The number of seconds a user has to disable a detected intrusion via the reader configured for the zone"
    ::= { siteSecIntrusionTable 9 }
    --1.3.6.1.4.1.3052.10.2.12.23.1.9


siteSecButtonEnable OBJECT-TYPE 
    SYNTAX DisplayString
    MAX-ACCESS read-write
    STATUS current
    DESCRIPTION
       "Button to disable an alarm is PRESENT/NOT PRESENT"
    ::= { siteSecIntrusionTable 10 }
    --1.3.6.1.4.1.3052.10.2.12.23.1.10


siteSecButtonES OBJECT-TYPE
    SYNTAX Integer32
    MAX-ACCESS read-write
    STATUS current
    DESCRIPTION
       "Configured event-sensor for the Site-Security button"
    ::= { siteSecIntrusionTable 11 }
    --1.3.6.1.4.1.3052.10.2.12.23.1.11


siteSecButtonPoint  OBJECT-TYPE 
    SYNTAX Integer32
    MAX-ACCESS read-write
    STATUS current
    DESCRIPTION
       "Configured pont for the Site-Security button"
    ::= { siteSecIntrusionTable 12 }
    --1.3.6.1.4.1.3052.10.2.12.23.1.12


siteSecButtonType  OBJECT-TYPE 
    SYNTAX DisplayString
    MAX-ACCESS read-write
    STATUS current
    DESCRIPTION
       "Button type configured : MOMENTARY/TOGGLE"
    ::= { siteSecIntrusionTable 13 }
    --1.3.6.1.4.1.3052.10.2.12.23.1.13


siteSecButtonThresholdArm OBJECT-TYPE 
    SYNTAX Integer32
    MAX-ACCESS read-write
    STATUS current
    DESCRIPTION
       "Seconds to hold button to arm a zone"
    ::= { siteSecIntrusionTable 14 }
    --1.3.6.1.4.1.3052.10.2.12.23.1.14


siteSecButtonThresholdDisarm OBJECT-TYPE 
    SYNTAX Integer32
    MAX-ACCESS read-write
    STATUS current
    DESCRIPTION
       "Seconds to hold button to disarm a zone"
    ::= { siteSecIntrusionTable 15 }
    --1.3.6.1.4.1.3052.10.2.12.23.1.15


siteSecSirenEnable OBJECT-TYPE 
    SYNTAX DisplayString
    MAX-ACCESS read-write
    STATUS current
    DESCRIPTION
       "ON/OFF enable realy output for siren"
    ::= { siteSecIntrusionTable 16 }
    --1.3.6.1.4.1.3052.10.2.12.23.1.16


siteSecSirenES OBJECT-TYPE 
    SYNTAX Integer32
    MAX-ACCESS read-write
    STATUS current
    DESCRIPTION
       "Event-sensor relay location of siren for the zone"
    ::= { siteSecIntrusionTable 17 }
    --1.3.6.1.4.1.3052.10.2.12.23.1.17


siteSecSirenPoint OBJECT-TYPE 
    SYNTAX Integer32
    MAX-ACCESS read-write
    STATUS current
    DESCRIPTION
       "Event-sensor point location of siren for the zone"
    ::= { siteSecIntrusionTable 18 }
    --1.3.6.1.4.1.3052.10.2.12.23.1.18


siteSecRearmDelay OBJECT-TYPE 
    SYNTAX Integer32
    MAX-ACCESS read-write
    STATUS current
    DESCRIPTION
       "A delay in seconds after a rearm event before the site is actually rearmed"
    ::= { siteSecIntrusionTable 19 }
    --1.3.6.1.4.1.3052.10.2.12.23.1.19

siteSecMotionTable OBJECT-TYPE
    SYNTAX SEQUENCE OF SiteSecMotion
    MAX-ACCESS not-accessible
    STATUS current
    DESCRIPTION
        "Table of for Site Security motion sensors"
    ::= { siteSecurity 2 }
    --1.3.6.1.4.1.3052.10.2.12.23.2

siteSecMotionES OBJECT-TYPE 
    SYNTAX Integer32
    MAX-ACCESS read-write
    STATUS current
    DESCRIPTION
       "Event-sensor for motion detection device"
    ::= { siteSecMotionTable 1 }
    --1.3.6.1.4.1.3052.10.2.12.23.2.1

 siteSecMotionPoint OBJECT-TYPE 
    SYNTAX Integer32
    MAX-ACCESS read-write
    STATUS current
    DESCRIPTION
       "Point for event-sensor motion detection device"
    ::= { siteSecMotionTable 2 }
    --1.3.6.1.4.1.3052.10.2.12.23.2.2

siteSecMotionEnable OBJECT-TYPE 
    SYNTAX DisplayString
    MAX-ACCESS read-write
    STATUS current
    DESCRIPTION
       "ON/OFF enable or disable motion alarm"
    ::= { siteSecMotionTable 3 }
    --1.3.6.1.4.1.3052.10.2.12.23.2.3

siteSecMotionName OBJECT-TYPE 
    SYNTAX DisplayString
    MAX-ACCESS read-write
    STATUS current
    DESCRIPTION
       "Name of the motion sensor"
    ::= { siteSecMotionTable 4 }
    --1.3.6.1.4.1.3052.10.2.12.23.2.4

siteSecMotionThresholdRearm OBJECT-TYPE 
    SYNTAX Integer32
    MAX-ACCESS read-write
    STATUS current
    DESCRIPTION
       "A threshold to wait for no motion before rearming"
    ::= { siteSecMotionTable 5 }
    --1.3.6.1.4.1.3052.10.2.12.23.2.5

siteSecDoorAjarTable OBJECT-TYPE
    SYNTAX SEQUENCE OF SiteSecDoorAjar
    MAX-ACCESS not-accessible
    STATUS current
    DESCRIPTION
        "Table of for Site Security Door Ajar sensors"
    ::= { siteSecurity 3 }
    --1.3.6.1.4.1.3052.10.2.12.23.3

siteSecDoorAjarEnable OBJECT-TYPE 
    SYNTAX DisplayString
    MAX-ACCESS read-write
    STATUS current
    DESCRIPTION
       "ON/OFF enable or disable door ajar sensor"
    ::= { siteSecDoorAjarTable 1 }
    --1.3.6.1.4.1.3052.10.2.12.23.3.1

siteSecDoorAjarName OBJECT-TYPE 
    SYNTAX DisplayString
    MAX-ACCESS read-write
    STATUS current
    DESCRIPTION
       "Name for the door ajar sensor"
    ::= { siteSecDoorAjarTable 2 }
    --1.3.6.1.4.1.3052.10.2.12.23.3.2

siteSecDoorAjarES OBJECT-TYPE 
    SYNTAX Integer32
    MAX-ACCESS read-write
    STATUS current
    DESCRIPTION
       "Event-sensor for door ajar detection device"

    ::= { siteSecDoorAjarTable 3 }
    --1.3.6.1.4.1.3052.10.2.12.23.3.3

siteSecDoorAjarPoint OBJECT-TYPE 
    SYNTAX Integer32
    MAX-ACCESS read-write
    STATUS current
    DESCRIPTION
       "Point for event-sensor door ajar detection device"

    ::= { siteSecDoorAjarTable 4 }
    --1.3.6.1.4.1.3052.10.2.12.23.3.4

siteSecDoorAjarThresholdNormal OBJECT-TYPE 
    SYNTAX Integer32
    MAX-ACCESS read-write
    STATUS current
    DESCRIPTION
       "Threshold to wait in seconds before tripping the door ajar alarm "
    ::= { siteSecDoorAjarTable 5 }
    --1.3.6.1.4.1.3052.10.2.12.23.3.5

siteSecDoorAjarThresholdExtraTime OBJECT-TYPE 
    SYNTAX Integer32
    MAX-ACCESS read-write
    STATUS current
    DESCRIPTION
       "Extra seconds added to the door ajar threshold for disabled person before door ajar alarm is set"
    ::= { siteSecDoorAjarTable 6 }
    --1.3.6.1.4.1.3052.10.2.12.23.3.6



--***************************************************************************************
--Action Section   2.14
--***************************************************************************************



actionCallNumberTable OBJECT-TYPE
    SYNTAX SEQUENCE OF ActionCallNumberConfig
    MAX-ACCESS not-accessible
    STATUS current
    DESCRIPTION
        "Table of phone numbers to dial for modem actions"
    ::= { action 1 }
    --1.3.6.1.4.1.3052.10.2.14.1

actionCallNumberEntry OBJECT-TYPE
    SYNTAX ActionCallNumberConfig
    MAX-ACCESS not-accessible
    STATUS current
    DESCRIPTION
        "Entry for table of phone numbers to dial for modem actions"
    INDEX { actionCallNumberIndex }
    ::= { actionCallNumberTable 1 }
    --1.3.6.1.4.1.3052.10.2.14.1.1

actionCallNumberIndex OBJECT-TYPE
    SYNTAX Integer32 (1..4)
    MAX-ACCESS read-only
    STATUS current
    DESCRIPTION
        "Index for table of phone numbers to dial for modem actions"
    ::= { actionCallNumberEntry 1 }
    --1.3.6.1.4.1.3052.10.2.14.1.1.1

actionCallNumber OBJECT-TYPE
    SYNTAX DisplayString
    MAX-ACCESS read-write
    STATUS current
    DESCRIPTION
        "The number to dial for this action slot"
    ::= { actionCallNumberEntry 2 }
    --1.3.6.1.4.1.3052.10.2.14.1.1.2

actionPagerTable OBJECT-TYPE
    SYNTAX SEQUENCE OF ActionPagerConfig
    MAX-ACCESS not-accessible
    STATUS current
    DESCRIPTION
        "Table of pager configurations"
    ::= { action 2 }
    --1.3.6.1.4.1.3052.10.2.14.2

actionPagerEntry OBJECT-TYPE
    SYNTAX ActionPagerConfig
    MAX-ACCESS not-accessible
    STATUS current
    DESCRIPTION
        "Entry for table of pager configurations"
    INDEX { actionPagerIndex }
    ::= { actionPagerTable 1 }
    --1.3.6.1.4.1.3052.10.2.14.2.1

actionPagerIndex OBJECT-TYPE
    SYNTAX Integer32 (1..4)
    MAX-ACCESS read-only
    STATUS current
    DESCRIPTION
        "index for table of pager configurations"
    ::= { actionPagerEntry 1 }
    --1.3.6.1.4.1.3052.10.2.14.2.1.1

actionPagerType OBJECT-TYPE
    SYNTAX DisplayString
    MAX-ACCESS read-write
    STATUS current
    DESCRIPTION
        "type of this pager configuration"
    ::= { actionPagerEntry 2 }
    --1.3.6.1.4.1.3052.10.2.14.2.1.2

actionPagerNumber OBJECT-TYPE
    SYNTAX DisplayString
    MAX-ACCESS read-write
    STATUS current
    DESCRIPTION
        "phone number to dial for this pager configuration"
    ::= { actionPagerEntry 3 }
    --1.3.6.1.4.1.3052.10.2.14.2.1.3

actionPagerID OBJECT-TYPE
    SYNTAX DisplayString
    MAX-ACCESS read-write
    STATUS current
    DESCRIPTION
        "ID to use for this pager configuration"
    ::= { actionPagerEntry 4 }
    --1.3.6.1.4.1.3052.10.2.14.2.1.4

actionPagerMessage OBJECT-TYPE
    SYNTAX DisplayString
    MAX-ACCESS read-write
    STATUS current
    DESCRIPTION
        "message to use for this pager configuration"
    ::= { actionPagerEntry 5 }
    --1.3.6.1.4.1.3052.10.2.14.2.1.5

actionPagerPostCalloutDelay OBJECT-TYPE
    SYNTAX Integer32 (0..255)
    MAX-ACCESS read-write
    STATUS current
    DESCRIPTION
        "Seconds to wait after dialing before sending ID"
    ::= { actionPagerEntry 6 }
    --1.3.6.1.4.1.3052.10.2.14.2.1.6

actionPagerPostIDDelay OBJECT-TYPE
    SYNTAX Integer32 (0..255)
    MAX-ACCESS read-write
    STATUS current
    DESCRIPTION
        "Seconds to wait after sending ID to send message"
    ::= { actionPagerEntry 7 }
    --1.3.6.1.4.1.3052.10.2.14.2.1.7

actionSchedEnable OBJECT-TYPE
    SYNTAX DisplayString
    MAX-ACCESS read-write
    STATUS current
    DESCRIPTION
        "ON/OFF enable action schedule"
    ::= { actionSched 1 }
    --1.3.6.1.4.1.3052.10.2.14.3.1

actionSchedBegin OBJECT-TYPE
    SYNTAX DisplayString
    MAX-ACCESS read-write
    STATUS current
    DESCRIPTION
        "action schedule begin time (HH:MM)"
    ::= { actionSched 2 }
    --1.3.6.1.4.1.3052.10.2.14.3.2

actionSchedEnd OBJECT-TYPE
    SYNTAX DisplayString
    MAX-ACCESS read-write
    STATUS current
    DESCRIPTION
        "action schedule end time (HH:MM)"
    ::= { actionSched 3 }
    --1.3.6.1.4.1.3052.10.2.14.3.3

actionSchedWeekdaysOnly OBJECT-TYPE
    SYNTAX DisplayString
    MAX-ACCESS read-write
    STATUS current
    DESCRIPTION
        "ON/OFF whether the action schedule applies to weekdays only
        (ON) or all days (OFF)"
    ::= { actionSched 4 }
    --1.3.6.1.4.1.3052.10.2.14.3.4

actionAsentriaRequireAck OBJECT-TYPE
    SYNTAX DisplayString
    MAX-ACCESS read-write
    STATUS current
    DESCRIPTION
        "ON/OFF Asentria action requires an ack from the receiver"
    ::= { actionAsentria 1 }
    --1.3.6.1.4.1.3052.10.2.14.4.1

actionAsentriaVersion OBJECT-TYPE
    SYNTAX DisplayString
    MAX-ACCESS read-write
    STATUS current
    DESCRIPTION
        "version 1.0 or 1.1"
    ::= { actionAsentria 2 }
    --1.3.6.1.4.1.3052.10.2.14.4.2

actionAsentriaTCPPort OBJECT-TYPE
    SYNTAX Integer32
    MAX-ACCESS read-write
    STATUS current
    DESCRIPTION
        "TCP port used for TCP-based Asentria alarms"
    ::= { actionAsentria 3 }
    --1.3.6.1.4.1.3052.10.2.14.4.3

actionHostTable OBJECT-TYPE
    SYNTAX SEQUENCE OF ActionHostConfig
    MAX-ACCESS not-accessible
    STATUS current
    DESCRIPTION
        "Table of network hosts to use for network-based actions"
    ::= { action 6 }
    --1.3.6.1.4.1.3052.10.2.14.6

actionHostEntry OBJECT-TYPE
    SYNTAX ActionHostConfig
    MAX-ACCESS not-accessible
    STATUS current
    DESCRIPTION
        "Entry for table of network hosts to use for network-based
        actions"
    INDEX { actionHostIndex }
    ::= { actionHostTable 1 }
    --1.3.6.1.4.1.3052.10.2.14.6.1

actionHostIndex OBJECT-TYPE
    SYNTAX Integer32 (1..6)
    MAX-ACCESS read-only
    STATUS current
    DESCRIPTION
        "Index for table of network hosts to use for network-based
        actions"
    ::= { actionHostEntry 1 }
    --1.3.6.1.4.1.3052.10.2.14.6.1.1

actionHost OBJECT-TYPE
    SYNTAX DisplayString
    MAX-ACCESS read-write
    STATUS current
    DESCRIPTION
        "Hostname/IP address used as destination for network-based
        action (e.g., trap)"
    ::= { actionHostEntry 2 }
    --1.3.6.1.4.1.3052.10.2.14.6.1.2

actionEmailTable OBJECT-TYPE
    SYNTAX SEQUENCE OF ActionEmailConfig
    MAX-ACCESS not-accessible
    STATUS current
    DESCRIPTION
        "Table of email addresses to use for email actions"
    ::= { action 7 }
    --1.3.6.1.4.1.3052.10.2.14.7

actionEmailEntry OBJECT-TYPE
    SYNTAX ActionEmailConfig
    MAX-ACCESS not-accessible
    STATUS current
    DESCRIPTION
        "Entry for table of email addresses to use for email actions"
    INDEX { actionEmailIndex }
    ::= { actionEmailTable 1 }
    --1.3.6.1.4.1.3052.10.2.14.7.1

actionEmailIndex OBJECT-TYPE
    SYNTAX Integer32 (1..6)
    MAX-ACCESS read-only
    STATUS current
    DESCRIPTION
        "Index for table of email addresses to use for email actions"
    ::= { actionEmailEntry 1 }
    --1.3.6.1.4.1.3052.10.2.14.7.1.1

actionEmail OBJECT-TYPE
    SYNTAX DisplayString
    MAX-ACCESS read-write
    STATUS current
    DESCRIPTION
        "email address"
    ::= { actionEmailEntry 2 }
    --1.3.6.1.4.1.3052.10.2.14.7.1.2

actionParseError OBJECT-TYPE
    SYNTAX DisplayString
    MAX-ACCESS read-only
    STATUS current
    DESCRIPTION
        "When a user attempts to configure an invalid action setting/
        object, this object says why it was invalid."
    ::= { action 8 }
    --1.3.6.1.4.1.3052.10.2.14.8

--***************************************************************************************
--System Section   2.16
--***************************************************************************************


sysTimeAutoDST OBJECT-TYPE
    SYNTAX DisplayString
    MAX-ACCESS read-write
    STATUS current
    DESCRIPTION
        "ON/OFF automatically adjust for Daylight Savings Time"
    ::= { sysTime 1 }
    --1.3.6.1.4.1.3052.10.2.16.1.1

sysTimeGMTOffset OBJECT-TYPE
    SYNTAX Integer32
    MAX-ACCESS read-write
    STATUS current
    DESCRIPTION
        "Absolute value of offset (hours) from GMT of the timezone"
    ::= { sysTime 2 }
    --1.3.6.1.4.1.3052.10.2.16.1.2

sysTimeGMTDirection OBJECT-TYPE
    SYNTAX DisplayString
    MAX-ACCESS read-write
    STATUS current
    DESCRIPTION
        "Direction (AHEAD/BEHIND) of timezone relative to GMT"
    ::= { sysTime 3 }
    --1.3.6.1.4.1.3052.10.2.16.1.3


sysTimeNetEnable OBJECT-TYPE
    SYNTAX DisplayString
    MAX-ACCESS read-write
    STATUS current
    DESCRIPTION
        "Network time mode"
    ::= { sysTimeNet 1 }
    --1.3.6.1.4.1.3052.10.2.16.1.4.1

sysTimeNetHostTable OBJECT-TYPE
    SYNTAX SEQUENCE OF NetworkTimeHostConfig
    MAX-ACCESS not-accessible
    STATUS current
    DESCRIPTION
        "Table of hosts to use for network time services"
    ::= { sysTimeNet 2 }
    --1.3.6.1.4.1.3052.10.2.16.1.4.2

sysTimeNetHostEntry OBJECT-TYPE
    SYNTAX NetworkTimeHostConfig
    MAX-ACCESS not-accessible
    STATUS current
    DESCRIPTION
        "Entry for table of hosts to use for network time services"
    INDEX { sysTimeNetHostIndex }
    ::= { sysTimeNetHostTable 1 }
    --1.3.6.1.4.1.3052.10.2.16.1.4.2.1

sysTimeNetHostIndex OBJECT-TYPE
    SYNTAX Integer32 (1..6)
    MAX-ACCESS read-only
    STATUS current
    DESCRIPTION
        "Index for table of hosts to use for network time services"
    ::= { sysTimeNetHostEntry 1 }
    --1.3.6.1.4.1.3052.10.2.16.1.4.2.1.1

sysTimeNetHost OBJECT-TYPE
    SYNTAX DisplayString
    MAX-ACCESS read-write
    STATUS current
    DESCRIPTION
        "host to use for network time services"
    ::= { sysTimeNetHostEntry 2 }
    --1.3.6.1.4.1.3052.10.2.16.1.4.2.1.2

sysPTTimeout  OBJECT-TYPE
    SYNTAX Integer32
    MAX-ACCESS read-write
    STATUS current
    DESCRIPTION
        "Timeout (minutes) of inactivity after which a pass-through
        session is terminated (0 means it never terminates)"
    ::= { sysPT 1 }
    --1.3.6.1.4.1.3052.10.2.16.2.1

sysPTEndPause OBJECT-TYPE
    SYNTAX Integer32
    MAX-ACCESS read-write
    STATUS current
    DESCRIPTION
        "number of 16ths of a second between escape characters
        received on pass-through origin IO handle that are reuired
        for the escape characters to register as pass-through escape
        characters in the pass-through escape sequence.  Set to 0 to
        make the escape character register as part of the pass-
        through escape sequence without requiring a pause."
    ::= { sysPT 2 }
    --1.3.6.1.4.1.3052.10.2.16.2.2

sysPTJoinable OBJECT-TYPE
    SYNTAX DisplayString
    MAX-ACCESS read-write
    STATUS current
    DESCRIPTION
        "Enable joinable pass-through sessions."
    ::= { sysPT 3 }
    --1.3.6.1.4.1.3052.10.2.16.2.3

sysMTU OBJECT-TYPE
    SYNTAX Integer32
    MAX-ACCESS read-write
    STATUS current
    DESCRIPTION
        "Maximum transfer unit for ethernet interfaces"
    ::= { sys 3 }
    --1.3.6.1.4.1.3052.10.2.16.3

sysAnswerString OBJECT-TYPE
    SYNTAX DisplayString
    MAX-ACCESS read-write
    STATUS current
    DESCRIPTION
        "String displayed upon login"
    ::= { sys 4 }
    --1.3.6.1.4.1.3052.10.2.16.4

sysEventFileID OBJECT-TYPE
    SYNTAX DisplayString
    MAX-ACCESS read-write
    STATUS current
    DESCRIPTION
        "ID string for events file"
    ::= { sys 6 }
    --1.3.6.1.4.1.3052.10.2.16.6

sysEscapeCharacter OBJECT-TYPE
    SYNTAX Integer32
    MAX-ACCESS read-write
    STATUS current
    DESCRIPTION
        "Decimal ASCII code of the system escape character"
    ::= { sys 7 }
    --1.3.6.1.4.1.3052.10.2.16.7

sysTimeStampTimeFormat OBJECT-TYPE
    SYNTAX DisplayString
    MAX-ACCESS read-write
    STATUS current
    DESCRIPTION
        "Format of time stamp: HH:MM,HH:MM:SS,BLANK"
    ::= { sysTimeStamp 1 }
    --1.3.6.1.4.1.3052.10.2.16.8.1

sysTimeStampDateFormat OBJECT-TYPE
    SYNTAX DisplayString
    MAX-ACCESS read-write
    STATUS current
    DESCRIPTION
        "Format of date stamp: MM/DD,MM/DD/YY,MM/DD/YYYY,BLANK"
    ::= { sysTimeStamp 2 }
    --1.3.6.1.4.1.3052.10.2.16.8.2

sysTimeStampSpaceAfter OBJECT-TYPE
    SYNTAX DisplayString
    MAX-ACCESS read-write
    STATUS current
    DESCRIPTION
        "ON/OFF Inlude a space after timestamp"
    ::= { sysTimeStamp 3 }
    --1.3.6.1.4.1.3052.10.2.16.8.3

sysLogMode OBJECT-TYPE
    SYNTAX DisplayString
    MAX-ACCESS read-write
    STATUS current
    DESCRIPTION
        "Syslog mode: disabled, emit UDP (REMOTE), save in a
        rotating file set (FILE), or emit on a listening socket
        (SERVER)"
    ::= { sysLog 1 }
    --1.3.6.1.4.1.3052.10.2.16.9.1

sysLoghost OBJECT-TYPE
    SYNTAX DisplayString
    MAX-ACCESS read-write
    STATUS current
    DESCRIPTION
        "Syslog host: destination machine when syslog mode is REMOTE"
    ::= { sysLog 2 }
    --1.3.6.1.4.1.3052.10.2.16.9.2

sysLogFilter OBJECT-TYPE
    SYNTAX DisplayString
    MAX-ACCESS read-write
    STATUS current
    DESCRIPTION
        "String describing what functions place data in the syslog"
    ::= { sysLog 3 }
    --1.3.6.1.4.1.3052.10.2.16.9.3

sysLogFileSize OBJECT-TYPE
    SYNTAX Integer32
    MAX-ACCESS read-write
    STATUS current
    DESCRIPTION
        "Size (in KB) of syslog files (when syslog mode is SERVER or
        FILE)"
    ::= { sysLog 4 }
    --1.3.6.1.4.1.3052.10.2.16.9.4

sysLogFileCount OBJECT-TYPE
    SYNTAX Integer32
    MAX-ACCESS read-write
    STATUS current
    DESCRIPTION
        "Number of files in syslog file set (when syslog mode is
        SERVER or FILE)"
    ::= { sysLog 5 }
    --1.3.6.1.4.1.3052.10.2.16.9.5

sysLogListenPort OBJECT-TYPE
    SYNTAX Integer32
    MAX-ACCESS read-write
    STATUS current
    DESCRIPTION
        "TCP port on which the unit listens for a connection on
        which syslog data is dumped (when syslog mode is SERVER)"
    ::= { sysLog 6 }
    --1.3.6.1.4.1.3052.10.2.16.9.6

sysCRDBCapacity OBJECT-TYPE
    SYNTAX Integer32
    MAX-ACCESS read-only
    STATUS current
    DESCRIPTION
        "Capacity of Call Record Database (in KB)"
    ::= { sysCRDB 1 }
    --1.3.6.1.4.1.3052.10.2.16.10.1

sysCRDBPercentFull OBJECT-TYPE
    SYNTAX Integer32
    MAX-ACCESS read-only
    STATUS current
    DESCRIPTION
        "Percent of the CRDB used"
    ::= { sysCRDB 2 }
    --1.3.6.1.4.1.3052.10.2.16.10.2


sysCRDBFileIDTable OBJECT-TYPE
    SYNTAX SEQUENCE OF CRDBFileIDConfig
    MAX-ACCESS not-accessible
    STATUS current
    DESCRIPTION
        "Table of CRDB file IDs"
    ::= { sysCRDB 3 }
    --1.3.6.1.4.1.3052.10.2.16.10.3

sysCRDBFileIDEntry OBJECT-TYPE
    SYNTAX CRDBFileIDConfig
    MAX-ACCESS not-accessible
    STATUS current
    DESCRIPTION
        "Entry for table of CRDB file IDs"
    INDEX { sysCRDBFileIDIndex }
    ::= { sysCRDBFileIDTable 1 }
    --1.3.6.1.4.1.3052.10.2.16.10.3.1

sysCRDBFileIDIndex OBJECT-TYPE
    SYNTAX Integer32 (1..16)
    MAX-ACCESS read-only
    STATUS current
    DESCRIPTION
        "Index for table of CRDB file IDs"
    ::= { sysCRDBFileIDEntry 1 }
    --1.3.6.1.4.1.3052.10.2.16.10.3.1.1

sysCRDBFileID OBJECT-TYPE
    SYNTAX DisplayString
    MAX-ACCESS read-write
    STATUS current
    DESCRIPTION
        "ID of CRDB file for this port-associated file x"
    ::= { sysCRDBFileIDEntry 2 }
    --1.3.6.1.4.1.3052.10.2.16.10.3.1.2

sysCRDBFileEnforceMinTable OBJECT-TYPE
    SYNTAX SEQUENCE OF CRDBFileEnforceMinConfig
    MAX-ACCESS not-accessible
    STATUS current
    DESCRIPTION
        "Table of CRDB file minimum size enforcement settings"
    ::= { sysCRDB 4 }
    --1.3.6.1.4.1.3052.10.2.16.10.4

sysCRDBFileEnforceMinEntry OBJECT-TYPE
    SYNTAX CRDBFileEnforceMinConfig
    MAX-ACCESS not-accessible
    STATUS current
    DESCRIPTION
        "Entry for table of CRDB file minimum size enforcement
        settings"
    INDEX { sysCRDBFileEnforceMinIndex }
    ::= { sysCRDBFileEnforceMinTable 1 }
    --1.3.6.1.4.1.3052.10.2.16.10.4.1

sysCRDBFileEnforceMinIndex OBJECT-TYPE
    SYNTAX Integer32 (1..24)
    MAX-ACCESS read-only
    STATUS current
    DESCRIPTION
        "Index for table of CRDB file minimum size enforcement
        settings"
    ::= { sysCRDBFileEnforceMinEntry 1 }
    --1.3.6.1.4.1.3052.10.2.16.10.4.1.1

sysCRDBFileEnforceMin OBJECT-TYPE
    SYNTAX DisplayString
    MAX-ACCESS read-write
    STATUS current
    DESCRIPTION
        "ON/OFF: enforce minimum size for this CRDB file x"
    ::= { sysCRDBFileEnforceMinEntry 2 }
    --1.3.6.1.4.1.3052.10.2.16.10.4.1.2

sysCharMask OBJECT-TYPE
    SYNTAX OCTET STRING
    MAX-ACCESS read-write
    STATUS current
    DESCRIPTION
        "Character mask used for ignoring certain characters on
        serial ports when assembling data records (when port mode is
        ASCII)"
    ::= { sys 11 }
    --1.3.6.1.4.1.3052.10.2.16.11

sysPrompt OBJECT-TYPE
    SYNTAX DisplayString
    MAX-ACCESS read-write
    STATUS current
    DESCRIPTION
        "Prompt to use in a commnand session"
    ::= { sys 12 }
    --1.3.6.1.4.1.3052.10.2.16.12

sysBootStatus OBJECT-TYPE
    SYNTAX DisplayString
    MAX-ACCESS read-only
    STATUS current
    DESCRIPTION
        "String describing the boot status of the unit (Booted OK/
        still booting"
    ::= { sys 13 }
    --1.3.6.1.4.1.3052.10.2.16.13

--***************************************************************************************
--Sys Location Section 2.16.14
--***************************************************************************************

sysLocLatitude OBJECT-TYPE
    SYNTAX DisplayString
    MAX-ACCESS read-write
    STATUS current
    DESCRIPTION
        "Latitude portion of geographic coordinates as string"
    ::= { sysLoc 1 }
    --1.3.6.1.4.1.3052.10.2.16.14.1

sysLocLongitude OBJECT-TYPE
    SYNTAX DisplayString
    MAX-ACCESS read-write
    STATUS current
    DESCRIPTION
        "Longitude portion of geographic coordinates as string"
    ::= { sysLoc 2 }
    --1.3.6.1.4.1.3052.10.2.16.14.2

sysLocXOffset OBJECT-TYPE
    SYNTAX DisplayString
    MAX-ACCESS read-write
    STATUS current
    DESCRIPTION
        "X-offset portion of geographic coordinates as string"
    ::= { sysLoc 3 }
    --1.3.6.1.4.1.3052.10.2.16.14.3

sysLocYOffset OBJECT-TYPE
    SYNTAX DisplayString
    MAX-ACCESS read-write
    STATUS current
    DESCRIPTION
        "Y offset portion of geographic coordinates as string"
    ::= { sysLoc 4 }
    --1.3.6.1.4.1.3052.10.2.16.14.4

sysLocAngle OBJECT-TYPE
    SYNTAX DisplayString
    MAX-ACCESS read-write
    STATUS current
    DESCRIPTION
        "Angle portion of geographic coordinates as string"
    ::= { sysLoc 5 }
    --1.3.6.1.4.1.3052.10.2.16.14.5

sysLocAltitude OBJECT-TYPE
    SYNTAX DisplayString
    MAX-ACCESS read-write
    STATUS current
    DESCRIPTION
        "Altitude as string"
    ::= { sysLoc 6 }
    --1.3.6.1.4.1.3052.10.2.16.14.6

--***************************************************************************************
--Sys Asset Managment 2.16.15
--***************************************************************************************
sysAMManufacturer OBJECT-TYPE
    SYNTAX DisplayString
    MAX-ACCESS read-only
    STATUS current
    DESCRIPTION
    "Device manufacturer"
    ::= { sysAssetMgmt 1 }
    --1.3.6.1.4.1.3052.10.2.16.15.1

sysAMProduct OBJECT-TYPE
    SYNTAX DisplayString
    MAX-ACCESS read-only
    STATUS current
    DESCRIPTION
    "Device product description (i.e., model or model number)"
    ::= { sysAssetMgmt 2 }
    --1.3.6.1.4.1.3052.10.2.16.15.2

sysAMSerialNumber OBJECT-TYPE
    SYNTAX DisplayString
    MAX-ACCESS read-only
    STATUS current
    DESCRIPTION
    "Manufacturer serial number for device"
    ::= { sysAssetMgmt 3 }
    --1.3.6.1.4.1.3052.10.2.16.15.3

sysAMHardwareOptions OBJECT-TYPE
    SYNTAX DisplayString
    MAX-ACCESS read-only
    STATUS current
    DESCRIPTION
    "Hardware options currently installed on device"
    ::= { sysAssetMgmt 4 }
    --1.3.6.1.4.1.3052.10.2.16.15.4

sysAMSoftwareVersion OBJECT-TYPE
    SYNTAX DisplayString
    MAX-ACCESS read-only
    STATUS current
    DESCRIPTION
    "Currently-running software version on device"
    ::= { sysAssetMgmt 5 }
    --1.3.6.1.4.1.3052.10.2.16.15.5

sysAMSiteName OBJECT-TYPE
    SYNTAX DisplayString
    MAX-ACCESS read-write
    STATUS current
    DESCRIPTION
    "Site Name of device (user definable, also known as the
    siteName object under the productIds branch."
    ::= { sysAssetMgmt 6 }
    --1.3.6.1.4.1.3052.10.2.16.15.6


--***************************************************************************************
--Sys File Transfer Section 2.16.17
--***************************************************************************************

sysFileTransferStatus OBJECT-TYPE
    SYNTAX DisplayString
    MAX-ACCESS read-write
    STATUS current
    DESCRIPTION
        "Start/cancel file transfer, or check transfer status.  To start, set this object
        to 'start'.  To cancel, set this object to 'cancel'.  To check status, get the
        object"
    ::= { sysFileTransfer 1 }
    --1.3.6.1.4.1.3052.10.2.16.17.1

sysFileTransferURL OBJECT-TYPE
    SYNTAX DisplayString
    MAX-ACCESS read-write
    STATUS current
    DESCRIPTION
        "URL (describing protocol, host, directory, and file) on which file transfer
        function operates."
    ::= { sysFileTransfer 2 }
    --1.3.6.1.4.1.3052.10.2.16.17.2

sysFileTransferUsername OBJECT-TYPE
    SYNTAX DisplayString
    MAX-ACCESS read-write
    STATUS current
    DESCRIPTION
        "Username for user account at the resource specified by sysFileTransferURL."
    ::= { sysFileTransfer 3 }
    --1.3.6.1.4.1.3052.10.2.16.17.3

sysFileTransferPassword OBJECT-TYPE
    SYNTAX DisplayString
    MAX-ACCESS read-write
    STATUS current
    DESCRIPTION
        "Password for user account at the resource specified by sysFileTransferURL."
    ::= { sysFileTransfer 4 }
    --1.3.6.1.4.1.3052.10.2.16.17.4

--***************************************************************************************
--Sys Update Section 2.16.18
--***************************************************************************************

sysUpdateStatus OBJECT-TYPE
    SYNTAX DisplayString
    MAX-ACCESS read-only
    STATUS current
    DESCRIPTION
        "Check time/result of last update attempt."
    ::= { sysUpdate 1 }
    --1.3.6.1.4.1.3052.10.2.16.18.1


--***************************************************************************************
--Audit Log Section   2.17
--***************************************************************************************

auditLogEnable OBJECT-TYPE
    SYNTAX DisplayString
    MAX-ACCESS read-write
    STATUS current
    DESCRIPTION
        "ON/OFF enable audit log"
    ::= { auditLog 1 }
    --1.3.6.1.4.1.3052.10.2.17.1

auditLogStoreResets OBJECT-TYPE
    SYNTAX DisplayString
    MAX-ACCESS read-write
    STATUS current
    DESCRIPTION
        "ON/OFF audit log stores when the unit resets"
    ::= { auditLog 2 }
    --1.3.6.1.4.1.3052.10.2.17.1

auditLogStoreCommands OBJECT-TYPE
    SYNTAX DisplayString
    MAX-ACCESS read-write
    STATUS current
    DESCRIPTION
        "ON/OFF audit log stores commands entered in a command
        session"
    ::= { auditLog 3 }
    --1.3.6.1.4.1.3052.10.2.17.1

auditLogStoreOutputs OBJECT-TYPE
    SYNTAX DisplayString
    MAX-ACCESS read-write
    STATUS current
    DESCRIPTION
        "ON/OFF audit log stores output (relay output and power output)
        activity"
    ::= { auditLog 4 }
    --1.3.6.1.4.1.3052.10.2.17.1

auditLogStoreAlarmActions OBJECT-TYPE
    SYNTAX DisplayString
    MAX-ACCESS read-write
    STATUS current
    DESCRIPTION
        "ON/OFF audit log stores action delivery activity"
    ::= { auditLog 5 }
    --1.3.6.1.4.1.3052.10.2.17.1

auditLogStorePwdFailures OBJECT-TYPE
    SYNTAX DisplayString
    MAX-ACCESS read-write
    STATUS current
    DESCRIPTION
        "ON/OFF audit log stores when user was denied login"
    ::= { auditLog 6 }
    --1.3.6.1.4.1.3052.10.2.17.1

auditLogStoreLogins OBJECT-TYPE
    SYNTAX DisplayString
    MAX-ACCESS read-write
    STATUS current
    DESCRIPTION
        "ON/OFF audit log stores when a user was allowed login"
    ::= { auditLog 7 }
    --1.3.6.1.4.1.3052.10.2.17.1

auditLogStoreSHSK OBJECT-TYPE
    SYNTAX DisplayString
    MAX-ACCESS read-write
    STATUS current
    DESCRIPTION
        "ON/OFF audit log stores serial handshaking status
        (regardless of serial handshaking event)"
    ::= { auditLog 8 }
    --1.3.6.1.4.1.3052.10.2.17.1

auditLogStorePassthrough OBJECT-TYPE
    SYNTAX DisplayString
    MAX-ACCESS read-write
    STATUS current
    DESCRIPTION
        "ON/OFF audit log stores pass-through activity"
    ::= { auditLog 9 }
    --1.3.6.1.4.1.3052.10.2.17.1

auditLogStoreInactivity OBJECT-TYPE
    SYNTAX DisplayString
    MAX-ACCESS read-write
    STATUS current
    DESCRIPTION
        "ON/OFF audit log stores when sessions expire due to
        inactivity"
    ::= { auditLog 10 }
    --1.3.6.1.4.1.3052.10.2.17.1

auditLogStorePolling OBJECT-TYPE
    SYNTAX DisplayString
    MAX-ACCESS read-write
    STATUS current
    DESCRIPTION
        "ON/OFF audit log stores CRDB polling activity"
    ::= { auditLog 11 }
    --1.3.6.1.4.1.3052.10.2.17.1

auditLogMaxSize OBJECT-TYPE
    SYNTAX Integer32
    MAX-ACCESS read-write
    STATUS current
    DESCRIPTION
        "Maximum size (in KB) of audit log"
    ::= { auditLog 12 }
    --1.3.6.1.4.1.3052.10.2.17.1

--***************************************************************************************
--Scripting Section   2.17
--***************************************************************************************

scrGlobalEnable OBJECT-TYPE
    SYNTAX DisplayString
    MAX-ACCESS read-write
    STATUS current
    DESCRIPTION
        "ON/OFF enable scripting"
    ::= { scripting 1 }
    --1.3.6.1.4.1.3052.10.2.18.1

scrDTRCtrlPortEnableTable OBJECT-TYPE
    SYNTAX SEQUENCE OF ScriptingDTRCtrlPortEnableConfig
    MAX-ACCESS not-accessible
    STATUS current
    DESCRIPTION
        "Table of DTR control port enables"
    ::= { scripting 2 }
    --1.3.6.1.4.1.3052.10.2.18.2

scrDTRCtrlPortEnableEntry OBJECT-TYPE
    SYNTAX ScriptingDTRCtrlPortEnableConfig
    MAX-ACCESS not-accessible
    STATUS current
    DESCRIPTION
        "Entry for table of DTR control port enables"
    INDEX { scrDTRCtrlPortEnableIndex }
    ::= { scrDTRCtrlPortEnableTable 1 }
    --1.3.6.1.4.1.3052.10.2.18.2.1

scrDTRCtrlPortEnableIndex OBJECT-TYPE
    SYNTAX Integer32 (1..16)
    MAX-ACCESS read-only
    STATUS current
    DESCRIPTION
        "Index for table of DTR control port enables"
    ::= { scrDTRCtrlPortEnableEntry 1 }
    --1.3.6.1.4.1.3052.10.2.18.2.1.1

scrDTRCtrlPortEnable OBJECT-TYPE
    SYNTAX DisplayString
    MAX-ACCESS read-write
    STATUS current
    DESCRIPTION
        "ON/OFF enable DTR control of scripting for this port"
    ::= { scrDTRCtrlPortEnableEntry 2 }
    --1.3.6.1.4.1.3052.10.2.18.2.1.2


scrTable OBJECT-TYPE
    SYNTAX SEQUENCE OF ScriptingConfig
    MAX-ACCESS not-accessible
    STATUS current
    DESCRIPTION
        "Table of scripts"
    ::= { scripting 3 }
    --1.3.6.1.4.1.3052.10.2.18.3

scrEntry OBJECT-TYPE
    SYNTAX ScriptingConfig
    MAX-ACCESS not-accessible
    STATUS current
    DESCRIPTION
        "Entry for table of scripts"
    INDEX { scrIndex }
    ::= { scrTable 1 }
    --1.3.6.1.4.1.3052.10.2.18.3.1

scrIndex OBJECT-TYPE
    SYNTAX Integer32 (1..20)
    MAX-ACCESS read-only
    STATUS current
    DESCRIPTION
        "Index for table of scripts"
    ::= { scrEntry 1 }
    --1.3.6.1.4.1.3052.10.2.18.3.1.1

scrEnable OBJECT-TYPE
    SYNTAX DisplayString
    MAX-ACCESS read-write
    STATUS current
    DESCRIPTION
        "ON/OFF enable this script"
    ::= { scrEntry 2 }
    --1.3.6.1.4.1.3052.10.2.18.3.1.2

scrName OBJECT-TYPE
    SYNTAX DisplayString
    MAX-ACCESS read-write
    STATUS current
    DESCRIPTION
        "Name of this script"
    ::= { scrEntry 3 }
    --1.3.6.1.4.1.3052.10.2.18.3.1.3

scrFilename OBJECT-TYPE
    SYNTAX DisplayString
    MAX-ACCESS read-write
    STATUS current
    DESCRIPTION
        "Filename for this script"
    ::= { scrEntry 4 }
    --1.3.6.1.4.1.3052.10.2.18.3.1.4

scrRunAlways OBJECT-TYPE
    SYNTAX DisplayString
    MAX-ACCESS read-write
    STATUS current
    DESCRIPTION
        "ON/OFF: this script always runs"
    ::= { scrEntry 5 }
    --1.3.6.1.4.1.3052.10.2.18.3.1.5

scrRunAtStartup OBJECT-TYPE
    SYNTAX DisplayString
    MAX-ACCESS read-write
    STATUS current
    DESCRIPTION
        "ON/OFF: this script runs at startup"
    ::= { scrEntry 6 }
    --1.3.6.1.4.1.3052.10.2.18.3.1.6

scrRunScheduled OBJECT-TYPE
    SYNTAX DisplayString
    MAX-ACCESS read-write
    STATUS current
    DESCRIPTION
        "ON/OFF: this script runs at a certain time of day"
    ::= { scrEntry 7 }
    --1.3.6.1.4.1.3052.10.2.18.3.1.7

scrScheduleTime OBJECT-TYPE
    SYNTAX DisplayString
    MAX-ACCESS read-write
    STATUS current
    DESCRIPTION
        "Time of day (HH:MM) this script is scheduled to run"
    ::= { scrEntry 8 }
    --1.3.6.1.4.1.3052.10.2.18.3.1.8

scrArguments OBJECT-TYPE
    SYNTAX DisplayString
    MAX-ACCESS read-write
    STATUS current
    DESCRIPTION
        "Arguments for this script"
    ::= { scrEntry 9 }
    --1.3.6.1.4.1.3052.10.2.18.3.1.9

scrRepeatInterval OBJECT-TYPE
    SYNTAX Integer32
    MAX-ACCESS read-write
    STATUS current
    DESCRIPTION
        "How often this script runs (minutes)"
    ::= { scrEntry 10 }
    --1.3.6.1.4.1.3052.10.2.18.3.1.10

scrVolatileStringTable OBJECT-TYPE
    SYNTAX SEQUENCE OF ScriptingVolatileString
    MAX-ACCESS not-accessible
    STATUS current
    DESCRIPTION
        "Table of volatile string settings for use in
         scripts."
    ::= { scripting 4 }
    --1.3.6.1.4.1.3052.10.2.18.4

scrVolatileStringEntry OBJECT-TYPE
    SYNTAX ScriptingVolatileString
    MAX-ACCESS not-accessible
    STATUS current
    DESCRIPTION
        "Entry for table of volatile script string
        settings"
    INDEX { scrVolatileStringIndex }
    ::= { scrVolatileStringTable 1 }
    --1.3.6.1.4.1.3052.10.2.18.4.1

scrVolatileStringIndex OBJECT-TYPE
    SYNTAX Integer32 (1..50)
    MAX-ACCESS read-only
    STATUS current
    DESCRIPTION
        "Index for table of volatile script string
        settings"
    ::= { scrVolatileStringEntry 1 }
    --1.3.6.1.4.1.3052.10.2.18.4.1.1

scrVolatileString OBJECT-TYPE
    SYNTAX DisplayString
    MAX-ACCESS read-write
    STATUS current
    DESCRIPTION
        "Volatile string for use in scripts. Use this
         object to cache frequently-changing string values
         or string values that do not need to persist
         through reset.  This object corresponds to the
         scripting.vstring[] setting key branch; use those
         keys in scripts and you can view or change their
         values with this object."
    ::= { scrVolatileStringEntry 2 }
    --1.3.6.1.4.1.3052.10.2.18.4.1.2

scrVolatileIntTable OBJECT-TYPE
    SYNTAX SEQUENCE OF ScriptingVolatileInt
    MAX-ACCESS not-accessible
    STATUS current
    DESCRIPTION
        "Table of volatile integer settings for use in
         scripts."
    ::= { scripting 5 }
    --1.3.6.1.4.1.3052.10.2.18.5

scrVolatileIntEntry OBJECT-TYPE
    SYNTAX ScriptingVolatileInt
    MAX-ACCESS not-accessible
    STATUS current
    DESCRIPTION
        "Entry for table of volatile script integer
        settings"
    INDEX { scrVolatileIntIndex }
    ::= { scrVolatileIntTable 1 }
    --1.3.6.1.4.1.3052.10.2.18.5.1

scrVolatileIntIndex OBJECT-TYPE
    SYNTAX Integer32 (1..50)
    MAX-ACCESS read-only
    STATUS current
    DESCRIPTION
        "Index for table of volatile script integer
        settings"
    ::= { scrVolatileIntEntry 1 }
    --1.3.6.1.4.1.3052.10.2.18.5.1.1

scrVolatileInt OBJECT-TYPE
    SYNTAX Integer32 (0..2147483647)
    MAX-ACCESS read-write
    STATUS current
    DESCRIPTION
        "Volatile integer for use in scripts. Use this
         object to cache frequently-changing integer values
         or integer values that do not need to persist
         through reset.  This object corresponds to the
         scripting.vint[] setting key branch; use those
         keys in scripts and you can view or change their
         values with this object."
    ::= { scrVolatileIntEntry 2 }
    --1.3.6.1.4.1.3052.10.2.18.5.1.2

scrNonVolatileStringTable OBJECT-TYPE
    SYNTAX SEQUENCE OF ScriptingNonVolatileString
    MAX-ACCESS not-accessible
    STATUS current
    DESCRIPTION
        "Table of non-volatile string settings for use in
         scripts."
    ::= { scripting 6 }
    --1.3.6.1.4.1.3052.10.2.18.6

scrNonVolatileStringEntry OBJECT-TYPE
    SYNTAX ScriptingNonVolatileString
    MAX-ACCESS not-accessible
    STATUS current
    DESCRIPTION
        "Entry for table of non-volatile script string
        settings"
    INDEX { scrNonVolatileStringIndex }
    ::= { scrNonVolatileStringTable 1 }
    --1.3.6.1.4.1.3052.10.2.18.6.1

scrNonVolatileStringIndex OBJECT-TYPE
    SYNTAX Integer32 (1..50)
    MAX-ACCESS read-only
    STATUS current
    DESCRIPTION
        "Index for table of non-volatile script string
        settings"
    ::= { scrNonVolatileStringEntry 1 }
    --1.3.6.1.4.1.3052.10.2.18.6.1.1

scrNonVolatileString OBJECT-TYPE
    SYNTAX DisplayString
    MAX-ACCESS read-write
    STATUS current
    DESCRIPTION
        "Non-volatile string for use in scripts. Use this
         object to store values that need to persist
         through reset.  This object corresponds to the
         scripting.nvstring[] setting key branch; use those
         keys in scripts and you can view or change their
         values with this object.  Note: to store frequently-
         changing integers, use the scrVolatileString object,
         otherwise your scripts may cause unnecessary wear of
         the non-volatile storage medium on the unit."
    ::= { scrNonVolatileStringEntry 2 }
    --1.3.6.1.4.1.3052.10.2.18.6.1.2

scrNonVolatileIntTable OBJECT-TYPE
    SYNTAX SEQUENCE OF ScriptingNonVolatileInt
    MAX-ACCESS not-accessible
    STATUS current
    DESCRIPTION
        "Table of non-volatile integer settings for use in
         scripts."
    ::= { scripting 7 }
    --1.3.6.1.4.1.3052.10.2.18.7

scrNonVolatileIntEntry OBJECT-TYPE
    SYNTAX ScriptingNonVolatileInt
    MAX-ACCESS not-accessible
    STATUS current
    DESCRIPTION
        "Entry for table of non-volatile script integer
        settings"
    INDEX { scrNonVolatileIntIndex }
    ::= { scrNonVolatileIntTable 1 }
    --1.3.6.1.4.1.3052.10.2.18.7.1

scrNonVolatileIntIndex OBJECT-TYPE
    SYNTAX Integer32 (1..50)
    MAX-ACCESS read-only
    STATUS current
    DESCRIPTION
        "Index for table of non-volatile script integer
        settings"
    ::= { scrNonVolatileIntEntry 1 }
    --1.3.6.1.4.1.3052.10.2.18.7.1.1

scrNonVolatileInt OBJECT-TYPE
    SYNTAX Integer32 (0..2147483647)
    MAX-ACCESS read-write
    STATUS current
    DESCRIPTION
        "Non-volatile integer for use in scripts. Use this
         object to store integer values that need to persist
         through reset.  This object corresponds to the
         scripting.nvint[] setting key branch; use those
         keys in scripts and you can view or change their
         values with this object.  Note: to store frequently-
         changing integers, use the scrVolatileInt object,
         otherwise your scripts may cause unnecessary wear of
         the non-volatile storage medium on the unit."
    ::= { scrNonVolatileIntEntry 2 }
    --1.3.6.1.4.1.3052.10.2.18.7.1.2


--***************************************************************************************
--Generator Section   2.19
--***************************************************************************************

genSetEnable OBJECT-TYPE
    SYNTAX DisplayString
    MAX-ACCESS read-write
    STATUS current
    DESCRIPTION
        "Enable genset functionality; that is, a generator is in use."
    ::= { genSet 1 }
    --1.3.6.1.4.1.3052.10.2.19.1.1

genSetRelayEs OBJECT-TYPE
    SYNTAX Integer32 (1..200)
    MAX-ACCESS read-write
    STATUS current
    DESCRIPTION
        "Which EventSensor has the relay which starts the generator,
        for genset relay configuration 1 only.  This object maps to the
        same setting as genSetRelayTableEs.1."
    ::= { genSetRelay 1 }
    --1.3.6.1.4.1.3052.10.2.19.1.2.1

genSetRelayPoint OBJECT-TYPE
    SYNTAX Integer32 (1..13)
    MAX-ACCESS read-write
    STATUS current
    DESCRIPTION
        "Which relay starts the generator, for genset relay configuration
        1 only.  This object maps to the same setting as genSetRelayTablePoint.1."
    ::= { genSetRelay 2 }
    --1.3.6.1.4.1.3052.10.2.19.1.2.2

genSetRelayRunningstate OBJECT-TYPE
    SYNTAX DisplayString
    MAX-ACCESS read-write
    STATUS current
    DESCRIPTION
        "Which relay state corresponds with the generator starting/running.
        This object maps to the same setting as genSetRelayTableRunningstate.1."
    ::= { genSetRelay 3 }
    --1.3.6.1.4.1.3052.10.2.19.1.2.3

genSetRelayTable OBJECT-TYPE
    SYNTAX SEQUENCE OF GenSetRelaySequence
    MAX-ACCESS not-accessible
    STATUS current
    DESCRIPTION
        "Table of relays for genset ignition."
    ::= { genSetRelay 5 }
    --1.3.6.1.4.1.3052.10.2.19.1.2.5

genSetRelayTableEntry OBJECT-TYPE
    SYNTAX GenSetRelaySequence
    MAX-ACCESS not-accessible
    STATUS current
    DESCRIPTION
        "Entry for table of relays for genset ignition."
    INDEX { genSetRelayTableIndex }
    ::= { genSetRelayTable 1 }
    --1.3.6.1.4.1.3052.10.2.19.1.2.5.1

genSetRelayTableIndex OBJECT-TYPE
    SYNTAX Integer32 (1..2)
    MAX-ACCESS read-only
    STATUS current
    DESCRIPTION
        "Index for table of relays for genset ignition."
    ::= { genSetRelayTableEntry 1 }
    --1.3.6.1.4.1.3052.10.2.19.1.2.5.1.1

genSetRelayTableEnable OBJECT-TYPE
    SYNTAX DisplayString
    MAX-ACCESS read-write
    STATUS current
    DESCRIPTION
        "Enable this relay for starting the generator."
    ::= { genSetRelayTableEntry 2 }
    --1.3.6.1.4.1.3052.10.2.19.1.2.5.1.2

genSetRelayTableEs OBJECT-TYPE
    SYNTAX Integer32 (1..200)
    MAX-ACCESS read-write
    STATUS current
    DESCRIPTION
        "Which EventSensor has the relay which starts the generator, for this
         genset relay configuration specified by the table index."
    ::= { genSetRelayTableEntry 3 }
    --1.3.6.1.4.1.3052.10.2.19.1.2.5.1.3

genSetRelayTablePoint OBJECT-TYPE
    SYNTAX Integer32 (1..13)
    MAX-ACCESS read-write
    STATUS current
    DESCRIPTION
        "Which relay point on the EventSensor used for starting the generator,
        for this genset relay configuration specified by the table index."
    ::= { genSetRelayTableEntry 4 }
    --1.3.6.1.4.1.3052.10.2.19.1.2.5.1.4

genSetRelayTableRunningstate OBJECT-TYPE
    SYNTAX DisplayString
    MAX-ACCESS read-write
    STATUS current
    DESCRIPTION
        "Which relay state corresponds with the generator starting/running,
        for this genset relay configuration specified by the table index."
    ::= { genSetRelayTableEntry 5 }
    --1.3.6.1.4.1.3052.10.2.19.1.2.5.1.5

genSetCCEnable OBJECT-TYPE
    SYNTAX DisplayString
    MAX-ACCESS read-write
    STATUS current
    DESCRIPTION
        "Enable generator running detection functionality; that is, the
        associated CC is valid for determining if generator is running."
    ::= { genSetCC 1 }
    --1.3.6.1.4.1.3052.10.2.19.1.3.1

genSetCCEs OBJECT-TYPE
    SYNTAX Integer32 (1..200)
    MAX-ACCESS read-write
    STATUS current
    DESCRIPTION
        "Which CC EventSensor has the CC which is connected to the genertor
        running detection monitor."
    ::= { genSetCC 2 }
    --1.3.6.1.4.1.3052.10.2.19.1.3.2

genSetCCPoint OBJECT-TYPE
    SYNTAX Integer32 (1..64)
    MAX-ACCESS read-write
    STATUS current
    DESCRIPTION
        "Which CC is connected to the genertor running detection monitor."
    ::= { genSetCC 3 }
    --1.3.6.1.4.1.3052.10.2.19.1.3.3

genSetCCRunningState OBJECT-TYPE
    SYNTAX DisplayString
    MAX-ACCESS read-write
    STATUS current
    DESCRIPTION
        "Which CC physical state corresponds with the generator running."
    ::= { genSetCC 4 }
    --1.3.6.1.4.1.3052.10.2.19.1.3.4

genSetCCDelay OBJECT-TYPE
    SYNTAX Integer32 (0..600)
    MAX-ACCESS read-write
    STATUS current
    DESCRIPTION
        "How long (in seconds) to wait for the generator to indicate
        itself as running after engaging the generator-starting mechanism."
    ::= { genSetCC 5 }
    --1.3.6.1.4.1.3052.10.2.19.1.3.5


genRunMode OBJECT-TYPE
    SYNTAX DisplayString
    MAX-ACCESS read-write
    STATUS current
    DESCRIPTION
        "Generator Exercising function main operating mode; set to INHIBIT
        to inhibit exercising the generator."
    ::= { genRun 1 }
    --1.3.6.1.4.1.3052.10.2.19.2.1

genRunSched OBJECT-TYPE
    SYNTAX DisplayString
    MAX-ACCESS read-write
    STATUS current
    DESCRIPTION
        "Schedule number(s) which govern(s) when Generator Exercising function
        runs."
    ::= { genRun 2 }
    --1.3.6.1.4.1.3052.10.2.19.2.2

genRunDuration OBJECT-TYPE
    SYNTAX Integer32 (600..3600)
    MAX-ACCESS read-write
    STATUS current
    DESCRIPTION
        "Number of seconds that generator should run, started when the
        generator needs to start by SCHEDULE or by being forced to start."
    ::= { genRun 3 }
    --1.3.6.1.4.1.3052.10.2.19.2.3

genRunForce OBJECT-TYPE
    SYNTAX Integer32 (0..1)
    MAX-ACCESS read-write
    STATUS current
    DESCRIPTION
        "Write 1 to this to force the generator exercising to start.  Always
        reads as 0."
    ::= { genRun 4 }
    --1.3.6.1.4.1.3052.10.2.19.2.4

genRunReqasm OBJECT-TYPE
    SYNTAX DisplayString
    MAX-ACCESS read-write
    STATUS current
    DESCRIPTION
        "Require ASM connectivity before starting the generator from a schedule."
    ::= { genRun 5 }
    --1.3.6.1.4.1.3052.10.2.19.2.5

genRunStatus OBJECT-TYPE
    SYNTAX DisplayString
    MAX-ACCESS read-only
    STATUS current
    DESCRIPTION
        "Status of Generator Exercising function."
    ::= { genRun 6 }
    --1.3.6.1.4.1.3052.10.2.19.2.6


genRunNonstartEventEnable OBJECT-TYPE
    SYNTAX DisplayString
    MAX-ACCESS read-write
    STATUS current
    DESCRIPTION
        "Enable generator non-start event."
    ::= { genRunNonstartEvent 1 }
    --1.3.6.1.4.1.3052.10.2.19.2.7.1

genRunNonstartEventActions OBJECT-TYPE
    SYNTAX DisplayString
    MAX-ACCESS read-write
    STATUS current
    DESCRIPTION
        "Actions for generator non-start event."
    ::= { genRunNonstartEvent 2 }
    --1.3.6.1.4.1.3052.10.2.19.2.7.2

genRunNonstartEventTrap OBJECT-TYPE
    SYNTAX Integer32 (536..1199)
    MAX-ACCESS read-write
    STATUS current
    DESCRIPTION
        "Trap number for generator non-start event."
    ::= { genRunNonstartEvent 3 }
    --1.3.6.1.4.1.3052.10.2.19.2.7.3

genRunNonstartEventClass OBJECT-TYPE
    SYNTAX DisplayString
    MAX-ACCESS read-write
    STATUS current
    DESCRIPTION
        "Class (severity) for generator non-start event."
    ::= { genRunNonstartEvent 4 }
    --1.3.6.1.4.1.3052.10.2.19.2.7.4


--***************************************************************************************
--Calendar Section   2.20
--***************************************************************************************

schedTable OBJECT-TYPE
    SYNTAX SEQUENCE OF ScheduleConfig
    MAX-ACCESS not-accessible
    STATUS current
    DESCRIPTION
        "Table of schedules"
    ::= { calendar 1 }
    --1.3.6.1.4.1.3052.10.2.20.1

schedEntry OBJECT-TYPE
    SYNTAX ScheduleConfig
    MAX-ACCESS not-accessible
    STATUS current
    DESCRIPTION
        "Entry for table of schedules."
    INDEX { schedIndex }
    ::= { schedTable 1 }
    --1.3.6.1.4.1.3052.10.2.20.1.1

schedIndex OBJECT-TYPE
    SYNTAX Integer32 (1..8)
    MAX-ACCESS read-only
    STATUS current
    DESCRIPTION
        "Index for table of schedules."
    ::= { schedEntry 1 }
    --1.3.6.1.4.1.3052.10.2.20.1.1.1

schedEnable OBJECT-TYPE
    SYNTAX DisplayString
    MAX-ACCESS read-write
    STATUS current
    DESCRIPTION
        "Enable this schedule."
    ::= { schedEntry 2 }
    --1.3.6.1.4.1.3052.10.2.20.1.1.2

schedStart OBJECT-TYPE
    SYNTAX DisplayString
    MAX-ACCESS read-write
    STATUS current
    DESCRIPTION
        "This is of the form 'mm/dd/yy hh:mm:ss'. This controls on which
        date/time the schedule starts."
    ::= { schedEntry 3 }
    --1.3.6.1.4.1.3052.10.2.20.1.1.3

schedRepeatMode OBJECT-TYPE
    SYNTAX DisplayString
    MAX-ACCESS read-write
    STATUS current
    DESCRIPTION
        "Controls in which way the schedule should repeat."
    ::= { schedEntry 4 }
    --1.3.6.1.4.1.3052.10.2.20.1.1.4

schedRepeatFreq OBJECT-TYPE
    SYNTAX Integer32 (1..400)
    MAX-ACCESS read-write
    STATUS current
    DESCRIPTION
        "Controls how often the schedule should repeat: every nth day, week,
        month, or year."
    ::= { schedEntry 5 }
    --1.3.6.1.4.1.3052.10.2.20.1.1.5

schedRepeatEndMode OBJECT-TYPE
    SYNTAX DisplayString
    MAX-ACCESS read-write
    STATUS current
    DESCRIPTION
        "Controls how the repeating schedule should end."
    ::= { schedEntry 6 }
    --1.3.6.1.4.1.3052.10.2.20.1.1.6

schedRepeatEndAfter OBJECT-TYPE
    SYNTAX Integer32 (1..1000)
    MAX-ACCESS read-write
    STATUS current
    DESCRIPTION
        "Number of times this schedule should be repeated; relevant when the
        repeat end mode is AFTER."
    ::= { schedEntry 7 }
    --1.3.6.1.4.1.3052.10.2.20.1.1.7

schedRepeatEndOn OBJECT-TYPE
    SYNTAX DisplayString
    MAX-ACCESS read-write
    STATUS current
    DESCRIPTION
        "Date/time (in the form 'mm/yy/dd hh:mm:ss' or blank string) after
        which repeating should end, relevant when repeat end mode is ON DATE."
    ::= { schedEntry 8 }
    --1.3.6.1.4.1.3052.10.2.20.1.1.8

schedRepeatWeeklySun OBJECT-TYPE
    SYNTAX DisplayString
    MAX-ACCESS read-write
    STATUS current
    DESCRIPTION
        "Run this schedule on Sunday(s); relevant when repeat mode is weekly."
    ::= { schedEntry 9 }
    --1.3.6.1.4.1.3052.10.2.20.1.1.9

schedRepeatWeeklyMon OBJECT-TYPE
    SYNTAX DisplayString
    MAX-ACCESS read-write
    STATUS current
    DESCRIPTION
        "Run this schedule on Monday(s); relevant when repeat mode is weekly."
    ::= { schedEntry 10 }
    --1.3.6.1.4.1.3052.10.2.20.1.1.10

schedRepeatWeeklyTue OBJECT-TYPE
    SYNTAX DisplayString
    MAX-ACCESS read-write
    STATUS current
    DESCRIPTION
        "Run this schedule on Tuesday(s); relevant when repeat mode is weekly."
    ::= { schedEntry 11 }
    --1.3.6.1.4.1.3052.10.2.20.1.1.11

schedRepeatWeeklyWed OBJECT-TYPE
    SYNTAX DisplayString
    MAX-ACCESS read-write
    STATUS current
    DESCRIPTION
        "Run this schedule on Wednesday(s); relevant when repeat mode is weekly."
    ::= { schedEntry 12 }
    --1.3.6.1.4.1.3052.10.2.20.1.1.12

schedRepeatWeeklyThu OBJECT-TYPE
    SYNTAX DisplayString
    MAX-ACCESS read-write
    STATUS current
    DESCRIPTION
        "Run this schedule on Thursday(s); relevant when repeat mode is weekly."
    ::= { schedEntry 13 }
    --1.3.6.1.4.1.3052.10.2.20.1.1.13

schedRepeatWeeklyFri OBJECT-TYPE
    SYNTAX DisplayString
    MAX-ACCESS read-write
    STATUS current
    DESCRIPTION
        "Run this schedule on Friday(s); relevant when repeat mode is weekly."
    ::= { schedEntry 14 }
    --1.3.6.1.4.1.3052.10.2.20.1.1.14

schedRepeatWeeklySat OBJECT-TYPE
    SYNTAX DisplayString
    MAX-ACCESS read-write
    STATUS current
    DESCRIPTION
        "Run this schedule on Saturday(s); relevant when repeat mode is weekly."
    ::= { schedEntry 15 }
    --1.3.6.1.4.1.3052.10.2.20.1.1.15

schedRepeatMonthlyMode OBJECT-TYPE
    SYNTAX DisplayString
    MAX-ACCESS read-write
    STATUS current
    DESCRIPTION
        "EACH means the schedule runs on specific dates of the month. ON THE
        means the schedule runs on calculated dates of the month according to
        which day that month starts."
    ::= { schedEntry 16 }
    --1.3.6.1.4.1.3052.10.2.20.1.1.16

schedRepeatMonthlyDates OBJECT-TYPE
    SYNTAX DisplayString
    MAX-ACCESS read-write
    STATUS current
    DESCRIPTION
        "Comma-separated list of dates of a month on which this schedule should
        run, relevant when repeat monthly mode is EACH."
    ::= { schedEntry 17 }
    --1.3.6.1.4.1.3052.10.2.20.1.1.17

schedRepeatMonthlyOnThe OBJECT-TYPE
    SYNTAX DisplayString
    MAX-ACCESS read-write
    STATUS current
    DESCRIPTION
        "Controls on which day of the month this schedule should run, relevant
        when repeat monthly mode is ON THE."
    ::= { schedEntry 18 }
    --1.3.6.1.4.1.3052.10.2.20.1.1.18

schedRepeatMonthlyOnDay OBJECT-TYPE
    SYNTAX DisplayString
    MAX-ACCESS read-write
    STATUS current
    DESCRIPTION
        "Controls the day of week on which this schedule is run, relevant when
        repeat monthly mode is ON THE"
    ::= { schedEntry 19 }
    --1.3.6.1.4.1.3052.10.2.20.1.1.19

schedRepeatYearlyJan OBJECT-TYPE
    SYNTAX DisplayString
    MAX-ACCESS read-write
    STATUS current
    DESCRIPTION
        "Run this schedule in January, relevant when repeat mode is YEARLY."
    ::= { schedEntry 20 }
    --1.3.6.1.4.1.3052.10.2.20.1.1.20

schedRepeatYearlyFeb OBJECT-TYPE
    SYNTAX DisplayString
    MAX-ACCESS read-write
    STATUS current
    DESCRIPTION
        "Run this schedule in February, relevant when repeat mode is YEARLY."
    ::= { schedEntry 21 }
    --1.3.6.1.4.1.3052.10.2.20.1.1.21

schedRepeatYearlyMar OBJECT-TYPE
    SYNTAX DisplayString
    MAX-ACCESS read-write
    STATUS current
    DESCRIPTION
        "Run this schedule in March, relevant when repeat mode is YEARLY."
    ::= { schedEntry 22 }
    --1.3.6.1.4.1.3052.10.2.20.1.1.22

schedRepeatYearlyApr OBJECT-TYPE
    SYNTAX DisplayString
    MAX-ACCESS read-write
    STATUS current
    DESCRIPTION
        "Run this schedule in April, relevant when repeat mode is YEARLY."
    ::= { schedEntry 23 }
    --1.3.6.1.4.1.3052.10.2.20.1.1.23

schedRepeatYearlyMay OBJECT-TYPE
    SYNTAX DisplayString
    MAX-ACCESS read-write
    STATUS current
    DESCRIPTION
        "Run this schedule in May, relevant when repeat mode is YEARLY."
    ::= { schedEntry 24 }
    --1.3.6.1.4.1.3052.10.2.20.1.1.24

schedRepeatYearlyJun OBJECT-TYPE
    SYNTAX DisplayString
    MAX-ACCESS read-write
    STATUS current
    DESCRIPTION
        "Run this schedule in June, relevant when repeat mode is YEARLY."
    ::= { schedEntry 25 }
    --1.3.6.1.4.1.3052.10.2.20.1.1.25

schedRepeatYearlyJul OBJECT-TYPE
    SYNTAX DisplayString
    MAX-ACCESS read-write
    STATUS current
    DESCRIPTION
        "Run this schedule in July, relevant when repeat mode is YEARLY."
    ::= { schedEntry 26 }
    --1.3.6.1.4.1.3052.10.2.20.1.1.26

schedRepeatYearlyAug OBJECT-TYPE
    SYNTAX DisplayString
    MAX-ACCESS read-write
    STATUS current
    DESCRIPTION
        "Run this schedule in August, relevant when repeat mode is YEARLY."
    ::= { schedEntry 27 }
    --1.3.6.1.4.1.3052.10.2.20.1.1.27

schedRepeatYearlySep OBJECT-TYPE
    SYNTAX DisplayString
    MAX-ACCESS read-write
    STATUS current
    DESCRIPTION
        "Run this schedule in September, relevant when repeat mode is YEARLY."
    ::= { schedEntry 28 }
    --1.3.6.1.4.1.3052.10.2.20.1.1.28

schedRepeatYearlyOct OBJECT-TYPE
    SYNTAX DisplayString
    MAX-ACCESS read-write
    STATUS current
    DESCRIPTION
        "Run this schedule in October, relevant when repeat mode is YEARLY."
    ::= { schedEntry 29 }
    --1.3.6.1.4.1.3052.10.2.20.1.1.29

schedRepeatYearlyNov OBJECT-TYPE
    SYNTAX DisplayString
    MAX-ACCESS read-write
    STATUS current
    DESCRIPTION
        "Run this schedule in November, relevant when repeat mode is YEARLY."
    ::= { schedEntry 30 }
    --1.3.6.1.4.1.3052.10.2.20.1.1.30

schedRepeatYearlyDec OBJECT-TYPE
    SYNTAX DisplayString
    MAX-ACCESS read-write
    STATUS current
    DESCRIPTION
        "Run this schedule in December, relevant when repeat mode is YEARLY."
    ::= { schedEntry 31 }
    --1.3.6.1.4.1.3052.10.2.20.1.1.31

schedRepeatYearlyOnThe OBJECT-TYPE
    SYNTAX DisplayString
    MAX-ACCESS read-write
    STATUS current
    DESCRIPTION
        "Controls on which day of the month this schedule should run, relevant
        when repeat mode is YEARLY."
    ::= { schedEntry 32 }
    --1.3.6.1.4.1.3052.10.2.20.1.1.32

schedRepeatYearlyOnDay OBJECT-TYPE
    SYNTAX DisplayString
    MAX-ACCESS read-write
    STATUS current
    DESCRIPTION
        "Controls the day of week on which this schedule is run, relevant when
        repeat mode is YEARLY."
    ::= { schedEntry 33 }
    --1.3.6.1.4.1.3052.10.2.20.1.1.33

schedNextTrigger OBJECT-TYPE
    SYNTAX DisplayString
    MAX-ACCESS read-only
    STATUS current
    DESCRIPTION
        "When this schedule will next trigger."
    ::= { schedEntry 34 }
    --1.3.6.1.4.1.3052.10.2.20.1.1.34


--***************************************************************************************
--Product IDs Section   3
--***************************************************************************************

siteName OBJECT-TYPE
    SYNTAX DisplayString
    MAX-ACCESS read-only
    STATUS current
    DESCRIPTION
        "Site Name string; Max 40 characters."
    ::= { productIds 1 }
    --1.3.6.1.4.1.3052.10.3.1

thisProduct OBJECT-TYPE
    SYNTAX DisplayString
    MAX-ACCESS read-only
    STATUS current
    DESCRIPTION
        "This is a factory configured string for the
        product name."
    ::= { productIds 2 }
    --1.3.6.1.4.1.3052.10.3.2

stockTrapString OBJECT-TYPE
    SYNTAX DisplayString
    MAX-ACCESS read-only
    STATUS current
    DESCRIPTION
        "The message defined for the event that triggers a trap."
    ::= { productIds 3 }
    --1.3.6.1.4.1.3052.10.3.3

trapEventTypeNumber OBJECT-TYPE
    SYNTAX Integer32
    MAX-ACCESS read-only
    STATUS current
    DESCRIPTION
        "The user-defined trap variable for the type of
        event that happened.  Definitions:
           4    Scheduled
           7    Serial Handshaking Low
           8    Serial Handshaking High
           10   Contact Closure Active
           11   Contact Closure Inactive
           12   Temperature High
           13   Temperature Very High
           14   Temperature Low
           15   Temperature Very Low
           16   Temperature Return to Normal
           17   Humidity High
           18   Humidity Very High
           19   Humidity Low
           20   Humidity Very Low
           21   Humidity Return to Normal
           26   Analog High
           27   Analog Very High
           28   Analog Low
           29   Analog Very Low
           30   Analog Normal
           40   EventSensor Unresponsive
           41   Custom
           42   CPE Down
           44   CPE Normal
           49   Fuel Sensor Disconnect
           50   Fuel Sensor Disconnect Return to Normal
           56   Fuel Sensor
           57   AC Power Monitor Average Voltage Very Low
           58   AC Power Monitor Average Voltage Low
           59   AC Power Monitor Average Voltage Return to Normal
           60   AC Power Monitor Average Voltage High
           61   AC Power Monitor Average Voltage Very High
           62   AC Power Monitor Average Current Very Low
           63   AC Power Monitor Average Current Low
           64   AC Power Monitor Average Current Return to Normal
           65   AC Power Monitor Average Current High
           66   AC Power Monitor Average Current Very High
           67   AC Power Monitor Frequency Very Low
           68   AC Power Monitor Frequency Low
           69   AC Power Monitor Frequency Return to Normal
           70   AC Power Monitor Frequency High
           71   AC Power Monitor Frequency Very High
           72   AC Power Monitor Total Real Power Very Low
           73   AC Power Monitor Total Real Power Low
           74   AC Power Monitor Total Real Power Return to Normal
           75   AC Power Monitor Total Real Power High
           76   AC Power Monitor Total Real Power Very High
           77   AC Power Monitor Disconnect
           78   AC Power Monitor Disconnect Return to Normal
           81   Fuel Sensor Volume Sudden Change
           82   Fuel Sensor Volume Slow Change
           83   CPE Down Reminder
           84   AC Power Monitor Total Power Factor Very Low
           85   AC Power Monitor Total Power Factor Low
           86   AC Power Monitor Total Power Factor Return to Normal
           100  Contact Closure Active Reminder
           101  Temperature High Reminder
           102  Temperature High Very Reminder
           103  Temperature Low Reminder
           104  Temperature Very Low Reminder
           105  Humidity High Reminder
           106  Humidity Very High Reminder
           107  Humidity Low Reminder
           108  Humidity Very Low Reminder
           109  Analog High Reminder
           110  Analog Very High Reminder
           111  Analog Low Reminder
           112  Analog Very Low Reminder
           130  Relay Output Active
           131  Relay Output Inactive
           132  Power Output On
           133  Power Output Off
           161  Camera
           164  Reset
           166  Fuel Sensor Levels Auto Adjust

           "
    ::= { productIds 4 }
    --1.3.6.1.4.1.3052.10.3.4

trapEventTypeName OBJECT-TYPE
    SYNTAX DisplayString
    MAX-ACCESS read-only
    STATUS current
    DESCRIPTION
        "The user-defined trap variable for the string
        corresponding to the event type."
    ::= { productIds 5 }
    --1.3.6.1.4.1.3052.10.3.5

trapIncludedValue OBJECT-TYPE
    SYNTAX Integer32 (-2147483648..2147483647)
    MAX-ACCESS read-only
    STATUS current
    DESCRIPTION
        "The user-defined trap variable for the generic
        included value."
    ::= { productIds 6 }
    --1.3.6.1.4.1.3052.10.3.6

trapIncludedString OBJECT-TYPE
    SYNTAX DisplayString
    MAX-ACCESS read-only
    STATUS current
    DESCRIPTION
        "The user-defined trap variable for the generic
        included string."
    ::= { productIds 7 }
    --1.3.6.1.4.1.3052.10.3.7

trapTypeString OBJECT-TYPE
    SYNTAX DisplayString
    MAX-ACCESS read-only
    STATUS current
    DESCRIPTION
        "The cause of the trap, added for DL880 compatibility."
    ::= { productIds 8 }
    --1.3.6.1.4.1.3052.10.3.8

trapEventClassNumber OBJECT-TYPE
    SYNTAX Integer32
    MAX-ACCESS read-only
    STATUS current
    DESCRIPTION
        "The user-defined trap variable for the configurable
        class number associated with the triggering event."
    ::= { productIds 9 }
    --1.3.6.1.4.1.3052.10.3.9

trapEventClassName OBJECT-TYPE
    SYNTAX DisplayString
    MAX-ACCESS read-only
    STATUS current
    DESCRIPTION
        "The user-defined trap variable for the configurable
         class name associated with the class number."
    ::= { productIds 10 }
    --1.3.6.1.4.1.3052.10.3.10


--***************************************************************************************
--Key Interface Section 4
--***************************************************************************************

keyInterface OBJECT-TYPE
    SYNTAX DisplayString
    MAX-ACCESS read-write
    STATUS current
    DESCRIPTION
        "This object represents a setting key interface.  When
        setting this object, the value to set is the 'sk' command
        you would enter on the command line (without the 'sk').  To
        get the result of the operation, read this object after you
        write it.

        For example, to configure EventSensor 1 contact closure 34
        event actions to be an SNMP InformRequest to host foo, set
        this object to:
        'event.sensor[1].cc[34].eventactions=inform(foo)'.  The SNMP
        response is the result of the operation: if setting that key
        to that value was a success then the SNMP response will be a
        success and the response value will be what you had set.  If
        you subsequently read this object then you will see a
        message 'OK: ...'.

        If setting that key to that value failed then the SNMP
        response will be a failure (a badValue response).  If you
        subsequently read this object then the value returned is the
        reason that setting that key to that value failed.

        For another example, to read user 3's pass-through access
        for port 7, set this object to:
        'sec.user[3].port[7].ptaccess'.  The SNMP response is the
        result of the operation: if reading that key is a success
        then the SNMP response will be a success and the response
        value will be what you had SET (i.e., the opertion of
        reading a key, which is just the key itself with no '='
        operator, and this is not the key value you want to read).
        If you subsequently read this object then the value
        returned is the value of the key you want to read.

        If reading that key failed (e.g., if the key is invalid)
        then the SNMP response to your SNMP set operation (the
        value you set being the invalid key to read) will be a
        failure (a badValue response).  If you subsequently read
        this object then the value returned is the reason that
        reading that key failed (i.e., 'invalid key')."
    ::= { s550 4 }
    --1.3.6.1.4.1.3052.10.4


--***************************************************************************************
--TABLE DEFINITIONS
--***************************************************************************************

ESPointConfigTemp ::=
    SEQUENCE {
    espcTempIndexES
            Integer32,
    espcTempIndexPoint
            Integer32,
    espcTempEnable
            DisplayString,
    espcTempScale
            DisplayString,
    espcTempDeadband
            DisplayString,
    espcTempVHighTemp
            DisplayString,
    espcTempVHighActions
            DisplayString,
    espcTempVHighTrapnum
            Integer32,
    espcTempVHighClass
            DisplayString,
    espcTempHighTemp
            DisplayString,
    espcTempHighActions
            DisplayString,
    espcTempHighTrapnum
            Integer32,
    espcTempHighClass
            DisplayString,
    espcTempNormalActions
            DisplayString,
    espcTempNormalTrapnum
            Integer32,
    espcTempNormalClass
            DisplayString,
    espcTempLowTemp
            DisplayString,
    espcTempLowActions
            DisplayString,
    espcTempLowTrapnum
            Integer32,
    espcTempLowClass
            DisplayString,
    espcTempVLowTemp
            DisplayString,
    espcTempVLowActions
            DisplayString,
    espcTempVLowTrapnum
            Integer32,
    espcTempVLowClass
            DisplayString,
    espcTempGroup
            DisplayString
}


ESPointConfigCC ::=
    SEQUENCE {
        espcCCIndexES
            Integer32,
        espcCCIndexPoint
            Integer32,
        espcCCEnable
            DisplayString,
        espcCCName
            DisplayString,
        espcCCEventState
            DisplayString,
        espcCCThreshold
            Integer32,
        espcCCEventActions
            DisplayString,
        espcCCEventTrapnum
            Integer32,
        espcCCEventClass
            DisplayString,
        espcCCNormalActions
            DisplayString,
        espcCCNormalTrapnum
            Integer32,
        espcCCNormalClass
            DisplayString,
        espcCCAlarmAlias
            DisplayString,
        espcCCNormalAlias
            DisplayString,
        espcCCNormalThreshold
            Integer32,
        espcCCOverrideGlobalReminder
            DisplayString,
        espcCCReminderInterval
            Integer32,
        espcCCGroup
            DisplayString
}

ESPointConfigHumid ::=
    SEQUENCE {
    espcHumidIndexES
            Integer32,
    espcHumidIndexPoint
            Integer32,
    espcHumidEnable
            DisplayString,
    espcHumidDeadband
            Integer32,
    espcHumidVHighHumid
            Integer32,
    espcHumidVHighActions
            DisplayString,
    espcHumidVHighTrapnum
            Integer32,
    espcHumidVHighClass
            DisplayString,
    espcHumidHighHumid
            Integer32,
    espcHumidHighActions
            DisplayString,
    espcHumidHighTrapnum
            Integer32,
    espcHumidHighClass
            DisplayString,
    espcHumidNormalActions
            DisplayString,
    espcHumidNormalTrapnum
            Integer32,
    espcHumidNormalClass
            DisplayString,
    espcHumidLowHumid
            Integer32,
    espcHumidLowActions
            DisplayString,
    espcHumidLowTrapnum
            Integer32,
    espcHumidLowClass
            DisplayString,
    espcHumidVLowHumid
            Integer32,
    espcHumidVLowActions
            DisplayString,
    espcHumidVLowTrapnum
            Integer32,
    espcHumidVLowClass
            DisplayString,
    espcHumidGroup
            DisplayString
}

ESPointConfigAnalogInput ::=
    SEQUENCE {
    espcAIIndexES
            Integer32,
    espcAIIndexPoint
            Integer32,
    espcAIEnable
            DisplayString,
    espcAIDeadband
            DisplayString,
    espcAIVhighValue
            DisplayString,
    espcAIVhighActions
            DisplayString,
    espcAIVhighTrapnum
            Integer32,
    espcAIVhighClass
            DisplayString,
    espcAIHighValue
            DisplayString,
    espcAIHighActions
            DisplayString,
    espcAIHighTrapnum
            Integer32,
    espcAIHighClass
            DisplayString,
    espcAINormalActions
            DisplayString,
    espcAINormalTrapnum
            Integer32,
    espcAINormalClass
            DisplayString,
    espcAILowValue
            DisplayString,
    espcAILowActions
            DisplayString,
    espcAILowTrapnum
            Integer32,
    espcAILowClass
            DisplayString,
    espcAIVlowValue
            DisplayString,
    espcAIVlowActions
            DisplayString,
    espcAIVlowTrapnum
            Integer32,
    espcAIVlowClass
            DisplayString,
    espcAIConvUnitName
            DisplayString,
    espcAIConvHighValue
            DisplayString,
    espcAIConvHighUnit
            DisplayString,
    espcAIConvLowValue
            DisplayString,
    espcAIConvLowUnit
            DisplayString,
    espcAIDisplayFormat
            DisplayString,
    espcAIGroup
            DisplayString
}


ActionCallNumberConfig ::=
    SEQUENCE {
        actionCallNumberIndex
            Integer32,
        actionCallNumber
            DisplayString

}

ActionPagerConfig ::=
    SEQUENCE {
        actionPagerIndex
            Integer32,
        actionPagerType
            DisplayString,
        actionPagerNumber
            DisplayString,
        actionPagerID
            DisplayString,
        actionPagerMessage
            DisplayString,
        actionPagerPostCalloutDelay
            Integer32,
        actionPagerPostIDDelay
            Integer32
}

ESPointConfigOutput ::=
    SEQUENCE {
        espcOutputIndexES
            Integer32,
        espcOutputIndexPoint
            Integer32,
        espcOutputEnable
            DisplayString,
        espcOutputActiveState
            DisplayString,
        espcOutputType
            DisplayString,
        espcOutputAliasValue
            DisplayString,
        espcOutputAliasColor
            DisplayString,
        espcOutputActiveAlias
            DisplayString,
        espcOutputActiveColor
            DisplayString,
        espcOutputActiveActions
            DisplayString,
        espcOutputActiveTrapnum
            Integer32,
        espcOutputActiveClass
            DisplayString,
        espcOutputInactiveAlias
            DisplayString,
        espcOutputInactiveColor
            DisplayString,
        espcOutputInactiveActions
            DisplayString,
        espcOutputInactiveTrapnum
            Integer32,
        espcOutputInactiveClass
            DisplayString,
        espcOutputGroup
            DisplayString
}

EventClassConfig ::=
    SEQUENCE {
        evClassNameIndex
            Integer32,
        evClassName
            DisplayString
}

RTSFileConfig ::=
    SEQUENCE {
        rtsFileIndex
            Integer32,
        rtsFileMode
            DisplayString,
        rtsFileShowAnswer
            DisplayString,
        rtsFileReqXON
            DisplayString,
        rtsFileTimeout
            Integer32,
        rtsFileEmptyClose
            DisplayString,
        rtsFilePushHost
            DisplayString,
        rtsFilePushPort
            Integer32,
        rtsFilePushRetryTimer
            Integer32
}


ModemCLIDLogConfig ::=
    SEQUENCE {
        modemCLIDLogIndex
            Integer32,
        modemCLIDLogNumber
            DisplayString
}

CPEConfig ::=
    SEQUENCE {
        cpeIndex
            Integer32,
        cpeHost
            DisplayString,
        cpeName
            DisplayString,
        cpeDescription
            DisplayString,
        cpeKeepalive
            Integer32,
        cpeThreshold
            Integer32,
        cpeEventReminderInterval
            Integer32,
        cpeKeepaliveTicks
            Integer32,
        cpePingSize
            Integer32,
        cpeInfoReset
            Integer32,
        cpeInfoNumReq
            Integer32,
        cpeInfoNumGoodResp
            Integer32,
        cpeInfoNumBadResp
            Integer32,
        cpeInfoNumLostResp
            Integer32,
        cpeInfoPercentLoss
            DisplayString,
        cpeInfoPercentBad
            DisplayString
}

ScriptingConfig ::=
    SEQUENCE {
        scrIndex
            Integer32,
        scrEnable
            DisplayString,
        scrName
            DisplayString,
        scrFilename
            DisplayString,
        scrRunAlways
            DisplayString,
        scrRunAtStartup
            DisplayString,
        scrRunScheduled
            DisplayString,
        scrScheduleTime
            DisplayString,
        scrArguments
            DisplayString,
        scrRepeatInterval
            Integer32
}

ScriptingDTRCtrlPortEnableConfig ::=
    SEQUENCE {
        scrDTRCtrlPortEnableIndex
            Integer32,
        scrDTRCtrlPortEnable
            DisplayString

}

ScriptingVolatileString ::=
    SEQUENCE {
        scrVolatileStringIndex
            Integer32,
        scrVolatileString
            DisplayString
}

ScriptingVolatileInt ::=
    SEQUENCE {
        scrVolatileIntIndex
            Integer32,
        scrVolatileInt
            Integer32
}

ScriptingNonVolatileString ::=
    SEQUENCE {
        scrNonVolatileStringIndex
            Integer32,
        scrNonVolatileString
            DisplayString
}

ScriptingNonVolatileInt ::=
    SEQUENCE {
        scrNonVolatileIntIndex
            Integer32,
        scrNonVolatileInt
            Integer32
}

GenSetRelaySequence ::=
    SEQUENCE {
        genSetRelayTableIndex
            Integer32,
        genSetRelayTableEnable
            DisplayString,
        genSetRelayTableEs
            Integer32,
        genSetRelayTablePoint
            Integer32,
        genSetRelayTableRunningstate
            DisplayString
}

CRDBFileEnforceMinConfig ::=
    SEQUENCE {
        sysCRDBFileEnforceMinIndex
            Integer32,
        sysCRDBFileEnforceMin
            DisplayString
}

CRDBFileIDConfig ::=
    SEQUENCE {
        sysCRDBFileIDIndex
            Integer32,
        sysCRDBFileID
            DisplayString
}

NetworkTimeHostConfig ::=
    SEQUENCE {
        sysTimeNetHostIndex
            Integer32,
        sysTimeNetHost
            DisplayString
}

ActionHostConfig ::=
    SEQUENCE {
        actionHostIndex
            Integer32,
        actionHost
            DisplayString
}

ActionEmailConfig ::=
    SEQUENCE {
        actionEmailIndex
            Integer32,
        actionEmail
            DisplayString
}

FileEnforceMinimumConfig ::=
    SEQUENCE {
        sysCRDBFileEnforceMinIndex
            Integer32,
        sysCRDBFileEnforceMin
            DisplayString
}

SerialHandshakingLowEventConfig ::=
    SEQUENCE {
        evShskLowIndex
            Integer32,
        evShskLowEnable
            DisplayString,
        evShskLowActions
            DisplayString,
        evShskLowMessage
            DisplayString,
        evShskLowClass
            DisplayString,
        evShskLowTrapNum
            Integer32
}

SerialHandshakingHighEventConfig ::=
    SEQUENCE {
        evShskHighIndex
            Integer32,
        evShskHighEnable
            DisplayString,
        evShskHighActions
            DisplayString,
        evShskHighMessage
            DisplayString,
        evShskHighClass
            DisplayString,
        evShskHighTrapNum
            Integer32
}

NoDataEvent1PortEnableConfig ::=
    SEQUENCE {
        evNoData1PortEnableIndex
            Integer32,
        evNoData1PortEnable
            DisplayString
}

NoDataEvent2PortEnableConfig ::=
    SEQUENCE {
        evNoData2PortEnableIndex
            Integer32,
        evNoData2PortEnable
            DisplayString
}

DataEventMacroConfig ::=
    SEQUENCE {
        evdMacroIndex
            Integer32,
        evdMacroName
            DisplayString,
        evdMacroEquation
            DisplayString
}

DataEventFieldConfig ::=
    SEQUENCE {
        evdFieldIndex
            Integer32,
        evdFieldStart
            Integer32,
        evdFieldLength
            Integer32,
        evdFieldName
            DisplayString,
        evdFieldLine
            Integer32,
        evdFieldType
            DisplayString
}

DataEventConfig ::=
    SEQUENCE {
        evdIndex
            Integer32,
        evdEnable
            DisplayString,
        evdName
            DisplayString,
        evdEquation
            DisplayString,
        evdThreshold
            Integer32,
        evdAutoClear
            DisplayString,
        evdClearInterval
            DisplayString,
        evdClearTime
            DisplayString,
        evdActions
            DisplayString,
        evdClass
            DisplayString,
        evdTrapNum
            Integer32,
        evdMode
            DisplayString
}

SecUserConfig ::=
    SEQUENCE {
        secUserIndex
            Integer32,
        secUserEnable
            DisplayString,
        secUserConnectVia
            DisplayString,
        secUserLoginTo
            DisplayString,
        secUserAccessFile
            DisplayString,
        secUserPTEscapeTo
            DisplayString,
        secUserPPPType
            DisplayString,
        secUserRights
            DisplayString,
        secUserEventsReadAccess
            DisplayString,
        secUserAuditReadAccess
            DisplayString,
        secUserEventsWriteAccess
            DisplayString,
        secUserAuditWriteAccess
            DisplayString,
        secUserExpiration
            DisplayString,
        secUserCallbackNumber1
            DisplayString,
        secUserCallbackNumber2
            DisplayString,
        secUserCallbackNumber3
            DisplayString,
        secUserChallengeTelnetMode
            DisplayString,
        secUserChallengeModemMode
            DisplayString,
        secUserChallengeConsoleMode
            DisplayString,
        secUserChallengeTelnetSendTo
            DisplayString,
        secUserChallengeModemSendTo
            DisplayString,
        secUserChallengeExpiration
            Integer32
}




ModemCLIDNumberConfig ::=
    SEQUENCE {
        modemCLIDNumberIndex
            Integer32,
        modemCLIDNumber
            DisplayString
}


RouteTestConfig ::=
    SEQUENCE {
        routeTestAddressIndex
            Integer32,
        routeTestAddress
            DisplayString
}

IPRestrictionConfig ::=
    SEQUENCE {
        ipRestrictionIndex
            Integer32,
        ipRestrictionEnable
            DisplayString,
        ipRestrictionMask
            DisplayString
}

DNSConfig ::=
    SEQUENCE {
        dnsIndex
            Integer32,
        dnsAddress
            IpAddress
}

HostConfig ::=
    SEQUENCE {
        hostIndex
            Integer32,
        hostDeclaration
            DisplayString
}

SNMPProxyTable ::=
    SEQUENCE {
        snmpProxyIndex
            Integer32,
        snmpProxyEgressOIDBranch
            DisplayString,
        snmpProxyIP
            DisplayString,
        snmpProxyPort
            Integer32,
        snmpProxyIngressOIDBranch
            DisplayString,
        snmpProxyName
            DisplayString
}

SNMPPollRequestConfig ::=
    SEQUENCE {
        snmpPRequestIndex
            Integer32,
        snmpPRequestDescription
            DisplayString,
        snmpPRequestAgent
            DisplayString,
        snmpPRequestReadcom
            DisplayString,
        snmpPRequestOID
            DisplayString,
        snmpPRequestPeriod
            Integer32,
        snmpPRequestID
            DisplayString,
        snmpPRequestThreshold
            DisplayString,
        snmpPRequestResultStatus
            DisplayString,
        snmpPRequestResultValue
            DisplayString,
        snmpPRequestResultTime
            DisplayString,
        snmpPRequestResultType
            DisplayString
}

FTPPushPushFileConfig ::=
    SEQUENCE {
        ftpPushPushFileIndex
            Integer32,
        ftpPushPushFile
            DisplayString
}

FTPPushRemoteFileConfig ::=
    SEQUENCE {
        ftpPushRemoteFileIndex
            Integer32,
        ftpPushRemoteFileName
            DisplayString
}

PortConfig ::=
    SEQUENCE {
        portConfigIndex
            Integer32,
        portConfigBaud
            Integer32,
        portConfigDataFormat
            Integer32,
        portConfigStripPtOutputLfs
            Integer32,
        portConfigStripPtInputLfs
            Integer32,
        portConfigMaskEnable
            Integer32,
        portConfigDAEnable
            Integer32,
        portConfigStoreAlarmsDPT
            DisplayString,
        portConfigRecordTimeout
            Integer32,
        portConfigDataType
            DisplayString,
        portConfigEtxToCRLF
            DisplayString,
        portConfigMLREnable
            DisplayString,
        portConfigMLRStartField1Pos
            Integer32,
        portConfigMLRStartField1Text
            DisplayString,
        portConfigMLRStartField2Pos
            Integer32,
        portConfigMLRStartField2Text
            DisplayString,
        portConfigMLRNumLinesBefore
            Integer32,
        portConfigMLREndDetection
            DisplayString,
        portConfigMLRLineCount
            Integer32,
        portConfigMLREndField1Pos
            Integer32,
        portConfigMLREndField1Text
            DisplayString,
        portConfigMLREndField2Pos
            Integer32,
        portConfigMLREndField2Text
            DisplayString,
        portConfigMLRUseComplexRules
            DisplayString,
        portConfigBufferPT
            DisplayString,
        portConfigId
            DisplayString,
        portConfigMode
            DisplayString,
        portConfigHsk
            DisplayString

}

ESPoint ::=
    SEQUENCE {
        esIndexES
            Integer32,
        esIndexPC
            Integer32,
        esIndexPoint
            Integer32,
        esPointName
            DisplayString,
        esPointInEventState
            Integer32,
        esPointValueInt
            Integer32,
        esPointValueStr
            DisplayString,
        esPointTimeLastChange
            DisplayString,
        esPointTimetickLastChange
            TimeTicks,
        esPointAliasValueStr
            DisplayString,
        esPointClassValueStr
            DisplayString
}

ESExist ::=
    SEQUENCE {
        esIndex
            Integer32,
        esName
            DisplayString,
        esID
            DisplayString,
        esNumberTempSensors
            Integer32,
        esTempReportingMode
            DisplayString,
        esNumberCCs
            Integer32,
        esCCReportingMode
            DisplayString,
        esNumberHumidSensors
            Integer32,
        esHumidReportingMode
            DisplayString,
        esNumberNoiseSensors
            Integer32,
        esNoiseReportingMode
            DisplayString,
        esNumberAirflowSensors
            Integer32,
        esAirflowReportingMode
            DisplayString,
        esNumberAnalog
            Integer32,
        esAnalogReportingMode
            DisplayString,
        esNumberOutputs
            Integer32,
        esOutputReportingMode
            DisplayString,
        esTempCombinedStatus
            DisplayString,
        esCCCombinedStatusBlock1
            DisplayString,
        esCCCombinedStatusBlock2
            DisplayString,
        esCCCombinedStatusBlock3
            DisplayString,
        esCCCombinedStatusBlock4
            DisplayString,
        esCCCombinedStatusBlock5
            DisplayString,
        esCCCombinedStatusBlock6
            DisplayString,
        esCCCombinedStatusBlock7
            DisplayString,
        esCCCombinedStatusBlock8
            DisplayString,
        esHumidCombinedStatus
            DisplayString,
        esAnalogCombinedStatusBlock1
            DisplayString,
        esAnalogCombinedStatusBlock2
            DisplayString,
        esAnalogCombinedStatusBlock3
            DisplayString,
        esAnalogCombinedStatusBlock4
            DisplayString,
        esAnalogCombinedStatusBlock5
            DisplayString,
        esAnalogCombinedStatusBlock6
            DisplayString,
        esOutputCombinedStatusBlock1
            DisplayString,
        esOutputCombinedStatusBlock2
            DisplayString
}

DEStatus ::=
    SEQUENCE {
        deStatusIndex
            Integer32,
        deStatusName
            DisplayString,
        deStatusCounter
            Integer32,
        deStatusThreshold
            Integer32
}

FSStatus ::=
    SEQUENCE {
        fsStatusIndex
            Integer32,
        fsStatusName
            DisplayString,
        fsStatusDeviceState
            DisplayString,
        fsStatusVolumeValueString
            DisplayString,
        fsStatusVolumePercentLevel
            DisplayString,
        fsStatusVolumeInEventState
            DisplayString,
        fsStatusCombined
            DisplayString
}

ACPMStatus ::=
    SEQUENCE {
        acpmsIndex
            Integer32,
        acpmsName
            DisplayString,
        acpmsAvgVoltageValueStr
            DisplayString,
        acpmsAvgVoltageMinStr
            DisplayString,
        acpmsAvgVoltageMaxStr
            DisplayString,
        acpmsAvgVoltageAvgStr
            DisplayString,
        acpmsAvgVoltageInEventState
            DisplayString,
        acpmsVoltagePhaseAValueStr
            DisplayString,
        acpmsVoltagePhaseBValueStr
            DisplayString,
        acpmsVoltagePhaseCValueStr
            DisplayString,
        acpmsAvgCurrentValueStr
            DisplayString,
        acpmsAvgCurrentMinStr
            DisplayString,
        acpmsAvgCurrentMaxStr
            DisplayString,
        acpmsAvgCurrentAvgStr
            DisplayString,
        acpmsAvgCurrentInEventState
            DisplayString,
        acpmsCurrentPhaseAValueStr
            DisplayString,
        acpmsCurrentPhaseBValueStr
            DisplayString,
        acpmsCurrentPhaseCValueStr
            DisplayString,
        acpmsVoltageL1L2Value
            DisplayString,
        acpmsVoltageL2L3Value
            DisplayString,
        acpmsVoltageL3L1Value
            DisplayString,
        acpmsAvgFreqValueStr
            DisplayString,
        acpmsAvgFreqMinStr
            DisplayString,
        acpmsAvgFreqMaxStr
            DisplayString,
        acpmsAvgFreqAvgStr
            DisplayString,
        acpmsAvgFreqInEventState
            DisplayString,
        acpmsTRPValueStr
            DisplayString,
        acpmsTRPMinStr
            DisplayString,
        acpmsTRPMaxStr
            DisplayString,
        acpmsTRPAvgStr
            DisplayString,
        acpmsTRPInEventState
            DisplayString,
        acpmsRPPhaseAValueStr
            DisplayString,
        acpmsRPPhaseBValueStr
            DisplayString,
        acpmsRPPhaseCValueStr
            DisplayString,
        acpmsCombined
            DisplayString,
        acpmsTPFValueStr
            DisplayString,
        acpmsTPFMinStr
            DisplayString,
        acpmsTPFMaxStr
            DisplayString,
        acpmsTPFAvgStr
            DisplayString,
        acpmsTPFInEventState
            DisplayString,
        acpmsPFPhaseAValueStr
            DisplayString,
        acpmsPFPhaseBValueStr
            DisplayString,
        acpmsPFPhaseCValueStr
            DisplayString,
        acpmsTRcPValueStr
            DisplayString,
        acpmsTRcPMinStr
            DisplayString,
        acpmsTRcPMaxStr
            DisplayString,
        acpmsTRcPAvgStr
            DisplayString,
        acpmsRcPPhaseAValueStr
            DisplayString,
        acpmsRcPPhaseBValueStr
            DisplayString,
        acpmsRcPPhaseCValueStr
            DisplayString,
        acpmsTAPValueStr
            DisplayString,
        acpmsTAPMinStr
            DisplayString,
        acpmsTAPMaxStr
            DisplayString,
        acpmsTAPAvgStr
            DisplayString,
        acpmsAPPhaseAValueStr
            DisplayString,
        acpmsAPPhaseBValueStr
            DisplayString,
        acpmsAPPhaseCValueStr
            DisplayString,
        acpmsTotalEnergyWh
            Integer32,
        acpmsTotalEnergyVAR
            Integer32,
        acpmsTotalEnergyVA
            Integer32,
        acmpsAvgVoltageAlarmDatetime
            DisplayString,
        acmpsAvgCurrentAlarmDatetime
            DisplayString,
        acmpsFreqAlarmDatetime
            DisplayString,
        acmpsRealPowerAlarmDatetime
            DisplayString,
        acmpsPowerFactorAlarmDatetime
            DisplayString
}

HVACStatusAsentriaSequence ::=
    SEQUENCE {
        evHVACStatusAsentriaSequenceIndex
            Integer32,
        evHVACStatusAsentriaSeqVentTime
            DisplayString,
        evHVACStatusAsentriaSeqCoolTime
            DisplayString,
        evHVACStatusAsentriaSeqHeatTime
            DisplayString,
        evHVACStatusAsentriaSeqIdleTime
            DisplayString
}

HVACStatusAsentriaUnit ::=
    SEQUENCE {
        evHVACStatusAsentriaUnitIndex
            Integer32,
        evHVACStatusAsentriaUnitState
            DisplayString,
        evHVACStatusAsentriaUnitVentTime
            DisplayString,
        evHVACStatusAsentriaUnitCoolTime
            DisplayString,
        evHVACStatusAsentriaUnitHeatTime
            DisplayString,
        evHVACStatusAsentriaUnitIdleTime
            DisplayString
}
        
HVACStatusAirsysAlarmUnit ::=
    SEQUENCE {
        evHVACStatusAirsysAlarmUnitIndex
            Integer32,
        evHVACStatusAirsysAlarmUnitLowPress
            DisplayString,
        evHVACStatusAirsysAlarmUnitHighPress
            DisplayString,
        evHVACStatusAirsysAlarmUnitEvapFan
            DisplayString,
        evHVACStatusAirsysAlarmUnitDirty
            DisplayString,
        evHVACStatusAirsysAlarmUnitDamper
            DisplayString,
        evHVACStatusAirsysAlarmUnitSupProbe
            DisplayString
}
        
HVACStatusAirsysUnit ::=
    SEQUENCE {
        evHVACStatusAirsysUnitIndex
            Integer32,
        evHVACStatusAirsysUnitTempSupply
            DisplayString,
        evHVACStatusAirsysUnitFanspeed
            DisplayString,
        evHVACStatusAirsysUnitFreeOpening
            DisplayString,
        evHVACStatusAirsysUnitStatus
            DisplayString,
        evHVACStatusAirsysUnitLocked
            DisplayString,
        evHVACStatusAirsysUnitCompressor
            DisplayString,
        evHVACStatusAirsysUnitHeater
            DisplayString,
        evHVACStatusAirsysURuntimeSupplyFan
            DisplayString,
        evHVACStatusAirsysURuntimeCompressor
            DisplayString,
        evHVACStatusAirsysURuntimeHeat
            DisplayString,
        evHVACStatusAirsysURuntimeFreeCooling
            DisplayString,
        evHVACStatusAirsysUCountSupplyFan
            DisplayString,
        evHVACStatusAirsysUCountCompressor
            DisplayString,
        evHVACStatusAirsysUCountHeat
            DisplayString,
        evHVACStatusAirsysUCountFreeCooling
            DisplayString
}

HVACAsentriaSensorList ::=
    SEQUENCE {
        evHVACAsentriaSensorListIndex
            Integer32,
        evHVACAsentriaSensorListES
            DisplayString,
        evHVACAsentriaSensorListPT
            Integer32,
        evHVACAsentriaSensorListType
            DisplayString,
        evHVACAsentriaSensorListLoc
            DisplayString
}

HVACAsentriaUnit ::=
    SEQUENCE {
        evHVACAsentriaUnitIndex
            Integer32,
        evHVACAsentriaUnitEnable
            DisplayString,
        evHVACAsentriaUnitFanRelayES
            DisplayString,
        evHVACAsentriaUnitFanRelayPT
            Integer32,
        evHVACAsentriaUnitVentRelayES
            DisplayString,
        evHVACAsentriaUnitVentRelayPT
            Integer32,
        evHVACAsentriaUnitTimereset
            Integer32,
        evHVACAsentriaSeqTimereset
            Integer32,
        evHVACAsentriaUnitStage1CoolES
            DisplayString,
        evHVACAsentriaUnitStage1CoolPT
            Integer32,
        evHVACAsentriaUnitStage1HeatES
            DisplayString,
        evHVACAsentriaUnitStage1HeatPT
            Integer32,
        evHVACAsentriaUnitStage2CoolES
            DisplayString,
        evHVACAsentriaUnitStage2CoolPT
            Integer32,
        evHVACAsentriaUnitStage2HeatES
            DisplayString,
        evHVACAsentriaUnitStage2HeatPT
            Integer32
}

HVACAirsysUnit::=
    SEQUENCE {
        evHVACAirsysUnitIndex
            Integer32,
        evHVACAirsysULowPEnable
            DisplayString,
        evHVACAirsysULowPActions
            DisplayString,
        evHVACAirsysULowPTrapnum
            Integer32,
        evHVACAirsysULowPClass
            DisplayString,
        evHVACAirsysULowPNormActions
            DisplayString,
        evHVACAirsysULowPNormTrapNum
            Integer32,
        evHVACAirsysULowPNormClass
            DisplayString,
        evHVACAirsysUHighPEnable
            DisplayString,
        evHVACAirsysUHighPActions
            DisplayString,
        evHVACAirsysUHighPTrapnum
            Integer32,
        evHVACAirsysUHighPClass
            DisplayString,
        evHVACAirsysUHighPNormActions
            DisplayString,
        evHVACAirsysUHighPNormTrapNum
            Integer32,
        evHVACAirsysUHighPNormClass
            DisplayString,
        evHVACAirsysUEvapFanEnable
            DisplayString,
        evHVACAirsysUEvapFanActions
            DisplayString,
        evHVACAirsysUEvapFanTrapnum
            Integer32,
        evHVACAirsysUEvapFanClass
            DisplayString,
        evHVACAirsysUEvapFanNormActions
            DisplayString,
        evHVACAirsysUEvapFanNormTrapNum
            Integer32,
        evHVACAirsysUEvapFanNormClass
            DisplayString,
        evHVACAirsysUDirtyEnable
            DisplayString,
        evHVACAirsysUDirtyActions
            DisplayString,
        evHVACAirsysUDirtyTrapnum
            Integer32,
        evHVACAirsysUDirtyClass
            DisplayString,
        evHVACAirsysUDirtyNormActions
            DisplayString,
        evHVACAirsysUDirtyNormTrapNum
            Integer32,
        evHVACAirsysUDirtyNormClass
            DisplayString,
        evHVACAirsysUInProbeEnable
            DisplayString,
        evHVACAirsysUInProbeActions
            DisplayString,
        evHVACAirsysUInProbeTrapnum
            Integer32,
        evHVACAirsysUInProbeClass
            DisplayString,
        evHVACAirsysUInProbeNormActions
            DisplayString,
        evHVACAirsysUInProbeNormTrapNum
            Integer32,
        evHVACAirsysUInProbeNormClass
            DisplayString,
        evHVACAirsysUDamperEnable
            DisplayString,
        evHVACAirsysUDamperActions
            DisplayString,
        evHVACAirsysUDamperTrapnum
            Integer32,
        evHVACAirsysUDamperClass
            DisplayString,
        evHVACAirsysUDamperNormActions
            DisplayString,
        evHVACAirsysUDamperNormTrapNum
            Integer32,
        evHVACAirsysUDamperNormClass
            DisplayString,
        evHVACAirsysUSupProbeEnable
            DisplayString,
        evHVACAirsysUSupProbeActions
            DisplayString,
        evHVACAirsysUSupProbeTrapnum
            Integer32,
        evHVACAirsysUSupProbeClass
            DisplayString,
        evHVACAirsysUSupProbeNormActions
            DisplayString,
        evHVACAirsysUSupProbeNormTrapNum
            Integer32,
        evHVACAirsysUSupProbeNormClass
            DisplayString
}

ScheduleConfig ::=
    SEQUENCE {
        schedIndex
            Integer32,
        schedEnable
            DisplayString,
        schedStart
            DisplayString,
        schedRepeatMode
            DisplayString,
        schedRepeatFreq
            Integer32,
        schedRepeatEndMode
            DisplayString,
        schedRepeatEndAfter
            Integer32,
        schedRepeatEndOn
            DisplayString,
        schedRepeatWeeklySun
            DisplayString,
        schedRepeatWeeklyMon
            DisplayString,
        schedRepeatWeeklyTue
            DisplayString,
        schedRepeatWeeklyWed
            DisplayString,
        schedRepeatWeeklyThu
            DisplayString,
        schedRepeatWeeklyFri
            DisplayString,
        schedRepeatWeeklySat
            DisplayString,
        schedRepeatMonthlyMode
            DisplayString,
        schedRepeatMonthlyDates
            DisplayString,
        schedRepeatMonthlyOnThe
            DisplayString,
        schedRepeatMonthlyOnDay
            DisplayString,
        schedRepeatYearlyJan
            DisplayString,
        schedRepeatYearlyFeb
            DisplayString,
        schedRepeatYearlyMar
            DisplayString,
        schedRepeatYearlyApr
            DisplayString,
        schedRepeatYearlyMay
            DisplayString,
        schedRepeatYearlyJun
            DisplayString,
        schedRepeatYearlyJul
            DisplayString,
        schedRepeatYearlyAug
            DisplayString,
        schedRepeatYearlySep
            DisplayString,
        schedRepeatYearlyOct
            DisplayString,
        schedRepeatYearlyNov
            DisplayString,
        schedRepeatYearlyDec
            DisplayString,
        schedRepeatYearlyOnThe
            DisplayString,
        schedRepeatYearlyOnDay
            DisplayString,
        schedNextTrigger
            DisplayString
}

FuelSensorConfigGeneral ::=
    SEQUENCE {
        fsGenIndex
            Integer32,
        fsGenName
            DisplayString,
        fsGenSensorType
            DisplayString,
        fsGenDistanceUnit
            DisplayString,
        fsGenRawValueTop
            DisplayString,
        fsGenTopOffset
            DisplayString,
        fsGenRawValueBottom
            DisplayString,
        fsGenBottomOffset
            DisplayString,
        fsGenInputES
            Integer32,
        fsGenInputPoint
            Integer32,
        fsGenFilterAveraging
            Integer32,
        fsGenSysrepEnable
            DisplayString,
        fsGenSysrepThreshold
            DisplayString,
        fsGenSysrepLimit
            Integer32,
        fsGenSysrepPackage
            Integer32,
        fsGenGroup
            DisplayString,
        fsGenEnable
            DisplayString,
        fsGenFuelType
            DisplayString
}

FuelSensorConfigTank ::=
    SEQUENCE {
        fsTankIndex
            Integer32,
        fsTankHeight
            DisplayString,
        fsTankDimA
            DisplayString,
        fsTankDimB
            DisplayString,
        fsTankVolume
            DisplayString,
        fsTankVolumeUnit
            DisplayString,
        fsTankShape
            DisplayString
}

FuelSensorConfigCustomTankStrapping ::=
    SEQUENCE {
        fsCustomTankIndexFS
            Integer32,
        fsCustomTankIndexDatum
            Integer32,
        fsCustomTankHeight
            DisplayString,
        fsCustomTankVolume
            DisplayString
}

FuelSensorConfigVolume ::=
    SEQUENCE {
        fsVolumeIndex
            Integer32,
        fsVolumeEnable
            DisplayString,
        fsVolumeDeadband
            DisplayString,
        fsVolumeVHighValue
            DisplayString,
        fsVolumeVHighActions
            DisplayString,
        fsVolumeVHighTrapNum
            Integer32,
        fsVolumeVHighClass
            DisplayString,
        fsVolumeHighValue
            DisplayString,
        fsVolumeHighActions
            DisplayString,
        fsVolumeHighTrapNum
            Integer32,
        fsVolumeHighClass
            DisplayString,
        fsVolumeNormalActions
            DisplayString,
        fsVolumeNormalTrapNum
            Integer32,
        fsVolumeNormalClass
            DisplayString,
        fsVolumeLowValue
            DisplayString,
        fsVolumeLowActions
            DisplayString,
        fsVolumeLowTrapNum
            Integer32,
        fsVolumeLowClass
            DisplayString,
        fsVolumeVLowValue
            DisplayString,
        fsVolumeVLowActions
            DisplayString,
        fsVolumeVLowTrapNum
            Integer32,
        fsVolumeVLowClass
            DisplayString
}

FuelSensorConfigDisconnect ::=
    SEQUENCE {
        fsDiscIndex
            Integer32,
        fsDiscEnable
            DisplayString,
        fsDiscHighValue
            DisplayString,
        fsDiscLowValue
            DisplayString,
        fsDiscActions
            DisplayString,
        fsDiscTrapNum
            Integer32,
        fsDiscClass
            DisplayString,
        fsDiscNormalActions
            DisplayString,
        fsDiscNormalTrapNum
            Integer32,
        fsDiscNormalClass
            DisplayString
}

FuelSensorConfigSuddenChange ::=
    SEQUENCE {
        fsSuddenChangeIndex
            Integer32,
        fsSuddenChangeEnable
            DisplayString,
        fsSuddenChangeTime
            Integer32,
        fsSuddenChangeAmplitude
            DisplayString,
        fsSuddenChangeActions
            DisplayString,
        fsSuddenChangeTrapNum
            Integer32,
        fsSuddenChangeClass
            DisplayString
}

FuelSensorConfigSlowChange ::=
    SEQUENCE {
        fsSlowChangeIndex
            Integer32,
        fsSlowChangeEnable
            DisplayString,
        fsSlowChangeTime
            Integer32,
        fsSlowChangeAmplitude
            DisplayString,
        fsSlowChangeActions
            DisplayString,
        fsSlowChangeTrapNum
            Integer32,
        fsSlowChangeClass
            DisplayString
}

ACPMConfigGeneral ::=
    SEQUENCE {
        acpmGenIndex
            Integer32,
        acpmGenDevice
            DisplayString,
        acpmGenName
            DisplayString,
        acpmGenAddress
            Integer32,
        acpmGenPtRatio
            Integer32,
        acpmGenCtRatio
            Integer32,
        acpmGenPowerType
            DisplayString,
        acpmGenSysrepPackage
            Integer32,
        acpmGenGroup
            DisplayString,
        acpmGenEnable
            DisplayString
}

ACPMConfigAvgVoltage ::=
    SEQUENCE {
        acpmAvgVoltageIndex
            Integer32,
        acpmAvgVoltageEnable
            DisplayString,
        acpmAvgVoltageDeadband
            DisplayString,
        acpmAvgVoltageVHighValue
            DisplayString,
        acpmAvgVoltageVHighActions
            DisplayString,
        acpmAvgVoltageVHighTrapNum
            Integer32,
        acpmAvgVoltageVHighClass
            DisplayString,
        acpmAvgVoltageHighValue
            DisplayString,
        acpmAvgVoltageHighActions
            DisplayString,
        acpmAvgVoltageHighTrapNum
            Integer32,
        acpmAvgVoltageHighClass
            DisplayString,
        acpmAvgVoltageNormalActions
            DisplayString,
        acpmAvgVoltageNormalTrapNum
            Integer32,
        acpmAvgVoltageNormalClass
            DisplayString,
        acpmAvgVoltageLowValue
            DisplayString,
        acpmAvgVoltageLowActions
            DisplayString,
        acpmAvgVoltageLowTrapNum
            Integer32,
        acpmAvgVoltageLowClass
            DisplayString,
        acpmAvgVoltageVLowValue
            DisplayString,
        acpmAvgVoltageVLowActions
            DisplayString,
        acpmAvgVoltageVLowTrapNum
            Integer32,
        acpmAvgVoltageVLowClass
            DisplayString,
        acpmAvgVoltageSysrepEnable
            DisplayString,
        acpmAvgVoltageSysrepThreshold
            DisplayString,
        acpmAvgVoltageSysrepLimit
            Integer32
}

ACPMConfigAvgCurrent ::=
    SEQUENCE {
        acpmAvgCurrentIndex
            Integer32,
        acpmAvgCurrentEnable
            DisplayString,
        acpmAvgCurrentDeadband
            DisplayString,
        acpmAvgCurrentVHighValue
            DisplayString,
        acpmAvgCurrentVHighActions
            DisplayString,
        acpmAvgCurrentVHighTrapNum
            Integer32,
        acpmAvgCurrentVHighClass
            DisplayString,
        acpmAvgCurrentHighValue
            DisplayString,
        acpmAvgCurrentHighActions
            DisplayString,
        acpmAvgCurrentHighTrapNum
            Integer32,
        acpmAvgCurrentHighClass
            DisplayString,
        acpmAvgCurrentNormalActions
            DisplayString,
        acpmAvgCurrentNormalTrapNum
            Integer32,
        acpmAvgCurrentNormalClass
            DisplayString,
        acpmAvgCurrentLowValue
            DisplayString,
        acpmAvgCurrentLowActions
            DisplayString,
        acpmAvgCurrentLowTrapNum
            Integer32,
        acpmAvgCurrentLowClass
            DisplayString,
        acpmAvgCurrentVLowValue
            DisplayString,
        acpmAvgCurrentVLowActions
            DisplayString,
        acpmAvgCurrentVLowTrapNum
            Integer32,
        acpmAvgCurrentVLowClass
            DisplayString,
        acpmAvgCurrentSysrepEnable
            DisplayString,
        acpmAvgCurrentSysrepThreshold
            DisplayString,
        acpmAvgCurrentSysrepLimit
            Integer32
}

ACPMConfigFreq ::=
    SEQUENCE {
        acpmFreqIndex
            Integer32,
        acpmFreqEnable
            DisplayString,
        acpmFreqDeadband
            DisplayString,
        acpmFreqVHighValue
            DisplayString,
        acpmFreqVHighActions
            DisplayString,
        acpmFreqVHighTrapNum
            Integer32,
        acpmFreqVHighClass
            DisplayString,
        acpmFreqHighValue
            DisplayString,
        acpmFreqHighActions
            DisplayString,
        acpmFreqHighTrapNum
            Integer32,
        acpmFreqHighClass
            DisplayString,
        acpmFreqNormalActions
            DisplayString,
        acpmFreqNormalTrapNum
            Integer32,
        acpmFreqNormalClass
            DisplayString,
        acpmFreqLowValue
            DisplayString,
        acpmFreqLowActions
            DisplayString,
        acpmFreqLowTrapNum
            Integer32,
        acpmFreqLowClass
            DisplayString,
        acpmFreqVLowValue
            DisplayString,
        acpmFreqVLowActions
            DisplayString,
        acpmFreqVLowTrapNum
            Integer32,
        acpmFreqVLowClass
            DisplayString,
        acpmFreqSysrepEnable
            DisplayString,
        acpmFreqSysrepThreshold
            DisplayString,
        acpmFreqSysrepLimit
            Integer32
}

ACPMConfigTRP ::=
    SEQUENCE {
        acpmTRPIndex
            Integer32,
        acpmTRPEnable
            DisplayString,
        acpmTRPDeadband
            DisplayString,
        acpmTRPVHighValue
            DisplayString,
        acpmTRPVHighActions
            DisplayString,
        acpmTRPVHighTrapNum
            Integer32,
        acpmTRPVHighClass
            DisplayString,
        acpmTRPHighValue
            DisplayString,
        acpmTRPHighActions
            DisplayString,
        acpmTRPHighTrapNum
            Integer32,
        acpmTRPHighClass
            DisplayString,
        acpmTRPNormalActions
            DisplayString,
        acpmTRPNormalTrapNum
            Integer32,
        acpmTRPNormalClass
            DisplayString,
        acpmTRPLowValue
            DisplayString,
        acpmTRPLowActions
            DisplayString,
        acpmTRPLowTrapNum
            Integer32,
        acpmTRPLowClass
            DisplayString,
        acpmTRPVLowValue
            DisplayString,
        acpmTRPVLowActions
            DisplayString,
        acpmTRPVLowTrapNum
            Integer32,
        acpmTRPVLowClass
            DisplayString,
        acpmTRPSysrepEnable
            DisplayString,
        acpmTRPSysrepThreshold
            DisplayString,
        acpmTRPSysrepLimit
            Integer32
}

ACPMConfigDisconnect ::=
    SEQUENCE {
        acpmDisconnectIndex
            Integer32,
        acpmDisconnectEnable
            DisplayString,
        acpmDisconnectActions
            DisplayString,
        acpmDisconnectTrapNum
            Integer32,
        acpmDisconnectClass
            DisplayString,
        acpmDisconnectNormalActions
            DisplayString,
        acpmDisconnectNormalTrapNum
            Integer32,
        acpmDisconnectNormalClass
            DisplayString
}

ACPMConfigTotalPowerFactor ::=
    SEQUENCE {
        acpmTPFIndex
            Integer32,
        acpmTPFEnable
            DisplayString,
        acpmTPFDeadband
            DisplayString,
        acpmTPFNormalActions
            DisplayString,
        acpmTPFNormalTrapNum
            Integer32,
        acpmTPFNormalClass
            DisplayString,
        acpmTPFLowValue
            DisplayString,
        acpmTPFLowActions
            DisplayString,
        acpmTPFLowTrapNum
            Integer32,
        acpmTPFLowClass
            DisplayString,
        acpmTPFVLowValue
            DisplayString,
        acpmTPFVLowActions
            DisplayString,
        acpmTPFVLowTrapNum
            Integer32,
        acpmTPFVLowClass
            DisplayString,
        acpmTPFSysrepEnable
            DisplayString,
        acpmTPFSysrepThreshold
            DisplayString,
        acpmTPFSysrepLimit
            Integer32
}

WebXMLProxyDeviceConfig ::=
    SEQUENCE {
        wxpDeviceIndex
            Integer32,
        wxpDeviceEnable
            DisplayString,
        wxpDeviceIPAddress
            IpAddress,
        wxpDevicePort
            Integer32,
        wxpDeviceRemoteFile
            DisplayString,
        wxpDeviceLocalFile
            DisplayString,
        wxpDeviceTimeout
            Integer32,
        wxpDeviceTimestamp
            DisplayString
}

EthernetExpansionCardConfig ::=
    SEQUENCE {
        ethExpanCardIndex
            Integer32,
        ethExpanCardMAC
            DisplayString
}


AccessControlDevice ::=
    SEQUENCE {
        acdIndex
            Integer32,
        acdEnable
            DisplayString,
        acdName
            DisplayString,
        acdReader
            DisplayString,
        acdWiegandES
            Integer32,
        acdWiegandPoint
            Integer32,
        acdRelayType
            DisplayString,
        acdRelayES
            Integer32,
        acdRelayPoint
            Integer32,
        acdOpenTime
            Integer32,
        acdUserGroup
            Integer32
}

AccessControlUser ::=
    SEQUENCE {
        acuIndexUserGroup
            Integer32,
        acuIndexUser
            Integer32,
        acuEnable
            DisplayString,
        acuName
            DisplayString,
        acuSn
            DisplayString,
        acuSunBegin
            DisplayString,
        acuSunEnd
            DisplayString,
        acuMonBegin
            DisplayString,
        acuMonEnd
            DisplayString,
        acuTueBegin
            DisplayString,
        acuTueEnd
            DisplayString,
        acuWedBegin
            DisplayString,
        acuWedEnd
            DisplayString,
        acuThuBegin
            DisplayString,
        acuThuEnd
            DisplayString,
        acuFriBegin
            DisplayString,
        acuFriEnd
            DisplayString,
        acuSatBegin
            DisplayString,
        acuSatEnd
            DisplayString
}

TelemetryPoint ::=
    SEQUENCE {
        telemetryPointIndex
            Integer32,
        telemetryPointName
            DisplayString,
        telemetryPointKey
            DisplayString,
        telemetryPointType
            DisplayString,
        telemetryPointClass
            DisplayString,
        telemetryPointDeadband
            DisplayString,
        telemetryPointShortcode
            DisplayString
}


SiteSecIntrusion ::=
    SEQUENCE {
       siteSecEnable                     
            DisplayString,
       siteSecDisarmed                   
            DisplayString,
       siteSecName                       
            DisplayString,
       siteSecState                      
            DisplayString,
       siteSecSensorES                   
            Integer32,
       siteSecSensorPoint                
            Integer32,
       siteSecIntrusionThreshold         
            Integer32,
       siteSecReader                     
            DisplayString,
       siteSecReaderThreshold            
            Integer32,
       siteSecButtonEnable               
            DisplayString,
       siteSecButtonES                   
            Integer32,
       siteSecButtonPoint                
            Integer32,
       siteSecButtonType                 
            DisplayString,
       siteSecButtonThresholdArm         
            Integer32,
       siteSecButtonThresholdDisarm      
            Integer32,
       siteSecSirenEnable                
            DisplayString,
       siteSecSirenES                    
            Integer32,
       siteSecSirenPoint                 
            Integer32,
       siteSecRearmDelay                 
            Integer32
}            

SiteSecMotion ::=
    SEQUENCE {

       siteSecMotionES                    
            Integer32,
       siteSecMotionPoint                 
            Integer32,
       siteSecMotionEnable                
            DisplayString,
       siteSecMotionName                  
            DisplayString,
       siteSecMotionThresholdRearm         
            Integer32
}

SiteSecDoorAjar ::=
    SEQUENCE {
       siteSecDoorAjarEnable               
            DisplayString,
       siteSecDoorAjarName                 
            DisplayString,
       siteSecDoorAjarES                   
            Integer32,
       siteSecDoorAjarPoint                
            Integer32,
       siteSecDoorAjarThresholdNormal      
            Integer32,
       siteSecDoorAjarThresholdExtraTime   
            Integer32
}




--***************************************************************************************
--TRAP DEFINITIONS
--***************************************************************************************

s550StockSensorUnresponsiveTrap NOTIFICATION-TYPE
    OBJECTS { siteName, stockTrapString, trapTypeString }
    STATUS current
    DESCRIPTION
        "A stock unresponsive trap is issued when a sensor is unresponsive."
    ::= { s550notifications 50 }

s550notificationsStockContactClosureTrap NOTIFICATION-TYPE
    OBJECTS { siteName, stockTrapString, trapTypeString }
    STATUS current
    DESCRIPTION
        "A stock contact closure trap is issued when a contact closure
        event happens."
    ::= { s550notifications 110 }

s550notificationsStockTempTrap NOTIFICATION-TYPE
    OBJECTS { siteName, stockTrapString, trapTypeString }
    STATUS current
    DESCRIPTION
        "A stock temperature trap is issued when a temperature event
        happens."
    ::= { s550notifications 120 }

s550notificationsStockHumidityTrap NOTIFICATION-TYPE
    OBJECTS { siteName, stockTrapString, trapTypeString }
    STATUS current
    DESCRIPTION
        "A stock humidity trap is issued when a humidity event
        happens."
    ::= { s550notifications 130 }

s550notificationsStockAnalogTrap NOTIFICATION-TYPE
    OBJECTS { siteName, stockTrapString, trapTypeString }
    STATUS current
    DESCRIPTION
        "A stock analog trap is issued when an analog sensor event
        happens."
    ::= { s550notifications 140 }

s550notificationsStockOutputTrap NOTIFICATION-TYPE
    OBJECTS { siteName, stockTrapString, trapTypeString }
    STATUS current
    DESCRIPTION
        "A stock output trap is issued when an output event
        happens.  That is, depending on the configuration,
        when an output changes state for any reason, this
        trap will be sent."
    ::= { s550notifications 150 }

s550StockPDCurrentTrap NOTIFICATION-TYPE
    OBJECTS { siteName, stockTrapString, trapTypeString }
    STATUS current
    DESCRIPTION
        "A stock analog trap is issued when a power distribution
        current event happens."
    ::= { s550notifications 180 }

s550StockPDVoltageTrap NOTIFICATION-TYPE
    OBJECTS { siteName, stockTrapString, trapTypeString }
    STATUS current
    DESCRIPTION
        "A stock analog trap is issued when a power distribution
        voltage event happens."
    ::= { s550notifications 190 }

s550StockPDFuseTrap NOTIFICATION-TYPE
    OBJECTS { siteName, stockTrapString, trapTypeString }
    STATUS current
    DESCRIPTION
        "A stock analog trap is issued when a power distribution
        fuse event happens."
    ::= { s550notifications 210 }

s550notificationsStockDbasePfullTrap NOTIFICATION-TYPE
    OBJECTS { siteName, stockTrapString, trapTypeString }
    STATUS current
    DESCRIPTION
        "The stock database percent full trap is issued
        when the database size surpasses the threshold."
    ::= { s550notifications 501 }

s550notificationsStockDataAlarmTrap NOTIFICATION-TYPE
    OBJECTS { siteName, stockTrapString, trapTypeString }
    STATUS current
    DESCRIPTION
        "The stock data alarm trap is issued when a
        data alarm happens."
    ::= { s550notifications 503 }

s550notificationsStockNoDataAlarmTrap NOTIFICATION-TYPE
    OBJECTS { siteName, stockTrapString, trapTypeString }
    STATUS current
    DESCRIPTION
        "The stock no-data alarm trap is issued when
        the unit has received no data for a configured
        interval within a configured schedule."
    ::= { s550notifications 505 }

s550notificationsStockSchedTrap NOTIFICATION-TYPE
    OBJECTS { siteName, stockTrapString, trapTypeString }
    STATUS current
    DESCRIPTION
        "The stock scheduled alarm trap is issued
        when the current time reaches the scheduled
        alarm time."
    ::= { s550notifications 506 }

s550notificationsStockImmediateTrap NOTIFICATION-TYPE
    OBJECTS { siteName, stockTrapString, trapTypeString }
    STATUS current
    DESCRIPTION
        "The stock immediate alarm trap is issued
        when the user enters the DOTRAP command."
    ::= { s550notifications 507 }

s550StockBattRunningTrap NOTIFICATION-TYPE
    OBJECTS { siteName, liBattPercentCharge, liBattRunning }
    STATUS current
    DESCRIPTION
        "The stock trap issued when the battery power state change.
         Gives the unit name, percentage charge of the battery and
         if unit is running on battery backup (0 is False and 1 is True)"
    ::= { s550notifications 508 }

s550notificationsStockCTSTrap  NOTIFICATION-TYPE
    OBJECTS { siteName, stockTrapString, trapTypeString }
    STATUS current
    DESCRIPTION
        "A stock CTS trap is issued when an RS-232 CTS event
        happens."
    ::= { s550notifications 510 }

s550notificationsCPEDownTrap  NOTIFICATION-TYPE
    OBJECTS { siteName, stockTrapString, trapTypeString }
    STATUS current
    DESCRIPTION
        "A stock CPE Down trap is issued when a CPE Down event
        happens."
    ::= { s550notifications 511 }

s550notificationsFuelSensorDisconnectTrap  NOTIFICATION-TYPE
    OBJECTS { siteName, stockTrapString, trapTypeString }
    STATUS current
    DESCRIPTION
        "A stock Fuel Sensor Disconnect trap is issued when a Fuel
        Sensor Disconnect or Connect (Return to Normal) event happens."
    ::= { s550notifications 515 }

s550notificationsFuelSensorVolumeTrap  NOTIFICATION-TYPE
    OBJECTS { siteName, stockTrapString, trapTypeString }
    STATUS current
    DESCRIPTION
        "A stock Fuel Sensor Volume trap is issued when a Fuel
        Sensor Volume event happens"
    ::= { s550notifications 519 }

s550notificationsACPowerMonitorAvgVoltageTrap  NOTIFICATION-TYPE
    OBJECTS { siteName, stockTrapString, trapTypeString }
    STATUS current
    DESCRIPTION
        "A stock AC power monitor average voltage trap is issued when an
        AC power monitor average voltage event happens."
    ::= { s550notifications 520 }

s550notificationsACPowerMonitorAvgCurrentTrap  NOTIFICATION-TYPE
    OBJECTS { siteName, stockTrapString, trapTypeString }
    STATUS current
    DESCRIPTION
        "A stock AC power monitor average current trap is issued when an
        AC power monitor average current event happens."
    ::= { s550notifications 521 }

s550notificationsACPowerMonitorFrequencyTrap  NOTIFICATION-TYPE
    OBJECTS { siteName, stockTrapString, trapTypeString }
    STATUS current
    DESCRIPTION
        "A stock AC power monitor frequency trap is issued when an
        AC power monitor frequency event happens."
    ::= { s550notifications 522 }

s550notificationsACPowerMonitorTRPTrap  NOTIFICATION-TYPE
    OBJECTS { siteName, stockTrapString, trapTypeString }
    STATUS current
    DESCRIPTION
        "A stock AC power monitor TRP (total real power) trap is issued
        when an AC power monitor TRP event happens."
    ::= { s550notifications 523 }

s550notificationsACPowerMonitorDisconnectTrap  NOTIFICATION-TYPE
    OBJECTS { siteName, stockTrapString, trapTypeString }
    STATUS current
    DESCRIPTION
        "A stock AC power monitor disconnect trap is issued
        when an AC power monitor disconnect event happens."
    ::= { s550notifications 524 }

s550notificationsStockScriptTrap  NOTIFICATION-TYPE
    OBJECTS { siteName, stockTrapString, trapTypeString }
    STATUS current
    DESCRIPTION
        "A stock script trap is issued when a script triggers
        an event via a_lib.PostEvent() called with no trap
        number (or this trap number) specified."
    ::= { s550notifications 526 }

s550notificationsFuelSensorVolumeSuddenChangeTrap  NOTIFICATION-TYPE
    OBJECTS { siteName, stockTrapString, trapTypeString }
    STATUS current
    DESCRIPTION
        "A stock Fuel Sensor Volume Sudden Change trap is issued
        when a Fuel Sensor Volume Sudden Change event happens"
    ::= { s550notifications 527 }

s550notificationsFuelSensorVolumeSlowChangeTrap  NOTIFICATION-TYPE
    OBJECTS { siteName, stockTrapString, trapTypeString }
    STATUS current
    DESCRIPTION
        "A stock Fuel Sensor Volume Slow Change trap is issued
        when a Fuel Sensor Volume Slow Change event happens"
    ::= { s550notifications 528 }

s550notificationsCameraTrap  NOTIFICATION-TYPE
    OBJECTS { siteName, stockTrapString, trapTypeString }
    STATUS current
    DESCRIPTION
        "A stock camera trap is issued when a camera event happens."
    ::= { s550notifications 539 }

s550notificationsGeneratorNonStartTrap  NOTIFICATION-TYPE
    OBJECTS { siteName, stockTrapString, trapTypeString }
    STATUS current
    DESCRIPTION
        "A stock Generator Non-start trap is issued
        when the unit commands the generator to start as
        part of the generator exercising feature, and the
        generator fails to register as started after 30
        seconds (as detected by CC generator running
        detection)."
    ::= { s550notifications 536 }

s550notificationsACTotalPowerFactorTrap  NOTIFICATION-TYPE
    OBJECTS { siteName, stockTrapString, trapTypeString }
    STATUS current
    DESCRIPTION
        "A stock AC power monitor total power factor trap is issued
        when an AC power monitor total power factor event happens."
    ::= { s550notifications 540 }

s550notificationsResetTrap  NOTIFICATION-TYPE
    OBJECTS { siteName, stockTrapString, trapTypeString }
    STATUS current
    DESCRIPTION
        "A stock reset trap is issued when a reset event happens."
    ::= { s550notifications 543 }

s550notificationHVACAsentriaControlTrap  NOTIFICATION-TYPE
    OBJECTS { siteName, stockTrapString, trapTypeString }
    STATUS current
    DESCRIPTION
        "A stock HVAC Asentria Control trap is issued when an issue with 
         temperature, humidity, fire detection and other HVAC related
         event happens."
    ::= { s550notifications 545 }

s550notificationAccessControlTrap  NOTIFICATION-TYPE
    OBJECTS { siteName, stockTrapString, trapTypeString }
    STATUS current
    DESCRIPTION
        "A stock access control trap is issued when an access control
        device management event happens."
    ::= { s550notifications 547 }

s550notificationHVACAirsysControlTrap  NOTIFICATION-TYPE
    OBJECTS { siteName, stockTrapString, trapTypeString }
    STATUS current
    DESCRIPTION
        "A stock HVAC Airsys Control trap is issued when an issue
         related to alarm conditions for the Airsys HVAC system
         event happens."
    ::= { s550notifications 548 }

s550notificationsUserTrap1000 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1000."
    ::= { s550notifications 1000 }

s550notificationsUserTrap1001 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1001."
    ::= { s550notifications 1001 }

s550notificationsUserTrap1002 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1002."
    ::= { s550notifications 1002 }

s550notificationsUserTrap1003 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1003."
    ::= { s550notifications 1003 }

s550notificationsUserTrap1004 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1004."
    ::= { s550notifications 1004 }

s550notificationsUserTrap1005 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1005."
    ::= { s550notifications 1005 }

s550notificationsUserTrap1006 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1006."
    ::= { s550notifications 1006 }

s550notificationsUserTrap1007 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1007."
    ::= { s550notifications 1007 }

s550notificationsUserTrap1008 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1008."
    ::= { s550notifications 1008 }

s550notificationsUserTrap1009 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1009."
    ::= { s550notifications 1009 }

s550notificationsUserTrap1010 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1010."
    ::= { s550notifications 1010 }

s550notificationsUserTrap1011 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1011."
    ::= { s550notifications 1011 }

s550notificationsUserTrap1012 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1012."
    ::= { s550notifications 1012 }

s550notificationsUserTrap1013 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1013."
    ::= { s550notifications 1013 }

s550notificationsUserTrap1014 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1014."
    ::= { s550notifications 1014 }

s550notificationsUserTrap1015 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1015."
    ::= { s550notifications 1015 }

s550notificationsUserTrap1016 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1016."
    ::= { s550notifications 1016 }

s550notificationsUserTrap1017 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1017."
    ::= { s550notifications 1017 }

s550notificationsUserTrap1018 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1018."
    ::= { s550notifications 1018 }

s550notificationsUserTrap1019 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1019."
    ::= { s550notifications 1019 }

s550notificationsUserTrap1020 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1020."
    ::= { s550notifications 1020 }

s550notificationsUserTrap1021 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1021."
    ::= { s550notifications 1021 }

s550notificationsUserTrap1022 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1022."
    ::= { s550notifications 1022 }

s550notificationsUserTrap1023 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1023."
    ::= { s550notifications 1023 }

s550notificationsUserTrap1024 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1024."
    ::= { s550notifications 1024 }

s550notificationsUserTrap1025 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1025."
    ::= { s550notifications 1025 }

s550notificationsUserTrap1026 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1026."
    ::= { s550notifications 1026 }

s550notificationsUserTrap1027 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1027."
    ::= { s550notifications 1027 }

s550notificationsUserTrap1028 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1028."
    ::= { s550notifications 1028 }

s550notificationsUserTrap1029 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1029."
    ::= { s550notifications 1029 }

s550notificationsUserTrap1030 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1030."
    ::= { s550notifications 1030 }

s550notificationsUserTrap1031 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1031."
    ::= { s550notifications 1031 }

s550notificationsUserTrap1032 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1032."
    ::= { s550notifications 1032 }

s550notificationsUserTrap1033 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1033."
    ::= { s550notifications 1033 }

s550notificationsUserTrap1034 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1034."
    ::= { s550notifications 1034 }

s550notificationsUserTrap1035 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1035."
    ::= { s550notifications 1035 }

s550notificationsUserTrap1036 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1036."
    ::= { s550notifications 1036 }

s550notificationsUserTrap1037 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1037."
    ::= { s550notifications 1037 }

s550notificationsUserTrap1038 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1038."
    ::= { s550notifications 1038 }

s550notificationsUserTrap1039 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1039."
    ::= { s550notifications 1039 }

s550notificationsUserTrap1040 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1040."
    ::= { s550notifications 1040 }

s550notificationsUserTrap1041 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1041."
    ::= { s550notifications 1041 }

s550notificationsUserTrap1042 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1042."
    ::= { s550notifications 1042 }

s550notificationsUserTrap1043 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1043."
    ::= { s550notifications 1043 }

s550notificationsUserTrap1044 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1044."
    ::= { s550notifications 1044 }

s550notificationsUserTrap1045 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1045."
    ::= { s550notifications 1045 }

s550notificationsUserTrap1046 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1046."
    ::= { s550notifications 1046 }

s550notificationsUserTrap1047 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1047."
    ::= { s550notifications 1047 }

s550notificationsUserTrap1048 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1048."
    ::= { s550notifications 1048 }

s550notificationsUserTrap1049 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1049."
    ::= { s550notifications 1049 }

s550notificationsUserTrap1050 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1050."
    ::= { s550notifications 1050 }

s550notificationsUserTrap1051 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1051."
    ::= { s550notifications 1051 }

s550notificationsUserTrap1052 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1052."
    ::= { s550notifications 1052 }

s550notificationsUserTrap1053 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1053."
    ::= { s550notifications 1053 }

s550notificationsUserTrap1054 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1054."
    ::= { s550notifications 1054 }

s550notificationsUserTrap1055 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1055."
    ::= { s550notifications 1055 }

s550notificationsUserTrap1056 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1056."
    ::= { s550notifications 1056 }

s550notificationsUserTrap1057 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1057."
    ::= { s550notifications 1057 }

s550notificationsUserTrap1058 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1058."
    ::= { s550notifications 1058 }

s550notificationsUserTrap1059 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1059."
    ::= { s550notifications 1059 }

s550notificationsUserTrap1060 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1060."
    ::= { s550notifications 1060 }

s550notificationsUserTrap1061 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1061."
    ::= { s550notifications 1061 }

s550notificationsUserTrap1062 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1062."
    ::= { s550notifications 1062 }

s550notificationsUserTrap1063 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1063."
    ::= { s550notifications 1063 }

s550notificationsUserTrap1064 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1064."
    ::= { s550notifications 1064 }

s550notificationsUserTrap1065 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1065."
    ::= { s550notifications 1065 }

s550notificationsUserTrap1066 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1066."
    ::= { s550notifications 1066 }

s550notificationsUserTrap1067 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1067."
    ::= { s550notifications 1067 }

s550notificationsUserTrap1068 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1068."
    ::= { s550notifications 1068 }

s550notificationsUserTrap1069 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1069."
    ::= { s550notifications 1069 }

s550notificationsUserTrap1070 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1070."
    ::= { s550notifications 1070 }

s550notificationsUserTrap1071 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1071."
    ::= { s550notifications 1071 }

s550notificationsUserTrap1072 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1072."
    ::= { s550notifications 1072 }

s550notificationsUserTrap1073 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1073."
    ::= { s550notifications 1073 }

s550notificationsUserTrap1074 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1074."
    ::= { s550notifications 1074 }

s550notificationsUserTrap1075 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1075."
    ::= { s550notifications 1075 }

s550notificationsUserTrap1076 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1076."
    ::= { s550notifications 1076 }

s550notificationsUserTrap1077 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1077."
    ::= { s550notifications 1077 }

s550notificationsUserTrap1078 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1078."
    ::= { s550notifications 1078 }

s550notificationsUserTrap1079 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1079."
    ::= { s550notifications 1079 }

s550notificationsUserTrap1080 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1080."
    ::= { s550notifications 1080 }

s550notificationsUserTrap1081 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1081."
    ::= { s550notifications 1081 }

s550notificationsUserTrap1082 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1082."
    ::= { s550notifications 1082 }

s550notificationsUserTrap1083 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1083."
    ::= { s550notifications 1083 }

s550notificationsUserTrap1084 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1084."
    ::= { s550notifications 1084 }

s550notificationsUserTrap1085 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1085."
    ::= { s550notifications 1085 }

s550notificationsUserTrap1086 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1086."
    ::= { s550notifications 1086 }

s550notificationsUserTrap1087 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1087."
    ::= { s550notifications 1087 }

s550notificationsUserTrap1088 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1088."
    ::= { s550notifications 1088 }

s550notificationsUserTrap1089 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1089."
    ::= { s550notifications 1089 }

s550notificationsUserTrap1090 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1090."
    ::= { s550notifications 1090 }

s550notificationsUserTrap1091 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1091."
    ::= { s550notifications 1091 }

s550notificationsUserTrap1092 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1092."
    ::= { s550notifications 1092 }

s550notificationsUserTrap1093 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1093."
    ::= { s550notifications 1093 }

s550notificationsUserTrap1094 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1094."
    ::= { s550notifications 1094 }

s550notificationsUserTrap1095 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1095."
    ::= { s550notifications 1095 }

s550notificationsUserTrap1096 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1096."
    ::= { s550notifications 1096 }

s550notificationsUserTrap1097 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1097."
    ::= { s550notifications 1097 }

s550notificationsUserTrap1098 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1098."
    ::= { s550notifications 1098 }

s550notificationsUserTrap1099 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1099."
    ::= { s550notifications 1099 }

s550notificationsUserTrap1100 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1100."
    ::= { s550notifications 1100 }

s550notificationsUserTrap1101 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1101."
    ::= { s550notifications 1101 }

s550notificationsUserTrap1102 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1102."
    ::= { s550notifications 1102 }

s550notificationsUserTrap1103 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1103."
    ::= { s550notifications 1103 }

s550notificationsUserTrap1104 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1104."
    ::= { s550notifications 1104 }

s550notificationsUserTrap1105 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1105."
    ::= { s550notifications 1105 }

s550notificationsUserTrap1106 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1106."
    ::= { s550notifications 1106 }

s550notificationsUserTrap1107 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1107."
    ::= { s550notifications 1107 }

s550notificationsUserTrap1108 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1108."
    ::= { s550notifications 1108 }

s550notificationsUserTrap1109 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1109."
    ::= { s550notifications 1109 }

s550notificationsUserTrap1110 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1110."
    ::= { s550notifications 1110 }

s550notificationsUserTrap1111 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1111."
    ::= { s550notifications 1111 }

s550notificationsUserTrap1112 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1112."
    ::= { s550notifications 1112 }

s550notificationsUserTrap1113 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1113."
    ::= { s550notifications 1113 }

s550notificationsUserTrap1114 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1114."
    ::= { s550notifications 1114 }

s550notificationsUserTrap1115 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1115."
    ::= { s550notifications 1115 }

s550notificationsUserTrap1116 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1116."
    ::= { s550notifications 1116 }

s550notificationsUserTrap1117 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1117."
    ::= { s550notifications 1117 }

s550notificationsUserTrap1118 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1118."
    ::= { s550notifications 1118 }

s550notificationsUserTrap1119 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1119."
    ::= { s550notifications 1119 }

s550notificationsUserTrap1120 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1120."
    ::= { s550notifications 1120 }

s550notificationsUserTrap1121 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1121."
    ::= { s550notifications 1121 }

s550notificationsUserTrap1122 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1122."
    ::= { s550notifications 1122 }

s550notificationsUserTrap1123 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1123."
    ::= { s550notifications 1123 }

s550notificationsUserTrap1124 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1124."
    ::= { s550notifications 1124 }

s550notificationsUserTrap1125 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1125."
    ::= { s550notifications 1125 }

s550notificationsUserTrap1126 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1126."
    ::= { s550notifications 1126 }

s550notificationsUserTrap1127 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1127."
    ::= { s550notifications 1127 }

s550notificationsUserTrap1128 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1128."
    ::= { s550notifications 1128 }

s550notificationsUserTrap1129 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1129."
    ::= { s550notifications 1129 }

s550notificationsUserTrap1130 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1130."
    ::= { s550notifications 1130 }

s550notificationsUserTrap1131 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1131."
    ::= { s550notifications 1131 }

s550notificationsUserTrap1132 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1132."
    ::= { s550notifications 1132 }

s550notificationsUserTrap1133 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1133."
    ::= { s550notifications 1133 }

s550notificationsUserTrap1134 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1134."
    ::= { s550notifications 1134 }

s550notificationsUserTrap1135 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1135."
    ::= { s550notifications 1135 }

s550notificationsUserTrap1136 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1136."
    ::= { s550notifications 1136 }

s550notificationsUserTrap1137 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1137."
    ::= { s550notifications 1137 }

s550notificationsUserTrap1138 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1138."
    ::= { s550notifications 1138 }

s550notificationsUserTrap1139 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1139."
    ::= { s550notifications 1139 }

s550notificationsUserTrap1140 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1140."
    ::= { s550notifications 1140 }

s550notificationsUserTrap1141 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1141."
    ::= { s550notifications 1141 }

s550notificationsUserTrap1142 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1142."
    ::= { s550notifications 1142 }

s550notificationsUserTrap1143 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1143."
    ::= { s550notifications 1143 }

s550notificationsUserTrap1144 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1144."
    ::= { s550notifications 1144 }

s550notificationsUserTrap1145 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1145."
    ::= { s550notifications 1145 }

s550notificationsUserTrap1146 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1146."
    ::= { s550notifications 1146 }

s550notificationsUserTrap1147 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1147."
    ::= { s550notifications 1147 }

s550notificationsUserTrap1148 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1148."
    ::= { s550notifications 1148 }

s550notificationsUserTrap1149 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1149."
    ::= { s550notifications 1149 }

s550notificationsUserTrap1150 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1150."
    ::= { s550notifications 1150 }

s550notificationsUserTrap1151 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1151."
    ::= { s550notifications 1151 }

s550notificationsUserTrap1152 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1152."
    ::= { s550notifications 1152 }

s550notificationsUserTrap1153 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1153."
    ::= { s550notifications 1153 }

s550notificationsUserTrap1154 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1154."
    ::= { s550notifications 1154 }

s550notificationsUserTrap1155 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1155."
    ::= { s550notifications 1155 }

s550notificationsUserTrap1156 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1156."
    ::= { s550notifications 1156 }

s550notificationsUserTrap1157 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1157."
    ::= { s550notifications 1157 }

s550notificationsUserTrap1158 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1158."
    ::= { s550notifications 1158 }

s550notificationsUserTrap1159 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1159."
    ::= { s550notifications 1159 }

s550notificationsUserTrap1160 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1160."
    ::= { s550notifications 1160 }

s550notificationsUserTrap1161 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1161."
    ::= { s550notifications 1161 }

s550notificationsUserTrap1162 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1162."
    ::= { s550notifications 1162 }

s550notificationsUserTrap1163 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1163."
    ::= { s550notifications 1163 }

s550notificationsUserTrap1164 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1164."
    ::= { s550notifications 1164 }

s550notificationsUserTrap1165 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1165."
    ::= { s550notifications 1165 }

s550notificationsUserTrap1166 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1166."
    ::= { s550notifications 1166 }

s550notificationsUserTrap1167 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1167."
    ::= { s550notifications 1167 }

s550notificationsUserTrap1168 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1168."
    ::= { s550notifications 1168 }

s550notificationsUserTrap1169 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1169."
    ::= { s550notifications 1169 }

s550notificationsUserTrap1170 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1170."
    ::= { s550notifications 1170 }

s550notificationsUserTrap1171 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1171."
    ::= { s550notifications 1171 }

s550notificationsUserTrap1172 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1172."
    ::= { s550notifications 1172 }

s550notificationsUserTrap1173 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1173."
    ::= { s550notifications 1173 }

s550notificationsUserTrap1174 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1174."
    ::= { s550notifications 1174 }

s550notificationsUserTrap1175 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1175."
    ::= { s550notifications 1175 }

s550notificationsUserTrap1176 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1176."
    ::= { s550notifications 1176 }

s550notificationsUserTrap1177 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1177."
    ::= { s550notifications 1177 }

s550notificationsUserTrap1178 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1178."
    ::= { s550notifications 1178 }

s550notificationsUserTrap1179 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1179."
    ::= { s550notifications 1179 }

s550notificationsUserTrap1180 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1180."
    ::= { s550notifications 1180 }

s550notificationsUserTrap1181 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1181."
    ::= { s550notifications 1181 }

s550notificationsUserTrap1182 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1182."
    ::= { s550notifications 1182 }

s550notificationsUserTrap1183 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1183."
    ::= { s550notifications 1183 }

s550notificationsUserTrap1184 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1184."
    ::= { s550notifications 1184 }

s550notificationsUserTrap1185 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1185."
    ::= { s550notifications 1185 }

s550notificationsUserTrap1186 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1186."
    ::= { s550notifications 1186 }

s550notificationsUserTrap1187 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1187."
    ::= { s550notifications 1187 }

s550notificationsUserTrap1188 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1188."
    ::= { s550notifications 1188 }

s550notificationsUserTrap1189 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1189."
    ::= { s550notifications 1189 }

s550notificationsUserTrap1190 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1190."
    ::= { s550notifications 1190 }

s550notificationsUserTrap1191 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1191."
    ::= { s550notifications 1191 }

s550notificationsUserTrap1192 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1192."
    ::= { s550notifications 1192 }

s550notificationsUserTrap1193 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1193."
    ::= { s550notifications 1193 }

s550notificationsUserTrap1194 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1194."
    ::= { s550notifications 1194 }

s550notificationsUserTrap1195 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1195."
    ::= { s550notifications 1195 }

s550notificationsUserTrap1196 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1196."
    ::= { s550notifications 1196 }

s550notificationsUserTrap1197 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1197."
    ::= { s550notifications 1197 }

s550notificationsUserTrap1198 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1198."
    ::= { s550notifications 1198 }

s550notificationsUserTrap1199 NOTIFICATION-TYPE
    OBJECTS { siteName, esIndex, esName, trapEventTypeNumber,
        trapEventTypeName, esIndexPoint, esPointName, esID,
        clock, trapIncludedValue, trapIncludedString,
        trapEventClassNumber, trapEventClassName }
    STATUS current
    DESCRIPTION
        "This user-defined trap is issued when an event happens that causes a
        trap with specific trap type 1199."
    ::= { s550notifications 1199 }

END
