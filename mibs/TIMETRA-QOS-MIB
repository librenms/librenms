TIMETRA-QOS-MIB DEFINITIONS ::= BEGIN

IMPORTS
    MODULE-IDENTITY, OBJECT-TYPE,
    Unsigned32, IpAddress, Integer32
                                                     FROM SNMPv2-SMI
    MODULE-COMPLIANCE, OBJECT-GROUP
                                                     FROM SNMPv2-CONF
    RowStatus, MacAddress, TruthValue, 
    StorageType, TimeStamp, TEXTUAL-CONVENTION
                                                     FROM SNMPv2-TC
    AtmServiceCategory, AtmTrafficDescrParamIndex,
    AtmVcIdentifier
                                                     FROM ATM-TC-MIB
    InetAddress, InetAddressType,                                                 
    InetAddressIPv6, InetAddressPrefixLength
                                                     FROM INET-ADDRESS-MIB

    timetraSRMIBModules, tmnxSRObjs,
    tmnxSRNotifyPrefix, tmnxSRConfs
                                                     FROM TIMETRA-GLOBAL-MIB

    TmnxMcMlpppClassIndex                            FROM TIMETRA-PORT-MIB
           
    Dot1PPriority, IpAddressPrefixLength,
    ServiceAccessPoint,TItemDescription,
    TNamedItem, TNamedItemOrEmpty, TLNamedItemOrEmpty,
    TDSCPValue,  TDSCPName, TDSCPNameOrEmpty,
    TIpProtocol, TTcpUdpPort,
    TTcpUdpPortOperator, TFrameType, TFCName,
    TLspExpValue, TQueueId, TIngressQueueId,
    TEgressQueueId, TIngressHsmdaQueueId,
    TEgressHsmdaQueueId, TPortSchedulerPIR, 
    TPortSchedulerCIR, THsmdaSchedulerPolicyGroupId,
    TWeight, TCIRRate, TPIRRate, THsmdaWeight, THsmdaWeightClass,
    THsmdaWrrWeight,
    THPolPIRRate, THPolCIRRate, TNonZeroWeight,
    TmnxEnabledDisabled, TSapIngressPolicyID,
    TAnyQosPolicyID,
    TSapEgressPolicyID, TIngressHsmdaPerPacketOffset,
    TEgressHsmdaPerPacketOffset,
    THsmdaPIRKRate, THsmdaCIRKRate,
    THsmdaPIRMRate, TIngressHsmdaCounterIdOrZero,
    TEgressHsmdaCounterIdOrZero,
    TMlpppQoSProfileId, TQosQGrpInstanceIDorZero,
    TFCNameOrEmpty,
    TMcFrQoSProfileId,
    TNetworkPolicyID, TItemScope, TItemMatch,
    TPriority, TPriorityOrDefault,
    TProfile, TProfileOrDei, TDEProfile, TDEProfileOrDei, TProfileOrNone,
    TAdaptationRule, TRemarkType,
    TPrecValue, TPrecValueOrNone,
    TBurstSize, TBurstPercent,
    TBurstHundredthsOfPercent, TBurstPercentOrDefault,
    TRatePercent, TPIRRatePercent,
    TLevel, TLevelOrDefault,
    TQueueMode, TEntryId, TMatchCriteria,
    TAtmTdpDescrType, TDEValue, TPolicerWeight,
    TIngPolicerId, TEgrPolicerId, TEgrPolicerIdOrNone, TEgrDynPolicerIdOrNone,
    TIngPolicerIdOrNone, TIngDynPolicerIdOrNone, TRateType,
    TPerPacketOffset, TBurstSizeBytes, TPlcrBurstSizeBytes,
    TmnxIngPolicerStatMode,
    TBurstLimit, TClassBurstLimit,
    TmnxEgrPolicerStatMode, QTagFullRange, QTagFullRangeOrNone,
    TMacFilterType, TBWRateType,
    TEgressQPerPacketOffset,TPolicerRateType,
    THsmdaPolicyIncludeQueues, THsmdaPolicyScheduleClass,
    THSMDABurstSizeBytes, THSMDAQueueBurstLimit,
    TProfileUseDEOrNone, TmnxSlopeMap,
    TAdvCfgRate, TMaxDecRate, TPortSchedulerPIRRate, TPortSchedLevel,
    TEgressPerPacketOffset,
    TPSPRateType,
     TQosQueuePIRRate, TQosQueueCIRRate,
    TmnxInternalSchedWeightMode,
    TIngressQPerPacketOffset,
    THPolVirtualSchePIRRate, THPolVirtualScheCIRRate,
    TIngressPolicerId, TIngressPolicerIdOrNone,
    TEgressPolicerId, TEgressPolicerIdOrNone
                                                     FROM TIMETRA-TC-MIB

    TEntryIdOrZero FROM TIMETRA-FILTER-MIB
    ;

timetraQosMIBModule   MODULE-IDENTITY
        LAST-UPDATED "201501010000Z"
        ORGANIZATION "Nokia"
        CONTACT-INFO
            "Nokia SROS Support
             Web: http://www.nokia.com"
        DESCRIPTION
            "This document is the SNMP MIB module to manage and provision
             Quality of Service features on Nokia SROS systems.

             Copyright 2003-2015 Nokia. All rights reserved.
             Reproduction of this document is authorized on the condition that
             the foregoing copyright notice is included.

             This SNMP MIB module (Specification) embodies Nokia's
             proprietary intellectual property.  Nokia retains
             all title and ownership in the Specification, including any
             revisions.

             Nokia grants all interested parties a non-exclusive
             license to use and distribute an unmodified copy of this
             Specification in connection with management of Nokia
             products, and without fee, provided this copyright notice and
             license appear on all copies.

             This Specification is supplied 'as is', and Nokia
             makes no warranty, either express or implied, as to the use,
             operation, condition, or performance of the Specification."

--
--  Revision History
--
        REVISION        "201501010000Z"
        DESCRIPTION     "Rev 13.0                1 Jan 2015 00:00
                         13.0 release of the TIMETRA-QOS-MIB."

        REVISION        "201401010000Z"
        DESCRIPTION     "Rev 12.0                1 Jan 2014 00:00
                         12.0 release of the TIMETRA-QOS-MIB."

        REVISION        "200902280000Z"
        DESCRIPTION     "Rev 7.0                28 Feb 2009 00:00
                         7.0 release of the TIMETRA-QOS-MIB."

        REVISION        "200807010000Z"
        DESCRIPTION     "Rev 6.1                01 Jul 2008 00:00
                         6.1 release of the TIMETRA-QOS-MIB."

        REVISION        "200801010000Z"
        DESCRIPTION     "Rev 6.0                01 Jan 2008 00:00
                         6.0 release of the TIMETRA-QOS-MIB."

        REVISION        "200701010000Z"
        DESCRIPTION     "Rev 5.0                01 Jan 2007 00:00
                         5.0 release of the TIMETRA-QOS-MIB."

        REVISION        "200602280000Z"
        DESCRIPTION     "Rev 4.0                28 Feb 2006 00:00
                         4.0 release of the TIMETRA-QOS-MIB."

        REVISION        "200508310000Z"
        DESCRIPTION     "Rev 3.0                31 Aug 2005 00:00
                         3.0 release of the TIMETRA-QOS-MIB."

        REVISION        "200501240000Z"
        DESCRIPTION     "Rev 2.1                24 Jan 2005 00:00
                         2.1 release of the TIMETRA-QOS-MIB."

        REVISION        "200401150000Z"
        DESCRIPTION     "Rev 2.0                    15 Jan 2004 00:00
                         2.0 release of the TIMETRA-QOS-MIB."

        REVISION        "200308150000Z"
        DESCRIPTION     "Rev 1.2                    15 Aug 2003 00:00
                         1.2 release of the TIMETRA-QOS-MIB."

        REVISION        "200301200000Z"
        DESCRIPTION     "Rev 1.0                    20 Jan 2003 00:00
                         1.0 Release of the TIMETRA-QOS-MIB."

        REVISION        "200105290000Z"
        DESCRIPTION     "Rev 0.1                    29 May 2001 00:00
                         Initial version of the TIMETRA-QOS-MIB."

        ::= { timetraSRMIBModules 16 }

tQosObjects                    OBJECT IDENTIFIER ::= { tmnxSRObjs 16 }
tQosNotifyPrefix              OBJECT IDENTIFIER ::= { tmnxSRNotifyPrefix 16}
    tQosNotifications           OBJECT IDENTIFIER ::= { tQosNotifyPrefix 0}
tmnxQosConformance             OBJECT IDENTIFIER ::= { tmnxSRConfs 16 }

tDSCPObjects                   OBJECT IDENTIFIER ::= { tQosObjects 1 }
tFCObjects                     OBJECT IDENTIFIER ::= { tQosObjects 2 }
tSapIngressObjects             OBJECT IDENTIFIER ::= { tQosObjects 3 }
tSapEgressObjects              OBJECT IDENTIFIER ::= { tQosObjects 4 }
tNetworkObjects                OBJECT IDENTIFIER ::= { tQosObjects 5 }
tNetworkQueueObjects           OBJECT IDENTIFIER ::= { tQosObjects 6 }
tSharedQueueObjects            OBJECT IDENTIFIER ::= { tQosObjects 7 }
tSlopeObjects                  OBJECT IDENTIFIER ::= { tQosObjects 10 }
tSchedulerObjects              OBJECT IDENTIFIER ::= { tQosObjects 12 }
tQosTimeStampObjects           OBJECT IDENTIFIER ::= { tQosObjects 20 }
tAtmTdpObjects                 OBJECT IDENTIFIER ::= { tQosObjects 21 }
tPoolObjects                   OBJECT IDENTIFIER ::= { tQosObjects 22 }
tMcMlpppIngressObjects         OBJECT IDENTIFIER ::= { tQosObjects 23 } 
tMcMlpppEgressObjects          OBJECT IDENTIFIER ::= { tQosObjects 24 }
tMcFrIngressObjects            OBJECT IDENTIFIER ::= { tQosObjects 25 } 
tMcFrEgressObjects             OBJECT IDENTIFIER ::= { tQosObjects 26 }
tQosPolicerObjects             OBJECT IDENTIFIER ::= { tQosObjects 27 }
tWrrObjects                    OBJECT IDENTIFIER ::= { tQosObjects 28 }
tQosDCObjects                  OBJECT IDENTIFIER ::= { tQosObjects 29 }
  tQosDCTimeStampObjs            OBJECT IDENTIFIER ::= { tQosDCObjects 1 } 
  tQosDCObjs                     OBJECT IDENTIFIER ::= { tQosDCObjects 2 }
tQosMatchListObjects           OBJECT IDENTIFIER ::= { tQosObjects 30 }

--
--
-- mib objects
--

--
--      TmnxMcFrClassIndex
--
TmnxMcFrClassIndex ::= TEXTUAL-CONVENTION
    STATUS      current
    DESCRIPTION
        "The TmnxMcFrClassIndex indicates the class
         of a Multiclass Fr bundle.
         For example, a 4-class Fr link has 4 classes with 
         indices 0, 1, 2, and 3."
    SYNTAX      INTEGER (0..15)

TProfileOrDeiOrNone ::= TEXTUAL-CONVENTION
    STATUS       current
    DESCRIPTION
        "the profile marking of a packet at the ingress."
    SYNTAX INTEGER { in(1), out(2), use-dei(13), none(0) }

TmnxSchedPlcyParentLocation ::= TEXTUAL-CONVENTION
    STATUS      current
    DESCRIPTION
        "TmnxSchedPlcyParentLocation is an enumerated integer that indicates
         the location in which the schedulers in the scheduler-policy
         will look to find their parent.
         
         none (1) - Indicates that the schedulers may not have a parent 
         configured.

         sub (2) - Indicates that the schedulers should look for their
         parent in the subscriber-profile's ingress or egress (as appropriate)
         scheduler policy. 

         vport (3) - Indicates that the schedulers should look for 
         their parent in the VPort's ingress or egress (as appropriate)
         scheduler policy."
    SYNTAX       INTEGER {
                    none    (1),
                    sub     (2),
                    vport   (3)
                 }
   

--
-- DSCP Name -> DSCP value mapping table
--

tDSCPNameTable OBJECT-TYPE
    SYNTAX       SEQUENCE OF TDSCPNameEntry
    MAX-ACCESS   not-accessible
    STATUS       current
    DESCRIPTION
        "A list of all DSCP Names.  DSCP Name entries must
         exist here and be active before they can be referenced
         elsewhere (e.g. IP filter)."
    ::= { tDSCPObjects 1 }

tDSCPNameEntry OBJECT-TYPE
    SYNTAX       TDSCPNameEntry
    MAX-ACCESS   not-accessible
    STATUS       current
    DESCRIPTION
        "Information about a particular DSCP Name, particularly
         the DSCP value. It maps a DSCP Name into a DSCP value.

         Some default entries are created by the agent.
         Default entries have tDSCPNameStorageType permanent,
         and can not be deleted.

         Entries cannot be created by user but may be supported later.

         An attempt to create a row in this table would return no creation."
    INDEX { tDSCPName }
    ::= { tDSCPNameTable 1 }

TDSCPNameEntry ::= SEQUENCE
    {
        tDSCPName            TDSCPName,
        tDSCPNameRowStatus   RowStatus,
        tDSCPNameStorageType StorageType,
        tDSCPNameDscpValue   TDSCPValue,
        tDSCPNameLastChanged TimeStamp
    }

tDSCPName OBJECT-TYPE
    SYNTAX       TDSCPName
    MAX-ACCESS   not-accessible
    STATUS       current
    DESCRIPTION
        "The name assigned to the DSCP Value."
    REFERENCE
        ""
    ::= { tDSCPNameEntry 1 }

tDSCPNameRowStatus OBJECT-TYPE
    SYNTAX       RowStatus
    MAX-ACCESS   read-create
    STATUS       current
    DESCRIPTION
        "Row Status of the entry."
    ::= { tDSCPNameEntry 2 }

tDSCPNameStorageType OBJECT-TYPE
    SYNTAX       StorageType
    MAX-ACCESS   read-create
    STATUS       current
    DESCRIPTION
        "The storage type of this row in the table."
    DEFVAL { nonVolatile }
    ::= { tDSCPNameEntry 3 }

tDSCPNameDscpValue OBJECT-TYPE
    SYNTAX       TDSCPValue
    MAX-ACCESS   read-create
    STATUS       current
    DESCRIPTION
        "The DSCP Value."
    REFERENCE
        ""
    DEFVAL { 0 }
    ::= { tDSCPNameEntry 4 }

tDSCPNameLastChanged OBJECT-TYPE
    SYNTAX       TimeStamp
    MAX-ACCESS   read-only
    STATUS       current
    DESCRIPTION
        "timestamp of last change to this row in tDSCPNameTable."
    ::= { tDSCPNameEntry 5 }

--
-- Forwarding Class name table
--

tFCNameTable OBJECT-TYPE
    SYNTAX       SEQUENCE OF TFCNameEntry
    MAX-ACCESS   not-accessible
    STATUS       current
    DESCRIPTION
        "A list of all Forwarding Class Names.  Forwarding Class Name entries
        must exist here and be active before they can be referenced
        elsewhere (e.g. qos queue)."
    ::= { tFCObjects 1 }

tFCNameEntry OBJECT-TYPE
    SYNTAX       TFCNameEntry
    MAX-ACCESS   not-accessible
    STATUS       current
    DESCRIPTION
        "Information about a particular Forwarding Class Name, particularly
         the Forwarding Class value.

         Some default entries are created by the agent.
         Default entries have tFCStorageType permanent,
         and can not be deleted.

         Entries cannot be created by user but maybe supported in future.

         An attempt to create a row in this table would return no creation."
    INDEX { tFCName }
    ::= { tFCNameTable 1 }

TFCNameEntry ::= SEQUENCE
    {
        tFCName               TFCName,
        tFCRowStatus          RowStatus,
        tFCStorageType        StorageType,
        tFCValue              Integer32,
        tFCNameLastChanged    TimeStamp
    }

tFCName OBJECT-TYPE
    SYNTAX       TFCName
    MAX-ACCESS   not-accessible
    STATUS       current
    DESCRIPTION "Forwarding class name."
    REFERENCE ""
    ::= { tFCNameEntry 1 }

tFCRowStatus OBJECT-TYPE
    SYNTAX       RowStatus
    MAX-ACCESS   read-create
    STATUS       current
    DESCRIPTION "Row Status of the entry."
    ::= { tFCNameEntry 2 }

tFCStorageType OBJECT-TYPE
    SYNTAX       StorageType
    MAX-ACCESS   read-create
    STATUS       current
    DESCRIPTION "The storage type of this row in the table."
    DEFVAL { nonVolatile }
    ::= { tFCNameEntry 3 }

tFCValue OBJECT-TYPE
    SYNTAX       Integer32 (0..7)
    MAX-ACCESS   read-create
    STATUS       current
    DESCRIPTION "FC Value."
    REFERENCE ""
    DEFVAL { 0 }
    ::= { tFCNameEntry 4 }

tFCNameLastChanged OBJECT-TYPE
    SYNTAX       TimeStamp
    MAX-ACCESS   read-only
    STATUS       current
    DESCRIPTION
        "timestamp of last change to this row in tFCNameTable."
    ::= { tFCNameEntry 5 }

--
-- sap-ingress policy table
--

tSapIngressTable OBJECT-TYPE
    SYNTAX       SEQUENCE OF TSapIngressEntry
    MAX-ACCESS   not-accessible
    STATUS       current
    DESCRIPTION  "  "
    ::= { tSapIngressObjects 1 }

tSapIngressEntry OBJECT-TYPE
    SYNTAX       TSapIngressEntry
    MAX-ACCESS   not-accessible
    STATUS       current
    DESCRIPTION
        "Information about a particular Sap Ingress Policy.

         sap-ingress policy (1) is the default entry.

         Default Entry is created by the agent, other entries are
         created by user.

         Default Entry cannot be modified/deleted. The other
         entries are deleted by user.

         There is no StorageType object, entries have a presumed
         StorageType of nonVolatile.
        "
    INDEX { tSapIngressIndex }
    ::= { tSapIngressTable 1 }

TSapIngressEntry ::= SEQUENCE
    {
        tSapIngressIndex                 TAnyQosPolicyID,
        tSapIngressRowStatus             RowStatus,
        tSapIngressScope                 TItemScope,
        tSapIngressDescription           TItemDescription,
        tSapIngressDefaultFC             TNamedItem,
        tSapIngressDefaultFCPriority     TPriority,
        tSapIngressMatchCriteria         TMatchCriteria,
        tSapIngressLastChanged           TimeStamp,
        tSapIngressHsmdaPacketOffset     TIngressHsmdaPerPacketOffset,
        tSapIngressDefFCHsmdaCntrOvr     TIngressHsmdaCounterIdOrZero,
        tSapIngressMacCritType           TMacFilterType,
        tSapIngressPolicyName            TLNamedItemOrEmpty
    }

tSapIngressIndex OBJECT-TYPE
    SYNTAX       TAnyQosPolicyID
    MAX-ACCESS   not-accessible
    STATUS       current
    DESCRIPTION
        "The value of tSapIngressIndex uniquely identifies sap-ingress QoS
         policy.

         User configured policies can only have values between (1..65535).
         All other values are reserved for system generated policies."
    ::= { tSapIngressEntry 1 }

tSapIngressRowStatus OBJECT-TYPE
    SYNTAX       RowStatus
    MAX-ACCESS   read-create
    STATUS       current
    DESCRIPTION
        "Row Status for the policy. The deletion of this row has
         an action of removing the dependent rows in the following
         tables :
           - tSapIngressQueueTable
           - tSapIngressDSCPTable
           - tSapIngressDot1pTable
        "
    ::= { tSapIngressEntry 2 }

tSapIngressScope OBJECT-TYPE
    SYNTAX       TItemScope
    MAX-ACCESS   read-create
    STATUS       current
    DESCRIPTION
        "Scope of the policy. If the scope is 'exclusive', it can only be
         instantiated once whereas it could have multiple instances if defined
         as 'exclusive'."
    DEFVAL { template }
    ::= { tSapIngressEntry 3 }

tSapIngressDescription OBJECT-TYPE
    SYNTAX       TItemDescription
    MAX-ACCESS   read-create
    STATUS       current
    DESCRIPTION
        "user-provided description of the policy."
    DEFVAL { ''H }
    ::= { tSapIngressEntry 4 }

tSapIngressDefaultFC OBJECT-TYPE
    SYNTAX       TNamedItem
    MAX-ACCESS   read-create
    STATUS       current
    DESCRIPTION
        "tSapIngressDefaultFC specifies the forwarding class or the
         sub forwarding class which should be used for all traffic that
         does not match a specific classification specified in this
         SAP ingress QoS policy.

         Specification of a sub forwarding class is also allowed. The
         format of a sub forwarding class is the concatenation of the
         base forwarding class and a sub class identifier in the form

             base-fc-name[.sub-fc-name]

         To reference a sub forwarding class, the mapping of the sub
         forwarding class should be existing in this QoS policy.

         If not specified explicitly, all traffic will be classified
         as best-effort 'be'."
    DEFVAL { 'be'H }
    ::= { tSapIngressEntry 5 }

tSapIngressDefaultFCPriority OBJECT-TYPE
    SYNTAX       TPriority
    MAX-ACCESS   read-create
    STATUS       current
    DESCRIPTION
        "the priority to assign to traffic ingressing as the default
         action queue."
    DEFVAL { low }
    ::= { tSapIngressEntry 6 }

tSapIngressMatchCriteria OBJECT-TYPE
    SYNTAX       TMatchCriteria
    MAX-ACCESS   read-only
    STATUS       current
    DESCRIPTION
        "indicates which type of match criteria the policy should use.
         when set to ip(1), the policy looks for match entries in
         tSapIngressIPCriteriaTable or tSapIngressIPv6CriteriaTable.
         When set to mac(2), the policy looks for match entries in 
         tSapIngressMacCriteriaTable.

         the value of tSapIngressMatchCriteria is set when the first
         match criteria table entry is created.  the value is set to
         none(3) when the last criteria table entry is removed.

         when tSapIngressMatchCriteria is set to ip(1), no
         tSapIngressMacCriteriaTable entries can be created.
         when set to mac(2), no tSapIngressIPCriteriaTable or 
         tSapIngressIPv6CriteriaTable entries can be created.
        "
    ::= { tSapIngressEntry 7 }

tSapIngressLastChanged OBJECT-TYPE
    SYNTAX       TimeStamp
    MAX-ACCESS   read-only
    STATUS       current
    DESCRIPTION
        "timestamp of last change to this row in tSapIngressTable."
    ::= { tSapIngressEntry 8 }

tSapIngressHsmdaPacketOffset    OBJECT-TYPE
    SYNTAX      TIngressHsmdaPerPacketOffset
    UNITS       "bytes"
    MAX-ACCESS  read-create
    STATUS      obsolete
    DESCRIPTION
        "The value of tSapIngressHsmdaPacketOffset specifies the
         value, in bytes, of the adjustment to make to the size of each
         packet for HSMDA queue accounting.

        This object is obsoleted in 10.0 Release."
    DEFVAL { 0 }
    ::= { tSapIngressEntry 9 }

tSapIngressDefFCHsmdaCntrOvr OBJECT-TYPE
    SYNTAX       TIngressHsmdaCounterIdOrZero
    MAX-ACCESS   read-create
    STATUS       obsolete
    DESCRIPTION
        "The value of the object tSapIngressDefFCHsmdaCntrOvr specifies
         the counter to use for all traffic that does not match a specific 
         classification specified in this SAP ingress QoS policy.

         A value of zero implies that the default counters should be used.

        This object is obsoleted in 10.0 Release."
    DEFVAL { 0 }
    ::= { tSapIngressEntry 10 }

tSapIngressMacCritType OBJECT-TYPE
    SYNTAX       TMacFilterType       
    MAX-ACCESS   read-create
    STATUS       current
    DESCRIPTION
        "tSapIngressMacCritType specifies which type of entries this mac filter
         can contain.

         If tSapIngressMacCritType is set to 'normal(1)', all match criteria
         are accepted except the criteria mentioned below that belong to type
         vid(3) or isid(2). 
         
         tSapIngressMacCritType 'isid(2)' is not supported here. 

         If tSapIngressMacCritType is set to vid(3) the only accepted match
         criteria for the filter entries are:
         - tSapIngressMacCritInnerTagValue
         - tSapIngressMacCritInnerTagMask 
         - tSapIngressMacCritOuterTagValue
         - tSapIngressMacCritOuterTagMask 
         
         tSapIngressMacCritType can only be changed if the filter
         has no entries.
         
         The value will be set to  'normal(1)' if IP or IPV6 criteria are added
         to the this SAP ingress QoS policy. Any change attempt in this case 
         will be silently discarded.
         "
    DEFVAL { normal }
    ::= { tSapIngressEntry 11 }

tSapIngressPolicyName OBJECT-TYPE
    SYNTAX       TLNamedItemOrEmpty
    MAX-ACCESS   read-create
    STATUS       current
    DESCRIPTION
        "The value of tSapIngressPolicyName specifies the name to associate
        with this policy."
    DEFVAL { ''H }
    ::= { tSapIngressEntry 12 }

--
-- sap-ingress policy queue table
--

tSapIngressQueueTable OBJECT-TYPE
    SYNTAX       SEQUENCE OF TSapIngressQueueEntry
    MAX-ACCESS   not-accessible
    STATUS       current
    DESCRIPTION
        "information about all sap-ingress policies' queues."
    ::= { tSapIngressObjects 2 }

tSapIngressQueueEntry OBJECT-TYPE
    SYNTAX       TSapIngressQueueEntry
    MAX-ACCESS   not-accessible
    STATUS       current
    DESCRIPTION
        "Information about a particular queue for a sap-ingress policy.

         Queue (1) is the used as a default for unicast and queue (11) is
         used as a default for multicast. Both these are created by the
         agent and can be edited but not removed from the system.

         Other entries are created by user."
    INDEX { tSapIngressIndex, tSapIngressQueue }
    ::= { tSapIngressQueueTable 1 }

TSapIngressQueueEntry ::= SEQUENCE
    {
        tSapIngressQueue                 TIngressQueueId,
        tSapIngressQueueRowStatus        RowStatus,
        tSapIngressQueueParent           TNamedItemOrEmpty,
        tSapIngressQueueLevel            TLevel,
        tSapIngressQueueWeight           TWeight,
        tSapIngressQueueCIRLevel         TLevelOrDefault,
        tSapIngressQueueCIRWeight        TWeight,
        tSapIngressQueueMCast            TruthValue,
        tSapIngressQueueExpedite         INTEGER,
        tSapIngressQueueCBS              TBurstSize,
        tSapIngressQueueMBS              TBurstSize,
        tSapIngressQueueHiPrioOnly       TBurstPercentOrDefault,
        tSapIngressQueuePIRAdaptation    TAdaptationRule,
        tSapIngressQueueCIRAdaptation    TAdaptationRule,
        tSapIngressQueueAdminPIR         TQosQueuePIRRate,
        tSapIngressQueueAdminCIR         TQosQueueCIRRate,
        tSapIngressQueueOperPIR          TPIRRate,
        tSapIngressQueueOperCIR          TCIRRate,
        tSapIngressQueueLastChanged      TimeStamp,
        tSapIngressQueuePoliced          TruthValue,
        tSapIngressQueueMode             TQueueMode,
        tSapIngressQueuePoolName         TNamedItemOrEmpty,
        tSapIngressQueueMBSBytes         TBurstSizeBytes,
        tSapIngressQueueBurstLimit       TBurstLimit,
        tSapIngressQueueAdminPIRPercent  Unsigned32,
        tSapIngressQueueAdminCIRPercent  Unsigned32,
        tSapIngressQueueRateType         TBWRateType,
        tSapIngressQueueAdvCfgPolicy     TNamedItemOrEmpty,
        tSapIngressQueuePktOffset        TIngressQPerPacketOffset
    }

tSapIngressQueue OBJECT-TYPE
    SYNTAX       TIngressQueueId (1..32)
    MAX-ACCESS   not-accessible
    STATUS       current
    DESCRIPTION
        "The queue ID is used as the secondary index to the table entry."
    ::= { tSapIngressQueueEntry 1 }

tSapIngressQueueRowStatus OBJECT-TYPE
    SYNTAX       RowStatus
    MAX-ACCESS   read-create
    STATUS       current
    DESCRIPTION
        "Row Status of the entry. This allows creation/deletion of rows in this
         table."
    ::= { tSapIngressQueueEntry 2 }

tSapIngressQueueParent OBJECT-TYPE
    SYNTAX       TNamedItemOrEmpty
    MAX-ACCESS   read-create
    STATUS       current
    DESCRIPTION
        "The scheduler to which this queue would be feeding to."
    DEFVAL { ''H }
    ::= { tSapIngressQueueEntry 3 }

tSapIngressQueueLevel OBJECT-TYPE
    SYNTAX       TLevel
    MAX-ACCESS   read-create
    STATUS       current
    DESCRIPTION
        "This specifies the level of priority while feeding to the parent."
    DEFVAL { 1 }
    ::= { tSapIngressQueueEntry 4 }

tSapIngressQueueWeight OBJECT-TYPE
    SYNTAX       TWeight
    MAX-ACCESS   read-create
    STATUS       current
    DESCRIPTION
        "The weight that needs to be used by the scheduler to which this queue
         would be feeding to."
    DEFVAL { 1 }
    ::= { tSapIngressQueueEntry 5 }

tSapIngressQueueCIRLevel OBJECT-TYPE
    SYNTAX       TLevelOrDefault
    MAX-ACCESS   read-create
    STATUS       current
    DESCRIPTION
        "This specifies the level of priority while feeding to the parent.
         The level '0' means treat all offered load for this queue as for
         the above CIR traffic."
    DEFVAL { 0 }
    ::= { tSapIngressQueueEntry 6 }

tSapIngressQueueCIRWeight OBJECT-TYPE
    SYNTAX       TWeight
    MAX-ACCESS   read-create
    STATUS       current
    DESCRIPTION
        "The weight that needs to be used until the committed rate by the
         scheduler to which this queue would be feeding to."
    DEFVAL { 1 }
    ::= { tSapIngressQueueEntry 7 }

tSapIngressQueueMCast OBJECT-TYPE
    SYNTAX       TruthValue
    MAX-ACCESS   read-create
    STATUS       current
    DESCRIPTION
        "This object specifies if this is a multicast queue or not."
    DEFVAL { false }
    ::= { tSapIngressQueueEntry 8 }

tSapIngressQueueExpedite OBJECT-TYPE
    SYNTAX       INTEGER {
                    expedited     (1),
                    auto-expedited(2),
                    non-expedited (3)
                 }
    MAX-ACCESS   read-create
    STATUS       current
    DESCRIPTION
        "tSapIngressQueueExpedite specifies the priority that this queue should
         be assigned by the hardware level schedulers.

         The value 'auto-expedited' implies that this attribute should be
         dynamically updated by looking at the forwarding classes mapping
         into this queue. In such a case the queue is treated as
         'non-expedited' if there is even a single non-expedited forwarding
         class using this queue.

         This attribute is associated with the queue at the time of creation and
         cannot be modified thereafter."
    DEFVAL { auto-expedited }
    ::= { tSapIngressQueueEntry 9 }

tSapIngressQueueCBS OBJECT-TYPE
    SYNTAX       TBurstSize
    MAX-ACCESS   read-create
    STATUS       current
    DESCRIPTION
        "The amount of reserved buffer space (in kilo bytes) for the queue."
    DEFVAL { -1 }
    ::= { tSapIngressQueueEntry 10 }

tSapIngressQueueMBS OBJECT-TYPE
    SYNTAX       TBurstSize
    MAX-ACCESS   read-create
    STATUS       obsolete
    DESCRIPTION
        "The maximum amount of buffer space (in kilo bytes) allowed for the
         queue.

         This object has been replaced with tSapIngressQueueMBSBytes object."
    DEFVAL { -1 }
    ::= { tSapIngressQueueEntry 11 }

tSapIngressQueueHiPrioOnly OBJECT-TYPE
    SYNTAX       TBurstPercentOrDefault
    MAX-ACCESS   read-create
    STATUS       current
    DESCRIPTION
        "The percentage of buffer space for the queue, used
         exclusively by high priority packets."
    DEFVAL { -1 }
    ::= { tSapIngressQueueEntry 12 }

tSapIngressQueuePIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tSapIngressQueueEntry 13 }

tSapIngressQueueCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tSapIngressQueueEntry 14 }

tSapIngressQueueAdminPIR OBJECT-TYPE
    SYNTAX       TQosQueuePIRRate
    UNITS        "kbps"
    MAX-ACCESS   read-create
    STATUS       current
    DESCRIPTION
        "The administrative PIR specified by the user."
    DEFVAL { -1 }
    ::= { tSapIngressQueueEntry 15 }

tSapIngressQueueAdminCIR OBJECT-TYPE
    SYNTAX       TQosQueueCIRRate
    UNITS        "kbps"
    MAX-ACCESS   read-create
    STATUS       current
    DESCRIPTION
        "The administrative CIR specified by the user."
    DEFVAL { 0 }
    ::= { tSapIngressQueueEntry 16 }

tSapIngressQueueOperPIR OBJECT-TYPE
    SYNTAX       TPIRRate
    UNITS        "kbps"
    MAX-ACCESS   read-only
    STATUS       obsolete
    DESCRIPTION
        "The operating PIR."
    ::= { tSapIngressQueueEntry 17 }

tSapIngressQueueOperCIR OBJECT-TYPE
    SYNTAX       TCIRRate
    UNITS        "kbps"
    MAX-ACCESS   read-only
    STATUS       obsolete
    DESCRIPTION
        "The operational value derived by computing the CIR value from
         the administrative CIR and PIR values and their corresponding
         adaptation rules."
    ::= { tSapIngressQueueEntry 18 }

tSapIngressQueueLastChanged OBJECT-TYPE
    SYNTAX       TimeStamp
    MAX-ACCESS   read-only
    STATUS       current
    DESCRIPTION
        "timestamp of last change to this row in tSapIngressQueueTable."
    ::= { tSapIngressQueueEntry 19 }

tSapIngressQueuePoliced OBJECT-TYPE
    SYNTAX       TruthValue
    MAX-ACCESS   read-create
    STATUS       current
    DESCRIPTION
        "tSapIngressQueuePoliced specifies that the out of profile
         traffic feeding into the physical queue instance should be
         dropped. tSapIngressQueuePoliced overrides the bandwidth
         specified by the object tSapIngressQueueAdminCIR."
    DEFVAL { false }
    ::= { tSapIngressQueueEntry 20 }

tSapIngressQueueMode OBJECT-TYPE
    SYNTAX       TQueueMode
    MAX-ACCESS   read-create
    STATUS       current
    DESCRIPTION
        "tSapIngressQueueMode specifies the mode in which the queue
         is operating. This attribute is associated with the queue
         at the time of creation and cannot be modified thereafter."
    DEFVAL { priority }
    ::= { tSapIngressQueueEntry 21 }

tSapIngressQueuePoolName OBJECT-TYPE   
    SYNTAX      TNamedItemOrEmpty
    MAX-ACCESS  read-create
    STATUS      current
    DESCRIPTION
        "The value of tSapIngressQueuePoolName specifies the name of 
         the pool to be applied for SAP ingress queue."
    DEFVAL { ''H }    
    ::= { tSapIngressQueueEntry 22 }

tSapIngressQueueMBSBytes OBJECT-TYPE
    SYNTAX       TBurstSizeBytes
    UNITS        "bytes"
    MAX-ACCESS   read-create
    STATUS       current
    DESCRIPTION
        "The maximum amount of buffer space (in bytes) allowed for the
         queue."
    DEFVAL { -1 }
    ::= { tSapIngressQueueEntry 23 }

tSapIngressQueueBurstLimit OBJECT-TYPE
    SYNTAX       TBurstLimit
    UNITS        "bytes"
    MAX-ACCESS   read-create
    STATUS       current
    DESCRIPTION
        "The value of tSapIngressQueueBurstLimit specifies the explicit shaping
         burst size of a queue."
    DEFVAL { -1 }
    ::= { tSapIngressQueueEntry 24 }

tSapIngressQueueAdminPIRPercent OBJECT-TYPE
    SYNTAX       Unsigned32 (1..10000)
    UNITS        "hundredths of a percent"
    MAX-ACCESS   read-create
    STATUS       current
    DESCRIPTION
        "The administrative PIR percentage, in hundredths of a percent.
         An 'inconsistentValue' error is returned if 
         tSapIngressQueueAdminPIRPercent is set to non-default value when the 
         object tSapIngressQueueRateType is set to 'kbps'."
    DEFVAL { 10000 }
    ::= { tSapIngressQueueEntry 25 }

tSapIngressQueueAdminCIRPercent OBJECT-TYPE
    SYNTAX       Unsigned32 (0..10000)
    UNITS        "hundredths of a percent"
    MAX-ACCESS   read-create
    STATUS       current
    DESCRIPTION
        "The administrative CIR percentage, in hundredths of a percent.
         An 'inconsistentValue' error is returned if 
         tSapIngressQueueAdminCIRPercent is set to non-default value when the
         object tSapIngressQueueRateType is set to 'kbps'."
    DEFVAL { 0 }
    ::= { tSapIngressQueueEntry 26 }

tSapIngressQueueRateType OBJECT-TYPE
    SYNTAX       TBWRateType
    MAX-ACCESS   read-create
    STATUS       current
    DESCRIPTION
        "The value of tSapIngressQueueRateType specifies the type of Ingress 
         Queue rate.

         When the value of the object is set to 'kbps', the ingresss queue rates
         are specified in kbps. The objects  tSapIngressQueueAdminCIRPercent and
         tSapIngressQueueAdminPIRPercent will be set to their default values.

         When the value of the object is set to either 'percentOfPortLimit' or
         'percentOfLocalLimit', the ingress queue rates are specified in 
         percentage. The objects tSapIngressQueueAdminCIR and 
         tSapIngressQueueAdminPIR will be set to their default values."
    DEFVAL { kbps }
    ::= { tSapIngressQueueEntry 27 }

tSapIngressQueueAdvCfgPolicy        OBJECT-TYPE
    SYNTAX      TNamedItemOrEmpty
    MAX-ACCESS  read-create
    STATUS      current
    DESCRIPTION
        "The value of tSapIngressQueueAdvCfgPolicy specifies the name of the 
         advanced configuration policy to be applied with this queue."
    DEFVAL { ''H }
    ::= { tSapIngressQueueEntry 28 }

tSapIngressQueuePktOffset           OBJECT-TYPE
    SYNTAX      TIngressQPerPacketOffset
    UNITS       "bytes"
    MAX-ACCESS  read-create
    STATUS      current
    DESCRIPTION
        "The value of tSapIngressQueuePktOffset specifies the value, in bytes,
         of the adjustment to make to the size of each packet for queue
         accounting.

         A 'wrongValue' error is returned while trying to set odd values for 
         this object.

         This object is only supported for queues residing on FP2 or greater
         forwarding planes. It is ignored for queues on FP1 forwarding planes."
    DEFVAL { 0 }
    ::= { tSapIngressQueueEntry 29 }

--
-- sap-ingress policy dscp table
--

tSapIngressDSCPTable OBJECT-TYPE
    SYNTAX       SEQUENCE OF TSapIngressDSCPEntry
    MAX-ACCESS   not-accessible
    STATUS       current
    DESCRIPTION
        "a list of all DSCP entries for all sap-ingress policies."
    ::= { tSapIngressObjects 3 }

tSapIngressDSCPEntry OBJECT-TYPE
    SYNTAX       TSapIngressDSCPEntry
    MAX-ACCESS   not-accessible
    STATUS       current
    DESCRIPTION
        "Information about a particular DSCP entry for a sap-ingress policy.

        Entries are created by user.
        Entries are deleted by user.

        There is no StorageType object, entries have a presumed
        StorageType of nonVolatile.

        in the event that one policy has multiple entries, and
        the tSapIngressDSCP values are the same, only one queue
        will be created (the queue for the lexicographically
        first tSapIngressDSCP).
        "
    INDEX { tSapIngressIndex, tSapIngressDSCP }
    ::= { tSapIngressDSCPTable 1 }

TSapIngressDSCPEntry ::= SEQUENCE
    {
        tSapIngressDSCP                    TDSCPName,
        tSapIngressDSCPRowStatus           RowStatus,
        tSapIngressDSCPFC                  TNamedItemOrEmpty,
        tSapIngressDSCPPriority            TPriorityOrDefault,
        tSapIngressDSCPLastChanged         TimeStamp,
        tSapIngressDSCPHsmdaCntrOvr    TIngressHsmdaCounterIdOrZero
    }

tSapIngressDSCP OBJECT-TYPE
    SYNTAX       TDSCPName
    MAX-ACCESS   not-accessible
    STATUS       current
    DESCRIPTION
        ""
    ::= { tSapIngressDSCPEntry 1 }

tSapIngressDSCPRowStatus OBJECT-TYPE
    SYNTAX       RowStatus
    MAX-ACCESS   read-create
    STATUS       current
    DESCRIPTION
        "This object allows creation/deletion of rows in this table."
    ::= { tSapIngressDSCPEntry 2 }

tSapIngressDSCPFC OBJECT-TYPE
    SYNTAX       TNamedItemOrEmpty
    MAX-ACCESS   read-create
    STATUS       current
    DESCRIPTION
        "tSapIngressDSCPFC specifies the forwarding class or the sub
         forwarding class to be used to classify all the traffic that
         matches the specific DSCP i.e. tSapIngressDSCP.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSapIngressDSCPFC is specified explicitly, this match
         will be ignored for classification purposes."
    DEFVAL { ''H }
    ::= { tSapIngressDSCPEntry 3 }

tSapIngressDSCPPriority OBJECT-TYPE
    SYNTAX       TPriorityOrDefault
    MAX-ACCESS   read-create
    STATUS       current
    DESCRIPTION
        ""
    DEFVAL { default }
    ::= { tSapIngressDSCPEntry 4 }

tSapIngressDSCPLastChanged OBJECT-TYPE
    SYNTAX       TimeStamp
    MAX-ACCESS   read-only
    STATUS       current
    DESCRIPTION
        "timestamp of last change to this row in tSapIngressDSCPTable."
    ::= { tSapIngressDSCPEntry 5 }

tSapIngressDSCPHsmdaCntrOvr OBJECT-TYPE
    SYNTAX       TIngressHsmdaCounterIdOrZero
    MAX-ACCESS   read-create
    STATUS       obsolete
    DESCRIPTION
        "The value of the object tSapIngressDSCPHsmdaCntrOvr 
         specifies the counter to use for all the traffic that
         matches the specific DSCP i.e. tSapIngressDSCP.

         A value of zero implies that the default counters should be used.

         This object is obsoleted in 10.0 Release."    
    DEFVAL { 0 }
    ::= { tSapIngressDSCPEntry 6 }

--
-- sap-ingress policy dot1p table
--

tSapIngressDot1pTable OBJECT-TYPE
    SYNTAX       SEQUENCE OF TSapIngressDot1pEntry
    MAX-ACCESS   not-accessible
    STATUS       current
    DESCRIPTION
        "a list of all dot1p entries for all sap-ingress policies."
    ::= { tSapIngressObjects 4 }

tSapIngressDot1pEntry OBJECT-TYPE
    SYNTAX       TSapIngressDot1pEntry
    MAX-ACCESS   not-accessible
    STATUS       current
    DESCRIPTION
        "Information about a particular dot1p match for a sap-ingress policy.
         Entries are created by user.
         Entries are deleted by user.

         There is no StorageType object, entries have a presumed
         StorageType of nonVolatile.
        "
    INDEX { tSapIngressIndex, tSapIngressDot1pValue }
    ::= { tSapIngressDot1pTable 1 }

TSapIngressDot1pEntry ::= SEQUENCE
    {
        tSapIngressDot1pValue               Dot1PPriority,
        tSapIngressDot1pRowStatus           RowStatus,
        tSapIngressDot1pFC                  TNamedItemOrEmpty,
        tSapIngressDot1pPriority            TPriorityOrDefault,
        tSapIngressDot1pLastChanged         TimeStamp,
        tSapIngressDot1pHsmdaCntrOvr    TIngressHsmdaCounterIdOrZero
    }

tSapIngressDot1pValue OBJECT-TYPE
    SYNTAX       Dot1PPriority (0..7)
    MAX-ACCESS   not-accessible
    STATUS       current
    DESCRIPTION
        "dot1p value to match in the packet.  this value is
        also used as an index so that for any dot1p value there
        is only one possible disposition queue and priority.
        "
    ::= { tSapIngressDot1pEntry 1 }

tSapIngressDot1pRowStatus OBJECT-TYPE
    SYNTAX       RowStatus
    MAX-ACCESS   read-create
    STATUS       current
    DESCRIPTION
        "Row Status for this sap-ingress policy's dot1p entry."
    ::= { tSapIngressDot1pEntry 2 }

tSapIngressDot1pFC OBJECT-TYPE
    SYNTAX       TNamedItemOrEmpty
    MAX-ACCESS   read-create
    STATUS       current
    DESCRIPTION
        "tSapIngressDot1pFC specifies the forwarding class or the sub
         forwarding class to be used to classify all the traffic that
         matches the specific Dot1p i.e. tSapIngressDot1pValue.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSapIngressDot1pFC is specified explicitly, this match
         will be ignored for classification purposes."
    DEFVAL { ''H }
    ::= { tSapIngressDot1pEntry 3 }

tSapIngressDot1pPriority OBJECT-TYPE
    SYNTAX       TPriorityOrDefault
    MAX-ACCESS   read-create
    STATUS       current
    DESCRIPTION
        "priority to use for packets that match the dot1p value
        tSapIngressDot1pValue."
    DEFVAL { default }
    ::= { tSapIngressDot1pEntry 4 }

tSapIngressDot1pLastChanged OBJECT-TYPE
    SYNTAX       TimeStamp
    MAX-ACCESS   read-only
    STATUS       current
    DESCRIPTION
        "timestamp of last change to this row in tSapIngressDot1pTable."
    ::= { tSapIngressDot1pEntry 5 }

tSapIngressDot1pHsmdaCntrOvr OBJECT-TYPE
    SYNTAX       TIngressHsmdaCounterIdOrZero
    MAX-ACCESS   read-create
    STATUS       obsolete
    DESCRIPTION
        "The value of the object tSapIngressDot1pHsmdaCntrOvr 
         specifies the counter to use for all the traffic that
         matches the specific Dot1p i.e. tSapIngressDot1pValue.

         A value of zero implies that the default counters should be used.

         This object is obsoleted in 10.0 Release."
    DEFVAL { 0 }
    ::= { tSapIngressDot1pEntry 6 }

--
-- sap-ingress policy ip criteria table
--

tSapIngressIPCriteriaTable OBJECT-TYPE
    SYNTAX       SEQUENCE OF TSapIngressIPCriteriaEntry
    MAX-ACCESS   not-accessible
    STATUS       current
    DESCRIPTION
        "information about all sap-ingress policies' ip-criteria entries."
    ::= { tSapIngressObjects 5 }

tSapIngressIPCriteriaEntry OBJECT-TYPE
    SYNTAX       TSapIngressIPCriteriaEntry
    MAX-ACCESS   not-accessible
    STATUS       current
    DESCRIPTION
        "Information about a particular ip-criteria entry for a sap-ingress
         policy.
         Entries are created by user.
         Entries are deleted by user.
         There is no StorageType object, entries have a presumed
         StorageType of nonVolatile.
        "
    INDEX { tSapIngressIndex, tSapIngressIPCriteriaIndex }
    ::= { tSapIngressIPCriteriaTable 1 }

TSapIngressIPCriteriaEntry ::= SEQUENCE
    {
        tSapIngressIPCriteriaIndex               TEntryId,
        tSapIngressIPCriteriaRowStatus           RowStatus,
        tSapIngressIPCriteriaDescription         TItemDescription,
        tSapIngressIPCriteriaActionFC            TNamedItemOrEmpty,
        tSapIngressIPCriteriaActionPriority      TPriorityOrDefault,
        tSapIngressIPCriteriaSourceIpAddr        IpAddress,
        tSapIngressIPCriteriaSourceIpMask        IpAddressPrefixLength,
        tSapIngressIPCriteriaDestIpAddr          IpAddress,
        tSapIngressIPCriteriaDestIpMask          IpAddressPrefixLength,
        tSapIngressIPCriteriaProtocol            TIpProtocol,
        tSapIngressIPCriteriaSourcePortValue1    TTcpUdpPort,
        tSapIngressIPCriteriaSourcePortValue2    TTcpUdpPort,
        tSapIngressIPCriteriaSourcePortOperator  TTcpUdpPortOperator,
        tSapIngressIPCriteriaDestPortValue1      TTcpUdpPort,
        tSapIngressIPCriteriaDestPortValue2      TTcpUdpPort,
        tSapIngressIPCriteriaDestPortOperator    TTcpUdpPortOperator,
        tSapIngressIPCriteriaDSCP                TDSCPNameOrEmpty,
        tSapIngressIPCriteriaFragment            TItemMatch,
        tSapIngressIPCriteriaLastChanged         TimeStamp,
        tSapIngressIPCritHsmdaCntrOvr            TIngressHsmdaCounterIdOrZero,
        tSapIngressIPCritSrcIpFullMask           IpAddress,
        tSapIngressIPCritDstIpFullMask           IpAddress,
        tSapIngressIPCritActionPolicer           TIngressPolicerIdOrNone,
        tSapIngressIPCriteriaIpPrecValue     Dot1PPriority,
        tSapIngressIPCriteriaIpPrecMask      Dot1PPriority
    }

tSapIngressIPCriteriaIndex OBJECT-TYPE
    SYNTAX       TEntryId
    MAX-ACCESS   not-accessible
    STATUS       current
    DESCRIPTION
        "unique identifier separates this entry from others in this
         policy."
    ::= { tSapIngressIPCriteriaEntry 1 }

tSapIngressIPCriteriaRowStatus OBJECT-TYPE
    SYNTAX       RowStatus
    MAX-ACCESS   read-create
    STATUS       current
    DESCRIPTION
        "Row Status for the IP Criteria entry."
    ::= { tSapIngressIPCriteriaEntry 2 }

tSapIngressIPCriteriaDescription OBJECT-TYPE
    SYNTAX       TItemDescription
    MAX-ACCESS   read-create
    STATUS       current
    DESCRIPTION
        "description of this IP criteria entry."
    DEFVAL { ''H }
    ::= { tSapIngressIPCriteriaEntry 3 }

tSapIngressIPCriteriaActionFC OBJECT-TYPE
    SYNTAX       TNamedItemOrEmpty
    MAX-ACCESS   read-create
    STATUS       current
    DESCRIPTION
        "tSapIngressIPCriteriaActionFC specifies the forwarding class
         or the sub forwarding class to be used to classify all the
         traffic that matches the specific IP criteria.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSapIngressIPCriteriaActionFC is specified explicitly,
         this match will be ignored for classification purposes."
    DEFVAL { ''H }
    ::= { tSapIngressIPCriteriaEntry 4 }

tSapIngressIPCriteriaActionPriority OBJECT-TYPE
    SYNTAX       TPriorityOrDefault
    MAX-ACCESS   read-create
    STATUS       current
    DESCRIPTION
       "priority for packets which match this entry's criteria.

        when set to default, the packet is sent to the queue
        from DSCP/dot1p/FC which matched the packet, using the
        priority from the DSCP/dot1p/FC which matched the packet."
    DEFVAL { default }
    ::= { tSapIngressIPCriteriaEntry 5 }

tSapIngressIPCriteriaSourceIpAddr OBJECT-TYPE
    SYNTAX       IpAddress
    MAX-ACCESS   read-create
    STATUS       current
    DESCRIPTION
        "IP address to match with source-IP of the packet."
    DEFVAL { '00000000'H }
    ::= { tSapIngressIPCriteriaEntry 6 }

tSapIngressIPCriteriaSourceIpMask OBJECT-TYPE
    SYNTAX       IpAddressPrefixLength
    MAX-ACCESS   read-create
    STATUS       current
    DESCRIPTION
        "If different from 0, the object tSapIngressIPCriteriaSourceIpMask
         specifies the IP Mask value for this policy IP Filter entry.
         The mask is ANDed with the received source IP address to match
         the tSapIngressIPCriteriaSourceIpAddr.

         If the value of tSapIngressIPCriteriaSourceIpMask is 0, and the
         value of tSapIngressIPCritSrcIpFullMask is non zero then the
         value of tSapIngressIPCritSrcIpFullMask is used as mask.

         If the value of tSapIngressIPCriteriaSourceIpMask is non zero,
         it will be equal to the mask expressed the object
         tSapIngressIPCritSrcIpFullMask.

         If both tSapIngressIPCriteriaSourceIpMask and
         tSapIngressIPCritSrcIpFullMask are set to 0, no matching is done
         on the source Ip address.

         If a value is specified for this object, then the value of the
         object tSapIngressIPCritSrcIpFullMask will be set to reflect
         this same mask."
    DEFVAL { 0 }
    ::= { tSapIngressIPCriteriaEntry 7 }

tSapIngressIPCriteriaDestIpAddr OBJECT-TYPE
    SYNTAX       IpAddress
    MAX-ACCESS   read-create
    STATUS       current
    DESCRIPTION
        "IP address to match with destination-IP of the packet."
    DEFVAL { '00000000'H }
    ::= { tSapIngressIPCriteriaEntry 8 }

tSapIngressIPCriteriaDestIpMask OBJECT-TYPE
    SYNTAX       IpAddressPrefixLength
    MAX-ACCESS   read-create
    STATUS       current
    DESCRIPTION
        "If different from 0, the object tSapIngressIPCriteriaDestIpMask
         specifies the IP Mask value for this policy IP Filter entry.
         The mask is ANDed with the received Destination IP address to match
         the tSapIngressIPCriteriaDestIpAddr.

         If the value of tSapIngressIPCriteriaDestIpMask is 0, and the
         value of tSapIngressIPCritDstIpFullMask is non zero then the
         value of tSapIngressIPCritDstIpFullMask is used as mask.

         If the value of tSapIngressIPCriteriaDestIpMask is non zero,
         it will be equal to the mask expressed the object
         tSapIngressIPCritDstIpFullMask.

         If both tSapIngressIPCriteriaDestIpMask and
         tSapIngressIPCritDstIpFullMask are set to 0, no matching is done
         on the Destination Ip address.

         If a value is specified for this object, then the value of the
         object tSapIngressIPCritDstIpFullMask will be set to reflect
         this same mask."
    DEFVAL { 0 }
    ::= { tSapIngressIPCriteriaEntry 9 }

tSapIngressIPCriteriaProtocol OBJECT-TYPE
    SYNTAX       TIpProtocol
    MAX-ACCESS   read-create
    STATUS       current
    DESCRIPTION
        "IP protocol to match.  use -1 to disable matching by IP protocol."
    DEFVAL { -1 }
    ::= { tSapIngressIPCriteriaEntry 10 }

tSapIngressIPCriteriaSourcePortValue1 OBJECT-TYPE
    SYNTAX       TTcpUdpPort
    MAX-ACCESS   read-create
    STATUS       current
    DESCRIPTION
        "TCP/UDP port value1. The value of this object is used according
         to the description for tSapIngressIPCriteriaSourcePortOperator."
    DEFVAL { 0 }
    ::= { tSapIngressIPCriteriaEntry 11 }

tSapIngressIPCriteriaSourcePortValue2 OBJECT-TYPE
    SYNTAX       TTcpUdpPort
    MAX-ACCESS   read-create
    STATUS       current
    DESCRIPTION
        "TCP/UDP port value2. The value of this object is used according
         to the description for tSapIngressIPCriteriaSourcePortOperator."
    DEFVAL { 0 }
    ::= { tSapIngressIPCriteriaEntry 12 }

tSapIngressIPCriteriaSourcePortOperator OBJECT-TYPE
    SYNTAX       TTcpUdpPortOperator
    MAX-ACCESS   read-create
    STATUS       current
    DESCRIPTION
        "The operator specifies the manner in which
         tSapIngressIPCriteriaSourcePortValue1 and 
         tSapIngressIPCriteriaSourcePortValue2 are to be used. The value 
         of these latter 2 objects and 
         tSapIngressIPCriteriaSourcePortOperator is used as described in 
         TTcpUdpPortOperator."
    DEFVAL { none }
    ::= { tSapIngressIPCriteriaEntry 13 }

tSapIngressIPCriteriaDestPortValue1 OBJECT-TYPE
    SYNTAX       TTcpUdpPort
    MAX-ACCESS   read-create
    STATUS       current
    DESCRIPTION
        "TCP/UDP port value1. The value of this object is used according
         to the description for tSapIngressIPCriteriaDestPortOperator."
    DEFVAL { 0 }
    ::= { tSapIngressIPCriteriaEntry 14 }

tSapIngressIPCriteriaDestPortValue2 OBJECT-TYPE
    SYNTAX       TTcpUdpPort
    MAX-ACCESS   read-create
    STATUS       current
    DESCRIPTION
        "TCP/UDP port value2. The value of this object is used according
         to the description for tSapIngressIPCriteriaDestPortOperator."
    DEFVAL { 0 }
    ::= { tSapIngressIPCriteriaEntry 15 }

tSapIngressIPCriteriaDestPortOperator OBJECT-TYPE
    SYNTAX       TTcpUdpPortOperator
    MAX-ACCESS   read-create
    STATUS       current
    DESCRIPTION
        "The operator specifies the manner in which
         tSapIngressIPCriteriaDestPortValue1 and 
         tSapIngressIPCriteriaDestPortValue2 are to be used. The value 
         of these latter 2 objects and 
         tSapIngressIPCriteriaDestPortOperator is used as described in 
         TTcpUdpPortOperator."
    DEFVAL { none }
    ::= { tSapIngressIPCriteriaEntry 16 }

tSapIngressIPCriteriaDSCP OBJECT-TYPE
    SYNTAX       TDSCPNameOrEmpty
    MAX-ACCESS   read-create
    STATUS       current
    DESCRIPTION
        "DSCP value to match in the packet"
    DEFVAL { ''H }
    ::= { tSapIngressIPCriteriaEntry 17 }

tSapIngressIPCriteriaFragment OBJECT-TYPE
    SYNTAX       TItemMatch
    MAX-ACCESS   read-create
    STATUS       current
    DESCRIPTION
        "matches when the packet is a fragment (true)
         or when the packet is not a fragment (false)
         or matches all packets fragmented or not (off)."
    DEFVAL { off }
    ::= { tSapIngressIPCriteriaEntry 19 }

tSapIngressIPCriteriaLastChanged OBJECT-TYPE
    SYNTAX       TimeStamp
    MAX-ACCESS   read-only
    STATUS       current
    DESCRIPTION
        "timestamp of last change to this row in tSapIngressIPCriteriaTable."
    ::= { tSapIngressIPCriteriaEntry 20 }

tSapIngressIPCritHsmdaCntrOvr OBJECT-TYPE
    SYNTAX       TIngressHsmdaCounterIdOrZero
    MAX-ACCESS   read-create
    STATUS       obsolete
    DESCRIPTION
        "The value of the object tSapIngressIPCritHsmdaCntrOvr specifies
         the Hsmda counter to use for matching packets. This value will be
         ignored when the sap-ingress policy specified by tSapIngressIndex,
         is applied to a SAP on a non-Hsmda MDA type. 

         A value of zero implies that the default counters should be used.

         This object is obsoleted in 10.0 Release."
    DEFVAL { 0 }
    ::= { tSapIngressIPCriteriaEntry 21 }

tSapIngressIPCritSrcIpFullMask OBJECT-TYPE
    SYNTAX       IpAddress
    MAX-ACCESS  read-create
    STATUS      current
    DESCRIPTION
        "If different from 0, the object tSapIngressIPCritSrcIpFullMask
         specifies the IP Mask value for this policy IP Filter entry.
         The mask is ANDed with the received Source IP address to match
         the tSapIngressIPCriteriaSourceIpAddr.

         If the value of tSapIngressIPCriteriaSourceIpMask
         is non zero, it will be equal to the mask expressed in the object
         tSapIngressIPCritSrcIpFullMask.

         If both tSapIngressIPCriteriaSourceIpMask and
         tSapIngressIPCritSrcIpFullMask are set to 0, no matching is done
         on the Source IP address.

         If a regular mask is specified for tSapIngressIPCritSrcIpFullMask
         then the value of tSapIngressIPCriteriaSourceIpMask will
         be changed to reflect this value."
    DEFVAL { 0 }
    ::= { tSapIngressIPCriteriaEntry 22 }

tSapIngressIPCritDstIpFullMask OBJECT-TYPE
    SYNTAX       IpAddress
    MAX-ACCESS  read-create
    STATUS      current
    DESCRIPTION
        "If different from 0, the object tSapIngressIPCritDstIpFullMask
         specifies the IP Mask value for this policy IP Filter entry.
         The mask is ANDed with the received Dest IP address to match
         the tSapIngressIPCriteriaDestIpAddr.

         If the value of tSapIngressIPCriteriaDestIpMask
         is non zero, it will be equal to the mask expressed in the object
         tSapIngressIPCritDstIpFullMask.

         If both tSapIngressIPCriteriaDestIpMask and
         tSapIngressIPCritDstIpFullMask are set to 0, no matching is done
         on the Dest IP address.

         If a regular mask is specified for tSapIngressIPCritDstIpFullMask
         then the value of tSapIngressIPCriteriaDestIpMask will
         be changed to reflect this value."
    DEFVAL { 0 }
    ::= { tSapIngressIPCriteriaEntry 23 }

tSapIngressIPCritActionPolicer OBJECT-TYPE
    SYNTAX       TIngressPolicerIdOrNone
    MAX-ACCESS   read-create
    STATUS       current
    DESCRIPTION
        "The value of tSapIngressIPCritActionPolicer specifies the policer
         identifier to be used for the traffic matching this IP Criteria Entry.
         It provides the ability to direct specific traffic to a different SAP
         ingress policer (tSapIngressIPCritActionPolicer) independently from
         that configured for the traffic's FC in tSapIngressFCPolicer. This
         action policer will be referred to as a bypass-policer.
         
         An 'inconsistentValue' error is returned if tSapIngressIPCritActionPolicer
         is set to a non-default value when tSapIngressIPCriteriaRowStatus is set
         to not in service."
    DEFVAL { 0 }
    ::= { tSapIngressIPCriteriaEntry 24 }


tSapIngressIPCriteriaIpPrecValue OBJECT-TYPE
    SYNTAX       Dot1PPriority
    MAX-ACCESS   read-create
    STATUS       current
    DESCRIPTION ""
    DEFVAL { -1 }
    ::= { tSapIngressIPCriteriaEntry 31 }

tSapIngressIPCriteriaIpPrecMask OBJECT-TYPE
    SYNTAX       Dot1PPriority (0..7)
    MAX-ACCESS   read-create
    STATUS       current
    DESCRIPTION ""
    DEFVAL { 0 }
    ::= { tSapIngressIPCriteriaEntry 32 }


--
-- sap-ingress policy mac criteria table
--

tSapIngressMacCriteriaTable OBJECT-TYPE
    SYNTAX       SEQUENCE OF TSapIngressMacCriteriaEntry
    MAX-ACCESS   not-accessible
    STATUS       current
    DESCRIPTION
        "information about all sap-ingress policies' mac-criteria entries."
    ::= { tSapIngressObjects 6 }

tSapIngressMacCriteriaEntry OBJECT-TYPE
    SYNTAX       TSapIngressMacCriteriaEntry
    MAX-ACCESS   not-accessible
    STATUS       current
    DESCRIPTION
        "Information about a particular mac-criteria entry
         for a sap-ingress policy.
         Entries are created by user.
         Entries are deleted by user.
         There is no StorageType object, entries have a presumed
         StorageType of nonVolatile."
    INDEX { tSapIngressIndex, tSapIngressMacCriteriaIndex }
    ::= { tSapIngressMacCriteriaTable 1 }

TSapIngressMacCriteriaEntry ::= SEQUENCE
    {
        tSapIngressMacCriteriaIndex          TEntryId,
        tSapIngressMacCriteriaRowStatus      RowStatus,
        tSapIngressMacCriteriaDescription    TItemDescription,
        tSapIngressMacCriteriaActionFC       TNamedItemOrEmpty,
        tSapIngressMacCriteriaActionPriority TPriorityOrDefault,
        tSapIngressMacCriteriaFrameType      TFrameType,
        tSapIngressMacCriteriaSrcMacAddr     MacAddress,
        tSapIngressMacCriteriaSrcMacMask     MacAddress,
        tSapIngressMacCriteriaDstMacAddr     MacAddress,
        tSapIngressMacCriteriaDstMacMask     MacAddress,
        tSapIngressMacCriteriaDot1PValue     Dot1PPriority,
        tSapIngressMacCriteriaDot1PMask      Dot1PPriority,
        tSapIngressMacCriteriaEthernetType   Integer32,
        tSapIngressMacCriteriaDSAP           ServiceAccessPoint,
        tSapIngressMacCriteriaDSAPMask       ServiceAccessPoint,
        tSapIngressMacCriteriaSSAP           ServiceAccessPoint,
        tSapIngressMacCriteriaSSAPMask       ServiceAccessPoint,
        tSapIngressMacCriteriaSnapPid        Integer32,
        tSapIngressMacCriteriaSnapOui        INTEGER,
        tSapIngressMacCriteriaLastChanged    TimeStamp,
        tSapIngressMacCriteriaAtmVci         AtmVcIdentifier,
        tSapIngressMacCritInnerTagValue      QTagFullRangeOrNone,
        tSapIngressMacCritInnerTagMask       QTagFullRange,
        tSapIngressMacCritOuterTagValue      QTagFullRangeOrNone,
        tSapIngressMacCritOuterTagMask       QTagFullRange,
        tSapIngressMacCritActionPolicer      TIngressPolicerIdOrNone
    }

tSapIngressMacCriteriaIndex OBJECT-TYPE
    SYNTAX       TEntryId
    MAX-ACCESS   not-accessible
    STATUS       current
    DESCRIPTION ""
    ::= { tSapIngressMacCriteriaEntry 1 }

tSapIngressMacCriteriaRowStatus OBJECT-TYPE
    SYNTAX       RowStatus
    MAX-ACCESS   read-create
    STATUS       current
    DESCRIPTION ""
    ::= { tSapIngressMacCriteriaEntry 2 }

tSapIngressMacCriteriaDescription OBJECT-TYPE
    SYNTAX       TItemDescription
    MAX-ACCESS   read-create
    STATUS       current
    DESCRIPTION ""
    DEFVAL { ''H }
    ::= { tSapIngressMacCriteriaEntry 3 }

tSapIngressMacCriteriaActionFC OBJECT-TYPE
    SYNTAX       TNamedItemOrEmpty
    MAX-ACCESS   read-create
    STATUS       current
    DESCRIPTION
        "tSapIngressMacCriteriaActionFC specifies the forwarding class
         or the sub forwarding class to be used to classify all the
         traffic that matches the specific Mac criteria.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSapIngressMacCriteriaActionFC is specified explicitly,
         this match will be ignored for classification purposes."
    ::= { tSapIngressMacCriteriaEntry 4 }

tSapIngressMacCriteriaActionPriority OBJECT-TYPE
    SYNTAX       TPriorityOrDefault
    MAX-ACCESS   read-create
    STATUS       current
    DESCRIPTION ""
    DEFVAL { default }
    ::= { tSapIngressMacCriteriaEntry 5 }

tSapIngressMacCriteriaFrameType OBJECT-TYPE
    SYNTAX       TFrameType
    MAX-ACCESS   read-create
    STATUS       current
    DESCRIPTION
        "The type of mac frame for which we are defining this match criteria."
    DEFVAL { e802dot3 }
    ::= { tSapIngressMacCriteriaEntry 6 }

tSapIngressMacCriteriaSrcMacAddr OBJECT-TYPE
    SYNTAX       MacAddress
    MAX-ACCESS   read-create
    STATUS       current
    DESCRIPTION ""
    DEFVAL { '000000000000'H }
    ::= { tSapIngressMacCriteriaEntry 8 }

tSapIngressMacCriteriaSrcMacMask OBJECT-TYPE
    SYNTAX       MacAddress
    MAX-ACCESS   read-create
    STATUS       current
    DESCRIPTION ""
    DEFVAL { '000000000000'H }
    ::= { tSapIngressMacCriteriaEntry 9 }

tSapIngressMacCriteriaDstMacAddr OBJECT-TYPE
    SYNTAX       MacAddress
    MAX-ACCESS   read-create
    STATUS       current
    DESCRIPTION ""
    DEFVAL { '000000000000'H }
    ::= { tSapIngressMacCriteriaEntry 10 }

tSapIngressMacCriteriaDstMacMask OBJECT-TYPE
    SYNTAX       MacAddress
    MAX-ACCESS   read-create
    STATUS       current
    DESCRIPTION ""
    DEFVAL { '000000000000'H }
    ::= { tSapIngressMacCriteriaEntry 11 }

tSapIngressMacCriteriaDot1PValue OBJECT-TYPE
    SYNTAX       Dot1PPriority
    MAX-ACCESS   read-create
    STATUS       current
    DESCRIPTION ""
    DEFVAL { -1 }
    ::= { tSapIngressMacCriteriaEntry 12 }

tSapIngressMacCriteriaDot1PMask OBJECT-TYPE
    SYNTAX       Dot1PPriority (0..7)
    MAX-ACCESS   read-create
    STATUS       current
    DESCRIPTION ""
    DEFVAL { 0 }
    ::= { tSapIngressMacCriteriaEntry 13 }

tSapIngressMacCriteriaEthernetType OBJECT-TYPE
    SYNTAX       Integer32 (-1 | 1536..65535)
    MAX-ACCESS   read-create
    STATUS       current
    DESCRIPTION
        "the ethernet type, ssap/dsap, and snap-pid match criteria
         are mutually exclusive and only one can be set per entry."
    DEFVAL { -1 }
    ::= { tSapIngressMacCriteriaEntry 14 }

tSapIngressMacCriteriaDSAP OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tSapIngressMacCriteriaEntry 15 }

tSapIngressMacCriteriaDSAPMask OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tSapIngressMacCriteriaEntry 16 }

tSapIngressMacCriteriaSSAP OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tSapIngressMacCriteriaEntry 17 }

tSapIngressMacCriteriaSSAPMask OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tSapIngressMacCriteriaEntry 18 }

tSapIngressMacCriteriaSnapPid OBJECT-TYPE
    SYNTAX       Integer32 (-1 | 0..65535)
    MAX-ACCESS   read-create
    STATUS       current
    DESCRIPTION
        "the ethernet type, ssap/dsap, and snap-pid match criteria
         are mutually exclusive and only one can be set per entry."
    DEFVAL { -1 }
    ::= { tSapIngressMacCriteriaEntry 19 }

tSapIngressMacCriteriaSnapOui OBJECT-TYPE
    SYNTAX          INTEGER { off(1), zero(2), nonZero(3) }
    MAX-ACCESS      read-create
    STATUS          current
    DESCRIPTION     "whether to match snap-oui, and what to match."
    DEFVAL { off }
    ::= { tSapIngressMacCriteriaEntry 20 }

tSapIngressMacCriteriaLastChanged OBJECT-TYPE
    SYNTAX       TimeStamp
    MAX-ACCESS   read-only
    STATUS       current
    DESCRIPTION
        "timestamp of last change to this row in tSapIngressMacCriteriaTable."
    ::= { tSapIngressMacCriteriaEntry 21 }

tSapIngressMacCriteriaAtmVci OBJECT-TYPE
    SYNTAX          AtmVcIdentifier
    MAX-ACCESS      read-create
    STATUS          current
    DESCRIPTION
        "The value of tSapIngressMacCriteriaAtmVci specifies ATM VC Identifier
         to match as part of the MAC criteria for this SAP on the ingress.

         An inconsistentValue error is returned if this object is set when
         tSapIngressMacCriteriaFrameType is not set to 'atm'."
    DEFVAL { 0 }
    ::= { tSapIngressMacCriteriaEntry 22 }

tSapIngressMacCritInnerTagValue OBJECT-TYPE
    SYNTAX       QTagFullRangeOrNone
    MAX-ACCESS   read-create
    STATUS       current
    DESCRIPTION
        "The value of tSapIngressMacCritInnerTagValue specifies the value to
         match against the VID of the second VLAN tag in the packet
         that is carried transparently through the service (the second vlan tag
         after the service delimiting tags).

         This object can only be set if  tSapIngressMacCritType is set to 'vid(3)'.
         
         The (default) value of '-1' indicates no VLAN tag matching will be
         performed."
    DEFVAL { -1 }
    ::= { tSapIngressMacCriteriaEntry 23 }

tSapIngressMacCritInnerTagMask OBJECT-TYPE
    SYNTAX       QTagFullRange (1..4095)
    MAX-ACCESS   read-create
    STATUS       current
    DESCRIPTION
        "The value of tSapIngressMacCritInnerTagMask is applied as a mask to VID
         of the inner VLAN tag of the packet prior to comparing it
         with tSapIngressMacCritInnerTagValue.  The inner tag is the second tag
         in the packet that is carried transparently through the
         service (the second tag after the service delimiting tags).

         This object can only be set if tSapIngressMacCritType is set
         to 'vid(3)'."
    DEFVAL { 4095 } -- 0xFFF : all ones mask.
    ::= { tSapIngressMacCriteriaEntry 24 }

tSapIngressMacCritOuterTagValue OBJECT-TYPE
    SYNTAX       QTagFullRangeOrNone
    MAX-ACCESS   read-create
    STATUS       current
    DESCRIPTION
        "The value of tSapIngressMacCritOuterTagValue specifies the value to
         match against the VID of the first VLAN tag in the packet that
         is carried transparently through the service (the first vlan tag after
         the service delimiting tags).

         This object can only be set if tSapIngressMacCritType is set to 'vid(3)'.

         The (default) value of '-1' indicates no outer VLAN tag matching will
         be performed."
    DEFVAL { -1 }
    ::= { tSapIngressMacCriteriaEntry 25 }

tSapIngressMacCritOuterTagMask OBJECT-TYPE
    SYNTAX       QTagFullRange (1..4095)
    MAX-ACCESS   read-create
    STATUS       current
    DESCRIPTION
        "The value of tSapIngressMacCritOuterTagMask is applied as a mask to VID
         of the outer VLAN tag of the packet prior to comparing it
         with tSapIngressMacCritOuterTagValue.  The outer tag is the first tag
         in the packet that is carried transparently through the
         service (the first tag after the service delimiting tags).

         This object can only be set if tSapIngressMacCritType is set to 'vid(3)'."
    DEFVAL { 4095 } -- 0xFFF : all ones mask.
    ::= { tSapIngressMacCriteriaEntry 26 }

tSapIngressMacCritActionPolicer OBJECT-TYPE
    SYNTAX       TIngressPolicerIdOrNone
    MAX-ACCESS   read-create
    STATUS       current
    DESCRIPTION
        "The value of tSapIngressMacCritActionPolicer specifies the policer
         identifier to be used for the traffic matching this MAC Criteria Entry.
         It provides the ability to direct specific traffic to a different SAP
         ingress policer (tSapIngressMacCritActionPolicer) independently from
         that configured for the traffic's FC in tSapIngressFCPolicer. This
         action policer will be referred to as a bypass-policer."
    DEFVAL { 0 }
    ::= { tSapIngressMacCriteriaEntry 27 }
    
--
-- sap-ingress policy fc table
--

tSapIngressFCTable OBJECT-TYPE
    SYNTAX       SEQUENCE OF TSapIngressFCEntry
    MAX-ACCESS   not-accessible
    STATUS       current
    DESCRIPTION
        "This table maintains the mapping of a particular
         forwarding class traffic into the specified queue."
    ::= { tSapIngressObjects 7 }

tSapIngressFCEntry OBJECT-TYPE
    SYNTAX       TSapIngressFCEntry
    MAX-ACCESS   not-accessible
    STATUS       current
    DESCRIPTION
        "Information about a particular sap-ingress policy's
         forwarding class mappings to queues.

         Entries are created and deleted by user. They have
         a presumed StorageType of nonVolatile."
    INDEX { tSapIngressIndex, tSapIngressFCName }
    ::= { tSapIngressFCTable 1 }

TSapIngressFCEntry ::= SEQUENCE
    {
        tSapIngressFCName              TNamedItem,
        tSapIngressFCRowStatus         RowStatus,
        tSapIngressFCQueue             TIngressQueueId,
        tSapIngressFCMCastQueue        TIngressQueueId,
        tSapIngressFCBCastQueue        TIngressQueueId,
        tSapIngressFCUnknownQueue      TIngressQueueId,
        tSapIngressFCLastChanged       TimeStamp,
        tSapIngressFCInProfRemark      TRemarkType,
        tSapIngressFCInProfDscp        TNamedItemOrEmpty,
        tSapIngressFCInProfPrec        TPrecValueOrNone,
        tSapIngressFCOutProfRemark     TRemarkType,
        tSapIngressFCOutProfDscp       TNamedItemOrEmpty,
        tSapIngressFCOutProfPrec       TPrecValueOrNone,
        tSapIngressFCProfile           TProfileOrNone,
        tSapIngressFCHsmdaQueue        TIngressHsmdaQueueId,
        tSapIngressFCHsmdaMCastQueue   TIngressHsmdaQueueId,
        tSapIngressFCHsmdaBCastQueue   TIngressHsmdaQueueId,
        tSapIngressFCDE1OutOfProfile   TruthValue,
        tSapIngressFCQGrp              TNamedItemOrEmpty,
        tSapIngressFCQGrpMCast         TNamedItemOrEmpty,
        tSapIngressFCQGrpBCast         TNamedItemOrEmpty,
        tSapIngressFCQGrpUnknown       TNamedItemOrEmpty,
        tSapIngressFCPolicer           TIngressPolicerIdOrNone,
        tSapIngressFCMCastPolicer      TIngressPolicerIdOrNone,
        tSapIngressFCBCastPolicer      TIngressPolicerIdOrNone,
        tSapIngressFCUnknownPolicer    TIngressPolicerIdOrNone,
        tSapIngressFCPlcrFPQGrp        TruthValue,
        tSapIngressFCMCastPlcrFPQGrp   TruthValue,
        tSapIngressFCBCastPlcrFPQGrp   TruthValue,
        tSapIngressFCUnknownPlcrFPQGrp TruthValue,
        tSapIngressFCEgressOverrideFC  TFCNameOrEmpty
    }

tSapIngressFCName OBJECT-TYPE
    SYNTAX       TNamedItem
    MAX-ACCESS   not-accessible
    STATUS       current
    DESCRIPTION
        "tSapIngressFCName specifies the forwarding class or the sub
         forwarding class for which this mapping is defined.

         A sub forwarding class mapping can also be configured. The
         format of a sub forwarding class is the concatenation of the
         base forwarding class and a sub class identifier in the form

             base-fc-name[.sub-fc-name]

         A sub forwarding class mapping should exist in this table if
         any explicit match criteria in this SAP ingress QoS policy
         try to use it. However, it is not the same for the base
         forwarding classes."
    ::= { tSapIngressFCEntry 1 }

tSapIngressFCRowStatus OBJECT-TYPE
    SYNTAX       RowStatus
    MAX-ACCESS   read-create
    STATUS       current
    DESCRIPTION
        "Row Status for this queue."
    ::= { tSapIngressFCEntry 2 }

tSapIngressFCQueue OBJECT-TYPE
    SYNTAX       TIngressQueueId
    MAX-ACCESS   read-create
    STATUS       current
    DESCRIPTION
        "The specific queue to be used for packets in this forwarding class.

         Default value for this object along with default value for
         tSapIngressFCQGrp implies that the default queues should be used."
    DEFVAL { 0 }
    ::= { tSapIngressFCEntry 3 }

tSapIngressFCMCastQueue OBJECT-TYPE
    SYNTAX       TIngressQueueId
    MAX-ACCESS   read-create
    STATUS       current
    DESCRIPTION
        "The specific multicast queue to be used for packets in this forwarding
         class. The queue is used only for specific entities and will be
         ignored wherever it is irrelevant.

         Default value for this object along with default value for
         tSapIngressFCQGrpMCast implies that the default queues should be used."
    DEFVAL { 0 }
    ::= { tSapIngressFCEntry 4 }

tSapIngressFCBCastQueue OBJECT-TYPE
    SYNTAX       TIngressQueueId
    MAX-ACCESS   read-create
    STATUS       current
    DESCRIPTION
        "The specific broadcast queue to be used for packets in this forwarding
         class. The queue is used only for specific entities and will be
         ignored wherever it is irrelevant.

         Default value for this object along with default value for
         tSapIngressFCQGrpBCast implies that the default queues should be used."
    DEFVAL { 0 }
    ::= { tSapIngressFCEntry 5 }

tSapIngressFCUnknownQueue OBJECT-TYPE
    SYNTAX       TIngressQueueId
    MAX-ACCESS   read-create
    STATUS       current
    DESCRIPTION
        "The specific unknown destination queue to be used for packets in this
         forwarding class. The queue is used only for specific entities and
         will be ignored wherever it is irrelevant.

         Default value for this object along with default value for
         tSapIngressFCQGrpUnknown implies that the default queues should be used."
    DEFVAL { 0 }
    ::= { tSapIngressFCEntry 6 }

tSapIngressFCLastChanged OBJECT-TYPE
    SYNTAX       TimeStamp
    MAX-ACCESS   read-only
    STATUS       current
    DESCRIPTION
        "tSapIngressFCLastChanged indicates the value of sysUpTime
         when the forwarding class entry was last modified."
    ::= { tSapIngressFCEntry 7 }

tSapIngressFCInProfRemark OBJECT-TYPE
    SYNTAX       TRemarkType
    MAX-ACCESS   read-create
    STATUS       current
    DESCRIPTION
        "tSapIngressFCInProfRemark specifies the remarking type to
         be used for the in profile packets feeding into the queues."
    DEFVAL { none }
    ::= { tSapIngressFCEntry 8 }

tSapIngressFCInProfDscp OBJECT-TYPE
    SYNTAX       TNamedItemOrEmpty
    MAX-ACCESS   read-create
    STATUS       current
    DESCRIPTION
        "tSapIngressFCInProfDscp specifies the DSCP to be used while
         remarking the in profile packets when the in-profile
         remarking type, tSapIngressFCInProfRemark is specified to be
         'dscp'."
    DEFVAL { ''H }
    ::= { tSapIngressFCEntry 9 }

tSapIngressFCInProfPrec OBJECT-TYPE
    SYNTAX       TPrecValueOrNone
    MAX-ACCESS   read-create
    STATUS       current
    DESCRIPTION
        "tSapIngressFCInProfPrec specifies the precedence value to be used
         while remarking the in profile packets when the in-profile
         remarking type, tSapIngressFCInProfRemark is specified to be
         'precedence'."
    DEFVAL { -1 }
    ::= { tSapIngressFCEntry 10 }

tSapIngressFCOutProfRemark OBJECT-TYPE
    SYNTAX       TRemarkType
    MAX-ACCESS   read-create
    STATUS       current
    DESCRIPTION
        "tSapIngressFCOutProfRemark specifies the remarking type to
         be used for the in profile packets feeding into the queues."
    DEFVAL { none }
    ::= { tSapIngressFCEntry 11 }

tSapIngressFCOutProfDscp OBJECT-TYPE
    SYNTAX       TNamedItemOrEmpty
    MAX-ACCESS   read-create
    STATUS       current
    DESCRIPTION
        "tSapIngressFCOutProfDscp specifies the DSCP to be used while
         remarking the in profile packets when the in-profile
         remarking type, tSapIngressFCOutProfRemark is specified to be
         'dscp'."
    DEFVAL { ''H }
    ::= { tSapIngressFCEntry 12 }

tSapIngressFCOutProfPrec OBJECT-TYPE
    SYNTAX       TPrecValueOrNone
    MAX-ACCESS   read-create
    STATUS       current
    DESCRIPTION
        "tSapIngressFCOutProfPrec specifies the precedence value to be used
         while remarking the in profile packets when the in-profile
         remarking type, tSapIngressFCOutProfRemark is specified to be
         'precedence'."
    DEFVAL { -1 }
    ::= { tSapIngressFCEntry 13 }

tSapIngressFCProfile OBJECT-TYPE
    SYNTAX       TProfileOrNone
    MAX-ACCESS   read-create
    STATUS       current
    DESCRIPTION
        "tSapIngressFCProfile specifies the profile of the packets
         associated with this forwarding class.

         This object can not be set to anything but 'none' if the
         queues being used by this mapping do not have their modes,
         tSapIngressQueueMode set to 'profile'."
    DEFVAL { none }
    ::= { tSapIngressFCEntry 14 }

tSapIngressFCHsmdaQueue OBJECT-TYPE
    SYNTAX       TIngressHsmdaQueueId
    MAX-ACCESS   read-create
    STATUS       obsolete
    DESCRIPTION
        "The value of the object tSapIngressFCHsmdaQueue specifies the 
         HSMDA queue to use for packets in this forwarding class. This 
         mapping will be used when the SAP is on a HSMDA MDA.
         A value of zero implies that the default queues should be used.

        This object is obsoleted in 10.0 Release."
    DEFVAL { 0 }
    ::= { tSapIngressFCEntry 15 }

tSapIngressFCHsmdaMCastQueue OBJECT-TYPE
    SYNTAX       TIngressHsmdaQueueId
    MAX-ACCESS   read-create
    STATUS       obsolete
    DESCRIPTION
        "The value of the object tSapIngressFCHsmdaMCastQueue specifies the 
         multicast queue to use for packets in this forwarding class. This 
         mapping will be used when the SAP is on a HSMDA MDA. 
         A value of zero implies that the default queues should be used.

        This object is obsoleted in 10.0 Release."
    DEFVAL { 0 }
    ::= { tSapIngressFCEntry 16 }

tSapIngressFCHsmdaBCastQueue OBJECT-TYPE
    SYNTAX       TIngressHsmdaQueueId
    MAX-ACCESS   read-create
    STATUS       obsolete
    DESCRIPTION
        "The value of the object tSapIngressFCHsmdaBCastQueue specifies the 
         broadcast queue to use for packets in this forwarding class. This 
         mapping will be used when the SAP is on a HSMDA MDA. 
         A value of zero implies that the default queues should be used.

        This object is obsoleted in 10.0 Release."
    DEFVAL { 0 }
    ::= { tSapIngressFCEntry 17 }

tSapIngressFCDE1OutOfProfile OBJECT-TYPE
    SYNTAX       TruthValue
    MAX-ACCESS   read-create
    STATUS       current
    DESCRIPTION
        "The value of tSapIngressFCDE1OutOfProfile specifies whether frames
        with DE value of '1' are to be treated as out-of-profile (as if
        tSapIngressFCProfile was set to 'out'). 
        
        When tSapIngressFCDE1OutOfProfile is set to 'true', frames with DE value
        of '1' are autmatically classified as out-of-profile.

        Frames with DE value of '0' will continue to be policed based on the
        value of tSapIngressQueueAdminCIR.  That is, if the dynamic rate of
        ingress queue is within CIR, frames with DE=0 will be treated as
        in-profile (as if tSapIngressFCProfile was set to 'in') otherwise these
        frames are treated as out-of-profile.
        
        When tSapIngressFCDE1OutOfProfile is set to 'true', it supercedes action
        specified by the value of tSapIngressFCProfile."
    DEFVAL { false }
    ::= { tSapIngressFCEntry 18 }

tSapIngressFCQGrp OBJECT-TYPE
    SYNTAX       TNamedItemOrEmpty
    MAX-ACCESS   read-create
    STATUS       current
    DESCRIPTION
        "tSapIngressFCQGrp specifies the tQosIngQGroupName.

        This object must be set along with tSapIngressFCQueue object.
        An 'inconsistentValue' error is returned if this object is set to the
        default and other is set to a non-default value."
    DEFVAL { ''H }
    ::= { tSapIngressFCEntry 19 }

tSapIngressFCQGrpMCast OBJECT-TYPE
    SYNTAX       TNamedItemOrEmpty
    MAX-ACCESS   read-create
    STATUS       current
    DESCRIPTION
        "tSapIngressFCQGrpMCast specifies the tQosIngQGroupName.

        This object must be set along with tSapIngressFCMCastQueue object.
        An 'inconsistentValue' error is returned if this object is set to the
        default and other is set to a non-default value."
    DEFVAL { ''H }
    ::= { tSapIngressFCEntry 20 }

tSapIngressFCQGrpBCast OBJECT-TYPE
    SYNTAX       TNamedItemOrEmpty
    MAX-ACCESS   read-create
    STATUS       current
    DESCRIPTION
        "tSapIngressFCQGrpBCast specifies the tQosIngQGroupName.

        This object must be set along with tSapIngressFCBCastQueue object.
        An 'inconsistentValue' error is returned if this object is set to the
        default and other is set to a non-default value."
    DEFVAL { ''H }
    ::= { tSapIngressFCEntry 21 }

tSapIngressFCQGrpUnknown OBJECT-TYPE
    SYNTAX       TNamedItemOrEmpty
    MAX-ACCESS   read-create
    STATUS       current
    DESCRIPTION
        "tSapIngressFCQGrpUnknown specifies the tQosIngQGroupName.

        This object must be set along with tSapIngressFCUnknownQueue object.
        An 'inconsistentValue' error is returned if this object is set to the
        default and other is set to a non-default value."
    DEFVAL { ''H }
    ::= { tSapIngressFCEntry 22 }

tSapIngressFCPolicer OBJECT-TYPE
    SYNTAX       TIngressPolicerIdOrNone
    MAX-ACCESS   read-create
    STATUS       current
    DESCRIPTION
        "tSapIngressFCPolicer specifies the policer ID to be used for the normal
        traffic in this forwarding class."
    DEFVAL { 0 }
    ::= { tSapIngressFCEntry 23 }

tSapIngressFCMCastPolicer OBJECT-TYPE
    SYNTAX       TIngressPolicerIdOrNone
    MAX-ACCESS   read-create
    STATUS       current
    DESCRIPTION
        "tSapIngressFCMCastPolicer specifies the policer ID to be used for
        multicast in this forwarding class."
    DEFVAL { 0 }
    ::= { tSapIngressFCEntry 24 }

tSapIngressFCBCastPolicer OBJECT-TYPE
    SYNTAX       TIngressPolicerIdOrNone
    MAX-ACCESS   read-create
    STATUS       current
    DESCRIPTION
        "tSapIngressFCBCastPolicer specifies the policer ID to be used for
        broadcast traffic in this forwarding class."
    DEFVAL { 0 }
    ::= { tSapIngressFCEntry 25 }

tSapIngressFCUnknownPolicer OBJECT-TYPE
    SYNTAX       TIngressPolicerIdOrNone
    MAX-ACCESS   read-create
    STATUS       current
    DESCRIPTION
        "tSapIngressFCUnknownPolicer specifies the policer ID to be used for
        unknown traffic in this forwarding class."
    DEFVAL { 0 }
    ::= { tSapIngressFCEntry 26 }

tSapIngressFCPlcrFPQGrp OBJECT-TYPE
    SYNTAX       TruthValue
    MAX-ACCESS   read-create
    STATUS       current
    DESCRIPTION
        "The value of tSapIngressFCPlcrFPQGrp specifies whether to use
        the specified policer defined in FP(forwading-plane) Queue group for
        this SAP.

        When tSapIngressFCPlcrFPQGrp is set to 'true', it specifies the FC to 
        use the specific policer defined in the FP Queue Group instance attached
        to the SAP specified by sapIngressFPQGrp and sapIngressFPQGrpInstanceId.
        
        An 'inconsistentValue' error is returned if tSapIngressFCPlcrFPQGrp is 
        set to a non-default value and an entry corresponding to the policer 
        tSapIngressFCPolicer does not exist in Queue group attached at the FP."
    DEFVAL { false }
    ::= { tSapIngressFCEntry 27 }

tSapIngressFCMCastPlcrFPQGrp OBJECT-TYPE
    SYNTAX       TruthValue
    MAX-ACCESS   read-create
    STATUS       current
    DESCRIPTION
        "The value of tSapIngressFCMCastPlcrFPQGrp specifies whether to use
        the specified multicast policer defined in FP(forwading-plane) Queue 
        group for this SAP.

        When tSapIngressFCMCastPlcrFPQGrp is set to 'true', it specifies the FC
        to use the specific multicast policer defined in the FP Queue Group 
        instance attached to the SAP specified by sapIngressFPQGrp and 
        sapIngressFPQGrpInstanceId.
        
        An 'inconsistentValue' error is returned if tSapIngressFCMCastPlcrFPQGrp
        is set to a non-default value and an entry corresponding to the policer 
        tSapIngressFCPolicer does not exist in Queue group attached at the FP."
    DEFVAL { false }
    ::= { tSapIngressFCEntry 28 }

tSapIngressFCBCastPlcrFPQGrp OBJECT-TYPE
    SYNTAX       TruthValue
    MAX-ACCESS   read-create
    STATUS       current
    DESCRIPTION
        "The value of tSapIngressFCBCastPlcrFPQGrp specifies whether to use
        the specified broadcast policer defined in FP(forwading-plane) Queue 
        group for this SAP.

        When tSapIngressFCBCastPlcrFPQGrp is set to 'true', it specifies the FC
        to use the specific broadcast policer defined in the FP Queue Group 
        instance attached to the SAP specified by sapIngressFPQGrp and 
        sapIngressFPQGrpInstanceId.
        
        An 'inconsistentValue' error is returned if tSapIngressFCBCastPlcrFPQGrp
        is set to a non-default value and an entry corresponding to the policer 
        tSapIngressFCPolicer does not exist in Queue group attached at the FP."
    DEFVAL { false }
    ::= { tSapIngressFCEntry 29 }

tSapIngressFCUnknownPlcrFPQGrp OBJECT-TYPE
    SYNTAX       TruthValue
    MAX-ACCESS   read-create
    STATUS       current
    DESCRIPTION
        "The value of tSapIngressFCUnknownPlcrFPQGrp specifies whether to use
        the specified unknown policer defined in FP(forwading-plane) Queue 
        group for this SAP.

        When tSapIngressFCUnknownPlcrFPQGrp is set to 'true', it specifies the FC
        to use the specific broadcast policer defined in the FP Queue Group 
        instance attached to the SAP specified by sapIngressFPQGrp and 
        sapIngressFPQGrpInstanceId.
        
        An 'inconsistentValue' error is returned if 
        tSapIngressFCUnknownPlcrFPQGrp is set to a non-default value and an 
        entry corresponding to the policer tSapIngressFCPolicer does not exist 
        in Queue group attached at the FP."
    DEFVAL { false }
    ::= { tSapIngressFCEntry 30 }

tSapIngressFCEgressOverrideFC OBJECT-TYPE
    SYNTAX       TFCNameOrEmpty
    MAX-ACCESS   read-create
    STATUS       current
    DESCRIPTION
        "The value of tSapIngressFCEgressOverrideFC specifies the forwarding 
        class that overrides the forwarding class determined by ingress 
        classification.
    
        The forwarding class and/or forwading sub-class can be overriden. The 
        new egress forwarding class is applicable to both SAP egress and 
        network egress."
    DEFVAL { ''H }
    ::= { tSapIngressFCEntry 31 }

--
-- sap-ingress policy precedence table
--

tSapIngressPrecTable OBJECT-TYPE
    SYNTAX       SEQUENCE OF TSapIngressPrecEntry
    MAX-ACCESS   not-accessible
    STATUS       current
    DESCRIPTION  "This table maintains the mapping of a particular
                  precedence value into a forwarding class"
    ::= { tSapIngressObjects 8 }

tSapIngressPrecEntry OBJECT-TYPE
    SYNTAX       TSapIngressPrecEntry
    MAX-ACCESS   not-accessible
    STATUS       current
    DESCRIPTION
        "Information about a particular sap-ingress policy's
         IP precedence values to forwarding class mappings.

         Entries are created and deleted by user. They have
         a presumed StorageType of nonVolatile."
    INDEX { tSapIngressIndex, tSapIngressPrecValue }
    ::= { tSapIngressPrecTable 1 }

TSapIngressPrecEntry ::= SEQUENCE
    {
        tSapIngressPrecValue               TPrecValue,
        tSapIngressPrecRowStatus           RowStatus,
        tSapIngressPrecFC                  TNamedItemOrEmpty,
        tSapIngressPrecFCPriority          TPriorityOrDefault,
        tSapIngressPrecLastChanged         TimeStamp,
        tSapIngressPrecHsmdaCntrOvr    TIngressHsmdaCounterIdOrZero
    }

tSapIngressPrecValue OBJECT-TYPE
    SYNTAX       TPrecValue
    MAX-ACCESS   not-accessible
    STATUS       current
    DESCRIPTION
        "Precedence value for which the mapping is done."
    ::= { tSapIngressPrecEntry 1 }

tSapIngressPrecRowStatus OBJECT-TYPE
    SYNTAX       RowStatus
    MAX-ACCESS   read-create
    STATUS       current
    DESCRIPTION
        "Row Status for this mapping."
    ::= { tSapIngressPrecEntry 2 }

tSapIngressPrecFC OBJECT-TYPE
    SYNTAX       TNamedItemOrEmpty
    MAX-ACCESS   read-create
    STATUS       current
    DESCRIPTION
        "tSapIngressPrecFC specifies the forwarding class or the sub
         forwarding class to be used to classify all the traffic that
         matches the specific precedence value i.e. tSapIngressPrecValue.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSapIngressPrecFC is specified explicitly, this match
         will be ignored for classification purposes."
    DEFVAL { ''H }
    ::= { tSapIngressPrecEntry 3 }

tSapIngressPrecFCPriority OBJECT-TYPE
    SYNTAX       TPriorityOrDefault
    MAX-ACCESS   read-create
    STATUS       current
    DESCRIPTION
        "The priority to be assigned to the matching traffic."
    DEFVAL { default }
    ::= { tSapIngressPrecEntry 4 }

tSapIngressPrecLastChanged OBJECT-TYPE
    SYNTAX       TimeStamp
    MAX-ACCESS   read-only
    STATUS       current
    DESCRIPTION
        "timestamp of last change to this row in tSapIngressPrecTable."
    ::= { tSapIngressPrecEntry 5 }

tSapIngressPrecHsmdaCntrOvr OBJECT-TYPE
    SYNTAX       TIngressHsmdaCounterIdOrZero
    MAX-ACCESS   read-create
    STATUS       obsolete
    DESCRIPTION
        "The value of the object tSapIngressPrecHsmdaCntrOvr 
         specifies the counter to use for all the traffic that
         matches the specific precedence value i.e. tSapIngressPrecValue.

         A value of zero implies that the default counters should be used.

         This object is obsoleted in 10.0 Release."
    DEFVAL { 0 }
    ::= { tSapIngressPrecEntry 6 }

--
-- sap-ingress policy ipv6 criteria table
--

tSapIngressIPv6CriteriaTable OBJECT-TYPE
    SYNTAX       SEQUENCE OF TSapIngressIPv6CriteriaEntry
    MAX-ACCESS   not-accessible
    STATUS       current
    DESCRIPTION
        "Information about all sap-ingress policies' ipv6-criteria entries."
    ::= { tSapIngressObjects 9 }

tSapIngressIPv6CriteriaEntry OBJECT-TYPE
    SYNTAX       TSapIngressIPv6CriteriaEntry
    MAX-ACCESS   not-accessible
    STATUS       current
    DESCRIPTION
        "Information about a particular ipv6-criteria entry for a sap-ingress
         policy.
         Entries are created/deleted by user.
         There is no StorageType object, entries have a presumed
         StorageType of nonVolatile."
    INDEX { tSapIngressIndex, tSapIngressIPv6CriteriaIndex }
    ::= { tSapIngressIPv6CriteriaTable 1 }

TSapIngressIPv6CriteriaEntry ::= SEQUENCE
    {
        tSapIngressIPv6CriteriaIndex               TEntryId,
        tSapIngressIPv6CriteriaRowStatus           RowStatus,
        tSapIngressIPv6CriteriaDescription         TItemDescription,
        tSapIngressIPv6CriteriaActionFC            TNamedItemOrEmpty,
        tSapIngressIPv6CriteriaActionPriority      TPriorityOrDefault,
        tSapIngressIPv6CriteriaSourceIpAddr        InetAddressIPv6,
        tSapIngressIPv6CriteriaSourceIpMask        InetAddressPrefixLength,
        tSapIngressIPv6CriteriaDestIpAddr          InetAddressIPv6,
        tSapIngressIPv6CriteriaDestIpMask          InetAddressPrefixLength,
        tSapIngressIPv6CriteriaNextHeader          TIpProtocol,
        tSapIngressIPv6CriteriaSourcePortValue1    TTcpUdpPort,
        tSapIngressIPv6CriteriaSourcePortValue2    TTcpUdpPort,
        tSapIngressIPv6CriteriaSourcePortOperator  TTcpUdpPortOperator,
        tSapIngressIPv6CriteriaDestPortValue1      TTcpUdpPort,
        tSapIngressIPv6CriteriaDestPortValue2      TTcpUdpPort,
        tSapIngressIPv6CriteriaDestPortOperator    TTcpUdpPortOperator,
        tSapIngressIPv6CriteriaDSCP                TDSCPNameOrEmpty,
        tSapIngressIPv6CriteriaLastChanged         TimeStamp,
        tSapIngressIPv6CritSrcIpFullMask           InetAddressIPv6,
        tSapIngressIPv6CritDstIpFullMask           InetAddressIPv6,
        tSapIngressIPv6CritActionPolicer           TIngressPolicerIdOrNone,
        tSapIngressIPv6CriteriaFragment            INTEGER,
        tSapIngressIPv6CriteriaIpPrecValue     Dot1PPriority,
        tSapIngressIPv6CriteriaIpPrecMask      Dot1PPriority
    }

tSapIngressIPv6CriteriaIndex OBJECT-TYPE
    SYNTAX       TEntryId
    MAX-ACCESS   not-accessible
    STATUS       current
    DESCRIPTION
        "The value of the object tSapIngressIPv6CriteriaIndex specifies
         uniquely each entry in the policy."
    ::= { tSapIngressIPv6CriteriaEntry 1 }

tSapIngressIPv6CriteriaRowStatus OBJECT-TYPE
    SYNTAX       RowStatus
    MAX-ACCESS   read-create
    STATUS       current
    DESCRIPTION
        "The value of the object tSapIngressIPv6CriteriaRowStatus specifies the
         Row Status for the IPv6 Criteria entry."
    ::= { tSapIngressIPv6CriteriaEntry 2 }

tSapIngressIPv6CriteriaDescription OBJECT-TYPE
    SYNTAX       TItemDescription
    MAX-ACCESS   read-create
    STATUS       current
    DESCRIPTION
        "The value of the object tSapIngressIPv6CriteriaDescription specifies
         an optional user provided description of this IPv6 criteria entry."
    DEFVAL { ''H }
    ::= { tSapIngressIPv6CriteriaEntry 3 }

tSapIngressIPv6CriteriaActionFC OBJECT-TYPE
    SYNTAX       TNamedItemOrEmpty
    MAX-ACCESS   read-create
    STATUS       current
    DESCRIPTION
        "The value of the object tSapIngressIPv6CriteriaActionFC specifies the
         forwarding class or the sub forwarding class to be used to classify
         all the traffic that matches the specific IPv6 criteria.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSapIngressIPv6CriteriaActionFC is specified explicitly,
         this match will be ignored for classification purposes."
    DEFVAL { ''H }
    ::= { tSapIngressIPv6CriteriaEntry 4 }

tSapIngressIPv6CriteriaActionPriority OBJECT-TYPE
    SYNTAX       TPriorityOrDefault
    MAX-ACCESS   read-create
    STATUS       current
    DESCRIPTION
       "The value of the object tSapIngressIPv6CriteriaActionPriority specifies
        the priority for packets which match this entry's criteria.
        When set to 'default', the packet is sent to the queue
        from DSCP/dot1p/FC which matched the packet, using the
        priority from the DSCP/dot1p/FC which matched the packet."
    DEFVAL { default }
    ::= { tSapIngressIPv6CriteriaEntry 5 }

tSapIngressIPv6CriteriaSourceIpAddr OBJECT-TYPE
    SYNTAX       InetAddressIPv6
    MAX-ACCESS   read-create
    STATUS       current
    DESCRIPTION
        "The value of the object tSapIngressIPv6CriteriaSourceIpAddr specifies
         the IPv6 address to match with source-IPv6 of the packet."
    DEFVAL { '00000000000000000000000000000000'H }
    ::= { tSapIngressIPv6CriteriaEntry 6 }

tSapIngressIPv6CriteriaSourceIpMask OBJECT-TYPE
    SYNTAX       InetAddressPrefixLength (0..128)
    MAX-ACCESS   read-create
    STATUS       current
    DESCRIPTION
        "If different from 0, the object tSapIngressIPv6CriteriaSourceIpMask
         specifies the IPv6 Mask value for this policy IPv6 Filter entry.
         The mask is ANDed with the received source IPv6 address to match
         the tSapIngressIPv6CriteriaSourceIpAddr.

         If the value of tSapIngressIPv6CriteriaSourceIpMask is 0, and the
         value of tSapIngressIPv6CritSrcIpFullMask is non zero then the
         value of tSapIngressIPv6CritSrcIpFullMask is used as mask.

         If the value of tSapIngressIPv6CriteriaSourceIpMask is non zero,
         it will be equal to the mask expressed the object
         tSapIngressIPv6CritSrcIpFullMask.

         If both tSapIngressIPv6CriteriaSourceIpMask and
         tSapIngressIPv6CritSrcIpFullMask are set to 0, not matching is done
         on the source Ip address.

         If a value is specified for this object, then the value of the
         object tSapIngressIPv6CritSrcIpFullMask will be set to reflect
         this same mask."
    DEFVAL { 0 }
    ::= { tSapIngressIPv6CriteriaEntry 7 }

tSapIngressIPv6CriteriaDestIpAddr OBJECT-TYPE
    SYNTAX       InetAddressIPv6
    MAX-ACCESS   read-create
    STATUS       current
    DESCRIPTION
        "The value of the object tSapIngressIPv6CriteriaDestIpAddr specifies
         the IPv6 address to match with destination-IPv6 of the packet."
    DEFVAL { '00000000000000000000000000000000'H }
    ::= { tSapIngressIPv6CriteriaEntry 8 }

tSapIngressIPv6CriteriaDestIpMask OBJECT-TYPE
    SYNTAX       InetAddressPrefixLength (0..128)
    MAX-ACCESS   read-create
    STATUS       current
    DESCRIPTION
        "If different from 0, the object tSapIngressIPv6CriteriaDestIpMask
         specifies the IPv6 Mask value for this policy IPv6 Filter entry.
         The mask is ANDed with the received Destination IPv6 address to match
         the tSapIngressIPv6CriteriaDestIpAddr.

         If the value of tSapIngressIPv6CriteriaDestIpMask is 0, and the
         value of tSapIngressIPv6CritDstIpFullMask is non zero then the
         value of tSapIngressIPv6CritDstIpFullMask is used as mask.

         If the value of tSapIngressIPv6CriteriaDestIpMask is non zero,
         it will be equal to the mask expressed the object
         tSapIngressIPv6CritDstIpFullMask.

         If both tSapIngressIPv6CriteriaDestIpMask and
         tSapIngressIPv6CritDstIpFullMask are set to 0, no matching is done
         on the Destination Ip address.

         If a value is specified for this object, then the value of the
         object tSapIngressIPv6CritDstIpFullMask will be set to reflect
         this same mask."
    DEFVAL { 0 }
    ::= { tSapIngressIPv6CriteriaEntry 9 }

tSapIngressIPv6CriteriaNextHeader OBJECT-TYPE
    SYNTAX       TIpProtocol
    MAX-ACCESS   read-create
    STATUS       current
    DESCRIPTION
        "The value of the object tSapIngressIPv6CriteriaNextHeader specifies
         the Next Header to match.  use -1 to disable matching by Next Header.
         Because the match criteria only pertains to the last next-header, the
         following values are not accepted: 0, 43, 44, 50, 51, and 60."
    DEFVAL { -1 }
    ::= { tSapIngressIPv6CriteriaEntry 10 }

tSapIngressIPv6CriteriaSourcePortValue1 OBJECT-TYPE
    SYNTAX       TTcpUdpPort
    MAX-ACCESS   read-create
    STATUS       current
    DESCRIPTION
        "The value of the object tSapIngressIPv6CriteriaSourcePortValue1
         specifies the TCP/UDP port value1. The value of this object is used
         according to the description for
         tSapIngressIPv6CriteriaSourcePortOperator."
    DEFVAL { 0 }
    ::= { tSapIngressIPv6CriteriaEntry 11 }

tSapIngressIPv6CriteriaSourcePortValue2 OBJECT-TYPE
    SYNTAX       TTcpUdpPort
    MAX-ACCESS   read-create
    STATUS       current
    DESCRIPTION
        "The value of the object tSapIngressIPv6CriteriaSourcePortValue2
         specifies TCP/UDP port value2. The value of this object is used
         according to the description for
         tSapIngressIPv6CriteriaSourcePortOperator."
    DEFVAL { 0 }
    ::= { tSapIngressIPv6CriteriaEntry 12 }

tSapIngressIPv6CriteriaSourcePortOperator OBJECT-TYPE
    SYNTAX       TTcpUdpPortOperator
    MAX-ACCESS   read-create
    STATUS       current
    DESCRIPTION
        "The value of the object tSapIngressIPv6CriteriaSourcePortOperator
         specifies The operator specifies the manner in which
         tSapIngressIPv6CriteriaSourcePortValue1 and
         tSapIngressIPv6CriteriaSourcePortValue2 are to be used."
    DEFVAL { none }
    ::= { tSapIngressIPv6CriteriaEntry 13 }

tSapIngressIPv6CriteriaDestPortValue1 OBJECT-TYPE
    SYNTAX       TTcpUdpPort
    MAX-ACCESS   read-create
    STATUS       current
    DESCRIPTION
        "The value of the object tSapIngressIPv6CriteriaDestPortValue1
         specifies the TCP/UDP port value1. The value of this object is used
         according to the description for
         tSapIngressIPv6CriteriaDestPortOperator."
    DEFVAL { 0 }
    ::= { tSapIngressIPv6CriteriaEntry 14 }

tSapIngressIPv6CriteriaDestPortValue2 OBJECT-TYPE
    SYNTAX       TTcpUdpPort
    MAX-ACCESS   read-create
    STATUS       current
    DESCRIPTION
        "The value of the object tSapIngressIPv6CriteriaDestPortValue2
         specifies the TCP/UDP port value2. The value of this object is used
         according to the description for
         tSapIngressIPv6CriteriaDestPortOperator."
    DEFVAL { 0 }
    ::= { tSapIngressIPv6CriteriaEntry 15 }

tSapIngressIPv6CriteriaDestPortOperator OBJECT-TYPE
    SYNTAX       TTcpUdpPortOperator
    MAX-ACCESS   read-create
    STATUS       current
    DESCRIPTION
        "The value of the object tSapIngressIPv6CriteriaDestPortOperator
         specifies the manner in which
         tSapIngressIPv6CriteriaDestPortValue1 and
         tSapIngressIPv6CriteriaDestPortValue2 are to be used."
    DEFVAL { none }
    ::= { tSapIngressIPv6CriteriaEntry 16 }

tSapIngressIPv6CriteriaDSCP OBJECT-TYPE
    SYNTAX       TDSCPNameOrEmpty
    MAX-ACCESS   read-create
    STATUS       current
    DESCRIPTION
        "The value of the object tSapIngressIPv6CriteriaDSCP specifies the
         DSCP value to match in the packet"
    DEFVAL { ''H }
    ::= { tSapIngressIPv6CriteriaEntry 17 }

tSapIngressIPv6CriteriaLastChanged OBJECT-TYPE
    SYNTAX       TimeStamp
    MAX-ACCESS   read-only
    STATUS       current
    DESCRIPTION
        "The value of the object indicates timestamp of last change to this
         row in tSapIngressIPv6CriteriaTable."
    ::= { tSapIngressIPv6CriteriaEntry 20 }

tSapIngressIPv6CritSrcIpFullMask OBJECT-TYPE
    SYNTAX       InetAddressIPv6
    MAX-ACCESS  read-create
    STATUS      current
    DESCRIPTION
        "If different from 0, the object tSapIngressIPv6CritSrcIpFullMask
         specifies the IPv6 Mask value for this policy IPv6 Filter entry.
         The mask is ANDed with the received Source IPv6 address to match
         the tSapIngressIPv6CriteriaSourceIpAddr.

         If the value of tSapIngressIPv6CriteriaSourceIpMask
         is non zero, it will be equal to the mask expressed in the object
         tSapIngressIPv6CritSrcIpFullMask.

         If both tSapIngressIPv6CriteriaSourceIpMask and
         tSapIngressIPv6CritSrcIpFullMask are set to 0, no matching is done
         on the Source IPv6 address.

         If a regular mask is specified for tSapIngressIPv6CritSrcIpFullMask
         then the value of tSapIngressIPv6CriteriaSourceIpMask will
         be changed to reflect this value."
    DEFVAL { '00000000000000000000000000000000'H }
    ::= { tSapIngressIPv6CriteriaEntry 22 }

tSapIngressIPv6CritDstIpFullMask OBJECT-TYPE
    SYNTAX       InetAddressIPv6
    MAX-ACCESS  read-create
    STATUS      current
    DESCRIPTION
        "If different from 0, the object tSapIngressIPv6CritDstIpFullMask
         specifies the IPv6 Mask value for this policy IPv6 Filter entry.
         The mask is ANDed with the received Dest IPv6 address to match
         the tSapIngressIPv6CriteriaDestIpAddr.

         If the value of tSapIngressIPv6CriteriaDestIpMask
         is non zero, it will be equal to the mask expressed in the object
         tSapIngressIPv6CritDstIpFullMask.

         If both tSapIngressIPv6CriteriaDestIpMask and
         tSapIngressIPv6CritDstIpFullMask are set to 0, no matching is done
         on the Dest IPv6 address.

         If a regular mask is specified for tSapIngressIPv6CritDstIpFullMask
         then the value of tSapIngressIPv6CriteriaDestIpMask will
         be changed to reflect this value."
    DEFVAL { '00000000000000000000000000000000'H }
    ::= { tSapIngressIPv6CriteriaEntry 23 }

tSapIngressIPv6CritActionPolicer OBJECT-TYPE
    SYNTAX       TIngressPolicerIdOrNone
    MAX-ACCESS   read-create
    STATUS       current
    DESCRIPTION
        "The value of tSapIngressIPv6CritActionPolicer specifies the policer
         identifier to be used for the traffic matching this IPv6 Criteria
         Entry. It provides the ability to direct specific traffic to a
         different SAP ingress policer (tSapIngressIPv6CritActionPolicer)
         independently from that configured for the traffic's FC in
         tSapIngressFCPolicer. This action policer will be referred to as a
         bypass-policer.
         
         An 'inconsistentValue' error is returned if
         tSapIngressIPv6CritActionPolicer is set to a non-default value when
         tSapIngressIPv6CriteriaRowStatus is set to not in service."
    DEFVAL { 0 }
    ::= { tSapIngressIPv6CriteriaEntry 24 }

tSapIngressIPv6CriteriaFragment OBJECT-TYPE
    SYNTAX INTEGER {
               off          (1),
               false        (2),
               true         (3),
               firstOnly    (4),
               nonFirstOnly (5)
           }
    MAX-ACCESS   read-create
    STATUS       current
    DESCRIPTION
        "The value of tSapIngressIPv6CriteriaFragment specifies matching
         criteria to be used for fragmented or non-fragmented IPv6 packtes.
           off          (1) - match all IPv6 packets regardless of fragmented
                              or not.
           false        (2) - match all non-fragmented IPv6 packets.
           true         (3) - match all fragmented IPv6 packets.
           firstOnly    (4) - match only the initial IPv6 packet fragment.
           nonFirstOnly (5) - match non-initial IPv6 packet fragment."
    DEFVAL { off }
    ::= { tSapIngressIPv6CriteriaEntry 25 }

tSapIngressIPv6CriteriaIpPrecValue OBJECT-TYPE
    SYNTAX       Dot1PPriority
    MAX-ACCESS   read-create
    STATUS       current
    DESCRIPTION ""
    DEFVAL { -1 }
    ::= { tSapIngressIPv6CriteriaEntry 31 }

tSapIngressIPv6CriteriaIpPrecMask OBJECT-TYPE
    SYNTAX       Dot1PPriority (0..7)
    MAX-ACCESS   read-create
    STATUS       current
    DESCRIPTION ""
    DEFVAL { 0 }
    ::= { tSapIngressIPv6CriteriaEntry 32 }
--
-- sap-ingress hsmda queue table
--

tSapIngressHsmdaQueueTable OBJECT-TYPE
    SYNTAX      SEQUENCE OF TSapIngressHsmdaQueueEntry
    MAX-ACCESS  not-accessible
    STATUS      obsolete
    DESCRIPTION
        "Information about all sap-ingress policies' HSMDA queues.

         This table is obsoleted in 10.0 release."
    ::= { tSapIngressObjects 10 }

tSapIngressHsmdaQueueEntry    OBJECT-TYPE
    SYNTAX      TSapIngressHsmdaQueueEntry
    MAX-ACCESS  not-accessible
    STATUS      obsolete
    DESCRIPTION
        "Information about a particular HSMDA queue for a sap-ingress policy.
         Entries are created by user."
    INDEX { tSapIngressIndex, tSapIngressHsmdaQueue }
    ::= { tSapIngressHsmdaQueueTable 1}

TSapIngressHsmdaQueueEntry ::= SEQUENCE
    {
        tSapIngressHsmdaQueue                 TIngressHsmdaQueueId,
        tSapIngressHsmdaQueueRowStatus        RowStatus,
        tSapIngressHsmdaQueueLastChanged      TimeStamp,
        tSapIngressHsmdaQueueCIRAdaptn        TAdaptationRule,
        tSapIngressHsmdaQueuePIRAdaptn        TAdaptationRule,
        tSapIngressHsmdaQueueAdminPIR         THsmdaPIRKRate,
        tSapIngressHsmdaQueueAdminCIR         THsmdaCIRKRate,
        tSapIngressHsmdaQueueSlopePolicy      TNamedItem,
        tSapIngressHsmdaQueuePoliced          TruthValue
    }

tSapIngressHsmdaQueue        OBJECT-TYPE
    SYNTAX      TIngressHsmdaQueueId (1..8)
    MAX-ACCESS  not-accessible
    STATUS      obsolete
    DESCRIPTION
        "The HSMDA queue ID is used as the secondary index to the table entry."
    ::= { tSapIngressHsmdaQueueEntry 1 }

tSapIngressHsmdaQueueRowStatus        OBJECT-TYPE
    SYNTAX      RowStatus
    MAX-ACCESS  read-create
    STATUS      obsolete
    DESCRIPTION
        "The value of tSapIngressHsmdaQueueRowStatus is used for the creation
        and deletion of entries in the tSapIngressHsmdaQueueTable."
    ::= { tSapIngressHsmdaQueueEntry 2 }

tSapIngressHsmdaQueueLastChanged        OBJECT-TYPE
    SYNTAX      TimeStamp
    MAX-ACCESS  read-only
    STATUS      obsolete
    DESCRIPTION
        "The value of tSapIngressHsmdaQueueLastChanged indicates the timestamp 
         of last change to this row in tSapIngressHsmdaQueueTable."
    ::= { tSapIngressHsmdaQueueEntry 3 }

tSapIngressHsmdaQueueCIRAdaptn        OBJECT-TYPE
    SYNTAX      TAdaptationRule
    MAX-ACCESS  read-create
    STATUS      obsolete
    DESCRIPTION
        "The value of tSapIngressHsmdaQueueCIRAdaptn specifies the 
         adaptation rule to be used while computing the operational CIR
         value. The adaptation rule specifies the rules to compute the
         operational values while maintaining minimum offset."
    DEFVAL { closest }
    ::= { tSapIngressHsmdaQueueEntry 4 }

tSapIngressHsmdaQueuePIRAdaptn        OBJECT-TYPE
    SYNTAX      TAdaptationRule
    MAX-ACCESS  read-create
    STATUS      obsolete
    DESCRIPTION
        "The value of tSapIngressHsmdaQueuePIRAdaptn specifies the 
         adaptation rule to be used while computing the operational PIR
         value. The adaptation rule specifies the rules to compute the
         operational values while maintaining minimum offset."
    DEFVAL { closest }
    ::= { tSapIngressHsmdaQueueEntry 5 }

tSapIngressHsmdaQueueAdminPIR        OBJECT-TYPE
    SYNTAX      THsmdaPIRKRate
    UNITS       "kbps"
    MAX-ACCESS  read-create
    STATUS      obsolete
    DESCRIPTION
        "The value of tSapIngressHsmdaQueueAdminPIR specifies the 
         administrative PIR specified by the user."
    DEFVAL { -1 }
    ::= { tSapIngressHsmdaQueueEntry 6 }

tSapIngressHsmdaQueueAdminCIR        OBJECT-TYPE
    SYNTAX      THsmdaCIRKRate
    UNITS       "kbps"
    MAX-ACCESS  read-create
    STATUS      obsolete
    DESCRIPTION
        "The value of tSapIngressHsmdaQueueAdminCIR specifies the 
         administrative CIR specified by the user."
    DEFVAL { 0 }
    ::= { tSapIngressHsmdaQueueEntry 7 }

tSapIngressHsmdaQueueSlopePolicy        OBJECT-TYPE
    SYNTAX      TNamedItem
    MAX-ACCESS  read-create
    STATUS      obsolete
    DESCRIPTION
        "The value of tSapIngressHsmdaQueueSlopePolicy specifies the slope
         policy specified by the user."
    DEFVAL { "default" }
    ::= { tSapIngressHsmdaQueueEntry 8 }

tSapIngressHsmdaQueuePoliced OBJECT-TYPE
    SYNTAX       TruthValue
    MAX-ACCESS   read-create
    STATUS       obsolete
    DESCRIPTION
        "The value of tSapIngressHsmdaQueuePoliced specifies whether
         the out of profile traffic feeding into the physical queue 
         instance should be dropped. When the value is 'true', 
         out-of-profile packets are discarded.

         This policing function is different than the shaping function
         normally performed by the queues defined rate in that scheduling
         is not stopped for the queue when the rate is exceeded.

         Accordingly, tSapIngressHsmdaQueuePoliced overrides the bandwidth
         specified by the object tSapIngressHsmdaQueueAdminCIR."
    DEFVAL { false }
    ::= { tSapIngressHsmdaQueueEntry 9 }

--
-- sap-ingress policy LspExp table
--

tSapIngressLspExpTable OBJECT-TYPE
    SYNTAX       SEQUENCE OF TSapIngressLspExpEntry
    MAX-ACCESS   not-accessible
    STATUS       current
    DESCRIPTION  "This table maintains the mappings of an 
                  Lsp Exp Bit value into a forwarding class"
    ::= { tSapIngressObjects 11 }

tSapIngressLspExpEntry OBJECT-TYPE
    SYNTAX       TSapIngressLspExpEntry
    MAX-ACCESS   not-accessible
    STATUS       current
    DESCRIPTION
        "Information about a particular sap-ingress policy's
         Lsp Exp Bit values to forwarding class mappings.

         Entries are created and deleted by user. They have
         a presumed StorageType of nonVolatile."
    INDEX { tSapIngressIndex, tSapIngressLspExpValue }
    ::= { tSapIngressLspExpTable 1 }

TSapIngressLspExpEntry ::= SEQUENCE
    {
        tSapIngressLspExpValue               TLspExpValue,
        tSapIngressLspExpRowStatus           RowStatus,
        tSapIngressLspExpLastChanged         TimeStamp,
        tSapIngressLspExpFC                  TNamedItemOrEmpty,
        tSapIngressLspExpFCPriority          TPriorityOrDefault,
        tSapIngressLspExpHsmdaCntrOvr        TIngressHsmdaCounterIdOrZero
    }

tSapIngressLspExpValue OBJECT-TYPE
    SYNTAX       TLspExpValue (0..7)
    MAX-ACCESS   not-accessible
    STATUS       current
    DESCRIPTION
        "The value of the object tSapIngressLspExpValue specifies the value for 
         which the mapping is done."
    ::= { tSapIngressLspExpEntry 1 }

tSapIngressLspExpRowStatus OBJECT-TYPE
    SYNTAX       RowStatus
    MAX-ACCESS   read-create
    STATUS       current
    DESCRIPTION
        "The value of tSapIngressLspExpRowStatus specifies the Row Status
         for this mapping."
    ::= { tSapIngressLspExpEntry 2 }

tSapIngressLspExpLastChanged OBJECT-TYPE
    SYNTAX       TimeStamp
    MAX-ACCESS   read-only
    STATUS       current
    DESCRIPTION
        "The value of tSapIngressLspExpLastChanged indicates the 
         timestamp of last change to this row in tSapIngressLspExpTable."
    ::= { tSapIngressLspExpEntry 3 }

tSapIngressLspExpFC OBJECT-TYPE
    SYNTAX       TNamedItemOrEmpty
    MAX-ACCESS   read-create
    STATUS       current
    DESCRIPTION
        "The value of the object tSapIngressLspExpFC specifies the 
         forwarding class or the sub forwarding class to be used to
         classify all the traffic that matches the specific Lsp Exp
         value i.e. tSapIngressLspExpValue.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSapIngressLspExpFC is specified explicitly, this match
         will be ignored for classification purposes."
    DEFVAL { ''H }
    ::= { tSapIngressLspExpEntry 4 }

tSapIngressLspExpFCPriority OBJECT-TYPE
    SYNTAX       TPriorityOrDefault 
    MAX-ACCESS   read-create
    STATUS       current
    DESCRIPTION
        "The value of the object tSapIngressLspExpFCPriority specifies the 
         priority to be assigned to the matching traffic."
    DEFVAL { default }
    ::= { tSapIngressLspExpEntry 5 }

tSapIngressLspExpHsmdaCntrOvr OBJECT-TYPE
    SYNTAX       TIngressHsmdaCounterIdOrZero
    MAX-ACCESS   read-create
    STATUS       obsolete
    DESCRIPTION
        "The value of the object tSapIngressPrecHsmdaCntrOvr 
         specifies the counter to use for all the traffic that
         matches the specific Lsp Exp value i.e. tSapIngressLspExpValue.

         A value of zero implies that the default counters should be used.

         This object is obsoleted in 10.0 Release."
    DEFVAL { 0 }
    ::= { tSapIngressLspExpEntry 6 }

-- -------------------------
-- SAP Ingress Policer table
-- -------------------------

tSapIngPolicerTableLastChanged OBJECT-TYPE
    SYNTAX       TimeStamp
    MAX-ACCESS   read-only
    STATUS       current
    DESCRIPTION
        "tSapIngPolicerTableLastChanged indicates the timestamp of last change
        to the tSapIngPolicerTable."
    ::= { tQosTimeStampObjects 85 }

tSapIngPolicerTable OBJECT-TYPE
    SYNTAX       SEQUENCE OF TSapIngPolicerEntry
    MAX-ACCESS   not-accessible
    STATUS       current
    DESCRIPTION
        "tSapIngPolicerTable defines SAP Ingress Policer Table for providing,
         via SNMP, the capability of defining the policers.

         tSapIngPolicerTable holds a list of all the policers configured in
         the managed system. Policers must exist in this table before being
         referenced by the forwarding class mappings within the queue policy
         as defined in the tSapIngressFCTable."
    ::= { tSapIngressObjects 12 }

tSapIngPolicerEntry OBJECT-TYPE
    SYNTAX       TSapIngPolicerEntry
    MAX-ACCESS   not-accessible
    STATUS       current
    DESCRIPTION
        "tSapIngPolicerEntry defines an entry in the tSapIngPolicerTable.

         Entries are created/deleted in this table by SNMP sets to
         tSapIngPolicerRowStatus."
    INDEX { tSapIngressIndex, tSapIngPolicerId }
    ::= { tSapIngPolicerTable 1 }

TSapIngPolicerEntry ::= SEQUENCE
    {
        tSapIngPolicerId               TIngressPolicerId,
        tSapIngPolicerRowStatus        RowStatus,
        tSapIngPolicerLastChanged      TimeStamp,
        tSapIngPolicerDescr            TItemDescription,
        tSapIngPolicerPIRAdaptation    TAdaptationRule,
        tSapIngPolicerCIRAdaptation    TAdaptationRule,
        tSapIngPolicerParent           TNamedItemOrEmpty,
        tSapIngPolicerLevel            TLevel,
        tSapIngPolicerWeight           TPolicerWeight,
        tSapIngPolicerAdminPIR         THPolPIRRate,
        tSapIngPolicerAdminCIR         THPolCIRRate,
        tSapIngPolicerStatMode         TmnxIngPolicerStatMode,
        tSapIngPolicerMBS              TPlcrBurstSizeBytes,
        tSapIngPolicerHiPrioOnly       TBurstPercentOrDefault,
        tSapIngPolicerCBS              TPlcrBurstSizeBytes,
        tSapIngPolicerPktOffset        TPerPacketOffset,
        tSapIngPolicerAdminPIRPercent  Unsigned32,
        tSapIngPolicerAdminCIRPercent  Unsigned32,
        tSapIngPolicerRateType         TPolicerRateType,
        tSapIngPolicerSlopeStartDepth  Unsigned32,
        tSapIngPolicerSlopeMaxDepth    Unsigned32,
        tSapIngPolicerSlopeMaxProb     Unsigned32,
        tSapIngPolicerSlopeMap         TmnxSlopeMap,
        tSapIngPolicerAdvCfgPolicy     TNamedItemOrEmpty,
        tSapIngPolicerProfileCapped    TruthValue 
    }

tSapIngPolicerId OBJECT-TYPE
    SYNTAX       TIngressPolicerId
    MAX-ACCESS   not-accessible
    STATUS       current
    DESCRIPTION
        "tSapIngPolicerId defines the SAP Ingress Policer identifier.
         It identifies an sap-ingress policer in the managed
         system."
    ::= { tSapIngPolicerEntry 1 }

tSapIngPolicerRowStatus OBJECT-TYPE
    SYNTAX       RowStatus
    MAX-ACCESS   read-create
    STATUS       current
    DESCRIPTION
        "tSapIngPolicerRowStatus allows entries to be created and deleted
         in the tSapIngPolicerTable."
    REFERENCE
        "See definition of RowStatus in RFC 2579, 'Textual Conventions for
         SMIv2.'"
    ::= { tSapIngPolicerEntry 2 }

tSapIngPolicerLastChanged OBJECT-TYPE
    SYNTAX       TimeStamp
    MAX-ACCESS   read-only
    STATUS       current
    DESCRIPTION
        "tSapIngPolicerLastChanged indicates the value of sysUpTime when
         the entry was last modified."
    ::= { tSapIngPolicerEntry 3 }

tSapIngPolicerDescr OBJECT-TYPE
    SYNTAX       TItemDescription
    MAX-ACCESS   read-create
    STATUS       current
    DESCRIPTION
        "tSapIngPolicerDescr specifies the description of the policer."
    DEFVAL { ''H }
    ::= { tSapIngPolicerEntry 4 }

tSapIngPolicerPIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tSapIngPolicerEntry 5 }

tSapIngPolicerCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tSapIngPolicerEntry 6 }

tSapIngPolicerParent OBJECT-TYPE
    SYNTAX       TNamedItemOrEmpty
    MAX-ACCESS   read-create
    STATUS       current
    DESCRIPTION
        "tSapIngPolicerParent specifies the scheduler to which this queue would
        be feeding."
    DEFVAL { ''H }
    ::= { tSapIngPolicerEntry 7 }

tSapIngPolicerLevel OBJECT-TYPE
    SYNTAX       TLevel
    MAX-ACCESS   read-create
    STATUS       current
    DESCRIPTION
        "tSapIngPolicerLevel specifies the level of priority while feeding
        the parent."
    DEFVAL { 1 }
    ::= { tSapIngPolicerEntry 8 }

tSapIngPolicerWeight OBJECT-TYPE
    SYNTAX       TPolicerWeight
    MAX-ACCESS   read-create
    STATUS       current
    DESCRIPTION
        "tSapIngPolicerWeight specifies the weight that needs to be used by the
        scheduler to which this queue would be feeding."
    DEFVAL { 1 }
    ::= { tSapIngPolicerEntry 9 }

tSapIngPolicerAdminPIR OBJECT-TYPE
    SYNTAX       THPolPIRRate
    UNITS        "kbps"
    MAX-ACCESS   read-create
    STATUS       current
    DESCRIPTION
        "tSapIngPolicerAdminPIR specifies the administrative PIR specified by
        the user."
    DEFVAL { -1 }
    ::= { tSapIngPolicerEntry 10 }

tSapIngPolicerAdminCIR OBJECT-TYPE
    SYNTAX       THPolCIRRate
    UNITS        "kbps"
    MAX-ACCESS   read-create
    STATUS       current
    DESCRIPTION
        "tSapIngPolicerAdminCIR specifies the administrative CIR specified by
        the user."
    DEFVAL { 0 }
    ::= { tSapIngPolicerEntry 11 }

tSapIngPolicerStatMode OBJECT-TYPE
    SYNTAX       TmnxIngPolicerStatMode
    MAX-ACCESS   read-create
    STATUS       current
    DESCRIPTION
        "tSapIngPolicerStatMode specifies the mode of statistics collected by
        this policer."
    DEFVAL { minimal }
    ::= { tSapIngPolicerEntry 12 }

tSapIngPolicerMBS OBJECT-TYPE
    SYNTAX       TPlcrBurstSizeBytes
    UNITS        "bytes"
    MAX-ACCESS   read-create
    STATUS       current
    DESCRIPTION
        "The tSapIngPolicerMBS specifies the high priority 'violate' threshold
        of PIR leaky bucket of this policer."
    DEFVAL { -1 }
    ::= { tSapIngPolicerEntry 13 }

tSapIngPolicerHiPrioOnly OBJECT-TYPE
    SYNTAX       TBurstPercentOrDefault
    UNITS        "percent"
    MAX-ACCESS   read-create
    STATUS       current
    DESCRIPTION
        "The tSapIngPolicerHiPrioOnly specifies the percentage of PIR leaky
        bucket's MBS (maximum burst size) of this policer that is reserved for
        high priority traffic."
    DEFVAL { -1 }
    ::= { tSapIngPolicerEntry 14 }

tSapIngPolicerCBS OBJECT-TYPE
    SYNTAX       TPlcrBurstSizeBytes
    UNITS        "bytes"
    MAX-ACCESS   read-create
    STATUS       current
    DESCRIPTION
        "The tSapIngPolicerCBS specifies the 'exceed' threshold of the CIR leaky
        bucket of this policer."
    DEFVAL { -1 }
    ::= { tSapIngPolicerEntry 15 }

tSapIngPolicerPktOffset OBJECT-TYPE
    SYNTAX       TPerPacketOffset
    MAX-ACCESS   read-create
    STATUS       current
    DESCRIPTION
        "tSapIngPolicerPktOffset specifies the packet byte offset for
        addition of policing information by this policer."
    DEFVAL { 0 }
    ::= { tSapIngPolicerEntry 16 }

tSapIngPolicerAdminPIRPercent OBJECT-TYPE
    SYNTAX       Unsigned32 (1..10000)
    UNITS        "hundredths of a percent"
    MAX-ACCESS   read-create
    STATUS       current
    DESCRIPTION
        "The administrative PIR percentage, in hundredths of a percent.
         An 'inconsistentValue' error is returned if
         tSapIngPolicerAdminPIRPercent is set to non-default value when the
         object tSapIngPolicerRateType is set to 'kbps'."
    DEFVAL { 10000 }
    ::= { tSapIngPolicerEntry 17 }
 
tSapIngPolicerAdminCIRPercent OBJECT-TYPE
    SYNTAX       Unsigned32 (0..10000)
    UNITS        "hundredths of a percent"
    MAX-ACCESS   read-create
    STATUS       current
    DESCRIPTION
        "The administrative CIR percentage, in hundredths of a percent.
         An 'inconsistentValue' error is returned if
         tSapIngPolicerAdminCIRPercent is set to non-default value when the
         object tSapIngPolicerRateType is set to 'kbps'."
    DEFVAL { 0 }
    ::= { tSapIngPolicerEntry 18 }
 
tSapIngPolicerRateType OBJECT-TYPE
    SYNTAX       TPolicerRateType
    MAX-ACCESS   read-create
    STATUS       current
    DESCRIPTION
        "The value of tSapIngPolicerRateType specifies the type of ingress
         policer rate.
 
         When the value of the object is set to 'kbps', the ingresss policer
         rates are specified in kbps. The objects
         tSapIngPolicerAdminPIRPercent and tSapIngPolicerAdminCIRPercent
         will be set to their default values.
 
         When the value of the object is set to 'percentOfLocalLimit', 
         the ingress policer rates are specified in percentage. The objects 
         tSapIngPolicerAdminPIR and tSapIngPolicerAdminCIR will be set to 
         their default values."
    DEFVAL { kbps }
    ::= { tSapIngPolicerEntry 19 }

tSapIngPolicerSlopeStartDepth OBJECT-TYPE
    SYNTAX       Unsigned32 (1..10000)
    UNITS        "hundredths of a percent"
    MAX-ACCESS   read-create
    STATUS       current
    DESCRIPTION
        "The value of tSapIngPolicerSlopeStartDepth specifies the percentage of
         the buffer utilized after which the drop probability starts to rise
         above 0."
    DEFVAL { 10000 }
    ::= { tSapIngPolicerEntry 20 }

tSapIngPolicerSlopeMaxDepth OBJECT-TYPE
    SYNTAX       Unsigned32 (1..10000)
    UNITS        "hundredths of a percent"
    MAX-ACCESS   read-create
    STATUS       current
    DESCRIPTION
        "The value of tSapIngPolicerSlopeMaxDepth specifies the percentage of
         the buffer utilized after which the drop probability is 100 percent.
         This implies that all packets beyond this point will be
         dropped."
    DEFVAL { 10000 }
    ::= { tSapIngPolicerEntry 21 }

tSapIngPolicerSlopeMaxProb OBJECT-TYPE
    SYNTAX       Unsigned32 (1..10000)
    UNITS        "hundredths of a percent"
    MAX-ACCESS   read-create
    STATUS       current
    DESCRIPTION
        "The value of tSapIngPolicerSlopeMaxProb specifies the drop 
         probability, as a percentage, when the queue depth reaches
         tSapIngPolicerSlopeMaxDepth. The drop increases steadily from 0 at
         the tSapIngPolicerSlopeStartDepth up to the
         tSapIngPolicerSlopeMaxProb at the tSapIngPolicerSlopeMaxDepth."
    DEFVAL { 10000 }
    ::= { tSapIngPolicerEntry 22 }

tSapIngPolicerSlopeMap OBJECT-TYPE
    SYNTAX       TmnxSlopeMap
    MAX-ACCESS   read-create
    STATUS       current
    DESCRIPTION
        "The value of tSapIngPolicerSlopeMap specifies the slope map to be used
         with this policer."
    DEFVAL { none }
    ::= { tSapIngPolicerEntry 23 }

tSapIngPolicerAdvCfgPolicy        OBJECT-TYPE
    SYNTAX      TNamedItemOrEmpty
    MAX-ACCESS  read-create
    STATUS      current
    DESCRIPTION
        "The value of tSapIngPolicerAdvCfgPolicy specifies the name of the 
         advanced configuration policy to be applied with this policer."
    DEFVAL { ''H }
    ::= { tSapIngPolicerEntry 24 }

tSapIngPolicerProfileCapped   OBJECT-TYPE
    SYNTAX       TruthValue
    MAX-ACCESS   read-create
    STATUS       current
    DESCRIPTION
        "The value of tSapIngPolicerProfileCapped specifies how the explicit 
         in-profile and undetermined profile traffic should be handled at the 
         ingress policer.
        
         When the value of tSapIngPolicerProfileCapped is set to 'true', both 
         explicit in-profile and undetermined profile traffic is honored up to 
         CIR, above which it is marked as out-of-profile. If CIR is set to zero, 
         then all explicit in-profile and undetermined profile packets, along 
         with the explicit out-of-profile packets are marked as out-of-profile.
    
         The default behavior when tSapIngPolicerProfileCapped is set to 
         'false' is to ignore the CIR output state when an explicit in-profile 
         packet is handled by an ingress policer."
    DEFVAL { false }
    ::= { tSapIngPolicerEntry 25 }

-- ----------------------
-- tSapIngPolicyNameTable
-- ----------------------
tSapIngPolicyNameTableLastChgd  OBJECT-TYPE
    SYNTAX          TimeStamp
    MAX-ACCESS      read-only
    STATUS          current
    DESCRIPTION     
        "The value of tSapIngPolicyNameTableLastChgd indicates the
         sysUpTime at the time of the last modification
         of tSapIngPolicyNameTable.

         If no changes were made to the entry since the last
         re-initialization of the local network management subsystem,
         then this object contains a zero value."
    ::= { tQosTimeStampObjects 95 }

tSapIngPolicyNameTable OBJECT-TYPE
    SYNTAX          SEQUENCE OF TSapIngPolicyNameEntry
    MAX-ACCESS      not-accessible
    STATUS          current
    DESCRIPTION     
        "A table that contains SAP ingress policy name information. Entries
         are created automatically by the system
         when tSapIngressPolicyName object is set for the SAP ingress policy."
    ::= { tSapIngressObjects 13 }

tSapIngPolicyNameEntry OBJECT-TYPE
    SYNTAX          TSapIngPolicyNameEntry
    MAX-ACCESS      not-accessible
    STATUS          current
    DESCRIPTION
        "Basic information about a specific SAP ingress policy name."
    INDEX           { tSapIngressPolicyName }
    ::= { tSapIngPolicyNameTable 1 }

TSapIngPolicyNameEntry ::=
    SEQUENCE {
        tSapIngPolicyNameId                   TSapIngressPolicyID,
        tSapIngPolicyNameRowStatus            RowStatus,
        tSapIngPolicyNameLastChanged          TimeStamp
    }

tSapIngPolicyNameId OBJECT-TYPE
    SYNTAX          TSapIngressPolicyID
    MAX-ACCESS      read-only
    STATUS          current
    DESCRIPTION     
        "The value of the object tSapIngPolicyNameId specifies the policy
         name associated with this SAP ingress policy."
    ::= { tSapIngPolicyNameEntry 1 }

tSapIngPolicyNameRowStatus OBJECT-TYPE
    SYNTAX          RowStatus
    MAX-ACCESS      read-only
    STATUS          current
    DESCRIPTION     
        "This value of the object tSapIngPolicyNameRowStatus specifies the
         status of this row."
    ::= { tSapIngPolicyNameEntry 2 }

tSapIngPolicyNameLastChanged        OBJECT-TYPE
    SYNTAX          TimeStamp
    MAX-ACCESS      read-only
    STATUS          current
    DESCRIPTION     
        "The value of tSapIngPolicyNameLastChanged indicates the sysUpTime at
         the time of the last modification of this entry.
                     
         If no changes were made to the entry since the last 
         re-initialization of the local network management 
         subsystem, then this object contains a zero value."
    ::= { tSapIngPolicyNameEntry 3 }

--
-- sap-egress policy table
--
tSapEgressTable OBJECT-TYPE
    SYNTAX       SEQUENCE OF TSapEgressEntry
    MAX-ACCESS   not-accessible
    STATUS       current
    DESCRIPTION
        "information about all sap-egress policies."
    ::= { tSapEgressObjects 1 }

tSapEgressEntry OBJECT-TYPE
    SYNTAX       TSapEgressEntry
    MAX-ACCESS   not-accessible
    STATUS       current
    DESCRIPTION
        "Information about a particular sap-egress policy.
         Entries are created by user.
         Entries are deleted by user.
         There is no StorageType object, entries have a presumed
         StorageType of nonVolatile.

         the default sap-egress policy (1) cannot be changed or
         destroyed.
        "
    INDEX { tSapEgressIndex }
    ::= { tSapEgressTable 1 }

TSapEgressEntry ::= SEQUENCE
    {
        tSapEgressIndex                 TAnyQosPolicyID,
        tSapEgressRowStatus              RowStatus,
        tSapEgressScope                  TItemScope,
        tSapEgressDescription            TItemDescription,
        tSapEgressLastChanged            TimeStamp,
        tSapEgressHsmdaPacketOffset      TEgressHsmdaPerPacketOffset,
        tSapEgressMatchCriteria          TMatchCriteria,
        tSapEgressHsmdaWrrPolicy         TNamedItemOrEmpty,
        tSapEgressHsmdaLowBrstMaxCls     Unsigned32,
        tSapEgressPolicyName             TLNamedItemOrEmpty,
        tSapEgressEthernetCtag           TruthValue,
        tSapEgressParentLocation         INTEGER
    }

tSapEgressIndex OBJECT-TYPE
    SYNTAX       TAnyQosPolicyID
    MAX-ACCESS   not-accessible
    STATUS       current
    DESCRIPTION
        "The value of tSapEgressIndex uniquely identifies sap-egress QoS
         policy.

         User configured policies can only have values between (1..65535).
         All other values are reserved for system generated policies."
    ::= { tSapEgressEntry 1 }

tSapEgressRowStatus OBJECT-TYPE
    SYNTAX       RowStatus
    MAX-ACCESS   read-create
    STATUS       current
    DESCRIPTION
        "Row Status of this policy's entry."
    ::= { tSapEgressEntry 2 }

tSapEgressScope OBJECT-TYPE
    SYNTAX       TItemScope
    MAX-ACCESS   read-create
    STATUS       current
    DESCRIPTION
        "scope of the sap-egress policy."
    DEFVAL { template }
    ::= { tSapEgressEntry 3 }

tSapEgressDescription OBJECT-TYPE
    SYNTAX       TItemDescription
    MAX-ACCESS   read-create
    STATUS       current
    DESCRIPTION
        "user-supplied description of this sap-egress policy."
    DEFVAL { ''H }
    ::= { tSapEgressEntry 4 }

tSapEgressLastChanged OBJECT-TYPE
    SYNTAX       TimeStamp
    MAX-ACCESS   read-only
    STATUS       current
    DESCRIPTION
        "timestamp of last change to this row in tSapEgressTable."
    ::= { tSapEgressEntry 5 }

tSapEgressHsmdaPacketOffset    OBJECT-TYPE
    SYNTAX      TEgressHsmdaPerPacketOffset
    UNITS       "bytes"
    MAX-ACCESS  read-create
    STATUS      current
    DESCRIPTION
        "The value of tSapEgressHsmdaPacketOffset specifies the
         value, in bytes, of the adjustment to make to the size of each
         packet for HSMDA queue accounting."
    DEFVAL { 0 }
    ::= { tSapEgressEntry 6 }

tSapEgressMatchCriteria  OBJECT-TYPE
    SYNTAX       TMatchCriteria
    MAX-ACCESS   read-only
    STATUS       current
    DESCRIPTION
        "The value of tSapEgressMatchCriteria indicates which type of match
         criteria the policy should use.

         When tSapEgressMatchCriteria has a value of 'ip', the sap-egress 
         policy looks for match entries in tSapEgrIPCritTable.

         The value of tSapEgressMatchCriteria is set when the first match criteria
         table entry is created. The value of tSapEgressMatchCriteria is set to
         'none' when the last criteria table entry is removed."
    ::= { tSapEgressEntry 7 }

tSapEgressHsmdaWrrPolicy  OBJECT-TYPE
    SYNTAX       TNamedItemOrEmpty
    MAX-ACCESS   read-create
    STATUS       current
    DESCRIPTION
        "The value of tSapEgressHsmdaWrrPolicy specifies the HSMDA Weighted
         Round Robin (WRR) scheduling policy to use."
    DEFVAL { "" }
    ::= { tSapEgressEntry 8 }

tSapEgressHsmdaLowBrstMaxCls OBJECT-TYPE
    SYNTAX       Unsigned32 (1..8)
    MAX-ACCESS   read-create
    STATUS       current
    DESCRIPTION
        "The value of tSapEgressHsmdaLowBrstMaxCls specifies which class should
        use the low priority burst threshold.
        
        All classes starting from 1, up to and including that specified by
        tSapEgressHsmdaLowBrstMaxCls use the low priority burst threshold.
        
        All classes greater than the value of tSapEgressHsmdaLowBrstMaxCls up
        to and including class 8 use the high priority burst threshold."
    DEFVAL { 8 }
    ::= { tSapEgressEntry 9 }

tSapEgressPolicyName OBJECT-TYPE
    SYNTAX       TLNamedItemOrEmpty
    MAX-ACCESS   read-create
    STATUS       current
    DESCRIPTION
        "The value of tSapEgressPolicyName specifies the name to associate
        with this policy."
    DEFVAL { ''H }
    ::= { tSapEgressEntry 10 }

tSapEgressEthernetCtag OBJECT-TYPE
    SYNTAX       TruthValue
    MAX-ACCESS   read-create
    STATUS       current
    DESCRIPTION
        "The value of tSapEgressEthernetCtag specifies the tag from which 
        the dot1p and DE (Drop-Eligible) values will be drawn to be used by all
        tSapEgressDot1pEntry objects related to this policy.

        The value 'true' specifies that the top customer tag will be
        used for egress reclassification based on dot1p criteria.

        The value 'false' specifies that a service delimiting tag
        will be used for egress reclassification based on dot1p criteria."
    DEFVAL { false }
    ::= { tSapEgressEntry 11 }

tSapEgressParentLocation OBJECT-TYPE
    SYNTAX       INTEGER {
                    default (1),
                    sla (2)
                 }
    MAX-ACCESS   read-create
    STATUS       current
    DESCRIPTION
        "The value of the object tSapEgressParentLocation specifies the
         location in which queues will look to find their parent scheduler;
         in case the parent scheduler is not found, the queue will be orphaned.
         
         The value of tSapEgressParentLocation applies to all queues in 
         this sap-egress policy which have parents configured; 
         for queues with no parent configured (or which are port-parented),
         tSapEgressParentLocation has no effect.

         The value 'default' specifies that the queues should look for 
         their parent in the default way; i.e. 
         SAP queues will look for their parents in the 
         SAP's egress scheduler-policy or the multi-service-site's egress
         scheduler policy depending on which is configured and 
         Subscriber queues will look for their parents in the 
         subscriber-profile's egress scheduler-policy.

         The value 'sla' specifies that the queues should look for their
         parent in the SLA-profile's egress scheduler-policy; all queues
         that are not port-parented and to which SLA-profile is 
         not applicable will behave as orphans in this case."
    DEFVAL { default }
    ::= { tSapEgressEntry 12 }

--
-- sap-egress policy queue table
--

tSapEgressQueueTable OBJECT-TYPE
    SYNTAX       SEQUENCE OF TSapEgressQueueEntry
    MAX-ACCESS   not-accessible
    STATUS       current
    DESCRIPTION  "information about all sap-egress policies' queues."
    ::= { tSapEgressObjects 2 }

tSapEgressQueueEntry OBJECT-TYPE
    SYNTAX       TSapEgressQueueEntry
    MAX-ACCESS   not-accessible
    STATUS       current
    DESCRIPTION
        "Information about a particular sap-egress queue.
         Entries are created/deleted by user.
         There is no StorageType object, entries have a presumed
         StorageType of nonVolatile."
    INDEX { tSapEgressIndex, tSapEgressQueueIndex }
    ::= { tSapEgressQueueTable 1 }

TSapEgressQueueEntry ::= SEQUENCE
    {
        tSapEgressQueueIndex             TEgressQueueId,
        tSapEgressQueueRowStatus         RowStatus,
        tSapEgressQueueParent            TNamedItemOrEmpty,
        tSapEgressQueueLevel             TLevel,
        tSapEgressQueueWeight            TWeight,
        tSapEgressQueueCIRLevel          TLevelOrDefault,
        tSapEgressQueueCIRWeight         TWeight,
        tSapEgressQueueExpedite          INTEGER,
        tSapEgressQueueCBS               TBurstSize,
        tSapEgressQueueMBS               TBurstSize,
        tSapEgressQueueHiPrioOnly        TBurstPercentOrDefault,
        tSapEgressQueuePIRAdaptation     TAdaptationRule,
        tSapEgressQueueCIRAdaptation     TAdaptationRule,
        tSapEgressQueueAdminPIR          TQosQueuePIRRate,
        tSapEgressQueueAdminCIR          TQosQueueCIRRate,
        tSapEgressQueueOperPIR           TPIRRate,
        tSapEgressQueueOperCIR           TCIRRate,
        tSapEgressQueueLastChanged       TimeStamp,
        tSapEgressQueueUsePortParent     TruthValue,
        tSapEgressQueuePortLvl           TLevel,
        tSapEgressQueuePortWght          TWeight,
        tSapEgressQueuePortCIRLvl        TLevelOrDefault,
        tSapEgressQueuePortCIRWght       TWeight,
        tSapEgressQueuePortAvgOverhead   Unsigned32,
        tSapEgressQueuePoolName          TNamedItemOrEmpty,
        tSapEgressQueueXPWredQ           TruthValue,
        tSapEgressQueueXPWredQSlope      TNamedItem,
        tSapEgressQueueMBSBytes          TBurstSizeBytes,
        tSapEgressQueueBurstLimit        TBurstLimit,
        tSapEgressQueuePktOffset         TEgressQPerPacketOffset,
        tSapEgressQueueAdminPIRPercent   Unsigned32,
        tSapEgressQueueAdminCIRPercent   Unsigned32,
        tSapEgressQueueRateType          TBWRateType,
        tSapEgressQueueAdvCfgPolicy      TNamedItemOrEmpty 
    }

tSapEgressQueueIndex OBJECT-TYPE
    SYNTAX       TEgressQueueId (1..8)
    MAX-ACCESS   not-accessible
    STATUS       current
    DESCRIPTION
        "the number of a queue.  zero is not allowed.
         for sap-egress, only three queues are allowed,
         so the queue index range is restricted."
    ::= { tSapEgressQueueEntry 1 }

tSapEgressQueueRowStatus OBJECT-TYPE
    SYNTAX       RowStatus
    MAX-ACCESS   read-create
    STATUS       current
    DESCRIPTION
        "Row Status of the entry."
    ::= { tSapEgressQueueEntry 2 }

tSapEgressQueueParent OBJECT-TYPE
    SYNTAX       TNamedItemOrEmpty
    MAX-ACCESS   read-create
    STATUS       current
    DESCRIPTION
        "The scheduler to which this queue would be feeding to."
    DEFVAL { ''H }
    ::= { tSapEgressQueueEntry 3 }

tSapEgressQueueLevel OBJECT-TYPE
    SYNTAX       TLevel
    MAX-ACCESS   read-create
    STATUS       current
    DESCRIPTION
        "This specifies the level of priority while feeding to the parent."
    DEFVAL { 1 }
    ::= { tSapEgressQueueEntry 4 }

tSapEgressQueueWeight OBJECT-TYPE
    SYNTAX       TWeight
    MAX-ACCESS   read-create
    STATUS       current
    DESCRIPTION
        "The weight that needs to be used by the scheduler to which this queue
         would be feeding to."
    DEFVAL { 1 }
    ::= { tSapEgressQueueEntry 5 }

tSapEgressQueueCIRLevel OBJECT-TYPE
    SYNTAX       TLevelOrDefault
    MAX-ACCESS   read-create
    STATUS       current
    DESCRIPTION
        "This specifies the level of priority while feeding to the parent.
         The level '0' means treat all offered load for this queue as for
         the above CIR traffic."
    DEFVAL { 0 }
    ::= { tSapEgressQueueEntry 6 }

tSapEgressQueueCIRWeight OBJECT-TYPE
    SYNTAX       TWeight
    MAX-ACCESS   read-create
    STATUS       current
    DESCRIPTION
        "The weight that needs to be used until the committed rate by the
         scheduler to which this queue would be feeding to."
    DEFVAL { 1 }
    ::= { tSapEgressQueueEntry 7 }

tSapEgressQueueExpedite OBJECT-TYPE
    SYNTAX       INTEGER {
                    expedited     (1),
                    auto-expedited(2),
                    non-expedited (3)
                 }
    MAX-ACCESS   read-create
    STATUS       current
    DESCRIPTION
        "tSapEgressQueueExpedite specifies the priority that this queue should
         be assigned by the hardware level schedulers.

         The value 'auto-expedited' implies that this attribute should be
         dynamically updated by looking at the forwarding classes mapping
         into this queue. In such a case the queue is treated as
         'non-expedited' if there is even a single non-expedited forwarding
         class using this queue.

         This attribute is associated with the queue at the time of creation
         and cannot be modified thereafter."
    DEFVAL { auto-expedited }
    ::= { tSapEgressQueueEntry 8 }

tSapEgressQueueCBS OBJECT-TYPE
    SYNTAX       TBurstSize
    MAX-ACCESS   read-create
    STATUS       current
    DESCRIPTION
        "The amount of reserved buffer space (in kilo bytes) for the queue."
    DEFVAL { -1 }
    ::= { tSapEgressQueueEntry 9 }

tSapEgressQueueMBS OBJECT-TYPE
    SYNTAX       TBurstSize
    MAX-ACCESS   read-create
    STATUS       obsolete
    DESCRIPTION
        "The maximum amount of buffer space (in kilo bytes) allowed for the
        queue.

        This object has been replaced with tSapEgressQueueMBSBytes object."
    DEFVAL { -1 }
    ::= { tSapEgressQueueEntry 10 }

tSapEgressQueueHiPrioOnly OBJECT-TYPE
    SYNTAX       TBurstPercentOrDefault
    MAX-ACCESS   read-create
    STATUS       current
    DESCRIPTION
        "The percentage of buffer space for the queue, used
         exclusively by high priority packets."
    DEFVAL { -1 }
    ::= { tSapEgressQueueEntry 11 }

tSapEgressQueuePIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tSapEgressQueueEntry 12 }

tSapEgressQueueCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tSapEgressQueueEntry 13 }

tSapEgressQueueAdminPIR OBJECT-TYPE
    SYNTAX       TQosQueuePIRRate
    UNITS        "kbps"
    MAX-ACCESS   read-create
    STATUS       current
    DESCRIPTION
        "The administrative PIR specified by the user."
    DEFVAL { -1 }
    ::= { tSapEgressQueueEntry 14 }

tSapEgressQueueAdminCIR OBJECT-TYPE
    SYNTAX       TQosQueueCIRRate
    UNITS        "kbps"
    MAX-ACCESS   read-create
    STATUS       current
    DESCRIPTION
        "The administrative CIR specified by the user."
    DEFVAL { 0 }
    ::= { tSapEgressQueueEntry 15 }

tSapEgressQueueOperPIR OBJECT-TYPE
    SYNTAX       TPIRRate
    UNITS        "kbps"
    MAX-ACCESS   read-only
    STATUS       obsolete
    DESCRIPTION
        "The administrative PIR specified by the user."
    ::= { tSapEgressQueueEntry 16 }

tSapEgressQueueOperCIR OBJECT-TYPE
    SYNTAX       TCIRRate
    UNITS        "kbps"
    MAX-ACCESS   read-only
    STATUS       obsolete
    DESCRIPTION
        "The operational value derived by computing the CIR value from
         the administrative CIR and PIR values and their corresponding
         adaptation rules."
    ::= { tSapEgressQueueEntry 17 }

tSapEgressQueueLastChanged OBJECT-TYPE
    SYNTAX       TimeStamp
    MAX-ACCESS   read-only
    STATUS       current
    DESCRIPTION
        "timestamp of last change to this row in tSapEgressQueueTable."
    ::= { tSapEgressQueueEntry 18 }

tSapEgressQueueUsePortParent  OBJECT-TYPE
    SYNTAX      TruthValue
    MAX-ACCESS  read-create
    STATUS      current
    DESCRIPTION
        "The value of the object tSapEgressQueueUsePortParent specifies
         whether this queue is parented by a port-level scheduler. When
         the value is 'true', this SAP egress queue is parented by a 
         port-level scheduler. This object is mutually exclusive with 
         tSapEgressQueueParent. Only one kind of parent is allowed."
    DEFVAL      { false }
    ::= { tSapEgressQueueEntry 19 }

tSapEgressQueuePortLvl        OBJECT-TYPE
    SYNTAX       TLevel
    MAX-ACCESS  read-create
    STATUS      current
    DESCRIPTION
        "The value of the object tSapEgressQueuePortLvl specifies the
         port priority this queue will use to receive bandwidth from
         the port-level scheduler for its above-cir offered load."
    DEFVAL      { 1 }
    ::= { tSapEgressQueueEntry 20 }

tSapEgressQueuePortWght       OBJECT-TYPE
    SYNTAX      TWeight
    MAX-ACCESS  read-create
    STATUS      current
    DESCRIPTION
        "The value of the object tSapEgressQueuePortWght specifies the
         weight this queue will use to receive bandwidth from the
         port-level scheduler for its above-cir offered load."
    DEFVAL      { 1 }
    ::= { tSapEgressQueueEntry 21 }

tSapEgressQueuePortCIRLvl        OBJECT-TYPE
    SYNTAX      TLevelOrDefault
    MAX-ACCESS  read-create
    STATUS      current
    DESCRIPTION
        "The value of the object tSapEgressQueuePortCIRLvl specifies the
         port priority this queue will use to receive bandwidth from
         the port-level scheduler for its within-cir offered load."
    DEFVAL      { 0 }
    ::= { tSapEgressQueueEntry 22 }

tSapEgressQueuePortCIRWght       OBJECT-TYPE
    SYNTAX      TWeight
    MAX-ACCESS  read-create
    STATUS      current
    DESCRIPTION
        "The value of the object tSapEgressQueuePortCIRWght specifies the
         weight this queue will use to receive bandwidth from the
         port-level scheduler for its within-cir offered load."
    DEFVAL      { 0 }
    ::= { tSapEgressQueueEntry 23 }

tSapEgressQueuePortAvgOverhead  OBJECT-TYPE
    SYNTAX      Unsigned32 (0..10000)
    UNITS       "Hundredths of a percent"
    MAX-ACCESS  read-create
    STATUS      current
    DESCRIPTION
        "The value of tSapEgressQueuePortAvgOverhead specifies the 
         encapsulation overhead, in hundredths of a percent,  used to 
         translate packet-based rate to frame-based rate and vice versa."
    DEFVAL      { 0 }
    ::= { tSapEgressQueueEntry 24 }

tSapEgressQueuePoolName OBJECT-TYPE   
    SYNTAX      TNamedItemOrEmpty
    MAX-ACCESS  read-create
    STATUS      current
    DESCRIPTION
        "The value of tSapEgressQueuePoolName specifies the name of 
         the pool to be applied for SAP egress queue."
    DEFVAL { ''H }    
    ::= { tSapEgressQueueEntry 25 }

tSapEgressQueueXPWredQ OBJECT-TYPE   
    SYNTAX      TruthValue
    MAX-ACCESS  read-create
    STATUS      current
    DESCRIPTION
        "The value of tSapEgressQueueXPWredQ specifies whether to alter the
         generic pool association of the queue for the purpose of allowing
         queue-specific WRED slopes with minimal provisioning."
    DEFVAL { false }    
    ::= { tSapEgressQueueEntry 26 }

tSapEgressQueueXPWredQSlope OBJECT-TYPE   
    SYNTAX      TNamedItem
    MAX-ACCESS  read-create
    STATUS      current
    DESCRIPTION
        "The value of tSapEgressQueueXPWredQSlope specifies the name of 
         the slope-policy to be applied for SAP egress queue.
         
         An 'inconsistentValue' error is returned when this object is set to
         a non-default value when tSapEgressQueueXPWredQ is set to 'false'."
    DEFVAL { "default" }    
    ::= { tSapEgressQueueEntry 27 }

tSapEgressQueueMBSBytes OBJECT-TYPE
    SYNTAX       TBurstSizeBytes
    UNITS        "bytes"
    MAX-ACCESS   read-create
    STATUS       current
    DESCRIPTION
        "The maximum amount of buffer space (in bytes) allowed for the
        queue."
    DEFVAL { -1 }
    ::= { tSapEgressQueueEntry 28 }

tSapEgressQueueBurstLimit OBJECT-TYPE
    SYNTAX       TBurstLimit
    UNITS        "bytes"
    MAX-ACCESS   read-create
    STATUS       current
    DESCRIPTION
        "The value of tSapIngressQueueBurstLimit specifies the explicit shaping
         burst size of a queue."
    DEFVAL { -1 }
    ::= { tSapEgressQueueEntry 29 }

tSapEgressQueuePktOffset OBJECT-TYPE
    SYNTAX       TEgressQPerPacketOffset
    UNITS        "bytes"
    MAX-ACCESS   read-create
    STATUS       current
    DESCRIPTION
        "The value of tSapEgressQueuePktOffset specifies the per packet byte
         offset for this queue."
    DEFVAL { 0 }
    ::= { tSapEgressQueueEntry 30 }

tSapEgressQueueAdminPIRPercent OBJECT-TYPE
    SYNTAX       Unsigned32 (1..10000)
    UNITS        "hundredths of a percent"
    MAX-ACCESS   read-create
    STATUS       current
    DESCRIPTION
        "The administrative PIR percentage, in hundredths of a percent.
         An 'inconsistentValue' error is returned if 
         tSapEgressQueueAdminPIRPercent is set to non-default value when the 
         object tSapEgressQueueRateType is set to 'kbps'."
    DEFVAL { 10000 }
    ::= { tSapEgressQueueEntry 31 }

tSapEgressQueueAdminCIRPercent OBJECT-TYPE
    SYNTAX       Unsigned32 (0..10000)
    UNITS        "hundredths of a percent"
    MAX-ACCESS   read-create
    STATUS       current
    DESCRIPTION
        "The administrative CIR percentage, in hundredths of a percent.
         An 'inconsistentValue' error is returned if 
         tSapEgressQueueAdminCIRPercent is set to non-default value when the
         object tSapEgressQueueRateType is set to 'kbps'."
    DEFVAL { 0 }
    ::= { tSapEgressQueueEntry 32 }

tSapEgressQueueRateType OBJECT-TYPE
    SYNTAX       TBWRateType
    MAX-ACCESS   read-create
    STATUS       current
    DESCRIPTION
        "The value of tSapEgressQueueRateType specifies the type of Egress 
         Queue rate.

         When the value of the object is set to 'kbps', the ingresss queue rates
         are specified in kbps. The objects  tSapEgressQueueAdminCIRPercent and
         tSapEgressQueueAdminPIRPercent will be set to their default values.

         When the value of the object is set to either 'percentOfPortLimit' or
         'percentOfLocalLimit', the egress queue rates are specified in 
         percentage. The objects tSapEgressQueueAdminCIR and 
         tSapEgressQueueAdminPIR will be set to their default values."
    DEFVAL { kbps }
    ::= { tSapEgressQueueEntry 33 }

tSapEgressQueueAdvCfgPolicy        OBJECT-TYPE
    SYNTAX      TNamedItemOrEmpty
    MAX-ACCESS  read-create
    STATUS      current
    DESCRIPTION
        "The value of tSapEgressQueueAdvCfgPolicy specifies the name of the 
         advanced configuration policy to be applied with this queue."
    DEFVAL { ''H }
    ::= { tSapEgressQueueEntry 34 }
--
-- sap-egress policy fc table
--

tSapEgressFCTable OBJECT-TYPE
    SYNTAX       SEQUENCE OF TSapEgressFCEntry
    MAX-ACCESS   not-accessible
    STATUS       current
    DESCRIPTION  "  "
    ::= { tSapEgressObjects 3 }

tSapEgressFCEntry OBJECT-TYPE
    SYNTAX       TSapEgressFCEntry
    MAX-ACCESS   not-accessible
    STATUS       current
    DESCRIPTION
        "Information about a particular sap-egress policy's
         forwarding class mappings to queues and dot1p values.
         Entries are created/deleted by user.
         There is no StorageType object, entries have a presumed
         StorageType of nonVolatile.
        "
    INDEX { tSapEgressIndex, tSapEgressFCName }
    ::= { tSapEgressFCTable 1 }

TSapEgressFCEntry ::= SEQUENCE
    {
        tSapEgressFCName                   TFCName,
        tSapEgressFCRowStatus              RowStatus,
        tSapEgressFCQueue                  TEgressQueueId,
        tSapEgressFCDot1PValue             Dot1PPriority,
        tSapEgressFCLastChanged            TimeStamp,
        tSapEgressFCHsmdaQueue             TEgressHsmdaQueueId,
        tSapEgressFCDot1PHsmdaProfile      TruthValue,
        tSapEgressFCDot1PInProfile         Dot1PPriority,
        tSapEgressFCDot1POutProfile        Dot1PPriority,
        tSapEgressFCForceDEValue           TDEValue,
        tSapEgressFCDEMark                 TruthValue,
        tSapEgressFCInProfDscp             TNamedItemOrEmpty,
        tSapEgressFCOutProfDscp            TNamedItemOrEmpty,
        tSapEgressFCInProfPrec             TPrecValueOrNone,
        tSapEgressFCOutProfPrec            TPrecValueOrNone,
        tSapEgressFCQGrp                   TNamedItemOrEmpty,
        tSapEgressFCPolicer                TEgressPolicerIdOrNone,
        tSapEgressFCQGrpFC                 TFCNameOrEmpty,
        tSapEgressFCQGrpInstanceId         TQosQGrpInstanceIDorZero,
        tSapEgressFCPortQGrpQueue          TruthValue,
        tSapEgressFCHsmdaQueuePortQGrpQ    TruthValue,
        tSapEgressFCOuterTagDot1PInProf    Dot1PPriority,
        tSapEgressFCOuterTagDot1POutProf   Dot1PPriority,
        tSapEgressFCInnerTagDot1PInProf    Dot1PPriority,
        tSapEgressFCInnerTagDot1POutProf   Dot1PPriority,
        tSapEgressFCOuterTagForceDEValue   TDEValue,
        tSapEgressFCOuterTagDEMark         TruthValue,
        tSapEgressFCInnerTagForceDEValue   TDEValue,
        tSapEgressFCInnerTagDEMark         TruthValue
    }

tSapEgressFCName OBJECT-TYPE
    SYNTAX       TFCName
    MAX-ACCESS   not-accessible
    STATUS       current
    DESCRIPTION
        "forwarding class name."
    ::= { tSapEgressFCEntry 1 }

tSapEgressFCRowStatus OBJECT-TYPE
    SYNTAX       RowStatus
    MAX-ACCESS   read-create
    STATUS       current
    DESCRIPTION
        "Row Status for this queue."
    ::= { tSapEgressFCEntry 2 }

tSapEgressFCQueue OBJECT-TYPE
    SYNTAX       TEgressQueueId
    MAX-ACCESS   read-create
    STATUS       current
    DESCRIPTION
        "The queue to use for packets in this forwarding class.

         When tSapEgressFCQGrp is set to its default value, tSapEgressFCQueue
         represents the local queue to which traffic will be forwarded.

         When tSapEgressFCQGrp and tSapEgressFCQGrpInstanceId are set to a 
         non-default values, tSapEgressFCQueue represents the queue within 
         the specified queue-group instance to which traffic will be forwarded."
    DEFVAL { 0 }
    ::= { tSapEgressFCEntry 3 }

tSapEgressFCDot1PValue OBJECT-TYPE
    SYNTAX       Dot1PPriority
    MAX-ACCESS   read-create
    STATUS       obsolete
    DESCRIPTION
        "The value of tSapEgressFCDot1PValue specifies 802.1p value to use for
        packets in this forwarding class.

        This object has been replaced by tSapEgressFCDot1PInProfile and
        tSapEgressFCDot1POutProfile objects."
    DEFVAL { -1 }
    ::= { tSapEgressFCEntry 4 }

tSapEgressFCLastChanged OBJECT-TYPE
    SYNTAX       TimeStamp
    MAX-ACCESS   read-only
    STATUS       current
    DESCRIPTION
        "timestamp of last change to this row in tSapEgressFCTable."
    ::= { tSapEgressFCEntry 5 }

tSapEgressFCHsmdaQueue OBJECT-TYPE
    SYNTAX       TEgressHsmdaQueueId
    MAX-ACCESS   read-create
    STATUS       current
    DESCRIPTION
        "The HSMDA queue to use for packets in this forwarding class.
         This mapping will be used when the SAP is on a HSMDA MDA."
    DEFVAL { 0 }
    ::= { tSapEgressFCEntry 6 }

tSapEgressFCDot1PHsmdaProfile OBJECT-TYPE
    SYNTAX       TruthValue
    MAX-ACCESS   read-create
    STATUS       obsolete
    DESCRIPTION
        "The value of the object tSapEgressFCDot1PHsmdaProfile specifies 
         if the system will perform egress profiling on HSMDA queues or not.

         The tSapEgressFCDot1PHsmdaProfile object is obsoleted in 9.0 Release."
    DEFVAL { false }
    ::= { tSapEgressFCEntry 7 }

tSapEgressFCDot1PInProfile OBJECT-TYPE
    SYNTAX       Dot1PPriority
    MAX-ACCESS   read-create
    STATUS       current
    DESCRIPTION
       "The value of tSapEgressFCDot1PInProfile specifies 802.1p value to set
       for in-profile frames in this forwarding class.

       An inconsistentValue error is returned if this object is set to any value
       other than '-1', when tSapEgressFCDot1POutProfile object is set to '-1'."
    DEFVAL { -1 }
    ::= { tSapEgressFCEntry 8 }

tSapEgressFCDot1POutProfile OBJECT-TYPE
    SYNTAX       Dot1PPriority
    MAX-ACCESS   read-create
    STATUS       current
    DESCRIPTION
       "The value of tSapEgressFCDot1POutProfile specifies 802.1p value to set
       for out-profile frames in this forwarding class.
        
       An inconsistentValue error is returned if this object is set to any value
       other than '-1', when tSapEgressFCDot1PInProfile object is set to '-1'."
    DEFVAL { -1 }
    ::= { tSapEgressFCEntry 9 }

tSapEgressFCForceDEValue OBJECT-TYPE
    SYNTAX       TDEValue
    MAX-ACCESS   read-create
    STATUS       current
    DESCRIPTION
       "The value of tSapEgressFCForceDEValue specifies the DE value to set
       for all the frames of this forwarding class regardless of frame's profile
       status.

       An inconsistentValue error is returned if this object is set to any value
       other than '-1', when tSapEgressFCDEMark object is set to 'false'."
    DEFVAL { -1 }
    ::= { tSapEgressFCEntry 10 }

tSapEgressFCDEMark OBJECT-TYPE
    SYNTAX       TruthValue
    MAX-ACCESS   read-create
    STATUS       current
    DESCRIPTION
       "The value of tSapEgressFCDEMark specifies whether to set DE value in the
       frames of this forwarding class.

       An inconsistentValue error is returned if this object is set to 'false'
       when tSapEgressFCForceDEValue object is not set to '-1'."
    DEFVAL { false }
    ::= { tSapEgressFCEntry 11 }

tSapEgressFCInProfDscp OBJECT-TYPE
    SYNTAX       TNamedItemOrEmpty
    MAX-ACCESS   read-create
    STATUS       current
    DESCRIPTION
       "The value of tSapEgressFCInProfDscp specifies the DSCP name to set
       for in-profile frames in this forwarding class.

       The values of tSapEgressFCInProfDscp and tSapEgressFCOutProfDscp
       must be set to either the default or non-default values for both.
       An inconsistentValue error is returned if one object is set to the
       default and other is set to a non-default value.

       The values of tSapEgressFCInProfPrec and tSapEgressFCOutProfPrec are
       reset to default values when tSapEgressFCInProfDscp is set to any value
       other than default.

       An inconsistentValue error is returned if this object is set to any value
       other than its default value when setting tSapEgressFCInProfPrec object
       or tSapEgressFCOutProfPrec to a value other than their default values."
    DEFVAL { ''H }
    ::= { tSapEgressFCEntry 12 }

tSapEgressFCOutProfDscp OBJECT-TYPE
    SYNTAX       TNamedItemOrEmpty
    MAX-ACCESS   read-create
    STATUS       current
    DESCRIPTION
       "The value of tSapEgressFCOutProfDscp specifies the DSCP name to set
       for out-profile frames in this forwarding class.

       The values of tSapEgressFCInProfDscp and tSapEgressFCOutProfDscp
       must be set to either the default or non-default values for both.
       An inconsistentValue error is returned if one object is set to the
       default and other is set to a non-default value.

       The values of tSapEgressFCInProfPrec and tSapEgressFCOutProfPrec are
       reset to default values when tSapEgressFCOutProfDscp is set to any value
       other than default.
       
       An inconsistentValue error is returned if this object is set to any value
       other than its default value when setting tSapEgressFCInProfPrec object
       or tSapEgressFCOutProfPrec to a value other than their default values."
    DEFVAL { ''H }
    ::= { tSapEgressFCEntry 13 }

tSapEgressFCInProfPrec OBJECT-TYPE
    SYNTAX       TPrecValueOrNone
    MAX-ACCESS   read-create
    STATUS       current
    DESCRIPTION
       "The value of tSapEgressFCInProfPrec specifies the precedence value to
       set for in-profile frames in this forwarding class.

       The values of tSapEgressFCInProfPrec and tSapEgressFCOutProfPrec
       must be set to either the default or non-default values for both.
       An inconsistentValue error is returned if one object is set to the
       default and other is set to a non-default value.

       The values of tSapEgressFCInProfDscp and tSapEgressFCOutProfDscp are
       reset to default values when tSapEgressFCOutProfPrec is set to any value
       other than default.

       An inconsistentValue error is returned if this object is set to any value
       other than its default value when setting tSapEgressFCInProfDscp object
       or tSapEgressFCOutProfDscp to a value other than their default values."
    DEFVAL { -1 }
    ::= { tSapEgressFCEntry 14 }

tSapEgressFCOutProfPrec OBJECT-TYPE
    SYNTAX       TPrecValueOrNone
    MAX-ACCESS   read-create
    STATUS       current
    DESCRIPTION
       "The value of tSapEgressFCOutProfPrec specifies the precedence value to
       set for out-profile frames in this forwarding class.

       The values of tSapEgressFCInProfPrec and tSapEgressFCOutProfPrec must be
       be set to either the default or non-default values for both.
       An inconsistentValue error is returned if one object is set to the
       default and other is set to a non-default value.

       The values of tSapEgressFCInProfDscp and tSapEgressFCOutProfDscp are
       reset to default values when tSapEgressFCOutProfPrec is set to any value
       other than default.
       
       An inconsistentValue error is returned if this object is set to any value
       other than its default value when setting tSapEgressFCInProfDscp object
       or tSapEgressFCOutProfDscp to a value other than their default values."
    DEFVAL { -1 }
    ::= { tSapEgressFCEntry 15 }

tSapEgressFCQGrp OBJECT-TYPE
    SYNTAX       TNamedItemOrEmpty
    MAX-ACCESS   read-create
    STATUS       current
    DESCRIPTION
        "The value of tSapEgressFCQGrp specifies the tQosEgrQGroupName.
        When set to non-default value, this indicates the name of the
        queue-group to which traffic will be forwarded.

        The values of both tSapEgressFCQGrp and tSapEgressFCQGrpInstanceId 
        should be set to non-default values for the queue-group instance to be
        referenced for redirection at egress access port.
 
        An 'inconsistentValue' error is returned if tSapEgressFCQGrpFC and
        tSapEgressFCQGrpInstanceId are set to non-default values and 
        tSapEgressFCPortQGrpQueue is also set to non-default value for another
        FC specified by tSapEgressFCName within the same SAP egress qos policy."
    DEFVAL { ''H }
    ::= { tSapEgressFCEntry 16 }

tSapEgressFCPolicer OBJECT-TYPE
    SYNTAX       TEgressPolicerIdOrNone
    MAX-ACCESS   read-create
    STATUS       current
    DESCRIPTION
        "The value of tSapEgressFCPolicer specifies the SAP Egress 
         Policer identifier.
         
         If a corresponding Sap Egress Policer Id does not exist in 
         tSapEgrPolicerTable, an 'inconsistentValue' error will be
         returned.

         When tSapEgressFCPolicer is set to its default value, then
         traffic for this forwarding class will not use policers.

         When tSapEgressFCPolicer is set to a non-default value, and
         tSapEgressFCQGrp is set to default, and tSapEgressFCQueue is
         set to default, then traffic will use the given policer, and
         then feed into a system determined queue-group queue.

         When tSapEgressFCPolicer is set to a non-default value, and
         tSapEgressFCQGrp is set to a non-default value, and tSapEgressFCQueue
         is set to default, then traffic will use the given policer, and
         then feed into a queue within the given queue-group according to
         the appropriate tQosEgrQGroupFCEntry.

         When tSapEgressFCPolicer is set to a non-default value, and
         tSapEgressFCQGrp is set to a non-default value, and tSapEgressFCQueue
         is set to a non-default value, then trafifc will use the given
         policer, and then feed into the given queue within the given
         queue-group.

         When tSapEgressFCPolicer is set to a non-default value, and
         tSapEgressFCQGrp is set its default value, and tSapEgressFCQueue
         is set to a non-default value, then trafifc will use the given
         policer, and then feed into the given local queue."
    DEFVAL { 0 }
    ::= { tSapEgressFCEntry 17 }

tSapEgressFCQGrpFC OBJECT-TYPE
    SYNTAX       TFCNameOrEmpty
    MAX-ACCESS   read-create
    STATUS       current
    DESCRIPTION
        "The value of tSapEgressFCQGrpFC, when specified, will replace the
        forwarding class derived from ingress as the forwarding class to
        use inside the egress queue group.  tSapEgressFCQGrpFC is only
        allowed to be used in conjunction with egress policers, and is
        mutually exclusive with direct queue-group queue mappings.

        An 'inconsistentValue' error is returned if tSapEgressFCQGrpFC is
        set to a non-default value when tSapEgressFCPolicer is set to default."
    DEFVAL { ''H }
    ::= { tSapEgressFCEntry 18 }

tSapEgressFCQGrpInstanceId OBJECT-TYPE
    SYNTAX       TQosQGrpInstanceIDorZero  
    MAX-ACCESS   read-create
    STATUS       current
    DESCRIPTION
        "The value of tSapEgressFCQGrpInstanceId defines the unique instance of
        the queue-group is instantiated at egress access port.  It, along with 
        tSapEgressFCQGrp, uniquely identifies egress access port queue-group
        instance to which the traffic will be forwarded" 
    DEFVAL { 0 }
    ::= { tSapEgressFCEntry 19 }
 
tSapEgressFCPortQGrpQueue OBJECT-TYPE
    SYNTAX       TruthValue
    MAX-ACCESS   read-create
    STATUS       current
    DESCRIPTION
        "The value of tSapEgressFCPortQGrpQueue specifies whether to use
        the queue specified in egress access port queue-group instance for 
        this SAP.
                
        With tSapEgressFCQueue set to non-default value, 
        tSapEgressFCPortQGrpQueue set to non-default value and 
        tSapEgressFCPolicer set to default value, it specifies this FC traffic
        to use the tSapEgressFCQueue in the egress access port-queue group 
        instance (TIMETRA-SAP-MIB::sapEgressPortQGrp, 
        sapEgressPortQGrpInstanceId) attached to the SAP.
        
        With tSapEgressFCPolicer set to non-default value, 
        tSapEgressFCPortQGrpQueue set to non-default value and tSapEgressFCQueue
        set to default value , it specifies this FC traffic to use the local
        policer and then feed into the queue within the egress access port 
        queue-group instance (TIMETRA-SAP-MIB::sapEgressPortQGrp, 
        sapEgressPortQGrpInstanceId) attached to the SAP.
 
        With tSapEgressFCPolicer set to non-default value, 
        tSapEgressFCPortQGrpQueue set to non-default value and tSapEgressFCQueue
        set to non-default value, it specifies this FC traffic to use the local
        policer and then feed into tSapEgressFCQueue within the egress access 
        port queue-group instance (TIMETRA-SAP-MIB::sapEgressPortQGrp, 
        sapEgressPortQGrpInstanceId) attached to the SAP.
 
        An 'inconsistentValue' error is returned if this object is set to
        non-default value and tSapEgressFCQGrp and tSapEgressFCQGrpInstanceId 
        are also set to non-default value for another FC specified by 
        tSapEgressFCName within the same SAP egress qos policy.    

        An 'inconsistentValue' error is returned if tSapEgressFCQGrp is 
        set to a non-default value and an entry corresponding to the queue 
        tSapIngressFCQueue does not exist in Queue group instance attached 
        at the port."
    DEFVAL { false }
    ::= { tSapEgressFCEntry 20 }

tSapEgressFCHsmdaQueuePortQGrpQ OBJECT-TYPE
    SYNTAX       TruthValue
    MAX-ACCESS   read-create
    STATUS       current
    DESCRIPTION
        "The value of tSapEgressFCHsmdaQueuePortQGrpQ specifies whether to use
        the queue specified in egress queue-group template.
  
        When tSapEgressFCHsmdaQueuePortQGrpQ is set to non-default value, it 
        specifies this FC traffic to use the queue specified by 
        tQosEgrHsmdaQueue in Queue-Group template."
    DEFVAL { false }
    ::= { tSapEgressFCEntry 21 }


tSapEgressFCOuterTagDot1PInProf OBJECT-TYPE
    SYNTAX       Dot1PPriority
    MAX-ACCESS   read-create
    STATUS       current
    DESCRIPTION
        "The value of tSapEgressFCOuterTagDot1PInProf specifies 802.1p value to
         set in the outer VLAN tag of the packet for in-profile frames in this
         forwarding class.
 
         An 'inconsistentValue' error is returned if this object is set to any
         value other than '-1', when tSapEgressFCOuterTagDot1POutProf object is
         set to '-1'."
    DEFVAL { -1 }
    ::= { tSapEgressFCEntry 22 }
 
tSapEgressFCOuterTagDot1POutProf OBJECT-TYPE
    SYNTAX       Dot1PPriority
    MAX-ACCESS   read-create
    STATUS       current
    DESCRIPTION
        "The value of tSapEgressFCOuterTagDot1POutProf specifies 802.1p value to
         set in the outer VLAN tag of the packet for out-profile frames in this
         forwarding class.
        
         An 'inconsistentValue' error is returned if this object is set to any
         value other than '-1', when tSapEgressFCOuterTagDot1PInProf object is
         set to '-1'."
    DEFVAL { -1 }
    ::= { tSapEgressFCEntry 23 }
 
tSapEgressFCInnerTagDot1PInProf OBJECT-TYPE
    SYNTAX       Dot1PPriority
    MAX-ACCESS   read-create
    STATUS       current
    DESCRIPTION
        "The value of tSapEgressFCInnerTagDot1PInProf specifies 802.1p value to
         set in the inner VLAN tag of the packet for in-profile frames in this
         forwarding class.
 
         An 'inconsistentValue' error is returned if this object is set to any
         value other than '-1', when tSapEgressFCInnerTagDot1POutProf object is
         set to '-1'."
    DEFVAL { -1 }
    ::= { tSapEgressFCEntry 24 }
 
tSapEgressFCInnerTagDot1POutProf OBJECT-TYPE
    SYNTAX       Dot1PPriority
    MAX-ACCESS   read-create
    STATUS       current
    DESCRIPTION
        "The value of tSapEgressFCInnerTagDot1POutProf specifies 802.1p value to
         set in the inner VLAN tag of the packet for out-profile frames in this
         forwarding class.
        
         An 'inconsistentValue' error is returned if this object is set to any
         value other than '-1', when tSapEgressFCInnerTagDot1PInProf object is
         set to '-1'."
    DEFVAL { -1 }
    ::= { tSapEgressFCEntry 25 }
 
tSapEgressFCOuterTagForceDEValue OBJECT-TYPE
    SYNTAX       TDEValue
    MAX-ACCESS   read-create
    STATUS       current
    DESCRIPTION
        "The value of tSapEgressFCOuterTagForceDEValue specifies the DE value to
         set in the outer VLAN tag of the packet for all the frames of this
         forwarding class regardless of frame's profile status.
 
         An 'inconsistentValue' error is returned if this object is set to any
         value other than '-1', when tSapEgressFCOuterTagDEMark object is set to
         'false'."
    DEFVAL { -1 }
    ::= { tSapEgressFCEntry 26 }
 
tSapEgressFCOuterTagDEMark OBJECT-TYPE
    SYNTAX       TruthValue
    MAX-ACCESS   read-create
    STATUS       current
    DESCRIPTION
        "The value of tSapEgressFCOuterTagDEMark specifies whether to set DE 
         value in the outer VLAN tag of the packet for all the frames of this
         forwarding class.
 
         An 'inconsistentValue' error is returned if this object is set to 
         'false', when tSapEgressFCOuterTagForceDEValue object is not set to
         '-1'."
    DEFVAL { false }
    ::= { tSapEgressFCEntry 27 }
 
tSapEgressFCInnerTagForceDEValue OBJECT-TYPE
    SYNTAX       TDEValue
    MAX-ACCESS   read-create
    STATUS       current
    DESCRIPTION
        "The value of tSapEgressFCInnerTagForceDEValue specifies the DE value to
         set in the inner VLAN tag of the packet for all the frames of this 
         forwarding class regardless of frame's profile status.
 
         An 'inconsistentValue' error is returned if this object is set to any
         value other than '-1', when tSapEgressFCInnerTagDEMark object is set to
         'false'."
    DEFVAL { -1 }
    ::= { tSapEgressFCEntry 28 }
 
tSapEgressFCInnerTagDEMark OBJECT-TYPE
    SYNTAX       TruthValue
    MAX-ACCESS   read-create
    STATUS       current
    DESCRIPTION
        "The value of tSapEgressFCInnerTagDEMark specifies whether to set DE 
         value in the inner VLAN tag of the packet for all the frames of this
         forwarding class.
 
         An 'inconsistentValue' error is returned if this object is set to
         'false', when tSapEgressFCInnerTagForceDEValue object is not set to
          '-1'."
    DEFVAL { false }
    ::= { tSapEgressFCEntry 29 }


--
-- sap-egress hsmda queue table
--


tSapEgressHsmdaQueueTable OBJECT-TYPE
    SYNTAX      SEQUENCE OF TSapEgressHsmdaQueueEntry
    MAX-ACCESS  not-accessible
    STATUS      current
    DESCRIPTION
        "Information about all sap-egress policies' HSMDA queues."
    ::= { tSapEgressObjects 4 }

tSapEgressHsmdaQueueEntry    OBJECT-TYPE
    SYNTAX      TSapEgressHsmdaQueueEntry
    MAX-ACCESS  not-accessible
    STATUS      current
    DESCRIPTION
        "Information about a particular HSMDA queue for a sap-egress policy.
         Entries are created by user."
    INDEX { tSapEgressIndex, tSapEgressHsmdaQueue }
    ::= { tSapEgressHsmdaQueueTable 1}

TSapEgressHsmdaQueueEntry ::= SEQUENCE
    {
        tSapEgressHsmdaQueue                 TEgressHsmdaQueueId,
        tSapEgressHsmdaQueueRowStatus        RowStatus,
        tSapEgressHsmdaQueueCIRAdaptn        TAdaptationRule,
        tSapEgressHsmdaQueuePIRAdaptn        TAdaptationRule,
        tSapEgressHsmdaQueueAdminPIR         THsmdaPIRKRate,
        tSapEgressHsmdaQueueAdminCIR         THsmdaCIRKRate,
        tSapEgressHsmdaQueueSlopePolicy      TNamedItem,
        tSapEgressHsmdaQueueLastChanged      TimeStamp,
        tSapEgressHsmdaQueueWrrWeight        THsmdaWrrWeight,
        tSapEgressHsmdaQueueMBS              THSMDABurstSizeBytes,
        tSapEgressHsmdaQueueBurstLimit       THSMDAQueueBurstLimit        
    }

tSapEgressHsmdaQueue        OBJECT-TYPE
    SYNTAX      TEgressHsmdaQueueId (1..8)
    MAX-ACCESS  not-accessible
    STATUS      current
    DESCRIPTION
        "The HSMDA queue ID is used as the secondary index to the table entry."
    ::= { tSapEgressHsmdaQueueEntry 1 }

tSapEgressHsmdaQueueRowStatus        OBJECT-TYPE
    SYNTAX      RowStatus
    MAX-ACCESS  read-create
    STATUS      current
    DESCRIPTION
        "The value of tSapEgressHsmdaQueueRowStatus is used for the creation
        and deletion of entries in the tSapEgressHsmdaQueueTable."
    ::= { tSapEgressHsmdaQueueEntry 2 }

tSapEgressHsmdaQueueCIRAdaptn        OBJECT-TYPE
    SYNTAX      TAdaptationRule
    MAX-ACCESS  read-create
    STATUS      obsolete
    DESCRIPTION
        "The value of tSapEgressHsmdaQueueCIRAdaptn specifies the 
         adaptation rule to be used while computing the operational CIR
         value. The adaptation rule specifies the rules to compute the
         operational values while maintaining minimum offset.

         This object is obsoleted in 10.0 Release."
    DEFVAL { closest }
    ::= { tSapEgressHsmdaQueueEntry 3 }

tSapEgressHsmdaQueuePIRAdaptn        OBJECT-TYPE
    SYNTAX      TAdaptationRule
    MAX-ACCESS  read-create
    STATUS      current
    DESCRIPTION
        "The value of tSapEgressHsmdaQueuePIRAdaptn specifies the 
         adaptation rule to be used while computing the operational PIR
         value. The adaptation rule specifies the rules to compute the
         operational values while maintaining minimum offset."
    DEFVAL { closest }
    ::= { tSapEgressHsmdaQueueEntry 4 }

tSapEgressHsmdaQueueAdminPIR        OBJECT-TYPE
    SYNTAX      THsmdaPIRKRate
    UNITS       "kbps"
    MAX-ACCESS  read-create
    STATUS      current
    DESCRIPTION
        "The value of tSapEgressHsmdaQueueAdminPIR specifies the 
         administrative PIR specified by the user."
    DEFVAL { -1 }
    ::= { tSapEgressHsmdaQueueEntry 5 }

tSapEgressHsmdaQueueAdminCIR        OBJECT-TYPE
    SYNTAX      THsmdaCIRKRate
    UNITS       "kbps"
    MAX-ACCESS  read-create
    STATUS      obsolete
    DESCRIPTION
        "The value of tSapEgressHsmdaQueueAdminCIR specifies the 
         administrative CIR specified by the user.

         This object is obsoleted in 10.0 Release."
    DEFVAL { 0 }
    ::= { tSapEgressHsmdaQueueEntry 6 }

tSapEgressHsmdaQueueSlopePolicy        OBJECT-TYPE
    SYNTAX      TNamedItem
    MAX-ACCESS  read-create
    STATUS      current
    DESCRIPTION
        "The value of tSapEgressHsmdaQueueSlopePolicy specifies the slope
         policy specified by the user."
    DEFVAL { "default" }
    ::= { tSapEgressHsmdaQueueEntry 7 }

tSapEgressHsmdaQueueLastChanged        OBJECT-TYPE
    SYNTAX      TimeStamp
    MAX-ACCESS  read-only
    STATUS      current
    DESCRIPTION
        "The value of tSapEgressHsmdaQueueLastChanged indicates the timestamp 
         of last change to this row in tSapEgressHsmdaQueueTable."
    ::= { tSapEgressHsmdaQueueEntry 8 }

tSapEgressHsmdaQueueWrrWeight OBJECT-TYPE
    SYNTAX      THsmdaWrrWeight
    MAX-ACCESS  read-create
    STATUS      current
    DESCRIPTION
        "The value of tSapEgressHsmdaQueueWrrWeight specifies the weight with 
         which this queue should parent into the HSMDA scheduler, provided it is
         not superseded by the Weighted Round Robin (WRR) policy. The weight of 
         each queue determines how much bandwidth that queue gets out of the 
         total rate for the scheduling class."
    DEFVAL      { 1 }
    ::= { tSapEgressHsmdaQueueEntry 9 }

tSapEgressHsmdaQueueMBS OBJECT-TYPE
    SYNTAX      THSMDABurstSizeBytes
    UNITS       "bytes"
    MAX-ACCESS  read-create
    STATUS      current
    DESCRIPTION
        "The value of tSapEgressHsmdaQueueMBS specifies the maximum amount of 
         buffer space (in bytes) allowed for this HSMDA queue."
    DEFVAL      { -1 }
    ::= { tSapEgressHsmdaQueueEntry 10 }

tSapEgressHsmdaQueueBurstLimit OBJECT-TYPE
    SYNTAX      THSMDAQueueBurstLimit
    UNITS       "bytes"
    MAX-ACCESS  read-create
    STATUS      current
    DESCRIPTION
        "The value of tSapEgressHsmdaQueueBurstLimit specifies the explicit 
         shaping burst size of the queue."
    DEFVAL      { -1 }
    ::= { tSapEgressHsmdaQueueEntry 11 }

--
-- sap-egress policy dscp table
--

tSapEgressDSCPTable OBJECT-TYPE
    SYNTAX       SEQUENCE OF TSapEgressDSCPEntry
    MAX-ACCESS   not-accessible
    STATUS       current
    DESCRIPTION
        "a list of all DSCP entries for all sap-egress policies."
    ::= { tSapEgressObjects 5 }

tSapEgressDSCPEntry OBJECT-TYPE
    SYNTAX       TSapEgressDSCPEntry
    MAX-ACCESS   not-accessible
    STATUS       current
    DESCRIPTION
        "Information about a particular DSCP entry for a sap-egress policy.

        Entries are created by user.
        Entries are deleted by user.

        There is no StorageType object, entries have a presumed
        StorageType of nonVolatile.

        in the event that one policy has multiple entries, and
        the tSapEgressDSCP values are the same, only one queue
        will be created (the queue for the lexicographically
        first tSapEgressDSCP).
        "
    INDEX { tSapEgressIndex, tSapEgressDSCP }
    ::= { tSapEgressDSCPTable 1 }

TSapEgressDSCPEntry ::= SEQUENCE
    {
        tSapEgressDSCP                    TDSCPName,
        tSapEgressDSCPRowStatus           RowStatus,
        tSapEgressDSCPLastChanged         TimeStamp,
        tSapEgressDSCPHsmdaCntrOverride   TEgressHsmdaCounterIdOrZero,
        tSapEgressDSCPfc                  TFCNameOrEmpty, 
        tSapEgressDSCPprofile             TProfileOrNone
    }

tSapEgressDSCP OBJECT-TYPE
    SYNTAX       TDSCPName
    MAX-ACCESS   not-accessible
    STATUS       current
    DESCRIPTION
        ""
    ::= { tSapEgressDSCPEntry 1 }

tSapEgressDSCPRowStatus OBJECT-TYPE
    SYNTAX       RowStatus
    MAX-ACCESS   read-create
    STATUS       current
    DESCRIPTION
        "The value of tSapEgressDSCPRowStatus controls the creation/deletion 
         of rows in this table."
    ::= { tSapEgressDSCPEntry 2 }

tSapEgressDSCPLastChanged OBJECT-TYPE
    SYNTAX       TimeStamp
    MAX-ACCESS   read-only
    STATUS       current
    DESCRIPTION
        "The value of tSapEgressDSCPLastChanged indicates the sysUpTime
         at the time of the most recent management-initiated change to this
         table row."
    ::= { tSapEgressDSCPEntry 3 }

tSapEgressDSCPHsmdaCntrOverride OBJECT-TYPE
    SYNTAX       TEgressHsmdaCounterIdOrZero
    MAX-ACCESS   read-create
    STATUS       current
    DESCRIPTION
        "The value of the object tSapEgressDSCPHsmdaCntrOverride 
         specifies the counter to use for all the traffic that
         matches the specific DSCP i.e. tSapEgressDSCP.

         A value of zero implies that the default counters should be used."
    DEFVAL { 0 }
    ::= { tSapEgressDSCPEntry 4 }

tSapEgressDSCPfc OBJECT-TYPE
    SYNTAX       TFCNameOrEmpty
    MAX-ACCESS   read-create
    STATUS       current
    DESCRIPTION
        "The value of tSapEgressDSCPfc, when specified, will overwrite the
         forwarding class derived from ingress. The new forwarding class is
         used for egress remarking and queue mapping decisions."
    DEFVAL { ''H }
    ::= { tSapEgressDSCPEntry 5 }

tSapEgressDSCPprofile OBJECT-TYPE
    SYNTAX       TProfileOrNone
    MAX-ACCESS   read-create
    STATUS       current
    DESCRIPTION
        "The value of tSapEgressDSCPprofile, when provided, specifies the
         egress classification rule that will overwrite the profile of the
         packet derived from the ingress. The new profile value is used for
         egress remarking and queue congestion behavior."
    DEFVAL { none }
    ::= { tSapEgressDSCPEntry 6 }

--
-- sap-egress policy precedence table
--

tSapEgressPrecTable OBJECT-TYPE
    SYNTAX       SEQUENCE OF TSapEgressPrecEntry
    MAX-ACCESS   not-accessible
    STATUS       current
    DESCRIPTION 
        "This table maintains the mapping of a particular
        precedence value into a forwarding class"
    ::= { tSapEgressObjects 6 }

tSapEgressPrecEntry OBJECT-TYPE
    SYNTAX       TSapEgressPrecEntry
    MAX-ACCESS   not-accessible
    STATUS       current
    DESCRIPTION
        "Information about a particular sap-egress policy's
         IP precedence values to forwarding class mappings.

         Entries are created and deleted by user. They have
         a presumed StorageType of nonVolatile."
    INDEX { tSapEgressIndex, tSapEgressPrecValue }
    ::= { tSapEgressPrecTable 1 }

TSapEgressPrecEntry ::= SEQUENCE
    {
        tSapEgressPrecValue               TPrecValue,
        tSapEgressPrecRowStatus           RowStatus,
        tSapEgressPrecLastChanged         TimeStamp,
        tSapEgressPrecHsmdaCntrOverride   TEgressHsmdaCounterIdOrZero,
        tSapEgressPrecFC                  TFCNameOrEmpty, 
        tSapEgressPrecProfile             TProfileOrNone
    }

tSapEgressPrecValue OBJECT-TYPE
    SYNTAX       TPrecValue
    MAX-ACCESS   not-accessible
    STATUS       current
    DESCRIPTION
        "The value of tSapEgressPrecValue indicates the precedence value
        for which the mapping is done. It is used as a secondary index for
        tSapEgressPrecTable."
    ::= { tSapEgressPrecEntry 1 }

tSapEgressPrecRowStatus OBJECT-TYPE
    SYNTAX       RowStatus
    MAX-ACCESS   read-create
    STATUS       current
    DESCRIPTION
        "The value of tSapEgressPrecRowStatus controls the creation/deletion 
         of rows in this table."
    ::= { tSapEgressPrecEntry 2 }

tSapEgressPrecLastChanged OBJECT-TYPE
    SYNTAX       TimeStamp
    MAX-ACCESS   read-only
    STATUS       current
    DESCRIPTION
        "The value of tSapEgressPrecLastChanged indicates the sysUpTime
         at the time of the most recent management-initiated change to this
         table row."
    ::= { tSapEgressPrecEntry 3 }

tSapEgressPrecHsmdaCntrOverride OBJECT-TYPE
    SYNTAX       TEgressHsmdaCounterIdOrZero
    MAX-ACCESS   read-create
    STATUS       current
    DESCRIPTION
        "The value of tSapEgressPrecHsmdaCntrOverride specifies the counter 
         to use for all the traffic that matches the specific precedence value
         i.e. tSapEgressPrecValue.

         A value of zero implies that the default counters should be used."
    DEFVAL { 0 }
    ::= { tSapEgressPrecEntry 4 }

tSapEgressPrecFC OBJECT-TYPE
    SYNTAX       TFCNameOrEmpty
    MAX-ACCESS   read-create
    STATUS       current
    DESCRIPTION
        "The value of tSapEgressPrecFC, when specified, will overwrite the
         forwarding class derived from ingress. The new forwarding class is
         used for egress remarking and queue mapping decisions."
    DEFVAL { ''H }
    ::= { tSapEgressPrecEntry 5 }

tSapEgressPrecProfile OBJECT-TYPE
    SYNTAX       TProfileOrNone
    MAX-ACCESS   read-create
    STATUS       current
    DESCRIPTION
        "The value of tSapEgressPrecProfile, when provided, specifies the
         egress classification rule that will overwrite the profile of the
         packet derived from the ingress. The new profile value is used for
         egress remarking and queue congestion behavior."
    DEFVAL { none }
    ::= { tSapEgressPrecEntry 6 }

--
-- sap-egress ip-crit table
--

tSapEgrIPCritTable OBJECT-TYPE
    SYNTAX      SEQUENCE OF TSapEgrIPCritEntry
    MAX-ACCESS  not-accessible
    STATUS      current
    DESCRIPTION
        "This table maintains the entries for matching
         criteria for IP packets on egress. In release 10.0 and higher, 
         this table can also contain IPv6 criteria."
    ::= { tSapEgressObjects 7 }

tSapEgrIPCritEntry    OBJECT-TYPE
    SYNTAX      TSapEgrIPCritEntry
    MAX-ACCESS  not-accessible
    STATUS      current
    DESCRIPTION
        "Information about a particular egress IP or IPv6 matching
         criteria entry.

         Entries are created and deleted by user. They have
         a presumed StorageType of nonVolatile."
    INDEX { tSapEgressIndex,  tSapEgrIPCritAddrType, tSapEgrIPCritIndex }
    ::= { tSapEgrIPCritTable 1}

TSapEgrIPCritEntry ::= SEQUENCE
    {
        tSapEgrIPCritAddrType                   InetAddressType,
        tSapEgrIPCritIndex                      Unsigned32,
        tSapEgrIPCritRowStatus                  RowStatus,
        tSapEgrIPCritLastChanged                TimeStamp,
        tSapEgrIPCritDescription                TItemDescription,
        tSapEgrIPCritActionHsmdaCntrOvr         TEgressHsmdaCounterIdOrZero,
        tSapEgrIPCritSourceIpAddrType           InetAddressType,
        tSapEgrIPCritSourceIpAddr               InetAddress,
        tSapEgrIPCritSourceIpMask               InetAddressPrefixLength,
        tSapEgrIPCritDestIpAddrType             InetAddressType,
        tSapEgrIPCritDestIpAddr                 InetAddress,
        tSapEgrIPCritDestIpMask                 InetAddressPrefixLength,
        tSapEgrIPCritProtocol                   TIpProtocol,
        tSapEgrIPCritSourcePortValue1           TTcpUdpPort,
        tSapEgrIPCritSourcePortValue2           TTcpUdpPort,
        tSapEgrIPCritSourcePortOperator         TTcpUdpPortOperator,
        tSapEgrIPCritDestPortValue1             TTcpUdpPort,
        tSapEgrIPCritDestPortValue2             TTcpUdpPort,
        tSapEgrIPCritDestPortOperator           TTcpUdpPortOperator,
        tSapEgrIPCritDSCP                       TDSCPNameOrEmpty,
        tSapEgrIPCritFragment                   TItemMatch,
        tSapEgrIPCritActionFC                   TFCNameOrEmpty,
        tSapEgrIPCritActionProfile              TProfileOrNone,
        tSapEgrIPCritSrcIpFullMask              InetAddress,
        tSapEgrIPCritDstIpFullMask              InetAddress,
        tSapEgrIPCritActionPolicer              TEgressPolicerIdOrNone,
        tSapEgrIPCritActionPortQGrpQueue        TruthValue,
        tSapEgrIPCritActionQueue                TEgressQueueId,
        tSapEgrIPCritActionPolicerUseFCQ        TruthValue
    }

tSapEgrIPCritAddrType OBJECT-TYPE
    SYNTAX       InetAddressType
    MAX-ACCESS   not-accessible
    STATUS       current
    DESCRIPTION
        "The value of tSapEgrIPCritAddrType specifies the index address
         type this entry should match against."
    DEFVAL { ipv4 }
    ::= { tSapEgrIPCritEntry 1 }

tSapEgrIPCritIndex        OBJECT-TYPE
    SYNTAX      Unsigned32 (1..65535)
    MAX-ACCESS  not-accessible
    STATUS      current
    DESCRIPTION
        "The value of tSapEgrIPCritIndex specifies the index for a sap-egress
         IP or IPv6 criteria entry."
    ::= { tSapEgrIPCritEntry 2 }

tSapEgrIPCritRowStatus        OBJECT-TYPE
    SYNTAX      RowStatus
    MAX-ACCESS  read-create
    STATUS      current
    DESCRIPTION
        "The value of tSapEgrIPCritRowStatus is used for the creation
         and deletion of sap-egress IP or IPv6 criteria entries."
    ::= { tSapEgrIPCritEntry 3 }

tSapEgrIPCritLastChanged        OBJECT-TYPE
    SYNTAX      TimeStamp
    MAX-ACCESS  read-only
    STATUS      current
    DESCRIPTION
        "The value of tSapEgrIPCritLastChanged indicates the sysUpTime
         at the time of the last modification of this entry.

         If no changes were made to the entry since the last
         re-initialization of the local network management subsystem,
         then this object contains a zero value."
    ::= { tSapEgrIPCritEntry 4 }

tSapEgrIPCritDescription        OBJECT-TYPE
    SYNTAX      TItemDescription
    MAX-ACCESS  read-create
    STATUS      current
    DESCRIPTION
        "The value of tSapEgrIPCritDescription specifies a description
         of the sap-egress IP or IPv6 criteria entry."
    DEFVAL { "" }
    ::= { tSapEgrIPCritEntry 5 }

tSapEgrIPCritActionHsmdaCntrOvr OBJECT-TYPE
    SYNTAX       TEgressHsmdaCounterIdOrZero
    MAX-ACCESS   read-create
    STATUS       current
    DESCRIPTION
        "The value of the object tSapEgrIPCritActionHsmdaCntrOvr specifies
         the Hsmda counter to use for matching packets. This value will be
         ignored when the sap-egress policy specified by tSapEgressIndex,
         is applied to a SAP on a non-Hsmda MDA type. 

         A value of zero implies that the default counters should be used."
    DEFVAL { 0 }
    ::= { tSapEgrIPCritEntry 6 }

tSapEgrIPCritSourceIpAddrType OBJECT-TYPE
    SYNTAX       InetAddressType
    MAX-ACCESS   read-create
    STATUS       current
    DESCRIPTION
        "The value of tSapEgrIPCritSourceIpAddrType specifies the address type
         of tSapEgrIPCritSourceIpAddr. If the value of this object is not
         'none', it must have the same value as tSapEgrIPCritAddrType."
    DEFVAL { unknown }
    ::= { tSapEgrIPCritEntry 7 }

tSapEgrIPCritSourceIpAddr OBJECT-TYPE
    SYNTAX       InetAddress (SIZE(0|4|16))
    MAX-ACCESS   read-create
    STATUS       current
    DESCRIPTION
        "The value of tSapEgrIPCritSourceIpAddr specifies the IP or IPv6 
         address to match with source-IP of the packet."
    DEFVAL { ''H }
    ::= { tSapEgrIPCritEntry 8 }

tSapEgrIPCritSourceIpMask OBJECT-TYPE
    SYNTAX       InetAddressPrefixLength
    MAX-ACCESS   read-create
    STATUS       current
    DESCRIPTION
        "If different from 0, the object tSapEgrIPCritSourceIpMask
         specifies the IP Mask value for this policy IP Filter entry.
         The mask is ANDed with the received source IP address to match
         the tSapEgrIPCritSourceIpAddr.

         If the value of tSapEgrIPCritSourceIpMask is 0, and the
         value of tSapEgrIPCritSrcIpFullMask is non zero then the
         value of tSapEgrIPCritSrcIpFullMask is used as mask.

         If the value of tSapEgrIPCritSourceIpMask is non zero,
         it will be equal to the mask expressed the object
         tSapEgrIPCritSrcIpFullMask.

         If both tSapEgrIPCritSourceIpMask and
         tSapEgrIPCritSrcIpFullMask are set to 0, no matching is done
         on the source Ip address.

         If a value is specified for this object, then the value of the
         object tSapEgrIPCritSrcIpFullMask will be set to reflect
         this same mask."
    DEFVAL { 0 }
    ::= { tSapEgrIPCritEntry 9 }

tSapEgrIPCritDestIpAddrType OBJECT-TYPE
    SYNTAX       InetAddressType
    MAX-ACCESS   read-create
    STATUS       current
    DESCRIPTION
        "The value of tSapEgrIPCritDestIpAddrType specifies the address type
         of tSapEgrIPCritDestIpAddr. If the value of this object is not
         'none', it must have the same value as tSapEgrIPCritAddrType."
    DEFVAL { unknown }
    ::= { tSapEgrIPCritEntry 10 }

tSapEgrIPCritDestIpAddr OBJECT-TYPE
    SYNTAX       InetAddress (SIZE(0|4|16))
    MAX-ACCESS   read-create
    STATUS       current
    DESCRIPTION
        "The value of tSapEgrIPCritDestIpAddr specifies the IP or IPv6 
         address to match with destination-IP of the packet."
    DEFVAL { ''H }
    ::= { tSapEgrIPCritEntry 11 }

tSapEgrIPCritDestIpMask OBJECT-TYPE
    SYNTAX       InetAddressPrefixLength
    MAX-ACCESS   read-create
    STATUS       current
    DESCRIPTION
        "If different from 0, the object tSapEgrIPCritDestIpMask
         specifies the IP Mask value for this policy IP Filter entry.
         The mask is ANDed with the received Destination IP address to match
         the tSapEgrIPCritDestIpAddr.

         If the value of tSapEgrIPCritDestIpMask is 0, and the
         value of tSapEgrIPCritDstIpFullMask is non zero then the
         value of tSapEgrIPCritDstIpFullMask is used as mask.

         If the value of tSapEgrIPCritDestIpMask is non zero,
         it will be equal to the mask expressed the object
         tSapEgrIPCritDstIpFullMask.

         If both tSapEgrIPCritDestIpMask and
         tSapEgrIPCritDstIpFullMask are set to 0, no matching is done
         on the Destination Ip address.

         If a value is specified for this object, then the value of the
         object tSapEgrIPCritDstIpFullMask will be set to reflect
         this same mask."
    DEFVAL { 0 }
    ::= { tSapEgrIPCritEntry 12 }

tSapEgrIPCritProtocol OBJECT-TYPE
    SYNTAX       TIpProtocol
    MAX-ACCESS   read-create
    STATUS       current
    DESCRIPTION
        "The value of tSapEgrIPCritProtocol specifies the IP protocol or
         IPv6 next-header to match. The value '-1' is used to disable matching 
         by IP protocol or IPv6 next-header. 
         When this value specifies an IPv6 next-header, since the match 
         criteria only pertains to the last next-header, the following values 
         are not accepted: 0, 43, 44, 50, 51, and 60."
    DEFVAL { -1 }
    ::= { tSapEgrIPCritEntry 13 }

tSapEgrIPCritSourcePortValue1 OBJECT-TYPE
    SYNTAX       TTcpUdpPort
    MAX-ACCESS   read-create
    STATUS       current
    DESCRIPTION
        "The value of tSapEgrIPCritSourcePortValue1 specifies the first TCP/UDP
         source port value. The value of this object is used according to the 
         value of tSapEgrIPCritSourcePortOperator."
    DEFVAL { 0 }
    ::= { tSapEgrIPCritEntry 14 }

tSapEgrIPCritSourcePortValue2 OBJECT-TYPE
    SYNTAX       TTcpUdpPort
    MAX-ACCESS   read-create
    STATUS       current
    DESCRIPTION
        "The value of tSapEgrIPCritSourcePortValue2 specifies the second TCP/UDP
         source port value. The value of this object is used according to the 
         value of tSapEgrIPCritSourcePortOperator."
    DEFVAL { 0 }
    ::= { tSapEgrIPCritEntry 15 }

tSapEgrIPCritSourcePortOperator OBJECT-TYPE
    SYNTAX       TTcpUdpPortOperator
    MAX-ACCESS   read-create
    STATUS       current
    DESCRIPTION
        "The value of tSapEgrIPCritSourcePortOperator specifies the manner in
         which tSapEgrIPCritSourcePortValue1 and tSapEgrIPCritSourcePortValue2
         are to be used."
    DEFVAL { none }
    ::= { tSapEgrIPCritEntry 16 }

tSapEgrIPCritDestPortValue1 OBJECT-TYPE
    SYNTAX       TTcpUdpPort
    MAX-ACCESS   read-create
    STATUS       current
    DESCRIPTION
        "The value of tSapEgrIPCritDestPortValue1 specifies the first TCP/UDP
         destination port value. The value of this object is used according to the 
         value of tSapEgrIPCritDestPortOperator."
    DEFVAL { 0 }
    ::= { tSapEgrIPCritEntry 17 }

tSapEgrIPCritDestPortValue2 OBJECT-TYPE
    SYNTAX       TTcpUdpPort
    MAX-ACCESS   read-create
    STATUS       current
    DESCRIPTION
        "The value of tSapEgrIPCritDestPortValue2 specifies the second TCP/UDP
         destination port value. The value of this object is used according to the 
         value of tSapEgrIPCritDestPortOperator."
    DEFVAL { 0 }
    ::= { tSapEgrIPCritEntry 18 }

tSapEgrIPCritDestPortOperator OBJECT-TYPE
    SYNTAX       TTcpUdpPortOperator
    MAX-ACCESS   read-create
    STATUS       current
    DESCRIPTION
        "The value of tSapEgrIPCritDestPortOperator specifies the manner in
         which tSapEgrIPCritDestPortValue1 and tSapEgrIPCritDestPortValue2
         are to be used."
    DEFVAL { none }
    ::= { tSapEgrIPCritEntry 19 }

tSapEgrIPCritDSCP OBJECT-TYPE
    SYNTAX       TDSCPNameOrEmpty
    MAX-ACCESS   read-create
    STATUS       current
    DESCRIPTION
        "The value of tSapEgrIPCritDSCP specifies the DSCP value to match in 
         the packet"
    DEFVAL { ''H }
    ::= { tSapEgrIPCritEntry 20 }

tSapEgrIPCritFragment OBJECT-TYPE
    SYNTAX       TItemMatch
    MAX-ACCESS   read-create
    STATUS       current
    DESCRIPTION
        "The value of tSapEgrIPCritFragment specifies fragmented packet
         matching. If the value is 'true', only fragmented packets match. 
         If the value is 'false', only non-fragmented packets match.
         If the value is 'off', all packets match regardless.
         
         This field is only relevant for ipv4. An inconsistentValue error 
         is returned when the value of tSapEgrIPCritFragment is not 'off' 
         and the value of tSapEgrIPCritAddrType is not 'ipv4'."
    DEFVAL { off }
    ::= { tSapEgrIPCritEntry 21 }

tSapEgrIPCritActionFC OBJECT-TYPE
    SYNTAX       TFCNameOrEmpty
    MAX-ACCESS   read-create
    STATUS       current
    DESCRIPTION
        "tSapEgrIPCritActionFC specifies the forwarding class to be used to
         classify all the traffic that matches the specific IP or IPv6 criteria.

         The value ''H indicates that the FC is derived
         from ingress classification and profiling functions."
    DEFVAL { ''H }
    ::= { tSapEgrIPCritEntry 22 }

tSapEgrIPCritActionProfile OBJECT-TYPE
    SYNTAX       TProfileOrNone
    MAX-ACCESS   read-create
    STATUS       current
    DESCRIPTION
        "tSapEgrIPCritActionProfile specifies the profile of the
         traffic that matches the specific IP or IPv6 criteria.

         The value none indicates that the profile is derived
         from ingress classification and profiling functions."
    DEFVAL { none }
    ::= { tSapEgrIPCritEntry 23 }

tSapEgrIPCritSrcIpFullMask OBJECT-TYPE
    SYNTAX       InetAddress (SIZE(0|4|16))
    MAX-ACCESS  read-create
    STATUS      current
    DESCRIPTION
        "If different from 0, the object tSapEgrIPCritSrcIpFullMask
         specifies the IP Mask value for this policy IP Filter entry.
         The mask is ANDed with the received Source IP address to match
         the tSapEgrIPCritSourceIpAddr.

         If the value of tSapEgrIPCritSourceIpMask is non zero,
         it will be equal to the mask expressed in the object
         tSapEgrIPCritSrcIpFullMask.

         If both tSapEgrIPCritSourceIpMask and
         tSapEgrIPCritSrcIpFullMask are set to 0, no matching is done
         on the Source IP address.

         If a regular mask is specified for tSapEgrIPCritSrcIpFullMask
         then the value of tSapEgrIPCritSourceIpMask will
         be changed to reflect this value."
    DEFVAL { ''H }
    ::= { tSapEgrIPCritEntry 24 }

tSapEgrIPCritDstIpFullMask OBJECT-TYPE
    SYNTAX       InetAddress (SIZE(0|4|16))
    MAX-ACCESS  read-create
    STATUS      current
    DESCRIPTION
        "If different from 0, the object tSapEgrIPCritDstIpFullMask
         specifies the IP Mask value for this policy IP Filter entry.
         The mask is ANDed with the received Dest IP address to match
         the tSapEgrIPCritDestIpAddr.

         If the value of tSapEgrIPCritDestIpMask is non zero,
         it will be equal to the mask expressed in the object
         tSapEgrIPCritDstIpFullMask.

         If both tSapEgrIPCritDestIpMask and
         tSapEgrIPCritDstIpFullMask are set to 0, no matching is done
         on the Dest IP address.

         If a regular mask is specified for tSapEgrIPCritDstIpFullMask
         then the value of tSapEgrIPCritDestIpMask will
         be changed to reflect this value."
    DEFVAL { ''H }
    ::= { tSapEgrIPCritEntry 25 }


tSapEgrIPCritActionPolicer   OBJECT-TYPE
    SYNTAX       TEgressPolicerIdOrNone
    MAX-ACCESS   read-create
    STATUS       current
    DESCRIPTION
        "The value of tSapEgrIPCritActionPolicer specifies the policer
         identifier to be used for the traffic matching this IP Criteria entry.
         It provides the ability to direct specific traffic to a different SAP
         egress local policer (tSapEgrIPCritActionPolicer) independently from
         that configured for the traffic's FC in tSapEgressFCPolicer. This
         action policer will be referred to as a bypass-policer.

         If a corresponding sap-egress policer identifier does not exist in
         tSapEgrPolicerTable, an 'inconsistentValue' error is returned.

         When the value of tSapEgrIPCritActionPolicer is set to its default
         value, then the traffic for this forwarding class will not use a
         bypass-policer.

         When the value of tSapEgrIPCritActionPolicer is set to non-default
         value, the value of tSapEgrIPCritActionPortQGrpQueue is set to default
         value and the value of tSapEgrIPCritActionQueue set to default value,
         then the traffic matching this IP Criteria entry will use the local
         policer specified by tSapEgrIPCritActionPolicer and then feed into a
         system determined egress access port queue-group queue.

         When the value of tSapEgrIPCritActionPolicer is set to non-default
         value, the value of tSapEgrIPCritActionPortQGrpQueue is set to
         non-default value and the value of tSapEgrIPCritActionQueue is set to
         non-default value, then the traffic matching this IP Criteria entry
         will use the local policer specified by tSapEgrIPCritActionPolicer and
         then feed into a queue within the egress access port queue-group
         instance (TIMETRA-SAP-MIB::sapEgressPortQGrp,
         TIMETRA-SAP-MIB::sapEgressPortQGrpInstanceId) attached to the SAP. The
         queue used will be specified by tSapEgrIPCritActionQueue.

         When the value of tSapEgrIPCritActionPolicer is set to non-default
         value, the value of tSapEgrIPCritActionPortQGrpQueue set to default
         value and the value of tSapEgrIPCritActionQueue is set to non-default
         value, then traffic matching this IP Criteria entry will use the local
         policer specified by tSapEgrIPCritActionPolicer, and then feed into the
         local queue specified by tSapEgrIPCritActionQueue.

         An 'inconsistentValue' error is returned if tSapEgrIPCritActionPolicer
         is set to a default value and either tSapEgrIPCritActionPortQGrpQueue
         or tSapEgrIPCritActionQueue are set to non-default value(s).
         
         An 'inconsistentValue' error is returned if the value of 
         tSapEgrIPCritActionPolicer is set to a non-default value when the value
         of tSapEgrIPCritRowStatus is set to 'notInService."
    DEFVAL { 0 }
    ::= { tSapEgrIPCritEntry 28 }

tSapEgrIPCritActionPortQGrpQueue OBJECT-TYPE
    SYNTAX       TruthValue
    MAX-ACCESS   read-create
    STATUS       current
    DESCRIPTION
        "The value of tSapEgrIPCritActionPortQGrpQueue specifies whether to use
         the queue specified in egress access port queue-group instance
         (TIMETRA-SAP-MIB::sapEgressPortQGrp,
         TIMETRA-SAP-MIB::sapEgressPortQGrpInstanceId) for this IP Criteria
         entry.

         When the value of tSapEgrIPCritActionPolicer is set to non-default
         value, the value of tSapEgrIPCritActionPortQGrpQueue is set to default
         value and the value of tSapEgrIPCritActionQueue set to default value,
         then the traffic matching this IP Criteria entry will use the local
         policer specified by tSapEgrIPCritActionPolicer and then feed into a
         system determined egress access port queue-group queue.

         When the value of tSapEgrIPCritActionPolicer is set to non-default
         value, the value of tSapEgrIPCritActionPortQGrpQueue is set to
         non-default value and the value of tSapEgrIPCritActionQueue is set to
         non-default value, then the traffic matching this IP Criteria entry
         will use the local policer specified by tSapEgrIPCritActionPolicer and
         then feed into a queue within the egress access port queue-group
         instance (TIMETRA-SAP-MIB::sapEgressPortQGrp,
         TIMETRA-SAP-MIB::sapEgressPortQGrpInstanceId) attached to the SAP. The
         queue used will be specified by tSapEgrIPCritActionQueue.

         When the value of tSapEgrIPCritActionPolicer is set to non-default
         value, the value of tSapEgrIPCritActionPortQGrpQueue set to default
         value and the value of tSapEgrIPCritActionQueue is set to non-default
         value, then traffic matching this IP Criteria entry will use the local
         policer specified by tSapEgrIPCritActionPolicer, and then feed into the
         local queue specified by tSapEgrIPCritActionQueue.

         An 'inconsistentValue' error is returned if tSapEgrIPCritActionPolicer
         is set to a default value and either tSapEgrIPCritActionPortQGrpQueue
         or tSapEgrIPCritActionQueue are set to non-default value(s).

         An 'inconsistentValue' error is returned if the value of
         tSapEgrIPCritActionPortQGrpQueue is set to a non-default value when the 
         value of tSapEgrIPCritRowStatus is set to 'notInService."
    DEFVAL { false }
    ::= { tSapEgrIPCritEntry 29 }

tSapEgrIPCritActionQueue OBJECT-TYPE
    SYNTAX       TEgressQueueId
    MAX-ACCESS   read-create
    STATUS       current
    DESCRIPTION
        "The value of tSapEgrIPCritActionQueue specifies queue to use once
         traffic matching this IP Criteria entry has been policed by
         the local policer tSapEgrIPCritActionPolicer.

         When the value of tSapEgrIPCritActionPolicer is set to non-default
         value, the value of tSapEgrIPCritActionPortQGrpQueue is set to default
         value and the value of tSapEgrIPCritActionQueue set to default value,
         then the traffic matching this IP Criteria entry will use the local
         policer specified by tSapEgrIPCritActionPolicer and then feed into a
         system determined egress access port queue-group queue.

         When the value of tSapEgrIPCritActionPolicer is set to non-default
         value, the value of tSapEgrIPCritActionPortQGrpQueue is set to
         non-default value and the value of tSapEgrIPCritActionQueue is set to
         non-default value, then the traffic matching this IP Criteria entry
         will use the local policer specified by tSapEgrIPCritActionPolicer and
         then feed into a queue within the egress access port queue-group
         instance (TIMETRA-SAP-MIB::sapEgressPortQGrp,
         TIMETRA-SAP-MIB::sapEgressPortQGrpInstanceId) attached to the SAP. The
         queue used will be specified by tSapEgrIPCritActionQueue.

         When the value of tSapEgrIPCritActionPolicer is set to non-default
         value, the value of tSapEgrIPCritActionPortQGrpQueue set to default
         value and the value of tSapEgrIPCritActionQueue is set to non-default
         value, then traffic matching this IP Criteria entry will use the local
         policer specified by tSapEgrIPCritActionPolicer, and then feed into the
         local queue specified by tSapEgrIPCritActionQueue.

         An 'inconsistentValue' error is returned if tSapEgrIPCritActionPolicer
         is set to a default value and any of tSapEgrIPCritActionPortQGrpQueue,
         tSapEgrIPCritActionQueue, tSapEgrIPCritActionPolicerUseFCQ are set to
         non-default value(s).

         An 'inconsistentValue' error is returned if the value of 
         tSapEgrIPCritActionQueue is set to a non-default value when the value
         of tSapEgrIPCritRowStatus is set to 'notInService."
    DEFVAL { 0 }
    ::= { tSapEgrIPCritEntry 30 }

tSapEgrIPCritActionPolicerUseFCQ OBJECT-TYPE
    SYNTAX       TruthValue
    MAX-ACCESS   read-create
    STATUS       current
    DESCRIPTION
        "tSapEgrIPCritActionPolicerUseFCQ specifies whether to direct the
         output of the policer to the configured (fc-mapped) queues instead
         of the default behavior.

         An 'inconsistentValue' error is returned if
         tSapEgrIPCritActionPolicerUseFCQ is set to a non-default value and
         any of tSapEgrIPCritActionPortQGrpQueue, tSapEgrIPCritActionQueue
         are set to non-default value.

         An 'inconsistentValue' error is returned if
         tSapEgrIPCritActionPolicerUseFCQ is set to a non-default value and
         tSapEgrIPCritActionPolicer is set to default value."
    DEFVAL { false }
    ::= { tSapEgrIPCritEntry 31 }

-- -------------------------
-- SAP Egress Policer table
-- -------------------------

tSapEgrPolicerTableLastChanged OBJECT-TYPE
    SYNTAX       TimeStamp
    MAX-ACCESS   read-only
    STATUS       current
    DESCRIPTION
        "tSapEgrPolicerTableLastChanged indicates the timestamp of last change
        to the tSapEgrPolicerTable."
    ::= { tQosTimeStampObjects 86 }

tSapEgrPolicerTable OBJECT-TYPE
    SYNTAX       SEQUENCE OF TSapEgrPolicerEntry
    MAX-ACCESS   not-accessible
    STATUS       current
    DESCRIPTION
        "tSapEgrPolicerTable defines SAP Egress Policer Table for providing,
         via SNMP, the capability of defining the policers.

         tSapEgrPolicerTable holds a list of all the policers configured in
         the managed system. Policers must exist in this table before being
         referenced by the forwarding class mappings within the queue policy
         as defined in the tSapEgressFCTable."
    ::= { tSapEgressObjects 8 }

tSapEgrPolicerEntry OBJECT-TYPE
    SYNTAX       TSapEgrPolicerEntry
    MAX-ACCESS   not-accessible
    STATUS       current
    DESCRIPTION
        "tSapEgrPolicerEntry defines an entry in the tSapEgrPolicerTable.

         Entries are created/deleted in this table by SNMP sets to
         tSapEgrPolicerRowStatus."
    INDEX { tSapEgressIndex, tSapEgrPolicerId }
    ::= { tSapEgrPolicerTable 1 }

TSapEgrPolicerEntry ::= SEQUENCE
    {
        tSapEgrPolicerId                    TEgressPolicerId,
        tSapEgrPolicerRowStatus             RowStatus,
        tSapEgrPolicerLastChanged           TimeStamp,
        tSapEgrPolicerDescr                 TItemDescription,
        tSapEgrPolicerPIRAdaptation         TAdaptationRule,
        tSapEgrPolicerCIRAdaptation         TAdaptationRule,
        tSapEgrPolicerParent                TNamedItemOrEmpty,
        tSapEgrPolicerLevel                 TLevel,
        tSapEgrPolicerWeight                TPolicerWeight,
        tSapEgrPolicerAdminPIR              THPolPIRRate,
        tSapEgrPolicerAdminCIR              THPolCIRRate,
        tSapEgrPolicerStatMode              TmnxEgrPolicerStatMode,
        tSapEgrPolicerMBS                   TPlcrBurstSizeBytes,
        tSapEgrPolicerHiPrioOnly            TBurstPercentOrDefault,
        tSapEgrPolicerCBS                   TPlcrBurstSizeBytes,
        tSapEgrPolicerPktOffset             TEgressPerPacketOffset,
        tSapEgrPolicerAdminPIRPercent       Unsigned32,
        tSapEgrPolicerAdminCIRPercent       Unsigned32,
        tSapEgrPolicerRateType              TPolicerRateType,
        tSapEgrPolicerSlopeStartDepth       Unsigned32,
        tSapEgrPolicerSlopeMaxDepth         Unsigned32,
        tSapEgrPolicerSlopeMaxProb          Unsigned32,
        tSapEgrPolicerSlopeMap              TmnxSlopeMap,
        tSapEgrPolicerAdvCfgPolicy          TNamedItemOrEmpty,
        tSapEgrPolicerProfileCapped         TruthValue,
        tSapEgrPolicerProfileOutPreserve    TruthValue
    }

tSapEgrPolicerId OBJECT-TYPE
    SYNTAX       TEgressPolicerId
    MAX-ACCESS   not-accessible
    STATUS       current
    DESCRIPTION
        "tSapEgrPolicerId defines the SAP Egress Policer identifier.
         It identifies an sap-egress policer in the managed
         system."
    ::= { tSapEgrPolicerEntry 1 }

tSapEgrPolicerRowStatus OBJECT-TYPE
    SYNTAX       RowStatus
    MAX-ACCESS   read-create
    STATUS       current
    DESCRIPTION
        "tSapEgrPolicerRowStatus allows entries to be created and deleted
         in the tSapEgrPolicerTable."
    REFERENCE
        "See definition of RowStatus in RFC 2579, 'Textual Conventions for
         SMIv2.'"
    ::= { tSapEgrPolicerEntry 2 }

tSapEgrPolicerLastChanged OBJECT-TYPE
    SYNTAX       TimeStamp
    MAX-ACCESS   read-only
    STATUS       current
    DESCRIPTION
        "tSapEgrPolicerLastChanged indicates the value of sysUpTime when
         the entry was last modified."
    ::= { tSapEgrPolicerEntry 3 }

tSapEgrPolicerDescr OBJECT-TYPE
    SYNTAX       TItemDescription
    MAX-ACCESS   read-create
    STATUS       current
    DESCRIPTION
        "tSapEgrPolicerDescr specifies the description of the policer."
    DEFVAL { ''H }
    ::= { tSapEgrPolicerEntry 4 }

tSapEgrPolicerPIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tSapEgrPolicerEntry 5 }

tSapEgrPolicerCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tSapEgrPolicerEntry 6 }

tSapEgrPolicerParent OBJECT-TYPE
    SYNTAX       TNamedItemOrEmpty
    MAX-ACCESS   read-create
    STATUS       current
    DESCRIPTION
        "tSapEgrPolicerParent specifies the scheduler to which this queue would
        be feeding."
    DEFVAL { ''H }
    ::= { tSapEgrPolicerEntry 7 }

tSapEgrPolicerLevel OBJECT-TYPE
    SYNTAX       TLevel
    MAX-ACCESS   read-create
    STATUS       current
    DESCRIPTION
        "tSapEgrPolicerLevel specifies the level of priority while feeding
        the parent."
    DEFVAL { 1 }
    ::= { tSapEgrPolicerEntry 8 }

tSapEgrPolicerWeight OBJECT-TYPE
    SYNTAX       TPolicerWeight
    MAX-ACCESS   read-create
    STATUS       current
    DESCRIPTION
        "tSapEgrPolicerWeight specifies the weight that needs to be used by the
        scheduler to which this queue would be feeding."
    DEFVAL { 1 }
    ::= { tSapEgrPolicerEntry 9 }

tSapEgrPolicerAdminPIR OBJECT-TYPE
    SYNTAX       THPolPIRRate
    UNITS        "kbps"
    MAX-ACCESS   read-create
    STATUS       current
    DESCRIPTION
        "tSapEgrPolicerAdminPIR specifies the administrative PIR specified by
        the user."
    DEFVAL { -1 }
    ::= { tSapEgrPolicerEntry 10 }

tSapEgrPolicerAdminCIR OBJECT-TYPE
    SYNTAX       THPolCIRRate
    UNITS        "kbps"
    MAX-ACCESS   read-create
    STATUS       current
    DESCRIPTION
        "tSapEgrPolicerAdminCIR specifies the administrative CIR specified by
        the user."
    DEFVAL { 0 }
    ::= { tSapEgrPolicerEntry 11 }

tSapEgrPolicerStatMode OBJECT-TYPE
    SYNTAX       TmnxEgrPolicerStatMode
    MAX-ACCESS   read-create
    STATUS       current
    DESCRIPTION
        "tSapEgrPolicerStatMode specifies the mode of statistics collected by
        this policer."
    DEFVAL { minimal }
    ::= { tSapEgrPolicerEntry 12 }

tSapEgrPolicerMBS OBJECT-TYPE
    SYNTAX       TPlcrBurstSizeBytes
    UNITS        "bytes"
    MAX-ACCESS   read-create
    STATUS       current
    DESCRIPTION
        "The tSapEgrPolicerMBS specifies the high priority 'violate' threshold
        of PIR leaky bucket of this policer."
    DEFVAL { -1 }
    ::= { tSapEgrPolicerEntry 13 }

tSapEgrPolicerHiPrioOnly OBJECT-TYPE
    SYNTAX       TBurstPercentOrDefault
    UNITS        "percent"
    MAX-ACCESS   read-create
    STATUS       current
    DESCRIPTION
        "The tSapEgrPolicerHiPrioOnly specifies the percentage of PIR leaky
        bucket's MBS (maximum burst size) of this policer that is reserved for
        high priority traffic."
    DEFVAL { -1 }
    ::= { tSapEgrPolicerEntry 14 }

tSapEgrPolicerCBS OBJECT-TYPE
    SYNTAX       TPlcrBurstSizeBytes
    UNITS        "bytes"
    MAX-ACCESS   read-create
    STATUS       current
    DESCRIPTION
        "The tSapEgrPolicerCBS specifies the 'exceed' threshold of the CIR leaky
        bucket of this policer."
    DEFVAL { -1 }
    ::= { tSapEgrPolicerEntry 15 }

tSapEgrPolicerPktOffset OBJECT-TYPE
    SYNTAX       TEgressPerPacketOffset
    MAX-ACCESS   read-create
    STATUS       current
    DESCRIPTION
        "tSapEgrPolicerPktOffset specifies the packet byte offset for
        addition of policing information by this policer."
    DEFVAL { 0 }
    ::= { tSapEgrPolicerEntry 16 }

tSapEgrPolicerAdminPIRPercent OBJECT-TYPE
    SYNTAX       Unsigned32 (1..10000)
    UNITS        "hundredths of a percent"
    MAX-ACCESS   read-create
    STATUS       current
    DESCRIPTION
        "The administrative PIR percentage, in hundredths of a percent.
         An 'inconsistentValue' error is returned if
         tSapEgrPolicerAdminPIRPercent is set to non-default value when the
         object tSapEgrPolicerRateType is set to 'kbps'."
    DEFVAL { 10000 }
    ::= { tSapEgrPolicerEntry 17 }
 
tSapEgrPolicerAdminCIRPercent OBJECT-TYPE
    SYNTAX       Unsigned32 (0..10000)
    UNITS        "hundredths of a percent"
    MAX-ACCESS   read-create
    STATUS       current
    DESCRIPTION
        "The administrative CIR percentage, in hundredths of a percent.
         An 'inconsistentValue' error is returned if
         tSapEgrPolicerAdminCIRPercent is set to non-default value when the
         object tSapEgrPolicerRateType is set to 'kbps'."
    DEFVAL { 0 }
    ::= { tSapEgrPolicerEntry 18 }
 
tSapEgrPolicerRateType OBJECT-TYPE
    SYNTAX       TPolicerRateType
    MAX-ACCESS   read-create
    STATUS       current
    DESCRIPTION
        "The value of tSapEgrPolicerRateType specifies the type of egress
         policer rate.
 
         When the value of the object is set to 'kbps', the egresss policer
         rates are specified in kbps. The objects
         tSapEgrPolicerAdminPIRPercent and tSapEgrPolicerAdminCIRPercent
         will be set to their default values.
 
         When the value of the object is set to 'percentOfLocalLimit', 
         the egress policer rates are specified in percentage. The objects 
         tSapEgrPolicerAdminPIR and tSapEgrPolicerAdminCIR will be set to 
         their default values."
    DEFVAL { kbps }
    ::= { tSapEgrPolicerEntry 19 }

tSapEgrPolicerSlopeStartDepth OBJECT-TYPE
    SYNTAX       Unsigned32 (1..10000)
    UNITS        "hundredths of a percent"
    MAX-ACCESS   read-create
    STATUS       current
    DESCRIPTION
        "The value of tSapEgrPolicerSlopeStartDepth specifies the percentage of
         the buffer utilized after which the drop probability starts to rise
         above 0."
    DEFVAL { 10000 }
    ::= { tSapEgrPolicerEntry 20 }

tSapEgrPolicerSlopeMaxDepth OBJECT-TYPE
    SYNTAX       Unsigned32 (1..10000)
    UNITS        "hundredths of a percent"
    MAX-ACCESS   read-create
    STATUS       current
    DESCRIPTION
        "The value of tSapEgrPolicerSlopeMaxDepth specifies the percentage of
         the buffer utilized after which the drop probability is 100 percent.
         This implies that all packets beyond this point will be
         dropped."
    DEFVAL { 10000 }
    ::= { tSapEgrPolicerEntry 21 }

tSapEgrPolicerSlopeMaxProb OBJECT-TYPE
    SYNTAX       Unsigned32 (1..10000)
    UNITS        "hundredths of a percent"
    MAX-ACCESS   read-create
    STATUS       current
    DESCRIPTION
        "The value of tSapEgrPolicerSlopeMaxProb specifies the drop 
         probability, as a percentage, when the queue depth reaches
         tSapEgrPolicerSlopeMaxDepth. The drop increases steadily from 0 at
         the tSapEgrPolicerSlopeStartDepth up to the
         tSapEgrPolicerSlopeMaxProb at the tSapEgrPolicerSlopeMaxDepth."
    DEFVAL { 10000 }
    ::= { tSapEgrPolicerEntry 22 }

tSapEgrPolicerSlopeMap OBJECT-TYPE
    SYNTAX       TmnxSlopeMap
    MAX-ACCESS   read-create
    STATUS       current
    DESCRIPTION
        "The value of tSapEgrPolicerSlopeMap specifies the slope map to be used
         with this policer."
    DEFVAL { none }
    ::= { tSapEgrPolicerEntry 23 }

tSapEgrPolicerAdvCfgPolicy        OBJECT-TYPE
    SYNTAX      TNamedItemOrEmpty
    MAX-ACCESS  read-create
    STATUS      current
    DESCRIPTION
        "The value of tSapEgrPolicerAdvCfgPolicy specifies the name of the 
         advanced configuration policy to be applied with this policer."
    DEFVAL { ''H }
    ::= { tSapEgrPolicerEntry 24 }

tSapEgrPolicerProfileCapped   OBJECT-TYPE
    SYNTAX       TruthValue
    MAX-ACCESS   read-create
    STATUS       current
    DESCRIPTION
        "The value of tSapEgrPolicerProfileCapped specifies how the explicit 
         in-profile and undetermined profile traffic should be handled at the 
         egress policer.
     
         When the value of tSapEgrPolicerProfileCapped is set to 'true', both 
         explicit in-profile and undetermined profile traffic is honored up to 
         CIR, above which it is marked as out-of-profile. If CIR is set to zero, 
         then all explicit in-profile and undetermined profile packets, along
         with the explicit out-of-profile packets are marked as out-of-profile.
    
         The default behavior when tSapEgrPolicerProfileCapped is set to 
         'false' is to ignore the CIR output state when an explicit in-profile 
         packet is handled by an egress policer."
    DEFVAL { false }
    ::= { tSapEgrPolicerEntry 25 }

tSapEgrPolicerProfileOutPreserve   OBJECT-TYPE
    SYNTAX      TruthValue
    MAX-ACCESS  read-create
    STATUS      current
    DESCRIPTION
        "The value of tSapEgrPolicerProfileOutPreserve specifies whether to
         preserve the color of offered out-of-profile traffic at sap-egress
         policer (profility of the packet can change based on egress CIR state).
 
         If the value of tSapEgrPolicerProfileOutPreserve is set to 'true',
         traffic determined as out-of-profile at ingress policer will be 
         treated as out-of-profile at sap-egress policer."
    DEFVAL { false }
    ::= { tSapEgrPolicerEntry 26 }

-- ----------------------
-- tSapEgrPolicyNameTable
-- ----------------------
tSapEgrPolicyNameTableLastChgd  OBJECT-TYPE
    SYNTAX          TimeStamp
    MAX-ACCESS      read-only
    STATUS          current
    DESCRIPTION     
        "The value of tSapEgrPolicyNameTableLastChgd indicates the
         sysUpTime at the time of the last modification
         of tSapEgrPolicyNameTable.

         If no changes were made to the entry since the last
         re-initialization of the local network management subsystem,
         then this object contains a zero value."
    ::= { tQosTimeStampObjects 96 }

tSapEgrPolicyNameTable OBJECT-TYPE
    SYNTAX          SEQUENCE OF TSapEgrPolicyNameEntry
    MAX-ACCESS      not-accessible
    STATUS          current
    DESCRIPTION     
        "A table that contains SAP egress policy name information. Entries
         are created automatically by the system
         when tSapEgressPolicyName object is set for the SAP egress policy."
    ::= { tSapEgressObjects 9 }

tSapEgrPolicyNameEntry OBJECT-TYPE
    SYNTAX          TSapEgrPolicyNameEntry
    MAX-ACCESS      not-accessible
    STATUS          current
    DESCRIPTION
        "Basic information about a specific SAP egress policy name."
    INDEX           { tSapEgressPolicyName }
    ::= { tSapEgrPolicyNameTable 1 }

TSapEgrPolicyNameEntry ::=
    SEQUENCE {
        tSapEgrPolicyNameId                   TSapEgressPolicyID,
        tSapEgrPolicyNameRowStatus            RowStatus,
        tSapEgrPolicyNameLastChanged          TimeStamp
    }

tSapEgrPolicyNameId OBJECT-TYPE
    SYNTAX          TSapEgressPolicyID
    MAX-ACCESS      read-only
    STATUS          current
    DESCRIPTION     
        "The value of the object tSapEgrPolicyNameId specifies the policy
         name associated with this SAP egress policy."
    ::= { tSapEgrPolicyNameEntry 1 }

tSapEgrPolicyNameRowStatus OBJECT-TYPE
    SYNTAX          RowStatus
    MAX-ACCESS      read-only
    STATUS          current
    DESCRIPTION     
        "This value of the object tSapEgrPolicyNameRowStatus specifies the
         status of this row."
    ::= { tSapEgrPolicyNameEntry 2 }

tSapEgrPolicyNameLastChanged        OBJECT-TYPE
    SYNTAX          TimeStamp
    MAX-ACCESS      read-only
    STATUS          current
    DESCRIPTION     
        "The value of tSapEgrPolicyNameLastChanged indicates the sysUpTime at
         the time of the last modification of this entry.
                     
         If no changes were made to the entry since the last 
         re-initialization of the local network management 
         subsystem, then this object contains a zero value."
    ::= { tSapEgrPolicyNameEntry 3 }

--
-- sap-egress policy dot1p table
--
tSapEgressDot1pTableLastChanged OBJECT-TYPE
    SYNTAX       TimeStamp
    MAX-ACCESS   read-only
    STATUS       current
    DESCRIPTION
        "tSapEgressDot1pTableLastChanged indicates the timestamp of last change
         to the tSapEgressDot1pTable."
    ::= { tQosTimeStampObjects 99 }

tSapEgressDot1pTable OBJECT-TYPE
    SYNTAX       SEQUENCE OF TSapEgressDot1pEntry
    MAX-ACCESS   not-accessible
    STATUS       current
    DESCRIPTION
        "A table that contains the list of all dot1p entries for all sap-egress
         policies."
    ::= { tSapEgressObjects 10 }

tSapEgressDot1pEntry OBJECT-TYPE
    SYNTAX       TSapEgressDot1pEntry
    MAX-ACCESS   not-accessible
    STATUS       current
    DESCRIPTION
        "Information about a particular dot1p match for a sap-egress policy.
         Entries are created/deleted by user. There is no StorageType object, 
         entries have a presumed StorageType of nonVolatile."
    INDEX { tSapEgressIndex, tSapEgressDot1pValue }
    ::= { tSapEgressDot1pTable 1 }

TSapEgressDot1pEntry ::= SEQUENCE
    {
        tSapEgressDot1pValue               Dot1PPriority,
        tSapEgressDot1pRowStatus           RowStatus,
        tSapEgressDot1pLastChanged         TimeStamp,
        tSapEgressDot1pFC                  TNamedItemOrEmpty,
        tSapEgressDot1pProfile             TProfileUseDEOrNone        
    }

tSapEgressDot1pValue OBJECT-TYPE
    SYNTAX       Dot1PPriority (0..7)
    MAX-ACCESS   not-accessible
    STATUS       current
    DESCRIPTION
        "The value of tSapEgressDot1pValue specifies the dotp value to match in 
         the packet. This value is also used as an index so that for any dot1p
         value there is only one possible disposition queue and priority."
    ::= { tSapEgressDot1pEntry 1 }

tSapEgressDot1pRowStatus OBJECT-TYPE
    SYNTAX       RowStatus
    MAX-ACCESS   read-create
    STATUS       current
    DESCRIPTION
        "tSapEgressDot1pRowStatus allows entries to be created and deleted
         in the tSapEgressDot1pTable."
    ::= { tSapEgressDot1pEntry 2 }

tSapEgressDot1pLastChanged OBJECT-TYPE
    SYNTAX       TimeStamp
    MAX-ACCESS   read-only
    STATUS       current
    DESCRIPTION
        "The value of tSapEgressDot1pLastChanged indicates the sysUpTime at
         the time of the last modification of this entry."
    ::= { tSapEgressDot1pEntry 3 }

tSapEgressDot1pFC OBJECT-TYPE
    SYNTAX       TNamedItemOrEmpty
    MAX-ACCESS   read-create
    STATUS       current
    DESCRIPTION
        "The value of tSapEgressDot1pFC specifies the forwarding class to be
         used to classify all the traffic that matches the Dot1p value specified
         by tSapEgressDot1pValue.

         Unless tSapEgressDot1pFC is specified explicitly, this match will be 
         ignored for classification purposes."
    DEFVAL { ''H }
    ::= { tSapEgressDot1pEntry 4 }

tSapEgressDot1pProfile OBJECT-TYPE
    SYNTAX       TProfileUseDEOrNone
    MAX-ACCESS   read-create
    STATUS       current
    DESCRIPTION
        "The value of tSapEgressDot1pProfile specifies the profile to use for
         packets that match the dot1p value specified by tSapEgressDot1pValue."
    DEFVAL { none }
    ::= { tSapEgressDot1pEntry 5 }

--
-- network policy table
--

tNetworkPolicyTable OBJECT-TYPE
    SYNTAX       SEQUENCE OF TNetworkPolicyEntry
    MAX-ACCESS   not-accessible
    STATUS       current
    DESCRIPTION  "  "
    ::= { tNetworkObjects 1 }

tNetworkPolicyEntry OBJECT-TYPE
    SYNTAX       TNetworkPolicyEntry
    MAX-ACCESS   not-accessible
    STATUS       current
    DESCRIPTION
        "Information about a particular Network Policy.

         network policy (1) is the default entry.

         Default Entry is created by the agent, other entries are
         created by user.

         Default Entry cannot be modified/deleted. The other
         entries are deleted by user.

         There is no StorageType object, entries have a presumed
         StorageType of nonVolatile.

         The default Egress FC entries are created as an action
         of setting the rowstatus."
    INDEX { tNetworkPolicyIndex }
    ::= { tNetworkPolicyTable 1 }

TNetworkPolicyEntry ::= SEQUENCE
    {
        tNetworkPolicyIndex                       TNetworkPolicyID,
        tNetworkPolicyRowStatus                   RowStatus,
        tNetworkPolicyScope                       TItemScope,
        tNetworkPolicyDescription                 TItemDescription,
        tNetworkPolicyIngressDefaultActionFC      TFCName,
        tNetworkPolicyIngressDefaultActionProfile TProfileOrDeiOrNone,
        tNetworkPolicyEgressRemark                TruthValue,
        tNetworkPolicyLastChanged                 TimeStamp,
        tNetworkPolicyIngressLerUseDscp           TruthValue,
        tNetworkPolicyEgressRemarkDscp            TruthValue,
        tNetworkPolicyIngMatchCriteria           TMatchCriteria
    }

tNetworkPolicyIndex OBJECT-TYPE
    SYNTAX       TNetworkPolicyID (1..65535|65536|65537|65538)
    MAX-ACCESS   not-accessible
    STATUS       current
    DESCRIPTION  ""
    REFERENCE    ""
    ::= { tNetworkPolicyEntry 1 }

tNetworkPolicyRowStatus OBJECT-TYPE
    SYNTAX       RowStatus
    MAX-ACCESS   read-create
    STATUS       current
    DESCRIPTION  ""
    ::= { tNetworkPolicyEntry 2 }

tNetworkPolicyScope OBJECT-TYPE
    SYNTAX       TItemScope
    MAX-ACCESS   read-create
    STATUS       current
    DESCRIPTION  ""
    DEFVAL { template }
    ::= { tNetworkPolicyEntry 5 }

tNetworkPolicyDescription OBJECT-TYPE
    SYNTAX       TItemDescription
    MAX-ACCESS   read-create
    STATUS       current
    DESCRIPTION
        "tNetworkPolicyDescription holds the description for this policy."
    DEFVAL { ''H }
    ::= { tNetworkPolicyEntry 6 }

tNetworkPolicyIngressDefaultActionFC OBJECT-TYPE
    SYNTAX       TFCName
    MAX-ACCESS   read-create
    STATUS       current
    DESCRIPTION
        "tNetworkPolicyIngressDefaultActionFC specifies the default
         forwarding class to be used while classifying the ingress traffic."
    DEFVAL { 'be'H }
    ::= { tNetworkPolicyEntry 7 }

tNetworkPolicyIngressDefaultActionProfile OBJECT-TYPE
    SYNTAX       TProfileOrDeiOrNone
    MAX-ACCESS   read-create
    STATUS       current
    DESCRIPTION
        "tNetworkPolicyIngressDefaultActionProfile specifies the
         default profile to be used for the ingressing traffic."
    DEFVAL { out }
    ::= { tNetworkPolicyEntry 8 }

tNetworkPolicyEgressRemark OBJECT-TYPE
    SYNTAX       TruthValue
    MAX-ACCESS   read-create
    STATUS       current
    DESCRIPTION
        "The object tNetworkPolicyEgressRemark specifies if the system
         will remark the egress packets or not."
    DEFVAL { false }
    ::= { tNetworkPolicyEntry 9 }

tNetworkPolicyLastChanged OBJECT-TYPE
    SYNTAX       TimeStamp
    MAX-ACCESS   read-only
    STATUS       current
    DESCRIPTION
        "Timestamp of last change to this row in tNetworkPolicyTable."
    ::= { tNetworkPolicyEntry 10 }

tNetworkPolicyIngressLerUseDscp OBJECT-TYPE
    SYNTAX       TruthValue
    MAX-ACCESS   read-create
    STATUS       current
    DESCRIPTION
        "The object has significance only for the label edge routers
         which should honor the DSCP markings instead of the LSPEXP bits."
    DEFVAL { false }
    ::= { tNetworkPolicyEntry 11 }

tNetworkPolicyEgressRemarkDscp OBJECT-TYPE
    SYNTAX       TruthValue
    MAX-ACCESS   read-create
    STATUS       current
    DESCRIPTION
         "The value of tNetworkPolicyEgressRemarkDscp object specifies
          whether DSCP bits in the internal IP header should be remarked.
          
          This object is valid only when tNetworkPolicyEgressRemark is set to
          'true'."
    DEFVAL { false }
    ::= { tNetworkPolicyEntry 12 }

tNetworkPolicyIngMatchCriteria      OBJECT-TYPE
    SYNTAX       TMatchCriteria
    MAX-ACCESS   read-only
    STATUS       current
    DESCRIPTION
        "The value of tNetworkPolicyIngMatchCriteria indicates which type of
         match-criteria the policy should use.

         When set to 'ip (1)', the policy looks for match entries in
         tNetworkIngIPCritTable.

         The value of tNetworkPolicyIngMatchCriteria is set to 'ip (1)' when the
         first match-criteria table entry is created. The value is set to
         'none (3)' when the last match-criteria table entry is removed."
    ::= { tNetworkPolicyEntry 13 }

--
-- network ingress policy dscp table
--

tNetworkIngressDSCPTable OBJECT-TYPE
    SYNTAX       SEQUENCE OF TNetworkIngressDSCPEntry
    MAX-ACCESS   not-accessible
    STATUS       current
    DESCRIPTION
        "The value of tNetworkIngressDSCPTable contains information about 
         DSCP mapping for network policy."
    ::= { tNetworkObjects 2 }

tNetworkIngressDSCPEntry OBJECT-TYPE
    SYNTAX       TNetworkIngressDSCPEntry
    MAX-ACCESS   not-accessible
    STATUS       current
    DESCRIPTION
        "Information about a dscp map for a network policy.

         Some default entries are created by the agent for the
         default network policy (1). These cannot be deleted or
         modified. Other entries are created/deleted by user.

         There is no StorageType object, entries have a presumed
         StorageType of nonVolatile.
        "
    INDEX { tNetworkPolicyIndex, tNetworkIngressDSCP }
    ::= { tNetworkIngressDSCPTable 1 }

TNetworkIngressDSCPEntry ::= SEQUENCE
    {
        tNetworkIngressDSCP            TDSCPName,
        tNetworkIngressDSCPRowStatus   RowStatus,
        tNetworkIngressDSCPFC          TFCName,
        tNetworkIngressDSCPProfile     TProfile,
        tNetworkIngressDSCPLastChanged TimeStamp
    }

tNetworkIngressDSCP OBJECT-TYPE
    SYNTAX       TDSCPName
    MAX-ACCESS   not-accessible
    STATUS       current
    DESCRIPTION
        "The value of tNetworkIngressDSCP specifies Differentiated Services
         Code Point (DSCP) value name."
    ::= { tNetworkIngressDSCPEntry 1 }

tNetworkIngressDSCPRowStatus OBJECT-TYPE
    SYNTAX       RowStatus
    MAX-ACCESS   read-create
    STATUS       current
    DESCRIPTION
        "The value of tNetworkIngressDSCPRowStatus is used for the creation and
         deletion of DSCP entries for network ingress Qos policy."
    ::= { tNetworkIngressDSCPEntry 2 }

tNetworkIngressDSCPFC OBJECT-TYPE
    SYNTAX       TFCName
    MAX-ACCESS   read-create
    STATUS       current
    DESCRIPTION
        "The value of tNetworkIngressDSCPFC specifies the forwarding class (FC)
         assosicated with this DSCP value.

         There is no default value for this object. It must be set at the time 
         of row creation."
    ::= { tNetworkIngressDSCPEntry 3 }

tNetworkIngressDSCPProfile OBJECT-TYPE
    SYNTAX       TProfile
    MAX-ACCESS   read-create
    STATUS       current
    DESCRIPTION
        "The value of tNetworkIngressDSCPProfile specifies the profile of the  
         packet assosicated with this DSCP value.

         There is no default value for this object. It must be set at the time 
         of row creation."
    ::= { tNetworkIngressDSCPEntry 4 }

tNetworkIngressDSCPLastChanged OBJECT-TYPE
    SYNTAX       TimeStamp
    MAX-ACCESS   read-only
    STATUS       current
    DESCRIPTION
        "timestamp of last change to this row in tNetworkIngressDSCPTable."
    ::= { tNetworkIngressDSCPEntry 5 }

--
-- network ingress policy dot1p table
--

tNetworkIngressDot1pTable OBJECT-TYPE
    SYNTAX       SEQUENCE OF TNetworkIngressDot1pEntry
    MAX-ACCESS   not-accessible
    STATUS       current
    DESCRIPTION
        "THe value of tNetworkIngressDot1pTable contains information about a
         dot1p priority mapping for a network policy."
    ::= { tNetworkObjects 3 }

tNetworkIngressDot1pEntry OBJECT-TYPE
    SYNTAX       TNetworkIngressDot1pEntry
    MAX-ACCESS   not-accessible
    STATUS       current
    DESCRIPTION
        "Information about a dot1p map for a network policy.

         Some default entries are created by the agent for the
         default network policy (1). These cannot be deleted or
         modified. Other entries are created/deleted by user.

         There is no StorageType object, entries have a presumed
         StorageType of nonVolatile.
        "
    INDEX { tNetworkPolicyIndex, tNetworkIngressDot1pValue }
    ::= { tNetworkIngressDot1pTable 1 }

TNetworkIngressDot1pEntry ::= SEQUENCE
    {
        tNetworkIngressDot1pValue       Dot1PPriority,
        tNetworkIngressDot1pRowStatus   RowStatus,
        tNetworkIngressDot1pFC          TFCName,
        tNetworkIngressDot1pProfile     TDEProfileOrDei,
        tNetworkIngressDot1pLastChanged TimeStamp
    }

tNetworkIngressDot1pValue OBJECT-TYPE
    SYNTAX       Dot1PPriority (0..7)
    MAX-ACCESS   not-accessible
    STATUS       current
    DESCRIPTION
        "The value of tNetworkIngressDot1pValue specifies IEEE 802.1p priority
         value."
    ::= { tNetworkIngressDot1pEntry 1 }

tNetworkIngressDot1pRowStatus OBJECT-TYPE
    SYNTAX       RowStatus
    MAX-ACCESS   read-create
    STATUS       current
    DESCRIPTION
        "The value of tNetworkIngressDot1pRowStatus is used for the creation and
         deletion of dot1p entries for network ingress Qos policy."
    ::= { tNetworkIngressDot1pEntry 2 }

tNetworkIngressDot1pFC OBJECT-TYPE
    SYNTAX       TFCName
    MAX-ACCESS   read-create
    STATUS       current
    DESCRIPTION
        "The value of tNetworkIngressDot1pFC specifies the forwarding class (FC)
         assosicated with this dot1p value.

         There is no default value for this object. It must be set at the time 
         of row creation."
    ::= { tNetworkIngressDot1pEntry 3 }

tNetworkIngressDot1pProfile OBJECT-TYPE
    SYNTAX       TDEProfileOrDei
    MAX-ACCESS   read-create
    STATUS       current
    DESCRIPTION
        "The value of tNetworkIngressDot1pProfile specifies the profile of the  
         packet assosicated with this dot1p value.

         There is no default value for this object. It must be set at the time 
         of row creation."
    ::= { tNetworkIngressDot1pEntry 4 }

tNetworkIngressDot1pLastChanged OBJECT-TYPE
    SYNTAX       TimeStamp
    MAX-ACCESS   read-only
    STATUS       current
    DESCRIPTION
        "timestamp of last change to this row in tNetworkIngressDot1pTable."
    ::= { tNetworkIngressDot1pEntry 5 }

--
-- network ingress policy lspexp table
--

tNetworkIngressLSPEXPTable OBJECT-TYPE
    SYNTAX       SEQUENCE OF TNetworkIngressLSPEXPEntry
    MAX-ACCESS   not-accessible
    STATUS       current
    DESCRIPTION
        "The value of tNetworkIngressLSPEXPTable contains information about LSP
         EXP mapping for a network policy."
    ::= { tNetworkObjects 4 }

tNetworkIngressLSPEXPEntry OBJECT-TYPE
    SYNTAX       TNetworkIngressLSPEXPEntry
    MAX-ACCESS   not-accessible
    STATUS       current
    DESCRIPTION
        "Information about LSP EXP mapping for a network policy.

         Some default entries are created by the agent for the
         default network policy (1). These cannot be deleted or
         modified. Other entries are created/deleted by user.

         There is no StorageType object, entries have a presumed
         StorageType of nonVolatile."
    INDEX { tNetworkPolicyIndex, tNetworkIngressLSPEXP }
    ::= { tNetworkIngressLSPEXPTable 1 }

TNetworkIngressLSPEXPEntry ::= SEQUENCE
    {
        tNetworkIngressLSPEXP            TLspExpValue,
        tNetworkIngressLSPEXPRowStatus   RowStatus,
        tNetworkIngressLSPEXPFC          TFCName,
        tNetworkIngressLSPEXPProfile     TProfile,
        tNetworkIngressLSPEXPLastChanged TimeStamp
    }

tNetworkIngressLSPEXP OBJECT-TYPE
    SYNTAX       TLspExpValue (0..7)
    MAX-ACCESS   not-accessible
    STATUS       current
    DESCRIPTION
        "The value of tNetworkIngressLSPEXP specifies LSP EXP experimental
         bit values."
    ::= { tNetworkIngressLSPEXPEntry 1 }

tNetworkIngressLSPEXPRowStatus OBJECT-TYPE
    SYNTAX       RowStatus
    MAX-ACCESS   read-create
    STATUS       current
    DESCRIPTION
        "The value of tNetworkIngressLSPEXPRowStatus is used for the creation
         and deletion of LSP EXP entries for network ingress Qos policy."
    ::= { tNetworkIngressLSPEXPEntry 2 }

tNetworkIngressLSPEXPFC OBJECT-TYPE
    SYNTAX       TFCName
    MAX-ACCESS   read-create
    STATUS       current
    DESCRIPTION
        "The value of tNetworkIngressLSPEXPFC specifies the forwarding class
         (FC) assosicated with this LSP EXP value.

         There is no default value for this object. It must be set at the time 
         of row creation."
    ::= { tNetworkIngressLSPEXPEntry 3 }

tNetworkIngressLSPEXPProfile OBJECT-TYPE
    SYNTAX       TProfile
    MAX-ACCESS   read-create
    STATUS       current
    DESCRIPTION
        "The value of tNetworkIngressLSPEXPProfile specifies the profile of the
         packet assosicated with this LSP EXP value.

         There is no default value for this object. It must be set at the time 
         of row creation."
    ::= { tNetworkIngressLSPEXPEntry 4 }

tNetworkIngressLSPEXPLastChanged OBJECT-TYPE
    SYNTAX       TimeStamp
    MAX-ACCESS   read-only
    STATUS       current
    DESCRIPTION
        "timestamp of last change to this row in tNetworkIngressLSPEXPTable."
    ::= { tNetworkIngressLSPEXPEntry 5 }

--
-- network egress fc table
--

tNetworkEgressFCTable OBJECT-TYPE
    SYNTAX       SEQUENCE OF TNetworkEgressFCEntry
    MAX-ACCESS   not-accessible
    STATUS       current
    DESCRIPTION
        "Information about all network policies' egress FC traffic disposition."
    ::= { tNetworkObjects 7 }

tNetworkEgressFCEntry OBJECT-TYPE
    SYNTAX       TNetworkEgressFCEntry
    MAX-ACCESS   not-accessible
    STATUS       current
    DESCRIPTION
        "Information about a particular network policy's egress
         per-forwarding-class traffic disposition.

         Entries are created/deleted as an action of creating/deleting
         a row in the tNetworkPolicyTable.

         There is no StorageType object, entries have a presumed
         StorageType of nonVolatile."
    INDEX { tNetworkPolicyIndex, tNetworkEgressFCName }
    ::= { tNetworkEgressFCTable 1 }

TNetworkEgressFCEntry ::= SEQUENCE
    {
        tNetworkEgressFCName              TFCName,
        tNetworkEgressFCDSCPInProfile     TDSCPNameOrEmpty,
        tNetworkEgressFCDSCPOutProfile    TDSCPNameOrEmpty,
        tNetworkEgressFCLspExpInProfile   TLspExpValue,
        tNetworkEgressFCLspExpOutProfile  TLspExpValue,
        tNetworkEgressFCDot1pInProfile    Dot1PPriority,
        tNetworkEgressFCDot1pOutProfile   Dot1PPriority,
        tNetworkEgressFCLastChanged       TimeStamp,
        tNetworkEgressFCForceDEValue      TDEValue,
        tNetworkEgressFCDEMark            TruthValue,
        tNetworkEgressFCQGrpQueue         TEgressQueueId,
        tNetworkEgressFCQGrpPolicer       TEgrPolicerIdOrNone
    }

tNetworkEgressFCName OBJECT-TYPE
    SYNTAX       TFCName
    MAX-ACCESS   not-accessible
    STATUS       current
    DESCRIPTION
        "the name of the forwarding class (FC)."
    ::= { tNetworkEgressFCEntry 1 }

tNetworkEgressFCDSCPInProfile OBJECT-TYPE
    SYNTAX       TDSCPNameOrEmpty
    MAX-ACCESS   read-write
    STATUS       current
    DESCRIPTION
        "the DSCP to use for in-profile traffic."
    ::= { tNetworkEgressFCEntry 2 }

tNetworkEgressFCDSCPOutProfile OBJECT-TYPE
    SYNTAX       TDSCPNameOrEmpty
    MAX-ACCESS   read-write
    STATUS       current
    DESCRIPTION
        "the DSCP to use for out-of-profile traffic."
    ::= { tNetworkEgressFCEntry 3 }

tNetworkEgressFCLspExpInProfile OBJECT-TYPE
    SYNTAX       TLspExpValue
    MAX-ACCESS   read-write
    STATUS       current
    DESCRIPTION
        "the lsp-exp value to use for in-profile traffic."
    ::= { tNetworkEgressFCEntry 4 }

tNetworkEgressFCLspExpOutProfile OBJECT-TYPE
    SYNTAX       TLspExpValue
    MAX-ACCESS   read-write
    STATUS       current
    DESCRIPTION
        "the lsp-exp value to use for out-of-profile traffic."
    ::= { tNetworkEgressFCEntry 5 }

tNetworkEgressFCDot1pInProfile OBJECT-TYPE
    SYNTAX       Dot1PPriority
    MAX-ACCESS   read-write
    STATUS       current
    DESCRIPTION
        "the Dot1p to use for in-profile traffic."
    ::= { tNetworkEgressFCEntry 6 }

tNetworkEgressFCDot1pOutProfile OBJECT-TYPE
    SYNTAX       Dot1PPriority
    MAX-ACCESS   read-write
    STATUS       current
    DESCRIPTION
        "the Dot1p to use for out-of-profile traffic."
    ::= { tNetworkEgressFCEntry 7 }

tNetworkEgressFCLastChanged OBJECT-TYPE
    SYNTAX       TimeStamp
    MAX-ACCESS   read-only
    STATUS       current
    DESCRIPTION
        "timestamp of last change to this row in tNetworkEgressFCTable."
    ::= { tNetworkEgressFCEntry 8 }

tNetworkEgressFCForceDEValue OBJECT-TYPE
    SYNTAX       TDEValue
    MAX-ACCESS   read-write
    STATUS       current
    DESCRIPTION
        "The value of tNetworkEgressFCForceDEValue specifies the DE value to set
        for network egress packets in this forwarding class regardless of
        profile status of the frames.

       An inconsistentValue error is returned if this object is set to any value
       other than '-1', when tNetworkEgressFCDEMark object is set to
       'false'."
    DEFVAL { -1 }
    ::= { tNetworkEgressFCEntry 9 }

tNetworkEgressFCDEMark OBJECT-TYPE
    SYNTAX       TruthValue
    MAX-ACCESS   read-write
    STATUS       current
    DESCRIPTION
       "The value of tNetworkEgressFCDEMark specifies whether to set DE value
       in the frames of this forwarding class.

       An inconsistentValue error is returned if this object is set to 'false'
       when tNetworkEgressFCForceDEValue object is not set to '-1'."
    DEFVAL { false }
    ::= { tNetworkEgressFCEntry 10 }

tNetworkEgressFCQGrpQueue OBJECT-TYPE
    SYNTAX       TEgressQueueId
    MAX-ACCESS   read-write
    STATUS       current
    DESCRIPTION
        "tNetworkEgressFCQGrpQueue specifies the specific queue from queue-group
        TIMETRA-VRTR-MIB::vRtrIfQosQGrp to be used for packets in this
        forwarding class."
    DEFVAL { 0 }
    ::= { tNetworkEgressFCEntry 11 }

tNetworkEgressFCQGrpPolicer OBJECT-TYPE
    SYNTAX       TEgrPolicerIdOrNone
    MAX-ACCESS   read-write
    STATUS       current
    DESCRIPTION
        "The value of tNetworkEgressFCQGrpPolicer specifies the policer
         from queue-group to be used for packets in this forwarding class."
    DEFVAL { 0 }
    ::= { tNetworkEgressFCEntry 12 }

--
-- network-queue policy table
--

tNetworkQueuePolicyTable OBJECT-TYPE
    SYNTAX       SEQUENCE OF TNetworkQueuePolicyEntry
    MAX-ACCESS   not-accessible
    STATUS       current
    DESCRIPTION  "  "
    ::= { tNetworkQueueObjects 1 }

tNetworkQueuePolicyEntry OBJECT-TYPE
    SYNTAX       TNetworkQueuePolicyEntry
    MAX-ACCESS   not-accessible
    STATUS       current
    DESCRIPTION  ""
    INDEX { tNetworkQueuePolicy }
    ::= { tNetworkQueuePolicyTable 1 }

TNetworkQueuePolicyEntry ::= SEQUENCE
    {
        tNetworkQueuePolicy                         TNamedItem,
        tNetworkQueuePolicyRowStatus                RowStatus,
        tNetworkQueuePolicyDescription              TItemDescription,
        tNetworkQueuePolicyLastChanged              TimeStamp,
        tNetworkQueuePolicyEHWrrPlcy                TNamedItemOrEmpty,
        tNetworkQueuePolicyEHPktBOffst              TEgressHsmdaPerPacketOffset
    }

tNetworkQueuePolicy OBJECT-TYPE
    SYNTAX       TNamedItem
    MAX-ACCESS   not-accessible
    STATUS       current
    DESCRIPTION  ""
    ::= { tNetworkQueuePolicyEntry 1 }

tNetworkQueuePolicyRowStatus OBJECT-TYPE
    SYNTAX       RowStatus
    MAX-ACCESS   read-create
    STATUS       current
    DESCRIPTION  ""
    ::= { tNetworkQueuePolicyEntry 2 }

tNetworkQueuePolicyDescription OBJECT-TYPE
    SYNTAX       TItemDescription
    MAX-ACCESS   read-create
    STATUS       current
    DESCRIPTION  ""
    DEFVAL { ''H }
    ::= { tNetworkQueuePolicyEntry 3 }

tNetworkQueuePolicyLastChanged OBJECT-TYPE
    SYNTAX       TimeStamp
    MAX-ACCESS   read-only
    STATUS       current
    DESCRIPTION  ""
    ::= { tNetworkQueuePolicyEntry 8 }

tNetworkQueuePolicyEHWrrPlcy OBJECT-TYPE
    SYNTAX       TNamedItemOrEmpty
    MAX-ACCESS   read-create
    STATUS       current
    DESCRIPTION  
        "The value of tNetworkQueuePolicyEHWrrPlcy specifies the 
         Weighted Round Robin (WRR) policy to use on this HSMDA egress queue."
    DEFVAL { "" }
    ::= { tNetworkQueuePolicyEntry 9 }

tNetworkQueuePolicyEHPktBOffst OBJECT-TYPE
    SYNTAX       TEgressHsmdaPerPacketOffset
    MAX-ACCESS   read-create
    STATUS       current
    DESCRIPTION  
        "The value of tNetworkQueuePolicyEHPktBOffst specifies the packet byte 
         offset to use for the HSMDA egress queues. This value is used for the 
         adjustment to make to the size of each packet for HSMDA queue
         accounting."
    DEFVAL { 0 }
    ::= { tNetworkQueuePolicyEntry 10 }

--
-- network-queue policy queue table
--

tNetworkQueueTable OBJECT-TYPE
    SYNTAX       SEQUENCE OF TNetworkQueueEntry
    MAX-ACCESS   not-accessible
    STATUS       current
    DESCRIPTION  ""
    ::= { tNetworkQueueObjects 2 }

tNetworkQueueEntry OBJECT-TYPE
    SYNTAX       TNetworkQueueEntry
    MAX-ACCESS   not-accessible
    STATUS       current
    DESCRIPTION  ""
    INDEX { tNetworkQueuePolicy, tNetworkQueue }
    ::= { tNetworkQueueTable 1 }

TNetworkQueueEntry ::= SEQUENCE
    {
        tNetworkQueue                 TQueueId,
        tNetworkQueueRowStatus        RowStatus,
        tNetworkQueuePoolName         TNamedItemOrEmpty,
        tNetworkQueueParent           TNamedItemOrEmpty,
        tNetworkQueueLevel            TLevel,
        tNetworkQueueWeight           TWeight,
        tNetworkQueueCIRLevel         TLevelOrDefault,
        tNetworkQueueCIRWeight        TWeight,
        tNetworkQueueMCast            TruthValue,
        tNetworkQueueExpedite         INTEGER,
        tNetworkQueueCIR              TRatePercent,
        tNetworkQueuePIR              TPIRRatePercent,
        tNetworkQueueCBS              TBurstHundredthsOfPercent,
        tNetworkQueueMBS              TBurstHundredthsOfPercent,
        tNetworkQueueHiPrioOnly       TBurstPercentOrDefault,
        tNetworkQueueLastChanged      TimeStamp,
        tNetworkQueueUsePortParent    TruthValue,
        tNetworkQueuePortLvl          TLevel,
        tNetworkQueuePortWght         TWeight,
        tNetworkQueuePortCIRLvl       TLevelOrDefault,
        tNetworkQueuePortCIRWght      TWeight,
        tNetworkQueuePortAvgOverhead  Unsigned32,
        tNetworkQueueCIRAdaptation    TAdaptationRule,
        tNetworkQueuePIRAdaptation    TAdaptationRule
    }

tNetworkQueue OBJECT-TYPE
    SYNTAX       TQueueId (1..16)
    MAX-ACCESS   not-accessible
    STATUS       current
    DESCRIPTION
        "The queue ID is used as the secondary index to the table entry."
    ::= { tNetworkQueueEntry 1 }

tNetworkQueueRowStatus OBJECT-TYPE
    SYNTAX       RowStatus
    MAX-ACCESS   read-create
    STATUS       current
    DESCRIPTION
        "Row Status of the entry. This allows creation/deletion of rows in this
         table."
    ::= { tNetworkQueueEntry 2 }

tNetworkQueuePoolName OBJECT-TYPE
    SYNTAX       TNamedItemOrEmpty
    MAX-ACCESS   read-create
    STATUS       current
    DESCRIPTION
        "The tNetworkQueuePoolName specifies the pool that is associated
         with this network queue. If tNetworkQueuePoolName is empty, no pool
         has been associated with the queue."
    DEFVAL { ''H }
    ::= { tNetworkQueueEntry 3 }

tNetworkQueueParent OBJECT-TYPE
    SYNTAX       TNamedItemOrEmpty
    MAX-ACCESS   read-create
    STATUS       current
    DESCRIPTION
        "The scheduler to which this queue would be feeding to."
    DEFVAL { ''H }
    ::= { tNetworkQueueEntry 4 }

tNetworkQueueLevel OBJECT-TYPE
    SYNTAX       TLevel
    MAX-ACCESS   read-create
    STATUS       current
    DESCRIPTION
        "This specifies the level of priority while feeding to the parent."
    DEFVAL { 1 }
    ::= { tNetworkQueueEntry 5 }

tNetworkQueueWeight OBJECT-TYPE
    SYNTAX       TWeight
    MAX-ACCESS   read-create
    STATUS       current
    DESCRIPTION
        "The weight that needs to be used by the scheduler to which this queue
         would be feeding to."
    DEFVAL { 1 }
    ::= { tNetworkQueueEntry 6 }

tNetworkQueueCIRLevel OBJECT-TYPE
    SYNTAX       TLevelOrDefault
    MAX-ACCESS   read-create
    STATUS       current
    DESCRIPTION
        "This specifies the level of priority while feeding to the parent.
         The level '0' means treat all offered load for this queue as for
         the above CIR traffic."
    DEFVAL { 0 }
    ::= { tNetworkQueueEntry 7 }

tNetworkQueueCIRWeight OBJECT-TYPE
    SYNTAX       TWeight
    MAX-ACCESS   read-create
    STATUS       current
    DESCRIPTION
        "The weight that needs to be used until the committed rate by the
         scheduler to which this queue would be feeding to."
    DEFVAL { 1 }
    ::= { tNetworkQueueEntry 8 }

tNetworkQueueMCast OBJECT-TYPE
    SYNTAX       TruthValue
    MAX-ACCESS   read-create
    STATUS       current
    DESCRIPTION
        "This object specifies if this is a multicast queue or not."
    DEFVAL { false }
    ::= { tNetworkQueueEntry 9 }

tNetworkQueueExpedite OBJECT-TYPE
    SYNTAX       INTEGER {
                     expedited     (1),
                     auto-expedited(2),
                     non-expedited (3)
                 }
    MAX-ACCESS   read-create
    STATUS       current
    DESCRIPTION
        "tNetworkQueueExpedite specifies the priority that this queue should
         be assigned by the hardware level schedulers.

         The value 'auto-expedited' implies that this attribute should be
         dynamically updated by looking at the forwarding classes mapping
         into this queue. In such a case the queue is treated as
         'non-expedited' if there is even a single non-expedited forwarding
         class using this queue.

         This attribute is associated with the queue at the time of creation
         and cannot be modified thereafter."
    DEFVAL { auto-expedited }
    ::= { tNetworkQueueEntry 10 }

tNetworkQueueCIR OBJECT-TYPE
    SYNTAX       TRatePercent
    MAX-ACCESS   read-create
    STATUS       current
    DESCRIPTION
        "The percentage of max rate allowed."
    DEFVAL { 0 }
    ::= { tNetworkQueueEntry 11 }

tNetworkQueuePIR OBJECT-TYPE
    SYNTAX       TPIRRatePercent
    MAX-ACCESS   read-create
    STATUS       current
    DESCRIPTION
        "The percentage of max rate allowed."
    DEFVAL { 100 }
    ::= { tNetworkQueueEntry 12 }

tNetworkQueueCBS OBJECT-TYPE
    SYNTAX       TBurstHundredthsOfPercent
    UNITS        "Hundredths of a percent"
    MAX-ACCESS   read-create
    STATUS       current
    DESCRIPTION
        "The percentage of reserved buffer space for the queue, 
         defined to two decimal places."
    DEFVAL { 100 }
    ::= { tNetworkQueueEntry 13 }

tNetworkQueueMBS OBJECT-TYPE
    SYNTAX       TBurstHundredthsOfPercent
    UNITS        "Hundredths of a percent"
    MAX-ACCESS   read-create
    STATUS       current
    DESCRIPTION
        "The percentage of reserved buffer space for the queue, 
         defined to two decimal places."
    DEFVAL { 10000 }
    ::= { tNetworkQueueEntry 14 }

tNetworkQueueHiPrioOnly OBJECT-TYPE
    SYNTAX       TBurstPercentOrDefault
    MAX-ACCESS   read-create
    STATUS       current
    DESCRIPTION
        "The percentage of buffer space for the queue, used
         exclusively by high priority packets."
    DEFVAL { -1 }
    ::= { tNetworkQueueEntry 15 }

tNetworkQueueLastChanged OBJECT-TYPE
    SYNTAX       TimeStamp
    MAX-ACCESS   read-only
    STATUS       current
    DESCRIPTION
        "The value of the object tNetworkQueueLastChanged indicates the 
         timestamp of last change to this row in tNetworkQueueTable."
    ::= { tNetworkQueueEntry 16 }

tNetworkQueueUsePortParent  OBJECT-TYPE
    SYNTAX      TruthValue
    MAX-ACCESS  read-create
    STATUS      current
    DESCRIPTION
        "The value of the object tNetworkQueueUsePortParent specifies
         whether this queue is parented by a port-level scheduler. When
         the value is 'true', this network queue is parented by a 
         port-level scheduler."
    DEFVAL      { false }
    ::= { tNetworkQueueEntry 17 }

tNetworkQueuePortLvl        OBJECT-TYPE
    SYNTAX       TLevel
    MAX-ACCESS  read-create
    STATUS      current
    DESCRIPTION
        "The value of the object tNetworkQueuePortLvl specifies the
         port priority this queue will use to receive bandwidth from
         the port-level scheduler for its above-cir offered load."
    DEFVAL      { 1 }
    ::= { tNetworkQueueEntry 18 }

tNetworkQueuePortWght       OBJECT-TYPE
    SYNTAX      TWeight
    MAX-ACCESS  read-create
    STATUS      current
    DESCRIPTION
        "The value of the object tNetworkQueuePortWght specifies the
         weight this queue will use to receive bandwidth from the
         port-level scheduler for its above-cir offered load."
    DEFVAL      { 1 }
    ::= { tNetworkQueueEntry 19 }

tNetworkQueuePortCIRLvl        OBJECT-TYPE
    SYNTAX      TLevelOrDefault
    MAX-ACCESS  read-create
    STATUS      current
    DESCRIPTION
        "The value of the object tNetworkQueuePortCIRLvl specifies the
         port priority this queue will use to receive bandwidth from
         the port-level scheduler for its within-cir offered load."
    DEFVAL      { 0 }
    ::= { tNetworkQueueEntry 20 }

tNetworkQueuePortCIRWght       OBJECT-TYPE
    SYNTAX      TWeight
    MAX-ACCESS  read-create
    STATUS      current
    DESCRIPTION
        "The value of the object tNetworkQueuePortCIRWght specifies the
         weight this queue will use to receive bandwidth from the
         port-level scheduler for its within-cir offered load."
    DEFVAL      { 0 }
    ::= { tNetworkQueueEntry 21 }

tNetworkQueuePortAvgOverhead    OBJECT-TYPE
    SYNTAX      Unsigned32 (0..10000)
    UNITS       "Hundredths of a percent"
    MAX-ACCESS  read-create
    STATUS      current
    DESCRIPTION
        "The value of tNetworkQueuePortAvgOverhead specifies the 
         encapsulation overhead, in hundredths of a percent,  used to 
         translate packet-based rate to frame-based rate and vice versa."
    DEFVAL      { 0 }
    ::= { tNetworkQueueEntry 22 }

tNetworkQueueCIRAdaptation       OBJECT-TYPE
    SYNTAX      TAdaptationRule
    MAX-ACCESS  read-create
    STATUS      current
    DESCRIPTION
        "The value of tNetworkQueueCIRAdaptation specifies the adaptation rule
         to be used while computing the operational CIR value. The adaptation
         rule specifies the rules to compute the operational value while
         maintaining the minimum offset."
    DEFVAL      { closest }
    ::= { tNetworkQueueEntry 23 }

tNetworkQueuePIRAdaptation       OBJECT-TYPE
    SYNTAX      TAdaptationRule
    MAX-ACCESS  read-create
    STATUS      current
    DESCRIPTION
        "The value of tNetworkQueuePIRAdaptation specifies the adaptation rule
         to be used while computing the operational PIR value. The adaptation
         rule specifies the rules to compute the operational value while
         maintaining the minimum offset."
    DEFVAL      { closest }
    ::= { tNetworkQueueEntry 24 }

--
-- network-queue policy fc table
--

tNetworkQueueFCTable OBJECT-TYPE
    SYNTAX       SEQUENCE OF TNetworkQueueFCEntry
    MAX-ACCESS   not-accessible
    STATUS       current
    DESCRIPTION  ""
    ::= { tNetworkQueueObjects 3 }

tNetworkQueueFCEntry OBJECT-TYPE
    SYNTAX       TNetworkQueueFCEntry
    MAX-ACCESS   not-accessible
    STATUS       current
    DESCRIPTION  ""
    INDEX { tNetworkQueuePolicy, tNetworkQueueFCName }
    ::= { tNetworkQueueFCTable 1 }

TNetworkQueueFCEntry ::= SEQUENCE
    {
        tNetworkQueueFCName          TFCName,
        tNetworkQueueFCRowStatus     RowStatus,
        tNetworkQueueFC              TQueueId,
        tNetworkQueueFCMCast         TQueueId,
        tNetworkQueueFCLastChanged   TimeStamp,
        tNetworkQueueFCEgrHsmdaQueue TQueueId
    }

tNetworkQueueFCName OBJECT-TYPE
    SYNTAX       TFCName
    MAX-ACCESS   not-accessible
    STATUS       current
    DESCRIPTION
        "Forwarding class name."
    ::= { tNetworkQueueFCEntry 1 }

tNetworkQueueFCRowStatus OBJECT-TYPE
    SYNTAX       RowStatus
    MAX-ACCESS   read-create
    STATUS       current
    DESCRIPTION
        "Row Status for this queue."
    ::= { tNetworkQueueFCEntry 2 }

tNetworkQueueFC OBJECT-TYPE
    SYNTAX       TQueueId (1..16)
    MAX-ACCESS   read-create
    STATUS       current
    DESCRIPTION
        "The specific queue to be used for packets in this forwarding class."
    DEFVAL { 1 }
    ::= { tNetworkQueueFCEntry 3 }

tNetworkQueueFCMCast OBJECT-TYPE
    SYNTAX       TQueueId (1..16)
    MAX-ACCESS   read-create
    STATUS       current
    DESCRIPTION
        "The specific multicast queue to be used for packets in this forwarding
         class. The queue is used only for specific entities and will be
         ignored wherever it is irrelevant."
    DEFVAL { 9 }
    ::= { tNetworkQueueFCEntry 4 }

tNetworkQueueFCLastChanged OBJECT-TYPE
    SYNTAX       TimeStamp
    MAX-ACCESS   read-only
    STATUS       current
    DESCRIPTION
        "timestamp of last change to this row in tNetworkQueueFCTable."
    ::= { tNetworkQueueFCEntry 7 }

tNetworkQueueFCEgrHsmdaQueue OBJECT-TYPE
    SYNTAX       TQueueId (1..8)
    MAX-ACCESS   read-create
    STATUS       current
    DESCRIPTION
        "The value of tNetworkQueueFCEgrHsmdaQueue specifies the egress hsmda 
         queue to be used for packets in this forwarding class. This is only 
         applicable on supported hsmda ports."
    ::= { tNetworkQueueFCEntry 8 }

--
--  Network egress queue HSMDA table
--

tNetworkEgrHsmdaQueueTblLastChgd      OBJECT-TYPE
    SYNTAX       TimeStamp
    MAX-ACCESS   read-only
    STATUS       current
    DESCRIPTION
        "The value of tNetworkEgrHsmdaQueueTblLastChgd indicates the timestamp 
         of last change to this row in tNetworkEgrHsmdaQueueTable."
    ::= { tQosTimeStampObjects 94 }

tNetworkEgrHsmdaQueueTable       OBJECT-TYPE
    SYNTAX      SEQUENCE OF TNetworkEgrHsmdaQueueEntry
    MAX-ACCESS  not-accessible
    STATUS      current
    DESCRIPTION
        "The tNetworkEgrHsmdaQueueTable contains the information about all
         network egress policies on HSMDA queues. Entries in this table are
         created whenever a network queue policy is created in 
         tNetworkQueuePolicyEntry."
    ::= { tNetworkQueueObjects 4 }

tNetworkEgrHsmdaQueueEntry       OBJECT-TYPE
    SYNTAX      TNetworkEgrHsmdaQueueEntry
    MAX-ACCESS  not-accessible
    STATUS      current
    DESCRIPTION
        "Each entry in tNetworkEgrHsmdaQueueEntry represents the information 
         about a particular HSMDA queue for a network egress policy specified by
         tNetworkEgrHsmdaQueue."
    INDEX { tNetworkQueuePolicy, tNetworkEgrHsmdaQueue }
    ::= { tNetworkEgrHsmdaQueueTable 1 }

TNetworkEgrHsmdaQueueEntry ::= SEQUENCE
    {
        tNetworkEgrHsmdaQueue                   TEgressHsmdaQueueId,
        tNetworkEgrHsmdaQueuePIRPercent         Unsigned32,
        tNetworkEgrHsmdaQueuePIRAdaptn          TAdaptationRule,
        tNetworkEgrHsmdaQueueWrrWeight          THsmdaWrrWeight,
        tNetworkEgrHsmdaQueueMBS                THSMDABurstSizeBytes,
        tNetworkEgrHsmdaQueueSlopePolicy        TNamedItem,
        tNetworkEgrHsmdaQueueLastChanged        TimeStamp,
        tNetworkEgrHsmdaQueueBurstLimit         THSMDAQueueBurstLimit
    }

tNetworkEgrHsmdaQueue OBJECT-TYPE
    SYNTAX      TEgressHsmdaQueueId (1..8)
    MAX-ACCESS  not-accessible
    STATUS      current
    DESCRIPTION
        "The value of tNetworkEgrHsmdaQueue indicates the HSMDA queue ID 
         used as the secondary index to the table entry."
    ::= { tNetworkEgrHsmdaQueueEntry 1 }

tNetworkEgrHsmdaQueuePIRPercent OBJECT-TYPE
    SYNTAX       Unsigned32 (1..10000)
    UNITS        "hundredths of a percent"
    MAX-ACCESS   read-write
    STATUS       current
    DESCRIPTION
        "The value of tNetworkEgrHsmdaQueuePIRPercent specifies the queue's PIR
         expressed as a percentage of port line rate."
    DEFVAL { 10000 }
    ::= { tNetworkEgrHsmdaQueueEntry 2 }

tNetworkEgrHsmdaQueuePIRAdaptn OBJECT-TYPE
    SYNTAX      TAdaptationRule
    MAX-ACCESS  read-write
    STATUS      current
    DESCRIPTION
        "The value of tNetworkEgrHsmdaQueuePIRAdaptn specifies the adaptation 
         rule to be used while computing the operational PIR value. The 
         adaptation rule specifies the rules to compute the operational values 
         while maintaining minimum offset."
    DEFVAL      { closest }
    ::= { tNetworkEgrHsmdaQueueEntry 3 }

tNetworkEgrHsmdaQueueWrrWeight OBJECT-TYPE
    SYNTAX      THsmdaWrrWeight
    MAX-ACCESS  read-write
    STATUS      current
    DESCRIPTION
        "The value of tNetworkEgrHsmdaQueueWrrWeight specifies the weight with 
         which this queue should parent into the HSMDA scheduler, provided it is
         not superseded by the Weighted Round Robin (WRR) policy. The weight of
         each queue determines how much bandwidth that queue gets out of the 
         total rate for the scheduling class."
    DEFVAL      { 1 }
    ::= { tNetworkEgrHsmdaQueueEntry 4 }

tNetworkEgrHsmdaQueueMBS OBJECT-TYPE
    SYNTAX      THSMDABurstSizeBytes
    UNITS       "bytes"
    MAX-ACCESS  read-write
    STATUS      current
    DESCRIPTION
        "The value of tNetworkEgrHsmdaQueueMBS specifies the maximum amount of 
         buffer space, in bytes, allowed for this network egress HSMDA queue."
    DEFVAL      { -1 }
    ::= { tNetworkEgrHsmdaQueueEntry 5 }

tNetworkEgrHsmdaQueueSlopePolicy OBJECT-TYPE
    SYNTAX      TNamedItem
    MAX-ACCESS  read-write
    STATUS      current
    DESCRIPTION
        "The value of tNetworkEgrHsmdaQueueSlopePolicy specifies the slope
         policy on this network egress HSMDA queue. The slope policy defines the
         WRED slope behavior for this queue."
    DEFVAL      { "default" }
    ::= { tNetworkEgrHsmdaQueueEntry 6 }

tNetworkEgrHsmdaQueueLastChanged  OBJECT-TYPE
    SYNTAX       TimeStamp
    MAX-ACCESS   read-only
    STATUS       current
    DESCRIPTION  
        "The value of tNetworkEgrHsmdaQueueLastChanged indicates the sysUpTime 
         for the last change to this row."
    ::= { tNetworkEgrHsmdaQueueEntry 7 }

tNetworkEgrHsmdaQueueBurstLimit OBJECT-TYPE
    SYNTAX      THSMDAQueueBurstLimit
    UNITS       "bytes"
    MAX-ACCESS  read-write
    STATUS      current
    DESCRIPTION
        "The value of tNetworkEgrHsmdaQueueBurstLimit specifies the explicit 
         shaping burst size of the queue."
    DEFVAL      { -1 }
    ::= { tNetworkEgrHsmdaQueueEntry 8 }
--
-- shared queue policy table
--

tSharedQueuePolicyTable OBJECT-TYPE
    SYNTAX       SEQUENCE OF TSharedQueuePolicyEntry
    MAX-ACCESS   not-accessible
    STATUS       current
    DESCRIPTION
        "Defines the Nokia SROS series Shared Queue Policy Table
         for providing, via SNMP, the capability of defining the queue
         policies.

         tSharedQueuePolicyTable holds a list of all shared queue
         policies in the managed system. Shared queue policies should
         exist in this table before being referenced elsewhere.

         There is a default queue policy 'default' created by the
         agent and can not be deleted."
    ::= { tSharedQueueObjects 1 }

tSharedQueuePolicyEntry OBJECT-TYPE
    SYNTAX       TSharedQueuePolicyEntry
    MAX-ACCESS   not-accessible
    STATUS       current
    DESCRIPTION
        "Defines an entry in the tSharedQueuePolicyTable. Entries are
         created and deleted in this table by SNMP sets to
         tSharedQueuePolicyRowStatus."
    INDEX { tSharedQueuePolicy }
    ::= { tSharedQueuePolicyTable 1 }

TSharedQueuePolicyEntry ::= SEQUENCE
    {
        tSharedQueuePolicy                TNamedItem,
        tSharedQueuePolicyRowStatus       RowStatus,
        tSharedQueuePolicyLastChanged     TimeStamp,
        tSharedQueuePolicyDescription     TItemDescription
    }

tSharedQueuePolicy OBJECT-TYPE
    SYNTAX       TNamedItem
    MAX-ACCESS   not-accessible
    STATUS       current
    DESCRIPTION
        "tSharedQueuePolicy serves as an index and uniquely identifies
         a queue policy in the managed system."
    ::= { tSharedQueuePolicyEntry 1 }

tSharedQueuePolicyRowStatus OBJECT-TYPE
    SYNTAX       RowStatus
    MAX-ACCESS   read-create
    STATUS       current
    DESCRIPTION
        "tSharedQueuePolicyRowStatus allows entries to be created and
         deleted in the tSharedQueuePolicyTable. The deletion of an
         entry in this table will fail if the action is performed on the
         default policy or the policy is being used within the system."
    REFERENCE
        "See definition of RowStatus in RFC 2579, 'Textual Conventions
         for SMIv2.'"
    ::= { tSharedQueuePolicyEntry 2 }

tSharedQueuePolicyLastChanged OBJECT-TYPE
    SYNTAX       TimeStamp
    MAX-ACCESS   read-only
    STATUS       current
    DESCRIPTION
        "tSharedQueuePolicyLastChanged indicates the value of sysUpTime
         when the queue policy entry was last modified."
    ::= { tSharedQueuePolicyEntry 3 }

tSharedQueuePolicyDescription OBJECT-TYPE
    SYNTAX       TItemDescription
    MAX-ACCESS   read-create
    STATUS       current
    DESCRIPTION
        "tSharedQueuePolicyDescription specifies the user provided
         description string for this queue policy entry. It can consist
         of only the printable, seven-bit ASCII characters."
    DEFVAL { ''H }
    ::= { tSharedQueuePolicyEntry 4 }

--
-- queue policy queue table
--

tSharedQueueTable OBJECT-TYPE
    SYNTAX       SEQUENCE OF TSharedQueueEntry
    MAX-ACCESS   not-accessible
    STATUS       current
    DESCRIPTION
        "Defines the Nokia SROS series Shared Queue Table for
         providing, via SNMP, the capability of defining the queues for
         the shared queue policies existing in the tSharedQueuePolicyTable.

         tSharedQueueTable holds a list of all the shared queues in the
         managed system defined for the queue policies. Queues should exist
         in this table before being referenced by the forwarding class
         mappings within the queue policy as defined in the
         tSharedQueueFCTable.

         There is a default queue with the queue identifier '1' which
         gets created automatically when a new queue policy is created."
    ::= { tSharedQueueObjects 2 }

tSharedQueueEntry OBJECT-TYPE
    SYNTAX       TSharedQueueEntry
    MAX-ACCESS   not-accessible
    STATUS       current
    DESCRIPTION
        "Defines an entry in the tSharedQueueTable.

         Entries are created/deleted in this table by SNMP sets to
         tSharedQueueRowStatus.

         An exception to this rule is the default queue. The default queue
         is created/deleted as a result of the creation/deletion of a new
         queue policy in the tSharedQueuePolicyTable."
    INDEX { tSharedQueuePolicy, tSharedQueueId }
    ::= { tSharedQueueTable 1 }

TSharedQueueEntry ::= SEQUENCE
    {
        tSharedQueueId               TQueueId,
        tSharedQueueRowStatus        RowStatus,
        tSharedQueueLastChanged      TimeStamp, 
        tSharedQueuePoolName         TNamedItemOrEmpty,
        tSharedQueueParent           TNamedItemOrEmpty,
        tSharedQueueLevel            TLevel,
        tSharedQueueWeight           TWeight,
        tSharedQueueCIRLevel         TLevelOrDefault,
        tSharedQueueCIRWeight        TWeight,
        tSharedQueueExpedite         INTEGER,
        tSharedQueueCIR              TRatePercent,
        tSharedQueuePIR              TPIRRatePercent,
        tSharedQueueCBS              TBurstPercent,
        tSharedQueueMBS              TBurstPercent,
        tSharedQueueHiPrioOnly       TBurstPercentOrDefault,
        tSharedQueueIsMultipoint     TruthValue
    }

tSharedQueueId OBJECT-TYPE
    SYNTAX       TQueueId (1..32)
    MAX-ACCESS   not-accessible
    STATUS       current
    DESCRIPTION
        "tSharedQueueId serves as the secondary index. When used in
         conjunction with tSharedQueuePolicy, it uniquely identifies
         a shared queue in the managed system."
    ::= { tSharedQueueEntry 1 }

tSharedQueueRowStatus OBJECT-TYPE
    SYNTAX       RowStatus
    MAX-ACCESS   read-create
    STATUS       current
    DESCRIPTION
        "tSharedQueueRowStatus allows entries to be created and deleted
         in the tSharedQueueTable. The deletion of an entry in this table
         will fail if the action is performed on the default queue or if
         the queue is being referenced by a forwarding class mapping in
         the queue policy."
    REFERENCE
        "See definition of RowStatus in RFC 2579, 'Textual Conventions for
         SMIv2.'"
    ::= { tSharedQueueEntry 2 }

tSharedQueueLastChanged OBJECT-TYPE
    SYNTAX       TimeStamp
    MAX-ACCESS   read-only
    STATUS       current
    DESCRIPTION
        "tSharedQueueLastChanged indicates the value of sysUpTime when
         the queue entry was last modified."
    ::= { tSharedQueueEntry 3 }

tSharedQueuePoolName OBJECT-TYPE
    SYNTAX       TNamedItemOrEmpty
    MAX-ACCESS   read-create
    STATUS       current
    DESCRIPTION
        "tSharedQueuePoolName specifies the pool from which the queue
         should be allocating its buffer. By default it will share the
         default pool being used by the entity where the queue is
         instantiated."
    DEFVAL { ''H }
    ::= { tSharedQueueEntry 4 }

tSharedQueueParent OBJECT-TYPE
    SYNTAX       TNamedItemOrEmpty
    MAX-ACCESS   read-create
    STATUS       current
    DESCRIPTION
        "tSharedQueueParent specifies the scheduler to which this queue
         should be feeding into. By default there would be no parent for
         the queue and it will be controlled by the entity where the
         queue is instantiated."
    DEFVAL { ''H }
    ::= { tSharedQueueEntry 5 }

tSharedQueueLevel OBJECT-TYPE
    SYNTAX       TLevel
    MAX-ACCESS   read-create
    STATUS       current
    DESCRIPTION
        "tSharedQueueLevel specifies the level of priority to be used
         by the parent entity to compute the priority of this queue
         when the traffic is exceeding the committed rate."
    DEFVAL { 1 }
    ::= { tSharedQueueEntry 6 }

tSharedQueueWeight OBJECT-TYPE
    SYNTAX       TWeight
    MAX-ACCESS   read-create
    STATUS       current
    DESCRIPTION
        "tSharedQueueWeight specifies the weight that this queue should
         be assigned by the parent among all the entities feeding into
         the parent with the same level when the traffic is exceeding the
         committed rate."
    DEFVAL { 1 }
    ::= { tSharedQueueEntry 7 }

tSharedQueueCIRLevel OBJECT-TYPE
    SYNTAX       TLevelOrDefault
    MAX-ACCESS   read-create
    STATUS       current
    DESCRIPTION
        "tSharedQueueCIRLevel specifies the level of priority to be used
         by the parent entity to compute the priority of this queue when
         the traffic is conforming to the committed rate.

         The level '0' means treat all offered load for this queue same
         as the load which is exceeding the committed rate."
    DEFVAL { 0 }
    ::= { tSharedQueueEntry 8 }

tSharedQueueCIRWeight OBJECT-TYPE
    SYNTAX       TWeight
    MAX-ACCESS   read-create
    STATUS       current
    DESCRIPTION
        "tSharedQueueCIRWeight specifies the weight that this queue should
         be assigned by the parent among all the entities feeding into the
         parent with the same level when the traffic is conforming to the
         committed rate."
    DEFVAL { 1 }
    ::= { tSharedQueueEntry 9 }

tSharedQueueExpedite OBJECT-TYPE
    SYNTAX       INTEGER {
                     expedited     (1),
                     auto-expedited(2),
                     non-expedited (3)
                 }
    MAX-ACCESS   read-create
    STATUS       current
    DESCRIPTION
        "tSharedQueueExpedite specifies the priority that this queue should
         be assigned by the hardware level schedulers.

         The value 'auto-expedited' implies that this attribute should be
         dynamically updated by looking at the forwarding classes mapping
         into this queue. In such a case the queue is treated as
         'non-expedited' if there is even a single non-expedited forwarding
         class using this queue."
    DEFVAL { auto-expedited }
    ::= { tSharedQueueEntry 10 }

tSharedQueueCIR OBJECT-TYPE
    SYNTAX       TRatePercent
    MAX-ACCESS   read-create
    STATUS       current
    DESCRIPTION
        "tSharedQueueCIR specifies the committed rate as a percentage of
         maximum rate for this queue."
    DEFVAL { 0 }
    ::= { tSharedQueueEntry 11 }

tSharedQueuePIR OBJECT-TYPE
    SYNTAX       TPIRRatePercent
    MAX-ACCESS   read-create
    STATUS       current
    DESCRIPTION
        "tSharedQueuePIR specifies the peak rate as a percentage of
         maximum rate for this queue."
    DEFVAL { 100 }
    ::= { tSharedQueueEntry 12 }

tSharedQueueCBS OBJECT-TYPE
    SYNTAX       TBurstPercent
    MAX-ACCESS   read-create
    STATUS       current
    DESCRIPTION
        "tSharedQueueCBS specifies the committed burst size as a percentage
         of maximum reserved buffer space for the queue."
    DEFVAL { 0 }
    ::= { tSharedQueueEntry 13 }

tSharedQueueMBS OBJECT-TYPE
    SYNTAX       TBurstPercent
    MAX-ACCESS   read-create
    STATUS       current
    DESCRIPTION
        "tSharedQueueMBS specifies the maximum burst size as a percentage
         of maximum reserved buffer space for the queue."
    DEFVAL { 100 }
    ::= { tSharedQueueEntry 14 }

tSharedQueueHiPrioOnly OBJECT-TYPE
    SYNTAX       TBurstPercentOrDefault
    MAX-ACCESS   read-create
    STATUS       current
    DESCRIPTION
        "tSharedQueueHiPrioOnly specifies the percentage of buffer space
         to be exclusively by high priority packets as a percentage of
         maximum reserved buffer space for the queue."
    DEFVAL { -1 }
    ::= { tSharedQueueEntry 15 }

tSharedQueueIsMultipoint        OBJECT-TYPE
    SYNTAX      TruthValue
    MAX-ACCESS  read-create
    STATUS      current
    DESCRIPTION
        "The value of tSharedQueueIsMultipoint specifies whether this 
         shared queue is a multipoint-shared queue. 
         
         This object can only be modified at row creation time; any attempt to 
         set it after creation is silently ignored."
    DEFVAL { false }
    ::= { tSharedQueueEntry 16 }

--
-- queue policy fc table
--

tSharedQueueFCTable OBJECT-TYPE
    SYNTAX       SEQUENCE OF TSharedQueueFCEntry
    MAX-ACCESS   not-accessible
    STATUS       current
    DESCRIPTION
        "Defines the Nokia SROS series forwarding class to
         shared queue mapping table for providing, via SNMP, the
         capability of defining the forwarding class to shared queue
         mapping for the queue policies existing in the
         tSharedQueuePolicyTable.

         tSharedQueueFCTable holds a list of forwarding class to
         queue mappings managed system defined for the queue policies.
         The forwarding classes which are not existing in this table
         should use the default shared queue for this policy."
    ::= { tSharedQueueObjects 3 }

tSharedQueueFCEntry OBJECT-TYPE
    SYNTAX       TSharedQueueFCEntry
    MAX-ACCESS   not-accessible
    STATUS       current
    DESCRIPTION
        "Defines an entry in the tSharedQueueFCTable.

         Entries are created/deleted in this table by SNMP sets to
         tSharedQueueFCRowStatus."
    INDEX { tSharedQueuePolicy, tSharedQueueFCName }
    ::= { tSharedQueueFCTable 1 }

TSharedQueueFCEntry ::= SEQUENCE
    {
        tSharedQueueFCName          TFCName,
        tSharedQueueFCRowStatus     RowStatus,
        tSharedQueueFCLastChanged   TimeStamp,
        tSharedQueueFCQueue         TQueueId,
        tSharedQueueFCMCastQueue    TQueueId,
        tSharedQueueFCBCastQueue    TQueueId,
        tSharedQueueFCUnknownQueue  TQueueId
    }

tSharedQueueFCName OBJECT-TYPE
    SYNTAX       TFCName
    MAX-ACCESS   not-accessible
    STATUS       current
    DESCRIPTION
        "tSharedQueueFCName serves as the secondary index. When used in
         conjunction with tSharedQueuePolicy, it uniquely identifies a
         forwarding class to queue mapping in the managed system."
    ::= { tSharedQueueFCEntry 1 }

tSharedQueueFCRowStatus OBJECT-TYPE
    SYNTAX       RowStatus
    MAX-ACCESS   read-create
    STATUS       current
    DESCRIPTION
        "tSharedQueueFCRowStatus allows entries to be created and
         deleted in the tSharedQueueFCTable. Deletion of an entry from
         this table will cause the forwarding class to use the default
         mapping."
    REFERENCE
        "See definition of RowStatus in RFC 2579, 'Textual Conventions
         for SMIv2.'"
    ::= { tSharedQueueFCEntry 2 }

tSharedQueueFCLastChanged OBJECT-TYPE
    SYNTAX       TimeStamp
    MAX-ACCESS   read-only
    STATUS       current
    DESCRIPTION
        "tSharedQueueFCLastChanged indicates the value of sysUpTime
         when the forwarding class to queue mapping entry was last
         modified."
    ::= { tSharedQueueFCEntry 3 }

tSharedQueueFCQueue OBJECT-TYPE
    SYNTAX       TQueueId (1..8)
    MAX-ACCESS   read-create
    STATUS       current
    DESCRIPTION
        "tSharedQueueFCQueue specifies the logical queue that the
         traffic classified into this forwarding class should use."
    DEFVAL { 1 }
    ::= { tSharedQueueFCEntry 4 }

tSharedQueueFCMCastQueue OBJECT-TYPE
    SYNTAX       TQueueId (0 | 9..32)
    MAX-ACCESS   read-create
    STATUS       current
    DESCRIPTION
        "The value of tSharedQueueFCMCastQueue specifies the logical 
         queue that mutlticast traffic classified into this forwarding 
         class should use."
    DEFVAL { 9 }
    ::= { tSharedQueueFCEntry 5 }

tSharedQueueFCBCastQueue OBJECT-TYPE
    SYNTAX       TQueueId (0 | 9..32)
    MAX-ACCESS   read-create
    STATUS       current
    DESCRIPTION
        "The value of tSharedQueueFCBCastQueue specifies the logical 
         queue that broadscast traffic classified into this forwarding 
         class should use."
    DEFVAL { 17 }
    ::= { tSharedQueueFCEntry 6 }

tSharedQueueFCUnknownQueue OBJECT-TYPE
    SYNTAX       TQueueId (0 | 9..32)
    MAX-ACCESS   read-create
    STATUS       current
    DESCRIPTION
        "The value of tSharedQueueFCUnknownQueue specifies the logical 
         queue that unknown traffic classified into this forwarding 
         class should use."
    DEFVAL { 25 }
    ::= { tSharedQueueFCEntry 7 }

--
-- ingress queue group table
--

tQosIngQGroupTableLastChanged OBJECT-TYPE
    SYNTAX       TimeStamp
    MAX-ACCESS   read-only
    STATUS       current
    DESCRIPTION
        "tQosIngQGroupTableLastChanged indicates the timestamp of last change
        to the tQosIngQGroupTable."
    ::= { tQosTimeStampObjects 6 }

tQosIngQGroupTable OBJECT-TYPE
    SYNTAX       SEQUENCE OF TQosIngQGroupEntry
    MAX-ACCESS   not-accessible
    STATUS       current
    DESCRIPTION
        "tQosIngQGroupTable defines Ingress Queue Group Table for providing,
         via SNMP, the capability of defining the queue groups for the queues
         existing in the tQosIngQueueTable.

         tQosIngQGroupTable holds a list of all the queue-groups in
         the managed system defined. Queue-groups should exist
         in this table before being referenced by the forwarding class
         mappings within the queue policy as defined in the
         tSapIngressFCTable."
    ::= { tSharedQueueObjects 4 }

tQosIngQGroupEntry OBJECT-TYPE
    SYNTAX       TQosIngQGroupEntry
    MAX-ACCESS   not-accessible
    STATUS       current
    DESCRIPTION
        "tQosIngQGroupEntry defines an entry in the tQosIngQGroupTable.

         Entries are created/deleted in this table by SNMP sets to
         tQosIngQGroupRowStatus."
    INDEX { tQosIngQGroupName }
    ::= { tQosIngQGroupTable 1 }

TQosIngQGroupEntry ::= SEQUENCE
    {
        tQosIngQGroupName             TNamedItem,
        tQosIngQGroupRowStatus        RowStatus,
        tQosIngQGroupLastChanged      TimeStamp,
        tQosIngQGroupDescr            TItemDescription
    }

tQosIngQGroupName OBJECT-TYPE
    SYNTAX       TNamedItem
    MAX-ACCESS   not-accessible
    STATUS       current
    DESCRIPTION
        "tQosIngQGroupName defines the Ingress Queue Group name.
         It uniquely identifies an ingress queue group in the managed
         system."
    ::= { tQosIngQGroupEntry 1 }

tQosIngQGroupRowStatus OBJECT-TYPE
    SYNTAX       RowStatus
    MAX-ACCESS   read-create
    STATUS       current
    DESCRIPTION
        "tQosIngQGroupRowStatus allows entries to be created and deleted
         in the tQosIngQGroupTable. The deletion of an entry in this table
         will fail if the queue is being referenced by a forwarding class
         mapping in the queue policy."
    REFERENCE
        "See definition of RowStatus in RFC 2579, 'Textual Conventions for
         SMIv2.'"
    ::= { tQosIngQGroupEntry 2 }

tQosIngQGroupLastChanged OBJECT-TYPE
    SYNTAX       TimeStamp
    MAX-ACCESS   read-only
    STATUS       current
    DESCRIPTION
        "tQosIngQGroupLastChanged indicates the value of sysUpTime when
         the queue entry was last modified."
    ::= { tQosIngQGroupEntry 3 }

tQosIngQGroupDescr OBJECT-TYPE
    SYNTAX       TItemDescription
    MAX-ACCESS   read-create
    STATUS       current
    DESCRIPTION
        "tQosIngQGroupDescr specifies the description of the queue-group."
    DEFVAL { ''H }
    ::= { tQosIngQGroupEntry 4 }


--
-- ingress queue table
--

tQosIngQTableLastChanged OBJECT-TYPE
    SYNTAX       TimeStamp
    MAX-ACCESS   read-only
    STATUS       current
    DESCRIPTION
        "tQosIngQTableLastChanged indicates the timestamp of last change to
        the tQosIngQueueTable."
    ::= { tQosTimeStampObjects 7 }


tQosIngQueueTable OBJECT-TYPE
    SYNTAX       SEQUENCE OF TQosIngQueueEntry
    MAX-ACCESS   not-accessible
    STATUS       current
    DESCRIPTION
        "tQosIngQueueTable defines all ingress queues."
    ::= { tSharedQueueObjects 5 }

tQosIngQueueEntry OBJECT-TYPE
    SYNTAX       TQosIngQueueEntry
    MAX-ACCESS   not-accessible
    STATUS       current
    DESCRIPTION
        "tQosIngQueueEntry defines a particular ingress queue.
         Entries are created by user by setting tQosIngQueueRowStatus."
    INDEX { tQosIngQGroupName, tQosIngQueue }
    ::= { tQosIngQueueTable 1 }

TQosIngQueueEntry ::= SEQUENCE
    {
        tQosIngQueue                 TIngressQueueId,
        tQosIngQueueRowStatus        RowStatus,
        tQosIngQueueParent           TNamedItemOrEmpty,
        tQosIngQueueLevel            TLevel,
        tQosIngQueueWeight           TWeight,
        tQosIngQueueCIRLevel         TLevelOrDefault,
        tQosIngQueueCIRWeight        TWeight,
        tQosIngQueueMCast            TruthValue,
        tQosIngQueueExpedite         INTEGER,
        tQosIngQueueCBS              TBurstSize,
        tQosIngQueueMBS              TBurstSize,
        tQosIngQueueHiPrioOnly       TBurstPercentOrDefault,
        tQosIngQueuePIRAdaptation    TAdaptationRule,
        tQosIngQueueCIRAdaptation    TAdaptationRule,
        tQosIngQueueAdminPIR         TQosQueuePIRRate,
        tQosIngQueueAdminCIR         TQosQueueCIRRate,
        tQosIngQueueLastChanged      TimeStamp,
        tQosIngQueuePoliced          TruthValue,
        tQosIngQueueMode             TQueueMode,
        tQosIngQueuePoolName         TNamedItemOrEmpty,
        tQosIngQueueMBSBytes         TBurstSizeBytes,
        tQosIngQueueBurstLimit       TBurstLimit,
        tQosIngQueueAdvCfgPolicy     TNamedItemOrEmpty,
        tQosIngQueuePktOffset        TIngressQPerPacketOffset
    }

tQosIngQueue OBJECT-TYPE
    SYNTAX       TIngressQueueId (1..32)
    MAX-ACCESS   not-accessible
    STATUS       current
    DESCRIPTION
        "tQosIngQueue specifies the queue ID which is used as the
        secondary index to the table entry."
    ::= { tQosIngQueueEntry 1 }

tQosIngQueueRowStatus OBJECT-TYPE
    SYNTAX       RowStatus
    MAX-ACCESS   read-create
    STATUS       current
    DESCRIPTION
        "tQosIngQueueRowStatus is the Row-Status of the entry.
         This allows creation/deletion of rows in this table."
    ::= { tQosIngQueueEntry 2 }

tQosIngQueueParent OBJECT-TYPE
    SYNTAX       TNamedItemOrEmpty
    MAX-ACCESS   read-create
    STATUS       current
    DESCRIPTION
        "tQosIngQueueParent specifies the scheduler to which this queue would
        be feeding."
    DEFVAL { ''H }
    ::= { tQosIngQueueEntry 3 }

tQosIngQueueLevel OBJECT-TYPE
    SYNTAX       TLevel
    MAX-ACCESS   read-create
    STATUS       current
    DESCRIPTION
        "tQosIngQueueLevel specifies the level of priority while feeding
        the parent."
    DEFVAL { 1 }
    ::= { tQosIngQueueEntry 4 }

tQosIngQueueWeight OBJECT-TYPE
    SYNTAX       TWeight
    MAX-ACCESS   read-create
    STATUS       current
    DESCRIPTION
        "tQosIngQueueWeight specifies the weight that needs to be used by the
        scheduler to which this queue would be feeding."
    DEFVAL { 1 }
    ::= { tQosIngQueueEntry 5 }

tQosIngQueueCIRLevel OBJECT-TYPE
    SYNTAX       TLevelOrDefault
    MAX-ACCESS   read-create
    STATUS       current
    DESCRIPTION
        "tQosIngQueueCIRLevel specifies the level of priority while feeding
        to the parent.  The level '0' means treat all offered load for this
        queue as for the above CIR traffic."
    DEFVAL { 0 }
    ::= { tQosIngQueueEntry 6 }

tQosIngQueueCIRWeight OBJECT-TYPE
    SYNTAX       TWeight
    MAX-ACCESS   read-create
    STATUS       current
    DESCRIPTION
        "tQosIngQueueCIRWeight specifies the weight that needs to be used
        until the committed rate by the scheduler to which this queue would
        be feeding."
    DEFVAL { 1 }
    ::= { tQosIngQueueEntry 7 }

tQosIngQueueMCast OBJECT-TYPE
    SYNTAX       TruthValue
    MAX-ACCESS   read-create
    STATUS       current
    DESCRIPTION
        "tQosIngQueueMCast specifies if this is a multicast queue."
    DEFVAL { false }
    ::= { tQosIngQueueEntry 8 }

tQosIngQueueExpedite OBJECT-TYPE
    SYNTAX       INTEGER {
                    expedited     (1),
                    bestEffort    (3)
                 }
    MAX-ACCESS   read-create
    STATUS       current
    DESCRIPTION
        "tQosIngQueueExpedite specifies the priority that this queue should
         be assigned by the hardware level schedulers.

         This attribute is associated with the queue at the time of creation and
         cannot be modified thereafter."
    DEFVAL { bestEffort }
    ::= { tQosIngQueueEntry 9 }

tQosIngQueueCBS OBJECT-TYPE
    SYNTAX       TBurstSize
    UNITS        "kilo-bytes"
    MAX-ACCESS   read-create
    STATUS       current
    DESCRIPTION
        "tQosIngQueueCBS specifies the amount of reserved buffer space
        for the queue."
    DEFVAL { -1 }
    ::= { tQosIngQueueEntry 10 }

tQosIngQueueMBS OBJECT-TYPE
    SYNTAX       TBurstSize
    UNITS        "kilo-bytes"
    MAX-ACCESS   read-create
    STATUS       obsolete
    DESCRIPTION
        "tQosIngQueueMBS specifies the maximum amount of buffer space allowed
        for the queue.

        This object has been replaced with tQosIngQueueMBSBytes object."
    DEFVAL { -1 }
    ::= { tQosIngQueueEntry 11 }

tQosIngQueueHiPrioOnly OBJECT-TYPE
    SYNTAX       TBurstPercentOrDefault
    MAX-ACCESS   read-create
    STATUS       current
    DESCRIPTION
        "tQosIngQueueHiPrioOnly specifies the percentage of buffer space for
        the queue, used exclusively by high priority packets."
    DEFVAL { -1 }
    ::= { tQosIngQueueEntry 12 }

tQosIngQueuePIRAdaptation OBJECT-TYPE
    SYNTAX       TAdaptationRule
    MAX-ACCESS   read-create
    STATUS       current
    DESCRIPTION
        "tQosIngQueuePIRAdaptation specifies the adaptation rule to be used
        while computing the operational PIR value. The adaptation rule
        specifies the rules to compute the operational values while maintaining
        minimum offset."
    DEFVAL { closest }
    ::= { tQosIngQueueEntry 13 }

tQosIngQueueCIRAdaptation OBJECT-TYPE
    SYNTAX       TAdaptationRule
    MAX-ACCESS   read-create
    STATUS       current
    DESCRIPTION
        "tQosIngQueueCIRAdaptation specifies the adaptation rule to be used
        while computing the operational CIR value. The adaptation rule
        specifies the rules to compute the operational values while maintaining
        minimum offset."
    DEFVAL { closest }
    ::= { tQosIngQueueEntry 14 }

tQosIngQueueAdminPIR OBJECT-TYPE
    SYNTAX       TQosQueuePIRRate
    UNITS        "kbps"
    MAX-ACCESS   read-create
    STATUS       current
    DESCRIPTION
        "tQosIngQueueAdminPIR specifies the administrative PIR specified by
        the user."
    DEFVAL { -1 }
    ::= { tQosIngQueueEntry 15 }

tQosIngQueueAdminCIR OBJECT-TYPE
    SYNTAX       TQosQueueCIRRate
    UNITS        "kbps"
    MAX-ACCESS   read-create
    STATUS       current
    DESCRIPTION
        "tQosIngQueueAdminCIR specifies the administrative CIR specified by
        the user."
    DEFVAL { 0 }
    ::= { tQosIngQueueEntry 16 }

tQosIngQueueLastChanged OBJECT-TYPE
    SYNTAX       TimeStamp
    MAX-ACCESS   read-only
    STATUS       current
    DESCRIPTION
        "tQosIngQueueLastChanged specifies the timestamp of last change to
        this row in tQosIngQueueTable."
    ::= { tQosIngQueueEntry 17 }

tQosIngQueuePoliced OBJECT-TYPE
    SYNTAX       TruthValue
    MAX-ACCESS   read-create
    STATUS       current
    DESCRIPTION
        "tQosIngQueuePoliced specifies that the out of profile
         traffic feeding into the physical queue instance should be
         dropped. tQosIngQueuePoliced overrides the bandwidth
         specified by the object tQosIngQueueAdminCIR."
    DEFVAL { false }
    ::= { tQosIngQueueEntry 18 }

tQosIngQueueMode OBJECT-TYPE
    SYNTAX       TQueueMode
    MAX-ACCESS   read-create
    STATUS       current
    DESCRIPTION
        "tQosIngQueueMode specifies the mode in which the queue
         is operating. This attribute is associated with the queue
         at the time of creation and cannot be modified thereafter."
    DEFVAL { priority }
    ::= { tQosIngQueueEntry 19 }

tQosIngQueuePoolName OBJECT-TYPE   
    SYNTAX      TNamedItemOrEmpty
    MAX-ACCESS  read-create
    STATUS      current
    DESCRIPTION
        "tQosIngQueuePoolName specifies the name of the pool to be applied
        for the ingress queue."
    DEFVAL { ''H }    
    ::= { tQosIngQueueEntry 20 }

tQosIngQueueMBSBytes OBJECT-TYPE
    SYNTAX       TBurstSizeBytes
    UNITS        "bytes"
    MAX-ACCESS   read-create
    STATUS       current
    DESCRIPTION
        "tQosIngQueueMBSBytes specifies the maximum amount of buffer space
        allowed for the queue."
    DEFVAL { -1 }
    ::= { tQosIngQueueEntry 21 }

tQosIngQueueBurstLimit OBJECT-TYPE
    SYNTAX       TBurstLimit
    UNITS        "bytes"
    MAX-ACCESS   read-create
    STATUS       current
    DESCRIPTION
        "The value of tQosIngQueueBurstLimit specifies the explicit shaping
         burst size of a queue."
    DEFVAL { -1 }
    ::= { tQosIngQueueEntry 22 }

tQosIngQueueAdvCfgPolicy        OBJECT-TYPE
    SYNTAX      TNamedItemOrEmpty
    MAX-ACCESS  read-create
    STATUS      current
    DESCRIPTION
        "The value of tQosIngQueueAdvCfgPolicy specifies the name of the 
         advanced configuration policy to be applied with this queue."
    DEFVAL { ''H }
    ::= { tQosIngQueueEntry 23 }

tQosIngQueuePktOffset               OBJECT-TYPE
    SYNTAX       TIngressQPerPacketOffset
    MAX-ACCESS   read-create
    STATUS       current
    DESCRIPTION
        "The value of tQosIngQueuePktOffset specifies the value, in bytes,
         of the adjustment to make to the size of each packet for queue
         accounting.

         A 'wrongValue' error is returned while trying to set odd values for 
         this object.

         This object is only supported for queues residing on FP2 or greater
         forwarding planes. It is ignored for queues on FP1 forwarding planes."
    DEFVAL { 0 }
    ::= { tQosIngQueueEntry 24 }

--
-- egress queue group table
--

tQosEgrQGroupTableLastChanged OBJECT-TYPE
    SYNTAX       TimeStamp
    MAX-ACCESS   read-only
    STATUS       current
    DESCRIPTION
        "tQosEgrQGroupTableLastChanged indicates the timestamp of last change
        to the tQosEgrQGroupTable."
    ::= { tQosTimeStampObjects 8 }

tQosEgrQGroupTable OBJECT-TYPE
    SYNTAX       SEQUENCE OF TQosEgrQGroupEntry
    MAX-ACCESS   not-accessible
    STATUS       current
    DESCRIPTION
        "tQosEgrQGroupTable defines the Ingress Queue Group Table for
         providing, via SNMP, the capability of defining the queue groups
         for the queues existing in the tQosEgrQueueTable.

         tQosEgrQGroupTable holds a list of all the queue-groups in
         the managed system defined. Queue-groups should exist
         in this table before being referenced by the forwarding class
         mappings within the queue policy as defined in the
         tSapIngressFCTable."
    ::= { tSharedQueueObjects 6 }

tQosEgrQGroupEntry OBJECT-TYPE
    SYNTAX       TQosEgrQGroupEntry
    MAX-ACCESS   not-accessible
    STATUS       current
    DESCRIPTION
        "tQosEgrQGroupEntry defines an entry in the tQosEgrQGroupTable.

         Entries are created/deleted in this table by SNMP sets to
         tQosEgrQGroupRowStatus."
    INDEX { tQosEgrQGroupName }
    ::= { tQosEgrQGroupTable 1 }

TQosEgrQGroupEntry ::= SEQUENCE
    {
        tQosEgrQGroupName               TNamedItem,
        tQosEgrQGroupRowStatus          RowStatus,
        tQosEgrQGroupLastChanged        TimeStamp,
        tQosEgrQGroupDescr              TItemDescription,
        tQosEgrQGroupHsmdaPacketOffset  TEgressHsmdaPerPacketOffset,
        tQosEgrQGroupHsmdaWrrPolicy     TNamedItemOrEmpty,
        tQosEgrQGroupHsmdaLowBrstMaxCls Unsigned32
    }

tQosEgrQGroupName OBJECT-TYPE
    SYNTAX       TNamedItem
    MAX-ACCESS   not-accessible
    STATUS       current
    DESCRIPTION
        "tQosEgrQGroupName defines the Egress Queue Group name.
         It uniquely identifies an egress queue group in the managed
         system."
    ::= { tQosEgrQGroupEntry 1 }

tQosEgrQGroupRowStatus OBJECT-TYPE
    SYNTAX       RowStatus
    MAX-ACCESS   read-create
    STATUS       current
    DESCRIPTION
        "tQosEgrQGroupRowStatus allows entries to be created and deleted
         in the tQosEgrQGroupTable. The deletion of an entry in this table
         will fail if the queue is being referenced by a forwarding class
         mapping in the queue policy."
    REFERENCE
        "See definition of RowStatus in RFC 2579, 'Textual Conventions for
         SMIv2.'"
    ::= { tQosEgrQGroupEntry 2 }

tQosEgrQGroupLastChanged OBJECT-TYPE
    SYNTAX       TimeStamp
    MAX-ACCESS   read-only
    STATUS       current
    DESCRIPTION
        "tQosEgrQGroupLastChanged indicates the value of sysUpTime when
         the queue entry was last modified."
    ::= { tQosEgrQGroupEntry 3 }

tQosEgrQGroupDescr OBJECT-TYPE
    SYNTAX       TItemDescription
    MAX-ACCESS   read-create
    STATUS       current
    DESCRIPTION
        "tQosEgrQGroupDescr specifies the description of the queue-group."
    DEFVAL { ''H }
    ::= { tQosEgrQGroupEntry 4 }

tQosEgrQGroupHsmdaPacketOffset    OBJECT-TYPE
    SYNTAX      TEgressHsmdaPerPacketOffset
    UNITS       "bytes"
    MAX-ACCESS  read-create
    STATUS      current
    DESCRIPTION
        "The value of tQosEgrQGroupHsmdaPacketOffset specifies the value, in 
         bytes, of the adjustment to make to the size of each packet for HSMDA
         queue accounting."
    DEFVAL { 0 }
    ::= { tQosEgrQGroupEntry 5 }

tQosEgrQGroupHsmdaWrrPolicy  OBJECT-TYPE
    SYNTAX       TNamedItemOrEmpty
    MAX-ACCESS   read-create
    STATUS       current
    DESCRIPTION
        "The value of tQosEgrQGroupHsmdaWrrPolicy specifies the HSMDA Weighted
         Round Robin (WRR) scheduling policy to use."
    DEFVAL { "" }
    ::= { tQosEgrQGroupEntry 6 }

tQosEgrQGroupHsmdaLowBrstMaxCls  OBJECT-TYPE
    SYNTAX       Unsigned32 (1..8)
    MAX-ACCESS   read-create
    STATUS       current
    DESCRIPTION
        "The value of tQosEgrQGroupHsmdaLowBrstMaxCls specifies which class
         should use the low priority burst threshold.
        
         Use the low priority burst threshold for all classes starting from 1,
         up to and including that specified by tQosEgrQGroupHsmdaLowBrstMaxCls.

         Use the high priority burst threshold for all classes greater than the
         value of tQosEgrQGroupHsmdaLowBrstMaxCls, up to and including class 8."
    DEFVAL { 8 }
    ::= { tQosEgrQGroupEntry 7 }

--
-- qos egress policy queue table
--

tQosEgrQTableLastChanged OBJECT-TYPE
    SYNTAX       TimeStamp
    MAX-ACCESS   read-only
    STATUS       current
    DESCRIPTION
        "tQosEgrQTableLastChanged indicates the timestamp of last change to
        the tQosEgrQueueTable."
    ::= { tQosTimeStampObjects 9 }

tQosEgrQueueTable OBJECT-TYPE
    SYNTAX       SEQUENCE OF TQosEgrQueueEntry
    MAX-ACCESS   not-accessible
    STATUS       current
    DESCRIPTION
        "tQosEgrQueueTable defines all egress queues."
    ::= { tSharedQueueObjects 7 }

tQosEgrQueueEntry OBJECT-TYPE
    SYNTAX       TQosEgrQueueEntry
    MAX-ACCESS   not-accessible
    STATUS       current
    DESCRIPTION
        "tQosEgrQueueEntry defines a particular egress queue.
         Entries are created and deleted by user."
    INDEX { tQosEgrQGroupName, tQosEgrQueue }
    ::= { tQosEgrQueueTable 1 }

TQosEgrQueueEntry ::= SEQUENCE
    {
        tQosEgrQueue                  TEgressQueueId,
        tQosEgrQueueRowStatus         RowStatus,
        tQosEgrQueueParent            TNamedItemOrEmpty,
        tQosEgrQueueLevel             TLevel,
        tQosEgrQueueWeight            TWeight,
        tQosEgrQueueCIRLevel          TLevelOrDefault,
        tQosEgrQueueCIRWeight         TWeight,
        tQosEgrQueueExpedite          INTEGER,
        tQosEgrQueueCBS               TBurstSize,
        tQosEgrQueueMBS               TBurstSize,
        tQosEgrQueueHiPrioOnly        TBurstPercentOrDefault,
        tQosEgrQueuePIRAdaptation     TAdaptationRule,
        tQosEgrQueueCIRAdaptation     TAdaptationRule,
        tQosEgrQueueAdminPIR          TQosQueuePIRRate,
        tQosEgrQueueAdminCIR          TQosQueueCIRRate,
        tQosEgrQueueLastChanged       TimeStamp,
        tQosEgrQueueUsePortParent     TruthValue,
        tQosEgrQueuePortLvl           TLevel,
        tQosEgrQueuePortWght          TWeight,
        tQosEgrQueuePortCIRLvl        TLevelOrDefault,
        tQosEgrQueuePortCIRWght       TWeight,
        tQosEgrQueuePoolName          TNamedItemOrEmpty,
        tQosEgrQueueXPWredQ           TruthValue,  
        tQosEgrQueueXPWredQSlope      TNamedItem,
        tQosEgrQueueMBSBytes          TBurstSizeBytes,
        tQosEgrQueueAdminPIRPercent   Unsigned32,
        tQosEgrQueueAdminCIRPercent   Unsigned32,
        tQosEgrQueueRateType          TRateType,
        tQosEgrQueueBurstLimit        TBurstLimit,
        tQosEgrQueueAdvCfgPolicy      TNamedItemOrEmpty,
        tQosEgrQueuePktOffset         TEgressPerPacketOffset
    }

tQosEgrQueue OBJECT-TYPE
    SYNTAX       TEgressQueueId (1..8)
    MAX-ACCESS   not-accessible
    STATUS       current
    DESCRIPTION
        "The value of tQosEgrQueue identifies the queue index which is used as
         the second index to the table entry.  Zero is not allowed."
    ::= { tQosEgrQueueEntry 1 }

tQosEgrQueueRowStatus OBJECT-TYPE
    SYNTAX       RowStatus
    MAX-ACCESS   read-create
    STATUS       current
    DESCRIPTION
        "This is the Row Status of the entry.
         This allows creation/deletion of rows in this table."
    ::= { tQosEgrQueueEntry 2 }

tQosEgrQueueParent OBJECT-TYPE
    SYNTAX       TNamedItemOrEmpty
    MAX-ACCESS   read-create
    STATUS       current
    DESCRIPTION
        "The value of tQosEgrQueueParent specifies the scheduler to which this
         queue would be feeding."
    DEFVAL { ''H }
    ::= { tQosEgrQueueEntry 3 }

tQosEgrQueueLevel OBJECT-TYPE
    SYNTAX       TLevel
    MAX-ACCESS   read-create
    STATUS       current
    DESCRIPTION
        "The value of tQosEgrQueueLevel specifies the level of priority while
         feeding the parent."
    DEFVAL { 1 }
    ::= { tQosEgrQueueEntry 4 }

tQosEgrQueueWeight OBJECT-TYPE
    SYNTAX       TWeight
    MAX-ACCESS   read-create
    STATUS       current
    DESCRIPTION
        "The value of tQosEgrQueueWeight specifies the weight that needs to be
         used by the scheduler to which this queue would be feeding."
    DEFVAL { 1 }
    ::= { tQosEgrQueueEntry 5 }

tQosEgrQueueCIRLevel OBJECT-TYPE
    SYNTAX       TLevelOrDefault
    MAX-ACCESS   read-create
    STATUS       current
    DESCRIPTION
        "The value of tQosEgrQueueCIRLevel specifies the level of priority
         while feeding the parent.  The level '0' means treat all offered
         load for this queue as for the above CIR traffic."
    DEFVAL { 0 }
    ::= { tQosEgrQueueEntry 6 }

tQosEgrQueueCIRWeight OBJECT-TYPE
    SYNTAX       TWeight
    MAX-ACCESS   read-create
    STATUS       current
    DESCRIPTION
        "The value of tQosEgrQueueCIRWeight specifies the weight that needs to
         be used until the committed rate by the scheduler to which this queue
         would be feeding."
    DEFVAL { 1 }
    ::= { tQosEgrQueueEntry 7 }

tQosEgrQueueExpedite OBJECT-TYPE
    SYNTAX       INTEGER {
                    expedited     (1),
                    bestEffort    (3)
                 }
    MAX-ACCESS   read-create
    STATUS       current
    DESCRIPTION
        "The value of tQosEgrQueueExpedite specifies the priority that this
         queue should be assigned by the hardware level schedulers."
    DEFVAL { bestEffort }
    ::= { tQosEgrQueueEntry 8 }

tQosEgrQueueCBS OBJECT-TYPE
    SYNTAX       TBurstSize
    UNITS        "kilo-bytes"
    MAX-ACCESS   read-create
    STATUS       current
    DESCRIPTION
        "The value of tQosEgrQueueCBS specifies the amount of reserved buffer
         space for the queue."
    DEFVAL { -1 }
    ::= { tQosEgrQueueEntry 9 }

tQosEgrQueueMBS OBJECT-TYPE
    SYNTAX       TBurstSize
    UNITS        "kilo-bytes"
    MAX-ACCESS   read-create
    STATUS       obsolete
    DESCRIPTION
        "The value of tQosEgrQueueMBS specifies the maximum amount of buffer
         space allowed for the queue.

         This object has been replaced with tQosEgrQueueMBSBytes object."
    DEFVAL { -1 }
    ::= { tQosEgrQueueEntry 10 }

tQosEgrQueueHiPrioOnly OBJECT-TYPE
    SYNTAX       TBurstPercentOrDefault
    MAX-ACCESS   read-create
    STATUS       current
    DESCRIPTION
        "The value of tQosEgrQueueHiPrioOnly specifies the percentage of buffer
         space for the queue, used exclusively by high priority packets."
    DEFVAL { -1 }
    ::= { tQosEgrQueueEntry 11 }

tQosEgrQueuePIRAdaptation OBJECT-TYPE
    SYNTAX       TAdaptationRule
    MAX-ACCESS   read-create
    STATUS       current
    DESCRIPTION
        "The value of tQosEgrQueuePIRAdaptation specifies the adaptation rule to
         be used while computing the operational PIR value. The adaptation rule
         specifies the rules to compute the operational values while
         maintaining minimum offset."
    DEFVAL { closest }
    ::= { tQosEgrQueueEntry 12 }

tQosEgrQueueCIRAdaptation OBJECT-TYPE
    SYNTAX       TAdaptationRule
    MAX-ACCESS   read-create
    STATUS       current
    DESCRIPTION
        "The value of tQosEgrQueueCIRAdaptation specifies the adaptation rule
         to be used while computing the operational CIR value. The adaptation
         rule specifies the rules to compute the operational values while
         maintaining minimum offset."
    DEFVAL { closest }
    ::= { tQosEgrQueueEntry 13 }

tQosEgrQueueAdminPIR OBJECT-TYPE
    SYNTAX       TQosQueuePIRRate
    UNITS        "kbps"
    MAX-ACCESS   read-create
    STATUS       current
    DESCRIPTION
        "The value of tQosEgrQueueAdminPIR specifies the administrative PIR.

         An 'inconsistentValue' error is returned if tQosEgrQueueAdminPIR  
         is set to non-default value when the object tQosEgrQueueRateType 
         is set to 'percent'."
    DEFVAL { -1 }
    ::= { tQosEgrQueueEntry 14 }

tQosEgrQueueAdminCIR OBJECT-TYPE
    SYNTAX       TQosQueueCIRRate
    UNITS        "kbps"
    MAX-ACCESS   read-create
    STATUS       current
    DESCRIPTION
        "The value of tQosEgrQueueAdminCIR specifies the administrative CIR.

        An 'inconsistentValue' error is returned if tQosEgrQueueAdminCIR  
        is set to non-default value when the object tQosEgrQueueRateType 
        is set to 'percent'."
    DEFVAL { 0 }
    ::= { tQosEgrQueueEntry 15 }

tQosEgrQueueLastChanged OBJECT-TYPE
    SYNTAX       TimeStamp
    MAX-ACCESS   read-only
    STATUS       current
    DESCRIPTION
        "The value of tQosEgrQueueLastChanged indicates the timestamp of last 
         change to this row in tQosEgrQueueTable."
    ::= { tQosEgrQueueEntry 18 }

tQosEgrQueueUsePortParent  OBJECT-TYPE
    SYNTAX      TruthValue
    MAX-ACCESS  read-create
    STATUS      current
    DESCRIPTION
        "The value of tQosEgrQueueUsePortParent specifies whether this queue is
         parented by a port-level scheduler. When the value is 'true', this SAP
         egress queue is parented by a port-level scheduler. This object is 
         mutually exclusive with tQosEgrQueueParent. Only one kind of parent is
         allowed."
    DEFVAL      { false }
    ::= { tQosEgrQueueEntry 19 }

tQosEgrQueuePortLvl        OBJECT-TYPE
    SYNTAX       TLevel
    MAX-ACCESS  read-create
    STATUS      current
    DESCRIPTION
        "The value of the object tQosEgrQueuePortLvl specifies the
         port priority this queue will use to receive bandwidth from
         the port-level scheduler for its above-cir offered load."
    DEFVAL      { 1 }
    ::= { tQosEgrQueueEntry 20 }

tQosEgrQueuePortWght       OBJECT-TYPE
    SYNTAX      TWeight
    MAX-ACCESS  read-create
    STATUS      current
    DESCRIPTION
        "The value of the object tQosEgrQueuePortWght specifies the
         weight this queue will use to receive bandwidth from the
         port-level scheduler for its above-cir offered load."
    DEFVAL      { 1 }
    ::= { tQosEgrQueueEntry 21 }

tQosEgrQueuePortCIRLvl        OBJECT-TYPE
    SYNTAX      TLevelOrDefault
    MAX-ACCESS  read-create
    STATUS      current
    DESCRIPTION
        "The value of the object tQosEgrQueuePortCIRLvl specifies the
         port priority this queue will use to receive bandwidth from
         the port-level scheduler for its within-cir offered load."
    DEFVAL      { 0 }
    ::= { tQosEgrQueueEntry 22 }

tQosEgrQueuePortCIRWght       OBJECT-TYPE
    SYNTAX      TWeight
    MAX-ACCESS  read-create
    STATUS      current
    DESCRIPTION
        "The value of the object tQosEgrQueuePortCIRWght specifies the
         weight this queue will use to receive bandwidth from the
         port-level scheduler for its within-cir offered load."
    DEFVAL      { 0 }
    ::= { tQosEgrQueueEntry 23 }

tQosEgrQueuePoolName OBJECT-TYPE   
    SYNTAX      TNamedItemOrEmpty
    MAX-ACCESS  read-create
    STATUS      current
    DESCRIPTION
        "The value of tQosEgrQueuePoolName specifies the name of 
         the pool to be applied for SAP egress queue."
    DEFVAL { ''H }    
    ::= { tQosEgrQueueEntry 24 }

tQosEgrQueueXPWredQ OBJECT-TYPE   
    SYNTAX      TruthValue
    MAX-ACCESS  read-create
    STATUS      current
    DESCRIPTION
        "The value of tQosEgrQueueXPWredQ specifies whether to alter the
         generic pool association of the queue for the purpose of allowing
         queue-specific WRED slopes with minimal provisioning."
    DEFVAL { false }    
    ::= { tQosEgrQueueEntry 25 }

tQosEgrQueueXPWredQSlope OBJECT-TYPE   
    SYNTAX      TNamedItem
    MAX-ACCESS  read-create
    STATUS      current
    DESCRIPTION
        "The value of tQosEgrQueueXPWredQSlope specifies the name of 
         the slope-policy to be applied for QOS egress queue.
         
         When tQosEgrQueueXPWredQ has the value 'false', an 'inconsistentValue'
         error is returned if an attempt is made to set this object to a value
         other than 'default'."
    DEFVAL { "default" }    
    ::= { tQosEgrQueueEntry 26 }

tQosEgrQueueMBSBytes OBJECT-TYPE
    SYNTAX       TBurstSizeBytes
    UNITS        "bytes"
    MAX-ACCESS   read-create
    STATUS       current
    DESCRIPTION
        "The value of tQosEgrQueueMBSBytes specifies the maximum amount of
         buffer space allowed for the queue."
    DEFVAL { -1 }
    ::= { tQosEgrQueueEntry 27 }

tQosEgrQueueAdminPIRPercent OBJECT-TYPE
    SYNTAX      Unsigned32 (1..10000)
    UNITS       "hundredths of a percent"
    MAX-ACCESS  read-create
    STATUS      current
    DESCRIPTION
        "The value of tQosEgrQueueAdminPIRPercent specifies the administrative
         PIR percentage, in hudredths of a percent.

         An 'inconsistentValue' error is returned if tQosEgrQueueAdminPIRPercent  
         is set to non-default value when the object tQosEgrQueueRateType is set 
         to 'kbps'."
    DEFVAL { 10000 }
    ::= { tQosEgrQueueEntry 28 }

tQosEgrQueueAdminCIRPercent OBJECT-TYPE
    SYNTAX      Unsigned32 (0..10000)
    UNITS       "hundredths of a percent"
    MAX-ACCESS  read-create
    STATUS      current
    DESCRIPTION
        "The value of tQosEgrQueueAdminCIRPercent specifies the administrative
         CIR percentage, in hudredths of a percent.

         An 'inconsistentValue' error is returned if tQosEgrQueueAdminCIRPercent  
         is set to non-default value when the object tQosEgrQueueRateType is set 
         to 'kbps'."
    DEFVAL { 0 }
    ::= { tQosEgrQueueEntry 29 }

tQosEgrQueueRateType OBJECT-TYPE   
    SYNTAX      TRateType
    MAX-ACCESS  read-create
    STATUS      current
    DESCRIPTION
        "The value of tQosEgrQueueRateType specifies the type of Egress queue
         rate.
         
         When the value of the object is set to 'kbps', the egresss queue rates
         are specified in kbps. The objects  tQosEgrQueueAdminCIRPercent and
         tQosEgrQueueAdminPIRPercent will be set to their default values.

         When the value of the object is set to 'percent', the egress queue rates
         are specified in percentage. The objects tQosEgrQueueAdminCIR and 
         tQosEgrQueueAdminPIR will be set to their default values."
    DEFVAL { kbps }    
    ::= { tQosEgrQueueEntry 30 }

tQosEgrQueueBurstLimit OBJECT-TYPE
    SYNTAX       TBurstLimit
    UNITS        "bytes"
    MAX-ACCESS   read-create
    STATUS       current
    DESCRIPTION
        "The value of tQosEgrQueueBurstLimit specifies the explicit shaping
         burst size of a queue."
    DEFVAL { -1 }
    ::= { tQosEgrQueueEntry 31 }

tQosEgrQueueAdvCfgPolicy        OBJECT-TYPE
    SYNTAX      TNamedItemOrEmpty
    MAX-ACCESS  read-create
    STATUS      current
    DESCRIPTION
        "The value of tQosEgrQueueAdvCfgPolicy specifies the name of the 
         advanced configuration policy to be applied with this queue."
    DEFVAL { ''H }
    ::= { tQosEgrQueueEntry 32 }

tQosEgrQueuePktOffset OBJECT-TYPE
    SYNTAX       TEgressPerPacketOffset
    MAX-ACCESS   read-create
    STATUS       current
    DESCRIPTION  
        "The value of tQosEgrQueuePktOffset specifies the packet byte 
         offset to  be applied with this queue."
    DEFVAL { 0 }
    ::= { tQosEgrQueueEntry 33 }

--
-- qos egress queue group FC table
--
tQosEgrQGroupFCTableLastChanged OBJECT-TYPE
    SYNTAX       TimeStamp
    MAX-ACCESS   read-only
    STATUS       current
    DESCRIPTION
        "The value of tQosEgrQGroupFCTableLastChanged indicates the sysUpTime
         at the time of the last modification of an entry in the tQosEgrQGroupFCTable.

         If no changes were made to the table since the last re-initialization
         of the local network management subsystem, then this object
         contains a zero value."
    ::= { tQosTimeStampObjects 90 }

tQosEgrQGroupFCTable OBJECT-TYPE
    SYNTAX       SEQUENCE OF TQosEgrQGroupFCEntry
    MAX-ACCESS   not-accessible
    STATUS       current
    DESCRIPTION
        "This table maintains the information of forwarding
         classes in a egress queue group."
    ::= { tSharedQueueObjects 8 }

tQosEgrQGroupFCEntry OBJECT-TYPE
    SYNTAX       TQosEgrQGroupFCEntry
    MAX-ACCESS   not-accessible
    STATUS       current
    DESCRIPTION  
        "Information about a particular queue group's 
         forwarding class."
    INDEX { tQosEgrQGroupName, tQosEgrQGroupFCName }
    ::= { tQosEgrQGroupFCTable 1 }

TQosEgrQGroupFCEntry ::= SEQUENCE
    {
        tQosEgrQGroupFCName          TFCName,
        tQosEgrQGroupFCRowStatus     RowStatus,
        tQosEgrQGroupFCLastChanged   TimeStamp,
        tQosEgrQGroupFCQueue         TEgressQueueId
    }

tQosEgrQGroupFCName OBJECT-TYPE
    SYNTAX       TFCName
    MAX-ACCESS   not-accessible
    STATUS       current
    DESCRIPTION
        "The value of the object tQosEgrQGroupFCName specifies
         the name of the forwarding class"
    ::= { tQosEgrQGroupFCEntry 1 }  

tQosEgrQGroupFCRowStatus  OBJECT-TYPE
    SYNTAX       RowStatus
    MAX-ACCESS   read-create
    STATUS       current
    DESCRIPTION
        "The value of tQosEgrQGroupFCRowStatus specifies the Row Status
         for this entry."
    ::= { tQosEgrQGroupFCEntry 2 }

tQosEgrQGroupFCLastChanged  OBJECT-TYPE
    SYNTAX       TimeStamp
    MAX-ACCESS   read-only
    STATUS       current
    DESCRIPTION
        "The value of tQosEgrQGroupFCLastChanged indicates the 
         timestamp of last change to this row in tQosEgrQGroupFCTable."
    ::= { tQosEgrQGroupFCEntry 3 }
    
tQosEgrQGroupFCQueue OBJECT-TYPE
    SYNTAX       TEgressQueueId
    MAX-ACCESS   read-create
    STATUS       current
    DESCRIPTION
        "The value of tQosEgrQGroupFCQueue specifies the queue to 
         be used for the packets in this forwarding class. "
    DEFVAL { 0 }
    ::= { tQosEgrQGroupFCEntry 4 }        

--
-- HSMDA Egress Queue table
--

tQosEgrHsmdaQueueTable OBJECT-TYPE
    SYNTAX      SEQUENCE OF TQosEgrHsmdaQueueEntry
    MAX-ACCESS  not-accessible
    STATUS      current
    DESCRIPTION
        "Information about all Queue Group template HSMDA queues."
    ::= { tSharedQueueObjects 9 }

tQosEgrHsmdaQueueEntry    OBJECT-TYPE
    SYNTAX      TQosEgrHsmdaQueueEntry
    MAX-ACCESS  not-accessible
    STATUS      current
    DESCRIPTION
        "Information about a particular HSMDA queue in a queue group template.

         Entries are created by the system when a Queue group template
         tQosEgrQGroupName is created. Individual HSMDA queue properties
         can be modified by the user."
    INDEX { tQosEgrQGroupName, tQosEgrHsmdaQueue }
    ::= { tQosEgrHsmdaQueueTable 1}

TQosEgrHsmdaQueueEntry ::= SEQUENCE
    {
        tQosEgrHsmdaQueue                 TEgressHsmdaQueueId,
        tQosEgrHsmdaQueueRowStatus        RowStatus,
        tQosEgrHsmdaQueueLastChanged      TimeStamp,
        tQosEgrHsmdaQueuePIRAdaptn        TAdaptationRule,
        tQosEgrHsmdaQueueAdminPIR         THsmdaPIRKRate,
        tQosEgrHsmdaQueueSlopePolicy      TNamedItem,
        tQosEgrHsmdaQueueWrrWeight        THsmdaWrrWeight,
        tQosEgrHsmdaQueueMBS              THSMDABurstSizeBytes,
        tQosEgrHsmdaQueueBurstLimit       THSMDAQueueBurstLimit
    }

tQosEgrHsmdaQueue        OBJECT-TYPE
    SYNTAX      TEgressHsmdaQueueId (1..8)
    MAX-ACCESS  not-accessible
    STATUS      current
    DESCRIPTION
        "The HSMDA queue ID is used as the secondary index to the table entry."
    ::= { tQosEgrHsmdaQueueEntry 1 }

tQosEgrHsmdaQueueRowStatus        OBJECT-TYPE
    SYNTAX      RowStatus
    MAX-ACCESS  read-create
    STATUS      current
    DESCRIPTION
        "The value of tQosEgrHsmdaQueueRowStatus is used for the creation
         and deletion of entries in the tQosEgrHsmdaQueueTable."
    ::= { tQosEgrHsmdaQueueEntry 2 }

tQosEgrHsmdaQueueLastChanged        OBJECT-TYPE
    SYNTAX      TimeStamp
    MAX-ACCESS  read-only
    STATUS      current
    DESCRIPTION
        "The value of tQosEgrHsmdaQueueLastChanged indicates the timestamp 
         of last change to this row in tQosEgrHsmdaQueueTable."
    ::= { tQosEgrHsmdaQueueEntry 3 }

tQosEgrHsmdaQueuePIRAdaptn        OBJECT-TYPE
    SYNTAX      TAdaptationRule
    MAX-ACCESS  read-create
    STATUS      current
    DESCRIPTION
        "The value of tQosEgrHsmdaQueuePIRAdaptn specifies the adaptation rule
         to be used while computing the operational PIR value. The adaptation
         rule specifies the rules to compute the operational values while 
         maintaining minimum offset."
    DEFVAL { closest }
    ::= { tQosEgrHsmdaQueueEntry 4 }

tQosEgrHsmdaQueueAdminPIR        OBJECT-TYPE
    SYNTAX      THsmdaPIRKRate
    UNITS       "kbps"
    MAX-ACCESS  read-create
    STATUS      current
    DESCRIPTION
        "The value of tQosEgrHsmdaQueueAdminPIR specifies the administrative 
         PIR specified by the user."
    DEFVAL { -1 }
    ::= { tQosEgrHsmdaQueueEntry 5 }

tQosEgrHsmdaQueueSlopePolicy     OBJECT-TYPE
    SYNTAX      TNamedItem
    MAX-ACCESS  read-create
    STATUS      current
    DESCRIPTION
        "The value of tQosEgrHsmdaQueueSlopePolicy specifies the slope policy 
         specified by the user."
    DEFVAL { "default" }
    ::= { tQosEgrHsmdaQueueEntry 6 }

tQosEgrHsmdaQueueWrrWeight OBJECT-TYPE
    SYNTAX      THsmdaWrrWeight
    MAX-ACCESS  read-create
    STATUS      current
    DESCRIPTION
        "The value of tQosEgrHsmdaQueueWrrWeight specifies the weight with 
         which this queue should parent into the HSMDA scheduler, provided it is
         not superseded by the Weighted Round Robin (WRR) policy. The weight of 
         each queue determines how much bandwidth that queue gets out of the 
         total rate for the scheduling class."
    DEFVAL      { 1 }
    ::= { tQosEgrHsmdaQueueEntry 7 }

tQosEgrHsmdaQueueMBS OBJECT-TYPE
    SYNTAX      THSMDABurstSizeBytes
    UNITS       "bytes"
    MAX-ACCESS  read-create
    STATUS      current
    DESCRIPTION
        "The value of tQosEgrHsmdaQueueMBS specifies the maximum amount of 
         buffer space (in bytes) allowed for this HSMDA queue."
    DEFVAL      { -1 }
    ::= { tQosEgrHsmdaQueueEntry 8 }

tQosEgrHsmdaQueueBurstLimit OBJECT-TYPE
    SYNTAX      THSMDAQueueBurstLimit
    UNITS       "bytes"
    MAX-ACCESS  read-create
    STATUS      current
    DESCRIPTION
        "The value of tQosEgrHsmdaQueueBurstLimit specifies the explicit 
         shaping burst size of the queue."
    DEFVAL      { -1 }
    ::= { tQosEgrHsmdaQueueEntry 9 }

--
-- Slope policy table
--

tSlopePolicyTable OBJECT-TYPE
    SYNTAX       SEQUENCE OF TSlopePolicyEntry
    MAX-ACCESS   not-accessible
    STATUS       current
    DESCRIPTION
        "Slope Policy Table. Each entry in this table defines the RED
        slopes for the high and the low priority traffic."
    ::= { tSlopeObjects 1 }

tSlopePolicyEntry OBJECT-TYPE
    SYNTAX       TSlopePolicyEntry
    MAX-ACCESS   not-accessible
    STATUS       current
    DESCRIPTION
        "Slope Policy Entry."
    INDEX { tSlopePolicy }
    ::= { tSlopePolicyTable 1 }

TSlopePolicyEntry ::= SEQUENCE
    {
        tSlopePolicy            TNamedItem,
        tSlopeRowStatus         RowStatus,
        tSlopeDescription       TItemDescription,
        tSlopeHiAdminStatus     INTEGER,
        tSlopeHiStartAverage    Unsigned32,
        tSlopeHiMaxAverage      Unsigned32,
        tSlopeHiMaxProbability  Unsigned32,
        tSlopeLoAdminStatus     INTEGER,
        tSlopeLoStartAverage    Unsigned32,
        tSlopeLoMaxAverage      Unsigned32,
        tSlopeLoMaxProbability  Unsigned32,
        tSlopeTimeAvgFactor     Unsigned32,
        tSlopeLastChanged       TimeStamp
    }

tSlopePolicy OBJECT-TYPE
    SYNTAX       TNamedItem
    MAX-ACCESS   not-accessible
    STATUS       current
    DESCRIPTION
        "tSlopePolicy maintains the name of the slope policy
        identifying the policy."
    ::= { tSlopePolicyEntry 1 }

tSlopeRowStatus OBJECT-TYPE
    SYNTAX       RowStatus
    MAX-ACCESS   read-create
    STATUS       current
    DESCRIPTION
        "Row Status of the entry. This allows creation/deletion of rows in this
         table."
    ::= { tSlopePolicyEntry 2 }

tSlopeDescription OBJECT-TYPE
    SYNTAX       TItemDescription
    MAX-ACCESS   read-create
    STATUS       current
    DESCRIPTION
        "User-provided description of the policy."
    DEFVAL { ''H }
    ::= { tSlopePolicyEntry 3 }

tSlopeHiAdminStatus OBJECT-TYPE
    SYNTAX       INTEGER {
                     up  (1),
                     down(2)
                 }
    MAX-ACCESS   read-create
    STATUS       current
    DESCRIPTION
        "tSlopeHiAdminStatus specifies the admin state for the high priority RED
         slope. If the tSlopeHiAdminStatus is set to 'down', the RED slope is
         inactive."
    DEFVAL { down }
    ::= { tSlopePolicyEntry 4 }

tSlopeHiStartAverage OBJECT-TYPE
    SYNTAX       Unsigned32 (0..100)
    MAX-ACCESS   read-create
    STATUS       current
    DESCRIPTION
        "The percentage of the buffer utilized after which the drop probability
         starts to rise above 0."
    DEFVAL { 70 }
    ::= { tSlopePolicyEntry 5 }

tSlopeHiMaxAverage OBJECT-TYPE
    SYNTAX       Unsigned32 (0..100)
    MAX-ACCESS   read-create
    STATUS       current
    DESCRIPTION
        "The percentage of the buffer utilized after which the drop probability
         is 100 percent. This implies that all packets beyond this point will be
         dropped."
    DEFVAL { 90 }
    ::= { tSlopePolicyEntry 6 }

tSlopeHiMaxProbability OBJECT-TYPE
    SYNTAX       Unsigned32 (0..100)
    MAX-ACCESS   read-create
    STATUS       current
    DESCRIPTION
        "The drop probability increases steadily from 0 at the
         tSlopeHiStartAverage upto the tSlopeHiMaxProbability at the
         tSlopeHiMaxAverage."
    DEFVAL { 80 }
    ::= { tSlopePolicyEntry 7 }

tSlopeLoAdminStatus OBJECT-TYPE
    SYNTAX       INTEGER {
                     up(1),
                     down(2)
                 }
    MAX-ACCESS   read-create
    STATUS       current
    DESCRIPTION
        "tSlopeLoAdminStatus specifies the admin state for the high priority RED
        slope. If the tSlopeLoAdminStatus is set to 'down', the RED slope is
        inactive."
    DEFVAL { down }
    ::= { tSlopePolicyEntry 8 }

tSlopeLoStartAverage OBJECT-TYPE
    SYNTAX       Unsigned32 (0..100)
    MAX-ACCESS   read-create
    STATUS       current
    DESCRIPTION
        "The percentage of the buffer utilized after which the drop probability
        starts to rise above 0."
    DEFVAL { 50 }
    ::= { tSlopePolicyEntry 9 }

tSlopeLoMaxAverage OBJECT-TYPE
    SYNTAX       Unsigned32 (0..100)
    MAX-ACCESS   read-create
    STATUS       current
    DESCRIPTION
        "The percentage of the buffer utilized after which the drop probability
        is 100 percent. This implies that all packets beyond this point will be
        dropped."
    DEFVAL { 75 }
    ::= { tSlopePolicyEntry 10 }

tSlopeLoMaxProbability OBJECT-TYPE
    SYNTAX       Unsigned32 (0..100)
    MAX-ACCESS   read-create
    STATUS       current
    DESCRIPTION
        "The drop probability increases steadily from 0 at the
        tSlopeLoStartAverage upto the tSlopeLoMaxProbability at the
        tSlopeLoMaxAverage."
    DEFVAL { 80 }
    ::= { tSlopePolicyEntry 11 }

tSlopeTimeAvgFactor OBJECT-TYPE
    SYNTAX       Unsigned32 (0..15)
    MAX-ACCESS   read-create
    STATUS       current
    DESCRIPTION
        "The time average factor describes the weighting between the previous
        shared buffer average utilization result and the new shared buffer
        utilization in determining the new shared buffer average utilization."
    DEFVAL { 7 }
    ::= { tSlopePolicyEntry 12 }

tSlopeLastChanged OBJECT-TYPE
    SYNTAX       TimeStamp
    MAX-ACCESS   read-only
    STATUS       current
    DESCRIPTION
        "Timestamp of when this entry was last changed."
    ::= { tSlopePolicyEntry 13 }


--
-- Slope policy table
--

tHsmdaSlopePolicyTable OBJECT-TYPE
    SYNTAX       SEQUENCE OF THsmdaSlopePolicyEntry
    MAX-ACCESS   not-accessible
    STATUS       current
    DESCRIPTION
        "The tHsmdaSlopePolicyTable has an entry for each HSMDA slope
         policy configured on this system."
    ::= { tSlopeObjects 2 }

tHsmdaSlopePolicyEntry OBJECT-TYPE
    SYNTAX       THsmdaSlopePolicyEntry
    MAX-ACCESS   not-accessible
    STATUS       current
    DESCRIPTION
        "Each row represents a particular HSMDA slope policy. Entries are 
         created and deleted by the user."
    INDEX { tHsmdaSlopePolicyName }
    ::= { tHsmdaSlopePolicyTable 1 }

THsmdaSlopePolicyEntry ::= SEQUENCE
    {
        tHsmdaSlopePolicyName        TNamedItem,
        tHsmdaSlopePolicyRowStatus   RowStatus,
        tHsmdaSlopeLastChanged       TimeStamp,
        tHsmdaSlopeDescription       TItemDescription,
        tHsmdaSlopeQueueMbs          Unsigned32,
        tHsmdaSlopeHiAdminStatus     TmnxEnabledDisabled,
        tHsmdaSlopeHiStartDepth      Unsigned32,
        tHsmdaSlopeHiMaxDepth        Unsigned32,
        tHsmdaSlopeHiMaxProbability  Unsigned32,
        tHsmdaSlopeLoAdminStatus     TmnxEnabledDisabled,
        tHsmdaSlopeLoStartDepth      Unsigned32,
        tHsmdaSlopeLoMaxDepth        Unsigned32,
        tHsmdaSlopeLoMaxProbability  Unsigned32
    }

tHsmdaSlopePolicyName OBJECT-TYPE
    SYNTAX       TNamedItem
    MAX-ACCESS   not-accessible
    STATUS       current
    DESCRIPTION
        "The value of tHsmdaSlopePolicyName specifies the name of the HSMDA
         slope policy."
    ::= { tHsmdaSlopePolicyEntry 1 }

tHsmdaSlopePolicyRowStatus OBJECT-TYPE
    SYNTAX       RowStatus
    MAX-ACCESS   read-create
    STATUS       current
    DESCRIPTION
        "The value of tHsmdaSlopePolicyRowStatus is used for the creation
         and deletion of HSMDA slope policies."
    ::= { tHsmdaSlopePolicyEntry 2 }

tHsmdaSlopeLastChanged OBJECT-TYPE
    SYNTAX       TimeStamp
    MAX-ACCESS   read-only
    STATUS       current
    DESCRIPTION
        "The value of tHsmdaSlopeLastChanged indicates the sysUpTime
         at the time of the last modification of this entry.

         If no changes were made to the entry since the last
         re-initialization of the local network management subsystem,
         then this object contains a zero value."
    ::= { tHsmdaSlopePolicyEntry 3 }

tHsmdaSlopeDescription OBJECT-TYPE
    SYNTAX       TItemDescription
    MAX-ACCESS   read-create
    STATUS       current
    DESCRIPTION
        "The value of tHsmdaSlopeDescription specifies the description
         of this HSMDA slope policy."
    DEFVAL { "" }
    ::= { tHsmdaSlopePolicyEntry 4 }

tHsmdaSlopeQueueMbs          OBJECT-TYPE
    SYNTAX       Unsigned32 (0..500000)
    UNITS        "bytes"
    MAX-ACCESS   read-create
    STATUS       obsolete
    DESCRIPTION
        "The value of tHsmdaSlopeQueueMbs specifies the maximum amount of buffer
         space, in bytes, allowed for any HSMDA queue associated with this HSMDA
         slope policy.

         Specifying a value of 0 effectively disables all queues associated with
         this slope policy causing each queue to discard all packets.

         This object is obsoleted in 10.0 Release."
    DEFVAL { 16800 }
    ::= { tHsmdaSlopePolicyEntry 5 }

tHsmdaSlopeHiAdminStatus OBJECT-TYPE
    SYNTAX       TmnxEnabledDisabled
    MAX-ACCESS   read-create
    STATUS       current
    DESCRIPTION
        "The value of tHsmdaSlopeHiAdminStatus specifies the admin state for
         the high priority RED slope. If the tHsmdaSlopeHiAdminStatus is set
         to 'disabled', the RED slope is inactive."
    DEFVAL { enabled }
    ::= { tHsmdaSlopePolicyEntry 6 }

tHsmdaSlopeHiStartDepth OBJECT-TYPE
    SYNTAX       Unsigned32 (1..10000)
    UNITS        "hundredths of a percent"
    MAX-ACCESS   read-create
    STATUS       current
    DESCRIPTION
        "The value of tHsmdaSlopeHiStartDepth specifies the percentage of the
         buffer utilized after which the drop probability starts to rise
         above 0."
    DEFVAL { 10000 }
    ::= { tHsmdaSlopePolicyEntry 7 }

tHsmdaSlopeHiMaxDepth OBJECT-TYPE
    SYNTAX       Unsigned32 (1..10000)
    UNITS        "hundredths of a percent"
    MAX-ACCESS   read-create
    STATUS       current
    DESCRIPTION
        "The value of tHsmdaSlopeHiMaxDepth specifies the percentage of the
         buffer utilized after which the drop probability is 100 percent.
         This implies that all packets beyond this point will be
         dropped."
    DEFVAL { 10000 }
    ::= { tHsmdaSlopePolicyEntry 8 }

tHsmdaSlopeHiMaxProbability OBJECT-TYPE
    SYNTAX       Unsigned32 (1..10000)
    UNITS        "hundredths of a percent"
    MAX-ACCESS   read-create
    STATUS       current
    DESCRIPTION
        "The value of tHsmdaSlopeHiMaxProbability specifies the drop 
         probability, as a percentage, when the Hsmda queue depth reaches
         tHsmdaSlopeHiMaxDepth. The drop increases steadily from 0 at
         the tHsmdaSlopeHiStartDepth up to the tHsmdaSlopeHiMaxProbability
         at the tHsmdaSlopeHiMaxDepth."
    DEFVAL { 10000 }
    ::= { tHsmdaSlopePolicyEntry 9 }

tHsmdaSlopeLoAdminStatus OBJECT-TYPE
    SYNTAX       TmnxEnabledDisabled
    MAX-ACCESS   read-create
    STATUS       current
    DESCRIPTION
        "The value of tHsmdaSlopeLoAdminStatus specifies the admin state for
         the low priority RED slope. If the tHsmdaSlopeLoAdminStatus is set
         to 'disabled', the RED slope is inactive."
    DEFVAL { enabled }
    ::= { tHsmdaSlopePolicyEntry 10 }

tHsmdaSlopeLoStartDepth OBJECT-TYPE
    SYNTAX       Unsigned32 (1..10000)
    UNITS        "hundredths of a percent"
    MAX-ACCESS   read-create
    STATUS       current
    DESCRIPTION
        "The value of tHsmdaSlopeLoStartDepth specifies the percentage of the
         buffer utilized after which the drop probability starts to rise
         above 0."
    DEFVAL { 9000 }
    ::= { tHsmdaSlopePolicyEntry 11 }

tHsmdaSlopeLoMaxDepth OBJECT-TYPE
    SYNTAX       Unsigned32 (1..10000)
    UNITS        "hundredths of a percent"
    MAX-ACCESS   read-create
    STATUS       current
    DESCRIPTION
        "The value of tHsmdaSlopeLoMaxDepth specifies the percentage of the
         buffer utilized after which the drop probability is 100 percent.
         This implies that all packets beyond this point will be
         dropped."
    DEFVAL { 9000 }
    ::= { tHsmdaSlopePolicyEntry 12 }

tHsmdaSlopeLoMaxProbability OBJECT-TYPE
    SYNTAX       Unsigned32 (1..10000)
    UNITS        "hundredths of a percent"
    MAX-ACCESS   read-create
    STATUS       current
    DESCRIPTION
        "The value of tHsmdaSlopeLoMaxProbability specifies the drop 
         probability, as a percentage, when the Hsmda queue depth reaches
         tHsmdaSlopeLoMaxDepth. The drop increases steadily from 0 at
         the tHsmdaSlopeLoStartDepth up to the tHsmdaSlopeLoMaxProbability
         at the tHsmdaSlopeLoMaxDepth."
    DEFVAL { 10000 }
    ::= { tHsmdaSlopePolicyEntry 13 }

--
-- Scheduler policy table
--

tSchedulerPolicyTable OBJECT-TYPE
    SYNTAX       SEQUENCE OF TSchedulerPolicyEntry
    MAX-ACCESS   not-accessible
    STATUS       current
    DESCRIPTION
        " "
    ::= { tSchedulerObjects 1 }

tSchedulerPolicyEntry OBJECT-TYPE
    SYNTAX       TSchedulerPolicyEntry
    MAX-ACCESS   not-accessible
    STATUS       current
    DESCRIPTION
        "Information about a particular Scheduler Policy."
    INDEX { IMPLIED tSchedulerPolicyName }
    ::= { tSchedulerPolicyTable 1 }

TSchedulerPolicyEntry ::= SEQUENCE
    {
        tSchedulerPolicyName            TNamedItem,
        tSchedulerPolicyRowStatus       RowStatus,
        tSchedulerPolicyDescription     TItemDescription,
        tSchedulerPolicyLastChanged     TimeStamp,
        tSchedulerPolicyFrameBasedAccnt TruthValue,
        tSchedulerPolicyTier1ParentLoc  TmnxSchedPlcyParentLocation
    }

tSchedulerPolicyName OBJECT-TYPE
    SYNTAX       TNamedItem
    MAX-ACCESS   not-accessible
    STATUS       current
    DESCRIPTION
        "Name of the scheduler policy."
    ::= { tSchedulerPolicyEntry 1 }

tSchedulerPolicyRowStatus OBJECT-TYPE
    SYNTAX       RowStatus
    MAX-ACCESS   read-create
    STATUS       current
    DESCRIPTION
        "Row Status of the entry."
    ::= { tSchedulerPolicyEntry 2 }

tSchedulerPolicyDescription OBJECT-TYPE
    SYNTAX      TItemDescription
    MAX-ACCESS  read-create
    STATUS      current
    DESCRIPTION
        "Description for the scheduler policy"
    DEFVAL { ''H }
    ::= { tSchedulerPolicyEntry 3 }

tSchedulerPolicyLastChanged OBJECT-TYPE
    SYNTAX       TimeStamp
    MAX-ACCESS   read-only
    STATUS       current
    DESCRIPTION
        "timestamp of last change to this row in tSchedulerPolicyTable."
    ::= { tSchedulerPolicyEntry 4 }

tSchedulerPolicyFrameBasedAccnt OBJECT-TYPE
    SYNTAX       TruthValue
    MAX-ACCESS   read-create
    STATUS       current
    DESCRIPTION
        "The value of tSchedulerPolicyFrameBasedAccnt specifies whether
         to use frame-based accounting for the schedulers within the
         scheduler policy and the children queues parented to the
         scheduling policy.

         If the value is 'false', the default packet-based accounting
         method will be used."
    DEFVAL { false }
    ::= { tSchedulerPolicyEntry 5 }

tSchedulerPolicyTier1ParentLoc OBJECT-TYPE
    SYNTAX       TmnxSchedPlcyParentLocation
    MAX-ACCESS   read-create
    STATUS       current
    DESCRIPTION
        "The value of the object tSchedulerPolicyTier1ParentLoc specifies
         the location in which the tier 1 schedulers in this scheduler-policy
         will look to find their parent.
         
         The value of tSchedulerPolicyTier1ParentLoc has no effect 
         for schedulers with no parent configured (or which are port-parented).
         
         In case the parent scheduler is not found, the scheduler will be 
         orphaned."
    DEFVAL { none }
    ::= { tSchedulerPolicyEntry 6 }
    
--
-- Virtual Scheduler table
--

tVirtualSchedulerTable OBJECT-TYPE
    SYNTAX       SEQUENCE OF TVirtualSchedulerEntry
    MAX-ACCESS   not-accessible
    STATUS       current
    DESCRIPTION
        " "
    ::= { tSchedulerObjects 2 }

tVirtualSchedulerEntry OBJECT-TYPE
    SYNTAX       TVirtualSchedulerEntry
    MAX-ACCESS   not-accessible
    STATUS       current
    DESCRIPTION
        "Information about a particular Scheduler belonging to a Scheduler
        Policy."
    INDEX { tSchedulerPolicyName, tVirtualSchedulerTier,
            IMPLIED tVirtualSchedulerName }
    ::= { tVirtualSchedulerTable 1 }

TVirtualSchedulerEntry ::= SEQUENCE
    {
        tVirtualSchedulerTier          INTEGER,
        tVirtualSchedulerName          TNamedItem,
        tVirtualSchedulerRowStatus     RowStatus,
        tVirtualSchedulerDescription   TItemDescription,
        tVirtualSchedulerParent        TNamedItemOrEmpty,
        tVirtualSchedulerLevel         TLevel,
        tVirtualSchedulerWeight        TWeight,
        tVirtualSchedulerCIRLevel      TLevelOrDefault,
        tVirtualSchedulerCIRWeight     TWeight,
        tVirtualSchedulerPIR           THPolVirtualSchePIRRate,
        tVirtualSchedulerCIR           THPolVirtualScheCIRRate,
        tVirtualSchedulerSummedCIR     TruthValue,
        tVirtualSchedulerLastChanged   TimeStamp,
        tVirtualSchedulerUsePortParent TruthValue,
        tVirtualSchedulerPortLvl       TLevel,
        tVirtualSchedulerPortWght      TWeight,
        tVirtualSchedulerPortCIRLvl    TLevelOrDefault,
        tVirtualSchedulerPortCIRWght   TWeight,
        tVirtualSchedulerPIRHi         Unsigned32,
        tVirtualSchedulerPIRLo         Unsigned32,
        tVirtualSchedulerCIRHi         Unsigned32,
        tVirtualSchedulerCIRLo         Unsigned32,
        tVirtualSchedulerRateLUB       TruthValue
    }

tVirtualSchedulerTier OBJECT-TYPE
    SYNTAX       INTEGER (1..3)
    MAX-ACCESS   not-accessible
    STATUS       current
    DESCRIPTION
        "Tier to which this scheduler belongs to."
    ::= { tVirtualSchedulerEntry 1 }

tVirtualSchedulerName OBJECT-TYPE
    SYNTAX       TNamedItem
    MAX-ACCESS   not-accessible
    STATUS       current
    DESCRIPTION
        "Name of the scheduler policy."
    ::= { tVirtualSchedulerEntry 2 }

tVirtualSchedulerRowStatus OBJECT-TYPE
    SYNTAX       RowStatus
    MAX-ACCESS   read-create
    STATUS       current
    DESCRIPTION
        "Row Status of the entry."
    ::= { tVirtualSchedulerEntry 3 }

tVirtualSchedulerDescription OBJECT-TYPE
    SYNTAX       TItemDescription
    MAX-ACCESS   read-create
    STATUS       current
    DESCRIPTION
        "Description for the scheduler policy"
    DEFVAL { ''H }
    ::= { tVirtualSchedulerEntry 4 }

tVirtualSchedulerParent OBJECT-TYPE
    SYNTAX       TNamedItemOrEmpty
    MAX-ACCESS   read-create
    STATUS       current
    DESCRIPTION
        "The scheduler to which this scheduler would be feeding."
    DEFVAL { ''H }
    ::= { tVirtualSchedulerEntry 5 }

tVirtualSchedulerLevel OBJECT-TYPE
    SYNTAX  TLevel
    MAX-ACCESS   read-create
    STATUS       current
    DESCRIPTION
        "This specifies the level of priority while feeding the parent."
    DEFVAL { 1 }
    ::= { tVirtualSchedulerEntry 6 }

tVirtualSchedulerWeight OBJECT-TYPE
    SYNTAX       TWeight
    MAX-ACCESS   read-create
    STATUS       current
    DESCRIPTION
        "The weight that needs to be used by the scheduler to which this queue
         would be feeding."
    DEFVAL { 1 }
    ::= { tVirtualSchedulerEntry 7 }

tVirtualSchedulerCIRLevel OBJECT-TYPE
    SYNTAX  TLevelOrDefault
    MAX-ACCESS   read-create
    STATUS       current
    DESCRIPTION
        "This specifies the level of priority while feeding the parent.
         The level '0' means treat all offered load for this queue as for
         the above CIR traffic."
    DEFVAL { 0 }
    ::= { tVirtualSchedulerEntry 8 }

tVirtualSchedulerCIRWeight OBJECT-TYPE
    SYNTAX       TWeight
    MAX-ACCESS   read-create
    STATUS       current
    DESCRIPTION
        "The weight that needs to be used until the committed rate by the
         scheduler to which this queue would be feeding."
    DEFVAL { 1 }
    ::= { tVirtualSchedulerEntry 9 }

tVirtualSchedulerPIR OBJECT-TYPE
    SYNTAX       THPolVirtualSchePIRRate
    UNITS        "kbps"
    MAX-ACCESS   read-create
    STATUS       obsolete
    DESCRIPTION
        "The rate allowed for this scheduler. A value of -1 implies
         maximum.

         This object is obsoleted in 11.0 Release. It is replaced by 
         tVirtualSchedulerPIRHi and tVirtualSchedulerPIRLo."
    DEFVAL { -1 }
    ::= { tVirtualSchedulerEntry 10 }

tVirtualSchedulerCIR OBJECT-TYPE
    SYNTAX       THPolVirtualScheCIRRate
    UNITS        "kbps"
    MAX-ACCESS   read-create
    STATUS       obsolete
    DESCRIPTION
        "The rate allowed for this scheduler. A value of -1 implies
         maximum.
      
         This object is obsoleted in 11.0 Release. It is replaced by 
         tVirtualSchedulerCIRHi and tVirtualSchedulerCIRLo."
    DEFVAL { 0 }
    ::= { tVirtualSchedulerEntry 11 }

tVirtualSchedulerSummedCIR OBJECT-TYPE
    SYNTAX       TruthValue
    MAX-ACCESS   read-create
    STATUS       current
    DESCRIPTION
        "tVirtualSchedulerSummedCIR specifies if the CIR should be
         used as the summed value of the children. If set to 'true',
         tVirtualSchedulerCIR loses its meaning."
    DEFVAL { true }
    ::= { tVirtualSchedulerEntry 12 }

tVirtualSchedulerLastChanged OBJECT-TYPE
    SYNTAX       TimeStamp
    MAX-ACCESS   read-only
    STATUS       current
    DESCRIPTION
        "The value of the object tVirtualSchedulerLastChanged indicates the
         timestamp of last change to this row in tVirtualSchedulerTable."
    ::= { tVirtualSchedulerEntry 13 }

tVirtualSchedulerUsePortParent  OBJECT-TYPE
    SYNTAX      TruthValue
    MAX-ACCESS  read-create
    STATUS      current
    DESCRIPTION
        "The value of the object tVirtualSchedulerUsePortParent specifies
         whether this scheduler is parented by a port-level scheduler. When
         the value is 'true', this virtual scheduler is parented by a 
         port-level scheduler. This object is mutually exclusive with 
         tVirtualSchedulerParent. Only one kind of parent is allowed."
    DEFVAL      { false }
    ::= { tVirtualSchedulerEntry 14 }

tVirtualSchedulerPortLvl        OBJECT-TYPE
    SYNTAX       TLevel
    MAX-ACCESS  read-create
    STATUS      current
    DESCRIPTION
        "The value of the object tVirtualSchedulerPortLvl specifies the
         port priority this scheduler will use to receive bandwidth from
         the port-level scheduler for its above-cir offered load."
    DEFVAL      { 1 }
    ::= { tVirtualSchedulerEntry 15 }

tVirtualSchedulerPortWght       OBJECT-TYPE
    SYNTAX      TWeight
    MAX-ACCESS  read-create
    STATUS      current
    DESCRIPTION
        "The value of the object tVirtualSchedulerPortWght specifies the
         weight this scheduler will use to receive bandwidth from the
         port-level scheduler for its above-cir offered load."
    DEFVAL      { 1 }
    ::= { tVirtualSchedulerEntry 16 }

tVirtualSchedulerPortCIRLvl     OBJECT-TYPE
    SYNTAX      TLevelOrDefault
    MAX-ACCESS  read-create
    STATUS      current
    DESCRIPTION
        "The value of the object tVirtualSchedulerPortCIRLvl specifies the
         port priority this scheduler will use to receive bandwidth from
         the port-level scheduler for its within-cir offered load."
    DEFVAL      { 0 }
    ::= { tVirtualSchedulerEntry 17 }

tVirtualSchedulerPortCIRWght    OBJECT-TYPE
    SYNTAX      TWeight
    MAX-ACCESS  read-create
    STATUS      current
    DESCRIPTION
        "The value of the object tVirtualSchedulerPortCIRWght specifies the
         weight this scheduler will use to receive bandwidth from the
         port-level scheduler for its within-cir offered load."
    DEFVAL      { 0 }
    ::= { tVirtualSchedulerEntry 18 }

tVirtualSchedulerPIRHi OBJECT-TYPE
    SYNTAX       Unsigned32 (0 | 4294967295)
    UNITS        "kbps"
    MAX-ACCESS   read-create
    STATUS       current
    DESCRIPTION
        "The value of tVirtualSchedulerPIRHi indicates upper 32 bits of the
         pir-rate allowed for this scheduler.    

         This value should always be set along with tVirtualSchedulerPIRLo,
         otherwise an 'inconsistentValue' error is returned.

         When the value of tVirtualSchedulerPIRHi along with the value of
         tVirtualSchedulerPIRLo is set to 4294967295 (0xFFFFFFFF), rate
         for this scheduler indicates maximum rate."
    DEFVAL { 4294967295 }
    ::= { tVirtualSchedulerEntry 19 }

tVirtualSchedulerPIRLo OBJECT-TYPE
    SYNTAX       Unsigned32 (1..3200000000 | 4294967295)
    UNITS        "kbps"
    MAX-ACCESS   read-create
    STATUS       current
    DESCRIPTION
        "The value of tVirtualSchedulerPIRHi indicates lower 32 bits of the 
         pir-rate allowed for this scheduler.    
    
         This value should always be set along with tVirtualSchedulerPIRHi,
         otherwise an 'inconsistentValue' error is returned.
            
         When the value of tVirtualSchedulerPIRHi along with the value of
         tVirtualSchedulerPIRLo is set to 4294967295 (0xFFFFFFFF), rate
         for this scheduler indicates maximum rate."
    DEFVAL { 4294967295 }
    ::= { tVirtualSchedulerEntry 20 }

tVirtualSchedulerCIRHi OBJECT-TYPE
    SYNTAX       Unsigned32 (0 | 4294967295)
    UNITS        "kbps"
    MAX-ACCESS   read-create
    STATUS       current
    DESCRIPTION
        "The value of tVirtualSchedulerCIRHi indicates upper 32 bits of the 
         cir-rate allowed for this scheduler.    
        
         This value should always be set along with tVirtualSchedulerCIRLo,
         otherwise an 'inconsistentValue' error is returned.

         When the value of tVirtualSchedulerCIRHi along with the value of
         tVirtualSchedulerCIRLo is set to 4294967295 (0xFFFFFFFF), rate
         for this scheduler indicates maximum rate."
    DEFVAL { 0 }
    ::= { tVirtualSchedulerEntry 21 }

tVirtualSchedulerCIRLo OBJECT-TYPE
    SYNTAX       Unsigned32 (0..3200000000 | 4294967295)
    UNITS        "kbps"
    MAX-ACCESS   read-create
    STATUS       current
    DESCRIPTION
        "The value of tVirtualSchedulerCIRLo indicates lower 32 bits of the 
         cir-rate allowed for this scheduler.    
        
         This value should always be set along with tVirtualSchedulerCIRHi,
         otherwise an 'inconsistentValue' error is returned.

         When the value of tVirtualSchedulerCIRHi along with the value of
         tVirtualSchedulerCIRLo is set to 4294967295 (0xFFFFFFFF), rate
         for this scheduler indicates maximum rate."
    DEFVAL { 0 }
    ::= { tVirtualSchedulerEntry 22 }

tVirtualSchedulerRateLUB        OBJECT-TYPE
    SYNTAX       TruthValue
    MAX-ACCESS   read-create
    STATUS       current
    DESCRIPTION
        "The value of tVirtualSchedulerRateLUB specifies whether to limit the
         unused bandwidth and allow a tighter control in allocation of bandwidth
         by HQos.

         When the value of tVirtualSchedulerRateLUB is set to 'true', HQos
         algorithm distributes any unused aggregate bandwidth between queues
         operating below their fair share rates. This allows a simplified
         aggregate rate protection while allocating bandwidth by HQos scheduling
         algorithm."
    DEFVAL { false }
    ::= { tVirtualSchedulerEntry 23 }


--
--  Port Scheduler plcy table
--

tPortSchedulerPlcyTable       OBJECT-TYPE
    SYNTAX      SEQUENCE OF TPortSchedulerPlcyEntry
    MAX-ACCESS  not-accessible
    STATUS      current
    DESCRIPTION
        "The tPortSchedulerPlcyTable has an entry for each port scheduler
         configured on this system."
    ::= { tSchedulerObjects 3 }

tPortSchedulerPlcyEntry       OBJECT-TYPE
    SYNTAX      TPortSchedulerPlcyEntry
    MAX-ACCESS  not-accessible
    STATUS      current
    DESCRIPTION
        "Each row represents a particular port scheduler. Entries are created
         and deleted by the user."
    INDEX { IMPLIED tPortSchedulerPlcyName }
    ::= { tPortSchedulerPlcyTable 1 }

TPortSchedulerPlcyEntry ::= SEQUENCE
    {
        tPortSchedulerPlcyName                  TNamedItem,
        tPortSchedulerPlcyRowStatus             RowStatus,
        tPortSchedulerPlcyDescription           TItemDescription,
        tPortSchedulerPlcyLastChanged           TimeStamp,
        tPortSchedulerPlcyMaxRate               TPortSchedulerPIRRate,
        tPortSchedulerPlcyLvl1PIR               TPortSchedulerPIRRate,
        tPortSchedulerPlcyLvl1CIR               TPortSchedulerCIR,
        tPortSchedulerPlcyLvl2PIR               TPortSchedulerPIRRate,
        tPortSchedulerPlcyLvl2CIR               TPortSchedulerCIR,
        tPortSchedulerPlcyLvl3PIR               TPortSchedulerPIRRate,
        tPortSchedulerPlcyLvl3CIR               TPortSchedulerCIR,
        tPortSchedulerPlcyLvl4PIR               TPortSchedulerPIRRate,
        tPortSchedulerPlcyLvl4CIR               TPortSchedulerCIR,
        tPortSchedulerPlcyLvl5PIR               TPortSchedulerPIRRate,
        tPortSchedulerPlcyLvl5CIR               TPortSchedulerCIR,
        tPortSchedulerPlcyLvl6PIR               TPortSchedulerPIRRate,
        tPortSchedulerPlcyLvl6CIR               TPortSchedulerCIR,
        tPortSchedulerPlcyLvl7PIR               TPortSchedulerPIRRate,
        tPortSchedulerPlcyLvl7CIR               TPortSchedulerCIR,
        tPortSchedulerPlcyLvl8PIR               TPortSchedulerPIRRate,
        tPortSchedulerPlcyLvl8CIR               TPortSchedulerCIR,
        tPortSchedulerPlcyOrphanLvl             TLevel,
        tPortSchedulerPlcyOrphanWeight          TWeight,
        tPortSchedulerPlcyOrphanCIRLvl          TLevelOrDefault,
        tPortSchedulerPlcyOrphanCIRWght         TWeight,
        tPortSchedPlcyDistLagRateShared         TruthValue,
        tPortSchedPlcyMaxRatePercent            Unsigned32,
        tPortSchedPlcyMaxRateType               TPSPRateType,
        tPortSchedPlcyLvl1PIRPercent            Unsigned32,
        tPortSchedPlcyLvl1CIRPercent            Unsigned32,
        tPortSchedPlcyLvl1RateType              TPSPRateType,
        tPortSchedPlcyLvl2PIRPercent            Unsigned32,
        tPortSchedPlcyLvl2CIRPercent            Unsigned32,
        tPortSchedPlcyLvl2RateType              TPSPRateType,
        tPortSchedPlcyLvl3PIRPercent            Unsigned32,
        tPortSchedPlcyLvl3CIRPercent            Unsigned32,
        tPortSchedPlcyLvl3RateType              TPSPRateType,
        tPortSchedPlcyLvl4PIRPercent            Unsigned32,
        tPortSchedPlcyLvl4CIRPercent            Unsigned32,
        tPortSchedPlcyLvl4RateType              TPSPRateType,
        tPortSchedPlcyLvl5PIRPercent            Unsigned32,
        tPortSchedPlcyLvl5CIRPercent            Unsigned32,
        tPortSchedPlcyLvl5RateType              TPSPRateType,
        tPortSchedPlcyLvl6PIRPercent            Unsigned32,
        tPortSchedPlcyLvl6CIRPercent            Unsigned32,
        tPortSchedPlcyLvl6RateType              TPSPRateType,
        tPortSchedPlcyLvl7PIRPercent            Unsigned32,
        tPortSchedPlcyLvl7CIRPercent            Unsigned32,
        tPortSchedPlcyLvl7RateType              TPSPRateType,
        tPortSchedPlcyLvl8PIRPercent            Unsigned32,
        tPortSchedPlcyLvl8CIRPercent            Unsigned32,
        tPortSchedPlcyLvl8RateType              TPSPRateType,
        tPortSchedPlcyMaxRate                   Unsigned32
    }

tPortSchedulerPlcyName  OBJECT-TYPE
    SYNTAX      TNamedItem
    MAX-ACCESS  not-accessible
    STATUS      current
    DESCRIPTION
        "The value of tPortSchedulerPlcyName specifies the name of the port
         scheduler."
    ::= { tPortSchedulerPlcyEntry 1 } 

tPortSchedulerPlcyRowStatus     OBJECT-TYPE
    SYNTAX      RowStatus
    MAX-ACCESS  read-create
    STATUS      current
    DESCRIPTION
        "The value of tPortSchedulerPlcyRowStatus is used for the creation
         and deletion of port scheduler policies."
    ::= { tPortSchedulerPlcyEntry 2 } 
        
tPortSchedulerPlcyDescription   OBJECT-TYPE
    SYNTAX      TItemDescription
    MAX-ACCESS  read-create
    STATUS      current
    DESCRIPTION
        "The value of tPortSchedulerPlcyDescription specifies the description
         of this port scheduler."
    DEFVAL      { "" }
    ::= { tPortSchedulerPlcyEntry 3 } 

tPortSchedulerPlcyLastChanged        OBJECT-TYPE
    SYNTAX      TimeStamp
    MAX-ACCESS  read-only
    STATUS      current
    DESCRIPTION
        "The value of tPortSchedulerPlcyLastChanged indicates the value of 
         sysUpTime at the time of the most recent management change to this
         row."
    ::= { tPortSchedulerPlcyEntry 4 }

tPortSchedulerPlcyMaxRate        OBJECT-TYPE
    SYNTAX      TPortSchedulerPIRRate
    UNITS       "kbps"
    MAX-ACCESS  read-create
    STATUS      obsolete
    DESCRIPTION
        "The value of tPortSchedulerPlcyMaxRate specifies the explicit maximum
         frame based bandwidth limit of this port scheduler.

         An 'inconsistentValue' error is returned if tPortSchedulerPlcyMaxRate
         is set to non-default value when the value of
         tPortSchedPlcyMaxRateType is set to 'percentLagActive'.

         This object is obsoleted in 13.0 release and replaced by
         tPortSchedPlcyMaxRate."
    DEFVAL      { -1 }
    ::= { tPortSchedulerPlcyEntry 5 }

tPortSchedulerPlcyLvl1PIR        OBJECT-TYPE
    SYNTAX      TPortSchedulerPIRRate
    UNITS       "kbps"
    MAX-ACCESS  read-create
    STATUS      obsolete
    DESCRIPTION
        "The value of tPortSchedulerPlcyLvl1PIR specifies the total bandwidth
         limit, PIR, for priority level 1.

         An 'inconsistentValue' error is returned if tPortSchedulerPlcyLvl1PIR
         is set to non-default value when the value of
         tPortSchedPlcyLvl1RateType is set to 'percentLocal'.

         This object is obsoleted in 13.0 release and replaced by
         tPortSchedPolicyLevelPIR."
    DEFVAL      { -1 }
    ::= { tPortSchedulerPlcyEntry 6 }

tPortSchedulerPlcyLvl1CIR        OBJECT-TYPE
    SYNTAX      TPortSchedulerCIR
    UNITS       "kbps"
    MAX-ACCESS  read-create
    STATUS      obsolete
    DESCRIPTION
        "The value of tPortSchedulerPlcyLvl1CIR specifies the within-cir
         bandwidth limit for priority level 1.

         An 'inconsistentValue' error is returned if tPortSchedulerPlcyLvl1CIR
         is set to non-default value when the value of
         tPortSchedPlcyLvl1RateType is set to 'percentLocal'.

         This object is obsoleted in 13.0 release and replaced by
         tPortSchedPolicyLevelCIR."
    DEFVAL      { -1 }
    ::= { tPortSchedulerPlcyEntry 7 }

tPortSchedulerPlcyLvl2PIR        OBJECT-TYPE
    SYNTAX      TPortSchedulerPIRRate
    UNITS       "kbps"
    MAX-ACCESS  read-create
    STATUS      obsolete
    DESCRIPTION
        "The value of tPortSchedulerPlcyLvl2PIR specifies the total bandwidth
         limit, PIR, for priority level 2.

         An 'inconsistentValue' error is returned if tPortSchedulerPlcyLvl2PIR
         is set to non-default value when the value of
         tPortSchedPlcyLvl2RateType is set to 'percentLocal'.

         This object is obsoleted in 13.0 release and replaced by
         tPortSchedPolicyLevelPIR."
    DEFVAL      { -1 }
    ::= { tPortSchedulerPlcyEntry 8 }

tPortSchedulerPlcyLvl2CIR        OBJECT-TYPE
    SYNTAX      TPortSchedulerCIR
    UNITS       "kbps"
    MAX-ACCESS  read-create
    STATUS      obsolete
    DESCRIPTION
        "The value of tPortSchedulerPlcyLvl2CIR specifies the within-cir
         bandwidth limit for priority level 2.

         An 'inconsistentValue' error is returned if tPortSchedulerPlcyLvl2CIR
         is set to non-default value when the value of
         tPortSchedPlcyLvl2RateType is set to 'percentLocal'.

         This object is obsoleted in 13.0 release and replaced by
         tPortSchedPolicyLevelCIR."
    DEFVAL      { -1 }
    ::= { tPortSchedulerPlcyEntry 9 }

tPortSchedulerPlcyLvl3PIR        OBJECT-TYPE
    SYNTAX      TPortSchedulerPIRRate
    UNITS       "kbps"
    MAX-ACCESS  read-create
    STATUS      obsolete
    DESCRIPTION
        "The value of tPortSchedulerPlcyLvl3PIR specifies the total bandwidth
         limit, PIR, for priority level 3.

         An 'inconsistentValue' error is returned if tPortSchedulerPlcyLvl3PIR
         is set to non-default value when the value of
         tPortSchedPlcyLvl3RateType is set to 'percentLocal'.

         This object is obsoleted in 13.0 release and replaced by
         tPortSchedPolicyLevelPIR."
    DEFVAL      { -1 }
    ::= { tPortSchedulerPlcyEntry 10 }

tPortSchedulerPlcyLvl3CIR        OBJECT-TYPE
    SYNTAX      TPortSchedulerCIR
    UNITS       "kbps"
    MAX-ACCESS  read-create
    STATUS      obsolete
    DESCRIPTION
        "The value of tPortSchedulerPlcyLvl3CIR specifies the within-cir
         bandwidth limit for priority level 3.

         An 'inconsistentValue' error is returned if tPortSchedulerPlcyLvl3CIR
         is set to non-default value when the value of
         tPortSchedPlcyLvl3RateType is set to 'percentLocal'.

         This object is obsoleted in 13.0 release and replaced by
         tPortSchedPolicyLevelCIR."
    DEFVAL      { -1 }
    ::= { tPortSchedulerPlcyEntry 11 }

tPortSchedulerPlcyLvl4PIR        OBJECT-TYPE
    SYNTAX      TPortSchedulerPIRRate
    UNITS       "kbps"
    MAX-ACCESS  read-create
    STATUS      obsolete
    DESCRIPTION
        "The value of tPortSchedulerPlcyLvl4PIR specifies the total bandwidth
         limit, PIR, for priority level 4.

         An 'inconsistentValue' error is returned if tPortSchedulerPlcyLvl4PIR
         is set to non-default value when the value of
         tPortSchedPlcyLvl4RateType is set to 'percentLocal'.

         This object is obsoleted in 13.0 release and replaced by
         tPortSchedPolicyLevelPIR."
    DEFVAL      { -1 }
    ::= { tPortSchedulerPlcyEntry 12 }

tPortSchedulerPlcyLvl4CIR        OBJECT-TYPE
    SYNTAX      TPortSchedulerCIR
    UNITS       "kbps"
    MAX-ACCESS  read-create
    STATUS      obsolete
    DESCRIPTION
        "The value of tPortSchedulerPlcyLvl4CIR specifies the within-cir
         bandwidth limit for priority level 4.

         An 'inconsistentValue' error is returned if tPortSchedulerPlcyLvl4CIR
         is set to non-default value when the value of
         tPortSchedPlcyLvl4RateType is set to 'percentLocal'.

         This object is obsoleted in 13.0 release and replaced by
         tPortSchedPolicyLevelCIR."
    DEFVAL      { -1 }
    ::= { tPortSchedulerPlcyEntry 13 }

tPortSchedulerPlcyLvl5PIR        OBJECT-TYPE
    SYNTAX      TPortSchedulerPIRRate
    UNITS       "kbps"
    MAX-ACCESS  read-create
    STATUS      obsolete
    DESCRIPTION
        "The value of tPortSchedulerPlcyLvl5PIR specifies the total bandwidth
         limit, PIR, for priority level 5.

         An 'inconsistentValue' error is returned if tPortSchedulerPlcyLvl5PIR
         is set to non-default value when the value of
         tPortSchedPlcyLvl5RateType is set to 'percentLocal'.

         This object is obsoleted in 13.0 release and replaced by
         tPortSchedPolicyLevelPIR."
    DEFVAL      { -1 }
    ::= { tPortSchedulerPlcyEntry 14 }

tPortSchedulerPlcyLvl5CIR        OBJECT-TYPE
    SYNTAX      TPortSchedulerCIR
    UNITS       "kbps"
    MAX-ACCESS  read-create
    STATUS      obsolete
    DESCRIPTION
        "The value of tPortSchedulerPlcyLvl5CIR specifies the within-cir
         bandwidth limit for priority level 5.

         An 'inconsistentValue' error is returned if tPortSchedulerPlcyLvl5CIR
         is set to non-default value when the value of
         tPortSchedPlcyLvl5RateType is set to 'percentLocal'.

         This object is obsoleted in 13.0 release and replaced by
         tPortSchedPolicyLevelCIR."
    DEFVAL      { -1 }
    ::= { tPortSchedulerPlcyEntry 15 }

tPortSchedulerPlcyLvl6PIR        OBJECT-TYPE
    SYNTAX      TPortSchedulerPIRRate
    UNITS       "kbps"
    MAX-ACCESS  read-create
    STATUS      obsolete
    DESCRIPTION
        "The value of tPortSchedulerPlcyLvl6PIR specifies the total bandwidth
         limit, PIR, for priority level 6.

         An 'inconsistentValue' error is returned if tPortSchedulerPlcyLvl6PIR
         is set to non-default value when the value of
         tPortSchedPlcyLvl6RateType is set to 'percentLocal'.

         This object is obsoleted in 13.0 release and replaced by
         tPortSchedPolicyLevelPIR."
    DEFVAL      { -1 }
    ::= { tPortSchedulerPlcyEntry 16 }

tPortSchedulerPlcyLvl6CIR        OBJECT-TYPE
    SYNTAX      TPortSchedulerCIR
    UNITS       "kbps"
    MAX-ACCESS  read-create
    STATUS      obsolete
    DESCRIPTION
        "The value of tPortSchedulerPlcyLvl6CIR specifies the within-cir
         bandwidth limit for priority level 6.

         An 'inconsistentValue' error is returned if tPortSchedulerPlcyLvl6CIR
         is set to non-default value when the value of
         tPortSchedPlcyLvl6RateType is set to 'percentLocal'.

         This object is obsoleted in 13.0 release and replaced by
         tPortSchedPolicyLevelCIR."
    DEFVAL      { -1 }
    ::= { tPortSchedulerPlcyEntry 17 }

tPortSchedulerPlcyLvl7PIR        OBJECT-TYPE
    SYNTAX      TPortSchedulerPIRRate
    UNITS       "kbps"
    MAX-ACCESS  read-create
    STATUS      obsolete
    DESCRIPTION
        "The value of tPortSchedulerPlcyLvl7PIR specifies the total bandwidth
         limit, PIR, for priority level 7.

         An 'inconsistentValue' error is returned if tPortSchedulerPlcyLvl7PIR
         is set to non-default value when the value of
         tPortSchedPlcyLvl7RateType is set to 'percentLocal'.

         This object is obsoleted in 13.0 release and replaced by
         tPortSchedPolicyLevelPIR."
    DEFVAL      { -1 }
    ::= { tPortSchedulerPlcyEntry 18 }

tPortSchedulerPlcyLvl7CIR        OBJECT-TYPE
    SYNTAX      TPortSchedulerCIR
    UNITS       "kbps"
    MAX-ACCESS  read-create
    STATUS      obsolete
    DESCRIPTION
        "The value of tPortSchedulerPlcyLvl7CIR specifies the within-cir
         bandwidth limit for priority level 7.

         An 'inconsistentValue' error is returned if tPortSchedulerPlcyLvl7CIR
         is set to non-default value when the value of
         tPortSchedPlcyLvl7RateType is set to 'percentLocal'.

         This object is obsoleted in 13.0 release and replaced by
         tPortSchedPolicyLevelCIR."
    DEFVAL      { -1 }
    ::= { tPortSchedulerPlcyEntry 19 }

tPortSchedulerPlcyLvl8PIR        OBJECT-TYPE
    SYNTAX      TPortSchedulerPIRRate
    UNITS       "kbps"
    MAX-ACCESS  read-create
    STATUS      obsolete
    DESCRIPTION
        "The value of tPortSchedulerPlcyLvl8PIR specifies the total bandwidth
         limit, PIR, for priority level 8.

         An 'inconsistentValue' error is returned if tPortSchedulerPlcyLvl8PIR
         is set to non-default value when the value of
         tPortSchedPlcyLvl8RateType is set to 'percentLocal'.

         This object is obsoleted in 13.0 release and replaced by
         tPortSchedPolicyLevelPIR."
    DEFVAL      { -1 }
    ::= { tPortSchedulerPlcyEntry 20 }

tPortSchedulerPlcyLvl8CIR        OBJECT-TYPE
    SYNTAX      TPortSchedulerCIR
    UNITS       "kbps"
    MAX-ACCESS  read-create
    STATUS      obsolete
    DESCRIPTION
        "The value of tPortSchedulerPlcyLvl8CIR specifies the within-cir
         bandwidth limit for priority level 8.

         An 'inconsistentValue' error is returned if tPortSchedulerPlcyLvl8CIR
         is set to non-default value when the value of
         tPortSchedPlcyLvl8RateType is set to 'percentLocal'.

         This object is obsoleted in 13.0 release and replaced by
         tPortSchedPolicyLevelCIR."
    DEFVAL      { -1 }
    ::= { tPortSchedulerPlcyEntry 21 }

tPortSchedulerPlcyOrphanLvl        OBJECT-TYPE
    SYNTAX      TLevel
    MAX-ACCESS  read-create
    STATUS      current
    DESCRIPTION
        "The value of tPortSchedulerPlcyOrphanLvl specifies the port priority
         of orphaned queues and schedulers that are above-cir."
    DEFVAL      { 1 }
    ::= { tPortSchedulerPlcyEntry 22 }

tPortSchedulerPlcyOrphanWeight        OBJECT-TYPE
    SYNTAX      TWeight
    MAX-ACCESS  read-create
    STATUS      current
    DESCRIPTION
        "The value of tPortSchedulerPlcyOrphanWeight specifies the weight of
         orphaned queues and schedulers that are above-cir."
    DEFVAL      { 0 } 
    ::= { tPortSchedulerPlcyEntry 23 }

tPortSchedulerPlcyOrphanCIRLvl        OBJECT-TYPE
    SYNTAX      TLevelOrDefault
    MAX-ACCESS  read-create
    STATUS      current
    DESCRIPTION
        "The value of tPortSchedulerPlcyOrphanCIRLvl specifies the port priority
         of orphaned queues and schedulers that are within-cir."
    DEFVAL      { 0 }
    ::= { tPortSchedulerPlcyEntry 24 }

tPortSchedulerPlcyOrphanCIRWght        OBJECT-TYPE
    SYNTAX      TWeight
    MAX-ACCESS  read-create
    STATUS      current
    DESCRIPTION
        "The value of tPortSchedulerPlcyOrphanCIRWght specifies the weight of
         orphaned queues and schedulers that are within-cir."
    DEFVAL      { 0 }
    ::= { tPortSchedulerPlcyEntry 25 }

tPortSchedPlcyDistLagRateShared        OBJECT-TYPE
    SYNTAX      TruthValue
    MAX-ACCESS  read-create
    STATUS      current
    DESCRIPTION
        "The value of tPortSchedPlcyDistLagRateShared specifies whether to
         enable sharing of rates when the port on which this
         port-scheduler-policy is configured is part of a LAG configured in
         'distribute' mode.

         When the value of tPortSchedPlcyDistLagRateShared is set to 'true', the
         absolute rate values configured as part of the max-rate, PIR/CIR group
         rates and PIR/CIR level rates are shared across the member ports of the
         LAG when configured in 'distribute' mode.

         The value of tPortSchedPlcyDistLagRateShared does not have any affect
         when the port on which this port-scheduler-policy is configured is part
         of a LAG in 'link' mode. Similarly when rates are configured as
         percent-active rates, i.e., rate-type is 'percentActivePortBW'
         the value of this object is irrelevant."
    DEFVAL { false }
    ::= { tPortSchedulerPlcyEntry 26 }

tPortSchedPlcyMaxRatePercent           OBJECT-TYPE
    SYNTAX      Unsigned32 (1..10000)
    UNITS       "hundredths of a percent"
    MAX-ACCESS  read-create
    STATUS      current
    DESCRIPTION
        "The value of tPortSchedPlcyMaxRatePercent specifies the explicit
         maximum frame based bandwidth percentage, in hudredths of a percent,
         for this port scheduler.

         An 'inconsistentValue' error is returned if
         tPortSchedPlcyMaxRatePercent is set to non-default value when the
         object tPortSchedPlcyMaxRateType is set to 'kbps'."
    DEFVAL { 10000 }
    ::= { tPortSchedulerPlcyEntry 27 }

tPortSchedPlcyMaxRateType              OBJECT-TYPE
    SYNTAX      TPSPRateType (1|3)
    MAX-ACCESS  read-create
    STATUS      current
    DESCRIPTION
        "The value of tPortSchedPlcyMaxRateType specifies the type of port
         scheduler rate.
         
         When the value of tPortSchedPlcyMaxRateType is set to 'kbps', the
         port scheduler max-rate is specified in 'kbps'. The value of
         tPortSchedPlcyMaxRatePercent will be set to default value.

         When the value of tPortSchedPlcyMaxRateType is set to
         'percentLagActive', the port scheduler max-rate is specified in
         percentage of active port bandwidth. The value of
         tPortSchedulerPlcyMaxRate will be set to default value."
    DEFVAL { kbps }
    ::= { tPortSchedulerPlcyEntry 28 }

tPortSchedPlcyLvl1PIRPercent       OBJECT-TYPE
    SYNTAX      Unsigned32 (1..10000)
    UNITS       "hundredths of a percent"
    MAX-ACCESS  read-create
    STATUS      obsolete
    DESCRIPTION
        "The value of tPortSchedPlcyLvl1PIRPercent specifies the total
         bandwidth percentage, PIR percent, for priority level 1.

         An 'inconsistentValue' error is returned if
         tPortSchedPlcyLvl1PIRPercent is set to non-default value when the
         object tPortSchedPlcyLvl1RateType is set to 'kbps'.

         This object is obsoleted in 13.0 release and replaced by
         tPortSchedPolicyLevelPIRPercent."
    DEFVAL { 10000 }
    ::= { tPortSchedulerPlcyEntry 29 }

tPortSchedPlcyLvl1CIRPercent       OBJECT-TYPE
    SYNTAX      Unsigned32 (0..10000)
    UNITS       "hundredths of a percent"
    MAX-ACCESS  read-create
    STATUS      obsolete
    DESCRIPTION
        "The value of tPortSchedPlcyLvl1CIRPercent specifies the within-cir
         bandwidth percentage, for priority level 1.

         An 'inconsistentValue' error is returned if
         tPortSchedPlcyLvl1CIRPercent is set to non-default value when the
         object tPortSchedPlcyLvl1RateType is set to 'kbps'.

         This object is obsoleted in 13.0 release and replaced by
         tPortSchedPolicyLevelCIRPercent."
    DEFVAL { 10000 }
    ::= { tPortSchedulerPlcyEntry 30 }

tPortSchedPlcyLvl1RateType             OBJECT-TYPE
    SYNTAX      TPSPRateType (1|2)
    MAX-ACCESS  read-create
    STATUS      obsolete
    DESCRIPTION
        "The value of tPortSchedPlcyLvl1RateType specifies the type of port
         scheduler rate for priority level 1.
         
         When the value of tPortSchedPlcyLvl1RateType is set to 'kbps', the
         port scheduler rate for priority level 1 is specified in 'kbps'. The
         values of tPortSchedPlcyLvl1PIRPercent and 
         tPortSchedPlcyLvl1CIRPercent will be set to their default values.

         When the value of tPortSchedPlcyLvl1RateType is set to
         'percentLocal', the port scheduler rate for priority level 1 
         is specified in percentage of local limit. The values of
         tPortSchedulerPlcyLvl1PIR and tPortSchedulerPlcyLvl1CIR will be set to
         their default values.

         This object is obsoleted in 13.0 release and replaced by
         tPortSchedPolicyLevelRateType."
    DEFVAL { kbps }
    ::= { tPortSchedulerPlcyEntry 31 }

tPortSchedPlcyLvl2PIRPercent       OBJECT-TYPE
    SYNTAX      Unsigned32 (1..10000)
    UNITS       "hundredths of a percent"
    MAX-ACCESS  read-create
    STATUS      obsolete
    DESCRIPTION
        "The value of tPortSchedPlcyLvl2PIRPercent specifies the total
         bandwidth percentage, PIR percent, for priority level 2.

         An 'inconsistentValue' error is returned if
         tPortSchedPlcyLvl2PIRPercent is set to non-default value when the
         object tPortSchedPlcyLvl2RateType is set to 'kbps'.

         This object is obsoleted in 13.0 release and replaced by
         tPortSchedPolicyLevelPIRPercent."
    DEFVAL { 10000 }
    ::= { tPortSchedulerPlcyEntry 32 }

tPortSchedPlcyLvl2CIRPercent       OBJECT-TYPE
    SYNTAX      Unsigned32 (0..10000)
    UNITS       "hundredths of a percent"
    MAX-ACCESS  read-create
    STATUS      obsolete
    DESCRIPTION
        "The value of tPortSchedPlcyLvl2CIRPercent specifies the within-cir
         bandwidth percentage, for priority level 2.

         An 'inconsistentValue' error is returned if
         tPortSchedPlcyLvl2CIRPercent is set to non-default value when the
         object tPortSchedPlcyLvl2RateType is set to 'kbps'.

         This object is obsoleted in 13.0 release and replaced by
         tPortSchedPolicyLevelCIRPercent."
    DEFVAL { 10000 }
    ::= { tPortSchedulerPlcyEntry 33 }

tPortSchedPlcyLvl2RateType             OBJECT-TYPE
    SYNTAX      TPSPRateType (1|2)
    MAX-ACCESS  read-create
    STATUS      obsolete
    DESCRIPTION
        "The value of tPortSchedPlcyLvl2RateType specifies the type of port
         scheduler rate for priority level 2.
         
         When the value of tPortSchedPlcyLvl2RateType is set to 'kbps', the
         port scheduler rate for priority level 2 is specified in 'kbps'. The
         values of tPortSchedPlcyLvl2PIRPercent and 
         tPortSchedPlcyLvl2CIRPercent will be set to their default values.

         When the value of tPortSchedPlcyLvl2RateType is set to
         'percentLocal', the port scheduler rate for priority level 2 
         is specified in percentage of local limit. The values of
         tPortSchedulerPlcyLvl2PIR and tPortSchedulerPlcyLvl2CIR will be set to
         their default values.

         This object is obsoleted in 13.0 release and replaced by
         tPortSchedPolicyLevelRateType."
    DEFVAL { kbps }
    ::= { tPortSchedulerPlcyEntry 34 }

tPortSchedPlcyLvl3PIRPercent       OBJECT-TYPE
    SYNTAX      Unsigned32 (1..10000)
    UNITS       "hundredths of a percent"
    MAX-ACCESS  read-create
    STATUS      obsolete
    DESCRIPTION
        "The value of tPortSchedPlcyLvl3PIRPercent specifies the total
         bandwidth percentage, PIR percent, for priority level 3.

         An 'inconsistentValue' error is returned if
         tPortSchedPlcyLvl3PIRPercent is set to non-default value when the
         object tPortSchedPlcyLvl3RateType is set to 'kbps'.

         This object is obsoleted in 13.0 release and replaced by
         tPortSchedPolicyLevelPIRPercent."
    DEFVAL { 10000 }
    ::= { tPortSchedulerPlcyEntry 35 }

tPortSchedPlcyLvl3CIRPercent       OBJECT-TYPE
    SYNTAX      Unsigned32 (0..10000)
    UNITS       "hundredths of a percent"
    MAX-ACCESS  read-create
    STATUS      obsolete
    DESCRIPTION
        "The value of tPortSchedPlcyLvl3CIRPercent specifies the within-cir
         bandwidth percentage, for priority level 3.

         An 'inconsistentValue' error is returned if
         tPortSchedPlcyLvl3CIRPercent is set to non-default value when the
         object tPortSchedPlcyLvl3RateType is set to 'kbps'.

         This object is obsoleted in 13.0 release and replaced by
         tPortSchedPolicyLevelCIRPercent."
    DEFVAL { 10000 }
    ::= { tPortSchedulerPlcyEntry 36 }

tPortSchedPlcyLvl3RateType             OBJECT-TYPE
    SYNTAX      TPSPRateType (1|2)
    MAX-ACCESS  read-create
    STATUS      obsolete
    DESCRIPTION
        "The value of tPortSchedPlcyLvl3RateType specifies the type of port
         scheduler rate for priority level 3.
         
         When the value of tPortSchedPlcyLvl3RateType is set to 'kbps', the
         port scheduler rate for priority level 3 is specified in 'kbps'. The
         values of tPortSchedPlcyLvl3PIRPercent and 
         tPortSchedPlcyLvl3CIRPercent will be set to their default values.

         When the value of tPortSchedPlcyLvl3RateType is set to
         'percentLocal', the port scheduler rate for priority level 3 
         is specified in percentage of local limit. The values of
         tPortSchedulerPlcyLvl3PIR and tPortSchedulerPlcyLvl3CIR will be set to
         their default values.

         This object is obsoleted in 13.0 release and replaced by
         tPortSchedPolicyLevelRateType."
    DEFVAL { kbps }
    ::= { tPortSchedulerPlcyEntry 37 }

tPortSchedPlcyLvl4PIRPercent       OBJECT-TYPE
    SYNTAX      Unsigned32 (1..10000)
    UNITS       "hundredths of a percent"
    MAX-ACCESS  read-create
    STATUS      obsolete
    DESCRIPTION
        "The value of tPortSchedPlcyLvl4PIRPercent specifies the total
         bandwidth percentage, PIR percent, for priority level 4.

         An 'inconsistentValue' error is returned if
         tPortSchedPlcyLvl4PIRPercent is set to non-default value when the
         object tPortSchedPlcyLvl4RateType is set to 'kbps'.

         This object is obsoleted in 13.0 release and replaced by
         tPortSchedPolicyLevelPIRPercent."
    DEFVAL { 10000 }
    ::= { tPortSchedulerPlcyEntry 38 }

tPortSchedPlcyLvl4CIRPercent       OBJECT-TYPE
    SYNTAX      Unsigned32 (0..10000)
    UNITS       "hundredths of a percent"
    MAX-ACCESS  read-create
    STATUS      obsolete
    DESCRIPTION
        "The value of tPortSchedPlcyLvl4CIRPercent specifies the within-cir
         bandwidth percentage, for priority level 4.

         An 'inconsistentValue' error is returned if
         tPortSchedPlcyLvl4CIRPercent is set to non-default value when the
         object tPortSchedPlcyLvl4RateType is set to 'kbps'.

         This object is obsoleted in 13.0 release and replaced by
         tPortSchedPolicyLevelCIRPercent."
    DEFVAL { 10000 }
    ::= { tPortSchedulerPlcyEntry 39 }

tPortSchedPlcyLvl4RateType             OBJECT-TYPE
    SYNTAX      TPSPRateType (1|2)
    MAX-ACCESS  read-create
    STATUS      obsolete
    DESCRIPTION
        "The value of tPortSchedPlcyLvl4RateType specifies the type of port
         scheduler rate for priority level 4.
         
         When the value of tPortSchedPlcyLvl4RateType is set to 'kbps', the
         port scheduler rate for priority level 4 is specified in 'kbps'. The
         values of tPortSchedPlcyLvl4PIRPercent and 
         tPortSchedPlcyLvl4CIRPercent will be set to their default values.

         When the value of tPortSchedPlcyLvl4RateType is set to
         'percentLocal', the port scheduler rate for priority level 4 
         is specified in percentage of local limit. The values of
         tPortSchedulerPlcyLvl4PIR and tPortSchedulerPlcyLvl4CIR will be set to
         their default values.

         This object is obsoleted in 13.0 release and replaced by
         tPortSchedPolicyLevelRateType."
    DEFVAL { kbps }
    ::= { tPortSchedulerPlcyEntry 40 }

tPortSchedPlcyLvl5PIRPercent       OBJECT-TYPE
    SYNTAX      Unsigned32 (1..10000)
    UNITS       "hundredths of a percent"
    MAX-ACCESS  read-create
    STATUS      obsolete
    DESCRIPTION
        "The value of tPortSchedPlcyLvl5PIRPercent specifies the total
         bandwidth percentage, PIR percent, for priority level 5.

         An 'inconsistentValue' error is returned if
         tPortSchedPlcyLvl5PIRPercent is set to non-default value when the
         object tPortSchedPlcyLvl5RateType is set to 'kbps'.

         This object is obsoleted in 13.0 release and replaced by
         tPortSchedPolicyLevelPIRPercent."
    DEFVAL { 10000 }
    ::= { tPortSchedulerPlcyEntry 41 }

tPortSchedPlcyLvl5CIRPercent       OBJECT-TYPE
    SYNTAX      Unsigned32 (0..10000)
    UNITS       "hundredths of a percent"
    MAX-ACCESS  read-create
    STATUS      obsolete
    DESCRIPTION
        "The value of tPortSchedPlcyLvl5CIRPercent specifies the within-cir
         bandwidth percentage, for priority level 5.

         An 'inconsistentValue' error is returned if
         tPortSchedPlcyLvl5CIRPercent is set to non-default value when the
         object tPortSchedPlcyLvl5RateType is set to 'kbps'.

         This object is obsoleted in 13.0 release and replaced by
         tPortSchedPolicyLevelCIRPercent."
    DEFVAL { 10000 }
    ::= { tPortSchedulerPlcyEntry 42 }

tPortSchedPlcyLvl5RateType             OBJECT-TYPE
    SYNTAX      TPSPRateType (1|2)
    MAX-ACCESS  read-create
    STATUS      obsolete
    DESCRIPTION
        "The value of tPortSchedPlcyLvl5RateType specifies the type of port
         scheduler rate for priority level 5.
         
         When the value of tPortSchedPlcyLvl5RateType is set to 'kbps', the
         port scheduler rate for priority level 5 is specified in 'kbps'. The
         values of tPortSchedPlcyLvl5PIRPercent and 
         tPortSchedPlcyLvl5CIRPercent will be set to their default values.

         When the value of tPortSchedPlcyLvl5RateType is set to
         'percentLocal', the port scheduler rate for priority level 5 
         is specified in percentage of local limit. The values of
         tPortSchedulerPlcyLvl5PIR and tPortSchedulerPlcyLvl5CIR will be set to
         their default values.

         This object is obsoleted in 13.0 release and replaced by
         tPortSchedPolicyLevelRateType."
    DEFVAL { kbps }
    ::= { tPortSchedulerPlcyEntry 43 }

tPortSchedPlcyLvl6PIRPercent       OBJECT-TYPE
    SYNTAX      Unsigned32 (1..10000)
    UNITS       "hundredths of a percent"
    MAX-ACCESS  read-create
    STATUS      obsolete
    DESCRIPTION
        "The value of tPortSchedPlcyLvl6PIRPercent specifies the total
         bandwidth percentage, PIR percent, for priority level 6.

         An 'inconsistentValue' error is returned if
         tPortSchedPlcyLvl6PIRPercent is set to non-default value when the
         object tPortSchedPlcyLvl6RateType is set to 'kbps'.

         This object is obsoleted in 13.0 release and replaced by
         tPortSchedPolicyLevelPIRPercent."
    DEFVAL { 10000 }
    ::= { tPortSchedulerPlcyEntry 44 }

tPortSchedPlcyLvl6CIRPercent       OBJECT-TYPE
    SYNTAX      Unsigned32 (0..10000)
    UNITS       "hundredths of a percent"
    MAX-ACCESS  read-create
    STATUS      obsolete
    DESCRIPTION
        "The value of tPortSchedPlcyLvl6CIRPercent specifies the within-cir
         bandwidth percentage, for priority level 6.

         An 'inconsistentValue' error is returned if
         tPortSchedPlcyLvl6CIRPercent is set to non-default value when the
         object tPortSchedPlcyLvl6RateType is set to 'kbps'.

         This object is obsoleted in 13.0 release and replaced by
         tPortSchedPolicyLevelCIRPercent."
    DEFVAL { 10000 }
    ::= { tPortSchedulerPlcyEntry 45 }

tPortSchedPlcyLvl6RateType             OBJECT-TYPE
    SYNTAX      TPSPRateType (1|2)
    MAX-ACCESS  read-create
    STATUS      obsolete
    DESCRIPTION
        "The value of tPortSchedPlcyLvl6RateType specifies the type of port
         scheduler rate for priority level 6.
         
         When the value of tPortSchedPlcyLvl6RateType is set to 'kbps', the
         port scheduler rate for priority level 6 is specified in 'kbps'. The
         values of tPortSchedPlcyLvl6PIRPercent and 
         tPortSchedPlcyLvl6CIRPercent will be set to their default values.

         When the value of tPortSchedPlcyLvl6RateType is set to
         'percentLocal', the port scheduler rate for priority level 6 
         is specified in percentage of local limit. The values of
         tPortSchedulerPlcyLvl6PIR and tPortSchedulerPlcyLvl6CIR will be set to
         their default values.

         This object is obsoleted in 13.0 release and replaced by
         tPortSchedPolicyLevelRateType."
    DEFVAL { kbps }
    ::= { tPortSchedulerPlcyEntry 46 }

tPortSchedPlcyLvl7PIRPercent       OBJECT-TYPE
    SYNTAX      Unsigned32 (1..10000)
    UNITS       "hundredths of a percent"
    MAX-ACCESS  read-create
    STATUS      obsolete
    DESCRIPTION
        "The value of tPortSchedPlcyLvl7PIRPercent specifies the total
         bandwidth percentage, PIR percent, for priority level 7.

         An 'inconsistentValue' error is returned if
         tPortSchedPlcyLvl7PIRPercent is set to non-default value when the
         object tPortSchedPlcyLvl7RateType is set to 'kbps'.

         This object is obsoleted in 13.0 release and replaced by
         tPortSchedPolicyLevelPIRPercent."
    DEFVAL { 10000 }
    ::= { tPortSchedulerPlcyEntry 47 }

tPortSchedPlcyLvl7CIRPercent       OBJECT-TYPE
    SYNTAX      Unsigned32 (0..10000)
    UNITS       "hundredths of a percent"
    MAX-ACCESS  read-create
    STATUS      obsolete
    DESCRIPTION
        "The value of tPortSchedPlcyLvl7CIRPercent specifies the within-cir
         bandwidth percentage, for priority level 7.

         An 'inconsistentValue' error is returned if
         tPortSchedPlcyLvl7CIRPercent is set to non-default value when the
         object tPortSchedPlcyLvl7RateType is set to 'kbps'.

         This object is obsoleted in 13.0 release and replaced by
         tPortSchedPolicyLevelCIRPercent."
    DEFVAL { 10000 }
    ::= { tPortSchedulerPlcyEntry 48 }

tPortSchedPlcyLvl7RateType             OBJECT-TYPE
    SYNTAX      TPSPRateType (1|2)
    MAX-ACCESS  read-create
    STATUS      obsolete
    DESCRIPTION
        "The value of tPortSchedPlcyLvl7RateType specifies the type of port
         scheduler rate for priority level 7.
         
         When the value of tPortSchedPlcyLvl7RateType is set to 'kbps', the
         port scheduler rate for priority level 7 is specified in 'kbps'. The
         values of tPortSchedPlcyLvl7PIRPercent and 
         tPortSchedPlcyLvl7CIRPercent will be set to their default values.

         When the value of tPortSchedPlcyLvl7RateType is set to
         'percentLocal', the port scheduler rate for priority level 7 
         is specified in percentage of local limit. The values of
         tPortSchedulerPlcyLvl7PIR and tPortSchedulerPlcyLvl7CIR will be set to
         their default values.

         This object is obsoleted in 13.0 release and replaced by
         tPortSchedPolicyLevelRateType."
    DEFVAL { kbps }
    ::= { tPortSchedulerPlcyEntry 49 }

tPortSchedPlcyLvl8PIRPercent       OBJECT-TYPE
    SYNTAX      Unsigned32 (1..10000)
    UNITS       "hundredths of a percent"
    MAX-ACCESS  read-create
    STATUS      obsolete
    DESCRIPTION
        "The value of tPortSchedPlcyLvl8PIRPercent specifies the total
         bandwidth percentage, PIR percent, for priority level 8.

         An 'inconsistentValue' error is returned if
         tPortSchedPlcyLvl8PIRPercent is set to non-default value when the
         object tPortSchedPlcyLvl8RateType is set to 'kbps'.

         This object is obsoleted in 13.0 release and replaced by
         tPortSchedPolicyLevelPIRPercent."
    DEFVAL { 10000 }
    ::= { tPortSchedulerPlcyEntry 50 }

tPortSchedPlcyLvl8CIRPercent       OBJECT-TYPE
    SYNTAX      Unsigned32 (0..10000)
    UNITS       "hundredths of a percent"
    MAX-ACCESS  read-create
    STATUS      obsolete
    DESCRIPTION
        "The value of tPortSchedPlcyLvl8CIRPercent specifies the within-cir
         bandwidth percentage, for priority level 8.

         An 'inconsistentValue' error is returned if
         tPortSchedPlcyLvl8CIRPercent is set to non-default value when the
         object tPortSchedPlcyLvl8RateType is set to 'kbps'.

         This object is obsoleted in 13.0 release and replaced by
         tPortSchedPolicyLevelCIRPercent."
    DEFVAL { 10000 }
    ::= { tPortSchedulerPlcyEntry 51 }

tPortSchedPlcyLvl8RateType             OBJECT-TYPE
    SYNTAX      TPSPRateType (1|2)
    MAX-ACCESS  read-create
    STATUS      obsolete
    DESCRIPTION
        "The value of tPortSchedPlcyLvl8RateType specifies the type of port
         scheduler rate for priority level 8.
         
         When the value of tPortSchedPlcyLvl8RateType is set to 'kbps', the
         port scheduler rate for priority level 8 is specified in 'kbps'. The
         values of tPortSchedPlcyLvl8PIRPercent and 
         tPortSchedPlcyLvl8CIRPercent will be set to their default values.

         When the value of tPortSchedPlcyLvl8RateType is set to
         'percentLocal', the port scheduler rate for priority level 8 
         is specified in percentage of local limit. The values of
         tPortSchedulerPlcyLvl8PIR and tPortSchedulerPlcyLvl8CIR will be set to
         their default values.

         This object is obsoleted in 13.0 release and replaced by
         tPortSchedPolicyLevelRateType."
    DEFVAL { kbps }
    ::= { tPortSchedulerPlcyEntry 52 }


tPortSchedPlcyMaxRate               OBJECT-TYPE
    SYNTAX       Unsigned32 (1..3200000000 | 4294967295)
    UNITS       "kbps"
    MAX-ACCESS  read-create
    STATUS      current
    DESCRIPTION
        "The value of tPortSchedPlcyMaxRate specifies the explicit maximum
         frame based bandwidth limit of this port scheduler.

         An 'inconsistentValue' error is returned if tPortSchedPlcyMaxRate
         is set to non-default value when the value of
         tPortSchedPlcyMaxRateType is set to 'percentLagActive'.

         When the value of tPortSchedPlcyMaxRate is set to 4294967295
         (0xFFFFFFFF), rate for this port scheduler policy indicates
         maximum rate."
    DEFVAL { 4294967295 }
    ::= { tPortSchedulerPlcyEntry 54 }


--
-- Hsmda Scheduler Policy Table
--

tHsmdaSchedulerPlcyTable OBJECT-TYPE
    SYNTAX      SEQUENCE OF THsmdaSchedulerPlcyEntry
    MAX-ACCESS  not-accessible
    STATUS      current
    DESCRIPTION
        "The tHsmdaSchedulerPlcyTable has an entry for each HSMDA scheduler
         policy configured on this system."
    ::= { tSchedulerObjects 4 }

tHsmdaSchedulerPlcyEntry    OBJECT-TYPE
    SYNTAX      THsmdaSchedulerPlcyEntry
    MAX-ACCESS  not-accessible
    STATUS      current
    DESCRIPTION
        "Each row represents a particular HSMDA scheduler policy. Entries are 
         created and deleted by the user."
    INDEX { tHsmdaSchedulerPlcyName }
    ::= { tHsmdaSchedulerPlcyTable 1}

THsmdaSchedulerPlcyEntry ::= SEQUENCE
    {
        tHsmdaSchedulerPlcyName              TNamedItem,
        tHsmdaSchedulerPlcyRowStatus         RowStatus,
        tHsmdaSchedulerPlcyDescription       TItemDescription,
        tHsmdaSchedulerPlcyMaxRate           THsmdaPIRMRate,
        tHsmdaSchedulerPlcyLvl1Rate          THsmdaPIRMRate,
        tHsmdaSchedulerPlcyLvl1GrpId         THsmdaSchedulerPolicyGroupId,
        tHsmdaSchedulerPlcyLvl1WgtInGrp      THsmdaWeight,
        tHsmdaSchedulerPlcyLvl2Rate          THsmdaPIRMRate,
        tHsmdaSchedulerPlcyLvl2GrpId         THsmdaSchedulerPolicyGroupId,
        tHsmdaSchedulerPlcyLvl2WgtInGrp      THsmdaWeight,
        tHsmdaSchedulerPlcyLvl3Rate          THsmdaPIRMRate,
        tHsmdaSchedulerPlcyLvl3GrpId         THsmdaSchedulerPolicyGroupId,
        tHsmdaSchedulerPlcyLvl3WgtInGrp      THsmdaWeight,
        tHsmdaSchedulerPlcyLvl4Rate          THsmdaPIRMRate,
        tHsmdaSchedulerPlcyLvl4GrpId         THsmdaSchedulerPolicyGroupId,
        tHsmdaSchedulerPlcyLvl4WgtInGrp      THsmdaWeight,
        tHsmdaSchedulerPlcyLvl5Rate          THsmdaPIRMRate,
        tHsmdaSchedulerPlcyLvl5GrpId         THsmdaSchedulerPolicyGroupId,
        tHsmdaSchedulerPlcyLvl5WgtInGrp      THsmdaWeight,
        tHsmdaSchedulerPlcyLvl6Rate          THsmdaPIRMRate,
        tHsmdaSchedulerPlcyLvl6GrpId         THsmdaSchedulerPolicyGroupId,
        tHsmdaSchedulerPlcyLvl6WgtInGrp      THsmdaWeight,
        tHsmdaSchedulerPlcyLvl7Rate          THsmdaPIRMRate,
        tHsmdaSchedulerPlcyLvl7GrpId         THsmdaSchedulerPolicyGroupId,
        tHsmdaSchedulerPlcyLvl7WgtInGrp      THsmdaWeight,
        tHsmdaSchedulerPlcyLvl8Rate          THsmdaPIRMRate,
        tHsmdaSchedulerPlcyLvl8GrpId         THsmdaSchedulerPolicyGroupId,
        tHsmdaSchedulerPlcyLvl8WgtInGrp      THsmdaWeight,
        tHsmdaSchedulerPlcyLastChanged       TimeStamp,
        tHsmdaSchedulerPlcyGrp1Rate          THsmdaPIRMRate,
        tHsmdaSchedulerPlcyGrp2Rate          THsmdaPIRMRate,
        tHsmdaSchedulerPlcyBrstLimit         TClassBurstLimit,
        tHsmdaSchedulerPlcyGrp1BrstLimit     TClassBurstLimit,
        tHsmdaSchedulerPlcyGrp2BrstLimit     TClassBurstLimit,
        tHsmdaSchedulerPlcyLvl1BrstLimit     TClassBurstLimit,
        tHsmdaSchedulerPlcyLvl2BrstLimit     TClassBurstLimit,
        tHsmdaSchedulerPlcyLvl3BrstLimit     TClassBurstLimit,
        tHsmdaSchedulerPlcyLvl4BrstLimit     TClassBurstLimit,
        tHsmdaSchedulerPlcyLvl5BrstLimit     TClassBurstLimit,
        tHsmdaSchedulerPlcyLvl6BrstLimit     TClassBurstLimit,
        tHsmdaSchedulerPlcyLvl7BrstLimit     TClassBurstLimit,
        tHsmdaSchedulerPlcyLvl8BrstLimit     TClassBurstLimit
    }

tHsmdaSchedulerPlcyName        OBJECT-TYPE
    SYNTAX      TNamedItem
    MAX-ACCESS  not-accessible
    STATUS      current
    DESCRIPTION
        "The value of tHsmdaSchedulerPlcyName specifies the name of the HSMDA
         scheduler policy."
    ::= { tHsmdaSchedulerPlcyEntry 1 }

tHsmdaSchedulerPlcyRowStatus        OBJECT-TYPE
    SYNTAX      RowStatus
    MAX-ACCESS  read-create
    STATUS      current
    DESCRIPTION
        "The value of tHsmdaSchedulerPlcyRowStatus is used for the creation
         and deletion of HSMDA scheduler policies."
    ::= { tHsmdaSchedulerPlcyEntry 2 }

tHsmdaSchedulerPlcyDescription        OBJECT-TYPE
    SYNTAX      TItemDescription
    MAX-ACCESS  read-create
    STATUS      current
    DESCRIPTION
        "The value of tHsmdaSchedulerPlcyDescription specifies the description
         of this HSMDA scheduling policy."
    ::= { tHsmdaSchedulerPlcyEntry 3 }

tHsmdaSchedulerPlcyMaxRate        OBJECT-TYPE
    SYNTAX      THsmdaPIRMRate
    UNITS       "Mbps"
    MAX-ACCESS  read-create
    STATUS      current
    DESCRIPTION
        "The value of tHsmdaSchedulerPlcyMaxRate specifies the explicit maximum
         frame based bandwidth limit, in megabits per second, of this HSMDA 
         scheduler policy."
    DEFVAL { -1 }
    ::= { tHsmdaSchedulerPlcyEntry 4 }

tHsmdaSchedulerPlcyLvl1Rate        OBJECT-TYPE
    SYNTAX      THsmdaPIRMRate
    UNITS       "Mbps"
    MAX-ACCESS  read-create
    STATUS      current
    DESCRIPTION
        "The value of tHsmdaSchedulerPlcyLvl1Rate specifies the explicit maximum
         frame based bandwidth limit, in megabits per second, for this HSMDA
         scheduler policy level. This object may not be set simultaneously with
         tHsmdaSchedulerPlcyLvl1GrpId.

         Setting tHsmdaSchedulerPlcyLvl1Rate to any value (including default)
         while tHsmdaSchedulerPlcyLvl1GrpId is non-default, results in the level
         being removed from the group, tHsmdaSchedulerPlcyLvl1GrpId being set to 
         default, and tHsmdaSchedulerPlcyLvl1WgtInGrp being set to default."
    DEFVAL { -1 }
    ::= { tHsmdaSchedulerPlcyEntry 5 }

tHsmdaSchedulerPlcyLvl1GrpId        OBJECT-TYPE
    SYNTAX      THsmdaSchedulerPolicyGroupId
    MAX-ACCESS  read-create
    STATUS      current
    DESCRIPTION
        "The value of tHsmdaSchedulerPlcyLvl1GrpId specifies the group this
         HSMDA scheduler policy level belongs to. If the value is '0', this 
         level is not assigned to a scheduler policy group. This object may not
         be set simultaneously with tHsmdaSchedulerPlcyLvl1Rate.

         Setting tHsmdaSchedulerPlcyLvl1GrpId to non-default value while 
         tHsmdaSchedulerPlcyLvl1Rate is non-default, results in the level being
         added to the group and tHsmdaSchedulerPlcyLvl1Rate being set to 
         default.

         Setting tHsmdaSchedulerPlcyLvl1GrpId to default value results in the 
         level being removed from any group and tHsmdaSchedulerPlcyLvl1WgtInGrp
         being set to default."
    DEFVAL { 0 }
    ::= { tHsmdaSchedulerPlcyEntry 6 }

tHsmdaSchedulerPlcyLvl1WgtInGrp        OBJECT-TYPE
    SYNTAX      THsmdaWeight
    MAX-ACCESS  read-create
    STATUS      current
    DESCRIPTION
        "The value of tHsmdaSchedulerPlcyLvl1WgtInGrp specifies the weight
         the HSMDA scheduler policy should apply to this policy level within
         the group it belongs to.

         The value of tHsmdaSchedulerPlcyLvl1WgtInGrp will only be
         used if this policy level has been assigned to a group
         by setting tHsmdaSchedulerPlcyLvl1GrpId to a non-zero value.

         The value of tHsmdaSchedulerPlcyLvl1WgtInGrp is only allowed to be
         non-default when tHsmdaSchedulerPlcyLvl1GrpId is non-default."
    DEFVAL { 1 }
    ::= { tHsmdaSchedulerPlcyEntry 7 }

tHsmdaSchedulerPlcyLvl2Rate        OBJECT-TYPE
    SYNTAX      THsmdaPIRMRate
    UNITS       "Mbps"
    MAX-ACCESS  read-create
    STATUS      current
    DESCRIPTION
        "The value of tHsmdaSchedulerPlcyLvl2Rate specifies the explicit maximum
         frame based bandwidth limit, in megabits per second, for this HSMDA
         scheduler policy level. This object may not be set simultaneously with
         tHsmdaSchedulerPlcyLvl2GrpId.

         Setting tHsmdaSchedulerPlcyLvl2Rate to any value (including default)
         while tHsmdaSchedulerPlcyLvl2GrpId is non-default, results in the level
         being removed from the group, tHsmdaSchedulerPlcyLvl2GrpId being set to 
         default, and tHsmdaSchedulerPlcyLvl2WgtInGrp being set to default."
    DEFVAL { -1 }
    ::= { tHsmdaSchedulerPlcyEntry 8 }

tHsmdaSchedulerPlcyLvl2GrpId        OBJECT-TYPE
    SYNTAX      THsmdaSchedulerPolicyGroupId
    MAX-ACCESS  read-create
    STATUS      current
    DESCRIPTION
        "The value of tHsmdaSchedulerPlcyLvl2GrpId specifies the group this
         HSMDA scheduler policy level belongs to. If the value is '0', this 
         level is not assigned to a scheduler policy group. This object may not
         be set simultaneously with tHsmdaSchedulerPlcyLvl2Rate.

         Setting tHsmdaSchedulerPlcyLvl2GrpId to non-default value while 
         tHsmdaSchedulerPlcyLvl2Rate is non-default, results in the level being
         added to the group and tHsmdaSchedulerPlcyLvl2Rate being set to 
         default.

         Setting tHsmdaSchedulerPlcyLvl2GrpId to default value results in the 
         level being removed from any group and tHsmdaSchedulerPlcyLvl2WgtInGrp
         being set to default."
    DEFVAL { 0 }
    ::= { tHsmdaSchedulerPlcyEntry 9 }

tHsmdaSchedulerPlcyLvl2WgtInGrp        OBJECT-TYPE
    SYNTAX      THsmdaWeight
    MAX-ACCESS  read-create
    STATUS      current
    DESCRIPTION
        "The value of tHsmdaSchedulerPlcyLvl2WgtInGrp specifies the weight
         the HSMDA scheduler policy should apply to this policy level within
         the group it belongs to.

         The value of tHsmdaSchedulerPlcyLvl2WgtInGrp will only be
         used if this policy level has been assigned to a group
         by setting tHsmdaSchedulerPlcyLvl2GrpId to a non-zero value.

         The value of tHsmdaSchedulerPlcyLvl2WgtInGrp is only allowed to be
         non-default when tHsmdaSchedulerPlcyLvl2GrpId is non-default."
    DEFVAL { 1 }
    ::= { tHsmdaSchedulerPlcyEntry 10 }

tHsmdaSchedulerPlcyLvl3Rate        OBJECT-TYPE
    SYNTAX      THsmdaPIRMRate
    UNITS       "Mbps"
    MAX-ACCESS  read-create
    STATUS      current
    DESCRIPTION
        "The value of tHsmdaSchedulerPlcyLvl3Rate specifies the explicit maximum
         frame based bandwidth limit, in megabits per second, for this HSMDA
         scheduler policy level. This object may not be set simultaneously with
         tHsmdaSchedulerPlcyLvl3GrpId.

         Setting tHsmdaSchedulerPlcyLvl3Rate to any value (including default)
         while tHsmdaSchedulerPlcyLvl3GrpId is non-default, results in the level
         being removed from the group, tHsmdaSchedulerPlcyLvl3GrpId being set to 
         default, and tHsmdaSchedulerPlcyLvl3WgtInGrp being set to default."
    DEFVAL { -1 }
    ::= { tHsmdaSchedulerPlcyEntry 11 }

tHsmdaSchedulerPlcyLvl3GrpId        OBJECT-TYPE
    SYNTAX      THsmdaSchedulerPolicyGroupId
    MAX-ACCESS  read-create
    STATUS      current
    DESCRIPTION
        "The value of tHsmdaSchedulerPlcyLvl3GrpId specifies the group this
         HSMDA scheduler policy level belongs to. If the value is '0', this 
         level is not assigned to a scheduler policy group. This object may not
         be set simultaneously with tHsmdaSchedulerPlcyLvl3Rate.

         Setting tHsmdaSchedulerPlcyLvl3GrpId to non-default value while 
         tHsmdaSchedulerPlcyLvl3Rate is non-default, results in the level being
         added to the group and tHsmdaSchedulerPlcyLvl3Rate being set to 
         default.

         Setting tHsmdaSchedulerPlcyLvl3GrpId to default value results in the 
         level being removed from any group and tHsmdaSchedulerPlcyLvl3WgtInGrp
         being set to default."
    DEFVAL { 0 }
    ::= { tHsmdaSchedulerPlcyEntry 12 }

tHsmdaSchedulerPlcyLvl3WgtInGrp        OBJECT-TYPE
    SYNTAX      THsmdaWeight
    MAX-ACCESS  read-create
    STATUS      current
    DESCRIPTION
        "The value of tHsmdaSchedulerPlcyLvl3WgtInGrp specifies the weight
         the HSMDA scheduler policy should apply to this policy level within
         the group it belongs to.

         The value of tHsmdaSchedulerPlcyLvl3WgtInGrp will only be
         used if this policy level has been assigned to a group
         by setting tHsmdaSchedulerPlcyLvl3GrpId to a non-zero value.

         The value of tHsmdaSchedulerPlcyLvl3WgtInGrp is only allowed to be
         non-default when tHsmdaSchedulerPlcyLvl3GrpId is non-default."
    DEFVAL { 1 }
    ::= { tHsmdaSchedulerPlcyEntry 13 }

tHsmdaSchedulerPlcyLvl4Rate        OBJECT-TYPE
    SYNTAX      THsmdaPIRMRate
    UNITS       "Mbps"
    MAX-ACCESS  read-create
    STATUS      current
    DESCRIPTION
        "The value of tHsmdaSchedulerPlcyLvl4Rate specifies the explicit maximum
         frame based bandwidth limit, in megabits per second, for this HSMDA
         scheduler policy level. This object may not be set simultaneously with
         tHsmdaSchedulerPlcyLvl4GrpId.

         Setting tHsmdaSchedulerPlcyLvl4Rate to any value (including default)
         while tHsmdaSchedulerPlcyLvl4GrpId is non-default, results in the level
         being removed from the group, tHsmdaSchedulerPlcyLvl4GrpId being set to 
         default, and tHsmdaSchedulerPlcyLvl4WgtInGrp being set to default."
    DEFVAL { -1 }
    ::= { tHsmdaSchedulerPlcyEntry 14 }

tHsmdaSchedulerPlcyLvl4GrpId        OBJECT-TYPE
    SYNTAX      THsmdaSchedulerPolicyGroupId
    MAX-ACCESS  read-create
    STATUS      current
    DESCRIPTION
        "The value of tHsmdaSchedulerPlcyLvl4GrpId specifies the group this
         HSMDA scheduler policy level belongs to. If the value is '0', this 
         level is not assigned to a scheduler policy group. This object may not
         be set simultaneously with tHsmdaSchedulerPlcyLvl4Rate.

         Setting tHsmdaSchedulerPlcyLvl4GrpId to non-default value while 
         tHsmdaSchedulerPlcyLvl4Rate is non-default, results in the level being
         added to the group and tHsmdaSchedulerPlcyLvl4Rate being set to 
         default.

         Setting tHsmdaSchedulerPlcyLvl4GrpId to default value results in the 
         level being removed from any group and tHsmdaSchedulerPlcyLvl4WgtInGrp
         being set to default."
    DEFVAL { 0 }
    ::= { tHsmdaSchedulerPlcyEntry 15 }

tHsmdaSchedulerPlcyLvl4WgtInGrp        OBJECT-TYPE
    SYNTAX      THsmdaWeight
    MAX-ACCESS  read-create
    STATUS      current
    DESCRIPTION
        "The value of tHsmdaSchedulerPlcyLvl4WgtInGrp specifies the weight
         the HSMDA scheduler policy should apply to this policy level within
         the group it belongs to.

         The value of tHsmdaSchedulerPlcyLvl4WgtInGrp will only be
         used if this policy level has been assigned to a group
         by setting tHsmdaSchedulerPlcyLvl4GrpId to a non-zero value.

         The value of tHsmdaSchedulerPlcyLvl4WgtInGrp is only allowed to be
         non-default when tHsmdaSchedulerPlcyLvl4GrpId is non-default."
    DEFVAL { 1 }
    ::= { tHsmdaSchedulerPlcyEntry 16 }

tHsmdaSchedulerPlcyLvl5Rate        OBJECT-TYPE
    SYNTAX      THsmdaPIRMRate
    UNITS       "Mbps"
    MAX-ACCESS  read-create
    STATUS      current
    DESCRIPTION
        "The value of tHsmdaSchedulerPlcyLvl5Rate specifies the explicit maximum
         frame based bandwidth limit, in megabits per second, for this HSMDA
         scheduler policy level. This object may not be set simultaneously with
         tHsmdaSchedulerPlcyLvl5GrpId.

         Setting tHsmdaSchedulerPlcyLvl5Rate to any value (including default)
         while tHsmdaSchedulerPlcyLvl5GrpId is non-default, results in the level
         being removed from the group, tHsmdaSchedulerPlcyLvl5GrpId being set to 
         default, and tHsmdaSchedulerPlcyLvl5WgtInGrp being set to default."
    DEFVAL { -1 }
    ::= { tHsmdaSchedulerPlcyEntry 17 }

tHsmdaSchedulerPlcyLvl5GrpId        OBJECT-TYPE
    SYNTAX      THsmdaSchedulerPolicyGroupId
    MAX-ACCESS  read-create
    STATUS      current
    DESCRIPTION
        "The value of tHsmdaSchedulerPlcyLvl5GrpId specifies the group this
         HSMDA scheduler policy level belongs to. If the value is '0', this 
         level is not assigned to a scheduler policy group. This object may not
         be set simultaneously with tHsmdaSchedulerPlcyLvl5Rate.

         Setting tHsmdaSchedulerPlcyLvl5GrpId to non-default value while 
         tHsmdaSchedulerPlcyLvl5Rate is non-default, results in the level being
         added to the group and tHsmdaSchedulerPlcyLvl5Rate being set to 
         default.

         Setting tHsmdaSchedulerPlcyLvl5GrpId to default value results in the 
         level being removed from any group and tHsmdaSchedulerPlcyLvl5WgtInGrp
         being set to default."
    DEFVAL { 0 }
    ::= { tHsmdaSchedulerPlcyEntry 18 }

tHsmdaSchedulerPlcyLvl5WgtInGrp        OBJECT-TYPE
    SYNTAX      THsmdaWeight
    MAX-ACCESS  read-create
    STATUS      current
    DESCRIPTION
        "The value of tHsmdaSchedulerPlcyLvl5WgtInGrp specifies the weight
         the HSMDA scheduler policy should apply to this policy level within
         the group it belongs to.

         The value of tHsmdaSchedulerPlcyLvl5WgtInGrp will only be
         used if this policy level has been assigned to a group
         by setting tHsmdaSchedulerPlcyLvl5GrpId to a non-zero value.

         The value of tHsmdaSchedulerPlcyLvl5WgtInGrp is only allowed to be
         non-default when tHsmdaSchedulerPlcyLvl5GrpId is non-default."
    DEFVAL { 1 }
    ::= { tHsmdaSchedulerPlcyEntry 19 }

tHsmdaSchedulerPlcyLvl6Rate        OBJECT-TYPE
    SYNTAX      THsmdaPIRMRate
    UNITS       "Mbps"
    MAX-ACCESS  read-create
    STATUS      current
    DESCRIPTION
        "The value of tHsmdaSchedulerPlcyLvl6Rate specifies the explicit maximum
         frame based bandwidth limit, in megabits per second, for this HSMDA
         scheduler policy level. This object may not be set simultaneously with
         tHsmdaSchedulerPlcyLvl6GrpId.

         Setting tHsmdaSchedulerPlcyLvl6Rate to any value (including default)
         while tHsmdaSchedulerPlcyLvl6GrpId is non-default, results in the level
         being removed from the group, tHsmdaSchedulerPlcyLvl6GrpId being set to 
         default, and tHsmdaSchedulerPlcyLvl6WgtInGrp being set to default."
    DEFVAL { -1 }
    ::= { tHsmdaSchedulerPlcyEntry 20 }

tHsmdaSchedulerPlcyLvl6GrpId        OBJECT-TYPE
    SYNTAX      THsmdaSchedulerPolicyGroupId
    MAX-ACCESS  read-create
    STATUS      current
    DESCRIPTION
        "The value of tHsmdaSchedulerPlcyLvl6GrpId specifies the group this
         HSMDA scheduler policy level belongs to. If the value is '0', this 
         level is not assigned to a scheduler policy group. This object may not
         be set simultaneously with tHsmdaSchedulerPlcyLvl6Rate.

         Setting tHsmdaSchedulerPlcyLvl6GrpId to non-default value while 
         tHsmdaSchedulerPlcyLvl6Rate is non-default, results in the level being
         added to the group and tHsmdaSchedulerPlcyLvl6Rate being set to 
         default.

         Setting tHsmdaSchedulerPlcyLvl6GrpId to default value results in the 
         level being removed from any group and tHsmdaSchedulerPlcyLvl6WgtInGrp
         being set to default."
    DEFVAL { 0 }
    ::= { tHsmdaSchedulerPlcyEntry 21 }

tHsmdaSchedulerPlcyLvl6WgtInGrp        OBJECT-TYPE
    SYNTAX      THsmdaWeight
    MAX-ACCESS  read-create
    STATUS      current
    DESCRIPTION
        "The value of tHsmdaSchedulerPlcyLvl6WgtInGrp specifies the weight
         the HSMDA scheduler policy should apply to this policy level within
         the group it belongs to.

         The value of tHsmdaSchedulerPlcyLvl6WgtInGrp will only be
         used if this policy level has been assigned to a group
         by setting tHsmdaSchedulerPlcyLvl6GrpId to a non-zero value.

         The value of tHsmdaSchedulerPlcyLvl6WgtInGrp is only allowed to be
         non-default when tHsmdaSchedulerPlcyLvl6GrpId is non-default."
    DEFVAL { 1 }
    ::= { tHsmdaSchedulerPlcyEntry 22 }

tHsmdaSchedulerPlcyLvl7Rate        OBJECT-TYPE
    SYNTAX      THsmdaPIRMRate
    UNITS       "Mbps"
    MAX-ACCESS  read-create
    STATUS      current
    DESCRIPTION
        "The value of tHsmdaSchedulerPlcyLvl7Rate specifies the explicit maximum
         frame based bandwidth limit, in megabits per second, for this HSMDA
         scheduler policy level. This object may not be set simultaneously with
         tHsmdaSchedulerPlcyLvl7GrpId.

         Setting tHsmdaSchedulerPlcyLvl7Rate to any value (including default)
         while tHsmdaSchedulerPlcyLvl7GrpId is non-default, results in the level
         being removed from the group, tHsmdaSchedulerPlcyLvl7GrpId being set to 
         default, and tHsmdaSchedulerPlcyLvl7WgtInGrp being set to default."
    DEFVAL { -1 }
    ::= { tHsmdaSchedulerPlcyEntry 23 }

tHsmdaSchedulerPlcyLvl7GrpId        OBJECT-TYPE
    SYNTAX      THsmdaSchedulerPolicyGroupId
    MAX-ACCESS  read-create
    STATUS      current
    DESCRIPTION
        "The value of tHsmdaSchedulerPlcyLvl7GrpId specifies the group this
         HSMDA scheduler policy level belongs to. If the value is '0', this 
         level is not assigned to a scheduler policy group. This object may not
         be set simultaneously with tHsmdaSchedulerPlcyLvl7Rate.

         Setting tHsmdaSchedulerPlcyLvl7GrpId to non-default value while 
         tHsmdaSchedulerPlcyLvl7Rate is non-default, results in the level being
         added to the group and tHsmdaSchedulerPlcyLvl7Rate being set to 
         default.

         Setting tHsmdaSchedulerPlcyLvl7GrpId to default value results in the 
         level being removed from any group and tHsmdaSchedulerPlcyLvl7WgtInGrp
         being set to default."
    DEFVAL { 0 }
    ::= { tHsmdaSchedulerPlcyEntry 24 }

tHsmdaSchedulerPlcyLvl7WgtInGrp        OBJECT-TYPE
    SYNTAX      THsmdaWeight
    MAX-ACCESS  read-create
    STATUS      current
    DESCRIPTION
        "The value of tHsmdaSchedulerPlcyLvl7WgtInGrp specifies the weight
         the HSMDA scheduler policy should apply to this policy level within
         the group it belongs to.

         The value of tHsmdaSchedulerPlcyLvl7WgtInGrp will only be
         used if this policy level has been assigned to a group
         by setting tHsmdaSchedulerPlcyLvl7GrpId to a non-zero value.

         The value of tHsmdaSchedulerPlcyLvl7WgtInGrp is only allowed to be
         non-default when tHsmdaSchedulerPlcyLvl7GrpId is non-default."
    DEFVAL { 1 }
    ::= { tHsmdaSchedulerPlcyEntry 25 }

tHsmdaSchedulerPlcyLvl8Rate        OBJECT-TYPE
    SYNTAX      THsmdaPIRMRate
    UNITS       "Mbps"
    MAX-ACCESS  read-create
    STATUS      current
    DESCRIPTION
        "The value of tHsmdaSchedulerPlcyLvl8Rate specifies the explicit maximum
         frame based bandwidth limit, in megabits per second, for this HSMDA
         scheduler policy level. This object may not be set simultaneously with
         tHsmdaSchedulerPlcyLvl8GrpId.

         Setting tHsmdaSchedulerPlcyLvl8Rate to any value (including default)
         while tHsmdaSchedulerPlcyLvl8GrpId is non-default, results in the level
         being removed from the group, tHsmdaSchedulerPlcyLvl8GrpId being set to 
         default, and tHsmdaSchedulerPlcyLvl8WgtInGrp being set to default."
    DEFVAL { -1 }
    ::= { tHsmdaSchedulerPlcyEntry 26 }

tHsmdaSchedulerPlcyLvl8GrpId        OBJECT-TYPE
    SYNTAX      THsmdaSchedulerPolicyGroupId
    MAX-ACCESS  read-create
    STATUS      current
    DESCRIPTION
        "The value of tHsmdaSchedulerPlcyLvl8GrpId specifies the group this
         HSMDA scheduler policy level belongs to. If the value is '0', this 
         level is not assigned to a scheduler policy group. This object may not
         be set simultaneously with tHsmdaSchedulerPlcyLvl8Rate.

         Setting tHsmdaSchedulerPlcyLvl8GrpId to non-default value while 
         tHsmdaSchedulerPlcyLvl8Rate is non-default, results in the level being
         added to the group and tHsmdaSchedulerPlcyLvl8Rate being set to 
         default.

         Setting tHsmdaSchedulerPlcyLvl8GrpId to default value results in the 
         level being removed from any group and tHsmdaSchedulerPlcyLvl8WgtInGrp
         being set to default."
    DEFVAL { 0 }
    ::= { tHsmdaSchedulerPlcyEntry 27 }

tHsmdaSchedulerPlcyLvl8WgtInGrp        OBJECT-TYPE
    SYNTAX      THsmdaWeight
    MAX-ACCESS  read-create
    STATUS      current
    DESCRIPTION
        "The value of tHsmdaSchedulerPlcyLvl8WgtInGrp specifies the weight
         the HSMDA scheduler policy should apply to this policy level within
         the group it belongs to.

         The value of tHsmdaSchedulerPlcyLvl8WgtInGrp will only be
         used if this policy level has been assigned to a group
         by setting tHsmdaSchedulerPlcyLvl8GrpId to a non-zero value.

         The value of tHsmdaSchedulerPlcyLvl8WgtInGrp is only allowed to be
         non-default when tHsmdaSchedulerPlcyLvl8GrpId is non-default."
    DEFVAL { 1 }
    ::= { tHsmdaSchedulerPlcyEntry 28 }

tHsmdaSchedulerPlcyLastChanged        OBJECT-TYPE
    SYNTAX      TimeStamp
    MAX-ACCESS  read-only
    STATUS      current
    DESCRIPTION
        "The value of tHsmdaSchedulerPlcyLastChanged indicates the timestamp of 
         last change to this row in tHsmdaSchedulerPlcyTable."
    ::= { tHsmdaSchedulerPlcyEntry 29 }

tHsmdaSchedulerPlcyGrp1Rate           OBJECT-TYPE
    SYNTAX      THsmdaPIRMRate
    UNITS       "Mbps"
    MAX-ACCESS  read-create
    STATUS      current
    DESCRIPTION
        "The value of tHsmdaSchedulerPlcyGrp1Rate specifies the explicit 
         maximum frame based bandwidth limit, in megabits per second, for 
         group 1 for this HSMDA scheduler policy group."
    DEFVAL { -1 }
    ::= { tHsmdaSchedulerPlcyEntry 30 }

tHsmdaSchedulerPlcyGrp2Rate           OBJECT-TYPE
    SYNTAX      THsmdaPIRMRate
    UNITS       "Mbps"
    MAX-ACCESS  read-create
    STATUS      current
    DESCRIPTION
        "The value of tHsmdaSchedulerPlcyGrp2Rate specifies the explicit 
         maximum frame based bandwidth limit, in megabits per second, for 
         group 2 for this HSMDA scheduler policy group."
    DEFVAL { -1 }
    ::= { tHsmdaSchedulerPlcyEntry 31 }

tHsmdaSchedulerPlcyBrstLimit OBJECT-TYPE
    SYNTAX       TClassBurstLimit
    UNITS        "bytes"
    MAX-ACCESS   read-create
    STATUS       current
    DESCRIPTION
        "The value of tHsmdaSchedulerPlcyBrstLimit specifies the explicit
         shaping burst size for this HSMDA scheduler policy."
    DEFVAL { -1 }
    ::= { tHsmdaSchedulerPlcyEntry 32 }

tHsmdaSchedulerPlcyGrp1BrstLimit OBJECT-TYPE
    SYNTAX       TClassBurstLimit
    UNITS        "bytes"
    MAX-ACCESS   read-create
    STATUS       current
    DESCRIPTION
        "The value of tHsmdaSchedulerPlcyGrp1BrstLimit specifies the explicit
         shaping burst size for group 1 of this HSMDA scheduler policy."
    DEFVAL { -1 }
    ::= { tHsmdaSchedulerPlcyEntry 33 }

tHsmdaSchedulerPlcyGrp2BrstLimit OBJECT-TYPE
    SYNTAX       TClassBurstLimit
    UNITS        "bytes"
    MAX-ACCESS   read-create
    STATUS       current
    DESCRIPTION
        "The value of tHsmdaSchedulerPlcyGrp2BrstLimit specifies the explicit
         shaping burst size for group 2 of this HSMDA scheduler policy."
    DEFVAL { -1 }
    ::= { tHsmdaSchedulerPlcyEntry 34 }

tHsmdaSchedulerPlcyLvl1BrstLimit OBJECT-TYPE
    SYNTAX       TClassBurstLimit
    UNITS        "bytes"
    MAX-ACCESS   read-create
    STATUS       current
    DESCRIPTION
        "The value of tHsmdaSchedulerPlcyLvl1BrstLimit specifies the explicit
         shaping burst size for level 1 of this HSMDA scheduler policy."
    DEFVAL { -1 }
    ::= { tHsmdaSchedulerPlcyEntry 35 }

tHsmdaSchedulerPlcyLvl2BrstLimit OBJECT-TYPE
    SYNTAX       TClassBurstLimit
    UNITS        "bytes"
    MAX-ACCESS   read-create
    STATUS       current
    DESCRIPTION
        "The value of tHsmdaSchedulerPlcyLvl2BrstLimit specifies the explicit
         shaping burst size for level 2 of this HSMDA scheduler policy."
    DEFVAL { -1 }
    ::= { tHsmdaSchedulerPlcyEntry 36 }

tHsmdaSchedulerPlcyLvl3BrstLimit OBJECT-TYPE
    SYNTAX       TClassBurstLimit
    UNITS        "bytes"
    MAX-ACCESS   read-create
    STATUS       current
    DESCRIPTION
        "The value of tHsmdaSchedulerPlcyLvl3BrstLimit specifies the explicit
         shaping burst size for level 3 of this HSMDA scheduler policy."
    DEFVAL { -1 }
    ::= { tHsmdaSchedulerPlcyEntry 37 }

tHsmdaSchedulerPlcyLvl4BrstLimit OBJECT-TYPE
    SYNTAX       TClassBurstLimit
    UNITS        "bytes"
    MAX-ACCESS   read-create
    STATUS       current
    DESCRIPTION
        "The value of tHsmdaSchedulerPlcyLvl4BrstLimit specifies the explicit
         shaping burst size for level 4 of this HSMDA scheduler policy."
    DEFVAL { -1 }
    ::= { tHsmdaSchedulerPlcyEntry 38 }

tHsmdaSchedulerPlcyLvl5BrstLimit OBJECT-TYPE
    SYNTAX       TClassBurstLimit
    UNITS        "bytes"
    MAX-ACCESS   read-create
    STATUS       current
    DESCRIPTION
        "The value of tHsmdaSchedulerPlcyLvl5BrstLimit specifies the explicit
         shaping burst size for level 5 of this HSMDA scheduler policy."
    DEFVAL { -1 }
    ::= { tHsmdaSchedulerPlcyEntry 39 }

tHsmdaSchedulerPlcyLvl6BrstLimit OBJECT-TYPE
    SYNTAX       TClassBurstLimit
    UNITS        "bytes"
    MAX-ACCESS   read-create
    STATUS       current
    DESCRIPTION
        "The value of tHsmdaSchedulerPlcyLvl6BrstLimit specifies the explicit
         shaping burst size for level 6 of this HSMDA scheduler policy."
    DEFVAL { -1 }
    ::= { tHsmdaSchedulerPlcyEntry 40 }

tHsmdaSchedulerPlcyLvl7BrstLimit OBJECT-TYPE
    SYNTAX       TClassBurstLimit
    UNITS        "bytes"
    MAX-ACCESS   read-create
    STATUS       current
    DESCRIPTION
        "The value of tHsmdaSchedulerPlcyLvl7BrstLimit specifies the explicit
         shaping burst size for level 7 of this HSMDA scheduler policy."
    DEFVAL { -1 }
    ::= { tHsmdaSchedulerPlcyEntry 41 }

tHsmdaSchedulerPlcyLvl8BrstLimit OBJECT-TYPE
    SYNTAX       TClassBurstLimit
    UNITS        "bytes"
    MAX-ACCESS   read-create
    STATUS       current
    DESCRIPTION
        "The value of tHsmdaSchedulerPlcyLvl8BrstLimit specifies the explicit
         shaping burst size for level 8 of this HSMDA scheduler policy."
    DEFVAL { -1 }
    ::= { tHsmdaSchedulerPlcyEntry 42 }

--
-- Qos Domain Time Stamps
--
tQosDomainLastChanged OBJECT-TYPE
    SYNTAX       TimeStamp
    MAX-ACCESS   read-only
    STATUS       current
    DESCRIPTION
        "The value of the object tQosDomainLastChanged indicates the
         timestamp of last change to the QoS Domain."
    ::= { tQosTimeStampObjects 1 }

tDSCPNameTableLastChanged OBJECT-TYPE
    SYNTAX       TimeStamp
    MAX-ACCESS   read-only
    STATUS       current
    DESCRIPTION
        "The value of the object tDSCPNameTableLastChanged indicates the
         timestamp of last change  to the DSCP Name Table."
    ::= { tQosTimeStampObjects 5 }

tFCNameTableLastChanged OBJECT-TYPE
    SYNTAX       TimeStamp
    MAX-ACCESS   read-only
    STATUS       current
    DESCRIPTION
        "The value of the object tFCNameTableLastChanged indicates the
         timestamp of last change to the FC Name Table."
    ::= { tQosTimeStampObjects 10 }

tSapIngressTableLastChanged OBJECT-TYPE
    SYNTAX       TimeStamp
    MAX-ACCESS   read-only
    STATUS       current
    DESCRIPTION
        "The value of the object tSapIngressTableLastChanged indicates the
         timestamp of last change  to the Sap Ingress Policy Table."
    ::= { tQosTimeStampObjects 20 }

tSapIngressQueueTableLastChanged OBJECT-TYPE
    SYNTAX       TimeStamp
    MAX-ACCESS   read-only
    STATUS       current
    DESCRIPTION
        "tSapIngressQueueTableLastChanged maintains the timestamp of
        the last change made to the Sap Ingress Queue Table."
    ::= { tQosTimeStampObjects 21 }

tSapIngressDSCPTableLastChanged OBJECT-TYPE
    SYNTAX       TimeStamp
    MAX-ACCESS   read-only
    STATUS       current
    DESCRIPTION
        "tSapIngressDSCPTableLastChanged maintains the timestamp of the
        last change made to the Sap Ingress DSCP Mapping Table."
    ::= { tQosTimeStampObjects 22 }

tSapIngressDot1pTableLastChanged OBJECT-TYPE
    SYNTAX       TimeStamp
    MAX-ACCESS   read-only
    STATUS       current
    DESCRIPTION
        "tSapIngressDot1pTableLastChanged maintains the timestamp of the
        last change made to the Sap Ingress Dot1p Table."
    ::= { tQosTimeStampObjects 23 }

tSapIngressIPCriteriaTableLastChanged OBJECT-TYPE
    SYNTAX       TimeStamp
    MAX-ACCESS   read-only
    STATUS       current
    DESCRIPTION
        "tSapIngressIPCriteriaTableLastChanged maintains the timestamp of
        the last change made to the Sap Ingress IP Criteria Table."
    ::= { tQosTimeStampObjects 24 }

tSapIngressMacCriteriaTableLastChanged OBJECT-TYPE
    SYNTAX       TimeStamp
    MAX-ACCESS   read-only
    STATUS       current
    DESCRIPTION
        "tSapIngressMacCriteriaTableLastChanged maintains the timestamp
        of the last change made to the Sap Ingress Mac Criteria Table."
    ::= { tQosTimeStampObjects 25 }

tSapIngressFCTableLastChanged OBJECT-TYPE
    SYNTAX       TimeStamp
    MAX-ACCESS   read-only
    STATUS       current
    DESCRIPTION
        "tSapIngressFCTableLastChanged maintains the timestamp of the
        last change made to the Sap Ingress FC Table."
    ::= { tQosTimeStampObjects 26 }

tSapIngressPrecTableLastChanged OBJECT-TYPE
    SYNTAX       TimeStamp
    MAX-ACCESS   read-only
    STATUS       current
    DESCRIPTION
        "tSapIngressPrecTableLastChanged maintains the timestamp of the
        last change made to the Sap Ingress Precedence Table."
    ::= { tQosTimeStampObjects 27 }  
    
tSapEgressTableLastChanged OBJECT-TYPE
    SYNTAX       TimeStamp
    MAX-ACCESS   read-only
    STATUS       current
    DESCRIPTION
        "tSapEgressTableLastChanged maintains the timestamp of the
        last change made to the Sap Egress Policy Table."
    ::= { tQosTimeStampObjects 30 }

tSapEgressQueueTableLastChanged OBJECT-TYPE
    SYNTAX       TimeStamp
    MAX-ACCESS   read-only
    STATUS       current
    DESCRIPTION
        "tSapEgressQueueTableLastChanged maintains the timestamp of
        the last change made to the Sap Egress Queue Table."
    ::= { tQosTimeStampObjects 31 }

tSapEgressFCTableLastChanged OBJECT-TYPE
    SYNTAX       TimeStamp
    MAX-ACCESS   read-only
    STATUS       current
    DESCRIPTION
        "tSapEgressFCTableLastChanged maintains the timestamp of the
        last change made to the Sap Egress FC Table."
    ::= { tQosTimeStampObjects 32 }

tNetworkPolicyTableLastChanged OBJECT-TYPE
    SYNTAX       TimeStamp
    MAX-ACCESS   read-only
    STATUS       current
    DESCRIPTION
        "tNetworkPolicyTableLastChanged maintains the timestamp of the
        last change made to the Network Policy Table."
    ::= { tQosTimeStampObjects 40 }

tNetworkIngressDSCPTableLastChanged OBJECT-TYPE
    SYNTAX       TimeStamp
    MAX-ACCESS   read-only
    STATUS       current
    DESCRIPTION
        "tNetworkIngressDSCPTableLastChanged maintains the timestamp of
        the last change made to the Network Ingress DSCP Mapping Table."
    ::= { tQosTimeStampObjects 41 }

tNetworkIngressLSPEXPTableLastChanged OBJECT-TYPE
    SYNTAX       TimeStamp
    MAX-ACCESS   read-only
    STATUS       current
    DESCRIPTION
        "tNetworkIngressLSPEXPTableLastChanged maintains the timestamp
        of the last change made to the Network Ingress LSPEXP Table."
    ::= { tQosTimeStampObjects 42 }

tNetworkEgressFCTableLastChanged OBJECT-TYPE
    SYNTAX       TimeStamp
    MAX-ACCESS   read-only
    STATUS       current
    DESCRIPTION
        "tNetworkEgressFCTableLastChanged maintains the timestamp of
        the last change made to the Network Egress FC Table."
    ::= { tQosTimeStampObjects 43 }

tNetworkIngressDot1pTableLastChanged OBJECT-TYPE
    SYNTAX       TimeStamp
    MAX-ACCESS   read-only
    STATUS       current
    DESCRIPTION
        "tNetworkIngressDot1pTableLastChanged maintains the timestamp
        of the last change made to the Network Ingress Dot1p Table."
    ::= { tQosTimeStampObjects 44 }

tNetworkQueuePolicyTableLastChanged OBJECT-TYPE
    SYNTAX       TimeStamp
    MAX-ACCESS   read-only
    STATUS       current
    DESCRIPTION
        "tNetworkQueuePolicyTableLastChanged maintains the timestamp of
        the last change made to the Network Queue Policy Table."
    ::= { tQosTimeStampObjects 50 }

tNetworkQueueTableLastChanged OBJECT-TYPE
    SYNTAX       TimeStamp
    MAX-ACCESS   read-only
    STATUS       current
    DESCRIPTION
        "tNetworkQueueTableLastChanged maintains the timestamp of the
        last change made to the Network Queue Table."
    ::= { tQosTimeStampObjects 51 }

tNetworkQueueFCTableLastChanged OBJECT-TYPE
    SYNTAX       TimeStamp
    MAX-ACCESS   read-only
    STATUS       current
    DESCRIPTION
        "tNetworkQueueFCTableLastChanged maintains the timestamp of the
        last change made to the Network Queue FC Table."
    ::= { tQosTimeStampObjects 52 }

tSlopePolicyTableLastChanged OBJECT-TYPE
    SYNTAX       TimeStamp
    MAX-ACCESS   read-only
    STATUS       current
    DESCRIPTION
        "tSlopePolicyTableLastChanged maintains the timestamp of the
        last change made to the Slope Policy Table."
    ::= { tQosTimeStampObjects 55 }

tSchedulerPolicyTableLastChanged OBJECT-TYPE
    SYNTAX       TimeStamp
    MAX-ACCESS   read-only
    STATUS       current
    DESCRIPTION
        "tSchedulerPolicyTableLastChanged maintains the timestamp of
        the last change made to the Scheduler Policy Table."
    ::= { tQosTimeStampObjects 60 }

tVirtualSchedulerTableLastChanged OBJECT-TYPE
    SYNTAX       TimeStamp
    MAX-ACCESS   read-only
    STATUS       current
    DESCRIPTION
        "tVirtualSchedulerTableLastChanged maintains the timestamp of
        the last change made to the Virtual Scheduler Table."
    ::= { tQosTimeStampObjects 61 }

tAtmTdpTableLastChanged OBJECT-TYPE
    SYNTAX       TimeStamp
    MAX-ACCESS   read-only
    STATUS       current
    DESCRIPTION
        "tAtmTdpTableLastChanged maintains the timestamp of
         the last change made to the Traffic Descriptor Profile Table."
    ::= { tQosTimeStampObjects 62 }

tSharedQueuePolicyTableLastChanged OBJECT-TYPE
    SYNTAX       TimeStamp
    MAX-ACCESS   read-only
    STATUS       current
    DESCRIPTION
        "tSharedQueuePolicyTableLastChanged maintains the timestamp of
        the last change made to the Queue Policy Table."
    ::= { tQosTimeStampObjects 63 }

tSharedQueueTableLastChanged OBJECT-TYPE
    SYNTAX       TimeStamp
    MAX-ACCESS   read-only
    STATUS       current
    DESCRIPTION
        "tSharedQueueTableLastChanged maintains the timestamp of the
        last change made to the Queue Table."
    ::= { tQosTimeStampObjects 64 }

tSharedQueueFCTableLastChanged OBJECT-TYPE
    SYNTAX       TimeStamp
    MAX-ACCESS   read-only
    STATUS       current
    DESCRIPTION
        "tSharedQueueFCTableLastChanged maintains the timestamp of the
        last change made to the Queue FC Table."
    ::= { tQosTimeStampObjects 65 }


tSapIngressIPv6CriteriaTableLastChanged OBJECT-TYPE
    SYNTAX       TimeStamp
    MAX-ACCESS   read-only
    STATUS       current
    DESCRIPTION
        "The value of the object tSapIngressIPv6CriteriaTableLastChanged
         indicates the timestamp of the last change made to the Sap Ingress
         IPv6 Criteria Table."
    ::= { tQosTimeStampObjects 66 }

tSapIngrHsmdaQueueTblLastChngd OBJECT-TYPE
    SYNTAX       TimeStamp
    MAX-ACCESS   read-only
    STATUS       obsolete
    DESCRIPTION
        "tSapIngrHsmdaQueueTblLastChngd maintains the timestamp of the
        last change made to the Sap Ingress HSMDA Queue Table.

        This object is obsoleted in 10.0 Release."
    ::= { tQosTimeStampObjects 67 }

tSapEgrHsmdaQueueTblLastChngd OBJECT-TYPE
    SYNTAX       TimeStamp
    MAX-ACCESS   read-only
    STATUS       current
    DESCRIPTION
        "tSapEgrHsmdaQueueTblLastChngd maintains the timestamp of the
        last change made to the Sap Egress HSMDA Queue Table."
    ::= { tQosTimeStampObjects 68 }

tHsmdaSchedPlcyTblLastChngd OBJECT-TYPE
    SYNTAX       TimeStamp
    MAX-ACCESS   read-only
    STATUS       current
    DESCRIPTION
        "tHsmdaSchedPlcyTblLastChngd maintains the timestamp of the
        last change made to the HSMDA Scheduler Policy Table."
    ::= { tQosTimeStampObjects 69 }

tHsmdaSchedPlcyGrpTblLastChngd OBJECT-TYPE
    SYNTAX       TimeStamp
    MAX-ACCESS   read-only
    STATUS       current
    DESCRIPTION
        "tHsmdaSchedPlcyGrpTblLastChngd maintains the timestamp of the
        last change made to the HSMDA Scheduler Policy Group Table."
    ::= { tQosTimeStampObjects 70 }

tHsmdaPoolPlcyTblLastChngd OBJECT-TYPE
    SYNTAX       TimeStamp
    MAX-ACCESS   read-only
    STATUS       current
    DESCRIPTION
        "tHsmdaPoolPlcyTblLastChngd maintains the timestamp of the
        last change made to the HSMDA Pool Policy Table."
    ::= { tQosTimeStampObjects 71 }

tHsmdaSlopePolicyTableLastChanged OBJECT-TYPE
    SYNTAX       TimeStamp
    MAX-ACCESS   read-only
    STATUS       current
    DESCRIPTION
        "tHsmdaSlopePolicyTableLastChanged maintains the timestamp of the
        last change made to the Hsmda Slope Policy Table."
    ::= { tQosTimeStampObjects 72 }

tNamedPoolPolicyTableLastChanged OBJECT-TYPE
    SYNTAX       TimeStamp
    MAX-ACCESS   read-only
    STATUS       current
    DESCRIPTION
        "The value of tNamedPoolPolicyTableLastChanged indicates the sysUpTime
         at the time of the last modification of an entry in the
         tNamedPoolPolicyTable.

         If no changes were made to the table since the last re-initialization
         of the local network management subsystem, then this object
         contains a zero value."
    ::= { tQosTimeStampObjects 73 }

tQ1NamedPoolTableLastChanged OBJECT-TYPE
    SYNTAX       TimeStamp
    MAX-ACCESS   read-only
    STATUS       current
    DESCRIPTION
        "The value of tQ1NamedPoolTableLastChanged indicates the sysUpTime
         at the time of the last modification of an entry in the
         tQ1NamedPoolTable.

         If no changes were made to the table since the last re-initialization
         of the local network management subsystem, then this object
         contains a zero value."
    ::= { tQosTimeStampObjects 74 }

tMcMlpppIngrProfTableLastChanged OBJECT-TYPE
    SYNTAX       TimeStamp
    MAX-ACCESS   read-only
    STATUS       current
    DESCRIPTION
        "The value of tMcMlpppIngrProfTableLastChanged indicates the sysUpTime
         at the time of the last modification of an entry in the
         tMcMlpppIngrProfTable.

         If no changes were made to the table since the last re-initialization
         of the local network management subsystem, then this object
         contains a zero value."
    ::= { tQosTimeStampObjects 75 }

tMcMlpppIngrClassTableLastChanged OBJECT-TYPE
    SYNTAX       TimeStamp
    MAX-ACCESS   read-only
    STATUS       current
    DESCRIPTION
        "The value of tMcMlpppIngrClassTableLastChanged indicates the sysUpTime
         at the time of the last modification of an entry in the
         tMcMlpppIngrClassTable.

         If no changes were made to the table since the last re-initialization
         of the local network management subsystem, then this object
         contains a zero value."
    ::= { tQosTimeStampObjects 76 }

tMcMlpppEgrProfTableLastChanged OBJECT-TYPE
    SYNTAX       TimeStamp
    MAX-ACCESS   read-only
    STATUS       current
    DESCRIPTION
        "The value of tMcMlpppEgrProfTableLastChanged indicates the sysUpTime
         at the time of the last modification of an entry in the
         tMcMlpppEgrProfTable.

         If no changes were made to the table since the last re-initialization
         of the local network management subsystem, then this object
         contains a zero value."
    ::= { tQosTimeStampObjects 77 }

tMcMlpppEgrClassTableLastChanged OBJECT-TYPE
    SYNTAX       TimeStamp
    MAX-ACCESS   read-only
    STATUS       current
    DESCRIPTION
        "The value of tMcMlpppEgrClassTableLastChanged indicates the sysUpTime
         at the time of the last modification of an entry in the
         tMcMlpppEgrClassTable.

         If no changes were made to the table since the last re-initialization
         of the local network management subsystem, then this object
         contains a zero value."
    ::= { tQosTimeStampObjects 78 }

tMcMlpppEgrFCTableLastChanged OBJECT-TYPE
    SYNTAX       TimeStamp
    MAX-ACCESS   read-only
    STATUS       current
    DESCRIPTION
        "The value of tMcMlpppEgrFCTableLastChanged indicates the sysUpTime
         at the time of the last modification of an entry in the
         tMcMlpppEgrFCTable.

         If no changes were made to the table since the last re-initialization
         of the local network management subsystem, then this object
         contains a zero value."
    ::= { tQosTimeStampObjects 79 }

tMcFrIngrProfTableLastChanged OBJECT-TYPE
    SYNTAX       TimeStamp
    MAX-ACCESS   read-only
    STATUS       current
    DESCRIPTION
        "The value of tMcFrIngrProfTableLastChanged indicates the sysUpTime
         at the time of the last modification of an entry in the
         tMcFrIngrProfTable.

         If no changes were made to the table since the last re-initialization
         of the local network management subsystem, then this object
         contains a zero value."
    ::= { tQosTimeStampObjects 80 }

tMcFrIngrClassTableLastChanged OBJECT-TYPE
    SYNTAX       TimeStamp
    MAX-ACCESS   read-only
    STATUS       current
    DESCRIPTION
        "The value of tMcFrIngrClassTableLastChanged indicates the sysUpTime
         at the time of the last modification of an entry in the
         tMcFrIngrClassTable.

         If no changes were made to the table since the last re-initialization
         of the local network management subsystem, then this object
         contains a zero value."
    ::= { tQosTimeStampObjects 81 }

tMcFrEgrProfTableLastChanged OBJECT-TYPE
    SYNTAX       TimeStamp
    MAX-ACCESS   read-only
    STATUS       current
    DESCRIPTION
        "The value of tMcFrEgrProfTableLastChanged indicates the sysUpTime
         at the time of the last modification of an entry in the
         tMcFrEgrProfTable.

         If no changes were made to the table since the last re-initialization
         of the local network management subsystem, then this object
         contains a zero value."
    ::= { tQosTimeStampObjects 82 }

tMcFrEgrClassTableLastChanged OBJECT-TYPE
    SYNTAX       TimeStamp
    MAX-ACCESS   read-only
    STATUS       current
    DESCRIPTION
        "The value of tMcFrEgrClassTableLastChanged indicates the sysUpTime
         at the time of the last modification of an entry in the
         tMcFrEgrClassTable.

         If no changes were made to the table since the last re-initialization
         of the local network management subsystem, then this object
         contains a zero value."
    ::= { tQosTimeStampObjects 83 }  
    
tSapIngressLspExpTableLastChange OBJECT-TYPE
    SYNTAX       TimeStamp
    MAX-ACCESS   read-only
    STATUS       current
    DESCRIPTION
        "The value of tSapIngressLspExpTableLastChange indicates the sysUpTime
         at the time of the last modification of an entry in the
         tSapIngressLspExpTable.

         If no changes were made to the table since the last re-initialization
         of the local network management subsystem, then this object
         contains a zero value."
    ::= { tQosTimeStampObjects 84 }


--
-- Atm Traffic Descriptor Table
--

tAtmTdpTable OBJECT-TYPE
    SYNTAX       SEQUENCE OF TAtmTdpEntry
    MAX-ACCESS   not-accessible
    STATUS       current
    DESCRIPTION
        "This table contains information on ATM traffic
         descriptors for controlling ATM traffic
         management capabilities."
    ::= { tAtmTdpObjects 1}

tAtmTdpEntry OBJECT-TYPE
    SYNTAX       TAtmTdpEntry
    MAX-ACCESS   not-accessible
    STATUS       current
    DESCRIPTION
        "This list contains ATM traffic descriptor
         objects and the associated parameters. All objects that
         do not apply to a given service category are given default
         values of zero."
    INDEX  {tAtmTdpIndex}
    ::= { tAtmTdpTable 1}

TAtmTdpEntry ::= SEQUENCE
    {
        tAtmTdpIndex        AtmTrafficDescrParamIndex,
        tAtmTdpSir          Unsigned32,
        tAtmTdpPir          Unsigned32,
        tAtmTdpMbs          Unsigned32,
        tAtmTdpMir          Unsigned32,
        tAtmTdpShaping      INTEGER,
        tAtmTdpServCat      AtmServiceCategory,
        tAtmTdpDescription  TItemDescription,
        tAtmTdpLastChanged  TimeStamp,
        tAtmTdpRowStatus    RowStatus,
        tAtmTdpDescrType    TAtmTdpDescrType,
        tAtmTdpCdvt         Unsigned32,
        tAtmTdpPolicing     INTEGER,
        tAtmTdpCLPTagging   INTEGER,
        tAtmTdpWeight       Integer32
    }

tAtmTdpIndex OBJECT-TYPE
    SYNTAX       AtmTrafficDescrParamIndex (1..1000)
    MAX-ACCESS   not-accessible
    STATUS       current
    DESCRIPTION
        "This object is used to identify an entity
         inside the tAtmTdpTable.
         When creating a new row in the table
         the value of this index may be obtained
         by retrieving the value of tAtmTdpIndexNext."
    ::= { tAtmTdpEntry 1 }

tAtmTdpSir OBJECT-TYPE
    SYNTAX       Unsigned32 (0..4294967295)
    MAX-ACCESS   read-create
    STATUS       current
    DESCRIPTION
        "tAtmTdpSir identifies the sustained information rate
         in kilobits per second.
         The default Sir is determined by the Service Category.
         The following default applies to Sir that is modifiable
         depending upon a given service category:

           Applicable Service Category  Default Sir Value
                   RT-VBR                       0
                  NRT-VBR                       0

         Note that for the service categories given above,
         the value of Sir must be less than or equal to
         the value of Pir."
    ::= { tAtmTdpEntry 2 }

tAtmTdpPir OBJECT-TYPE
    SYNTAX       Unsigned32 (0..4294967295)
    MAX-ACCESS   read-create
    STATUS       current
    DESCRIPTION
        "tAtmTdpPir identifies the peak information rate
         in kilobits per second.
         The default Pir is determined by the Service Category.
         The following default applies to Pir that is modifiable
         depending upon a given service category:

           Applicable Service Category   Default Pir Value
                UBR (with/without Mir)          4294967295
                CBR                             0
             RT-VBR                             0
            NRT-VBR                             0"
    ::= { tAtmTdpEntry 3 }

tAtmTdpMbs OBJECT-TYPE
    SYNTAX       Unsigned32 (0..4294967295)
    MAX-ACCESS   read-create
    STATUS       current
    DESCRIPTION
        "tAtmTdpMbs identifies the maximum burst size
         in cells.
         The default Mbs is determined by the Service Category.
         The following default applies to Mbs that is modifiable
         depending upon a given service category:

           Applicable Service Category  Default Mbs Value
                    RT-VBR                     32
                   NRT-VBR                     32"
    ::= { tAtmTdpEntry 4 }

tAtmTdpMir OBJECT-TYPE
    SYNTAX       Unsigned32 (0..4294967295)
    MAX-ACCESS   read-create
    STATUS       current
    DESCRIPTION
        "tAtmTdpMir identifies the Minimum Information Rate
         in kilobits per second.
         The default Mir is determined by the Service Category.
         The following default applies for Mir that is modifiable
         depending upon a given service category:

           Applicable Service Category  Default Mir Value
             UBR (with/without Mir)             0

         Note that for the service categories given above,
         the value of Mir must be less than or equal to
         the value of Pir."
    ::= { tAtmTdpEntry 5 }

tAtmTdpShaping OBJECT-TYPE
    SYNTAX       INTEGER {
                     disabled(0),
                     enabled(1)
                 }
    MAX-ACCESS   read-create
    STATUS       current
    DESCRIPTION
        "tAtmTdpShaping determines whether egress shaping should occur.
         The default tAtmTdpShaping is determined by the Service Category.
         The following default applies for tAtmTdpShaping
         depending upon a given service category:

          Applicable Service Category  Default Shaping Value
                UBR                         disabled
                CBR                         enabled
             RT-VBR                         enabled
            NRT-VBR                         enabled

         For a Service Category of UBR, tAtmTdpShaping cannot be enabled.
        
         For CBR and RT-VBR service cateories disabling shaping is 
         MDA-dependent.

         Shaping is only applied in the egress direction."
    ::= { tAtmTdpEntry 6 }

tAtmTdpServCat OBJECT-TYPE
    SYNTAX       AtmServiceCategory
    MAX-ACCESS   read-create
    STATUS       current
    DESCRIPTION
        "tAtmTdpServCat determines the ATM service category."
    DEFVAL { ubr }
    ::= { tAtmTdpEntry 7 }

tAtmTdpDescription OBJECT-TYPE
    SYNTAX       TItemDescription
    MAX-ACCESS   read-create
    STATUS       current
    DESCRIPTION
        "The value of tAtmTdpDescription specifies an ASCII string used
         to describe the ATM traffic descriptor."
    ::= { tAtmTdpEntry 8 }

tAtmTdpLastChanged OBJECT-TYPE
    SYNTAX       TimeStamp
    MAX-ACCESS   read-only
    STATUS       current
    DESCRIPTION
        "tAtmTdpLastChanged maintains the timestamp of the last change
         made to a row in the Traffic Descriptor Profile Table."
    ::= { tAtmTdpEntry 9 }

tAtmTdpRowStatus OBJECT-TYPE
    SYNTAX       RowStatus
    MAX-ACCESS   read-create
    STATUS       current
    DESCRIPTION
        "tAtmTdpRowStatus is used to create/modify/delete a new row in
         this table. Only createAndGo/Active/Destroy are supported"
    ::= { tAtmTdpEntry 10 }

tAtmTdpDescrType OBJECT-TYPE
    SYNTAX       TAtmTdpDescrType
    MAX-ACCESS   read-create
    STATUS       current
    DESCRIPTION
        "tAtmTdpDescrType identifies the types of ATM traffic descriptor.
         The default is determined by the value of tAtmTdpServCat.
         The following default rules apply:

         Applicable Service Category       tAtmTdpDescrType
                UBR                          clp0And1pcr
                CBR                          clp0And1pcr
             RT-VBR                    clp0And1pcrPlusClp0And1scr
            NRT-VBR                    clp0And1pcrPlusClp0And1scr"
    ::= { tAtmTdpEntry 11 }

tAtmTdpCdvt OBJECT-TYPE
    SYNTAX       Unsigned32 (0..4294967295)
    MAX-ACCESS   read-create
    STATUS       current
    DESCRIPTION
        "tAtmTdpCdvt identifies the Cell Delay Variation
         Tolerance in microseconds.
         The following default applies for Cdvt that is modifiable
         depending upon a given service category:

           Applicable Service Category  Default Cdvt Value
             CBR/RT-VBR/NRT-VBR/UBR             250 "

    ::= { tAtmTdpEntry 12 }

tAtmTdpPolicing OBJECT-TYPE
    SYNTAX       INTEGER {
                     disabled(0),
                     enabled(1)
                 }
    MAX-ACCESS   read-create
    STATUS       current
    DESCRIPTION
        "tAtmTdpPolicing determines whether ingress traffic is policed.
         Policing by default is disabled. Policing is valid for CBR, UBR
         RT-VBR and NRT-VBR. This is cell-based policing.

          tAtmTdpDescrType           Policing Scheme    Applicable Serv Cat
           clp0And1pcr                 CBR.1             CBR and UBR
           clp0And1pcrPlusClp0And1scr  VBR.1             RT/NRT-VBR
           clp0And1pcrPlusClp0scr      VBR.2             RT/NRT-VBR
           clp0And1pcrPlusClp0scrTag   VBR.3             RT/NRT-VBR"
    ::= { tAtmTdpEntry 13 }

tAtmTdpCLPTagging OBJECT-TYPE
    SYNTAX       INTEGER {
                     disabled(0),
                     enabled(1)
                 }
    MAX-ACCESS   read-create
    STATUS       current
    DESCRIPTION
        "tAtmTdpCLPTagging controls the setting of the CLP bit in the 
         ATM cell  header for egress traffic on an IES or VPRN SAP. 
         If disabled (the default), all traffic has the CLP bit set 
         to zero. If enabled, traffic queued on expedited queues has 
         the CLP bit set to zero, while traffic on non-expedited queues 
         has the CLP bit set to one."
    DEFVAL { 0 }
    ::= { tAtmTdpEntry 14 }

tAtmTdpWeight OBJECT-TYPE
    SYNTAX       Integer32 (1..255)
    MAX-ACCESS   read-create
    STATUS       current
    DESCRIPTION
        "The value of tAtmTdpWeight specifies the relative weight assigned
         to this ATM traffic descriptor with respect to ATM VP shaper scheduling.
         
         The value of tAtmTdpWeight is only relevant for MDA where the value
         of TIMETRA-CHASSIS-MIB::tmnxMDAAtmMode is equal to max16kVc, and is
         ignored otherwise.
         
         If the value of tAtmTdpWeight is not specified when the conceptual row 
         is created, the weight is derived from the ATM service category:
             CBR                10
             rt-VBR             7
             nrt-VBR            5
             UBR+ (nonzero MIR) 2
             UBR (zero MIR)     1."
    ::= { tAtmTdpEntry 15 }


--
-- Named Pool Policy Table
--

tNamedPoolPolicyTable OBJECT-TYPE
    SYNTAX       SEQUENCE OF TNamedPoolPolicyEntry
    MAX-ACCESS   not-accessible
    STATUS       current
    DESCRIPTION
        "This table contains information on Named buffer pools policy."
    ::= { tPoolObjects 1 }

tNamedPoolPolicyEntry OBJECT-TYPE
    SYNTAX       TNamedPoolPolicyEntry
    MAX-ACCESS   not-accessible
    STATUS       current
    DESCRIPTION
        "This list contains Named buffer pools policy related information."
    INDEX  {tNamedPoolPolicyName}
    ::= { tNamedPoolPolicyTable 1}

TNamedPoolPolicyEntry ::= SEQUENCE
    {
       tNamedPoolPolicyName               TNamedItem,
       tNamedPoolPolicyRowStatus          RowStatus,
       tNamedPoolPolicyLastChanged        TimeStamp,
       tNamedPoolPolicyDescription        TItemDescription,
       tNamedPoolPolicyQ1DefaultWeight    Unsigned32,
       tNamedPoolPolicyQ1MdaWeight        Unsigned32,
       tNamedPoolPolicyQ1PortWeight       Unsigned32
    }

tNamedPoolPolicyName OBJECT-TYPE
    SYNTAX      TNamedItem
    MAX-ACCESS  not-accessible
    STATUS      current
    DESCRIPTION
        "The value of tNamedPoolPolicyName indicates the name of 
         Named pool policy."
    ::= { tNamedPoolPolicyEntry 1 }

tNamedPoolPolicyRowStatus OBJECT-TYPE
    SYNTAX      RowStatus
    MAX-ACCESS  read-create
    STATUS      current
    DESCRIPTION
        "The value of tNamedPoolPolicyRowStatus is used for 
         creation or deletion of named pool policies."
    ::= { tNamedPoolPolicyEntry 2 }

tNamedPoolPolicyLastChanged OBJECT-TYPE
    SYNTAX      TimeStamp
    MAX-ACCESS  read-only
    STATUS      current
    DESCRIPTION
        "The value of tNamedPoolPolicyLastChanged indicates the 
         sysUpTime when this row was last modified."
    ::= { tNamedPoolPolicyEntry 3 }

tNamedPoolPolicyDescription OBJECT-TYPE
    SYNTAX      TItemDescription
    MAX-ACCESS  read-create
    STATUS      current
    DESCRIPTION
        "The value of tNamedPoolPolicyDescription specifies the 
         description for a specific named pool policy."
    DEFVAL { "" }
    ::= { tNamedPoolPolicyEntry 4 }

tNamedPoolPolicyQ1DefaultWeight OBJECT-TYPE
    SYNTAX      Unsigned32 (0..100)
    MAX-ACCESS  read-create
    STATUS      current
    DESCRIPTION
        "The value of tNamedPoolPolicyQ1DefaultWeight specifies 
         the port allocation weight given to the default pools."
    DEFVAL { 50 }
    ::= { tNamedPoolPolicyEntry 5 }

tNamedPoolPolicyQ1MdaWeight OBJECT-TYPE
    SYNTAX      Unsigned32 (0..100)
    MAX-ACCESS  read-create
    STATUS      current
    DESCRIPTION
        "The value of tNamedPoolPolicyQ1MdaWeight specifies 
         the port allocation weight given to the MDA named pools."
    DEFVAL { 50 }
    ::= { tNamedPoolPolicyEntry 6 }

tNamedPoolPolicyQ1PortWeight OBJECT-TYPE
    SYNTAX      Unsigned32 (0..100)
    MAX-ACCESS  read-create
    STATUS      current
    DESCRIPTION
        "The value of tNamedPoolPolicyQ1PortWeight specifies 
         the port allocation weight given to the local port 
         named pools."
    DEFVAL { 50 }
    ::= { tNamedPoolPolicyEntry 7 }



--
-- Q1 Named Pool Table
--

tQ1NamedPoolTable OBJECT-TYPE
    SYNTAX       SEQUENCE OF TQ1NamedPoolEntry
    MAX-ACCESS   not-accessible
    STATUS       current
    DESCRIPTION
        "This table contains information on Q1 pools policy."
    ::= { tPoolObjects 2 }

tQ1NamedPoolEntry OBJECT-TYPE
    SYNTAX       TQ1NamedPoolEntry
    MAX-ACCESS   not-accessible
    STATUS       current
    DESCRIPTION
        "This list contains Q1 pools policy related information."
    INDEX  {tQ1NamedPoolPolicyName, 
            tQ1NamedPoolName}
    ::= { tQ1NamedPoolTable 1}

TQ1NamedPoolEntry ::= SEQUENCE
    {
       tQ1NamedPoolPolicyName               TNamedItem,
       tQ1NamedPoolName                     TNamedItem,
       tQ1NamedPoolRowStatus                RowStatus,
       tQ1NamedPoolLastChanged              TimeStamp,
       tQ1NamedPoolDescription              TItemDescription,
       tQ1NamedPoolNetworkAllocWeight       Unsigned32,
       tQ1NamedPoolAccessAllocWeight        Unsigned32,
       tQ1NamedPoolSlopePolicy              TNamedItemOrEmpty,
       tQ1NamedPoolReservedCbs              Integer32,
       tQ1NamedPoolResvCbsAmbrAlrmStep     Integer32,
       tQ1NamedPoolResvCbsAmbrAlrmMax      Integer32,
       tQ1NamedPoolAmbrAlrmThresh          Integer32,
       tQ1NamedPoolRedAlrmThresh            Integer32
    }

tQ1NamedPoolPolicyName OBJECT-TYPE
    SYNTAX      TNamedItem
    MAX-ACCESS  not-accessible
    STATUS      current
    DESCRIPTION
        "The value of tQ1NamedPoolPolicyName indicates the name of 
         the existing Q1 named pool policy."
    ::= { tQ1NamedPoolEntry 1 }

tQ1NamedPoolName OBJECT-TYPE
    SYNTAX      TNamedItem
    MAX-ACCESS  not-accessible
    STATUS      current
    DESCRIPTION
        "The value of tQ1NamedPoolName indicates the name of 
         the existing pool within the policy."
    ::= { tQ1NamedPoolEntry 2 }

tQ1NamedPoolRowStatus OBJECT-TYPE
    SYNTAX      RowStatus
    MAX-ACCESS  read-create
    STATUS      current
    DESCRIPTION
        "The value of tQ1NamedPoolRowStatus is used for 
         creation or deletion of Q1 named pools."       
    ::= { tQ1NamedPoolEntry 3 }

tQ1NamedPoolLastChanged OBJECT-TYPE
    SYNTAX      TimeStamp
    MAX-ACCESS  read-only
    STATUS      current
    DESCRIPTION
        "The value of tQ1NamedPoolLastChanged indicates the 
         sysUpTime when this row was last modified. "
    ::= { tQ1NamedPoolEntry 4 }

tQ1NamedPoolDescription OBJECT-TYPE
    SYNTAX      TItemDescription
    MAX-ACCESS  read-create
    STATUS      current
    DESCRIPTION
        "The value of tQ1NamedPoolDescription specifies the 
         description for a specific Q1 named pool."
    DEFVAL { "" }
    ::= { tQ1NamedPoolEntry 5 }

tQ1NamedPoolNetworkAllocWeight OBJECT-TYPE
    SYNTAX      Unsigned32 (0..100)
    MAX-ACCESS  read-create
    STATUS      current
    DESCRIPTION
        "The value of tQ1NamedPoolNetworkAllocWeight specifies 
         the weight used to divide network associated buffer 
         space between named pools."
    DEFVAL { 50 }
    ::= { tQ1NamedPoolEntry 6 }


tQ1NamedPoolAccessAllocWeight OBJECT-TYPE
    SYNTAX      Unsigned32 (0..100)
    MAX-ACCESS  read-create
    STATUS      current
    DESCRIPTION
        "The value of tQ1NamedPoolAccessAllocWeight specifies 
         the weight used to divide access associated buffer 
         space between named pools."
    DEFVAL { 50 }
    ::= { tQ1NamedPoolEntry 7 }

tQ1NamedPoolSlopePolicy OBJECT-TYPE
    SYNTAX      TNamedItemOrEmpty
    MAX-ACCESS  read-create
    STATUS      current
    DESCRIPTION
        "The value of tQ1NamedPoolSlopePolicy specifies the 
         name of the slop-policy which is used to override 
         the default slope-policy for the named buffer pool."
    DEFVAL { ''H }
    ::= { tQ1NamedPoolEntry 8 }

tQ1NamedPoolReservedCbs OBJECT-TYPE
    SYNTAX      Integer32 (0..100)
    MAX-ACCESS  read-create
    STATUS      current
    DESCRIPTION
        "The value of tQ1NamedPoolReservedCbs specifies the 
         reserved CBS size of the pool. The reserved CBS 
         (Committed Burst Size) defines the amount of buffer 
         space within the pool that is not considered shared."
    DEFVAL { 30 }
    ::= { tQ1NamedPoolEntry 9 }

tQ1NamedPoolResvCbsAmbrAlrmStep OBJECT-TYPE
    SYNTAX      Integer32 (0..100)
    UNITS       "percent"
    MAX-ACCESS  read-create
    STATUS      current
    DESCRIPTION
        "The value of tQ1NamedPoolResvCbsAmbrAlrmStep specifies the 
         percentage step-size for the reserved CBS size of the pool.
         When tQ1NamedPoolResvCbsAmbrAlrmStep is set to default value, the 
         adaptive CBS sizing is disabled. To enable adaptive CBS sizing,
         tQ1NamedPoolResvCbsAmbrAlrmStep MUST be set to non-default value along 
         with tQ1NamedPoolResvCbsAmbrAlrmMax. When reserved CBS is default 
         adaptive CBS sizing cannot be enabled. The reserved CBS (Committed 
         Burst Size) defines the amount of buffer space within the pool that is
         not considered shared."
    DEFVAL { 0 }
    ::= { tQ1NamedPoolEntry 10 }

tQ1NamedPoolResvCbsAmbrAlrmMax OBJECT-TYPE
    SYNTAX      Integer32 (0..100)
    UNITS       "percent"
    MAX-ACCESS  read-create
    STATUS      current
    DESCRIPTION
        "The value of tQ1NamedPoolResvCbsAmbrAlrmMax specifies the 
         maximum percentage for the reserved CBS size of the pool. 
         When tQ1NamedPoolResvCbsAmbrAlrmMax is set to default value, the 
         adaptive CBS sizing is disabled. To enable adaptive CBS sizing,
         tQ1NamedPoolResvCbsAmbrAlrmMax MUST be set to non-default value along
         with tQ1NamedPoolResvCbsAmbrAlrmStep. When reserved CBS is default 
         adaptive CBS sizing cannot be enabled. The reserved CBS (Committed 
         Burst Size) defines the amount of buffer space within the pool that is 
         not considered shared. Max reserved CBS must not be more than the
         reserved CBS."
    DEFVAL { 0 }
    ::= { tQ1NamedPoolEntry 11 }

tQ1NamedPoolAmbrAlrmThresh OBJECT-TYPE
    SYNTAX      Integer32 (0..1000)
    UNITS       "percent"
    MAX-ACCESS  read-create
    STATUS      current
    DESCRIPTION
        "The value of tQ1NamedPoolAmbrAlrmThresh specifies the 
         threshold for the amber alarm on the over-subscription allowed."
    DEFVAL { 0 }
    ::= { tQ1NamedPoolEntry 12 }

tQ1NamedPoolRedAlrmThresh OBJECT-TYPE
    SYNTAX      Integer32 (0..1000)
    UNITS       "percent"
    MAX-ACCESS  read-create
    STATUS      current
    DESCRIPTION
        "The value of tQ1NamedPoolRedAlrmThresh specifies the 
         threshold for the red alarm on the over-subscription allowed."
    DEFVAL { 0 }
    ::= { tQ1NamedPoolEntry 13 }

--
-- The following object may be used in conjunction with
-- the atmTrafficDescrParamTable for the creation of
-- new table entries.
--

tAtmTdpIndexNext OBJECT-TYPE
    SYNTAX       Integer32 (0..1000)
    MAX-ACCESS   read-only
    STATUS       current
    DESCRIPTION
        "This object contains an appropriate value to be used for
         tAtmTdpIndex when creating entries in the tAtmTdpTable.
         The value 0 indicates that no unassigned entries are
         available. To obtain the tAtmTdpIndex value for a new
         entry, the manager issues a management protocol
         retrieval operation to obtain the current value of this
         object.  After each retrieval, the agent should modify the
         value to the next unassigned index.
         After a manager retrieves a value the agent will determine
         through its local policy when this index value will be made
         available for reuse."
    ::= { tAtmTdpObjects 2 }

---
--- The following objects are to be used in
--- conjunction with the tAtmTdpTable
--- for information on profile limits and consumed
--- profiles.
---

tAtmTdpsMaxSupported OBJECT-TYPE
    SYNTAX       Integer32
    MAX-ACCESS   read-only
    STATUS       current
    DESCRIPTION
        "This object contains the maximum number of ATM
         Traffic Descriptor Profiles that can be configured
         on this system."
    ::= { tAtmTdpObjects 3 }

tAtmTdpsCurrentlyConfigured OBJECT-TYPE
    SYNTAX       Integer32
    MAX-ACCESS   read-only
    STATUS       current
    DESCRIPTION
        "This object contains the number of currently configured
         ATM Traffic Descriptor Profiles on this system."
    ::= { tAtmTdpObjects 4 }

--
-- Hsmda Pool Policy Table
--

tHsmdaPoolPolicyTable OBJECT-TYPE
    SYNTAX      SEQUENCE OF THsmdaPoolPolicyEntry
    MAX-ACCESS  not-accessible
    STATUS      current
    DESCRIPTION
        "The tHsmdaPoolPolicyTable has an entry for each HSMDA pool
         policy configured on this system."
    ::= { tPoolObjects 3 }

tHsmdaPoolPolicyEntry    OBJECT-TYPE
    SYNTAX      THsmdaPoolPolicyEntry
    MAX-ACCESS  not-accessible
    STATUS      current
    DESCRIPTION
        "Each row represents a particular HSMDA pool policy. Entries are 
         created and deleted by the user."
    INDEX { tHsmdaPoolPolicyName }
    ::= { tHsmdaPoolPolicyTable 1}

THsmdaPoolPolicyEntry ::= SEQUENCE
    {
         tHsmdaPoolPolicyName             TNamedItem,
         tHsmdaPoolPolicyRowStatus        RowStatus,
         tHsmdaPoolLastChanged            TimeStamp,
         tHsmdaPoolDescription            TItemDescription,
         tHsmdaPoolSystemReserve          Unsigned32,
         tHsmdaPoolRoot1AllocWeight       TWeight,
         tHsmdaPoolRoot2AllocWeight       TWeight,
         tHsmdaPoolRoot3AllocWeight       TWeight,
         tHsmdaPoolRoot4AllocWeight       TWeight,
         tHsmdaPoolRoot5AllocWeight       TWeight,
         tHsmdaPoolRoot6AllocWeight       TWeight,
         tHsmdaPoolRoot7AllocWeight       TWeight,
         tHsmdaPoolRoot8AllocWeight       TWeight,
         tHsmdaPoolClass1Parent           Unsigned32,
         tHsmdaPoolClass1AllocPercent     Unsigned32,
         tHsmdaPoolClass2Parent           Unsigned32,
         tHsmdaPoolClass2AllocPercent     Unsigned32,
         tHsmdaPoolClass3Parent           Unsigned32,
         tHsmdaPoolClass3AllocPercent     Unsigned32,
         tHsmdaPoolClass4Parent           Unsigned32,
         tHsmdaPoolClass4AllocPercent     Unsigned32,
         tHsmdaPoolClass5Parent           Unsigned32,
         tHsmdaPoolClass5AllocPercent     Unsigned32,
         tHsmdaPoolClass6Parent           Unsigned32,
         tHsmdaPoolClass6AllocPercent     Unsigned32,
         tHsmdaPoolClass7Parent           Unsigned32,
         tHsmdaPoolClass7AllocPercent     Unsigned32,
         tHsmdaPoolClass8Parent           Unsigned32,
         tHsmdaPoolClass8AllocPercent     Unsigned32
    }

tHsmdaPoolPolicyName        OBJECT-TYPE
    SYNTAX      TNamedItem
    MAX-ACCESS  not-accessible
    STATUS      current
    DESCRIPTION
        "The value of tHsmdaPoolPolicyName specifies the name of the HSMDA
         pool policy."
    ::= { tHsmdaPoolPolicyEntry 1 }

tHsmdaPoolPolicyRowStatus        OBJECT-TYPE
    SYNTAX      RowStatus
    MAX-ACCESS  read-create
    STATUS      current
    DESCRIPTION
        "The value of tHsmdaPoolPolicyRowStatus is used for the creation
         and deletion of HSMDA pool policies."
    ::= { tHsmdaPoolPolicyEntry 2 }

tHsmdaPoolLastChanged        OBJECT-TYPE
    SYNTAX      TimeStamp
    MAX-ACCESS  read-only
    STATUS      current
    DESCRIPTION
        "The value of tHsmdaPoolLastChanged indicates the sysUpTime
         at the time of the last modification of this entry.

         If no changes were made to the entry since the last
         re-initialization of the local network management subsystem,
         then this object contains a zero value."
    ::= { tHsmdaPoolPolicyEntry 3 }

tHsmdaPoolDescription        OBJECT-TYPE
    SYNTAX      TItemDescription
    MAX-ACCESS  read-create
    STATUS      current
    DESCRIPTION
        "The value of tHsmdaPoolDescription specifies the description
         of this HSMDA pool policy."
    DEFVAL { "" }
    ::= { tHsmdaPoolPolicyEntry 4 }

tHsmdaPoolSystemReserve        OBJECT-TYPE
    SYNTAX      Unsigned32 (100..3000)
    UNITS       "hundredths of a percent"
    MAX-ACCESS  read-create
    STATUS      current
    DESCRIPTION
        "The value of tHsmdaPoolSystemReserve specifies the percentage of HSMDA
         buffers that will be reserved for internal system use.

         When this value is set, all the provisioned buffer pool allocation
         sizes will be re-evaluated. This includes the port class allocations
         specified by indirectly by tmnxPortIngPoolPercentRate and 
         tmnxPortEgrPoolPercentRate, and class and root pools specified
         indirectly by tHsmdaPoolClass1AllocPercent through
         tHsmdaPoolClass8AllocPercent and tHsmdaPoolRoot1AllocWeight through
         tHsmdaPoolRoot8AllocWeight."
    DEFVAL { 1000 }
    ::= { tHsmdaPoolPolicyEntry 5 }

tHsmdaPoolRoot1AllocWeight        OBJECT-TYPE
    SYNTAX      TWeight (1..100)
    MAX-ACCESS  read-create
    STATUS      current
    DESCRIPTION
        "The value of tHsmdaPoolRoot1AllocWeight specifies the weight that
         will be applied to the first root pool and is divided by the sum
         of all root pool weights to derive the pool's buffer allocation
         factor."
    DEFVAL { 75 }
    ::= { tHsmdaPoolPolicyEntry 6 }

tHsmdaPoolRoot2AllocWeight        OBJECT-TYPE
    SYNTAX      TWeight
    MAX-ACCESS  read-create
    STATUS      current
    DESCRIPTION
        "The value of tHsmdaPoolRoot2AllocWeight specifies the weight that
         will be applied to the second root pool and is divided by the sum
         of all root pool weights to derive the pool's buffer allocation
         factor."
    DEFVAL { 25 }
    ::= { tHsmdaPoolPolicyEntry 7 }

tHsmdaPoolRoot3AllocWeight        OBJECT-TYPE
    SYNTAX      TWeight
    MAX-ACCESS  read-create
    STATUS      current
    DESCRIPTION
        "The value of tHsmdaPoolRoot3AllocWeight specifies the weight that
         will be applied to the third root pool and is divided by the sum
         of all root pool weights to derive the pool's buffer allocation
         factor."
    DEFVAL { 0 }
    ::= { tHsmdaPoolPolicyEntry 8 }

tHsmdaPoolRoot4AllocWeight        OBJECT-TYPE
    SYNTAX      TWeight
    MAX-ACCESS  read-create
    STATUS      current
    DESCRIPTION
        "The value of tHsmdaPoolRoot4AllocWeight specifies the weight that
         will be applied to the fourth root pool and is divided by the sum
         of all root pool weights to derive the pool's buffer allocation
         factor."
    DEFVAL { 0 }
    ::= { tHsmdaPoolPolicyEntry 9 }

tHsmdaPoolRoot5AllocWeight        OBJECT-TYPE
    SYNTAX      TWeight
    MAX-ACCESS  read-create
    STATUS      current
    DESCRIPTION
        "The value of tHsmdaPoolRoot5AllocWeight specifies the weight that
         will be applied to the fifth root pool and is divided by the sum
         of all root pool weights to derive the pool's buffer allocation
         factor."
    DEFVAL { 0 }
    ::= { tHsmdaPoolPolicyEntry 10 }

tHsmdaPoolRoot6AllocWeight        OBJECT-TYPE
    SYNTAX      TWeight
    MAX-ACCESS  read-create
    STATUS      current
    DESCRIPTION
        "The value of tHsmdaPoolRoot6AllocWeight specifies the weight that
         will be applied to the sixth root pool and is divided by the sum
         of all root pool weights to derive the pool's buffer allocation
         factor."
    DEFVAL { 0 }
    ::= { tHsmdaPoolPolicyEntry 11 }

tHsmdaPoolRoot7AllocWeight        OBJECT-TYPE
    SYNTAX      TWeight
    MAX-ACCESS  read-create
    STATUS      current
    DESCRIPTION
        "The value of tHsmdaPoolRoot7AllocWeight specifies the weight that
         will be applied to the seventh root pool and is divided by the sum
         of all root pool weights to derive the pool's buffer allocation
         factor."
    DEFVAL { 0 }
    ::= { tHsmdaPoolPolicyEntry 12 }

tHsmdaPoolRoot8AllocWeight        OBJECT-TYPE
    SYNTAX      TWeight
    MAX-ACCESS  read-create
    STATUS      current
    DESCRIPTION
        "The value of tHsmdaPoolRoot8AllocWeight specifies the weight that
         will be applied to the eighth root pool and is divided by the sum
         of all root pool weights to derive the pool's buffer allocation
         factor."
    DEFVAL { 0 }
    ::= { tHsmdaPoolPolicyEntry 13 }

tHsmdaPoolClass1Parent        OBJECT-TYPE
    SYNTAX      Unsigned32 (1..8)
    MAX-ACCESS  read-create
    STATUS      current
    DESCRIPTION
        "The value of tHsmdaPoolClass1Parent specifies the root pool to which
         the first class pool will be associated."
    DEFVAL { 1 }
    ::= { tHsmdaPoolPolicyEntry 14 }

tHsmdaPoolClass1AllocPercent        OBJECT-TYPE
    SYNTAX      Unsigned32 (1..10000)
    UNITS       "hundredths of a percent"
    MAX-ACCESS  read-create
    STATUS      current
    DESCRIPTION
        "The value of tHsmdaPoolClass1AllocPercent specifies, indirectly,
         the size of the first class pool. The specified percentage, in
         hundredths of a percent, determines what percentage of the root
         pool with which it is associated, as specified by
         tHsmdaPoolClass1Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 4000 }
    ::= { tHsmdaPoolPolicyEntry 15 }

tHsmdaPoolClass2Parent        OBJECT-TYPE
    SYNTAX      Unsigned32 (1..8)
    MAX-ACCESS  read-create
    STATUS      current
    DESCRIPTION
        "The value of tHsmdaPoolClass2Parent specifies the root pool to which
         the second class pool will be associated."
    DEFVAL { 1 }
    ::= { tHsmdaPoolPolicyEntry 16 }

tHsmdaPoolClass2AllocPercent        OBJECT-TYPE
    SYNTAX      Unsigned32 (1..10000)
    UNITS       "hundredths of a percent"
    MAX-ACCESS  read-create
    STATUS      current
    DESCRIPTION
        "The value of tHsmdaPoolClass2AllocPercent specifies, indirectly,
         the size of the first class pool. The specified percentage, in
         hundredths of a percent, determines what percentage of the root
         pool with which it is associated, as specified by
         tHsmdaPoolClass2Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 3500 }
    ::= { tHsmdaPoolPolicyEntry 17 }

tHsmdaPoolClass3Parent        OBJECT-TYPE
    SYNTAX      Unsigned32 (1..8)
    MAX-ACCESS  read-create
    STATUS      current
    DESCRIPTION
        "The value of tHsmdaPoolClass3Parent specifies the root pool to which
         the third class pool will be associated."
    DEFVAL { 1 }
    ::= { tHsmdaPoolPolicyEntry 18 }

tHsmdaPoolClass3AllocPercent        OBJECT-TYPE
    SYNTAX      Unsigned32 (1..10000)
    UNITS       "hundredths of a percent"
    MAX-ACCESS  read-create
    STATUS      current
    DESCRIPTION
        "The value of tHsmdaPoolClass3AllocPercent specifies, indirectly,
         the size of the first class pool. The specified percentage, in
         hundredths of a percent, determines what percentage of the root
         pool with which it is associated, as specified by
         tHsmdaPoolClass3Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 3000 }
    ::= { tHsmdaPoolPolicyEntry 19 }

tHsmdaPoolClass4Parent        OBJECT-TYPE
    SYNTAX      Unsigned32 (1..8)
    MAX-ACCESS  read-create
    STATUS      current
    DESCRIPTION
        "The value of tHsmdaPoolClass4Parent specifies the root pool to which
         the fourth class pool will be associated."
    DEFVAL { 1 }
    ::= { tHsmdaPoolPolicyEntry 20 }

tHsmdaPoolClass4AllocPercent        OBJECT-TYPE
    SYNTAX      Unsigned32 (1..10000)
    UNITS       "hundredths of a percent"
    MAX-ACCESS  read-create
    STATUS      current
    DESCRIPTION
        "The value of tHsmdaPoolClass4AllocPercent specifies, indirectly,
         the size of the first class pool. The specified percentage, in
         hundredths of a percent, determines what percentage of the root
         pool with which it is associated, as specified by
         tHsmdaPoolClass4Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 2500 }
    ::= { tHsmdaPoolPolicyEntry 21 }

tHsmdaPoolClass5Parent        OBJECT-TYPE
    SYNTAX      Unsigned32 (1..8)
    MAX-ACCESS  read-create
    STATUS      current
    DESCRIPTION
        "The value of tHsmdaPoolClass5Parent specifies the root pool to which
         the fifth class pool will be associated."
    DEFVAL { 1 }
    ::= { tHsmdaPoolPolicyEntry 22 }

tHsmdaPoolClass5AllocPercent        OBJECT-TYPE
    SYNTAX      Unsigned32 (1..10000)
    UNITS       "hundredths of a percent"
    MAX-ACCESS  read-create
    STATUS      current
    DESCRIPTION
        "The value of tHsmdaPoolClass5AllocPercent specifies, indirectly,
         the size of the first class pool. The specified percentage, in
         hundredths of a percent, determines what percentage of the root
         pool with which it is associated, as specified by
         tHsmdaPoolClass5Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 2000 }
    ::= { tHsmdaPoolPolicyEntry 23 }

tHsmdaPoolClass6Parent        OBJECT-TYPE
    SYNTAX      Unsigned32 (1..8)
    MAX-ACCESS  read-create
    STATUS      current
    DESCRIPTION
        "The value of tHsmdaPoolClass6Parent specifies the root pool to which
         the sixth class pool will be associated."
    DEFVAL { 2 }
    ::= { tHsmdaPoolPolicyEntry 24 }

tHsmdaPoolClass6AllocPercent        OBJECT-TYPE
    SYNTAX      Unsigned32 (1..10000)
    UNITS       "hundredths of a percent"
    MAX-ACCESS  read-create
    STATUS      current
    DESCRIPTION
        "The value of tHsmdaPoolClass6AllocPercent specifies, indirectly,
         the size of the first class pool. The specified percentage, in
         hundredths of a percent, determines what percentage of the root
         pool with which it is associated, as specified by
         tHsmdaPoolClass6Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 5000 }
    ::= { tHsmdaPoolPolicyEntry 25 }

tHsmdaPoolClass7Parent        OBJECT-TYPE
    SYNTAX      Unsigned32 (1..8)
    MAX-ACCESS  read-create
    STATUS      current
    DESCRIPTION
        "The value of tHsmdaPoolClass7Parent specifies the root pool to which
         the seventh class pool will be associated."
    DEFVAL { 2 }
    ::= { tHsmdaPoolPolicyEntry 26 }

tHsmdaPoolClass7AllocPercent        OBJECT-TYPE
    SYNTAX      Unsigned32 (1..10000)
    UNITS       "hundredths of a percent"
    MAX-ACCESS  read-create
    STATUS      current
    DESCRIPTION
        "The value of tHsmdaPoolClass7AllocPercent specifies, indirectly,
         the size of the first class pool. The specified percentage, in
         hundredths of a percent, determines what percentage of the root
         pool with which it is associated, as specified by
         tHsmdaPoolClass7Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 4000 }
    ::= { tHsmdaPoolPolicyEntry 27 }

tHsmdaPoolClass8Parent        OBJECT-TYPE
    SYNTAX      Unsigned32 (1..8)
    MAX-ACCESS  read-create
    STATUS      current
    DESCRIPTION
        "The value of tHsmdaPoolClass8Parent specifies the root pool to which
         the eigth class pool will be associated."
    DEFVAL { 2 }
    ::= { tHsmdaPoolPolicyEntry 28 }

tHsmdaPoolClass8AllocPercent        OBJECT-TYPE
    SYNTAX      Unsigned32 (1..10000)
    UNITS       "hundredths of a percent"
    MAX-ACCESS  read-create
    STATUS      current
    DESCRIPTION
        "The value of tHsmdaPoolClass8AllocPercent specifies, indirectly,
         the size of the first class pool. The specified percentage, in
         hundredths of a percent, determines what percentage of the root
         pool with which it is associated, as specified by
         tHsmdaPoolClass8Parent, will be available to this class.

         The sum of the class pool percentages for a root pool may exceed
         100 percent(10000 hundredths of a percent), allowing the root pool
         to be oversubscribed. The sum of the class pool percentages for
         a root pool may also total less than 100 percent, allowing the
         root pool to be undersubscribed."
    DEFVAL { 3000 }
    ::= { tHsmdaPoolPolicyEntry 29 }

--
-- Multi-class mlppp Ingress profile table
--

tMcMlpppIngrProfTable OBJECT-TYPE
    SYNTAX       SEQUENCE OF TMcMlpppIngrProfEntry
    MAX-ACCESS   not-accessible
    STATUS       current
    DESCRIPTION
        "The tMcMlpppIngrProfTable has an entry for each ingress multi-class 
         mlppp profile configured in the system."
    ::= { tMcMlpppIngressObjects 1 }

tMcMlpppIngrProfEntry OBJECT-TYPE
    SYNTAX       TMcMlpppIngrProfEntry
    MAX-ACCESS   not-accessible
    STATUS       current
    DESCRIPTION
        "Each row entry contains information about a particular ingress 
         multi-class mlppp profile.
         
         Multi-class mlppp ingress profile 1 is created by the agent. 
         It cannot be deleted.
         
         Other entries are created by the user."
    INDEX { tMcMlpppIngrProfIndex }
    ::= { tMcMlpppIngrProfTable 1 }

TMcMlpppIngrProfEntry ::= SEQUENCE
    {
        tMcMlpppIngrProfIndex                 TMlpppQoSProfileId,
        tMcMlpppIngrProfDescription           TItemDescription,
        tMcMlpppIngrProfLastChanged           TimeStamp,
        tMcMlpppIngrProfRowStatus             RowStatus
    }

tMcMlpppIngrProfIndex OBJECT-TYPE
    SYNTAX       TMlpppQoSProfileId (1..65535)
    MAX-ACCESS   not-accessible
    STATUS       current
    DESCRIPTION  
        "The value of tMcMlpppIngrProfIndex specifies a specific multi-class 
         ingress profile."
    ::= { tMcMlpppIngrProfEntry 1 }

tMcMlpppIngrProfDescription OBJECT-TYPE
    SYNTAX       TItemDescription
    MAX-ACCESS   read-create
    STATUS       current
    DESCRIPTION  
        "The value of tMcMlpppIngrProfDescription holds the description for
         this profile."
    DEFVAL { ''H }
    ::= { tMcMlpppIngrProfEntry 2 }
    
tMcMlpppIngrProfLastChanged OBJECT-TYPE
    SYNTAX       TimeStamp
    MAX-ACCESS   read-only
    STATUS       current
    DESCRIPTION  
        "The value of tMcMlpppIngrProfTable indicates the sysUpTime for the 
         last change to this row."
    ::= { tMcMlpppIngrProfEntry 3 }
    
tMcMlpppIngrProfRowStatus OBJECT-TYPE
    SYNTAX       RowStatus
    MAX-ACCESS   read-create
    STATUS       current
    DESCRIPTION  
        "The value of tMcMlpppIngrProfRowStatus controls the creation
         and deletion of rows in this table."
    ::= { tMcMlpppIngrProfEntry 4 }

--
-- Multi-class mlppp ingress class table
--

tMcMlpppIngrClassTable OBJECT-TYPE
    SYNTAX       SEQUENCE OF TMcMlpppIngrClassEntry
    MAX-ACCESS   not-accessible
    STATUS       current
    DESCRIPTION
        "The tMcMlpppIngrClassTable has an entry for each multi-class
         mlppp ingress class per multi-class mlppp ingress profile in
         the system."
    ::= { tMcMlpppIngressObjects 2 }

tMcMlpppIngrClassEntry OBJECT-TYPE
    SYNTAX       TMcMlpppIngrClassEntry
    MAX-ACCESS   not-accessible
    STATUS       current
    DESCRIPTION
        "Each entry contains information about a particular 
         mlppp ingress multi-class class per mlppp ingress profile.
         Entries are created/destroyed as each tMcMlpppIngrProfEntry
         is created/destroyed."
    INDEX { tMcMlpppIngrProfIndex, tMcMlpppIngrClassIndex }
    ::= { tMcMlpppIngrClassTable 1 }

TMcMlpppIngrClassEntry ::= SEQUENCE
    {
        tMcMlpppIngrClassIndex              TmnxMcMlpppClassIndex,
        tMcMlpppIngrClassReassemblyTmout    Unsigned32,
        tMcMlpppIngrClassLastChanged        TimeStamp 
    }

tMcMlpppIngrClassIndex OBJECT-TYPE
    SYNTAX       TmnxMcMlpppClassIndex
    MAX-ACCESS   not-accessible
    STATUS       current
    DESCRIPTION  
        "The value of tMcMlpppIngrClassIndex specifies a specific mlppp ingress
         class per multi-class mlppp ingress profile."
    ::= { tMcMlpppIngrClassEntry 1 }

tMcMlpppIngrClassReassemblyTmout OBJECT-TYPE
    SYNTAX       Unsigned32 (1..1000)
    MAX-ACCESS   read-write
    STATUS       current
    DESCRIPTION  
        "The value of tMcMlpppIngrClassReassemblyTmout specifies the
         reassembly timeout for a specific mlppp multi-class ingress class.
         The default reassembly timeout value is determined by the 
         tMcMlpppIngrClassIndex value.
         Currently only four multi-class classes are supported per profile.

                    tMcMlpppIngrClassIndex    Default Reassembly Value
                             0                           10
                             1                           10
                             2                           100
                             3                           1000"
    
    ::= { tMcMlpppIngrClassEntry 2 }    

tMcMlpppIngrClassLastChanged OBJECT-TYPE
    SYNTAX       TimeStamp
    MAX-ACCESS   read-only
    STATUS       current
    DESCRIPTION  
        "The value of tMcMlpppIngrClassLastChanged indicates the sysUpTime 
         for the last change to this entry."
    ::= { tMcMlpppIngrClassEntry 3 }  
        
--
-- Multi-class mlppp egress profile table
--

tMcMlpppEgrProfTable OBJECT-TYPE
    SYNTAX       SEQUENCE OF TMcMlpppEgrProfEntry
    MAX-ACCESS   not-accessible
    STATUS       current
    DESCRIPTION
        "The tMcMlpppEgrProfTable has an entry for each egress multi-class 
         mlppp profile configured in the system."
    ::= { tMcMlpppEgressObjects 1 }

tMcMlpppEgrProfEntry OBJECT-TYPE
    SYNTAX       TMcMlpppEgrProfEntry
    MAX-ACCESS   not-accessible
    STATUS       current
    DESCRIPTION
        "Each row entry contains information about a particular egress
         multi-class mlppp profile.
         
         Multi-class mlppp egress profiles 1,2 and 3 are created by the agent. 
         They cannot be deleted.
         
         Other entries are created by the user."
    INDEX { tMcMlpppEgrProfIndex }
    ::= { tMcMlpppEgrProfTable 1 }

TMcMlpppEgrProfEntry ::= SEQUENCE
    {
        tMcMlpppEgrProfIndex                TMlpppQoSProfileId,
        tMcMlpppEgrProfDescription          TItemDescription,
        tMcMlpppEgrProfLastChanged          TimeStamp,
        tMcMlpppEgrProfRowStatus            RowStatus
    }

tMcMlpppEgrProfIndex OBJECT-TYPE
    SYNTAX       TMlpppQoSProfileId (1..65535)
    MAX-ACCESS   not-accessible
    STATUS       current
    DESCRIPTION  
        "The value of tMcMlpppEgrProfIndex specifies a specific multi-class 
         egress profile."
    ::= { tMcMlpppEgrProfEntry 1 }

tMcMlpppEgrProfDescription OBJECT-TYPE
    SYNTAX       TItemDescription
    MAX-ACCESS   read-create
    STATUS       current
    DESCRIPTION  
        "The value of tMcMlpppEgrProfDescription holds the description for
         this profile."
    DEFVAL { ''H }
    ::= { tMcMlpppEgrProfEntry 2 }
    
tMcMlpppEgrProfLastChanged OBJECT-TYPE
    SYNTAX       TimeStamp
    MAX-ACCESS   read-only
    STATUS       current
    DESCRIPTION  
        "The value of tMcMlpppEgrProfLastChanged indicates the sysUpTime 
         for the last change to this row."
    ::= { tMcMlpppEgrProfEntry 3 }
    
tMcMlpppEgrProfRowStatus OBJECT-TYPE
    SYNTAX       RowStatus
    MAX-ACCESS   read-create
    STATUS       current
    DESCRIPTION  
        "The value of tMcMlpppEgrProfRowStatus controls the creation
         and deletion of rows in this table."
    ::= { tMcMlpppEgrProfEntry 4 }

--
-- Multi-class mlppp egress class table
--

tMcMlpppEgrClassTable OBJECT-TYPE
    SYNTAX       SEQUENCE OF TMcMlpppEgrClassEntry
    MAX-ACCESS   not-accessible
    STATUS       current
    DESCRIPTION
        "The tMcMlpppEgrClassTable has an entry for each multiclass
         mlppp egress profile in the system."
    ::= { tMcMlpppEgressObjects 3 }

tMcMlpppEgrClassEntry OBJECT-TYPE
    SYNTAX       TMcMlpppEgrClassEntry
    MAX-ACCESS   not-accessible
    STATUS       current
    DESCRIPTION
        "Each entry contains information about a particular 
         mlppp egress multi-class class per mlppp multi-class
         mlppp egress profile.
         Entries are created/destroyed as each tMcMlpppEgrProfEntry
         is created/destroyed."
    INDEX { tMcMlpppEgrProfIndex, tMcMlpppEgrClassIndex }
    ::= { tMcMlpppEgrClassTable 1 }

TMcMlpppEgrClassEntry ::= SEQUENCE
    {
        tMcMlpppEgrClassIndex       TmnxMcMlpppClassIndex,
        tMcMlpppEgrClassMir         Unsigned32,
        tMcMlpppEgrClassWeight      Unsigned32, 
        tMcMlpppEgrClassMaxSize     Unsigned32,
        tMcMlpppEgrClassLastChanged TimeStamp
    }

tMcMlpppEgrClassIndex OBJECT-TYPE
    SYNTAX       TmnxMcMlpppClassIndex
    MAX-ACCESS   not-accessible
    STATUS       current
    DESCRIPTION  
        "The value of tMcMlpppEgrClassIndex specifies a specific mlppp egress class 
         per multi-class mlppp egress profile."
    ::= { tMcMlpppEgrClassEntry 1 }

tMcMlpppEgrClassMir OBJECT-TYPE
    SYNTAX       Unsigned32 (0|1..100)
    UNITS        "percent"
    MAX-ACCESS   read-write
    STATUS       current
    DESCRIPTION  
        "The value of tMcMlpppEgrClassMir specifies the Minimum Information
         Rate given as a percentage. A value of zero represents this object
         is not applicable for this class.
         The default Mir is determined by the tMcMlpppEgrClassIndex value.
         Currently only four multi-class classes are supported per profile.

               tMcMlpppEgrClassIndex     Default Mir Value
                         0                      100
                         1                      85
                         2                      0
                         3                      0"        
    ::= { tMcMlpppEgrClassEntry 2 }

tMcMlpppEgrClassWeight OBJECT-TYPE
    SYNTAX       Unsigned32 (0|1..100)
    UNITS        "percent"
    MAX-ACCESS   read-write
    STATUS       current
    DESCRIPTION  
        "The value of tMcMlpppEgrClassWeight specifies the weight of this
         multiclass class given as a percentage. A value of zero represents 
         this object is not applicable for this class.
         The default Weight is determined by the tMcMlpppEgrClassIndex value.
         Currently only four multi-class classes are supported per profile.

               tMcMlpppEgrClassIndex     Default Weight Value
                         0                      0
                         1                      0
                         2                      66
                         3                      33" 
    ::= { tMcMlpppEgrClassEntry 3 }
    
tMcMlpppEgrClassMaxSize OBJECT-TYPE
    SYNTAX       Unsigned32 (1..1000)
    UNITS       "milliseconds"
    MAX-ACCESS   read-write
    STATUS       current
    DESCRIPTION  
        "The value of tMcMlpppEgrClassMaxSize specifies the buffer queue size.
         The default buffer size is determined by the tMcMlpppEgrClassIndex
         value.
         Currently only four multi-class classes are supported per profile.

               tMcMlpppEgrClassIndex     Default Max Size
                        0                      25
                        1                      5
                        2                      200
                        3                      1000" 
        
    ::= { tMcMlpppEgrClassEntry 4 }

tMcMlpppEgrClassLastChanged OBJECT-TYPE
    SYNTAX       TimeStamp
    MAX-ACCESS   read-only
    STATUS       current
    DESCRIPTION  
        "The value of tMcMlpppEgrClassLastChanged indicates the sysUpTime 
         for the last change to this entry."
    ::= { tMcMlpppEgrClassEntry 5 }      
--
-- Multi-class mlppp egress fc table
--

tMcMlpppEgrFCTable OBJECT-TYPE
    SYNTAX       SEQUENCE OF TMcMlpppEgrFCEntry
    MAX-ACCESS   not-accessible
    STATUS       current
    DESCRIPTION
        "The tMcMlpppEgrFCTable has an entry for all egress FC Mappings 
         to multi-class mlppp classes."
    ::= { tMcMlpppEgressObjects 4 }

tMcMlpppEgrFCEntry OBJECT-TYPE
    SYNTAX       TMcMlpppEgrFCEntry
    MAX-ACCESS   not-accessible
    STATUS       current
    DESCRIPTION
        "Each entry contains information about all egress FC Mappings to
         multi-class mlppp classes. Entries are created/destroyed as each 
         tMcMlpppEgrProfEntry is created/destroyed."
    INDEX { tMcMlpppEgrProfIndex, tMcMlpppEgrFCName }
    ::= { tMcMlpppEgrFCTable 1 }

TMcMlpppEgrFCEntry ::= SEQUENCE
    {
        tMcMlpppEgrFCName        TFCName,  
        tMcMlpppEgrFCClass       Unsigned32,
        tMcMlpppEgrFCLastChanged TimeStamp
    }

tMcMlpppEgrFCName OBJECT-TYPE
    SYNTAX       TFCName
    MAX-ACCESS   not-accessible
    STATUS       current
    DESCRIPTION
        "The value tMcMlpppEgrFCName specifies of the name of the forwarding class."
    ::= { tMcMlpppEgrFCEntry 1 }
    
tMcMlpppEgrFCClass OBJECT-TYPE
    SYNTAX       Unsigned32 (0..3)
    MAX-ACCESS   read-write
    STATUS       current
    DESCRIPTION  
        "The value of tMcMlpppEgrFCClass specifies the mlppp multi-class class
         for the per-forwarding-class specified. The default class value is determined
         by the Forwarding Class Name.    
            
            Forwarding Class Name             Mlppp Class Value
                   be                                 3
                   l2                                 2 
                   af                                 2 
                   l1                                 2 
                   h2                                 2
                   ef                                 1  
                   h1                                 0
                   nc                                 0"           
    ::= { tMcMlpppEgrFCEntry 2 }

tMcMlpppEgrFCLastChanged OBJECT-TYPE
    SYNTAX       TimeStamp
    MAX-ACCESS   read-only
    STATUS       current
    DESCRIPTION  
        "The value of tMcMlpppEgrFCLastChanged indicates the sysUpTime 
         for the last change to this entry."
    ::= { tMcMlpppEgrFCEntry 3 }

--
-- Multi-class Frame-Relay Ingress profile table
--

tMcFrIngrProfTable OBJECT-TYPE
    SYNTAX       SEQUENCE OF TMcFrIngrProfEntry
    MAX-ACCESS   not-accessible
    STATUS       current
    DESCRIPTION
        "The tMcFrIngrProfTable has an entry for each ingress multi-class 
         frame-relay profile configured in the system."
    ::= { tMcFrIngressObjects 1 }

tMcFrIngrProfEntry OBJECT-TYPE
    SYNTAX       TMcFrIngrProfEntry
    MAX-ACCESS   not-accessible
    STATUS       current
    DESCRIPTION
        "Each row entry contains information about a particular ingress 
         multi-class frame-relay profile.
         
         Multi-class frame-relay ingress profile 1 is created by the agent. 
         It cannot be modified/deleted.
         
         Other entries are created by the user."
    INDEX { tMcFrIngrProfIndex }
    ::= { tMcFrIngrProfTable 1 }

TMcFrIngrProfEntry ::= SEQUENCE
    {
        tMcFrIngrProfIndex                 TMcFrQoSProfileId,
        tMcFrIngrProfDescription           TItemDescription,
        tMcFrIngrProfLastChanged           TimeStamp,
        tMcFrIngrProfRowStatus             RowStatus
    }

tMcFrIngrProfIndex OBJECT-TYPE
    SYNTAX       TMcFrQoSProfileId (1..65535)
    MAX-ACCESS   not-accessible
    STATUS       current
    DESCRIPTION  
        "The value of tMcFrIngrProfIndex specifies a specific multi-class 
         ingress profile."
    ::= { tMcFrIngrProfEntry 1 }

tMcFrIngrProfDescription OBJECT-TYPE
    SYNTAX       TItemDescription
    MAX-ACCESS   read-create
    STATUS       current
    DESCRIPTION  
        "The value of tMcFrIngrProfDescription holds the description for
         this profile."
    DEFVAL { ''H }
    ::= { tMcFrIngrProfEntry 2 }
    
tMcFrIngrProfLastChanged OBJECT-TYPE
    SYNTAX       TimeStamp
    MAX-ACCESS   read-only
    STATUS       current
    DESCRIPTION  
        "The value of tMcFrIngrProfTable indicates the sysUpTime for the 
         last change to this row."
    ::= { tMcFrIngrProfEntry 3 }
    
tMcFrIngrProfRowStatus OBJECT-TYPE
    SYNTAX       RowStatus
    MAX-ACCESS   read-create
    STATUS       current
    DESCRIPTION  
        "The value of tMcFrIngrProfRowStatus controls the creation
         and deletion of rows in this table."
    ::= { tMcFrIngrProfEntry 4 }

--
-- Multi-class Frame-Relay ingress class table
--

tMcFrIngrClassTable OBJECT-TYPE
    SYNTAX       SEQUENCE OF TMcFrIngrClassEntry
    MAX-ACCESS   not-accessible
    STATUS       current
    DESCRIPTION
        "The tMcFrIngrClassTable has an entry for each multi-class
         frame-relay ingress class per multi-class frame-relay ingress 
         profile in the system."
    ::= { tMcFrIngressObjects 2 }

tMcFrIngrClassEntry OBJECT-TYPE
    SYNTAX       TMcFrIngrClassEntry
    MAX-ACCESS   not-accessible
    STATUS       current
    DESCRIPTION
        "Each entry contains information about a particular frame-relay 
         ingress multi-class class per frame-relay ingress profile.
         
         Entries are created/destroyed as each tMcFrIngrProfEntry
         is created/destroyed."
    INDEX { tMcFrIngrProfIndex, tMcFrIngrClassIndex }
    ::= { tMcFrIngrClassTable 1 }

TMcFrIngrClassEntry ::= SEQUENCE
    {
        tMcFrIngrClassIndex              TmnxMcFrClassIndex,
        tMcFrIngrClassReassemblyTmout    Unsigned32,
        tMcFrIngrClassLastChanged        TimeStamp 
    }

tMcFrIngrClassIndex OBJECT-TYPE
    SYNTAX       TmnxMcFrClassIndex
    MAX-ACCESS   not-accessible
    STATUS       current
    DESCRIPTION  
        "The value of tMcFrIngrClassIndex specifies a specific frame-relay
         ingress class per multi-class frame-relay ingress profile."
    ::= { tMcFrIngrClassEntry 1 }

tMcFrIngrClassReassemblyTmout OBJECT-TYPE
    SYNTAX       Unsigned32 (1..1000)
    MAX-ACCESS   read-write
    STATUS       current
    DESCRIPTION  
        "The value of tMcFrIngrClassReassemblyTmout specifies the
         reassembly timeout for a specific frame-relay multi-class ingress class.
         Currently only four multi-class classes are supported per profile."
    ::= { tMcFrIngrClassEntry 2 }    

tMcFrIngrClassLastChanged OBJECT-TYPE
    SYNTAX       TimeStamp
    MAX-ACCESS   read-only
    STATUS       current
    DESCRIPTION  
        "The value of tMcFrIngrClassLastChanged indicates the sysUpTime 
         for the last change to this entry."
    ::= { tMcFrIngrClassEntry 3 }  
        
--
-- Multi-class Frame-Relay egress profile table
--

tMcFrEgrProfTable OBJECT-TYPE
    SYNTAX       SEQUENCE OF TMcFrEgrProfEntry
    MAX-ACCESS   not-accessible
    STATUS       current
    DESCRIPTION
        "The tMcFrEgrProfTable has an entry for each egress multi-class 
         frame-relay profile configured in the system."
    ::= { tMcFrEgressObjects 1 }

tMcFrEgrProfEntry OBJECT-TYPE
    SYNTAX       TMcFrEgrProfEntry
    MAX-ACCESS   not-accessible
    STATUS       current
    DESCRIPTION
        "Each row entry contains information about a particular egress
         multi-class frame-relay profile.
         
         Multi-class frame-relay egress profile 1 is created by the agent. 
         It cannot be modified/deleted.
         
         Other entries are created by the user."
    INDEX { tMcFrEgrProfIndex }
    ::= { tMcFrEgrProfTable 1 }

TMcFrEgrProfEntry ::= SEQUENCE
    {
        tMcFrEgrProfIndex                TMcFrQoSProfileId,
        tMcFrEgrProfDescription          TItemDescription,
        tMcFrEgrProfLastChanged          TimeStamp,
        tMcFrEgrProfRowStatus            RowStatus
    }

tMcFrEgrProfIndex OBJECT-TYPE
SYNTAX       TMcFrQoSProfileId (1..65535)
    MAX-ACCESS   not-accessible
    STATUS       current
    DESCRIPTION  
        "The value of tMcFrEgrProfIndex specifies a specific multi-class 
         egress profile."
    ::= { tMcFrEgrProfEntry 1 }

tMcFrEgrProfDescription OBJECT-TYPE
    SYNTAX       TItemDescription
    MAX-ACCESS   read-create
    STATUS       current
    DESCRIPTION  
        "The value of tMcFrEgrProfDescription holds the description for
         this profile."
    DEFVAL { ''H }
    ::= { tMcFrEgrProfEntry 2 }
    
tMcFrEgrProfLastChanged OBJECT-TYPE
    SYNTAX       TimeStamp
    MAX-ACCESS   read-only
    STATUS       current
    DESCRIPTION  
        "The value of tMcFrEgrProfLastChanged indicates the sysUpTime 
         for the last change to this row."
    ::= { tMcFrEgrProfEntry 3 }
    
tMcFrEgrProfRowStatus OBJECT-TYPE
    SYNTAX       RowStatus
    MAX-ACCESS   read-create
    STATUS       current
    DESCRIPTION  
        "The value of tMcFrEgrProfRowStatus controls the creation
         and deletion of rows in this table."
    ::= { tMcFrEgrProfEntry 4 }

--
-- Multi-class Frame-Relay egress class table
--

tMcFrEgrClassTable OBJECT-TYPE
    SYNTAX       SEQUENCE OF TMcFrEgrClassEntry
    MAX-ACCESS   not-accessible
    STATUS       current
    DESCRIPTION
        "The tMcFrEgrClassTable has an entry for each multiclass
         mlppp egress profile in the system."
    ::= { tMcFrEgressObjects 3 }

tMcFrEgrClassEntry OBJECT-TYPE
    SYNTAX       TMcFrEgrClassEntry
    MAX-ACCESS   not-accessible
    STATUS       current
    DESCRIPTION
        "Each entry contains information about a particular 
         frame-relay egress multi-class class per multi-class
         frame-relay egress profile.
         Entries are created/destroyed as each tMcFrEgrProfEntry
         is created/destroyed."
    INDEX { tMcFrEgrProfIndex, tMcFrEgrClassIndex }
    ::= { tMcFrEgrClassTable 1 }

TMcFrEgrClassEntry ::= SEQUENCE
    {
        tMcFrEgrClassIndex       TmnxMcFrClassIndex,
        tMcFrEgrClassMir         Unsigned32,
        tMcFrEgrClassWeight      Unsigned32, 
        tMcFrEgrClassMaxSize     Unsigned32,
        tMcFrEgrClassLastChanged TimeStamp
    }

tMcFrEgrClassIndex OBJECT-TYPE
    SYNTAX       TmnxMcFrClassIndex
    MAX-ACCESS   not-accessible
    STATUS       current
    DESCRIPTION  
        "The value of tMcFrEgrClassIndex specifies a specific frame-relay
         egress class per multi-class frame-relay egress profile."
    ::= { tMcFrEgrClassEntry 1 }

tMcFrEgrClassMir OBJECT-TYPE
    SYNTAX       Unsigned32 (0|1..100)
    UNITS        "percent"
    MAX-ACCESS   read-write
    STATUS       current
    DESCRIPTION  
        "The value of tMcFrEgrClassMir specifies the Minimum Information
         Rate given as a percentage. A value of zero represents this object
         is not applicable for this class.
         Currently only four multi-class classes are supported per profile."        
    ::= { tMcFrEgrClassEntry 2 }

tMcFrEgrClassWeight OBJECT-TYPE
    SYNTAX       Unsigned32 (0|1..100)
    UNITS        "percent"
    MAX-ACCESS   read-write
    STATUS       current
    DESCRIPTION  
        "The value of tMcMlpppEgrClassWeight specifies the weight of this
         multiclass class given as a percentage. A value of zero represents 
         this object is not applicable for this class.
         Currently only four multi-class classes are supported per profile." 
    ::= { tMcFrEgrClassEntry 3 }
    
tMcFrEgrClassMaxSize OBJECT-TYPE
    SYNTAX       Unsigned32 (1..1000)
    UNITS       "milliseconds"
    MAX-ACCESS   read-write
    STATUS       current
    DESCRIPTION  
        "The value of tMcFrEgrClassMaxSize specifies the buffer queue size.
         The default buffer size is determined by the tMcFrEgrClassIndex
         value.
         Currently only four multi-class classes are supported per profile." 
    ::= { tMcFrEgrClassEntry 4 }

tMcFrEgrClassLastChanged OBJECT-TYPE
    SYNTAX       TimeStamp
    MAX-ACCESS   read-only
    STATUS       current
    DESCRIPTION  
        "The value of tMcFrEgrClassLastChanged indicates the sysUpTime 
         for the last change to this entry."
    ::= { tMcFrEgrClassEntry 5 }      

-- --------------------------------
-- QoS Policer Control Policy table
-- --------------------------------

tQosPolicerCtrlPolTblLastChgd OBJECT-TYPE
    SYNTAX       TimeStamp
    MAX-ACCESS   read-only
    STATUS       current
    DESCRIPTION
        "tQosPolicerCtrlPolTblLastChgd indicates the timestamp of last change to
        the tQosPolicerCtrlPolTable."
    ::= { tQosTimeStampObjects 87 }

tQosPolicerCtrlPolTable OBJECT-TYPE
    SYNTAX       SEQUENCE OF TQosPolicerCtrlPolEntry
    MAX-ACCESS   not-accessible
    STATUS       current
    DESCRIPTION
        "tQosPolicerCtrlPolTable defines all egress queues."
    ::= { tQosPolicerObjects 1 }

tQosPolicerCtrlPolEntry OBJECT-TYPE
    SYNTAX       TQosPolicerCtrlPolEntry
    MAX-ACCESS   not-accessible
    STATUS       current
    DESCRIPTION
        "tQosPolicerCtrlPolEntry defines a particular egress queue.
         Entries are created and deleted by user."
    INDEX { tQosPolicerCtrlPolName }
    ::= { tQosPolicerCtrlPolTable 1 }

TQosPolicerCtrlPolEntry ::= SEQUENCE
    {
        tQosPolicerCtrlPolName              TNamedItem,
        tQosPolicerCtrlPolRowStatus         RowStatus,
        tQosPolicerCtrlPolLastChgd          TimeStamp,
        tQosPolicerCtrlPolDescr             TItemDescription,
        tQosPolicerCtrlPolRootMaxRate       THPolPIRRate,
        tQosPolicerCtrlPolMinMBSSep         TPlcrBurstSizeBytes,
        tQosPolicerCtrlPolProfPref          TruthValue
    }

tQosPolicerCtrlPolName OBJECT-TYPE
    SYNTAX       TNamedItem
    MAX-ACCESS   not-accessible
    STATUS       current
    DESCRIPTION
        "The value of tQosPolicerCtrlPolName identifies the name of the
        policer control policy."
    ::= { tQosPolicerCtrlPolEntry 1 }

tQosPolicerCtrlPolRowStatus OBJECT-TYPE
    SYNTAX       RowStatus
    MAX-ACCESS   read-create
    STATUS       current
    DESCRIPTION
        "This is the Row Status of the entry.
        This allows creation/deletion of rows in this table."
    ::= { tQosPolicerCtrlPolEntry 2 }

tQosPolicerCtrlPolLastChgd OBJECT-TYPE
    SYNTAX       TimeStamp
    MAX-ACCESS   read-only
    STATUS       current
    DESCRIPTION
        "The value of tQosPolicerCtrlPolLastChgd indicates the timestamp of
        last change to this row in tQosPolicerCtrlPolTable."
    ::= { tQosPolicerCtrlPolEntry 3 }

tQosPolicerCtrlPolDescr OBJECT-TYPE
    SYNTAX       TItemDescription
    MAX-ACCESS   read-create
    STATUS       current
    DESCRIPTION
        "The value of tQosPolicerCtrlPolDescr specifies the description for the
        policer control policy."
    DEFVAL { ''H }
    ::= { tQosPolicerCtrlPolEntry 4 }

tQosPolicerCtrlPolRootMaxRate OBJECT-TYPE
    SYNTAX       THPolPIRRate
    UNITS        "kbps"
    MAX-ACCESS   read-create
    STATUS       current
    DESCRIPTION
        "The value of tQosPolicerCtrlPolRootMaxRate specifies the
        maximum frame based bandwidth limit of this policer."
    DEFVAL { -1 }
    ::= { tQosPolicerCtrlPolEntry 5 }

tQosPolicerCtrlPolMinMBSSep OBJECT-TYPE
    SYNTAX       TPlcrBurstSizeBytes
    UNITS        "bytes"
    MAX-ACCESS   read-create
    STATUS       current
    DESCRIPTION
        "The value of tQosPolicerCtrlPolMinMBSSep specifies the
        minimum amount of seperation buffer space (in bytes) allowed 
        by this policer."
    DEFVAL { -1 }
    ::= { tQosPolicerCtrlPolEntry 6 }

tQosPolicerCtrlPolProfPref OBJECT-TYPE
    SYNTAX       TruthValue
    MAX-ACCESS   read-create
    STATUS       current
    DESCRIPTION
        "The value of tQosPolicerCtrlPolProfPref specifies the
        minimum amount of seperation buffer space (in bytes) allowed 
        by this policer.
         
        When the value of this object is set to 'true', preferred profile is 
        applied to this policy. When the value is set to 'false', no preffered
        profile is set to this policy."   
    DEFVAL { false }
    ::= { tQosPolicerCtrlPolEntry 7 }

-- ----------------------------------
-- Policer Control Policy Level Table
-- ----------------------------------
tQosPolicerLevelTblLastChgd OBJECT-TYPE
    SYNTAX       TimeStamp
    MAX-ACCESS   read-only
    STATUS       current
    DESCRIPTION
        "tQosPolicerLevelTblLastChgd indicates the timestamp of last
        change to the tQosPolicerLevelTable."
    ::= { tQosTimeStampObjects 88 }

tQosPolicerLevelTable OBJECT-TYPE
    SYNTAX       SEQUENCE OF TQosPolicerLevelEntry
    MAX-ACCESS   not-accessible
    STATUS       current
    DESCRIPTION
        "tQosPolicerLevelTable defines all levels of QoS Policer control
        policy defined by tQosPolicerCtrlPolTable."
    ::= { tQosPolicerObjects 2 }

tQosPolicerLevelEntry OBJECT-TYPE
    SYNTAX       TQosPolicerLevelEntry
    MAX-ACCESS   not-accessible
    STATUS       current
    DESCRIPTION
        "tQosPolicerLevelEntry defines a specific level of QoS policer
        control policy defined by tQosPolicerCtrlPolTable.
        
        Entries are created and deleted by the system when QoS policer control
        policy is created and deleted."
    INDEX { tQosPolicerCtrlPolName, tQosPolicerLevel }
    ::= { tQosPolicerLevelTable 1 }

TQosPolicerLevelEntry ::= SEQUENCE
    {
        tQosPolicerLevel             TLevel,
        tQosPolicerLevelLastChgd     TimeStamp,
        tQosPolicerLevelCumMBS       TPlcrBurstSizeBytes,
        tQosPolicerLevelFixedMBS     TruthValue 
    }

tQosPolicerLevel OBJECT-TYPE
    SYNTAX       TLevel
    MAX-ACCESS   not-accessible
    STATUS       current
    DESCRIPTION
        "The value of tQosPolicerLevel identifies the level of the policer
        control policy defined by tQosPolicerCtrlPolName."
    ::= { tQosPolicerLevelEntry 1 }

tQosPolicerLevelLastChgd OBJECT-TYPE
    SYNTAX       TimeStamp
    MAX-ACCESS   read-only
    STATUS       current
    DESCRIPTION
        "The value of tQosPolicerLevelLastChgd indicates the timestamp of last
        change to this row in tQosPolicerLevelTable."
    ::= { tQosPolicerLevelEntry 2 }

tQosPolicerLevelCumMBS OBJECT-TYPE
    SYNTAX       TPlcrBurstSizeBytes
    UNITS        "bytes"
    MAX-ACCESS   read-create
    STATUS       current
    DESCRIPTION
        "The value of tQosPolicerLevelCumMBS specifies the maximum amount of
        cumulative buffer space (in bytes) allowed for this level by this
        policer."
    DEFVAL { -1 }
    ::= { tQosPolicerLevelEntry 3 }

tQosPolicerLevelFixedMBS OBJECT-TYPE
    SYNTAX       TruthValue
    MAX-ACCESS   read-create
    STATUS       current
    DESCRIPTION
        "The value of tQosPolicerLevelFixedMBS specifies whether the
        cumulative buffer space is fixed for this level.
         
        When the value of this object is set to 'true', cumulative buffer 
        space for this level is fixed. When the value is set to 'false',
        cumulative buffer space for this level is not fixed."         
    DEFVAL { false }
    ::= { tQosPolicerLevelEntry 4 }

                                
-- --------------------------------
-- QoS Policer Arbiter table
-- --------------------------------

tQosPolicerArbiterTblLastChgd OBJECT-TYPE
    SYNTAX       TimeStamp
    MAX-ACCESS   read-only
    STATUS       current
    DESCRIPTION
        "tQosPolicerArbiterTblLastChgd indicates the timestamp of last change to
        the tQosPolicerArbiterTable."
    ::= { tQosTimeStampObjects 89 }

tQosPolicerArbiterTable OBJECT-TYPE
    SYNTAX       SEQUENCE OF TQosPolicerArbiterEntry
    MAX-ACCESS   not-accessible
    STATUS       current
    DESCRIPTION
        "tQosPolicerArbiterTable defines policy arbiters for all policer control
        policies."
    ::= { tQosPolicerObjects 3 }

tQosPolicerArbiterEntry OBJECT-TYPE
    SYNTAX       TQosPolicerArbiterEntry
    MAX-ACCESS   not-accessible
    STATUS       current
    DESCRIPTION
        "tQosPolicerArbiterEntry defines a particular policy arbiter for a
        specific QoS policer control policy on a given tier.

        Entries are created and deleted by user."
    INDEX {
            tQosPolicerCtrlPolName,
            tQosPolicerArbiterTier,
            tQosPolicerArbiterName
    }
    ::= { tQosPolicerArbiterTable 1 }

TQosPolicerArbiterEntry ::= SEQUENCE
    {
        tQosPolicerArbiterTier             INTEGER,
        tQosPolicerArbiterName             TNamedItem,
        tQosPolicerArbiterRowStatus        RowStatus,
        tQosPolicerArbiterLastChgd         TimeStamp,
        tQosPolicerArbiterDescr            TItemDescription,
        tQosPolicerArbiterRate             THPolPIRRate,
        tQosPolicerArbiterParent           TNamedItemOrEmpty,
        tQosPolicerArbiterLevel            TLevel,
        tQosPolicerArbiterWeight           TPolicerWeight
    }

tQosPolicerArbiterTier OBJECT-TYPE
    SYNTAX       INTEGER {
                       tier1 (1),
                       tier2 (2)
                 }
    MAX-ACCESS   not-accessible
    STATUS       current
    DESCRIPTION
        "The value of tQosPolicerArbiterTier identifies the tier of the
        policer control policy arbiter."
    ::= { tQosPolicerArbiterEntry 1 }

tQosPolicerArbiterName OBJECT-TYPE
    SYNTAX       TNamedItem
    MAX-ACCESS   not-accessible
    STATUS       current
    DESCRIPTION
        "The value of tQosPolicerArbiterName identifies the name of the
        policer control policy arbiter."
    ::= { tQosPolicerArbiterEntry 2 }

tQosPolicerArbiterRowStatus OBJECT-TYPE
    SYNTAX       RowStatus
    MAX-ACCESS   read-create
    STATUS       current
    DESCRIPTION
        "This is the Row Status of the entry.
        This allows creation/deletion of rows in this table."
    ::= { tQosPolicerArbiterEntry 3 }

tQosPolicerArbiterLastChgd OBJECT-TYPE
    SYNTAX       TimeStamp
    MAX-ACCESS   read-only
    STATUS       current
    DESCRIPTION
        "The value of tQosPolicerArbiterLastChgd indicates the timestamp of
        last change to this row in tQosPolicerArbiterTable."
    ::= { tQosPolicerArbiterEntry 4 }

tQosPolicerArbiterDescr OBJECT-TYPE
    SYNTAX       TItemDescription
    MAX-ACCESS   read-create
    STATUS       current
    DESCRIPTION
        "The value of tQosPolicerArbiterDescr specifies the description for the
        policer control policy arbiter for the given tier."
    DEFVAL { ''H }
    ::= { tQosPolicerArbiterEntry 5 }

tQosPolicerArbiterRate OBJECT-TYPE
    SYNTAX       THPolPIRRate
    UNITS        "kbps"
    MAX-ACCESS   read-create
    STATUS       current
    DESCRIPTION
        "The value of tQosPolicerArbiterRate specifies the maximum frame based
        bandwidth limit of this policer control policy arbiter for the given
        tier."
    DEFVAL { -1 }
    ::= { tQosPolicerArbiterEntry 6 }

tQosPolicerArbiterParent OBJECT-TYPE
    SYNTAX       TNamedItemOrEmpty
    MAX-ACCESS   read-create
    STATUS       current
    DESCRIPTION
        "tQosPolicerArbiterParent specifies the scheduler to which this queue
        would be feeding."
    DEFVAL { "root" }
    ::= { tQosPolicerArbiterEntry 7 }

tQosPolicerArbiterLevel OBJECT-TYPE
    SYNTAX       TLevel
    MAX-ACCESS   read-create
    STATUS       current
    DESCRIPTION
        "tQosPolicerArbiterLevel specifies the level of priority while feeding
        the parent."
    DEFVAL { 1 }
    ::= { tQosPolicerArbiterEntry 8 }

tQosPolicerArbiterWeight OBJECT-TYPE
    SYNTAX       TPolicerWeight
    MAX-ACCESS   read-create
    STATUS       current
    DESCRIPTION
        "tQosPolicerArbiterWeight specifies the weight that needs to be used
        by the scheduler to which this queue would be feeding."
    DEFVAL { 1 }
    ::= { tQosPolicerArbiterEntry 9 }

-- -------------------------
-- QOS Ingress Policer table
-- -------------------------

tQosIngPolicerTableLastChanged OBJECT-TYPE
    SYNTAX       TimeStamp
    MAX-ACCESS   read-only
    STATUS       current
    DESCRIPTION
        "tQosIngPolicerTableLastChanged indicates the timestamp of last change
         to the tQosIngPolicerTable."
    ::= { tQosTimeStampObjects 97 }

tQosIngPolicerTable OBJECT-TYPE
    SYNTAX       SEQUENCE OF TQosIngPolicerEntry
    MAX-ACCESS   not-accessible
    STATUS       current
    DESCRIPTION
        "tQosIngPolicerTable defines QOS Ingress Policer Table for providing,
         via SNMP, the capability of defining the policers in the ingress queue
         groups.

         tQosIngPolicerTable holds a list of all the policers configured in
         the managed system. Policers must exist in this table before being
         referenced by the forwarding class mappings within the Qos policies."
    ::= { tQosPolicerObjects 4 }

tQosIngPolicerEntry OBJECT-TYPE
    SYNTAX       TQosIngPolicerEntry
    MAX-ACCESS   not-accessible
    STATUS       current
    DESCRIPTION
        "tQosIngPolicerEntry defines an entry in the tQosIngPolicerTable.

         Entries are created/deleted in this table by SNMP sets to
         tQosIngPolicerRowStatus."
    INDEX { tQosIngQGroupName, tQosIngPolicerId }
    ::= { tQosIngPolicerTable 1 }

TQosIngPolicerEntry ::= SEQUENCE
    {
        tQosIngPolicerId               TIngPolicerId,
        tQosIngPolicerRowStatus        RowStatus,
        tQosIngPolicerLastChanged      TimeStamp,
        tQosIngPolicerDescr            TItemDescription,
        tQosIngPolicerPIRAdaptation    TAdaptationRule,
        tQosIngPolicerCIRAdaptation    TAdaptationRule,
        tQosIngPolicerParent           TNamedItemOrEmpty,
        tQosIngPolicerLevel            TLevel,
        tQosIngPolicerWeight           TPolicerWeight,
        tQosIngPolicerAdminPIR         THPolPIRRate,
        tQosIngPolicerAdminCIR         THPolCIRRate,
        tQosIngPolicerCBS              TPlcrBurstSizeBytes,
        tQosIngPolicerMBS              TPlcrBurstSizeBytes,
        tQosIngPolicerHiPrioOnly       TBurstPercentOrDefault,
        tQosIngPolicerPktOffset        TPerPacketOffset,
        tQosIngPolicerProfileCapped    TruthValue,
        tQosIngPolicerStatMode         TmnxIngPolicerStatMode,
        tQosIngPolicerSlopeStartDepth  Unsigned32,
        tQosIngPolicerSlopeMaxDepth    Unsigned32,
        tQosIngPolicerSlopeMaxProb     Unsigned32,
        tQosIngPolicerSlopeMap         TmnxSlopeMap,
        tQosIngPolicerAdvCfgPolicy     TNamedItemOrEmpty 
    }

tQosIngPolicerId OBJECT-TYPE
    SYNTAX       TIngPolicerId
    MAX-ACCESS   not-accessible
    STATUS       current
    DESCRIPTION
        "tQosIngPolicerId defines the Ingress Queue Group Policer identifier.
         It identifies an ingress queue group policer in the managed system."
    ::= { tQosIngPolicerEntry 1 }

tQosIngPolicerRowStatus OBJECT-TYPE
    SYNTAX       RowStatus
    MAX-ACCESS   read-create
    STATUS       current
    DESCRIPTION
        "tQosIngPolicerRowStatus allows entries to be created and deleted
         in the tQosIngPolicerTable."
    ::= { tQosIngPolicerEntry 2 }

tQosIngPolicerLastChanged OBJECT-TYPE
    SYNTAX       TimeStamp
    MAX-ACCESS   read-only
    STATUS       current
    DESCRIPTION
        "tQosIngPolicerLastChanged indicates the value of sysUpTime when
         the entry was last modified."
    ::= { tQosIngPolicerEntry 3 }

tQosIngPolicerDescr OBJECT-TYPE
    SYNTAX       TItemDescription
    MAX-ACCESS   read-create
    STATUS       current
    DESCRIPTION
        "tQosIngPolicerDescr specifies the description of the policer."
    DEFVAL { ''H }
    ::= { tQosIngPolicerEntry 4 }

tQosIngPolicerPIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tQosIngPolicerEntry 5 }

tQosIngPolicerCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tQosIngPolicerEntry 6 }

tQosIngPolicerParent OBJECT-TYPE
    SYNTAX       TNamedItemOrEmpty
    MAX-ACCESS   read-create
    STATUS       current
    DESCRIPTION
        "tQosIngPolicerParent specifies the  arbiter to which this policer
         would be feeding."
    DEFVAL { ''H }
    ::= { tQosIngPolicerEntry 7 }

tQosIngPolicerLevel OBJECT-TYPE
    SYNTAX       TLevel
    MAX-ACCESS   read-create
    STATUS       current
    DESCRIPTION
        "tQosIngPolicerLevel specifies the level of priority while feeding
         the parent."
    DEFVAL { 1 }
    ::= { tQosIngPolicerEntry 8 }

tQosIngPolicerWeight OBJECT-TYPE
    SYNTAX       TPolicerWeight
    MAX-ACCESS   read-create
    STATUS       current
    DESCRIPTION
        "tQosIngPolicerWeight specifies the weight that needs to be used by the
         arbiter to which this  policer would be feeding"
    DEFVAL { 1 }
    ::= { tQosIngPolicerEntry 9 }

tQosIngPolicerAdminPIR OBJECT-TYPE
    SYNTAX       THPolPIRRate
    UNITS        "kbps"
    MAX-ACCESS   read-create
    STATUS       current
    DESCRIPTION
        "tQosIngPolicerAdminPIR specifies the administrative PIR specified by
         the user."
    DEFVAL { -1 }
    ::= { tQosIngPolicerEntry 10 }

tQosIngPolicerAdminCIR OBJECT-TYPE
    SYNTAX       THPolCIRRate
    UNITS        "kbps"
    MAX-ACCESS   read-create
    STATUS       current
    DESCRIPTION
        "tQosIngPolicerAdminCIR specifies the administrative CIR specified by
         the user."
    DEFVAL { 0 }
    ::= { tQosIngPolicerEntry 11 }

tQosIngPolicerCBS OBJECT-TYPE
    SYNTAX       TPlcrBurstSizeBytes
    UNITS        "bytes"
    MAX-ACCESS   read-create
    STATUS       current
    DESCRIPTION
        "tQosIngPolicerCBS specifies the amount of reserved buffer space 
         (in bytes) used to configure the policer's CIR leaky bucket's 'exceed'
         threshold."
    DEFVAL { -1 }
    ::= { tQosIngPolicerEntry 12 }

tQosIngPolicerMBS OBJECT-TYPE
    SYNTAX       TPlcrBurstSizeBytes
    UNITS        "bytes"
    MAX-ACCESS   read-create
    STATUS       current
    DESCRIPTION
        "tQosIngPolicerMBS specifies the maximum amount of buffer space
         (in bytes) used to configure the policer's PIR leaky bucket's high 
         priority 'violate' threshold."
    DEFVAL { -1 }
    ::= { tQosIngPolicerEntry 13 }

tQosIngPolicerHiPrioOnly OBJECT-TYPE
    SYNTAX       TBurstPercentOrDefault
    UNITS        "percent"
    MAX-ACCESS   read-create
    STATUS       current
    DESCRIPTION
        "tQosIngPolicerHiPrioOnly specifies the percentage of buffer space
         for the queue, used to configure the percentage of the policer's PIR
         leaky bucket's MBS (maximum burst size) that is reserved for high 
         priority traffic."
    DEFVAL { -1 }
    ::= { tQosIngPolicerEntry 14 }

tQosIngPolicerPktOffset OBJECT-TYPE
    SYNTAX       TPerPacketOffset
    MAX-ACCESS   read-create
    STATUS       current
    DESCRIPTION
        "tQosIngPolicerPktOffset specifies the packet byte offset for
         addition of policing information by this policer."
    DEFVAL { 0 }
    ::= { tQosIngPolicerEntry 15 }

tQosIngPolicerProfileCapped OBJECT-TYPE
    SYNTAX       TruthValue
    MAX-ACCESS   read-create
    STATUS       current
    DESCRIPTION
        "The value of tQosIngPolicerProfileCapped specifies how the explicit
         in-profile and undetermined profile traffic should be handled at the 
         ingress policer.
        
         When the value of tQosIngPolicerProfileCapped is set to 'true', both
         explicit in-profile and undetermined profile traffic is honored up to
         CIR, above which it marked as out-of-profile. If CIR is set to zero, 
         then all explicit in-profile and undetermined profile packets, along
         with the explicit out-of-profile packets are marked as out-of-profile.

         The default behavior when tQosIngPolicerProfileCapped is set to 
         'false' is to ignore the CIR output state when an explicit in-profile 
         packet is handled by an ingress policer."
   DEFVAL { false }
    ::= { tQosIngPolicerEntry 16 }

tQosIngPolicerStatMode OBJECT-TYPE
    SYNTAX       TmnxIngPolicerStatMode
    MAX-ACCESS   read-create
    STATUS       current
    DESCRIPTION
        "tQosIngPolicerStatMode specifies the mode of statistics collected by
         this policer."
    DEFVAL { minimal }
    ::= { tQosIngPolicerEntry 17 }

tQosIngPolicerSlopeStartDepth OBJECT-TYPE
    SYNTAX       Unsigned32 (1..10000)
    UNITS        "hundredths of a percent"
    MAX-ACCESS   read-create
    STATUS       current
    DESCRIPTION
        "The value of tQosIngPolicerSlopeStartDepth specifies the percentage of
         the buffer utilized after which the drop probability starts to rise
         above 0."
    DEFVAL { 10000 }
    ::= { tQosIngPolicerEntry 18 }

tQosIngPolicerSlopeMaxDepth OBJECT-TYPE
    SYNTAX       Unsigned32 (1..10000)
    UNITS        "hundredths of a percent"
    MAX-ACCESS   read-create
    STATUS       current
    DESCRIPTION
        "The value of tQosIngPolicerSlopeMaxDepth specifies the percentage of
         the buffer utilized after which the drop probability is 100 percent.
         This implies that all packets beyond this point will be
         dropped."
    DEFVAL { 10000 }
    ::= { tQosIngPolicerEntry 19 }

tQosIngPolicerSlopeMaxProb OBJECT-TYPE
    SYNTAX       Unsigned32 (1..10000)
    UNITS        "hundredths of a percent"
    MAX-ACCESS   read-create
    STATUS       current
    DESCRIPTION
        "The value of tQosIngPolicerSlopeMaxProb specifies the drop 
         probability, as a percentage, when the queue depth reaches
         tQosIngPolicerSlopeMaxDepth. The drop increases steadily from 0 at
         the tQosIngPolicerSlopeStartDepth up to the
         tQosIngPolicerSlopeMaxProb at the tQosIngPolicerSlopeMaxDepth."
    DEFVAL { 10000 }
    ::= { tQosIngPolicerEntry 20 }

tQosIngPolicerSlopeMap OBJECT-TYPE
    SYNTAX       TmnxSlopeMap
    MAX-ACCESS   read-create
    STATUS       current
    DESCRIPTION
        "The value of tQosIngPolicerSlopeMap specifies the slope map to be used
         with this policer."
    DEFVAL { none }
    ::= { tQosIngPolicerEntry 21 }

tQosIngPolicerAdvCfgPolicy        OBJECT-TYPE
    SYNTAX      TNamedItemOrEmpty
    MAX-ACCESS  read-create
    STATUS      current
    DESCRIPTION
        "The value of tQosIngPolicerAdvCfgPolicy specifies the name of the 
         advanced configuration policy to be applied with this policer."
    DEFVAL { ''H }
    ::= { tQosIngPolicerEntry 22 }

-- -------------------------
-- QOS Egress Policer table
-- -------------------------

tQosEgrPolicerTableLastChanged OBJECT-TYPE
    SYNTAX       TimeStamp
    MAX-ACCESS   read-only
    STATUS       current
    DESCRIPTION
        "tQosEgrPolicerTableLastChanged indicates the timestamp of last change
         to the tQosEgrPolicerTable."
    ::= { tQosTimeStampObjects 98 }

tQosEgrPolicerTable OBJECT-TYPE
    SYNTAX       SEQUENCE OF TQosEgrPolicerEntry
    MAX-ACCESS   not-accessible
    STATUS       current
    DESCRIPTION
        "tQosEgrPolicerTable defines QOS egress Policer Table for providing,
         via SNMP, the capability of defining the policers in the egress queue
         groups.

         tQosEgrPolicerTable holds a list of all the policers configured in
         the managed system. Policers must exist in this table before being
         referenced by the forwarding class mappings within Qos policies."
    ::= { tQosPolicerObjects 5 }

tQosEgrPolicerEntry OBJECT-TYPE
    SYNTAX       TQosEgrPolicerEntry
    MAX-ACCESS   not-accessible
    STATUS       current
    DESCRIPTION
        "tQosEgrPolicerEntry defines an entry in the tQosEgrPolicerTable.

         Entries are created/deleted in this table by SNMP sets to
         tQosEgrPolicerRowStatus."
    INDEX { tQosEgrQGroupName, tQosEgrPolicerId }
    ::= { tQosEgrPolicerTable 1 }

TQosEgrPolicerEntry ::= SEQUENCE
    {
        tQosEgrPolicerId               TEgrPolicerId,
        tQosEgrPolicerRowStatus        RowStatus,
        tQosEgrPolicerLastChanged      TimeStamp,
        tQosEgrPolicerDescr            TItemDescription,
        tQosEgrPolicerPIRAdaptation    TAdaptationRule,
        tQosEgrPolicerCIRAdaptation    TAdaptationRule,
        tQosEgrPolicerParent           TNamedItemOrEmpty,
        tQosEgrPolicerLevel            TLevel,
        tQosEgrPolicerWeight           TPolicerWeight,
        tQosEgrPolicerAdminPIR         THPolPIRRate,
        tQosEgrPolicerAdminCIR         THPolCIRRate,
        tQosEgrPolicerCBS              TPlcrBurstSizeBytes,
        tQosEgrPolicerMBS              TPlcrBurstSizeBytes,
        tQosEgrPolicerHiPrioOnly       TBurstPercentOrDefault,
        tQosEgrPolicerPktOffset        TEgressPerPacketOffset,
        tQosEgrPolicerProfileCapped    TruthValue,
        tQosEgrPolicerStatMode         TmnxEgrPolicerStatMode,
        tQosEgrPolicerSlopeStartDepth  Unsigned32,
        tQosEgrPolicerSlopeMaxDepth    Unsigned32,
        tQosEgrPolicerSlopeMaxProb     Unsigned32,
        tQosEgrPolicerSlopeMap         TmnxSlopeMap,
        tQosEgrPolicerAdvCfgPolicy     TNamedItemOrEmpty 
    }

tQosEgrPolicerId OBJECT-TYPE
    SYNTAX       TEgrPolicerId
    MAX-ACCESS   not-accessible
    STATUS       current
    DESCRIPTION
        "tQosEgrPolicerId defines the Egress Queue Group Policer identifier.
         It identifies an  egress queue group policer in the managed system."
    ::= { tQosEgrPolicerEntry 1 }

tQosEgrPolicerRowStatus OBJECT-TYPE
    SYNTAX       RowStatus
    MAX-ACCESS   read-create
    STATUS       current
    DESCRIPTION
        "tQosEgrPolicerRowStatus allows entries to be created and deleted
         in the tQosEgrPolicerTable."
    ::= { tQosEgrPolicerEntry 2 }

tQosEgrPolicerLastChanged OBJECT-TYPE
    SYNTAX       TimeStamp
    MAX-ACCESS   read-only
    STATUS       current
    DESCRIPTION
        "tQosEgrPolicerLastChanged indicates the value of sysUpTime when
         the entry was last modified."
    ::= { tQosEgrPolicerEntry 3 }

tQosEgrPolicerDescr OBJECT-TYPE
    SYNTAX       TItemDescription
    MAX-ACCESS   read-create
    STATUS       current
    DESCRIPTION
        "tQosEgrPolicerDescr specifies the description of the policer."
    DEFVAL { ''H }
    ::= { tQosEgrPolicerEntry 4 }

tQosEgrPolicerPIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tQosEgrPolicerEntry 5 }

tQosEgrPolicerCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tQosEgrPolicerEntry 6 }

tQosEgrPolicerParent OBJECT-TYPE
    SYNTAX       TNamedItemOrEmpty
    MAX-ACCESS   read-create
    STATUS       current
    DESCRIPTION
        "tQosEgrPolicerParent specifies the  arbiter to which this policer would
         be feeding"
    DEFVAL { ''H }
    ::= { tQosEgrPolicerEntry 7 }

tQosEgrPolicerLevel OBJECT-TYPE
    SYNTAX       TLevel
    MAX-ACCESS   read-create
    STATUS       current
    DESCRIPTION
        "tQosEgrPolicerLevel specifies the level of priority while feeding
         the parent."
    DEFVAL { 1 }
    ::= { tQosEgrPolicerEntry 8 }

tQosEgrPolicerWeight OBJECT-TYPE
    SYNTAX       TPolicerWeight
    MAX-ACCESS   read-create
    STATUS       current
    DESCRIPTION
        "tQosEgrPolicerWeight specifies the weight that needs to be used by the
         scheduler to which this queue would be feeding."
    DEFVAL { 1 }
    ::= { tQosEgrPolicerEntry 9 }

tQosEgrPolicerAdminPIR OBJECT-TYPE
    SYNTAX       THPolPIRRate
    UNITS        "kbps"
    MAX-ACCESS   read-create
    STATUS       current
    DESCRIPTION
        "tQosEgrPolicerAdminPIR specifies the administrative PIR specified by
         the user."
    DEFVAL { -1 }
    ::= { tQosEgrPolicerEntry 10 }

tQosEgrPolicerAdminCIR OBJECT-TYPE
    SYNTAX       THPolCIRRate
    UNITS        "kbps"
    MAX-ACCESS   read-create
    STATUS       current
    DESCRIPTION
        "tQosEgrPolicerAdminCIR specifies the administrative CIR specified by
         the user."
    DEFVAL { 0 }
    ::= { tQosEgrPolicerEntry 11 }

tQosEgrPolicerCBS OBJECT-TYPE
    SYNTAX       TPlcrBurstSizeBytes
    UNITS        "bytes"
    MAX-ACCESS   read-create
    STATUS       current
    DESCRIPTION
        "tQosEgrPolicerCBS specifies the amount of reserved buffer space
         (in bytes) used to configure the policer's CIR leaky bucket's 'exceed'
         threshold."
    DEFVAL { -1 }
    ::= { tQosEgrPolicerEntry 12 }

tQosEgrPolicerMBS OBJECT-TYPE
    SYNTAX       TPlcrBurstSizeBytes
    UNITS        "bytes"
    MAX-ACCESS   read-create
    STATUS       current
    DESCRIPTION
        "tQosEgrPolicerMBS specifies the maximum amount of buffer space
         (in bytes) used to configure the policer's PIR leaky bucket's high 
         priority 'violate' threshold."
    DEFVAL { -1 }
    ::= { tQosEgrPolicerEntry 13 }

tQosEgrPolicerHiPrioOnly OBJECT-TYPE
    SYNTAX       TBurstPercentOrDefault
    UNITS        "percent"
    MAX-ACCESS   read-create
    STATUS       current
    DESCRIPTION
        "tQosEgrPolicerHiPrioOnly specifies the percentage of buffer space for 
         the queue, used to configure the percentage of the policer's PIR leaky
         bucket's MBS (maximum burst size) that is reserved for high priority
         traffic."
    DEFVAL { -1 }
    ::= { tQosEgrPolicerEntry 14 }

tQosEgrPolicerPktOffset OBJECT-TYPE
    SYNTAX       TEgressPerPacketOffset
    MAX-ACCESS   read-create
    STATUS       current
    DESCRIPTION
        "tQosEgrPolicerPktOffset specifies the packet byte offset for
         addition of policing information by this policer."
    DEFVAL { 0 }
    ::= { tQosEgrPolicerEntry 15 }

tQosEgrPolicerProfileCapped OBJECT-TYPE
    SYNTAX       TruthValue
    MAX-ACCESS   read-create
    STATUS       current
    DESCRIPTION
        "The value of tQosEgrPolicerProfileCapped specifies how the explicit 
         in-profile and undetermined profile traffic should be handled at the 
         egress policer.

         When the value of tQosEgrPolicerProfileCapped is set to 'true', both 
         explicit in-profile and undetermined profile traffic is honored up to 
         CIR, above which it is marked as out-of-profile. If CIR is set to zero,
         then all explicit in-profile and undetermined profile packets, along
         with the explicit out-of-profile packets are marked as out-of-profile.

         The default behavior when tQosEgrPolicerProfileCapped is set to 
         'false' is to ignore the CIR output state when an explicit in-profile 
         packet is handled by an egress policer."
    DEFVAL { false }
    ::= { tQosEgrPolicerEntry 16 }

tQosEgrPolicerStatMode OBJECT-TYPE
    SYNTAX       TmnxEgrPolicerStatMode
    MAX-ACCESS   read-create
    STATUS       current
    DESCRIPTION
        "tQosEgrPolicerStatMode specifies the mode of statistics collected by
        this policer."
    DEFVAL { minimal }
    ::= { tQosEgrPolicerEntry 17 }

tQosEgrPolicerSlopeStartDepth OBJECT-TYPE
    SYNTAX       Unsigned32 (1..10000)
    UNITS        "hundredths of a percent"
    MAX-ACCESS   read-create
    STATUS       current
    DESCRIPTION
        "The value of tQosEgrPolicerSlopeStartDepth specifies the percentage of
         the buffer utilized after which the drop probability starts to rise
         above 0."
    DEFVAL { 10000 }
    ::= { tQosEgrPolicerEntry 18 }

tQosEgrPolicerSlopeMaxDepth OBJECT-TYPE
    SYNTAX       Unsigned32 (1..10000)
    UNITS        "hundredths of a percent"
    MAX-ACCESS   read-create
    STATUS       current
    DESCRIPTION
        "The value of tQosEgrPolicerSlopeMaxDepth specifies the percentage of
         the buffer utilized after which the drop probability is 100 percent.
         This implies that all packets beyond this point will be
         dropped."
    DEFVAL { 10000 }
    ::= { tQosEgrPolicerEntry 20 }

tQosEgrPolicerSlopeMaxProb OBJECT-TYPE
    SYNTAX       Unsigned32 (1..10000)
    UNITS        "hundredths of a percent"
    MAX-ACCESS   read-create
    STATUS       current
    DESCRIPTION
        "The value of tQosEgrPolicerSlopeMaxProb specifies the drop 
         probability, as a percentage, when the queue depth reaches
         tQosEgrPolicerSlopeMaxDepth. The drop increases steadily from 0 at
         the tQosEgrPolicerSlopeStartDepth up to the
         tQosEgrPolicerSlopeMaxProb at the tQosEgrPolicerSlopeMaxDepth."
    DEFVAL { 10000 }
    ::= { tQosEgrPolicerEntry 21 }

tQosEgrPolicerSlopeMap OBJECT-TYPE
    SYNTAX       TmnxSlopeMap
    MAX-ACCESS   read-create
    STATUS       current
    DESCRIPTION
        "The value of tQosEgrPolicerSlopeMap specifies the slope map to be used
         with this policer."
    DEFVAL { none }
    ::= { tQosEgrPolicerEntry 22 }

tQosEgrPolicerAdvCfgPolicy        OBJECT-TYPE
    SYNTAX      TNamedItemOrEmpty
    MAX-ACCESS  read-create
    STATUS      current
    DESCRIPTION
        "The value of tQosEgrPolicerAdvCfgPolicy specifies the name of the 
         advanced configuration policy to be applied with this policer."
    DEFVAL { ''H }
    ::= { tQosEgrPolicerEntry 23 }

--
-- Advanced Configuration Policy Table
--
tAdvCfgPolicyTblLastChgd      OBJECT-TYPE
    SYNTAX       TimeStamp
    MAX-ACCESS   read-only
    STATUS       current
    DESCRIPTION
        "The value of tAdvCfgPolicyTblLastChgd indicates the timestamp of last
         change to the tAdvCfgPolicyTable."
    ::= { tQosTimeStampObjects 100 }

tAdvCfgPolicyTable OBJECT-TYPE
    SYNTAX      SEQUENCE OF TAdvCfgPolicyEntry
    MAX-ACCESS  not-accessible
    STATUS      current
    DESCRIPTION
        "The tAdvCfgPolicyTable has an entry for each configuration
         policy for queue and policer parameters configured on this system."
    ::= { tQosPolicerObjects 6 }

tAdvCfgPolicyEntry    OBJECT-TYPE
    SYNTAX      TAdvCfgPolicyEntry
    MAX-ACCESS  not-accessible
    STATUS      current
    DESCRIPTION
        "Each row represents a particular configuration policy. Entries are 
         created and deleted by the user."
    INDEX { tAdvCfgPolicyName }
    ::= { tAdvCfgPolicyTable 1}

TAdvCfgPolicyEntry ::= SEQUENCE
    {
         tAdvCfgPolicyName                   TNamedItem,
         tAdvCfgPolicyRowStatus              RowStatus,
         tAdvCfgLastChanged                  TimeStamp,
         tAdvCfgDescription                  TItemDescription,
         tAdvCfgChildAdmnPirPrcnt            Unsigned32,
         tAdvCfgChildAdminRate               TAdvCfgRate,
         tAdvCfgOMGranPirPrcnt               Unsigned32,
         tAdvCfgOMGranRate                   TAdvCfgRate,
         tAdvCfgMaxDecPirPrcnt               Unsigned32,
         tAdvCfgMaxDecRate                   TMaxDecRate,
         tAdvCfgHiRateHoldTime               Unsigned32,
         tAdvCfgTimeAvgFactor                Unsigned32,
         tAdvCfgSampleInterval               Unsigned32,
         tAdvCfgFastStart                    TruthValue,
         tAdvCfgFastStop                     TruthValue,
         tAdvCfgAbvOffCapPirPrcnt            Unsigned32,
         tAdvCfgAbvOffCapRate                Integer32,
         tAdvCfgBWDGranPirPrcnt              Unsigned32,
         tAdvCfgBWDGranRate                  TAdvCfgRate,
         tAdvCfgMinOnly                      TruthValue,
         tAdvCfgDecOnly                      TruthValue,
         tAdvCfgChildAdminRateActMinOnly     TruthValue,    
         tAdvCfgHiRateHoldTimeActMinOnly     TruthValue, 
         tAdvCfgBWDEnqueueOnPIRZero          TruthValue,
         tAdvCfgBWDLimitPIRZeroDrain         TruthValue,
         tAdvCfgBWDLmtUnusedBWInitMinPIR     TruthValue,
         tAdvCfgBWDInternalSchedWghtMode     TmnxInternalSchedWeightMode
    }

tAdvCfgPolicyName        OBJECT-TYPE
    SYNTAX      TNamedItem
    MAX-ACCESS  not-accessible
    STATUS      current
    DESCRIPTION
        "The value of tAdvCfgPolicyName specifies the name of the advanced
         configuration policy."
    ::= { tAdvCfgPolicyEntry 1 }

tAdvCfgPolicyRowStatus        OBJECT-TYPE
    SYNTAX      RowStatus
    MAX-ACCESS  read-create
    STATUS      current
    DESCRIPTION
        "The value of tAdvCfgPolicyRowStatus is used for the creation
         and deletion of advanced configuration policies."
    ::= { tAdvCfgPolicyEntry 2 }

tAdvCfgLastChanged        OBJECT-TYPE
    SYNTAX      TimeStamp
    MAX-ACCESS  read-only
    STATUS      current
    DESCRIPTION
        "The value of tAdvCfgLastChanged indicates the sysUpTime
         at the time of the last modification of this entry.

         If no changes were made to the entry since the last
         re-initialization of the local network management subsystem,
         then this object contains a zero value."
    ::= { tAdvCfgPolicyEntry 3 }

tAdvCfgDescription        OBJECT-TYPE
    SYNTAX      TItemDescription
    MAX-ACCESS  read-create
    STATUS      current
    DESCRIPTION
        "The value of tAdvCfgDescription specifies the description
         of this advanced configuration policy."
    DEFVAL { ''H }
    ::= { tAdvCfgPolicyEntry 4 }

tAdvCfgChildAdmnPirPrcnt    OBJECT-TYPE
    SYNTAX       Unsigned32 (0..10000)
    UNITS        "hundredths of a percent"
    MAX-ACCESS   read-create
    STATUS       current
    DESCRIPTION
        "The value of tAdvCfgChildAdmnPirPrcnt specifies the percentage of the 
         child's administrative PIR that should be added to the child's offered
         rate, capped by the child's PIR. 

         When the value of tAdvCfgChildAdmnPirPrcnt is set to '0', offered rate
         increase from all child policers and queues specified by 
         tAdvCfgPolicyName policy are removed."
    DEFVAL { 0 }
    ::= { tAdvCfgPolicyEntry 5 }

tAdvCfgChildAdminRate        OBJECT-TYPE
    SYNTAX       TAdvCfgRate
    UNITS        "kbps"
    MAX-ACCESS   read-create
    STATUS       current
    DESCRIPTION
        "The value of tAdvCfgChildAdminRate specifies the explicit number of 
         kilobits-per-second that should be added to the child's offered rate.

         When the value of tAdvCfgChildAdminRate is set to '0', offered rate
         increase from all child policers and queues  specified by  
         tAdvCfgPolicyName policy are removed."
    DEFVAL { 0 }
    ::= { tAdvCfgPolicyEntry 6 }

tAdvCfgOMGranPirPrcnt OBJECT-TYPE
    SYNTAX       Unsigned32 (0..10000)
    UNITS        "hundredths of a percent"
    MAX-ACCESS   read-create
    STATUS       current
    DESCRIPTION
        "The value of tAdvCfgOMGranPirPrcnt specifies the granularity 
         percentage of the child's administrative PIR that should be used as the
         threshold sensitivity to offered rate.

         When the value of tAdvCfgOMGranPirPrcnt is set to '0', it restores 
         the default offered rate sensitivity behavior to all child policers and
         queues associated with the policy specified by tAdvCfgPolicyName."
    DEFVAL { 0 }
    ::= { tAdvCfgPolicyEntry 7 }

tAdvCfgOMGranRate        OBJECT-TYPE
    SYNTAX       TAdvCfgRate
    UNITS        "kbps"
    MAX-ACCESS   read-create
    STATUS       current
    DESCRIPTION
        "The value of tAdvCfgOMGranRate specifies the explicit number of 
         kilobits-per-second that should be used as the child's offered rate
         change sensitivity value.

         When the value of tAdvCfgOMGranRate is set to '0', the 
         default offered rate sensitivity behavior to all child policers and
         queues associated with the policy specified by tAdvCfgPolicyName are
         restored."
    DEFVAL { 0 }
    ::= { tAdvCfgPolicyEntry 8 }

tAdvCfgMaxDecPirPrcnt OBJECT-TYPE
    SYNTAX       Unsigned32 (0..10000)
    UNITS        "hundredths of a percent"
    MAX-ACCESS   read-create
    STATUS       current
    DESCRIPTION
        "The value of tAdvCfgMaxDecPirPrcnt specifies the percentage of the 
         child's administrative PIR that should be used as the decrement limit 
         to offered rate change.

         When the value of tAdvCfgMaxDecPirPrcnt is set to '10000', any 
         currently configured maximum decrement limit for all child policers and
         queues associated with the policy specified by tAdvCfgPolicyName are 
         removed."
    DEFVAL { 10000 }
    ::= { tAdvCfgPolicyEntry 9 }

tAdvCfgMaxDecRate        OBJECT-TYPE
    SYNTAX       TMaxDecRate
    UNITS        "kbps"
    MAX-ACCESS   read-create
    STATUS       current
    DESCRIPTION
        "The value of tAdvCfgMaxDecRate specifies the explicit number of 
         kilobits-per-second that should be used as the child's offered rate 
         decrement limit value."
    DEFVAL { 0 }
    ::= { tAdvCfgPolicyEntry 10 }

tAdvCfgHiRateHoldTime OBJECT-TYPE
    SYNTAX       Unsigned32 (0..60)
    UNITS        "seconds"
    MAX-ACCESS   read-create
    STATUS       current
    DESCRIPTION  
        "The value of tAdvCfgHiRateHoldTime specifies the time period that the
         current offered rate should be maintained for a child policer or queue.

         When tAdvCfgHiRateHoldTime is set to '0', any currently configured hold
         time for all child policers and queues associated with the policy 
         specified by tAdvCfgPolicyName are removed." 
    DEFVAL { 0 }
    ::= { tAdvCfgPolicyEntry 11 }

tAdvCfgTimeAvgFactor        OBJECT-TYPE
    SYNTAX      Unsigned32 (0..64)
    MAX-ACCESS  read-create
    STATUS      current
    DESCRIPTION
        "The value of tAdvCfgTimeAvgFactor is used the weight the new offered
         rate with a portion of the pervious offered rate.

         When tAdvCfgTimeAvgFactor is set to '0', time average factor 
         adjustments to new offered rate measurements specified by 
         tAdvCfgPolicyName are removed." 
    DEFVAL { 0 }
    ::= { tAdvCfgPolicyEntry 12 }

tAdvCfgSampleInterval        OBJECT-TYPE
    SYNTAX      Unsigned32 (1..8)
    MAX-ACCESS  read-create
    STATUS      current
    DESCRIPTION
        "The value of tAdvCfgSampleInterval specifies the interval for sampling
         the child's offered rate. A value of '1' of tAdvCfgSampleInterval
         represents fastest sampling rate available while a value of '8' 
         represents  slowest sampling period available.        

         When tAdvCfgSampleInterval is set to '4', time average factor 
         adjustments to new offered rate measurements specified by 
         tAdvCfgPolicyName are removed." 
    DEFVAL { 1 }
    ::= { tAdvCfgPolicyEntry 13 }

tAdvCfgFastStart        OBJECT-TYPE
    SYNTAX      TruthValue
    MAX-ACCESS  read-create
    STATUS      current
    DESCRIPTION
        "The value of tAdvCfgFastStart specifies the whether fast detection of
         initial bandwidth on a child policer or queue associated with 
         tAdvCfgPolicyName is enabled/disabled.

         When the tAdvCfgFastStart is set to 'false', the system uses the normal
         sampling interval behavior of both newly active and currently active
         children."
    DEFVAL { false }
    ::= { tAdvCfgPolicyEntry 14 }

tAdvCfgFastStop        OBJECT-TYPE
    SYNTAX      TruthValue
    MAX-ACCESS  read-create
    STATUS      current
    DESCRIPTION
        "The value of tAdvCfgFastStop specifies the whether fast detection of
         lack of offered rate on a child policer or queue associated with 
         tAdvCfgPolicyName is enabled/disabled.

         When the tAdvCfgFastStop is set to 'false', the system uses the normal
         sampling interval behavior of both newly active and currently active
         children."
    DEFVAL { false }
    ::= { tAdvCfgPolicyEntry 15 }

tAdvCfgAbvOffCapPirPrcnt OBJECT-TYPE
    SYNTAX       Unsigned32 (0..10000)
    UNITS        "hundredths of a percent"
    MAX-ACCESS   read-create
    STATUS       current
    DESCRIPTION
        "The value of tAdvCfgAbvOffCapPirPrcnt specifies the percentage of the 
         child's administrative PIR that should be fair share increase limit,
         capped by the child's PIR. 

         When the value of tAdvCfgAbvOffCapPirPrcnt is set to '0', the system
         disables the fair share increase function and configures the actual 
         distribution rate. 

         When the value of tAdvCfgAbvOffCapPirPrcnt is set to '10000', the 
         fair share operational PIR rate increase limit from all child policers 
         and queues associated with tAdvCfgPolicyName policy are removed."
    DEFVAL { 10000 }
    ::= { tAdvCfgPolicyEntry 16 }

tAdvCfgAbvOffCapRate        OBJECT-TYPE
    SYNTAX       Integer32 (-1 | 0..100000000)
    UNITS        "kbps"
    MAX-ACCESS   read-create
    STATUS       current
    DESCRIPTION
        "The value of tAdvCfgAbvOffCapRate specifies the explicit number of 
         kilobits-per-second that should be used as the limit to the child's 
         fair share increase to the operational PIR.

         When the value of tAdvCfgAbvOffCapRate is set to '0', the system
         disables the fair share increase function and configures the actual 
         distribution rate.

         When the value of tAdvCfgAbvOffCapRate is set to '-1', it means maximum
         rate." 
    DEFVAL { -1 }
    ::= { tAdvCfgPolicyEntry 17 }

tAdvCfgBWDGranPirPrcnt OBJECT-TYPE
    SYNTAX       Unsigned32 (0..10000)
    UNITS        "hundredths of a percent"
    MAX-ACCESS   read-create
    STATUS       current
    DESCRIPTION
        "The value of tAdvCfgBWDGranPirPrcnt specifies the granularity 
         percentage of the child's administrative PIR that should be used as the
         rounding step value.

         When the value of tAdvCfgBWDGranPirPrcnt is set to '0', the system
         removes the operational PIR rounding behavior from all child policers
         and queues associated with the policy specified by tAdvCfgPolicyName."
    DEFVAL { 0 }
    ::= { tAdvCfgPolicyEntry 18 }

tAdvCfgBWDGranRate        OBJECT-TYPE
    SYNTAX       TAdvCfgRate
    UNITS        "kbps"
    MAX-ACCESS   read-create
    STATUS       current
    DESCRIPTION
        "The value of tAdvCfgBWDGranRate specifies the explicit number of 
         kilobits-per-second that should be used as the child's rounding step 
         value.

         When the value of tAdvCfgBWDGranRate is set to '0', the system
         removes the operational PIR rounding behavior from all child policers
         and queues associated with the policy specified by tAdvCfgPolicyName."
    DEFVAL { 0 }
    ::= { tAdvCfgPolicyEntry 19 }

tAdvCfgMinOnly        OBJECT-TYPE
    SYNTAX      TruthValue
    MAX-ACCESS  read-create
    STATUS      current
    DESCRIPTION
        "The value of tAdvCfgMinOnly specifies the system to interpret the
         increase in tAdvCfgChildAdminRate as a minimum offered rate.

         When the tAdvCfgFastStop is set to 'false', the system uses the 
         specified increase in tAdvCfgChildAdmnPirPrcnt or tAdvCfgChildAdminRate
         as a minimum offered rate even for inactive queues or policers 
         associated with tAdvCfgPolicyName."
    DEFVAL { false }
    ::= { tAdvCfgPolicyEntry 20 }

tAdvCfgDecOnly        OBJECT-TYPE
    SYNTAX      TruthValue
    MAX-ACCESS  read-create
    STATUS      current
    DESCRIPTION
        "The value of tAdvCfgDecOnly specifies the tAdvCfgTimeAvgFactor 
         adjustment to be applied if the new offered rate is decreasing compared
         to the previous offered rate.  If the new offered rate is greater than
         the previous offered rate, the adjustment is not applied.

         When the tAdvCfgDecOnly is set to 'false', it has no impact on 
         tAdvCfgTimeAvgFactor adjustment."
    DEFVAL { false }
    ::= { tAdvCfgPolicyEntry 21 }

tAdvCfgChildAdminRateActMinOnly    OBJECT-TYPE
    SYNTAX      TruthValue
    MAX-ACCESS  read-create
    STATUS      current
    DESCRIPTION
        "The value of tAdvCfgChildAdminRateActMinOnly specifies whether HQos 
         should use the specified increase in tAdvCfgChildAdmnPirPrcnt or 
         tAdvCfgChildAdminRate as a minimum offered rate only for the active
         queues or policers associated with this tAdvCfgPolicyName."
    DEFVAL { false }
    ::= { tAdvCfgPolicyEntry 22 }
 
tAdvCfgHiRateHoldTimeActMinOnly    OBJECT-TYPE
    SYNTAX      TruthValue
    MAX-ACCESS  read-create
    STATUS      current
    DESCRIPTION
        "The value of tAdvCfgHiRateHoldTimeActMinOnly specifies whether HQos
         should use the specified increase in tAdvCfgChildAdmnPirPrcnt or
         tAdvCfgChildAdminRate as a minimum offered rate for the time duration
         specified by tAdvCfgHiRateHoldTime only for the active queues or
         policers associated with this tAdvCfgPolicyName.
 
         The value of tAdvCfgHiRateHoldTimeActMinOnly can only be set to 'true',
         when the value of tAdvCfgChildAdminRateActMinOnly is set to 'true'."
    DEFVAL { false }
    ::= { tAdvCfgPolicyEntry 23 }
 
tAdvCfgBWDEnqueueOnPIRZero         OBJECT-TYPE
    SYNTAX      TruthValue
    MAX-ACCESS  read-create
    STATUS      current
    DESCRIPTION
        "The value of tAdvCfgBWDEnqueueOnPIRZero specifies whether the queue
         should enqueue the packets when the value of tAdvCfgBWDGranRate is set
         to zero."
    DEFVAL { false }
    ::= { tAdvCfgPolicyEntry 24 }
 
tAdvCfgBWDLimitPIRZeroDrain        OBJECT-TYPE
    SYNTAX      TruthValue
    MAX-ACCESS  read-create
    STATUS      current
    DESCRIPTION
        "The value of tAdvCfgBWDLimitPIRZeroDrain specifies whether the queue
         should throttle its draining when the value of tAdvCfgBWDGranRate is
         set to zero."
    DEFVAL { false }
    ::= { tAdvCfgPolicyEntry 25 }
 
tAdvCfgBWDLmtUnusedBWInitMinPIR    OBJECT-TYPE
    SYNTAX      TruthValue
    MAX-ACCESS  read-create
    STATUS      current
    DESCRIPTION
        "The value of tAdvCfgBWDLmtUnusedBWInitMinPIR specifies whether the
         newly created queue should have minimal PIR when
         limit-unused-bandwidth (LUB) is enabled in the HQos hierarchy."
    DEFVAL { false }
    ::= { tAdvCfgPolicyEntry 26 }

tAdvCfgBWDInternalSchedWghtMode     OBJECT-TYPE
    SYNTAX      TmnxInternalSchedWeightMode
    MAX-ACCESS  read-create
    STATUS      current
    DESCRIPTION
       "The value of tAdvCfgBWDInternalSchedWghtMode specifies the weight-mode
        applied to this advanced-config-policy."
    DEFVAL { noOverride }
    ::= { tAdvCfgPolicyEntry 27 }

--
--  Port Scheduler Policy Group table
--

tPortSchPlcyGrpTblLastChgd OBJECT-TYPE
    SYNTAX       TimeStamp
    MAX-ACCESS   read-only
    STATUS       current
    DESCRIPTION
        "tPortSchPlcyGrpTblLastChgd indicates the timestamp of last change to
        the tPortSchPlcyGrpTable."
    ::= { tQosTimeStampObjects 91 }

tPortSchPlcyGrpTable       OBJECT-TYPE
    SYNTAX      SEQUENCE OF TPortSchPlcyGrpEntry
    MAX-ACCESS  not-accessible
    STATUS      current
    DESCRIPTION
        "The tPortSchPlcyGrpTable has an entry for each port scheduler group
         configured on this system."
    ::= { tSchedulerObjects 5 }

tPortSchPlcyGrpEntry       OBJECT-TYPE
    SYNTAX      TPortSchPlcyGrpEntry
    MAX-ACCESS  not-accessible
    STATUS      current
    DESCRIPTION
        "Each row represents a particular port scheduler group.
         Entries are created and deleted by the user."
    INDEX { tPortSchedulerPlcyName, tPortSchPlcyGrpName }
    ::= { tPortSchPlcyGrpTable 1 }

TPortSchPlcyGrpEntry ::= SEQUENCE
    {
        tPortSchPlcyGrpName                  TNamedItem,
        tPortSchPlcyGrpRowStatus             RowStatus,
        tPortSchPlcyGrpLastChanged           TimeStamp,
        tPortSchPlcyGrpAdminPIR              TPortSchedulerPIRRate,
        tPortSchPlcyGrpAdminCIR              TPortSchedulerCIR,
        tPortSchPlcyGrpPIRPercent            Unsigned32,
        tPortSchPlcyGrpCIRPercent            Unsigned32,
        tPortSchPlcyGrpRateType              TPSPRateType,
        tPortSchPlcyGroupAdminPIR            Unsigned32,
        tPortSchPlcyGroupAdminCIR            Unsigned32
    }

tPortSchPlcyGrpName  OBJECT-TYPE
    SYNTAX      TNamedItem
    MAX-ACCESS  not-accessible
    STATUS      current
    DESCRIPTION
        "The value of tPortSchPlcyGrpName specifies the name of the port
         scheduler group."
    ::= { tPortSchPlcyGrpEntry 1 }

tPortSchPlcyGrpRowStatus     OBJECT-TYPE
    SYNTAX      RowStatus
    MAX-ACCESS  read-create
    STATUS      current
    DESCRIPTION
        "The value of tPortSchPlcyGrpRowStatus is used for the creation
         and deletion of port scheduler policies."
    ::= { tPortSchPlcyGrpEntry 2 }

tPortSchPlcyGrpLastChanged        OBJECT-TYPE
    SYNTAX      TimeStamp
    MAX-ACCESS  read-only
    STATUS      current
    DESCRIPTION
        "The value of tPortSchPlcyGrpLastChanged indicates the value of 
         sysUpTime at the time of the most recent management change to this
         row."
    ::= { tPortSchPlcyGrpEntry 3 }

tPortSchPlcyGrpAdminPIR        OBJECT-TYPE
    SYNTAX      TPortSchedulerPIRRate
    UNITS       "kbps"
    MAX-ACCESS  read-create
    STATUS      obsolete
    DESCRIPTION
        "The value of tPortSchPlcyGrpAdminPIR specifies the total bandwidth
         limit, Admin PIR of this port scheduler group.

         An 'inconsistentValue' error is returned if tPortSchPlcyGrpAdminPIR
         is set to non-default value when the value of
         tPortSchPlcyGrpRateType is set to 'percentLocal'.

         This object is obsoleted in 13.0 release and replaced by
         tPortSchPlcyGroupAdminPIR."
    DEFVAL      { -1 }
    ::= { tPortSchPlcyGrpEntry 4 }

tPortSchPlcyGrpAdminCIR        OBJECT-TYPE
    SYNTAX      TPortSchedulerCIR
    UNITS       "kbps"
    MAX-ACCESS  read-create
    STATUS      obsolete
    DESCRIPTION
        "The value of tPortSchPlcyGrpAdminCIR specifies the within-cir
         bandwidth limit of this port scheduler group.

         An 'inconsistentValue' error is returned if tPortSchPlcyGrpAdminCIR
         is set to non-default value when the value of
         tPortSchPlcyGrpRateType is set to 'percentLocal'.

         This object is obsoleted in 13.0 release and replaced by
         tPortSchPlcyGroupAdminCIR."
    DEFVAL      { -1 }
    ::= { tPortSchPlcyGrpEntry 5 }

tPortSchPlcyGrpPIRPercent      OBJECT-TYPE
    SYNTAX      Unsigned32 (1..10000)
    UNITS       "hundredths of a percent"
    MAX-ACCESS  read-create
    STATUS      current
    DESCRIPTION
        "The value of tPortSchPlcyGrpPIRPercent specifies the total
         bandwidth percentage, PIR percent, for this port scheduler group.

         An 'inconsistentValue' error is returned if 
         tPortSchPlcyGrpPIRPercent is set to non-default value when the
         object tPortSchPlcyGrpRateType is set to 'kbps'."
    DEFVAL { 10000 }
    ::= { tPortSchPlcyGrpEntry 6 }

tPortSchPlcyGrpCIRPercent       OBJECT-TYPE
    SYNTAX      Unsigned32 (0..10000)
    UNITS       "hundredths of a percent"
    MAX-ACCESS  read-create
    STATUS      current
    DESCRIPTION
        "The value of tPortSchPlcyGrpCIRPercent specifies the within-cir
         bandwidth percentage for this port scheduler.

         An 'inconsistentValue' error is returned if
         tPortSchPlcyGrpCIRPercent is set to non-default value when the
         object tPortSchPlcyGrpRateType is set to 'kbps'."
    DEFVAL { 10000 }
    ::= { tPortSchPlcyGrpEntry 7 }

tPortSchPlcyGrpRateType            OBJECT-TYPE
    SYNTAX      TPSPRateType (1|2)
    MAX-ACCESS  read-create
    STATUS      current
    DESCRIPTION
        "The value of tPortSchPlcyGrpRateType specifies the type of port
         scheduler rate for this group.
         
         When the value of tPortSchPlcyGrpRateType is set to 'kbps', the
         port scheduler group rate is specified in 'kbps'. The values of
         tPortSchPlcyGrpPIRPercent and tPortSchPlcyGrpCIRPercent
         will be set to their default values.

         When the value of tPortSchPlcyGrpRateType is set to
         'percentLocal', the port scheduler group rate is specified in
         percentage of local limit. The values of
         tPortSchPlcyGroupAdminPIR and tPortSchPlcyGroupAdminCIR will be set
         to their default values."
    DEFVAL { kbps }
    ::= { tPortSchPlcyGrpEntry 8 }


tPortSchPlcyGroupAdminPIR           OBJECT-TYPE
    SYNTAX       Unsigned32 (1..3200000000 | 4294967295)
    UNITS       "kbps"
    MAX-ACCESS  read-create
    STATUS      current
    DESCRIPTION
        "The value of tPortSchPlcyGroupAdminPIR specifies the total bandwidth
         limit, Admin PIR of this port scheduler group.

         An 'inconsistentValue' error is returned if tPortSchPlcyGroupAdminPIR
         is set to non-default value when the value of tPortSchPlcyGrpRateType
         is set to 'percentLocal'.

         When the value of tPortSchPlcyGroupAdminPIR is set to 4294967295
         (0xFFFFFFFF), rate for this port scheduler group indicates maximum
         rate."
    DEFVAL { 4294967295 }
    ::= { tPortSchPlcyGrpEntry 10 }


tPortSchPlcyGroupAdminCIR           OBJECT-TYPE
    SYNTAX       Unsigned32 (0..3200000000 | 4294967295)
    UNITS       "kbps"
    MAX-ACCESS  read-create
    STATUS      current
    DESCRIPTION
        "The value of tPortSchPlcyGroupAdminCIR specifies the within-cir
         bandwidth limit of this port scheduler group.

         An 'inconsistentValue' error is returned if tPortSchPlcyGroupAdminCIR
         is set to non-default value when the value of tPortSchPlcyGrpRateType
         is set to 'percentLocal'.

         When the value of tPortSchPlcyGroupAdminCIR is set to 4294967295
         (0xFFFFFFFF), rate for this port scheduler group indicates maximum
         rate."
    DEFVAL { 4294967295 }
    ::= { tPortSchPlcyGrpEntry 12 }


--
--  Port Scheduler Policy level group table
--
tPortSchPlcyLvlGrpTblLastChgd      OBJECT-TYPE
    SYNTAX       TimeStamp
    MAX-ACCESS   read-only
    STATUS       obsolete
    DESCRIPTION
        "tPortSchPlcyLvlGrpTblLastChgd indicates the timestamp of last change to
        the tPortSchPlcyLvlGrpTable."
    ::= { tQosTimeStampObjects 92 }

tPortSchPlcyLvlGrpTable       OBJECT-TYPE
    SYNTAX      SEQUENCE OF TPortSchPlcyLvlGrpEntry
    MAX-ACCESS  not-accessible
    STATUS      obsolete
    DESCRIPTION
        "The tPortSchPlcyLvlGrpTable has an entry for each port scheduler
         configured on this system for priority level group objects.
         
         This table is obsoleted in 13.0 release and replaced by 
         tPortSchedPolicyLevelTable."
    ::= { tSchedulerObjects 6 }

tPortSchPlcyLvlGrpEntry       OBJECT-TYPE
    SYNTAX      TPortSchPlcyLvlGrpEntry
    MAX-ACCESS  not-accessible
    STATUS      obsolete
    DESCRIPTION
        "Each row represents a particular port scheduler specific priority 
         level group information."
    AUGMENTS        { tPortSchedulerPlcyEntry }
    ::= { tPortSchPlcyLvlGrpTable 1 }

TPortSchPlcyLvlGrpEntry ::= SEQUENCE
    {
        tPortSchPlcyLvlGrpLastChanged        TimeStamp,
        tPortSchPlcyLvl1GrpName              TNamedItemOrEmpty,
        tPortSchPlcyLvl2GrpName              TNamedItemOrEmpty,
        tPortSchPlcyLvl3GrpName              TNamedItemOrEmpty,
        tPortSchPlcyLvl4GrpName              TNamedItemOrEmpty,
        tPortSchPlcyLvl5GrpName              TNamedItemOrEmpty,
        tPortSchPlcyLvl6GrpName              TNamedItemOrEmpty,
        tPortSchPlcyLvl7GrpName              TNamedItemOrEmpty,
        tPortSchPlcyLvl8GrpName              TNamedItemOrEmpty,
        tPortSchPlcyLvl1GrpWeight            TNonZeroWeight,
        tPortSchPlcyLvl2GrpWeight            TNonZeroWeight,
        tPortSchPlcyLvl3GrpWeight            TNonZeroWeight,
        tPortSchPlcyLvl4GrpWeight            TNonZeroWeight,
        tPortSchPlcyLvl5GrpWeight            TNonZeroWeight,
        tPortSchPlcyLvl6GrpWeight            TNonZeroWeight,
        tPortSchPlcyLvl7GrpWeight            TNonZeroWeight,
        tPortSchPlcyLvl8GrpWeight            TNonZeroWeight
    }

tPortSchPlcyLvlGrpLastChanged        OBJECT-TYPE
    SYNTAX      TimeStamp
    MAX-ACCESS  read-only
    STATUS      obsolete
    DESCRIPTION
        "The value of tPortSchPlcyLvlGrpLastChanged indicates the value of 
         sysUpTime at the time of the most recent management change to this
         row."
    ::= { tPortSchPlcyLvlGrpEntry 1 }

tPortSchPlcyLvl1GrpName        OBJECT-TYPE
    SYNTAX      TNamedItemOrEmpty
    MAX-ACCESS  read-create
    STATUS      obsolete
    DESCRIPTION
        "The value of tPortSchPlcyLvl1GrpName specifies the group associated
         with this scheduler policy for priority level set to '1'."
    DEFVAL      { ''H }
    ::= { tPortSchPlcyLvlGrpEntry 2 }

tPortSchPlcyLvl2GrpName        OBJECT-TYPE
    SYNTAX      TNamedItemOrEmpty
    MAX-ACCESS  read-create
    STATUS      obsolete
    DESCRIPTION
        "The value of tPortSchPlcyLvl2GrpName specifies the group associated
         with this scheduler policy for priority level set to '2'."
    DEFVAL      { ''H }
    ::= { tPortSchPlcyLvlGrpEntry 3 }

tPortSchPlcyLvl3GrpName        OBJECT-TYPE
    SYNTAX      TNamedItemOrEmpty
    MAX-ACCESS  read-create
    STATUS      obsolete
    DESCRIPTION
        "The value of tPortSchPlcyLvl3GrpName specifies the group associated
         with this scheduler policy for priority level set to '3'."
    DEFVAL      { ''H }
    ::= { tPortSchPlcyLvlGrpEntry 4 }

tPortSchPlcyLvl4GrpName        OBJECT-TYPE
    SYNTAX      TNamedItemOrEmpty
    MAX-ACCESS  read-create
    STATUS      obsolete
    DESCRIPTION
        "The value of tPortSchPlcyLvl4GrpName specifies the group associated
         with this scheduler policy for priority level set to '4'."
    DEFVAL      { ''H }
    ::= { tPortSchPlcyLvlGrpEntry 5 }

tPortSchPlcyLvl5GrpName        OBJECT-TYPE
    SYNTAX      TNamedItemOrEmpty
    MAX-ACCESS  read-create
    STATUS      obsolete
    DESCRIPTION
        "The value of tPortSchPlcyLvl5GrpName specifies the group associated
         with this scheduler policy for priority level set to '5'."
    DEFVAL      { ''H }
    ::= { tPortSchPlcyLvlGrpEntry 6 }

tPortSchPlcyLvl6GrpName        OBJECT-TYPE
    SYNTAX      TNamedItemOrEmpty
    MAX-ACCESS  read-create
    STATUS      obsolete
    DESCRIPTION
        "The value of tPortSchPlcyLvl6GrpName specifies the group associated
         with this scheduler policy for priority level set to '6'."
    DEFVAL      { ''H }
    ::= { tPortSchPlcyLvlGrpEntry 7 }

tPortSchPlcyLvl7GrpName        OBJECT-TYPE
    SYNTAX      TNamedItemOrEmpty
    MAX-ACCESS  read-create
    STATUS      obsolete
    DESCRIPTION
        "The value of tPortSchPlcyLvl7GrpName specifies the group associated
         with this scheduler policy for priority level set to '7'."
    DEFVAL      { ''H }
    ::= { tPortSchPlcyLvlGrpEntry 8 }

tPortSchPlcyLvl8GrpName        OBJECT-TYPE
    SYNTAX      TNamedItemOrEmpty
    MAX-ACCESS  read-create
    STATUS      obsolete
    DESCRIPTION
        "The value of tPortSchPlcyLvl8GrpName specifies the group associated
         with this scheduler policy for priority level set to '8'."
    DEFVAL      { ''H }
    ::= { tPortSchPlcyLvlGrpEntry 9 }

tPortSchPlcyLvl1GrpWeight        OBJECT-TYPE
    SYNTAX      TNonZeroWeight
    MAX-ACCESS  read-create
    STATUS      obsolete
    DESCRIPTION
        "The value of tPortSchPlcyLvl1GrpWeight specifies the weight 
         associated with the group tPortSchPlcyLvl1GrpName.

         An 'inconsistentValue' error is returned when this object is set to
         non-default value and tPortSchPlcyLvl1GrpName is set to a default
         value."
    DEFVAL      { 1 } 
    ::= { tPortSchPlcyLvlGrpEntry 10 }

tPortSchPlcyLvl2GrpWeight        OBJECT-TYPE
    SYNTAX      TNonZeroWeight
    MAX-ACCESS  read-create
    STATUS      obsolete
    DESCRIPTION
        "The value of tPortSchPlcyLvl2GrpWeight specifies the weight 
         associated with the group tPortSchPlcyLvl2GrpName.

         An 'inconsistentValue' error is returned when this object is set to
         non-default value and tPortSchPlcyLvl2GrpName is set to a default
         value."
    DEFVAL      { 1 } 
    ::= { tPortSchPlcyLvlGrpEntry 11 }

tPortSchPlcyLvl3GrpWeight        OBJECT-TYPE
    SYNTAX      TNonZeroWeight
    MAX-ACCESS  read-create
    STATUS      obsolete
    DESCRIPTION
        "The value of tPortSchPlcyLvl1GrpWeight specifies the weight 
         associated with the group tPortSchPlcyLvl3GrpName.

         An 'inconsistentValue' error is returned when this object is set to
         non-default value and tPortSchPlcyLvl3GrpName is set to a default
         value."
    DEFVAL      { 1 } 
    ::= { tPortSchPlcyLvlGrpEntry 12 }

tPortSchPlcyLvl4GrpWeight        OBJECT-TYPE
    SYNTAX      TNonZeroWeight
    MAX-ACCESS  read-create
    STATUS      obsolete
    DESCRIPTION
        "The value of tPortSchPlcyLvl4GrpWeight specifies the weight 
         associated with the group tPortSchPlcyLvl4GrpName.

         An 'inconsistentValue' error is returned when this object is set to
         non-default value and tPortSchPlcyLvl4GrpName is set to a default
         value."
    DEFVAL      { 1 } 
    ::= { tPortSchPlcyLvlGrpEntry 13 }

tPortSchPlcyLvl5GrpWeight        OBJECT-TYPE
    SYNTAX      TNonZeroWeight
    MAX-ACCESS  read-create
    STATUS      obsolete
    DESCRIPTION
        "The value of tPortSchPlcyLvl5GrpWeight specifies the weight 
         associated with the group tPortSchPlcyLvl5GrpName.

         An 'inconsistentValue' error is returned when this object is set to
         non-default value and tPortSchPlcyLvl5GrpName is set to a default
         value."
    DEFVAL      { 1 } 
    ::= { tPortSchPlcyLvlGrpEntry 14 }

tPortSchPlcyLvl6GrpWeight        OBJECT-TYPE
    SYNTAX      TNonZeroWeight
    MAX-ACCESS  read-create
    STATUS      obsolete
    DESCRIPTION
        "The value of tPortSchPlcyLvl6GrpWeight specifies the weight 
         associated with the group tPortSchPlcyLvl6GrpName.

         An 'inconsistentValue' error is returned when this object is set to
         non-default value and tPortSchPlcyLvl6GrpName is set to a default
         value."
    DEFVAL      { 1 } 
    ::= { tPortSchPlcyLvlGrpEntry 15 }

tPortSchPlcyLvl7GrpWeight        OBJECT-TYPE
    SYNTAX      TNonZeroWeight
    MAX-ACCESS  read-create
    STATUS      obsolete
    DESCRIPTION
        "The value of tPortSchPlcyLvl7GrpWeight specifies the weight 
         associated with the group tPortSchPlcyLvl7GrpName.

         An 'inconsistentValue' error is returned when this object is set to
         non-default value and tPortSchPlcyLvl7GrpName is set to a default
         value."
    DEFVAL      { 1 } 
    ::= { tPortSchPlcyLvlGrpEntry 16 }

tPortSchPlcyLvl8GrpWeight        OBJECT-TYPE
    SYNTAX      TNonZeroWeight
    MAX-ACCESS  read-create
    STATUS      obsolete
    DESCRIPTION
        "The value of tPortSchPlcyLvl8GrpWeight specifies the weight 
         associated with the group tPortSchPlcyLvl8GrpName.

         An 'inconsistentValue' error is returned when this object is set to
         non-default value and tPortSchPlcyLvl8GrpName is set to a default
         value."
    DEFVAL      { 1 } 
    ::= { tPortSchPlcyLvlGrpEntry 17 }
    
--
--  HSMDA WRR Policy table
--
tHsmdaWrrPolicyTblLastChgd      OBJECT-TYPE
    SYNTAX       TimeStamp
    MAX-ACCESS   read-only
    STATUS       current
    DESCRIPTION
        "The value of tHsmdaWrrPolicyTblLastChgd indicates the timestamp of last
         change to the tHsmdaWrrPolicyTable."
    ::= { tQosTimeStampObjects 93 }

tHsmdaWrrPolicyTable       OBJECT-TYPE
    SYNTAX      SEQUENCE OF THsmdaWrrPolicyEntry
    MAX-ACCESS  not-accessible
    STATUS      current
    DESCRIPTION
        "The tHsmdaWrrPolicyTable contains the information of the 
         Weighted Round Robin (WRR) policies configured on HSDMA queues."
    ::= { tWrrObjects 1 }

tHsmdaWrrPolicyEntry       OBJECT-TYPE
    SYNTAX      THsmdaWrrPolicyEntry
    MAX-ACCESS  not-accessible
    STATUS      current
    DESCRIPTION
        "Each row in tHsmdaWrrPolicyEntry represents a HSMDA Weighted 
         Round Robin (WRR) policy specified by tHsmdaWrrPolicyName."
    INDEX { tHsmdaWrrPolicyName }
    ::= { tHsmdaWrrPolicyTable 1 }

THsmdaWrrPolicyEntry ::= SEQUENCE
    {
        tHsmdaWrrPolicyName                 TNamedItem,
        tHsmdaWrrPolicyRowStatus            RowStatus,
        tHsmdaWrrPolicyLastChanged          TimeStamp,
        tHsmdaWrrPolicyDescription          TItemDescription,
        tHsmdaWrrPolicyIncludeQueues        THsmdaPolicyIncludeQueues,
        tHsmdaWrrPolicySchedUsingClass      THsmdaPolicyScheduleClass,
        tHsmdaWrrPolicyAggWeightAtClass     THsmdaWeightClass
    }

tHsmdaWrrPolicyName        OBJECT-TYPE
    SYNTAX      TNamedItem
    MAX-ACCESS  not-accessible
    STATUS      current
    DESCRIPTION
        "The value of tHsmdaWrrPolicyName specifies the name of the Weighted 
         Round Robin (WRR) policy associated with this HSDMA queue."
    ::= { tHsmdaWrrPolicyEntry 1 }

tHsmdaWrrPolicyRowStatus OBJECT-TYPE
    SYNTAX      RowStatus
    MAX-ACCESS  read-create
    STATUS      current
    DESCRIPTION
        "The value of tHsmdaWrrPolicyRowStatus is used for the creation
         and deletion of entries in the tHsmdaWrrPolicyTable."
    ::= { tHsmdaWrrPolicyEntry 2 }

tHsmdaWrrPolicyLastChanged OBJECT-TYPE
    SYNTAX       TimeStamp
    MAX-ACCESS   read-only
    STATUS       current
    DESCRIPTION  
        "The value of tHsmdaWrrPolicyLastChanged indicates the sysUpTime for the
         last change to this row."
    ::= { tHsmdaWrrPolicyEntry 3 }

tHsmdaWrrPolicyDescription        OBJECT-TYPE
    SYNTAX      TItemDescription
    MAX-ACCESS  read-create
    STATUS      current
    DESCRIPTION
        "The value of tHsmdaWrrPolicyDescription specifies the description of
         the Weighted Round Robin (WRR) policy on this HSMDA queue."
    ::= { tHsmdaWrrPolicyEntry 4 }

tHsmdaWrrPolicyIncludeQueues        OBJECT-TYPE
    SYNTAX      THsmdaPolicyIncludeQueues
    MAX-ACCESS  read-create
    STATUS      current
    DESCRIPTION
        "The value of tHsmdaWrrPolicyIncludeQueues specifies the queues 
         that can be scheduled in the same class in a Weighted Round Robin (WRR)
         fashion within the HSMDA scheduler."
    DEFVAL      { q1to2 }
    ::= { tHsmdaWrrPolicyEntry 5 }

tHsmdaWrrPolicySchedUsingClass        OBJECT-TYPE
    SYNTAX      THsmdaPolicyScheduleClass
    MAX-ACCESS  read-create
    STATUS      current
    DESCRIPTION
        "The value of tHsmdaWrrPolicySchedUsingClass specifies which class
         to schedule the queues specified by tHsmdaWrrPolicyIncludeQueues within
         the HSMDA scheduler."
    DEFVAL      { 1 }
    ::= { tHsmdaWrrPolicyEntry 6 }

tHsmdaWrrPolicyAggWeightAtClass        OBJECT-TYPE
    SYNTAX      THsmdaWeightClass
    MAX-ACCESS  read-create
    STATUS      current
    DESCRIPTION
        "The value of tHsmdaWrrPolicyAggWeightAtClass specifies the weight 
         assigned to the group of queues specified by 
         tHsmdaWrrPolicyIncludeQueues within the HSMDA scheduler."
    DEFVAL      { class1 }
    ::= { tHsmdaWrrPolicyEntry 7 }

--
-- network ingress fc table
--
tNetworkIngressFCTableLstChanged      OBJECT-TYPE
    SYNTAX       TimeStamp
    MAX-ACCESS   read-only
    STATUS       current
    DESCRIPTION
        "The value of tNetworkIngressFCTableLstChanged indicates the timestamp 
         of last change to the tNetworkIngressFCTable."
    ::= { tQosTimeStampObjects 101 }

tNetworkIngressFCTable OBJECT-TYPE
    SYNTAX       SEQUENCE OF TNetworkIngressFCEntry
    MAX-ACCESS   not-accessible
    STATUS       current
    DESCRIPTION
        "Information about all network policies' ingress FC traffic
         disposition."
    ::= { tNetworkObjects 8 }

tNetworkIngressFCEntry OBJECT-TYPE
    SYNTAX       TNetworkIngressFCEntry
    MAX-ACCESS   not-accessible
    STATUS       current
    DESCRIPTION
        "Information about a particular network policy's ingress
         per-forwarding-class traffic disposition.

         Entries are created/deleted as an action of creating/deleting
         a row in the tNetworkPolicyTable.

         There is no StorageType object, entries have a presumed
         StorageType of nonVolatile."
    INDEX { tNetworkPolicyIndex, tNetworkIngressFCName }
    ::= { tNetworkIngressFCTable 1 }

TNetworkIngressFCEntry ::= SEQUENCE
    {
        tNetworkIngressFCName              TFCName,
        tNetworkIngressFCLastChanged       TimeStamp,
        tNetworkIngressFCMultiCastPlcr     TIngPolicerIdOrNone,
        tNetworkIngressFCUniCastPlcr       TIngPolicerIdOrNone,
        tNetworkIngressFCBroadCastPlcr     TIngPolicerIdOrNone,
        tNetworkIngressFCUnknownPlcr       TIngPolicerIdOrNone
    }

tNetworkIngressFCName OBJECT-TYPE
    SYNTAX       TFCName
    MAX-ACCESS   not-accessible
    STATUS       current
    DESCRIPTION
        "The value of tNetworkIngressFCName specifies the name of the forwarding
         class (FC)."
    ::= { tNetworkIngressFCEntry 1 }

tNetworkIngressFCLastChanged OBJECT-TYPE
    SYNTAX       TimeStamp
    MAX-ACCESS   read-only
    STATUS       current
    DESCRIPTION
        "The value of tNetworkIngressFCLastChanged indicates the sysUpTime 
         for the last change to this entry."
    ::= { tNetworkIngressFCEntry 2 }

tNetworkIngressFCMultiCastPlcr OBJECT-TYPE
    SYNTAX       TIngPolicerIdOrNone
    MAX-ACCESS   read-write
    STATUS       current
    DESCRIPTION
        "The value of tNetworkIngressFCMultiCastPlcr specifies the policer to be
         used for multicast traffic for this forwarding-class."
    DEFVAL      { 0 }
    ::= { tNetworkIngressFCEntry 3 }

tNetworkIngressFCUniCastPlcr OBJECT-TYPE
    SYNTAX       TIngPolicerIdOrNone
    MAX-ACCESS   read-write
    STATUS       current
    DESCRIPTION
        "The value of tNetworkIngressFCUniCastPlcr specifies the policer to be
         used for unicast traffic for this forwarding-class."
    DEFVAL      { 0 }
    ::= { tNetworkIngressFCEntry 4 }

tNetworkIngressFCBroadCastPlcr OBJECT-TYPE
    SYNTAX       TIngPolicerIdOrNone
    MAX-ACCESS   read-write
    STATUS       current
    DESCRIPTION
        "The value of tNetworkIngressFCBroadCastPlcr specifies the policer to be
         used for broadcast traffic for this forwarding-class."
    DEFVAL      { 0 }
    ::= { tNetworkIngressFCEntry 5 }

tNetworkIngressFCUnknownPlcr OBJECT-TYPE
    SYNTAX       TIngPolicerIdOrNone
    MAX-ACCESS   read-write
    STATUS       current
    DESCRIPTION
        "The value of tNetworkIngressFCUnknownPlcr specifies the policer to be
         used for unknown traffic for this forwarding-class."
    DEFVAL      { 0 }
    ::= { tNetworkIngressFCEntry 6 }

--
-- network-egress policy dscp table
--

tNetworkEgrDSCPTableLastChanged      OBJECT-TYPE
    SYNTAX       TimeStamp
    MAX-ACCESS   read-only
    STATUS       current
    DESCRIPTION
        "The value of tNetworkEgrDSCPTableLastChanged indicates the timestamp 
         of last change to the tNetworkEgressDSCPTable."
    ::= { tQosTimeStampObjects 102 }

tNetworkEgressDSCPTable OBJECT-TYPE
    SYNTAX       SEQUENCE OF TNetworkEgressDSCPEntry
    MAX-ACCESS   not-accessible
    STATUS       current
    DESCRIPTION
        "tNetworkEgressDSCPTable lists all DSCP entries for all network 
         egress policies."
    ::= { tNetworkObjects 9 }

tNetworkEgressDSCPEntry OBJECT-TYPE
    SYNTAX       TNetworkEgressDSCPEntry
    MAX-ACCESS   not-accessible
    STATUS       current
    DESCRIPTION
        "The tNetworkEgressDSCPEntry defines a particular DSCP entry for a 
         network egress policy.

         Some default entries are created by the agent for the default network
         policy (1). These cannot be deleted or modified. Other entries are 
         created/deleted by user.

         In the event that one policy has multiple entries, and
         the tNetworkEgressDSCP values are the same, only one queue
         will be created (the queue for the lexicographically
         first tNetworkEgressDSCP)."
    INDEX { tNetworkPolicyIndex, tNetworkEgressDSCP }
    ::= { tNetworkEgressDSCPTable 1 }

TNetworkEgressDSCPEntry ::= SEQUENCE
    {
        tNetworkEgressDSCP                    TDSCPName,
        tNetworkEgressDSCPRowStatus           RowStatus,
        tNetworkEgressDSCPLastChanged         TimeStamp,
        tNetworkEgressDSCPFC                  TFCName, 
        tNetworkEgressDSCPProfile             TProfile
    }

tNetworkEgressDSCP OBJECT-TYPE
    SYNTAX       TDSCPName
    MAX-ACCESS   not-accessible
    STATUS       current
    DESCRIPTION
        "The value of tNetworkEgressDSCP indicates the DSCP value for
         which the mapping is done. It is used as a secondary index for
         tNetworkEgressDSCPTable."
    ::= { tNetworkEgressDSCPEntry 1 }

tNetworkEgressDSCPRowStatus OBJECT-TYPE
    SYNTAX       RowStatus
    MAX-ACCESS   read-create
    STATUS       current
    DESCRIPTION
        "The value of tNetworkEgressDSCPRowStatus is used for the creation and
         the deletion of rows in this table.

         The value of tNetworkEgressDSCPProfile must be specified when row 
         is created."
    ::= { tNetworkEgressDSCPEntry 2 }

tNetworkEgressDSCPLastChanged OBJECT-TYPE
    SYNTAX       TimeStamp
    MAX-ACCESS   read-only
    STATUS       current
    DESCRIPTION
        "The value of tNetworkEgressDSCPLastChanged indicates the sysUpTime at
         the time of the most recent management-initiated change to this table
         row."
    ::= { tNetworkEgressDSCPEntry 3 }

tNetworkEgressDSCPFC OBJECT-TYPE
    SYNTAX       TFCName
    MAX-ACCESS   read-create
    STATUS       current
    DESCRIPTION
        "The value of tNetworkEgressDSCPFC will overwrite the
         forwarding class derived from ingress. The new forwarding class is
         used for egress remarking and queue mapping decisions.

         There is no DEFVAL for tNetworkEgressDSCPFC. It must be set at the
         time of row creation."
    ::= { tNetworkEgressDSCPEntry 4 }

tNetworkEgressDSCPProfile OBJECT-TYPE
    SYNTAX       TProfile
    MAX-ACCESS   read-create
    STATUS       current
    DESCRIPTION
        "The value of tNetworkEgressDSCPProfile specifies the egress 
         classification rule that will overwrite the profile of the
         packet derived from the ingress. The new profile value is used for
         egress remarking and queue congestion behavior.
         
         There is no DEFVAL for tNetworkEgressDSCPProfile. It must be 
         set at the time of row creation."
    ::= { tNetworkEgressDSCPEntry 5 }

--
-- network-egress policy precedence table
--

tNetworkEgrPrecTableLastChanged      OBJECT-TYPE
    SYNTAX       TimeStamp
    MAX-ACCESS   read-only
    STATUS       current
    DESCRIPTION
        "The value of tNetworkEgrPrecTableLastChanged indicates the timestamp 
         of last change to the tNetworkEgressPrecTable."
    ::= { tQosTimeStampObjects 103 }

tNetworkEgressPrecTable OBJECT-TYPE
    SYNTAX       SEQUENCE OF TNetworkEgressPrecEntry
    MAX-ACCESS   not-accessible
    STATUS       current
    DESCRIPTION
        "The tNetworkEgressPrecTable table maintains the mapping of a particular
         precedence value into a forwarding class"
    ::= { tNetworkObjects 10 }

tNetworkEgressPrecEntry OBJECT-TYPE
    SYNTAX       TNetworkEgressPrecEntry
    MAX-ACCESS   not-accessible
    STATUS       current
    DESCRIPTION
        "The tNetworkEgressPrecEntry defines a particular network egress 
         policy's IP precedence values to forwarding class mappings.

         Entries are created and deleted by user."
    INDEX { tNetworkPolicyIndex, tNetworkEgressPrecValue }
    ::= { tNetworkEgressPrecTable 1 }

TNetworkEgressPrecEntry ::= SEQUENCE
    {
        tNetworkEgressPrecValue               TPrecValue,
        tNetworkEgressPrecRowStatus           RowStatus,
        tNetworkEgressPrecLastChanged         TimeStamp,
        tNetworkEgressPrecFC                  TFCName, 
        tNetworkEgressPrecProfile             TProfile
    }

tNetworkEgressPrecValue OBJECT-TYPE
    SYNTAX       TPrecValue
    MAX-ACCESS   not-accessible
    STATUS       current
    DESCRIPTION
        "The value of tNetworkEgressPrecValue indicates the precedence value
         for which the mapping is done. It is used as a secondary index for
         tNetworkEgressPrecTable."
    ::= { tNetworkEgressPrecEntry 1 }

tNetworkEgressPrecRowStatus OBJECT-TYPE
    SYNTAX       RowStatus
    MAX-ACCESS   read-create
    STATUS       current
    DESCRIPTION
        "The value of tNetworkEgressPrecRowStatus is used for the creation and
         the deletion of rows in this table.
         
         The value of tNetworkEgressPrecProfile must be specified when row 
         is created."
    ::= { tNetworkEgressPrecEntry 2 }

tNetworkEgressPrecLastChanged OBJECT-TYPE
    SYNTAX       TimeStamp
    MAX-ACCESS   read-only
    STATUS       current
    DESCRIPTION
        "The value of tNetworkEgressPrecLastChanged indicates the sysUpTime
         at the time of the most recent management-initiated change to this
         table row."
    ::= { tNetworkEgressPrecEntry 3 }

tNetworkEgressPrecFC OBJECT-TYPE
    SYNTAX       TFCName
    MAX-ACCESS   read-create
    STATUS       current
    DESCRIPTION
        "The value of tNetworkEgressPrecFC will overwrite the
         forwarding class derived from egress. The new forwarding class is
         used for egress remarking and queue mapping decisions.

         There is no DEFVAL for tNetworkEgressPrecFC. It must be set at the
         time of row creation."
    ::= { tNetworkEgressPrecEntry 4 }

tNetworkEgressPrecProfile OBJECT-TYPE
    SYNTAX       TProfile
    MAX-ACCESS   read-create
    STATUS       current
    DESCRIPTION
        "The value of tNetworkEgressPrecProfile specifies the
         egress classification rule that will overwrite the profile of the
         packet derived from the egress. The new profile value is used for
         egress remarking and queue congestion behavior.

         There is no DEFVAL for tNetworkEgressPrecProfile. It must be 
         set at the time of row creation."
    ::= { tNetworkEgressPrecEntry 5 }

--
-- Network Policy Ingress IP Criteria
--
tNetworkIngIPCritTableLstChanged    OBJECT-TYPE
    SYNTAX       TimeStamp
    MAX-ACCESS   read-only
    STATUS       current
    DESCRIPTION
        "The value of tNetworkIngIPCritTableLstChanged indicates the timestamp 
         of last change to the tNetworkIngIPCritTable."
    ::= { tQosTimeStampObjects 104 }

tNetworkIngIPCritTable OBJECT-TYPE
    SYNTAX      SEQUENCE OF TNetworkIngIPCritEntry
    MAX-ACCESS  not-accessible
    STATUS      current
    DESCRIPTION
        "The value of tNetworkIngIPCritTable maintains the entries for matching
         of IP/IPv6 packets on ingress network Qos policy."
    ::= { tNetworkObjects 11 }

tNetworkIngIPCritEntry    OBJECT-TYPE
    SYNTAX      TNetworkIngIPCritEntry
    MAX-ACCESS  not-accessible
    STATUS      current
    DESCRIPTION
        "Information about a particular ingress IP/IPv6 matching criteria entry.

         Entries are created and deleted by user. They have a presumed
         StorageType of nonVolatile."
    INDEX { tNetworkPolicyIndex, tNetworkIngIPCritType, tNetworkIngIPCritIndex }
    ::= { tNetworkIngIPCritTable 1}

TNetworkIngIPCritEntry ::= SEQUENCE
    {
        tNetworkIngIPCritType               InetAddressType,
        tNetworkIngIPCritIndex              Unsigned32,
        tNetworkIngIPCritRowStatus          RowStatus,
        tNetworkIngIPCritLastChanged        TimeStamp,
        tNetworkIngIPCritDescription        TItemDescription,
        tNetworkIngIPCritActionFC           TFCNameOrEmpty,
        tNetworkIngIPCritActionProfile      TProfileOrNone,
        tNetworkIngIPCritSrcIpAddrType      InetAddressType,
        tNetworkIngIPCritSrcIpAddr          InetAddress,
        tNetworkIngIPCritSrcIpMask          InetAddressPrefixLength,
        tNetworkIngIPCritSrcIpFullMask      InetAddress,
        tNetworkIngIPCritDstIpAddrType      InetAddressType,
        tNetworkIngIPCritDstIpAddr          InetAddress,
        tNetworkIngIPCritDstIpMask          InetAddressPrefixLength,
        tNetworkIngIPCritDstIpFullMask      InetAddress,
        tNetworkIngIPCritProtocol           TIpProtocol,
        tNetworkIngIPCritSrcPortValue1      TTcpUdpPort,
        tNetworkIngIPCritSrcPortValue2      TTcpUdpPort,
        tNetworkIngIPCritSrcPortOperator    TTcpUdpPortOperator,
        tNetworkIngIPCritDstPortValue1      TTcpUdpPort,
        tNetworkIngIPCritDstPortValue2      TTcpUdpPort,
        tNetworkIngIPCritDstPortOperator    TTcpUdpPortOperator,
        tNetworkIngIPCritDSCP               TDSCPNameOrEmpty,
        tNetworkIngIPCritFragment           INTEGER
    }

tNetworkIngIPCritType               OBJECT-TYPE
    SYNTAX       InetAddressType { ipv4(1), ipv6(2) }
    MAX-ACCESS   not-accessible
    STATUS       current
    DESCRIPTION
        "The value of tNetworkIngIPCritType specifies the address-type this
         entry should match against."
    ::= { tNetworkIngIPCritEntry 1 }

tNetworkIngIPCritIndex              OBJECT-TYPE
    SYNTAX      Unsigned32 (1..65535)
    MAX-ACCESS  not-accessible
    STATUS      current
    DESCRIPTION
        "The value of tNetworkIngIPCritIndex specifies the IP criteria entry
         index for network ingress Qos policy."
    ::= { tNetworkIngIPCritEntry 2 }

tNetworkIngIPCritRowStatus          OBJECT-TYPE
    SYNTAX      RowStatus
    MAX-ACCESS  read-create
    STATUS      current
    DESCRIPTION
        "The value of tNetworkIngIPCritRowStatus is used for the creation and
         deletion of IP criteria entries for network ingress Qos policy."
    ::= { tNetworkIngIPCritEntry 3 }

tNetworkIngIPCritLastChanged        OBJECT-TYPE
    SYNTAX      TimeStamp
    MAX-ACCESS  read-only
    STATUS      current
    DESCRIPTION
        "The value of tNetworkIngIPCritLastChanged indicates the sysUpTime at
         the time of the last modification of this entry.

         If no changes were made to the entry since the last re-initialization
         of the local network management subsystem, then this object contains
         a zero value."
    ::= { tNetworkIngIPCritEntry 4 }

tNetworkIngIPCritDescription        OBJECT-TYPE
    SYNTAX      TItemDescription
    MAX-ACCESS  read-create
    STATUS      current
    DESCRIPTION
        "The value of tNetworkIngIPCritDescription specifies a description of
         IP criteria entry for network ingress Qos policy."
    DEFVAL { ''H }
    ::= { tNetworkIngIPCritEntry 5 }

tNetworkIngIPCritActionFC           OBJECT-TYPE
    SYNTAX       TFCNameOrEmpty
    MAX-ACCESS   read-create
    STATUS       current
    DESCRIPTION
        "The value of tNetworkIngIPCritActionFC specifies the forwarding class
         to be used to classify all the traffic that matches the specific IP
         criteria.

         The value ''H indicates that the FC is derived from ingress
         classification and profiling functions."
    DEFVAL { ''H }
    ::= { tNetworkIngIPCritEntry 6 }

tNetworkIngIPCritActionProfile      OBJECT-TYPE
    SYNTAX       TProfileOrNone
    MAX-ACCESS   read-create
    STATUS       current
    DESCRIPTION
       "The value of tNetworkIngIPCritActionProfile specifies the profile of
        the packets associated with the forwarding class specified by 
        tNetworkIngIPCritActionFC."
    DEFVAL { none }
    ::= { tNetworkIngIPCritEntry 7 }

tNetworkIngIPCritSrcIpAddrType      OBJECT-TYPE
    SYNTAX       InetAddressType
    MAX-ACCESS   read-create
    STATUS       current
    DESCRIPTION
        "The value of tNetworkIngIPCritSrcIpAddrType specifies the address type
         of tNetworkIngIPCritSrcIpAddr.

         If the value of this object is not 'unknown (0)', it must have the same
         value as tNetworkIngIPCritType."
    DEFVAL { unknown }
    ::= { tNetworkIngIPCritEntry 8 }

tNetworkIngIPCritSrcIpAddr          OBJECT-TYPE
    SYNTAX       InetAddress (SIZE(0|4|16))
    MAX-ACCESS   read-create
    STATUS       current
    DESCRIPTION
        "The value of tNetworkIngIPCritSrcIpAddr specifies the IP address to
         match with source-IP of the packet."
    DEFVAL { ''H }
    ::= { tNetworkIngIPCritEntry 9 }

tNetworkIngIPCritSrcIpMask          OBJECT-TYPE
    SYNTAX       InetAddressPrefixLength
    MAX-ACCESS   read-create
    STATUS       current
    DESCRIPTION
        "The value of tNetworkIngIPCritSrcIpMask specifies the mask value for
         this policy IP criteria entry. The mask is ANDed with the received
         source IP-address to match the tNetworkIngIPCritSrcIpAddr.

         If the value of tNetworkIngIPCritSrcIpMask is zero and the value of
         tNetworkIngIPCritSrcIpFullMask is non-zero, then the value of
         tNetworkIngIPCritSrcIpFullMask is used as mask.

         If both tNetworkIngIPCritSrcIpMask and tNetworkIngIPCritSrcIpFullMask
         are set to 0, no matching is done on the source-IP address.

         If a value is specified for this object, then the value of the
         tNetworkIngIPCritSrcIpFullMask will be set to reflect this same mask."
    DEFVAL { 0 }
    ::= { tNetworkIngIPCritEntry 10 }

tNetworkIngIPCritSrcIpFullMask      OBJECT-TYPE
    SYNTAX      InetAddress (SIZE(0|4|16))
    MAX-ACCESS  read-create
    STATUS      current
    DESCRIPTION
        "The value of tNetworkIngIPCritSrcIpFullMask specifies the mask value
         for this policy IP criteria entry. The mask is ANDed with the received
         source IP-address to match the tNetworkIngIPCritSrcIpAddr.

         If the value of tNetworkIngIPCritSrcIpMask is zero and the value of
         tNetworkIngIPCritSrcIpFullMask is non-zero, then the value of
         tNetworkIngIPCritSrcIpFullMask is used as mask.

         If both tNetworkIngIPCritSrcIpMask and tNetworkIngIPCritSrcIpFullMask
         are set to 0, no matching is done on the Source-IP address.

         If a regular mask is specified for tNetworkIngIPCritSrcIpFullMask,
         then the value of tNetworkIngIPCritSrcIpMask will be changed to
         reflect this value."
    DEFVAL { ''H }
    ::= { tNetworkIngIPCritEntry 11 }

tNetworkIngIPCritDstIpAddrType      OBJECT-TYPE
    SYNTAX       InetAddressType
    MAX-ACCESS   read-create
    STATUS       current
    DESCRIPTION
        "The value of tNetworkIngIPCritDstIpAddrType specifies the address type
         of tNetworkIngIPCritDstIpAddr.

         If the value of this object is not 'unknown (0)', it must have the same
         value as tNetworkIngIPCritType."
    DEFVAL { unknown }
    ::= { tNetworkIngIPCritEntry 12 }

tNetworkIngIPCritDstIpAddr          OBJECT-TYPE
    SYNTAX       InetAddress (SIZE(0|4|16))
    MAX-ACCESS   read-create
    STATUS       current
    DESCRIPTION
        "The value of tNetworkIngIPCritDstIpAddr specifies the IP address to
         match with destination-IP of the packet."
    DEFVAL { ''H }
    ::= { tNetworkIngIPCritEntry 13 }

tNetworkIngIPCritDstIpMask          OBJECT-TYPE
    SYNTAX       InetAddressPrefixLength
    MAX-ACCESS   read-create
    STATUS       current
    DESCRIPTION
        "The value of tNetworkIngIPCritDstIpMask specifies the mask value for
         this policy IP criteria entry. The mask is ANDed with the received
         destination IP-address to match the tNetworkIngIPCritDstIpAddr.

         If the value of tNetworkIngIPCritDstIpMask is zero and the value of
         tNetworkIngIPCritDstIpFullMask is non-zero, then the value of
         tNetworkIngIPCritDstIpFullMask is used as mask.

         If both tNetworkIngIPCritDstIpMask and tNetworkIngIPCritDstIpFullMask
         are set to 0, no matching is done on the source-IP address.

         If a value is specified for this object, then the value of the
         tNetworkIngIPCritDstIpFullMask will be set to reflect this same mask."
    DEFVAL { 0 }
    ::= { tNetworkIngIPCritEntry 14 }

tNetworkIngIPCritDstIpFullMask      OBJECT-TYPE
    SYNTAX      InetAddress (SIZE(0|4|16))
    MAX-ACCESS  read-create
    STATUS      current
    DESCRIPTION
        "The value of tNetworkIngIPCritDstIpFullMask specifies the mask value
         for this policy IP criteria entry. The mask is ANDed with the received
         destiantion IP-address to match the tNetworkIngIPCritDstIpAddr.

         If the value of tNetworkIngIPCritDstIpMask is zero and the value of
         tNetworkIngIPCritDstIpFullMask is non-zero, then the value of
         tNetworkIngIPCritDstIpFullMask is used as mask.

         If both tNetworkIngIPCritDstIpMask and tNetworkIngIPCritDstIpFullMask
         are set to 0, no matching is done on the Source-IP address.

         If a regular mask is specified for tNetworkIngIPCritDstIpFullMask,
         then the value of tNetworkIngIPCritDstIpMask will be changed to
         reflect this value."
    DEFVAL { ''H }
    ::= { tNetworkIngIPCritEntry 15 }

tNetworkIngIPCritProtocol           OBJECT-TYPE
    SYNTAX       TIpProtocol
    MAX-ACCESS   read-create
    STATUS       current
    DESCRIPTION
        "The value of tNetworkIngIPCritProtocol specifies the IP protocol to
         match.

         The value '-1' is used to disable matching by IP protocol."
    DEFVAL { -1 }
    ::= { tNetworkIngIPCritEntry 16 }

tNetworkIngIPCritSrcPortValue1      OBJECT-TYPE
    SYNTAX       TTcpUdpPort
    MAX-ACCESS   read-create
    STATUS       current
    DESCRIPTION
        "The value of tNetworkIngIPCritSrcPortValue1 specifies the first TCP/UDP
         source port value. The value of this object is used according to the
         value of tNetworkIngIPCritSrcPortOperator."
    DEFVAL { 0 }
    ::= { tNetworkIngIPCritEntry 17 }

tNetworkIngIPCritSrcPortValue2      OBJECT-TYPE
    SYNTAX       TTcpUdpPort
    MAX-ACCESS   read-create
    STATUS       current
    DESCRIPTION
        "The value of tNetworkIngIPCritSrcPortValue2 specifies the second
         TCP/UDP source port value. The value of this object is used according
         to the value of tNetworkIngIPCritSrcPortOperator."
    DEFVAL { 0 }
    ::= { tNetworkIngIPCritEntry 18 }

tNetworkIngIPCritSrcPortOperator    OBJECT-TYPE
    SYNTAX       TTcpUdpPortOperator
    MAX-ACCESS   read-create
    STATUS       current
    DESCRIPTION
        "The value of tNetworkIngIPCritSrcPortOperator specifies the manner in
         which tNetworkIngIPCritSrcPortValue1 and tNetworkIngIPCritSrcPortValue2
         are to be used."
    DEFVAL { none }
    ::= { tNetworkIngIPCritEntry 19 }

tNetworkIngIPCritDstPortValue1      OBJECT-TYPE
    SYNTAX       TTcpUdpPort
    MAX-ACCESS   read-create
    STATUS       current
    DESCRIPTION
        "The value of tNetworkIngIPCritDstPortValue1 specifies the first TCP/UDP
         destination port value. The value of this object is used according to
         the value of tNetworkIngIPCritDstPortOperator."
    DEFVAL { 0 }
    ::= { tNetworkIngIPCritEntry 20 }

tNetworkIngIPCritDstPortValue2      OBJECT-TYPE
    SYNTAX       TTcpUdpPort
    MAX-ACCESS   read-create
    STATUS       current
    DESCRIPTION
        "The value of tNetworkIngIPCritDstPortValue2 specifies the second
         TCP/UDP destination port value. The value of this object is used
         according to the value of tNetworkIngIPCritDstPortOperator."
    DEFVAL { 0 }
    ::= { tNetworkIngIPCritEntry 21 }

tNetworkIngIPCritDstPortOperator    OBJECT-TYPE
    SYNTAX       TTcpUdpPortOperator
    MAX-ACCESS   read-create
    STATUS       current
    DESCRIPTION
        "The value of tNetworkIngIPCritDstPortOperator specifies the manner in
         which tNetworkIngIPCritDstPortValue1 and tNetworkIngIPCritDstPortValue2
         are to be used."
    DEFVAL { none }
    ::= { tNetworkIngIPCritEntry 22 }

tNetworkIngIPCritDSCP               OBJECT-TYPE
    SYNTAX       TDSCPNameOrEmpty
    MAX-ACCESS   read-create
    STATUS       current
    DESCRIPTION
        "The value of tNetworkIngIPCritDSCP specifies the DSCP value to match
         in the packet"
    DEFVAL { ''H }
    ::= { tNetworkIngIPCritEntry 23 }

tNetworkIngIPCritFragment           OBJECT-TYPE
    SYNTAX INTEGER {
               off          (1),
               false        (2),
               true         (3),
               firstOnly    (4),
               nonFirstOnly (5)
           }
    MAX-ACCESS   read-create
    STATUS       current
    DESCRIPTION
        "The value of tNetworkIngIPCritFragment specifies matching criteria to
         be used for fragmented or non-fragmented packets.

           off          (1) - match all packets regardless of fragmented or not.
           false        (2) - match all non-fragmented packets.
           true         (3) - match all fragmented packets.
           firstOnly    (4) - match only the initial packet fragment.
           nonFirstOnly (5) - match non-initial packet fragment.
            
         The values 'firstOnly (4)' and 'nonFirstOnly (5)' are supported only
         when the value of tNetworkIngIPCritType is set to 'ipv6 (2)'."
    DEFVAL { off }
    ::= { tNetworkIngIPCritEntry 24 }



-- ----------------------------------------------------------------------------
--  Port Scheduler Policy Level Table
-- ----------------------------------------------------------------------------
tPortSchedPolicyLevelTblLastChgd    OBJECT-TYPE
    SYNTAX      TimeStamp
    MAX-ACCESS  read-only
    STATUS      current
    DESCRIPTION
        "The value of tPortSchedPolicyLevelTblLastChgd indicates the sysUpTime
         at the time of the last modification to tPortSchedPolicyLevelTable.

         If no changes were made to the table since the last re-initialization
         of the local network management subsystem, this object contains the
         value zero."
    ::= { tQosTimeStampObjects 108 }

tPortSchedPolicyLevelTable          OBJECT-TYPE
    SYNTAX      SEQUENCE OF TPortSchedPolicyLevelEntry
    MAX-ACCESS  not-accessible
    STATUS      current
    DESCRIPTION
        "The value of tPortSchedPolicyLevelTable has an entry for each port
         scheduler policy priority level configured on this system."
    ::= { tSchedulerObjects 8 }

tPortSchedPolicyLevelEntry          OBJECT-TYPE
    SYNTAX      TPortSchedPolicyLevelEntry
    MAX-ACCESS  not-accessible
    STATUS      current
    DESCRIPTION
        "the value of tPortSchedPolicyLevelEntry represents row entry for
         particular port scheduler policy priority level.

         Entries in tPortSchedPolicyLevelTable are created when entries are
         created in tPortSchedulerPlcyTable."
    INDEX { tPortSchedulerPlcyName, tPortSchedPolicyLevel }
    ::= { tPortSchedPolicyLevelTable 1 }

TPortSchedPolicyLevelEntry ::= SEQUENCE
    {
        tPortSchedPolicyLevel                   TPortSchedLevel,
        tPortSchedPolicyLevelLastChanged        TimeStamp,
        tPortSchedPolicyLevelRateType           TPSPRateType,
        tPortSchedPolicyLevelPIR                Unsigned32,
        tPortSchedPolicyLevelCIR                Unsigned32,
        tPortSchedPolicyLevelPIRPercent         Unsigned32,
        tPortSchedPolicyLevelCIRPercent         Unsigned32,
        tPortSchedPolicyLevelGroupName          TNamedItemOrEmpty,
        tPortSchedPolicyLevelGroupWeight        TNonZeroWeight
    }

tPortSchedPolicyLevel               OBJECT-TYPE
    SYNTAX      TPortSchedLevel
    MAX-ACCESS  not-accessible
    STATUS      current
    DESCRIPTION
        "The value of tPortSchedPolicyLevel specifies the priority level of
         this port scheduler policy."
    ::= { tPortSchedPolicyLevelEntry 1 }

tPortSchedPolicyLevelLastChanged    OBJECT-TYPE
    SYNTAX      TimeStamp
    MAX-ACCESS  read-only
    STATUS      current
    DESCRIPTION
        "The value of tPortSchedPolicyLevelLastChanged indicates the value of 
         sysUpTime at the time of the most recent management change to this
         row."
    ::= { tPortSchedPolicyLevelEntry 2 }

tPortSchedPolicyLevelRateType       OBJECT-TYPE
    SYNTAX      TPSPRateType (1|2)
    MAX-ACCESS  read-create
    STATUS      current
    DESCRIPTION
        "The value of tPortSchedPolicyLevelRateType specifies the type of port
         scheduler rate for this priority level.
         
         When the value of tPortSchedPolicyLevelRateType is set to 'kbps', the
         port scheduler rate for this priority level is specified in 'kbps'. The
         values of tPortSchedPolicyLevelPIRPercent and 
         tPortSchedPolicyLevelCIRPercent will be set to their default values.

         When the value of tPortSchedPolicyLevelRateType is set to
         'percentLocal', the port scheduler rate for this priority level is
         specified in percentage of local limit. The values of
         tPortSchedPolicyLevelPIR and tPortSchedPolicyLevelCIR will be set to
         their default values."
    DEFVAL { kbps }
    ::= { tPortSchedPolicyLevelEntry 3 }


tPortSchedPolicyLevelPIR            OBJECT-TYPE
    SYNTAX       Unsigned32 (1..3200000000 | 4294967295)
    UNITS       "kbps"
    MAX-ACCESS  read-create
    STATUS      current
    DESCRIPTION
        "The value of tPortSchedPolicyLevelPIR specifies the total bandwidth
         limit, PIR, for this priority level.

         An 'inconsistentValue' error is returned if tPortSchedPolicyLevelPIR
         is set to non-default value when the value of
         tPortSchedPolicyLevelRateType is set to 'percentLocal'.

         When the value of tPortSchedPolicyLevelPIR is set to 4294967295
         (0xFFFFFFFF), rate for this port scheduler priority level indicates
         maximum rate."
    DEFVAL { 4294967295 }
    ::= { tPortSchedPolicyLevelEntry 5 }


tPortSchedPolicyLevelCIR            OBJECT-TYPE
    SYNTAX       Unsigned32 (0..3200000000 | 4294967295)
    UNITS       "kbps"
    MAX-ACCESS  read-create
    STATUS      current
    DESCRIPTION
        "The value of tPortSchedPolicyLevelCIR specifies the within-cir
         bandwidth limit for this priority level.

         An 'inconsistentValue' error is returned if tPortSchedPolicyLevelCIR
         is set to non-default value when the value of
         tPortSchedPolicyLevelRateType is set to 'percentLocal'.

         When the value of tPortSchedPolicyLevelCIR is set to 4294967295
         (0xFFFFFFFF), rate for this port scheduler priority level indicates 
         maximum rate."
    DEFVAL { 4294967295 }
    ::= { tPortSchedPolicyLevelEntry 7 }

tPortSchedPolicyLevelPIRPercent     OBJECT-TYPE
    SYNTAX      Unsigned32 (1..10000)
    UNITS       "hundredths of a percent"
    MAX-ACCESS  read-create
    STATUS      current
    DESCRIPTION
        "The value of tPortSchedPolicyLevelPIRPercent specifies the total
         bandwidth percentage, PIR percent, for this priority level.

         An 'inconsistentValue' error is returned if the value of
         tPortSchedPolicyLevelPIRPercent is set to non-default value when the
         object tPortSchedPolicyLevelRateType is set to 'kbps'."
    DEFVAL { 10000 }
    ::= { tPortSchedPolicyLevelEntry 8 }

tPortSchedPolicyLevelCIRPercent     OBJECT-TYPE
    SYNTAX      Unsigned32 (0..10000)
    UNITS       "hundredths of a percent"
    MAX-ACCESS  read-create
    STATUS      current
    DESCRIPTION
        "The value of tPortSchedPolicyLevelCIRPercent specifies the within-cir
         bandwidth percentage for this priority level.

         An 'inconsistentValue' error is returned if the value of
         tPortSchedPolicyLevelCIRPercent is set to non-default value when the
         object tPortSchedPolicyLevelRateType is set to 'kbps'."
    DEFVAL { 10000 }
    ::= { tPortSchedPolicyLevelEntry 9 }

tPortSchedPolicyLevelGroupName      OBJECT-TYPE
    SYNTAX      TNamedItemOrEmpty
    MAX-ACCESS  read-create
    STATUS      current
    DESCRIPTION
        "The value of tPortSchedPolicyLevelGroupName specifies the group
         associated with this scheduler policy priority level."
    DEFVAL { ''H }
    ::= { tPortSchedPolicyLevelEntry 10 }

tPortSchedPolicyLevelGroupWeight    OBJECT-TYPE
    SYNTAX      TNonZeroWeight
    MAX-ACCESS  read-create
    STATUS      current
    DESCRIPTION
        "The value of tPortSchedPolicyLevelGroupWeight specifies the weight 
         associated with the group tPortSchedPolicyLevelGroupName.

         An 'inconsistentValue' error is returned when this object is set to
         non-default value and tPortSchedPolicyLevelGroupName is set to default
         value."
    DEFVAL { 1 }
    ::= { tPortSchedPolicyLevelEntry 11 }


-- ----------------------------------------------------------------------------
-- Sap Ingress Dynamic Object Table
-- ----------------------------------------------------------------------------
tSapIngDynamicCfgTblLastChanged         OBJECT-TYPE
    SYNTAX      TimeStamp
    MAX-ACCESS  read-only
    STATUS      current
    DESCRIPTION
        "The value of tSapIngDynamicCfgTblLastChanged indicates the sysUpTime
         at the time of the last modification to tSapIngDynamicCfgTable.

         If no changes were made to the table since the last re-initialization
         of the local network management subsystem, this object contains the
         value zero."
    ::= { tQosTimeStampObjects 109 }

tSapIngDynamicCfgTable                  OBJECT-TYPE
    SYNTAX       SEQUENCE OF TSapIngDynamicCfgEntry
    MAX-ACCESS   not-accessible
    STATUS       current
    DESCRIPTION
        "The tSapIngDynamicCfgTable has an entry for each Sap Ingress
         QoS Policy."
    ::= { tSapIngressObjects 14 }

tSapIngDynamicCfgEntry                  OBJECT-TYPE
    SYNTAX       TSapIngDynamicCfgEntry
    MAX-ACCESS   not-accessible
    STATUS       current
    DESCRIPTION
        "The value of tSapIngDynamicCfgEntry represents information about a
         particular Sap Ingress QoS Policy.

         Sap Ingress policy (1) is the default entry and created by the agent,
         while all other entries are created by user.

         Default Entry cannot be modified/deleted. The other entries can be
         modified/deleted are deleted by user."
    AUGMENTS { tSapIngressEntry }
    ::= { tSapIngDynamicCfgTable 1 }

TSapIngDynamicCfgEntry ::=
    SEQUENCE {
        tSapIngDynamicCfgLastChanged        TimeStamp,
        tSapIngSharedPccRuleInsertPoint     TEntryIdOrZero,
        tSapIngSharedPccRuleInsertSize      TEntryIdOrZero,
        tSapIngSharedPccRuleNbrInsert       Unsigned32,
        tSapIngSharedPccRuleNbrPolicy       Unsigned32,
        tSapIngDynamicPolicerInsertPoint    TIngDynPolicerIdOrNone,
        tSapIngDynamicPolicerInsertSize     TIngDynPolicerIdOrNone,
        tSapIngDynamicPolicerNbrInsert      Unsigned32,
        tSapIngDynamicPolicerPktOffset      TPerPacketOffset,
        tSapIngDynamicPolicerMBS            TPlcrBurstSizeBytes,
        tSapIngDynamicPolicerCBS            TPlcrBurstSizeBytes,
        tSapIngDynamicPolicerParent         TNamedItemOrEmpty,
        tSapIngDynamicPolicerLevel          TLevel,
        tSapIngDynamicPolicerWeight         TPolicerWeight,
        tSapIngDynamicPolicerStatMode       TmnxIngPolicerStatMode
    }

tSapIngDynamicCfgLastChanged            OBJECT-TYPE
    SYNTAX       TimeStamp
    MAX-ACCESS   read-only
    STATUS       current
    DESCRIPTION
        "The value of tSapIngDynamicCfgLastChanged indicates the sysUpTime
         at the time of the last modification of this row."
    ::= { tSapIngDynamicCfgEntry 1 }

tSapIngSharedPccRuleInsertPoint         OBJECT-TYPE
    SYNTAX     TEntryIdOrZero
    MAX-ACCESS read-create
    STATUS     current
    DESCRIPTION
        "The value of tSapIngSharedPccRuleInsertPoint specifies the place at
         which the pcc-rule ip-criteria entries that are received from Diameter
         and that are shared across several hosts will be inserted in
         the policy.

         The range defined here will be reserved for those entries; no other
         entries will be allowed in this range.

         The value of zero means that no pcc-rule ip-criteria entries can be
         inserted in the policy by Diameter.

         If tSapIngSharedPccRuleInsertSize is set to zero, then
         tSapIngSharedPccRuleInsertPoint is also set to zero by the system.

         Note that the range reserved for pcc-rule entries is the same for
         IPv4 criteria and IPv6 criteria."
    DEFVAL { 0 }
    ::= { tSapIngDynamicCfgEntry 2 }

tSapIngSharedPccRuleInsertSize          OBJECT-TYPE
    SYNTAX     TEntryIdOrZero
    MAX-ACCESS read-create
    STATUS     current
    DESCRIPTION
        "The value of tSapIngSharedPccRuleInsertSize specifies how many pcc-rule
         ip-criteria entries that are received from Diameter and that are shared
         across several hosts can be inserted in the policy.

         The range defined here will be reserved for those entries; no other
         entries will be allowed in this range.

         The value of zero means that no pcc-rule ip-criteria entries can be
         inserted in the policy by Diameter.

         If tSapIngSharedPccRuleInsertPoint is set to zero, then
         tSapIngSharedPccRuleInsertSize is also set zero by the system.

         Note that the range reserved for pcc-rule entries is the same for
         IPv4 criteria and IPv6 criteria."
    DEFVAL { 0 }
    ::= { tSapIngDynamicCfgEntry 3 }

tSapIngSharedPccRuleNbrInsert           OBJECT-TYPE
    SYNTAX     Unsigned32
    MAX-ACCESS read-only
    STATUS     current
    DESCRIPTION
        "The value of the object tSapIngSharedPccRuleNbrInsert indicates how
         many pcc-rule ip-criteria entries received from Diameter have been
         inserted in this policy."
    ::= { tSapIngDynamicCfgEntry 4 }

tSapIngSharedPccRuleNbrPolicy           OBJECT-TYPE
    SYNTAX     Unsigned32
    MAX-ACCESS read-only
    STATUS     current
    DESCRIPTION
        "The value of the object tSapIngSharedPccRuleNbrPolicy indicates how
         many pcc-rule shared policies are currently created based on this
         policy."
    ::= { tSapIngDynamicCfgEntry 5 }

tSapIngDynamicPolicerInsertPoint        OBJECT-TYPE
    SYNTAX     TIngDynPolicerIdOrNone
    MAX-ACCESS read-create
    STATUS     current
    DESCRIPTION
        "The value of tSapIngDynamicPolicerInsertPoint specifies the place at
         which the dynamic policers required for pcc-rule ip-criteria entries
         that are received from Diameter and that are shared across several
         hosts will be inserted in the policy.

         The range defined here will be reserved for those dynamic policers; no
         other policers will be allowed in this range.

         The value of 0 means that no dynamic policers can be inserted in the
         policy by Diameter.

         If tSapIngDynamicPolicerInsertSize is set to zero, then
         tSapIngDynamicPolicerInsertPoint is also set zero by the system.

         Note that the range reserved for pcc-rule dynamic policers is the same
         for IPv4 criteria and IPv6 criteria."
    DEFVAL { 0 }
    ::= { tSapIngDynamicCfgEntry 6 }

tSapIngDynamicPolicerInsertSize         OBJECT-TYPE
    SYNTAX     TIngDynPolicerIdOrNone
    MAX-ACCESS read-create
    STATUS     current
    DESCRIPTION
        "The value of tSapIngDynamicPolicerInsertSize specifies how many
         dynamic policers required for pcc-rule ip-criteria entries that are
         received from Diameter and that are shared across several hosts can be
         inserted in the policy.

         The range defined here will be reserved for those dynamic policers; no
         other policers will be allowed in this range.

         The value of zero means that no dynamic policers can be inserted in the
         policy by Diameter.

         If tSapIngDynamicPolicerInsertSize is set to zero, then
         tSapIngDynamicPolicerInsertPoint is also set zero by the system.

         Note that the range reserved for pcc-rule dynamic policers is the same
         for IPv4 criteria and IPv6 criteria."
    DEFVAL { 0 }
    ::= { tSapIngDynamicCfgEntry 7 }

tSapIngDynamicPolicerNbrInsert          OBJECT-TYPE
    SYNTAX     Unsigned32
    MAX-ACCESS read-only
    STATUS     current
    DESCRIPTION
        "The value of the object tSapIngDynamicPolicerNbrInsert indicates how
         many dynamic policers required for pcc-rule ip-criteria entries
         received from Diameter have been inserted in this policy."
    ::= { tSapIngDynamicCfgEntry 8 }

tSapIngDynamicPolicerPktOffset          OBJECT-TYPE
    SYNTAX       TPerPacketOffset
    MAX-ACCESS   read-create
    STATUS       current
    DESCRIPTION
        "The value of tSapIngDynamicPolicerPktOffset specifies the packet byte
         offset for addition of policing information by this policer."
    DEFVAL { 0 }
    ::= { tSapIngDynamicCfgEntry 9 }

tSapIngDynamicPolicerMBS                OBJECT-TYPE
    SYNTAX       TPlcrBurstSizeBytes
    UNITS        "bytes"
    MAX-ACCESS   read-create
    STATUS       current
    DESCRIPTION
        "The value of tSapIngDynamicPolicerMBS specifies the high priority
         'violate' threshold of PIR leaky bucket of this policer."
    DEFVAL { -1 }
    ::= { tSapIngDynamicCfgEntry 10 }

tSapIngDynamicPolicerCBS                OBJECT-TYPE
    SYNTAX       TPlcrBurstSizeBytes
    UNITS        "bytes"
    MAX-ACCESS   read-create
    STATUS       current
    DESCRIPTION
        "The value of tSapIngDynamicPolicerCBS specifies the 'exceed' threshold
         of the CIR leaky bucket of this policer."
    DEFVAL { -1 }
    ::= { tSapIngDynamicCfgEntry 11 }

tSapIngDynamicPolicerParent             OBJECT-TYPE
    SYNTAX       TNamedItemOrEmpty
    MAX-ACCESS   read-create
    STATUS       current
    DESCRIPTION
        "The value of tSapIngDynamicPolicerParent specifies the arbiter to which
         this policer would be feeding."
    DEFVAL { ''H }
    ::= { tSapIngDynamicCfgEntry 12 }

tSapIngDynamicPolicerLevel              OBJECT-TYPE
    SYNTAX       TLevel
    MAX-ACCESS   read-create
    STATUS       current
    DESCRIPTION
        "The value of tSapIngDynamicPolicerLevel specifies the level of priority
         while feeding the parent."
    DEFVAL { 1 }
    ::= { tSapIngDynamicCfgEntry 13 }

tSapIngDynamicPolicerWeight             OBJECT-TYPE
    SYNTAX       TPolicerWeight
    MAX-ACCESS   read-create
    STATUS       current
    DESCRIPTION
        "The value of tSapIngDynamicPolicerWeight specifies the weight that
         needs to be used by the arbiter to which this policer would be
         feeding."
    DEFVAL { 1 }
    ::= { tSapIngDynamicCfgEntry 14 }

tSapIngDynamicPolicerStatMode           OBJECT-TYPE
    SYNTAX       TmnxIngPolicerStatMode
    MAX-ACCESS   read-create
    STATUS       current
    DESCRIPTION
        "The value of tSapIngDynamicPolicerStatMode specifies the mode of
         statistics collected by this policer."
    DEFVAL { minimal }
    ::= { tSapIngDynamicCfgEntry 15 }

-- ----------------------------------------------------------------------------
-- Sap Egress Dynamic Object Table
-- ----------------------------------------------------------------------------
tSapEgrDynamicCfgTblLastChanged         OBJECT-TYPE
    SYNTAX      TimeStamp
    MAX-ACCESS  read-only
    STATUS      current
    DESCRIPTION
        "The value of tSapEgrDynamicCfgTblLastChanged indicates the sysUpTime
         at the time of the last modification to tSapEgrDynamicCfgTable.

         If no changes were made to the table since the last re-initialization
         of the local network management subsystem, this object contains the
         value zero."
    ::= { tQosTimeStampObjects 110 }

tSapEgrDynamicCfgTable                  OBJECT-TYPE
    SYNTAX       SEQUENCE OF TSapEgrDynamicCfgEntry
    MAX-ACCESS   not-accessible
    STATUS       current
    DESCRIPTION
        "The tSapEgrDynamicCfgTable has an entry for each Sap Egress
         QoS Policy."
    ::= { tSapEgressObjects 14 }

tSapEgrDynamicCfgEntry                  OBJECT-TYPE
    SYNTAX       TSapEgrDynamicCfgEntry
    MAX-ACCESS   not-accessible
    STATUS       current
    DESCRIPTION
        "The value of tSapEgrDynamicCfgEntry represents information about a
         particular Sap Egress QoS Policy.

         Sap Egress policy (1) is the default entry and created by the agent,
         while all other entries are created by user.

         Default Entry cannot be modified/deleted. The other entries can be
         modified/deleted are deleted by user."
    AUGMENTS { tSapEgressEntry }
    ::= { tSapEgrDynamicCfgTable 1 }

TSapEgrDynamicCfgEntry ::=
    SEQUENCE {
        tSapEgrDynamicCfgLastChanged        TimeStamp,
        tSapEgrSharedPccRuleInsertPoint     TEntryIdOrZero,
        tSapEgrSharedPccRuleInsertSize      TEntryIdOrZero,
        tSapEgrSharedPccRuleNbrInsert       Unsigned32,
        tSapEgrSharedPccRuleNbrPolicy       Unsigned32,
        tSapEgrDynamicPolicerInsertPoint    TEgrDynPolicerIdOrNone,
        tSapEgrDynamicPolicerInsertSize     TEgrDynPolicerIdOrNone,
        tSapEgrDynamicPolicerNbrInsert      Unsigned32,
        tSapEgrDynamicPolicerPktOffset      TEgressPerPacketOffset,
        tSapEgrDynamicPolicerMBS            TPlcrBurstSizeBytes,
        tSapEgrDynamicPolicerCBS            TPlcrBurstSizeBytes,
        tSapEgrDynamicPolicerParent         TNamedItemOrEmpty,
        tSapEgrDynamicPolicerLevel          TLevel,
        tSapEgrDynamicPolicerWeight         TPolicerWeight,
        tSapEgrDynamicPolicerStatMode       TmnxEgrPolicerStatMode
    }

tSapEgrDynamicCfgLastChanged            OBJECT-TYPE
    SYNTAX       TimeStamp
    MAX-ACCESS   read-only
    STATUS       current
    DESCRIPTION
        "The value of tSapEgrDynamicCfgLastChanged indicates the sysUpTime
         at the time of the last modification of this row."
    ::= { tSapEgrDynamicCfgEntry 1 }

tSapEgrSharedPccRuleInsertPoint         OBJECT-TYPE
    SYNTAX     TEntryIdOrZero
    MAX-ACCESS read-create
    STATUS     current
    DESCRIPTION
        "The value of tSapEgrSharedPccRuleInsertPoint specifies the place at
         which the pcc-rule ip-criteria entries that are received from Diameter
         and that are shared across several hosts will be inserted in
         the policy.

         The range defined here will be reserved for those entries; no other
         entries will be allowed in this range.

         The value of zero means that no pcc-rule ip-criteria entries can be
         inserted in the policy by Diameter.

         If tSapEgrSharedPccRuleInsertSize is set to zero, then
         tSapEgrSharedPccRuleInsertPoint is also set to zero by the system.

         Note that the range reserved for pcc-rule entries is the same for
         IPv4 criteria and IPv6 criteria."
    DEFVAL { 0 }
    ::= { tSapEgrDynamicCfgEntry 2 }

tSapEgrSharedPccRuleInsertSize          OBJECT-TYPE
    SYNTAX     TEntryIdOrZero
    MAX-ACCESS read-create
    STATUS     current
    DESCRIPTION
        "The value of tSapEgrSharedPccRuleInsertSize specifies how many pcc-rule
         ip-criteria entries that are received from Diameter and that are shared
         across several hosts can be inserted in the policy.

         The range defined here will be reserved for those entries; no other
         entries will be allowed in this range.

         The value of zero means that no pcc-rule ip-criteria entries can be
         inserted in the policy by Diameter.

         If tSapEgrSharedPccRuleInsertPoint is set to zero, then
         tSapEgrSharedPccRuleInsertSize is also set zero by the system.

         Note that the range reserved for pcc-rule entries is the same for
         IPv4 criteria and IPv6 criteria."
    DEFVAL { 0 }
    ::= { tSapEgrDynamicCfgEntry 3 }

tSapEgrSharedPccRuleNbrInsert           OBJECT-TYPE
    SYNTAX     Unsigned32
    MAX-ACCESS read-only
    STATUS     current
    DESCRIPTION
        "The value of the object tSapEgrSharedPccRuleNbrInsert indicates how
         many pcc-rule ip-criteria entries received from Diameter have been
         inserted in this policy."
    ::= { tSapEgrDynamicCfgEntry 4 }

tSapEgrSharedPccRuleNbrPolicy           OBJECT-TYPE
    SYNTAX     Unsigned32
    MAX-ACCESS read-only
    STATUS     current
    DESCRIPTION
        "The value of the object tSapEgrSharedPccRuleNbrPolicy indicates how
         many pcc-rule shared policies are currently created based on this
         policy."
    ::= { tSapEgrDynamicCfgEntry 5 }

tSapEgrDynamicPolicerInsertPoint        OBJECT-TYPE
    SYNTAX     TEgrDynPolicerIdOrNone
    MAX-ACCESS read-create
    STATUS     current
    DESCRIPTION
        "The value of tSapEgrDynamicPolicerInsertPoint specifies the place at
         which the dynamic policers required for pcc-rule ip-criteria entries
         that are received from Diameter and that are shared across several
         hosts will be inserted in the policy.

         The range defined here will be reserved for those dynamic policers; no
         other policers will be allowed in this range.

         The value of zero means that no dynamic policers can be inserted in the
         policy by Diameter.

         If tSapEgrDynamicPolicerInsertSize is set to zero, then
         tSapEgrDynamicPolicerInsertPoint is also set zero by the system.

         Note that the range reserved for pcc-rule dynamic policers is the same
         for IPv4 criteria and IPv6 criteria."
    DEFVAL { 0 }
    ::= { tSapEgrDynamicCfgEntry 6 }

tSapEgrDynamicPolicerInsertSize         OBJECT-TYPE
    SYNTAX     TEgrDynPolicerIdOrNone
    MAX-ACCESS read-create
    STATUS     current
    DESCRIPTION
        "The value of tSapEgrDynamicPolicerInsertSize specifies how many
         dynamic policers required for pcc-rule ip-criteria entries that are
         received from Diameter and that are shared across several hosts can be
         inserted in the policy.

         The range defined here will be reserved for those dynamic policers; no
         other policers will be allowed in this range.

         The value of zero means that no dynamic policers can be inserted in the
         policy by Diameter.

         If tSapEgrDynamicPolicerInsertSize is set to zero, then
         tSapEgrDynamicPolicerInsertPoint is also set zero by the system.

         Note that the range reserved for pcc-rule dynamic policers is the same
         for IPv4 criteria and IPv6 criteria."
    DEFVAL { 0 }
    ::= { tSapEgrDynamicCfgEntry 7 }

tSapEgrDynamicPolicerNbrInsert          OBJECT-TYPE
    SYNTAX     Unsigned32
    MAX-ACCESS read-only
    STATUS     current
    DESCRIPTION
        "The value of the object tSapEgrDynamicPolicerNbrInsert indicates how
         many dynamic policers required for pcc-rule ip-criteria entries
         received from Diameter have been inserted in this policy."
    ::= { tSapEgrDynamicCfgEntry 8 }

tSapEgrDynamicPolicerPktOffset          OBJECT-TYPE
    SYNTAX       TEgressPerPacketOffset
    MAX-ACCESS   read-create
    STATUS       current
    DESCRIPTION
        "The value of tSapEgrDynamicPolicerPktOffset specifies the packet byte
         offset for addition of policing information by this policer."
    DEFVAL { 0 }
    ::= { tSapEgrDynamicCfgEntry 9 }

tSapEgrDynamicPolicerMBS                OBJECT-TYPE
    SYNTAX       TPlcrBurstSizeBytes
    UNITS        "bytes"
    MAX-ACCESS   read-create
    STATUS       current
    DESCRIPTION
        "The value of tSapEgrDynamicPolicerMBS specifies the high priority
         'violate' threshold of PIR leaky bucket of this policer."
    DEFVAL { -1 }
    ::= { tSapEgrDynamicCfgEntry 10 }

tSapEgrDynamicPolicerCBS                OBJECT-TYPE
    SYNTAX       TPlcrBurstSizeBytes
    UNITS        "bytes"
    MAX-ACCESS   read-create
    STATUS       current
    DESCRIPTION
        "The value of tSapEgrDynamicPolicerCBS specifies the 'exceed' threshold
         of the CIR leaky bucket of this policer."
    DEFVAL { -1 }
    ::= { tSapEgrDynamicCfgEntry 11 }

tSapEgrDynamicPolicerParent             OBJECT-TYPE
    SYNTAX       TNamedItemOrEmpty
    MAX-ACCESS   read-create
    STATUS       current
    DESCRIPTION
        "The value of tSapEgrDynamicPolicerParent specifies the arbiter to which
         this policer would be feeding."
    DEFVAL { ''H }
    ::= { tSapEgrDynamicCfgEntry 12 }

tSapEgrDynamicPolicerLevel              OBJECT-TYPE
    SYNTAX       TLevel
    MAX-ACCESS   read-create
    STATUS       current
    DESCRIPTION
        "The value of tSapEgrDynamicPolicerLevel specifies the level of priority
         while feeding the parent."
    DEFVAL { 1 }
    ::= { tSapEgrDynamicCfgEntry 13 }

tSapEgrDynamicPolicerWeight             OBJECT-TYPE
    SYNTAX       TPolicerWeight
    MAX-ACCESS   read-create
    STATUS       current
    DESCRIPTION
        "The value of tSapEgrDynamicPolicerWeight specifies the weight that
         needs to be used by the arbiter to which this policer would be
         feeding."
    DEFVAL { 1 }
    ::= { tSapEgrDynamicCfgEntry 14 }

tSapEgrDynamicPolicerStatMode           OBJECT-TYPE
    SYNTAX       TmnxEgrPolicerStatMode
    MAX-ACCESS   read-create
    STATUS       current
    DESCRIPTION
        "The value of tSapEgrDynamicPolicerStatMode specifies the mode of
         statistics collected by this policer."
    DEFVAL { minimal }
    ::= { tSapEgrDynamicCfgEntry 15 }


--
-- Conformance Information
--

tmnxQosCompliances OBJECT IDENTIFIER ::= { tmnxQosConformance 1 }
tmnxQosGroups      OBJECT IDENTIFIER ::= { tmnxQosConformance 2 }
tmnxQosDCCompliances OBJECT IDENTIFIER ::= { tmnxQosConformance 3 }
tmnxQosDCGroups      OBJECT IDENTIFIER ::= { tmnxQosConformance 4 }

--
-- compliance statements
--

-- tmnxQosCompliance   MODULE-COMPLIANCE
--    ::= { tmnxQosCompliances 1 }

-- tmnxQosR2r1Compliance   MODULE-COMPLIANCE
--    ::= { tmnxQosCompliances 2 }

-- tmnxQosV3v0Compliance   MODULE-COMPLIANCE
--    ::= { tmnxQosCompliances 3 }

tmnxQos7450V4v0Compliance   MODULE-COMPLIANCE
    STATUS   obsolete
    DESCRIPTION
        "The compliance statement for management of QOS features
         on Nokia 7450 ESS series systems release R4.0."
    MODULE  -- this module
        MANDATORY-GROUPS {
            tmnxQosGlobalGroup,
            tmnxQosDSCPGroup,
            tmnxQosFCGroup,
            tmnxQosSapIngressV4v0Group,
            tmnxQosSapEgressR2r1Group,
            tmnxQosNetworkR2r1Group,
            tmnxQosSlopeGroup,
            tmnxQosSchedulerGroup,
            -- tmnxQosAtmTdpV3v0Group,
            tmnxQosQueueV4v0Group
            -- tmnxQosSapIpv6FilterR4r0Group
        }
    ::= { tmnxQosCompliances 4 }

tmnxQos7750V4v0Compliance   MODULE-COMPLIANCE
    STATUS   obsolete
    DESCRIPTION
        "The compliance statement for management of QOS features
         on Nokia SROS series systems release R4.0."
    MODULE  -- this module
        MANDATORY-GROUPS {
            tmnxQosGlobalGroup,
            tmnxQosDSCPGroup,
            tmnxQosFCGroup,
            tmnxQosSapIngressV4v0Group,
            tmnxQosSapEgressR2r1Group,
            tmnxQosNetworkR2r1Group,
            tmnxQosSlopeGroup,
            tmnxQosSchedulerGroup,
            tmnxQosAtmTdpV3v0Group,
            tmnxQosQueueV4v0Group,
            tmnxQosSapIpv6FilterR4r0Group
        }
    ::= { tmnxQosCompliances 5 }

tmnxQos7450V5v0Compliance   MODULE-COMPLIANCE
    STATUS   obsolete
    DESCRIPTION
        "The compliance statement for management of QOS features
         on Nokia 7450 ESS series systems release R5.0."
    MODULE  -- this module
        MANDATORY-GROUPS {
            tmnxQosGlobalGroup,
            tmnxQosDSCPGroup,
            tmnxQosFCGroup,
            tmnxQosSapIngressV4v0Group,
            tmnxQosSapEgressV5v0Group,
            tmnxQosNetworkV5v0Group,
            tmnxQosSlopeGroup,
            tmnxQosSchedulerV5v0Group,
            -- tmnxQosAtmTdpV5v0Group,
            tmnxQosQueueV4v0Group
            -- tmnxQosSapIpv6FilterR4r0Group
        }
    ::= { tmnxQosCompliances 6 }

tmnxQos7750V5v0Compliance   MODULE-COMPLIANCE
    STATUS   obsolete
    DESCRIPTION
        "The compliance statement for management of QOS features
         on Nokia SROS series systems release R5.0."
    MODULE  -- this module
        MANDATORY-GROUPS {
            tmnxQosGlobalGroup,
            tmnxQosDSCPGroup,
            tmnxQosFCGroup,
            tmnxQosSapIngressV4v0Group,
            tmnxQosSapEgressV5v0Group,
            tmnxQosNetworkV5v0Group,
            tmnxQosSlopeGroup,
            tmnxQosSchedulerV5v0Group,
            tmnxQosAtmTdpV5v0Group,
            tmnxQosQueueV4v0Group,
            tmnxQosSapIpv6FilterR4r0Group
        }
    ::= { tmnxQosCompliances 7 }

tmnxQos7450V6v0Compliance   MODULE-COMPLIANCE
    STATUS   obsolete
    DESCRIPTION
        "The compliance statement for management of QOS features
         on Nokia 7450 ESS series systems release R6.0."
    MODULE  -- this module
        MANDATORY-GROUPS {
            tmnxQosGlobalGroup,
            tmnxQosDSCPGroup,
            tmnxQosFCGroup,
            tmnxQosSapIngressV6v0Group,
            tmnxQosSapEgressV6v0Group,
            tmnxQosNetworkV6v0Group,
            tmnxQosSlopeGroup,
            tmnxQosSchedulerV5v0Group,
            -- tmnxQosAtmTdpV5v0Group,
            tmnxQosQueueV4v0Group,
            -- tmnxQosSapIpv6FilterR4r0Group
            tmnxQosHsmdaV6v0Group,
            tmnxQosFrameBasedV6v0Group,
            tmnxQosNamedPoolPolicyV6v0Group
        }
    ::= { tmnxQosCompliances 8 }

tmnxQos7750V6v0Compliance   MODULE-COMPLIANCE
    STATUS   obsolete
    DESCRIPTION
        "The compliance statement for management of QOS features
         on Nokia SROS series systems release R6.0."
    MODULE  -- this module
        MANDATORY-GROUPS {
            tmnxQosGlobalGroup,
            tmnxQosDSCPGroup,
            tmnxQosFCGroup,
            tmnxQosSapIngressV6v0Group,
            tmnxQosSapEgressV6v0Group,
            tmnxQosNetworkV6v0Group,
            tmnxQosSlopeGroup,
            tmnxQosSchedulerV5v0Group,
            tmnxQosAtmTdpV5v0Group,
            tmnxQosQueueV4v0Group,
            tmnxQosSapIpv6FilterR4r0Group,
            tmnxQosHsmdaV6v0Group,
            tmnxQosFrameBasedV6v0Group,
            tmnxQosNamedPoolPolicyV6v0Group
        }
    ::= { tmnxQosCompliances 9 }

tmnxQos7450V6v1Compliance   MODULE-COMPLIANCE
    STATUS   obsolete
    DESCRIPTION
        "The compliance statement for management of QOS features
         on Nokia 7450 ESS series systems release R6.1."
    MODULE  -- this module
        MANDATORY-GROUPS {
            tmnxQosGlobalGroup,
            tmnxQosDSCPGroup,
            tmnxQosFCGroup,
            tmnxQosSapIngressV6v0Group,
            tmnxQosSapEgressV6v0Group,
            tmnxQosNetworkV6v0Group,
            tmnxQosSlopeGroup,
            tmnxQosSchedulerV5v0Group,
            -- tmnxQosAtmTdpV5v0Group,
            tmnxQosQueueV4v0Group,
            -- tmnxQosSapIpv6FilterR4r0Group
            tmnxQosHsmdaV6v0Group,
            tmnxQosFrameBasedV6v0Group,
            tmnxQosNamedPoolPolicyV6v0Group,
            tmnxQosMcMlpppIngrGroup,
            tmnxQosMcMlpppEgrGroup
        }
    ::= { tmnxQosCompliances 10 }

tmnxQos77x0V6v1Compliance   MODULE-COMPLIANCE
    STATUS   obsolete
    DESCRIPTION
        "The compliance statement for management of QOS features
         on Nokia SROS series systems release R6.1."
    MODULE  -- this module
        MANDATORY-GROUPS {
            tmnxQosGlobalGroup,
            tmnxQosDSCPGroup,
            tmnxQosFCGroup,
            tmnxQosSapIngressV6v0Group,
            tmnxQosSapEgressV6v0Group,
            tmnxQosNetworkV6v0Group,
            tmnxQosSlopeGroup,
            tmnxQosSchedulerV5v0Group,
            tmnxQosAtmTdpV5v0Group,
            tmnxQosQueueV4v0Group,
            tmnxQosSapIpv6FilterR4r0Group,
            tmnxQosHsmdaV6v0Group,
            tmnxQosFrameBasedV6v0Group,
            tmnxQosNamedPoolPolicyV6v0Group,
            tmnxQosMcMlpppIngrGroup,
            tmnxQosMcMlpppEgrGroup
        }
    ::= { tmnxQosCompliances 11 }

tmnxQos7450V7v0Compliance   MODULE-COMPLIANCE
    STATUS   obsolete
    DESCRIPTION
        "The compliance statement for management of QOS features
         on Nokia 7450 ESS series systems release R6.1."
    MODULE  -- this module
        MANDATORY-GROUPS {
            tmnxQosGlobalGroup,
            tmnxQosDSCPGroup,
            tmnxQosFCGroup,
            tmnxQosSapIngressV6v0Group,
            tmnxQosSapEgressV6v0Group,
            tmnxQosNetworkV7v0Group,
            tmnxQosSlopeGroup,
            tmnxQosSchedulerV5v0Group,
            -- tmnxQosAtmTdpV5v0Group,
            tmnxQosQueueV4v0Group,
            -- tmnxQosSapIpv6FilterR4r0Group
            tmnxQosHsmdaV7v0Group,
            tmnxQosFrameBasedV6v0Group,
            tmnxQosNamedPoolPolicyV6v0Group,
            tmnxQosMcMlpppIngrGroup,
            tmnxQosMcMlpppEgrGroup,
            tmnxQosQueueObjGroup,
            tQosQGrpFCGroup,
            tmnxQosSapAtmV7v0Group,
            tmnxQosSapEgrQWredGroup
        }
    ::= { tmnxQosCompliances 12 }

tmnxQos77x0V7v0Compliance   MODULE-COMPLIANCE
    STATUS   obsolete
    DESCRIPTION
        "The compliance statement for management of QOS features
         on Nokia 7750 SROS series systems release R6.1."
    MODULE  -- this module
        MANDATORY-GROUPS {
            tmnxQosGlobalGroup,
            tmnxQosDSCPGroup,
            tmnxQosFCGroup,
            tmnxQosSapIngressV6v0Group,
            tmnxQosSapEgressV6v0Group,
            tmnxQosNetworkV7v0Group,
            tmnxQosSlopeGroup,
            tmnxQosSchedulerV5v0Group,
            tmnxQosAtmTdpV5v0Group,
            tmnxQosQueueV4v0Group,
            tmnxQosSapIpv6FilterR4r0Group,
            tmnxQosHsmdaV7v0Group,
            tmnxQosFrameBasedV6v0Group,
            tmnxQosNamedPoolPolicyV6v0Group,
            tmnxQosMcMlpppIngrGroup,
            tmnxQosMcMlpppEgrGroup,
            tmnxQosQueueObjGroup,
            tQosQGrpFCGroup,
            tmnxQosSapAtmV7v0Group,
            tmnxQosMcFrIngrGroup,
            tmnxQosMcFrEgrGroup,
            tmnxQosSapEgrQWredGroup
        }
    ::= { tmnxQosCompliances 13 }   
    
tmnxQos7450V8v0Compliance   MODULE-COMPLIANCE
    STATUS   obsolete
    DESCRIPTION
        "The compliance statement for management of QOS features
         on Nokia 7450 ESS series systems release R8.0."
    MODULE  -- this module
        MANDATORY-GROUPS {
            tmnxQosGlobalGroup,
            tmnxQosDSCPGroup,
            tmnxQosFCGroup,
            tmnxQosSapIngressV8v0Group,
            tmnxQosSapEgressV8v0Group,
            tmnxQosNetworkV7v0Group,
            tmnxQosSlopeGroup,
            tmnxQosSchedulerV5v0Group,
            -- tmnxQosAtmTdpV5v0Group,
            tmnxQosQueueV4v0Group,
            -- tmnxQosSapIpv6FilterR4r0Group
            tmnxQosHsmdaV7v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosSapEgrQWredGroup, 
            tmnxQosPolicerV8v0Group,
            tmnxQosPortSchPlcyGrpGroup,
            tmnxQosBurstLimitGroup,
            tQosFCQGrpFC8v0Group
        }
    ::= { tmnxQosCompliances 14 }

tmnxQos77x0V8v0Compliance   MODULE-COMPLIANCE
    STATUS   obsolete
    DESCRIPTION
        "The compliance statement for management of QOS features
         on Nokia SROS series systems release R8.0."
    MODULE  -- this module
        MANDATORY-GROUPS {
            tmnxQosGlobalGroup,
            tmnxQosDSCPGroup,
            tmnxQosFCGroup,
            tmnxQosSapIngressV8v0Group,
            tmnxQosSapEgressV8v0Group,
            tmnxQosNetworkV7v0Group,
            tmnxQosSlopeGroup,
            tmnxQosSchedulerV5v0Group,
            tmnxQosAtmTdpV5v0Group,
            tmnxQosQueueV4v0Group,
            tmnxQosSapIpv6FilterR4r0Group,
            tmnxQosHsmdaV7v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosMcFrIngrGroup,
            tmnxQosMcFrEgrGroup,
            tmnxQosSapEgrQWredGroup,
            tmnxQosPolicerV8v0Group,
            tQosQGrpV8v0Group,
            tmnxQosPortSchPlcyGrpGroup,
            tmnxQosBurstLimitGroup,
            tQosFCQGrpFC8v0Group
        }
    ::= { tmnxQosCompliances 15 }

tmnxQos77x0V9v0Compliance   MODULE-COMPLIANCE
    STATUS   obsolete
    DESCRIPTION
        "The compliance statement for management of QOS features
         on Nokia SROS series systems release R9.0."
    MODULE  -- this module
        MANDATORY-GROUPS {
            tmnxQosGlobalGroup,
            tmnxQosDSCPGroup,
            tmnxQosFCGroup,
            tmnxQosSapIngressV8v0Group,
            tmnxQosSapEgressV8v0Group,
            tmnxQosNetworkV7v0Group,
            tmnxQosNetworkV9v0Group,
            tmnxQosSlopeGroup,
            tmnxQosSchedulerV8v0Group,
            tmnxQosAtmTdpV5v0Group,
            tmnxQosAtmTdpV9v0Group,
            tmnxQosQueueV4v0Group,
            tmnxQosSapIpv6FilterR4r0Group,
            tmnxQosHsmdaV7v0Group,
            tmnxQosHsmdaV9v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosMcFrIngrGroup,
            tmnxQosMcFrEgrGroup,
            tmnxQosSapEgrQWredGroup,
            tmnxQosPolicerV8v0Group,
            tmnxQosPolicerV9v0Group,
            tQosQGrpV8v0Group,
            tmnxQosPortSchPlcyGrpGroup,
            tmnxQosBurstLimitGroup,
            tmnxQosMacCritVidFltrV9v0Group,
            tmnxQosSapEgressV9v0Group,
            tmnxQosSapIngressV9v0Group,
            tmnxQosNamedPoolV9v0Group
        }
    ::= { tmnxQosCompliances 16 }
    
tmnxQos7450V10v0Compliance   MODULE-COMPLIANCE
    STATUS   obsolete
    DESCRIPTION
        "The compliance statement for management of QOS features
         on Nokia 7450 ESS series systems release R10.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosSlopeGroup,
            tmnxQosSchedulerV5v0Group,
            -- tmnxQosAtmTdpV5v0Group,
            tmnxQosQueueV4v0Group,
            -- tmnxQosSapIpv6FilterR4r0Group
            tmnxQosHsmdaV10v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosSapEgrQWredGroup, 
            tmnxQosPolicerV8v0Group,
            tmnxQosPortSchPlcyGrpGroup,
            tmnxQosBurstLimitGroup,
            tQosFCQGrpFC8v0Group,
            tmnxQosPolicyV10v0Group,
            tmnxQosPolicerSlopeGroup
        }
    ::= { tmnxQosCompliances 17 }

tmnxQos77x0V10v0Compliance   MODULE-COMPLIANCE
    STATUS   obsolete
    DESCRIPTION
        "The compliance statement for management of QOS features
         on Nokia SROS series systems release R10.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosNetworkV9v0Group,
            tmnxQosSlopeGroup,
            tmnxQosSchedulerV8v0Group,
            tmnxQosAtmTdpV5v0Group,
            tmnxQosAtmTdpV9v0Group,
            tmnxQosQueueV4v0Group,
            tmnxQosSapIpv6FilterR4r0Group,
            tmnxQosHsmdaV10v0Group,
            tmnxQosHsmdaV9v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosMcFrIngrGroup,
            tmnxQosMcFrEgrGroup,
            tmnxQosSapEgrQWredGroup,
            tmnxQosPolicerV8v0Group,
            tmnxQosPolicerV9v0Group,
            tQosQGrpV8v0Group,
            tmnxQosPortSchPlcyGrpGroup,
            tmnxQosBurstLimitGroup,
            tmnxQosMacCritVidFltrV9v0Group,
            tmnxQosSapEgressV9v0Group,
            tmnxQosSapIngressV9v0Group,
            tmnxQosNamedPoolV9v0Group,
            tmnxQosPolicyV10v0Group,
            tmnxQosQueueGrpPolcrV10v0Group,
            tmnxQosEgrReClassifyV10v0Group,
            tmnxQosPolicerSlopeGroup,
            tmnxQosAdvConfigV10v0Group,
            tmnxQosHsmdaV10v0Group,
            tmnxQosNetworkV10v0Group
        }
    ::= { tmnxQosCompliances 18 }

tmnxQos7450V11v0Compliance   MODULE-COMPLIANCE
    STATUS   obsolete
    DESCRIPTION
        "The compliance statement for management of QOS features
         on Nokia 7450 ESS series systems release R11.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosSlopeGroup,
            tmnxQosSchedulerV5v0Group,
            -- tmnxQosAtmTdpV5v0Group,
            tmnxQosQueueV4v0Group,
            -- tmnxQosSapIpv6FilterR4r0Group
            tmnxQosHsmdaV10v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosSapEgrQWredGroup, 
            tmnxQosPolicerV8v0Group,
            tmnxQosPortSchPlcyGrpGroup,
            tmnxQosBurstLimitGroup,
            tQosFCQGrpFC8v0Group,
            tmnxQosPolicyV10v0Group,
            tmnxQosPolicerSlopeGroup,
            tmnxQosNetworkV11v0Group,
            tmnxSapEgressFCV11v0Group,
            tmnxQosHsmdaV11v0Group,
            tmnxQosSchedulerRateV11v0Group,
            tmnxQosSchedulerV11v0Group
        }
    ::= { tmnxQosCompliances 19 }

tmnxQos77x0V11v0Compliance   MODULE-COMPLIANCE
    STATUS   obsolete
    DESCRIPTION
        "The compliance statement for management of QOS features
         on Nokia SROS series systems release R11.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosNetworkV9v0Group,
            tmnxQosSlopeGroup,
            tmnxQosAtmTdpV5v0Group,
            tmnxQosAtmTdpV9v0Group,
            tmnxQosQueueV4v0Group,
            tmnxQosSapIpv6FilterR4r0Group,
            tmnxQosHsmdaV10v0Group,
            tmnxQosHsmdaV9v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosMcFrIngrGroup,
            tmnxQosMcFrEgrGroup,
            tmnxQosSapEgrQWredGroup,
            tmnxQosPolicerV8v0Group,
            tmnxQosPolicerV9v0Group,
            tQosQGrpV8v0Group,
            tmnxQosPortSchPlcyGrpGroup,
            tmnxQosBurstLimitGroup,
            tmnxQosMacCritVidFltrV9v0Group,
            tmnxQosSapEgressV9v0Group,
            tmnxQosSapIngressV9v0Group,
            tmnxQosNamedPoolV9v0Group,
            tmnxQosPolicyV10v0Group,
            tmnxQosQueueGrpPolcrV10v0Group,
            tmnxQosEgrReClassifyV10v0Group,
            tmnxQosPolicerSlopeGroup,
            tmnxQosAdvConfigV10v0Group,
            tmnxQosHsmdaV10v0Group,
            tmnxQosNetworkV10v0Group,
            tmnxQosNetworkV11v0Group,
            tmnxSapEgressFCV11v0Group,
            tmnxQosHsmdaV11v0Group,
            tmnxQosSchedulerRateV11v0Group,
            tmnxQosSchedulerV11v0Group
        }
    ::= { tmnxQosCompliances 20 }    

tmnxQos7450V12v0Compliance   MODULE-COMPLIANCE
    STATUS   obsolete
    DESCRIPTION
        "The compliance statement for management of QOS features
         on Nokia 7450 ESS series systems release R12.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosSlopeGroup,
            tmnxQosSchedulerV5v0Group,
            -- tmnxQosAtmTdpV5v0Group,
            tmnxQosQueueV4v0Group,
            -- tmnxQosSapIpv6FilterR4r0Group
            tmnxQosHsmdaV10v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosSapEgrQWredGroup, 
            tmnxQosPolicerV8v0Group,
            tmnxQosPortSchPlcyGrpGroup,
            tmnxQosBurstLimitGroup,
            tQosFCQGrpFC8v0Group,
            tmnxQosPolicyV10v0Group,
            tmnxQosPolicerSlopeGroup,
            tmnxQosNetworkV11v0Group,
            tmnxSapEgressFCV11v0Group,
            tmnxQosHsmdaV11v0Group,
            tmnxQosSchedulerRateV11v0Group,
            tmnxQosSchedulerV11v0Group,
            tmnxQosSapEgrFCDot1pDEV12v0Group,
            tmnxQosSapIPCritExtV12v0Group,
            tmnxQosParentLocV12v0Group,
            tmnxQosParentLocEsmV12v0Group,
            tmnxQosSapIngIPMacCritV12v0Group,
            tmnxQosPlcyV12v0Group,
            tmnxQosSapEgrPlcrV12v0Group,
            tmnxQosPortSchedV12v0Group
        }
    ::= { tmnxQosCompliances 21 }

tmnxQos77x0V12v0Compliance   MODULE-COMPLIANCE
    STATUS   obsolete
    DESCRIPTION
        "The compliance statement for management of QOS features
         on Nokia SROS series systems release R12.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosNetworkV9v0Group,
            tmnxQosSlopeGroup,
            tmnxQosAtmTdpV5v0Group,
            tmnxQosAtmTdpV9v0Group,
            tmnxQosQueueV4v0Group,
            tmnxQosSapIpv6FilterR4r0Group,
            tmnxQosHsmdaV10v0Group,
            tmnxQosHsmdaV9v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosMcFrIngrGroup,
            tmnxQosMcFrEgrGroup,
            tmnxQosSapEgrQWredGroup,
            tmnxQosPolicerV8v0Group,
            tmnxQosPolicerV9v0Group,
            tQosQGrpV8v0Group,
            tmnxQosPortSchPlcyGrpGroup,
            tmnxQosBurstLimitGroup,
            tmnxQosMacCritVidFltrV9v0Group,
            tmnxQosSapEgressV9v0Group,
            tmnxQosSapIngressV9v0Group,
            tmnxQosNamedPoolV9v0Group,
            tmnxQosPolicyV10v0Group,
            tmnxQosQueueGrpPolcrV10v0Group,
            tmnxQosEgrReClassifyV10v0Group,
            tmnxQosPolicerSlopeGroup,
            tmnxQosAdvConfigV10v0Group,
            tmnxQosHsmdaV10v0Group,
            tmnxQosNetworkV10v0Group,
            tmnxQosNetworkV11v0Group,
            tmnxSapEgressFCV11v0Group,
            tmnxQosHsmdaV11v0Group,
            tmnxQosSchedulerRateV11v0Group,
            tmnxQosSchedulerV11v0Group,
            tmnxQosSapEgrFCDot1pDEV12v0Group,
            tmnxQosParentLocV12v0Group,
            tmnxQosParentLocEsmV12v0Group,
            tmnxQosSapIngIPMacCritV12v0Group,
            tmnxQosPlcyV12v0Group,
            tmnxQosSapEgrPlcrV12v0Group,
            tmnxQosPortSchedV12v0Group
        }
    ::= { tmnxQosCompliances 22 }    

tmnxQos7450V13v0Compliance   MODULE-COMPLIANCE
    STATUS   current
    DESCRIPTION
        "The compliance statement for management of QOS features
         on Nokia 7450 ESS series systems release R13.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosSlopeGroup,
            -- tmnxQosAtmTdpV5v0Group,
            tmnxQosQueueV4v0Group,
            -- tmnxQosSapIpv6FilterR4r0Group
            tmnxQosHsmdaV10v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosSapEgrQWredGroup, 
            tmnxQosPolicerV8v0Group,
            tmnxQosBurstLimitGroup,
            tQosFCQGrpFC8v0Group,
            tmnxQosPolicyV10v0Group,
            tmnxQosPolicerSlopeGroup,
            tmnxQosNetworkV11v0Group,
            tmnxSapEgressFCV11v0Group,
            tmnxQosHsmdaV11v0Group,
            tmnxQosSchedulerRateV11v0Group,
            tmnxQosSapEgrFCDot1pDEV12v0Group,
            tmnxQosSapIPCritExtV12v0Group,
            tmnxQosParentLocV12v0Group,
            tmnxQosParentLocEsmV12v0Group,
            tmnxQosSapIngIPMacCritV12v0Group,
            tmnxQosPlcyV12v0Group,
            tmnxQosSapEgrPlcrV12v0Group,
            tmnxQosSapIngressV13v0Group,
            tmnxQosNetworkPlcyV13v0Group,
            tmnxQosNetworkIngFCV13v0Group,
            tmnxQosAdvCfgPlcyV13v0Group,
            tmnxQosFlowBasedRulesV13v0Group,
            tmnxQosIngressPlcyV13v0Group,
            tmnxQosSapEgrIPCritV13v0Group,
            tmnxQosPortSchedPlcyV13v0Group,
            tmnxQosSapEgrIpCritGroup,
            tmnxQosSchedulerV13v0Group
        }
    ::= { tmnxQosCompliances 23 }

tmnxQos77x0V13v0Compliance   MODULE-COMPLIANCE
    STATUS   current
    DESCRIPTION
        "The compliance statement for management of QOS features
         on Nokia SROS series systems release R13.0."
    MODULE  -- this module
        MANDATORY-GROUPS {
            tmnxQosGlobalGroup,
            tmnxQosDSCPGroup,
            tmnxQosFCGroup,
            tmnxQosSapIngressV10v0Group,
            tmnxQosSapEgressV8v0Group,
            tmnxQosNetworkV7v0Group,
            tmnxQosNetworkV9v0Group,
            tmnxQosSlopeGroup,
            tmnxQosAtmTdpV5v0Group,
            tmnxQosAtmTdpV9v0Group,
            tmnxQosQueueV4v0Group,
            tmnxQosSapIpv6FilterR4r0Group,
            tmnxQosHsmdaV10v0Group,
            tmnxQosHsmdaV9v0Group,
            tmnxQosFrameBasedV6v0Group,
            tmnxQosNamedPoolPolicyV6v0Group,
            tmnxQosMcMlpppIngrGroup,
            tmnxQosMcMlpppEgrGroup,
            tmnxQosQueueObjV8v0Group,
            tQosQGrpFCGroup,
            tmnxQosSapAtmV7v0Group,
            tmnxQosMcFrIngrGroup,
            tmnxQosMcFrEgrGroup,
            tmnxQosSapEgrQWredGroup,
            tmnxQosPolicerV8v0Group,
            tmnxQosPolicerV9v0Group,
            tQosQGrpV8v0Group,
            tmnxQosBurstLimitGroup,
            tmnxQosMacCritVidFltrV9v0Group,
            tmnxQosSapEgressV9v0Group,
            tmnxQosSapIngressV9v0Group,
            tmnxQosNamedPoolV9v0Group,
            tmnxQosPolicyV10v0Group,
            tmnxQosQueueGrpPolcrV10v0Group,
            tmnxQosEgrReClassifyV10v0Group,
            tmnxQosPolicerSlopeGroup,
            tmnxQosAdvConfigV10v0Group,
            tmnxQosHsmdaV10v0Group,
            tmnxQosNetworkV10v0Group,
            tmnxQosNetworkV11v0Group,
            tmnxSapEgressFCV11v0Group,
            tmnxQosHsmdaV11v0Group,
            tmnxQosSchedulerRateV11v0Group,
            tmnxQosSapEgrFCDot1pDEV12v0Group,
            tmnxQosParentLocV12v0Group,
            tmnxQosParentLocEsmV12v0Group,
            tmnxQosSapIngIPMacCritV12v0Group,
            tmnxQosPlcyV12v0Group,
            tmnxQosSapEgrPlcrV12v0Group,
            tmnxQosSapIngressV13v0Group,
            tmnxQosNetworkPlcyV13v0Group,
            tmnxQosNetworkIngFCV13v0Group,
            tmnxQosAdvCfgPlcyV13v0Group,
            tmnxQosFlowBasedRulesV13v0Group,
            tmnxQosIngressPlcyV13v0Group,
            tmnxQosSapEgrIPCritV13v0Group,
            tmnxQosPortSchedPlcyV13v0Group,
            tmnxQosSapEgrIpCritGroup,
            tmnxQosSchedulerV13v0Group
        }
    ::= { tmnxQosCompliances 24 }

--
-- units of conformance
--
tmnxQosGlobalGroup OBJECT-GROUP
    OBJECTS {
        tQosDomainLastChanged
    }
    STATUS      current
    DESCRIPTION
        "The group of objects supporting general management of QOS
         features on Nokia SROS series systems."
    ::= { tmnxQosGroups 1 }

tmnxQosDSCPGroup OBJECT-GROUP
    OBJECTS {
        tDSCPNameRowStatus,
        tDSCPNameStorageType,
        tDSCPNameDscpValue,
        tDSCPNameLastChanged,
        tDSCPNameTableLastChanged
    }
    STATUS      current
    DESCRIPTION
        "The group of objects supporting management of Differential Services
         Code Points on Nokia SROS series systems."
    ::= { tmnxQosGroups 2 }

tmnxQosFCGroup OBJECT-GROUP
    OBJECTS {
        tFCRowStatus,
        tFCStorageType,
        tFCValue,
        tFCNameLastChanged,
        tFCNameTableLastChanged
    }
    STATUS      current
    DESCRIPTION
        "The group of objects supporting management of Forwarding Classes
         on Nokia SROS series systems."
    ::= { tmnxQosGroups 3 }

-- tmnxQosSapIngressGroup OBJECT-GROUP
--    ::= { tmnxQosGroups 4 }

-- tmnxQosSapEgressGroup OBJECT-GROUP
--    ::= { tmnxQosGroups 5 }

-- tmnxQosNetworkGroup OBJECT-GROUP
--    ::= { tmnxQosGroups 6 }

tmnxQosSlopeGroup OBJECT-GROUP
    OBJECTS {
        tSlopeRowStatus,
        tSlopeDescription,
        tSlopeHiAdminStatus,
        tSlopeHiStartAverage,
        tSlopeHiMaxAverage,
        tSlopeHiMaxProbability,
        tSlopeLoAdminStatus,
        tSlopeLoStartAverage,
        tSlopeLoMaxAverage,
        tSlopeLoMaxProbability,
        tSlopeTimeAvgFactor,
        tSlopeLastChanged,
        tSlopePolicyTableLastChanged
    }
    STATUS      current
    DESCRIPTION
        "The group of objects supporting management of Slope policies
         on Nokia SROS series systems."
    ::= { tmnxQosGroups 7 }

tmnxQosSchedulerGroup OBJECT-GROUP
    OBJECTS {
        tSchedulerPolicyRowStatus,
        tSchedulerPolicyDescription,
        tSchedulerPolicyLastChanged,
        tSchedulerPolicyTableLastChanged,
        tVirtualSchedulerRowStatus,
        tVirtualSchedulerDescription,
        tVirtualSchedulerParent,
        tVirtualSchedulerLevel,
        tVirtualSchedulerWeight,
        tVirtualSchedulerCIRLevel,
        tVirtualSchedulerCIRWeight,
        tVirtualSchedulerPIR,
        tVirtualSchedulerCIR,
        tVirtualSchedulerSummedCIR,
        tVirtualSchedulerLastChanged,
        tVirtualSchedulerTableLastChanged
    }
    STATUS      obsolete
    DESCRIPTION
        "The group of objects supporting management of Scheduler policies
         on Nokia SROS series systems."
    ::= { tmnxQosGroups 8 }

-- tmnxQosAtmTdpR2r1Group OBJECT-GROUP
--    ::= { tmnxQosGroups 9 }

tQosObsoleteObjectsGroup    OBJECT-GROUP
    OBJECTS {
        tSapIngressQueueOperPIR,
        tSapIngressQueueOperCIR,
        tSapEgressQueueOperPIR,
        tSapEgressQueueOperCIR
    }
    STATUS    current
    DESCRIPTION
        "The group of obsolete objects in the TIMETRA-QOS-MIB."
    ::= { tmnxQosGroups 10 }

-- tmnxQosSapIngressR2r1Group OBJECT-GROUP
--    ::= { tmnxQosGroups 11 }

tmnxQosSapEgressR2r1Group OBJECT-GROUP
    OBJECTS {
        tSapEgressRowStatus,
        tSapEgressScope,
        tSapEgressDescription,
        tSapEgressLastChanged,
        tSapEgressTableLastChanged,
        tSapEgressQueueRowStatus,
        tSapEgressQueueParent,
        tSapEgressQueueLevel,
        tSapEgressQueueWeight,
        tSapEgressQueueCIRLevel,
        tSapEgressQueueCIRWeight,
        tSapEgressQueueExpedite,
        tSapEgressQueueCBS,
        tSapEgressQueueMBS,
        tSapEgressQueueHiPrioOnly,
        tSapEgressQueueCIRAdaptation,
        tSapEgressQueuePIRAdaptation,
        tSapEgressQueueAdminPIR,
        tSapEgressQueueAdminCIR,
        tSapEgressQueueLastChanged,
        tSapEgressQueueTableLastChanged,
        tSapEgressFCRowStatus,
        tSapEgressFCQueue,
        tSapEgressFCDot1PValue,
        tSapEgressFCLastChanged,
        tSapEgressFCTableLastChanged
    }
    STATUS      obsolete
    DESCRIPTION
        "The group of objects supporting management of SAP egress QoS
         policies on Nokia SROS series systems."
    ::= { tmnxQosGroups 12 }

tmnxQosNetworkR2r1Group OBJECT-GROUP
    OBJECTS {
        tNetworkPolicyRowStatus,
        tNetworkPolicyScope,
        tNetworkPolicyDescription,
        tNetworkPolicyIngressDefaultActionFC,
        tNetworkPolicyIngressDefaultActionProfile,
        tNetworkPolicyEgressRemark,
        tNetworkPolicyLastChanged,
        tNetworkPolicyIngressLerUseDscp,
        tNetworkPolicyTableLastChanged,
        tNetworkIngressDSCPRowStatus,
        tNetworkIngressDSCPFC,
        tNetworkIngressDSCPProfile,
        tNetworkIngressDSCPLastChanged,
        tNetworkIngressDSCPTableLastChanged,
        tNetworkIngressDot1pRowStatus,
        tNetworkIngressDot1pFC,
        tNetworkIngressDot1pProfile,
        tNetworkIngressDot1pLastChanged,
        tNetworkIngressDot1pTableLastChanged,
        tNetworkIngressLSPEXPRowStatus,
        tNetworkIngressLSPEXPFC,
        tNetworkIngressLSPEXPProfile,
        tNetworkIngressLSPEXPLastChanged,
        tNetworkIngressLSPEXPTableLastChanged,
        tNetworkEgressFCDSCPInProfile,
        tNetworkEgressFCDSCPOutProfile,
        tNetworkEgressFCLspExpInProfile,
        tNetworkEgressFCLspExpOutProfile,
        tNetworkEgressFCDot1pInProfile,
        tNetworkEgressFCDot1pOutProfile,
        tNetworkEgressFCLastChanged,
        tNetworkEgressFCTableLastChanged,
        tNetworkQueuePolicyRowStatus,
        tNetworkQueuePolicyDescription,
        tNetworkQueuePolicyLastChanged,
        tNetworkQueuePolicyTableLastChanged,
        tNetworkQueueRowStatus,
        tNetworkQueuePoolName,
        tNetworkQueueParent,
        tNetworkQueueLevel,
        tNetworkQueueWeight,
        tNetworkQueueCIRLevel,
        tNetworkQueueCIRWeight,
        tNetworkQueueMCast,
        tNetworkQueueExpedite,
        tNetworkQueueCIR,
        tNetworkQueuePIR,
        tNetworkQueueCBS,
        tNetworkQueueMBS,
        tNetworkQueueHiPrioOnly,
        tNetworkQueueLastChanged ,
        tNetworkQueueTableLastChanged,
        tNetworkQueueFCRowStatus,
        tNetworkQueueFC,
        tNetworkQueueFCMCast,
        tNetworkQueueFCLastChanged,
        tNetworkQueueFCTableLastChanged
    }
    STATUS      obsolete
    DESCRIPTION
        "The group of objects supporting management of Network QoS policies
         on Nokia SROS series systems."
    ::= { tmnxQosGroups 13 }

-- tmnxQosQueueR2r1Group OBJECT-GROUP
--    ::= { tmnxQosGroups 14 }

tmnxQosAtmTdpV3v0Group OBJECT-GROUP
    OBJECTS   {
        tAtmTdpSir,
        tAtmTdpPir,
        tAtmTdpMbs,
        tAtmTdpMir,
        tAtmTdpShaping,
        tAtmTdpServCat,
        tAtmTdpLastChanged,
        tAtmTdpDescription,
        tAtmTdpRowStatus,
        tAtmTdpDescrType,
        tAtmTdpCdvt,
        tAtmTdpPolicing,
        tAtmTdpIndexNext,
        tAtmTdpsMaxSupported,
        tAtmTdpsCurrentlyConfigured,
        tAtmTdpTableLastChanged
    }
    STATUS    obsolete
    DESCRIPTION
        "The group of objects for ATM Traffic Descriptor Profiles
         on Nokia SROS series systems release 3.0."
    ::= { tmnxQosGroups 15 }


tmnxQosSapIpv6FilterR4r0Group OBJECT-GROUP
    OBJECTS {
        tSapIngressIPv6CriteriaRowStatus,
        tSapIngressIPv6CriteriaDescription,
        tSapIngressIPv6CriteriaActionFC,
        tSapIngressIPv6CriteriaActionPriority,
        tSapIngressIPv6CriteriaSourceIpAddr,
        tSapIngressIPv6CriteriaSourceIpMask,
        tSapIngressIPv6CriteriaDestIpAddr,
        tSapIngressIPv6CriteriaDestIpMask,
        tSapIngressIPv6CriteriaNextHeader,
        tSapIngressIPv6CriteriaSourcePortValue1,
        tSapIngressIPv6CriteriaSourcePortValue2,
        tSapIngressIPv6CriteriaSourcePortOperator,
        tSapIngressIPv6CriteriaDestPortValue1,
        tSapIngressIPv6CriteriaDestPortValue2,
        tSapIngressIPv6CriteriaDestPortOperator,
        tSapIngressIPv6CriteriaDSCP,
        tSapIngressIPv6CriteriaLastChanged,
        tSapIngressIPv6CriteriaTableLastChanged
    }
    STATUS    current
    DESCRIPTION
        "The group of objects for Qos Policies related to IPv6
         on Nokia SROS series systems release 4.0."
    ::= { tmnxQosGroups 16 }

tmnxQosQueueV4v0Group OBJECT-GROUP
    OBJECTS {
        tSharedQueuePolicyRowStatus,
        tSharedQueuePolicyDescription,
        tSharedQueuePolicyLastChanged,
        tSharedQueuePolicyTableLastChanged,
        tSharedQueueRowStatus,
        tSharedQueuePoolName,
        tSharedQueueParent,
        tSharedQueueLevel,
        tSharedQueueWeight,
        tSharedQueueCIRLevel,
        tSharedQueueCIRWeight,
        tSharedQueueExpedite,
        tSharedQueueCIR,
        tSharedQueuePIR,
        tSharedQueueCBS,
        tSharedQueueMBS,
        tSharedQueueHiPrioOnly,
        tSharedQueueLastChanged,
        tSharedQueueIsMultipoint,
        tSharedQueueTableLastChanged,
        tSharedQueueFCRowStatus,
        tSharedQueueFCQueue,
        tSharedQueueFCLastChanged,
        tSharedQueueFCTableLastChanged,
        tSharedQueueFCMCastQueue,
        tSharedQueueFCBCastQueue,
        tSharedQueueFCUnknownQueue
    }
    STATUS      current
    DESCRIPTION
        "The group of objects supporting management of QoS queue policies
         on Nokia SROS series systems release 4.0."
    ::= { tmnxQosGroups 18 }

tmnxQosSapIngressV4v0Group OBJECT-GROUP
    OBJECTS {
        tSapIngressRowStatus,
        tSapIngressScope,
        tSapIngressDescription,
        tSapIngressDefaultFC,
        tSapIngressDefaultFCPriority,
        tSapIngressMatchCriteria,
        tSapIngressLastChanged,
        tSapIngressTableLastChanged,
        tSapIngressQueueRowStatus,
        tSapIngressQueueParent,
        tSapIngressQueueLevel,
        tSapIngressQueueWeight,
        tSapIngressQueueCIRLevel,
        tSapIngressQueueCIRWeight,
        tSapIngressQueueMCast,
        tSapIngressQueueExpedite,
        tSapIngressQueueCBS,
        tSapIngressQueueMBS,
        tSapIngressQueueHiPrioOnly,
        tSapIngressQueueCIRAdaptation,
        tSapIngressQueuePIRAdaptation,
        tSapIngressQueueAdminPIR,
        tSapIngressQueueAdminCIR,
        tSapIngressQueueLastChanged,
        tSapIngressQueueMode,
        tSapIngressQueueTableLastChanged,
        tSapIngressQueuePoliced,
        tSapIngressDSCPRowStatus,
        tSapIngressDSCPFC,
        tSapIngressDSCPPriority,
        tSapIngressDSCPLastChanged,
        tSapIngressDSCPTableLastChanged,
        tSapIngressDot1pRowStatus,
        tSapIngressDot1pFC,
        tSapIngressDot1pPriority,
        tSapIngressDot1pLastChanged,
        tSapIngressDot1pTableLastChanged,
        tSapIngressIPCriteriaRowStatus,
        tSapIngressIPCriteriaDescription,
        tSapIngressIPCriteriaActionFC,
        tSapIngressIPCriteriaActionPriority,
        tSapIngressIPCriteriaSourceIpAddr,
        tSapIngressIPCriteriaSourceIpMask,
        tSapIngressIPCriteriaDestIpAddr,
        tSapIngressIPCriteriaDestIpMask,
        tSapIngressIPCriteriaProtocol,
        tSapIngressIPCriteriaSourcePortValue1,
        tSapIngressIPCriteriaSourcePortValue2,
        tSapIngressIPCriteriaSourcePortOperator,
        tSapIngressIPCriteriaDestPortValue1,
        tSapIngressIPCriteriaDestPortValue2,
        tSapIngressIPCriteriaDestPortOperator,
        tSapIngressIPCriteriaDSCP,
        tSapIngressIPCriteriaFragment,
        tSapIngressIPCriteriaLastChanged,
        tSapIngressIPCriteriaTableLastChanged,
        tSapIngressMacCriteriaRowStatus,
        tSapIngressMacCriteriaDescription,
        tSapIngressMacCriteriaActionFC,
        tSapIngressMacCriteriaActionPriority,
        tSapIngressMacCriteriaFrameType,
        tSapIngressMacCriteriaSrcMacAddr,
        tSapIngressMacCriteriaSrcMacMask,
        tSapIngressMacCriteriaDstMacAddr,
        tSapIngressMacCriteriaDstMacMask,
        tSapIngressMacCriteriaDot1PValue,
        tSapIngressMacCriteriaDot1PMask,
        tSapIngressMacCriteriaEthernetType,
        tSapIngressMacCriteriaDSAP,
        tSapIngressMacCriteriaDSAPMask,
        tSapIngressMacCriteriaSSAP,
        tSapIngressMacCriteriaSSAPMask,
        tSapIngressMacCriteriaSnapPid,
        tSapIngressMacCriteriaSnapOui,
        tSapIngressMacCriteriaLastChanged,
        tSapIngressMacCriteriaTableLastChanged,
        tSapIngressFCRowStatus,
        tSapIngressFCQueue,
        tSapIngressFCMCastQueue,
        tSapIngressFCBCastQueue,
        tSapIngressFCUnknownQueue,
        tSapIngressFCLastChanged,
        tSapIngressFCInProfRemark,
        tSapIngressFCInProfDscp,
        tSapIngressFCInProfPrec,
        tSapIngressFCOutProfRemark,
        tSapIngressFCOutProfDscp,
        tSapIngressFCOutProfPrec,
        tSapIngressFCProfile,
        tSapIngressFCTableLastChanged,
        tSapIngressPrecRowStatus,
        tSapIngressPrecFC,
        tSapIngressPrecFCPriority,
        tSapIngressPrecLastChanged,
        tSapIngressPrecTableLastChanged
    }
    STATUS      obsolete
    DESCRIPTION
        "The group of objects supporting management of SAP ingress QoS
         policies on Nokia SROS series systems release 4.0."
    ::= { tmnxQosGroups 19 }

tmnxQosSchedulerV5v0Group OBJECT-GROUP
    OBJECTS {
        tSchedulerPolicyRowStatus,
        tSchedulerPolicyDescription,
        tSchedulerPolicyLastChanged,
        tSchedulerPolicyTableLastChanged,
        tVirtualSchedulerRowStatus,
        tVirtualSchedulerDescription,
        tVirtualSchedulerParent,
        tVirtualSchedulerLevel,
        tVirtualSchedulerWeight,
        tVirtualSchedulerCIRLevel,
        tVirtualSchedulerCIRWeight,
        tVirtualSchedulerPIR,
        tVirtualSchedulerCIR,
        tVirtualSchedulerSummedCIR,
        tVirtualSchedulerLastChanged,
        tVirtualSchedulerUsePortParent,
        tVirtualSchedulerPortLvl,
        tVirtualSchedulerPortWght,
        tVirtualSchedulerPortCIRLvl,
        tVirtualSchedulerPortCIRWght,
        tVirtualSchedulerTableLastChanged,
        tPortSchedulerPlcyRowStatus,
        tPortSchedulerPlcyDescription,
        tPortSchedulerPlcyLastChanged,
        tPortSchedulerPlcyMaxRate,
        tPortSchedulerPlcyLvl1PIR,
        tPortSchedulerPlcyLvl1CIR,
        tPortSchedulerPlcyLvl2PIR,
        tPortSchedulerPlcyLvl2CIR,
        tPortSchedulerPlcyLvl3PIR,
        tPortSchedulerPlcyLvl3CIR,
        tPortSchedulerPlcyLvl4PIR,
        tPortSchedulerPlcyLvl4CIR,
        tPortSchedulerPlcyLvl5PIR,
        tPortSchedulerPlcyLvl5CIR,
        tPortSchedulerPlcyLvl6PIR,
        tPortSchedulerPlcyLvl6CIR,
        tPortSchedulerPlcyLvl7PIR,
        tPortSchedulerPlcyLvl7CIR,
        tPortSchedulerPlcyLvl8PIR,
        tPortSchedulerPlcyLvl8CIR,
        tPortSchedulerPlcyOrphanLvl,
        tPortSchedulerPlcyOrphanWeight,
        tPortSchedulerPlcyOrphanCIRLvl,
        tPortSchedulerPlcyOrphanCIRWght
    }
    STATUS      obsolete
    DESCRIPTION
        "The group of objects supporting management of Scheduler policies
         on Nokia SROS series systems."
    ::= { tmnxQosGroups 20 }

tmnxQosSapEgressV5v0Group OBJECT-GROUP
    OBJECTS {
        tSapEgressRowStatus,
        tSapEgressScope,
        tSapEgressDescription,
        tSapEgressLastChanged,
        tSapEgressTableLastChanged,
        tSapEgressQueueRowStatus,
        tSapEgressQueueParent,
        tSapEgressQueueLevel,
        tSapEgressQueueWeight,
        tSapEgressQueueCIRLevel,
        tSapEgressQueueCIRWeight,
        tSapEgressQueueExpedite,
        tSapEgressQueueCBS,
        tSapEgressQueueMBS,
        tSapEgressQueueHiPrioOnly,
        tSapEgressQueueCIRAdaptation,
        tSapEgressQueuePIRAdaptation,
        tSapEgressQueueAdminPIR,
        tSapEgressQueueAdminCIR,
        tSapEgressQueueLastChanged,
        tSapEgressQueueTableLastChanged,
        tSapEgressFCRowStatus,
        tSapEgressFCQueue,
        tSapEgressFCDot1PValue,
        tSapEgressFCLastChanged,
        tSapEgressFCTableLastChanged,
        tSapEgressQueueUsePortParent,
        tSapEgressQueuePortLvl,
        tSapEgressQueuePortWght,
        tSapEgressQueuePortCIRLvl,
        tSapEgressQueuePortCIRWght,
        tSapEgressQueuePortAvgOverhead
    }
    STATUS      obsolete
    DESCRIPTION
        "The group of objects supporting management of SAP egress QoS
         policies on Nokia SROS series systems."
    ::= { tmnxQosGroups 21 }

tmnxQosNetworkV5v0Group OBJECT-GROUP
    OBJECTS {
        tNetworkPolicyRowStatus,
        tNetworkPolicyScope,
        tNetworkPolicyDescription,
        tNetworkPolicyIngressDefaultActionFC,
        tNetworkPolicyIngressDefaultActionProfile,
        tNetworkPolicyEgressRemark,
        tNetworkPolicyLastChanged,
        tNetworkPolicyIngressLerUseDscp,
        tNetworkPolicyTableLastChanged,
        tNetworkIngressDSCPRowStatus,
        tNetworkIngressDSCPFC,
        tNetworkIngressDSCPProfile,
        tNetworkIngressDSCPLastChanged,
        tNetworkIngressDSCPTableLastChanged,
        tNetworkIngressDot1pRowStatus,
        tNetworkIngressDot1pFC,
        tNetworkIngressDot1pProfile,
        tNetworkIngressDot1pLastChanged,
        tNetworkIngressDot1pTableLastChanged,
        tNetworkIngressLSPEXPRowStatus,
        tNetworkIngressLSPEXPFC,
        tNetworkIngressLSPEXPProfile,
        tNetworkIngressLSPEXPLastChanged,
        tNetworkIngressLSPEXPTableLastChanged,
        tNetworkEgressFCDSCPInProfile,
        tNetworkEgressFCDSCPOutProfile,
        tNetworkEgressFCLspExpInProfile,
        tNetworkEgressFCLspExpOutProfile,
        tNetworkEgressFCDot1pInProfile,
        tNetworkEgressFCDot1pOutProfile,
        tNetworkEgressFCLastChanged,
        tNetworkEgressFCTableLastChanged,
        tNetworkQueuePolicyRowStatus,
        tNetworkQueuePolicyDescription,
        tNetworkQueuePolicyLastChanged,
        tNetworkQueuePolicyTableLastChanged,
        tNetworkQueueRowStatus,
        tNetworkQueuePoolName,
        tNetworkQueueParent,
        tNetworkQueueLevel,
        tNetworkQueueWeight,
        tNetworkQueueCIRLevel,
        tNetworkQueueCIRWeight,
        tNetworkQueueMCast,
        tNetworkQueueExpedite,
        tNetworkQueueCIR,
        tNetworkQueuePIR,
        tNetworkQueueCBS,
        tNetworkQueueMBS,
        tNetworkQueueHiPrioOnly,
        tNetworkQueueLastChanged,
        tNetworkQueueUsePortParent,
        tNetworkQueuePortLvl,
        tNetworkQueuePortWght,
        tNetworkQueuePortCIRLvl,
        tNetworkQueuePortCIRWght,
        tNetworkQueuePortAvgOverhead,
        tNetworkQueuePIRAdaptation,       
        tNetworkQueueCIRAdaptation,
        tNetworkQueueTableLastChanged,
        tNetworkQueueFCRowStatus,
        tNetworkQueueFC,
        tNetworkQueueFCMCast,
        tNetworkQueueFCLastChanged,
        tNetworkQueueFCTableLastChanged
    }
    STATUS      obsolete
    DESCRIPTION
        "The group of objects supporting management of Network QoS policies
         on Nokia SROS series systems."
    ::= { tmnxQosGroups 22 }

tmnxQosHsmdaV6v0Group OBJECT-GROUP
    OBJECTS {
        tHsmdaSchedulerPlcyRowStatus,
        tHsmdaSchedulerPlcyDescription,
        tHsmdaSchedulerPlcyMaxRate,
        tHsmdaSchedulerPlcyLvl1Rate,
        tHsmdaSchedulerPlcyLvl1GrpId,
        tHsmdaSchedulerPlcyLvl1WgtInGrp,
        tHsmdaSchedulerPlcyLvl2Rate,
        tHsmdaSchedulerPlcyLvl2GrpId,
        tHsmdaSchedulerPlcyLvl2WgtInGrp,
        tHsmdaSchedulerPlcyLvl3Rate,
        tHsmdaSchedulerPlcyLvl3GrpId,
        tHsmdaSchedulerPlcyLvl3WgtInGrp,
        tHsmdaSchedulerPlcyLvl4Rate,
        tHsmdaSchedulerPlcyLvl4GrpId,
        tHsmdaSchedulerPlcyLvl4WgtInGrp,
        tHsmdaSchedulerPlcyLvl5Rate,
        tHsmdaSchedulerPlcyLvl5GrpId,
        tHsmdaSchedulerPlcyLvl5WgtInGrp,
        tHsmdaSchedulerPlcyLvl6Rate,
        tHsmdaSchedulerPlcyLvl6GrpId,
        tHsmdaSchedulerPlcyLvl6WgtInGrp,
        tHsmdaSchedulerPlcyLvl7Rate,
        tHsmdaSchedulerPlcyLvl7GrpId,
        tHsmdaSchedulerPlcyLvl7WgtInGrp,
        tHsmdaSchedulerPlcyLvl8Rate,
        tHsmdaSchedulerPlcyLvl8GrpId,
        tHsmdaSchedulerPlcyLvl8WgtInGrp,
        tHsmdaSchedulerPlcyLastChanged,
        tHsmdaSchedulerPlcyGrp1Rate,
        tHsmdaSchedulerPlcyGrp2Rate,
        tSapEgressFCHsmdaQueue,
        tSapEgressFCDot1PHsmdaProfile,
        tSapEgressHsmdaQueueRowStatus,
        tSapEgressHsmdaQueueCIRAdaptn,
        tSapEgressHsmdaQueuePIRAdaptn,
        tSapEgressHsmdaQueueAdminPIR,
        tSapEgressHsmdaQueueAdminCIR,
        tSapEgressHsmdaQueueSlopePolicy,
        tSapEgressHsmdaQueueLastChanged,
        tSapIngressHsmdaPacketOffset,
        tSapIngressDefFCHsmdaCntrOvr,
        tSapIngressDot1pHsmdaCntrOvr,
        tSapIngressDSCPHsmdaCntrOvr,
        tSapIngressFCHsmdaQueue,
        tSapIngressFCHsmdaMCastQueue,
        tSapIngressFCHsmdaBCastQueue,
        tSapIngressPrecHsmdaCntrOvr,
        tSapIngressHsmdaQueueRowStatus,
        tSapIngressHsmdaQueueLastChanged,
        tSapIngressHsmdaQueueCIRAdaptn,
        tSapIngressHsmdaQueuePIRAdaptn,
        tSapIngressHsmdaQueueAdminPIR,
        tSapIngressHsmdaQueueAdminCIR,
        tSapIngressHsmdaQueueSlopePolicy,
        tSapIngressHsmdaQueuePoliced,
        tHsmdaPoolPolicyRowStatus,
        tHsmdaPoolLastChanged,
        tHsmdaPoolDescription,
        tHsmdaPoolSystemReserve,
        tHsmdaPoolRoot1AllocWeight,
        tHsmdaPoolRoot2AllocWeight,
        tHsmdaPoolRoot3AllocWeight,
        tHsmdaPoolRoot4AllocWeight,
        tHsmdaPoolRoot5AllocWeight,
        tHsmdaPoolRoot6AllocWeight,
        tHsmdaPoolRoot7AllocWeight,
        tHsmdaPoolRoot8AllocWeight,
        tHsmdaPoolClass1Parent,
        tHsmdaPoolClass1AllocPercent,
        tHsmdaPoolClass2Parent,
        tHsmdaPoolClass2AllocPercent,
        tHsmdaPoolClass3Parent,
        tHsmdaPoolClass3AllocPercent,
        tHsmdaPoolClass4Parent,
        tHsmdaPoolClass4AllocPercent,
        tHsmdaPoolClass5Parent,
        tHsmdaPoolClass5AllocPercent,
        tHsmdaPoolClass6Parent,
        tHsmdaPoolClass6AllocPercent,
        tHsmdaPoolClass7Parent,
        tHsmdaPoolClass7AllocPercent,
        tHsmdaPoolClass8Parent,
        tHsmdaPoolClass8AllocPercent,
        tHsmdaSlopePolicyRowStatus,
        tHsmdaSlopeLastChanged,
        tHsmdaSlopeDescription,
        tHsmdaSlopeQueueMbs,
        tHsmdaSlopeHiAdminStatus,
        tHsmdaSlopeHiStartDepth,
        tHsmdaSlopeHiMaxDepth,
        tHsmdaSlopeHiMaxProbability,
        tHsmdaSlopeLoAdminStatus,
        tHsmdaSlopeLoStartDepth,
        tHsmdaSlopeLoMaxDepth,
        tHsmdaSlopeLoMaxProbability,
        tSapIngrHsmdaQueueTblLastChngd,
        tSapEgrHsmdaQueueTblLastChngd,
        tHsmdaSchedPlcyTblLastChngd,
        tHsmdaSchedPlcyGrpTblLastChngd,
        tHsmdaPoolPlcyTblLastChngd,
        tHsmdaSlopePolicyTableLastChanged,
        tSapIngressIPCritHsmdaCntrOvr,
        tSapEgressDSCPRowStatus,
        tSapEgressDSCPLastChanged,
        tSapEgressDSCPHsmdaCntrOverride,
        tSapEgressPrecRowStatus,
        tSapEgressPrecLastChanged,
        tSapEgressPrecHsmdaCntrOverride,
        tSapEgrIPCritRowStatus,
        tSapEgrIPCritLastChanged,
        tSapEgrIPCritDescription,
        tSapEgrIPCritActionHsmdaCntrOvr,
        tSapEgrIPCritSourceIpAddrType,
        tSapEgrIPCritSourceIpAddr,
        tSapEgrIPCritSourceIpMask,
        tSapEgrIPCritDestIpAddrType,
        tSapEgrIPCritDestIpAddr,
        tSapEgrIPCritDestIpMask,
        tSapEgrIPCritProtocol,
        tSapEgrIPCritSourcePortValue1,
        tSapEgrIPCritSourcePortValue2,
        tSapEgrIPCritSourcePortOperator,
        tSapEgrIPCritDestPortValue1,
        tSapEgrIPCritDestPortValue2,
        tSapEgrIPCritDestPortOperator,
        tSapEgrIPCritDSCP,
        tSapEgrIPCritFragment,
        tSapEgressMatchCriteria,
        tSapEgressHsmdaPacketOffset
   }
    STATUS      obsolete
    DESCRIPTION
        "The group of objects supporting management of QoS policies 
         for HSMDA MDAs on Nokia SROS series systems release 6.0."
    ::= { tmnxQosGroups 23 }

tmnxQosAtmTdpV5v0Group OBJECT-GROUP
    OBJECTS   {
        tAtmTdpSir,
        tAtmTdpPir,
        tAtmTdpMbs,
        tAtmTdpMir,
        tAtmTdpShaping,
        tAtmTdpServCat,
        tAtmTdpLastChanged,
        tAtmTdpDescription,
        tAtmTdpRowStatus,
        tAtmTdpDescrType,
        tAtmTdpCdvt,
        tAtmTdpPolicing,
        tAtmTdpCLPTagging,
        tAtmTdpIndexNext,
        tAtmTdpsMaxSupported,
        tAtmTdpsCurrentlyConfigured,
        tAtmTdpTableLastChanged
    }
    STATUS    current
    DESCRIPTION
        "The group of objects for ATM Traffic Descriptor Profiles
         on Nokia SROS series systems release 5.0."
    ::= { tmnxQosGroups 24 }

tmnxQosSapIngressV6v0Group OBJECT-GROUP
    OBJECTS {
        tSapIngressRowStatus,
        tSapIngressScope,
        tSapIngressDescription,
        tSapIngressDefaultFC,
        tSapIngressDefaultFCPriority,
        tSapIngressMatchCriteria,
        tSapIngressLastChanged,
        tSapIngressTableLastChanged,
        tSapIngressQueueRowStatus,
        tSapIngressQueueParent,
        tSapIngressQueueLevel,
        tSapIngressQueueWeight,
        tSapIngressQueueCIRLevel,
        tSapIngressQueueCIRWeight,
        tSapIngressQueueMCast,
        tSapIngressQueueExpedite,
        tSapIngressQueueCBS,
        tSapIngressQueueMBS,
        tSapIngressQueueHiPrioOnly,
        tSapIngressQueueCIRAdaptation,
        tSapIngressQueuePIRAdaptation,
        tSapIngressQueueAdminPIR,
        tSapIngressQueueAdminCIR,
        tSapIngressQueueLastChanged,
        tSapIngressQueueMode,
        tSapIngressQueuePoolName,
        tSapIngressQueueTableLastChanged,
        tSapIngressQueuePoliced,
        tSapIngressDSCPRowStatus,
        tSapIngressDSCPFC,
        tSapIngressDSCPPriority,
        tSapIngressDSCPLastChanged,
        tSapIngressDSCPTableLastChanged,
        tSapIngressDot1pRowStatus,
        tSapIngressDot1pFC,
        tSapIngressDot1pPriority,
        tSapIngressDot1pLastChanged,
        tSapIngressDot1pTableLastChanged,
        tSapIngressIPCriteriaRowStatus,
        tSapIngressIPCriteriaDescription,
        tSapIngressIPCriteriaActionFC,
        tSapIngressIPCriteriaActionPriority,
        tSapIngressIPCriteriaSourceIpAddr,
        tSapIngressIPCriteriaSourceIpMask,
        tSapIngressIPCriteriaDestIpAddr,
        tSapIngressIPCriteriaDestIpMask,
        tSapIngressIPCriteriaProtocol,
        tSapIngressIPCriteriaSourcePortValue1,
        tSapIngressIPCriteriaSourcePortValue2,
        tSapIngressIPCriteriaSourcePortOperator,
        tSapIngressIPCriteriaDestPortValue1,
        tSapIngressIPCriteriaDestPortValue2,
        tSapIngressIPCriteriaDestPortOperator,
        tSapIngressIPCriteriaDSCP,
        tSapIngressIPCriteriaFragment,
        tSapIngressIPCriteriaLastChanged,
        tSapIngressIPCriteriaTableLastChanged,
        tSapIngressMacCriteriaRowStatus,
        tSapIngressMacCriteriaDescription,
        tSapIngressMacCriteriaActionFC,
        tSapIngressMacCriteriaActionPriority,
        tSapIngressMacCriteriaFrameType,
        tSapIngressMacCriteriaSrcMacAddr,
        tSapIngressMacCriteriaSrcMacMask,
        tSapIngressMacCriteriaDstMacAddr,
        tSapIngressMacCriteriaDstMacMask,
        tSapIngressMacCriteriaDot1PValue,
        tSapIngressMacCriteriaDot1PMask,
        tSapIngressMacCriteriaEthernetType,
        tSapIngressMacCriteriaDSAP,
        tSapIngressMacCriteriaDSAPMask,
        tSapIngressMacCriteriaSSAP,
        tSapIngressMacCriteriaSSAPMask,
        tSapIngressMacCriteriaSnapPid,
        tSapIngressMacCriteriaSnapOui,
        tSapIngressMacCriteriaLastChanged,
        tSapIngressMacCriteriaTableLastChanged,
        tSapIngressFCRowStatus,
        tSapIngressFCQueue,
        tSapIngressFCMCastQueue,
        tSapIngressFCBCastQueue,
        tSapIngressFCUnknownQueue,
        tSapIngressFCLastChanged,
        tSapIngressFCInProfRemark,
        tSapIngressFCInProfDscp,
        tSapIngressFCInProfPrec,
        tSapIngressFCDE1OutOfProfile,
        tSapIngressFCOutProfRemark,
        tSapIngressFCOutProfDscp,
        tSapIngressFCOutProfPrec,
        tSapIngressFCProfile,
        tSapIngressFCTableLastChanged,
        tSapIngressPrecRowStatus,
        tSapIngressPrecFC,
        tSapIngressPrecFCPriority,
        tSapIngressPrecLastChanged,
        tSapIngressPrecTableLastChanged
    }
    STATUS      obsolete
    DESCRIPTION
        "The group of objects supporting management of SAP ingress QoS
         policies on Nokia SROS series systems release 6.0."
    ::= { tmnxQosGroups 25 }

tmnxQosSapEgressV6v0Group OBJECT-GROUP
    OBJECTS {
        tSapEgressRowStatus,
        tSapEgressScope,
        tSapEgressDescription,
        tSapEgressLastChanged,
        tSapEgressTableLastChanged,
        tSapEgressQueueRowStatus,
        tSapEgressQueueParent,
        tSapEgressQueueLevel,
        tSapEgressQueueWeight,
        tSapEgressQueueCIRLevel,
        tSapEgressQueueCIRWeight,
        tSapEgressQueueExpedite,
        tSapEgressQueueCBS,
        tSapEgressQueueMBS,
        tSapEgressQueueHiPrioOnly,
        tSapEgressQueueCIRAdaptation,
        tSapEgressQueuePIRAdaptation,
        tSapEgressQueueAdminPIR,
        tSapEgressQueueAdminCIR,
        tSapEgressQueueLastChanged,
        tSapEgressQueueTableLastChanged,
        tSapEgressFCRowStatus,
        tSapEgressFCQueue,
        tSapEgressFCLastChanged,
        tSapEgressFCTableLastChanged,
        tSapEgressFCDot1PInProfile,
        tSapEgressFCDot1POutProfile,
        tSapEgressFCForceDEValue,
        tSapEgressFCDEMark,
        tSapEgressFCInProfDscp,
        tSapEgressFCOutProfDscp,
        tSapEgressFCInProfPrec,
        tSapEgressFCOutProfPrec,
        tSapEgressQueueUsePortParent,
        tSapEgressQueuePortLvl,
        tSapEgressQueuePortWght,
        tSapEgressQueuePortCIRLvl,
        tSapEgressQueuePortCIRWght,
        tSapEgressQueuePortAvgOverhead,
        tSapEgressQueuePoolName
    }
    STATUS      obsolete
    DESCRIPTION
        "The group of objects supporting management of SAP egress QoS
         policies on Nokia SROS series systems."
    ::= { tmnxQosGroups 26 }

tmnxQosNetworkV6v0Group OBJECT-GROUP
    OBJECTS {
        tNetworkPolicyRowStatus,
        tNetworkPolicyScope,
        tNetworkPolicyDescription,
        tNetworkPolicyIngressDefaultActionFC,
        tNetworkPolicyIngressDefaultActionProfile,
        tNetworkPolicyEgressRemark,
        tNetworkPolicyLastChanged,
        tNetworkPolicyIngressLerUseDscp,
        tNetworkPolicyTableLastChanged,
        tNetworkIngressDSCPRowStatus,
        tNetworkIngressDSCPFC,
        tNetworkIngressDSCPProfile,
        tNetworkIngressDSCPLastChanged,
        tNetworkIngressDSCPTableLastChanged,
        tNetworkIngressDot1pRowStatus,
        tNetworkIngressDot1pFC,
        tNetworkIngressDot1pProfile,
        tNetworkIngressDot1pLastChanged,
        tNetworkIngressDot1pTableLastChanged,
        tNetworkIngressLSPEXPRowStatus,
        tNetworkIngressLSPEXPFC,
        tNetworkIngressLSPEXPProfile,
        tNetworkIngressLSPEXPLastChanged,
        tNetworkIngressLSPEXPTableLastChanged,
        tNetworkEgressFCDSCPInProfile,
        tNetworkEgressFCDSCPOutProfile,
        tNetworkEgressFCLspExpInProfile,
        tNetworkEgressFCLspExpOutProfile,
        tNetworkEgressFCDot1pInProfile,
        tNetworkEgressFCDot1pOutProfile,
        tNetworkEgressFCLastChanged,
        tNetworkEgressFCForceDEValue,
        tNetworkEgressFCDEMark,
        tNetworkEgressFCTableLastChanged,
        tNetworkQueuePolicyRowStatus,
        tNetworkQueuePolicyDescription,
        tNetworkQueuePolicyLastChanged,
        tNetworkQueuePolicyTableLastChanged,
        tNetworkQueueRowStatus,
        tNetworkQueuePoolName,
        tNetworkQueueParent,
        tNetworkQueueLevel,
        tNetworkQueueWeight,
        tNetworkQueueCIRLevel,
        tNetworkQueueCIRWeight,
        tNetworkQueueMCast,
        tNetworkQueueExpedite,
        tNetworkQueueCIR,
        tNetworkQueuePIR,
        tNetworkQueueCBS,
        tNetworkQueueMBS,
        tNetworkQueueHiPrioOnly,
        tNetworkQueueLastChanged,
        tNetworkQueueUsePortParent,
        tNetworkQueuePortLvl,
        tNetworkQueuePortWght,
        tNetworkQueuePortCIRLvl,
        tNetworkQueuePortCIRWght,
        tNetworkQueuePortAvgOverhead,
        tNetworkQueuePIRAdaptation,       
        tNetworkQueueCIRAdaptation,
        tNetworkQueueTableLastChanged,
        tNetworkQueueFCRowStatus,
        tNetworkQueueFC,
        tNetworkQueueFCMCast,
        tNetworkQueueFCLastChanged,
        tNetworkQueueFCTableLastChanged
    }
    STATUS      obsolete
    DESCRIPTION
        "The group of objects supporting management of Network QoS policies
         on Nokia SROS series systems."
    ::= { tmnxQosGroups 27 }

tmnxQosFrameBasedV6v0Group OBJECT-GROUP
    OBJECTS {
        tSchedulerPolicyFrameBasedAccnt
   }
    STATUS      current
    DESCRIPTION
        "The group of objects supporting management of frame-based queue
         accounting on Nokia SROS series systems release 6.0."
    ::= { tmnxQosGroups 28 }

tmnxQosObsoletedV6v0Group OBJECT-GROUP
    OBJECTS {
        tSapEgressFCDot1PValue
    }
    STATUS      current
    DESCRIPTION
        "The group of obsolete objects for the QoS on
         Nokia SROS series systems."
    ::= { tmnxQosGroups 29 }

tmnxQosNamedPoolPolicyV6v0Group OBJECT-GROUP
    OBJECTS {
        tNamedPoolPolicyTableLastChanged,
        tNamedPoolPolicyRowStatus,
        tNamedPoolPolicyLastChanged,
        tNamedPoolPolicyDescription,
        tNamedPoolPolicyQ1DefaultWeight,
        tNamedPoolPolicyQ1MdaWeight,
        tNamedPoolPolicyQ1PortWeight,
        tQ1NamedPoolTableLastChanged,
        tQ1NamedPoolRowStatus,
        tQ1NamedPoolLastChanged,
        tQ1NamedPoolDescription,
        tQ1NamedPoolNetworkAllocWeight,
        tQ1NamedPoolAccessAllocWeight,
        tQ1NamedPoolSlopePolicy,
        tQ1NamedPoolReservedCbs
    }
    STATUS      current
    DESCRIPTION
        "The group of objects for the named pool policy on
         Nokia SROS series systems."
    ::= { tmnxQosGroups 30 }

tmnxQosMcMlpppIngrGroup OBJECT-GROUP
    OBJECTS {
        tMcMlpppIngrProfDescription,
        tMcMlpppIngrProfLastChanged,
        tMcMlpppIngrProfRowStatus,
        tMcMlpppIngrProfTableLastChanged,
        tMcMlpppIngrClassReassemblyTmout,
        tMcMlpppIngrClassLastChanged,
        tMcMlpppIngrClassTableLastChanged
    }
    STATUS      current
    DESCRIPTION
        "The group of objects for the multi-class mlppp ingress information on
         Nokia SROS series systems."
    ::= { tmnxQosGroups 31 }

tmnxQosMcMlpppEgrGroup OBJECT-GROUP
    OBJECTS {
        tMcMlpppEgrProfDescription,
        tMcMlpppEgrProfLastChanged,
        tMcMlpppEgrProfRowStatus,       
        tMcMlpppEgrProfTableLastChanged,
        tMcMlpppEgrClassMir,
        tMcMlpppEgrClassWeight,
        tMcMlpppEgrClassMaxSize,
        tMcMlpppEgrClassLastChanged,        
        tMcMlpppEgrClassTableLastChanged,
        tMcMlpppEgrFCClass,
        tMcMlpppEgrFCLastChanged,
        tMcMlpppEgrFCTableLastChanged
    }
    STATUS      current
    DESCRIPTION
        "The group of objects for the multi-class mlppp egress information on
         Nokia SROS series systems."
    ::= { tmnxQosGroups 32 }

tmnxQosQueueObjGroup OBJECT-GROUP
    OBJECTS {
       tQosEgrQGroupDescr,
       tQosEgrQGroupLastChanged,
       tQosEgrQGroupRowStatus,
       tQosEgrQGroupTableLastChanged,
       tQosEgrQTableLastChanged,
       tQosEgrQueueAdminCIR,  
       tQosEgrQueueAdminPIR,  
       tQosEgrQueueCBS,  
       tQosEgrQueueCIRAdaptation,  
       tQosEgrQueueCIRLevel,  
       tQosEgrQueueCIRWeight,  
       tQosEgrQueueExpedite,  
       tQosEgrQueueHiPrioOnly,  
       tQosEgrQueueLastChanged,  
       tQosEgrQueueLevel,  
       tQosEgrQueueMBS,  
       tQosEgrQueuePIRAdaptation,  
       tQosEgrQueueParent,  
       tQosEgrQueuePoolName,  
       tQosEgrQueuePortCIRLvl,  
       tQosEgrQueuePortCIRWght,  
       tQosEgrQueuePortLvl,  
       tQosEgrQueuePortWght,  
       tQosEgrQueueRowStatus,  
       tQosEgrQueueUsePortParent,  
       tQosEgrQueueWeight,  
       tQosIngQTableLastChanged,
       tQosIngQGroupDescr,
       tQosIngQGroupLastChanged,
       tQosIngQGroupRowStatus,
       tQosIngQGroupTableLastChanged,
       tQosIngQueueAdminCIR,
       tQosIngQueueAdminPIR,
       tQosIngQueueCBS,
       tQosIngQueueCIRAdaptation,
       tQosIngQueueCIRLevel,
       tQosIngQueueCIRWeight,
       tQosIngQueueExpedite,
       tQosIngQueueHiPrioOnly,
       tQosIngQueueLastChanged,
       tQosIngQueueLevel,
       tQosIngQueueMBS,
       tQosIngQueueMCast,
       tQosIngQueueMode,
       tQosIngQueuePIRAdaptation,
       tQosIngQueueParent,
       tQosIngQueuePoliced,
       tQosIngQueuePoolName,
       tQosIngQueueRowStatus,
       tQosIngQueueWeight
       }
    STATUS      obsolete
    DESCRIPTION
        "The group of objects for the multi-class mlppp egress information on
         Nokia SROS series systems."
    ::= { tmnxQosGroups 33 }

tQosQGrpFCGroup OBJECT-GROUP
    OBJECTS {
        tSapIngressFCQGrp,
        tSapIngressFCQGrpMCast,
        tSapIngressFCQGrpBCast,
        tSapIngressFCQGrpUnknown,
        tSapEgressFCQGrp,
        tNetworkEgressFCQGrpQueue
        }
    STATUS      current
    DESCRIPTION
        "The group of objects for the multi-class mlppp egress information on
         Nokia SROS series systems."
    ::= { tmnxQosGroups 34 }

tmnxQosNetworkV7v0Group OBJECT-GROUP
    OBJECTS {
        tNetworkPolicyRowStatus,
        tNetworkPolicyScope,
        tNetworkPolicyDescription,
        tNetworkPolicyIngressDefaultActionFC,
        tNetworkPolicyIngressDefaultActionProfile,
        tNetworkPolicyEgressRemark,
        tNetworkPolicyLastChanged,
        tNetworkPolicyIngressLerUseDscp,
        tNetworkPolicyEgressRemarkDscp,
        tNetworkPolicyTableLastChanged,
        tNetworkIngressDSCPRowStatus,
        tNetworkIngressDSCPFC,
        tNetworkIngressDSCPProfile,
        tNetworkIngressDSCPLastChanged,
        tNetworkIngressDSCPTableLastChanged,
        tNetworkIngressDot1pRowStatus,
        tNetworkIngressDot1pFC,
        tNetworkIngressDot1pProfile,
        tNetworkIngressDot1pLastChanged,
        tNetworkIngressDot1pTableLastChanged,
        tNetworkIngressLSPEXPRowStatus,
        tNetworkIngressLSPEXPFC,
        tNetworkIngressLSPEXPProfile,
        tNetworkIngressLSPEXPLastChanged,
        tNetworkIngressLSPEXPTableLastChanged,
        tNetworkEgressFCDSCPInProfile,
        tNetworkEgressFCDSCPOutProfile,
        tNetworkEgressFCLspExpInProfile,
        tNetworkEgressFCLspExpOutProfile,
        tNetworkEgressFCDot1pInProfile,
        tNetworkEgressFCDot1pOutProfile,
        tNetworkEgressFCLastChanged,
        tNetworkEgressFCForceDEValue,
        tNetworkEgressFCDEMark,
        tNetworkEgressFCTableLastChanged,
        tNetworkQueuePolicyRowStatus,
        tNetworkQueuePolicyDescription,
        tNetworkQueuePolicyLastChanged,
        tNetworkQueuePolicyTableLastChanged,
        tNetworkQueueRowStatus,
        tNetworkQueuePoolName,
        tNetworkQueueParent,
        tNetworkQueueLevel,
        tNetworkQueueWeight,
        tNetworkQueueCIRLevel,
        tNetworkQueueCIRWeight,
        tNetworkQueueMCast,
        tNetworkQueueExpedite,
        tNetworkQueueCIR,
        tNetworkQueuePIR,
        tNetworkQueueCBS,
        tNetworkQueueMBS,
        tNetworkQueueHiPrioOnly,
        tNetworkQueueLastChanged,
        tNetworkQueueUsePortParent,
        tNetworkQueuePortLvl,
        tNetworkQueuePortWght,
        tNetworkQueuePortCIRLvl,
        tNetworkQueuePortCIRWght,
        tNetworkQueuePortAvgOverhead,
        tNetworkQueuePIRAdaptation,       
        tNetworkQueueCIRAdaptation,
        tNetworkQueueTableLastChanged,
        tNetworkQueueFCRowStatus,
        tNetworkQueueFC,
        tNetworkQueueFCMCast,
        tNetworkQueueFCLastChanged,
        tNetworkQueueFCTableLastChanged
    }
    STATUS      current
    DESCRIPTION
        "The group of objects supporting management of Network QoS policies
         on Nokia SROS series systems."
    ::= { tmnxQosGroups 35 }

tmnxQosHsmdaV7v0Group OBJECT-GROUP
    OBJECTS {
        tHsmdaSchedulerPlcyRowStatus,
        tHsmdaSchedulerPlcyDescription,
        tHsmdaSchedulerPlcyMaxRate,
        tHsmdaSchedulerPlcyLvl1Rate,
        tHsmdaSchedulerPlcyLvl1GrpId,
        tHsmdaSchedulerPlcyLvl1WgtInGrp,
        tHsmdaSchedulerPlcyLvl2Rate,
        tHsmdaSchedulerPlcyLvl2GrpId,
        tHsmdaSchedulerPlcyLvl2WgtInGrp,
        tHsmdaSchedulerPlcyLvl3Rate,
        tHsmdaSchedulerPlcyLvl3GrpId,
        tHsmdaSchedulerPlcyLvl3WgtInGrp,
        tHsmdaSchedulerPlcyLvl4Rate,
        tHsmdaSchedulerPlcyLvl4GrpId,
        tHsmdaSchedulerPlcyLvl4WgtInGrp,
        tHsmdaSchedulerPlcyLvl5Rate,
        tHsmdaSchedulerPlcyLvl5GrpId,
        tHsmdaSchedulerPlcyLvl5WgtInGrp,
        tHsmdaSchedulerPlcyLvl6Rate,
        tHsmdaSchedulerPlcyLvl6GrpId,
        tHsmdaSchedulerPlcyLvl6WgtInGrp,
        tHsmdaSchedulerPlcyLvl7Rate,
        tHsmdaSchedulerPlcyLvl7GrpId,
        tHsmdaSchedulerPlcyLvl7WgtInGrp,
        tHsmdaSchedulerPlcyLvl8Rate,
        tHsmdaSchedulerPlcyLvl8GrpId,
        tHsmdaSchedulerPlcyLvl8WgtInGrp,
        tHsmdaSchedulerPlcyLastChanged,
        tHsmdaSchedulerPlcyGrp1Rate,
        tHsmdaSchedulerPlcyGrp2Rate,
        tSapEgressFCHsmdaQueue,
        tSapEgressHsmdaQueueRowStatus,
        tSapEgressHsmdaQueueCIRAdaptn,
        tSapEgressHsmdaQueuePIRAdaptn,
        tSapEgressHsmdaQueueAdminPIR,
        tSapEgressHsmdaQueueAdminCIR,
        tSapEgressHsmdaQueueSlopePolicy,
        tSapEgressHsmdaQueueLastChanged,
        tSapIngressHsmdaPacketOffset,
        tSapIngressDefFCHsmdaCntrOvr,
        tSapIngressDot1pHsmdaCntrOvr,
        tSapIngressDSCPHsmdaCntrOvr,
        tSapIngressFCHsmdaQueue,
        tSapIngressFCHsmdaMCastQueue,
        tSapIngressFCHsmdaBCastQueue,
        tSapIngressPrecHsmdaCntrOvr,
        tSapIngressHsmdaQueueRowStatus,
        tSapIngressHsmdaQueueLastChanged,
        tSapIngressHsmdaQueueCIRAdaptn,
        tSapIngressHsmdaQueuePIRAdaptn,
        tSapIngressHsmdaQueueAdminPIR,
        tSapIngressHsmdaQueueAdminCIR,
        tSapIngressHsmdaQueueSlopePolicy,
        tSapIngressHsmdaQueuePoliced,
        tHsmdaPoolPolicyRowStatus,
        tHsmdaPoolLastChanged,
        tHsmdaPoolDescription,
        tHsmdaPoolSystemReserve,
        tHsmdaPoolRoot1AllocWeight,
        tHsmdaPoolRoot2AllocWeight,
        tHsmdaPoolRoot3AllocWeight,
        tHsmdaPoolRoot4AllocWeight,
        tHsmdaPoolRoot5AllocWeight,
        tHsmdaPoolRoot6AllocWeight,
        tHsmdaPoolRoot7AllocWeight,
        tHsmdaPoolRoot8AllocWeight,
        tHsmdaPoolClass1Parent,
        tHsmdaPoolClass1AllocPercent,
        tHsmdaPoolClass2Parent,
        tHsmdaPoolClass2AllocPercent,
        tHsmdaPoolClass3Parent,
        tHsmdaPoolClass3AllocPercent,
        tHsmdaPoolClass4Parent,
        tHsmdaPoolClass4AllocPercent,
        tHsmdaPoolClass5Parent,
        tHsmdaPoolClass5AllocPercent,
        tHsmdaPoolClass6Parent,
        tHsmdaPoolClass6AllocPercent,
        tHsmdaPoolClass7Parent,
        tHsmdaPoolClass7AllocPercent,
        tHsmdaPoolClass8Parent,
        tHsmdaPoolClass8AllocPercent,
        tHsmdaSlopePolicyRowStatus,
        tHsmdaSlopeLastChanged,
        tHsmdaSlopeDescription,
        tHsmdaSlopeQueueMbs,
        tHsmdaSlopeHiAdminStatus,
        tHsmdaSlopeHiStartDepth,
        tHsmdaSlopeHiMaxDepth,
        tHsmdaSlopeHiMaxProbability,
        tHsmdaSlopeLoAdminStatus,
        tHsmdaSlopeLoStartDepth,
        tHsmdaSlopeLoMaxDepth,
        tHsmdaSlopeLoMaxProbability,
        tSapIngrHsmdaQueueTblLastChngd,
        tSapEgrHsmdaQueueTblLastChngd,
        tHsmdaSchedPlcyTblLastChngd,
        tHsmdaSchedPlcyGrpTblLastChngd,
        tHsmdaPoolPlcyTblLastChngd,
        tHsmdaSlopePolicyTableLastChanged,
        tSapIngressIPCritHsmdaCntrOvr,
        tSapEgressDSCPRowStatus,
        tSapEgressDSCPLastChanged,
        tSapEgressDSCPHsmdaCntrOverride,
        tSapEgressPrecRowStatus,
        tSapEgressPrecLastChanged,
        tSapEgressPrecHsmdaCntrOverride,
        tSapEgrIPCritRowStatus,
        tSapEgrIPCritLastChanged,
        tSapEgrIPCritDescription,
        tSapEgrIPCritActionHsmdaCntrOvr,
        tSapEgrIPCritSourceIpAddrType,
        tSapEgrIPCritSourceIpAddr,
        tSapEgrIPCritSourceIpMask,
        tSapEgrIPCritDestIpAddrType,
        tSapEgrIPCritDestIpAddr,
        tSapEgrIPCritDestIpMask,
        tSapEgrIPCritProtocol,
        tSapEgrIPCritSourcePortValue1,
        tSapEgrIPCritSourcePortValue2,
        tSapEgrIPCritSourcePortOperator,
        tSapEgrIPCritDestPortValue1,
        tSapEgrIPCritDestPortValue2,
        tSapEgrIPCritDestPortOperator,
        tSapEgrIPCritDSCP,
        tSapEgrIPCritFragment,
        tSapEgressMatchCriteria,
        tSapEgressHsmdaPacketOffset,
        tSapEgrIPCritActionFC,
        tSapEgrIPCritActionProfile,
        tSapEgressDSCPfc,
        tSapEgressDSCPprofile,
        tSapEgressPrecFC,
        tSapEgressPrecProfile
   }
    STATUS      obsolete
    DESCRIPTION
        "The group of objects supporting management of QoS policies 
         for QMDA MDAs on Nokia SROS series systems release 7.0."
    ::= { tmnxQosGroups 36 }

tmnxQosSapAtmV7v0Group OBJECT-GROUP
    OBJECTS {
        tSapIngressMacCriteriaAtmVci
    }
    STATUS      current
    DESCRIPTION
        "The group of objects supporting management of SAP ATM related
         QoS policies for Nokia SROS series systems release 7.0."
    ::= { tmnxQosGroups 37 }
    
tmnxQosMcFrIngrGroup OBJECT-GROUP
    OBJECTS {
        tMcFrIngrProfDescription,
        tMcFrIngrProfLastChanged,
        tMcFrIngrProfRowStatus,
        tMcFrIngrProfTableLastChanged,
        tMcFrIngrClassReassemblyTmout,
        tMcFrIngrClassLastChanged,
        tMcFrIngrClassTableLastChanged
    }
    STATUS      current
    DESCRIPTION
        "The group of objects for the multi-class Fr ingress information on
         Nokia SROS series systems."
    ::= { tmnxQosGroups 38 }

tmnxQosMcFrEgrGroup OBJECT-GROUP
    OBJECTS {
        tMcFrEgrProfDescription,
        tMcFrEgrProfLastChanged,
        tMcFrEgrProfRowStatus,       
        tMcFrEgrProfTableLastChanged,
        tMcFrEgrClassMir,
        tMcFrEgrClassWeight,
        tMcFrEgrClassMaxSize,
        tMcFrEgrClassLastChanged,        
        tMcFrEgrClassTableLastChanged
    }
    STATUS      current
    DESCRIPTION
        "The group of objects for the multi-class Fr egress information on
         Nokia SROS series systems."
    ::= { tmnxQosGroups 39 }
    
tmnxQosSapEgrQWredGroup OBJECT-GROUP
    OBJECTS {
        tSapEgressQueueXPWredQ,
        tSapEgressQueueXPWredQSlope,
        tQosEgrQueueXPWredQ,
        tQosEgrQueueXPWredQSlope
    }
    STATUS      current
    DESCRIPTION
        "The group of objects for the WRED specific SAP egress queue
        information on Nokia SROS series systems."
    ::= { tmnxQosGroups 40 }

tmnxQosSapIngressV8v0Group OBJECT-GROUP
    OBJECTS {
        tSapIngressRowStatus,
        tSapIngressScope,
        tSapIngressDescription,
        tSapIngressDefaultFC,
        tSapIngressDefaultFCPriority,
        tSapIngressMatchCriteria,
        tSapIngressLastChanged,
        tSapIngressTableLastChanged,
        tSapIngressQueueRowStatus,
        tSapIngressQueueParent,
        tSapIngressQueueLevel,
        tSapIngressQueueWeight,
        tSapIngressQueueCIRLevel,
        tSapIngressQueueCIRWeight,
        tSapIngressQueueMCast,
        tSapIngressQueueExpedite,
        tSapIngressQueueCBS,
        tSapIngressQueueHiPrioOnly,
        tSapIngressQueueCIRAdaptation,
        tSapIngressQueuePIRAdaptation,
        tSapIngressQueueAdminPIR,
        tSapIngressQueueAdminCIR,
        tSapIngressQueueLastChanged,
        tSapIngressQueueMode,
        tSapIngressQueuePoolName,
        tSapIngressQueueTableLastChanged,
        tSapIngressQueuePoliced,
        tSapIngressDSCPRowStatus,
        tSapIngressDSCPFC,
        tSapIngressDSCPPriority,
        tSapIngressDSCPLastChanged,
        tSapIngressDSCPTableLastChanged,
        tSapIngressDot1pRowStatus,
        tSapIngressDot1pFC,
        tSapIngressDot1pPriority,
        tSapIngressDot1pLastChanged,
        tSapIngressDot1pTableLastChanged,
        tSapIngressIPCriteriaRowStatus,
        tSapIngressIPCriteriaDescription,
        tSapIngressIPCriteriaActionFC,
        tSapIngressIPCriteriaActionPriority,
        tSapIngressIPCriteriaSourceIpAddr,
        tSapIngressIPCriteriaSourceIpMask,
        tSapIngressIPCriteriaDestIpAddr,
        tSapIngressIPCriteriaDestIpMask,
        tSapIngressIPCriteriaProtocol,
        tSapIngressIPCriteriaSourcePortValue1,
        tSapIngressIPCriteriaSourcePortValue2,
        tSapIngressIPCriteriaSourcePortOperator,
        tSapIngressIPCriteriaDestPortValue1,
        tSapIngressIPCriteriaDestPortValue2,
        tSapIngressIPCriteriaDestPortOperator,
        tSapIngressIPCriteriaDSCP,
        tSapIngressIPCriteriaFragment,
        tSapIngressIPCriteriaLastChanged,
        tSapIngressIPCriteriaTableLastChanged,
        tSapIngressMacCriteriaRowStatus,
        tSapIngressMacCriteriaDescription,
        tSapIngressMacCriteriaActionFC,
        tSapIngressMacCriteriaActionPriority,
        tSapIngressMacCriteriaFrameType,
        tSapIngressMacCriteriaSrcMacAddr,
        tSapIngressMacCriteriaSrcMacMask,
        tSapIngressMacCriteriaDstMacAddr,
        tSapIngressMacCriteriaDstMacMask,
        tSapIngressMacCriteriaDot1PValue,
        tSapIngressMacCriteriaDot1PMask,
        tSapIngressMacCriteriaEthernetType,
        tSapIngressMacCriteriaDSAP,
        tSapIngressMacCriteriaDSAPMask,
        tSapIngressMacCriteriaSSAP,
        tSapIngressMacCriteriaSSAPMask,
        tSapIngressMacCriteriaSnapPid,
        tSapIngressMacCriteriaSnapOui,
        tSapIngressMacCriteriaLastChanged,
        tSapIngressMacCriteriaTableLastChanged,
        tSapIngressFCRowStatus,
        tSapIngressFCQueue,
        tSapIngressFCMCastQueue,
        tSapIngressFCBCastQueue,
        tSapIngressFCUnknownQueue,
        tSapIngressFCLastChanged,
        tSapIngressFCInProfRemark,
        tSapIngressFCInProfDscp,
        tSapIngressFCInProfPrec,
        tSapIngressFCDE1OutOfProfile,
        tSapIngressFCOutProfRemark,
        tSapIngressFCOutProfDscp,
        tSapIngressFCOutProfPrec,
        tSapIngressFCProfile,
        tSapIngressFCTableLastChanged,
        tSapIngressPrecRowStatus,
        tSapIngressPrecFC,
        tSapIngressPrecFCPriority,
        tSapIngressPrecLastChanged,
        tSapIngressPrecTableLastChanged,
        tSapIngressLspExpRowStatus,
        tSapIngressLspExpLastChanged,
        tSapIngressLspExpFC,
        tSapIngressLspExpFCPriority,
        tSapIngressLspExpHsmdaCntrOvr,
        tSapIngressLspExpTableLastChange
    }
    STATUS      obsolete
    DESCRIPTION
        "The group of objects supporting management of SAP ingress QoS
         policies on Nokia SROS series systems release 8.0."
    ::= { tmnxQosGroups 41 }

tmnxQosPolicerV8v0Group OBJECT-GROUP
    OBJECTS {
       tQosPolicerCtrlPolDescr,
       tQosPolicerCtrlPolLastChgd,
       tQosPolicerCtrlPolRowStatus,  
       tQosPolicerCtrlPolTblLastChgd,  
       tSapIngPolicerPktOffset,  
       tSapIngPolicerAdminCIR,  
       tSapIngPolicerAdminPIR,  
       tSapIngPolicerCIRAdaptation,  
       tSapIngPolicerDescr,  
       tSapIngPolicerHiPrioOnly,  
       tSapIngPolicerLastChanged,  
       tSapIngPolicerLevel,  
       tSapIngPolicerPIRAdaptation,  
       tSapIngPolicerParent,  
       tSapIngPolicerRowStatus,  
       tSapIngPolicerStatMode,  
       tSapIngPolicerTableLastChanged,  
       tSapIngPolicerCBS,  
       tSapIngPolicerMBS,  
       tSapIngPolicerWeight,  
       tSapEgrPolicerPktOffset,  
       tSapEgrPolicerAdminCIR,  
       tSapEgrPolicerAdminPIR,  
       tSapEgrPolicerCIRAdaptation,  
       tSapEgrPolicerDescr,  
       tSapEgrPolicerHiPrioOnly,  
       tSapEgrPolicerLastChanged,  
       tSapEgrPolicerLevel,  
       tSapEgrPolicerPIRAdaptation,  
       tSapEgrPolicerParent,  
       tSapEgrPolicerRowStatus,  
       tSapEgrPolicerStatMode,  
       tSapEgrPolicerTableLastChanged,  
       tSapEgrPolicerCBS,  
       tSapEgrPolicerMBS,  
       tSapEgrPolicerWeight,  
       tSapIngressFCBCastPolicer,  
       tSapIngressFCMCastPolicer,  
       tSapIngressFCPolicer,  
       tSapIngressFCUnknownPolicer,
       tQosPolicerArbiterDescr, 
       tQosPolicerArbiterLastChgd, 
       tQosPolicerArbiterLevel, 
       tQosPolicerArbiterParent, 
       tQosPolicerArbiterRate, 
       tQosPolicerArbiterRowStatus, 
       tQosPolicerArbiterTblLastChgd, 
       tQosPolicerArbiterWeight, 
       tQosPolicerCtrlPolMinMBSSep, 
       tQosPolicerCtrlPolRootMaxRate, 
       tQosPolicerLevelCumMBS, 
       tQosPolicerLevelLastChgd, 
       tQosPolicerLevelTblLastChgd,
       tSapEgressFCPolicer,
       tQosPolicerLevelFixedMBS
    }
    STATUS      current
    DESCRIPTION
        "The group of objects supporting management of Policer specific
         objects on Nokia SROS series systems release 8.0."
    ::= { tmnxQosGroups 42 }

tQosQGrpV8v0Group OBJECT-GROUP
    OBJECTS {
        tQosEgrQGroupFCRowStatus,
        tQosEgrQGroupFCLastChanged,
        tQosEgrQGroupFCQueue,
        tQosEgrQGroupFCTableLastChanged,
        tQosIngQueueMBSBytes,
        tQosEgrQueueMBSBytes,           
        tSapEgressQueueMBSBytes,
        tSapIngressQueueMBSBytes,
        tQosEgrQueueAdminPIRPercent,
        tQosEgrQueueAdminCIRPercent,
        tQosEgrQueueRateType
    }
    STATUS      current
    DESCRIPTION
        "The group of objects supporting the management of QOS Queue Groups 
         on Nokia SROS series systems release 8.0."
    ::= { tmnxQosGroups 43 }

tQosFCQGrpFC8v0Group OBJECT-GROUP
    OBJECTS {
        tSapEgressFCQGrpFC
        }
    STATUS      current
    DESCRIPTION
        "The group of objects for the SAP egress information on
         Nokia SROS series systems."
    ::= { tmnxQosGroups 44 }

tmnxQosSapEgressV8v0Group OBJECT-GROUP
    OBJECTS {
        tSapEgressRowStatus,
        tSapEgressScope,
        tSapEgressDescription,
        tSapEgressLastChanged,
        tSapEgressTableLastChanged,
        tSapEgressQueueRowStatus,
        tSapEgressQueueParent,
        tSapEgressQueueLevel,
        tSapEgressQueueWeight,
        tSapEgressQueueCIRLevel,
        tSapEgressQueueCIRWeight,
        tSapEgressQueueExpedite,
        tSapEgressQueueCBS,
        tSapEgressQueueHiPrioOnly,
        tSapEgressQueueCIRAdaptation,
        tSapEgressQueuePIRAdaptation,
        tSapEgressQueueAdminPIR,
        tSapEgressQueueAdminCIR,
        tSapEgressQueueLastChanged,
        tSapEgressQueueTableLastChanged,
        tSapEgressFCRowStatus,
        tSapEgressFCQueue,
        tSapEgressFCLastChanged,
        tSapEgressFCTableLastChanged,
        tSapEgressFCDot1PInProfile,
        tSapEgressFCDot1POutProfile,
        tSapEgressFCForceDEValue,
        tSapEgressFCDEMark,
        tSapEgressFCInProfDscp,
        tSapEgressFCOutProfDscp,
        tSapEgressFCInProfPrec,
        tSapEgressFCOutProfPrec,
        tSapEgressQueueUsePortParent,
        tSapEgressQueuePortLvl,
        tSapEgressQueuePortWght,
        tSapEgressQueuePortCIRLvl,
        tSapEgressQueuePortCIRWght,
        tSapEgressQueuePortAvgOverhead,
        tSapEgressQueuePoolName
    }
    STATUS      current
    DESCRIPTION
        "The group of objects supporting management of SAP egress QoS
         policies on Nokia SROS series systems."
    ::= { tmnxQosGroups 45 }

tmnxQosQueueObjV8v0Group OBJECT-GROUP
    OBJECTS {
       tQosEgrQGroupDescr,
       tQosEgrQGroupLastChanged,
       tQosEgrQGroupRowStatus,
       tQosEgrQGroupTableLastChanged,
       tQosEgrQTableLastChanged,
       tQosEgrQueueAdminCIR,  
       tQosEgrQueueAdminPIR,  
       tQosEgrQueueCBS,  
       tQosEgrQueueCIRAdaptation,  
       tQosEgrQueueCIRLevel,  
       tQosEgrQueueCIRWeight,  
       tQosEgrQueueExpedite,  
       tQosEgrQueueHiPrioOnly,  
       tQosEgrQueueLastChanged,  
       tQosEgrQueueLevel,  
       tQosEgrQueuePIRAdaptation,  
       tQosEgrQueueParent,  
       tQosEgrQueuePoolName,  
       tQosEgrQueuePortCIRLvl,  
       tQosEgrQueuePortCIRWght,  
       tQosEgrQueuePortLvl,  
       tQosEgrQueuePortWght,  
       tQosEgrQueueRowStatus,  
       tQosEgrQueueUsePortParent,  
       tQosEgrQueueWeight,  
       tQosIngQTableLastChanged,
       tQosIngQGroupDescr,
       tQosIngQGroupLastChanged,
       tQosIngQGroupRowStatus,
       tQosIngQGroupTableLastChanged,
       tQosIngQueueAdminCIR,
       tQosIngQueueAdminPIR,
       tQosIngQueueCBS,
       tQosIngQueueCIRAdaptation,
       tQosIngQueueCIRLevel,
       tQosIngQueueCIRWeight,
       tQosIngQueueExpedite,
       tQosIngQueueHiPrioOnly,
       tQosIngQueueLastChanged,
       tQosIngQueueLevel,
       tQosIngQueueMCast,
       tQosIngQueueMode,
       tQosIngQueuePIRAdaptation,
       tQosIngQueueParent,
       tQosIngQueuePoliced,
       tQosIngQueuePoolName,
       tQosIngQueueRowStatus,
       tQosIngQueueWeight
       }
    STATUS      current
    DESCRIPTION
        "The group of objects for the multi-class mlppp egress information on
         Nokia SROS series systems."
    ::= { tmnxQosGroups 46 }

tmnxQosObsoletedV8v0Group OBJECT-GROUP
    OBJECTS {
        tSapIngressQueueMBS,
        tSapEgressQueueMBS,
        tQosIngQueueMBS,
        tQosEgrQueueMBS
    }
    STATUS      current
    DESCRIPTION
        "The group of obsolete objects for the QoS on
         Nokia SROS series systems."
    ::= { tmnxQosGroups 47 }

tmnxQosPortSchPlcyGrpGroup OBJECT-GROUP
    OBJECTS {
       tPortSchPlcyLvl1GrpName, 
       tPortSchPlcyLvl1GrpWeight, 
       tPortSchPlcyLvl2GrpName, 
       tPortSchPlcyLvl2GrpWeight, 
       tPortSchPlcyLvl3GrpName, 
       tPortSchPlcyLvl3GrpWeight, 
       tPortSchPlcyLvl4GrpName, 
       tPortSchPlcyLvl4GrpWeight, 
       tPortSchPlcyLvl5GrpName, 
       tPortSchPlcyLvl5GrpWeight, 
       tPortSchPlcyLvl6GrpName, 
       tPortSchPlcyLvl6GrpWeight, 
       tPortSchPlcyLvl7GrpName, 
       tPortSchPlcyLvl7GrpWeight, 
       tPortSchPlcyLvl8GrpName, 
       tPortSchPlcyLvl8GrpWeight, 
       tPortSchPlcyLvlGrpLastChanged, 
       tPortSchPlcyLvlGrpTblLastChgd, 
       tPortSchPlcyGrpAdminCIR, 
       tPortSchPlcyGrpAdminPIR, 
       tPortSchPlcyGrpLastChanged, 
       tPortSchPlcyGrpRowStatus, 
       tPortSchPlcyGrpTblLastChgd
    }
    STATUS      obsolete
    DESCRIPTION
        "The group of objects supporting Port Scheduler Policy Group objects
        for the QoS on Nokia SROS series systems."
    ::= { tmnxQosGroups 48 }

tmnxQosSchedulerV8v0Group OBJECT-GROUP
    OBJECTS {
        tSchedulerPolicyRowStatus,
        tSchedulerPolicyDescription,
        tSchedulerPolicyLastChanged,
        tSchedulerPolicyTableLastChanged,
        tVirtualSchedulerRowStatus,
        tVirtualSchedulerDescription,
        tVirtualSchedulerParent,
        tVirtualSchedulerLevel,
        tVirtualSchedulerWeight,
        tVirtualSchedulerCIRLevel,
        tVirtualSchedulerCIRWeight,
        tVirtualSchedulerPIR,
        tVirtualSchedulerCIR,
        tVirtualSchedulerSummedCIR,
        tVirtualSchedulerLastChanged,
        tVirtualSchedulerUsePortParent,
        tVirtualSchedulerPortLvl,
        tVirtualSchedulerPortWght,
        tVirtualSchedulerPortCIRLvl,
        tVirtualSchedulerPortCIRWght,
        tVirtualSchedulerTableLastChanged,
        tPortSchedulerPlcyRowStatus,
        tPortSchedulerPlcyDescription,
        tPortSchedulerPlcyLastChanged,
        tPortSchedulerPlcyMaxRate,
        tPortSchedulerPlcyOrphanLvl,
        tPortSchedulerPlcyOrphanWeight,
        tPortSchedulerPlcyOrphanCIRLvl,
        tPortSchedulerPlcyOrphanCIRWght
    }
    STATUS      obsolete
    DESCRIPTION
        "The group of objects supporting management of Scheduler policies
         on Nokia SROS series systems."
    ::= { tmnxQosGroups 49 }

tmnxQosBurstLimitGroup OBJECT-GROUP
    OBJECTS {
        tSapIngressQueueBurstLimit,
        tSapEgressQueueBurstLimit,
        tQosIngQueueBurstLimit,
        tQosEgrQueueBurstLimit
    }
    STATUS      current
    DESCRIPTION
        "The group of objects supporting Burst-size management objects
        for the QoS on Nokia SROS series systems."
    ::= { tmnxQosGroups 50 }

tmnxQosMacCritVidFltrV9v0Group OBJECT-GROUP
    OBJECTS {
        tSapIngressMacCritInnerTagValue, 
        tSapIngressMacCritInnerTagMask,  
        tSapIngressMacCritOuterTagValue, 
        tSapIngressMacCritOuterTagMask,     
        tSapIngressMacCritType  
    }
    STATUS    current
    DESCRIPTION
     "The group of objects supporting management of mac VID filtering objects
     on Nokia SROS series systems 9.0 release."
    ::= { tmnxQosGroups 51 }

tmnxQosSapEgressV9v0Group OBJECT-GROUP
    OBJECTS {
        tSapEgressQueuePktOffset,
        tSapEgressQueueAdminPIRPercent,
        tSapEgressQueueAdminCIRPercent,
        tSapEgressQueueRateType
    }
    STATUS      current
    DESCRIPTION
        "The group of objects supporting management of SAP egress QoS
         policies on Nokia SROS series systems 9.0 release."
    ::= { tmnxQosGroups 52 }

tmnxQosSapIngressV9v0Group OBJECT-GROUP
    OBJECTS {
        tSapIngressQueueAdminPIRPercent,
        tSapIngressQueueAdminCIRPercent,
        tSapIngressQueueRateType
    }
    STATUS      current
    DESCRIPTION
        "The group of objects supporting management of SAP ingress QoS
         policies on Nokia SROS series systems 9.0 release."
    ::= { tmnxQosGroups 53 }

tmnxQosPolicerV9v0Group OBJECT-GROUP
    OBJECTS {
        tSapIngPolicerAdminCIRPercent,  
        tSapIngPolicerAdminPIRPercent,
        tSapIngPolicerRateType,  
        tSapEgrPolicerAdminCIRPercent,  
        tSapEgrPolicerAdminPIRPercent,
        tSapEgrPolicerRateType  
    }
    STATUS      current
    DESCRIPTION
        "The group of objects supporting management of Policer specific
         objects on Nokia SROS series systems release 9.0."
    ::= { tmnxQosGroups 54 }
    
tmnxQosAtmTdpV9v0Group OBJECT-GROUP
    OBJECTS   {
        tAtmTdpWeight
    }
    STATUS    current
    DESCRIPTION
        "The group of objects for ATM Traffic Descriptor Profiles
         added in release 9.0 of SROS."
    ::= { tmnxQosGroups 55 }

tmnxQosHsmdaV9v0Group OBJECT-GROUP
    OBJECTS {
        tHsmdaWrrPolicyTblLastChgd,
        tHsmdaWrrPolicyRowStatus,
        tHsmdaWrrPolicyLastChanged,
        tHsmdaWrrPolicyDescription,
        tHsmdaWrrPolicyIncludeQueues,       
        tHsmdaWrrPolicySchedUsingClass,  
        tHsmdaWrrPolicyAggWeightAtClass,    
        tNetworkQueuePolicyEHWrrPlcy, 
        tNetworkQueuePolicyEHPktBOffst, 
        tNetworkEgrHsmdaQueueTblLastChgd,
        tNetworkEgrHsmdaQueuePIRPercent,        
        tNetworkEgrHsmdaQueuePIRAdaptn,      
        tNetworkEgrHsmdaQueueWrrWeight,          
        tNetworkEgrHsmdaQueueMBS,                
        tNetworkEgrHsmdaQueueSlopePolicy,
        tNetworkEgrHsmdaQueueLastChanged,        
        tSapEgressHsmdaLowBrstMaxCls,
        tSapEgressHsmdaWrrPolicy,      
        tSapEgressHsmdaQueueWrrWeight, 
        tSapEgressHsmdaQueueMBS,
        tSapEgressHsmdaQueueBurstLimit,
        tNetworkEgrHsmdaQueueBurstLimit       
    }
    STATUS      current
    DESCRIPTION
        "The group of objects supporting management of QoS policies 
         for QMDA MDAs on Nokia SROS series systems release 9.0."
    ::= { tmnxQosGroups 56 }

tmnxQosNetworkV9v0Group OBJECT-GROUP
    OBJECTS {
        tNetworkQueueFCEgrHsmdaQueue
    }
    STATUS      current
    DESCRIPTION
        "The group of objects supporting management of Network QoS policies
         on Nokia SROS series systems release 9.0."
    ::= { tmnxQosGroups 57 }    

tmnxQosNamedPoolV9v0Group OBJECT-GROUP
    OBJECTS {
       tQ1NamedPoolResvCbsAmbrAlrmStep,
       tQ1NamedPoolResvCbsAmbrAlrmMax,
       tQ1NamedPoolAmbrAlrmThresh,
       tQ1NamedPoolRedAlrmThresh
    }
    STATUS      current
    DESCRIPTION
        "The group of objects supporting management of Network Named Pool
         policies on Nokia SROS series systems release 9.0."
    ::= { tmnxQosGroups 58 }

tmnxQosHsmdaObsoletedV9v0Group OBJECT-GROUP
    OBJECTS {
        tSapEgressFCDot1PHsmdaProfile
   }
    STATUS      current
    DESCRIPTION
        "The group of objects obsoleted supporting management of QoS policies 
         for HSMDA MDAs on Nokia SROS series systems release 9.0."
    ::= { tmnxQosGroups 59 }

tmnxQosPolicyV10v0Group OBJECT-GROUP
    OBJECTS {
        tSapEgrPolicyNameId,
        tSapEgrPolicyNameLastChanged,
        tSapEgrPolicyNameRowStatus,
        tSapEgrPolicyNameTableLastChgd,
        tSapEgressPolicyName,
        tSapIngPolicyNameId,
        tSapIngPolicyNameLastChanged,
        tSapIngPolicyNameRowStatus,
        tSapIngPolicyNameTableLastChgd,
        tSapIngressPolicyName
    }
    STATUS      current
    DESCRIPTION
        "The group of objects supporting management of Network QoS policies
         on Nokia SROS series systems release 10.0."
    ::= { tmnxQosGroups 60 }    

tmnxQosQueueGrpPolcrV10v0Group OBJECT-GROUP
    OBJECTS {
        tQosIngPolicerTableLastChanged,
        tQosIngPolicerRowStatus,
        tQosIngPolicerLastChanged,
        tQosIngPolicerDescr,
        tQosIngPolicerPIRAdaptation,
        tQosIngPolicerCIRAdaptation,
        tQosIngPolicerParent,
        tQosIngPolicerLevel,      
        tQosIngPolicerWeight,
        tQosIngPolicerAdminPIR,
        tQosIngPolicerAdminCIR,
        tQosIngPolicerCBS,    
        tQosIngPolicerMBS,
        tQosIngPolicerHiPrioOnly,
        tQosIngPolicerPktOffset,  
        tQosIngPolicerProfileCapped,
        tQosIngPolicerStatMode,
        tQosEgrPolicerTableLastChanged,
        tQosEgrPolicerRowStatus,
        tQosEgrPolicerLastChanged,
        tQosEgrPolicerDescr,
        tQosEgrPolicerPIRAdaptation,
        tQosEgrPolicerCIRAdaptation,
        tQosEgrPolicerParent,
        tQosEgrPolicerLevel,      
        tQosEgrPolicerWeight,
        tQosEgrPolicerAdminPIR,
        tQosEgrPolicerAdminCIR,
        tQosEgrPolicerCBS,    
        tQosEgrPolicerMBS,
        tQosEgrPolicerHiPrioOnly,
        tQosEgrPolicerPktOffset,  
        tQosEgrPolicerProfileCapped,
        tQosEgrPolicerStatMode,
        tSapIngressFCPlcrFPQGrp,        
        tSapIngressFCMCastPlcrFPQGrp,   
        tSapIngressFCBCastPlcrFPQGrp,   
        tSapIngressFCUnknownPlcrFPQGrp,
        tNetworkEgressFCQGrpPolicer,
        tNetworkIngressFCTableLstChanged,
        tNetworkIngressFCMultiCastPlcr,
        tNetworkIngressFCUniCastPlcr,
        tNetworkIngressFCLastChanged,
        tQosEgrQueuePktOffset,
        tQosPolicerCtrlPolProfPref,
        tSapEgrPolicerProfileCapped,
        tSapIngPolicerProfileCapped
    }
    STATUS      current
    DESCRIPTION
        "The group of objects supporting management of Network QoS policies
         on Nokia SROS series systems release 10.0."
    ::= { tmnxQosGroups 61 } 

tmnxQosEgrReClassifyV10v0Group OBJECT-GROUP
    OBJECTS {
        tSapEgressEthernetCtag,
        tSapEgressDot1pRowStatus,
        tSapEgressDot1pLastChanged,
        tSapEgressDot1pTableLastChanged,  
        tSapEgressDot1pFC, 
        tSapEgressDot1pProfile        
    }
    STATUS      current
    DESCRIPTION
        "The group of objects supporting management of QoS Egress policies
         on Nokia SROS series systems release 10.0."
    ::= { tmnxQosGroups 62 }    

tmnxQosPolicerSlopeGroup OBJECT-GROUP
    OBJECTS {
        tQosEgrPolicerSlopeMap, 
        tQosEgrPolicerSlopeMaxDepth, 
        tQosEgrPolicerSlopeMaxProb, 
        tQosEgrPolicerSlopeStartDepth, 
        tQosIngPolicerSlopeMap, 
        tQosIngPolicerSlopeMaxDepth, 
        tQosIngPolicerSlopeMaxProb, 
        tQosIngPolicerSlopeStartDepth, 
        tSapEgrPolicerSlopeMap, 
        tSapEgrPolicerSlopeMaxDepth, 
        tSapEgrPolicerSlopeMaxProb, 
        tSapEgrPolicerSlopeStartDepth, 
        tSapIngPolicerSlopeMap, 
        tSapIngPolicerSlopeMaxDepth, 
        tSapIngPolicerSlopeMaxProb, 
        tSapIngPolicerSlopeStartDepth
    }
    STATUS      current
    DESCRIPTION
        "The group of objects supporting management of QoS policer slope
         on Nokia SROS series systems release 10.0."
    ::= { tmnxQosGroups 63 }    

tmnxQosAdvConfigV10v0Group OBJECT-GROUP
    OBJECTS {
         tAdvCfgPolicyTblLastChgd,
         tAdvCfgPolicyRowStatus,  
         tAdvCfgLastChanged,      
         tAdvCfgDescription,      
         tAdvCfgChildAdmnPirPrcnt,
         tAdvCfgChildAdminRate,   
         tAdvCfgOMGranPirPrcnt,   
         tAdvCfgOMGranRate,       
         tAdvCfgMaxDecPirPrcnt,   
         tAdvCfgMaxDecRate,       
         tAdvCfgHiRateHoldTime,   
         tAdvCfgTimeAvgFactor,    
         tAdvCfgSampleInterval,   
         tAdvCfgFastStart,        
         tAdvCfgFastStop,         
         tAdvCfgAbvOffCapPirPrcnt,
         tAdvCfgAbvOffCapRate,    
         tAdvCfgBWDGranPirPrcnt,  
         tAdvCfgBWDGranRate,
         tQosEgrPolicerAdvCfgPolicy,
         tQosIngPolicerAdvCfgPolicy,
         tQosEgrQueueAdvCfgPolicy,
         tQosIngQueueAdvCfgPolicy,
         tSapEgrPolicerAdvCfgPolicy,
         tSapIngPolicerAdvCfgPolicy,
         tSapEgressQueueAdvCfgPolicy,
         tSapIngressQueueAdvCfgPolicy,
         tAdvCfgMinOnly,
         tAdvCfgDecOnly
    }
    STATUS      current
    DESCRIPTION
        "The group of objects supporting management of QoS  policer 
         and queue advanced configuration parameters on Nokia SROS 
         series systems release 10.0."
    ::= { tmnxQosGroups 64 }  

tmnxQosHsmdaV10v0Group OBJECT-GROUP
    OBJECTS {
        tHsmdaSchedulerPlcyRowStatus,
        tHsmdaSchedulerPlcyDescription,
        tHsmdaSchedulerPlcyMaxRate,
        tHsmdaSchedulerPlcyLvl1Rate,
        tHsmdaSchedulerPlcyLvl1GrpId,
        tHsmdaSchedulerPlcyLvl1WgtInGrp,
        tHsmdaSchedulerPlcyLvl2Rate,
        tHsmdaSchedulerPlcyLvl2GrpId,
        tHsmdaSchedulerPlcyLvl2WgtInGrp,
        tHsmdaSchedulerPlcyLvl3Rate,
        tHsmdaSchedulerPlcyLvl3GrpId,
        tHsmdaSchedulerPlcyLvl3WgtInGrp,
        tHsmdaSchedulerPlcyLvl4Rate,
        tHsmdaSchedulerPlcyLvl4GrpId,
        tHsmdaSchedulerPlcyLvl4WgtInGrp,
        tHsmdaSchedulerPlcyLvl5Rate,
        tHsmdaSchedulerPlcyLvl5GrpId,
        tHsmdaSchedulerPlcyLvl5WgtInGrp,
        tHsmdaSchedulerPlcyLvl6Rate,
        tHsmdaSchedulerPlcyLvl6GrpId,
        tHsmdaSchedulerPlcyLvl6WgtInGrp,
        tHsmdaSchedulerPlcyLvl7Rate,
        tHsmdaSchedulerPlcyLvl7GrpId,
        tHsmdaSchedulerPlcyLvl7WgtInGrp,
        tHsmdaSchedulerPlcyLvl8Rate,
        tHsmdaSchedulerPlcyLvl8GrpId,
        tHsmdaSchedulerPlcyLvl8WgtInGrp,
        tHsmdaSchedulerPlcyLastChanged,
        tHsmdaSchedulerPlcyGrp1Rate,
        tHsmdaSchedulerPlcyGrp2Rate,
        tSapEgressFCHsmdaQueue,
        tSapEgressHsmdaQueueRowStatus,
        tSapEgressHsmdaQueuePIRAdaptn,
        tSapEgressHsmdaQueueAdminPIR,
        tSapEgressHsmdaQueueSlopePolicy,
        tSapEgressHsmdaQueueLastChanged,
        tSapIngressHsmdaQueueRowStatus,
        tSapIngressHsmdaQueueLastChanged,
        tSapIngressHsmdaQueueCIRAdaptn,
        tSapIngressHsmdaQueuePIRAdaptn,
        tSapIngressHsmdaQueueAdminPIR,
        tSapIngressHsmdaQueueAdminCIR,
        tSapIngressHsmdaQueueSlopePolicy,
        tSapIngressHsmdaQueuePoliced,
        tHsmdaPoolPolicyRowStatus,
        tHsmdaPoolLastChanged,
        tHsmdaPoolDescription,
        tHsmdaPoolSystemReserve,
        tHsmdaPoolRoot1AllocWeight,
        tHsmdaPoolRoot2AllocWeight,
        tHsmdaPoolRoot3AllocWeight,
        tHsmdaPoolRoot4AllocWeight,
        tHsmdaPoolRoot5AllocWeight,
        tHsmdaPoolRoot6AllocWeight,
        tHsmdaPoolRoot7AllocWeight,
        tHsmdaPoolRoot8AllocWeight,
        tHsmdaPoolClass1Parent,
        tHsmdaPoolClass1AllocPercent,
        tHsmdaPoolClass2Parent,
        tHsmdaPoolClass2AllocPercent,
        tHsmdaPoolClass3Parent,
        tHsmdaPoolClass3AllocPercent,
        tHsmdaPoolClass4Parent,
        tHsmdaPoolClass4AllocPercent,
        tHsmdaPoolClass5Parent,
        tHsmdaPoolClass5AllocPercent,
        tHsmdaPoolClass6Parent,
        tHsmdaPoolClass6AllocPercent,
        tHsmdaPoolClass7Parent,
        tHsmdaPoolClass7AllocPercent,
        tHsmdaPoolClass8Parent,
        tHsmdaPoolClass8AllocPercent,
        tHsmdaSlopePolicyRowStatus,
        tHsmdaSlopeLastChanged,
        tHsmdaSlopeDescription,
        tHsmdaSlopeHiAdminStatus,
        tHsmdaSlopeHiStartDepth,
        tHsmdaSlopeHiMaxDepth,
        tHsmdaSlopeHiMaxProbability,
        tHsmdaSlopeLoAdminStatus,
        tHsmdaSlopeLoStartDepth,
        tHsmdaSlopeLoMaxDepth,
        tHsmdaSlopeLoMaxProbability,
        tSapEgrHsmdaQueueTblLastChngd,
        tHsmdaSchedPlcyTblLastChngd,
        tHsmdaSchedPlcyGrpTblLastChngd,
        tHsmdaPoolPlcyTblLastChngd,
        tHsmdaSlopePolicyTableLastChanged,
        tSapEgressDSCPRowStatus,
        tSapEgressDSCPLastChanged,
        tSapEgressDSCPHsmdaCntrOverride,
        tSapEgressPrecRowStatus,
        tSapEgressPrecLastChanged,
        tSapEgressPrecHsmdaCntrOverride,
        tSapEgrIPCritRowStatus,
        tSapEgrIPCritLastChanged,
        tSapEgrIPCritDescription,
        tSapEgrIPCritActionHsmdaCntrOvr,
        tSapEgrIPCritSourceIpAddrType,
        tSapEgrIPCritSourceIpAddr,
        tSapEgrIPCritSourceIpMask,
        tSapEgrIPCritDestIpAddrType,
        tSapEgrIPCritDestIpAddr,
        tSapEgrIPCritDestIpMask,
        tSapEgrIPCritProtocol,
        tSapEgrIPCritSourcePortValue1,
        tSapEgrIPCritSourcePortValue2,
        tSapEgrIPCritSourcePortOperator,
        tSapEgrIPCritDestPortValue1,
        tSapEgrIPCritDestPortValue2,
        tSapEgrIPCritDestPortOperator,
        tSapEgrIPCritDSCP,
        tSapEgrIPCritFragment,
        tSapEgressMatchCriteria,
        tSapEgressHsmdaPacketOffset,
        tSapEgrIPCritActionFC,
        tSapEgrIPCritActionProfile,
        tSapEgressDSCPfc,
        tSapEgressDSCPprofile,
        tSapEgressPrecFC,
        tSapEgressPrecProfile,
        tHsmdaSchedulerPlcyBrstLimit,
        tHsmdaSchedulerPlcyGrp1BrstLimit,
        tHsmdaSchedulerPlcyGrp2BrstLimit,
        tHsmdaSchedulerPlcyLvl1BrstLimit,
        tHsmdaSchedulerPlcyLvl2BrstLimit,
        tHsmdaSchedulerPlcyLvl3BrstLimit,
        tHsmdaSchedulerPlcyLvl4BrstLimit,
        tHsmdaSchedulerPlcyLvl5BrstLimit,
        tHsmdaSchedulerPlcyLvl6BrstLimit,
        tHsmdaSchedulerPlcyLvl7BrstLimit,
        tHsmdaSchedulerPlcyLvl8BrstLimit
    }
    STATUS      current
    DESCRIPTION
        "The group of objects supporting management of QoS policies 
         for QMDA MDAs on Nokia SROS series systems release 10.0."
    ::= { tmnxQosGroups 65 }   

tmnxQosNetworkV10v0Group OBJECT-GROUP
    OBJECTS {
        tNetworkEgressDSCPRowStatus,
        tNetworkEgressDSCPLastChanged,
        tNetworkEgressDSCPFC, 
        tNetworkEgressDSCPProfile,
        tNetworkEgressPrecRowStatus,
        tNetworkEgressPrecLastChanged,
        tNetworkEgressPrecFC, 
        tNetworkEgressPrecProfile,
        tNetworkEgrDSCPTableLastChanged,
        tNetworkEgrPrecTableLastChanged
    }
    STATUS      current
    DESCRIPTION
        "The group of objects supporting management of Network QoS policies
         on Nokia SROS series systems release 10.0."
    ::= { tmnxQosGroups 66 }   

tmnxQosNetworkV11v0Group OBJECT-GROUP
    OBJECTS {
        tSapIngressFCEgressOverrideFC
    }
    STATUS      current
    DESCRIPTION
        "The group of objects supporting management of Network QoS policies
         on Nokia SROS series systems release 11.0."
    ::= { tmnxQosGroups 67 } 

tmnxQosSapIngressV10v0Group OBJECT-GROUP
    OBJECTS {
        tSapIngressRowStatus,
        tSapIngressScope,
        tSapIngressDescription,
        tSapIngressDefaultFC,
        tSapIngressDefaultFCPriority,
        tSapIngressMatchCriteria,
        tSapIngressLastChanged,
        tSapIngressTableLastChanged,
        tSapIngressQueueRowStatus,
        tSapIngressQueueParent,
        tSapIngressQueueLevel,
        tSapIngressQueueWeight,
        tSapIngressQueueCIRLevel,
        tSapIngressQueueCIRWeight,
        tSapIngressQueueMCast,
        tSapIngressQueueExpedite,
        tSapIngressQueueCBS,
        tSapIngressQueueHiPrioOnly,
        tSapIngressQueueCIRAdaptation,
        tSapIngressQueuePIRAdaptation,
        tSapIngressQueueAdminPIR,
        tSapIngressQueueAdminCIR,
        tSapIngressQueueLastChanged,
        tSapIngressQueueMode,
        tSapIngressQueuePoolName,
        tSapIngressQueueTableLastChanged,
        tSapIngressQueuePoliced,
        tSapIngressDSCPRowStatus,
        tSapIngressDSCPFC,
        tSapIngressDSCPPriority,
        tSapIngressDSCPLastChanged,
        tSapIngressDSCPTableLastChanged,
        tSapIngressDot1pRowStatus,
        tSapIngressDot1pFC,
        tSapIngressDot1pPriority,
        tSapIngressDot1pLastChanged,
        tSapIngressDot1pTableLastChanged,
        tSapIngressIPCriteriaRowStatus,
        tSapIngressIPCriteriaDescription,
        tSapIngressIPCriteriaActionFC,
        tSapIngressIPCriteriaActionPriority,
        tSapIngressIPCriteriaSourceIpAddr,
        tSapIngressIPCriteriaSourceIpMask,
        tSapIngressIPCriteriaDestIpAddr,
        tSapIngressIPCriteriaDestIpMask,
        tSapIngressIPCriteriaProtocol,
        tSapIngressIPCriteriaSourcePortValue1,
        tSapIngressIPCriteriaSourcePortValue2,
        tSapIngressIPCriteriaSourcePortOperator,
        tSapIngressIPCriteriaDestPortValue1,
        tSapIngressIPCriteriaDestPortValue2,
        tSapIngressIPCriteriaDestPortOperator,
        tSapIngressIPCriteriaDSCP,
        tSapIngressIPCriteriaFragment,
        tSapIngressIPCriteriaLastChanged,
        tSapIngressIPCriteriaTableLastChanged,
        tSapIngressMacCriteriaRowStatus,
        tSapIngressMacCriteriaDescription,
        tSapIngressMacCriteriaActionFC,
        tSapIngressMacCriteriaActionPriority,
        tSapIngressMacCriteriaFrameType,
        tSapIngressMacCriteriaSrcMacAddr,
        tSapIngressMacCriteriaSrcMacMask,
        tSapIngressMacCriteriaDstMacAddr,
        tSapIngressMacCriteriaDstMacMask,
        tSapIngressMacCriteriaDot1PValue,
        tSapIngressMacCriteriaDot1PMask,
        tSapIngressMacCriteriaEthernetType,
        tSapIngressMacCriteriaDSAP,
        tSapIngressMacCriteriaDSAPMask,
        tSapIngressMacCriteriaSSAP,
        tSapIngressMacCriteriaSSAPMask,
        tSapIngressMacCriteriaSnapPid,
        tSapIngressMacCriteriaSnapOui,
        tSapIngressMacCriteriaLastChanged,
        tSapIngressMacCriteriaTableLastChanged,
        tSapIngressFCRowStatus,
        tSapIngressFCQueue,
        tSapIngressFCMCastQueue,
        tSapIngressFCBCastQueue,
        tSapIngressFCUnknownQueue,
        tSapIngressFCLastChanged,
        tSapIngressFCInProfRemark,
        tSapIngressFCInProfDscp,
        tSapIngressFCInProfPrec,
        tSapIngressFCDE1OutOfProfile,
        tSapIngressFCOutProfRemark,
        tSapIngressFCOutProfDscp,
        tSapIngressFCOutProfPrec,
        tSapIngressFCProfile,
        tSapIngressFCTableLastChanged,
        tSapIngressPrecRowStatus,
        tSapIngressPrecFC,
        tSapIngressPrecFCPriority,
        tSapIngressPrecLastChanged,
        tSapIngressPrecTableLastChanged,
        tSapIngressLspExpRowStatus,
        tSapIngressLspExpLastChanged,
        tSapIngressLspExpFC,
        tSapIngressLspExpFCPriority,
        tSapIngressLspExpTableLastChange
    }
    STATUS      current
    DESCRIPTION
        "The group of objects supporting management of SAP ingress QoS
         policies on Nokia SROS series systems release 10.0."
    ::= { tmnxQosGroups 68 }    

tmnxQosHsmdaObsoletedV10v0Group OBJECT-GROUP
    OBJECTS {
        tHsmdaSlopeQueueMbs,
        tSapIngressHsmdaPacketOffset,
        tSapIngressFCHsmdaQueue,
        tSapIngressFCHsmdaMCastQueue,
        tSapIngressFCHsmdaBCastQueue,
        tSapIngressDefFCHsmdaCntrOvr,
        tSapIngressDot1pHsmdaCntrOvr,
        tSapIngressPrecHsmdaCntrOvr,
        tSapIngressDSCPHsmdaCntrOvr,
        tSapIngressLspExpHsmdaCntrOvr,
        tSapIngressIPCritHsmdaCntrOvr,
        tSapEgressHsmdaQueueCIRAdaptn,
        tSapEgressHsmdaQueueAdminCIR,
        tSapIngrHsmdaQueueTblLastChngd,
        tSapIngressHsmdaQueueRowStatus,
        tSapIngressHsmdaQueueLastChanged,
        tSapIngressHsmdaQueueCIRAdaptn,
        tSapIngressHsmdaQueuePIRAdaptn,
        tSapIngressHsmdaQueueAdminPIR,
        tSapIngressHsmdaQueueAdminCIR,
        tSapIngressHsmdaQueueSlopePolicy,
        tSapIngressHsmdaQueuePoliced       
   }
    STATUS      current
    DESCRIPTION
        "The group of objects obsoleted supporting management of QoS policies 
         for HSMDA MDAs on Nokia SROS series systems release 10.0."
    ::= { tmnxQosGroups 69 }    

tmnxSapEgressFCV11v0Group OBJECT-GROUP
    OBJECTS {
        tSapEgressFCQGrpInstanceId,
        tSapEgressFCPortQGrpQueue
    }
    STATUS      current
    DESCRIPTION
        "The group of objects supporting management of Sap-Egress QoS policies
         on Nokia SROS series systems release 11.0."
    ::= { tmnxQosGroups 70 } 

tmnxQosHsmdaV11v0Group OBJECT-GROUP
    OBJECTS {
        tQosEgrQGroupHsmdaPacketOffset,
        tQosEgrQGroupHsmdaWrrPolicy,
        tQosEgrQGroupHsmdaLowBrstMaxCls,
        tQosEgrHsmdaQueueRowStatus,
        tQosEgrHsmdaQueueLastChanged,
        tQosEgrHsmdaQueuePIRAdaptn,
        tQosEgrHsmdaQueueAdminPIR,
        tQosEgrHsmdaQueueSlopePolicy,
        tQosEgrHsmdaQueueWrrWeight,
        tQosEgrHsmdaQueueMBS,
        tQosEgrHsmdaQueueBurstLimit,
        tSapEgressFCHsmdaQueuePortQGrpQ
    }
    STATUS      current
    DESCRIPTION
        "The group of objects supporting management of QoS policies for HSMDA 
         on Nokia SROS series systems release 11.0."
    ::= { tmnxQosGroups 71 } 

tmnxQosSchedulerRateV11v0Group OBJECT-GROUP
    OBJECTS {
        tVirtualSchedulerPIRHi,
        tVirtualSchedulerPIRLo,
        tVirtualSchedulerCIRHi,
        tVirtualSchedulerCIRLo
    }
    STATUS      current
    DESCRIPTION
        "The group of objects supporting management of Scheduler policies
         on Nokia SROS series systems release 11.0."
    ::= { tmnxQosGroups 72 } 

tmnxQosSchedulerV11v0Group OBJECT-GROUP
    OBJECTS {
        tSchedulerPolicyRowStatus,
        tSchedulerPolicyDescription,
        tSchedulerPolicyLastChanged,
        tSchedulerPolicyTableLastChanged,
        tVirtualSchedulerRowStatus,
        tVirtualSchedulerDescription,
        tVirtualSchedulerParent,
        tVirtualSchedulerLevel,
        tVirtualSchedulerWeight,
        tVirtualSchedulerCIRLevel,
        tVirtualSchedulerCIRWeight,
        tVirtualSchedulerSummedCIR,
        tVirtualSchedulerLastChanged,
        tVirtualSchedulerUsePortParent,
        tVirtualSchedulerPortLvl,
        tVirtualSchedulerPortWght,
        tVirtualSchedulerPortCIRLvl,
        tVirtualSchedulerPortCIRWght,
        tVirtualSchedulerTableLastChanged,
        tPortSchedulerPlcyRowStatus,
        tPortSchedulerPlcyDescription,
        tPortSchedulerPlcyLastChanged,
        tPortSchedulerPlcyMaxRate,
        tPortSchedulerPlcyOrphanLvl,
        tPortSchedulerPlcyOrphanWeight,
        tPortSchedulerPlcyOrphanCIRLvl,
        tPortSchedulerPlcyOrphanCIRWght
    }
    STATUS      obsolete
    DESCRIPTION
        "The group of objects supporting management of Scheduler policies
         on Nokia SROS series systems release 11.0."
    ::= { tmnxQosGroups 73 }

tmnxQosSchedObsoletedV11v0Group OBJECT-GROUP
    OBJECTS {
        tVirtualSchedulerPIR,
        tVirtualSchedulerCIR
   }
    STATUS      current
    DESCRIPTION
        "The group of objects obsoleted supporting management of QoS Scheduler 
         policies on Nokia SROS series systems release 11.0."
    ::= { tmnxQosGroups 74 }    

tmnxQosV12v0Groups                OBJECT IDENTIFIER ::= { tmnxQosGroups 75 }

tmnxQosSapEgrFCDot1pDEV12v0Group OBJECT-GROUP
    OBJECTS {
        tSapEgressFCOuterTagDot1PInProf,
        tSapEgressFCOuterTagDot1POutProf,
        tSapEgressFCInnerTagDot1PInProf,
        tSapEgressFCInnerTagDot1POutProf,
        tSapEgressFCOuterTagForceDEValue,
        tSapEgressFCOuterTagDEMark,  
        tSapEgressFCInnerTagForceDEValue,
        tSapEgressFCInnerTagDEMark
    }
    STATUS      current
    DESCRIPTION
        "The group of objects supporting management of QoS Sap-Egress policies
         on Nokia SROS series systems release 12.0."
    ::= { tmnxQosV12v0Groups 1 }


tmnxQosSapIPCritExtV12v0Group OBJECT-GROUP
    OBJECTS {
        tSapIngressIPCritSrcIpFullMask,
        tSapIngressIPCritDstIpFullMask,
        tSapIngressIPv6CritSrcIpFullMask,
        tSapIngressIPv6CritDstIpFullMask,
        tSapEgrIPCritSrcIpFullMask,
        tSapEgrIPCritDstIpFullMask
    }
    STATUS      current
    DESCRIPTION
        "The group of objects supporting management of SAP egress/ingress QoS
         policies with full mask IP address matching 
         on Nokia SROS series systems release 12.0."
    ::= { tmnxQosV12v0Groups 2 }

tmnxQosPolicyV12v0Group OBJECT-GROUP
    OBJECTS {
        tSapEgressParentLocation,
        tSchedulerPolicyTier1ParentLoc
    }
    STATUS      obsolete
    DESCRIPTION
        "The group of objects supporting management of SAP egress QoS and 
         scheduler policies on Nokia SROS series systems release 12.0."
    ::= { tmnxQosV12v0Groups 3 }

tmnxQosSapIngIPMacCritV12v0Group OBJECT-GROUP
    OBJECTS {
        tSapIngressIPCritActionPolicer,
        tSapIngressMacCritActionPolicer,
        tSapIngressIPv6CritActionPolicer
    }
    STATUS      current
    DESCRIPTION
        "The group of objects supporting management of SAP ingress QoS policies
         on Nokia SROS series systems release 12.0."
    ::= { tmnxQosV12v0Groups 4 }

tmnxQosPlcyV12v0Group OBJECT-GROUP
    OBJECTS {
        tAdvCfgChildAdminRateActMinOnly,
        tAdvCfgHiRateHoldTimeActMinOnly,
        tAdvCfgBWDEnqueueOnPIRZero,
        tAdvCfgBWDLimitPIRZeroDrain,
        tAdvCfgBWDLmtUnusedBWInitMinPIR,
        tVirtualSchedulerRateLUB        
    }
    STATUS      current
    DESCRIPTION
        "The group of objects supporting management of Advance Qos configuration
         Policies on Nokia SROS series systems release 12.0."
    ::= { tmnxQosV12v0Groups 5 }            

tmnxQosSapEgrPlcrV12v0Group OBJECT-GROUP
    OBJECTS {
        tSapEgrPolicerProfileOutPreserve
    }
    STATUS      current
    DESCRIPTION
        "The group of objects supporting management of SAP egress Qos policies
         on Nokia SROS series systems release 12.0."
    ::= { tmnxQosV12v0Groups 6 }

tmnxQosPortSchedV12v0Group OBJECT-GROUP
    OBJECTS {
        tPortSchedPlcyDistLagRateShared,
        tPortSchedPlcyMaxRatePercent,
        tPortSchedPlcyMaxRateType,
        tPortSchedPlcyLvl1PIRPercent,
        tPortSchedPlcyLvl1CIRPercent,
        tPortSchedPlcyLvl1RateType,
        tPortSchedPlcyLvl2PIRPercent,
        tPortSchedPlcyLvl2CIRPercent,
        tPortSchedPlcyLvl2RateType,
        tPortSchedPlcyLvl3PIRPercent,
        tPortSchedPlcyLvl3CIRPercent,
        tPortSchedPlcyLvl3RateType,
        tPortSchedPlcyLvl4PIRPercent,
        tPortSchedPlcyLvl4CIRPercent,
        tPortSchedPlcyLvl4RateType,
        tPortSchedPlcyLvl5PIRPercent,
        tPortSchedPlcyLvl5CIRPercent,
        tPortSchedPlcyLvl5RateType,
        tPortSchedPlcyLvl6PIRPercent,
        tPortSchedPlcyLvl6CIRPercent,
        tPortSchedPlcyLvl6RateType,
        tPortSchedPlcyLvl7PIRPercent,
        tPortSchedPlcyLvl7CIRPercent,
        tPortSchedPlcyLvl7RateType,
        tPortSchedPlcyLvl8PIRPercent,
        tPortSchedPlcyLvl8CIRPercent,
        tPortSchedPlcyLvl8RateType,
        tPortSchPlcyGrpPIRPercent,
        tPortSchPlcyGrpCIRPercent,
        tPortSchPlcyGrpRateType
    }
    STATUS      obsolete
    DESCRIPTION
        "The group of objects supporting management of Qos Port Scheduler
         policies on Nokia SROS series systems release 12.0."
    ::= { tmnxQosV12v0Groups 7 }


tmnxQosParentLocV12v0Group OBJECT-GROUP
    OBJECTS {
        tSchedulerPolicyTier1ParentLoc
    }
    STATUS      current
    DESCRIPTION
        "The group of objects supporting management of SAP egress QoS and 
         scheduler policies on Nokia SROS series systems release 12.0."
    ::= { tmnxQosV12v0Groups 8 }
    
 tmnxQosParentLocEsmV12v0Group OBJECT-GROUP
    OBJECTS {
        tSapEgressParentLocation
    }
    STATUS      current
    DESCRIPTION
        "The group of objects supporting management of SAP egress QoS and 
         scheduler policies on Nokia SROS series systems release 12.0."
    ::= { tmnxQosV12v0Groups 9 }

tmnxQosV13v0Groups                OBJECT IDENTIFIER ::= { tmnxQosGroups 76 }

tmnxQosSapIngressV13v0Group OBJECT-GROUP
    OBJECTS {
        tSapIngressIPv6CriteriaFragment
    }
    STATUS      current
    DESCRIPTION
        "The group of objects supporting management of SAP Ingress QoS policies
         on Nokia SROS series systems release 13.0."
    ::= { tmnxQosV13v0Groups 1 }

tmnxQosNetworkPlcyV13v0Group OBJECT-GROUP
    OBJECTS {
        tNetworkPolicyIngMatchCriteria,
        tNetworkIngIPCritTableLstChanged,
        tNetworkIngIPCritRowStatus,
        tNetworkIngIPCritLastChanged,
        tNetworkIngIPCritDescription,
        tNetworkIngIPCritActionFC,
        tNetworkIngIPCritActionProfile,
        tNetworkIngIPCritSrcIpAddrType,
        tNetworkIngIPCritSrcIpAddr,
        tNetworkIngIPCritSrcIpMask,
        tNetworkIngIPCritSrcIpFullMask,
        tNetworkIngIPCritDstIpAddrType,
        tNetworkIngIPCritDstIpAddr,
        tNetworkIngIPCritDstIpMask,
        tNetworkIngIPCritDstIpFullMask,
        tNetworkIngIPCritProtocol,
        tNetworkIngIPCritSrcPortValue1,
        tNetworkIngIPCritSrcPortValue2,
        tNetworkIngIPCritSrcPortOperator,
        tNetworkIngIPCritDstPortValue1,
        tNetworkIngIPCritDstPortValue2,
        tNetworkIngIPCritDstPortOperator,
        tNetworkIngIPCritDSCP,
        tNetworkIngIPCritFragment
    }
    STATUS      current
    DESCRIPTION
        "The group of objects supporting management of Network QoS policies on
         Nokia SROS series systems release 13.0."
    ::= { tmnxQosV13v0Groups 2 }

tmnxQosNetworkIngFCV13v0Group OBJECT-GROUP
    OBJECTS {
        tNetworkIngressFCBroadCastPlcr,
        tNetworkIngressFCUnknownPlcr
    }
    STATUS      current
    DESCRIPTION
        "The group of objects supporting management of Network QoS policies on
         Nokia SROS series systems release 13.0."
    ::= { tmnxQosV13v0Groups 3 }

tmnxQosAdvCfgPlcyV13v0Group OBJECT-GROUP
    OBJECTS {
        tAdvCfgBWDInternalSchedWghtMode
    }
    STATUS      current
    DESCRIPTION
        "The group of objects supporting management of Advance Qos configuration
         Policies on Nokia SROS series systems release 13.0."
    ::= { tmnxQosV13v0Groups 4 }

tmnxQosFlowBasedRulesV13v0Group OBJECT-GROUP
    OBJECTS {
        tSapIngDynamicCfgTblLastChanged,
        tSapIngDynamicCfgLastChanged,
        tSapIngSharedPccRuleInsertPoint,
        tSapIngSharedPccRuleInsertSize,
        tSapIngSharedPccRuleNbrInsert,
        tSapIngSharedPccRuleNbrPolicy,
        tSapIngDynamicPolicerInsertPoint,
        tSapIngDynamicPolicerInsertSize,
        tSapIngDynamicPolicerNbrInsert,
        tSapIngDynamicPolicerPktOffset,
        tSapIngDynamicPolicerMBS,
        tSapIngDynamicPolicerCBS,
        tSapIngDynamicPolicerParent,
        tSapIngDynamicPolicerLevel,
        tSapIngDynamicPolicerWeight,
        tSapIngDynamicPolicerStatMode,
        tSapEgrDynamicCfgTblLastChanged,
        tSapEgrDynamicCfgLastChanged,
        tSapEgrSharedPccRuleInsertPoint,
        tSapEgrSharedPccRuleInsertSize,
        tSapEgrSharedPccRuleNbrInsert,
        tSapEgrSharedPccRuleNbrPolicy,
        tSapEgrDynamicPolicerInsertPoint,
        tSapEgrDynamicPolicerInsertSize,
        tSapEgrDynamicPolicerNbrInsert,
        tSapEgrDynamicPolicerPktOffset,
        tSapEgrDynamicPolicerMBS,
        tSapEgrDynamicPolicerCBS,
        tSapEgrDynamicPolicerParent,
        tSapEgrDynamicPolicerLevel,
        tSapEgrDynamicPolicerWeight,
        tSapEgrDynamicPolicerStatMode
    }
    STATUS current
    DESCRIPTION
        "The group of objects supporting management of Flow based Rules for QoS
         configuration on Nokia SROS series systems release 13.0."
    ::= { tmnxQosV13v0Groups 5 }


tmnxQosIngressPlcyV13v0Group OBJECT-GROUP
    OBJECTS {
        tSapIngressQueuePktOffset,
        tQosIngQueuePktOffset
    }
    STATUS      current
    DESCRIPTION
        "The group of objects supporting management of QoS policies on
         Nokia SROS series systems release 13.0."
    ::= { tmnxQosV13v0Groups 7 }

tmnxQosSapEgrIPCritV13v0Group OBJECT-GROUP
    OBJECTS {
        tSapEgrIPCritActionPolicer,
        tSapEgrIPCritActionPortQGrpQueue,
        tSapEgrIPCritActionQueue
    }
    STATUS      current
    DESCRIPTION
        "The group of objects supporting management of SAP egress QoS policies
         on Nokia SROS series systems release 13.0."
    ::= { tmnxQosV13v0Groups 8 }


tmnxQosPortSchedPlcyV13v0Group OBJECT-GROUP
    OBJECTS {
        tPortSchedPlcyMaxRate,
        tPortSchedPolicyLevelTblLastChgd,
        tPortSchedPolicyLevelLastChanged,
        tPortSchedPolicyLevelRateType,
        tPortSchedPolicyLevelPIR,
        tPortSchedPolicyLevelCIR,
        tPortSchedPolicyLevelPIRPercent,
        tPortSchedPolicyLevelCIRPercent,
        tPortSchedPolicyLevelGroupName,
        tPortSchedPolicyLevelGroupWeight,
        tPortSchPlcyGroupAdminPIR,
        tPortSchPlcyGroupAdminCIR
  }
    STATUS      current
    DESCRIPTION
        "The group of objects supporting management of Qos Port Scheduler Policy
         configuration on Nokia SROS series systems release 13.0."
    ::= { tmnxQosV13v0Groups 10 }


tmnxQosSapEgrIpCritGroup OBJECT-GROUP
    OBJECTS {
        tSapEgrIPCritActionPolicerUseFCQ
    }
    STATUS      current
    DESCRIPTION
        "The group of objects supporting management of Qos SAP egress IP
         criteria configuration on Nokia SROS series systems."
    ::= { tmnxQosV13v0Groups 13 }

tmnxQosSchedulerV13v0Group OBJECT-GROUP
    OBJECTS {
        tSchedulerPolicyRowStatus,
        tSchedulerPolicyDescription,
        tSchedulerPolicyLastChanged,
        tSchedulerPolicyTableLastChanged,
        tVirtualSchedulerRowStatus,
        tVirtualSchedulerDescription,
        tVirtualSchedulerParent,
        tVirtualSchedulerLevel,
        tVirtualSchedulerWeight,
        tVirtualSchedulerCIRLevel,
        tVirtualSchedulerCIRWeight,
        tVirtualSchedulerSummedCIR,
        tVirtualSchedulerLastChanged,
        tVirtualSchedulerUsePortParent,
        tVirtualSchedulerPortLvl,
        tVirtualSchedulerPortWght,
        tVirtualSchedulerPortCIRLvl,
        tVirtualSchedulerPortCIRWght,
        tVirtualSchedulerTableLastChanged,
        tPortSchedulerPlcyRowStatus,
        tPortSchedulerPlcyDescription,
        tPortSchedulerPlcyLastChanged,
        tPortSchedulerPlcyOrphanLvl,
        tPortSchedulerPlcyOrphanWeight,
        tPortSchedulerPlcyOrphanCIRLvl,
        tPortSchedulerPlcyOrphanCIRWght,
        tPortSchedPlcyDistLagRateShared,
        tPortSchedPlcyMaxRatePercent,
        tPortSchedPlcyMaxRateType,
        tPortSchPlcyGrpPIRPercent,
        tPortSchPlcyGrpCIRPercent,
        tPortSchPlcyGrpRateType,
        tPortSchPlcyGrpLastChanged,
        tPortSchPlcyGrpRowStatus,
        tPortSchPlcyGrpTblLastChgd
    }
    STATUS      current
    DESCRIPTION
        "The group of objects supporting management of Scheduler policies
         on Nokia SROS series systems release 13.0."
    ::= { tmnxQosV13v0Groups 14 }

tmnxQosSchedObsoletedV13v0Group OBJECT-GROUP
    OBJECTS {
        tPortSchedulerPlcyMaxRate,
        tPortSchedulerPlcyLvl1PIR,
        tPortSchedulerPlcyLvl1CIR,
        tPortSchedulerPlcyLvl2PIR,
        tPortSchedulerPlcyLvl2CIR,
        tPortSchedulerPlcyLvl3PIR,
        tPortSchedulerPlcyLvl3CIR,
        tPortSchedulerPlcyLvl4PIR,
        tPortSchedulerPlcyLvl4CIR,
        tPortSchedulerPlcyLvl5PIR,
        tPortSchedulerPlcyLvl5CIR,
        tPortSchedulerPlcyLvl6PIR,
        tPortSchedulerPlcyLvl6CIR,
        tPortSchedulerPlcyLvl7PIR,
        tPortSchedulerPlcyLvl7CIR,
        tPortSchedulerPlcyLvl8PIR,
        tPortSchedulerPlcyLvl8CIR,
        tPortSchedPlcyLvl1PIRPercent,
        tPortSchedPlcyLvl1CIRPercent,
        tPortSchedPlcyLvl1RateType,
        tPortSchedPlcyLvl2PIRPercent,
        tPortSchedPlcyLvl2CIRPercent,
        tPortSchedPlcyLvl2RateType,
        tPortSchedPlcyLvl3PIRPercent,
        tPortSchedPlcyLvl3CIRPercent,
        tPortSchedPlcyLvl3RateType,
        tPortSchedPlcyLvl4PIRPercent,
        tPortSchedPlcyLvl4CIRPercent,
        tPortSchedPlcyLvl4RateType,
        tPortSchedPlcyLvl5PIRPercent,
        tPortSchedPlcyLvl5CIRPercent,
        tPortSchedPlcyLvl5RateType,
        tPortSchedPlcyLvl6PIRPercent,
        tPortSchedPlcyLvl6CIRPercent,
        tPortSchedPlcyLvl6RateType,
        tPortSchedPlcyLvl7PIRPercent,
        tPortSchedPlcyLvl7CIRPercent,
        tPortSchedPlcyLvl7RateType,
        tPortSchedPlcyLvl8PIRPercent,
        tPortSchedPlcyLvl8CIRPercent,
        tPortSchedPlcyLvl8RateType,
        tPortSchPlcyLvl1GrpName,
        tPortSchPlcyLvl1GrpWeight,
        tPortSchPlcyLvl2GrpName,
        tPortSchPlcyLvl2GrpWeight,
        tPortSchPlcyLvl3GrpName,
        tPortSchPlcyLvl3GrpWeight,
        tPortSchPlcyLvl4GrpName,
        tPortSchPlcyLvl4GrpWeight,
        tPortSchPlcyLvl5GrpName,
        tPortSchPlcyLvl5GrpWeight,
        tPortSchPlcyLvl6GrpName,
        tPortSchPlcyLvl6GrpWeight,
        tPortSchPlcyLvl7GrpName,
        tPortSchPlcyLvl7GrpWeight,
        tPortSchPlcyLvl8GrpName,
        tPortSchPlcyLvl8GrpWeight,
        tPortSchPlcyLvlGrpLastChanged,
        tPortSchPlcyLvlGrpTblLastChgd,
        tPortSchPlcyGrpAdminCIR,
        tPortSchPlcyGrpAdminPIR
   }
    STATUS      current
    DESCRIPTION
        "The group of obsoleted objects supporting management of QoS Scheduler 
         policies on Nokia SROS series systems release 13.0."
    ::= { tmnxQosV13v0Groups 15 }

END
