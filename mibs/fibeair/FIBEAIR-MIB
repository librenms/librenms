--
-- Ceragon Management Information Base (MIB)
-- Generated 03/11/15 12:54:04 Version: 9.6.40_b9610
--
	CERAGON-NET-MIB-FIBEAIR-4800 DEFINITIONS ::= BEGIN

	IMPORTS 
		enterprises, IpAddress, Counter, Gauge, TimeTicks
			FROM RFC1155-SMI
		OBJECT-TYPE
			FROM RFC-1212
		DisplayString, ifIndex
			FROM RFC1213-MIB
		TRAP-TYPE
		    FROM RFC-1215;
	

	ceragonNet			OBJECT IDENTIFIER ::= { enterprises 4458 }
	fibeAir4800		OBJECT IDENTIFIER ::= { ceragonNet 1000 }

	-- ###########################################################
	--                      ODU
	-- ###########################################################

	fibeAir4800Odu OBJECT IDENTIFIER ::= { fibeAir4800 1 }

	-- ###########################################################
	--                      ODU Admin
	-- ###########################################################

	fibeAir4800OduAdmin OBJECT IDENTIFIER ::= { fibeAir4800Odu 1 }

	fibeAir4800OduAdmProductType OBJECT-TYPE
		SYNTAX  DisplayString
		ACCESS  read-only
		STATUS  mandatory
		DESCRIPTION
		"ODU configuration description."
		::= { fibeAir4800OduAdmin 1 }

	fibeAir4800OduAdmHwRev OBJECT-TYPE
		SYNTAX  DisplayString
		ACCESS  read-only
		STATUS  mandatory
		DESCRIPTION
		"ODU Hardware Version."
		::= { fibeAir4800OduAdmin 2 }

	fibeAir4800OduAdmSwRev OBJECT-TYPE
		SYNTAX  DisplayString
		ACCESS  read-only
		STATUS  mandatory
		DESCRIPTION
		"ODU Software Version."
		::= { fibeAir4800OduAdmin 3 }

	fibeAir4800OduAdmLinkName OBJECT-TYPE
		SYNTAX  DisplayString
		ACCESS  read-write
		STATUS  mandatory
		DESCRIPTION
		"Link Name. A change is effective immediately."
		::= { fibeAir4800OduAdmin 4 }

	fibeAir4800OduAdmResetCmd OBJECT-TYPE
		SYNTAX  INTEGER
		ACCESS  read-write
		STATUS  mandatory
		DESCRIPTION
		"Reset Command. 
		A set command with a value of 3 will cause a device reset.
		HBS only: A set command with a value of 4 will cause a device reset for the entire sector.
		The read value is always 0."
		::= { fibeAir4800OduAdmin 5 }

	fibeAir4800OduAdmAddres OBJECT-TYPE
		SYNTAX  IpAddress
		ACCESS  read-write
		STATUS  mandatory
		DESCRIPTION
		"ODU IP address. A change is effective after reset.
		 The parameter is kept for backward compatibility.
		 Using the alternative parameter: fibeAir4800OduAdmIpParamsCnfg is recommended."
		::= { fibeAir4800OduAdmin 6 }

	fibeAir4800OduAdmMask OBJECT-TYPE
		SYNTAX  IpAddress
		ACCESS  read-write
		STATUS  mandatory
		DESCRIPTION
		"ODU Subnet Mask. A change is effective after reset.
		 The parameter is kept for backward compatibility.
		 Using the alternative parameter: fibeAir4800OduAdmIpParamsCnfg is recommended."
		::= { fibeAir4800OduAdmin 7 }

	fibeAir4800OduAdmGateway OBJECT-TYPE
		SYNTAX  IpAddress
		ACCESS  read-write
		STATUS  mandatory
		DESCRIPTION
		"ODU default gateway. A change is effective after reset.
		 The parameter is kept for backward compatibility.
		 Using the alternative parameter: fibeAir4800OduAdmIpParamsCnfg is recommended."
		::= { fibeAir4800OduAdmin 8 }	

	fibeAir4800OduAdmBroadcast OBJECT-TYPE
		SYNTAX  INTEGER
		ACCESS  read-write
		STATUS  mandatory
		DESCRIPTION
		"This parameter is reserved for the Manager application provided with the product."
		::= { fibeAir4800OduAdmin 10 }
	
	-- ###########################################################
	--                      ODU Admin Hosts Table
	-- ###########################################################

	fibeAir4800OduAdmHostsTable OBJECT-TYPE
		SYNTAX  SEQUENCE OF FibeAir4800OduAdmHostsEntry
		ACCESS  not-accessible
		STATUS  mandatory
		DESCRIPTION
		"Trap destinations table. Each trap destination is defined by an IP address and a UDP port.
		Up to 10 addresses can be configured."
		::= { fibeAir4800OduAdmin 12 }

	fibeAir4800OduAdmHostsEntry OBJECT-TYPE
		SYNTAX  FibeAir4800OduAdmHostsEntry
		ACCESS  not-accessible
		STATUS  mandatory
		DESCRIPTION
		"Trap destinations table entry."
		INDEX { fibeAir4800OduAdmHostsIndex }
		::= { fibeAir4800OduAdmHostsTable 1 }

	FibeAir4800OduAdmHostsEntry ::= SEQUENCE {
		fibeAir4800OduAdmHostsIndex
			INTEGER,
		fibeAir4800OduAdmHostsIp
			IpAddress,
		fibeAir4800OduAdmHostsPort
			INTEGER,
		fibeAir4800OduAdmHostsSecurityModel
			INTEGER,
		fibeAir4800OduAdmHostsUserName
			DisplayString,
		fibeAir4800OduAdmHostsPassword
			DisplayString,
		fibeAir4800OduAdmHostsIPv6
			DisplayString
		}

	fibeAir4800OduAdmHostsIndex OBJECT-TYPE
		SYNTAX  INTEGER
		ACCESS  read-only
		STATUS  mandatory
		DESCRIPTION
		"Trap destinations table index."
		::= { fibeAir4800OduAdmHostsEntry 1 }

	fibeAir4800OduAdmHostsIp OBJECT-TYPE
		SYNTAX  IpAddress
		ACCESS  read-write
		STATUS  mandatory
		DESCRIPTION
		"Trap destination IP address. A change is effective immediately."
		::= { fibeAir4800OduAdmHostsEntry 2 }

	fibeAir4800OduAdmHostsPort OBJECT-TYPE
		SYNTAX  INTEGER (1..65535)
		ACCESS  read-write
		STATUS  mandatory
		DESCRIPTION
		"UDP port of the trap destination. A change is effective immediately."
		::= { fibeAir4800OduAdmHostsEntry 3 }
		
	fibeAir4800OduAdmHostsSecurityModel OBJECT-TYPE
		SYNTAX  INTEGER {
			snmpv1(1),
			snmpv3(3)		
		}
		ACCESS  read-write
		STATUS  mandatory
		DESCRIPTION
		"Security model used for this trap generation."
		::= { fibeAir4800OduAdmHostsEntry 4 }
		
	fibeAir4800OduAdmHostsUserName OBJECT-TYPE
		SYNTAX  DisplayString
		ACCESS  read-write
		STATUS  mandatory
		DESCRIPTION
		"User name used to generate the snmpv3 trap."
		::= { fibeAir4800OduAdmHostsEntry 5 }
		
	fibeAir4800OduAdmHostsPassword OBJECT-TYPE
		SYNTAX  DisplayString
		ACCESS  read-write
		STATUS  mandatory
		DESCRIPTION
		"Password used to generate the snmpv3 trap."
		::= { fibeAir4800OduAdmHostsEntry 6 }

	fibeAir4800OduAdmHostsIPv6 OBJECT-TYPE
		SYNTAX  DisplayString
		ACCESS  read-write
		STATUS  mandatory
		DESCRIPTION
		"Trap destination IPv6 address. A change is effective immediately."
		::= { fibeAir4800OduAdmHostsEntry 7 }
		
	fibeAir4800OduBuzzerAdminState OBJECT-TYPE
		SYNTAX  INTEGER
		ACCESS  read-write
		STATUS  mandatory
		DESCRIPTION
		"This parameter controls the activation of the buzzer while the unit is in install mode.
		A change is effective immediately. The valid values are: disabled (0), enabledAuto (1), enabledConstantly(2), advancedAuto (3)."
		::= { fibeAir4800OduAdmin 13 }

	fibeAir4800OduProductId OBJECT-TYPE
		SYNTAX  DisplayString
		ACCESS  read-only
		STATUS  mandatory
		DESCRIPTION
		"This parameter is reserved for the Manager application provided with the product."
		::= { fibeAir4800OduAdmin 14 }

	fibeAir4800OduReadCommunity OBJECT-TYPE
		SYNTAX  DisplayString
		ACCESS  read-write
		STATUS  mandatory
		DESCRIPTION
		"Read Community String. This parameter always returns ***** when retrieving its value.
		It is used by the Manager application to change the Read Community String.
		The SNMP agent accepts only encrypted values."
		::= { fibeAir4800OduAdmin 15 }

	fibeAir4800OduReadWriteCommunity OBJECT-TYPE
		SYNTAX  DisplayString
		ACCESS  read-write
		STATUS  mandatory
		DESCRIPTION
		"Read/Write Community String. This parameter always returns ***** when retrieving its value.
		It is used by the Manager application to change the Read/Write Community String.
		The SNMP agent accepts only encrypted values."
		::= { fibeAir4800OduAdmin 16 }

	fibeAir4800OduTrapCommunity OBJECT-TYPE
		SYNTAX  DisplayString
		ACCESS  read-write
		STATUS  mandatory
		DESCRIPTION
		"Trap Community String. This parameter is used by the Manager application to change the Trap Community String.
		The SNMP agent accepts only encrypted values."
		::= { fibeAir4800OduAdmin 17 }

	fibeAir4800OduAdmSnmpAgentVersion OBJECT-TYPE
		SYNTAX  INTEGER
		ACCESS  read-only
		STATUS  mandatory
		DESCRIPTION
		"Major version of the SNMP agent."
		::= { fibeAir4800OduAdmin 18 }

	fibeAir4800OduAdmRemoteSiteName OBJECT-TYPE
		SYNTAX  DisplayString
		ACCESS  read-only
		STATUS  mandatory
		DESCRIPTION
		"Remote site name. Returns the same value as sysLocation parameter of the remote site."
		::= { fibeAir4800OduAdmin 19 }

	fibeAir4800OduAdmSnmpAgentMinorVersion OBJECT-TYPE
		SYNTAX  INTEGER
		ACCESS  read-only
		STATUS  mandatory
		DESCRIPTION
		"Minor version of the SNMP agent."
		::= { fibeAir4800OduAdmin 20 }

	fibeAir4800OduAdmLinkPassword OBJECT-TYPE
		SYNTAX  DisplayString
		ACCESS  read-write
		STATUS  mandatory
		DESCRIPTION
		"Link Password. This parameter always returns ***** when retrieving its value.
		It is used by the Manager application to change the Link Password.
		The SNMP agent accepts only encrypted values."
		::= { fibeAir4800OduAdmin 21 }

	fibeAir4800OduAdmSiteLinkPassword OBJECT-TYPE
		SYNTAX  DisplayString
		ACCESS  read-write
		STATUS  mandatory
		DESCRIPTION
		"Site Link Password. This parameter always returns ***** when retrieving its value.
		It is used by the Manager application to change the Link Password of the site.
		The SNMP agent accepts only encrypted values."
		::= { fibeAir4800OduAdmin 22 }

	fibeAir4800OduAdmDefaultPassword OBJECT-TYPE
		SYNTAX  INTEGER {
			default(1),
			nonDefault(2)
			}
		ACCESS  read-only
		STATUS  mandatory
		DESCRIPTION
		"This parameter indicates if the current Link Password is the default password."
		::= { fibeAir4800OduAdmin 23 }

	fibeAir4800OduAdmConnectionType OBJECT-TYPE
		SYNTAX  INTEGER {
			directConnection(1),
			indirectConnection(2),
			unknown(3)
			}
		ACCESS  read-only
		STATUS  mandatory
		DESCRIPTION
		"This parameter indicates if the Manager application is connected to the local ODU
		or to the remote ODU over the air. A value of 'unknown' indicates community string mismatch."
		::= { fibeAir4800OduAdmin 24 }

	fibeAir4800OduAdmBackToFactorySettingsCmd OBJECT-TYPE
		SYNTAX  INTEGER {
			withIP(1),
			withoutIP(2)
			}
		ACCESS  read-write
		STATUS  mandatory
		DESCRIPTION
		"Back to factory settings Command. A change is effective after reset. 
		The read value is always 0."
		::= { fibeAir4800OduAdmin 25 }
		
	fibeAir4800OduAdmIpParamsCnfg OBJECT-TYPE
		SYNTAX  DisplayString
		ACCESS  read-write
		STATUS  mandatory
		DESCRIPTION
		"ODU IP address Configuration. The format is: <IP_Address>|<Subnet_Mask>|<Default_Gateway>|"
		::= { fibeAir4800OduAdmin 26 }

	fibeAir4800OduAdmVlanID OBJECT-TYPE
		SYNTAX INTEGER (0..4094)
		ACCESS  read-write
		STATUS mandatory
		DESCRIPTION
		"VLAN ID. Valid values are 1 to 4094.
		Initial value is 0 meaning VLAN unaware."
		::= { fibeAir4800OduAdmin 27 }  

	fibeAir4800OduAdmVlanPriority OBJECT-TYPE
		SYNTAX INTEGER (0..7)
		ACCESS  read-write
		STATUS mandatory
		DESCRIPTION
		"VLAN Priority. 0 is lowest priority, 7 is highest priority."
		::= { fibeAir4800OduAdmin 28 }  
		
	fibeAir4800OduAdmSN OBJECT-TYPE
        SYNTAX  DisplayString
		ACCESS  read-only
		STATUS  mandatory
        DESCRIPTION
        "ODU Serial Number"
        ::= { fibeAir4800OduAdmin 29 }

	fibeAir4800OduAdmProductName OBJECT-TYPE
		SYNTAX DisplayString
		ACCESS  read-only
		STATUS mandatory
		DESCRIPTION
		"This is the product name as it exists at EC"
		::= { fibeAir4800OduAdmin 30 }
		
	fibeAir4800OduAdmActivationKey OBJECT-TYPE
		SYNTAX  DisplayString
		ACCESS  read-write
		STATUS  mandatory
		DESCRIPTION
		"Activates a general key."
		::= { fibeAir4800OduAdmin 31 }
		
	fibeAir4800OduAdmRmtPermittedOduType OBJECT-TYPE
		SYNTAX  DisplayString
		ACCESS  read-write
		STATUS  mandatory
		DESCRIPTION
		"Mobile Application: permitted partner OduType."
		::= { fibeAir4800OduAdmin 32 }
		
	fibeAir4800OduAdmCpuID OBJECT-TYPE
		SYNTAX  INTEGER (0..64)
		ACCESS  read-only
		STATUS  mandatory
		DESCRIPTION
		"CPU ID"
		::= { fibeAir4800OduAdmin 33 }
		
	fibeAir4800OduAdmOvrdCmd OBJECT-TYPE
		SYNTAX  DisplayString
		ACCESS  read-write
		STATUS  mandatory
		DESCRIPTION
		"Ability to perform special command in the ODU."
		::= { fibeAir4800OduAdmin 34 }
				
	fibeAir4800OduAdmLinkMode OBJECT-TYPE
		SYNTAX  INTEGER {
			pmpHbs (1),
			pmpHsu (2),
			pmpHsuHyb (3),
			pmpHbsHyb (4)
			}
		ACCESS  read-write
		STATUS  mandatory
		DESCRIPTION
		"Unit PMP operation mode."
		::= { fibeAir4800OduAdmin 35 }
		
	fibeAir4800OduAdmActualConnectMode OBJECT-TYPE
		SYNTAX  INTEGER {
			none (1),
			ptp (2),
			ptmp (3)
			}
		ACCESS  read-only
		STATUS  mandatory
		DESCRIPTION
		"Unit connected as part to ptp or ptmp."
		::= { fibeAir4800OduAdmin 36 }
		
	fibeAir4800OduAdmAES256Support OBJECT-TYPE
		SYNTAX  INTEGER {
			notSupported (1),
			supported (2)
			}
		ACCESS  read-only
		STATUS  mandatory
		DESCRIPTION
		"AES-256 security support indication."
		::= { fibeAir4800OduAdmin 37 }
		
	fibeAir4800OduAdmAES256State OBJECT-TYPE
		SYNTAX  INTEGER {
			disabled (1),
			enabled (2)
			}
		ACCESS  read-write
		STATUS  mandatory
		DESCRIPTION
		"Enable/Disable AES-256 security mode over the air link."
		::= { fibeAir4800OduAdmin 38 }
		
	fibeAir4800OduAdmAES256Status OBJECT-TYPE
		SYNTAX  INTEGER {
			notOperating (1),
			partiallyOperating (2),
			operating (3)
			}
		ACCESS  read-only
		STATUS  mandatory
		DESCRIPTION
		"AES256 operating status"
		::= { fibeAir4800OduAdmin 39 }

	fibeAir4800OduAdmBatterySavingShutdownTime OBJECT-TYPE
		SYNTAX  INTEGER (0..1000)
		ACCESS  read-write
		STATUS  mandatory
		DESCRIPTION
		"Battery Saving Shutdown Time in minutes, 0 till battery run out, -1 if not supported."
		::= { fibeAir4800OduAdmin 40 }

	fibeAir4800OduAdmWiFiPowerMode OBJECT-TYPE
		SYNTAX  INTEGER {
			undefined (1),
			powerON (2),
			powerOFF (3),
			alwaysON (4)
			}
		ACCESS  read-write
		STATUS  mandatory
		DESCRIPTION
		"WIFI unit power mode."
		::= { fibeAir4800OduAdmin 41 }
	
	fibeAir4800OduAdmShutdownTimer OBJECT-TYPE
		SYNTAX  INTEGER (0..2147483647)
		ACCESS  read-only
		STATUS  mandatory
		DESCRIPTION
		"Shutdown Timer in seconds."
		::= { fibeAir4800OduAdmin 42 }
	
	fibeAir4800OduAdmGPSState OBJECT-TYPE
		SYNTAX  INTEGER {
			undefined (1),
			notSynchronized (2),
			fixed (3),
			shortCircuit (4),
			faulty (5),
			synchronized (6),
			synchronizedGlonass (7)
			}
		ACCESS  read-only
		STATUS  mandatory
		DESCRIPTION
		"GPS state"
		::= { fibeAir4800OduAdmin 43 }
		
	fibeAir4800OduAdmTemperatureC OBJECT-TYPE
		SYNTAX  INTEGER
		ACCESS  read-only
		STATUS  mandatory
		DESCRIPTION
		"The temperature (Celsius) inside the Board."
		::= { fibeAir4800OduAdmin 44 }	
	
	fibeAir4800OduAdmIPStackMode OBJECT-TYPE
		SYNTAX  INTEGER {
			v4 (1),
			v6 (2),
			v4andv6 (3)
			}
		ACCESS  read-write
		STATUS  mandatory
		DESCRIPTION
		"The IP stack mode."
		::= { fibeAir4800OduAdmin 45 }	
		
	fibeAir4800OduAdmIPv6ParamsCnfg OBJECT-TYPE
		SYNTAX  DisplayString
		ACCESS  read-write
		STATUS  mandatory
		DESCRIPTION
		"ODU IPv6 address Configuration. The format is: <IP_Address>|<Subnet_Mask>|<Default_Gateway>|"
		::= { fibeAir4800OduAdmin 46 }

	fibeAir4800OduAdmIPv6Address OBJECT-TYPE
		SYNTAX  DisplayString
		ACCESS  read-only
		STATUS  mandatory
		DESCRIPTION
		"ODU IPv6 address."
		::= { fibeAir4800OduAdmin 47 }

	fibeAir4800OduAdmIPv6Prefix OBJECT-TYPE
		SYNTAX  INTEGER
		ACCESS  read-only
		STATUS  mandatory
		DESCRIPTION
		"ODU IPv6 subnet mask."
		::= { fibeAir4800OduAdmin 48 }	

	fibeAir4800OduAdmIPv6DefaultGateWay OBJECT-TYPE
		SYNTAX  DisplayString
		ACCESS  read-only
		STATUS  mandatory
		DESCRIPTION
		"ODU IPv6 default gateway."
		::= { fibeAir4800OduAdmin 49 }
					
	fibeAir4800OduAdmPowerConsumption OBJECT-TYPE
		SYNTAX  INTEGER
		ACCESS  read-only
		STATUS  mandatory
		DESCRIPTION
		"Power Consumption (mWatt)"
		::= { fibeAir4800OduAdmin 50 }	
	
	-- ###########################################################
	--                      ODU Wifi
	-- ###########################################################
	
	fibeAir4800OduAdmWifi OBJECT IDENTIFIER ::= { fibeAir4800OduAdmin 51 }
	
	fibeAir4800OduAdmWifiChannel OBJECT-TYPE
		SYNTAX  INTEGER (1..11)
		ACCESS  read-write
		STATUS  mandatory
		DESCRIPTION
		"Wifi Channel"
		::= { fibeAir4800OduAdmWifi 1 }	

	fibeAir4800OduAdmWifiTxPower OBJECT-TYPE
		SYNTAX  INTEGER (11..15)
		ACCESS  read-write
		STATUS  mandatory
		DESCRIPTION
		"Wifi TX Power"
		::= { fibeAir4800OduAdmWifi 2 }				

	fibeAir4800OduAdmWifiSSID OBJECT-TYPE
		SYNTAX  DisplayString
		ACCESS  read-only
		STATUS  mandatory
		DESCRIPTION
		"Wifi SSID"
		::= { fibeAir4800OduAdmWifi 3 }		

	fibeAir4800OduAdmWifiSecurityType OBJECT-TYPE
		SYNTAX  INTEGER {
			open (1),
			wep (2),
			wpa2 (3)
			}
		ACCESS  read-only
		STATUS  mandatory
		DESCRIPTION
		"Wifi Security type"
		::= { fibeAir4800OduAdmWifi 4 }			

	fibeAir4800OduAdmWifiPassword OBJECT-TYPE
		SYNTAX  DisplayString
		ACCESS  read-write
		STATUS  mandatory
		DESCRIPTION
		"Wifi Password"
		::= { fibeAir4800OduAdmWifi 5 }		
		
	fibeAir4800OduAdmWifiNetwork OBJECT-TYPE
		SYNTAX  IpAddress
		ACCESS  read-write
		STATUS  mandatory
		DESCRIPTION
		"Wifi Network"
		::= { fibeAir4800OduAdmWifi 6 }	

	fibeAir4800OduAdmWifiRssi OBJECT-TYPE
		SYNTAX  INTEGER
		ACCESS  read-only
		STATUS  mandatory
		DESCRIPTION
		"Wifi RSSI"
		::= { fibeAir4800OduAdmWifi 7 }	

	fibeAir4800OduAdmWifiStationMAC OBJECT-TYPE
		SYNTAX  DisplayString
		ACCESS  read-only
		STATUS  mandatory
		DESCRIPTION
		"Wifi Station MAC"
		::= { fibeAir4800OduAdmWifi 8 }		

	fibeAir4800OduAdmWifiRestart OBJECT-TYPE
		SYNTAX  INTEGER (1)
		ACCESS  read-write
		STATUS  mandatory
		DESCRIPTION
		"A set command with a value of 1 will cause a Wifi restart.
		The read value is always 0."
		::= { fibeAir4800OduAdmWifi 9 }		

	fibeAir4800OduAdmWifiApStatus OBJECT-TYPE
		SYNTAX  INTEGER {
			off (1),
			on (2),
			connected (3)
			}
		ACCESS  read-only
		STATUS  mandatory
		DESCRIPTION
		"Wifi AP Status"
		::= { fibeAir4800OduAdmWifi 10 }			

	fibeAir4800OduAdmBsaOperationMode OBJECT-TYPE
		SYNTAX  INTEGER {
			inactive (1),
			hbsTracking (2),
			hsuAlignment (3)
			}
		ACCESS  read-only
		STATUS  mandatory
		DESCRIPTION
		"BSA Operation Mode"
		::= { fibeAir4800OduAdmin 52 }		
		
	-- ###########################################################
	--                      ODU Service
	-- ###########################################################

	fibeAir4800OduService OBJECT IDENTIFIER ::= { fibeAir4800Odu 2 }

	fibeAir4800OduSrvMode OBJECT-TYPE
		SYNTAX  INTEGER {
			installMode (1),
			normalMode (2),
			slaveMode (3),
			tempInstallMode (4),
			inactiveMode (5)
			}
		ACCESS  read-write
		STATUS  mandatory
		DESCRIPTION
		"System mode. The only values that can be set are installMode and slaveMode;
		normalMode reserved to the Manager application provided with the product.
		A change is effective after link re-synchronization."
		::= { fibeAir4800OduService 1 }

	fibeAir4800OduSrvBridging OBJECT-TYPE
		SYNTAX  INTEGER
		ACCESS  read-only
		STATUS  mandatory
		DESCRIPTION
		"Bridging Mode. Valid values are: disabled (0), enabled (1)."
		::= { fibeAir4800OduService 3 }
		
	-- ###########################################################
	--                      ODU Ring Topology
	-- ###########################################################
	
	fibeAir4800OduServiceRingTopology OBJECT IDENTIFIER ::= { fibeAir4800OduService 4 }
	
	fibeAir4800OduSrvRingLinkMode OBJECT-TYPE
		SYNTAX  INTEGER {
			independentLink (1),				
			nonRpl (2),
			rpl (3)	
			}
		ACCESS  read-write
		STATUS  mandatory
		DESCRIPTION
		"Mode of the link regarding ring topology."
		::= { fibeAir4800OduServiceRingTopology 1 }		

	fibeAir4800OduSrvRingTopologySupported OBJECT-TYPE
		SYNTAX  INTEGER {
			notSupported (1),
			supported (2)			
			}
		ACCESS  read-only
		STATUS  mandatory
		DESCRIPTION
		"Ring Topology, options are: supported, not supported"
		::= { fibeAir4800OduServiceRingTopology 2 }
		
	fibeAir4800OduSrvRingVlanIdTable OBJECT-TYPE
		SYNTAX  SEQUENCE OF FibeAir4800OduSrvRingVlanIdEntry
		ACCESS  not-accessible
		STATUS  mandatory
		DESCRIPTION
		"Ring VLAN IDs table."
		::= { fibeAir4800OduServiceRingTopology 3 }

	fibeAir4800OduSrvRingVlanIdEntry OBJECT-TYPE
		SYNTAX  FibeAir4800OduSrvRingVlanIdEntry
		ACCESS  not-accessible
		STATUS  mandatory
		DESCRIPTION
		"VLAN ID of the internal ring messages. Valid values are 1 to 4094.
		Initial value is 0 meaning VLAN unaware."
		INDEX { fibeAir4800OduSrvRingVlanIdIndex }
		::= { fibeAir4800OduSrvRingVlanIdTable 1 }

	FibeAir4800OduSrvRingVlanIdEntry ::= SEQUENCE {
		fibeAir4800OduSrvRingVlanIdIndex
			INTEGER,
		fibeAir4800OduSrvRingVlanId
			INTEGER
		}

	fibeAir4800OduSrvRingVlanIdIndex OBJECT-TYPE
		SYNTAX  INTEGER (0..3)
		ACCESS  read-only
		STATUS  mandatory
		DESCRIPTION
		"Index of VLAN ID of the internal ring messages."			
		::= { fibeAir4800OduSrvRingVlanIdEntry 1 }

	fibeAir4800OduSrvRingVlanId OBJECT-TYPE
		SYNTAX  INTEGER (0..4094)
		ACCESS  read-write
		STATUS  mandatory
		DESCRIPTION
		"VLAN ID of the internal ring messages. Valid values are 1 to 4094.
		Initial value is 0 meaning VLAN unaware."
		::= { fibeAir4800OduSrvRingVlanIdEntry 2 }
		
		
	fibeAir4800OduSrvRingEthStatus OBJECT-TYPE
		SYNTAX  INTEGER {				
			unblocked(1),				
			blocked(2),
			notApplicable(3)
			}
		ACCESS  read-only
		STATUS  mandatory
		DESCRIPTION
		"Represents the Ethernet service blocking state of a Rings link"
		::= { fibeAir4800OduServiceRingTopology 4 } 			
			
	fibeAir4800OduSrvRingMaxAllowedTimeFromLastRpm OBJECT-TYPE
		SYNTAX  INTEGER 
		ACCESS  read-write
		STATUS  mandatory
		DESCRIPTION
		"Defines the minimal time (in ms) required for determination of ring failure."
		::= { fibeAir4800OduServiceRingTopology 5 }			
			
	fibeAir4800OduSrvRingWTR OBJECT-TYPE
		SYNTAX  INTEGER 
		ACCESS  read-write
		STATUS  mandatory
		DESCRIPTION
		"Defines the minimal time (in ms) required for ring recovery."
		::= { fibeAir4800OduServiceRingTopology 6 }			
		-- ###########################################################
		--                      ODU QoS
		-- ###########################################################
		
		fibeAir4800OduServiceQoS OBJECT IDENTIFIER ::= { fibeAir4800OduService 5 }
		
		fibeAir4800OduSrvQoSMode OBJECT-TYPE
			SYNTAX  INTEGER {
				notSupported (1),				
				notActive (2),
				classVlan (3),
				classDiffserv (4)
				}
			ACCESS  read-write
			STATUS  mandatory
			DESCRIPTION
			"Mode of QoS feature."
			::= { fibeAir4800OduServiceQoS 1 }
			
		fibeAir4800OduSrvQoSConfTable OBJECT-TYPE
			SYNTAX  SEQUENCE OF FibeAir4800OduSrvQoSConfEntry
			ACCESS  not-accessible
			STATUS  mandatory
			DESCRIPTION
			"QoS configuration table."
			::= { fibeAir4800OduServiceQoS 2 }
			
		fibeAir4800OduSrvQoSConfEntry OBJECT-TYPE
			SYNTAX  FibeAir4800OduSrvQoSConfEntry
			ACCESS  not-accessible
			STATUS  mandatory
			DESCRIPTION
			"QoS configuration table."
			INDEX { fibeAir4800OduSrvQoSConfIndex }
			::= { fibeAir4800OduSrvQoSConfTable 1 }
			
		FibeAir4800OduSrvQoSConfEntry ::= SEQUENCE {
			fibeAir4800OduSrvQoSConfIndex
				INTEGER,
			fibeAir4800OduSrvConfVlanQGroups
				INTEGER,
			fibeAir4800OduSrvConfDiffservQGroups
				INTEGER,
			fibeAir4800OduSrvConfQueMir
				INTEGER,
			fibeAir4800OduSrvConfQueWeight
				INTEGER
			}
			
		fibeAir4800OduSrvQoSConfIndex OBJECT-TYPE
			SYNTAX  INTEGER (0..3)
			ACCESS  read-only
			STATUS  mandatory
			DESCRIPTION
			"Index of QoS Configuration."			
			::= { fibeAir4800OduSrvQoSConfEntry 1 }
			
		fibeAir4800OduSrvConfVlanQGroups OBJECT-TYPE
			SYNTAX  INTEGER (0..7)
			ACCESS  read-only
			STATUS  mandatory
			DESCRIPTION
			"Frames classification according to VLAN Priority IDs."			
			::= { fibeAir4800OduSrvQoSConfEntry 2 }
			
		fibeAir4800OduSrvConfDiffservQGroups OBJECT-TYPE
			SYNTAX  INTEGER (0..48)
			ACCESS  read-only
			STATUS  mandatory
			DESCRIPTION
			"Frames classification according to Diffserv."			
			::= { fibeAir4800OduSrvQoSConfEntry 3 }
			
		fibeAir4800OduSrvConfQueMir OBJECT-TYPE
			SYNTAX  INTEGER 
			ACCESS  read-write
			STATUS  mandatory
			DESCRIPTION
			"Desired Private MIR."			
			::= { fibeAir4800OduSrvQoSConfEntry 4 }
			
		fibeAir4800OduSrvConfQueWeight OBJECT-TYPE
			SYNTAX  INTEGER (0..100)
			ACCESS  read-write
			STATUS  mandatory
			DESCRIPTION
			"QoS queueu's weights in percent."			
			::= { fibeAir4800OduSrvQoSConfEntry 5 }		
			
		fibeAir4800OduSrvQoSVlanQGroupsSetStr OBJECT-TYPE
			SYNTAX  DisplayString
			ACCESS  read-write
			STATUS  mandatory
			DESCRIPTION
			"Frames classification according to VLAN IDs string for set."
			::= { fibeAir4800OduServiceQoS 3 }
			
		fibeAir4800OduSrvQoSDiffservQGroupsSetStr OBJECT-TYPE
			SYNTAX  DisplayString
			ACCESS  read-write
			STATUS  mandatory
			DESCRIPTION
			"Frames classification according to Diffserv IDs string for set."
			::= { fibeAir4800OduServiceQoS 4 }
			
		fibeAir4800OduSrvQoSMaxRTQuePercent OBJECT-TYPE
			SYNTAX  INTEGER (0..100)				
			ACCESS  read-only
			STATUS  mandatory
			DESCRIPTION
			"Maximal percent for RT & NRT queues."
			::= { fibeAir4800OduServiceQoS 5 }
		
		-- ###########################################################
		--                      ODU VLAN Configuration
		-- ###########################################################
		
		fibeAir4800OduServiceVlan OBJECT IDENTIFIER ::= { fibeAir4800OduService 6 }
		
		fibeAir4800OduSrvVlanSupport OBJECT-TYPE
			SYNTAX  INTEGER {
				notSupported (1),				
				supported(2),
				available(3)
				}
			ACCESS  read-only
			STATUS  mandatory
			DESCRIPTION
			"ODU Ethernet port VLAN support and configuration availability indication.
			1 - ODU VLAN Functionality Not Supported
			2 - ODU VLAN Functionality Supported
			3 - ODU VLAN Functionality Supported and Available"
			::= { fibeAir4800OduServiceVlan 1 }
			
		fibeAir4800OduSrvVlanIngressMode OBJECT-TYPE
			SYNTAX  INTEGER {
				transparent (1),				
				untagAll    (2),
				filter      (3)
				}
			ACCESS  read-write
			STATUS  mandatory
			DESCRIPTION
			"ODU Ethernet port ingress VLAN mode."
			::= { fibeAir4800OduServiceVlan 2 }
			
		fibeAir4800OduSrvVlanEgressMode OBJECT-TYPE
			SYNTAX  INTEGER {
				transparent (1),				
				tag (2),
				provider (3)
				}
			ACCESS  read-write
			STATUS  mandatory
			DESCRIPTION
			"ODU Ethernet port egress VLAN mode."
			::= { fibeAir4800OduServiceVlan 3 }
			
		fibeAir4800OduSrvEgressTag OBJECT-TYPE
			SYNTAX  INTEGER (0..40947)
			ACCESS  read-write
			STATUS  mandatory
			DESCRIPTION
			"ODU ethernet port egress VLAN tag.
			Right most digit is Vlan priority (0-7), 
			other digits compose Vlan Id (2-4094)"
			::= { fibeAir4800OduServiceVlan 4 }
			
		fibeAir4800OduSrvEgressProviderTag OBJECT-TYPE
			SYNTAX  INTEGER (0..40947)
			ACCESS  read-write
			STATUS  mandatory
			DESCRIPTION
			"ODU ethernet port egress Provider VLAN tag.
			Right most digit is Vlan priority (0-7), 
			other digits compose Vlan Id (2-4094)"
			::= { fibeAir4800OduServiceVlan 5 }
			
		fibeAir4800OduSrvVlanIngressAllowedVIDs OBJECT-TYPE
			SYNTAX  DisplayString
			ACCESS  read-write
			STATUS  mandatory
			DESCRIPTION
			"ODU ethernet port VLAN IDs that will not be filtered on ingress.
			w|w|w|w|w|w|w|w| ( where w = {0-4094} and w != 1 )"
			::= { fibeAir4800OduServiceVlan 6 }
			
		fibeAir4800OduSrvVlanDisable OBJECT-TYPE
			SYNTAX  INTEGER
			ACCESS  read-write
			STATUS  mandatory
			DESCRIPTION
			"Disable VLAN functionality. The following values can be set:
			3 - Disable ODU & IDU VLAN Configurations."
			::= { fibeAir4800OduServiceVlan 7 }	
			
		fibeAir4800OduServiceVlanProviderListTPIDstr OBJECT-TYPE
			SYNTAX  DisplayString
			ACCESS  read-only
			STATUS  mandatory
			DESCRIPTION
			"Holds the possible Provider TPIDs."
			::= { fibeAir4800OduServiceVlan 8 }
			
	-- ###########################################################
	--                      ODU Ethernet
	-- ###########################################################

	fibeAir4800OduEthernet OBJECT IDENTIFIER ::= { fibeAir4800Odu 3 }

	fibeAir4800OduEthernetRemainingRate OBJECT-TYPE
		SYNTAX  INTEGER
		ACCESS  read-only
		STATUS  mandatory
		DESCRIPTION
		"Current Ethernet bandwidth in bps."
		::= { fibeAir4800OduEthernet 1 }	

	-- ###########################################################
	--                      ODU Ethernet Interface Table
	-- ###########################################################

	fibeAir4800OduEthernetIfTable OBJECT-TYPE
		SYNTAX  SEQUENCE OF FibeAir4800OduEthernetIfEntry
		ACCESS  not-accessible
		STATUS  mandatory
		DESCRIPTION
		"ODU Ethernet Interface table."
		::= { fibeAir4800OduEthernet 2 }

	fibeAir4800OduEthernetIfEntry OBJECT-TYPE
		SYNTAX  FibeAir4800OduEthernetIfEntry
		ACCESS  not-accessible
		STATUS  mandatory
		DESCRIPTION
		"ODU Ethernet Interface table entry."
		INDEX { fibeAir4800OduEthernetIfIndex }
		::= { fibeAir4800OduEthernetIfTable 1 }

	FibeAir4800OduEthernetIfEntry ::= SEQUENCE {
		fibeAir4800OduEthernetIfIndex
			INTEGER,
		fibeAir4800OduEthernetIfAddress
			DisplayString,
		fibeAir4800OduEthernetIfAdminStatus
			INTEGER,
		fibeAir4800OduEthernetIfOperStatus
			INTEGER,
		fibeAir4800OduEthernetIfFailAction
			INTEGER
		}

	fibeAir4800OduEthernetIfIndex OBJECT-TYPE
		SYNTAX  INTEGER
		ACCESS  read-only
		STATUS  mandatory
		DESCRIPTION
		"ODU Ethernet Interface Index." 
		::= { fibeAir4800OduEthernetIfEntry 1 }	

	fibeAir4800OduEthernetIfAddress OBJECT-TYPE
		SYNTAX  DisplayString
		ACCESS  read-only
		STATUS  mandatory
		DESCRIPTION
		"ODU MAC address."
		::= { fibeAir4800OduEthernetIfEntry 5 }

	fibeAir4800OduEthernetIfAdminStatus OBJECT-TYPE
		SYNTAX  INTEGER {
			portAutoSense(1),
			portAutoSense100Mbps(5),			
			forceHalfDuplex10Mbps(10),			
			forceFullDuplex10Mbps(11),
			forceHalfDuplex100Mbps(15),
			forceFullDuplex100Mbps(16),
			forceFullDuplex1000Mbps(21),
			disablePoePort(254),			
			disablePort(255)
			}
		ACCESS  read-write
		STATUS  mandatory
		DESCRIPTION
		"Required state of the interface."
		::= { fibeAir4800OduEthernetIfEntry 6 }	

	fibeAir4800OduEthernetIfOperStatus OBJECT-TYPE
		SYNTAX  INTEGER {
			notConnected(1),
			connectedHalfDuplex10Mbps(10),
			connectedFullDuplex10Mbps(11),
			connectedHalfDuplex100Mbps(15),
			connectedFullDuplex100Mbps(16),
			connectedHalfDuplex1000Mbps(20),
			connectedFullDuplex1000Mbps(21),
			unknown(65535)
			}
		ACCESS  read-only
		STATUS  mandatory
		DESCRIPTION
		"Current operational state of the interface."
		::= { fibeAir4800OduEthernetIfEntry 7 }
		
	fibeAir4800OduEthernetIfFailAction OBJECT-TYPE
		SYNTAX  INTEGER {
			faNoAction(1),
			faForceHalfDuplex10Mbps(10),			
			faForceFullDuplex10Mbps(11),
			faDisablePort(255)
			}
		ACCESS  read-write
		STATUS  mandatory
		DESCRIPTION
		"Failure action of the interface."
		::= { fibeAir4800OduEthernetIfEntry 8 }			

	fibeAir4800OduEthernetNumOfPorts OBJECT-TYPE
		SYNTAX  INTEGER
		ACCESS  read-only
		STATUS  mandatory
		DESCRIPTION
		"Number of ODU network interfaces."
		::= { fibeAir4800OduEthernet 3 }
		
	
	fibeAir4800OduEthernetGbeSupported OBJECT-TYPE
		SYNTAX  INTEGER {notSupported(1), supported(2)}
		ACCESS  read-only
		STATUS  mandatory
		DESCRIPTION
		"Supported Giga bit Ethernet in ODU."
		::= { fibeAir4800OduEthernet 4 }	

	-- ###########################################################
	--                      ODU Bridge
	-- ###########################################################

	fibeAir4800OduBridge OBJECT IDENTIFIER ::= { fibeAir4800Odu 4 }

	-- ###########################################################
	--                      ODU Bridge Base
	-- ###########################################################

	fibeAir4800OduBridgeBase OBJECT IDENTIFIER ::= { fibeAir4800OduBridge 1 }

	-- ###########################################################
	--                      ODU Bridge Ports Table
	-- ###########################################################

	fibeAir4800OduBridgeBasePortTable OBJECT-TYPE
		SYNTAX  SEQUENCE OF FibeAir4800OduBridgeBasePortEntry
		ACCESS  not-accessible
		STATUS  mandatory
		DESCRIPTION
		"ODU Bridge Ports table."
		::= { fibeAir4800OduBridgeBase 4 }

	fibeAir4800OduBridgeBasePortEntry OBJECT-TYPE
		SYNTAX  FibeAir4800OduBridgeBasePortEntry
		ACCESS  not-accessible
		STATUS  mandatory
		DESCRIPTION
		"ODU Bridge Ports table entry."
		INDEX { fibeAir4800OduBridgeBasePortIndex }
		::= { fibeAir4800OduBridgeBasePortTable 1 }

	FibeAir4800OduBridgeBasePortEntry ::= SEQUENCE {
		fibeAir4800OduBridgeBasePortIndex
			INTEGER,
		fibeAir4800OduBridgeBaseIfIndex
			INTEGER
		}

	fibeAir4800OduBridgeBasePortIndex OBJECT-TYPE
		SYNTAX  INTEGER
		ACCESS  read-only
		STATUS  mandatory
		DESCRIPTION
		"ODU Bridge Port Number."
		::= { fibeAir4800OduBridgeBasePortEntry 1 }

	fibeAir4800OduBridgeBaseIfIndex OBJECT-TYPE
		SYNTAX  INTEGER
		ACCESS  read-only
		STATUS  mandatory
		DESCRIPTION
		"IfIndex corresponding to ODU Bridge port."
		::= { fibeAir4800OduBridgeBasePortEntry 2 }

	-- ###########################################################
	--                      ODU Bridge Tp
	-- ###########################################################

	fibeAir4800OduBridgeTp OBJECT IDENTIFIER ::= { fibeAir4800OduBridge 4 }

	fibeAir4800OduBridgeTpMode OBJECT-TYPE
		SYNTAX  INTEGER
		ACCESS  read-write
		STATUS  mandatory
		DESCRIPTION
		"ODU bridge mode. 
		A change is effective after reset. Valid values: hubMode (0), bridgeMode (1)."
		::= { fibeAir4800OduBridgeTp 101 }

	-- ###########################################################
	--                      ODU Transparent Bridge Ports Table
	-- ###########################################################

	fibeAir4800OduBridgeTpPortTable OBJECT-TYPE
		SYNTAX  SEQUENCE OF FibeAir4800OduBridgeTpPortEntry
		ACCESS  not-accessible
		STATUS  mandatory
		DESCRIPTION
		"ODU Transparent Bridge Ports table."
		::= { fibeAir4800OduBridgeTp 3 }

	fibeAir4800OduBridgeTpPortEntry OBJECT-TYPE
		SYNTAX  FibeAir4800OduBridgeTpPortEntry
		ACCESS  not-accessible
		STATUS  mandatory
		DESCRIPTION
		"ODU Transparent Bridge Ports table entry."
		INDEX { fibeAir4800OduBridgeTpPortIndex }
		::= { fibeAir4800OduBridgeTpPortTable 1 }

	FibeAir4800OduBridgeTpPortEntry ::= SEQUENCE {
		fibeAir4800OduBridgeTpPortIndex
			INTEGER,
		fibeAir4800OduBridgeTpPortInFrames
			Counter,
		fibeAir4800OduBridgeTpPortOutFrames
			Counter,
		fibeAir4800OduBridgeTpPortInBytes
			Counter,
		fibeAir4800OduBridgeTpPortOutBytes
			Counter
		}

	fibeAir4800OduBridgeTpPortIndex OBJECT-TYPE
		SYNTAX  INTEGER
		ACCESS  read-only
		STATUS  mandatory
		DESCRIPTION
		"ODU Transparent Bridge Port Number."
		::= { fibeAir4800OduBridgeTpPortEntry 1 }

	fibeAir4800OduBridgeTpPortInFrames OBJECT-TYPE
		SYNTAX  Counter
		ACCESS  read-only
		STATUS  mandatory
		DESCRIPTION
		"Number of frames received by this port."
		::= { fibeAir4800OduBridgeTpPortEntry 3 }

	fibeAir4800OduBridgeTpPortOutFrames OBJECT-TYPE
		SYNTAX  Counter
		ACCESS  read-only
		STATUS  mandatory
		DESCRIPTION
		"Number of frames transmitted by this port."
		::= { fibeAir4800OduBridgeTpPortEntry 4 }

	fibeAir4800OduBridgeTpPortInBytes OBJECT-TYPE
		SYNTAX  Counter
		ACCESS  read-only
		STATUS  mandatory
		DESCRIPTION
		"Number of bytes received by this port."
		::= { fibeAir4800OduBridgeTpPortEntry 101 }

	fibeAir4800OduBridgeTpPortOutBytes OBJECT-TYPE
		SYNTAX  Counter
		ACCESS  read-only
		STATUS  mandatory
		DESCRIPTION
		"Number of bytes transmitted by this port."
		::= { fibeAir4800OduBridgeTpPortEntry 102 }
		
	fibeAir4800OduBridgeConfigMode OBJECT-TYPE
		SYNTAX  INTEGER{
			enable (1),
			disable (2)
			}
		ACCESS  read-only
		STATUS  mandatory
		DESCRIPTION
		"ODU bridge configuration mode"
		::= { fibeAir4800OduBridgeTp 102 }

	-- ###########################################################
	--                      ODU Air
	-- ###########################################################

	fibeAir4800OduAir OBJECT IDENTIFIER ::= { fibeAir4800Odu 5 }

	fibeAir4800OduAirFreq OBJECT-TYPE
		SYNTAX  INTEGER
		ACCESS  read-write
		STATUS  mandatory
		DESCRIPTION
		"Installation Center Frequency. Valid values are product dependent. A change is effective after link re-synchronization."
		::= { fibeAir4800OduAir 1 }

	fibeAir4800OduAirDesiredRate OBJECT-TYPE
		SYNTAX  INTEGER
		ACCESS  read-write
		STATUS  deprecated
		DESCRIPTION
		"Deprecated parameter, actual behavior is read-only. 
		Required Air Rate. For Channel Bandwidth of 20, 10, 5 MHz divide the value by 1, 2, 4 respectively."
		::= { fibeAir4800OduAir 2 }

	fibeAir4800OduAirSSID OBJECT-TYPE
		SYNTAX  DisplayString
		ACCESS  read-write
		STATUS  mandatory
		DESCRIPTION
		"Reserved for the Manager application provided with the product.
		 The Sector ID in Point-To-Multi-Point systems."
		::= { fibeAir4800OduAir 3 }

	fibeAir4800OduAirTxPower OBJECT-TYPE
		SYNTAX  INTEGER
		ACCESS  read-write
		STATUS  mandatory
		DESCRIPTION
		"Required Transmit power in dBm . This is a nominal value while the actual transmit power includes additional attenuation.
		The min and max values are product specific. A change is effective immediately."
		::= { fibeAir4800OduAir 4 }

	fibeAir4800OduAirSesState OBJECT-TYPE
		SYNTAX  INTEGER {
			sessionDown (1),
			basicRate (2),
			active (3),
			installation (4),
			scanning (5),
			probing (6),
			transmitting (7),
			activeWithDefaultEncryptionKey (8),
			installationWithDefaultEncryptionKey (9),
			bitFailed (10),
			activeWithVersionsMismatch (11),
			installationWithVersionsMismatch (12),
			inactive (13),
			iduIncompatible (14),
			spectrumAnalysis (15)
			}
		ACCESS  read-only
		STATUS  mandatory
		DESCRIPTION
		"Current Link State. The value is active (3) during normal operation." 
		::= { fibeAir4800OduAir 5 }

	fibeAir4800OduAirMstrSlv OBJECT-TYPE
		SYNTAX  INTEGER
		ACCESS  read-only
		STATUS  mandatory
		DESCRIPTION
		"This parameter indicates if the device was automatically selected into the radio link master or slave. 
		The value is undefined if there is no link.
		The value is relevant only for point to point systems."
		::= { fibeAir4800OduAir 6 }	

	fibeAir4800OduAirResync OBJECT-TYPE
		SYNTAX  INTEGER
		ACCESS  read-write
		STATUS  mandatory
		DESCRIPTION
		"Setting this parameter to 1 will cause the link to restart the synchronization process."
		::= { fibeAir4800OduAir 8 }

	-- ###########################################################
	--                      ODU Air Perf
	-- ###########################################################

	fibeAir4800OduAirPerf OBJECT IDENTIFIER ::= { fibeAir4800OduAir 9 }

	fibeAir4800OduAirRxPower OBJECT-TYPE
		SYNTAX  INTEGER
		ACCESS  read-only
		STATUS  mandatory
		DESCRIPTION
		"Received Signal Strength in dBm. Relevant only for point to point systems."
		::= { fibeAir4800OduAirPerf 1 }

	fibeAir4800OduAirTotalFrames OBJECT-TYPE
		SYNTAX  Counter
		ACCESS  read-only
		STATUS  mandatory
		DESCRIPTION
		"Total number of radio frames."
		::= { fibeAir4800OduAirPerf 2 }

	fibeAir4800OduAirBadFrames OBJECT-TYPE
		SYNTAX  Counter
		ACCESS  read-only
		STATUS  mandatory
		DESCRIPTION
		"Total number of received radio frames with CRC error. The value is relevant only for point to point systems ."
		::= { fibeAir4800OduAirPerf 3 }

	fibeAir4800OduAirCurrentRate OBJECT-TYPE
		SYNTAX  INTEGER
		ACCESS  read-only
		STATUS  deprecated
		DESCRIPTION
		"Deprecated parameter. Actual rate of the air interface in Mbps. 
		For Channel Bandwidth of 20, 10, 5 MHz divide the value by 1, 2, 4 respectively."
		::= { fibeAir4800OduAirPerf 4 }

	fibeAir4800OduAirCurrentRateIdx OBJECT-TYPE
		SYNTAX  INTEGER 
		ACCESS  read-only
		STATUS  mandatory
		DESCRIPTION
		"Index of current air rate."
		::= { fibeAir4800OduAirPerf 5 }
		
	fibeAir4800OduAirChainsRxPower OBJECT-TYPE
		SYNTAX  OCTET STRING
		ACCESS  read-only
		STATUS  mandatory
		DESCRIPTION
		"Received Signal Strength of Cpe chains in dBm.
		Chain 1 RSS: (1 Byte)
		Chain 2 RSS: (1 Byte)
		Chain 3 RSS: (1 Byte)"
		::= { fibeAir4800OduAirPerf 6 }

	fibeAir4800OduAirCurrentRateCBW OBJECT-TYPE
		SYNTAX  INTEGER 
		ACCESS  read-only
		STATUS  mandatory
		DESCRIPTION
		"CBW of current air rate."
		::= { fibeAir4800OduAirPerf 7 }
		
	fibeAir4800OduAirCurrentRateGI OBJECT-TYPE
		SYNTAX  INTEGER 
		ACCESS  read-only
		STATUS  mandatory
		DESCRIPTION
		"GI of current air rate."
		::= { fibeAir4800OduAirPerf 8 }
		
	fibeAir4800OduAirTxPower36 OBJECT-TYPE
		SYNTAX  INTEGER
		ACCESS  read-write
		STATUS  deprecated
		DESCRIPTION
		"Deprecated parameter. Actual behavior is read-only."
		::= { fibeAir4800OduAir 10 }

	fibeAir4800OduAirTxPower48 OBJECT-TYPE
		SYNTAX  INTEGER
		ACCESS  read-write
		STATUS  deprecated
		DESCRIPTION
		"Deprecated parameter. Actual behavior is read-only."
		::= { fibeAir4800OduAir 11 }

	fibeAir4800OduAirCurrentTxPower OBJECT-TYPE
		SYNTAX  INTEGER
		ACCESS  read-only
		STATUS  mandatory
		DESCRIPTION
		"Current Transmit Power in dBm. This is a nominal value while the actual transmit power includes additional attenuation."
		::= { fibeAir4800OduAir 12 }

	fibeAir4800OduAirMinFrequency OBJECT-TYPE
		SYNTAX  INTEGER
		ACCESS  read-only
		STATUS  mandatory
		DESCRIPTION
		"Minimum center frequency in MHz."
		::= { fibeAir4800OduAir 13 }

	fibeAir4800OduAirMaxFrequency OBJECT-TYPE
		SYNTAX  INTEGER
		ACCESS  read-only
		STATUS  mandatory
		DESCRIPTION
		"Maximum center frequency in MHz."
		::= { fibeAir4800OduAir 14 }

	fibeAir4800OduAirFreqResolution OBJECT-TYPE
		SYNTAX  INTEGER
		ACCESS  read-only
		STATUS  mandatory
		DESCRIPTION
		"Center Frequency resolution. 
		Measured in MHz if value < 100, otherwise in KHz."
		::= { fibeAir4800OduAir 15 }

	fibeAir4800OduAirCurrentFreq OBJECT-TYPE
		SYNTAX  INTEGER
		ACCESS  read-only
		STATUS  mandatory
		DESCRIPTION
		"Current Center Frequency.
		Measured in MHz if center frequency resolution value < 100, otherwise in KHz."
		::= { fibeAir4800OduAir 16 }

	fibeAir4800OduAirNumberOfChannels OBJECT-TYPE
		SYNTAX  INTEGER
		ACCESS  read-only
		STATUS  mandatory
		DESCRIPTION
		"Number of channels that can be used."
		::= { fibeAir4800OduAir 17 }

	-- ###########################################################
	--                      Channels Table
	-- ###########################################################

	fibeAir4800OduAirChannelsTable OBJECT-TYPE
		SYNTAX  SEQUENCE OF FibeAir4800OduAirChannelsEntry
		ACCESS  not-accessible
		STATUS  mandatory
		DESCRIPTION
		"Table of channels used by automatic channels selection (ACS)."
		::= { fibeAir4800OduAir 18 }

	fibeAir4800OduAirChannelsEntry OBJECT-TYPE
		SYNTAX  FibeAir4800OduAirChannelsEntry
		ACCESS  not-accessible
		STATUS  mandatory
		DESCRIPTION
		"ACS channels table entry."
		INDEX { fibeAir4800OduAirChannelsIndex }
		::= { fibeAir4800OduAirChannelsTable 1 }

	FibeAir4800OduAirChannelsEntry ::= SEQUENCE {
		fibeAir4800OduAirChannelsIndex
			INTEGER,
		fibeAir4800OduAirChannelsFrequency
			INTEGER,
		fibeAir4800OduAirChannelsOperState
			INTEGER,
		fibeAir4800OduAirChannelsAvail
			INTEGER,
		fibeAir4800OduAirChannelsDefaultFreq
			INTEGER
		}

	fibeAir4800OduAirChannelsIndex OBJECT-TYPE
		SYNTAX  INTEGER
		ACCESS  read-only
		STATUS  mandatory
		DESCRIPTION
		"Channel Index."
		::= { fibeAir4800OduAirChannelsEntry 1 }

	fibeAir4800OduAirChannelsFrequency OBJECT-TYPE
		SYNTAX  INTEGER
		ACCESS  read-only
		STATUS  mandatory
		DESCRIPTION
		"Channel frequency in MHz."
		::= { fibeAir4800OduAirChannelsEntry 2 }

	fibeAir4800OduAirChannelsOperState OBJECT-TYPE
		SYNTAX  INTEGER
		ACCESS  read-write
		STATUS  mandatory
		DESCRIPTION
		"Channel state. Can be set by the user. 
		 Automatic Channel Selection uses channels that are AirChannelsOperState enabled and AirChannelsAvail enabled. 
		 A change is effective after link re-synchronization. Valid values: disabled (0), enabled (1).
		 Rewriteable only in Point-To-Point products."
		::= { fibeAir4800OduAirChannelsEntry 3 }

	fibeAir4800OduAirChannelsAvail OBJECT-TYPE
		SYNTAX  INTEGER
		ACCESS  read-only
		STATUS  mandatory
		DESCRIPTION
		"Channel state. Product specific and cannot be changed by the user. 
		Automatic Channel Selection uses channels that are AirChannelsOperState enabled and AirChannelsAvail enabled. 
		Valid values: disabled (0), enabled (1)."
		::= { fibeAir4800OduAirChannelsEntry 4 }

	fibeAir4800OduAirChannelsDefaultFreq OBJECT-TYPE
		SYNTAX  INTEGER
		ACCESS  read-only
		STATUS  mandatory
		DESCRIPTION
		"Default channel's availability for all CBWs.
		The valid values are: forbidden (0), available (1)."
		::= { fibeAir4800OduAirChannelsEntry 5 }

	fibeAir4800OduAirDfsState OBJECT-TYPE
		SYNTAX  INTEGER
		ACCESS  read-only
		STATUS  mandatory
		DESCRIPTION
		"Radar detection state. Valid values: disabled (0), enabled (1)."
		::= { fibeAir4800OduAir 19 }

	fibeAir4800OduAirAutoChannelSelectionState OBJECT-TYPE
		SYNTAX  INTEGER
		ACCESS  read-only
		STATUS  deprecated
		DESCRIPTION
		"Deprecated parameter. Indicating Automatic Channel Selection availability at current channel bandwidth. 
		Valid values: disabled (0), enabled (1)."
		::= { fibeAir4800OduAir 20 }

	fibeAir4800OduAirEnableTxPower OBJECT-TYPE
		SYNTAX  INTEGER {
			enabled (1),
			disabled (2)
			}
		ACCESS  read-only
		STATUS  mandatory
		DESCRIPTION
		"Indicating Transmit power configuration enabled or disabled."
		::= { fibeAir4800OduAir 21 }

	fibeAir4800OduAirMinTxPower OBJECT-TYPE
		SYNTAX  INTEGER
		ACCESS  read-only
		STATUS  mandatory
		DESCRIPTION
		"Minimum Transmit power in dBm."
		::= { fibeAir4800OduAir 22 }

	-- ###########################################################
	--                      Max Tx Power Table
	-- ###########################################################

	fibeAir4800OduAirMaxTxPowerTable OBJECT-TYPE
		SYNTAX  SEQUENCE OF FibeAir4800OduAirMaxTxPowerEntry
		ACCESS  not-accessible
		STATUS  mandatory
		DESCRIPTION
		"Table of Maximum transmit power per air rate, in dBm."
		::= { fibeAir4800OduAir 23 }

	fibeAir4800OduAirMaxTxPowerEntry OBJECT-TYPE
		SYNTAX  FibeAir4800OduAirMaxTxPowerEntry
		ACCESS  not-accessible
		STATUS  mandatory
		DESCRIPTION
		"Maximum Transmit power table entry."
		INDEX { fibeAir4800OduAirMaxTxPowerIndex }
		::= { fibeAir4800OduAirMaxTxPowerTable 1 }

	FibeAir4800OduAirMaxTxPowerEntry ::= SEQUENCE {
		fibeAir4800OduAirMaxTxPowerIndex
			INTEGER,
		fibeAir4800OduAirMaxTxPower
			INTEGER
		}

	fibeAir4800OduAirMaxTxPowerIndex OBJECT-TYPE
		SYNTAX  INTEGER
		ACCESS  read-only
		STATUS  mandatory
		DESCRIPTION
		"Air interface rate index."
		::= { fibeAir4800OduAirMaxTxPowerEntry 1 }

	fibeAir4800OduAirMaxTxPower OBJECT-TYPE
		SYNTAX  INTEGER
		ACCESS  read-only
		STATUS  mandatory
		DESCRIPTION
		"Maximum Transmit power in dBm."
		::= { fibeAir4800OduAirMaxTxPowerEntry 2 }

	fibeAir4800OduAirChannelBandwidth OBJECT-TYPE
		SYNTAX  INTEGER
		ACCESS  read-write
		STATUS  mandatory
		DESCRIPTION
		"Channel bandwidth in KHz. A change is effective after reset."
		::= { fibeAir4800OduAir 24 }

	-- ###########################################################
	--                      Channel BW Table
	-- ###########################################################

	fibeAir4800OduAirChannelBWTable OBJECT-TYPE
		SYNTAX  SEQUENCE OF FibeAir4800OduAirChannelBWEntry
		ACCESS  not-accessible
		STATUS  mandatory
		DESCRIPTION
		"Channel Bandwidths table."
		::= { fibeAir4800OduAir 25 }

	fibeAir4800OduAirChannelBWEntry OBJECT-TYPE
		SYNTAX  FibeAir4800OduAirChannelBWEntry
		ACCESS  not-accessible
		STATUS  mandatory
		DESCRIPTION
		"Channel Bandwidth table entry."
		INDEX { fibeAir4800OduAirChannelBWIndex }
		::= { fibeAir4800OduAirChannelBWTable 1 }

	FibeAir4800OduAirChannelBWEntry ::= SEQUENCE {
		fibeAir4800OduAirChannelBWIndex
			INTEGER,
		fibeAir4800OduAirChannelBWAvail
			INTEGER,
		fibeAir4800OduAirChannelsAdminState
			DisplayString,
		fibeAir4800OduAirChannelBWHSSATDDConflictPerCBW
			INTEGER,
		fibeAir4800OduAirChannelBWMinRatioForSupporting
			INTEGER,
		fibeAir4800OduAirChannelBWMaxRatioForSupporting
			INTEGER	
		}

	fibeAir4800OduAirChannelBWIndex OBJECT-TYPE
		SYNTAX  INTEGER {
				channelBW5MHz(1),
				channelBW10MHz(2),
				channelBW20MHz(3),
				channelBW40MHz(4),
				channelBW80MHz(5)				
		}
		ACCESS  read-only
		STATUS  mandatory
		DESCRIPTION
		"Channel Bandwidth index."
		::= { fibeAir4800OduAirChannelBWEntry 1 }

	fibeAir4800OduAirChannelBWAvail OBJECT-TYPE
		SYNTAX  INTEGER {
			notSupported(1),
			supportedManual(2),
			supportedWithACS(3)
		}
		ACCESS  read-only
		STATUS  mandatory
		DESCRIPTION
		"Channel Bandwidth availability, product specific.
		Options are: Not supported, supported with manual channel selection, supported with Automatic Channel Selection."
		::= { fibeAir4800OduAirChannelBWEntry 2 }

	fibeAir4800OduAirChannelsAdminState OBJECT-TYPE
		SYNTAX  DisplayString
		ACCESS  read-only
		STATUS  mandatory
		DESCRIPTION
		"Channels' availability per CBW."
		::= { fibeAir4800OduAirChannelBWEntry 3 }

	fibeAir4800OduAirChannelBWHSSATDDConflictPerCBW OBJECT-TYPE
		SYNTAX  INTEGER {
			noConflict(1),
			conflictSingle(2),
			conflictDual(3)
		}
		ACCESS  read-only
		STATUS  mandatory
		DESCRIPTION
		"Indication for possible Link drop per CBW due to conflict between HSS and ATDD."
		::= { fibeAir4800OduAirChannelBWEntry 4 }

	fibeAir4800OduAirChannelBWMinRatioForSupporting OBJECT-TYPE
		SYNTAX  INTEGER
		ACCESS  read-only
		STATUS  mandatory
		DESCRIPTION
		"Minimal TX ratio that may be used by the HSM and still enable proper operation of the aforementioned CBW."
		::= { fibeAir4800OduAirChannelBWEntry 5 }

	fibeAir4800OduAirChannelBWMaxRatioForSupporting OBJECT-TYPE
		SYNTAX  INTEGER
		ACCESS  read-only
		STATUS  mandatory
		DESCRIPTION
		"Maximal TX ratio that may be used by the HSM and still enable proper operation of the aforementioned CBW."
		::= { fibeAir4800OduAirChannelBWEntry 6 }

	fibeAir4800OduAirRFD OBJECT-TYPE
		SYNTAX  INTEGER
		ACCESS  read-only
		STATUS  mandatory
		DESCRIPTION
		"Current radio frame duration in microseconds."
		::= { fibeAir4800OduAir 26 }

	-- ###########################################################
	--                      Available Rates Table
	-- ###########################################################

	fibeAir4800OduAirRatesTable OBJECT-TYPE
		SYNTAX  SEQUENCE OF FibeAir4800OduAirRatesEntry
		ACCESS  not-accessible
		STATUS  mandatory
		DESCRIPTION
		"Air Rate indexes table for current channel bandwidth."
		::= { fibeAir4800OduAir 27 }

	fibeAir4800OduAirRatesEntry OBJECT-TYPE
		SYNTAX  FibeAir4800OduAirRatesEntry
		ACCESS  not-accessible
		STATUS  mandatory
		DESCRIPTION
		"Air Rate indexes table entry."
		INDEX { fibeAir4800OduAirRatesIndex }
		::= { fibeAir4800OduAirRatesTable 1 }

	FibeAir4800OduAirRatesEntry ::= SEQUENCE {
		fibeAir4800OduAirRatesIndex
			INTEGER,
		fibeAir4800OduAirRatesAvail
			INTEGER
		}

	fibeAir4800OduAirRatesIndex OBJECT-TYPE
		SYNTAX  INTEGER 
		ACCESS  read-only
		STATUS  mandatory
		DESCRIPTION
		"Air Rate index."
		::= { fibeAir4800OduAirRatesEntry 1 }

	fibeAir4800OduAirRatesAvail OBJECT-TYPE
		SYNTAX  INTEGER {
			rateNotAvailable(1),
			rateAvailable(2)
		}
		ACCESS  read-only
		STATUS  mandatory
		DESCRIPTION
		"Air Rate availability, depending on air interface conditions."
		::= { fibeAir4800OduAirRatesEntry 2 }

	fibeAir4800OduAirDesiredRateIdx OBJECT-TYPE
		SYNTAX  INTEGER
		ACCESS  read-write
		STATUS  mandatory
		DESCRIPTION
		"Required Air Rate index. 0 reserved for Adaptive Rate.
		A change is effective immediately after Set operation to the master side
		while the link is up."
		::= { fibeAir4800OduAir 28 }

	fibeAir4800OduAirLinkDistance OBJECT-TYPE
		SYNTAX  INTEGER
		ACCESS  read-only
		STATUS  mandatory
		DESCRIPTION
		"Link distance in meters. 
		A value of -1 indicates an illegal value and is also used when a link is not established."
		::= { fibeAir4800OduAir 29 }

	fibeAir4800OduAirLinkWorkingMode OBJECT-TYPE
		SYNTAX  INTEGER {
			unknown(1),
			normal(2),
			fullCompatibilityRemoteUpgradeAvailable(3),
			fullCompatibilityLocalUpgradeAvailable(4),
			restrictedCompatibilityRemoteUpgradeRecomended(5),
			restrictedCompatibilityLocalUpgradeRecomended(6),
			softwareUpgradeRemoteUpgradeRequired(7),
			softwareUpgradeLocalUpgradeRequired(8),
			versionsIncompatibilityRemoteUpgradeRequired(9),
			versionsIncompatibilityLocalUpgradeRequired(10)
		}
		ACCESS  read-only
		STATUS  mandatory
		DESCRIPTION
		"Link working mode as a result of comparing versions of both sides of the link. 
		Possible modes are: Unknown - no link, Normal - versions on both sides are identical with full compatibility, 
		with restricted compatibility, or versions on both sides are different with software upgrade or versions incompatibility."
		::= { fibeAir4800OduAir 30 }

	fibeAir4800OduAirMajorLinkIfVersion OBJECT-TYPE
		SYNTAX  INTEGER
		ACCESS  read-only
		STATUS  mandatory
		DESCRIPTION
		"Major link interface version"
		::= { fibeAir4800OduAir 31 }

	fibeAir4800OduAirMinorLinkIfVersion OBJECT-TYPE
		SYNTAX  INTEGER
		ACCESS  read-only
		STATUS  mandatory
		DESCRIPTION
		"Minor link interface version"
		::= { fibeAir4800OduAir 32 }

	fibeAir4800OduAirHss OBJECT IDENTIFIER ::= { fibeAir4800OduAir 40 }

	fibeAir4800OduAirHssDesiredOpState OBJECT-TYPE
		SYNTAX  INTEGER {
			notSupported(1),
			independentUnit(2),
			hubSyncMaster(3),
			hubSyncClientContinueTx(4),
			hubSyncClientDisableTx(5),
			gpsSync(6),
			independentSyncUnit-ISU(7)
		}
		ACCESS  read-write
		STATUS  mandatory
		DESCRIPTION
		"Required Hub Site Synchronization operating state.
		For HssSyncUnits : 	For hssISU :[2,7] ,For hssGSU :[2,6]
		For HBS:			[2,3,4,5]"		
		::= { fibeAir4800OduAirHss 1 }

	fibeAir4800OduAirHssCurrentOpState OBJECT-TYPE
		SYNTAX  INTEGER {
			notSupported(1),
			independentUnit(2),
			hubSyncMaster(3),
			hubSyncClientContinueTx(4),
			hubSyncClientDisableTx(5),
			gpsSync(6),
			independentSyncUnit-ISU(7)
		}
		ACCESS  read-only
		STATUS  mandatory
		DESCRIPTION
		"Current Hub Site Synchronization operating state."		
		::= { fibeAir4800OduAirHss 2 }

	fibeAir4800OduAirHssSyncStatus OBJECT-TYPE
		SYNTAX  INTEGER {
			notApplicable(1),
			notSynchronized(2),
			synchronized(3)
		}
		ACCESS  read-only
		STATUS  mandatory
		DESCRIPTION
		"Hub Site Synchronization sync status."		
		::= { fibeAir4800OduAirHss 3 }

	fibeAir4800OduAirHssExtPulseStatus OBJECT-TYPE
		SYNTAX  INTEGER {
			notDetected(1),
			generating(2),
			generatingAndDetected(3),
			generatingAndImproperDetected(4),
			detected(5),
			improperDetected(6),
			multipleSourcesDetected(7)
		}
		ACCESS  read-only
		STATUS  mandatory
		DESCRIPTION
		"Hub Site Synchronization external pulse detection status.
		In GSS mode: 
		if generating then 1PSP is auto generated by the GSS Unit.
		if generatingAndDetecting then 1PSP is generated by GPS satellites signal."		
		::= { fibeAir4800OduAirHss 4 }

	fibeAir4800OduAirHssExtPulseType OBJECT-TYPE
		SYNTAX  INTEGER {
			notApplicable(1),
			typeA(2),
			typeB(3),
			typeC(4),
			typeD(5),
			typeE(6),
			typeF(7)
		}
		ACCESS  read-only
		STATUS  mandatory
		DESCRIPTION
		"Hub Site Synchronization external pulse type."		
		::= { fibeAir4800OduAirHss 5 }
		
	fibeAir4800OduAirHssDesiredExtPulseType OBJECT-TYPE
		SYNTAX  INTEGER {
			notApplicable(1),
			typeA(2),
			typeB(3),
			typeC(4),
			typeD(5),
			typeE(6),
			typeF(7)
		}
		ACCESS  read-write
		STATUS  mandatory
		DESCRIPTION
		"Hub Site Synchronization required external pulse type. Valid values for read write:
		 {typeA(2),typeB(3),typeC(4),typeD(5),typeE(6),typeF(7)}. Valid value for read only:
		 {notApplicable(1)}."		
		::= { fibeAir4800OduAirHss 6 }
		
	-- ###########################################################
	--                      HSS Radio Frame Pattern Table
	-- ###########################################################
	fibeAir4800OduAirHssRfpTable OBJECT-TYPE
		SYNTAX  SEQUENCE OF FibeAir4800OduAirHssRfpEntry
		ACCESS  not-accessible
		STATUS  mandatory
		DESCRIPTION
		"ODU Radio Frame Patterns (RFP) Table."
		::= { fibeAir4800OduAirHss 7 }

	fibeAir4800OduAirHssRfpEntry OBJECT-TYPE
		SYNTAX  FibeAir4800OduAirHssRfpEntry
		ACCESS  not-accessible
		STATUS  mandatory
		DESCRIPTION
		"ODU RFP Table entry."
		INDEX { fibeAir4800OduAirHssRfpIndex }
		::= { fibeAir4800OduAirHssRfpTable 1 }

	FibeAir4800OduAirHssRfpEntry ::= SEQUENCE {
		fibeAir4800OduAirHssRfpIndex
			INTEGER,
		fibeAir4800OduAirHssRfpEthChannelBW5MHz
			INTEGER,
		fibeAir4800OduAirHssRfpTdmChannelBW5MHz
			INTEGER,
		fibeAir4800OduAirHssRfpEthChannelBW10MHz
			INTEGER,
		fibeAir4800OduAirHssRfpTdmChannelBW10MHz
			INTEGER,
		fibeAir4800OduAirHssRfpEthChannelBW20MHz
			INTEGER,
		fibeAir4800OduAirHssRfpTdmChannelBW20MHz
			INTEGER,
		fibeAir4800OduAirHssRfpEthChannelBW40MHz
			INTEGER,
		fibeAir4800OduAirHssRfpTdmChannelBW40MHz
			INTEGER
		}
		
	fibeAir4800OduAirHssRfpIndex OBJECT-TYPE
		SYNTAX  INTEGER (2..5)
		ACCESS  read-only
		STATUS  mandatory
		DESCRIPTION
		"ODU RFP Table index. The index represent the Radio Frame Pattern:
		 typeA(2), typeB(3), typeC(4), typeD(5),typeE(6)."
		::= { fibeAir4800OduAirHssRfpEntry 1 }
		
	fibeAir4800OduAirHssRfpEthChannelBW5MHz OBJECT-TYPE
		SYNTAX  INTEGER {
			bestFit(1),
			nonOptimal(2),
			notAvailable(3)
		}
		ACCESS  read-only
		STATUS  mandatory
		DESCRIPTION
		"Represents the compatibility of Ethernet service under Channel BW of 5MHz 
		 in the specific Radio Frame Pattern."
		::= { fibeAir4800OduAirHssRfpEntry 2 }
		
	fibeAir4800OduAirHssRfpTdmChannelBW5MHz OBJECT-TYPE
		SYNTAX  INTEGER {
			bestFit(1),
			nonOptimal(2),
			notAvailable(3)
		}
		ACCESS  read-only
		STATUS  mandatory
		DESCRIPTION
		"Represents the compatibility of TDM service under Channel BW of 5MHz 
		 in the specific Radio Frame Pattern."
		::= { fibeAir4800OduAirHssRfpEntry 3 }
		
		fibeAir4800OduAirHssRfpEthChannelBW10MHz OBJECT-TYPE
		SYNTAX  INTEGER {
			bestFit(1),
			nonOptimal(2),
			notAvailable(3)
		}
		ACCESS  read-only
		STATUS  mandatory
		DESCRIPTION
		"Represents the compatibility of Ethernet service under Channel BW of 10MHz 
		 in the specific Radio Frame Pattern."
		::= { fibeAir4800OduAirHssRfpEntry 4 }
		
	fibeAir4800OduAirHssRfpTdmChannelBW10MHz OBJECT-TYPE
		SYNTAX  INTEGER {
			bestFit(1),
			nonOptimal(2),
			notAvailable(3)
		}
		ACCESS  read-only
		STATUS  mandatory
		DESCRIPTION
		"Represents the compatibility of TDM service under Channel BW of 10MHz 
		 in the specific Radio Frame Pattern."
		::= { fibeAir4800OduAirHssRfpEntry 5 }
		
	fibeAir4800OduAirHssRfpEthChannelBW20MHz OBJECT-TYPE
		SYNTAX  INTEGER {
			bestFit(1),
			nonOptimal(2),
			notAvailable(3)
		}
		ACCESS  read-only
		STATUS  mandatory
		DESCRIPTION
		"Represents the compatibility of Ethernet service under Channel BW of 20MHz 
		 in the specific Radio Frame Pattern."
		::= { fibeAir4800OduAirHssRfpEntry 6 }
		
	fibeAir4800OduAirHssRfpTdmChannelBW20MHz OBJECT-TYPE
		SYNTAX  INTEGER {
			bestFit(1),
			nonOptimal(2),
			notAvailable(3)
		}
		ACCESS  read-only
		STATUS  mandatory
		DESCRIPTION
		"Represents the compatibility of TDM service under Channel BW of 20MHz 
		 in the specific Radio Frame Pattern."
		::= { fibeAir4800OduAirHssRfpEntry 7 }
		
	fibeAir4800OduAirHssRfpEthChannelBW40MHz OBJECT-TYPE
		SYNTAX  INTEGER {
			bestFit(1),
			nonOptimal(2),
			notAvailable(3)
		}
		ACCESS  read-only
		STATUS  mandatory
		DESCRIPTION
		"Represents the compatibility of Ethernet service under Channel BW of 40MHz 
		 in the specific Radio Frame Pattern."
		::= { fibeAir4800OduAirHssRfpEntry 8 }
		
	fibeAir4800OduAirHssRfpTdmChannelBW40MHz OBJECT-TYPE
		SYNTAX  INTEGER {
			bestFit(1),
			nonOptimal(2),
			notAvailable(3)
		}
		ACCESS  read-only
		STATUS  mandatory
		DESCRIPTION
		"Represents the compatibility of TDM service under Channel BW of 40MHz 
		 in the specific Radio Frame Pattern."
		::= { fibeAir4800OduAirHssRfpEntry 9 }
		
	fibeAir4800OduAirHssRfpStr OBJECT-TYPE
		SYNTAX  DisplayString
		ACCESS  read-only
		STATUS  mandatory
		DESCRIPTION
		"Hub Site Synchronization supported patterns"
		::= { fibeAir4800OduAirHss 8 }
		
	fibeAir4800OduAirHssHsmID OBJECT-TYPE
		SYNTAX  INTEGER
		ACCESS  read-only
		STATUS  mandatory
		DESCRIPTION
		"A  unique ID which is common to the HSM and all its collocated ODUs"
		::= { fibeAir4800OduAirHss 9 }
		
	fibeAir4800OduAirHssTime OBJECT-TYPE
		SYNTAX  DisplayString
		ACCESS  read-only
		STATUS  mandatory
		DESCRIPTION
		"Hub Site Synchronization GPS time"
		::= { fibeAir4800OduAirHss 10 }
		
	fibeAir4800OduAirHssLatitude OBJECT-TYPE
		SYNTAX  DisplayString
		ACCESS  read-only
		STATUS  mandatory
		DESCRIPTION
		"Hub Site Synchronization GPS Latitude"
		::= { fibeAir4800OduAirHss 11 }
		
	fibeAir4800OduAirHssNSIndicator OBJECT-TYPE
		SYNTAX  DisplayString
		ACCESS  read-only
		STATUS  mandatory
		DESCRIPTION
		"Hub Site Synchronization GPS N/S Indicator"
		::= { fibeAir4800OduAirHss 12 }
		
	fibeAir4800OduAirHssLongitude OBJECT-TYPE
		SYNTAX  DisplayString
		ACCESS  read-only
		STATUS  mandatory
		DESCRIPTION
		"Hub Site Synchronization GPS Longitude"
		::= { fibeAir4800OduAirHss 13 }
		
	fibeAir4800OduAirHssEWIndicator OBJECT-TYPE
		SYNTAX  DisplayString
		ACCESS  read-only
		STATUS  mandatory
		DESCRIPTION
		"Hub Site Synchronization GPS E/W Indicator"
		::= { fibeAir4800OduAirHss 14 }
		
	fibeAir4800OduAirHssNumSatellites OBJECT-TYPE
		SYNTAX  DisplayString
		ACCESS  read-only
		STATUS  mandatory
		DESCRIPTION
		"Hub Site Synchronization GPS Number of satellites"
		::= { fibeAir4800OduAirHss 15 }
		
	fibeAir4800OduAirHssAltitude OBJECT-TYPE
		SYNTAX  DisplayString
		ACCESS  read-only
		STATUS  mandatory
		DESCRIPTION
		"Hub Site Synchronization GPS Altitude"
		::= { fibeAir4800OduAirHss 16 }
		
	fibeAir4800OduAirHssRfpPhase OBJECT-TYPE
		SYNTAX  INTEGER {
			rfpNormalPhase(1),
			rfpShiftedPhase(2)
		}
		ACCESS  read-write
		STATUS  mandatory
		DESCRIPTION
		"Hub Site Synchronization GPS RFP phase"
		::= { fibeAir4800OduAirHss 17 }
		
	fibeAir4800OduAirHssInterSiteSynchronizationMode OBJECT-TYPE
		SYNTAX  INTEGER {
			independent(1),
			synchronized(2)
		}
		ACCESS  read-write
		STATUS  mandatory
		DESCRIPTION
		"Inter-Site Synchronization Mode - independent / synchronized"
		::= { fibeAir4800OduAirHss 18 }
		
	fibeAir4800OduAirHssInterSiteSynchronizationAvailability OBJECT-TYPE
		SYNTAX  INTEGER {
			notAvailable(1),
			available(2)
		}
		ACCESS  read-only
		STATUS  mandatory
		DESCRIPTION
		"Inter-Site Synchronization Availability"
		::= { fibeAir4800OduAirHss 19 }
		
	fibeAir4800OduAirHssSatellitesSatSyncRequired OBJECT-TYPE
		SYNTAX  INTEGER {
			notRequired(1),
			required(2)
		}
		ACCESS  read-write
		STATUS  mandatory
		DESCRIPTION
		"Satellites Synchronization Is Required"
		::= { fibeAir4800OduAirHss 20 }
		
	fibeAir4800OduAirHssDomainID OBJECT-TYPE
		SYNTAX  DisplayString
		ACCESS  read-write
		STATUS  mandatory
		DESCRIPTION
		"EHSS domain. Indentify set of CUs with same HSS synchronization"
		::= { fibeAir4800OduAirHss 21 }
		
	fibeAir4800OduAirHssSupportedSynchronizationProtocol OBJECT-TYPE
		SYNTAX  INTEGER {
			serialOnly(1),
			ethOnly(2),
			both(3)
		}
		ACCESS  read-only
		STATUS  mandatory
		DESCRIPTION
		"Supported Synchronization Protocols"
		::= { fibeAir4800OduAirHss 22 }
		
	fibeAir4800OduAirHssDesiredSynchronizationProtocol OBJECT-TYPE
		SYNTAX  INTEGER {
			serialOnly(1),
			ethOnly(2),
			both(3)
		}
		ACCESS  read-write
		STATUS  mandatory
		DESCRIPTION
		"Desired Synchronization Protocols"
		::= { fibeAir4800OduAirHss 23 }
		
	fibeAir4800OduAirHssDiscover OBJECT-TYPE
		SYNTAX  INTEGER {
			startAll(1),
			startAllMstr(2),
			startMyDmn(3),
			startMyMstr(4)
		}
		ACCESS  read-write
		STATUS  mandatory
		DESCRIPTION
		"Initiate Discovery process of ODUs on the network."
		::= { fibeAir4800OduAirHss 24 }
		
	fibeAir4800OduAirHssNumberOfDiscoveredODUs OBJECT-TYPE
		SYNTAX  INTEGER (0..1000)
		ACCESS  read-only
		STATUS  mandatory
		DESCRIPTION
		"Number OF Discovered ODUs in network."
		::= { fibeAir4800OduAirHss 25 }
		
	-- ###########################################################
	--                      HSS Discover Table
	-- ###########################################################
	
	fibeAir4800OduAirHssDiscoverTable OBJECT-TYPE
		SYNTAX  SEQUENCE OF FibeAir4800OduAirHssDiscoverEntry
		ACCESS  not-accessible
		STATUS  mandatory
		DESCRIPTION
		"HSS Discover Table."
		::= { fibeAir4800OduAirHss 26 }

	fibeAir4800OduAirHssDiscoverEntry OBJECT-TYPE
		SYNTAX  FibeAir4800OduAirHssDiscoverEntry
		ACCESS  not-accessible
		STATUS  mandatory
		DESCRIPTION
		"ODU Discover Table entry."
		INDEX { fibeAir4800OduAirHssDiscoverIndex }
		::= { fibeAir4800OduAirHssDiscoverTable 1 }

	FibeAir4800OduAirHssDiscoverEntry ::= SEQUENCE {
		fibeAir4800OduAirHssDiscoverIndex
			INTEGER,
		fibeAir4800OduAirHssDiscoverODUDescription
			DisplayString
		}
		
	fibeAir4800OduAirHssDiscoverIndex OBJECT-TYPE
		SYNTAX  INTEGER (1..256)
		ACCESS  read-only
		STATUS  mandatory
		DESCRIPTION
		"HSS Discover Table Index."
		::= { fibeAir4800OduAirHssDiscoverEntry 1 }
		
	fibeAir4800OduAirHssDiscoverODUDescription OBJECT-TYPE
		SYNTAX  DisplayString
		ACCESS  read-only
		STATUS  mandatory
		DESCRIPTION
		"Hold ODU HSS status in compress format:
		Domain,IP,HSS Role,Hss support,
		Enabled HSS protocol,Sync Status,
		Location, IPv6."
		::= { fibeAir4800OduAirHssDiscoverEntry 2 }
		
	-- ###################### End of Discover Table ###################
	
	fibeAir4800OduAirHssMasterSlaveCompatibility OBJECT-TYPE
		SYNTAX  INTEGER {
			compatible(1),
			notCompatible(2)
		}
		ACCESS  read-only
		STATUS  mandatory
		DESCRIPTION
		"EHSM version compatibility. Relevant to Ethernet HSS Clients only."
		::= { fibeAir4800OduAirHss 27 }
		
	fibeAir4800OduAirHssNumberOfAssociatedCU OBJECT-TYPE
		SYNTAX  INTEGER (0..256)
		ACCESS  read-only
		STATUS  mandatory
		DESCRIPTION
		"Number of associated Ethernet HSS Clients. Relevant to Ethernet HSS Masters only"
		::= { fibeAir4800OduAirHss 28 }
		
	-- ###########################################################
	--                      HSS Associated CU Table
	-- ###########################################################
		
	fibeAir4800OduAirHssAssociatedCUTable OBJECT-TYPE
		SYNTAX  SEQUENCE OF FibeAir4800OduAirHssAssociatedCUTableEntry
		ACCESS  not-accessible
		STATUS  mandatory
		DESCRIPTION
		"Associated Ethernet HSS Clients Table. Releant for Ethernet HSS Masters only."
		::= { fibeAir4800OduAirHss 29 }

	fibeAir4800OduAirHssAssociatedCUTableEntry OBJECT-TYPE
		SYNTAX  FibeAir4800OduAirHssAssociatedCUTableEntry
		ACCESS  not-accessible
		STATUS  mandatory
		DESCRIPTION
		"Associated Ethernet HSS Clients Table Entry. Releant for Ethernet HSS Masters only."
		INDEX { fibeAir4800OduAirHssAssociatedCUIndex }
		::= { fibeAir4800OduAirHssAssociatedCUTable 1 }

	FibeAir4800OduAirHssAssociatedCUTableEntry ::= SEQUENCE {
		fibeAir4800OduAirHssAssociatedCUIndex
			INTEGER,
		fibeAir4800OduAirHssAssociatedCUDescription
			DisplayString
		}
		
	fibeAir4800OduAirHssAssociatedCUIndex OBJECT-TYPE
		SYNTAX  INTEGER (1..256)
		ACCESS  read-only
		STATUS  mandatory
		DESCRIPTION
		"Associated Ethernet HSS Clients Table Index. Releant for Ethernet HSS Masters only."
		::= { fibeAir4800OduAirHssAssociatedCUTableEntry 1 }
		
	fibeAir4800OduAirHssAssociatedCUDescription OBJECT-TYPE
		SYNTAX  DisplayString
		ACCESS  read-only
		STATUS  mandatory
		DESCRIPTION
		"Holds Associated Ethernet HSS Clients Description in compress format:
		IP,Delay,Compatibility,Ethernet Speed, Ethernet Rx rate, IPv6"
		::= { fibeAir4800OduAirHssAssociatedCUTableEntry 2 }
		
	-- ###################### End of Associated CU Table ###################
		
	fibeAir4800OduAirHssSyncStatusEth OBJECT-TYPE
		SYNTAX  INTEGER {
			notApplicable(1),
			notSynchronized(2),
			goodSynchronizationLevel(3),
			mediumSynchronizationLevel(4),
			badSynchronizationLevel(5),
			startSynchronization(6)
		}
		ACCESS  read-only
		STATUS  mandatory
		DESCRIPTION
		"Ethernet HSS Client Synchronization Level"
		::= { fibeAir4800OduAirHss 30 }
		
	fibeAir4800OduAirHssEthVLANTag OBJECT-TYPE
		SYNTAX  INTEGER (1..40947)
		ACCESS  read-write
		STATUS  mandatory
		DESCRIPTION
		"Ethernet HSS VLan Tag: 
		The least significate decimal digit is the VLan Priority(0-6) 
		and the rest of the digits represents VLan ID (2-4094)"
		::= { fibeAir4800OduAirHss 31 }
	
	fibeAir4800OduAirHssHSMIPAddress OBJECT-TYPE
		SYNTAX  IpAddress
		ACCESS  read-only
		STATUS  mandatory
		DESCRIPTION
		"HSMs IP address. Relevant for HSC synchronized over Ethernet."
		::= { fibeAir4800OduAirHss 32 }

	fibeAir4800OduAirHssDelayToHSM OBJECT-TYPE
		SYNTAX  INTEGER (0..1000000)
		ACCESS  read-only
		STATUS  mandatory
		DESCRIPTION
		"Delay in microseconds to HSM. Relevant for HSC synchronized over Ethernet."
		::= { fibeAir4800OduAirHss 33 }

	fibeAir4800OduAirHssSyncAcquisitionSeconds OBJECT-TYPE
		SYNTAX  INTEGER
		ACCESS  read-write
		STATUS  mandatory
		DESCRIPTION
		"Accumulated quantity of seconds in clock acquisition while connected to current HSM"
		::= { fibeAir4800OduAirHss 34 }
		
	fibeAir4800OduAirHssHSMIPv6Address OBJECT-TYPE
		SYNTAX  DisplayString
		ACCESS  read-only
		STATUS  mandatory
		DESCRIPTION
		"HSMs IPv6 address. Relevant for HSC synchronized over Ethernet."
		::= { fibeAir4800OduAirHss 35 }
		
	-- ###################### End of HSS Section ###################
	
	fibeAir4800OduAirLockRemote OBJECT-TYPE
		SYNTAX  INTEGER {
			unlock(1),
			lock(2)
			}
		ACCESS  read-write
		STATUS  mandatory
		DESCRIPTION
		"This parameter enables locking the link with a specific ODU.
		 The following values can be set:
		 Unlock (default) - The ODU is not locked on a specific remote ODU. Unlock can only be performed when the link is not connected.
		 Lock - The ODU is locked on a specific remote ODU. Lock can only be performed when the link is active."
		::= { fibeAir4800OduAir 41 }

	fibeAir4800OduAirAntennaGain OBJECT-TYPE
		SYNTAX  INTEGER
		ACCESS  read-write
		STATUS  mandatory
		DESCRIPTION
		"Current Antenna Gain in 0.1 dBi resolution. User defined value for 
		external antenna.
		Legal range: MinAntennaGain<AntennaGain<MaxAntennaGain."
		::= { fibeAir4800OduAir 42 }

	fibeAir4800OduAirFeederLoss OBJECT-TYPE
		SYNTAX  INTEGER
		ACCESS  read-write
		STATUS  mandatory
		DESCRIPTION
		"Current Feeder Loss in 0.1 dBm resolution. User defined value for 
		external antenna."
		::= { fibeAir4800OduAir 43 }

	fibeAir4800OduAirMaxAntennaGain OBJECT-TYPE
		SYNTAX  INTEGER
		ACCESS  read-only
		STATUS  mandatory
		DESCRIPTION
		"Maximum allowed Antenna Gain in 0.1 dBi resolution."
		::= { fibeAir4800OduAir 44 }

	fibeAir4800OduAirMinAntennaGain OBJECT-TYPE
		SYNTAX  INTEGER
		ACCESS  read-only
		STATUS  mandatory
		DESCRIPTION
		"Minimum allowed Antenna Gain in 0.1 dBi resolution."
		::= { fibeAir4800OduAir 45 }

	fibeAir4800OduAirMaxEIRP OBJECT-TYPE
		SYNTAX  INTEGER
		ACCESS  read-only
		STATUS  mandatory
		DESCRIPTION
		"Maximum EIRP value as defined by regulation in 0.1 dBm resolution."
		::= { fibeAir4800OduAir 46 }

	fibeAir4800OduAirAntennaGainConfigSupport OBJECT-TYPE
		SYNTAX  INTEGER {
			supported(1),
			notSupported(2)
			}
		ACCESS  read-only
		STATUS  mandatory
		DESCRIPTION
		"Antenna Gain Configurability, options are product specific: supported, not supported."
		::= { fibeAir4800OduAir 47 }

	fibeAir4800OduAirAntennaType OBJECT-TYPE
		SYNTAX  INTEGER {
			single(1),
			dual(2),
			unDefined(3),
			triple(4)
			}
		ACCESS  read-write
		STATUS  mandatory
		DESCRIPTION
		"External Antenna Type: Monopolar or Bipolar."
		::= { fibeAir4800OduAir 48 }

	fibeAir4800OduAirRssBalance OBJECT-TYPE
		SYNTAX  INTEGER (-2..2)
		ACCESS  read-only
		STATUS  mandatory
		DESCRIPTION
		"RSS balance. Relation between RSS in radio 1 and RSS in radio 2.
		-2 : Radio 2 RSS is much stronger than Radio 1 RSS.
		-1 : Radio 2 RSS is stronger than Radio 1 RSS.
		-0 : Radio 2 RSS is equal to Radio 1 RSS.
		1  : Radio 1 RSS is stronger than Radio 2 RSS.
		2  : Radio 1 RSS is much stronger than Radio 2 RSS."
		::= { fibeAir4800OduAir 49 }

	fibeAir4800OduAirTotalTxPower OBJECT-TYPE
		SYNTAX  INTEGER
		ACCESS  read-only
		STATUS  mandatory
		DESCRIPTION
		"Total Transmit Power in dBm. This is a nominal value While the actual transmit power includes additional attenuation."
		::= { fibeAir4800OduAir 50 }

	fibeAir4800OduAirInstallFreqAndCBW OBJECT-TYPE
		SYNTAX  DisplayString 
		ACCESS  read-write
		STATUS  mandatory
		DESCRIPTION
		"Installation frequency , Channel BW. Relevant in point to point systems."
		::= { fibeAir4800OduAir 51 }

	fibeAir4800OduAirDFStype OBJECT-TYPE
		SYNTAX  INTEGER {
			dfs01(1),
			dfs02(2),
			dfs04(4),
			dfs40(40),
			dfs50(50),
			dfs51(51)
			}
		ACCESS  read-only
		STATUS  mandatory
		DESCRIPTION
		"DFS regulation type."
		::= { fibeAir4800OduAir 52 }

	fibeAir4800OduAirCombo OBJECT IDENTIFIER ::= { fibeAir4800OduAir 53 }

	-- ###########################################################
	--                      Multi-band Sub Bands Table
	-- ###########################################################
	fibeAir4800OduAirComboSubBandTable OBJECT-TYPE
		SYNTAX  SEQUENCE OF FibeAir4800OduAirComboSubBandEntry
		ACCESS  not-accessible
		STATUS  mandatory
		DESCRIPTION
		"ODU Multi-band Sub Bands Table."
		::= { fibeAir4800OduAirCombo 1 }

	fibeAir4800OduAirComboSubBandEntry OBJECT-TYPE
		SYNTAX  FibeAir4800OduAirComboSubBandEntry
		ACCESS  not-accessible
		STATUS  mandatory
		DESCRIPTION
		"ODU Multi-band Sub Bands Table entry."
		INDEX { fibeAir4800OduAirComboSubBandIndex }
		::= { fibeAir4800OduAirComboSubBandTable 1 }

	FibeAir4800OduAirComboSubBandEntry ::= SEQUENCE {
		fibeAir4800OduAirComboSubBandIndex
			INTEGER,
		fibeAir4800OduAirComboSubBandId
			DisplayString,
		fibeAir4800OduAirComboSubBandDescription
			DisplayString,
		fibeAir4800OduAirComboSubBandInstallFreq
			INTEGER,
		fibeAir4800OduAirComboSubBandAdminState
			INTEGER,
		fibeAir4800OduAirComboSubBandInstallationAllowed
			INTEGER,
		fibeAir4800OduAirComboFrequencyBandId
			INTEGER,
		fibeAir4800OduAirComboSubBandChannelBW5AdminState
			DisplayString,
		fibeAir4800OduAirComboSubBandChannelBW10AdminState
			DisplayString,
		fibeAir4800OduAirComboSubBandChannelBW20AdminState
			DisplayString,
		fibeAir4800OduAirComboSubBandChannelBW40AdminState
			DisplayString,			
		fibeAir4800OduAirComboSubBandAllowableChannels
			DisplayString,	
		fibeAir4800OduAirComboSubBandChannelBWAvail
			DisplayString,
		fibeAir4800OduAirComboSubBandChannelBandwidth
			INTEGER,
		fibeAir4800OduAirComboSubBandMinFreq
			INTEGER,
		fibeAir4800OduAirComboSubBandMaxFreq
			INTEGER,
		fibeAir4800OduAirComboSubBandFrequencyResolution
			INTEGER,
		fibeAir4800OduAirComboSubBandDefaultChannelList
			DisplayString,
		fibeAir4800OduAirComboSubBandDfsState
			INTEGER,
		fibeAir4800OduAirComboSubBandChannelBW80AdminState
			DisplayString
		}
		
	fibeAir4800OduAirComboSubBandIndex OBJECT-TYPE
		SYNTAX  INTEGER
		ACCESS  read-only
		STATUS  mandatory
		DESCRIPTION
		"ODU Multi-band sub bands table index."
		::= { fibeAir4800OduAirComboSubBandEntry 1 }
		
	fibeAir4800OduAirComboSubBandId OBJECT-TYPE
		SYNTAX  DisplayString
		ACCESS  read-only
		STATUS  mandatory
		DESCRIPTION
		"Represents the Multi-band sub band ID."
		::= { fibeAir4800OduAirComboSubBandEntry 2 }

	fibeAir4800OduAirComboSubBandDescription OBJECT-TYPE
		SYNTAX  DisplayString
		ACCESS  read-only
		STATUS  mandatory
		DESCRIPTION
		"Multi-band sub band description."
		::= { fibeAir4800OduAirComboSubBandEntry 3 }

	fibeAir4800OduAirComboSubBandInstallFreq OBJECT-TYPE
		SYNTAX  INTEGER
		ACCESS  read-only
		STATUS  mandatory
		DESCRIPTION
		"Represents the Multi-band sub band installation frequency in KHz."
		::= { fibeAir4800OduAirComboSubBandEntry 4 }

	fibeAir4800OduAirComboSubBandAdminState OBJECT-TYPE
		SYNTAX  INTEGER {
			enabled (1),
			disabled (2)
		}
		ACCESS  read-only
		STATUS  mandatory
		DESCRIPTION
		"Represents the Multi-band sub band administrative state."
		::= { fibeAir4800OduAirComboSubBandEntry 5 }

	fibeAir4800OduAirComboSubBandInstallationAllowed OBJECT-TYPE
		SYNTAX  INTEGER {
			yes (1),
			no (2),
			inactive(3)
		}
		ACCESS  read-only
		STATUS  mandatory
		DESCRIPTION
		"Reflects if the Multi-band sub band allowes installtion."
		::= { fibeAir4800OduAirComboSubBandEntry 6 }

	fibeAir4800OduAirComboFrequencyBandId OBJECT-TYPE
		SYNTAX  INTEGER
		ACCESS  read-only
		STATUS  mandatory
		DESCRIPTION
		"Reflects the frequency band Id."
		::= { fibeAir4800OduAirComboSubBandEntry 7 }
	
	fibeAir4800OduAirComboSubBandChannelBW5AdminState OBJECT-TYPE
		SYNTAX	DisplayString
		ACCESS  read-only
		STATUS  mandatory
		DESCRIPTION
		"Reflects the CBW 5MHz admin state vector."
		::= { fibeAir4800OduAirComboSubBandEntry 8 }
		
	fibeAir4800OduAirComboSubBandChannelBW10AdminState OBJECT-TYPE
		SYNTAX	DisplayString
		ACCESS  read-only
		STATUS  mandatory
		DESCRIPTION
		"Reflects the CBW 10MHz admin state vector."
		::= { fibeAir4800OduAirComboSubBandEntry 9 }
		
	fibeAir4800OduAirComboSubBandChannelBW20AdminState OBJECT-TYPE
		SYNTAX	DisplayString
		ACCESS  read-only
		STATUS  mandatory
		DESCRIPTION
		"Reflects the CBW 20MHz admin state vector."
		::= { fibeAir4800OduAirComboSubBandEntry 10 }
		
	fibeAir4800OduAirComboSubBandChannelBW40AdminState OBJECT-TYPE
		SYNTAX	DisplayString
		ACCESS  read-only
		STATUS  mandatory
		DESCRIPTION
		"Reflects the CBW 40MHz admin state vector."
		::= { fibeAir4800OduAirComboSubBandEntry 11 }
		
	fibeAir4800OduAirComboSubBandAllowableChannels OBJECT-TYPE
		SYNTAX	DisplayString
		ACCESS  read-only
		STATUS  mandatory
		DESCRIPTION
		"Reflects the allowable channels vector."
		::= { fibeAir4800OduAirComboSubBandEntry 12 }
		
	fibeAir4800OduAirComboSubBandChannelBWAvail OBJECT-TYPE
		SYNTAX	DisplayString
		ACCESS  read-only
		STATUS  mandatory
		DESCRIPTION
		"Reflects the available CBWs vector."
		::= { fibeAir4800OduAirComboSubBandEntry 13 }
		
	fibeAir4800OduAirComboSubBandChannelBandwidth OBJECT-TYPE
		SYNTAX  INTEGER
		ACCESS  read-only
		STATUS  mandatory
		DESCRIPTION
		"Reflects the sub-band default channel bandwidth."
		::= { fibeAir4800OduAirComboSubBandEntry 14 }
		
	fibeAir4800OduAirComboSubBandMinFreq OBJECT-TYPE
		SYNTAX  INTEGER
		ACCESS  read-only
		STATUS  mandatory
		DESCRIPTION
		"Reflects the sub-band default minimal frequency."
		::= { fibeAir4800OduAirComboSubBandEntry 15 }
		
	fibeAir4800OduAirComboSubBandMaxFreq OBJECT-TYPE
		SYNTAX  INTEGER
		ACCESS  read-only
		STATUS  mandatory
		DESCRIPTION
		"Reflects the sub-band default maximal frequency."
		::= { fibeAir4800OduAirComboSubBandEntry 16 }
		
	fibeAir4800OduAirComboSubBandFrequencyResolution OBJECT-TYPE
		SYNTAX  INTEGER
		ACCESS  read-only
		STATUS  mandatory
		DESCRIPTION
		"Reflects the sub-band frequency resolution."
		::= { fibeAir4800OduAirComboSubBandEntry 17 }
			
	fibeAir4800OduAirComboSubBandDefaultChannelList OBJECT-TYPE
		SYNTAX	DisplayString
		ACCESS  read-only
		STATUS  mandatory
		DESCRIPTION
		"Reflects the default channel list vector."
		::= { fibeAir4800OduAirComboSubBandEntry 18 }
		
	fibeAir4800OduAirComboSubBandDfsState OBJECT-TYPE
		SYNTAX  INTEGER
		ACCESS  read-only
		STATUS  mandatory
		DESCRIPTION
		"Reflects the sub-band DFS state."
		::= { fibeAir4800OduAirComboSubBandEntry 19 }

	fibeAir4800OduAirComboSubBandChannelBW80AdminState OBJECT-TYPE
		SYNTAX	DisplayString
		ACCESS  read-only
		STATUS  mandatory
		DESCRIPTION
		"Reflects the CBW 80MHz admin state vector."
		::= { fibeAir4800OduAirComboSubBandEntry 20 }
		
	fibeAir4800OduAirComboNumberOfSubBands OBJECT-TYPE
		SYNTAX  INTEGER
		ACCESS  read-only
		STATUS  mandatory
		DESCRIPTION
		"Represents the number of Multi-band sub bands."
		::= { fibeAir4800OduAirCombo 2 }

	fibeAir4800OduAirComboSwitchSubBand OBJECT-TYPE
		SYNTAX  DisplayString
		ACCESS  read-write
		STATUS  mandatory
		DESCRIPTION
		"Switch sub band operation with a given sub band ID. 
		The get operation retrieves the current sub band ID."
		::= { fibeAir4800OduAirCombo 3 }
		
	fibeAir4800OduAirComboCurrentSubBandDesc OBJECT-TYPE
		SYNTAX  DisplayString
		ACCESS  read-only
		STATUS  mandatory
		DESCRIPTION
		"Current Sub Band description."
		::= { fibeAir4800OduAirCombo 4 }		

	-- ###########################################################
	--                      Video Surveillance
	-- ###########################################################
			
	fibeAir4800OduAirInternalMaxRate OBJECT-TYPE
		SYNTAX  INTEGER
		ACCESS  read-only
		STATUS  mandatory
		DESCRIPTION
		"Max Ethernet throughput of the site (in Kpbs)."
		::= { fibeAir4800OduAir 54 }

	fibeAir4800OduAirCapacityDirection OBJECT-TYPE
		SYNTAX  INTEGER {
			undefined (1),
			low (2), 
			high(3)
		}
		ACCESS  read-write
		STATUS  mandatory
		DESCRIPTION
		"Capacity direction of the site."
		::= { fibeAir4800OduAir 55 }

	-- ###########################################################
	--                      Spectrum Analysis
	-- ###########################################################
	
	fibeAir4800OduAirSpectrumAnalysis OBJECT IDENTIFIER ::= { fibeAir4800OduAir 56 }
	
	fibeAir4800OduAirSpectrumAnalysisOperState OBJECT-TYPE
		SYNTAX  INTEGER {
			notSupported (1),
			stopSpectrumAnalysis (2),
			startSpectrumAnalysis (3),
			restartSpectrumAnalysis (4)
		}
		ACCESS  read-write
		STATUS  mandatory
		DESCRIPTION
		"Spectrum Analysis operation state.
		 The configurable values are Spectrum Analysis Stop, Start and Restart.
		 Not Supported value indicates that the feature is not supported on the device.
		 Not Supported is not a configurable state."
		::= { fibeAir4800OduAirSpectrumAnalysis 1 }	

	fibeAir4800OduAirRxPowerAntennaA OBJECT-TYPE
		SYNTAX  INTEGER
		ACCESS  read-only
		STATUS  mandatory
		DESCRIPTION
		"Received Signal Strength in dBm of Antenna A."
		::= { fibeAir4800OduAirSpectrumAnalysis 2 }
		
	fibeAir4800OduAirRxPowerAntennaB OBJECT-TYPE
		SYNTAX  INTEGER
		ACCESS  read-only
		STATUS  mandatory
		DESCRIPTION
		"Received Signal Strength in dBm of Antenna B."
		::= { fibeAir4800OduAirSpectrumAnalysis 3 }
		
	fibeAir4800OduAirNumberOfSpectrumChannels OBJECT-TYPE
		SYNTAX  INTEGER
		ACCESS  read-only
		STATUS  mandatory
		DESCRIPTION
		"Represents the number of Spectrum Channels."
		::= { fibeAir4800OduAirSpectrumAnalysis 4 }
		
		
	-- ###########################################################
	--                      Spectrum Channel Table
	-- ###########################################################
	
	fibeAir4800OduAirSpectrumChannelTable OBJECT-TYPE
		SYNTAX  SEQUENCE OF FibeAir4800OduAirSpectrumChannelTableEntry
		ACCESS  not-accessible
		STATUS  mandatory
		DESCRIPTION
		"ODU Spectrum Analysis Channel Table."
		::= { fibeAir4800OduAirSpectrumAnalysis 5 }
		
	fibeAir4800OduAirSpectrumChannelTableEntry OBJECT-TYPE
		SYNTAX  FibeAir4800OduAirSpectrumChannelTableEntry
		ACCESS  not-accessible
		STATUS  mandatory
		DESCRIPTION
		"ODU Spectrum Analysis Channel Table entry."
		INDEX { fibeAir4800OduAirSpectrumChannelIndex }
		::= { fibeAir4800OduAirSpectrumChannelTable 1 }

	FibeAir4800OduAirSpectrumChannelTableEntry ::= SEQUENCE {
		fibeAir4800OduAirSpectrumChannelIndex
			INTEGER,
		fibeAir4800OduAirSpectrumChannelFrequency
			INTEGER,
		fibeAir4800OduAirSpectrumChannelScanned
			INTEGER,
		fibeAir4800OduAirSpectrumChannelScanningTimestamp
			TimeTicks,
		fibeAir4800OduAirSpectrumChannelLastNFAntennaA
			INTEGER,
		fibeAir4800OduAirSpectrumChannelLastNFAntennaB
			INTEGER,
		fibeAir4800OduAirSpectrumChannelAverageNFAntennaA
			INTEGER,
		fibeAir4800OduAirSpectrumChannelAverageNFAntennaB
			INTEGER,
		fibeAir4800OduAirSpectrumChannelMaxNFAntennaA
			INTEGER,
		fibeAir4800OduAirSpectrumChannelMaxNFAntennaB
			INTEGER,
		fibeAir4800OduAirSpectrumChannelCACPerformed
			INTEGER,
		fibeAir4800OduAirSpectrumChannelLastCACTimestamp
			TimeTicks,
		fibeAir4800OduAirSpectrumChannelRadarDetected
			INTEGER,
		fibeAir4800OduAirSpectrumChannelRadarDetectionTimestamp
			TimeTicks,
		fibeAir4800OduAirSpectrumChannelAvailable
			INTEGER,
		fibeAir4800OduAirSpectrumChannelMaxBeaconRss
			INTEGER,
		fibeAir4800OduAirSpectrumChannelCompressed
			OCTET STRING		
		}
		
	fibeAir4800OduAirSpectrumChannelIndex OBJECT-TYPE
		SYNTAX  INTEGER (1..1000000)
		ACCESS  read-only
		STATUS  mandatory
		DESCRIPTION
		"ODU Spectrum Channel index."
		::= { fibeAir4800OduAirSpectrumChannelTableEntry 1 }

	fibeAir4800OduAirSpectrumChannelFrequency OBJECT-TYPE
		SYNTAX  INTEGER
		ACCESS  read-only
		STATUS  mandatory
		DESCRIPTION
		"ODU Spectrum Channel frequency in MHz."
		::= { fibeAir4800OduAirSpectrumChannelTableEntry 2 }	

	fibeAir4800OduAirSpectrumChannelScanned OBJECT-TYPE
		SYNTAX  INTEGER {notScanned (1),
						 scanned (2)}
		ACCESS  read-only
		STATUS  mandatory
		DESCRIPTION
		"An indication of the vaildity of the channel's data.
		 If the channel was scanned the data is valid, else not."
		::= { fibeAir4800OduAirSpectrumChannelTableEntry 3 }

	fibeAir4800OduAirSpectrumChannelScanningTimestamp OBJECT-TYPE
		SYNTAX  TimeTicks
		ACCESS  read-only
		STATUS  mandatory
		DESCRIPTION
		"Channel last scan timestamp, in hundredths of a second, since device up time.
		 If the channel was not scanned than the return value will be 0."
		::= { fibeAir4800OduAirSpectrumChannelTableEntry 4 }

	fibeAir4800OduAirSpectrumChannelLastNFAntennaA OBJECT-TYPE
		SYNTAX  INTEGER
		ACCESS  read-only
		STATUS  mandatory
		DESCRIPTION
		"Normalized Noise Floor value in dBm - of Antenna A - (including 2 neighbor frequencies)."
		::= { fibeAir4800OduAirSpectrumChannelTableEntry 5 }

	fibeAir4800OduAirSpectrumChannelLastNFAntennaB OBJECT-TYPE
		SYNTAX  INTEGER
		ACCESS  read-only
		STATUS  mandatory
		DESCRIPTION
		"Normalized Noise Floor value in dBm - of Antenna B - (including 2 neighbor frequencies)."
		::= { fibeAir4800OduAirSpectrumChannelTableEntry 6 }

	fibeAir4800OduAirSpectrumChannelAverageNFAntennaA OBJECT-TYPE
		SYNTAX  INTEGER
		ACCESS  read-only
		STATUS  mandatory
		DESCRIPTION
		"Average normalized Noise Floor value in dBm - of Antenna A -  over all dwells."
		::= { fibeAir4800OduAirSpectrumChannelTableEntry 7 }
	
	fibeAir4800OduAirSpectrumChannelAverageNFAntennaB OBJECT-TYPE
		SYNTAX  INTEGER
		ACCESS  read-only
		STATUS  mandatory
		DESCRIPTION
		"Average normalized Noise Floor value in dBm - of Antenna B -  over all dwells."
		::= { fibeAir4800OduAirSpectrumChannelTableEntry 8 }

	fibeAir4800OduAirSpectrumChannelMaxNFAntennaA OBJECT-TYPE
		SYNTAX  INTEGER
		ACCESS  read-only
		STATUS  mandatory
		DESCRIPTION
		"Max normalized Noise Floor value in dBm - of Antenna A -  over all dwells."
		::= { fibeAir4800OduAirSpectrumChannelTableEntry 9 }
		
	fibeAir4800OduAirSpectrumChannelMaxNFAntennaB OBJECT-TYPE
		SYNTAX  INTEGER
		ACCESS  read-only
		STATUS  mandatory
		DESCRIPTION
		"Max normalized Noise Floor value in dBm - of Antenna B -  over all dwells."
		::= { fibeAir4800OduAirSpectrumChannelTableEntry 10 }
		
	fibeAir4800OduAirSpectrumChannelCACPerformed OBJECT-TYPE
		SYNTAX  INTEGER {notPerformed (1),
						 performed (2)}
		ACCESS  read-only
		STATUS  mandatory
		DESCRIPTION
		"Was CAC performed on the channel."
		::= { fibeAir4800OduAirSpectrumChannelTableEntry 11 }
		
	fibeAir4800OduAirSpectrumChannelLastCACTimestamp OBJECT-TYPE
		SYNTAX  TimeTicks
		ACCESS  read-only
		STATUS  mandatory
		DESCRIPTION
		"Last CAC performed timestamp, in hundredths of a second, since device up time.
		 If no CAC has performed on the channel, the return value will be 0."
		::= { fibeAir4800OduAirSpectrumChannelTableEntry 12 }
						
	fibeAir4800OduAirSpectrumChannelRadarDetected OBJECT-TYPE
		SYNTAX  INTEGER {notDetected (1),
						 detected (2)}
		ACCESS  read-only
		STATUS  mandatory
		DESCRIPTION
		"Was Radar detected on the channel."
		::= { fibeAir4800OduAirSpectrumChannelTableEntry 13 }
		
	fibeAir4800OduAirSpectrumChannelRadarDetectionTimestamp OBJECT-TYPE
		SYNTAX  TimeTicks
		ACCESS  read-only
		STATUS  mandatory
		DESCRIPTION
		"Last Radar Detection timestamp, in hundredths of a second, since device up time.
		 If no Radar has detected on the channel, the return value will be 0."
		::= { fibeAir4800OduAirSpectrumChannelTableEntry 14 }
	
	fibeAir4800OduAirSpectrumChannelAvailable OBJECT-TYPE
		SYNTAX  INTEGER {notAvailable (1),
						 available (2)}
		ACCESS  read-only
		STATUS  mandatory
		DESCRIPTION
		"Is the channel available for use."
		::= { fibeAir4800OduAirSpectrumChannelTableEntry 15 }	

	fibeAir4800OduAirSpectrumChannelMaxBeaconRss OBJECT-TYPE
		SYNTAX  INTEGER
		ACCESS  read-only
		STATUS  mandatory
		DESCRIPTION
		"The max RSS value of a received beacon on the specific channel in dBm."
		::= { fibeAir4800OduAirSpectrumChannelTableEntry 16 }

	fibeAir4800OduAirSpectrumChannelCompressed OBJECT-TYPE
		SYNTAX	OCTET STRING
		ACCESS  read-only
		STATUS  mandatory
		DESCRIPTION
		"Compress all the Spectrum data per channel into one variable.
		Frequency (4 bytes)
		Scanned (1 byte)
		Timestamp (4 bytes)
		Last NF Antenna A (1 byte)
		Last NF Antenna B (1 byte)
		Avg NF Antenna A (1 byte)
		Avg NF Antenna B (1 byte)
		Max NF Antenna A (1 byte)
		Max NF Antenna B (1 byte)
		CAC Performed (1 byte)
		Last CAC Timestamp (4 bytes)
		Radar Detected (1 byte)
		Radar Detected Timestamp (4 bytes)
		Channel Available (1 byte)
		Max Beacon RSS (1 byte)."
		::= { fibeAir4800OduAirSpectrumChannelTableEntry 17 }
	
	fibeAir4800OduAirChipMinMaxFreq OBJECT-TYPE
		SYNTAX  DisplayString
		ACCESS  read-only
		STATUS  mandatory
		DESCRIPTION
		"The minimum and maximum frequencies in MHz which the chip supports."
		::= { fibeAir4800OduAirSpectrumAnalysis 6 }	

	fibeAir4800OduAirSpectrumAnalysisTimeout OBJECT-TYPE
		SYNTAX  INTEGER
		ACCESS  read-write
		STATUS  mandatory
		DESCRIPTION
		"Spectrum analysis timeout in seconds."
		::= { fibeAir4800OduAirSpectrumAnalysis 7 }
		
	fibeAir4800OduAirAntConfAndRatesStatus OBJECT-TYPE
		SYNTAX  INTEGER {
			srsr(1),
			drdr(2),
			drsr(3)
		}
		ACCESS  read-only
		STATUS  mandatory
		DESCRIPTION
		"Description: Antenna configuration and Rates status (1 = Single antenna with single data 	stream, 2 = Dual antenna with single data stream, 3 = Dual antenna with dual data 	stream)."
		::= { fibeAir4800OduAir 57 }

	fibeAir4800OduAirDualAntTxMode OBJECT-TYPE
		SYNTAX  INTEGER {
			mimo(1),
			diversity(2)
		}
		ACCESS  read-write
		STATUS  mandatory
		DESCRIPTION
		"Description: Transmission type when using Dual radios (MIMO or AdvancedDiversity using  one stream of data)."
		::= { fibeAir4800OduAir 58 }		
				
	fibeAir4800OduAirTxOperationMode OBJECT-TYPE
		SYNTAX  INTEGER {
			regularMode(1),
			measurementMode (2)

		}
		ACCESS  read-write
		STATUS  mandatory
		DESCRIPTION
		"This parameter controls the Operation mode of frames sent over the air. 
		The Operation mode is either normal (1) for regular transmission where frame size is determined by the traffic or throughput test (2) when the user requests an actual over the air throughput estimation using full frames. 
		The latter lasts no more than a predetermined interval (default 30 sec)."
		::= { fibeAir4800OduAir 59 }		
				
				
	fibeAir4800OduAirAsymmetricTdd OBJECT IDENTIFIER ::= { fibeAir4800OduAir 60 }

	-- ###########################################################
	--                      A-Symmetric Table
	-- ###########################################################	
	
	fibeAir4800OduAirDesiredNetMasterTxRatio OBJECT-TYPE
		SYNTAX  INTEGER(0..1000)
		ACCESS  read-write
		STATUS  mandatory
		DESCRIPTION
		"This parameter is reserved to the element manager provided with the product."
		::= { fibeAir4800OduAirAsymmetricTdd 1 }

	fibeAir4800OduAirCurrentNetMasterTxRatio OBJECT-TYPE
		SYNTAX  INTEGER
		ACCESS  read-only
		STATUS  mandatory
		DESCRIPTION
		"Represents the actual Net Master Tx RAtio."
		::= { fibeAir4800OduAirAsymmetricTdd 2 }

	fibeAir4800OduAirMinUsableMasterTxRatio OBJECT-TYPE
		SYNTAX  INTEGER
		ACCESS  read-only
		STATUS  mandatory
		DESCRIPTION
		"Represents the minimal value the user can configure for Desired net mAster Tx Ratio."
		::= { fibeAir4800OduAirAsymmetricTdd 3 }

	fibeAir4800OduAirMaxUsableMasterTxRatio OBJECT-TYPE
		SYNTAX  INTEGER
		ACCESS  read-only
		STATUS  mandatory
		DESCRIPTION
		"Represents the maximal value the user can configure for Desired net mAster Tx Ratio."
		::= { fibeAir4800OduAirAsymmetricTdd 4 }

	fibeAir4800OduAirAccumulatedUAS OBJECT-TYPE
		SYNTAX  INTEGER
		ACCESS  read-only
		STATUS  mandatory
		DESCRIPTION
		"Accumulates the Unavailable seconds of the Air Interface. Relevant for point to point systems."
		::= { fibeAir4800OduAir 61 }
		
	fibeAir4800OduAirDistStr OBJECT-TYPE
		SYNTAX  DisplayString
		ACCESS  read-only
		STATUS  mandatory
		DESCRIPTION
		" Possibilities of the link according to RFP and CBW "
		::= { fibeAir4800OduAir  62}
	
	fibeAir4800OduAirChannelsDefaultFreqStr OBJECT-TYPE
		SYNTAX  DisplayString
		ACCESS  read-only
		STATUS  mandatory
		DESCRIPTION
		"A string representing the channels available. 
		Each character represents one frequency, when '1' means its available, and '0' means its not."
		::= { fibeAir4800OduAir 63 }		

	fibeAir4800OduAirAntConnectionType OBJECT-TYPE
		SYNTAX  INTEGER {
			external(1),
			integrated(2),
			embeddedExternal(3),
			embeddedIntegrated(4),
			integratedBSA(5)
			}
		ACCESS  read-write
		STATUS  mandatory
		DESCRIPTION
		"Antenna connection type (External(1), Integrated(2), Embedded_External(3), Embedded_Integrated(4), Integrated_BSA(5))."
		::= { fibeAir4800OduAir 64 }
		
	fibeAir4800OduAirAllowableChannelsStr OBJECT-TYPE
		SYNTAX  DisplayString
		ACCESS  read-write
		STATUS  mandatory
		DESCRIPTION
		"A string representing the allowable channels. 
		Each character represents one channel, when '1' means its available, and '0' means its not."
		::= { fibeAir4800OduAir 65 }
		
	fibeAir4800OduAirDfs OBJECT IDENTIFIER ::= { fibeAir4800OduAir 66 }
		
	fibeAir4800OduAirDfsAlgorithmTypeState OBJECT-TYPE
		SYNTAX  INTEGER
		ACCESS  read-write
		STATUS  mandatory
		DESCRIPTION
		"Bitmap for state of Radar Algorithm Type. Filters by bit's position:  
		0 = Zero PW,
		1 = Fixed,
		2 = Variable,
		3 = Staggered,
		4 = Long."
		::= { fibeAir4800OduAirDfs 1 }
		
	-- ###########################################################
	--                 Dfs Last Detected Radars Table
	-- ###########################################################
	fibeAir4800OduAirDfsLastDetectedTbl OBJECT-TYPE
		SYNTAX  SEQUENCE OF FibeAir4800OduAirDfsLastDetectedEntry
		ACCESS  not-accessible
		STATUS  mandatory
		DESCRIPTION
		"Last detected radars table."
		::= { fibeAir4800OduAirDfs 2 }

	fibeAir4800OduAirDfsLastDetectedEntry OBJECT-TYPE
		SYNTAX  FibeAir4800OduAirDfsLastDetectedEntry
		ACCESS  not-accessible
		STATUS  mandatory
		DESCRIPTION
		"ODU Multi-band Sub Bands Table entry."
		INDEX { fibeAir4800OduAirDfsLastDetectedIndex }
		::= { fibeAir4800OduAirDfsLastDetectedTbl 1 }

	FibeAir4800OduAirDfsLastDetectedEntry ::= SEQUENCE {
		fibeAir4800OduAirDfsLastDetectedIndex
			INTEGER,
		fibeAir4800OduAirDfsLastDetectedTime
			TimeTicks,
		fibeAir4800OduAirDfsLastDetectedAlgorithmType
			INTEGER,
		fibeAir4800OduAirDfsLastDetectedFrequency
			INTEGER
		}
		
	fibeAir4800OduAirDfsLastDetectedIndex OBJECT-TYPE
		SYNTAX  INTEGER
		ACCESS  read-only
		STATUS  mandatory
		DESCRIPTION
		"Dfs Last Detected Radars Table Index."
		::= { fibeAir4800OduAirDfsLastDetectedEntry 1 }
		
	fibeAir4800OduAirDfsLastDetectedTime OBJECT-TYPE
		SYNTAX  TimeTicks
		ACCESS  read-only
		STATUS  mandatory
		DESCRIPTION
		"Dfs time of the last detected radar."
		::= { fibeAir4800OduAirDfsLastDetectedEntry 2 }
		
	fibeAir4800OduAirDfsLastDetectedAlgorithmType OBJECT-TYPE
		SYNTAX  INTEGER
		ACCESS  read-only
		STATUS  mandatory
		DESCRIPTION
		"Dfs type of the last detected radar."
		::= { fibeAir4800OduAirDfsLastDetectedEntry 3 }
		
	fibeAir4800OduAirDfsLastDetectedFrequency OBJECT-TYPE
		SYNTAX  INTEGER
		ACCESS  read-only
		STATUS  mandatory
		DESCRIPTION
		"Dfs frequency of the last detected radar."
		::= { fibeAir4800OduAirDfsLastDetectedEntry 4 }

	fibeAir4800OduAirPreferredChannelsStr OBJECT-TYPE
		SYNTAX  DisplayString
		ACCESS  read-write
		STATUS  mandatory
		DESCRIPTION
		"A string representing the preferred channels. 
		Each character represents one channel, when '1' means its preferred, and '0' means its not."
		::= { fibeAir4800OduAir 67 }
		
	fibeAir4800OduAirSyncLossThreshold OBJECT-TYPE
		SYNTAX  INTEGER
		ACCESS  read-write
		STATUS  mandatory
		DESCRIPTION
		"When the current throughput is below this threshold (in Kbps), sync loss will occur."
		::= { fibeAir4800OduAir 68 }
	
	fibeAir4800OduAirGeoLocation OBJECT-TYPE
		SYNTAX  DisplayString
		ACCESS  read-write
		STATUS  mandatory
		DESCRIPTION
		"Geographic device location in format: 	latitude,longitude."
		::= { fibeAir4800OduAir 69 }

	fibeAir4800OduAirAggregateCapacity OBJECT-TYPE
		SYNTAX  INTEGER
		ACCESS  read-only
		STATUS  mandatory
		DESCRIPTION
		"Aggregate Capacity of the ODU in Mbps."
		::= { fibeAir4800OduAir 70 }
		
	fibeAir4800OduAirALPM OBJECT IDENTIFIER ::= { fibeAir4800OduAir 71 }
		
	fibeAir4800OduAirALPMDataBufferStr OBJECT-TYPE
		SYNTAX  OCTET STRING
		ACCESS  read-write
		STATUS  mandatory
		DESCRIPTION
		"A string that holds all of the ALPM events data"
		::= { fibeAir4800OduAirALPM 1 }
	
	fibeAir4800OduAirCurrentManualAngle OBJECT-TYPE
		SYNTAX  INTEGER
		ACCESS  read-only
		STATUS  mandatory
		DESCRIPTION
		"Absolute (manual) angle (Deg.) of the unit."
		::= { fibeAir4800OduAir 72 }

	fibeAir4800OduAirCurrentManualElevAngle OBJECT-TYPE
		SYNTAX  INTEGER
		ACCESS  read-only
		STATUS  mandatory
		DESCRIPTION
		"Absolute Elevation angle (Deg.) of the unit."
		::= { fibeAir4800OduAir 73 }

	fibeAir4800OduAirAntennaTemperatureC  OBJECT-TYPE
		SYNTAX  INTEGER
		ACCESS  read-only
		STATUS  mandatory
		DESCRIPTION
		"Antenna Temperature (C)"
		::= { fibeAir4800OduAir 74 }
		
	-- ###########################################################
	--                      ODU Perf Monitor
	-- ###########################################################

	fibeAir4800OduPerfMon OBJECT IDENTIFIER ::= { fibeAir4800Odu 6 }

	-- ###########################################################
	--                      PM Current Table
	-- ###########################################################

	fibeAir4800OduPerfMonCurrTable OBJECT-TYPE
		SYNTAX  SEQUENCE OF FibeAir4800OduPerfMonCurrEntry
		ACCESS  not-accessible
		STATUS  mandatory
		DESCRIPTION
		"This table defines/keeps the counters of the current 15 min interval."
		::= { fibeAir4800OduPerfMon 1 }

	fibeAir4800OduPerfMonCurrEntry OBJECT-TYPE
		SYNTAX  FibeAir4800OduPerfMonCurrEntry
		ACCESS  not-accessible
		STATUS  mandatory
		DESCRIPTION
		"This is an entry in the Current Interval Table."
		INDEX {ifIndex }
		::= { fibeAir4800OduPerfMonCurrTable 1 }

	FibeAir4800OduPerfMonCurrEntry ::= SEQUENCE {
		fibeAir4800OduPerfMonCurrUAS
	      Gauge,
   		fibeAir4800OduPerfMonCurrES
	      Gauge,
		fibeAir4800OduPerfMonCurrSES
	      Gauge,
		fibeAir4800OduPerfMonCurrBBE
	      Gauge,
		fibeAir4800OduPerfMonCurrIntegrity
	      INTEGER,
		fibeAir4800OduPerfMonCurrCompressed
	      OCTET STRING
	}

	fibeAir4800OduPerfMonCurrUAS OBJECT-TYPE
		SYNTAX  Gauge (0..900)
		ACCESS  read-only
		STATUS  mandatory
		DESCRIPTION
		" The current number of Unavailable Seconds starting from the present 15 minutes period."
		::= { fibeAir4800OduPerfMonCurrEntry 1 }

	fibeAir4800OduPerfMonCurrES OBJECT-TYPE
		SYNTAX  Gauge (0..900)
		ACCESS  read-only
		STATUS  mandatory
		DESCRIPTION
		"Current number of Errored Seconds starting from the present 15 minutes period."
		::= { fibeAir4800OduPerfMonCurrEntry 2 }

	fibeAir4800OduPerfMonCurrSES OBJECT-TYPE
		SYNTAX  Gauge (0..900)
		ACCESS  read-only
		STATUS  mandatory
		DESCRIPTION
		"Current number of Severely Errored Seconds starting from the present 15 minutes period."
		::= { fibeAir4800OduPerfMonCurrEntry 3 }

	fibeAir4800OduPerfMonCurrBBE OBJECT-TYPE
		SYNTAX  Gauge (0..1800000)
		ACCESS  read-only
		STATUS  mandatory
		DESCRIPTION
		"Current number of Background Block Errors starting from the present 15 minutes period."
		::= { fibeAir4800OduPerfMonCurrEntry 4 }

	fibeAir4800OduPerfMonCurrIntegrity OBJECT-TYPE
		SYNTAX  INTEGER {
			true(1),
			false(2)
			}
		ACCESS  read-only
		STATUS  mandatory
		DESCRIPTION
		"Indicates the integrity of the entry."
		::= { fibeAir4800OduPerfMonCurrEntry 5 }
		
	fibeAir4800OduPerfMonCurrCompressed OBJECT-TYPE
		SYNTAX  OCTET STRING
		ACCESS  read-only
		STATUS  mandatory
		DESCRIPTION
		"Holds a compressed string of all data per interface.
		
		Compressed Air Interface Structure (size in brackets):
			UAS (4), ES (4), SES (4), BBE (4), Integrity (1), 
			MinRSL (1), MaxRSL (1), RSLThresh1Exceeded (4), 
			RSLThresh2Exceeded (4), MinTSL (1), MaxTSL (1),
			TSLThresh1Exceed (4), BBERThresh1Exceed (4), RxMBytes (4)
			TxMBytes (4), EthCapacityThreshUnder (4), HighTrafficThreshExceed (4)
			
		Compressed Etherent ODU	interface (size in brackets):
			UAS (4), ES (4), SES (4), BBE (4), Integrity (1), 
			RxMBytes (4), TxMBytes (4), EthCapacityThreshUnder (4), 
			HighTrafficThreshExceed (4), ActiveSeconds (4)
		"
		::= { fibeAir4800OduPerfMonCurrEntry 6}
		
	-- ###########################################################
	--                      PM Interval Table
	-- ###########################################################	

	fibeAir4800OduPerfMonIntervalTable OBJECT-TYPE
		SYNTAX  SEQUENCE OF FibeAir4800OduPerfMonIntervalEntry
		ACCESS  not-accessible
		STATUS  mandatory
		DESCRIPTION
		"This table defines/keeps the counters of the last day (in resolution of 15 min intervals)."
		::= { fibeAir4800OduPerfMon 2 }

	fibeAir4800OduPerfMonIntervalEntry OBJECT-TYPE
		SYNTAX  FibeAir4800OduPerfMonIntervalEntry
		ACCESS  not-accessible
		STATUS  mandatory
		DESCRIPTION
		"This is an entry in the Interval Table."
		INDEX {ifIndex, fibeAir4800OduPerfMonIntervalIdx }
		::= { fibeAir4800OduPerfMonIntervalTable 1 }

	FibeAir4800OduPerfMonIntervalEntry ::= SEQUENCE {
		fibeAir4800OduPerfMonIntervalIdx
	      INTEGER,
		fibeAir4800OduPerfMonIntervalUAS
	      Gauge,
   		fibeAir4800OduPerfMonIntervalES
	      Gauge,
		fibeAir4800OduPerfMonIntervalSES
	      Gauge,
		fibeAir4800OduPerfMonIntervalBBE
	      Gauge,
		fibeAir4800OduPerfMonIntervalIntegrity
	      INTEGER,
		fibeAir4800OduPerfMonIntervalCompressed
	      OCTET STRING		  		
	}

	fibeAir4800OduPerfMonIntervalIdx OBJECT-TYPE
		SYNTAX  INTEGER (1..96)
		ACCESS  read-only
		STATUS  mandatory
		DESCRIPTION
		"This table is indexed per interval number. Each interval
		is of 15 minutes and the oldest is 96."
	::= { fibeAir4800OduPerfMonIntervalEntry 1 }

	fibeAir4800OduPerfMonIntervalUAS OBJECT-TYPE
		SYNTAX  Gauge (0..900)
		ACCESS  read-only
		STATUS  mandatory
		DESCRIPTION
		" The current number of Unavailable Seconds per interval."
		::= { fibeAir4800OduPerfMonIntervalEntry 2 }

	fibeAir4800OduPerfMonIntervalES OBJECT-TYPE
		SYNTAX  Gauge (0..900)
		ACCESS  read-only
		STATUS  mandatory
		DESCRIPTION
		"Current number of Errored Seconds per interval."
		::= { fibeAir4800OduPerfMonIntervalEntry 3 }

	fibeAir4800OduPerfMonIntervalSES OBJECT-TYPE
		SYNTAX  Gauge (0..900)
		ACCESS  read-only
		STATUS  mandatory
		DESCRIPTION
		"Current number of Severely Errored Seconds per interval."
		::= { fibeAir4800OduPerfMonIntervalEntry 4 }

	fibeAir4800OduPerfMonIntervalBBE OBJECT-TYPE
		SYNTAX  Gauge (0..1800000)
		ACCESS  read-only
		STATUS  mandatory
		DESCRIPTION
		"Current number of Background Block Errors per interval."
		::= { fibeAir4800OduPerfMonIntervalEntry 5 }

	fibeAir4800OduPerfMonIntervalIntegrity OBJECT-TYPE
		SYNTAX  INTEGER {
			true(1),
			false(2)
			}
		ACCESS  read-only
		STATUS  mandatory
		DESCRIPTION
		"Indicates the integrity of the entry per interval."
		::= { fibeAir4800OduPerfMonIntervalEntry 6 }

	fibeAir4800OduPerfMonIntervalCompressed OBJECT-TYPE
		SYNTAX  OCTET STRING
		ACCESS  read-only
		STATUS  mandatory
		DESCRIPTION
		"Holds a compressed string of all data per interface.
		
		Compressed Air Interface Structure (size in brackets):
			UAS (4), ES (4), SES (4), BBE (4), Integrity (1), 
			MinRSL (1), MaxRSL (1), RSLThresh1Exceeded (4), 
			RSLThresh2Exceeded (4), MinTSL (1), MaxTSL (1),
			TSLThresh1Exceed (4), BBERThresh1Exceed (4), RxMBytes (4)
			TxMBytes (4), EthCapacityThreshUnder (4), HighTrafficThreshExceed (4)
			
		Compressed Etherent ODU	interface (size in brackets):
			UAS (4), ES (4), SES (4), BBE (4), Integrity (1), 
			RxMBytes (4), TxMBytes (4), EthCapacityThreshUnder (4), 
			HighTrafficThreshExceed (4), ActiveSeconds (1)
		"
		::= { fibeAir4800OduPerfMonIntervalEntry 7}

	-- ###########################################################
	--                      PM Day Table
	-- ###########################################################	

	fibeAir4800OduPerfMonDayTable OBJECT-TYPE
		SYNTAX  SEQUENCE OF FibeAir4800OduPerfMonDayEntry
		ACCESS  not-accessible
		STATUS  mandatory
		DESCRIPTION
		"This table defines/keeps the counters of the last month (in resolution of days)."
		::= { fibeAir4800OduPerfMon 3 }

	fibeAir4800OduPerfMonDayEntry OBJECT-TYPE
		SYNTAX  FibeAir4800OduPerfMonDayEntry
		ACCESS  not-accessible
		STATUS  mandatory
		DESCRIPTION
		"This is an entry in the Days Table."
		INDEX {ifIndex, fibeAir4800OduPerfMonDayIdx }
		::= { fibeAir4800OduPerfMonDayTable 1 }

	FibeAir4800OduPerfMonDayEntry ::= SEQUENCE {
		fibeAir4800OduPerfMonDayIdx
	      INTEGER,
		fibeAir4800OduPerfMonDayUAS
	      Gauge,
   		fibeAir4800OduPerfMonDayES
	      Gauge,
		fibeAir4800OduPerfMonDaySES
	      Gauge,
		fibeAir4800OduPerfMonDayBBE
	      Gauge,
		fibeAir4800OduPerfMonDayIntegrity
	      INTEGER,
		fibeAir4800OduPerfMonDayCompressed
	      OCTET STRING		  		  		
	}

	fibeAir4800OduPerfMonDayIdx OBJECT-TYPE
		SYNTAX  INTEGER (1..30)
		ACCESS  read-only
		STATUS  mandatory
		DESCRIPTION
		"This table is indexed per interval number. Each interval
		is of 24 hours and the oldest is 30."
	::= { fibeAir4800OduPerfMonDayEntry 1 }

	fibeAir4800OduPerfMonDayUAS OBJECT-TYPE
		SYNTAX  Gauge (0..86400)
		ACCESS  read-only
		STATUS  mandatory
		DESCRIPTION
		"The current number of Unavailable Seconds per interval of 24 hours."
		::= { fibeAir4800OduPerfMonDayEntry 2 }

	fibeAir4800OduPerfMonDayES OBJECT-TYPE
		SYNTAX  Gauge (0..86400)
		ACCESS  read-only
		STATUS  mandatory
		DESCRIPTION
		"Current number of Errored Seconds per interval of 24 hours."
		::= { fibeAir4800OduPerfMonDayEntry 3 }

	fibeAir4800OduPerfMonDaySES OBJECT-TYPE
		SYNTAX  Gauge (0..86400)
		ACCESS  read-only
		STATUS  mandatory
		DESCRIPTION
		"Current number of Severely Errored Seconds per interval of 24 hours."
		::= { fibeAir4800OduPerfMonDayEntry 4 }

	fibeAir4800OduPerfMonDayBBE OBJECT-TYPE
		SYNTAX  Gauge (0..172800000)
		ACCESS  read-only
		STATUS  mandatory
		DESCRIPTION
		"Current number of Background Block Errors per interval of 24 hours."
		::= { fibeAir4800OduPerfMonDayEntry 5 }

	fibeAir4800OduPerfMonDayIntegrity OBJECT-TYPE
		SYNTAX  INTEGER {
			true(1),
			false(2)
			}
		ACCESS  read-only
		STATUS  mandatory
		DESCRIPTION
		"Indicates the integrity of the entry per interval of 24 hours."
		::= { fibeAir4800OduPerfMonDayEntry 6 }

	fibeAir4800OduPerfMonDayCompressed OBJECT-TYPE
		SYNTAX  OCTET STRING
		ACCESS  read-only
		STATUS  mandatory
		DESCRIPTION
		"Holds a compressed string of all data per interface.
		
		Compressed Air Interface Structure (size in brackets):
			UAS (4), ES (4), SES (4), BBE (4), Integrity (1), 
			MinRSL (1), MaxRSL (1), RSLThresh1Exceeded (4), 
			RSLThresh2Exceeded (4), MinTSL (1), MaxTSL (1),
			TSLThresh1Exceed (4), BBERThresh1Exceed (4), RxMBytes (4)
			TxMBytes (4), EthCapacityThreshUnder (4), HighTrafficThreshExceed (4)
			
		Compressed Etherent ODU	interface (size in brackets):
			UAS (4), ES (4), SES (4), BBE (4), Integrity (1), 
			RxMBytes (4), TxMBytes (4), EthCapacityThreshUnder (4), 
			HighTrafficThreshExceed (4), ActiveSeconds (1)
		"
		::= { fibeAir4800OduPerfMonDayEntry 7}

	-- ###########################################################
	--                      PM Air Current Table
	-- ###########################################################

	fibeAir4800OduPerfMonAirCurrTable OBJECT-TYPE
		SYNTAX  SEQUENCE OF FibeAir4800OduPerfMonAirCurrEntry
		ACCESS  not-accessible
		STATUS  mandatory
		DESCRIPTION
		"This table defines/keeps the air counters of the current 15 min interval."
		::= { fibeAir4800OduPerfMon 4 }

	fibeAir4800OduPerfMonAirCurrEntry OBJECT-TYPE
		SYNTAX  FibeAir4800OduPerfMonAirCurrEntry
		ACCESS  not-accessible
		STATUS  mandatory
		DESCRIPTION
		"This is an entry in the Current Interval Table."
		INDEX {ifIndex }
		::= { fibeAir4800OduPerfMonAirCurrTable 1 }

	FibeAir4800OduPerfMonAirCurrEntry ::= SEQUENCE {
		fibeAir4800OduPerfMonAirCurrMinRSL
	      INTEGER,
   		fibeAir4800OduPerfMonAirCurrMaxRSL
	      INTEGER,
		fibeAir4800OduPerfMonAirCurrRSLThresh1Exceed
	      Gauge,
		fibeAir4800OduPerfMonAirCurrRSLThresh2Exceed
	      Gauge,
		fibeAir4800OduPerfMonAirCurrMinTSL
		  INTEGER,
		fibeAir4800OduPerfMonAirCurrMaxTSL
		  INTEGER,
		fibeAir4800OduPerfMonAirCurrTSLThresh1Exceed
		  Gauge,		
		fibeAir4800OduPerfMonAirCurrBBERThresh1Exceed
		  Gauge
	}

	fibeAir4800OduPerfMonAirCurrMinRSL OBJECT-TYPE
		SYNTAX  INTEGER (-100..0)
		ACCESS  read-only
		STATUS  mandatory
		DESCRIPTION
		"Current Min Received Level Reference starting from the present 15 minutes period."
		::= { fibeAir4800OduPerfMonAirCurrEntry 1 }		

	fibeAir4800OduPerfMonAirCurrMaxRSL OBJECT-TYPE
		SYNTAX  INTEGER (-100..0)
		ACCESS  read-only
		STATUS  mandatory
		DESCRIPTION
		"Current Max Received Level Reference starting from the present 15 minutes period."
		::= { fibeAir4800OduPerfMonAirCurrEntry 2 }

	fibeAir4800OduPerfMonAirCurrRSLThresh1Exceed OBJECT-TYPE
		SYNTAX  Gauge (0..900)
		ACCESS  read-only
		STATUS  mandatory
		DESCRIPTION
		"Number of seconds Receive Signal Level exceeded the RSL1 threshold in the last 15 minutes."
		::= { fibeAir4800OduPerfMonAirCurrEntry 3 }

	fibeAir4800OduPerfMonAirCurrRSLThresh2Exceed OBJECT-TYPE
		SYNTAX  Gauge (0..900)
		ACCESS  read-only
		STATUS  mandatory
		DESCRIPTION
		"Number of seconds Receive Signal Level exceeded the RSL2 threshold in the last 15 minutes."
		::= { fibeAir4800OduPerfMonAirCurrEntry 4 }

	fibeAir4800OduPerfMonAirCurrMinTSL OBJECT-TYPE
		SYNTAX  INTEGER (-10..25)
		ACCESS  read-only
		STATUS  mandatory
		DESCRIPTION
		"Current Min Transmit Signal Level starting from the present 15 minutes period."
		::= { fibeAir4800OduPerfMonAirCurrEntry 5 }

	fibeAir4800OduPerfMonAirCurrMaxTSL OBJECT-TYPE
		SYNTAX  INTEGER (-10..25)
		ACCESS  read-only
		STATUS  mandatory
		DESCRIPTION
		"Current Max Transmit Signal Level starting from the present 15 minutes period."
		::= { fibeAir4800OduPerfMonAirCurrEntry 6 }

	fibeAir4800OduPerfMonAirCurrTSLThresh1Exceed OBJECT-TYPE
		SYNTAX  Gauge (0..900)
		ACCESS  read-only
		STATUS  mandatory
		DESCRIPTION
		"Number of seconds Transmit Signal Level exceeded the TSL1 threshold in the last 15 minutes."
		::= { fibeAir4800OduPerfMonAirCurrEntry 7 }

	fibeAir4800OduPerfMonAirCurrBBERThresh1Exceed OBJECT-TYPE
		SYNTAX  Gauge (0..900)
		ACCESS  read-only
		STATUS  mandatory
		DESCRIPTION
		"Number of seconds Background Block Error Ratio exceeded the BBER1 threshold in the last 15 minutes."
		::= { fibeAir4800OduPerfMonAirCurrEntry 8 }	
		
	-- ###########################################################
	--                      PM Air Interval Table
	-- ###########################################################	

	fibeAir4800OduPerfMonAirIntervalTable OBJECT-TYPE
		SYNTAX  SEQUENCE OF FibeAir4800OduPerfMonAirIntervalEntry
		ACCESS  not-accessible
		STATUS  mandatory
		DESCRIPTION
		"This table defines/keeps the air counters of the last day (in resolution of 15 min intervals)."
		::= { fibeAir4800OduPerfMon 5 }

	fibeAir4800OduPerfMonAirIntervalEntry OBJECT-TYPE
		SYNTAX  FibeAir4800OduPerfMonAirIntervalEntry
		ACCESS  not-accessible
		STATUS  mandatory
		DESCRIPTION
		"This is an entry in the Interval Table."
		INDEX {ifIndex, fibeAir4800OduPerfMonAirIntervalIdx }
		::= { fibeAir4800OduPerfMonAirIntervalTable 1 }

	FibeAir4800OduPerfMonAirIntervalEntry ::= SEQUENCE {
		fibeAir4800OduPerfMonAirIntervalIdx
	      INTEGER,
		fibeAir4800OduPerfMonAirIntervalMinRSL
	      INTEGER,
   		fibeAir4800OduPerfMonAirIntervalMaxRSL
	      INTEGER,
		fibeAir4800OduPerfMonAirIntervalRSLThresh1Exceed
	      Gauge,
		fibeAir4800OduPerfMonAirIntervalRSLThresh2Exceed
	      Gauge,
		fibeAir4800OduPerfMonAirIntervalMinTSL
		  INTEGER,
		fibeAir4800OduPerfMonAirIntervalMaxTSL
		  INTEGER,
		fibeAir4800OduPerfMonAirIntervalTSLThresh1Exceed
		  Gauge,		
		fibeAir4800OduPerfMonAirIntervalBBERThresh1Exceed
		  Gauge
	}

	fibeAir4800OduPerfMonAirIntervalIdx OBJECT-TYPE
		SYNTAX  INTEGER (1..96)
		ACCESS  read-only
		STATUS  mandatory
		DESCRIPTION
		"This table is indexed per interval number. Each interval
		is of 15 minutes and the oldest is 96."
	::= { fibeAir4800OduPerfMonAirIntervalEntry 1 }

	fibeAir4800OduPerfMonAirIntervalMinRSL OBJECT-TYPE
		SYNTAX  INTEGER (-100..0)
		ACCESS  read-only
		STATUS  mandatory
		DESCRIPTION
		"Current Min Received Level Reference per interval."
		::= { fibeAir4800OduPerfMonAirIntervalEntry 2 }		

	fibeAir4800OduPerfMonAirIntervalMaxRSL OBJECT-TYPE
		SYNTAX  INTEGER (-100..0)
		ACCESS  read-only
		STATUS  mandatory
		DESCRIPTION
		"Current Max Received Level Reference per interval."
		::= { fibeAir4800OduPerfMonAirIntervalEntry 3 }

	fibeAir4800OduPerfMonAirIntervalRSLThresh1Exceed OBJECT-TYPE
		SYNTAX  Gauge (0..900)
		ACCESS  read-only
		STATUS  mandatory
		DESCRIPTION
		"Number of seconds Receive Signal Level exceeded the RSL1 threshold per interval."
		::= { fibeAir4800OduPerfMonAirIntervalEntry 4 }

	fibeAir4800OduPerfMonAirIntervalRSLThresh2Exceed OBJECT-TYPE
		SYNTAX  Gauge (0..900)
		ACCESS  read-only
		STATUS  mandatory
		DESCRIPTION
		"Number of seconds Receive Signal Level exceeded the RSL2 threshold
		ACCESS  read-only per interval."
		::= { fibeAir4800OduPerfMonAirIntervalEntry 5 }

	fibeAir4800OduPerfMonAirIntervalMinTSL OBJECT-TYPE
		SYNTAX  INTEGER (-10..25)
		ACCESS  read-only
		STATUS  mandatory
		DESCRIPTION
		"Current Min Transmit Signal Level per interval."
		::= { fibeAir4800OduPerfMonAirIntervalEntry 6 }

	fibeAir4800OduPerfMonAirIntervalMaxTSL OBJECT-TYPE
		SYNTAX  INTEGER (-10..25)
		ACCESS  read-only
		STATUS  mandatory
		DESCRIPTION
		"Current Max Transmit Signal Level per interval."
		::= { fibeAir4800OduPerfMonAirIntervalEntry 7 }

	fibeAir4800OduPerfMonAirIntervalTSLThresh1Exceed OBJECT-TYPE
		SYNTAX  Gauge (0..900)
		ACCESS  read-only
		STATUS  mandatory
		DESCRIPTION
		"Number of seconds Transmit Signal Level exceeded the TSL1 threshold per interval."
		::= { fibeAir4800OduPerfMonAirIntervalEntry 8 }

	fibeAir4800OduPerfMonAirIntervalBBERThresh1Exceed OBJECT-TYPE
		SYNTAX  Gauge (0..900)
		ACCESS  read-only
		STATUS  mandatory
		DESCRIPTION
		"Number of seconds Background Block Error Ratio exceeded the BBER1 threshold per interval."
		::= { fibeAir4800OduPerfMonAirIntervalEntry 9 }

	-- ###########################################################
	--                      PM Air Day Table
	-- ###########################################################	

	fibeAir4800OduPerfMonAirDayTable OBJECT-TYPE
		SYNTAX  SEQUENCE OF FibeAir4800OduPerfMonAirDayEntry
		ACCESS  not-accessible
		STATUS  mandatory
		DESCRIPTION
		"This table defines/keeps the air counters of the last month (in resolution of days)."
		::= { fibeAir4800OduPerfMon 6 }

	fibeAir4800OduPerfMonAirDayEntry OBJECT-TYPE
		SYNTAX  FibeAir4800OduPerfMonAirDayEntry
		ACCESS  not-accessible
		STATUS  mandatory
		DESCRIPTION
		"This is an entry in the Days Table."
		INDEX {ifIndex, fibeAir4800OduPerfMonAirDayIdx }
		::= { fibeAir4800OduPerfMonAirDayTable 1 }

	FibeAir4800OduPerfMonAirDayEntry ::= SEQUENCE {
		fibeAir4800OduPerfMonAirDayIdx
	      INTEGER,
		fibeAir4800OduPerfMonAirDayMinRSL
	      INTEGER,
   		fibeAir4800OduPerfMonAirDayMaxRSL
	      INTEGER,
		fibeAir4800OduPerfMonAirDayRSLThresh1Exceed
	      Gauge,
		fibeAir4800OduPerfMonAirDayRSLThresh2Exceed
	      Gauge,
		fibeAir4800OduPerfMonAirDayMinTSL
		  INTEGER,
		fibeAir4800OduPerfMonAirDayMaxTSL
		  INTEGER,
		fibeAir4800OduPerfMonAirDayTSLThresh1Exceed
		  Gauge,		
		fibeAir4800OduPerfMonAirDayBBERThresh1Exceed
		  Gauge
	}

	fibeAir4800OduPerfMonAirDayIdx OBJECT-TYPE
		SYNTAX  INTEGER (1..96)
		ACCESS  read-only
		STATUS  mandatory
		DESCRIPTION
		"This table is indexed per Day number. Each Day
		is of 15 minutes and the oldest is 96."
	::= { fibeAir4800OduPerfMonAirDayEntry 1 }

	fibeAir4800OduPerfMonAirDayMinRSL OBJECT-TYPE
		SYNTAX  INTEGER (-100..0)
		ACCESS  read-only
		STATUS  mandatory
		DESCRIPTION
		"Current Min Received Level Reference per Day."
		::= { fibeAir4800OduPerfMonAirDayEntry 2 }		

	fibeAir4800OduPerfMonAirDayMaxRSL OBJECT-TYPE
		SYNTAX  INTEGER (-100..0)
		ACCESS  read-only
		STATUS  mandatory
		DESCRIPTION
		"Current Max Received Level Reference per Day."
		::= { fibeAir4800OduPerfMonAirDayEntry 3 }

	fibeAir4800OduPerfMonAirDayRSLThresh1Exceed OBJECT-TYPE
		SYNTAX  Gauge (0..86400)
		ACCESS  read-only
		STATUS  mandatory
		DESCRIPTION
		"Number of seconds Receive Signal Level exceeded the RSL1 threshold per Day."
		::= { fibeAir4800OduPerfMonAirDayEntry 4 }

	fibeAir4800OduPerfMonAirDayRSLThresh2Exceed OBJECT-TYPE
		SYNTAX  Gauge (0..86400)
		ACCESS  read-only
		STATUS  mandatory
		DESCRIPTION
		"Number of seconds Receive Signal Level exceeded the RSL2 threshold per Day."
		::= { fibeAir4800OduPerfMonAirDayEntry 5 }

	fibeAir4800OduPerfMonAirDayMinTSL OBJECT-TYPE
		SYNTAX  INTEGER (-10..25)
		ACCESS  read-only
		STATUS  mandatory
		DESCRIPTION
		"Current Min Transmit Signal Level per Day."
		::= { fibeAir4800OduPerfMonAirDayEntry 6 }

	fibeAir4800OduPerfMonAirDayMaxTSL OBJECT-TYPE
		SYNTAX  INTEGER (-10..25)
		ACCESS  read-only
		STATUS  mandatory
		DESCRIPTION
		"Current Max Transmit Signal Level per Day."
		::= { fibeAir4800OduPerfMonAirDayEntry 7 }

	fibeAir4800OduPerfMonAirDayTSLThresh1Exceed OBJECT-TYPE
		SYNTAX  Gauge (0..86400)
		ACCESS  read-only
		STATUS  mandatory
		DESCRIPTION
		"Number of seconds Transmit Signal Level exceeded the TSL1 threshold per Day."
		::= { fibeAir4800OduPerfMonAirDayEntry 8 }

	fibeAir4800OduPerfMonAirDayBBERThresh1Exceed OBJECT-TYPE
		SYNTAX  Gauge (0..86400)
		ACCESS  read-only
		STATUS  mandatory
		DESCRIPTION
		"Number of seconds Background Block Error Ratio exceeded the BBER1 threshold per Day."
		::= { fibeAir4800OduPerfMonAirDayEntry 9 }

	-- ###########################################################
	--                      PM Eth Current Table
	-- ###########################################################

	fibeAir4800OduPerfMonEthCurrTable OBJECT-TYPE
		SYNTAX  SEQUENCE OF FibeAir4800OduPerfMonEthCurrEntry
		ACCESS  not-accessible
		STATUS  mandatory
		DESCRIPTION
		"This table defines/keeps the ethernet counters of the current 15 min interval."
		::= { fibeAir4800OduPerfMon 7 }

	fibeAir4800OduPerfMonEthCurrEntry OBJECT-TYPE
		SYNTAX  FibeAir4800OduPerfMonEthCurrEntry
		ACCESS  not-accessible
		STATUS  mandatory
		DESCRIPTION
		"This is an entry in the Current Interval Table."
		INDEX {ifIndex }
		::= { fibeAir4800OduPerfMonEthCurrTable 1 }

	FibeAir4800OduPerfMonEthCurrEntry ::= SEQUENCE {
		fibeAir4800OduPerfMonEthCurrRxMBytes
	      Gauge,
   		fibeAir4800OduPerfMonEthCurrTxMBytes
	      Gauge,
		fibeAir4800OduPerfMonEthCurrEthCapacityThreshUnder
	      Gauge,
		fibeAir4800OduPerfMonEthCurrHighTrafficThreshExceed
	      Gauge,
		fibeAir4800OduPerfMonEthCurrActiveSeconds
	      Gauge
	}

	fibeAir4800OduPerfMonEthCurrRxMBytes OBJECT-TYPE
		SYNTAX  Gauge (0..11250)
		ACCESS  read-only
		STATUS  mandatory
		DESCRIPTION
		"Current RX Mega Bytes starting from the present 15 minutes period."
		::= { fibeAir4800OduPerfMonEthCurrEntry 1 }		

	fibeAir4800OduPerfMonEthCurrTxMBytes OBJECT-TYPE
		SYNTAX  Gauge (0..11250)
		ACCESS  read-only
		STATUS  mandatory
		DESCRIPTION
		"Current Transmit Mega Bytes starting from the present 15 minutes period."
		::= { fibeAir4800OduPerfMonEthCurrEntry 2 }	
		
	fibeAir4800OduPerfMonEthCurrEthCapacityThreshUnder OBJECT-TYPE
		SYNTAX  Gauge (0..900)
		ACCESS  read-only
		STATUS  mandatory
		DESCRIPTION
		"The number of times throughput was below threshold in the present 15 minutes period.
		Relevant for point to point systems."
		::= { fibeAir4800OduPerfMonEthCurrEntry 3 }
	
	fibeAir4800OduPerfMonEthCurrHighTrafficThreshExceed OBJECT-TYPE
		SYNTAX  Gauge (0..900)
		ACCESS  read-only
		STATUS  mandatory
		DESCRIPTION
		"The number of times actual traffic was above threshold in the present 15 minutes period."
		::= { fibeAir4800OduPerfMonEthCurrEntry 4 }
		
	fibeAir4800OduPerfMonEthCurrActiveSeconds OBJECT-TYPE
		SYNTAX  Gauge (0..900)
		ACCESS  read-only
		STATUS  mandatory
		DESCRIPTION
		"The number of seconds in which RPL Ethernet swervice was not blocked in the present 15 minutes period."
		::= { fibeAir4800OduPerfMonEthCurrEntry 5 }	

	-- ###########################################################
	--                      PM Eth Interval Table
	-- ###########################################################	

	fibeAir4800OduPerfMonEthIntervalTable OBJECT-TYPE
		SYNTAX  SEQUENCE OF FibeAir4800OduPerfMonEthIntervalEntry
		ACCESS  not-accessible
		STATUS  mandatory
		DESCRIPTION
		"This table defines/keeps the ethernet counters of the last day (in resolution of 15 min intervals)."
		::= { fibeAir4800OduPerfMon 8 }

	fibeAir4800OduPerfMonEthIntervalEntry OBJECT-TYPE
		SYNTAX  FibeAir4800OduPerfMonEthIntervalEntry
		ACCESS  not-accessible
		STATUS  mandatory
		DESCRIPTION
		"This is an entry in the Interval Table."
		INDEX {ifIndex, fibeAir4800OduPerfMonEthIntervalIdx }
		::= { fibeAir4800OduPerfMonEthIntervalTable 1 }

	FibeAir4800OduPerfMonEthIntervalEntry ::= SEQUENCE {
		fibeAir4800OduPerfMonEthIntervalIdx
	      INTEGER,
		fibeAir4800OduPerfMonEthIntervalRxMBytes
	      Gauge,
   		fibeAir4800OduPerfMonEthIntervalTxMBytes
	      Gauge,
		fibeAir4800OduPerfMonEthIntervalEthCapacityThreshUnder
	      Gauge,
		fibeAir4800OduPerfMonEthIntervalHighTrafficThreshExceed
	      Gauge,
		fibeAir4800OduPerfMonEthIntervalActiveSeconds
	      Gauge
	}

	fibeAir4800OduPerfMonEthIntervalIdx OBJECT-TYPE
		SYNTAX  INTEGER (1..96)
		ACCESS  read-only
		STATUS  mandatory
		DESCRIPTION
		"This table is indexed per interval number. Each interval
		is of 15 minutes and the oldest is 96."
		::= { fibeAir4800OduPerfMonEthIntervalEntry 1 }

	fibeAir4800OduPerfMonEthIntervalRxMBytes OBJECT-TYPE
		SYNTAX  Gauge (0..11250)
		ACCESS  read-only
		STATUS  mandatory
		DESCRIPTION
		"Current RX Mega Bytes per interval."
		::= { fibeAir4800OduPerfMonEthIntervalEntry 2 }		

	fibeAir4800OduPerfMonEthIntervalTxMBytes OBJECT-TYPE
		SYNTAX  Gauge (0..11250)
		ACCESS  read-only
		STATUS  mandatory
		DESCRIPTION
		"Current Transmit Mega Bytes per interval."
		::= { fibeAir4800OduPerfMonEthIntervalEntry 3 }	
		
	fibeAir4800OduPerfMonEthIntervalEthCapacityThreshUnder OBJECT-TYPE
		SYNTAX  Gauge (0..900)
		ACCESS  read-only
		STATUS  mandatory
		DESCRIPTION
		"The number of times throughput was below threshold in the each interval.
		Relevant for point to point systems."
		::= { fibeAir4800OduPerfMonEthIntervalEntry 4 }	
		
	fibeAir4800OduPerfMonEthIntervalHighTrafficThreshExceed OBJECT-TYPE
		SYNTAX  Gauge (0..900)
		ACCESS  read-only
		STATUS  mandatory
		DESCRIPTION
		"The number of times actual traffic was above threshold in the each interval."
		::= { fibeAir4800OduPerfMonEthIntervalEntry 5 }	
		
	fibeAir4800OduPerfMonEthIntervalActiveSeconds OBJECT-TYPE
		SYNTAX  Gauge (0..900)
		ACCESS  read-only
		STATUS  mandatory
		DESCRIPTION
		"The number of seconds in which RPL Ethernet service was not blocked in the each interval."
		::= { fibeAir4800OduPerfMonEthIntervalEntry 6 }	

	-- ###########################################################
	--                      PM Eth Day Table
	-- ###########################################################	

	fibeAir4800OduPerfMonEthDayTable OBJECT-TYPE
		SYNTAX  SEQUENCE OF FibeAir4800OduPerfMonEthDayEntry
		ACCESS  not-accessible
		STATUS  mandatory
		DESCRIPTION
		"This table defines/keeps the ethernet counters of the last month (in resolution of days)."
		::= { fibeAir4800OduPerfMon 9 }

	fibeAir4800OduPerfMonEthDayEntry OBJECT-TYPE
		SYNTAX  FibeAir4800OduPerfMonEthDayEntry
		ACCESS  not-accessible
		STATUS  mandatory
		DESCRIPTION
		"This is an entry in the Days Table."
		INDEX {ifIndex, fibeAir4800OduPerfMonEthDayIdx }
		::= { fibeAir4800OduPerfMonEthDayTable 1 }

	FibeAir4800OduPerfMonEthDayEntry ::= SEQUENCE {
		fibeAir4800OduPerfMonEthDayIdx
	      INTEGER,
		fibeAir4800OduPerfMonEthDayRxMBytes
	      Gauge,
   		fibeAir4800OduPerfMonEthDayTxMBytes
	      Gauge,
		fibeAir4800OduPerfMonEthDayEthCapacityThreshUnder
	      Gauge,
		fibeAir4800OduPerfMonEthDayHighTrafficThreshExceed
	      Gauge,
		fibeAir4800OduPerfMonEthDayActiveSeconds
	      Gauge
	}

	fibeAir4800OduPerfMonEthDayIdx OBJECT-TYPE
		SYNTAX  INTEGER (1..96)
		ACCESS  read-only
		STATUS  mandatory
		DESCRIPTION
		"This table is indexed per Day number. Each interval
		is of 15 minutes and the oldest is 96."
		::= { fibeAir4800OduPerfMonEthDayEntry 1 }

	fibeAir4800OduPerfMonEthDayRxMBytes OBJECT-TYPE
		SYNTAX  Gauge (0..1080000)
		ACCESS  read-only
		STATUS  mandatory
		DESCRIPTION
		"Current RX Mega Bytes per day."
		::= { fibeAir4800OduPerfMonEthDayEntry 2 }		

	fibeAir4800OduPerfMonEthDayTxMBytes OBJECT-TYPE
		SYNTAX  Gauge (0..1080000)
		ACCESS  read-only
		STATUS  mandatory
		DESCRIPTION
		"Current Transmit Mega Bytes per day."
		::= { fibeAir4800OduPerfMonEthDayEntry 3 }
		
	fibeAir4800OduPerfMonEthDayEthCapacityThreshUnder OBJECT-TYPE
		SYNTAX  Gauge (0..86400)
		ACCESS  read-only
		STATUS  mandatory
		DESCRIPTION
		"The number of times throughput was below threshold each day.
		Relevant for point to point systems."
		::= { fibeAir4800OduPerfMonEthDayEntry 4 }
		
	fibeAir4800OduPerfMonEthDayHighTrafficThreshExceed OBJECT-TYPE
		SYNTAX  Gauge (0..86400)
		ACCESS  read-only
		STATUS  mandatory
		DESCRIPTION
		"The number of times actual traffic was above threshold each day."
		::= { fibeAir4800OduPerfMonEthDayEntry 5 }
		
	fibeAir4800OduPerfMonEthDayActiveSeconds OBJECT-TYPE
		SYNTAX  Gauge (0..86400)
		ACCESS  read-only
		STATUS  mandatory
		DESCRIPTION
		"The number of seconds in which RPL Ethernet service was not blocked each day."
		::= { fibeAir4800OduPerfMonEthDayEntry 6 }	
		

	-- ###########################################################
	--                      PM Tdm Current Table
	-- ###########################################################

	fibeAir4800OduPerfMonTdmCurrTable OBJECT-TYPE
		SYNTAX  SEQUENCE OF FibeAir4800OduPerfMonTdmCurrEntry
		ACCESS  not-accessible
		STATUS  mandatory
		DESCRIPTION
		"This table defines/keeps the TDM counters of the current 15 min interval."
		::= { fibeAir4800OduPerfMon 10 }

	fibeAir4800OduPerfMonTdmCurrEntry OBJECT-TYPE
		SYNTAX  FibeAir4800OduPerfMonTdmCurrEntry
		ACCESS  not-accessible
		STATUS  mandatory
		DESCRIPTION
		"This is an entry in the Current Interval Table."
		INDEX {ifIndex }
		::= { fibeAir4800OduPerfMonTdmCurrTable 1 }

	FibeAir4800OduPerfMonTdmCurrEntry ::= SEQUENCE {
		fibeAir4800OduPerfMonTdmCurrActiveSeconds
	      Gauge
	}

	fibeAir4800OduPerfMonTdmCurrActiveSeconds OBJECT-TYPE
		SYNTAX  Gauge (0..900)
		ACCESS  read-only
		STATUS  mandatory
		DESCRIPTION
		"Parameter indicating whether the TDM service was active.
		 Under TDM backup link, the parameter indicates whether 
		 the backup link was active."
		::= { fibeAir4800OduPerfMonTdmCurrEntry 1 }
		
	-- ###########################################################
	--                      PM Tdm Interval Table
	-- ###########################################################	

	fibeAir4800OduPerfMonTdmIntervalTable OBJECT-TYPE
		SYNTAX  SEQUENCE OF FibeAir4800OduPerfMonTdmIntervalEntry
		ACCESS  not-accessible
		STATUS  mandatory
		DESCRIPTION
		"This table defines/keeps the TDM counters of the last day (in resolution of 15 min intervals)."
		::= { fibeAir4800OduPerfMon 11 }

	fibeAir4800OduPerfMonTdmIntervalEntry OBJECT-TYPE
		SYNTAX  FibeAir4800OduPerfMonTdmIntervalEntry
		ACCESS  not-accessible
		STATUS  mandatory
		DESCRIPTION
		"This is an entry in the Interval Table."
		INDEX {ifIndex, fibeAir4800OduPerfMonTdmIntervalIdx }
		::= { fibeAir4800OduPerfMonTdmIntervalTable 1 }

	FibeAir4800OduPerfMonTdmIntervalEntry ::= SEQUENCE {
		fibeAir4800OduPerfMonTdmIntervalIdx
	      INTEGER,
		fibeAir4800OduPerfMonTdmIntervalActiveSeconds
	      Gauge
	}

	fibeAir4800OduPerfMonTdmIntervalIdx OBJECT-TYPE
		SYNTAX  INTEGER (1..96)
		ACCESS  read-only
		STATUS  mandatory
		DESCRIPTION
		"This table is indexed per interval number. Each interval
		is of 15 minutes and the oldest is 96."
		::= { fibeAir4800OduPerfMonTdmIntervalEntry 1 }

	fibeAir4800OduPerfMonTdmIntervalActiveSeconds OBJECT-TYPE
		SYNTAX  Gauge (0..900)
		ACCESS  read-only
		STATUS  mandatory
		DESCRIPTION
		"Parameter indicating whether the TDM service was active.
		Under TDM backup link, the parameter indicates whether 
		the backup link was active."
		::= { fibeAir4800OduPerfMonTdmIntervalEntry 2 }		

	-- ###########################################################
	--                      PM Tdm Day Table
	-- ###########################################################	

	fibeAir4800OduPerfMonTdmDayTable OBJECT-TYPE
		SYNTAX  SEQUENCE OF FibeAir4800OduPerfMonTdmDayEntry
		ACCESS  not-accessible
		STATUS  mandatory
		DESCRIPTION
		"This table defines/keeps the TDM counters of the last month (in resolution of days)."
		::= { fibeAir4800OduPerfMon 12 }

	fibeAir4800OduPerfMonTdmDayEntry OBJECT-TYPE
		SYNTAX  FibeAir4800OduPerfMonTdmDayEntry
		ACCESS  not-accessible
		STATUS  mandatory
		DESCRIPTION
		"This is an entry in the Days Table."
		INDEX {ifIndex, fibeAir4800OduPerfMonTdmDayIdx }
		::= { fibeAir4800OduPerfMonTdmDayTable 1 }

	FibeAir4800OduPerfMonTdmDayEntry ::= SEQUENCE {
		fibeAir4800OduPerfMonTdmDayIdx
	      INTEGER,
		fibeAir4800OduPerfMonTdmDayActiveSeconds
	      Gauge
	}

	fibeAir4800OduPerfMonTdmDayIdx OBJECT-TYPE
		SYNTAX  INTEGER (1..96)
		ACCESS  read-only
		STATUS  mandatory
		DESCRIPTION
		"This table is indexed per Day number. Each interval
		is of 15 minutes and the oldest is 96."
		::= { fibeAir4800OduPerfMonTdmDayEntry 1 }

	fibeAir4800OduPerfMonTdmDayActiveSeconds OBJECT-TYPE
		SYNTAX  Gauge (0..86400)
		ACCESS  read-only
		STATUS  mandatory
		DESCRIPTION
		"Parameter indicating whether the TDM service was active.
		Under TDM backup link, the parameter indicates whether 
		the backup link was active."
		::= { fibeAir4800OduPerfMonTdmDayEntry 2 }

	-- ###########################################################
	--                      PM Configuration thresholds
	-- ###########################################################	

	fibeAir4800OduPerfMonTxThresh1 OBJECT-TYPE
		SYNTAX  INTEGER (-10..25)
		ACCESS  read-write
		STATUS  mandatory
		DESCRIPTION
		"When the Transmit power exceeds this threshold, a performance monitoring TSL1 counter is incremented."
		::= { fibeAir4800OduPerfMon 20 }

	fibeAir4800OduPerfMonRxThresh1 OBJECT-TYPE
		SYNTAX  INTEGER (-100..0)
		ACCESS  read-write
		STATUS  mandatory
		DESCRIPTION
		"When the RX power exceeds this threshold, a performance monitoring RSL1 counter is incremented."
		::= { fibeAir4800OduPerfMon 21 }

	fibeAir4800OduPerfMonRxThresh2 OBJECT-TYPE
		SYNTAX  INTEGER (-100..0)
		ACCESS  read-write
		STATUS  mandatory
		DESCRIPTION
		"When the RX power exceeds this threshold, a performance monitoring RSL2 counter is incremented."
		::= { fibeAir4800OduPerfMon 22 }

	fibeAir4800OduPerfMonBBERThresh1 OBJECT-TYPE
		SYNTAX  INTEGER (0..500)
		ACCESS  read-write
		STATUS  mandatory
		DESCRIPTION
		"When the BBER exceeds this threshold, a performance monitoring BBER counter is incremented. The units are 1/10 of a percent."
		::= { fibeAir4800OduPerfMon 23 }
		
	fibeAir4800OduPerfMonEthCapacityThreshKbps OBJECT-TYPE
		SYNTAX  INTEGER (0..100000)
		ACCESS  read-write
		STATUS  mandatory
		DESCRIPTION
		"When the current throughput is below this threshold, the corresponding counter is incremented"
		::= { fibeAir4800OduPerfMon 24 }
		
	fibeAir4800OduPerfMonHighTrafficThreshKbps OBJECT-TYPE
		SYNTAX  INTEGER (0..100000)
		ACCESS  read-write
		STATUS  mandatory
		DESCRIPTION
		"When the current traffic is above this threshold, then corresponding counter is incremented."
		::= { fibeAir4800OduPerfMon 25 }
	
	-- ###########################################################
	--                      ODU SNMP Agent
	-- ###########################################################

	fibeAir4800OduAgent OBJECT IDENTIFIER ::= { fibeAir4800Odu 7 }

	fibeAir4800OduAgnGeneral  OBJECT IDENTIFIER ::= { fibeAir4800OduAgent 1 }

	fibeAir4800OduAgnGenAddTrapExt OBJECT-TYPE
		SYNTAX  INTEGER {
			no(1),
			yes(2)
		}
		ACCESS  read-write
		STATUS  mandatory
		DESCRIPTION
		"If 'yes' is chosen, the ifIndex, Unit, Severity, Time_T and Alarm Id from the fibeAir4800OduAgnCurrAlarmTable
		will be bind to the end of each private trap."		
		::= { fibeAir4800OduAgnGeneral 1 }

	fibeAir4800OduAgnGenSetMode OBJECT-TYPE
		SYNTAX  INTEGER{
			enabled(1),
			disabledSWU(2),
			disabledSpectrumAnalysis(3),
			disabledBeforeResetAfterSWU(4),
			disabledUpdateConfigurationFiles(5),
			disabledSWK(6)
			}
		ACCESS  read-write
		STATUS  mandatory
		DESCRIPTION
		"This parameter is reserved to the element manager provided with the product."		
		::= { fibeAir4800OduAgnGeneral 2 }
		
	fibeAir4800OduAgnGenLocalConnectionMode OBJECT-TYPE
		SYNTAX  INTEGER{
			readWrite(1),
			readOnly(2)
			}
		ACCESS  read-write
		STATUS  mandatory
		DESCRIPTION
		"Local Connection (Broadcast) Configuration Mode. Options are:
		1 - SNMP Read-Write,
		2 - SNMP Read-Only."		
		::= { fibeAir4800OduAgnGeneral 3 }	

	fibeAir4800OduAgnNTPCfg  OBJECT IDENTIFIER ::= { fibeAir4800OduAgent 2 }	

	fibeAir4800OduAgnNTPCfgTimeServerIP OBJECT-TYPE
		SYNTAX  IpAddress
		ACCESS  read-write
		STATUS  mandatory
		DESCRIPTION
		"IP address of the server from which the current time is loaded."
		::= { fibeAir4800OduAgnNTPCfg 1 }

	fibeAir4800OduAgnNTPCfgTimeOffsetFromUTC OBJECT-TYPE
		SYNTAX  INTEGER (-1440..1440)
		ACCESS  read-write
		STATUS  mandatory
		DESCRIPTION
		"Offset from Coordinated Universal Time (minutes). Possible values: -1440..1440."
		::= { fibeAir4800OduAgnNTPCfg 2 }

	fibeAir4800OduAgnRealTimeAndDate OBJECT-TYPE
		SYNTAX OCTET STRING(SIZE(8))
		ACCESS  read-write
		STATUS mandatory
		DESCRIPTION
		"This parameter specifies the real time and date
        Format 'YYYY-MM-DD,HH:MM:SS' (Hexadecimal).        
		A date-time specification:

        field  octets  contents                  range
        -----  ------  --------                  -----
          1      1-2   year                      0..65536
          2       3    month                     1..12
          3       4    day                       1..31
          4       5    hour                      0..23
          5       6    minutes                   0..59
    	  6       7    seconds                   0..60
                       (use 60 for leap-second)
          7       8    deci-seconds              0..9
        
        For example, Tuesday May 26, 1992 at 1:30:15 PM EDT
        would be displayed as:	07 c8 05 1a 0d 1e 0f 00
							  ( 1992 -5 -26,13:30:15 )"
		::= { fibeAir4800OduAgnNTPCfg 3 }

	fibeAir4800OduAdmNTPCfgTimeServerIPv6 OBJECT-TYPE
		SYNTAX  DisplayString
		ACCESS  read-write
		STATUS  mandatory
		DESCRIPTION
		"IPv6 address of the server from which the current time is loaded."
		::= { fibeAir4800OduAgnNTPCfg 4 }
		
	fibeAir4800OduAgnCurrAlarm OBJECT IDENTIFIER ::= { fibeAir4800OduAgent 3 }

	fibeAir4800OduAgnCurrAlarmLastChange OBJECT-TYPE
		SYNTAX INTEGER
		ACCESS  read-only
		STATUS mandatory
		DESCRIPTION
		"This counter is initialized to 0 after a device reset and is incremented upon each change in the fibeAir4800OduAgnCurrAlarmTable
		(either an addition or removal of an entry)."
		::= { fibeAir4800OduAgnCurrAlarm 1 }  

	-- ###########################################################
	--                      Active Alarm Table
	-- ###########################################################	

	fibeAir4800OduAgnCurrAlarmTable  OBJECT-TYPE
       	SYNTAX  SEQUENCE OF FibeAir4800OduAgnCurrAlarmEntry
       	ACCESS  not-accessible
       	STATUS  mandatory
       	DESCRIPTION
       	"This table includes the currently active alarms. When a RAISED trap is 
       	sent, an alarm entry is added to the table. When a CLEAR trap is sent, 
       	the entry is removed."
      	::= { fibeAir4800OduAgnCurrAlarm 2 } 

	fibeAir4800OduAgnCurrAlarmEntry OBJECT-TYPE
		SYNTAX  FibeAir4800OduAgnCurrAlarmEntry
		ACCESS  not-accessible
		STATUS  mandatory
		DESCRIPTION
		"Entry containing the details of a currently RAISED trap."
		INDEX { fibeAir4800OduAgnCurrAlarmCounter }
		::= { fibeAir4800OduAgnCurrAlarmTable  1 }

	FibeAir4800OduAgnCurrAlarmEntry ::=	SEQUENCE {
   		fibeAir4800OduAgnCurrAlarmCounter
			INTEGER,
		fibeAir4800OduAgnCurrAlarmSeverity
			INTEGER,
		fibeAir4800OduAgnCurrAlarmId
			INTEGER,
   		fibeAir4800OduAgnCurrAlarmIfIndex
			INTEGER,
		fibeAir4800OduAgnCurrAlarmUnit
			INTEGER,
   		fibeAir4800OduAgnCurrAlarmTrapID
			INTEGER,
		fibeAir4800OduAgnCurrAlarmTimeT
			INTEGER,
		fibeAir4800OduAgnCurrAlarmText
			DisplayString
	} 

	fibeAir4800OduAgnCurrAlarmCounter OBJECT-TYPE
		SYNTAX  INTEGER
		ACCESS  read-only
		STATUS  mandatory
		DESCRIPTION
		"A running counter of active alarms. The counter is incremented for every new RAISED trap.
		It is cleared after a device reset."
		::= { fibeAir4800OduAgnCurrAlarmEntry 1 }

	fibeAir4800OduAgnCurrAlarmSeverity OBJECT-TYPE
		SYNTAX  INTEGER	{
			event		(1),
			normal		(2),
			warning		(4),
			minor		(8),
			major		(16),
			critical	(32)
			}
		ACCESS  read-only
		STATUS  mandatory
		DESCRIPTION
		"Current Alarm severity."
		::= { fibeAir4800OduAgnCurrAlarmEntry 2 }

	fibeAir4800OduAgnCurrAlarmId OBJECT-TYPE
		SYNTAX  INTEGER
		ACCESS  read-only
		STATUS  mandatory
		DESCRIPTION
		"Unique Alarm Identifier (combines alarm type and interface). The same AlarmId is used for RAISED and CLEARED alarms."
		::= { fibeAir4800OduAgnCurrAlarmEntry 3 }

	fibeAir4800OduAgnCurrAlarmIfIndex OBJECT-TYPE
		SYNTAX  INTEGER
		ACCESS  read-only
		STATUS  mandatory
		DESCRIPTION
		"Interface Index where the alarm occurred. Alarms that are
  		not associated with a specific interface will have the following value: 65535."
		::= { fibeAir4800OduAgnCurrAlarmEntry 4 }	

	fibeAir4800OduAgnCurrAlarmUnit OBJECT-TYPE
		SYNTAX  INTEGER {
			idu(1),
			odu(2)
		}
		ACCESS  read-only
		STATUS  mandatory
		DESCRIPTION
		"Unit associated with the alarm."
		::= { fibeAir4800OduAgnCurrAlarmEntry 5 }

	fibeAir4800OduAgnCurrAlarmTrapID OBJECT-TYPE
		SYNTAX  INTEGER 
		ACCESS  read-only
		STATUS  mandatory
		DESCRIPTION
		"ID of the raised trap that was sent when this alarm was raised."
		::= { fibeAir4800OduAgnCurrAlarmEntry 6 }

	fibeAir4800OduAgnCurrAlarmTimeT OBJECT-TYPE
		SYNTAX  INTEGER
		ACCESS  read-only
		STATUS  mandatory
		DESCRIPTION
		"Timestamp of this alarm. This number is in seconds from Midnight January 1st, 1970."
		::= { fibeAir4800OduAgnCurrAlarmEntry 7 }

	fibeAir4800OduAgnCurrAlarmText OBJECT-TYPE
		SYNTAX  DisplayString
		ACCESS  read-only
		STATUS  mandatory
		DESCRIPTION
		"Alarm display text (same as the text in the sent trap)."
		::= { fibeAir4800OduAgnCurrAlarmEntry 8 }


	fibeAir4800OduAgnLastEvents OBJECT IDENTIFIER ::= { fibeAir4800OduAgent 4 }

	fibeAir4800OduAgnLastEventsNumber OBJECT-TYPE
		SYNTAX INTEGER
		ACCESS  read-only
		STATUS mandatory
		DESCRIPTION
		"This counter indicates the size of the fibeAir4800OduAgnLastEventsTable"
		::= { fibeAir4800OduAgnLastEvents 1 }  

	-- ###########################################################
	--                      Last Events Table
	-- ###########################################################	

	fibeAir4800OduAgnLastEventsTable OBJECT-TYPE
       	SYNTAX  SEQUENCE OF FibeAir4800OduAgnLastEventsEntry
       	ACCESS  not-accessible
       	STATUS  mandatory
       	DESCRIPTION
       	"This table includes the last events. When a trap is 
       	sent, an event entry is added to the table."
      	::= { fibeAir4800OduAgnLastEvents 2 } 

	fibeAir4800OduAgnLastEventsEntry OBJECT-TYPE
		SYNTAX  FibeAir4800OduAgnLastEventsEntry
		ACCESS  not-accessible
		STATUS  mandatory
		DESCRIPTION
		"Entry containing the details of last traps."
		INDEX { fibeAir4800OduAgnLastEventsIndex }
		::= { fibeAir4800OduAgnLastEventsTable  1 }

	FibeAir4800OduAgnLastEventsEntry ::= SEQUENCE {
   		fibeAir4800OduAgnLastEventsIndex
			INTEGER,
		fibeAir4800OduAgnLastEventsSeverity
			INTEGER,
   		fibeAir4800OduAgnLastEventsIfIndex
			INTEGER,
		fibeAir4800OduAgnLastEventsTimeT
			INTEGER,
		fibeAir4800OduAgnLastEventsText
			DisplayString
	} 

	fibeAir4800OduAgnLastEventsIndex OBJECT-TYPE
		SYNTAX  INTEGER
		ACCESS  read-only
		STATUS  mandatory
		DESCRIPTION
		"The index of the table"
		::= { fibeAir4800OduAgnLastEventsEntry 1 }

	fibeAir4800OduAgnLastEventsSeverity OBJECT-TYPE
		SYNTAX  INTEGER	{
			event		(1),
			normal		(2),
			warning		(4),
			minor		(8),
			major		(16),
			critical	(32)
			}
		ACCESS  read-only
		STATUS  mandatory
		DESCRIPTION
		"Current Trap severity."
		::= { fibeAir4800OduAgnLastEventsEntry 2 }

	fibeAir4800OduAgnLastEventsIfIndex OBJECT-TYPE
		SYNTAX  INTEGER
		ACCESS  read-only
		STATUS  mandatory
		DESCRIPTION
		"Interface Index where the event occurred. Traps that are
  		not associated with a specific interface will have the following value: 65535."
		::= { fibeAir4800OduAgnLastEventsEntry 3 }	

	fibeAir4800OduAgnLastEventsTimeT OBJECT-TYPE
		SYNTAX  INTEGER
		ACCESS  read-only
		STATUS  mandatory
		DESCRIPTION
		"Timestamp of this trap. This number is in seconds from Midnight January 1st, 1970."
		::= { fibeAir4800OduAgnLastEventsEntry 4 }

	fibeAir4800OduAgnLastEventsText OBJECT-TYPE
		SYNTAX  DisplayString
		ACCESS  read-only
		STATUS  mandatory
		DESCRIPTION
		"Trap display text (same as the text in the sent trap)."
		::= { fibeAir4800OduAgnLastEventsEntry 5 }


	-- ###########################################################
	--                      ODU Agent Users Table
	-- ###########################################################

	fibeAir4800OduAgnUsersTable OBJECT-TYPE
		SYNTAX  SEQUENCE OF FibeAir4800OduAgnUsersEntry
		ACCESS  not-accessible
		STATUS  mandatory
		DESCRIPTION
		"SNMP users table. Each user is defined by name, password and profile."
		::= { fibeAir4800OduAgent 5 }

	fibeAir4800OduAgnUsersEntry OBJECT-TYPE
		SYNTAX  FibeAir4800OduAgnUsersEntry
		ACCESS  not-accessible
		STATUS  mandatory
		DESCRIPTION
		"SNMP users table entry."
		INDEX { fibeAir4800OduAgnUsersIndex }
		::= { fibeAir4800OduAgnUsersTable 1 }

	FibeAir4800OduAgnUsersEntry ::= SEQUENCE {
		fibeAir4800OduAgnUsersIndex
			INTEGER,
		fibeAir4800OduAgnUsersUserName
			DisplayString,
		fibeAir4800OduAgnUsersPassword
			DisplayString,
		fibeAir4800OduAgnUsersProfile
			INTEGER,
		fibeAir4800OduAgnUsersLastAccessTime
			INTEGER
		}

	fibeAir4800OduAgnUsersIndex OBJECT-TYPE
		SYNTAX  INTEGER
		ACCESS  read-only
		STATUS  mandatory
		DESCRIPTION
		"SNMP users table index."
		::= { fibeAir4800OduAgnUsersEntry 1 }
		
	fibeAir4800OduAgnUsersUserName OBJECT-TYPE
		SYNTAX  DisplayString
		ACCESS  read-write
		STATUS  mandatory
		DESCRIPTION
		"SNMP users user names."
		::= { fibeAir4800OduAgnUsersEntry 2 }
		
	fibeAir4800OduAgnUsersPassword OBJECT-TYPE
		SYNTAX  DisplayString
		ACCESS  read-write
		STATUS  mandatory
		DESCRIPTION
		"SNMP users passwords."
		::= { fibeAir4800OduAgnUsersEntry 3 }
		
	fibeAir4800OduAgnUsersProfile OBJECT-TYPE
		SYNTAX  INTEGER {
			disabled(1),
			readonly(2),
			readwrite(3)
			}
		ACCESS  read-write
		STATUS  mandatory
		DESCRIPTION
		"SNMP users profile (1=Disabled, 2=ReadOnly, 3=ReadWrite)."
		::= { fibeAir4800OduAgnUsersEntry 4 }
		
	fibeAir4800OduAgnUsersLastAccessTime OBJECT-TYPE
		SYNTAX  INTEGER
		ACCESS  read-only
		STATUS  mandatory
		DESCRIPTION
		"SNMP users last access time."
		::= { fibeAir4800OduAgnUsersEntry 5 }
		
	-- ###########################################################
	--                      IDU
	-- ###########################################################

	fibeAir4800Idu OBJECT IDENTIFIER ::= { fibeAir4800 2 }

	-- ###########################################################
	--                      IDU Admin
	-- ###########################################################

	fibeAir4800IduAdmin OBJECT IDENTIFIER ::= { fibeAir4800Idu 1 }

	fibeAir4800IduAdmProductType OBJECT-TYPE
		SYNTAX  DisplayString
		ACCESS  read-only
		STATUS  mandatory
		DESCRIPTION
		"IDU configuration description."
		::= { fibeAir4800IduAdmin 1 }

	fibeAir4800IduAdmHwRev OBJECT-TYPE
		SYNTAX  DisplayString
		ACCESS  read-only
		STATUS  mandatory
		DESCRIPTION
		"IDU Hardware Revision."
		::= { fibeAir4800IduAdmin 2 }

	fibeAir4800IduAdmSwRev OBJECT-TYPE
		SYNTAX  DisplayString
		ACCESS  read-only
		STATUS  mandatory
		DESCRIPTION
		"IDU Software Revision."
		::= { fibeAir4800IduAdmin 3 }

	fibeAir4800OduAdmNumOfExternalAlarmIn OBJECT-TYPE
		SYNTAX  INTEGER
		ACCESS  read-only
		STATUS  mandatory
		DESCRIPTION
		"Indicates the number of currently available External Alarm Inputs."
		::= { fibeAir4800IduAdmin 4 }	

	fibeAir4800OduAdmExternAlarmInTable   OBJECT-TYPE
        SYNTAX  SEQUENCE OF FibeAir4800OduAdmExternAlarmInEntry
        ACCESS  not-accessible
        STATUS  mandatory
        DESCRIPTION
        "This is the External Alarm Inputs table."
        ::= { fibeAir4800IduAdmin 5 }

	fibeAir4800OduAdmExternAlarmInEntry OBJECT-TYPE
        SYNTAX  FibeAir4800OduAdmExternAlarmInEntry
        ACCESS  not-accessible
        STATUS  mandatory
		DESCRIPTION
		"Entry containing the elements of a single External Alarm Input."
        INDEX { fibeAir4800OduAdmExternAlarmInIndex}
        ::= { fibeAir4800OduAdmExternAlarmInTable   1 }
	
	FibeAir4800OduAdmExternAlarmInEntry ::= SEQUENCE {
		fibeAir4800OduAdmExternAlarmInIndex
             INTEGER,		
		fibeAir4800OduAdmExternAlarmInText
       	     DisplayString,
		fibeAir4800OduAdmExternAlarmInAdminState
             INTEGER,
		fibeAir4800OduAdmExternAlarmInStatus
             INTEGER
		}	

	fibeAir4800OduAdmExternAlarmInIndex OBJECT-TYPE
        SYNTAX  INTEGER(1..2)
        ACCESS  read-only
   		STATUS  mandatory
        DESCRIPTION
        "This value indicates the index of the External Alarm Input entry."
        ::= { fibeAir4800OduAdmExternAlarmInEntry 1 }

	fibeAir4800OduAdmExternAlarmInText OBJECT-TYPE
		SYNTAX  DisplayString
        ACCESS  read-write
        STATUS  mandatory
        DESCRIPTION
        "This field describes the External Alarm Input. It is an optional string of no more than 64 characters,
		which will be used in the event being sent as a result of a change in the status of the External Alarm Input."
		DEFVAL {"Alarm Description"}
        ::= { fibeAir4800OduAdmExternAlarmInEntry 2 }

	fibeAir4800OduAdmExternAlarmInAdminState OBJECT-TYPE
		SYNTAX  INTEGER {
			enabled(1),
			disabled(2)
			}
        ACCESS  read-write
   		STATUS  mandatory
        DESCRIPTION
        "This value indicates if this External Alarm Input is enabled or disabled."
        ::= { fibeAir4800OduAdmExternAlarmInEntry 3 }

	fibeAir4800OduAdmExternAlarmInStatus OBJECT-TYPE
		SYNTAX  INTEGER {
			clear(1),
			alarm(2),
			unknown(3)
			}
        ACCESS  read-only
   		STATUS  mandatory
        DESCRIPTION
        "This value indicates the current status of the External Alarm Input."
        ::= { fibeAir4800OduAdmExternAlarmInEntry 4 }

	fibeAir4800IduAdmSN OBJECT-TYPE
        SYNTAX  DisplayString
		ACCESS  read-only
		STATUS  mandatory
        DESCRIPTION
        "IDU Serial Number"
        ::= { fibeAir4800IduAdmin 6 }

	fibeAir4800IduAdmIduDetectionMode OBJECT-TYPE
		SYNTAX  INTEGER {
			mandatoryDisabled(1),
			mandatoryEnabled(2),
			userDisabled(3),
			userEnabled(4)
			}
		ACCESS  read-write
		STATUS  mandatory
		DESCRIPTION
		"The parameter defines whether to send Ethernet frames to detect an IDU. 
		The valid writable values are: userDisabled (3), userEnabled (4). 
		A change requires a reset and is effective after reset."
		::= { fibeAir4800IduAdmin 7 }

	fibeAir4800IduAdmMountedTrunks   OBJECT-TYPE
	SYNTAX  INTEGER
		ACCESS  read-only
		STATUS  mandatory
		DESCRIPTION
		"Number of mounted trunks in the IDU "
		::= { fibeAir4800IduAdmin 8 }

	fibeAir4800IduAdmLicensedTrunks   OBJECT-TYPE
	SYNTAX  INTEGER
		ACCESS  read-only
		STATUS  mandatory
		DESCRIPTION
		"Number of Licensed Trunks in the IDU "
		::= { fibeAir4800IduAdmin 9 }

	fibeAir4800IduAdmVlanSupported   OBJECT-TYPE
	SYNTAX  INTEGER {
		notSupported(1),
		supported(2),
		supportedLimited(3)
		}
		ACCESS  read-only
		STATUS  mandatory
		DESCRIPTION
		"Identifies if the local IDU supports VLAN tag/untag"
		::= { fibeAir4800IduAdmin 10 }
	
	
	fibeAir4800IduAdmVlanEgressMode   OBJECT-TYPE
		SYNTAX  DisplayString
		ACCESS  read-write
		STATUS  mandatory
		DESCRIPTION
		"VLAN tag/untag egress values"
		::= { fibeAir4800IduAdmin 11 }

	fibeAir4800IduAdmVlanIngressMode   OBJECT-TYPE
		SYNTAX  DisplayString
		ACCESS  read-write
		STATUS  mandatory
		DESCRIPTION
		"VLAN tag/untag ingress values"
		::= { fibeAir4800IduAdmin 12 }

	fibeAir4800IduAdmVlanDefaultPortVIDs   OBJECT-TYPE
		SYNTAX  DisplayString
		ACCESS  read-write
		STATUS  mandatory
		DESCRIPTION
		"VLAN tag/untag default VLAN ids for each port - Right most digit is Vlan priority (0-6), other digits compose Vlan Id (1-4094)"
		::= { fibeAir4800IduAdmin 13 }

	fibeAir4800IduAdmVlanLan1UntaggedVIDs   OBJECT-TYPE
		SYNTAX  DisplayString
		ACCESS  read-write
		STATUS  mandatory
		DESCRIPTION
		"VLAN untagged VIDs for LAN1 port"
		::= { fibeAir4800IduAdmin 14 }
		
	fibeAir4800IduAdmVlanLan2UntaggedVIDs   OBJECT-TYPE
		SYNTAX  DisplayString
		ACCESS  read-write
		STATUS  mandatory
		DESCRIPTION
		"VLAN untagged VIDs for LAN2 port"
		::= { fibeAir4800IduAdmin 15 }

	fibeAir4800IduAdmVlanSfpUntaggedVIDs   OBJECT-TYPE
		SYNTAX  DisplayString
		ACCESS  read-write
		STATUS  mandatory
		DESCRIPTION
		"VLAN untagged VIDs for Sfp port"
		::= { fibeAir4800IduAdmin 16 }

	fibeAir4800IduAdmVlanLan1FilteredVIDs   OBJECT-TYPE
		SYNTAX  DisplayString
		ACCESS  read-write
		STATUS  mandatory
		DESCRIPTION
		"VLAN filtered VIDs for LAN1 port"
		::= { fibeAir4800IduAdmin 17 }
		
	fibeAir4800IduAdmVlanLan2FilteredVIDs   OBJECT-TYPE
		SYNTAX  DisplayString
		ACCESS  read-write
		STATUS  mandatory
		DESCRIPTION
		"VLAN filtered VIDs for LAN2 port"
		::= { fibeAir4800IduAdmin 18 }

	fibeAir4800IduAdmVlanSfpFilteredVIDs   OBJECT-TYPE
		SYNTAX  DisplayString
		ACCESS  read-write
		STATUS  mandatory
		DESCRIPTION
		"VLAN filtered VIDs for Sfp port"
		::= { fibeAir4800IduAdmin 19 }
		
	fibeAir4800IduAdmPortsConnection   OBJECT-TYPE
		SYNTAX  INTEGER
		ACCESS  read-write
		STATUS  mandatory
		DESCRIPTION
		"IDU ports connection bitmap.
		 bit 0 - LAN1-LAN2
		 bit 1 - SFP-LAN1
		 bit 2 - SFP-LAN2
		 bit values:
		 0 - ports are disconnected.
		 1 - ports are connected."
		::= { fibeAir4800IduAdmin 20 }

	fibeAir4800IduAdmVlanMode   OBJECT-TYPE
		SYNTAX  INTEGER {
			normal(1),
			membership(2)
		}
		ACCESS  read-write
		STATUS  mandatory
		DESCRIPTION
		"Local IDU Vlan Mode."
		::= { fibeAir4800IduAdmin 21 }

	fibeAir4800IduAdmVlanMembershipVIDs   OBJECT-TYPE
		SYNTAX  OCTET STRING
		ACCESS  read-write
		STATUS  mandatory
		DESCRIPTION
		"VLAN Membership VLAN IDs list."
		::= { fibeAir4800IduAdmin 22 }

	fibeAir4800IduAdmVlanMembershipPortsCode   OBJECT-TYPE
		SYNTAX  OCTET STRING
		ACCESS  read-write
		STATUS  mandatory
		DESCRIPTION
		"VLAN Membership ports code. Each value represent the relation (bitmap) 
		 Between the suitable VID to the IDU ports.
		 bit 0 - LAN1
		 bit 1 - LAN2
		 bit 2 - SFP
		 bit value 0 - not member of appropriate VID
		 bit value 1 - member of appropriate VID"
		::= { fibeAir4800IduAdmin 23 }

	fibeAir4800IduAdmVlanMembershipUntaggedHandle   OBJECT-TYPE
		SYNTAX  DisplayString
		ACCESS  read-write
		STATUS  mandatory
		DESCRIPTION
		"VLAN Membership Untagged frames handling.
		 The 3 values representing LAN1, LAN2 and SFP accordingly.
		 For each port, the optional values are:
		 1 - Discard
		 2 - Tag
		 3 - Leave Unmodified"
		::= { fibeAir4800IduAdmin 24 }

	fibeAir4800IduAdmVlanMembershipTagUntagged   OBJECT-TYPE
		SYNTAX  DisplayString
		ACCESS  read-write
		STATUS  mandatory
		DESCRIPTION
		"VLAN Membership Untagged frames tagging.
		 The 3 values representing LAN1, LAN2 and SFP accordingly.
		 The value on each port entry represent the tagging value which is built of:
		 VLAN ID & VLAN Priority."
		::= { fibeAir4800IduAdmin 25 }
				
	-- ###########################################################
	--                      IDU Service
	-- ###########################################################

	fibeAir4800IduService OBJECT IDENTIFIER ::= { fibeAir4800Idu 2 }

	fibeAir4800IduSrvDesiredTrunks OBJECT-TYPE
		SYNTAX  INTEGER
		ACCESS  read-write
		STATUS  mandatory
		DESCRIPTION
		"Required trunks bitmap. 
		Note that the number of possible trunks that can be configured may vary, based on the IDU hardware 
		configuration, the selected air interface rate and the range of the installation. 
		The provided Manager application enables the user to select only available configurations.
		A change is effective immediately if applied to a master unit and the link is in service mode."
		::= { fibeAir4800IduService 2 }

	fibeAir4800IduSrvServices OBJECT-TYPE
		SYNTAX  OBJECT IDENTIFIER
		ACCESS  read-only
		STATUS  mandatory
		DESCRIPTION
		"This parameter is reserved to the Manager application provided with the product."
		::= { fibeAir4800IduService 4 }

	fibeAir4800IduSrvActiveTrunks OBJECT-TYPE
		SYNTAX  INTEGER
		ACCESS  read-only
		STATUS  mandatory
		DESCRIPTION
		"A bitmap describing the currently open TDM trunks."
		::= { fibeAir4800IduService 6 }

	fibeAir4800IduSrvAvailableTrunks OBJECT-TYPE
		SYNTAX INTEGER
		ACCESS  read-only
		STATUS  mandatory
		DESCRIPTION
		"A bitmap describing the number of TDM trunks that can be opened in the current configuration.
		 The values take into account the IDU hardware configuration, the air rate and the installation range."
		::= { fibeAir4800IduService 8 }

	-- ###########################################################
	--                      IDU Possible Services Table (old)
	-- ###########################################################

	fibeAir4800IduSrvPossibleServicesTable OBJECT-TYPE
		SYNTAX  SEQUENCE OF FibeAir4800IduSrvPossibleServicesEntry
		ACCESS  not-accessible
		STATUS  mandatory
		DESCRIPTION
		"IDU Possible Services table."
		::= { fibeAir4800IduService 10 }

	fibeAir4800IduSrvPossibleServicesEntry OBJECT-TYPE
		SYNTAX  FibeAir4800IduSrvPossibleServicesEntry
		ACCESS  not-accessible
		STATUS  mandatory
		DESCRIPTION
		"IDU Services table entry."
		INDEX { fibeAir4800IduSrvPossibleServicesIndex }
		::= { fibeAir4800IduSrvPossibleServicesTable 1 }

	FibeAir4800IduSrvPossibleServicesEntry ::= SEQUENCE {
		fibeAir4800IduSrvPossibleServicesIndex
			INTEGER,
		fibeAir4800IduSrvPossibleTdmServices
			INTEGER,
		fibeAir4800IduSrvPossibleEthServices
			INTEGER,
		fibeAir4800IduSrvRemainingRate
			INTEGER,
		fibeAir4800IduSrvTrunkCost
			INTEGER
		}

	fibeAir4800IduSrvPossibleServicesIndex OBJECT-TYPE
		SYNTAX  INTEGER
		ACCESS  read-only
		STATUS  mandatory
		DESCRIPTION
		"Table index, Rate index of the air interface."
		::= { fibeAir4800IduSrvPossibleServicesEntry 1 }

	fibeAir4800IduSrvPossibleTdmServices OBJECT-TYPE
		SYNTAX  INTEGER
		ACCESS  read-only
		STATUS  deprecated
		DESCRIPTION
		"Deprecated parameter.
		A bitmap describing the TDM trunks that can be opened in the corresponding Air Rate."
		::= { fibeAir4800IduSrvPossibleServicesEntry 2 }

	fibeAir4800IduSrvPossibleEthServices OBJECT-TYPE
		SYNTAX  INTEGER
		ACCESS  read-only
		STATUS  deprecated
		DESCRIPTION
		"Deprecated parameter.
		This parameter describes if the Ethernet Service can be opened
		in the corresponding Air Rate. The valid values are: disabled (0), enabled (1)."
		::= { fibeAir4800IduSrvPossibleServicesEntry 3 }

	fibeAir4800IduSrvRemainingRate OBJECT-TYPE
		SYNTAX  INTEGER
		ACCESS  read-only
		STATUS  mandatory
		DESCRIPTION
		"Current Ethernet bandwidth in bps per air rate."
		::= { fibeAir4800IduSrvPossibleServicesEntry 4 }

	fibeAir4800IduSrvTrunkCost OBJECT-TYPE
		SYNTAX  INTEGER
		ACCESS  read-only
		STATUS  mandatory
		DESCRIPTION
		"Cost of the TDM Service in bps."
		::= { fibeAir4800IduSrvPossibleServicesEntry 5 }

	-- ###########################################################
	--                      IDU Possible Services Table (new)
	-- ###########################################################

	fibeAir4800IduSrvAvailServicesTable OBJECT-TYPE
		SYNTAX  SEQUENCE OF FibeAir4800IduSrvAvailServicesEntry
		ACCESS  not-accessible
		STATUS  mandatory
		DESCRIPTION
		"ODU Possible TDM Services table."
		::= { fibeAir4800IduService 11 }

	fibeAir4800IduSrvAvailServicesEntry OBJECT-TYPE
		SYNTAX  FibeAir4800IduSrvAvailServicesEntry
		ACCESS  not-accessible
		STATUS  mandatory
		DESCRIPTION
		"ODU TDM Services table entry."
		INDEX { fibeAir4800IduSrvAvailServicesIndex }
		::= { fibeAir4800IduSrvAvailServicesTable 1 }

	FibeAir4800IduSrvAvailServicesEntry ::= SEQUENCE {
		fibeAir4800IduSrvAvailServicesIndex
			INTEGER,
		fibeAir4800IduSrvAvailServicesState
			INTEGER,
		fibeAir4800IduSrvAvailServicesMinRateIdx
			INTEGER,
		fibeAir4800IduSrvAvailServicesMaxRateIdx
			INTEGER,
		fibeAir4800IduSrvAvailServicesReason
			INTEGER
		}

	fibeAir4800IduSrvAvailServicesIndex OBJECT-TYPE
		SYNTAX  INTEGER
		ACCESS  read-only
		STATUS  mandatory
		DESCRIPTION
		"Table index. The index is the bit mask of the TDM service."
		::= { fibeAir4800IduSrvAvailServicesEntry 1 }

	fibeAir4800IduSrvAvailServicesState OBJECT-TYPE
		SYNTAX  INTEGER {
			unavailable(1),
			available(2)
		}
		ACCESS  read-only
		STATUS  mandatory
		DESCRIPTION
		"Represents the TDM service availability."
		::= { fibeAir4800IduSrvAvailServicesEntry 2 }

	fibeAir4800IduSrvAvailServicesMinRateIdx OBJECT-TYPE
		SYNTAX  INTEGER 
		ACCESS  read-only
		STATUS  mandatory
		DESCRIPTION
		"Minimum rate index of the air interface which make the service possible."
		::= { fibeAir4800IduSrvAvailServicesEntry 3 }

	fibeAir4800IduSrvAvailServicesMaxRateIdx OBJECT-TYPE 
		SYNTAX  INTEGER 
		ACCESS  read-only
		STATUS  mandatory
		DESCRIPTION
		"Maximum rate index of the air interface which make the service possible."
		::= { fibeAir4800IduSrvAvailServicesEntry 4 }
		
	fibeAir4800IduSrvAvailServicesReason OBJECT-TYPE 
		SYNTAX  INTEGER {
				notApplicable(1),
				insufficientThroughput(2),
				notSupportedIDUHw(3),
				inconsistentLinkParams(4),
				improperExtPulseType(5),
				incompatibleSWVersion(6),
				asymmetricTDD(7)
		}
		ACCESS  read-only
		STATUS  mandatory
		DESCRIPTION
		"Information about the TDM Service availability.
		 - Not Applicable if the service is available.
		 The reasons for TDM Service unavailability:
		 - The available throughput isn't sufficient for Service demands;
		 - The IDU HW doesn't support the service;
		 - A Link Password mismatch was detected;
		 - The external pulse type detected is improper for TDM services;
		 - A Software versions mismatch was detected.
		 - A-Symetric TDD Mode Is Obligated."
		::= { fibeAir4800IduSrvAvailServicesEntry 5 }

	fibeAir4800IduSrvEthActive OBJECT-TYPE
		SYNTAX  INTEGER {
			inactive(1),
			active(2)
		}
		ACCESS  read-only
		STATUS  mandatory
		DESCRIPTION
		"Represents the Ethernet service activation state."
		::= { fibeAir4800IduService 12 }

	fibeAir4800IduSrvEthAvailable OBJECT-TYPE
		SYNTAX  INTEGER {
			unavailable(1),
			available(2)
		}
		ACCESS  read-only
		STATUS  mandatory
		DESCRIPTION
		"Represents the Ethernet service availability state."
		::= { fibeAir4800IduService 13 }

	fibeAir4800IduSrvEthThroughput OBJECT-TYPE
		SYNTAX  Gauge
		ACCESS  read-only
		STATUS  mandatory
		DESCRIPTION
		"Current available Ethernet service throughput in bps."
		::= { fibeAir4800IduService 14 }

	fibeAir4800IduSrvEthMaxInfoRate OBJECT-TYPE
		SYNTAX  INTEGER (0..122880)
		ACCESS  read-write
		STATUS  mandatory
		DESCRIPTION
		"Holds the maximum bandwidth (kbps) to be allocated for Ethernet service.
		 Value of zero means that Ethernet service works as best effort.
		 The maximum value is product specific. Refer to the user manual."
		::= { fibeAir4800IduService 15 }

	fibeAir4800IduSrvAvailableTrunksT1 OBJECT-TYPE
		SYNTAX INTEGER
		ACCESS  read-only
		STATUS  mandatory
		DESCRIPTION
		"A bitmap describing the TDM trunks that can be opened under T1 configuration. 
		The values take into account the IDU hardware configuration, the air rate and the installation range."
		::= { fibeAir4800IduService 16 }
	
	-- ###########################################################
	--                      IDU Ethernet
	-- ###########################################################

	fibeAir4800IduEthernet OBJECT IDENTIFIER ::= { fibeAir4800Idu 3 }

	-- ###########################################################
	--                      IDU Ethernet Interface Table
	-- ###########################################################

	fibeAir4800IduEthernetIfTable OBJECT-TYPE
		SYNTAX  SEQUENCE OF FibeAir4800IduEthernetIfEntry
		ACCESS  not-accessible
		STATUS  mandatory
		DESCRIPTION
		"IDU Ethernet Interface table."
		::= { fibeAir4800IduEthernet 1 }

	fibeAir4800IduEthernetIfEntry OBJECT-TYPE
		SYNTAX  FibeAir4800IduEthernetIfEntry
		ACCESS  not-accessible
		STATUS  mandatory
		DESCRIPTION
		"IDU Ethernet Interface table entry."
		INDEX { fibeAir4800IduEthernetIfIndex }
		::= { fibeAir4800IduEthernetIfTable 1 }

	FibeAir4800IduEthernetIfEntry ::= SEQUENCE {
		fibeAir4800IduEthernetIfIndex
			INTEGER,
		fibeAir4800IduEthernetIfAddress
			DisplayString
		}

	fibeAir4800IduEthernetIfIndex OBJECT-TYPE
		SYNTAX  INTEGER
		ACCESS  read-only
		STATUS  mandatory
		DESCRIPTION
		"If Index corresponding to this Interface."
		::= { fibeAir4800IduEthernetIfEntry 1 }
	
	fibeAir4800IduEthernetIfAddress OBJECT-TYPE
		SYNTAX  DisplayString
		ACCESS  read-only
		STATUS  mandatory
		DESCRIPTION
		"IDU MAC address."
		::= { fibeAir4800IduEthernetIfEntry 5 }	

	fibeAir4800IduEthernetNumOfLanPorts OBJECT-TYPE
		SYNTAX  INTEGER
		ACCESS  read-only
		STATUS  mandatory
		DESCRIPTION
		"Number of LAN interfaces in the IDU."
		::= { fibeAir4800IduEthernet 3 }

	fibeAir4800IduEthernetNumOfSfpPorts OBJECT-TYPE
		SYNTAX  INTEGER
		ACCESS  read-only
		STATUS  mandatory
		DESCRIPTION
		"The number of SFP interfaces in the IDU."
		::= { fibeAir4800IduEthernet 4 }

	fibeAir4800IduEthernetSfpProperties OBJECT-TYPE
		SYNTAX  DisplayString
		ACCESS  read-only
		STATUS  mandatory
		DESCRIPTION
		"SFP venfor properties : Vendor Name, PN and Revision."
		::= { fibeAir4800IduEthernet 5 }

	fibeAir4800IduEthernetGbeSupported OBJECT-TYPE
		SYNTAX  INTEGER {notSupported(1), supported(2)}
		ACCESS  read-only
		STATUS  mandatory
		DESCRIPTION
		"Supported Giga bit Ethernet in IDU."
		::= { fibeAir4800IduEthernet 6 }		

	fibeAir4800IduEthernetOduInErrors OBJECT-TYPE
		SYNTAX  Counter
		ACCESS  read-only
		STATUS  mandatory
		DESCRIPTION
		"The number of inbound packets that contained errors preventing them from being deliverable to a higher-layer protocol."
		::= { fibeAir4800IduEthernet 7 }			
	
	-- ###########################################################
	--                      IDU Bridge
	-- ###########################################################

	fibeAir4800IduBridge OBJECT IDENTIFIER ::= { fibeAir4800Idu 4 }

	-- ###########################################################
	--                      IDU Bridge Tp
	-- ###########################################################

	fibeAir4800IduBridgeTp OBJECT IDENTIFIER ::= { fibeAir4800IduBridge 4 }	
												   
	fibeAir4800IduBridgeTpAging OBJECT-TYPE
		SYNTAX  INTEGER (1..1048575)
		ACCESS  read-write
		STATUS  mandatory
		DESCRIPTION
		"Timeout in seconds for aging. Note that for this parameter to be effective,
		the ODU must be configured to HUB mode. A change is effective immediately."
		::= { fibeAir4800IduBridgeTp 2 }

	-- ###########################################################
	--                      IDU TDM
	-- ###########################################################

	fibeAir4800IduTdm OBJECT IDENTIFIER ::= { fibeAir4800Idu 6 }

	fibeAir4800IduTdmTxClock OBJECT IDENTIFIER ::= { fibeAir4800IduTdm 1 }

	fibeAir4800IduTdmTxClockAvailStates OBJECT-TYPE
		SYNTAX  INTEGER (0..62)
		ACCESS  read-only
		STATUS  mandatory
		DESCRIPTION
		"Available states of the TDM Transmit Clock Control, each input status is represented by a bit.
		When the state is available, the bit value is 1. When the state is unavailable, the bit 
		value is 0.
		The available states are:		
		bit 2 = Transparent
		bit 3 = Local Loop Timed
		bit 4 = Remote Loop Timed
		bit 5 = Local Internal
		bit 6 = Remote Internal"
		::= { fibeAir4800IduTdmTxClock 1 }

	fibeAir4800IduTdmTxClockDesiredState OBJECT-TYPE
		SYNTAX  INTEGER {
			transparent(2),
			localLT(4),
			remoteLT(8),
			localInternal(16),
			remoteInternal(32),
			multipleClock(64)
			}
		ACCESS  read-write
		STATUS  mandatory
		DESCRIPTION
		"Required state of the TDM Transmit Clock Control. A change is effective after re-activation of the TDM service."
		::= { fibeAir4800IduTdmTxClock 2 }

	fibeAir4800IduTdmTxClockActualState OBJECT-TYPE
		SYNTAX  INTEGER {
			notAvailable(1),
			transparent(2),
			localLT(4),
			remoteLT(8),
			localInternal(16),
			remoteInternal(32),
			multipleClock(64)
			}
		ACCESS  read-only
		STATUS  mandatory
		DESCRIPTION
		"Actual state of the TDM Transmit Clock Control."
		::= { fibeAir4800IduTdmTxClock 3 }

	fibeAir4800IduTdmMasterClock OBJECT IDENTIFIER ::= { fibeAir4800IduTdm 2 }

	fibeAir4800IduTdmMasterClockAvailOptions OBJECT-TYPE
		SYNTAX  INTEGER (0..62)
		ACCESS  read-only
		STATUS  mandatory
		DESCRIPTION
		"Available options of the TDM Master Clock Control, each input status is represented by a bit.
		When the option is available, the bit value is 1. When the option is unavailable, the bit value is 0.
		The available options are:		
		bit 2 = Automatic
		bit 3 = Trunk #1
		bit 4 = Trunk #2
		bit 5 = Trunk #3
		bit 6 = Trunk #4
		When no options are available the returned value is: 1"
		::= { fibeAir4800IduTdmMasterClock 1 }

	fibeAir4800IduTdmMasterClockDesired OBJECT-TYPE
		SYNTAX  INTEGER {
			automatic(2),
			trunk1(4),
			trunk2(8),
			trunk3(16),
			trunk4(32),
			multipleClocks(64)
			}
		ACCESS  read-write
		STATUS  mandatory
		DESCRIPTION
		"Required TDM Master Clock. A change is effective after re-activation of the TDM service."
		::= { fibeAir4800IduTdmMasterClock 2 }

	fibeAir4800IduTdmMasterClockActual OBJECT-TYPE
		SYNTAX  INTEGER {
			notAvailable(1),
			trunk1(4),
			trunk2(8),
			trunk3(16),
			trunk4(32),
			multipleClocks(64)
			}
		ACCESS  read-only
		STATUS  mandatory
		DESCRIPTION
		"Actual Trunk used for TDM Master Clock."
		::= { fibeAir4800IduTdmMasterClock 3 }

	-- ###########################################################
	--                      IDU TDM Links Configuration Table
	-- ###########################################################

	fibeAir4800IduTdmConfigTable OBJECT-TYPE
		SYNTAX  SEQUENCE OF FibeAir4800IduTdmConfigEntry
		ACCESS  not-accessible
		STATUS  mandatory
		DESCRIPTION
		"IDU TDM Links Configuration table."
		::= { fibeAir4800IduTdm 6 }

	fibeAir4800IduTdmConfigEntry OBJECT-TYPE
		SYNTAX  FibeAir4800IduTdmConfigEntry
		ACCESS  not-accessible
		STATUS  mandatory
		DESCRIPTION
		"IDU TDM Links Configuration table entry."
		INDEX { fibeAir4800IduTdmConfigIndex }
		::= { fibeAir4800IduTdmConfigTable 1 }

	FibeAir4800IduTdmConfigEntry ::= SEQUENCE {
		fibeAir4800IduTdmConfigIndex
			INTEGER,
		fibeAir4800IduTdmIfIndex
			INTEGER,
		fibeAir4800IduTdmLineCoding
			INTEGER,
		fibeAir4800IduTdmLoopbackConfig
			INTEGER,
		fibeAir4800IduTdmLineStatus
			INTEGER
		}

	fibeAir4800IduTdmConfigIndex OBJECT-TYPE
		SYNTAX  INTEGER
		ACCESS  read-only
		STATUS  mandatory
		DESCRIPTION
		"Table index."
		::= { fibeAir4800IduTdmConfigEntry 1 }

	fibeAir4800IduTdmIfIndex OBJECT-TYPE
		SYNTAX  INTEGER
		ACCESS  read-only
		STATUS  mandatory
		DESCRIPTION
		"Link index in the interface table."
		::= { fibeAir4800IduTdmConfigEntry 2 }

	fibeAir4800IduTdmLineCoding OBJECT-TYPE
		SYNTAX  INTEGER {
			b8zs (2),
			ami (5)
			}
		ACCESS  read-write
		STATUS  mandatory
		DESCRIPTION
		"This parameter applies to T1 trunks only. The parameter controls the line coding.
		Setting the value to each of the indices applies to all.
		A change is effective after the next open of the TDM service."
		::= { fibeAir4800IduTdmConfigEntry 6 }

	fibeAir4800IduTdmLoopbackConfig OBJECT-TYPE
		SYNTAX  INTEGER
			{ normal (1),
			  lineLoopBack (3),
			  revereseLineLoopBack (4)
			}
		ACCESS  read-write
		STATUS  mandatory
		DESCRIPTION
		"Loop back configuration table. Each of the trunks can be set Normal, Line loop back or Reverse line loop back.
		A change is effective immediately."
		::= { fibeAir4800IduTdmConfigEntry 9 }

	fibeAir4800IduTdmLineStatus OBJECT-TYPE
		SYNTAX  INTEGER 
			{ normal (1),
		 	  ais (8),
			  los (64),
			  loopback (128)
			}
		ACCESS  read-only
		STATUS  mandatory
		DESCRIPTION
		"Line status."
		::= { fibeAir4800IduTdmConfigEntry 10 }	

	-- ###########################################################
	--                      IDU TDM Links Statistics Table
	-- ###########################################################

	fibeAir4800IduTdmCurrentTable OBJECT-TYPE
		SYNTAX  SEQUENCE OF FibeAir4800IduTdmCurrentEntry
		ACCESS  not-accessible
		STATUS  mandatory
		DESCRIPTION
		"IDU TDM Links Statistics table."
		::= { fibeAir4800IduTdm 7 }

	fibeAir4800IduTdmCurrentEntry OBJECT-TYPE
		SYNTAX  FibeAir4800IduTdmCurrentEntry
		ACCESS  not-accessible
		STATUS  mandatory
		DESCRIPTION
		"IDU TDM Links Statistics table entry."
		INDEX { fibeAir4800IduTdmCurrentIndex }
		::= { fibeAir4800IduTdmCurrentTable 1 }

	FibeAir4800IduTdmCurrentEntry ::= SEQUENCE {
		fibeAir4800IduTdmCurrentIndex
			INTEGER,
		fibeAir4800IduTdmCurrentBlocks
			Counter,
		fibeAir4800IduTdmCurrentDrops
			Counter,
		fibeAir4800IduTdmCurrentTxClock
			INTEGER,
		fibeAir4800IduTdmCurrentBlocksHigh
			Counter
		}

	fibeAir4800IduTdmCurrentIndex OBJECT-TYPE
		SYNTAX  INTEGER
		ACCESS  read-only
		STATUS  mandatory
		DESCRIPTION
		"Table index (Same as fibeAir4800IduTdmLineIndex)."
		::= { fibeAir4800IduTdmCurrentEntry 1 }

	fibeAir4800IduTdmCurrentBlocks OBJECT-TYPE
		SYNTAX  Counter
		ACCESS  read-only
		STATUS  mandatory
		DESCRIPTION
		"Number of correct blocks transmitted to the line."
		::= { fibeAir4800IduTdmCurrentEntry 101 }

	fibeAir4800IduTdmCurrentDrops OBJECT-TYPE
		SYNTAX  Counter
		ACCESS  read-only
		STATUS  mandatory
		DESCRIPTION
		"Number of error blocks transmitted to the line."
		::= { fibeAir4800IduTdmCurrentEntry 102 }

	fibeAir4800IduTdmCurrentTxClock OBJECT-TYPE
		SYNTAX  INTEGER {
			transparent(2),
			localLT(4),
			remoteLT(8),
			localInternal(16),
			remoteInternal(32)
			}
		ACCESS  read-write
		STATUS  mandatory
		DESCRIPTION
		"TDM Transmit Clock. A change is effective after re-activation of the TDM service."
		::= { fibeAir4800IduTdmCurrentEntry 103 }
		
	fibeAir4800IduTdmCurrentBlocksHigh OBJECT-TYPE
		SYNTAX  Counter
		ACCESS  read-only
		STATUS  mandatory
		DESCRIPTION
		"High part of the 64 bits counter Current Blocks"
		::= { fibeAir4800IduTdmCurrentEntry 104 }

	fibeAir4800IduTdmRemoteQual OBJECT-TYPE
		SYNTAX  INTEGER
		ACCESS  read-only
		STATUS  mandatory
		DESCRIPTION
		"Estimated average interval between error second events. 
		The valid values are 1-2^31 where a value of -1 is used to indicate an undefined state."
		::= { fibeAir4800IduTdm 8 }

	fibeAir4800IduTdmRemoteQualEval OBJECT-TYPE
		SYNTAX  INTEGER
		ACCESS  read-only
		STATUS  mandatory
		DESCRIPTION
		"Estimated average interval between error second events during evaluation process.
		The valid values are 1-2^31 where a value of -1 is used to indicate an undefined state."
		::= { fibeAir4800IduTdm 9 }

	fibeAir4800IduTdmSrvEval OBJECT-TYPE
		SYNTAX  INTEGER
		ACCESS  read-write
		STATUS  mandatory
		DESCRIPTION
		"Evaluated TDM service bit mask.
		Setting this parameter to value that is bigger than the activated TDM service bit mask 
		will execute the evaluation process for 30 seconds. 
		Setting this parameter to 0 will stop the evaluation process immediately."
		::= { fibeAir4800IduTdm 10 }

	fibeAir4800IduTdmBackupAvailableLinks OBJECT-TYPE
		SYNTAX  INTEGER
		ACCESS  read-only
		STATUS  mandatory
		DESCRIPTION
		"Number of TDM backup trunks."
		::= { fibeAir4800IduTdm 11 }

	-- ###########################################################
	--                      IDU TDM Backup Links Table
	-- ###########################################################

	fibeAir4800IduTdmBackupTable OBJECT-TYPE
		SYNTAX  SEQUENCE OF FibeAir4800IduTdmBackupEntry
		ACCESS  not-accessible
		STATUS  mandatory
		DESCRIPTION
		"IDU TDM Links Statistics table."
		::= { fibeAir4800IduTdm 12 }

	fibeAir4800IduTdmBackupEntry OBJECT-TYPE
		SYNTAX  FibeAir4800IduTdmBackupEntry
		ACCESS  not-accessible
		STATUS  mandatory
		DESCRIPTION
		"IDU TDM Links Statistics table entry."
		INDEX { fibeAir4800IduTdmBackupIndex }
		::= { fibeAir4800IduTdmBackupTable 1 }

	FibeAir4800IduTdmBackupEntry ::= SEQUENCE {
		fibeAir4800IduTdmBackupIndex
			INTEGER,
		fibeAir4800IduTdmBackupMode
			INTEGER,
		fibeAir4800IduTdmBackupCurrentActiveLink
			INTEGER
		}

	fibeAir4800IduTdmBackupIndex OBJECT-TYPE
		SYNTAX  INTEGER (1..16)
		ACCESS  read-only
		STATUS  mandatory
		DESCRIPTION
		"Table index."
		::= { fibeAir4800IduTdmBackupEntry 1 }

	fibeAir4800IduTdmBackupMode OBJECT-TYPE
		SYNTAX  INTEGER {
			enableUseAirLinkAsBackupLink(1),
			enableUseExternalLinkAsBackupLink(2),			
			disableUseExternalLinkAsMainLink(3),
			disableUseAirLinkAsMainLink(4)
			}
		ACCESS  read-write
		STATUS  mandatory
		DESCRIPTION
		"TDM backup mode: Enable or Disable, where the 
		 main link is the air link or the external link.
		 Changes will be effective immediatly."
		::= { fibeAir4800IduTdmBackupEntry 2 }

	fibeAir4800IduTdmBackupCurrentActiveLink OBJECT-TYPE
		SYNTAX  INTEGER {
			notAvailable(1),
			airLinkIsActive(2),
			externalLinkIsActive(3),
			noLinkIsActive(4)
			}
		ACCESS  read-only
		STATUS  mandatory
		DESCRIPTION
		"TDM backup current active link: N/A, 
		 air link is active or external link is active."
		::= { fibeAir4800IduTdmBackupEntry 3 }
		
	fibeAir4800IduTdmJitterBufferSize OBJECT-TYPE
		SYNTAX  INTEGER
		ACCESS  read-write
		STATUS  mandatory
		DESCRIPTION
		"TDM Jitter Buffer Size.
		 The value must be between the minimum and the maximum TDM Jitter Buffer Size.  
		 The units are 0.1 x millisecond."
		::= { fibeAir4800IduTdm 13 }
		
	fibeAir4800IduTdmJitterBufferDefaultSize OBJECT-TYPE
		SYNTAX  INTEGER
		ACCESS  read-only
		STATUS  mandatory
		DESCRIPTION
		"TDM Jitter Buffer Default Size. The units are 0.1 x millisecond."
		::= { fibeAir4800IduTdm 14 }
		
	fibeAir4800IduTdmJitterBufferMinSize OBJECT-TYPE
		SYNTAX  INTEGER
		ACCESS  read-only
		STATUS  mandatory
		DESCRIPTION
		"TDM Jitter Buffer Minimum Size. The units are 0.1 x millisecond."
		::= { fibeAir4800IduTdm 15 }
		
	fibeAir4800IduTdmJitterBufferMaxSize OBJECT-TYPE
		SYNTAX  INTEGER
		ACCESS  read-only
		STATUS  mandatory
		DESCRIPTION
		"TDM Jitter Buffer Maximum Size. The units are 0.1 x millisecond."
		::= { fibeAir4800IduTdm 16 }
		
	fibeAir4800IduTdmJitterBufferSizeEval OBJECT-TYPE
		SYNTAX  INTEGER
		ACCESS  read-write
		STATUS  mandatory
		DESCRIPTION
		"TDM Jitter Buffer Size for evaluation. 
		 The value must be between the minimum and the maximum TDM Jitter Buffer Size. 
		 The units are 0.1 x millisecond."
		::= { fibeAir4800IduTdm 17 }

	fibeAir4800IduTdmType OBJECT-TYPE
		SYNTAX  INTEGER{
			unDefined(1),
			e1(2),
			t1(3)
			}
		ACCESS  read-write
		STATUS  mandatory
		DESCRIPTION
		"TDM Type (The value undefined is read-only)."
		::= { fibeAir4800IduTdm 18 }

	fibeAir4800IduTdmTypeEval OBJECT-TYPE
		SYNTAX  INTEGER{
			unDefined(1),
			e1(2),
			t1(3)
			}
		ACCESS  read-write
		STATUS  mandatory
		DESCRIPTION
		"TDM Type for evaluation."
		::= { fibeAir4800IduTdm 19 }

	fibeAir4800IduTdmLineStatusStr OBJECT-TYPE
		SYNTAX  DisplayString
		ACCESS  read-only
		STATUS  mandatory
		DESCRIPTION
		"Line status."
		::= { fibeAir4800IduTdm 20 }	

	fibeAir4800IduTdmHotStandbySupport OBJECT-TYPE
		SYNTAX  INTEGER{
			supported(1),
			notSupported(2)
			}
		ACCESS  read-only
		STATUS  mandatory
		DESCRIPTION
		"Indicates if Hot Standby is supported."
		::= { fibeAir4800IduTdm 21 }

	fibeAir4800IduTdmDesiredHotStandbyMode OBJECT-TYPE
		SYNTAX  INTEGER{
			primary(1),
			secondary(2),
			disabled(3)
			}
		ACCESS  read-write
		STATUS  mandatory
		DESCRIPTION
		"Desired Hot Standby Mode."
		::= { fibeAir4800IduTdm 22 }	

	fibeAir4800IduTdmHotStandbyOperationStatus OBJECT-TYPE
		SYNTAX  INTEGER{
			active(1),
			notActive(2)
			}
		ACCESS  read-only
		STATUS  mandatory
		DESCRIPTION
		"The Link Actual Status."
		::= { fibeAir4800IduTdm 23 }		
		
	fibeAir4800IduTdmBackupLinkConfiguration OBJECT-TYPE
		SYNTAX  INTEGER{
			independent(1),
			repeaterEnd(2),
			lineEnd(3)
			}
		ACCESS  read-write
		STATUS  mandatory
		DESCRIPTION
		"The current configuration of the backup link."
		::= { fibeAir4800IduTdm 24 }


	fibeAir4800IduTdmLineInterfaceConfiguration OBJECT-TYPE
		SYNTAX  INTEGER{
			balanced(1),
			unBalanced(2)
			}
		ACCESS  read-write
		STATUS  mandatory
		DESCRIPTION
		"TDM Line interface configuration."
		::= { fibeAir4800IduTdm 25 }

		
	fibeAir4800IduTdmLineImpedanceConfiguration OBJECT-TYPE
        	SYNTAX  INTEGER{
			standardT1(1),
			nonStandardT1(2)
            		}
        	ACCESS  read-write
        	STATUS  mandatory
        	DESCRIPTION
        	"TDM line impedance configuration (standardT1 - 100Ohm, nonStandardT1 - 110Ohm)
        	Applicable only for T1 TDM type."
        	::= { fibeAir4800IduTdm 26 }

		
	-- ###########################################################
	--                      HBS
	-- ###########################################################

	fibeAir4800Hbs OBJECT IDENTIFIER ::= { fibeAir4800 3 }

	-- ###########################################################
	--                      HBS Air
	-- ###########################################################

	fibeAir4800HbsAir OBJECT IDENTIFIER ::= { fibeAir4800Hbs 1 }
	
	fibeAir4800HbsAirState OBJECT-TYPE
		SYNTAX  INTEGER	{
			init				(1),
			bitFailed			(2),
			inactive			(3),
			spectrumMeasurement	(4),
			scanning			(5),
			cac					(6),
			transceiving		(7),
			standBy				(8)
			}
		ACCESS  read-only
		STATUS  mandatory
		DESCRIPTION
		"Holds the state of the HBS."
		::= { fibeAir4800HbsAir 1 }
		
	fibeAir4800HbsAirOpMode OBJECT-TYPE
		SYNTAX  INTEGER	{
			inactive			(1),
			active				(2)
			}
		ACCESS  read-write
		STATUS  mandatory
		DESCRIPTION
		"Holds the operation mode of the HBS."
		::= { fibeAir4800HbsAir 2 }
		
	fibeAir4800HbsAirAvailTimeSlots OBJECT-TYPE
		SYNTAX  INTEGER
		ACCESS  read-only
		STATUS  mandatory
		DESCRIPTION
		"This parameter holds the number of available time slots (not in use) in the air interface."
		::= { fibeAir4800HbsAir 3 }

	fibeAir4800HbsAirSectorCbwSupportedStr OBJECT-TYPE
		SYNTAX  DisplayString
		ACCESS  read-only
		STATUS  mandatory
		DESCRIPTION
		"Represents the channel bandwidth which is supported by the HBS and all connected HSUs."
		::= { fibeAir4800HbsAir 4 }
				
	fibeAir4800HbsAirCompressedMon OBJECT-TYPE
		SYNTAX  OCTET STRING
		ACCESS  read-only
		STATUS  mandatory
		DESCRIPTION
		"Holds HBS monitor data in compressed format:
		HBS Traffic Monitor
		In Bytes(4)
		Out Bytes(4)
		In Frames(4)
		Out Frames(4)
		HBS State (1)
		HBS Freq (4)
		Number of Links (2)
		EC Change Counter (4)
		Current Ratio (2)
		Total Air Frames (4)
		HBS Rx Rate in Kbps (4)
		HBS Tx Rate in Kbps (4)
		HBS Rx Rate in Fps (4)
		HBS Tx Rate in Fps (4)
		HBS Set Mode (1)."
		::= { fibeAir4800HbsAir 5 }		
		
	fibeAir4800HbsAirConf OBJECT IDENTIFIER ::= { fibeAir4800HbsAir 6 }	
			
	fibeAir4800HbsAirConfChanges OBJECT-TYPE
		SYNTAX	OCTET STRING(SIZE(16))
		ACCESS  read-only
		STATUS  mandatory
		DESCRIPTION
		"16 characters that represent 16 HSUs.
		Each time a configuration is been changed, increment the relevant character."
		::= { fibeAir4800HbsAirConf 1 }
		
	-- ###########################################################
	--                      HSUs Configuration Table
	-- ###########################################################		
	
	fibeAir4800HbsAirConfTable OBJECT-TYPE
		SYNTAX  SEQUENCE OF FibeAir4800HbsAirConfEntry
		ACCESS  not-accessible
		STATUS  mandatory
		DESCRIPTION
		"Holds the table for all registered HSUs in the sector (16 entries)."
		::= { fibeAir4800HbsAirConf 2 }

	fibeAir4800HbsAirConfEntry OBJECT-TYPE
		SYNTAX  FibeAir4800HbsAirConfEntry
		ACCESS  not-accessible
		STATUS  mandatory
		DESCRIPTION
		"HSUs configuration table entry."
		INDEX { fibeAir4800HbsAirConfIndex }
		::= { fibeAir4800HbsAirConfTable 1 }

	FibeAir4800HbsAirConfEntry ::= SEQUENCE {
		fibeAir4800HbsAirConfIndex
			INTEGER,	
		fibeAir4800HbsAirConfUpMir
			INTEGER,
		fibeAir4800HbsAirConfDownMir
			INTEGER,		
		fibeAir4800HbsAirConfHsuName
			DisplayString,
		fibeAir4800HbsAirConfHsuLocation
			DisplayString,
		fibeAir4800HbsAirConfDualAntTxMode
			INTEGER,
		fibeAir4800HbsAirConfNumOfTs
			INTEGER,
		fibeAir4800HbsAirConfGeoLocation
			DisplayString,
		fibeAir4800HbsAirConfHsuType
			INTEGER,
		fibeAir4800HbsAirConfHsuLevel
			INTEGER,
		fibeAir4800HbsAirConfDesiredRateIndex
			INTEGER,
		fibeAir4800HbsAirConfMacAddress
			DisplayString,
		fibeAir4800HbsAirConfNumOfTsUp
			INTEGER
		}
		
	fibeAir4800HbsAirConfIndex OBJECT-TYPE
		SYNTAX  INTEGER
		ACCESS  read-only
		STATUS  mandatory
		DESCRIPTION
		"HSUs configuration table index."
		::= { fibeAir4800HbsAirConfEntry 1 }
		
	fibeAir4800HbsAirConfUpMir OBJECT-TYPE
		SYNTAX  INTEGER
		ACCESS  read-write
		STATUS  mandatory
		DESCRIPTION
		"Uplink MIR towards specific HSU in units of kbps."
		::= { fibeAir4800HbsAirConfEntry 2 }
		
	fibeAir4800HbsAirConfDownMir OBJECT-TYPE
		SYNTAX  INTEGER
		ACCESS  read-write
		STATUS  mandatory
		DESCRIPTION
		"Downlink MIR towards specific HSU in units of kbps."
		::= { fibeAir4800HbsAirConfEntry 3 }
			
	fibeAir4800HbsAirConfHsuName OBJECT-TYPE
		SYNTAX  DisplayString
		ACCESS  read-write
		STATUS  mandatory
		DESCRIPTION
		"HSU name."
		::= { fibeAir4800HbsAirConfEntry 4 }
		
	fibeAir4800HbsAirConfHsuLocation OBJECT-TYPE
		SYNTAX  DisplayString
		ACCESS  read-write
		STATUS  mandatory
		DESCRIPTION
		"HSU location."
		::= { fibeAir4800HbsAirConfEntry 5 }
		
	fibeAir4800HbsAirConfDualAntTxMode OBJECT-TYPE
		SYNTAX  INTEGER	{
			mimo			(1),
			diversity		(2),
			autoSelection	(3)
			}
		ACCESS  read-write
		STATUS  mandatory
		DESCRIPTION
		"Transmission type when using Dual Antenna on both link's sides. 
		 spatial Multiplexing, Diversity (using a single spatial stream), and
		 Auto Selection (OMS control)."
		::= { fibeAir4800HbsAirConfEntry 6 }
		
	fibeAir4800HbsAirConfNumOfTs OBJECT-TYPE
		SYNTAX  INTEGER
		ACCESS  read-write
		STATUS  mandatory
		DESCRIPTION
		"Number of time slot which are allocated to specific HSU."
		::= { fibeAir4800HbsAirConfEntry 7 }
		
	fibeAir4800HbsAirConfGeoLocation OBJECT-TYPE
		SYNTAX  DisplayString
		ACCESS  read-write
		STATUS  mandatory
		DESCRIPTION
		"Geographic device location in format: 	latitude,longitude."
		::= { fibeAir4800HbsAirConfEntry 8 }

	fibeAir4800HbsAirConfHsuType OBJECT-TYPE
		SYNTAX  INTEGER	{
			fixed		(1),
			stationary	(2),
			mobile		(3),
			transport	(4)
			}
		ACCESS  read-write
		STATUS  mandatory
		DESCRIPTION
		"HSU type (1 = Fixed, 2 = Stationary, 3 = Mobile, 4 = Transport)"
		::= { fibeAir4800HbsAirConfEntry 9 }
		
	fibeAir4800HbsAirConfHsuLevel OBJECT-TYPE
		SYNTAX  INTEGER
		ACCESS  read-write
		STATUS  mandatory
		DESCRIPTION
		"HSU level (1 .. 4)"
		::= { fibeAir4800HbsAirConfEntry 10 }
		
	fibeAir4800HbsAirConfDesiredRateIndex OBJECT-TYPE
		SYNTAX  INTEGER
		ACCESS  read-write
		STATUS  mandatory
		DESCRIPTION
		"The rate index of both sides of the link to this HSU."
		::= { fibeAir4800HbsAirConfEntry 11 }
		
	fibeAir4800HbsAirConfMacAddress OBJECT-TYPE
		SYNTAX  DisplayString
		ACCESS  read-only
		STATUS  mandatory
		DESCRIPTION
		"HSU MAC Address."
		::= { fibeAir4800HbsAirConfEntry 12 }
		
	fibeAir4800HbsAirConfNumOfTsUp OBJECT-TYPE
		SYNTAX  INTEGER
		ACCESS  read-write
		STATUS  mandatory
		DESCRIPTION
		"Number of UL time slot which are allocated to specific HSU."
		::= { fibeAir4800HbsAirConfEntry 13 }
		
	fibeAir4800HbsAirLink OBJECT IDENTIFIER ::= { fibeAir4800HbsAir 7 }
	
	-- ###########################################################
	--                      Sector Links Table
	-- ###########################################################			
			
	fibeAir4800HbsAirLinkNumOfLinks OBJECT-TYPE
		SYNTAX  INTEGER
		ACCESS  read-only
		STATUS  mandatory
		DESCRIPTION
		"Number of links in the links table."
		::= { fibeAir4800HbsAirLink 1 }
		
	fibeAir4800HbsAirLinkTable OBJECT-TYPE
		SYNTAX  SEQUENCE OF FibeAir4800HbsAirLinkEntry
		ACCESS  not-accessible
		STATUS  mandatory
		DESCRIPTION
		"Holds the table for all links in the sector."
		::= { fibeAir4800HbsAirLink 2 }		
		
	fibeAir4800HbsAirLinkEntry OBJECT-TYPE
		SYNTAX  FibeAir4800HbsAirLinkEntry
		ACCESS  not-accessible
		STATUS  mandatory
		DESCRIPTION
		"Link table entry."
		INDEX { fibeAir4800HbsAirLinkIndex }
		::= { fibeAir4800HbsAirLinkTable 1 }

	FibeAir4800HbsAirLinkEntry ::= SEQUENCE {
		fibeAir4800HbsAirLinkIndex
			INTEGER,
		fibeAir4800HbsAirLinkHsuId
			INTEGER,
		fibeAir4800HbsAirLinkState
			INTEGER,
		fibeAir4800HbsAirLinkWorkingMode
			INTEGER,
		fibeAir4800HbsAirLinkSessionId
			INTEGER,
		fibeAir4800HbsAirLinkHbsEstTput
			INTEGER,
		fibeAir4800HbsAirLinkHsuEstTput
			INTEGER,			
		fibeAir4800HbsAirLinkRange
			INTEGER,
		fibeAir4800HbsAirLinkHbsRss
			INTEGER,
		fibeAir4800HbsAirLinkHbsRssBal
			INTEGER,
		fibeAir4800HbsAirLinkHsuRss
			INTEGER,
		fibeAir4800HbsAirLinkHsuRssBal
			INTEGER,			
		fibeAir4800HbsAirLinkHsuSerial
			DisplayString,
		fibeAir4800HbsAirLinkTxOperMode
			INTEGER,
		fibeAir4800HbsAirHsuInBytes
			INTEGER,
		fibeAir4800HbsAirHsuOutBytes
			INTEGER,
		fibeAir4800HbsAirHsuInFrames
			INTEGER,			
		fibeAir4800HbsAirHsuOutFrames
			INTEGER,				
		fibeAir4800HbsAirHsuMacAddress
			DisplayString,
		fibeAir4800HbsAirMaxTputDown
			INTEGER,
		fibeAir4800HbsAirMaxTputUp
			INTEGER,		
		fibeAir4800HbsAirLinkCompressedMon
			OCTET STRING,
		fibeAir4800HbsAirLinkCompressedStatic
			DisplayString,
		fibeAir4800HbsAirCpeCapacityLimit
			INTEGER,
		fibeAir4800HbsAirLinkAntennaType
			INTEGER,
		fibeAir4800HbsAirHsuRxRateInKbps
			INTEGER,
		fibeAir4800HbsAirHsuTxRateInKbps
			INTEGER,
		fibeAir4800HbsAirHsuRxRateInFps
			INTEGER,
		fibeAir4800HbsAirHsuTxRateInFps
			INTEGER,
		fibeAir4800HbsAirLinkPeakTputDown
			INTEGER,
		fibeAir4800HbsAirLinkPeakTputUp
			INTEGER,
		fibeAir4800HbsAirLinkUtilDownSecRelMill
			INTEGER,	
		fibeAir4800HbsAirLinkUtilUpSecRelMill
			INTEGER,
		fibeAir4800HbsAirLinkUtilDownAllocRelMill
			INTEGER,	
		fibeAir4800HbsAirLinkUtilUpAllocRelMill
			INTEGER,
		fibeAir4800HbsAirLinkUtilDownTrafficKbps
			INTEGER,	
		fibeAir4800HbsAirLinkUtilUpTrafficKbps
			INTEGER,
		fibeAir4800HbsAirLinkUtilCompressedMon
			OCTET STRING,
		fibeAir4800HbsAirLinkBsaAzimuth
			INTEGER
		}
		
	fibeAir4800HbsAirLinkIndex OBJECT-TYPE
		SYNTAX  INTEGER
		ACCESS  read-only
		STATUS  mandatory
		DESCRIPTION
		"HSUs configuration table index."
		::= { fibeAir4800HbsAirLinkEntry 1 }
		
	fibeAir4800HbsAirLinkHsuId OBJECT-TYPE
		SYNTAX  INTEGER
		ACCESS  read-only
		STATUS  mandatory
		DESCRIPTION
		"HSU ID of specific link (if registered). Unregistered links have -1."
		::= { fibeAir4800HbsAirLinkEntry 2 }
		
	fibeAir4800HbsAirLinkState OBJECT-TYPE
		SYNTAX  INTEGER	{
			noSync 				(1),
			violated			(2),
			syncUnregistered		(3),
			syncRegistered			(4),
			authenticationError		(5),
			swUpgradeRequired		(6),
			syncRegisteredPassive		(7)
			}
		ACCESS  read-only
		STATUS  mandatory
		DESCRIPTION
		"Holds the state of specific link."
		::= { fibeAir4800HbsAirLinkEntry 3 }
		
	fibeAir4800HbsAirLinkWorkingMode OBJECT-TYPE
		SYNTAX  INTEGER {
			unknown(1),
			normal(2),
			fullCompatibilityRemoteUpgradeAvailable(3),
			fullCompatibilityLocalUpgradeAvailable(4),
			restrictedCompatibilityRemoteUpgradeRecomended(5),
			restrictedCompatibilityLocalUpgradeRecomended(6),
			softwareUpgradeRemoteUpgradeRequired(7),
			softwareUpgradeLocalUpgradeRequired(8),
			versionsIncompatibilityRemoteUpgradeRequired(9),
			versionsIncompatibilityLocalUpgradeRequired(10)
		}
		ACCESS  read-only
		STATUS  mandatory
		DESCRIPTION
		"Indicates the sub-state within the version compatibility."
		::= { fibeAir4800HbsAirLinkEntry 4 }
				
	fibeAir4800HbsAirLinkSessionId OBJECT-TYPE
		SYNTAX  INTEGER
		ACCESS  read-only
		STATUS  mandatory
		DESCRIPTION
		"Holds the Session ID of the link."
		::= { fibeAir4800HbsAirLinkEntry 5 }
		
	fibeAir4800HbsAirLinkHbsEstTput OBJECT-TYPE
		SYNTAX  INTEGER
		ACCESS  read-only
		STATUS  mandatory
		DESCRIPTION
		"Holds the Estimated throughput from the HBS to the HSU."
		::= { fibeAir4800HbsAirLinkEntry 6 }
		
	fibeAir4800HbsAirLinkHsuEstTput OBJECT-TYPE
		SYNTAX  INTEGER
		ACCESS  read-only
		STATUS  mandatory
		DESCRIPTION
		"Holds the Estimated throughput from the HSU to the HBS."
		::= { fibeAir4800HbsAirLinkEntry 7 }		

	fibeAir4800HbsAirLinkRange OBJECT-TYPE
		SYNTAX  INTEGER
		ACCESS  read-only
		STATUS  mandatory
		DESCRIPTION
		"Holds the range of specific link."
		::= { fibeAir4800HbsAirLinkEntry 8 }		
	
	fibeAir4800HbsAirLinkHbsRss OBJECT-TYPE
		SYNTAX  INTEGER
		ACCESS  read-only
		STATUS  mandatory
		DESCRIPTION
		"Holds the RSS of specific link (HBS side)."
		::= { fibeAir4800HbsAirLinkEntry 9 }
	
	fibeAir4800HbsAirLinkHbsRssBal OBJECT-TYPE
		SYNTAX  INTEGER
		ACCESS  read-only
		STATUS  mandatory
		DESCRIPTION
		"Holds the RSS Balance of specific link (HBS side).
		-2 : Radio 2 RSS is much stronger than Radio 1 RSS.
		-1 : Radio 2 RSS is stronger than Radio 1 RSS.
		-0 : Radio 2 RSS is equal to Radio 1 RSS.
		1  : Radio 1 RSS is stronger than Radio 2 RSS.
		2  : Radio 1 RSS is much stronger than Radio 2 RSS."
		::= { fibeAir4800HbsAirLinkEntry 10 }
		
	fibeAir4800HbsAirLinkHsuRss OBJECT-TYPE
		SYNTAX  INTEGER
		ACCESS  read-only
		STATUS  mandatory
		DESCRIPTION
		"Holds the RSS of specific link (HSU side)."
		::= { fibeAir4800HbsAirLinkEntry 11 }
	
	fibeAir4800HbsAirLinkHsuRssBal OBJECT-TYPE
		SYNTAX  INTEGER
		ACCESS  read-only
		STATUS  mandatory
		DESCRIPTION
		"Holds the RSS Balance of specific link (HSU side).
		-2 : Radio 2 RSS is much stronger than Radio 1 RSS.
		-1 : Radio 2 RSS is stronger than Radio 1 RSS.
		-0 : Radio 2 RSS is equal to Radio 1 RSS.
		1  : Radio 1 RSS is stronger than Radio 2 RSS.
		2  : Radio 1 RSS is much stronger than Radio 2 RSS."
		::= { fibeAir4800HbsAirLinkEntry 12 }
		
	fibeAir4800HbsAirLinkHsuSerial OBJECT-TYPE
		SYNTAX  DisplayString
		ACCESS  read-only
		STATUS  mandatory
		DESCRIPTION
		"Holds the serial number for specific HSU."
		::= { fibeAir4800HbsAirLinkEntry 13 }		

	fibeAir4800HbsAirLinkTxOperMode OBJECT-TYPE
		SYNTAX  INTEGER	{
			regularMode (1),
			measurementMode	(2)
			}
		ACCESS  read-only
		STATUS  mandatory
		DESCRIPTION
		"Holds the TX operation mode."
		::= { fibeAir4800HbsAirLinkEntry 14 }
		
	fibeAir4800HbsAirHsuInBytes OBJECT-TYPE
		SYNTAX  INTEGER
		ACCESS  read-only
		STATUS  mandatory
		DESCRIPTION
		"Number of frames received in the HSU Lan port."
		::= { fibeAir4800HbsAirLinkEntry 15 }
		
	fibeAir4800HbsAirHsuOutBytes OBJECT-TYPE
		SYNTAX  INTEGER
		ACCESS  read-only
		STATUS  mandatory
		DESCRIPTION
		"Number of frames transmitted from the HSU Lan port."
		::= { fibeAir4800HbsAirLinkEntry 16 }
		
	fibeAir4800HbsAirHsuInFrames OBJECT-TYPE
		SYNTAX  INTEGER
		ACCESS  read-only
		STATUS  mandatory
		DESCRIPTION
		"Number of bytes received in the HSU Lan port."
		::= { fibeAir4800HbsAirLinkEntry 17 }
		
	fibeAir4800HbsAirHsuOutFrames OBJECT-TYPE
		SYNTAX  INTEGER
		ACCESS  read-only
		STATUS  mandatory
		DESCRIPTION
		"Number of bytes transmitted from the HSU Lan port."
		::= { fibeAir4800HbsAirLinkEntry 18 }		
		
	fibeAir4800HbsAirHsuMacAddress OBJECT-TYPE
		SYNTAX  DisplayString
		ACCESS  read-only
		STATUS  mandatory
		DESCRIPTION
		"HSU MAC Address."
		::= { fibeAir4800HbsAirLinkEntry 19 }
		
	fibeAir4800HbsAirMaxTputDown OBJECT-TYPE
		SYNTAX  INTEGER
		ACCESS  read-only
		STATUS  mandatory
		DESCRIPTION
		"Max Throughput Downlink."
		::= { fibeAir4800HbsAirLinkEntry 20 }
		
	fibeAir4800HbsAirMaxTputUp OBJECT-TYPE
		SYNTAX  INTEGER
		ACCESS  read-only
		STATUS  mandatory
		DESCRIPTION
		"Max Throughput Uplink."
		::= { fibeAir4800HbsAirLinkEntry 21 }	

	fibeAir4800HbsAirLinkCompressedMon OBJECT-TYPE
		SYNTAX	OCTET STRING
		ACCESS  read-only
		STATUS  mandatory
		DESCRIPTION
		"Holds all the link information in compressed binary (Bytes/octets).
		Fields included (size in bytes):
		Link State(1)										
		Link Working Mode(1)								
		Session Id(4)										
		HBS Est. Tput(4)									
		HSU Est. Tput(4)									
		HBS Rss(1)											
		HBS Rss Balance(1)									
		HSU Rss(1)											
		HSU Rss Balance(1)									
		Tx Operation Mode(1)								
		HSU In Bytes(4)										
		HSU Out Bytes(4)									
		HSU In Frames(4)									
		HSU Out Frames(4)									
		HSU ID (1 bytes)
		HSU Rx Rate In Kbps (4)
		HSU Tx Rate In Kbps (4)
		HSU Rx Rate In Fps (4)
		HSU Tx Rate In Fps (4)
		Peak throughput in the DL direction (4)
		Peak throughput in the UL direction (4)
		Number of local changes at HSU(1)
		Alignment Status(1)
		HBS Chain 1 Rss(1)
		HBS Chain 2 Rss(1)
		HBS Chain 3 Rss(1)
		HSU Chain 1 Rss(1)
		HSU Chain 2 Rss(1)
		HSU Chain 3 Rss(1)
		HSU Current Rate Index (2 bytes)
		HSU Current Rate CBW (1 bytes)
		HSU Current Rate GI (1 bytes)
		HBS Current Rate Index (2 bytes)
		HBS Current Rate CBW (1 bytes)
		HBS Current Rate GI (1 bytes)
		Bsa Azimuth(2)"
		::= { fibeAir4800HbsAirLinkEntry 22 }
		
	fibeAir4800HbsAirLinkCompressedStatic OBJECT-TYPE
		SYNTAX	DisplayString
		ACCESS  read-only
		STATUS  mandatory
		DESCRIPTION
		"Holds all the configuration data of this link in compressed format.
		Helps the NMS to get info regarding new Unregistered links.
		Fields Included:
		SessionID (4 bytes)
		HSU IP address (4 bytes)
		HSU Name (32 bytes)
		HSU Location (32 bytes)
		HSU Serial number (16 bytes)		
		HSU MAC Address (12 bytes)
		Air Link Range
		Max Throughput Down (4 bytes)
		Max Throughput Up. (4 bytes)
		Cpacity Limit (4 bytes)
		HSU Antenna type (1 byte)
		Aggregate Capacity (4 bytes)"
		::= { fibeAir4800HbsAirLinkEntry 23 }				
		
				
	fibeAir4800HbsAirCpeCapacityLimit OBJECT-TYPE
		SYNTAX  INTEGER
		ACCESS  read-only
		STATUS  mandatory
		DESCRIPTION
		"Capacity Limit in Kilo bit per second."
		::= { fibeAir4800HbsAirLinkEntry 24 }

	fibeAir4800HbsAirLinkAntennaType OBJECT-TYPE
		SYNTAX  INTEGER {
			single(1), 
			dual(2), 
			undefined(3),
			triple(4)
			}
		ACCESS  read-only
		STATUS  mandatory
		DESCRIPTION
		"HSU External Antenna Type: Monopolar or Bipolar."
		::= { fibeAir4800HbsAirLinkEntry 25 }
		
	fibeAir4800HbsAirHsuRxRateInKbps OBJECT-TYPE
		SYNTAX  INTEGER
		ACCESS  read-only
		STATUS  mandatory
		DESCRIPTION
		"HSU Rx Rate in Kbps."
		::= { fibeAir4800HbsAirLinkEntry 26 }

	fibeAir4800HbsAirHsuTxRateInKbps OBJECT-TYPE
		SYNTAX  INTEGER
		ACCESS  read-only
		STATUS  mandatory
		DESCRIPTION
		"HSU Tx Rate in Kbps."
		::= { fibeAir4800HbsAirLinkEntry 27 }
		
	fibeAir4800HbsAirHsuRxRateInFps OBJECT-TYPE
		SYNTAX  INTEGER
		ACCESS  read-only
		STATUS  mandatory
		DESCRIPTION
		"HSU Tx Rate in Fps."
		::= { fibeAir4800HbsAirLinkEntry 28 }
	
	fibeAir4800HbsAirHsuTxRateInFps OBJECT-TYPE
		SYNTAX  INTEGER
		ACCESS  read-only
		STATUS  mandatory
		DESCRIPTION
		"HSU Tx Rate in Fps."
		::= { fibeAir4800HbsAirLinkEntry 29 }		
	
	fibeAir4800HbsAirLinkPeakTputDown OBJECT-TYPE
		SYNTAX  INTEGER
		ACCESS  read-only
		STATUS  mandatory
		DESCRIPTION
		"Peak throughput in the DL direction (kbps)."
		::= { fibeAir4800HbsAirLinkEntry 30 }
		
	fibeAir4800HbsAirLinkPeakTputUp OBJECT-TYPE
		SYNTAX  INTEGER
		ACCESS  read-only
		STATUS  mandatory
		DESCRIPTION
		"Peak throughput in the UL direction (kbps)."
		::= { fibeAir4800HbsAirLinkEntry 31 }
		
	fibeAir4800HbsAirLinkUtilDownSecRelMill OBJECT-TYPE
		SYNTAX  INTEGER
		ACCESS  read-only
		STATUS  mandatory
		DESCRIPTION
		"The average time percentage (in thousandths), out of the BTS DL capability,
		that was used for transmitting data to the SU."
		::= { fibeAir4800HbsAirLinkEntry 32 }
	
	fibeAir4800HbsAirLinkUtilUpSecRelMill OBJECT-TYPE
		SYNTAX  INTEGER
		ACCESS  read-only
		STATUS  mandatory
		DESCRIPTION
		"The average time percentage (in thousandths), out of the BTS UL capability,
		that was used for receiving data from the SU."
		::= { fibeAir4800HbsAirLinkEntry 33 }	
		
	fibeAir4800HbsAirLinkUtilDownAllocRelMill OBJECT-TYPE
		SYNTAX  INTEGER
		ACCESS  read-only
		STATUS  mandatory
		DESCRIPTION
		"The time percentage (in thousandths), relative to the SU DL allocation,
		that was used for transmitting data to the SU."
		::= { fibeAir4800HbsAirLinkEntry 34 }
		
	fibeAir4800HbsAirLinkUtilUpAllocRelMill OBJECT-TYPE
		SYNTAX  INTEGER
		ACCESS  read-only
		STATUS  mandatory
		DESCRIPTION
		"The time percentage (in thousandths), relative to the SU UL allocation,
		that was used for receiving data from the SU."
		::= { fibeAir4800HbsAirLinkEntry 35 }	
		
	fibeAir4800HbsAirLinkUtilDownTrafficKbps OBJECT-TYPE
		SYNTAX  INTEGER
		ACCESS  read-only
		STATUS  mandatory
		DESCRIPTION
		"Average data throughput (Exported in Kbps) transmitted in the DL
		towards the SU during the last second."
		::= { fibeAir4800HbsAirLinkEntry 36 }
		
	fibeAir4800HbsAirLinkUtilUpTrafficKbps OBJECT-TYPE
		SYNTAX  INTEGER
		ACCESS  read-only
		STATUS  mandatory
		DESCRIPTION
		"Average data throughput (Exported in Kbps) received in the UL
		from the SU during the last second."
		::= { fibeAir4800HbsAirLinkEntry 37 }
		
	fibeAir4800HbsAirLinkUtilCompressedMon OBJECT-TYPE
		SYNTAX	OCTET STRING
		ACCESS  read-only
		STATUS  mandatory
		DESCRIPTION
		"One string that holds the 6 Utilization per link values:
		DownSecRel     (2 bytes)
		UpSecRel       (2 bytes)
		DownAllocRel   (4 bytes)
		UpAllocRel     (4 bytes)
		DownTraffic    (4 bytes)
		UpTraffic      (4 bytes)."
		::= { fibeAir4800HbsAirLinkEntry 38 }
		
	fibeAir4800HbsAirLinkBsaAzimuth OBJECT-TYPE
		SYNTAX  INTEGER
		ACCESS  read-only
		STATUS  mandatory
		DESCRIPTION
		"Absolute (geographical) azimuth of the HSU (looking from HBS site)."
		::= { fibeAir4800HbsAirLinkEntry 39 }
			
	fibeAir4800HbsAirComboSwitchSectorFreqBandId OBJECT-TYPE
		SYNTAX  INTEGER
		ACCESS  read-write
		STATUS  mandatory
		DESCRIPTION
		"Switch Frequency band for the whole sector."
		::= { fibeAir4800HbsAir 8 }
		
	fibeAir4800HbsAirGeoAzimuth OBJECT-TYPE
		SYNTAX  INTEGER
		ACCESS  read-write
		STATUS  mandatory
		DESCRIPTION
		"Geographic sector azimuth in degrees * 10."
		::= { fibeAir4800HbsAir 9 }
		
	fibeAir4800HbsAirGeoBeamwidth OBJECT-TYPE
		SYNTAX  INTEGER
		ACCESS  read-write
		STATUS  mandatory
		DESCRIPTION
		"Geographic sector beamwidth in degrees * 10."
		::= { fibeAir4800HbsAir 10 }
		
	fibeAir4800HbsAirMaxDistanceMetersMobility OBJECT-TYPE
		SYNTAX  INTEGER
		ACCESS  read-write
		STATUS  mandatory
		DESCRIPTION
		"Maximum distance in meters. Used by Mobility links only."
		::= { fibeAir4800HbsAir 11 }
		
	fibeAir4800HbsAirComboSwitchSectorFreqBandIdStr OBJECT-TYPE
		SYNTAX  DisplayString
		ACCESS  read-write
		STATUS  mandatory
		DESCRIPTION
		"Switch Frequency band for the whole sector, overriding some of the Combo parameters."
		::= { fibeAir4800HbsAir 12 }
		
	fibeAir4800HbsAirTimeSlotAllocationBitmap OBJECT-TYPE
		SYNTAX  DisplayString
		ACCESS  read-write
		STATUS  mandatory
		DESCRIPTION
		"Time Slots Allocation Bitmap for the entire sector (Hex Value)."
		::= { fibeAir4800HbsAir 13 }
		
	fibeAir4800HbsAirAvailTimeSlotsUp OBJECT-TYPE
		SYNTAX  INTEGER
		ACCESS  read-only
		STATUS  mandatory
		DESCRIPTION
		"This parameter holds the number of available UL time slots (not in use) in the air interface."
		::= { fibeAir4800HbsAir 14 }

	fibeAir4800HbsAirDownUtilMill OBJECT-TYPE
		SYNTAX  INTEGER
		ACCESS  read-only
		STATUS  mandatory
		DESCRIPTION
		"Sector Air Interface utilization in the Downlink direction (thousandths).
		Average time percentage, out of the entire BTS DL capability,
		that was used for transmitting data to all the SUs."
		::= { fibeAir4800HbsAir 15 }
		
	fibeAir4800HbsAirUpUtilMill OBJECT-TYPE
		SYNTAX  INTEGER
		ACCESS  read-only
		STATUS  mandatory
		DESCRIPTION
		"Sector Air Interface utilization in the Uplink direction (thousandths).
		The average number of timeslots that were used in the UL (by all the links)
		out of the entire number of timeslots."
		::= { fibeAir4800HbsAir 16 }
		
	fibeAir4800HbsAirDownTrafficKbps OBJECT-TYPE
		SYNTAX  INTEGER
		ACCESS  read-only
		STATUS  mandatory
		DESCRIPTION
		"Average data throughput (expressed in Kbps) transmitted in the DL
		towards all the SUs during the last second."
		::= { fibeAir4800HbsAir 17 }
		
	fibeAir4800HbsAirUpTrafficKbps OBJECT-TYPE
		SYNTAX  INTEGER
		ACCESS  read-only
		STATUS  mandatory
		DESCRIPTION
		"Average data throughput (expressed in Kbps) received in the UL
		from all the SUs during the last second."
		::= { fibeAir4800HbsAir 18 }
		
	fibeAir4800HbsAirCompressedMonSec OBJECT-TYPE
		SYNTAX  DisplayString
		ACCESS  read-only
		STATUS  mandatory
		DESCRIPTION
		"One string that holds the 4 Utilization per Sector values:
		DownUtil	(2 bytes),
		UpUtil  	(2 bytes),
		DownTraffic (4 bytes),
		UpTraffic 	(4 bytes)."
		::= { fibeAir4800HbsAir 19 }
		
	fibeAir4800HbsAirDelayVsTputOpt OBJECT-TYPE
		SYNTAX  INTEGER {
			delaySensitivity(1),
			throughputOptimized(2)
			}
		ACCESS  read-write
		STATUS  mandatory
		DESCRIPTION
		"Delay vs. Throughput optimization type:
		 1 = Delay sensitivity
		 2 = Throughput optimized"
		::= { fibeAir4800HbsAir 20 }

	fibeAir4800HbsAirUCBP OBJECT IDENTIFIER ::= { fibeAir4800HbsAir 21 }
	
	-- ###########################################################
	--                      UCBP section
	-- ###########################################################			
			
	fibeAir4800HbsAirUCBPMinCS OBJECT-TYPE
		SYNTAX  INTEGER
		ACCESS  read-write
		STATUS  mandatory
		DESCRIPTION
		"Minimal contention slot length used for UCBP algorithm (in ms.) between 5-20ms."
		::= { fibeAir4800HbsAirUCBP 1 }
		
	fibeAir4800HbsAirUCBPSharingPercentage OBJECT-TYPE
		SYNTAX  INTEGER
		ACCESS  read-write
		STATUS  mandatory
		DESCRIPTION
		"Sharing percentage used by UCBP algorithm (15-75)"
		::= { fibeAir4800HbsAirUCBP 2 }
			
		fibeAir4800HbsAirSingleHsuMode OBJECT-TYPE   
		SYNTAX  INTEGER {
			notApplicable(1),
			singleHsu(2),
			multipleHsus(3)
			}
		ACCESS  read-write
		STATUS  mandatory
		DESCRIPTION
		"Single HSU mode:
		 1 = Not Applicable
		 2 = Single HSU
		 3 = Multiple HSUs"
		::= { fibeAir4800HbsAir 22 }
	fibeAir4800HbsAirMobilityAzTrack OBJECT-TYPE
		SYNTAX  INTEGER
		ACCESS  read-only
		STATUS  mandatory
		DESCRIPTION
		"Azimuth tracking for mobility status:
		1 = Not applicable
		2 = Active
		3 = Impossible"
		::= { fibeAir4800HbsAir 23 }
		
	-- ###########################################################
	--                      HBS Bridge
	-- ###########################################################

	fibeAir4800HbsBridge OBJECT IDENTIFIER ::= { fibeAir4800Hbs 2 }
	
	fibeAir4800HbsBridgeAgingTime OBJECT-TYPE
		SYNTAX  INTEGER
		ACCESS  read-write
		STATUS  mandatory
		DESCRIPTION
		"Timeout in seconds for aging."
		::= { fibeAir4800HbsBridge 1 }
		
	-- ###########################################################
	--                      HBS Bridge Vlan Table
	-- ###########################################################		
	
	fibeAir4800HbsBridgeVlanTable OBJECT-TYPE
		SYNTAX  SEQUENCE OF FibeAir4800HbsBridgeVlanEntry
		ACCESS  not-accessible
		STATUS  mandatory
		DESCRIPTION
		"Holds the bridge Vlan operations towards all the registered HSUs."
		::= { fibeAir4800HbsBridge 2 }

	fibeAir4800HbsBridgeVlanEntry OBJECT-TYPE
		SYNTAX  FibeAir4800HbsBridgeVlanEntry
		ACCESS  not-accessible
		STATUS  mandatory
		DESCRIPTION
		"HBS bridge Vlan table entry."
		INDEX { fibeAir4800HbsBridgeVlanIndex }
		::= { fibeAir4800HbsBridgeVlanTable 1 }

	FibeAir4800HbsBridgeVlanEntry ::= SEQUENCE {
		fibeAir4800HbsBridgeVlanIndex
			INTEGER,	
		fibeAir4800HbsBridgeVlanIngress
			INTEGER,
		fibeAir4800HbsBridgeVlanEgress
			INTEGER,
		fibeAir4800HbsBridgeVlanFilterIn
			INTEGER,
		fibeAir4800HbsBridgeVlanFilterOut
			INTEGER,
		fibeAir4800HbsBridgeVlanDoubleTag
			INTEGER,
		fibeAir4800HbsBridgeVlanDefaultId
			INTEGER		
		}
		
	fibeAir4800HbsBridgeVlanIndex OBJECT-TYPE
		SYNTAX  INTEGER
		ACCESS  read-only
		STATUS  mandatory
		DESCRIPTION
		"HBS bridge Vlan table index."
		::= { fibeAir4800HbsBridgeVlanEntry 1 }
		
	fibeAir4800HbsBridgeVlanIngress OBJECT-TYPE
		SYNTAX  INTEGER	{
			transparent (1),
			tag	(2)
			}
		ACCESS  read-write
		STATUS  mandatory
		DESCRIPTION
		"HBS bridge Vlan ingress."
		::= { fibeAir4800HbsBridgeVlanEntry 2 }
		
	fibeAir4800HbsBridgeVlanEgress OBJECT-TYPE
		SYNTAX  INTEGER	{
			transparent (1),
			unTag	(2)
			}
		ACCESS  read-write
		STATUS  mandatory
		DESCRIPTION
		"HBS bridge Vlan egress."
		::= { fibeAir4800HbsBridgeVlanEntry 3 }
		
	fibeAir4800HbsBridgeVlanFilterIn OBJECT-TYPE
		SYNTAX  INTEGER	{
			on (1),
			off	(2)
			}
		ACCESS  read-write
		STATUS  mandatory
		DESCRIPTION
		"HBS bridge Vlan filter in."
		::= { fibeAir4800HbsBridgeVlanEntry 4 }
		
	fibeAir4800HbsBridgeVlanFilterOut OBJECT-TYPE
		SYNTAX  INTEGER	{
			on (1),
			off	(2)
			}
		ACCESS  read-write
		STATUS  mandatory
		DESCRIPTION
		"HBS bridge Vlan filter out."
		::= { fibeAir4800HbsBridgeVlanEntry 5 }
		
	fibeAir4800HbsBridgeVlanDoubleTag OBJECT-TYPE
		SYNTAX  INTEGER	{
			on (1),
			off	(2)
			}
		ACCESS  read-write
		STATUS  mandatory
		DESCRIPTION
		"HBS bridge Vlan double tag."
		::= { fibeAir4800HbsBridgeVlanEntry 6 }
		
	fibeAir4800HbsBridgeVlanDefaultId OBJECT-TYPE
		SYNTAX  INTEGER
		ACCESS  read-write
		STATUS  mandatory
		DESCRIPTION
		"HBS bridge Vlan default id."
		::= { fibeAir4800HbsBridgeVlanEntry 7 }
		
	-- ###########################################################
	--                      HBS Bridge Membership Table
	-- ###########################################################		
	
	fibeAir4800HbsBridgeMembershipTable OBJECT-TYPE
		SYNTAX  SEQUENCE OF FibeAir4800HbsBridgeMembershipEntry
		ACCESS  not-accessible
		STATUS  mandatory
		DESCRIPTION
		"Holds the bridge membership relations for all the registered HSUs."
		::= { fibeAir4800HbsBridge 3 }

	fibeAir4800HbsBridgeMembershipEntry OBJECT-TYPE
		SYNTAX  FibeAir4800HbsBridgeMembershipEntry
		ACCESS  not-accessible
		STATUS  mandatory
		DESCRIPTION
		"HBS bridge membership table entry."
		INDEX { fibeAir4800HbsBridgeMembershipIndex }
		::= { fibeAir4800HbsBridgeMembershipTable 1 }

	FibeAir4800HbsBridgeMembershipEntry ::= SEQUENCE {
		fibeAir4800HbsBridgeMembershipIndex
			INTEGER,	
		fibeAir4800HbsBridgeMembershipState
			Gauge,
		fibeAir4800HbsBridgeMembershipState2nd
			Gauge
		}
		
	fibeAir4800HbsBridgeMembershipIndex OBJECT-TYPE
		SYNTAX  INTEGER
		ACCESS  read-only
		STATUS  mandatory
		DESCRIPTION
		"HBS bridge membership table index."
		::= { fibeAir4800HbsBridgeMembershipEntry 1 }
		
	fibeAir4800HbsBridgeMembershipState OBJECT-TYPE
		SYNTAX  Gauge
		ACCESS  read-write
		STATUS  mandatory
		DESCRIPTION
		"HBS bridge membership state bitmap.
		Each bit represents Blocked/Opened relation (membership) between two HSUs.
		Blocked=0 (bit), Opened=1 (bit). This object holds the relation to 32 HSUs."
		::= { fibeAir4800HbsBridgeMembershipEntry 2 }
	
	fibeAir4800HbsBridgeMembershipState2nd OBJECT-TYPE
		SYNTAX  Gauge
		ACCESS  read-write
		STATUS  mandatory
		DESCRIPTION
		"HBS bridge membership state bitmap.
		Each bit represents Blocked/Opened relation (membership) between HSU and LAN/Stack port of the HBS.
		Blocked=0 (bit), Opened=1 (bit). Only 2 bits are used."
		::= { fibeAir4800HbsBridgeMembershipEntry 3 }

	fibeAir4800HbsBridgeFloodOverloadProtect OBJECT-TYPE
		SYNTAX  INTEGER	{
				enabled (1),
				disabled (2)
			}
		ACCESS  read-write
		STATUS  mandatory
		DESCRIPTION
		"Flood overload protection 1- Enabled 2- Disabled."
		::= { fibeAir4800HbsBridge 4 }		
												
	-- ###########################################################
	--                      HBS Service
	-- ###########################################################

	fibeAir4800HbsService OBJECT IDENTIFIER ::= { fibeAir4800Hbs 3 }
	
	fibeAir4800HbsServiceCommandStr OBJECT-TYPE
		SYNTAX  DisplayString
		ACCESS  read-write
		STATUS  mandatory
		DESCRIPTION
		"Ability to perform special command in the HBS.
		Format (string): Operation, Index, Session, Param1, Param2,....| ParamN
		The index and SessionID can be uniting to one parameter.
		On registered HSU it is HSU-ID and on Unregistered it is Session-ID."
		::= { fibeAir4800HbsService 1 }	
		
	-- ###########################################################
	--                      HBS Service Vlan
	-- ###########################################################
	
	fibeAir4800HbsServiceVlan OBJECT IDENTIFIER ::= { fibeAir4800HbsService 2 }
	
	fibeAir4800HbsServiceVlanTable OBJECT-TYPE
		SYNTAX  SEQUENCE OF FibeAir4800HbsServiceVlanEntry
		ACCESS  not-accessible
		STATUS  mandatory
		DESCRIPTION
		"Holds the Vlan operations towards all the registered HSUs."
		::= { fibeAir4800HbsServiceVlan 1 }
		
	fibeAir4800HbsServiceVlanEntry OBJECT-TYPE
		SYNTAX  FibeAir4800HbsServiceVlanEntry
		ACCESS  not-accessible
		STATUS  mandatory
		DESCRIPTION
		"HBS service Vlan table entry."
		INDEX { fibeAir4800HbsServiceVlanIndex }
		::= { fibeAir4800HbsServiceVlanTable 1 }
		
	FibeAir4800HbsServiceVlanEntry ::= SEQUENCE {
		fibeAir4800HbsServiceVlanIndex
			INTEGER,	
		fibeAir4800OduServiceVlanTblTag
			INTEGER,
		fibeAir4800OduServiceVlanTblPri
			INTEGER,
		fibeAir4800OduServiceVlanTblMajorMode
			INTEGER,
		fibeAir4800OduServiceVlanTblEgressMode
			INTEGER,
		fibeAir4800OduServiceVlanTblIngressMode
			INTEGER,
		fibeAir4800OduServiceVlanTblEgressFilter1
			INTEGER,
		fibeAir4800OduServiceVlanTblEgressFilter2
			INTEGER,
		fibeAir4800OduServiceVlanTblEgressFilter3
			INTEGER,
		fibeAir4800OduServiceVlanTblEgressFilter4
			INTEGER,
		fibeAir4800OduServiceVlanTblUntagFilteredBitmap
			INTEGER,
		fibeAir4800OduServiceVlanTblProviderTPID
			DisplayString
		}
		
	fibeAir4800HbsServiceVlanIndex OBJECT-TYPE
		SYNTAX  INTEGER
		ACCESS  read-only
		STATUS  mandatory
		DESCRIPTION
		"HBS service Vlan table index."
		::= { fibeAir4800HbsServiceVlanEntry 1 }
		
	fibeAir4800OduServiceVlanTblTag OBJECT-TYPE
		SYNTAX  INTEGER	
		ACCESS  read-write
		STATUS  mandatory
		DESCRIPTION
		"The VID to be used when adding TAG or adding Provider"
		::= { fibeAir4800HbsServiceVlanEntry 2 }
		
	fibeAir4800OduServiceVlanTblPri OBJECT-TYPE
		SYNTAX  INTEGER	
		ACCESS  read-write
		STATUS  mandatory
		DESCRIPTION
		"The Vlan priority 0-7 to be used when adding TAG or adding Provider"
		::= { fibeAir4800HbsServiceVlanEntry 3 }
		
	fibeAir4800OduServiceVlanTblMajorMode OBJECT-TYPE
		SYNTAX  INTEGER	{
			none (1),
			tag	(2),
			provider(3)
			}
		ACCESS  read-write
		STATUS  mandatory
		DESCRIPTION
		"The Vlan major mode"
		::= { fibeAir4800HbsServiceVlanEntry 4 }
		
	fibeAir4800OduServiceVlanTblEgressMode OBJECT-TYPE
		SYNTAX  INTEGER	{
			none (1),
			untag(2),
			filter(3),
			untagFiltered(4)
			}
		ACCESS  read-write
		STATUS  mandatory
		DESCRIPTION
		"The Vlan mode in the Egress direction"
		::= { fibeAir4800HbsServiceVlanEntry 5 }
		
	fibeAir4800OduServiceVlanTblIngressMode OBJECT-TYPE
		SYNTAX  INTEGER	{
			none (1),
			tag(2)
			}	
		ACCESS  read-write
		STATUS  mandatory
		DESCRIPTION
		"The Vlan mode in the Ingress direction"
		::= { fibeAir4800HbsServiceVlanEntry 6 }
		
	fibeAir4800OduServiceVlanTblEgressFilter1 OBJECT-TYPE
		SYNTAX  INTEGER	
		ACCESS  read-write
		STATUS  mandatory
		DESCRIPTION
		"VLAN Filter1 VID "
		::= { fibeAir4800HbsServiceVlanEntry 7 }								
		
	fibeAir4800OduServiceVlanTblEgressFilter2 OBJECT-TYPE
		SYNTAX  INTEGER	
		ACCESS  read-write
		STATUS  mandatory
		DESCRIPTION
		"VLAN Filter2 VID "
		::= { fibeAir4800HbsServiceVlanEntry 8 }	
		
	fibeAir4800OduServiceVlanTblEgressFilter3 OBJECT-TYPE
		SYNTAX  INTEGER	
		ACCESS  read-write
		STATUS  mandatory
		DESCRIPTION
		"VLAN Filter3 VID "
		::= { fibeAir4800HbsServiceVlanEntry 9 }	
		
	fibeAir4800OduServiceVlanTblEgressFilter4 OBJECT-TYPE
		SYNTAX  INTEGER	
		ACCESS  read-write
		STATUS  mandatory
		DESCRIPTION
		"VLAN Filter4 VID "
		::= { fibeAir4800HbsServiceVlanEntry 10 }	
	
	fibeAir4800OduServiceVlanTblUntagFilteredBitmap OBJECT-TYPE
		SYNTAX  INTEGER	
		ACCESS  read-write
		STATUS  mandatory
		DESCRIPTION
		"Represents (in bitmap) if to Untag a frame after it is filtered (Egress direction) [4 bits represent 4 filters]."
		::= { fibeAir4800HbsServiceVlanEntry 11 }
		
	fibeAir4800OduServiceVlanTblProviderTPID OBJECT-TYPE
		SYNTAX  DisplayString	
		ACCESS  read-write
		STATUS  mandatory
		DESCRIPTION
		"Holds the Provider TPID that is used in all provider operations."
		::= { fibeAir4800HbsServiceVlanEntry 12 }
	
	-- ###########################################################
	--                      HBS Service QoS
	-- ###########################################################
	
	fibeAir4800HbsServiceQoS OBJECT IDENTIFIER ::= { fibeAir4800HbsService 3 }
	
	fibeAir4800HbsServiceQoSMode OBJECT-TYPE
		SYNTAX  INTEGER {
			notSupported (1),
			notActive (2),
			classVlan (3),
			classDiffserv (4)
			}
		ACCESS  read-write
		STATUS  mandatory
		DESCRIPTION
		"Quality of Service mode."
		::= { fibeAir4800HbsServiceQoS 1 }
		
	fibeAir4800HbsServiceQoSVlanQGroupsStr OBJECT-TYPE
		SYNTAX  DisplayString
		ACCESS  read-write
		STATUS  mandatory
		DESCRIPTION
		"Frame classification according to VLAN priority (all 4 groups separated by comma)."
		::= { fibeAir4800HbsServiceQoS 2 }
	
	fibeAir4800HbsServiceQoSDiffservQGroupsStr OBJECT-TYPE
		SYNTAX  DisplayString
		ACCESS  read-write
		STATUS  mandatory
		DESCRIPTION
		"Frame classification according to Diffserv (all 4 groups separated by comma)."
		::= { fibeAir4800HbsServiceQoS 3 }
	
	fibeAir4800HbsServiceQoSMaxRtQuePct OBJECT-TYPE
		SYNTAX  INTEGER
		ACCESS  read-only
		STATUS  mandatory
		DESCRIPTION
		"Maximal percent for RT and NRT queues."
		::= { fibeAir4800HbsServiceQoS 4 }
		
	fibeAir4800HbsServiceQoSTable OBJECT-TYPE
		SYNTAX  SEQUENCE OF FibeAir4800HbsServiceQoSEntry
		ACCESS  not-accessible
		STATUS  mandatory
		DESCRIPTION
		"Holds the QoS operations towards all the registered HSUs."
		::= { fibeAir4800HbsServiceQoS 5 }
		
	fibeAir4800HbsServiceQoSEntry OBJECT-TYPE
		SYNTAX  FibeAir4800HbsServiceQoSEntry
		ACCESS  not-accessible
		STATUS  mandatory
		DESCRIPTION
		"HBS service QoS table entry."
		INDEX { fibeAir4800HbsServiceQoSIndex }
		::= { fibeAir4800HbsServiceQoSTable 1 }
		
	FibeAir4800HbsServiceQoSEntry ::= SEQUENCE {
		fibeAir4800HbsServiceQoSIndex
			INTEGER,	
		fibeAir4800HbsServiceQoSConfAdminState
			INTEGER,
		fibeAir4800HbsServiceQoSConfUpQueMir
			DisplayString,
		fibeAir4800HbsServiceQoSConfUpQueWeight
			DisplayString,
		fibeAir4800HbsServiceQoSConfDownQueMir
			DisplayString,
		fibeAir4800HbsServiceQoSConfDownQueWeight
			DisplayString,
		fibeAir4800HbsServiceQoSUpTtlMs
			DisplayString,
		fibeAir4800HbsServiceQoSDownTtlMs
			DisplayString,
		fibeAir4800HbsServiceQoSUpStrict
			DisplayString,
		fibeAir4800HbsServiceQoSDownStrict
			DisplayString			
		}
		
	fibeAir4800HbsServiceQoSIndex OBJECT-TYPE
		SYNTAX  INTEGER
		ACCESS  read-only
		STATUS  mandatory
		DESCRIPTION
		"HBS service QoS table index."
		::= { fibeAir4800HbsServiceQoSEntry 1 }
		
	fibeAir4800HbsServiceQoSConfAdminState OBJECT-TYPE
		SYNTAX  INTEGER	{
				enabled (1),
				disabled (2)
			}
		ACCESS  read-write
		STATUS  mandatory
		DESCRIPTION
		"QoS administrative state. The valid values are: enabled (1), disabled (2)."
		::= { fibeAir4800HbsServiceQoSEntry 2 }
	
	fibeAir4800HbsServiceQoSConfUpQueMir OBJECT-TYPE
		SYNTAX  DisplayString	
		ACCESS  read-write
		STATUS  mandatory
		DESCRIPTION
		"Private MIR for each QoS group of the Uplink direction (4 values separated by comma)."
		::= { fibeAir4800HbsServiceQoSEntry 3 }
	
	fibeAir4800HbsServiceQoSConfUpQueWeight OBJECT-TYPE
		SYNTAX  DisplayString	
		ACCESS  read-write
		STATUS  mandatory
		DESCRIPTION
		"Weight in percent for each QoS group of the Uplink direction (4 values separated by comma)."
		::= { fibeAir4800HbsServiceQoSEntry 4 }
	
	fibeAir4800HbsServiceQoSConfDownQueMir OBJECT-TYPE
		SYNTAX  DisplayString	
		ACCESS  read-write
		STATUS  mandatory
		DESCRIPTION
		"Private MIR for each QoS group of the Downlink direction (4 values separated by comma)."
		::= { fibeAir4800HbsServiceQoSEntry 5 }
		
	fibeAir4800HbsServiceQoSConfDownQueWeight OBJECT-TYPE
		SYNTAX  DisplayString	
		ACCESS  read-write
		STATUS  mandatory
		DESCRIPTION
		"Weight in percent for each QoS group of the Downlink direction (4 values separated by comma)."
		::= { fibeAir4800HbsServiceQoSEntry 6 }
				
	fibeAir4800HbsServiceQoSUpTtlMs OBJECT-TYPE
		SYNTAX  DisplayString	
		ACCESS  read-write
		STATUS  mandatory
		DESCRIPTION
		"TTL in mili second for each QoS group of the Uplink direction (4 values separated by comma)."
		::= { fibeAir4800HbsServiceQoSEntry 7 }
						
	fibeAir4800HbsServiceQoSDownTtlMs  OBJECT-TYPE
		SYNTAX  DisplayString	
		ACCESS  read-write
		STATUS  mandatory
		DESCRIPTION
		"TTL in mili second for each QoS group of the Downlink direction (4 values separated by comma)."
		::= { fibeAir4800HbsServiceQoSEntry 8 }
		
	fibeAir4800HbsServiceQoSUpStrict OBJECT-TYPE
		SYNTAX  DisplayString	
		ACCESS  read-write
		STATUS  mandatory
		DESCRIPTION
		"Strict QOS Boolean indication for each QOS group of the Uplink direction (4 values separated by comma)."
		::= { fibeAir4800HbsServiceQoSEntry 9 }
		
	fibeAir4800HbsServiceQoSDownStrict OBJECT-TYPE
		SYNTAX  DisplayString	
		ACCESS  read-write
		STATUS  mandatory
		DESCRIPTION
		"Strict QOS Boolean indication for each QOS group of the Downlink direction (4 values separated by comma)."
		::= { fibeAir4800HbsServiceQoSEntry 10 }
		
	fibeAir4800HbsServiceMobilitySupported OBJECT-TYPE
		SYNTAX  INTEGER	{
			notSupported (1),
			supported (2),
			transportSupported (3)
		}
		ACCESS  read-only
		STATUS  mandatory
		DESCRIPTION
		"Mobility Support (1 = Not supported, 2 = Supported, 3 - Transport supported)"
		::= { fibeAir4800HbsService 4 }	
		
	fibeAir4800HbsServiceMaxNumOfHSUs OBJECT-TYPE
		SYNTAX  INTEGER
		ACCESS  read-only
		STATUS  mandatory
		DESCRIPTION
		"Holds the maximum number of registered HSUs in the HBS."
		::= { fibeAir4800HbsService 5 }
		
	-- ###########################################################
	--                      HBS PerfMon
	-- ###########################################################

	fibeAir4800HbsPerfMon OBJECT IDENTIFIER ::= { fibeAir4800Hbs 4 }
	
	-- ###########################################################
	--                      HBS PerfMon Threshold Table
	-- ###########################################################		
	
	fibeAir4800HbsPerfMonThreshTable OBJECT-TYPE
		SYNTAX  SEQUENCE OF FibeAir4800HbsPerfMonThreshEntry
		ACCESS  not-accessible
		STATUS  mandatory
		DESCRIPTION
		"Holds the performance monitor thresholds towards all the registered HSUs."
		::= { fibeAir4800HbsPerfMon 1 }

	fibeAir4800HbsPerfMonThreshEntry OBJECT-TYPE
		SYNTAX  FibeAir4800HbsPerfMonThreshEntry
		ACCESS  not-accessible
		STATUS  mandatory
		DESCRIPTION
		"HBS performance monitor threshold table entry."
		INDEX { fibeAir4800HbsPerfMonThreshIndex }
		::= { fibeAir4800HbsPerfMonThreshTable 1 }

	FibeAir4800HbsPerfMonThreshEntry ::= SEQUENCE {
		fibeAir4800HbsPerfMonThreshIndex
			INTEGER,	
		fibeAir4800HbsPerfMonTxThresh1
			INTEGER,
		fibeAir4800HbsPerfMonRxThresh1
			INTEGER,
		fibeAir4800HbsPerfMonRxThresh2
			INTEGER,
		fibeAir4800HbsPerfMonBBERThresh1
			INTEGER,
		fibeAir4800HbsPerfMonEstThroughputThreshKbps
			INTEGER,
		fibeAir4800HbsPerfMonHighTrafficThreshKbps
			INTEGER		
		}
		
	fibeAir4800HbsPerfMonThreshIndex OBJECT-TYPE
		SYNTAX  INTEGER
		ACCESS  read-only
		STATUS  mandatory
		DESCRIPTION
		"HBS performance monitor threshold table index."
		::= { fibeAir4800HbsPerfMonThreshEntry 1 }
		
	fibeAir4800HbsPerfMonTxThresh1 OBJECT-TYPE
		SYNTAX  INTEGER
		ACCESS  read-write
		STATUS  mandatory
		DESCRIPTION
		"HBS performance monitor transmit power threshold."
		::= { fibeAir4800HbsPerfMonThreshEntry 2 }
		
	fibeAir4800HbsPerfMonRxThresh1 OBJECT-TYPE
		SYNTAX  INTEGER
		ACCESS  read-write
		STATUS  mandatory
		DESCRIPTION
		"HBS performance monitor receive power threshold 1."
		::= { fibeAir4800HbsPerfMonThreshEntry 3 }			
		
	fibeAir4800HbsPerfMonRxThresh2 OBJECT-TYPE
		SYNTAX  INTEGER
		ACCESS  read-write
		STATUS  mandatory
		DESCRIPTION
		"HBS performance monitor receive power threshold 2."
		::= { fibeAir4800HbsPerfMonThreshEntry 4 }	
		
	fibeAir4800HbsPerfMonBBERThresh1 OBJECT-TYPE
		SYNTAX  INTEGER
		ACCESS  read-write
		STATUS  mandatory
		DESCRIPTION
		"HBS performance monitor BBER threshold."
		::= { fibeAir4800HbsPerfMonThreshEntry 5 }	
		
	fibeAir4800HbsPerfMonEstThroughputThreshKbps OBJECT-TYPE
		SYNTAX  INTEGER
		ACCESS  read-write
		STATUS  mandatory
		DESCRIPTION
		"HBS performance monitor estimated throughput Threshold."
		::= { fibeAir4800HbsPerfMonThreshEntry 6 }	
		
	fibeAir4800HbsPerfMonHighTrafficThreshKbps OBJECT-TYPE
		SYNTAX  INTEGER
		ACCESS  read-write
		STATUS  mandatory
		DESCRIPTION
		"HBS performance monitor high traffic threshold."
		::= { fibeAir4800HbsPerfMonThreshEntry 7 }
		
		
	-- ###########################################################
	--                      PM Air General Current Table
	-- ###########################################################

	fibeAir4800HbsPerfMonAirGenCurrTable OBJECT-TYPE
		SYNTAX  SEQUENCE OF FibeAir4800HbsPerfMonAirGenCurrEntry
		ACCESS  not-accessible
		STATUS  mandatory
		DESCRIPTION
		"This table defines/keeps the ethernet counters of the current 15 min interval."
		::= { fibeAir4800HbsPerfMon 2 }

	fibeAir4800HbsPerfMonAirGenCurrEntry OBJECT-TYPE
		SYNTAX  FibeAir4800HbsPerfMonAirGenCurrEntry
		ACCESS  not-accessible
		STATUS  mandatory
		DESCRIPTION
		"This is an entry in the Current Interval Table."
		INDEX {ifIndex }
		::= { fibeAir4800HbsPerfMonAirGenCurrTable 1 }

	FibeAir4800HbsPerfMonAirGenCurrEntry ::= SEQUENCE {
		fibeAir4800HbsPerfMonAirGenCurrRxMBytes
	      Gauge,
   		fibeAir4800HbsPerfMonAirGenCurrTxMBytes
	      Gauge,
		fibeAir4800HbsPerfMonAirGenCurrEthCapacityThreshUnder
	      Gauge,
		fibeAir4800HbsPerfMonAirGenCurrHighTrafficThreshExceed
	      Gauge,
		fibeAir4800HbsPerfMonAirGenCurrActiveSeconds
	      Gauge
	}

	fibeAir4800HbsPerfMonAirGenCurrRxMBytes OBJECT-TYPE
		SYNTAX  Gauge (0..11250)
		ACCESS  read-only
		STATUS  mandatory
		DESCRIPTION
		"Current RX Mega Bytes starting from the present 15 minutes period.
		(Represents the LAN traffic, RX direction, toward the HSU)"
		::= { fibeAir4800HbsPerfMonAirGenCurrEntry 1 }		

	fibeAir4800HbsPerfMonAirGenCurrTxMBytes OBJECT-TYPE
		SYNTAX  Gauge (0..11250)
		ACCESS  read-only
		STATUS  mandatory
		DESCRIPTION
		"Current Transmit Mega Bytes starting from the present 15 minutes period.
		(Represents the LAN traffic, TX direction, from the HSU)"
		::= { fibeAir4800HbsPerfMonAirGenCurrEntry 2 }	
		
	fibeAir4800HbsPerfMonAirGenCurrEthCapacityThreshUnder OBJECT-TYPE
		SYNTAX  Gauge (0..900)
		ACCESS  read-only
		STATUS  mandatory
		DESCRIPTION
		"The number of times throughput was below threshold in the present 15 minutes period.
		Relevant for point to point systems."
		::= { fibeAir4800HbsPerfMonAirGenCurrEntry 3 }
	
	fibeAir4800HbsPerfMonAirGenCurrHighTrafficThreshExceed OBJECT-TYPE
		SYNTAX  Gauge (0..900)
		ACCESS  read-only
		STATUS  mandatory
		DESCRIPTION
		"The number of times actual traffic was above threshold in the present 15 minutes period."
		::= { fibeAir4800HbsPerfMonAirGenCurrEntry 4 }
		
	fibeAir4800HbsPerfMonAirGenCurrActiveSeconds OBJECT-TYPE
		SYNTAX  Gauge (0..900)
		ACCESS  read-only
		STATUS  mandatory
		DESCRIPTION
		"The number of seconds in which RPL Ethernet swervice was not blocked in the present 15 minutes period."
		::= { fibeAir4800HbsPerfMonAirGenCurrEntry 5 }		
		
	-- ###########################################################
	--                      PM Air General Interval Table
	-- ###########################################################	

	fibeAir4800HbsPerfMonAirGenIntervalTable OBJECT-TYPE
		SYNTAX  SEQUENCE OF FibeAir4800HbsPerfMonAirGenIntervalEntry
		ACCESS  not-accessible
		STATUS  mandatory
		DESCRIPTION
		"This table defines/keeps the ethernet counters of the last day (in resolution of 15 min intervals)."
		::= { fibeAir4800HbsPerfMon 3 }

	fibeAir4800HbsPerfMonAirGenIntervalEntry OBJECT-TYPE
		SYNTAX  FibeAir4800HbsPerfMonAirGenIntervalEntry
		ACCESS  not-accessible
		STATUS  mandatory
		DESCRIPTION
		"This is an entry in the Interval Table."
		INDEX {ifIndex, fibeAir4800HbsPerfMonAirGenIntervalIdx }
		::= { fibeAir4800HbsPerfMonAirGenIntervalTable 1 }

	FibeAir4800HbsPerfMonAirGenIntervalEntry ::= SEQUENCE {
		fibeAir4800HbsPerfMonAirGenIntervalIdx
	      INTEGER,
		fibeAir4800HbsPerfMonAirGenIntervalRxMBytes
	      Gauge,
   		fibeAir4800HbsPerfMonAirGenIntervalTxMBytes
	      Gauge,
		fibeAir4800HbsPerfMonAirGenIntervalEthCapacityThreshUnder
	      Gauge,
		fibeAir4800HbsPerfMonAirGenIntervalHighTrafficThreshExceed
	      Gauge,
		fibeAir4800HbsPerfMonAirGenIntervalActiveSeconds
	      Gauge
	}

	fibeAir4800HbsPerfMonAirGenIntervalIdx OBJECT-TYPE
		SYNTAX  INTEGER (1..96)
		ACCESS  read-only
		STATUS  mandatory
		DESCRIPTION
		"This table is indexed per interval number. Each interval
		is of 15 minutes and the oldest is 96."
		::= { fibeAir4800HbsPerfMonAirGenIntervalEntry 1 }

	fibeAir4800HbsPerfMonAirGenIntervalRxMBytes OBJECT-TYPE
		SYNTAX  Gauge (0..11250)
		ACCESS  read-only
		STATUS  mandatory
		DESCRIPTION
		"Current RX Mega Bytes per interval.
		(Represents the LAN traffic, RX direction, toward the HSU)."
		::= { fibeAir4800HbsPerfMonAirGenIntervalEntry 2 }		

	fibeAir4800HbsPerfMonAirGenIntervalTxMBytes OBJECT-TYPE
		SYNTAX  Gauge (0..11250)
		ACCESS  read-only
		STATUS  mandatory
		DESCRIPTION
		"Current Transmit Mega Bytes per interval.
		(Represents the LAN traffic, TX direction, from the HSU)"
		::= { fibeAir4800HbsPerfMonAirGenIntervalEntry 3 }	
		
	fibeAir4800HbsPerfMonAirGenIntervalEthCapacityThreshUnder OBJECT-TYPE
		SYNTAX  Gauge (0..900)
		ACCESS  read-only
		STATUS  mandatory
		DESCRIPTION
		"The number of times throughput was below threshold in the each interval.
		Relevant for point to point systems."
		::= { fibeAir4800HbsPerfMonAirGenIntervalEntry 4 }	
		
	fibeAir4800HbsPerfMonAirGenIntervalHighTrafficThreshExceed OBJECT-TYPE
		SYNTAX  Gauge (0..900)
		ACCESS  read-only
		STATUS  mandatory
		DESCRIPTION
		"The number of times actual traffic was above threshold in the each interval."
		::= { fibeAir4800HbsPerfMonAirGenIntervalEntry 5 }	
		
	fibeAir4800HbsPerfMonAirGenIntervalActiveSeconds OBJECT-TYPE
		SYNTAX  Gauge (0..900)
		ACCESS  read-only
		STATUS  mandatory
		DESCRIPTION
		"The number of seconds in which RPL Ethernet service was not blocked in the each interval."
		::= { fibeAir4800HbsPerfMonAirGenIntervalEntry 6 }			

	-- ###########################################################
	--                      PM Air General Day Table
	-- ###########################################################	

	fibeAir4800HbsPerfMonAirGenDayTable OBJECT-TYPE
		SYNTAX  SEQUENCE OF FibeAir4800HbsPerfMonAirGenDayEntry
		ACCESS  not-accessible
		STATUS  mandatory
		DESCRIPTION
		"This table defines/keeps the ethernet counters of the last month (in resolution of days)."
		::= { fibeAir4800HbsPerfMon 4 }

	fibeAir4800HbsPerfMonAirGenDayEntry OBJECT-TYPE
		SYNTAX  FibeAir4800HbsPerfMonAirGenDayEntry
		ACCESS  not-accessible
		STATUS  mandatory
		DESCRIPTION
		"This is an entry in the Days Table."
		INDEX {ifIndex, fibeAir4800HbsPerfMonAirGenDayIdx }
		::= { fibeAir4800HbsPerfMonAirGenDayTable 1 }

	FibeAir4800HbsPerfMonAirGenDayEntry ::= SEQUENCE {
		fibeAir4800HbsPerfMonAirGenDayIdx
	      INTEGER,
		fibeAir4800HbsPerfMonAirGenDayRxMBytes
	      Gauge,
   		fibeAir4800HbsPerfMonAirGenDayTxMBytes
	      Gauge,
		fibeAir4800HbsPerfMonAirGenDayEthCapacityThreshUnder
	      Gauge,
		fibeAir4800HbsPerfMonAirGenDayHighTrafficThreshExceed
	      Gauge,
		fibeAir4800HbsPerfMonAirGenDayActiveSeconds
	      Gauge
	}

	fibeAir4800HbsPerfMonAirGenDayIdx OBJECT-TYPE
		SYNTAX  INTEGER (1..96)
		ACCESS  read-only
		STATUS  mandatory
		DESCRIPTION
		"This table is indexed per Day number. Each interval
		is of 15 minutes and the oldest is 96."
		::= { fibeAir4800HbsPerfMonAirGenDayEntry 1 }

	fibeAir4800HbsPerfMonAirGenDayRxMBytes OBJECT-TYPE
		SYNTAX  Gauge (0..1080000)
		ACCESS  read-only
		STATUS  mandatory
		DESCRIPTION
		"Current RX Mega Bytes per day.
		(Represents the LAN traffic, RX direction, toward the HSU)"
		::= { fibeAir4800HbsPerfMonAirGenDayEntry 2 }		

	fibeAir4800HbsPerfMonAirGenDayTxMBytes OBJECT-TYPE
		SYNTAX  Gauge (0..1080000)
		ACCESS  read-only
		STATUS  mandatory
		DESCRIPTION
		"Current Transmit Mega Bytes per day.
		(Represents the LAN traffic, TX direction, from the HSU)"
		::= { fibeAir4800HbsPerfMonAirGenDayEntry 3 }
		
	fibeAir4800HbsPerfMonAirGenDayEthCapacityThreshUnder OBJECT-TYPE
		SYNTAX  Gauge (0..86400)
		ACCESS  read-only
		STATUS  mandatory
		DESCRIPTION
		"The number of times throughput was below threshold each day.
		Relevant for point to point systems."
		::= { fibeAir4800HbsPerfMonAirGenDayEntry 4 }
		
	fibeAir4800HbsPerfMonAirGenDayHighTrafficThreshExceed OBJECT-TYPE
		SYNTAX  Gauge (0..86400)
		ACCESS  read-only
		STATUS  mandatory
		DESCRIPTION
		"The number of times actual traffic was above threshold each day."
		::= { fibeAir4800HbsPerfMonAirGenDayEntry 5 }
		
	fibeAir4800HbsPerfMonAirGenDayActiveSeconds OBJECT-TYPE
		SYNTAX  Gauge (0..86400)
		ACCESS  read-only
		STATUS  mandatory
		DESCRIPTION
		"The number of seconds in which RPL Ethernet service was not blocked each day."
		::= { fibeAir4800HbsPerfMonAirGenDayEntry 6 }	
		
	-- ###########################################################
	--                      HSU
	-- ###########################################################

	fibeAir4800Hsu OBJECT IDENTIFIER ::= { fibeAir4800 4 }

	-- ###########################################################
	--                      HSU Air
	-- ###########################################################

	fibeAir4800HsuAir OBJECT IDENTIFIER ::= { fibeAir4800Hsu 1 }
	
	fibeAir4800HsuAirState OBJECT-TYPE
		SYNTAX  INTEGER	{
			init				(1),
			bitFailed			(2),
			spectrumMeasurement	(4),
			transceiving		(7),
			standBy				(8)
			}
		ACCESS  read-only
		STATUS  mandatory
		DESCRIPTION
		"Holds the state of the HSU."
		::= { fibeAir4800HsuAir 1 }
		
	fibeAir4800HsuAirLinkState OBJECT-TYPE
		SYNTAX  INTEGER	{
			noSync 				(1),
			violated			(2),
			syncUnregistered		(3),
			syncRegistered			(4),
			authenticationError		(5),
			swUpgradeRequired		(6),
			syncRegisteredPassive	        (7)
			}
		ACCESS  read-only
		STATUS  mandatory
		DESCRIPTION
		"Holds the state of the HSU link."
		::= { fibeAir4800HsuAir 2 }
		
	fibeAir4800HsuAirHsuId OBJECT-TYPE
		SYNTAX  INTEGER
		ACCESS  read-only
		STATUS  mandatory
		DESCRIPTION
		"Holds the HSU ID as sent by the HBS."
		::= { fibeAir4800HsuAir 3 }
		
	fibeAir4800HsuAirLocalDeregister OBJECT-TYPE
		SYNTAX  INTEGER
		ACCESS  read-write
		STATUS  mandatory
		DESCRIPTION
		"Performs Local HSU Deregistration when - only when the link is off."
		::= { fibeAir4800HsuAir 5 }
		
	fibeAir4800HsuAirRemoteCompressedMon OBJECT-TYPE
		SYNTAX  OCTET STRING
		ACCESS  read-only
		STATUS  mandatory
		DESCRIPTION
		"Holds all the configuration data of The HBS in compressed format.		
		Fields Included:
		Rss (1 byte)											
		Rss Balance (1 byte)
		Est. Tput (4 bytes)	
		In Bytes of the whole sector (4 bytes)										
		Out Bytes of the whole sector (4 bytes)									
		In Frames of the whole sector (4 bytes)									
		Out Frames of the whole sector (4 bytes)
		Max Throughput DownLink (4 bytes)
		Max Throughput UpLink (4 bytes)
		Rx Rate In Kbps of the whole sector (4 bytes)
		Tx Rate In Kbps of the whole sector (4 bytes)
		Rx Rate In Fps of the whole sector (4 bytes)
		Tx Rate In Fps of the whole sector (4 bytes)
		Peak Throughput in the DL direction in Kbps (4 bytes)
		Peak Throughput in the UL direction in Kbps (4 bytes)
		Tx Ratio (2 bytes)
		Chain 1 Rss (1 byte)
		Chain 2 Rss (1 byte)
		Chain 3 Rss (1 byte)
		HBS Current Rate Index (2 bytes)
		HBS Current Rate CBW (1 bytes)
		HBS Current Rate GI (1 bytes)"
		::= { fibeAir4800HsuAir 6 }		
		
	fibeAir4800HsuAirRemoteCompressedStatic OBJECT-TYPE
		SYNTAX  DisplayString
		ACCESS  read-only
		STATUS  mandatory
		DESCRIPTION
		"Holds all the configuration data of the HBS in a compressed format.
		Helps the NMS to get info regarding new Unregistered links.
		Fields Included:
		Location			(32 bytes)
		IP address			(8 bytes in hexa)
		Subnet mask			(8 bytes in hexa)
		HBS Antenna type		(1 byte)
		HBS Agent Version (4 bytes)
		HBS Name (32 bytes)"
		::= { fibeAir4800HsuAir 7 }	
		
	fibeAir4800HsuAirRssThreshSync OBJECT-TYPE
		SYNTAX  INTEGER
		ACCESS  read-write
		STATUS  mandatory
		DESCRIPTION
		"HSUs will be sychnornized immediately if RSS is better than threshold."
		::= { fibeAir4800HsuAir 8 }
		
	-- ###########################################################
	--                      HSU Air Alignment
	-- ###########################################################

	fibeAir4800HsuAirAlignment OBJECT IDENTIFIER ::= { fibeAir4800HsuAir 9 }

	fibeAir4800HsuAirAlignmentCmd OBJECT-TYPE
		SYNTAX  INTEGER	{
			startAlignmentProcess      (1),
			evaluateCurrentManualAngle (2),
			finishAlignmentProcess	   (3),
			abortAlignmentProcess      (4),
			evaluteBestManualAngle     (5),
			stopAlignmentProcess       (6)
			}
		ACCESS  read-write
		STATUS  mandatory
		DESCRIPTION
		"1 Start Alignment process and initialize the GIRO
		 2 Evaluate current manual angle
		 3 Finish Alignment process
		 4 Abort Alignment process
		 5 Evaluate best manual angle
		 6 Stop Alignment process"
		::= { fibeAir4800HsuAirAlignment 1 }

	fibeAir4800HsuAirAlignmentStatus OBJECT-TYPE
		SYNTAX  INTEGER	{
		        na                    (-1),
			iss		      (1),
			csa		      (2),
			biDirectionalLink     (3),
			evaluate2x2	      (4),
			evaluate3x3	      (5),
			alignmentFinished     (6)
			}
		ACCESS  read-only
		STATUS  mandatory
		DESCRIPTION
		"Antenna Alignment status:
		 -1 N/A (for non BSA products)
		  1 ISS (scanning for HBS)
		  2 CSA (Sync to HBS, waiting for Evaluation command)
		  3 Bi-directional link
		  4 Evaluate 2x2
		  5 Evaluate 3x3
		  6 Alignment Finished."
		::= { fibeAir4800HsuAirAlignment 2 }

	fibeAir4800HsuAirAlignment3x3Step OBJECT-TYPE
		SYNTAX  INTEGER
		ACCESS  read-only
		STATUS  mandatory
		DESCRIPTION
		"Step number out of total steps in Throughput evaluation for 3x3 scenario."
		::= { fibeAir4800HsuAirAlignment 3 }

	fibeAir4800HsuAirAlignment3x3TotalSteps OBJECT-TYPE
		SYNTAX  INTEGER
		ACCESS  read-only
		STATUS  mandatory
		DESCRIPTION
		"Total  steps in Throughput evaluation for 3x3 scenario."
		::= { fibeAir4800HsuAirAlignment 4 }

	fibeAir4800HsuAirAlignmentEvalTo OBJECT-TYPE
		SYNTAX  INTEGER
		ACCESS  read-write
		STATUS  mandatory
		DESCRIPTION
		"Evaluation timeout."
		::= { fibeAir4800HsuAirAlignment 5 }

	-- ###########################################################
	--                      HSU Air Alignment Last Report
	-- ###########################################################

	fibeAir4800HsuAirAlignmentLastReport OBJECT IDENTIFIER ::= { fibeAir4800HsuAirAlignment 6 }

	fibeAir4800HsuAirAlignmentLastReportManualAngle OBJECT-TYPE
		SYNTAX  INTEGER
		ACCESS  read-only
		STATUS  mandatory
		DESCRIPTION
		"The angle of the antenna. Used in the alignment process."
		::= { fibeAir4800HsuAirAlignmentLastReport 1 }

	fibeAir4800HsuAirAlignmentLastReportTputUpSector OBJECT-TYPE
		SYNTAX  INTEGER
		ACCESS  read-only
		STATUS  mandatory
		DESCRIPTION
		"Expected throughput for the whole sector in the Uplink direction in this angle."
		::= { fibeAir4800HsuAirAlignmentLastReport 2 }

	fibeAir4800HsuAirAlignmentLastReportTputDownSector OBJECT-TYPE
		SYNTAX  INTEGER
		ACCESS  read-only
		STATUS  mandatory
		DESCRIPTION
		"Expected throughput for the whole sector in the Downlink direction in this angle."
		::= { fibeAir4800HsuAirAlignmentLastReport 3 }

	fibeAir4800HsuAirAlignmentLastReportMcsIndexUp OBJECT-TYPE
		SYNTAX  INTEGER
		ACCESS  read-only
		STATUS  mandatory
		DESCRIPTION
		"MCS index of the link in the uplink direction."
		::= { fibeAir4800HsuAirAlignmentLastReport 4 }
		
	fibeAir4800HsuAirAlignmentLastReportMcsIndexDown OBJECT-TYPE
		SYNTAX  INTEGER
		ACCESS  read-only
		STATUS  mandatory
		DESCRIPTION
		"MCS index of the link in the downlink direction."
		::= { fibeAir4800HsuAirAlignmentLastReport 5 }		

	fibeAir4800HsuAirAlignmentLastReportState OBJECT-TYPE
		SYNTAX  INTEGER	{
			finishedSuccessfully		     (1),
			partialEvaluationTimeoutExceeded (2),
			evaluationAbortedTimeoutExceeded (3),
			evaluationAbortedUnstableAntenna (4),
			evaluationAbortedSyncLost	     (5),
			evaluationAbortedExternalCommand (6),
			evaluating                       (7)
			}
		ACCESS  read-only
		STATUS  mandatory
		DESCRIPTION
		"State of the Evaluation
		 1 Finished successfully
		 2 Partial Evaluation (Timeout Exceeded)
		 3 Evaluation Aborted (Timeout Exceeded)
		 4 Evaluation aborted (Unstable Antenna)
		 5 Evaluation aborted (Sync Lost)
		 6 Evaluation aborted (External command)
		 7 Evaluating."
		::= { fibeAir4800HsuAirAlignmentLastReport 6 }

	fibeAir4800HsuAirAlignmentLastReportElectronicAnglesHsu OBJECT-TYPE
		SYNTAX  DisplayString
		ACCESS  read-only
		STATUS  mandatory
		DESCRIPTION
		"Electronic angles of 3 chains in the HSU side separated by comma."
		::= { fibeAir4800HsuAirAlignmentLastReport 7 }
		
	fibeAir4800HsuAirAlignmentLastReportElectronicAnglesHbs OBJECT-TYPE
		SYNTAX  DisplayString
		ACCESS  read-only
		STATUS  mandatory
		DESCRIPTION
		"Electronic angles of 3 chains in the HBS side separated by comma."
		::= { fibeAir4800HsuAirAlignmentLastReport 8 }

	fibeAir4800HsuAirAlignmentLastReportRss  OBJECT-TYPE
		SYNTAX  DisplayString
		ACCESS  read-only
		STATUS  mandatory
		DESCRIPTION
		"RSS on chain 1, 2 and 3 (separated by comma)"
		::= { fibeAir4800HsuAirAlignmentLastReport 9 }
		
	fibeAir4800HsuService OBJECT IDENTIFIER ::= { fibeAir4800Hsu 2 }
	
	fibeAir4800HsuServiceCommandStr OBJECT-TYPE
		SYNTAX  DisplayString
		ACCESS  read-write
		STATUS  mandatory
		DESCRIPTION
		"Ability to perform special command in the HSU.
		Format (string): Operation, Param1, Param2,....| ParamN."
		::= { fibeAir4800HsuService 1 }		
		
	fibeAir4800HsuServiceHsuType OBJECT-TYPE
		SYNTAX  INTEGER	{
			fixed		(1),
			stationary	(2),
			mobile		(3),
			transport	(4)
			}
		ACCESS  read-write
		STATUS  mandatory
		DESCRIPTION
		"HSU type (1 = Fixed, 2 = Stationary, 3 = Mobile, 4 = Transport)"
		::= { fibeAir4800HsuService 2 }
		
	fibeAir4800HsuServiceHsuLevel OBJECT-TYPE
		SYNTAX  INTEGER
		ACCESS  read-write
		STATUS  mandatory
		DESCRIPTION
		"HSU level (1 .. 4)"
		::= { fibeAir4800HsuService 3 }
	
	-- ###########################################################
	--                      HSU Ethernet 
	-- ###########################################################
	
	fibeAir4800HsuEthernet OBJECT IDENTIFIER ::= { fibeAir4800Hsu 3 }
	
	fibeAir4800HsuEthernetPoE OBJECT IDENTIFIER ::= { fibeAir4800HsuEthernet 1 }
	
	fibeAir4800HsuEthernetPoESupported OBJECT-TYPE
		SYNTAX  INTEGER {notSupported(1), supported(2)}
		ACCESS  read-only
		STATUS  mandatory
		DESCRIPTION
		"Indicated if this HSU has special port for PoE devices."
		::= { fibeAir4800HsuEthernetPoE 1 }
		
	fibeAir4800HsuEthernetPoETemperature OBJECT-TYPE
		SYNTAX  INTEGER
		ACCESS  read-only
		STATUS  mandatory
		DESCRIPTION
		"Holds the temperature (Celsius) of the POE component."
		::= { fibeAir4800HsuEthernetPoE 2 }
		
	fibeAir4800HsuEthernetPoEEquConsumption OBJECT-TYPE
		SYNTAX  INTEGER
		ACCESS  read-only
		STATUS  mandatory
		DESCRIPTION
		"Holds the consumption of the connected equipment (milliampere)."
		::= { fibeAir4800HsuEthernetPoE 3 }
		
	fibeAir4800HsuEthernetPoEEquVoltage OBJECT-TYPE
		SYNTAX  INTEGER
		ACCESS  read-only
		STATUS  mandatory
		DESCRIPTION
		"Holds the voltage of the connected equipment (Volt)."
		::= { fibeAir4800HsuEthernetPoE 4 }
		
	-- ###########################################################
	--                      General
	-- ###########################################################

	fibeAir4800General OBJECT IDENTIFIER ::= { fibeAir4800 100 }

	fibeAir4800GeneralTrapDescription OBJECT-TYPE
		SYNTAX  DisplayString
		ACCESS  read-only
		STATUS  mandatory
		DESCRIPTION
		"Trap's Description. Used for Trap parameters."
		::= { fibeAir4800General 1 }

	fibeAir4800GeneralTrapSeverity OBJECT-TYPE
		SYNTAX  INTEGER	{
			event		(1),
			normal		(2),
			warning		(4),
			minor		(8),
			major		(16),
			critical	(32)
			}
		ACCESS  read-only
		STATUS  mandatory
		DESCRIPTION
		"Trap's Severity. Used for Trap parameters."
		::= { fibeAir4800General 2 }
		
	fibeAir4800GeneralCookie OBJECT-TYPE
		SYNTAX  DisplayString
		ACCESS  read-write
		STATUS  mandatory
		DESCRIPTION
		"Reserved for the Manager application provided with the product, used for saving user preferences affecting ODU operation."
		::= { fibeAir4800General 3 }

	fibeAir4800GeneralEcChangesCounter OBJECT-TYPE
		SYNTAX INTEGER
		ACCESS  read-only
		STATUS mandatory
		DESCRIPTION
		"This counter is initialized to 0 after a device reset and is incremented upon each element constant write operation
		via SNMP or Telnet."
		::= { fibeAir4800General 4 }  
		
	fibeAir4800GeneralTelnetSupport OBJECT-TYPE
		SYNTAX  INTEGER	{
			enable		(1),
			disable		(2)
			}
		ACCESS  read-write
		STATUS  mandatory
		DESCRIPTION
		"Enable/Disable Telnet protocol."
		::= { fibeAir4800General 5 }

	fibeAir4800GeneralWISupport OBJECT-TYPE
		SYNTAX  INTEGER	{
			mandatoryDisabled(1),
			mandatoryEnabled(2),
			disabled(3),
			enabled	(4)
			}
		ACCESS  read-write
		STATUS  mandatory
		DESCRIPTION
		"Enable/Disable Web Interface protocol.
		  Mandatory Disabled - No option to enable the feature.
		  Mandatory Enabled - No option to disable the feature."
		::= { fibeAir4800General 6 }
			
	fibeAir4800GeneralSNMPSupport OBJECT-TYPE
		SYNTAX  INTEGER	{
			enabled(1),
			snmpv1Only(2),
			snmpv3Only(3)
			}
		ACCESS  read-write
		STATUS  mandatory
		DESCRIPTION
		"Enable/Disable SNMP protocols"
		::= { fibeAir4800General 7 }

	-- ###########################################################
	--                 Traps Section
	-- ###########################################################

	--
	--	The ifIndex, Unit, Time_T and Alarm Id will be bind to the Trap only if
	--	fibeAir4800OduAgnGenAddTrapExt	= 'yes'.
	--

	trunkStateChanged TRAP-TYPE
		ENTERPRISE fibeAir4800
		VARIABLES { fibeAir4800GeneralTrapDescription, fibeAir4800OduAgnCurrAlarmSeverity, fibeAir4800IduTdmIfIndex,
		fibeAir4800IduTdmLineStatus, fibeAir4800OduAgnCurrAlarmIfIndex, fibeAir4800OduAgnCurrAlarmUnit,
		fibeAir4800OduAgnCurrAlarmTimeT, fibeAir4800OduAgnCurrAlarmId }
		--&ACTIONS  { normal }
		--&MESG "$'1"
		DESCRIPTION
		"
		Indicates a change in the state of one of the TDM trunks.
		Raised by both sides of the link.
		Contains 3 parameters:
		1 - Description: TDM Interface %n - %x
		2 - %n: Is the trunk number
		3 - %x: Is the alarm type and can be one of the following: Normal, AIS, LOS, Loopback
		"
		::= 1

	linkUp TRAP-TYPE
		ENTERPRISE fibeAir4800
		VARIABLES { fibeAir4800GeneralTrapDescription, fibeAir4800OduAgnCurrAlarmSeverity, fibeAir4800OduAgnCurrAlarmIfIndex, 
		fibeAir4800OduAgnCurrAlarmUnit, fibeAir4800OduAgnCurrAlarmTimeT, fibeAir4800OduAgnCurrAlarmId  }
		--&ACTIONS  { normal }
		--&CLEARS   { 3 }
		--&MESG "$'1"
		DESCRIPTION
		"
		Indicates that the radio link is up.
		Contains a single parameter, which is its description:
		1 - Description: Radio Link - Sync on channel %n GHz.
		%n Is the channel frequency in GHz.
		"
		::= 2

	linkDown TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { critical }
		--&MESG "$'1"
		DESCRIPTION
		"
		Indicates that the radio link is down.
		Contains a single parameter, which is its description:
		1 - Description: Radio Link - Out of Sync. The reason is: %s.
		%s Is the reason.
		"
		::= 3

	detectIDU TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 5 }
		--&MESG "$'1"
		DESCRIPTION
		"
		Indicates that the IDU was detected.
		Raised by both sides of the link.
		Contains a single parameter, which is its description:
		1 - Description: IDU of Type %s was Detected.
		%s Is the type of the IDU.
		"
		::= 4

	disconnectIDU TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that the IDU was disconnected.
		Raised by both sides of the link.
		Contains a single parameter, which is its description:
		1 - Description: IDU Disconnected.
		"
		::= 5

	mismatchIDU TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates a mismatch between the IDUs.
		Raised by the master only.
		Contains a single parameter, which is its description:
		1 - Description: IDUs Mismatch: One Side is %s and the Other is %s.
		%s Is the type of the IDU.
		"
		::= 6

	openedServices TRAP-TYPE
		ENTERPRISE fibeAir4800
		VARIABLES { fibeAir4800GeneralTrapDescription, fibeAir4800OduAgnCurrAlarmSeverity, fibeAir4800IduSrvDesiredTrunks,
		fibeAir4800IduSrvActiveTrunks, fibeAir4800OduAgnCurrAlarmIfIndex, fibeAir4800OduAgnCurrAlarmUnit,
		fibeAir4800OduAgnCurrAlarmTimeT, fibeAir4800OduAgnCurrAlarmId }
		--&ACTIONS  { normal }
		--&MESG "$'1"
		DESCRIPTION
		"
		Indicates that services were opened. Raised by the master only.
		Contains 3 parameters:
		1 - Description: %n2 out of %n1 Requested TDM Trunks have been Opened
		2 - %n1: Is the requested number of TDM truncks
		3 - %n2: Is the actual number of TDM trunks that were opened
		"
		::= 7

	closedServices TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }	
		--&CLEARS   { 100 }
		--&MESG "$'1"
		DESCRIPTION
		"
		Indicates that services were closed.
		Raised by the master only.
		Contains a single parameter, which is its description:
		1 - Description: TDM Service has been closed. The reason is: %s.
		%s Is the reason.
		"
		::= 8

	incompatibleODUs TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { critical }
		--&MESG "$'1"
		DESCRIPTION
		"
		Indicates that the ODUs are incompatible.
		Contains a single parameter, which is its description:
		1 - Description: Incompatible ODUs.
		"
		::= 9

	incompatibleIDUs TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that the IDUs are incompatible.
		Contains a single parameter, which is its description:
		1 - Description: Incompatible IDUs.
		"
		::= 10

	incompatibleOduIdu TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that the ODU and IDU are incompatible.
		Contains a single parameter, which is its description:
		1 - Description: The IDU could not be loaded. The reason is: %s.
		%s Is the incompatibility type.
		"
		::= 11

	probingChannel TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that the ODU is monitoring radar activity.			
		Contains a single parameter, which is its description:
		1 - Description: Monitoring for radar activity on channel %n GHz.
		%n is the channel frequency in GHz.
		"
		::= 12

	radarDetected TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that radar activity was detected.
		Contains a single parameter, which is its description:
		1 - Description: Radar activity was detected in %s, on channel %n GHz.
		%s Is the site name.
		%n Is the channel frequency in GHz.
		"
		::= 13
		
	transmittingOnChannel TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that the ODU is transmitting on channel.
		Contains a single parameter, which is its description:
		1 - Description: Transmitting on channel %n GHz.
		%n Is the channel frequency in GHz.
		"
		::= 14

	scanningChannels TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that the ODU is scanning channels.
		Contains a single parameter, which is its description:
		1 - Description: Channel scanning in progress.
		"
		::= 15
		
	incompatiblePartner TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { critical }
		--&MESG     "$'1"
		DESCRIPTION
		"
		Indicates that configuration problem was detected and that link installation is required in order to fix it.
		Contains a single parameter, which is its description:
		1 - Description: Configuration problem detected. Link installation required.
		"
		::= 16

	timeClockSet TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that the ODU time clock was set.
		Contains a single parameter, which is its description:
		1 - Description: The time was set to: %p.
		%p Is the date and time.
		"
		::= 17

	configurationChanged TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG "$'1"
		DESCRIPTION
		"
		Indicates that the ODU recovered from an error, but there are configuration changes.
		Contains two parameters:
		1 - Description: Configuration changed. Error code is: %n.
		2 - %n number.
		"
		::= 18

	hssOpStateChangedToINU TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 119 }
		--&MESG     "$'1"
		DESCRIPTION
		"
		Indicates that the HSS operating state was changed to INU type.
		Contains a single parameter, which is its description:
		1 - Description: HSS operating state was changed to: INU.
		"
		::= 19

	hssOpStateChangedToHSM TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 119 }
		--&MESG     "$'1"
		DESCRIPTION
		"
		Indicates that the HSS operating state was changed to HSM type.
		Contains a single parameter, which is its description:
		1 - Description: HSS operating state was changed to: HSM.
		"
		::= 20

	hssOpStateChangedToHSC TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 120 }
		--&MESG     "$'1"
		DESCRIPTION
		"
		Indicates that the HSS operating state was changed to HSC type.
		Contains a single parameter, which is its description:
		1 - Description: HSS operating state was changed to: HSC_DT/HSC_CT.		
		"
		::= 21
	
	vlanModeActive TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		" Indicates to non-VLAN PC that after 2 minutes the system will support only VLAN
		tag on management interface. Contains a single parameter, which is its description:
		1 - Description: VLAN Mode is active. Non-VLAN traffic will be blocked in 2 minutes.
		"
		::= 22
	
	spectrumAnalysis TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that the ODU is in Spectrum Analysis mode.
		Contains a single parameter, which is its description:
		1 - Description: Spectrum analysis in progress.
		"
		::= 23
		
	hbsHsuDeregisteredOffline TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that a HSU was deregistered offline (out of link)
		"
		::= 24
	
	hbsHsuDeregisteredSuccessfully TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that a HSU was deregistered successfully
		"
		::= 25
		
	hbsHsuRegisteredSuccessfully TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that a HSU was registered successfully
		"
		::= 26
		
	hbsHsuRegistrationFailed TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that registration has failed
		"
		::= 27
		
	hbsHsuViolatedState TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates (on the HBS side) that a HSU is is violated state
		"
		::= 28
		
	hsuViolatedState TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates (on the HSU side) that the HSU is is violated state
		"
		::= 29

	hbsUnregisteredSynchronizedHsu TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates an unregistered HSU has been synchronized.
		"
		::= 30
		
	hbsUnregisteredUnsynchronizedHsu TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates an unregistered HSU lost synchronization.
		"
		::= 31
		
	cableQuality TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		1Gbps rate is not supported due to bad line quality.
		"
		::= 32
		
	httpAuthentication TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		HTTP Authentication Failure.
		"
		::= 33
		
	telnetAuthentication TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Telnet Authentication Failure.
		"
		::= 34

	tdmServiceAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that TDM Service is in alarm state.
		Contains a single parameter, which is its description:
		1 - Description: TDM Service - Alarm.
		"
		::= 100

	ethServiceClosed TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that Ethernet Service is closed.
		Contains a single parameter, which is its description:
		1 - Description: Ethernet Service is closed.
		"
		::= 101

	ethServiceNotPermitted TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that Ethernet Service is not permitted.
		Contains a single parameter, which is its description:
		1 - Description: A valid IDU could not be detected at %s. Please check your configuration.
		%s - Is the Local Site name or Remote Site name or both sides of the Link.
		"
		::= 102

	encryptionAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates an encryption key mismatch.
		Contains a single parameter, which is its description:
		1 - Description: Encryption Status - Failed. No Services are available.
		"
		::= 103

	changeLinkPasswordAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that a failure has occurred while attempting to change the Link Password.
		Contains a single parameter, which is its description:
		1 - Description: Failed to change the Link Password at/on: %s.
		%s - Is the Local Site name or Remote Site name or both sides of the Link.
		"
		::= 104

	externalAlarmInPort1Alarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		The trap is sent every time an alarm occurs in the External Alarm Input of port #1.
		Contains a single parameter, which is its description:
		1 - Description: External Alarm 1 - <User Text> - Alarm.
		"
		::= 105

	externalAlarmInPort2Alarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		The trap is sent every time an alarm occurs in the External Alarm Input of port #2.
		Contains a single parameter, which is its description:
		1 - Description: External Alarm 2 - <User Text> - Alarm.
		"
		::= 106

	bitFailedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { critical }
		--&MESG "$'1"
		DESCRIPTION
		"
		The trap is sent if there is no way to recover from the situation.		
		Contains two parameters:
		1 - Description: ODU power up built in test failed. Error code is: %n
		2 - %n number
		"
		::= 107

	wrongConfigurationLoadedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		The trap is sent if there is a way to recover from the situation.		
		Contains two parameters:
		1 - Description: Wrong configuration loaded. Error code is: %n
		2 - %n number
		"
		::= 108

	lanPort1DisconnectedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the LAN port 1 status changed to disconnected.		
		Contains a single parameter, which is its description:
		1 - Description: LAN port 1 status changed to disconnected.
		"
		::= 109

	lanPort2DisconnectedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the LAN port 2 status changed to disconnected.		
		Contains a single parameter, which is its description:
		1 - Description: LAN port 2 status changed to disconnected.
		"
		::= 110

	mngPortDisconnectedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the management port status changed to disconnected.		
		Contains a single parameter, which is its description:
		1 - Description: Management port status changed to disconnected.
		"
		::= 111

	externalAlarmInPort3Alarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		The trap is sent every time an alarm occurs in the External Alarm Input of port #3.
		Contains a single parameter, which is its description:
		1 - Description: External Alarm 3 - <User Text> - Alarm.
		"
		::= 112

	externalAlarmInPort4Alarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		The trap is sent every time an alarm occurs in the External Alarm Input of port #4.
		Contains a single parameter, which is its description:
		1 - Description: External Alarm 4 - <User Text> - Alarm.
		"
		::= 113

	swVersionsMismatchFullCompatibilityAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { warning }
		--&MESG "$'1"
		DESCRIPTION
		"
		The trap is sent if SW versions mismatch with full link functionality.
		Contains a single parameter, which is its description:
		1 - Description: Software versions mismatch - full link functionality
		"
		::= 114

	swVersionsMismatchRestrictedCompatibilityAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { minor }
		--&MESG "$'1"
		DESCRIPTION
		"
		The trap is sent if SW versions mismatch with restricted link functionality.
		Contains a single parameter, which is its description:
		1 - Description: Software versions mismatch - restricted link functionality
		"
		::= 115

	swVersionsMismatchSoftwareUpgradeRequired TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		The trap is sent if SW versions mismatch and SW upgrade is required.
		Contains a single parameter, which is its description:
		1 - Description: Software versions mismatch - Software upgrade required
		"
		::= 116

	swVersionsIncompatible TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { critical }
		--&MESG "$'1"
		DESCRIPTION
		"
		The trap is sent if SW versions are incompatible.
		Contains a single parameter, which is its description:
		1 - Description: SW Versions incompatible
		"
		::= 117

	hssMultipleSourcesDetectedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that multiple sync pulse sources were detected.
		Contains a single parameter, which is its description:
		1 - Description: HSS multiple sync sources were detected.
		"
		::= 118

	hssSyncToProperSourceStoppedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that synchronization to a proper sync pulse source was stopped.
		Contains a single parameter, which is its description:
		1 - Description: HSS sync pulse - Down. The reason is: %s.
		%s - Is the reason for the sync down.
		"
		::= 119

	hssSyncPulseDetectedAlarm TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that HSS additional sync pulse was detected.
		Contains a single parameter, which is its description:
		1 - Description: HSS additional sync pulse was detected.		
		"
		::= 120

	tdmBackupAlarm TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that the TDM backup link was activated.
		Contains a single parameter, which is its description:
		1 - Description: TDM backup alarm - backup link was activated.
		"
		::= 121
		
	linkLockUnauthorizedRemoteODU TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that the remote ODU is unauthorized. 
		Contains a single parameter, which is its description:
		1 - Description: Unauthorized remote ODU connection rejected.
		"
		::= 122
		
	linkLockUnauthorizedODU TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that the ODU is unauthorized. 
		Contains a single parameter, which is its description:
		1 - Description: Unauthorized ODU connection rejected.
		"
		::= 123
		
	hotStandbyAlarm TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that the hot standby secondary link was activated.
		Contains a single parameter, which is its description:
		1 - Description: Secondary Link Is Active.
		"
		::= 124

	sfpInsertion TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that a device was inserted to SFP Port
		"
		::= 126

	sfpPort1DisconnectedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the SFP port 1 status changed to disconnected.		
		Contains a single parameter which is its description:
		1 - Description: SFP port 1 status changed to disconnected.
		"
		::= 127
		
	ringRplStateActiveAlarm TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		RPL state changed to Active.
		"
		::= 128
			

	desiredRatioCanNotBeAppliedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { minor }
		--&MESG "$'1"
		DESCRIPTION
		"
		Indicates Desired UL/DL RAtio Can Not Be Applied.
		"
		::= 129
		
	cbwMismatch TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates that a Channel Bandwidth mismatch was detected.		
		Contains two parameters:
		1 - Description: Channel Bandwidth Mismatch: one side is %n0 MHz and the other is %n1 MHz.
		%n0 is the local Channel Bandwidth value in MHz.
		%n1 is the remoet Channel Bandwidth value in MHz."
		::= 130

	gpsNotSynchronized TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that the GPS is not synchronized with satellites.
		Pulses are self generated.
		"
		::= 131
		
	pdTooHighDueCbwLimitations TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG     "$'1"
		DESCRIPTION
		"
		Indicates that link cannot be established because 
		link range is too large for channel bandwidth.
		"
		::= 132
		
	hbsEncryptionAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates an encryption key mismatch.
		Contains a single parameter, which is its description, including the HSU's name
		"
		::= 133
		
	hbsEhServiceClosedToHsu TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates an encryption key mismatch.
		Contains a single parameter, which is its description, including the HSU's name
		"
		::= 134

	hbsUnsynchronizedHsuAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { warning }
		--&MESG "$'1"
		DESCRIPTION
		"
		Indicates a registered HSU lost synchronization.
		"
		::= 135
		
	hbsInactiveHbsAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates HBS is InActive.
		"
		::= 136
		
	incompatibleHsu TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { critical }
		--&MESG "$'1"
		DESCRIPTION
		"
		Indicates that the HSU is not compatible to HBS.
		Contains a single parameter, which is its description:
		1 - Description: Incompatible ODUs.
		"
		::= 137
		
	hsuUnsupportedBeacon TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { warning }
		--&MESG "$'1"
		DESCRIPTION
		"
		Indicates an unsupported beacon has arrived at HSU
		"
		::= 138
		
	lanPortDisconnectedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the LAN port status changed to disconnected.		
		Contains a single parameter, which is its description:
		1 - Description: LAN port status changed to disconnected.
		"
		::= 139
		
	poePortDisconnectedAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the POE port status changed to disconnected.		
		Contains a single parameter, which is its description:
		1 - Description: POE port status changed to disconnected.
		"
		::= 140
		
	poePowerConsumptionAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the POE Power Consumption is above allowed maximum.		
		Contains a single parameter, which is its description:
		1 - Description: POE consumption above allowed maximum. port closed.
		"
		::= 141
		
	hobupFaultyStateAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		This Alarm will indicate that the Hot Backup module is in faulty state.
		1 - Description: Hot Backup fault detected: %s unit.
		%s - Primary Or Secondary Unit
		"
		::= 149

	gpsOverCurrentAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the GPS Antenna current consumption is above allowed maximum.		
		Contains a single parameter, which is its description:
		1 - Description: GPS Antenna current consumption above allowed maximum. GPS closed.
		"
		::= 150
		
	gpsCommunicationFailiureAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the GPS data isn't received.		
		Contains a single parameter, which is its description:
		1 - Description: GPS Communication failiure.
		"
		::= 151
	
	temperatureThresholdAlarm TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		Indicates the board temperature is above allowed maximum.		
		Contains a single parameter, which is its description:
		1 - Description: GPS Antenna current consumption above allowed maximum. GPS closed.
		"
		::= 152
		
	localRouterDiscoveryStatus TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		This Alarm will indicate that we have no connection with local train router.
		1 - Description: MacLearningUpdate detected disconnection with local train router %s
		%s - local train IP
		"
		::= 153
	
	trackRouterDiscoveryStatus TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		This Alarm will indicate that we have no connection with Track side router.
		1 - Description: MacLearningUpdate detected disconnection with Track side router %s
		%s - Default gateway IP
		"
		::= 154
		
	lastUserSnmpAccessOverHourAgo TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG "$'1"
		DESCRIPTION
		"
		This trap will indicate that the last access of the accessing user was more than an hour ago.
		1 - Description: User %s performed SNMP access after more than an hour.
		%s - user name
		"
		::= 155
		
	btsTargetUnreachable TRAP-TYPE
		ENTERPRISE fibeAir4800
		VARIABLES { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { major }
		--&MESG "$'1"
		DESCRIPTION
		"
		This Alarm will indicate that we have no connection with Bts desired target.
		1 - Description: TNC detected disconnection with the BTS target %s
		%s - Default gateway IP
		"
		::= 156
		
	tdmServiceClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 100 }
		--&MESG     "$'1"
		DESCRIPTION
		"
		Indicates that TDM Service fault is cleared.
		Contains a single parameter, which is its description:
		1 - Description: TDM Service - Normal.
		"
		::= 200

	ethServiceOpened TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 101 }
		--&MESG     "$'1"
		DESCRIPTION
		"
		Indicates that Ethernet Service has been opened.
		Contains a single parameter, which is its description:
		1 - Description: Ethernet Service has been opened.
		"
		::= 201

	encryptionClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 103 }
		--&MESG     "$'1"
		DESCRIPTION
		"
		Indicates that encryption is OK.
		Contains a single parameter, which is its description:
		1 - Description: Encryption Status - Normal.
		"
		::= 203

	changeLinkPasswordClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 104 }
		--&MESG     "$'1"
		DESCRIPTION
		"
		Indicates that the Link Password was changed successfully.
		Contains a single parameter, which is its description:
		1 - Description: Link Password has been changed at/on: %s.
		%s - Is the Local Site name or Remote Site name or both sides of the Link.
		"
		::= 204

	externalAlarmInPort1Clear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 105 }
		--&MESG     "$'1"
		DESCRIPTION
		"
		This Trap is sent every time an External Alarm Input fault of port # 1 is cleared.
		Contains a single parameter, which is its description:
		1 - Description: External Alarm 1 - <User Text> - Alarm Cleared.
		"
		::= 205	

	externalAlarmInPort2Clear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 106 }
		--&MESG     "$'1"
		DESCRIPTION
		"
		This Trap is sent every time an External Alarm Input fault of port # 2 is cleared.
		Contains a single parameter, which is its description:
		1 - Description: External Alarm 2 - <User Text> - Alarm Cleared.
		"
		::= 206
		
	lanPort1Clear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 109 }
		--&MESG     "$'1"
		DESCRIPTION
		"
		Indicates the LAN port 1 status changed to connected.
		Contains two parameters:
		1 - Description: LAN port 1 status changed to connected - %s
		2 - %s Is the Eth. mode (speed & duplex)
		"
		::= 209
		
	lanPort2Clear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 110 }
		--&MESG     "$'1"
		DESCRIPTION
		"
		Indicates the LAN port 2 status changed to connected.
		Contains two parameters:
		1 - Description: LAN port 2 status changed to connected - %s.
		2 - %s Is the Eth. mode (speed & duplex).
		"
		::= 210
		
	mngPortClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 111 }
		--&MESG     "$'1"
		DESCRIPTION
		"
		Indicates the management port status changed to connected.
		Contains two parameters:
		1 - Description: Management port status changed to connected - %s
		2 - %s Is the Eth. mode (speed & duplex)
		"
		::= 211

	externalAlarmInPort3Clear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 112 }
		--&MESG     "$'1"
		DESCRIPTION
		"
		This Trap is sent every time an External Alarm Input fault of port # 3 is cleared.
		Contains a single parameter, which is its description:
		1 - Description: External Alarm 3 - <User Text> - Alarm Cleared.
		"
		::= 212	

	externalAlarmInPort4Clear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 113 }
		--&MESG     "$'1"
		DESCRIPTION
		"
		This Trap is sent every time an External Alarm Input fault of port # 4 is cleared.
		Contains a single parameter, which is its description:
		1 - Description: External Alarm 4 - <User Text> - Alarm Cleared.
		"
		::= 213
	
	swVersionsMatchFullCompatibilityClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 114 }
		--&MESG     "$'1"
		DESCRIPTION
		"
		The trap is sent if SW versions match.
		Contains a single parameter, which is its description:
		1 - Description: Software Versions compatible
		"
		::= 214

	swVersionsMatchRestrictedCompatibilityClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 115 }
		--&MESG     "$'1"
		DESCRIPTION
		"
		The trap is sent if SW versions match and link functionality is not restricted.
		Contains a single parameter, which is its description:
		1 - Description: Software Versions compatible
		"
		::= 215

	swVersionsMatchSoftwareUpgradeRequiredClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 116 }
		--&MESG     "$'1"
		DESCRIPTION
		"
		The trap is sent if SW versions match and SW upgrade is successful.
		Contains a single parameter, which is its description:
		1 - Description: Software Versions compatible
		"
		::= 216

	swVersionsCompatibleClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 117 }
		--&MESG     "$'1"
		DESCRIPTION
		"
		The trap is sent if SW versions compatible
		Contains a single parameter, which is its description:
		1 - Description: Software Versions compatible
		"
		::= 217

	hssMultipleSourcesDisappearedClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 118 }
		--&MESG     "$'1"
		DESCRIPTION
		"
		Indicates that multiple sync pulse sources disappeared.
		Contains a single parameter, which is its description:
		1 - Description: HSS multiple sync pulse sources disappeared.
		"
		::= 218

	hssSyncToProperSourceAchievedClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 119 }
		--&MESG     "$'1"
		DESCRIPTION
		"
		Indicates that synchronization to a proper Sync source was achieved.
		Contains a single parameter, which is its description:
		1 - Description: HSS sync pulse - Up.
		"
		::= 219

	hssSyncPulseDisappearedClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 120 }
		--&MESG     "$'1"
		DESCRIPTION
		"
		Indicates that HSS additional sync pulse disappeared.
		Contains a single parameter, which is its description:
		1 - Description: HSS additional sync pulse was disappeared.		
		"
		::= 220

	tdmBackupClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 121 }
		--&MESG     "$'1"
		DESCRIPTION
		"
		Indicates that the TDM main link was activated.
		Contains a single parameter, which is its description:
		1 - Description: TDM main link was activated.
		"
		::= 221
		
	linkLockAuthorizedRemoteODU TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 122 }
		--&MESG     "$'1"
		DESCRIPTION
		"
		Indicates that the remote ODU is authorized.
		Contains a single parameter, which is its description:
		1 - Description: Authorized remote ODU connection accepted.
		"
		::= 222

	linkLockAuthorizedODU TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 123 }
		--&MESG     "$'1"
		DESCRIPTION
		"
		Indicates that the ODU is authorized.
		Contains a single parameter, which is its description:
		1 - Description: Authorized ODU connection permitted.
		"
		::= 223		

	linkAuthenticationDisabled TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 122 }
		--&MESG     "$'1"
		DESCRIPTION
		"
		Indicates that the Link Lock is disabled.
		Contains a single parameter, which is its description:
		1 - Description: Link Authentication has been disabled.
		"
		::= 224	

	hotStandbyClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 124 }
		--&MESG     "$'1"
		DESCRIPTION
		"
		Indicates that the Primary Link Was Activated.
		Contains a single parameter, which is its description:
		1 - Description: Primary Link Is Active.
		"
		::= 225
		
	sfpExtraction TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that a device was extracted from SFP Port
		"
		::= 226

	sfpPort1Clear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 127 }
		--&MESG     "$'1"
		DESCRIPTION
		"
		Indicates the SFP port 1 status changed to connected.
		Contains two parameters:
		1 - Description: SFP port 1 status changed to connected - %s
		2 - %s Is the Eth. mode (speed & duplex)
		"
		::= 227

	compatibleIdus TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 10 }
		--&MESG     "$'1"
		DESCRIPTION
		"
		Indicates that the ODU has identified compatible Idus on both sides of the link.
		"
		::= 228	

	desiredRatioCanNotBeAppliedClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 129 }
		--&MESG     "$'1"
		DESCRIPTION
		"
		Indicates Current UL/DL Ratio Is Equal To Desired Ratio.
		"
		::= 229
		
	cbwMatch TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 130 }
		--&MESG     "$'1"
		DESCRIPTION
		"
		Indicates that a Channel Bandwidth match was detected.
		Contains a single parameter, which is its description:
		1 - Channel Bandwidth value in MHz.
		"
		::= 230
		
	switchCbwAndChannel TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Indicates that the system is switching Channel Bandwidth and channel frequency.
		Contains two parameters:
		1 - Switching to Channel Bandwith %n0 MHz and to channel %n1 GHz.
		"
		::= 231			
		
	ringRplStateIdle TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 128 }
		--&MESG     "$'1"
		DESCRIPTION
		"
		RPL state changed to Idle.
		"
		::= 232
		
	ringEthServiceStatus TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }		
		--&MESG     "$'1"
		DESCRIPTION
		"
		Indicates Ethernet service's state - blocked \ unblocked.
		Contains a single parameter:
		1 - Description: Ethernet's state (blocked \ unblocked)
		"
		::= 233
		
	ringFirstRpmReceived TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }		
		--&MESG     "$'1"
		DESCRIPTION
		"
		Ring application: in non-RPL link indicates first from a specific RPL was received.
		Contains a single parameter:
		1 - Description: RPM's VLAN ID
		"
		::= 234
		
	ringEthernetSrviceUnblockedTO TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }		
		--&MESG     "$'1"
		DESCRIPTION
		"
		Ring application: in non-RPL link Ethernet service is unblocked due to RPM timeout.		
		"
		::= 235
		
	gpsSynchronized TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 131 }
		--&MESG     "$'1"
		DESCRIPTION
		"
		Indicates that the GPS is synchronized with satellites.
		"
		::= 236

	hbsEncryptionClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 133 }
		--&MESG     "$'1"
		DESCRIPTION
		"
		Indicates that encryption is OK.
		Contains a single parameter, which is its description, including the HSU's name
		"
		::= 237
		
	hbsEhServiceOpenedToHsu TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 134 }
		--&MESG     "$'1"
		DESCRIPTION
		"
		Indicates that encryption is OK.
		Contains a single parameter, which is its description, including the HSU's name
		"
		::= 238

	hbsSynchronizedHsuAlarm TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 135 }
		--&MESG     "$'1"
		DESCRIPTION
		"
		Indicates a registered HSU is synchronized.
		"
		::= 239
		
	hbsActiveHbs TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 136 }
		--&MESG     "$'1"
		DESCRIPTION
		"
		Indicates when HBS has been activated.
		"
		::= 240
		
	switchCBW TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Switching Channel Bandwidth.
		"
		::= 241		

	changeRatio TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		HBS Tx ratio has changed.
		"
		::= 242			

	lanPortClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 139 }
		--&MESG     "$'1"
		DESCRIPTION
		"
		Indicates the LAN port status changed to connected.
		Contains two parameters:
		1 - Description: LAN port status changed to connected - %s
		2 - %s Is the Eth. mode (speed & duplex)
		"
		::= 243

	poePortClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 140 }
		--&MESG     "$'1"
		DESCRIPTION
		"
		Indicates the POE port status changed to connected.
		Contains two parameters:
		1 - Description: POE port status changed to connected - %s
		2 - %s Is the Eth. mode (speed & duplex)
		"
		::= 244	
		
	poePowerConsumptionClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 141 }
		--&MESG     "$'1"
		DESCRIPTION
		"
		Indicates the POE power consumption is valid.
		Contains two parameters:
		1 - Description: POE consumption within limits. port is opened.
		2 - %s Is the Eth. mode (speed & duplex)
		"
		::= 245

	incompatibleHbsHsu TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Incompatible HBS/HSU software versions - no service.
		"
		::= 246

	mobilityLinkOff TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Mobility - Link cannot be established due to:
		1 - The HBS does not support Mobility
		2 - Lack of resources in the HBS for HSU level
		"
		::= 247

	enterLocalConnection TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		Entering Local Connection (Broadcast) Mode.
		"
		::= 248	
	
	hobupActiveStateFaultyClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 149 }
		--&MESG     "$'1"
		DESCRIPTION
		"
		this clear alarm will indicate that the Hot Backup unit is in active state.
		Contains a single parameter, which is its description:
		1 - Description: Hot Backup %s unit activated.
		%s - Primary Or Secondary Unit
		"	
		::= 249	
		
	hobupStandbyState TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		This info fault will indicate that the Hot backup module has entered standby/peer_detection state
		Contains a single parameter, which is its description:
		1 - Description: Hot Backup in Standby state: %s unit.
		%s - Primary Or Secondary Unit
		"	
		::= 250		

	gpsOverCurrentClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 150 }
		--&MESG     "$'1"
		DESCRIPTION
		"
		Indicates the GPS Antenna current consumption is valid.
		"
		::= 251
		
	temperatureThresholdClear TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 152 }
		--&MESG     "$'1"
		DESCRIPTION
		"
		Indicates the board temperature is valid.
		"
		::= 252		
		
	localRouterDiscoverySucceed TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 153 }
		--&MESG     "$'1"
		DESCRIPTION
		"
		Indicated the we succeeded to discover train router in ip %s MAC address %s
		%s Train IP
		%s Train MAC Address
		"
		::= 253	
	
	trackRouterDiscoverySucceed TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 154 }
		--&MESG     "$'1"
		DESCRIPTION
		"
		Indicated the we succeeded to discover track router in ip %s MAC address %s
		%s Train IP
		%s Train MAC Address
		"
		::= 254	
		
	qosVersion2StrictMismatch TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		CPE  doesn't support strict QOS configuration.
		"	
		::= 255
		
	qosVersion2TtlMismatch TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&MESG     "$'1"
		DESCRIPTION
		"
		CPE doesn't support TTL configuration.
		"	
		::= 256
		
	btsTargetIsReachable TRAP-TYPE
		ENTERPRISE fibeAir4800
		VARIABLES   { fibeAir4800GeneralTrapDescription, fibeAir4800OduAgnCurrAlarmSeverity, fibeAir4800OduAgnCurrAlarmIfIndex,
		fibeAir4800OduAgnCurrAlarmUnit, fibeAir4800OduAgnCurrAlarmTimeT, fibeAir4800OduAgnCurrAlarmId }
		--&ACTIONS  { normal }
		--&CLEARS   { 156 }
		--&MESG     "$'1"
		DESCRIPTION
		"
		Indicated the we succeeded to establish connection with the Bts desired target (%s)
		%s Target IP
		"
		::= 257
		
	-- ###########################################################
	--                 Products Section
	-- ###########################################################


	ceragonNetProducts		OBJECT IDENTIFIER ::= { ceragonNet 20 }
	fibeAir4800Family		OBJECT IDENTIFIER ::= { ceragonNetProducts 2 } 
	fibeAir2000Family		OBJECT IDENTIFIER ::= { ceragonNetProducts 3 }
	gpsSynchronizerFamily		OBJECT IDENTIFIER ::= { ceragonNetProducts 4 }
	ceragonNet5000HBSFamily		OBJECT IDENTIFIER ::= { ceragonNetProducts 5 }
        ceragonNet5000HSUFamily		OBJECT IDENTIFIER ::= { ceragonNetProducts 6 }
	ceragonNet6000Family		OBJECT IDENTIFIER ::= { ceragonNetProducts 10 }
	ceragonNetWiFiAPFamily		OBJECT IDENTIFIER ::= { ceragonNetProducts 20 }


	--
	-- the following identifiers are assigned to ODU Products
	--        

	odu	       		    OBJECT IDENTIFIER ::= { fibeAir4800Family 1 }

	oduIntegratedAntenna        OBJECT IDENTIFIER ::= { odu 1 }
	oduExternalAntenna          OBJECT IDENTIFIER ::= { odu 2 }

	--
	-- Suffix 3,4,5,6,7,8,9,10,11,12,13,14,15,16 in the products section
	-- are reserved for backward compatibility.
	--

	odu2000    					OBJECT IDENTIFIER ::= { fibeAir2000Family 1 }

	odu2KIntegratedAntenna        OBJECT IDENTIFIER ::= { odu2000 1 }
	odu2KExternalAntenna          OBJECT IDENTIFIER ::= { odu2000 2 }


	oduGSU						OBJECT IDENTIFIER ::= { gpsSynchronizerFamily  1 }
	
	oduGSUExternalAntenna		OBJECT IDENTIFIER ::= { oduGSU 2 }

	hssSyncUnits				OBJECT IDENTIFIER ::= { gpsSynchronizerFamily 2 }
	
	hssISU						OBJECT IDENTIFIER ::= { hssSyncUnits 1 }
	hssGSU						OBJECT IDENTIFIER ::= { hssSyncUnits 2 }

	oduHBS    					OBJECT IDENTIFIER ::= { ceragonNet5000HBSFamily 1 }

	oduHBSIntegratedAntenna		OBJECT IDENTIFIER ::= { oduHBS 1 }
	oduHBSExternalAntenna		OBJECT IDENTIFIER ::= { oduHBS 2 }

	
	oduHSU    					OBJECT IDENTIFIER ::= { ceragonNet5000HSUFamily 1 }

	oduHSUIntegratedAntenna		OBJECT IDENTIFIER ::= { oduHSU 1 }
	oduHSUExternalAntenna		OBJECT IDENTIFIER ::= { oduHSU 2 }	

	odu6000    					OBJECT IDENTIFIER ::= { ceragonNet6000Family 1 }

	odu6K						OBJECT IDENTIFIER ::= { odu6000 1 }
	
	gateway6000    				OBJECT IDENTIFIER ::= { ceragonNet6000Family 2 }

	gateway6K						OBJECT IDENTIFIER ::= { gateway6000 1 }
	
	odu600    					OBJECT IDENTIFIER ::= { ceragonNetWiFiAPFamily 1 }

	oduWiFiAP					OBJECT IDENTIFIER ::= { odu600 1 }
	
	END
