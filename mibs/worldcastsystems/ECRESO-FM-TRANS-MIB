--
-- ECRESO-FM-TRANS-MIB.mib
--
-- Copyright (c) WorldCast Systems
-- All rights reserved.


ECRESO-FM-TRANS-MIB DEFINITIONS ::= BEGIN

IMPORTS
	OBJECT-GROUP, NOTIFICATION-GROUP
		FROM SNMPv2-CONF
	sysDescr, sysName, sysLocation
		FROM SNMPv2-MIB
	DisplayString, DateAndTime
		FROM SNMPv2-TC
	enterprises, Integer32, Gauge32, OBJECT-TYPE, MODULE-IDENTITY, OBJECT-IDENTITY, NOTIFICATION-TYPE
		FROM SNMPv2-SMI;

transmitter MODULE-IDENTITY
	LAST-UPDATED "202301101047Z"
	ORGANIZATION
		"Ecreso"
	CONTACT-INFO
		"infos@ecreso.com"
	DESCRIPTION
		"Transmitter MIB"


	REVISION "202301101047Z"
	DESCRIPTION
		"Renamed txSfCoMode range."

	REVISION "202212051319Z"
	DESCRIPTION
		"Added txGnPrPresetsAuto3dB."

	REVISION "202210111500Z"
	DESCRIPTION
		"Added syGeAOIPMpx."

	REVISION "202207271420Z"
	DESCRIPTION
		"Added syLiPrAoipdecoder, syLiPrMpxoipdecoder, syLiPrSurestream, syLiPrSynchrostream,
		 syLiReAoipdecoder, syLiReMpxoipdecoder, syLiReSurestream, syLiReSynchrostream,
		 syLiAlAoipdecoder, syLiAlMpxoipdecoder, syLiAlSurestream, syLiAlSynchrostream,
		 eventSyLiAlAoipdecoderPriority, eventSyLiAlAoipdecoderEnable,
		 eventSyLiAlMpxoipdecoderPriority, eventSyLiAlMpxoipdecoderEnable,
		 eventSyLiAlSurestreamPriority, eventSyLiAlSurestreamEnable,
		 eventSyLiAlSynchrostreamPriority, eventSyLiAlSynchrostreamEnable,
		 eventTimeStampSyLiAlAoipdecoder, eventTimeStampSyLiAlMpxoipdecoder,
		 eventTimeStampSyLiAlSurestream, eventTimeStampSyLiAlSynchrostream,
		 eventSyLiAlAoipdecoder, eventSyLiAlMpxoipdecoder, eventSyLiAlSurestream, eventSyLiAlSynchrostream."

	REVISION "202206281200Z"
	DESCRIPTION
		"Added inSoAoipPresence, inSoAoipLeftPeakMax, inSoAoipRightPeakMax, inSoAoipLeftPeak,
		 inSoAoipRightPeak, inSoAoipPeakMax, inSoAoipPeak, inSoAoipLevel, inSoAoipDrive,
		 inSoAoipTrim, inSoAoipFilter, inSoAoipPreacc, inSoAoipLost, inSoAoipAlarmTrig,
		 inSeThAoipTh, inSeThAoipSil, inSeDeAoipBackDelay, inSeDeAoipDelay, inSeSyAoip, inAlAoip, 
		 eventInAlAoipPriority, eventInAlAoipEnable, eventTimeStampInAlAoip and eventInAlAoip."

	REVISION "202206241352Z"
	DESCRIPTION
		"Added maMoMeCur3, maMoAlCur3 and maMoMeVolt3."

	REVISION "202101261413Z"
	DESCRIPTION
		"Added maPaAlrCur, maPaVoltage, maPaAlrVolt, maPaAmbTemp, maPaAlrHeat, maPaAlrTemp,
		 maMoAlSecPref."

	REVISION "202101251443Z"
	DESCRIPTION
		"Added maPsMissing, maPsInputCurrent, maPsInputCurAlr, maPsInputVoltage, maPsInputVoltAlr,
		 maPsOutputCurrent, maPsOutputCurAlr, maPsOutputVoltage, maPsOutputVoltAlr, 
		 maPsAmbTemp, maPsAmbAlr, maPsHeat1Temp, maPsHeat1Alr, maPsFan1Speed, maPsFan1Alr,
		 maPsSerial, maPsSoftRel"

	REVISION "202101201209Z"
	DESCRIPTION
		"Fixed syGeDate description."

	REVISION "202008061322Z"
	DESCRIPTION
		"Added inSeAuBackupMode."

	REVISION "202008061002Z"
	DESCRIPTION
		"Added inSeThAes1Sil, inSeThAes2Sil, inSeThAes3Sil and inSeThAna1Sil."

	REVISION "202008060804Z"
	DESCRIPTION
		"Added inSoTySlot1,inSoTySlot2 and inSoTySlot3."

	REVISION "202008060743Z"
	DESCRIPTION
		"Added inSeDeMpx1BackDelay, inSeDeMpx1Delay, inSeDeMpx2BackDelay and inSeDeMpx2Delay."
	

	REVISION "202008050716Z"
	DESCRIPTION
		"Added 6 inputs to txGnPrGpioMode."

	REVISION "202003171535Z"
	DESCRIPTION
		"Added support for AiO series transmitters, renamed inSePriorities to inSeAudio."
	
	REVISION "201807051651Z"
	DESCRIPTION
		"Added txSfLiSavings, txSfLiBoost and txSfLiCredits."

	REVISION "201806190927Z"
	DESCRIPTION
		"Added maMoMaEffSys, maMoCoMeHeat1, maMoCoMeHeat2, maMoCoMePsuTemp, maMoCoMeIntTemp, maMoCoMeExcTemp, maMoCoAlHeat1, 
		maMoCoAlHeat2, maMoCoAlTemp1, maMoCoAlTemp2, maMoCoAlPsuTemp, maMoCoAlIntTemp, maMoCoAlExcTemp, maMoMeVolt1, 
		maMoMeVolt2, maMoMeCur1, maMoMeCur2, maMoMePin, maMoAlVolt1, maMoAlVolt2, maMoAlCur1, maMoAlCur2, maMoAlPin."

	REVISION "201806061301Z"
	DESCRIPTION
		"Added txSfCoKwhCost."

	REVISION "201806010810Z"
	DESCRIPTION
		"Increased size of rdMaGs and rdAtGs from 64 to 95."

	REVISION "201805301601Z"
	DESCRIPTION
		"Added txSfMeRangeMin,txSfMeRangeMax,txSfMeCurrentValue,txSfMePwr,txSfMeCurSavings,txSfMeCurBoost,txSfMePcons,
		txSfMePconsNoSfm,txSfCoState,txSfCoMode,txSfCoRdsCor,txSfStAct,txSfStAlarm and events eventTxSfStAct,
		eventTxSfStAlarm and their parameters/placeholders.
		Added syLiPrRds,syLiPrSoundProc,syLiPrSfm,syLiPrActivation,syLiReRds,syLiReSoundProc,syLiReSfm,syLiReActivation,
		syLiAlRds,syLiAlSoundProc,syLiAlSfm,syLiAlActivation and events eventSyLiAlRds,eventSyLiAlSoundProc,eventSyLiAlSfm,
		eventSyLiAlActivation and their parameters/placeholders."

	REVISION "201706021742Z"
	DESCRIPTION
		"Marked as obsolete monitoring tree. Added mainetnance tree : maMoMaEffTrans, maMoMaEffPa, maMoMaEffPsu, maMoCcFault, maMoCcWarn, maMoCoMeAmb,
 		maMoCoMeLoad1InputTemp, maMoCoMeLoad1HeatsinkTemp, maMoCoMeLoad2InputTemp, maMoCoMeLoad2HeatsinkTemp, maMoCoMePressure, maMoCoAlAmb,
 		maMoCoAlLoad1Heatsink, maMoCoAlLoad2Heatsink, maMoCoAlPressure, maMoAuMe5V, maMoAuMe12V, maMoAuMeN12V, maMoAuMe24V, maMoAuAlVoltAux,
 		maMoAuAl24V, maMoFanSpeed, maMoFanAlarms, maDrCommunication, maDrFault, maDrWarning, maDrForwardPower, maDrReflectedPower, maDrHeatsink,
 		maDrFanSpeed, maPaCommunication, maPaFault, maPaWarning, maPaForwardPower, maPaReflectedPower,maPaEfficiency, maPaCurrent, maPaHeatMax, maPsVoltageInput,
 		maPsCurrentInput, maPsPowerInput, maPsVoltageOutput, maPsCurrentOutput, maPsPowerOutput, maPsCommunication, maPsFault, maPsWarning, maPsEfficiency
		maPsOutputPower, maPsInputPower."

	REVISION "201705170912Z"
	DESCRIPTION
		"Modified inSeDeLine1Delay, inSeDeLine2Delay, inSeDePlayerDelay, inSeDeMpxDelay and inSeDeMpx34Delay ranges."

	REVISION "201702211553Z"
	DESCRIPTION
		"re-enable moSpMpMeasAtt"

	REVISION "201702171020Z"
	DESCRIPTION
		"Modified min/max range of moSpMpTarget to -120/120."

	REVISION "201702151400Z"
	DESCRIPTION
		"Renamed moAgcLim branch to moSoundProc. Marked as obsolete moSpMpMeasAtt and branches moSpAgc and moSpLimiter.
		Added moSpPrNum, moSpPrBypass and table moSpPrTableName."

	REVISION "201605130830Z"
	DESCRIPTION
		"Added syGeDigMPX and marked eventEquipmentFault and all its bindings and parameters as obsolete."

	REVISION "201604111846Z"
	DESCRIPTION
		"Added monitoring tree : moMaMeVolt1, moMaMeVolt2, moMaMeCur1, moMaMeCur2,
		 moMaMeEffSys, moMaMeEffTrans, moMaMePin, moMainAlVolt1, moMainAlVolt2,
		 moMainAlCur1, moMainAlCur2, moMainAlPin, moCoMeAmb, moCoMeHeat1, moCoMeHeat2,
		 moCoMePsuTemp, moCoMeIntTemp, moCoMePressure, moCoMeExcTemp, moCoAlHeat1,
		 moCoAlHeat2, moCoAlTemp1, moCoAlTemp2, moCoAlPsuTemp, moCoAlIntTemp, moCoAlExcTemp,
		 moCoAlPressure, moAuMe5V, moAuMe12V, moAuMeN12V, moFanMeFan1Speed,
		 moFanMeFan2Speed, moFanAlFan1Alarm and moFanAlFan2Alarm."

	REVISION "201604110818Z"
	DESCRIPTION
		"Added inSeSyMpx34."

	REVISION "201604070947Z"
	DESCRIPTION
		"Added MPX3 and MPX4 to inSeCurrentAudio,moSeCoderCurrentRds,inSeSelectAudio,moSeCoderRdsSelect,
		 moSeCoderScaSelect and moSeCoderCurrentSca ranges.
		Added inAlMpx3, inAlMpx4, inSeThMpx3Th, inSeThMpx4Th, inSeDeMpx34BackDelay, inSeDeMpx34Delay,
		 inSoM3Presence, inSoM4Presence, inSoM3PeakMax, inSoM4PeakMax, inSoM3Peak, inSoM4Peak,
		 inSoM3Level, inSoM4Level, inSoM3Drive, inSoM4Drive, inSoM3Lost, inSoM4Lost, inSoM3AlarmTrig,
		 inSoM4AlarmTrig, inSeMpx3Prio, inSeMpx4Prio, inSeSaMpx3 and inSeSaMpx4.
		Added events eventInAlMpx3 and eventInAlMpx4 with eventInAlMpx3Priority, eventInAlMpx3Enable,
		 eventTimeStampInAlMpx3 and eventInAlMpx4Priority, eventInAlMpx4Enable, eventTimeStampInAlMpx4."

	REVISION "201602240941Z"
	DESCRIPTION
		"Modified min range of inSeThLine1Th to -116."

	REVISION "201601190859Z"
	DESCRIPTION
		"Correction : fixed inSoM1Presence and inSoM2Presence ranges."

	REVISION "201501301248Z"
	DESCRIPTION
		"Correction : put correct timestamp binding in eventMoSfSwitch10MAlarm trap."

	REVISION "201412021554Z"
	DESCRIPTION
		"Correction : Replaced Integer32 with Gauge32 to be in phase with equipments."

	REVISION "201409241008Z"
	DESCRIPTION
		"Added syAlLogging and trap eventSyAlLogging."

	REVISION "201407180804Z"
	DESCRIPTION
		"Modified inSeDeLine1Delay, inSeDeLine2Delay, inSeDePlayerDelay and inSeDeMpxDelay ranges."

	REVISION "201403041101Z"
	DESCRIPTION
		"Added acGnGlDelaySwitch, acGnGlDelayStart, acGnGlSwOnFault and acGnGlSwNoComm."

	REVISION "201311071441Z"
	DESCRIPTION
		"Added moSfSwitch10MAlarm and trap eventMoSfSwitch10MAlarm with its parameters. Added trap counter syGeTrapCounter
		 (and added in trap bindings). Added txGnRfVswrTrig."

	REVISION "201310251455Z"
	DESCRIPTION
		"Added moSfConfOp10M moSfState10M moSfClockSource moSfState1PPS."

	REVISION "201310240931Z"
	DESCRIPTION
		"Added traps eventEquipmentOn, eventHeartBeat, eventConfigChanged, eventEquipmentFault, eventInAlFault and eventMoSfAlarm
		and objects inSeSaLine1, inSeSaLine2, inSeSaPlayer, inSeSaMpx1, inSeSaMpx2, inAlFault, moSfConfDelay, moSfConfState, moSfMeasDelay and moSfAlarm."

	REVISION "201309260953Z"
	DESCRIPTION
		"Added inSeSyLine1, inSeSyLine2, inSeSyPlayer, inSeFadein, rdSeCurrentPs, rdSeCurrentRt, syAlComm and eventSysAlComm (and its parameters)."

	REVISION "201309111434Z"
	DESCRIPTION
		"Marked inSeThMpxTh as obsolete. Replaced with inSeThMpx1Th and inSeThMpx2Th."

	REVISION "201308080909Z"
	DESCRIPTION
		"Added acGnGlManSwLoc."

	REVISION "201307181456Z"
	DESCRIPTION
		"Modified max range of inSeThPlayerTh, inSeThLine2Th from -116 to +0."

	REVISION "201307171334Z"
	DESCRIPTION
		"Modified max range of inSeThMpxTh, inSeThLine1Th from -114 to +24."

	REVISION "201307031354Z"
	DESCRIPTION
		"Modified max range of inSeThMpxTh, inSeThLine1Th to +18."

	REVISION "201306251356Z"
	DESCRIPTION
		"Changed syGeUnit from RO to RW."

	REVISION "201306061627Z"
	DESCRIPTION
		"Added syGeUnit, txGnRfRfPresentMin and txGnPrPresetsRfPresentMin."

	REVISION "201304220951Z"
	DESCRIPTION
		"Added acGnGlMainOpmode and corrected SignalSuppression descriptions."

	REVISION "201303180833Z"
	DESCRIPTION
		"Corrected standby trap description."

	REVISION "201302261409Z"
	DESCRIPTION
		"Set txInterlockLoad to obsolete and added acu interlock ant and load."

	REVISION "201302081424Z"
	DESCRIPTION
		"Added acu tx1 and tx2 com alarms."

	REVISION "201212131603Z"
	DESCRIPTION
		"Added presets, input alarms, ClockTime and MaxPower and some other vars."

	REVISION "201207111504Z"
	DESCRIPTION
		"Added Helios data."

	REVISION "201201101132Z"
	DESCRIPTION
		"Initial version"
	::= { fm 2 }

ecreso OBJECT-IDENTITY
	STATUS current
	DESCRIPTION
		"No description"
	::= { enterprises 6404 }

transv3 OBJECT-IDENTITY
	STATUS current
	DESCRIPTION
		"No description"
	::= { ecreso 3 }

fm OBJECT-IDENTITY
	STATUS current
	DESCRIPTION
		"No description"
	::= { transv3 1 }

eventsParams OBJECT-IDENTITY
	STATUS current
	DESCRIPTION
		"No description"
	::= { transmitter 3 }

eventTxLocalModeParams OBJECT-IDENTITY
	STATUS current
	DESCRIPTION
		"No description"
	::= { eventsParams 1 }

eventTxLocalModePriority OBJECT-TYPE
	SYNTAX Gauge32(0..2147483647)
	MAX-ACCESS read-write
	STATUS current
	DESCRIPTION
		"Priority for eventTxLocalMode event"
	::= { eventTxLocalModeParams 1 }

eventTxLocalModeEnable OBJECT-TYPE
	SYNTAX INTEGER
		{
			true(1),
			false(2)
		}
	MAX-ACCESS read-write
	STATUS current
	DESCRIPTION
		"Enable/Disable switch for eventTxLocalMode event"
	::= { eventTxLocalModeParams 2 }

txLocalModeSignalSuppression OBJECT-TYPE
	SYNTAX INTEGER
		{
			disable(1),
			enable(2)
		}
	MAX-ACCESS read-write
	STATUS current
	DESCRIPTION
		"Enable/Disable traps sending for Transmitter branch but localMode trap : 1:Disable 2:Enable"
	::= { eventTxLocalModeParams 3 }

eventTxAl3dBParams OBJECT-IDENTITY
	STATUS current
	DESCRIPTION
		"No description"
	::= { eventsParams 2 }

eventTxAl3dBPriority OBJECT-TYPE
	SYNTAX Gauge32(0..2147483647)
	MAX-ACCESS read-write
	STATUS current
	DESCRIPTION
		"Priority for eventTxAl3dB event"
	::= { eventTxAl3dBParams 1 }

eventTxAl3dBEnable OBJECT-TYPE
	SYNTAX INTEGER
		{
			true(1),
			false(2)
		}
	MAX-ACCESS read-write
	STATUS current
	DESCRIPTION
		"Enable/Disable switch for eventTxAl3dB event"
	::= { eventTxAl3dBParams 2 }

eventTxAlFaultParams OBJECT-IDENTITY
	STATUS current
	DESCRIPTION
		"No description"
	::= { eventsParams 3 }

eventTxAlFaultPriority OBJECT-TYPE
	SYNTAX Gauge32(0..2147483647)
	MAX-ACCESS read-write
	STATUS current
	DESCRIPTION
		"Priority for eventTxAlFault event"
	::= { eventTxAlFaultParams 1 }

eventTxAlFaultEnable OBJECT-TYPE
	SYNTAX INTEGER
		{
			true(1),
			false(2)
		}
	MAX-ACCESS read-write
	STATUS current
	DESCRIPTION
		"Enable/Disable switch for eventTxAlFault event"
	::= { eventTxAlFaultParams 2 }

eventTxAlWarningParams OBJECT-IDENTITY
	STATUS current
	DESCRIPTION
		"No description"
	::= { eventsParams 4 }

eventTxAlWarningPriority OBJECT-TYPE
	SYNTAX Gauge32(0..2147483647)
	MAX-ACCESS read-write
	STATUS current
	DESCRIPTION
		"Priority for eventTxAlWarning event"
	::= { eventTxAlWarningParams 1 }

eventTxAlWarningEnable OBJECT-TYPE
	SYNTAX INTEGER
		{
			true(1),
			false(2)
		}
	MAX-ACCESS read-write
	STATUS current
	DESCRIPTION
		"Enable/Disable switch for eventTxAlWarning event"
	::= { eventTxAlWarningParams 2 }

eventTxAlVSWRParams OBJECT-IDENTITY
	STATUS current
	DESCRIPTION
		"No description"
	::= { eventsParams 5 }

eventTxAlVSWRPriority OBJECT-TYPE
	SYNTAX Gauge32(0..2147483647)
	MAX-ACCESS read-write
	STATUS current
	DESCRIPTION
		"Priority for eventTxAlVSWR event"
	::= { eventTxAlVSWRParams 1 }

eventTxAlVSWREnable OBJECT-TYPE
	SYNTAX INTEGER
		{
			true(1),
			false(2)
		}
	MAX-ACCESS read-write
	STATUS current
	DESCRIPTION
		"Enable/Disable switch for eventTxAlVSWR event"
	::= { eventTxAlVSWRParams 2 }

eventTxAlInterlockAntParams OBJECT-IDENTITY
	STATUS current
	DESCRIPTION
		"No description"
	::= { eventsParams 6 }

eventTxAlInterlockAntPriority OBJECT-TYPE
	SYNTAX Gauge32(0..2147483647)
	MAX-ACCESS read-write
	STATUS current
	DESCRIPTION
		"Priority for eventTxAlInterlockAnt event"
	::= { eventTxAlInterlockAntParams 1 }

eventTxAlInterlockAntEnable OBJECT-TYPE
	SYNTAX INTEGER
		{
			true(1),
			false(2)
		}
	MAX-ACCESS read-write
	STATUS current
	DESCRIPTION
		"Enable/Disable switch for eventTxAlInterlockAnt event"
	::= { eventTxAlInterlockAntParams 2 }

eventTxAlInterlockLoadParams OBJECT-IDENTITY
	STATUS obsolete
	DESCRIPTION
		"No description"
	::= { eventsParams 7 }

eventTxAlInterlockLoadPriority OBJECT-TYPE
	SYNTAX Gauge32(0..2147483647)
	MAX-ACCESS read-write
	STATUS obsolete
	DESCRIPTION
		"Priority for eventTxAlInterlockLoad event"
	::= { eventTxAlInterlockLoadParams 1 }

eventTxAlInterlockLoadEnable OBJECT-TYPE
	SYNTAX INTEGER
		{
			true(1),
			false(2)
		}
	MAX-ACCESS read-write
	STATUS obsolete
	DESCRIPTION
		"Enable/Disable switch for eventTxAlInterlockLoad event"
	::= { eventTxAlInterlockLoadParams 2 }

eventTxRfOpmodeParams OBJECT-IDENTITY
	STATUS current
	DESCRIPTION
		"No description"
	::= { eventsParams 8 }

eventTxRfOpmodePriority OBJECT-TYPE
	SYNTAX Gauge32(0..2147483647)
	MAX-ACCESS read-write
	STATUS current
	DESCRIPTION
		"Priority for eventTxRfOpmode event"
	::= { eventTxRfOpmodeParams 1 }

eventTxRfOpmodeEnable OBJECT-TYPE
	SYNTAX INTEGER
		{
			true(1),
			false(2)
		}
	MAX-ACCESS read-write
	STATUS current
	DESCRIPTION
		"Enable/Disable switch for eventTxRfOpmode event"
	::= { eventTxRfOpmodeParams 2 }

eventTxRfRFPresentParams OBJECT-IDENTITY
	STATUS current
	DESCRIPTION
		"No description"
	::= { eventsParams 9 }

eventTxRfRFPresentPriority OBJECT-TYPE
	SYNTAX Gauge32(0..2147483647)
	MAX-ACCESS read-write
	STATUS current
	DESCRIPTION
		"Priority for eventTxRfRFPresent event"
	::= { eventTxRfRFPresentParams 1 }

eventTxRfRFPresentEnable OBJECT-TYPE
	SYNTAX INTEGER
		{
			true(1),
			false(2)
		}
	MAX-ACCESS read-write
	STATUS current
	DESCRIPTION
		"Enable/Disable switch for eventTxRfRFPresent event"
	::= { eventTxRfRFPresentParams 2 }

eventAcReserveControlParams OBJECT-IDENTITY
	STATUS current
	DESCRIPTION
		"No description"
	::= { eventsParams 10 }

eventAcReserveControlPriority OBJECT-TYPE
	SYNTAX Gauge32(0..2147483647)
	MAX-ACCESS read-write
	STATUS current
	DESCRIPTION
		"Priority for eventAcReserveControl event"
	::= { eventAcReserveControlParams 1 }

eventAcReserveControlEnable OBJECT-TYPE
	SYNTAX INTEGER
		{
			true(1),
			false(2)
		}
	MAX-ACCESS read-write
	STATUS current
	DESCRIPTION
		"Enable/Disable switch for eventAcReserveControl event"
	::= { eventAcReserveControlParams 2 }

eventAcLocalModeParams OBJECT-IDENTITY
	STATUS current
	DESCRIPTION
		"No description"
	::= { eventsParams 11 }

eventAcLocalModePriority OBJECT-TYPE
	SYNTAX Gauge32(0..2147483647)
	MAX-ACCESS read-write
	STATUS current
	DESCRIPTION
		"Priority for eventAcLocalMode event"
	::= { eventAcLocalModeParams 1 }

eventAcLocalModeEnable OBJECT-TYPE
	SYNTAX INTEGER
		{
			true(1),
			false(2)
		}
	MAX-ACCESS read-write
	STATUS current
	DESCRIPTION
		"Enable/Disable switch for eventAcLocalMode event"
	::= { eventAcLocalModeParams 2 }

acLocalModeSignalSuppression OBJECT-TYPE
	SYNTAX INTEGER
		{
			disable(1),
			enable(2)
		}
	MAX-ACCESS read-write
	STATUS current
	DESCRIPTION
		"Enable/Disable traps sending for ACU and System branch but localMode trap : 1:Disable 2:Enable"
	::= { eventAcLocalModeParams 3 }

eventAcFaultParams OBJECT-IDENTITY
	STATUS current
	DESCRIPTION
		"No description"
	::= { eventsParams 12 }

eventAcFaultPriority OBJECT-TYPE
	SYNTAX Gauge32(0..2147483647)
	MAX-ACCESS read-write
	STATUS current
	DESCRIPTION
		"Priority for eventAcFault event"
	::= { eventAcFaultParams 1 }

eventAcFaultEnable OBJECT-TYPE
	SYNTAX INTEGER
		{
			true(1),
			false(2)
		}
	MAX-ACCESS read-write
	STATUS current
	DESCRIPTION
		"Enable/Disable switch for eventAcFault event"
	::= { eventAcFaultParams 2 }

eventAcSwitchOverParams OBJECT-IDENTITY
	STATUS current
	DESCRIPTION
		"No description"
	::= { eventsParams 13 }

eventAcSwitchOverPriority OBJECT-TYPE
	SYNTAX Gauge32(0..2147483647)
	MAX-ACCESS read-write
	STATUS current
	DESCRIPTION
		"Priority for eventAcSwitchOver event"
	::= { eventAcSwitchOverParams 1 }

eventAcSwitchOverEnable OBJECT-TYPE
	SYNTAX INTEGER
		{
			true(1),
			false(2)
		}
	MAX-ACCESS read-write
	STATUS current
	DESCRIPTION
		"Enable/Disable switch for eventAcSwitchOver event"
	::= { eventAcSwitchOverParams 2 }

eventSysWarningParams OBJECT-IDENTITY
	STATUS current
	DESCRIPTION
		"No description"
	::= { eventsParams 14 }

eventSysWarningPriority OBJECT-TYPE
	SYNTAX Gauge32(0..2147483647)
	MAX-ACCESS read-write
	STATUS current
	DESCRIPTION
		"Priority for eventSysWarning event"
	::= { eventSysWarningParams 1 }

eventSysWarningEnable OBJECT-TYPE
	SYNTAX INTEGER
		{
			true(1),
			false(2)
		}
	MAX-ACCESS read-write
	STATUS current
	DESCRIPTION
		"Enable/Disable switch for eventSysWarning event"
	::= { eventSysWarningParams 2 }

eventSysFaultParams OBJECT-IDENTITY
	STATUS current
	DESCRIPTION
		"No description"
	::= { eventsParams 15 }

eventSysFaultPriority OBJECT-TYPE
	SYNTAX Gauge32(0..2147483647)
	MAX-ACCESS read-write
	STATUS current
	DESCRIPTION
		"Priority for eventSysFault event"
	::= { eventSysFaultParams 1 }

eventSysFaultEnable OBJECT-TYPE
	SYNTAX INTEGER
		{
			true(1),
			false(2)
		}
	MAX-ACCESS read-write
	STATUS current
	DESCRIPTION
		"Enable/Disable switch for eventSysFault event"
	::= { eventSysFaultParams 2 }

eventSysAlAmbParams OBJECT-IDENTITY
	STATUS current
	DESCRIPTION
		"No description"
	::= { eventsParams 16 }

eventSysAlAmbPriority OBJECT-TYPE
	SYNTAX Gauge32(0..2147483647)
	MAX-ACCESS read-write
	STATUS current
	DESCRIPTION
		"Priority for eventSysAlAmb event"
	::= { eventSysAlAmbParams 1 }

eventSysAlAmbEnable OBJECT-TYPE
	SYNTAX INTEGER
		{
			true(1),
			false(2)
		}
	MAX-ACCESS read-write
	STATUS current
	DESCRIPTION
		"Enable/Disable switch for eventSysAlAmb event"
	::= { eventSysAlAmbParams 2 }

eventSysAlVoltAuxParams OBJECT-IDENTITY
	STATUS current
	DESCRIPTION
		"No description"
	::= { eventsParams 17 }

eventSysAlVoltAuxPriority OBJECT-TYPE
	SYNTAX Gauge32(0..2147483647)
	MAX-ACCESS read-write
	STATUS current
	DESCRIPTION
		"Priority for eventSysAlVoltAux event"
	::= { eventSysAlVoltAuxParams 1 }

eventSysAlVoltAuxEnable OBJECT-TYPE
	SYNTAX INTEGER
		{
			true(1),
			false(2)
		}
	MAX-ACCESS read-write
	STATUS current
	DESCRIPTION
		"Enable/Disable switch for eventSysAlVoltAux event"
	::= { eventSysAlVoltAuxParams 2 }

eventSysAlRelayParams OBJECT-IDENTITY
	STATUS current
	DESCRIPTION
		"No description"
	::= { eventsParams 18 }

eventSysAlRelayPriority OBJECT-TYPE
	SYNTAX Gauge32(0..2147483647)
	MAX-ACCESS read-write
	STATUS current
	DESCRIPTION
		"Priority for eventSysAlRelay event"
	::= { eventSysAlRelayParams 1 }

eventSysAlRelayEnable OBJECT-TYPE
	SYNTAX INTEGER
		{
			true(1),
			false(2)
		}
	MAX-ACCESS read-write
	STATUS current
	DESCRIPTION
		"Enable/Disable switch for eventSysAlRelay event"
	::= { eventSysAlRelayParams 2 }

eventSysAlReserveParams OBJECT-IDENTITY
	STATUS current
	DESCRIPTION
		"No description"
	::= { eventsParams 19 }

eventSysAlReservePriority OBJECT-TYPE
	SYNTAX Gauge32(0..2147483647)
	MAX-ACCESS read-write
	STATUS current
	DESCRIPTION
		"Priority for eventSysAlReserve event"
	::= { eventSysAlReserveParams 1 }

eventSysAlReserveEnable OBJECT-TYPE
	SYNTAX INTEGER
		{
			true(1),
			false(2)
		}
	MAX-ACCESS read-write
	STATUS current
	DESCRIPTION
		"Enable/Disable switch for eventSysAlReserve event"
	::= { eventSysAlReserveParams 2 }

eventInSeAlrInputSwitchParams OBJECT-IDENTITY
	STATUS current
	DESCRIPTION
		"No description"
	::= { eventsParams 20 }

eventInSeAlrInputSwitchPriority OBJECT-TYPE
	SYNTAX Gauge32(0..2147483647)
	MAX-ACCESS read-write
	STATUS current
	DESCRIPTION
		"Priority for eventInSeAlrInputSwitch event"
	::= { eventInSeAlrInputSwitchParams 1 }

eventInSeAlrInputSwitchEnable OBJECT-TYPE
	SYNTAX INTEGER
		{
			true(1),
			false(2)
		}
	MAX-ACCESS read-write
	STATUS current
	DESCRIPTION
		"Enable/Disable switch for eventInSeAlrInputSwitch event"
	::= { eventInSeAlrInputSwitchParams 2 }

eventTxAl1dBParams OBJECT-IDENTITY
	STATUS current
	DESCRIPTION
		"No description"
	::= { eventsParams 21 }

eventTxAl1dBPriority OBJECT-TYPE
	SYNTAX Gauge32(0..2147483647)
	MAX-ACCESS read-write
	STATUS current
	DESCRIPTION
		"Priority for eventTxAl1dB event"
	::= { eventTxAl1dBParams 1 }

eventTxAl1dBEnable OBJECT-TYPE
	SYNTAX INTEGER
		{
			true(1),
			false(2)
		}
	MAX-ACCESS read-write
	STATUS current
	DESCRIPTION
		"Enable/Disable switch for eventTxAl1dB event"
	::= { eventTxAl1dBParams 2 }

eventTxGnGlStandbyParams OBJECT-IDENTITY
	STATUS current
	DESCRIPTION
		"No description"
	::= { eventsParams 22 }

eventTxGnGlStandbyPriority OBJECT-TYPE
	SYNTAX Gauge32(0..2147483647)
	MAX-ACCESS read-write
	STATUS current
	DESCRIPTION
		"Priority for eventTxGnGlStandby event"
	::= { eventTxGnGlStandbyParams 1 }

eventTxGnGlStandbyEnable OBJECT-TYPE
	SYNTAX INTEGER
		{
			true(1),
			false(2)
		}
	MAX-ACCESS read-write
	STATUS current
	DESCRIPTION
		"Enable/Disable switch for eventTxGnGlStandby event"
	::= { eventTxGnGlStandbyParams 2 }

eventInAlLine1Params OBJECT-IDENTITY
	STATUS current
	DESCRIPTION
		"No description"
	::= { eventsParams 23 }

eventInAlLine1Priority OBJECT-TYPE
	SYNTAX Gauge32(0..2147483647)
	MAX-ACCESS read-write
	STATUS current
	DESCRIPTION
		"Priority for eventInAlLine1 event"
	::= { eventInAlLine1Params 1 }

eventInAlLine1Enable OBJECT-TYPE
	SYNTAX INTEGER
		{
			true(1),
			false(2)
		}
	MAX-ACCESS read-write
	STATUS current
	DESCRIPTION
		"Enable/Disable switch for eventInAlLine1 event"
	::= { eventInAlLine1Params 2 }

eventInAlLine2Params OBJECT-IDENTITY
	STATUS current
	DESCRIPTION
		"No description"
	::= { eventsParams 24 }

eventInAlLine2Priority OBJECT-TYPE
	SYNTAX Gauge32(0..2147483647)
	MAX-ACCESS read-write
	STATUS current
	DESCRIPTION
		"Priority for eventInAlLine2 event"
	::= { eventInAlLine2Params 1 }

eventInAlLine2Enable OBJECT-TYPE
	SYNTAX INTEGER
		{
			true(1),
			false(2)
		}
	MAX-ACCESS read-write
	STATUS current
	DESCRIPTION
		"Enable/Disable switch for eventInAlLine2 event"
	::= { eventInAlLine2Params 2 }

eventInAlMpx1Params OBJECT-IDENTITY
	STATUS current
	DESCRIPTION
		"No description"
	::= { eventsParams 25 }

eventInAlMpx1Priority OBJECT-TYPE
	SYNTAX Gauge32(0..2147483647)
	MAX-ACCESS read-write
	STATUS current
	DESCRIPTION
		"Priority for eventInAlMpx1 event"
	::= { eventInAlMpx1Params 1 }

eventInAlMpx1Enable OBJECT-TYPE
	SYNTAX INTEGER
		{
			true(1),
			false(2)
		}
	MAX-ACCESS read-write
	STATUS current
	DESCRIPTION
		"Enable/Disable switch for eventInAlMpx1 event"
	::= { eventInAlMpx1Params 2 }

eventInAlMpx2Params OBJECT-IDENTITY
	STATUS current
	DESCRIPTION
		"No description"
	::= { eventsParams 26 }

eventInAlMpx2Priority OBJECT-TYPE
	SYNTAX Gauge32(0..2147483647)
	MAX-ACCESS read-write
	STATUS current
	DESCRIPTION
		"Priority for eventInAlMpx2 event"
	::= { eventInAlMpx2Params 1 }

eventInAlMpx2Enable OBJECT-TYPE
	SYNTAX INTEGER
		{
			true(1),
			false(2)
		}
	MAX-ACCESS read-write
	STATUS current
	DESCRIPTION
		"Enable/Disable switch for eventInAlMpx2 event"
	::= { eventInAlMpx2Params 2 }

eventInAlPlayerParams OBJECT-IDENTITY
	STATUS current
	DESCRIPTION
		"No description"
	::= { eventsParams 27 }

eventInAlPlayerPriority OBJECT-TYPE
	SYNTAX Gauge32(0..2147483647)
	MAX-ACCESS read-write
	STATUS current
	DESCRIPTION
		"Priority for eventInAlPlayer event"
	::= { eventInAlPlayerParams 1 }

eventInAlPlayerEnable OBJECT-TYPE
	SYNTAX INTEGER
		{
			true(1),
			false(2)
		}
	MAX-ACCESS read-write
	STATUS current
	DESCRIPTION
		"Enable/Disable switch for eventInAlPlayer event"
	::= { eventInAlPlayerParams 2 }

eventSysAlInvalidDataParams OBJECT-IDENTITY
	STATUS current
	DESCRIPTION
		"No description"
	::= { eventsParams 28 }

eventSysAlInvalidDataPriority OBJECT-TYPE
	SYNTAX Gauge32(0..2147483647)
	MAX-ACCESS read-write
	STATUS current
	DESCRIPTION
		"Priority for eventSysAlInvalidData event"
	::= { eventSysAlInvalidDataParams 1 }

eventSysAlInvalidDataEnable OBJECT-TYPE
	SYNTAX INTEGER
		{
			true(1),
			false(2)
		}
	MAX-ACCESS read-write
	STATUS current
	DESCRIPTION
		"Enable/Disable switch for eventSysAlInvalidData event"
	::= { eventSysAlInvalidDataParams 2 }

eventAcGnAlInterlockAntParams OBJECT-IDENTITY
	STATUS current
	DESCRIPTION
		"No description"
	::= { eventsParams 29 }

eventAcGnAlInterlockAntPriority OBJECT-TYPE
	SYNTAX Gauge32(0..2147483647)
	MAX-ACCESS read-write
	STATUS current
	DESCRIPTION
		"Priority for eventAcGnAlInterlockAnt event"
	::= { eventAcGnAlInterlockAntParams 1 }

eventAcGnAlInterlockAntEnable OBJECT-TYPE
	SYNTAX INTEGER
		{
			true(1),
			false(2)
		}
	MAX-ACCESS read-write
	STATUS current
	DESCRIPTION
		"Enable/Disable switch for eventAcGnAlInterlockAnt event"
	::= { eventAcGnAlInterlockAntParams 2 }

eventAcGnAlInterlockLoadParams OBJECT-IDENTITY
	STATUS current
	DESCRIPTION
		"No description"
	::= { eventsParams 30 }

eventAcGnAlInterlockLoadPriority OBJECT-TYPE
	SYNTAX Gauge32(0..2147483647)
	MAX-ACCESS read-write
	STATUS current
	DESCRIPTION
		"Priority for eventAcGnAlInterlockLoad event"
	::= { eventAcGnAlInterlockLoadParams 1 }

eventAcGnAlInterlockLoadEnable OBJECT-TYPE
	SYNTAX INTEGER
		{
			true(1),
			false(2)
		}
	MAX-ACCESS read-write
	STATUS current
	DESCRIPTION
		"Enable/Disable switch for eventAcGnAlInterlockLoad event"
	::= { eventAcGnAlInterlockLoadParams 2 }

eventSysAl24vParams OBJECT-IDENTITY
	STATUS current
	DESCRIPTION
		"No description"
	::= { eventsParams 31 }

eventSysAl24vPriority OBJECT-TYPE
	SYNTAX Gauge32(0..2147483647)
	MAX-ACCESS read-write
	STATUS current
	DESCRIPTION
		"Priority for eventSysAl24v event"
	::= { eventSysAl24vParams 1 }

eventSysAl24vEnable OBJECT-TYPE
	SYNTAX INTEGER
		{
			true(1),
			false(2)
		}
	MAX-ACCESS read-write
	STATUS current
	DESCRIPTION
		"Enable/Disable switch for eventSysAl24v event"
	::= { eventSysAl24vParams 2 }

eventSysAlCommParams OBJECT-IDENTITY
	STATUS current
	DESCRIPTION
		"No description"
	::= { eventsParams 32 }

eventSysAlCommPriority OBJECT-TYPE
	SYNTAX Gauge32(0..2147483647)
	MAX-ACCESS read-write
	STATUS current
	DESCRIPTION
		"Priority for eventSysAlComm event"
	::= { eventSysAlCommParams 1 }

eventSysAlCommEnable OBJECT-TYPE
	SYNTAX INTEGER
		{
			true(1),
			false(2)
		}
	MAX-ACCESS read-write
	STATUS current
	DESCRIPTION
		"Enable/Disable switch for eventSysAlComm event"
	::= { eventSysAlCommParams 2 }

eventEquipmentOnParams OBJECT-IDENTITY
	STATUS current
	DESCRIPTION
		"No description"
	::= { eventsParams 33 }

eventEquipmentOnPriority OBJECT-TYPE
	SYNTAX Gauge32(0..2147483647)
	MAX-ACCESS read-write
	STATUS current
	DESCRIPTION
		"Priority for eventEquipmentOn event"
	::= { eventEquipmentOnParams 1 }

eventEquipmentOnEnable OBJECT-TYPE
	SYNTAX INTEGER
		{
			true(1),
			false(2)
		}
	MAX-ACCESS read-write
	STATUS current
	DESCRIPTION
		"Enable/Disable switch for eventEquipmentOn event"
	::= { eventEquipmentOnParams 2 }

eventHeartBeatParams OBJECT-IDENTITY
	STATUS current
	DESCRIPTION
		"No description"
	::= { eventsParams 34 }

eventHeartBeatPriority OBJECT-TYPE
	SYNTAX Gauge32(0..2147483647)
	MAX-ACCESS read-write
	STATUS current
	DESCRIPTION
		"Priority for eventHeartBeat event"
	::= { eventHeartBeatParams 1 }

eventHeartBeatEnable OBJECT-TYPE
	SYNTAX INTEGER
		{
			true(1),
			false(2)
		}
	MAX-ACCESS read-write
	STATUS current
	DESCRIPTION
		"Enable/Disable switch for eventHeartBeat event"
	::= { eventHeartBeatParams 2 }

eventConfigChangedParams OBJECT-IDENTITY
	STATUS current
	DESCRIPTION
		"No description"
	::= { eventsParams 35 }

eventConfigChangedPriority OBJECT-TYPE
	SYNTAX Gauge32(0..2147483647)
	MAX-ACCESS read-write
	STATUS current
	DESCRIPTION
		"Priority for eventConfigChanged event"
	::= { eventConfigChangedParams 1 }

eventConfigChangedEnable OBJECT-TYPE
	SYNTAX INTEGER
		{
			true(1),
			false(2)
		}
	MAX-ACCESS read-write
	STATUS current
	DESCRIPTION
		"Enable/Disable switch for eventConfigChanged event"
	::= { eventConfigChangedParams 2 }

eventEquipmentFaultParams OBJECT-IDENTITY
	STATUS obsolete
	DESCRIPTION
		"No description"
	::= { eventsParams 36 }

eventEquipmentFaultPriority OBJECT-TYPE
	SYNTAX Gauge32(0..2147483647)
	MAX-ACCESS read-write
	STATUS obsolete
	DESCRIPTION
		"Priority for eventEquipmentFault event"
	::= { eventEquipmentFaultParams 1 }

eventEquipmentFaultEnable OBJECT-TYPE
	SYNTAX INTEGER
		{
			true(1),
			false(2)
		}
	MAX-ACCESS read-write
	STATUS obsolete
	DESCRIPTION
		"Enable/Disable switch for eventEquipmentFault event"
	::= { eventEquipmentFaultParams 2 }

eventInAlFaultParams OBJECT-IDENTITY
	STATUS obsolete
	DESCRIPTION
		"No description"
	::= { eventsParams 37 }

eventInAlFaultPriority OBJECT-TYPE
	SYNTAX Gauge32(0..2147483647)
	MAX-ACCESS read-write
	STATUS current
	DESCRIPTION
		"Priority for eventInAlFault event"
	::= { eventInAlFaultParams 1 }

eventInAlFaultEnable OBJECT-TYPE
	SYNTAX INTEGER
		{
			true(1),
			false(2)
		}
	MAX-ACCESS read-write
	STATUS current
	DESCRIPTION
		"Enable/Disable switch for eventInAlFault event"
	::= { eventInAlFaultParams 2 }

eventMoSfAlarmParams OBJECT-IDENTITY
	STATUS current
	DESCRIPTION
		"No description"
	::= { eventsParams 38 }

eventMoSfAlarmPriority OBJECT-TYPE
	SYNTAX Gauge32(0..2147483647)
	MAX-ACCESS read-write
	STATUS current
	DESCRIPTION
		"Priority for eventMoSfAlarm event"
	::= { eventMoSfAlarmParams 1 }

eventMoSfAlarmEnable OBJECT-TYPE
	SYNTAX INTEGER
		{
			true(1),
			false(2)
		}
	MAX-ACCESS read-write
	STATUS current
	DESCRIPTION
		"Enable/Disable switch for eventMoSfAlarm event"
	::= { eventMoSfAlarmParams 2 }

eventMoSfSwitch10MAlarmParams OBJECT-IDENTITY
	STATUS current
	DESCRIPTION
		"No description"
	::= { eventsParams 39 }

eventMoSfSwitch10MAlarmPriority OBJECT-TYPE
	SYNTAX Gauge32(0..2147483647)
	MAX-ACCESS read-write
	STATUS current
	DESCRIPTION
		"Priority for eventMoSfSwitch10MAlarm event"
	::= { eventMoSfSwitch10MAlarmParams 1 }

eventMoSfSwitch10MAlarmEnable OBJECT-TYPE
	SYNTAX INTEGER
		{
			true(1),
			false(2)
		}
	MAX-ACCESS read-write
	STATUS current
	DESCRIPTION
		"Enable/Disable switch for eventMoSfSwitch10MAlarm event"
	::= { eventMoSfSwitch10MAlarmParams 2 }

eventSyAlLoggingParams OBJECT-IDENTITY
	STATUS current
	DESCRIPTION
		"No description"
	::= { eventsParams 40 }

eventSyAlLoggingPriority OBJECT-TYPE
	SYNTAX Gauge32(0..2147483647)
	MAX-ACCESS read-write
	STATUS current
	DESCRIPTION
		"Priority for eventSyAlLogging event"
	::= { eventSyAlLoggingParams 1 }

eventSyAlLoggingEnable OBJECT-TYPE
	SYNTAX INTEGER
		{
			true(1),
			false(2)
		}
	MAX-ACCESS read-write
	STATUS current
	DESCRIPTION
		"Enable/Disable switch for eventSyAlLogging event"
	::= { eventSyAlLoggingParams 2 }


eventInAlMpx3Params OBJECT-IDENTITY
	STATUS current
	DESCRIPTION
		"No description"
	::= { eventsParams 41 }

eventInAlMpx3Priority OBJECT-TYPE
	SYNTAX Gauge32(0..2147483647)
	MAX-ACCESS read-write
	STATUS current
	DESCRIPTION
		"Priority for eventInAlMpx3 event"
	::= { eventInAlMpx3Params 1 }

eventInAlMpx3Enable OBJECT-TYPE
	SYNTAX INTEGER
		{
			true(1),
			false(2)
		}
	MAX-ACCESS read-write
	STATUS current
	DESCRIPTION
		"Enable/Disable switch for eventInAlMpx3 event"
	::= { eventInAlMpx3Params 2 }


eventInAlMpx4Params OBJECT-IDENTITY
	STATUS current
	DESCRIPTION
		"No description"
	::= { eventsParams 42 }

eventInAlMpx4Priority OBJECT-TYPE
	SYNTAX Gauge32(0..2147483647)
	MAX-ACCESS read-write
	STATUS current
	DESCRIPTION
		"Priority for eventInAlMpx4 event"
	::= { eventInAlMpx4Params 1 }

eventInAlMpx4Enable OBJECT-TYPE
	SYNTAX INTEGER
		{
			true(1),
			false(2)
		}
	MAX-ACCESS read-write
	STATUS current
	DESCRIPTION
		"Enable/Disable switch for eventInAlMpx4 event"
	::= { eventInAlMpx4Params 2 }


eventTxSfStActParams OBJECT-IDENTITY
	STATUS current
	DESCRIPTION
		"No description"
	::= { eventsParams 43 }

eventTxSfStActPriority OBJECT-TYPE
	SYNTAX Gauge32(0..2147483647)
	MAX-ACCESS read-write
	STATUS current
	DESCRIPTION
		"Priority for eventTxSfStAct event"
	::= { eventTxSfStActParams 1 }

eventTxSfStActEnable OBJECT-TYPE
	SYNTAX INTEGER
		{
			true(1),
			false(2)
		}
	MAX-ACCESS read-write
	STATUS current
	DESCRIPTION
		"Enable/Disable switch for eventTxSfStAct event"
	::= { eventTxSfStActParams 2 }


eventTxSfStAlarmParams OBJECT-IDENTITY
	STATUS current
	DESCRIPTION
		"No description"
	::= { eventsParams 44 }

eventTxSfStAlarmPriority OBJECT-TYPE
	SYNTAX Gauge32(0..2147483647)
	MAX-ACCESS read-write
	STATUS current
	DESCRIPTION
		"Priority for eventTxSfStAlarm event"
	::= { eventTxSfStAlarmParams 1 }

eventTxSfStAlarmEnable OBJECT-TYPE
	SYNTAX INTEGER
		{
			true(1),
			false(2)
		}
	MAX-ACCESS read-write
	STATUS current
	DESCRIPTION
		"Enable/Disable switch for eventTxSfStAlarm event"
	::= { eventTxSfStAlarmParams 2 }


eventSyLiAlRdsParams OBJECT-IDENTITY
	STATUS current
	DESCRIPTION
		"No description"
	::= { eventsParams 45 }

eventSyLiAlRdsPriority OBJECT-TYPE
	SYNTAX Gauge32(0..2147483647)
	MAX-ACCESS read-write
	STATUS current
	DESCRIPTION
		"Priority for eventSyLiAlRds event"
	::= { eventSyLiAlRdsParams 1 }

eventSyLiAlRdsEnable OBJECT-TYPE
	SYNTAX INTEGER
		{
			true(1),
			false(2)
		}
	MAX-ACCESS read-write
	STATUS current
	DESCRIPTION
		"Enable/Disable switch for eventSyLiAlRds event"
	::= { eventSyLiAlRdsParams 2 }


eventSyLiAlSoundProcParams OBJECT-IDENTITY
	STATUS current
	DESCRIPTION
		"No description"
	::= { eventsParams 46 }

eventSyLiAlSoundProcPriority OBJECT-TYPE
	SYNTAX Gauge32(0..2147483647)
	MAX-ACCESS read-write
	STATUS current
	DESCRIPTION
		"Priority for eventSyLiAlSoundProc event"
	::= { eventSyLiAlSoundProcParams 1 }

eventSyLiAlSoundProcEnable OBJECT-TYPE
	SYNTAX INTEGER
		{
			true(1),
			false(2)
		}
	MAX-ACCESS read-write
	STATUS current
	DESCRIPTION
		"Enable/Disable switch for eventSyLiAlSoundProc event"
	::= { eventSyLiAlSoundProcParams 2 }


eventSyLiAlSfmParams OBJECT-IDENTITY
	STATUS current
	DESCRIPTION
		"No description"
	::= { eventsParams 47 }

eventSyLiAlSfmPriority OBJECT-TYPE
	SYNTAX Gauge32(0..2147483647)
	MAX-ACCESS read-write
	STATUS current
	DESCRIPTION
		"Priority for eventSyLiAlSfm event"
	::= { eventSyLiAlSfmParams 1 }

eventSyLiAlSfmEnable OBJECT-TYPE
	SYNTAX INTEGER
		{
			true(1),
			false(2)
		}
	MAX-ACCESS read-write
	STATUS current
	DESCRIPTION
		"Enable/Disable switch for eventSyLiAlSfm event"
	::= { eventSyLiAlSfmParams 2 }


eventSyLiAlActivationParams OBJECT-IDENTITY
	STATUS current
	DESCRIPTION
		"No description"
	::= { eventsParams 48 }

eventSyLiAlActivationPriority OBJECT-TYPE
	SYNTAX Gauge32(0..2147483647)
	MAX-ACCESS read-write
	STATUS current
	DESCRIPTION
		"Priority for eventSyLiAlActivation event"
	::= { eventSyLiAlActivationParams 1 }

eventSyLiAlActivationEnable OBJECT-TYPE
	SYNTAX INTEGER
		{
			true(1),
			false(2)
		}
	MAX-ACCESS read-write
	STATUS current
	DESCRIPTION
		"Enable/Disable switch for eventSyLiAlActivation event"
	::= { eventSyLiAlActivationParams 2 }

eventInAlAes1Params OBJECT-IDENTITY
	STATUS current
	DESCRIPTION
		"No description"
	::= { eventsParams 49 }

eventInAlAes1Priority OBJECT-TYPE
	SYNTAX Gauge32(0..2147483647)
	MAX-ACCESS read-write
	STATUS current
	DESCRIPTION
		"Priority for eventInAlAes1 event"
	::= { eventInAlAes1Params 1 }

eventInAlAes1Enable OBJECT-TYPE
	SYNTAX INTEGER
		{
			true(1),
			false(2)
		}
	MAX-ACCESS read-write
	STATUS current
	DESCRIPTION
		"Enable/Disable switch for eventInAlAes1 event"
	::= { eventInAlAes1Params 2 }

eventInAlAes2Params OBJECT-IDENTITY
	STATUS current
	DESCRIPTION
		"No description"
	::= { eventsParams 50 }

eventInAlAes2Priority OBJECT-TYPE
	SYNTAX Gauge32(0..2147483647)
	MAX-ACCESS read-write
	STATUS current
	DESCRIPTION
		"Priority for eventInAlAes2 event"
	::= { eventInAlAes2Params 1 }

eventInAlAes2Enable OBJECT-TYPE
	SYNTAX INTEGER
		{
			true(1),
			false(2)
		}
	MAX-ACCESS read-write
	STATUS current
	DESCRIPTION
		"Enable/Disable switch for eventInAlAes2 event"
	::= { eventInAlAes2Params 2 }

eventInAlAes3Params OBJECT-IDENTITY
	STATUS current
	DESCRIPTION
		"No description"
	::= { eventsParams 51 }

eventInAlAes3Priority OBJECT-TYPE
	SYNTAX Gauge32(0..2147483647)
	MAX-ACCESS read-write
	STATUS current
	DESCRIPTION
		"Priority for eventInAlAes3 event"
	::= { eventInAlAes3Params 1 }

eventInAlAes3Enable OBJECT-TYPE
	SYNTAX INTEGER
		{
			true(1),
			false(2)
		}
	MAX-ACCESS read-write
	STATUS current
	DESCRIPTION
		"Enable/Disable switch for eventInAlAes3 event"
	::= { eventInAlAes3Params 2 }

eventInAlAna1Params OBJECT-IDENTITY
	STATUS current
	DESCRIPTION
		"No description"
	::= { eventsParams 52 }

eventInAlAna1Priority OBJECT-TYPE
	SYNTAX Gauge32(0..2147483647)
	MAX-ACCESS read-write
	STATUS current
	DESCRIPTION
		"Priority for eventInAlAna1 event"
	::= { eventInAlAna1Params 1 }

eventInAlAna1Enable OBJECT-TYPE
	SYNTAX INTEGER
		{
			true(1),
			false(2)
		}
	MAX-ACCESS read-write
	STATUS current
	DESCRIPTION
		"Enable/Disable switch for eventInAlAna1 event"
	::= { eventInAlAna1Params 2 }


eventInAlAoipParams OBJECT-IDENTITY
	STATUS current
	DESCRIPTION
		"No description"
	::= { eventsParams 53 }

eventInAlAoipPriority OBJECT-TYPE
	SYNTAX Gauge32(0..2147483647)
	MAX-ACCESS read-write
	STATUS current
	DESCRIPTION
		"Priority for eventInAlAoip event"
	::= { eventInAlAoipParams 1 }

eventInAlAoipEnable OBJECT-TYPE
	SYNTAX INTEGER
		{
			true(1),
			false(2)
		}
	MAX-ACCESS read-write
	STATUS current
	DESCRIPTION
		"Enable/Disable switch for eventInAlAoip event"
	::= { eventInAlAoipParams 2 }


eventLossOfEth0Params OBJECT-IDENTITY
	STATUS current
	DESCRIPTION
		"No description"
	::= { eventsParams 54 }

eventLossOfEth0Priority OBJECT-TYPE
	SYNTAX Gauge32(0..2147483647)
	MAX-ACCESS read-write
	STATUS current
	DESCRIPTION
		"Priority for eventLossOfEth0 event"
	::= { eventLossOfEth0Params 1 }

eventLossOfEth0Enable OBJECT-TYPE
	SYNTAX INTEGER
		{
			true(1),
			false(2)
		}
	MAX-ACCESS read-write
	STATUS current
	DESCRIPTION
		"Enable/Disable switch for eventLossOfEth0 event"
	::= { eventLossOfEth0Params 2 }


eventLossOfEth1Params OBJECT-IDENTITY
	STATUS current
	DESCRIPTION
		"No description"
	::= { eventsParams 55 }

eventLossOfEth1Priority OBJECT-TYPE
	SYNTAX Gauge32(0..2147483647)
	MAX-ACCESS read-write
	STATUS current
	DESCRIPTION
		"Priority for eventLossOfEth1 event"
	::= { eventLossOfEth1Params 1 }

eventLossOfEth1Enable OBJECT-TYPE
	SYNTAX INTEGER
		{
			true(1),
			false(2)
		}
	MAX-ACCESS read-write
	STATUS current
	DESCRIPTION
		"Enable/Disable switch for eventLossOfEth1 event"
	::= { eventLossOfEth1Params 2 }


eventSyLiAlAoipdecoderParams OBJECT-IDENTITY
	STATUS current
	DESCRIPTION
		"No description"
	::= { eventsParams 56 }

eventSyLiAlAoipdecoderPriority OBJECT-TYPE
	SYNTAX Gauge32(0..2147483647)
	MAX-ACCESS read-write
	STATUS current
	DESCRIPTION
		"Priority for eventSyLiAlAoipdecoder event"
	::= { eventSyLiAlAoipdecoderParams 1 }

eventSyLiAlAoipdecoderEnable OBJECT-TYPE
	SYNTAX INTEGER
		{
			true(1),
			false(2)
		}
	MAX-ACCESS read-write
	STATUS current
	DESCRIPTION
		"Enable/Disable switch for eventSyLiAlAoipdecoder event"
	::= { eventSyLiAlAoipdecoderParams 2 }


eventSyLiAlMpxoipdecoderParams OBJECT-IDENTITY
	STATUS current
	DESCRIPTION
		"No description"
	::= { eventsParams 57 }

eventSyLiAlMpxoipdecoderPriority OBJECT-TYPE
	SYNTAX Gauge32(0..2147483647)
	MAX-ACCESS read-write
	STATUS current
	DESCRIPTION
		"Priority for eventSyLiAlMpxoipdecoder event"
	::= { eventSyLiAlMpxoipdecoderParams 1 }

eventSyLiAlMpxoipdecoderEnable OBJECT-TYPE
	SYNTAX INTEGER
		{
			true(1),
			false(2)
		}
	MAX-ACCESS read-write
	STATUS current
	DESCRIPTION
		"Enable/Disable switch for eventSyLiAlMpxoipdecoder event"
	::= { eventSyLiAlMpxoipdecoderParams 2 }


eventSyLiAlSurestreamParams OBJECT-IDENTITY
	STATUS current
	DESCRIPTION
		"No description"
	::= { eventsParams 58 }

eventSyLiAlSurestreamPriority OBJECT-TYPE
	SYNTAX Gauge32(0..2147483647)
	MAX-ACCESS read-write
	STATUS current
	DESCRIPTION
		"Priority for eventSyLiAlSurestream event"
	::= { eventSyLiAlSurestreamParams 1 }

eventSyLiAlSurestreamEnable OBJECT-TYPE
	SYNTAX INTEGER
		{
			true(1),
			false(2)
		}
	MAX-ACCESS read-write
	STATUS current
	DESCRIPTION
		"Enable/Disable switch for eventSyLiAlSurestream event"
	::= { eventSyLiAlSurestreamParams 2 }


eventSyLiAlSynchrostreamParams OBJECT-IDENTITY
	STATUS current
	DESCRIPTION
		"No description"
	::= { eventsParams 59 }

eventSyLiAlSynchrostreamPriority OBJECT-TYPE
	SYNTAX Gauge32(0..2147483647)
	MAX-ACCESS read-write
	STATUS current
	DESCRIPTION
		"Priority for eventSyLiAlSynchrostream event"
	::= { eventSyLiAlSynchrostreamParams 1 }

eventSyLiAlSynchrostreamEnable OBJECT-TYPE
	SYNTAX INTEGER
		{
			true(1),
			false(2)
		}
	MAX-ACCESS read-write
	STATUS current
	DESCRIPTION
		"Enable/Disable switch for eventSyLiAlSynchrostream event"
	::= { eventSyLiAlSynchrostreamParams 2 }



-- Inputs --
inputs OBJECT-IDENTITY
	STATUS current
	DESCRIPTION
		"No description"
	::= { transmitter 4 }

inSource OBJECT-IDENTITY
	STATUS current
	DESCRIPTION
		"No description"
	::= { inputs 1 }

inSoLine1 OBJECT-IDENTITY
	STATUS current
	DESCRIPTION
		"No description"
	::= { inSource 1 }

inSoL1Presence OBJECT-TYPE
	SYNTAX INTEGER
		{
			undefined(0),
			left(1),
			right(2),
			leftRight(3),
			none(4)
		}
	MAX-ACCESS read-only
	STATUS current
	DESCRIPTION
		"Presence"
	::= { inSoLine1 1 }

inSoL1Type OBJECT-TYPE
	SYNTAX INTEGER
		{
			undefined(0),
			ana(1),
			aes(2),
			off(3)
		}
	MAX-ACCESS read-only
	STATUS current
	DESCRIPTION
		"Type"
	::= { inSoLine1 2 }

inSoL1LeftPeakMax OBJECT-TYPE
	SYNTAX Integer32(-32000..32000)
	UNITS "dB/100"
	MAX-ACCESS read-only
	STATUS current
	DESCRIPTION
		"Left Peak max"
	::= { inSoLine1 3 }

inSoL1RightPeakMax OBJECT-TYPE
	SYNTAX Integer32(-32000..32000)
	UNITS "dB/100"
	MAX-ACCESS read-only
	STATUS current
	DESCRIPTION
		"Right Peak max"
	::= { inSoLine1 4 }

inSoL1LeftPeak OBJECT-TYPE
	SYNTAX Integer32(-32000..32000)
	UNITS "dB/100"
	MAX-ACCESS read-only
	STATUS current
	DESCRIPTION
		"Left Peak"
	::= { inSoLine1 5 }

inSoL1RightPeak OBJECT-TYPE
	SYNTAX Integer32(-32000..32000)
	UNITS "dB/100"
	MAX-ACCESS read-only
	STATUS current
	DESCRIPTION
		"Right Peak"
	::= { inSoLine1 6 }

inSoL1Level OBJECT-TYPE
	SYNTAX Integer32(-2000..1800)
	UNITS "dB/100"
	MAX-ACCESS read-write
	STATUS current
	DESCRIPTION
		"Level"
	::= { inSoLine1 7 }

inSoL1Drive OBJECT-TYPE
	SYNTAX Integer32(-600..600)
	UNITS "dB/100"
	MAX-ACCESS read-write
	STATUS current
	DESCRIPTION
		"Drive"
	::= { inSoLine1 8 }

inSoL1Trim OBJECT-TYPE
	SYNTAX Integer32(-300..300)
	UNITS "dB/100"
	MAX-ACCESS read-write
	STATUS current
	DESCRIPTION
		"Trim"
	::= { inSoLine1 9 }

inSoL1Filter OBJECT-TYPE
	SYNTAX INTEGER
		{
			undefined(0),
			v0(1),
			v15(2),
			v16(3),
			v17(4)
		}
	MAX-ACCESS read-write
	STATUS current
	DESCRIPTION
		"Filter"
	::= { inSoLine1 10 }

inSoL1Preacc OBJECT-TYPE
	SYNTAX INTEGER
		{
			undefined(0),
			v50us(1),
			v75us(2),
			off(3)
		}
	MAX-ACCESS read-write
	STATUS current
	DESCRIPTION
		"Preacc"
	::= { inSoLine1 11 }

inSoL1Lost OBJECT-TYPE
	SYNTAX INTEGER
		{
			undefined(0),
			yes(1),
			no(2)
		}
	MAX-ACCESS read-only
	STATUS current
	DESCRIPTION
		"Verify Line1 presence"
	::= { inSoLine1 12 }

inSoL1AlarmTrig OBJECT-TYPE
	SYNTAX INTEGER
		{
			undefined(0),
			none(1),
			fault(2),
			warning(3)
		}
	MAX-ACCESS read-write
	STATUS current
	DESCRIPTION
		"Line1 alarm trigger"
	::= { inSoLine1 13 }

inSoLine2 OBJECT-IDENTITY
	STATUS current
	DESCRIPTION
		"No description"
	::= { inSource 2 }

inSoL2Presence OBJECT-TYPE
	SYNTAX INTEGER
		{
			undefined(0),
			left(1),
			right(2),
			leftRight(3),
			none(4)
		}
	MAX-ACCESS read-only
	STATUS current
	DESCRIPTION
		"Presence"
	::= { inSoLine2 1 }

inSoL2Type OBJECT-TYPE
	SYNTAX INTEGER
		{
			undefined(0),
			ana(1),
			aes(2),
			off(3)
		}
	MAX-ACCESS read-only
	STATUS current
	DESCRIPTION
		"Type"
	::= { inSoLine2 2 }

inSoL2LeftPeakMax OBJECT-TYPE
	SYNTAX Integer32(-32000..32000)
	UNITS "dB/100"
	MAX-ACCESS read-only
	STATUS current
	DESCRIPTION
		"Left Peak max"
	::= { inSoLine2 3 }

inSoL2RightPeakMax OBJECT-TYPE
	SYNTAX Integer32(-32000..32000)
	UNITS "dB/100"
	MAX-ACCESS read-only
	STATUS current
	DESCRIPTION
		"Right Peak max"
	::= { inSoLine2 4 }

inSoL2LeftPeak OBJECT-TYPE
	SYNTAX Integer32(-32000..32000)
	UNITS "dB/100"
	MAX-ACCESS read-only
	STATUS current
	DESCRIPTION
		"Left Peak"
	::= { inSoLine2 5 }

inSoL2RightPeak OBJECT-TYPE
	SYNTAX Integer32(-32000..32000)
	UNITS "dB/100"
	MAX-ACCESS read-only
	STATUS current
	DESCRIPTION
		"Right Peak"
	::= { inSoLine2 6 }

inSoL2Level OBJECT-TYPE
	SYNTAX Integer32(-2000..1800)
	UNITS "dB/100"
	MAX-ACCESS read-write
	STATUS current
	DESCRIPTION
		"Level"
	::= { inSoLine2 7 }

inSoL2Drive OBJECT-TYPE
	SYNTAX Integer32(-600..600)
	UNITS "dB/100"
	MAX-ACCESS read-write
	STATUS current
	DESCRIPTION
		"Drive"
	::= { inSoLine2 8 }

inSoL2Trim OBJECT-TYPE
	SYNTAX Integer32(-300..300)
	UNITS "dB/100"
	MAX-ACCESS read-write
	STATUS current
	DESCRIPTION
		"Trim"
	::= { inSoLine2 9 }

inSoL2Filter OBJECT-TYPE
	SYNTAX INTEGER
		{
			undefined(0),
			v0(1),
			v15(2),
			v16(3),
			v17(4)
		}
	MAX-ACCESS read-write
	STATUS current
	DESCRIPTION
		"Filter"
	::= { inSoLine2 10 }

inSoL2Preacc OBJECT-TYPE
	SYNTAX INTEGER
		{
			undefined(0),
			v50us(1),
			v75us(2),
			off(3)
		}
	MAX-ACCESS read-write
	STATUS current
	DESCRIPTION
		"Preacc"
	::= { inSoLine2 11 }

inSoL2Lost OBJECT-TYPE
	SYNTAX INTEGER
		{
			undefined(0),
			yes(1),
			no(2)
		}
	MAX-ACCESS read-only
	STATUS current
	DESCRIPTION
		"Verify Line2 presence"
	::= { inSoLine2 12 }

inSoL2AlarmTrig OBJECT-TYPE
	SYNTAX INTEGER
		{
			undefined(0),
			none(1),
			fault(2),
			warning(3)
		}
	MAX-ACCESS read-write
	STATUS current
	DESCRIPTION
		"Line2 alarm trigger"
	::= { inSoLine2 13 }

inSoMpx1 OBJECT-IDENTITY
	STATUS current
	DESCRIPTION
		"No description"
	::= { inSource 4 }

inSoM1Presence OBJECT-TYPE
	SYNTAX INTEGER
		{
			undefined(0),
			mono(1),
			monoRds(2),
			monoRdsSca(3),
			stereo(4),
			stereoRds(5),
			stereoRdsSca(6),
			rdsSca(7),
			rds(8),
			sca(9),
			none(10)
		}
	MAX-ACCESS read-only
	STATUS current
	DESCRIPTION
		"Mpx1 Presence"
	::= { inSoMpx1 1 }

inSoM1PeakMax OBJECT-TYPE
	SYNTAX Integer32(-32000..32000)
	UNITS "dB/100"
	MAX-ACCESS read-only
	STATUS current
	DESCRIPTION
		"Mpx1 Peak max"
	::= { inSoMpx1 2 }

inSoM1Peak OBJECT-TYPE
	SYNTAX Integer32(-32000..32000)
	UNITS "dB/100"
	MAX-ACCESS read-only
	STATUS current
	DESCRIPTION
		"Mpx1 Peak"
	::= { inSoMpx1 3 }

inSoM1Level OBJECT-TYPE
	SYNTAX Integer32(-1800..1800)
	UNITS "dB/100"
	MAX-ACCESS read-write
	STATUS current
	DESCRIPTION
		"Mpx1 Level"
	::= { inSoMpx1 4 }

inSoM1Drive OBJECT-TYPE
	SYNTAX Integer32(-600..600)
	UNITS "dB/100"
	MAX-ACCESS read-write
	STATUS current
	DESCRIPTION
		"mpx1 Drive"
	::= { inSoMpx1 5 }

inSoM1Lost OBJECT-TYPE
	SYNTAX INTEGER
		{
			undefined(0),
			yes(1),
			no(2)
		}
	MAX-ACCESS read-only
	STATUS current
	DESCRIPTION
		"Verify MPX1 presence"
	::= { inSoMpx1 6 }

inSoM1AlarmTrig OBJECT-TYPE
	SYNTAX INTEGER
		{
			undefined(0),
			none(1),
			fault(2),
			warning(3)
		}
	MAX-ACCESS read-write
	STATUS current
	DESCRIPTION
		"MPX1 alarm trigger"
	::= { inSoMpx1 7 }

inSoMpx2 OBJECT-IDENTITY
	STATUS current
	DESCRIPTION
		"No description"
	::= { inSource 5 }

inSoM2Presence OBJECT-TYPE
	SYNTAX INTEGER
		{
			undefined(0),
			mono(1),
			monoRds(2),
			monoRdsSca(3),
			stereo(4),
			stereoRds(5),
			stereoRdsSca(6),
			rdsSca(7),
			rds(8),
			sca(9),
			none(10)
		}
	MAX-ACCESS read-only
	STATUS current
	DESCRIPTION
		"Mpx2 Presence"
	::= { inSoMpx2 1 }

inSoM2PeakMax OBJECT-TYPE
	SYNTAX Integer32(-32000..32000)
	UNITS "dB/100"
	MAX-ACCESS read-only
	STATUS current
	DESCRIPTION
		"Mpx2 Peak max"
	::= { inSoMpx2 2 }

inSoM2Peak OBJECT-TYPE
	SYNTAX Integer32(-32000..32000)
	UNITS "dB/100"
	MAX-ACCESS read-only
	STATUS current
	DESCRIPTION
		"Mpx2 Peak"
	::= { inSoMpx2 3 }

inSoM2Level OBJECT-TYPE
	SYNTAX Integer32(-1800..1800)
	UNITS "dB/100"
	MAX-ACCESS read-write
	STATUS current
	DESCRIPTION
		"Mpx2 Level"
	::= { inSoMpx2 4 }

inSoM2Drive OBJECT-TYPE
	SYNTAX Integer32(-600..600)
	UNITS "dB/100"
	MAX-ACCESS read-write
	STATUS current
	DESCRIPTION
		"Mpx2 Drive"
	::= { inSoMpx2 5 }

inSoM2Lost OBJECT-TYPE
	SYNTAX INTEGER
		{
			undefined(0),
			yes(1),
			no(2)
		}
	MAX-ACCESS read-only
	STATUS current
	DESCRIPTION
		"Verify MPX2 presence"
	::= { inSoMpx2 6 }

inSoM2AlarmTrig OBJECT-TYPE
	SYNTAX INTEGER
		{
			undefined(0),
			none(1),
			fault(2),
			warning(3)
		}
	MAX-ACCESS read-write
	STATUS current
	DESCRIPTION
		"MPX2 alarm trigger"
	::= { inSoMpx2 7 }

inSoPlayer OBJECT-IDENTITY
	STATUS current
	DESCRIPTION
		"No description"
	::= { inSource 6 }

inSoPlPresence OBJECT-TYPE
	SYNTAX INTEGER
		{
			undefined(0),
			left(1),
			right(2),
			leftRight(3),
			none(4)
		}
	MAX-ACCESS read-only
	STATUS current
	DESCRIPTION
		"Player Presence"
	::= { inSoPlayer 1 }

inSoPlLeftPeakMax OBJECT-TYPE
	SYNTAX Integer32(-32000..32000)
	UNITS "dB/100"
	MAX-ACCESS read-only
	STATUS current
	DESCRIPTION
		"Player Left Peak max"
	::= { inSoPlayer 2 }

inSoPlRightPeakMax OBJECT-TYPE
	SYNTAX Integer32(-32000..32000)
	UNITS "dB/100"
	MAX-ACCESS read-only
	STATUS current
	DESCRIPTION
		"Player Right Peak max"
	::= { inSoPlayer 3 }

inSoPlLeftPeak OBJECT-TYPE
	SYNTAX Integer32(-32000..32000)
	UNITS "dB/100"
	MAX-ACCESS read-only
	STATUS current
	DESCRIPTION
		"Player Left Peak"
	::= { inSoPlayer 4 }

inSoPlRightPeak OBJECT-TYPE
	SYNTAX Integer32(-32000..32000)
	UNITS "dB/100"
	MAX-ACCESS read-only
	STATUS current
	DESCRIPTION
		"Player Right Peak"
	::= { inSoPlayer 5 }

inSoPlLevel OBJECT-TYPE
	SYNTAX Integer32(-2000..0)
	UNITS "dB/100"
	MAX-ACCESS read-write
	STATUS current
	DESCRIPTION
		"Player Level"
	::= { inSoPlayer 6 }

inSoPlDrive OBJECT-TYPE
	SYNTAX Integer32(-600..600)
	UNITS "dB/100"
	MAX-ACCESS read-write
	STATUS current
	DESCRIPTION
		"Player Drive"
	::= { inSoPlayer 7 }

inSoPlTrim OBJECT-TYPE
	SYNTAX Integer32(-300..300)
	UNITS "dB/100"
	MAX-ACCESS read-write
	STATUS current
	DESCRIPTION
		"Player Trim"
	::= { inSoPlayer 8 }

inSoPlFilter OBJECT-TYPE
	SYNTAX INTEGER
		{
			undefined(0),
			v0(1),
			v15(2),
			v16(3),
			v17(4)
		}
	MAX-ACCESS read-write
	STATUS current
	DESCRIPTION
		"Player Filter"
	::= { inSoPlayer 9 }

inSoPlPreacc OBJECT-TYPE
	SYNTAX INTEGER
		{
			undefined(0),
			v50us(1),
			v75us(2),
			off(3)
		}
	MAX-ACCESS read-write
	STATUS current
	DESCRIPTION
		"Player Pre-emphasis"
	::= { inSoPlayer 10 }

inSoPlSampling OBJECT-TYPE
	SYNTAX INTEGER
		{
			undefined(0),
			v44kHz(1),
			v48kHz(2),
			v96kHz(3)
		}
	MAX-ACCESS read-write
	STATUS current
	DESCRIPTION
		"Player Sampling"
	::= { inSoPlayer 11 }

inSoPlLost OBJECT-TYPE
	SYNTAX INTEGER
		{
			undefined(0),
			yes(1),
			no(2)
		}
	MAX-ACCESS read-only
	STATUS current
	DESCRIPTION
		"Verify Player presence"
	::= { inSoPlayer 12 }

inSoPlAlarmTrig OBJECT-TYPE
	SYNTAX INTEGER
		{
			undefined(0),
			none(1),
			fault(2),
			warning(3)
		}
	MAX-ACCESS read-write
	STATUS current
	DESCRIPTION
		"Player alarm trigger"
	::= { inSoPlayer 13 }

inSoGenerator OBJECT-IDENTITY
	STATUS current
	DESCRIPTION
		"No description"
	::= { inSource 7 }

inSoGeState OBJECT-TYPE
	SYNTAX INTEGER
		{
			undefined(0),
			off(1),
			pilot(2),
			left(3),
			right(4),
			leftRight(5),
			leftMinusRight(6)
		}
	MAX-ACCESS read-write
	STATUS current
	DESCRIPTION
		"Generator state"
	::= { inSoGenerator 1 }

inSoGeLevel1 OBJECT-TYPE
	SYNTAX Integer32(-10000..1200)
	UNITS "dB/100"
	MAX-ACCESS read-write
	STATUS current
	DESCRIPTION
		"Generator Level1"
	::= { inSoGenerator 2 }

inSoGeLevel2 OBJECT-TYPE
	SYNTAX Integer32(-10000..1200)
	UNITS "dB/100"
	MAX-ACCESS read-write
	STATUS current
	DESCRIPTION
		"Generator Level2"
	::= { inSoGenerator 3 }

inSoGeFreq1 OBJECT-TYPE
	SYNTAX Integer32(0..10000000)
	UNITS "Hz/100"
	MAX-ACCESS read-write
	STATUS current
	DESCRIPTION
		"Generator Frequency 1"
	::= { inSoGenerator 4 }

inSoGeFreq2 OBJECT-TYPE
	SYNTAX Integer32(0..10000000)
	UNITS "Hz/100"
	MAX-ACCESS read-write
	STATUS current
	DESCRIPTION
		"Generator Frequency 2"
	::= { inSoGenerator 5 }

inSoGePreacc OBJECT-TYPE
	SYNTAX INTEGER
		{
			undefined(0),
			v50us(1),
			v75us(2),
			off(3)
		}
	MAX-ACCESS read-write
	STATUS current
	DESCRIPTION
		"Generator Pre-emphasis"
	::= { inSoGenerator 6 }


inSoMpx3 OBJECT-IDENTITY
	STATUS current
	DESCRIPTION
		"No description"
	::= { inSource 8 }

inSoM3Presence OBJECT-TYPE
	SYNTAX INTEGER
		{
			undefined(0),
			mono(1),
			monoRds(2),
			monoRdsSca(3),
			stereo(4),
			stereoRds(5),
			stereoRdsSca(6),
			rdsSca(7),
			rds(8),
			sca(9),
			none(10)
		}
	MAX-ACCESS read-only
	STATUS current
	DESCRIPTION
		"Mpx3 Presence"
	::= { inSoMpx3 1 }

inSoM3PeakMax OBJECT-TYPE
	SYNTAX Integer32(-32000..32000)
	UNITS "dB/100"
	MAX-ACCESS read-only
	STATUS current
	DESCRIPTION
		"Mpx3 Peak max"
	::= { inSoMpx3 2 }

inSoM3Peak OBJECT-TYPE
	SYNTAX Integer32(-32000..32000)
	UNITS "dB/100"
	MAX-ACCESS read-only
	STATUS current
	DESCRIPTION
		"Mpx3 Peak"
	::= { inSoMpx3 3 }

inSoM3Level OBJECT-TYPE
	SYNTAX Integer32(-1800..1800)
	UNITS "dB/100"
	MAX-ACCESS read-write
	STATUS current
	DESCRIPTION
		"Mpx3 Level"
	::= { inSoMpx3 4 }

inSoM3Drive OBJECT-TYPE
	SYNTAX Integer32(-600..600)
	UNITS "dB/100"
	MAX-ACCESS read-write
	STATUS current
	DESCRIPTION
		"Mpx3 Drive"
	::= { inSoMpx3 5 }

inSoM3Lost OBJECT-TYPE
	SYNTAX INTEGER
		{
			undefined(0),
			yes(1),
			no(2)
		}
	MAX-ACCESS read-only
	STATUS current
	DESCRIPTION
		"Verify MPX3 presence"
	::= { inSoMpx3 6 }

inSoM3AlarmTrig OBJECT-TYPE
	SYNTAX INTEGER
		{
			undefined(0),
			none(1),
			fault(2),
			warning(3)
		}
	MAX-ACCESS read-write
	STATUS current
	DESCRIPTION
		"MPX3 alarm trigger"
	::= { inSoMpx3 7 }


inSoMpx4 OBJECT-IDENTITY
	STATUS current
	DESCRIPTION
		"No description"
	::= { inSource 9 }

inSoM4Presence OBJECT-TYPE
	SYNTAX INTEGER
		{
			undefined(0),
			mono(1),
			monoRds(2),
			monoRdsSca(3),
			stereo(4),
			stereoRds(5),
			stereoRdsSca(6),
			rdsSca(7),
			rds(8),
			sca(9),
			none(10)
		}
	MAX-ACCESS read-only
	STATUS current
	DESCRIPTION
		"Mpx4 Presence"
	::= { inSoMpx4 1 }

inSoM4PeakMax OBJECT-TYPE
	SYNTAX Integer32(-32000..32000)
	UNITS "dB/100"
	MAX-ACCESS read-only
	STATUS current
	DESCRIPTION
		"Mpx4 Peak max"
	::= { inSoMpx4 2 }

inSoM4Peak OBJECT-TYPE
	SYNTAX Integer32(-32000..32000)
	UNITS "dB/100"
	MAX-ACCESS read-only
	STATUS current
	DESCRIPTION
		"Mpx4 Peak"
	::= { inSoMpx4 3 }

inSoM4Level OBJECT-TYPE
	SYNTAX Integer32(-1800..1800)
	UNITS "dB/100"
	MAX-ACCESS read-write
	STATUS current
	DESCRIPTION
		"Mpx4 Level"
	::= { inSoMpx4 4 }

inSoM4Drive OBJECT-TYPE
	SYNTAX Integer32(-600..600)
	UNITS "dB/100"
	MAX-ACCESS read-write
	STATUS current
	DESCRIPTION
		"Mpx4 Drive"
	::= { inSoMpx4 5 }

inSoM4Lost OBJECT-TYPE
	SYNTAX INTEGER
		{
			undefined(0),
			yes(1),
			no(2)
		}
	MAX-ACCESS read-only
	STATUS current
	DESCRIPTION
		"Verify MPX4 presence"
	::= { inSoMpx4 6 }

inSoM4AlarmTrig OBJECT-TYPE
	SYNTAX INTEGER
		{
			undefined(0),
			none(1),
			fault(2),
			warning(3)
		}
	MAX-ACCESS read-write
	STATUS current
	DESCRIPTION
		"MPX4 alarm trigger"
	::= { inSoMpx4 7 }

-- AES 1 INPUT --
inSoAes1 OBJECT-IDENTITY
	STATUS current
	DESCRIPTION
		"No description"
	::= { inSource 10 }

inSoAes1Presence OBJECT-TYPE
	SYNTAX INTEGER
		{
			undefined(0),
			none(1),
			left(2),
			right(3),
			leftRight(4),
			mono(5),
			monoRds(6),
			monoRdsSca(7),
			stereo(8),
			stereoRds(9),
			stereoRdsSca(10),
			rds(11),
			rdsSca(12)
		}
	MAX-ACCESS read-only
	STATUS current
	DESCRIPTION
		"Presence"
	::= { inSoAes1 1 }

inSoAes1LeftPeakMax OBJECT-TYPE
	SYNTAX Integer32(-32000..32000)
	UNITS "dB/100"
	MAX-ACCESS read-only
	STATUS current
	DESCRIPTION
		"Left Peak max"
	::= { inSoAes1 2 }

inSoAes1RightPeakMax OBJECT-TYPE
	SYNTAX Integer32(-32000..32000)
	UNITS "dB/100"
	MAX-ACCESS read-only
	STATUS current
	DESCRIPTION
		"Right Peak max"
	::= { inSoAes1 3 }

inSoAes1LeftPeak OBJECT-TYPE
	SYNTAX Integer32(-32000..32000)
	UNITS "dB/100"
	MAX-ACCESS read-only
	STATUS current
	DESCRIPTION
		"Left Peak"
	::= { inSoAes1 4 }

inSoAes1RightPeak OBJECT-TYPE
	SYNTAX Integer32(-32000..32000)
	UNITS "dB/100"
	MAX-ACCESS read-only
	STATUS current
	DESCRIPTION
		"Right Peak"
	::= { inSoAes1 5 }

inSoAes1PeakMax OBJECT-TYPE
	SYNTAX Integer32(-32000..32000)
	UNITS "dB/100"
	MAX-ACCESS read-only
	STATUS current
	DESCRIPTION
		"Peak max"
	::= { inSoAes1 6 }

inSoAes1Peak OBJECT-TYPE
	SYNTAX Integer32(-32000..32000)
	UNITS "dB/100"
	MAX-ACCESS read-only
	STATUS current
	DESCRIPTION
		"Peak"
	::= { inSoAes1 7 }

inSoAes1Level OBJECT-TYPE
	SYNTAX Integer32(-2000..1800)
	UNITS "dB/100"
	MAX-ACCESS read-write
	STATUS current
	DESCRIPTION
		"Level"
	::= { inSoAes1 8 }

inSoAes1Drive OBJECT-TYPE
	SYNTAX Integer32(-600..600)
	UNITS "dB/100"
	MAX-ACCESS read-write
	STATUS current
	DESCRIPTION
		"Drive"
	::= { inSoAes1 9 }

inSoAes1Trim OBJECT-TYPE
	SYNTAX Integer32(-300..300)
	UNITS "dB/100"
	MAX-ACCESS read-write
	STATUS current
	DESCRIPTION
		"Trim"
	::= { inSoAes1 10 }

inSoAes1Filter OBJECT-TYPE
	SYNTAX INTEGER
		{
			undefined(0),
			v0(1),
			v15(2),
			v16(3),
			v17(4)
		}
	MAX-ACCESS read-write
	STATUS current
	DESCRIPTION
		"Filter"
	::= { inSoAes1 11 }

inSoAes1Preacc OBJECT-TYPE
	SYNTAX INTEGER
		{
			undefined(0),
			v50us(1),
			v75us(2),
			off(3)
		}
	MAX-ACCESS read-write
	STATUS current
	DESCRIPTION
		"Preacc"
	::= { inSoAes1 12 }

inSoAes1Lost OBJECT-TYPE
	SYNTAX INTEGER
		{
			undefined(0),
			yes(1),
			no(2)
		}
	MAX-ACCESS read-only
	STATUS current
	DESCRIPTION
		"Verify AES1 presence"
	::= { inSoAes1 13 }

inSoAes1AlarmTrig OBJECT-TYPE
	SYNTAX INTEGER
		{
			undefined(0),
			none(1),
			fault(2),
			warning(3)
		}
	MAX-ACCESS read-write
	STATUS current
	DESCRIPTION
		"AES1 alarm trigger"
	::= { inSoAes1 14 }

-- AES 2 INPUT --
inSoAes2 OBJECT-IDENTITY
	STATUS current
	DESCRIPTION
		"No description"
	::= { inSource 11 }

inSoAes2Presence OBJECT-TYPE
	SYNTAX INTEGER
		{
			undefined(0),
			none(1),
			left(2),
			right(3),
			leftRight(4),
			mono(5),
			monoRds(6),
			monoRdsSca(7),
			stereo(8),
			stereoRds(9),
			stereoRdsSca(10),
			rds(11),
			rdsSca(12)
		}
	MAX-ACCESS read-only
	STATUS current
	DESCRIPTION
		"Presence"
	::= { inSoAes2 1 }

inSoAes2LeftPeakMax OBJECT-TYPE
	SYNTAX Integer32(-32000..32000)
	UNITS "dB/100"
	MAX-ACCESS read-only
	STATUS current
	DESCRIPTION
		"Left Peak max"
	::= { inSoAes2 2 }

inSoAes2RightPeakMax OBJECT-TYPE
	SYNTAX Integer32(-32000..32000)
	UNITS "dB/100"
	MAX-ACCESS read-only
	STATUS current
	DESCRIPTION
		"Right Peak max"
	::= { inSoAes2 3 }

inSoAes2LeftPeak OBJECT-TYPE
	SYNTAX Integer32(-32000..32000)
	UNITS "dB/100"
	MAX-ACCESS read-only
	STATUS current
	DESCRIPTION
		"Left Peak"
	::= { inSoAes2 4 }

inSoAes2RightPeak OBJECT-TYPE
	SYNTAX Integer32(-32000..32000)
	UNITS "dB/100"
	MAX-ACCESS read-only
	STATUS current
	DESCRIPTION
		"Right Peak"
	::= { inSoAes2 5 }

inSoAes2PeakMax OBJECT-TYPE
	SYNTAX Integer32(-32000..32000)
	UNITS "dB/100"
	MAX-ACCESS read-only
	STATUS current
	DESCRIPTION
		"Peak max"
	::= { inSoAes2 6 }

inSoAes2Peak OBJECT-TYPE
	SYNTAX Integer32(-32000..32000)
	UNITS "dB/100"
	MAX-ACCESS read-only
	STATUS current
	DESCRIPTION
		"Peak"
	::= { inSoAes2 7 }

inSoAes2Level OBJECT-TYPE
	SYNTAX Integer32(-2000..1800)
	UNITS "dB/100"
	MAX-ACCESS read-write
	STATUS current
	DESCRIPTION
		"Level"
	::= { inSoAes2 8 }

inSoAes2Drive OBJECT-TYPE
	SYNTAX Integer32(-600..600)
	UNITS "dB/100"
	MAX-ACCESS read-write
	STATUS current
	DESCRIPTION
		"Drive"
	::= { inSoAes2 9 }

inSoAes2Trim OBJECT-TYPE
	SYNTAX Integer32(-300..300)
	UNITS "dB/100"
	MAX-ACCESS read-write
	STATUS current
	DESCRIPTION
		"Trim"
	::= { inSoAes2 10 }

inSoAes2Filter OBJECT-TYPE
	SYNTAX INTEGER
		{
			undefined(0),
			v0(1),
			v15(2),
			v16(3),
			v17(4)
		}
	MAX-ACCESS read-write
	STATUS current
	DESCRIPTION
		"Filter"
	::= { inSoAes2 11 }

inSoAes2Preacc OBJECT-TYPE
	SYNTAX INTEGER
		{
			undefined(0),
			v50us(1),
			v75us(2),
			off(3)
		}
	MAX-ACCESS read-write
	STATUS current
	DESCRIPTION
		"Preacc"
	::= { inSoAes2 12 }

inSoAes2Lost OBJECT-TYPE
	SYNTAX INTEGER
		{
			undefined(0),
			yes(1),
			no(2)
		}
	MAX-ACCESS read-only
	STATUS current
	DESCRIPTION
		"Verify AES2 presence"
	::= { inSoAes2 13 }

inSoAes2AlarmTrig OBJECT-TYPE
	SYNTAX INTEGER
		{
			undefined(0),
			none(1),
			fault(2),
			warning(3)
		}
	MAX-ACCESS read-write
	STATUS current
	DESCRIPTION
		"AES2 alarm trigger"
	::= { inSoAes2 14 }

-- AES 3 INPUT --
inSoAes3 OBJECT-IDENTITY
	STATUS current
	DESCRIPTION
		"No description"
	::= { inSource 12 }

inSoAes3Presence OBJECT-TYPE
	SYNTAX INTEGER
		{
			undefined(0),
			none(1),
			left(2),
			right(3),
			leftRight(4),
			mono(5),
			monoRds(6),
			monoRdsSca(7),
			stereo(8),
			stereoRds(9),
			stereoRdsSca(10),
			rds(11),
			rdsSca(12)
		}
	MAX-ACCESS read-only
	STATUS current
	DESCRIPTION
		"Presence"
	::= { inSoAes3 1 }

inSoAes3LeftPeakMax OBJECT-TYPE
	SYNTAX Integer32(-32000..32000)
	UNITS "dB/100"
	MAX-ACCESS read-only
	STATUS current
	DESCRIPTION
		"Left Peak max"
	::= { inSoAes3 2 }

inSoAes3RightPeakMax OBJECT-TYPE
	SYNTAX Integer32(-32000..32000)
	UNITS "dB/100"
	MAX-ACCESS read-only
	STATUS current
	DESCRIPTION
		"Right Peak max"
	::= { inSoAes3 3 }

inSoAes3LeftPeak OBJECT-TYPE
	SYNTAX Integer32(-32000..32000)
	UNITS "dB/100"
	MAX-ACCESS read-only
	STATUS current
	DESCRIPTION
		"Left Peak"
	::= { inSoAes3 4 }

inSoAes3RightPeak OBJECT-TYPE
	SYNTAX Integer32(-32000..32000)
	UNITS "dB/100"
	MAX-ACCESS read-only
	STATUS current
	DESCRIPTION
		"Right Peak"
	::= { inSoAes3 5 }

inSoAes3PeakMax OBJECT-TYPE
	SYNTAX Integer32(-32000..32000)
	UNITS "dB/100"
	MAX-ACCESS read-only
	STATUS current
	DESCRIPTION
		"Peak max"
	::= { inSoAes3 6 }

inSoAes3Peak OBJECT-TYPE
	SYNTAX Integer32(-32000..32000)
	UNITS "dB/100"
	MAX-ACCESS read-only
	STATUS current
	DESCRIPTION
		"Peak"
	::= { inSoAes3 7 }

inSoAes3Level OBJECT-TYPE
	SYNTAX Integer32(-2000..1800)
	UNITS "dB/100"
	MAX-ACCESS read-write
	STATUS current
	DESCRIPTION
		"Level"
	::= { inSoAes3 8 }

inSoAes3Drive OBJECT-TYPE
	SYNTAX Integer32(-600..600)
	UNITS "dB/100"
	MAX-ACCESS read-write
	STATUS current
	DESCRIPTION
		"Drive"
	::= { inSoAes3 9 }

inSoAes3Trim OBJECT-TYPE
	SYNTAX Integer32(-300..300)
	UNITS "dB/100"
	MAX-ACCESS read-write
	STATUS current
	DESCRIPTION
		"Trim"
	::= { inSoAes3 10 }

inSoAes3Filter OBJECT-TYPE
	SYNTAX INTEGER
		{
			undefined(0),
			v0(1),
			v15(2),
			v16(3),
			v17(4)
		}
	MAX-ACCESS read-write
	STATUS current
	DESCRIPTION
		"Filter"
	::= { inSoAes3 11 }

inSoAes3Preacc OBJECT-TYPE
	SYNTAX INTEGER
		{
			undefined(0),
			v50us(1),
			v75us(2),
			off(3)
		}
	MAX-ACCESS read-write
	STATUS current
	DESCRIPTION
		"Preacc"
	::= { inSoAes3 12 }

inSoAes3Lost OBJECT-TYPE
	SYNTAX INTEGER
		{
			undefined(0),
			yes(1),
			no(2)
		}
	MAX-ACCESS read-only
	STATUS current
	DESCRIPTION
		"Verify AES3 presence"
	::= { inSoAes3 13 }

inSoAes3AlarmTrig OBJECT-TYPE
	SYNTAX INTEGER
		{
			undefined(0),
			none(1),
			fault(2),
			warning(3)
		}
	MAX-ACCESS read-write
	STATUS current
	DESCRIPTION
		"AES3 alarm trigger"
	::= { inSoAes3 14 }

-- ANA 1 INPUT --
inSoAna1 OBJECT-IDENTITY
	STATUS current
	DESCRIPTION
		"No description"
	::= { inSource 13 }

inSoAna1Presence OBJECT-TYPE
	SYNTAX INTEGER
		{
			undefined(0),
			none(1),
			left(2),
			right(3),
			leftRight(4),
			mono(5),
			monoRds(6),
			monoRdsSca(7),
			stereo(8),
			stereoRds(9),
			stereoRdsSca(10),
			rds(11),
			rdsSca(12)
		}
	MAX-ACCESS read-only
	STATUS current
	DESCRIPTION
		"Presence"
	::= { inSoAna1 1 }

inSoAna1LeftPeakMax OBJECT-TYPE
	SYNTAX Integer32(-32000..32000)
	UNITS "dB/100"
	MAX-ACCESS read-only
	STATUS current
	DESCRIPTION
		"Left Peak max"
	::= { inSoAna1 2 }

inSoAna1RightPeakMax OBJECT-TYPE
	SYNTAX Integer32(-32000..32000)
	UNITS "dB/100"
	MAX-ACCESS read-only
	STATUS current
	DESCRIPTION
		"Right Peak max"
	::= { inSoAna1 3 }

inSoAna1LeftPeak OBJECT-TYPE
	SYNTAX Integer32(-32000..32000)
	UNITS "dB/100"
	MAX-ACCESS read-only
	STATUS current
	DESCRIPTION
		"Left Peak"
	::= { inSoAna1 4 }

inSoAna1RightPeak OBJECT-TYPE
	SYNTAX Integer32(-32000..32000)
	UNITS "dB/100"
	MAX-ACCESS read-only
	STATUS current
	DESCRIPTION
		"Right Peak"
	::= { inSoAna1 5 }

inSoAna1Level OBJECT-TYPE
	SYNTAX Integer32(-2000..1800)
	UNITS "dB/100"
	MAX-ACCESS read-write
	STATUS current
	DESCRIPTION
		"Level"
	::= { inSoAna1 6 }

inSoAna1Drive OBJECT-TYPE
	SYNTAX Integer32(-600..600)
	UNITS "dB/100"
	MAX-ACCESS read-write
	STATUS current
	DESCRIPTION
		"Drive"
	::= { inSoAna1 7 }

inSoAna1Trim OBJECT-TYPE
	SYNTAX Integer32(-300..300)
	UNITS "dB/100"
	MAX-ACCESS read-write
	STATUS current
	DESCRIPTION
		"Trim"
	::= { inSoAna1 8 }

inSoAna1Filter OBJECT-TYPE
	SYNTAX INTEGER
		{
			undefined(0),
			v0(1),
			v15(2),
			v16(3),
			v17(4)
		}
	MAX-ACCESS read-write
	STATUS current
	DESCRIPTION
		"Filter"
	::= { inSoAna1 9 }

inSoAna1Preacc OBJECT-TYPE
	SYNTAX INTEGER
		{
			undefined(0),
			v50us(1),
			v75us(2),
			off(3)
		}
	MAX-ACCESS read-write
	STATUS current
	DESCRIPTION
		"Preacc"
	::= { inSoAna1 10 }

inSoAna1Lost OBJECT-TYPE
	SYNTAX INTEGER
		{
			undefined(0),
			yes(1),
			no(2)
		}
	MAX-ACCESS read-only
	STATUS current
	DESCRIPTION
		"Verify Line1 presence"
	::= { inSoAna1 11 }

inSoAna1AlarmTrig OBJECT-TYPE
	SYNTAX INTEGER
		{
			undefined(0),
			none(1),
			fault(2),
			warning(3)
		}
	MAX-ACCESS read-write
	STATUS current
	DESCRIPTION
		"Ana1 alarm trigger"
	::= { inSoAna1 12 }


-- TYPE --
inSoType OBJECT-IDENTITY
	STATUS current
	DESCRIPTION
		"No description"
	::= { inSource 14 }

inSoTySlot1 OBJECT-TYPE
	SYNTAX INTEGER
		{
			undefined(0),
			none(1),
			aes1(2),
			aes2(3),
			aes1And2(4)
		}
	MAX-ACCESS read-write
	STATUS current
	DESCRIPTION
		"Slot 1 type."
	::= { inSoType 1 }

inSoTySlot2 OBJECT-TYPE
	SYNTAX INTEGER
		{
			undefined(0),
			none(1),
			aes(2),
			ana(3)
		}
	MAX-ACCESS read-write
	STATUS current
	DESCRIPTION
		"Slot 2 type."
	::= { inSoType 2 }

inSoTySlot3 OBJECT-TYPE
	SYNTAX INTEGER
		{
			undefined(0),
			none(1),
			mpx(2)
		}
	MAX-ACCESS read-write
	STATUS current
	DESCRIPTION
		"Slot 3 type."
	::= { inSoType 3 }


-- AOIP INPUT --
inSoAoip OBJECT-IDENTITY
	STATUS current
	DESCRIPTION
		"No description"
	::= { inSource 15 }

inSoAoipPresence OBJECT-TYPE
	SYNTAX INTEGER
		{
			undefined(0),
			none(1),
			left(2),
			right(3),
			leftRight(4),
			mono(5),
			monoRds(6),
			monoRdsSca(7),
			stereo(8),
			stereoRds(9),
			stereoRdsSca(10),
			rds(11),
			rdsSca(12)
		}
	MAX-ACCESS read-only
	STATUS current
	DESCRIPTION
		"Presence"
	::= { inSoAoip 1 }

inSoAoipLeftPeakMax OBJECT-TYPE
	SYNTAX Integer32(-32000..32000)
	UNITS "dB/100"
	MAX-ACCESS read-only
	STATUS current
	DESCRIPTION
		"Left Peak max"
	::= { inSoAoip 2 }

inSoAoipRightPeakMax OBJECT-TYPE
	SYNTAX Integer32(-32000..32000)
	UNITS "dB/100"
	MAX-ACCESS read-only
	STATUS current
	DESCRIPTION
		"Right Peak max"
	::= { inSoAoip 3 }

inSoAoipLeftPeak OBJECT-TYPE
	SYNTAX Integer32(-32000..32000)
	UNITS "dB/100"
	MAX-ACCESS read-only
	STATUS current
	DESCRIPTION
		"Left Peak"
	::= { inSoAoip 4 }

inSoAoipRightPeak OBJECT-TYPE
	SYNTAX Integer32(-32000..32000)
	UNITS "dB/100"
	MAX-ACCESS read-only
	STATUS current
	DESCRIPTION
		"Right Peak"
	::= { inSoAoip 5 }

inSoAoipPeakMax OBJECT-TYPE
	SYNTAX Integer32(-32000..32000)
	UNITS "dB/100"
	MAX-ACCESS read-only
	STATUS current
	DESCRIPTION
		"Peak max"
	::= { inSoAoip 6 }

inSoAoipPeak OBJECT-TYPE
	SYNTAX Integer32(-32000..32000)
	UNITS "dB/100"
	MAX-ACCESS read-only
	STATUS current
	DESCRIPTION
		"Peak"
	::= { inSoAoip 7 }

inSoAoipLevel OBJECT-TYPE
	SYNTAX Integer32(-2000..1800)
	UNITS "dB/100"
	MAX-ACCESS read-write
	STATUS current
	DESCRIPTION
		"Level"
	::= { inSoAoip 8 }

inSoAoipDrive OBJECT-TYPE
	SYNTAX Integer32(-600..600)
	UNITS "dB/100"
	MAX-ACCESS read-write
	STATUS current
	DESCRIPTION
		"Drive"
	::= { inSoAoip 9 }

inSoAoipTrim OBJECT-TYPE
	SYNTAX Integer32(-300..300)
	UNITS "dB/100"
	MAX-ACCESS read-write
	STATUS current
	DESCRIPTION
		"Trim"
	::= { inSoAoip 10 }

inSoAoipFilter OBJECT-TYPE
	SYNTAX INTEGER
		{
			undefined(0),
			v0(1),
			v15(2),
			v16(3),
			v17(4)
		}
	MAX-ACCESS read-write
	STATUS current
	DESCRIPTION
		"Filter"
	::= { inSoAoip 11 }

inSoAoipPreacc OBJECT-TYPE
	SYNTAX INTEGER
		{
			undefined(0),
			v50us(1),
			v75us(2),
			off(3)
		}
	MAX-ACCESS read-write
	STATUS current
	DESCRIPTION
		"Preacc"
	::= { inSoAoip 12 }

inSoAoipLost OBJECT-TYPE
	SYNTAX INTEGER
		{
			undefined(0),
			yes(1),
			no(2)
		}
	MAX-ACCESS read-only
	STATUS current
	DESCRIPTION
		"Verify AOIP presence"
	::= { inSoAoip 13 }

inSoAoipAlarmTrig OBJECT-TYPE
	SYNTAX INTEGER
		{
			undefined(0),
			none(1),
			fault(2),
			warning(3)
		}
	MAX-ACCESS read-write
	STATUS current
	DESCRIPTION
		"AOIP alarm trigger"
	::= { inSoAoip 14 }


-- INPUTS SELECT --
inSelect OBJECT-IDENTITY
	STATUS current
	DESCRIPTION
		"No description"
	::= { inputs 2 }

inSeAudio OBJECT-IDENTITY
	STATUS current
	DESCRIPTION
		"No description"
	::= { inSelect 1 }

inSeLine1Prio OBJECT-TYPE
	SYNTAX Gauge32(0..7)
	MAX-ACCESS read-write
	STATUS current
	DESCRIPTION
		"Input switch line1 priority"
	::= { inSeAudio 1 }

inSeLine2Prio OBJECT-TYPE
	SYNTAX Gauge32(0..7)
	MAX-ACCESS read-write
	STATUS current
	DESCRIPTION
		"Input switch line2 priority"
	::= { inSeAudio 2 }

inSeMpx1Prio OBJECT-TYPE
	SYNTAX Gauge32(0..7)
	MAX-ACCESS read-write
	STATUS current
	DESCRIPTION
		"Input switch mpx1 priority"
	::= { inSeAudio 3 }

inSeMpx2Prio OBJECT-TYPE
	SYNTAX Gauge32(0..7)
	MAX-ACCESS read-write
	STATUS current
	DESCRIPTION
		"Input switch mpx2 priority"
	::= { inSeAudio 4 }

inSePlayerPrio OBJECT-TYPE
	SYNTAX Gauge32(0..4)
	MAX-ACCESS read-write
	STATUS current
	DESCRIPTION
		"Input switch player priority"
	::= { inSeAudio 5 }

inSeCrossfade OBJECT-TYPE
	SYNTAX Gauge32(0..255)
	UNITS "s/10"
	MAX-ACCESS read-write
	STATUS current
	DESCRIPTION
		"Input switch crossfade"
	::= { inSeAudio 6 }

inSeSelectAudio OBJECT-TYPE
	SYNTAX INTEGER
		{
			undefined(0),
			auto(1),
			line1(2),
			line2(3),
			aoip(4),
			tuner(5),
			mpx1(6),
			mpx2(7),
			aoip1(8),
			aoip2(9),
			tuner1(10),
			tuner2(11),
			player(12),
			generator(13),
			mpx3(14),
			mpx4(15),
--			off(16),
			aes1(17),
			aes2(18),
			aes3(19),
			ana1(20)
		}
	MAX-ACCESS read-write
	STATUS current
	DESCRIPTION
		"Input coder audio select"
	::= { inSeAudio 7 }

inSeCurrentAudio OBJECT-TYPE
	SYNTAX INTEGER
		{
			undefined(0),
			none(1),
			line1(2),
			line2(3),
			aoip(4),
			tuner(5),
			mpx1(6),
			mpx2(7),
			aoip1(8),
			aoip2(9),
			tuner1(10),
			tuner2(11),
			player(12),
			generator(13),
			mpx3(14),
			mpx4(15),
			aes1(16),
			aes2(17),
			aes3(18),
			ana1(19)
		}
	MAX-ACCESS read-only
	STATUS current
	DESCRIPTION
		"Input coder current audio"
	::= { inSeAudio 8 }

inSeAlrInputSwitch OBJECT-TYPE
	SYNTAX INTEGER
		{
			undefined(0),
			on(1),
			off(2)
		}
	MAX-ACCESS read-only
	STATUS current
	DESCRIPTION
		"Input switch alarm"
	::= { inSeAudio 9 }

inSeFadein OBJECT-TYPE
	SYNTAX Gauge32(0..255)
	UNITS "s/10"
	MAX-ACCESS read-write
	STATUS current
	DESCRIPTION
		"Input switch fade in"
	::= { inSeAudio 10 }

inSeMpx3Prio OBJECT-TYPE
	SYNTAX Gauge32(0..7)
	MAX-ACCESS read-write
	STATUS current
	DESCRIPTION
		"Input switch mpx3 priority"
	::= { inSeAudio 11 }

inSeMpx4Prio OBJECT-TYPE
	SYNTAX Gauge32(0..7)
	MAX-ACCESS read-write
	STATUS current
	DESCRIPTION
		"Input switch mpx4 priority"
	::= { inSeAudio 12 }

inSeBackupsTable OBJECT-TYPE
	SYNTAX SEQUENCE OF InSeBackupsEntry
	MAX-ACCESS not-accessible
	STATUS current
	DESCRIPTION
		"Audio backup table"
	::= { inSeAudio 13 }

inSeBackupsEntry OBJECT-TYPE
	SYNTAX InSeBackupsEntry
	MAX-ACCESS not-accessible
	STATUS current
	DESCRIPTION
		"An entry of the audio backup table"
	INDEX { inSeBackupsIndex }
	::= { inSeBackupsTable 1 }

InSeBackupsEntry ::= SEQUENCE {
	inSeBackupsIndex	Integer32,
	inSeBackupsSource	INTEGER
}

inSeBackupsIndex OBJECT-TYPE
	SYNTAX Integer32 (0..6)
	MAX-ACCESS not-accessible
	STATUS current
	DESCRIPTION
		"Audio backup (1-6) source index for inSeBackups table"
	::= { inSeBackupsEntry 1 }

inSeBackupsSource OBJECT-TYPE
	SYNTAX INTEGER
		{
			undefined(0),
			none(1),
			aes1(2),
			aes2(3),
			aes3(4),
			ana1(5),
			mpx1(6),
			mpx2(7),
			aoip(8),
			player(9),
			generator(10),
			tuner(11)
		}
	MAX-ACCESS read-write
	STATUS current
	DESCRIPTION
		"Nth audio backup source"
	::= { inSeBackupsEntry 2 }


inSeAuBackupMode OBJECT-TYPE
	SYNTAX INTEGER
		{
			undefined(0),
			manu(1),
			auto(2)
		}
	MAX-ACCESS read-write
	STATUS current
	DESCRIPTION
		"Configure audio backup mode."
	::= { inSeAudio 14 }


-- Thresholods --
inSeThresholds OBJECT-IDENTITY
	STATUS current
	DESCRIPTION
		"No description"
	::= { inSelect 2 }

inSeThLine1Th OBJECT-TYPE
	SYNTAX Integer32(-116..24)
	UNITS "dB"
	MAX-ACCESS read-write
	STATUS current
	DESCRIPTION
		"Line1 switch threshold"
	::= { inSeThresholds 1 }

inSeThLine1Sil OBJECT-TYPE
	SYNTAX INTEGER
		{
			undefined(0),
			left(1),
			right(2),
			any(3),
			both(4)
		}
	MAX-ACCESS read-write
	STATUS current
	DESCRIPTION
		"Line1 switch silence"
	::= { inSeThresholds 2 }

inSeThLine2Th OBJECT-TYPE
	SYNTAX Integer32(-116..0)
	UNITS "dB"
	MAX-ACCESS read-write
	STATUS current
	DESCRIPTION
		"Line2 switch threshold"
	::= { inSeThresholds 3 }

inSeThLine2Sil OBJECT-TYPE
	SYNTAX INTEGER
		{
			undefined(0),
			left(1),
			right(2),
			any(3),
			both(4)
		}
	MAX-ACCESS read-write
	STATUS current
	DESCRIPTION
		"Line2 switch silence"
	::= { inSeThresholds 4 }

inSeThPlayerTh OBJECT-TYPE
	SYNTAX Integer32(-116..0)
	UNITS "dB"
	MAX-ACCESS read-write
	STATUS current
	DESCRIPTION
		"Player switch threshold"
	::= { inSeThresholds 5 }

inSeThPlayerSil OBJECT-TYPE
	SYNTAX INTEGER
		{
			undefined(0),
			left(1),
			right(2),
			any(3),
			both(4)
		}
	MAX-ACCESS read-write
	STATUS current
	DESCRIPTION
		"Player switch silence"
	::= { inSeThresholds 6 }

inSeThMpxTh OBJECT-TYPE
	SYNTAX Integer32(-114..24)
	UNITS "dB"
	MAX-ACCESS read-write
	STATUS obsolete
	DESCRIPTION
		"MPX switch threshold"
	::= { inSeThresholds 7 }

inSeThMpx1Th OBJECT-TYPE
	SYNTAX Integer32(-114..24)
	UNITS "dB"
	MAX-ACCESS read-write
	STATUS current
	DESCRIPTION
		"MPX1 switch threshold"
	::= { inSeThresholds 8 }

inSeThMpx2Th OBJECT-TYPE
	SYNTAX Integer32(-114..24)
	UNITS "dB"
	MAX-ACCESS read-write
	STATUS current
	DESCRIPTION
		"MPX2 switch threshold"
	::= { inSeThresholds 9 }

inSeThMpx3Th OBJECT-TYPE
	SYNTAX Integer32(-90..0)
	UNITS "dB"
	MAX-ACCESS read-write
	STATUS current
	DESCRIPTION
		"MPX3 switch threshold"
	::= { inSeThresholds 10 }

inSeThMpx4Th OBJECT-TYPE
	SYNTAX Integer32(-90..0)
	UNITS "dB"
	MAX-ACCESS read-write
	STATUS current
	DESCRIPTION
		"MPX4 switch threshold"
	::= { inSeThresholds 11 }

inSeThAes1Th OBJECT-TYPE
	SYNTAX Integer32(-90..0)
	UNITS "dB"
	MAX-ACCESS read-write
	STATUS current
	DESCRIPTION
		"AES1 switch threshold"
	::= { inSeThresholds 12 }

inSeThAes1Sil OBJECT-TYPE
	SYNTAX INTEGER
		{
			undefined(0),
			left(1),
			right(2),
			any(3),
			both(4)
		}
	MAX-ACCESS read-write
	STATUS current
	DESCRIPTION
		"AES1 switch silence"
	::= { inSeThresholds 13 }

inSeThAes2Th OBJECT-TYPE
	SYNTAX Integer32(-90..0)
	UNITS "dB"
	MAX-ACCESS read-write
	STATUS current
	DESCRIPTION
		"AES2 switch threshold"
	::= { inSeThresholds 14 }

inSeThAes2Sil OBJECT-TYPE
	SYNTAX INTEGER
		{
			undefined(0),
			left(1),
			right(2),
			any(3),
			both(4)
		}
	MAX-ACCESS read-write
	STATUS current
	DESCRIPTION
		"AES2 switch silence"
	::= { inSeThresholds 15 }

inSeThAes3Th OBJECT-TYPE
	SYNTAX Integer32(-90..0)
	UNITS "dB"
	MAX-ACCESS read-write
	STATUS current
	DESCRIPTION
		"AES3 switch threshold"
	::= { inSeThresholds 16 }

inSeThAes3Sil OBJECT-TYPE
	SYNTAX INTEGER
		{
			undefined(0),
			left(1),
			right(2),
			any(3),
			both(4)
		}
	MAX-ACCESS read-write
	STATUS current
	DESCRIPTION
		"AES3 switch silence"
	::= { inSeThresholds 17 }

inSeThAna1Th OBJECT-TYPE
	SYNTAX Integer32(-90..0)
	UNITS "dB"
	MAX-ACCESS read-write
	STATUS current
	DESCRIPTION
		"ANA1 switch threshold"
	::= { inSeThresholds 18 }

inSeThAna1Sil OBJECT-TYPE
	SYNTAX INTEGER
		{
			undefined(0),
			left(1),
			right(2),
			any(3),
			both(4)
		}
	MAX-ACCESS read-write
	STATUS current
	DESCRIPTION
		"ANA1 switch silence"
	::= { inSeThresholds 19 }

inSeThAoipTh OBJECT-TYPE
	SYNTAX Integer32(-90..0)
	UNITS "dB"
	MAX-ACCESS read-write
	STATUS current
	DESCRIPTION
		"AOIP switch threshold"
	::= { inSeThresholds 20 }

inSeThAoipSil OBJECT-TYPE
	SYNTAX INTEGER
		{
			undefined(0),
			left(1),
			right(2),
			any(3),
			both(4)
		}
	MAX-ACCESS read-write
	STATUS current
	DESCRIPTION
		"AOIP switch silence"
	::= { inSeThresholds 21 }


inSeDelays OBJECT-IDENTITY
	STATUS current
	DESCRIPTION
		"No description"
	::= { inSelect 3 }

inSeDeLine1BackDelay OBJECT-TYPE
	SYNTAX Gauge32(0..30)
	UNITS "s"
	MAX-ACCESS read-write
	STATUS current
	DESCRIPTION
		"Line1 switch back delay"
	::= { inSeDelays 1 }

inSeDeLine1Delay OBJECT-TYPE
	SYNTAX Gauge32(0..600)
	UNITS "s"
	MAX-ACCESS read-write
	STATUS current
	DESCRIPTION
		"Line1 switch delay"
	::= { inSeDelays 2 }

inSeDeLine2BackDelay OBJECT-TYPE
	SYNTAX Gauge32(0..30)
	UNITS "s"
	MAX-ACCESS read-write
	STATUS current
	DESCRIPTION
		"Line2 switch back delay"
	::= { inSeDelays 3 }

inSeDeLine2Delay OBJECT-TYPE
	SYNTAX Gauge32(0..600)
	UNITS "s"
	MAX-ACCESS read-write
	STATUS current
	DESCRIPTION
		"Line2 switch delay"
	::= { inSeDelays 4 }

inSeDePlayerBackDelay OBJECT-TYPE
	SYNTAX Gauge32(0..30)
	UNITS "s"
	MAX-ACCESS read-write
	STATUS current
	DESCRIPTION
		"Player switch back delay"
	::= { inSeDelays 5 }

inSeDePlayerDelay OBJECT-TYPE
	SYNTAX Gauge32(0..600)
	UNITS "s"
	MAX-ACCESS read-write
	STATUS current
	DESCRIPTION
		"Player switch delay"
	::= { inSeDelays 6 }

inSeDeMpxBackDelay OBJECT-TYPE
	SYNTAX Gauge32(0..30)
	UNITS "s"
	MAX-ACCESS read-write
	STATUS current
	DESCRIPTION
		"MPX1/2 switch back delay"
	::= { inSeDelays 7 }

inSeDeMpxDelay OBJECT-TYPE
	SYNTAX Gauge32(0..600)
	UNITS "s"
	MAX-ACCESS read-write
	STATUS current
	DESCRIPTION
		"MPX1/2 switch delay"
	::= { inSeDelays 8 }

inSeDeMpx34BackDelay OBJECT-TYPE
	SYNTAX Gauge32(0..30)
	UNITS "s"
	MAX-ACCESS read-write
	STATUS current
	DESCRIPTION
		"MPX3/4 switch back delay"
	::= { inSeDelays 9 }

inSeDeMpx34Delay OBJECT-TYPE
	SYNTAX Gauge32(0..600)
	UNITS "s"
	MAX-ACCESS read-write
	STATUS current
	DESCRIPTION
		"MPX3/4 switch delay"
	::= { inSeDelays 10 }

inSeDeAes1BackDelay OBJECT-TYPE
	SYNTAX Gauge32(0..30)
	UNITS "s"
	MAX-ACCESS read-write
	STATUS current
	DESCRIPTION
		"AES1 switch back delay"
	::= { inSeDelays 11 }

inSeDeAes1Delay OBJECT-TYPE
	SYNTAX Gauge32(0..600)
	UNITS "s"
	MAX-ACCESS read-write
	STATUS current
	DESCRIPTION
		"AES1 switch delay"
	::= { inSeDelays 12 }

inSeDeAes2BackDelay OBJECT-TYPE
	SYNTAX Gauge32(0..30)
	UNITS "s"
	MAX-ACCESS read-write
	STATUS current
	DESCRIPTION
		"AES2 switch back delay"
	::= { inSeDelays 13 }

inSeDeAes2Delay OBJECT-TYPE
	SYNTAX Gauge32(0..600)
	UNITS "s"
	MAX-ACCESS read-write
	STATUS current
	DESCRIPTION
		"AES2 switch delay"
	::= { inSeDelays 14 }

inSeDeAes3BackDelay OBJECT-TYPE
	SYNTAX Gauge32(0..30)
	UNITS "s"
	MAX-ACCESS read-write
	STATUS current
	DESCRIPTION
		"AES3 switch back delay"
	::= { inSeDelays 15 }

inSeDeAes3Delay OBJECT-TYPE
	SYNTAX Gauge32(0..600)
	UNITS "s"
	MAX-ACCESS read-write
	STATUS current
	DESCRIPTION
		"AES3 switch delay"
	::= { inSeDelays 16 }

inSeDeAna1BackDelay OBJECT-TYPE
	SYNTAX Gauge32(0..30)
	UNITS "s"
	MAX-ACCESS read-write
	STATUS current
	DESCRIPTION
		"ANA1 switch back delay"
	::= { inSeDelays 17 }

inSeDeAna1Delay OBJECT-TYPE
	SYNTAX Gauge32(0..600)
	UNITS "s"
	MAX-ACCESS read-write
	STATUS current
	DESCRIPTION
		"ANA1 switch delay"
	::= { inSeDelays 18 }

inSeDeMpx1BackDelay OBJECT-TYPE
	SYNTAX Gauge32(0..30)
	UNITS "s"
	MAX-ACCESS read-write
	STATUS current
	DESCRIPTION
		"MPX1 switch back delay"
	::= { inSeDelays 19 }

inSeDeMpx1Delay OBJECT-TYPE
	SYNTAX Gauge32(0..600)
	UNITS "s"
	MAX-ACCESS read-write
	STATUS current
	DESCRIPTION
		"MPX1 switch delay"
	::= { inSeDelays 20 }

inSeDeMpx2BackDelay OBJECT-TYPE
	SYNTAX Gauge32(0..30)
	UNITS "s"
	MAX-ACCESS read-write
	STATUS current
	DESCRIPTION
		"MPX2 switch back delay"
	::= { inSeDelays 21 }

inSeDeMpx2Delay OBJECT-TYPE
	SYNTAX Gauge32(0..600)
	UNITS "s"
	MAX-ACCESS read-write
	STATUS current
	DESCRIPTION
		"MPX2 switch delay"
	::= { inSeDelays 22 }

inSeDeAoipBackDelay OBJECT-TYPE
	SYNTAX Gauge32(0..30)
	UNITS "s"
	MAX-ACCESS read-write
	STATUS current
	DESCRIPTION
		"AOIP switch back delay"
	::= { inSeDelays 23 }

inSeDeAoipDelay OBJECT-TYPE
	SYNTAX Gauge32(0..600)
	UNITS "s"
	MAX-ACCESS read-write
	STATUS current
	DESCRIPTION
		"AOIP switch delay"
	::= { inSeDelays 24 }


inSeSync OBJECT-IDENTITY
	STATUS current
	DESCRIPTION
		"No description"
	::= { inSelect 4 }

inSeSyLine1 OBJECT-TYPE
	SYNTAX INTEGER
		{
			undefined(0),
			on(1),
			off(2)
		}
	MAX-ACCESS read-write
	STATUS current
	DESCRIPTION
		"Line1 NoSync Detection (Check sync)."
	::= { inSeSync 1 }

inSeSyLine2 OBJECT-TYPE
	SYNTAX INTEGER
		{
			undefined(0),
			on(1),
			off(2)
		}
	MAX-ACCESS read-write
	STATUS current
	DESCRIPTION
		"Line2 NoSync Detection (Check sync)."
	::= { inSeSync 2 }

inSeSyPlayer OBJECT-TYPE
	SYNTAX INTEGER
		{
			undefined(0),
			on(1),
			off(2)
		}
	MAX-ACCESS read-write
	STATUS current
	DESCRIPTION
		"Player NoSync Detection (Check sync)."
	::= { inSeSync 3 }

inSeSyMpx34 OBJECT-TYPE
	SYNTAX INTEGER
		{
			undefined(0),
			on(1),
			off(2)
		}
	MAX-ACCESS read-write
	STATUS current
	DESCRIPTION
		"MPX3/MPX4 NoSync Detection (Check sync)."
	::= { inSeSync 4 }

inSeSyAes1 OBJECT-TYPE
	SYNTAX INTEGER
		{
			undefined(0),
			on(1),
			off(2)
		}
	MAX-ACCESS read-write
	STATUS current
	DESCRIPTION
		"AES1 NoSync Detection (Check sync)."
	::= { inSeSync 5 }

inSeSyAes2 OBJECT-TYPE
	SYNTAX INTEGER
		{
			undefined(0),
			on(1),
			off(2)
		}
	MAX-ACCESS read-write
	STATUS current
	DESCRIPTION
		"AES2 NoSync Detection (Check sync)."
	::= { inSeSync 6 }

inSeSyAes3 OBJECT-TYPE
	SYNTAX INTEGER
		{
			undefined(0),
			on(1),
			off(2)
		}
	MAX-ACCESS read-write
	STATUS current
	DESCRIPTION
		"AES3 NoSync Detection (Check sync)."
	::= { inSeSync 7 }

inSeSyAoip OBJECT-TYPE
	SYNTAX INTEGER
		{
			undefined(0),
			on(1),
			off(2)
		}
	MAX-ACCESS read-write
	STATUS current
	DESCRIPTION
		"AOIP NoSync Detection (Check sync)."
	::= { inSeSync 8 }


inSeSampling OBJECT-IDENTITY
	STATUS current
	DESCRIPTION
		"No description"
	::= { inSelect 5 }

inSeSaLine1 OBJECT-TYPE
	SYNTAX Gauge32(0..200000)
	UNITS "Hz"
	MAX-ACCESS read-only
	STATUS current
	DESCRIPTION
		"Line1 sampling rate measurement"
	::= { inSeSampling 1 }

inSeSaLine2 OBJECT-TYPE
	SYNTAX Gauge32(0..200000)
	UNITS "Hz"
	MAX-ACCESS read-only
	STATUS current
	DESCRIPTION
		"Line2 sampling rate measurement"
	::= { inSeSampling 2 }

inSeSaPlayer OBJECT-TYPE
	SYNTAX Gauge32(0..200000)
	UNITS "Hz"
	MAX-ACCESS read-only
	STATUS current
	DESCRIPTION
		"Player sampling rate measurement"
	::= { inSeSampling 3 }

inSeSaMpx1 OBJECT-TYPE
	SYNTAX Gauge32(0..200000)
	UNITS "Hz"
	MAX-ACCESS read-only
	STATUS current
	DESCRIPTION
		"Mpx1 sampling rate measurement"
	::= { inSeSampling 4 }

inSeSaMpx2 OBJECT-TYPE
	SYNTAX Gauge32(0..200000)
	UNITS "Hz"
	MAX-ACCESS read-only
	STATUS current
	DESCRIPTION
		"Mpx2 sampling rate measurement"
	::= { inSeSampling 5 }

inSeSaMpx3 OBJECT-TYPE
	SYNTAX Gauge32(0..200000)
	UNITS "Hz"
	MAX-ACCESS read-only
	STATUS current
	DESCRIPTION
		"Mpx3 sampling rate measurement"
	::= { inSeSampling 6 }

inSeSaMpx4 OBJECT-TYPE
	SYNTAX Gauge32(0..200000)
	UNITS "Hz"
	MAX-ACCESS read-only
	STATUS current
	DESCRIPTION
		"Mpx4 sampling rate measurement"
	::= { inSeSampling 7 }


-- Input Alarms --
inAlarms OBJECT-IDENTITY
	STATUS current
	DESCRIPTION
		"No description"
	::= { inputs 3 }

inAlLine1 OBJECT-TYPE
	SYNTAX INTEGER
		{
			undefined(0),
			on(1),
			off(2)
		}
	MAX-ACCESS read-only
	STATUS current
	DESCRIPTION
		"Line1 alarm"
	::= { inAlarms 1 }

inAlLine2 OBJECT-TYPE
	SYNTAX INTEGER
		{
			undefined(0),
			on(1),
			off(2)
		}
	MAX-ACCESS read-only
	STATUS current
	DESCRIPTION
		"Line2 alarm"
	::= { inAlarms 2 }

inAlMpx1 OBJECT-TYPE
	SYNTAX INTEGER
		{
			undefined(0),
			on(1),
			off(2)
		}
	MAX-ACCESS read-only
	STATUS current
	DESCRIPTION
		"Mpx1 alarm"
	::= { inAlarms 3 }

inAlMpx2 OBJECT-TYPE
	SYNTAX INTEGER
		{
			undefined(0),
			on(1),
			off(2)
		}
	MAX-ACCESS read-only
	STATUS current
	DESCRIPTION
		"Mpx2 alarm"
	::= { inAlarms 4 }

inAlPlayer OBJECT-TYPE
	SYNTAX INTEGER
		{
			undefined(0),
			on(1),
			off(2)
		}
	MAX-ACCESS read-only
	STATUS current
	DESCRIPTION
		"Player alarm"
	::= { inAlarms 5 }

inAlFault OBJECT-TYPE
	SYNTAX INTEGER
		{
			undefined(0),
			on(1),
			off(2)
		}
	MAX-ACCESS read-only
	STATUS current
	DESCRIPTION
		"Input fault alarm"
	::= { inAlarms 6 }

inAlMpx3 OBJECT-TYPE
	SYNTAX INTEGER
		{
			undefined(0),
			on(1),
			off(2)
		}
	MAX-ACCESS read-only
	STATUS current
	DESCRIPTION
		"Mpx3 alarm"
	::= { inAlarms 7 }

inAlMpx4 OBJECT-TYPE
	SYNTAX INTEGER
		{
			undefined(0),
			on(1),
			off(2)
		}
	MAX-ACCESS read-only
	STATUS current
	DESCRIPTION
		"Mpx4 alarm"
	::= { inAlarms 8 }

inAlAes1 OBJECT-TYPE
	SYNTAX INTEGER
		{
			undefined(0),
			on(1),
			off(2)
		}
	MAX-ACCESS read-only
	STATUS current
	DESCRIPTION
		"AES1 alarm"
	::= { inAlarms 9 }

inAlAes2 OBJECT-TYPE
	SYNTAX INTEGER
		{
			undefined(0),
			on(1),
			off(2)
		}
	MAX-ACCESS read-only
	STATUS current
	DESCRIPTION
		"AES2 alarm"
	::= { inAlarms 10 }

inAlAes3 OBJECT-TYPE
	SYNTAX INTEGER
		{
			undefined(0),
			on(1),
			off(2)
		}
	MAX-ACCESS read-only
	STATUS current
	DESCRIPTION
		"AES3 alarm"
	::= { inAlarms 11 }

inAlAna1 OBJECT-TYPE
	SYNTAX INTEGER
		{
			undefined(0),
			on(1),
			off(2)
		}
	MAX-ACCESS read-only
	STATUS current
	DESCRIPTION
		"ANA1 alarm"
	::= { inAlarms 12 }

inAlAoip OBJECT-TYPE
	SYNTAX INTEGER
		{
			undefined(0),
			on(1),
			off(2)
		}
	MAX-ACCESS read-only
	STATUS current
	DESCRIPTION
		"AOIP alarm"
	::= { inAlarms 13 }


-- RDS --
rds OBJECT-IDENTITY
	STATUS current
	DESCRIPTION
		"No description"
	::= { transmitter 5 }

rdSettings OBJECT-IDENTITY
	STATUS current
	DESCRIPTION
		"No description"
	::= { rds 1 }

rdSeDsn OBJECT-TYPE
	SYNTAX INTEGER
		{
			undefined(0),
			main(1),
			alt(2)
		}
	MAX-ACCESS read-write
	STATUS current
	DESCRIPTION
		"RDS dsn selection"
	::= { rdSettings 1 }

rdSeMainId OBJECT-TYPE
	SYNTAX Gauge32(1..8)
	MAX-ACCESS read-write
	STATUS current
	DESCRIPTION
		"Main DSN ID"
	::= { rdSettings 2 }



rdSeAltId OBJECT-TYPE
	SYNTAX Gauge32(1..8)
	MAX-ACCESS read-write
	STATUS current
	DESCRIPTION
		"Alt DSN ID"
	::= { rdSettings 3 }

rdSeCtEnable OBJECT-TYPE
	SYNTAX INTEGER
		{
			undefined(0),
			on(1),
			off(2)
		}
	MAX-ACCESS read-write
	STATUS current
	DESCRIPTION
		"Enable RDS clock time"
	::= { rdSettings 4 }

rdSeCtOffset OBJECT-TYPE
	SYNTAX Integer32(-24..24)
	UNITS "Hour/2"
	MAX-ACCESS read-write
	STATUS current
	DESCRIPTION
		"RDS clock time offset"
	::= { rdSettings 5 }

rdSeCurrentPs OBJECT-TYPE
	SYNTAX DisplayString(SIZE(0..8))
	MAX-ACCESS read-only
	STATUS current
	DESCRIPTION
		"RDS current PS"
	::= { rdSettings 6 }

rdSeCurrentRt OBJECT-TYPE
	SYNTAX DisplayString(SIZE(0..64))
	MAX-ACCESS read-only
	STATUS current
	DESCRIPTION
		"RDS current RT"
	::= { rdSettings 7 }

rdMain OBJECT-IDENTITY
	STATUS current
	DESCRIPTION
		"No description"
	::= { rds 2 }

rdMaPi OBJECT-TYPE
	SYNTAX Integer32(0..65535)
	MAX-ACCESS read-write
	STATUS current
	DESCRIPTION
		"RDS Main Dsn PI"
	::= { rdMain 1 }

rdMaPs OBJECT-TYPE
	SYNTAX DisplayString(SIZE(0..8))
	MAX-ACCESS read-write
	STATUS current
	DESCRIPTION
		"RDS Main Dsn PS"
	::= { rdMain 2 }

rdMaPty OBJECT-TYPE
	SYNTAX Gauge32(0..31)
	MAX-ACCESS read-write
	STATUS current
	DESCRIPTION
		"RDS Main Dsn PTY"
	::= { rdMain 3 }

rdMaMs OBJECT-TYPE
	SYNTAX INTEGER
		{
			undefined(0),
			speech(1),
			music(2)
		}
	MAX-ACCESS read-write
	STATUS current
	DESCRIPTION
		"RDS Main Dsn MS"
	::= { rdMain 4 }

rdMaDi OBJECT-TYPE
	SYNTAX Gauge32(0..15)
	MAX-ACCESS read-write
	STATUS current
	DESCRIPTION
		"RDS Main Dsn DI"
	::= { rdMain 5 }

rdMaAf OBJECT-TYPE
	SYNTAX DisplayString(SIZE(0..182))
	MAX-ACCESS read-write
	STATUS current
	DESCRIPTION
		"RDS Main Dsn AF"
	::= { rdMain 6 }

rdMaRt OBJECT-TYPE
	SYNTAX DisplayString(SIZE(0..64))
	MAX-ACCESS read-write
	STATUS current
	DESCRIPTION
		"RDS Main Dsn RT"
	::= { rdMain 7 }

rdMaPtyn OBJECT-TYPE
	SYNTAX DisplayString(SIZE(0..8))
	MAX-ACCESS read-write
	STATUS current
	DESCRIPTION
		"RDS Main Dsn PTYN"
	::= { rdMain 8 }

rdMaGs OBJECT-TYPE
	SYNTAX DisplayString(SIZE(0..95))
	MAX-ACCESS read-write
	STATUS current
	DESCRIPTION
		"RDS Main Dsn GS"
	::= { rdMain 9 }

rdMaTa OBJECT-TYPE
	SYNTAX INTEGER
		{
			undefined(0),
			on(1),
			off(2)
		}
	MAX-ACCESS read-write
	STATUS current
	DESCRIPTION
		"RDS Main Dsn TA"
	::= { rdMain 10 }

rdMaTp OBJECT-TYPE
	SYNTAX INTEGER
		{
			undefined(0),
			on(1),
			off(2)
		}
	MAX-ACCESS read-write
	STATUS current
	DESCRIPTION
		"RDS Main Dsn TP"
	::= { rdMain 11 }

rdAlt OBJECT-IDENTITY
	STATUS current
	DESCRIPTION
		"No description"
	::= { rds 3 }

rdAtPi OBJECT-TYPE
	SYNTAX Integer32(0..65535)
	MAX-ACCESS read-write
	STATUS current
	DESCRIPTION
		"RDS Alt Dsn PI"
	::= { rdAlt 1 }

rdAtPs OBJECT-TYPE
	SYNTAX DisplayString(SIZE(0..8))
	MAX-ACCESS read-write
	STATUS current
	DESCRIPTION
		"RDS Alt Dsn PS"
	::= { rdAlt 2 }

rdAtPty OBJECT-TYPE
	SYNTAX Gauge32(0..31)
	MAX-ACCESS read-write
	STATUS current
	DESCRIPTION
		"RDS Alt Dsn PTY"
	::= { rdAlt 3 }

rdAtMs OBJECT-TYPE
	SYNTAX INTEGER
		{
			undefined(0),
			speech(1),
			music(2)
		}
	MAX-ACCESS read-write
	STATUS current
	DESCRIPTION
		"RDS Alt Dsn MS"
	::= { rdAlt 4 }

rdAtDi OBJECT-TYPE
	SYNTAX Gauge32(0..15)
	MAX-ACCESS read-write
	STATUS current
	DESCRIPTION
		"RDS Alt Dsn DI"
	::= { rdAlt 5 }

rdAtAf OBJECT-TYPE
	SYNTAX DisplayString(SIZE(0..182))
	MAX-ACCESS read-write
	STATUS current
	DESCRIPTION
		"RDS Alt Dsn AF"
	::= { rdAlt 6 }

rdAtRt OBJECT-TYPE
	SYNTAX DisplayString(SIZE(0..64))
	MAX-ACCESS read-write
	STATUS current
	DESCRIPTION
		"RDS Alt Dsn RT"
	::= { rdAlt 7 }

rdAtPtyn OBJECT-TYPE
	SYNTAX DisplayString(SIZE(0..8))
	MAX-ACCESS read-write
	STATUS current
	DESCRIPTION
		"RDS Alt Dsn PTYN"
	::= { rdAlt 8 }

rdAtGs OBJECT-TYPE
	SYNTAX DisplayString(SIZE(0..95))
	MAX-ACCESS read-write
	STATUS current
	DESCRIPTION
		"RDS Alt Dsn GS"
	::= { rdAlt 9 }

rdAtTa OBJECT-TYPE
	SYNTAX INTEGER
		{
			undefined(0),
			on(1),
			off(2)
		}
	MAX-ACCESS read-write
	STATUS current
	DESCRIPTION
		"RDS Alt Dsn TA"
	::= { rdAlt 10 }

rdAtTp OBJECT-TYPE
	SYNTAX INTEGER
		{
			undefined(0),
			on(1),
			off(2)
		}
	MAX-ACCESS read-write
	STATUS current
	DESCRIPTION
		"RDS Alt Dsn TP"
	::= { rdAlt 11 }

rdPsScrollTable OBJECT-TYPE
	SYNTAX SEQUENCE OF RdPsScrollEntry
	MAX-ACCESS not-accessible
	STATUS current
	DESCRIPTION
		"Ps Scroll configuration table"
	::= { rds 4 }

rdPsScrollEntry OBJECT-TYPE
	SYNTAX RdPsScrollEntry
	MAX-ACCESS not-accessible
	STATUS current
	DESCRIPTION
		"An entry of the rdPsScroll table"
	INDEX { rdPsScrollIndex }
	::= { rdPsScrollTable 1 }

RdPsScrollEntry ::=	SEQUENCE {
	rdPsScrollIndex		Integer32,
	rdPsScrollText		DisplayString,
	rdPsScrollRepetition	Gauge32,
	rdPsScrollEnable		INTEGER,
	rdPsScrollCenter		INTEGER,
	rdPsScrollTrunc		INTEGER,
	rdPsScrollIncrement	Gauge32,
	rdPsScrollDelay		Gauge32
}

rdPsScrollIndex OBJECT-TYPE
	SYNTAX Integer32 (0..2147483647)
	MAX-ACCESS not-accessible
	STATUS current
	DESCRIPTION
		"rdPsScrollTable index"
	::= { rdPsScrollEntry 1 }

rdPsScrollText OBJECT-TYPE
	SYNTAX DisplayString(SIZE(0..200))
	MAX-ACCESS read-write
	STATUS current
	DESCRIPTION
		"PS scroll text"
	::= { rdPsScrollEntry 2 }

rdPsScrollRepetition OBJECT-TYPE
	SYNTAX Gauge32(0..99)
	MAX-ACCESS read-write
	STATUS current
	DESCRIPTION
		"PS scroll repetition"
	::= { rdPsScrollEntry 3 }

rdPsScrollEnable OBJECT-TYPE
	SYNTAX INTEGER
		{
			undefined(0),
			on(1),
			off(2)
		}
	MAX-ACCESS read-write
	STATUS current
	DESCRIPTION
		"PS scroll enable"
	::= { rdPsScrollEntry 4 }

rdPsScrollCenter OBJECT-TYPE
	SYNTAX INTEGER
		{
			undefined(0),
			on(1),
			off(2)
		}
	MAX-ACCESS read-write
	STATUS current
	DESCRIPTION
		"PS scroll center"
	::= { rdPsScrollEntry 5 }

rdPsScrollTrunc OBJECT-TYPE
	SYNTAX INTEGER
		{
			undefined(0),
			on(1),
			off(2)
		}
	MAX-ACCESS read-write
	STATUS current
	DESCRIPTION
		"PS scroll truncate"
	::= { rdPsScrollEntry 6 }

rdPsScrollIncrement OBJECT-TYPE
	SYNTAX Gauge32(0..8)
	MAX-ACCESS read-write
	STATUS current
	DESCRIPTION
		"PS scroll increment"
	::= { rdPsScrollEntry 7 }

rdPsScrollDelay OBJECT-TYPE
	SYNTAX Gauge32(0..99)
	MAX-ACCESS read-write
	STATUS current
	DESCRIPTION
		"PS scroll delay"
	::= { rdPsScrollEntry 8 }

modulator OBJECT-IDENTITY
	STATUS current
	DESCRIPTION
		"No description"
	::= { transmitter 6 }

moDeviation OBJECT-IDENTITY
	STATUS current
	DESCRIPTION
		"No description"
	::= { modulator 1 }

moDevMpx OBJECT-TYPE
	SYNTAX Gauge32(0..15000)
	UNITS "kHz/100"
	MAX-ACCESS read-write
	STATUS current
	DESCRIPTION
		"MPX deviation"
	::= { moDeviation 1 }

moDevAudio OBJECT-TYPE
	SYNTAX Gauge32(0..15000)
	UNITS "kHz/100"
	MAX-ACCESS read-write
	STATUS current
	DESCRIPTION
		"Audio deviation"
	::= { moDeviation 2 }

moDevPilot OBJECT-TYPE
	SYNTAX Gauge32(0..255)
	UNITS "kHz/10"
	MAX-ACCESS read-write
	STATUS current
	DESCRIPTION
		"Pilot deviation"
	::= { moDeviation 3 }

moDevRds OBJECT-TYPE
	SYNTAX Gauge32(0..255)
	UNITS "kHz/10"
	MAX-ACCESS read-write
	STATUS current
	DESCRIPTION
		"RDS deviation"
	::= { moDeviation 4 }

moDevSca OBJECT-TYPE
	SYNTAX Gauge32(0..255)
	UNITS "kHz/10"
	MAX-ACCESS read-write
	STATUS current
	DESCRIPTION
		"SCA deviation"
	::= { moDeviation 5 }

moDevRmsMeas OBJECT-TYPE
	SYNTAX Gauge32(0..15000)
	UNITS "kHz/100"
	MAX-ACCESS read-only
	STATUS current
	DESCRIPTION
		"RMS deviation measure"
	::= { moDeviation 6 }

moDevPeakMeas OBJECT-TYPE
	SYNTAX Integer32(-15000..15000)
	UNITS "kHz/100"
	MAX-ACCESS read-only
	STATUS current
	DESCRIPTION
		"Peak deviation measure"
	::= { moDeviation 7 }

moDevPeakMaxMeas OBJECT-TYPE
	SYNTAX Integer32(-15000..15000)
	UNITS "kHz/100"
	MAX-ACCESS read-only
	STATUS current
	DESCRIPTION
		"Max peak deviation measure"
	::= { moDeviation 8 }

moDevMPeakMaxMeas OBJECT-TYPE
	SYNTAX Integer32(-15000..15000)
	UNITS "kHz/100"
	MAX-ACCESS read-only
	STATUS current
	DESCRIPTION
		"Max M component deviation peak measure"
	::= { moDeviation 9 }

moDevSPeakMaxMeas OBJECT-TYPE
	SYNTAX Integer32(-15000..15000)
	UNITS "kHz/100"
	MAX-ACCESS read-only
	STATUS current
	DESCRIPTION
		"Max S component deviation peak measure"
	::= { moDeviation 10 }

moSettings OBJECT-IDENTITY
	STATUS current
	DESCRIPTION
		"No description"
	::= { modulator 2 }

moSeCoder OBJECT-TYPE
	SYNTAX INTEGER
		{
			undefined(0),
			stereo(1),
			mono(2),
			monoLeft(3),
			monoRight(4)
		}
	MAX-ACCESS read-write
	STATUS current
	DESCRIPTION
		"Coder type"
	::= { moSettings 1 }

moSeCoderRdsSelect OBJECT-TYPE
	SYNTAX INTEGER
		{
			undefined(0),
			mpx1(1),
			mpx2(2),
			aoip1(3),
			aoip2(4),
			tuner1(5),
			tuner2(6),
			internal(7),
			auto(8),
			off(9),
			mpx3(10),
			mpx4(11),
			aes1(12),
			aes2(13),
			aes3(14)
		}
	MAX-ACCESS read-write
	STATUS current
	DESCRIPTION
		"Coder RDS selection"
	::= { moSettings 2 }

moSeCoderScaSelect OBJECT-TYPE
	SYNTAX INTEGER
		{
			undefined(0),
			mpx1(1),
			mpx2(2),
			aoip1(3),
			aoip2(4),
			tuner1(5),
			tuner2(6),
			auto(7),
			off(8),
			mpx3(9),
			mpx4(10),
			aes1(11),
			aes2(12),
			aes3(13)
		}
	MAX-ACCESS read-write
	STATUS current
	DESCRIPTION
		"Coder SCA selection"
	::= { moSettings 3 }

moSeCoderRdsBackup OBJECT-TYPE
	SYNTAX INTEGER
		{
			undefined(0),
			on(1),
			off(2)
		}
	MAX-ACCESS read-write
	STATUS current
	DESCRIPTION
		"Coder RDS Backup"
	::= { moSettings 4 }

moSeCoderCurrentRds OBJECT-TYPE
	SYNTAX INTEGER
		{
			undefined(0),
			none(1),
			mpx1(2),
			mpx2(3),
			aoip1(4),
			aoip2(5),
			tuner1(6),
			tuner2(7),
			internal(8),
			mpx3(9),
			mpx4(10),
			aes1(11),
			aes2(12),
			aes3(13),
			auto(14)
		}
	MAX-ACCESS read-only
	STATUS current
	DESCRIPTION
		"Coder Current RDS"
	::= { moSettings 5 }

moSeCoderCurrentSca OBJECT-TYPE
	SYNTAX INTEGER
		{
			undefined(0),
			none(1),
			mpx1(2),
			mpx2(3),
			aoip1(4),
			aoip2(5),
			tuner1(6),
			tuner2(7),
			mpx3(8),
			mpx4(9),
			aes1(10),
			aes2(11),
			aes3(12),
			auto(13)
		}
	MAX-ACCESS read-only
	STATUS current
	DESCRIPTION
		"Coder Current SCA"
	::= { moSettings 6 }

moSeCoder19kOutLevel OBJECT-TYPE
	SYNTAX Gauge32(0..8)
	MAX-ACCESS read-write
	STATUS current
	DESCRIPTION
		"19kHz Out level"
	::= { moSettings 7 }

moSeCoderAlrRdsSwitch OBJECT-TYPE
	SYNTAX INTEGER
		{
			undefined(0),
			on(1),
			off(2)
		}
	MAX-ACCESS read-only
	STATUS current
	DESCRIPTION
		"Coder RDS Switch Alarm"
	::= { moSettings 8 }

moSeCoderRdsPhase OBJECT-TYPE
	SYNTAX Integer32(-18000..18000)
	UNITS "deg/100"
	MAX-ACCESS read-write
	STATUS current
	DESCRIPTION
		"RDS Phase"
	::= { moSettings 9 }

moSeCoderRdsSelectBackup OBJECT-TYPE
	SYNTAX INTEGER
		{
			undefined(0),
			mpx1(1),
			mpx2(2),
			aoip1(3),
			aoip2(4),
			tuner1(5),
			tuner2(6),
			internal(7),
--			auto(8),
			off(9),
			mpx3(10),
			mpx4(11),
			aes1(12),
			aes2(13),
			aes3(14)
		}
	MAX-ACCESS read-write
	STATUS current
	DESCRIPTION
		"Coder RDS backup selection"
	::= { moSettings 10 }

moSoundProc OBJECT-IDENTITY
	STATUS current
	DESCRIPTION
		"No description"
	::= { modulator 3 }

moSpAgc OBJECT-IDENTITY
	STATUS obsolete
	DESCRIPTION
		"No description"
	::= { moSoundProc 1 }

moSpAgState OBJECT-TYPE
	SYNTAX INTEGER
		{
			undefined(0),
			on(1),
			off(2)
		}
	MAX-ACCESS read-write
	STATUS obsolete
	DESCRIPTION
		"AGC state"
	::= { moSpAgc 1 }

moSpAgDrive OBJECT-TYPE
	SYNTAX Integer32(-32000..32000)
	UNITS "dB/100"
	MAX-ACCESS read-write
	STATUS obsolete
	DESCRIPTION
		"AGC Drive"
	::= { moSpAgc 2 }

moSpAgAtt OBJECT-TYPE
	SYNTAX Gauge32(0..32000)
	UNITS "dB/s"
	MAX-ACCESS read-write
	STATUS obsolete
	DESCRIPTION
		"AGC Attack"
	::= { moSpAgc 3 }

moSpAgRel OBJECT-TYPE
	SYNTAX Gauge32(0..5000)
	UNITS "dB/s/100"
	MAX-ACCESS read-write
	STATUS obsolete
	DESCRIPTION
		"AGC Release"
	::= { moSpAgc 4 }

moSpAgThr OBJECT-TYPE
	SYNTAX Integer32(-7000..0)
	UNITS "dB/100"
	MAX-ACCESS read-write
	STATUS obsolete
	DESCRIPTION
		"AGC Threshold"
	::= { moSpAgc 5 }

moSpAgMeas OBJECT-TYPE
	SYNTAX Integer32(-32000..32000)
	UNITS "dB/100"
	MAX-ACCESS read-only
	STATUS obsolete
	DESCRIPTION
		"AGC measure"
	::= { moSpAgc 6 }

moSpLimiter OBJECT-IDENTITY
	STATUS obsolete
	DESCRIPTION
		"No description"
	::= { moSoundProc 2 }

moSpLimState OBJECT-TYPE
	SYNTAX INTEGER
		{
			undefined(0),
			on(1),
			off(2)
		}
	MAX-ACCESS read-write
	STATUS obsolete
	DESCRIPTION
		"Limiter state"
	::= { moSpLimiter 1 }

moSpLimVal OBJECT-TYPE
	SYNTAX Gauge32(0..200)
	UNITS "kHz"
	MAX-ACCESS read-write
	STATUS obsolete
	DESCRIPTION
		"Limiter value"
	::= { moSpLimiter 2 }

moSpLimDrive OBJECT-TYPE
	SYNTAX Gauge32(0..10)
	UNITS "db/10"
	MAX-ACCESS read-write
	STATUS obsolete
	DESCRIPTION
		"Limiter drive"
	::= { moSpLimiter 3 }

moSpLimMeas OBJECT-TYPE
	SYNTAX Gauge32(0..255)
	UNITS "db/10"
	MAX-ACCESS read-only
	STATUS obsolete
	DESCRIPTION
		"Limiter measure"
	::= { moSpLimiter 4 }

moSpLimPreset OBJECT-TYPE
	SYNTAX INTEGER
		{
			undefined(0),
			custom(1),
			preset1(2),
			preset2(3),
			preset3(4),
			preset4(5),
			preset5(6),
			preset6(7)
		}
	MAX-ACCESS read-write
	STATUS obsolete
	DESCRIPTION
		"Limiter Preset"
	::= { moSpLimiter 5 }

moSpClip OBJECT-IDENTITY
	STATUS current
	DESCRIPTION
		"No description"
	::= { moSoundProc 3 }

moSpClState OBJECT-TYPE
	SYNTAX INTEGER
		{
			undefined(0),
			on(1),
			off(2)
		}
	MAX-ACCESS read-write
	STATUS current
	DESCRIPTION
		"Clipper state"
	::= { moSpClip 1 }

moSpClVal OBJECT-TYPE
	SYNTAX Gauge32(0..200)
	UNITS "kHz"
	MAX-ACCESS read-write
	STATUS current
	DESCRIPTION
		"Clipper value"
	::= { moSpClip 2 }

moSpClMeas OBJECT-TYPE
	SYNTAX INTEGER
		{
			undefined(0),
			on(1),
			off(2)
		}
	MAX-ACCESS read-only
	STATUS current
	DESCRIPTION
		"AGC state measure"
	::= { moSpClip 3 }

moSpMpxPwr OBJECT-IDENTITY
	STATUS current
	DESCRIPTION
		"No description"
	::= { moSoundProc 4 }

moSpMpState OBJECT-TYPE
	SYNTAX INTEGER
		{
			undefined(0),
			on(1),
			off(2)
		}
	MAX-ACCESS read-write
	STATUS current
	DESCRIPTION
		"Mpx power state"
	::= { moSpMpxPwr 1 }

moSpMpTarget OBJECT-TYPE
	SYNTAX Integer32(-120..120)
	UNITS "dB"
	MAX-ACCESS read-write
	STATUS current
	DESCRIPTION
		"Mpx power target"
	::= { moSpMpxPwr 2 }

moSpMpMeas1m OBJECT-TYPE
	SYNTAX Integer32(-32000..32000)
	UNITS "dB/100"
	MAX-ACCESS read-only
	STATUS current
	DESCRIPTION
		"Mpx power measure 1m"
	::= { moSpMpxPwr 3 }

moSpMpMeas10s OBJECT-TYPE
	SYNTAX Integer32(-32000..32000)
	UNITS "dB/100"
	MAX-ACCESS read-only
	STATUS current
	DESCRIPTION
		"Mpx power measure 10s"
	::= { moSpMpxPwr 4 }

moSpMpMeasAtt OBJECT-TYPE
	SYNTAX Integer32(-32000..32000)
	UNITS "dB/100"
	MAX-ACCESS read-only
	STATUS current
	DESCRIPTION
		"Mpx power measure Att"
	::= { moSpMpxPwr 5 }


moSpPreset OBJECT-IDENTITY
	STATUS current
	DESCRIPTION
		"No description"
	::= { moSoundProc 5 }

moSpPrNum OBJECT-TYPE
	SYNTAX Gauge32(1..12)
	MAX-ACCESS read-write
	STATUS current
	DESCRIPTION
		"Current Preset number"
	::= { moSpPreset 1 }

moSpPrBypass OBJECT-TYPE
	SYNTAX INTEGER
		{
			undefined(0),
			on(1),
			off(2)
		}
	MAX-ACCESS read-write
	STATUS current
	DESCRIPTION
		"State of sound processing bypass"
	::= { moSpPreset 2 }

moSpPrPresetsTable OBJECT-TYPE
	SYNTAX SEQUENCE OF MoSpPrPresetsEntry
	MAX-ACCESS not-accessible
	STATUS current
	DESCRIPTION
		"Presets Name table"
	::= { moSpPreset 3 }

moSpPrPresetsEntry OBJECT-TYPE
	SYNTAX MoSpPrPresetsEntry
	MAX-ACCESS not-accessible
	STATUS current
	DESCRIPTION
		"An entry of the moSpPrPresetsTable"
	INDEX { moSpPrTableIndex }
	::= { moSpPrPresetsTable 1 }

MoSpPrPresetsEntry ::=	SEQUENCE {
	moSpPrTableIndex		Integer32,
	moSpPrTableName		DisplayString
}

moSpPrTableIndex OBJECT-TYPE
	SYNTAX Integer32 (0..2147483647)
	MAX-ACCESS not-accessible
	STATUS current
	DESCRIPTION
		"moSpPrPresetsTable index"
	::= { moSpPrPresetsEntry 1 }

moSpPrTableName OBJECT-TYPE
	SYNTAX DisplayString(SIZE(0..15))
	MAX-ACCESS read-only
	STATUS current
	DESCRIPTION
		"Preset Name"
	::= { moSpPrPresetsEntry 2 }


moSfn OBJECT-IDENTITY
	STATUS current
	DESCRIPTION
		"No description"
	::= { modulator 4 }

moSfConfDelay OBJECT-TYPE
	SYNTAX Gauge32(0..500000000)
	UNITS "us/100"
	MAX-ACCESS read-write
	STATUS current
	DESCRIPTION
		"Sfn delay configuration."
	::= { moSfn 1 }

moSfConfState OBJECT-TYPE
	SYNTAX INTEGER
		{
			undefined(0),
			on(1),
			off(2)
		}
	MAX-ACCESS read-write
	STATUS current
	DESCRIPTION
		"Sfn delay state : 0:Undefined 1:ON 2:OFF"
	::= { moSfn 2 }

moSfMeasDelay OBJECT-TYPE
	SYNTAX Gauge32(0..500000000)
	UNITS "us/100"
	MAX-ACCESS read-only
	STATUS current
	DESCRIPTION
		"Sfn delay measurement."
	::= { moSfn 3 }

moSfAlarm OBJECT-TYPE
	SYNTAX INTEGER
		{
			undefined(0),
			on(1),
			off(2)
		}
	MAX-ACCESS read-only
	STATUS current
	DESCRIPTION
		"Sfn alarm state : 0:Undefined 1:ON 2:OFF"
	::= { moSfn 4 }

moSfConfOp10M OBJECT-TYPE
	SYNTAX INTEGER
		{
			undefined(0),
			manual(1),
			auto(2)
		}
	MAX-ACCESS read-write
	STATUS current
	DESCRIPTION
		"Sfn 10MHz operation configuration : 0:Undefined 1:manual 2:auto"
	::= { moSfn 5 }

moSfState10M OBJECT-TYPE
	SYNTAX INTEGER
		{
			undefined(0),
			present(1),
			notPresent(2)
		}
	MAX-ACCESS read-only
	STATUS current
	DESCRIPTION
		"Sfn 10MHz state : 0:Undefined 1:present 2:not present"
	::= { moSfn 6 }

moSfClockSource OBJECT-TYPE
	SYNTAX INTEGER
		{
			undefined(0),
			internal(1),
			external(2)
		}
	MAX-ACCESS read-only
	STATUS current
	DESCRIPTION
		"Sfn clock source : 0:Undefined 1:internal 2:external"
	::= { moSfn 7 }

moSfState1PPS OBJECT-TYPE
	SYNTAX INTEGER
		{
			undefined(0),
			present(1),
			notPresent(2)
		}
	MAX-ACCESS read-only
	STATUS current
	DESCRIPTION
		"Sfn 1PPS state : 0:Undefined 1:present 2:not present"
	::= { moSfn 8 }

moSfSwitch10MAlarm OBJECT-TYPE
	SYNTAX INTEGER
		{
			undefined(0),
			on(1),
			off(2)
		}
	MAX-ACCESS read-only
	STATUS current
	DESCRIPTION
		"10MHz Switch input alarm : 0:Undefined 1:on 2:off"
	::= { moSfn 9 }

tx OBJECT-IDENTITY
	STATUS current
	DESCRIPTION
		"No description"
	::= { transmitter 7 }

txGeneral OBJECT-IDENTITY
	STATUS current
	DESCRIPTION
		"No description"
	::= { tx 1 }

txGnGlobal OBJECT-IDENTITY
	STATUS current
	DESCRIPTION
		"No description"
	::= { txGeneral 1 }

txGnGlName OBJECT-TYPE
	SYNTAX DisplayString(SIZE(0..15))
	MAX-ACCESS read-write
	STATUS current
	DESCRIPTION
		"Transmitter Name : User defined identifier for transmitter."
	::= { txGnGlobal 1 }

txGnGlType OBJECT-TYPE
	SYNTAX DisplayString(SIZE(0..8))
	MAX-ACCESS read-only
	STATUS current
	DESCRIPTION
		"Transmitter Type."
	::= { txGnGlobal 2 }

txGnGlStandby OBJECT-TYPE
	SYNTAX INTEGER
		{
			undefined(0),
			on(1),
			off(2)
		}
	MAX-ACCESS read-write
	STATUS current
	DESCRIPTION
		"Standby : 0:Undefined 1:ON 2:OFF"
	::= { txGnGlobal 3 }

txGnGlLocalMode OBJECT-TYPE
	SYNTAX INTEGER
		{
			undefined(0),
			local(1),
			remote(2)
		}
	MAX-ACCESS read-only
	STATUS current
	DESCRIPTION
		"LocalMode : 0:Undefined 1:Local 2:Remote"
	::= { txGnGlobal 4 }

txGnGlReserveType OBJECT-TYPE
	SYNTAX DisplayString(SIZE(0..8))
	MAX-ACCESS read-only
	STATUS current
	DESCRIPTION
		"Reserve transmitter Type."
	::= { txGnGlobal 5 }

txGnGlPcap OBJECT-TYPE
	SYNTAX Gauge32(0..99999)
	UNITS "W"
	MAX-ACCESS read-only
	STATUS current
	DESCRIPTION
		"Power capable"
	::= { txGnGlobal 6 }

txGnAlarms OBJECT-IDENTITY
	STATUS current
	DESCRIPTION
		"No description"
	::= { txGeneral 2 }

txGnAl3dB OBJECT-TYPE
	SYNTAX INTEGER
		{
			undefined(0),
			on(1),
			off(2)
		}
	MAX-ACCESS read-only
	STATUS current
	DESCRIPTION
		"3dB alarm State : 0:Undefined 1:ON 2:OFF"
	::= { txGnAlarms 1 }

txGnAlFault OBJECT-TYPE
	SYNTAX INTEGER
		{
			undefined(0),
			fault(1),
			off(2)
		}
	MAX-ACCESS read-only
	STATUS current
	DESCRIPTION
		"Fault State : 0:Undefined 1:FAULT 2:OFF"
	::= { txGnAlarms 2 }

txGnAlWarning OBJECT-TYPE
	SYNTAX INTEGER
		{
			undefined(0),
			on(1),
			off(2)
		}
	MAX-ACCESS read-only
	STATUS current
	DESCRIPTION
		"Warning State : 0:Undefined 1:ON 2:OFF"
	::= { txGnAlarms 3 }

txGnAlVSWR OBJECT-TYPE
	SYNTAX INTEGER
		{
			undefined(0),
			on(1),
			off(2)
		}
	MAX-ACCESS read-only
	STATUS current
	DESCRIPTION
		"VSWR State : 0:Undefined 1:ON 2:OFF"
	::= { txGnAlarms 4 }

txGnAlInterlockAnt OBJECT-TYPE
	SYNTAX INTEGER
		{
			undefined(0),
			close(1),
			open(2)
		}
	MAX-ACCESS read-only
	STATUS current
	DESCRIPTION
		"Antenna Interlock State : 0:Undefined 1:CLOSE 2:OPEN"
	::= { txGnAlarms 5 }

txGnAlInterlockLoad OBJECT-TYPE
	SYNTAX INTEGER
		{
			undefined(0),
			close(1),
			open(2)
		}
	MAX-ACCESS read-only
	STATUS obsolete
	DESCRIPTION
		"Load Interlock State : 0:Undefined 1:CLOSE 2:OPEN"
	::= { txGnAlarms 6 }

txGnAlLink OBJECT-TYPE
	SYNTAX INTEGER
		{
			undefined(0),
			open(1),
			close(2)
		}
	MAX-ACCESS read-only
	STATUS current
	DESCRIPTION
		"Link state : 0:Undefined 1:OPEN 2:CLOSE"
	::= { txGnAlarms 7 }

txGnAlVswrTrip OBJECT-TYPE
	SYNTAX INTEGER
		{
			undefined(0),
			on(1),
			off(2)
		}
	MAX-ACCESS read-only
	STATUS current
	DESCRIPTION
		"VswrTrip State : 0:Undefined 1:ON 2:OFF"
	::= { txGnAlarms 8 }

txGnAl1dB OBJECT-TYPE
	SYNTAX INTEGER
		{
			undefined(0),
			on(1),
			off(2)
		}
	MAX-ACCESS read-only
	STATUS current
	DESCRIPTION
		"1dB alarm State : 0:Undefined 1:ON 2:OFF"
	::= { txGnAlarms 9 }


txGnMeasures OBJECT-IDENTITY
	STATUS current
	DESCRIPTION
		"No description"
	::= { txGeneral 3 }

txGnMsForwardPower OBJECT-TYPE
	SYNTAX Gauge32(0..99999)
	UNITS "W"
	MAX-ACCESS read-only
	STATUS current
	DESCRIPTION
		"Forward Power (W)"
	::= { txGnMeasures 1 }

txGnMsReflectedPower OBJECT-TYPE
	SYNTAX Gauge32(0..99999)
	UNITS "W/10"
	MAX-ACCESS read-only
	STATUS current
	DESCRIPTION
		"Reflected Power (W/10)"
	::= { txGnMeasures 2 }

txGnMsVSWR OBJECT-TYPE
	SYNTAX Gauge32(10..999)
	UNITS "/10"
	MAX-ACCESS read-only
	STATUS current
	DESCRIPTION
		"VSWR (/10)"
	::= { txGnMeasures 3 }

txGnMsVswrTrip OBJECT-TYPE
	SYNTAX Gauge32(0..99)
	MAX-ACCESS read-only
	STATUS current
	DESCRIPTION
		"VswrTrip counter"
	::= { txGnMeasures 4 }


txGnRf OBJECT-IDENTITY
	STATUS current
	DESCRIPTION
		"No description"
	::= { txGeneral 4 }

txGnRfFrequency OBJECT-TYPE
	SYNTAX Gauge32(8750..10800)
	UNITS "MHz/100"
	MAX-ACCESS read-write
	STATUS current
	DESCRIPTION
		"Transmitter frequency (MHz/100) : RF frequency at the transmitter output."
	::= { txGnRf 1 }

txGnRfThreshold3dB OBJECT-TYPE
	SYNTAX Gauge32(0..99999)
	UNITS "W"
	MAX-ACCESS read-write
	STATUS current
	DESCRIPTION
		"Threshold 3dB (W) : If power fails below this threshold, an alarm will be generated"
	::= { txGnRf 2 }

txGnRfAutomatic3dBThreshold OBJECT-TYPE
	SYNTAX INTEGER
		{
			undefined(0),
			activate(1),
			deactive(2)
		}
	MAX-ACCESS read-write
	STATUS current
	DESCRIPTION
		"Automatic 3dB threshold : The 3dB threshold is automatically configured 0:Undefined 1:Activate 2:Deactive"
	::= { txGnRf 3 }

txGnRfThresholdVSWR OBJECT-TYPE
	SYNTAX Gauge32(10..999)
	UNITS "/10"
	MAX-ACCESS read-write
	STATUS current
	DESCRIPTION
		"Threshold VSWR (/10) : If VSWR is greater than this threshold, an alarm will be generated."
	::= { txGnRf 4 }

txGnRfOpmode OBJECT-TYPE
	SYNTAX INTEGER
		{
			undefined(0),
			on(1),
			off(2)
		}
	MAX-ACCESS read-write
	STATUS current
	DESCRIPTION
		"Opmode : Activate or deactive transmission 0:Undefined 1:ON 2:OFF"
	::= { txGnRf 5 }

txGnRfPower OBJECT-TYPE
	SYNTAX Gauge32(0..99999)
	UNITS "W"
	MAX-ACCESS read-write
	STATUS current
	DESCRIPTION
		"Wanted Power (W)"
	::= { txGnRf 6 }

txGnRfRFPresent OBJECT-TYPE
	SYNTAX INTEGER
		{
			undefined(0),
			on(1),
			off(2)
		}
	MAX-ACCESS read-only
	STATUS current
	DESCRIPTION
		"RFPresent : 0:Undefined 1:ON(Rf is present) 2:OFF(Rf is not present)."
	::= { txGnRf 7 }

txGnRfVswrTrip OBJECT-TYPE
	SYNTAX INTEGER
		{
			undefined(0),
			on(1),
			off(2)
		}
	MAX-ACCESS read-write
	STATUS current
	DESCRIPTION
		"VswrTrip : 0:Undefined 1:ON(enable) 2:OFF(disable)."
	::= { txGnRf 8 }

txGnRfThreshold1dB OBJECT-TYPE
	SYNTAX Gauge32(0..99999)
	UNITS "W"
	MAX-ACCESS read-write
	STATUS current
	DESCRIPTION
		"Threshold 1dB (W) : If power fails below this threshold, an alarm will be generated"
	::= { txGnRf 9 }

txGnRfMaxPower OBJECT-TYPE
	SYNTAX Gauge32(0..99999)
	UNITS "W"
	MAX-ACCESS read-write
	STATUS current
	DESCRIPTION
		"Maximum Wanted Power (W)"
	::= { txGnRf 10 }

txGnRfRfPresentMin OBJECT-TYPE
	SYNTAX Gauge32(0..99999)
	UNITS "W"
	MAX-ACCESS read-write
	STATUS current
	DESCRIPTION
		"RfPresent threshold (W) :  If power fails below this threshold, a RfPresent will be generated."
	::= { txGnRf 11 }

txGnRfVswrTrig OBJECT-TYPE
	SYNTAX INTEGER
		{
			undefined(0),
			warning(1),
			faultWarn(2),
			fault(3)
		}
	MAX-ACCESS read-write
	STATUS current
	DESCRIPTION
		"VswrTrig : Tells what kind of alarm vswr will trigger."
	::= { txGnRf 12 }


txGnPresets OBJECT-IDENTITY
	STATUS current
	DESCRIPTION
		"No description"
	::= { txGeneral 5 }

txGnPrCurrent OBJECT-TYPE
	SYNTAX Gauge32(0..8)
	MAX-ACCESS read-write
	STATUS current
	DESCRIPTION
		"Current preset : 0:no preset"
	::= { txGnPresets 1 }

txGnPrGpioMode OBJECT-TYPE
	SYNTAX INTEGER
		{
			off(0),
			input4(1),
			input8(2),
			input6(3)
		}
	MAX-ACCESS read-write
	STATUS current
	DESCRIPTION
		"Gpio Mode : 0:(off) 1:(4 inputs) 2:(8 inputs) 3:(6 inputs)."
	::= { txGnPresets 2 }

txGnPrPresetsTable OBJECT-TYPE
	SYNTAX SEQUENCE OF TxGnPrPresetsEntry
	MAX-ACCESS not-accessible
	STATUS current
	DESCRIPTION
		"Presets configuration table"
	::= { txGnPresets 3 }

txGnPrPresetsEntry OBJECT-TYPE
	SYNTAX TxGnPrPresetsEntry
	MAX-ACCESS not-accessible
	STATUS current
	DESCRIPTION
		"An entry of the txGnPrPresets table"
	INDEX { txGnPrPresetsIndex }
	::= { txGnPrPresetsTable 1 }

TxGnPrPresetsEntry ::=	SEQUENCE {
	txGnPrPresetsIndex		Integer32,
	txGnPrPresetsFreq		Gauge32,
	txGnPrPresetsPower		Gauge32,
	txGnPrPresetsName		DisplayString,
	txGnPrPresetsThreshold3dB	Gauge32,
	txGnPrPresetsThreshold1dB	Gauge32,
	txGnPrPresetsRfPresentMin	Gauge32,
	txGnPrPresetsAuto3dB		Integer32
}

txGnPrPresetsIndex OBJECT-TYPE
	SYNTAX Integer32 (0..2147483647)
	MAX-ACCESS not-accessible
	STATUS current
	DESCRIPTION
		"txGnPrPresetsTable index"
	::= { txGnPrPresetsEntry 1 }

txGnPrPresetsFreq OBJECT-TYPE
	SYNTAX Gauge32(8750..10800)
	UNITS "MHz/100"
	MAX-ACCESS read-write
	STATUS current
	DESCRIPTION
		"Preset frequency (MHz/100) : RF frequency at the transmitter output."
	::= { txGnPrPresetsEntry 2 }

txGnPrPresetsPower OBJECT-TYPE
	SYNTAX Gauge32(0..99999)
	UNITS "W"
	MAX-ACCESS read-write
	STATUS current
	DESCRIPTION
		"Wanted Power (W)"
	::= { txGnPrPresetsEntry 3 }

txGnPrPresetsName OBJECT-TYPE
	SYNTAX DisplayString(SIZE(0..15))
	MAX-ACCESS read-write
	STATUS current
	DESCRIPTION
		"Transmitter Name : User defined identifier for transmitter."
	::= { txGnPrPresetsEntry 4 }

txGnPrPresetsThreshold3dB OBJECT-TYPE
	SYNTAX Gauge32(0..99999)
	UNITS "W"
	MAX-ACCESS read-write
	STATUS current
	DESCRIPTION
		"Threshold 3dB (W) : If power fails below this threshold, an alarm will be generated"
	::= { txGnPrPresetsEntry 5 }

txGnPrPresetsThreshold1dB OBJECT-TYPE
	SYNTAX Gauge32(0..99999)
	UNITS "W"
	MAX-ACCESS read-write
	STATUS current
	DESCRIPTION
		"Threshold 1dB (W) : If power fails below this threshold, an alarm will be generated"
	::= { txGnPrPresetsEntry 6 }

txGnPrPresetsRfPresentMin OBJECT-TYPE
	SYNTAX Gauge32(0..99999)
	UNITS "W"
	MAX-ACCESS read-write
	STATUS current
	DESCRIPTION
		"Rf present threshold (W) : If power fails below this threshold, a RfPresent will be generated"
	::= { txGnPrPresetsEntry 7 }

txGnPrPresetsAuto3dB OBJECT-TYPE
	SYNTAX INTEGER
	{
		undefined(0),
		on(1),
		off(2)
	}
	MAX-ACCESS read-write
	STATUS current
	DESCRIPTION
		"Auto3dB : 0:Undefined 1:ON(enable) 2:OFF(disable)."
	::= { txGnPrPresetsEntry 8 }

txSmartFm OBJECT-IDENTITY
	STATUS current
	DESCRIPTION
		"No description"
	::= { tx 2 }

txSfMeasurements OBJECT-IDENTITY
	STATUS current
	DESCRIPTION
		"No description"
	::= { txSmartFm 1 }

txSfMeRangeMin OBJECT-TYPE
	SYNTAX Gauge32(0..150)
	UNITS "percent"
	MAX-ACCESS read-only
	STATUS current
	DESCRIPTION
		"SmartFM minimum limit."
	::= { txSfMeasurements 1 }

txSfMeRangeMax OBJECT-TYPE
	SYNTAX Gauge32(0..150)
	UNITS "percent"
	MAX-ACCESS read-only
	STATUS current
	DESCRIPTION
		"SmartFM maximum limit."
	::= { txSfMeasurements 2 }

txSfMeCurrentValue OBJECT-TYPE
	SYNTAX Gauge32(0..150)
	UNITS "percent"
	MAX-ACCESS read-only
	STATUS current
	DESCRIPTION
		"SmartFM current value."
	::= { txSfMeasurements 3 }

txSfMePwr OBJECT-TYPE
	SYNTAX Gauge32(0..99999)
	UNITS "W"
	MAX-ACCESS read-only
	STATUS current
	DESCRIPTION
		"Effective Pwr applied after SmartFM computation."
	::= { txSfMeasurements 4 }

txSfMeCurSavings OBJECT-TYPE
	SYNTAX Integer32(-99999..99999)
	UNITS "W"
	MAX-ACCESS read-only
	STATUS current
	DESCRIPTION
		"Current estimated power consumption saved, 10 seconds window average."
	::= { txSfMeasurements 5 }

txSfMeCurBoost OBJECT-TYPE
	SYNTAX Gauge32(0..100000)
	UNITS "W"
	MAX-ACCESS read-only
	STATUS current
	DESCRIPTION
		"Current estimated power boost."
	::= { txSfMeasurements 6 }

txSfMePcons OBJECT-TYPE
	SYNTAX Gauge32(0..99999)
	UNITS "W"
	MAX-ACCESS read-only
	STATUS current
	DESCRIPTION
		"Estimated power consumed by equipment."
	::= { txSfMeasurements 7 }

txSfMePconsNoSfm OBJECT-TYPE
	SYNTAX Gauge32(0..99999)
	UNITS "W"
	MAX-ACCESS read-only
	STATUS current
	DESCRIPTION
		"Power consumed by equipment estimation without SmartFM."
	::= { txSfMeasurements 8 }

txSfConfiguration OBJECT-IDENTITY
	STATUS current
	DESCRIPTION
		"No description"
	::= { txSmartFm 2 }

txSfCoState OBJECT-TYPE
	SYNTAX INTEGER
		{
			undefined(0),
			on(1),
			off(2)
		}
	MAX-ACCESS read-write
	STATUS current
	DESCRIPTION
		"SmartFM state configuration : 0:Undefined 1:ON(enable) 2:OFF(disable)."
	::= { txSfConfiguration 1 }

txSfCoMode OBJECT-TYPE
	SYNTAX INTEGER
		{
			undefined(0),
			strategy1(1),
			strategy2(2),
			strategy3(3),
			strategy4(4),
			strategy5(5)
		}
	MAX-ACCESS read-write
	STATUS current
	DESCRIPTION
		"SmartFM mode configuration : 0:Undefined 1:STANDARD 2:SAVINGS 3:SAVINGS SOFT 4:BOOST 5:LIMITED."
	::= { txSfConfiguration 2 }

txSfCoRdsCor OBJECT-TYPE
	SYNTAX INTEGER
		{
			undefined(0),
			on(1),
			off(2)
		}
	MAX-ACCESS read-write
	STATUS current
	DESCRIPTION
		"SmartFM RDS Correction : 0:Undefined 1:ON(enable) 2:OFF(disable)."
	::= { txSfConfiguration 3 }

txSfCoKwhCost OBJECT-TYPE
	SYNTAX Gauge32(0..999999999)
	UNITS "currency*10000"
	MAX-ACCESS read-write
	STATUS current
	DESCRIPTION
		"Cost for 1kWh in currency*10000."
	::= { txSfConfiguration 4 }


txSfStatus OBJECT-IDENTITY
	STATUS current
	DESCRIPTION
		"No description"
	::= { txSmartFm 3 }

txSfStAct OBJECT-TYPE
	SYNTAX INTEGER
		{
			undefined(0),
			on(1),
			off(2)
		}
	MAX-ACCESS read-only
	STATUS current
	DESCRIPTION
		"Internal SmartFM activation : 0:Undefined 1:ON(activated) 2:OFF(deactivated)."
	::= { txSfStatus 1 }

txSfStAlarm OBJECT-TYPE
	SYNTAX INTEGER
		{
			undefined(0),
			on(1),
			off(2)
		}
	MAX-ACCESS read-only
	STATUS current
	DESCRIPTION
		"SmartFM alarm status : 0:Undefined 1:ON(activated) 2:OFF(deactivated)."
	::= { txSfStatus 2 }


txSfLifeTime OBJECT-IDENTITY
	STATUS current
	DESCRIPTION
		"No description"
	::= { txSmartFm 4 }

txSfLiSavings OBJECT-TYPE
	SYNTAX Gauge32(0..2147483647)
	UNITS "Wh"
	MAX-ACCESS read-only
	STATUS current
	DESCRIPTION
		"Total lifetime savings in Wh."
	::= { txSfLifeTime 1 }

txSfLiBoost OBJECT-TYPE
	SYNTAX Gauge32(0..2147483647)
	UNITS "Wh"
	MAX-ACCESS read-only
	STATUS current
	DESCRIPTION
		"Total lifetime boost in Wh."
	::= { txSfLifeTime 2 }

txSfLiCredits OBJECT-TYPE
	SYNTAX Gauge32(0..2147483647)
	MAX-ACCESS read-only
	STATUS current
	DESCRIPTION
		"Total lifetime credits."
	::= { txSfLifeTime 3 }


acu OBJECT-IDENTITY
	STATUS current
	DESCRIPTION
		"No description"
	::= { transmitter 8 }

acGeneral OBJECT-IDENTITY
	STATUS current
	DESCRIPTION
		"No description"
	::= { acu 1 }

acGnGlobal OBJECT-IDENTITY
	STATUS current
	DESCRIPTION
		"No description"
	::= { acGeneral 1 }

acGnGlDelay OBJECT-TYPE
	SYNTAX Gauge32(0..99)
	UNITS "s"
	MAX-ACCESS read-write
	STATUS current
	DESCRIPTION
		"Acu delay (seconds)."
	::= { acGnGlobal 1 }

acGnGlIterConf OBJECT-TYPE
	SYNTAX Gauge32(0..99)
	MAX-ACCESS read-write
	STATUS current
	DESCRIPTION
		"Max ACU switches number."
	::= { acGnGlobal 2 }

acGnGlOperation OBJECT-TYPE
	SYNTAX INTEGER
		{
			undefined(0),
			manu(1),
			auto(2)
		}
	MAX-ACCESS read-write
	STATUS current
	DESCRIPTION
		"ACU Operation : 0:undefined 1:MANU 2:AUTO"
	::= { acGnGlobal 3 }

acGnGlPreselection OBJECT-TYPE
	SYNTAX INTEGER
		{
			undefined(0),
			tx1(1),
			tx2(2)
		}
	MAX-ACCESS read-write
	STATUS current
	DESCRIPTION
		"ACU Preselection mode : 0:undefined 1:TX1 2:TX2"
	::= { acGnGlobal 4 }

acGnGlVSWRInhibit OBJECT-TYPE
	SYNTAX INTEGER
		{
			undefined(0),
			on(1),
			off(2)
		}
	MAX-ACCESS read-write
	STATUS current
	DESCRIPTION
		"VSWRInhibit : 0:Undefined 1:ON(VSWR Alarm will not be take into account) 2:OFF(VSWR Alarm will be take into account)"
	::= { acGnGlobal 5 }

acGnGlReserveControl OBJECT-TYPE
	SYNTAX INTEGER
		{
			undefined(0),
			on(1),
			off(2)
		}
	MAX-ACCESS read-write
	STATUS current
	DESCRIPTION
		"Reserve transmitter Control 0:Undefined 1:ON 2:OFF"
	::= { acGnGlobal 6 }

acGnGlCurrentMain OBJECT-TYPE
	SYNTAX INTEGER
		{
			undefined(0),
			tx1(1),
			tx2(2)
		}
	MAX-ACCESS read-only
	STATUS current
	DESCRIPTION
		"ACU Current Position : 0:undefined 1:TX1 2:TX2"
	::= { acGnGlobal 7 }

acGnGlLocalMode OBJECT-TYPE
	SYNTAX INTEGER
		{
			undefined(0),
			local(1),
			remote(2)
		}
	MAX-ACCESS read-only
	STATUS current
	DESCRIPTION
		"ACU LocalMode : 0:Undefined 1:Local 2:Remote"
	::= { acGnGlobal 8 }

acGnGlMainOpmode OBJECT-TYPE
	SYNTAX INTEGER
		{
			undefined(0),
			on(1),
			off(2)
		}
	MAX-ACCESS read-write
	STATUS current
	DESCRIPTION
		"Main transmitter Opmode 0:Undefined 1:ON 2:OFF"
	::= { acGnGlobal 9 }

acGnGlManSwLoc OBJECT-TYPE
	SYNTAX INTEGER
		{
			undefined(0),
			on(1),
			off(2)
		}
	MAX-ACCESS read-write
	STATUS current
	DESCRIPTION
		"Manual switch allowed if tx is in local mode 0:Undefined 1:ON 2:OFF"
	::= { acGnGlobal 10 }

acGnGlDelaySwitch OBJECT-TYPE
	SYNTAX Gauge32(0..99)
	UNITS "s"
	MAX-ACCESS read-write
	STATUS current
	DESCRIPTION
		"Acu delay after switch (seconds)."
	::= { acGnGlobal 11 }

acGnGlDelayStart OBJECT-TYPE
	SYNTAX Gauge32(0..99)
	UNITS "s"
	MAX-ACCESS read-write
	STATUS current
	DESCRIPTION
		"Acu start delay (seconds)."
	::= { acGnGlobal 12 }

acGnGlSwOnFault OBJECT-TYPE
	SYNTAX INTEGER
		{
			undefined(0),
			on(1),
			off(2)
		}
	MAX-ACCESS read-write
	STATUS current
	DESCRIPTION
		"Allow Switch if reserve is on fault 0:Undefined 1:ON 2:OFF"
	::= { acGnGlobal 13 }

acGnGlSwNoComm OBJECT-TYPE
	SYNTAX INTEGER
		{
			undefined(0),
			on(1),
			off(2)
		}
	MAX-ACCESS read-write
	STATUS current
	DESCRIPTION
		"Switch if transmitter communication lost 0:Undefined 1:ON 2:OFF"
	::= { acGnGlobal 14 }

acGnAlarms OBJECT-IDENTITY
	STATUS current
	DESCRIPTION
		"No description"
	::= { acGeneral 2 }

acGnAlFault OBJECT-TYPE
	SYNTAX INTEGER
		{
			undefined(0),
			fault(1),
			off(2)
		}
	MAX-ACCESS read-only
	STATUS current
	DESCRIPTION
		"ACU Fault State : 0:Undefined 1:FAULT 2:OFF"
	::= { acGnAlarms 1 }

acGnAlSwitchOver OBJECT-TYPE
	SYNTAX INTEGER
		{
			undefined(0),
			on(1),
			off(2)
		}
	MAX-ACCESS read-only
	STATUS current
	DESCRIPTION
		"ACU Switch Over State : 0:Undefined 1:ON 2:OFF"
	::= { acGnAlarms 2 }

acGnAlInterlockAnt OBJECT-TYPE
	SYNTAX INTEGER
		{
			undefined(0),
			close(1),
			open(2)
		}
	MAX-ACCESS read-only
	STATUS current
	DESCRIPTION
		"Antenna Interlock State : 0:Undefined 1:CLOSE 2:OPEN"
	::= { acGnAlarms 3 }

acGnAlInterlockLoad OBJECT-TYPE
	SYNTAX INTEGER
		{
			undefined(0),
			close(1),
			open(2)
		}
	MAX-ACCESS read-only
	STATUS current
	DESCRIPTION
		"Load Interlock State : 0:Undefined 1:CLOSE 2:OPEN"
	::= { acGnAlarms 4 }

acGnMeasures OBJECT-IDENTITY
	STATUS current
	DESCRIPTION
		"No description"
	::= { acGeneral 3 }

acGnMsIter OBJECT-TYPE
	SYNTAX Gauge32(0..4294967295)
	MAX-ACCESS read-only
	STATUS current
	DESCRIPTION
		"Current ACU iteration number."
	::= { acGnMeasures 1 }

acGnMsPos OBJECT-TYPE
	SYNTAX INTEGER
		{
			undefined(0),
			pos1(1),
			pos2(2),
			invalid(3)
		}
	MAX-ACCESS read-only
	STATUS current
	DESCRIPTION
		"ACU Relay Current Position : 0:undefined 1:POS1 2:POS2 3:INVALID"
	::= { acGnMeasures 2 }

acGnMsSwitchLast OBJECT-TYPE
	SYNTAX DisplayString(SIZE(0..20))
	MAX-ACCESS read-only
	STATUS current
	DESCRIPTION
		"Indicates reason of last switch."
	::= { acGnMeasures 3 }

acTx1 OBJECT-IDENTITY
	STATUS current
	DESCRIPTION
		"No description"
	::= { acu 2 }

acTx1Global OBJECT-IDENTITY
	STATUS current
	DESCRIPTION
		"No description"
	::= { acTx1 1 }

acTx1GlLocalMode OBJECT-TYPE
	SYNTAX INTEGER
		{
			undefined(0),
			local(1),
			remote(2)
		}
	MAX-ACCESS read-only
	STATUS current
	DESCRIPTION
		"Transmitter 1 LocalMode : 0:Undefined 1:Local 2:Remote"
	::= { acTx1Global 1 }

acTx1Alarms OBJECT-IDENTITY
	STATUS current
	DESCRIPTION
		"No description"
	::= { acTx1 2 }

acTx1AlFault OBJECT-TYPE
	SYNTAX INTEGER
		{
			undefined(0),
			fault(1),
			off(2)
		}
	MAX-ACCESS read-only
	STATUS current
	DESCRIPTION
		"Transmitter 1 Fault State : 0:Undefined 1:FAULT 2:OFF"
	::= { acTx1Alarms 1 }

acTx1AlWarning OBJECT-TYPE
	SYNTAX INTEGER
		{
			undefined(0),
			on(1),
			off(2)
		}
	MAX-ACCESS read-only
	STATUS current
	DESCRIPTION
		"Transmitter 1 Warning State : 0:Undefined 1:ON 2:OFF"
	::= { acTx1Alarms 2 }

acTx1AlCom OBJECT-TYPE
	SYNTAX INTEGER
		{
			undefined(0),
			failed(1),
			ok(2)
		}
	MAX-ACCESS read-only
	STATUS current
	DESCRIPTION
		"Transmitter 1 Communication State : 0:Undefined 1:Failed 2:OK"
	::= { acTx1Alarms 3 }

acTx1Measures OBJECT-IDENTITY
	STATUS current
	DESCRIPTION
		"No description"
	::= { acTx1 3 }

acTx1Rf OBJECT-IDENTITY
	STATUS current
	DESCRIPTION
		"No description"
	::= { acTx1 4 }

acTx1RfRFPresent OBJECT-TYPE
	SYNTAX INTEGER
		{
			undefined(0),
			on(1),
			off(2)
		}
	MAX-ACCESS read-only
	STATUS current
	DESCRIPTION
		"RFPresent on Transmitter 1 : 0:Undefined 1:ON(Rf is present) 2:OFF(Rf is not present)."
	::= { acTx1Rf 1 }

acTx2 OBJECT-IDENTITY
	STATUS current
	DESCRIPTION
		"No description"
	::= { acu 3 }

acTx2Global OBJECT-IDENTITY
	STATUS current
	DESCRIPTION
		"No description"
	::= { acTx2 1 }

acTx2GlLocalMode OBJECT-TYPE
	SYNTAX INTEGER
		{
			undefined(0),
			local(1),
			remote(2)
		}
	MAX-ACCESS read-only
	STATUS current
	DESCRIPTION
		"Transmitter 2 LocalMode : 0:Undefined 1:Local 2:Remote"
	::= { acTx2Global 1 }

acTx2Alarms OBJECT-IDENTITY
	STATUS current
	DESCRIPTION
		"No description"
	::= { acTx2 2 }

acTx2AlFault OBJECT-TYPE
	SYNTAX INTEGER
		{
			undefined(0),
			fault(1),
			off(2)
		}
	MAX-ACCESS read-only
	STATUS current
	DESCRIPTION
		"Transmitter 2 Fault State : 0:Undefined 1:FAULT 2:OFF"
	::= { acTx2Alarms 1 }

acTx2AlWarning OBJECT-TYPE
	SYNTAX INTEGER
		{
			undefined(0),
			on(1),
			off(2)
		}
	MAX-ACCESS read-only
	STATUS current
	DESCRIPTION
		"Transmitter 2 Warning State : 0:Undefined 1:ON 2:OFF"
	::= { acTx2Alarms 2 }

acTx2AlCom OBJECT-TYPE
	SYNTAX INTEGER
		{
			undefined(0),
			failed(1),
			ok(2)
		}
	MAX-ACCESS read-only
	STATUS current
	DESCRIPTION
		"Transmitter 2 Communication State : 0:Undefined 1:Failed 2:OK"
	::= { acTx2Alarms 3 }

acTx2Measures OBJECT-IDENTITY
	STATUS current
	DESCRIPTION
		"No description"
	::= { acTx2 3 }

acTx2Rf OBJECT-IDENTITY
	STATUS current
	DESCRIPTION
		"No description"
	::= { acTx2 4 }

acTx2RfRFPresent OBJECT-TYPE
	SYNTAX INTEGER
		{
			undefined(0),
			on(1),
			off(2)
		}
	MAX-ACCESS read-only
	STATUS current
	DESCRIPTION
		"RFPresent on Transmitter 2 : 0:Undefined 1:ON(Rf is present) 2:OFF(Rf is not present)."
	::= { acTx2Rf 1 }

sys OBJECT-IDENTITY
	STATUS current
	DESCRIPTION
		"No description"
	::= { transmitter 9 }

syGeneral OBJECT-IDENTITY
	STATUS current
	DESCRIPTION
		"No description"
	::= { sys 1 }

syGeType OBJECT-TYPE
	SYNTAX DisplayString(SIZE(0..8))
	MAX-ACCESS read-only
	STATUS current
	DESCRIPTION
		"IP Option Type"
	::= { syGeneral 1 }

syGeDate OBJECT-TYPE
	SYNTAX DisplayString(SIZE(0..10))
	MAX-ACCESS read-write
	STATUS current
	DESCRIPTION
		"IP Option Date (dd/mm/yy)"
	::= { syGeneral 2 }

syGeTime OBJECT-TYPE
	SYNTAX DisplayString(SIZE(0..8))
	MAX-ACCESS read-write
	STATUS current
	DESCRIPTION
		"IP Option Time (hh:mm:ss)"
	::= { syGeneral 3 }

syGeName OBJECT-TYPE
	SYNTAX DisplayString(SIZE(0..15))
	MAX-ACCESS read-write
	STATUS current
	DESCRIPTION
		"System Control Name : User defined identifier for system."
	::= { syGeneral 4 }

syGeHardRel OBJECT-TYPE
	SYNTAX DisplayString(SIZE(0..8))
	MAX-ACCESS read-only
	STATUS current
	DESCRIPTION
		"System control hardware version."
	::= { syGeneral 5 }

syGeSoftRel OBJECT-TYPE
	SYNTAX DisplayString(SIZE(0..8))
	MAX-ACCESS read-only
	STATUS current
	DESCRIPTION
		"System control software version."
	::= { syGeneral 6 }

syGeDateCode OBJECT-TYPE
	SYNTAX DisplayString(SIZE(0..8))
	MAX-ACCESS read-only
	STATUS current
	DESCRIPTION
		"System control software date tag."
	::= { syGeneral 7 }

syGeSerial OBJECT-TYPE
	SYNTAX DisplayString(SIZE(0..8))
	MAX-ACCESS read-only
	STATUS current
	DESCRIPTION
		"System control serial number."
	::= { syGeneral 8 }

syGeUptime OBJECT-TYPE
	SYNTAX Gauge32(0..4294967295)
	MAX-ACCESS read-only
	STATUS current
	DESCRIPTION
		"System control uptime."
	::= { syGeneral 9 }

syGeOptList OBJECT-TYPE
	SYNTAX DisplayString(SIZE(0..24))
	MAX-ACCESS read-only
	STATUS current
	DESCRIPTION
		"System control Options list."
	::= { syGeneral 10 }

syGeLocation OBJECT-TYPE
	SYNTAX DisplayString(SIZE(0..32))
	MAX-ACCESS read-write
	STATUS current
	DESCRIPTION
		"System location for traps."
	::= { syGeneral 11 }

syGeContact OBJECT-TYPE
	SYNTAX DisplayString(SIZE(0..32))
	MAX-ACCESS read-write
	STATUS current
	DESCRIPTION
		"System contact."
	::= { syGeneral 12 }

syGeUnit OBJECT-TYPE
	SYNTAX INTEGER
		{
			undefined(0),
			absolute(1),
			relative(2)
		}
	MAX-ACCESS read-write
	STATUS current
	DESCRIPTION
		"Unit Mode for levels : 0:Undefined 1:Absolute 2:Relative."
	::= { syGeneral 13 }

syGeTrapCounter OBJECT-TYPE
	SYNTAX Gauge32
	MAX-ACCESS read-only
	STATUS current
	DESCRIPTION
		"This mib trap counter."
	::= { syGeneral 14 }

syGeDigMPX OBJECT-TYPE
	SYNTAX INTEGER
		{
			undefined(0),
			yes(1),
			no(2)
		}
	MAX-ACCESS read-write
	STATUS current
	DESCRIPTION
		"MPX over AES"
	::= { syGeneral 15 }

syGeDigMPX2 OBJECT-TYPE
	SYNTAX INTEGER
		{
			undefined(0),
			yes(1),
			no(2)
		}
	MAX-ACCESS read-write
	STATUS current
	DESCRIPTION
		"MPX over AES 2"
	::= { syGeneral 16 }

syGeDigMPX3 OBJECT-TYPE
	SYNTAX INTEGER
		{
			undefined(0),
			yes(1),
			no(2)
		}
	MAX-ACCESS read-write
	STATUS current
	DESCRIPTION
		"MPX over AES 3"
	::= { syGeneral 17 }

syGeAOIPMpx OBJECT-TYPE
	SYNTAX INTEGER
		{
			undefined(0),
			yes(1),
			no(2)
		}
	MAX-ACCESS read-only
	STATUS current
	DESCRIPTION
		"MPX over AOIP"
	::= { syGeneral 18 }

syAlarms OBJECT-IDENTITY
	STATUS current
	DESCRIPTION
		"No description"
	::= { sys 2 }

syAlWarning OBJECT-TYPE
	SYNTAX INTEGER
		{
			undefined(0),
			on(1),
			off(2)
		}
	MAX-ACCESS read-only
	STATUS current
	DESCRIPTION
		"System Warning State : 0:Undefined 1:ON 2:OFF"
	::= { syAlarms 1 }

syAlFault OBJECT-TYPE
	SYNTAX INTEGER
		{
			undefined(0),
			on(1),
			off(2)
		}
	MAX-ACCESS read-only
	STATUS current
	DESCRIPTION
		"System Fault State : 0:Undefined 1:ON 2:OFF"
	::= { syAlarms 2 }

syAlAmb OBJECT-TYPE
	SYNTAX INTEGER
		{
			undefined(0),
			on(1),
			off(2)
		}
	MAX-ACCESS read-only
	STATUS current
	DESCRIPTION
		"System Ambient temperature Alarm State : 0:Undefined 1:ON 2:OFF"
	::= { syAlarms 3 }

syAlVoltAux OBJECT-TYPE
	SYNTAX INTEGER
		{
			undefined(0),
			on(1),
			off(2)
		}
	MAX-ACCESS read-only
	STATUS current
	DESCRIPTION
		"System Volt Aux Alarm State : 0:Undefined 1:ON 2:OFF"
	::= { syAlarms 4 }

syAlRelay OBJECT-TYPE
	SYNTAX INTEGER
		{
			undefined(0),
			on(1),
			off(2)
		}
	MAX-ACCESS read-only
	STATUS current
	DESCRIPTION
		"System Relay Alarm State : 0:Undefined 1:ON 2:OFF"
	::= { syAlarms 5 }

syAlReserve OBJECT-TYPE
	SYNTAX INTEGER
		{
			undefined(0),
			on(1),
			off(2)
		}
	MAX-ACCESS read-only
	STATUS current
	DESCRIPTION
		"System Reserve Alarm State : 0:Undefined 1:ON(Reserve non available) 2:OFF(Reserve available)."
	::= { syAlarms 6 }

syAlInvalidData OBJECT-TYPE
	SYNTAX INTEGER
		{
			undefined(0),
			on(1),
			off(2)
		}
	MAX-ACCESS read-only
	STATUS current
	DESCRIPTION
		"System Invalid Data Alarm State : 0:Undefined 1:ON(Data are invalid) 2:OFF(Data are valid)."
	::= { syAlarms 7 }

syAl24v OBJECT-TYPE
	SYNTAX INTEGER
		{
			undefined(0),
			on(1),
			off(2)
		}
	MAX-ACCESS read-only
	STATUS current
	DESCRIPTION
		"System 24v Alarm State : 0:Undefined 1:ON 2:OFF."
	::= { syAlarms 8 }

syAlComm OBJECT-TYPE
	SYNTAX INTEGER
		{
			undefined(0),
			on(1),
			off(2)
		}
	MAX-ACCESS read-only
	STATUS current
	DESCRIPTION
		"Internal bus communication error Alarm State : 0:Undefined 1:ON 2:OFF."
	::= { syAlarms 9 }

syAlLogging OBJECT-TYPE
	SYNTAX INTEGER
		{
			undefined(0),
			on(1),
			off(2)
		}
	MAX-ACCESS read-only
	STATUS current
	DESCRIPTION
		"SD card Logging Alarm State : 0:Undefined 1:ON 2:OFF."
	::= { syAlarms 10 }

syLossOfEth0 OBJECT-TYPE
	SYNTAX INTEGER
		{
			undefined(0),
			on(1),
			off(2)
		}
	MAX-ACCESS read-only
	STATUS current
	DESCRIPTION
		"Loss of ETH0 Alarm State : 0:Undefined 1:ON 2:OFF."
	::= { syAlarms 11 }

syLossOfEth1 OBJECT-TYPE
	SYNTAX INTEGER
		{
			undefined(0),
			on(1),
			off(2)
		}
	MAX-ACCESS read-only
	STATUS current
	DESCRIPTION
		"Loss of ETH1 Alarm State : 0:Undefined 1:ON 2:OFF."
	::= { syAlarms 12 }

-- System / Network --
syNetwork OBJECT-IDENTITY
	STATUS current
	DESCRIPTION
		"No description"
	::= { sys 3 }

syPorts OBJECT-IDENTITY
	STATUS current
	DESCRIPTION
		"No description"
	::= { sys 4 }

syLicenses OBJECT-IDENTITY
	STATUS current
	DESCRIPTION
		"No description"
	::= { sys 5 }

syLiPresence OBJECT-IDENTITY
	STATUS current
	DESCRIPTION
		"No description"
	::= { syLicenses 1 }

syLiPrRds OBJECT-TYPE
	SYNTAX INTEGER
		{
			undefined(0),
			notPresent(1),
			temporary(2),
			definitive(3)
		}
	MAX-ACCESS read-only
	STATUS current
	DESCRIPTION
		"RDS License state."
	::= { syLiPresence 1 }

syLiPrSoundProc OBJECT-TYPE
	SYNTAX INTEGER
		{
			undefined(0),
			notPresent(1),
			temporary(2),
			definitive(3)
		}
	MAX-ACCESS read-only
	STATUS current
	DESCRIPTION
		"SoundProc License state."
	::= { syLiPresence 2 }

syLiPrSfm OBJECT-TYPE
	SYNTAX INTEGER
		{
			undefined(0),
			notPresent(1),
			temporary(2),
			definitive(3)
		}
	MAX-ACCESS read-only
	STATUS current
	DESCRIPTION
		"SmartFM License state."
	::= { syLiPresence 3 }

syLiPrActivation OBJECT-TYPE
	SYNTAX INTEGER
		{
			undefined(0),
			notPresent(1),
			temporary(2),
			definitive(3)
		}
	MAX-ACCESS read-only
	STATUS current
	DESCRIPTION
		"Activation License state."
	::= { syLiPresence 4 }

syLiPrAoipdecoder OBJECT-TYPE
	SYNTAX INTEGER
		{
			undefined(0),
			notPresent(1),
			temporary(2),
			definitive(3)
		}
	MAX-ACCESS read-only
	STATUS current
	DESCRIPTION
		"Aoip decoder License state."
	::= { syLiPresence 5 }

syLiPrMpxoipdecoder OBJECT-TYPE
	SYNTAX INTEGER
		{
			undefined(0),
			notPresent(1),
			temporary(2),
			definitive(3)
		}
	MAX-ACCESS read-only
	STATUS current
	DESCRIPTION
		"Mpxoip decoder License state."
	::= { syLiPresence 6 }

syLiPrSurestream OBJECT-TYPE
	SYNTAX INTEGER
		{
			undefined(0),
			notPresent(1),
			temporary(2),
			definitive(3)
		}
	MAX-ACCESS read-only
	STATUS current
	DESCRIPTION
		"Surestream License state."
	::= { syLiPresence 7 }

syLiPrSynchrostream OBJECT-TYPE
	SYNTAX INTEGER
		{
			undefined(0),
			notPresent(1),
			temporary(2),
			definitive(3)
		}
	MAX-ACCESS read-only
	STATUS current
	DESCRIPTION
		"Synchrostream License state."
	::= { syLiPresence 8 }


syLiRemaining OBJECT-IDENTITY
	STATUS current
	DESCRIPTION
		"No description"
	::= { syLicenses 2 }

syLiReRds OBJECT-TYPE
	SYNTAX Gauge32(0..4294967295)
	MAX-ACCESS read-only
	STATUS current
	DESCRIPTION
		"Remaining credits for RDS license when temporary."
	::= { syLiRemaining 1 }

syLiReSoundProc OBJECT-TYPE
	SYNTAX Gauge32(0..4294967295)
	MAX-ACCESS read-only
	STATUS current
	DESCRIPTION
		"Remaining credits for SoundProc license when temporary."
	::= { syLiRemaining 2 }

syLiReSfm OBJECT-TYPE
	SYNTAX Gauge32(0..4294967295)
	MAX-ACCESS read-only
	STATUS current
	DESCRIPTION
		"Remaining credits for SmartFM license when temporary."
	::= { syLiRemaining 3 }

syLiReActivation OBJECT-TYPE
	SYNTAX Gauge32(0..4294967295)
	MAX-ACCESS read-only
	STATUS current
	DESCRIPTION
		"Remaining credits for Activation license when temporary."
	::= { syLiRemaining 4 }

syLiReAoipdecoder OBJECT-TYPE
	SYNTAX Gauge32(0..4294967295)
	MAX-ACCESS read-only
	STATUS current
	DESCRIPTION
		"Remaining credits for Aoip decoder license when temporary."
	::= { syLiRemaining 5 }

syLiReMpxoipdecoder OBJECT-TYPE
	SYNTAX Gauge32(0..4294967295)
	MAX-ACCESS read-only
	STATUS current
	DESCRIPTION
		"Remaining credits for Mpxoip decoder license when temporary."
	::= { syLiRemaining 6 }

syLiReSurestream OBJECT-TYPE
	SYNTAX Gauge32(0..4294967295)
	MAX-ACCESS read-only
	STATUS current
	DESCRIPTION
		"Remaining credits for Surestream license when temporary."
	::= { syLiRemaining 7 }

syLiReSynchrostream OBJECT-TYPE
	SYNTAX Gauge32(0..4294967295)
	MAX-ACCESS read-only
	STATUS current
	DESCRIPTION
		"Remaining credits for Synchrostream license when temporary."
	::= { syLiRemaining 8 }


syLiAlarms OBJECT-IDENTITY
	STATUS current
	DESCRIPTION
		"No description"
	::= { syLicenses 3 }

syLiAlRds OBJECT-TYPE
	SYNTAX INTEGER
		{
			undefined(0),
			on(1),
			off(2)
		}
	MAX-ACCESS read-only
	STATUS current
	DESCRIPTION
		"RDS license expiration alarm."
	::= { syLiAlarms 1 }

syLiAlSoundProc OBJECT-TYPE
	SYNTAX INTEGER
		{
			undefined(0),
			on(1),
			off(2)
		}
	MAX-ACCESS read-only
	STATUS current
	DESCRIPTION
		"SoundProc license expiration alarm."
	::= { syLiAlarms 2 }

syLiAlSfm OBJECT-TYPE
	SYNTAX INTEGER
		{
			undefined(0),
			on(1),
			off(2)
		}
	MAX-ACCESS read-only
	STATUS current
	DESCRIPTION
		"SmartFM license expiration alarm."
	::= { syLiAlarms 3 }

syLiAlActivation OBJECT-TYPE
	SYNTAX INTEGER
		{
			undefined(0),
			on(1),
			off(2)
		}
	MAX-ACCESS read-only
	STATUS current
	DESCRIPTION
		"Activation license expiration alarm."
	::= { syLiAlarms 4 }

syLiAlAoipdecoder OBJECT-TYPE
	SYNTAX INTEGER
		{
			undefined(0),
			on(1),
			off(2)
		}
	MAX-ACCESS read-only
	STATUS current
	DESCRIPTION
		"Aoip decoder license expiration alarm."
	::= { syLiAlarms 5 }

syLiAlMpxoipdecoder OBJECT-TYPE
	SYNTAX INTEGER
		{
			undefined(0),
			on(1),
			off(2)
		}
	MAX-ACCESS read-only
	STATUS current
	DESCRIPTION
		"Mpxoip decoder license expiration alarm."
	::= { syLiAlarms 6 }

syLiAlSurestream OBJECT-TYPE
	SYNTAX INTEGER
		{
			undefined(0),
			on(1),
			off(2)
		}
	MAX-ACCESS read-only
	STATUS current
	DESCRIPTION
		"Surestream license expiration alarm."
	::= { syLiAlarms 7 }

syLiAlSynchrostream OBJECT-TYPE
	SYNTAX INTEGER
		{
			undefined(0),
			on(1),
			off(2)
		}
	MAX-ACCESS read-only
	STATUS current
	DESCRIPTION
		"Synchrostream license expiration alarm."
	::= { syLiAlarms 8 }


monitoring OBJECT-IDENTITY
	STATUS obsolete
	DESCRIPTION
		"No description"
	::= { transmitter 10 }

moMain OBJECT-IDENTITY
	STATUS obsolete
	DESCRIPTION
		"No description"
	::= { monitoring 1 }

moMaMeas OBJECT-IDENTITY
	STATUS obsolete
	DESCRIPTION
		"Main measurements"
	::= { moMain 1 }

moMaMeVolt1 OBJECT-TYPE
	SYNTAX Gauge32(0..999)
	UNITS "V/10"
	MAX-ACCESS read-only
	STATUS obsolete
	DESCRIPTION
		"Volt1 voltage measurement."
	::= { moMaMeas 1 }

moMaMeVolt2 OBJECT-TYPE
	SYNTAX Gauge32(0..999)
	UNITS "V/10"
	MAX-ACCESS read-only
	STATUS obsolete
	DESCRIPTION
		"Volt2 voltage measurement."
	::= { moMaMeas 2 }

moMaMeCur1 OBJECT-TYPE
	SYNTAX Gauge32(0..999)
	UNITS "A/10"
	MAX-ACCESS read-only
	STATUS obsolete
	DESCRIPTION
		"Cur1 current measurement."
	::= { moMaMeas 3 }

moMaMeCur2 OBJECT-TYPE
	SYNTAX Gauge32(0..999)
	UNITS "A/10"
	MAX-ACCESS read-only
	STATUS obsolete
	DESCRIPTION
		"Cur2 current measurement."
	::= { moMaMeas 4 }

moMaMeEffSys OBJECT-TYPE
	SYNTAX Gauge32(0..100)
	UNITS "percent"
	MAX-ACCESS read-only
	STATUS obsolete
	DESCRIPTION
		"System efficiency measurement."
	::= { moMaMeas 5 }

moMaMeEffTrans OBJECT-TYPE
	SYNTAX Gauge32(0..100)
	UNITS "percent"
	MAX-ACCESS read-only
	STATUS obsolete
	DESCRIPTION
		"Transmitter efficiency measurement."
	::= { moMaMeas 6 }

moMaMePin OBJECT-TYPE
	SYNTAX Gauge32(0..999)
	UNITS "W/10"
	MAX-ACCESS read-only
	STATUS obsolete
	DESCRIPTION
		"Input power measurement."
	::= { moMaMeas 7 }



moMaAlarms OBJECT-IDENTITY
	STATUS obsolete
	DESCRIPTION
		"Main Alarms"
	::= { moMain 2 }

moMainAlVolt1 OBJECT-TYPE
	SYNTAX INTEGER
		{
			undefined(0),
			on(1),
			off(2)
		}
	MAX-ACCESS read-only
	STATUS obsolete
	DESCRIPTION
		"Volt1 voltage alarm."
	::= { moMaAlarms 1 }

moMainAlVolt2 OBJECT-TYPE
	SYNTAX INTEGER
		{
			undefined(0),
			on(1),
			off(2)
		}
	MAX-ACCESS read-only
	STATUS obsolete
	DESCRIPTION
		"Volt2 voltage alarm."
	::= { moMaAlarms 2 }

moMainAlCur1 OBJECT-TYPE
	SYNTAX INTEGER
		{
			undefined(0),
			on(1),
			off(2)
		}
	MAX-ACCESS read-only
	STATUS obsolete
	DESCRIPTION
		"Cur1 current alarm."
	::= { moMaAlarms 3 }

moMainAlCur2 OBJECT-TYPE
	SYNTAX INTEGER
		{
			undefined(0),
			on(1),
			off(2)
		}
	MAX-ACCESS read-only
	STATUS obsolete
	DESCRIPTION
		"Cur2 current alarm."
	::= { moMaAlarms 4 }

moMainAlPin OBJECT-TYPE
	SYNTAX INTEGER
		{
			undefined(0),
			on(1),
			off(2)
		}
	MAX-ACCESS read-only
	STATUS obsolete
	DESCRIPTION
		"Input power alarm."
	::= { moMaAlarms 5 }


moConditions OBJECT-IDENTITY
	STATUS obsolete
	DESCRIPTION
		"Working conditions."
	::= { monitoring 2 }

moCoMeas OBJECT-IDENTITY
	STATUS obsolete
	DESCRIPTION
		"Working conditions measurements."
	::= { moConditions 1 }

moCoMeAmb OBJECT-TYPE
	SYNTAX Integer32(-125..125)
	UNITS "Celsius Degrees"
	MAX-ACCESS read-only
	STATUS obsolete
	DESCRIPTION
		"Ambient temperature measurement."
	::= { moCoMeas 1 }

moCoMeHeat1 OBJECT-TYPE
	SYNTAX Integer32(-125..125)
	UNITS "Celsius Degrees"
	MAX-ACCESS read-only
	STATUS obsolete
	DESCRIPTION
		"Heatsink 1 temperature measurement."
	::= { moCoMeas 2 }

moCoMeHeat2 OBJECT-TYPE
	SYNTAX Integer32(-125..125)
	UNITS "Celsius Degrees"
	MAX-ACCESS read-only
	STATUS obsolete
	DESCRIPTION
		"Heatsink 2 temperature measurement."
	::= { moCoMeas 3 }

moCoMePsuTemp OBJECT-TYPE
	SYNTAX Integer32(-125..125)
	UNITS "Celsius Degrees"
	MAX-ACCESS read-only
	STATUS obsolete
	DESCRIPTION
		"PSU temperature measurement."
	::= { moCoMeas 4 }

moCoMeIntTemp OBJECT-TYPE
	SYNTAX Gauge32(0..999)
	UNITS "Celsius Degrees"
	MAX-ACCESS read-only
	STATUS obsolete
	DESCRIPTION
		"Int temperature measurement."
	::= { moCoMeas 5 }

moCoMePressure OBJECT-TYPE
	SYNTAX Gauge32(0..2000)
	UNITS "hPa"
	MAX-ACCESS read-only
	STATUS obsolete
	DESCRIPTION
		"Pressure measurement."
	::= { moCoMeas 6 }

moCoMeExcTemp OBJECT-TYPE
	SYNTAX Integer32(-125..125)
	UNITS "Celsius Degrees"
	MAX-ACCESS read-only
	STATUS obsolete
	DESCRIPTION
		"Exciter temperature measurement."
	::= { moCoMeas 7 }

moCoAlarms OBJECT-IDENTITY
	STATUS obsolete
	DESCRIPTION
		"Main Alarms"
	::= { moConditions 2 }

moCoAlHeat1 OBJECT-TYPE
	SYNTAX INTEGER
		{
			undefined(0),
			on(1),
			off(2)
		}
	MAX-ACCESS read-only
	STATUS obsolete
	DESCRIPTION
		"Heatsink 1 temperature alarm."
	::= { moCoAlarms 1 }

moCoAlHeat2 OBJECT-TYPE
	SYNTAX INTEGER
		{
			undefined(0),
			on(1),
			off(2)
		}
	MAX-ACCESS read-only
	STATUS obsolete
	DESCRIPTION
		"Heatsink 2 temperature alarm."
	::= { moCoAlarms 2 }

moCoAlTemp1 OBJECT-TYPE
	SYNTAX INTEGER
		{
			undefined(0),
			on(1),
			off(2)
		}
	MAX-ACCESS read-only
	STATUS obsolete
	DESCRIPTION
		"Temp 1 temperature alarm."
	::= { moCoAlarms 3 }

moCoAlTemp2 OBJECT-TYPE
	SYNTAX INTEGER
		{
			undefined(0),
			on(1),
			off(2)
		}
	MAX-ACCESS read-only
	STATUS obsolete
	DESCRIPTION
		"Temp 2 temperature alarm."
	::= { moCoAlarms 4 }

moCoAlPsuTemp OBJECT-TYPE
	SYNTAX INTEGER
		{
			undefined(0),
			on(1),
			off(2)
		}
	MAX-ACCESS read-only
	STATUS obsolete
	DESCRIPTION
		"PSU temperature alarm."
	::= { moCoAlarms 5 }

moCoAlIntTemp OBJECT-TYPE
	SYNTAX INTEGER
		{
			undefined(0),
			on(1),
			off(2)
		}
	MAX-ACCESS read-only
	STATUS obsolete
	DESCRIPTION
		"Int temperature alarm."
	::= { moCoAlarms 6 }

moCoAlExcTemp OBJECT-TYPE
	SYNTAX INTEGER
		{
			undefined(0),
			on(1),
			off(2)
		}
	MAX-ACCESS read-only
	STATUS obsolete
	DESCRIPTION
		"Exciter temperature alarm."
	::= { moCoAlarms 7 }

moCoAlPressure OBJECT-TYPE
	SYNTAX INTEGER
		{
			undefined(0),
			on(1),
			off(2)
		}
	MAX-ACCESS read-only
	STATUS obsolete
	DESCRIPTION
		"Pressure alarm."
	::= { moCoAlarms 8 }

moAuxVolt OBJECT-IDENTITY
	STATUS obsolete
	DESCRIPTION
		"No description"
	::= { monitoring 3 }

moAuMeas OBJECT-IDENTITY
	STATUS obsolete
	DESCRIPTION
		"Aux Volt measurements."
	::= { moAuxVolt 1 }

moAuMe5V OBJECT-TYPE
	SYNTAX Gauge32(0..9999)
	UNITS "Volt/100"
	MAX-ACCESS read-only
	STATUS obsolete
	DESCRIPTION
		"Internal 5V measurement."
	::= { moAuMeas 1 }

moAuMe12V OBJECT-TYPE
	SYNTAX Gauge32(0..9999)
	UNITS "Volt/100"
	MAX-ACCESS read-only
	STATUS obsolete
	DESCRIPTION
		"Internal 12V measurement."
	::= { moAuMeas 2 }

moAuMeN12V OBJECT-TYPE
	SYNTAX Integer32(-9999..0)
	UNITS "Volt/100"
	MAX-ACCESS read-only
	STATUS obsolete
	DESCRIPTION
		"Internal -12V measurement."
	::= { moAuMeas 3 }

moAuAlarms OBJECT-IDENTITY
	STATUS obsolete
	DESCRIPTION
		"Aux Volt Alarms."
	::= { moAuxVolt 2 }


moFan OBJECT-IDENTITY
	STATUS obsolete
	DESCRIPTION
		"No description"
	::= { monitoring 4 }

moFanMes OBJECT-IDENTITY
	STATUS obsolete
	DESCRIPTION
		"Fan measurements"
	::= { moFan 1 }

moFanMeFan1Speed OBJECT-TYPE
	SYNTAX Gauge32(0..99999)
	UNITS "rpm"
	MAX-ACCESS read-only
	STATUS obsolete
	DESCRIPTION
		"Fan1 speed measurement."
	::= { moFanMes 1 }

moFanMeFan2Speed OBJECT-TYPE
	SYNTAX Gauge32(0..99999)
	UNITS "rpm"
	MAX-ACCESS read-only
	STATUS obsolete
	DESCRIPTION
		"Fan2 speed measurement."
	::= { moFanMes 2 }

moFanAlarms OBJECT-IDENTITY
	STATUS obsolete
	DESCRIPTION
		"Fan alarms."
	::= { moFan 2 }

moFanAlFan1Alarm OBJECT-TYPE
	SYNTAX INTEGER
		{
			undefined(0),
			on(1),
			off(2)
		}
	MAX-ACCESS read-only
	STATUS obsolete
	DESCRIPTION
		"Fan 1 speed alarm."
	::= { moFanAlarms 1 }

moFanAlFan2Alarm OBJECT-TYPE
	SYNTAX INTEGER
		{
			undefined(0),
			on(1),
			off(2)
		}
	MAX-ACCESS read-only
	STATUS obsolete
	DESCRIPTION
		"Fan 2 speed alarm."
	::= { moFanAlarms 2 }


maintenance OBJECT-IDENTITY
	STATUS current
	DESCRIPTION
		"No description"
	::= { transmitter 11 }

maMonitoring OBJECT-IDENTITY
	STATUS current
	DESCRIPTION
		"Maintenance monitoring"
	::= { maintenance 1 }

maMoMain OBJECT-IDENTITY
	STATUS current
	DESCRIPTION
		"Main measurements"
	::= { maMonitoring 1 }

maMoMaEffTrans OBJECT-TYPE
	SYNTAX Gauge32(0..100)
	UNITS "percent"
	MAX-ACCESS read-only
	STATUS current
	DESCRIPTION
		"Transmitter efficiency measurement."
	::= { maMoMain 1 }

maMoMaEffPa OBJECT-TYPE
	SYNTAX Gauge32(0..100)
	UNITS "percent"
	MAX-ACCESS read-only
	STATUS current
	DESCRIPTION
		"Power amplifiers efficiency measurement."
	::= { maMoMain 2 }

maMoMaEffPsu OBJECT-TYPE
	SYNTAX Gauge32(0..100)
	UNITS "percent"
	MAX-ACCESS read-only
	STATUS current
	DESCRIPTION
		"Power supplies efficiency measurement."
	::= { maMoMain 3 }

maMoMaEffSys OBJECT-TYPE
	SYNTAX Gauge32(0..100)
	UNITS "percent"
	MAX-ACCESS read-only
	STATUS current
	DESCRIPTION
		"System efficiency measurement."
	::= { maMoMain 4 }


maMoCcu OBJECT-IDENTITY
	STATUS current
	DESCRIPTION
		"Central control unit state"
	::= { maMonitoring 2 }

maMoCcFault OBJECT-TYPE
	SYNTAX INTEGER
		{
			undefined(0),
			on(1),
			off(2)
		}
	MAX-ACCESS read-only
	STATUS current
	DESCRIPTION
		"Central control unit fault State : 0:Undefined 1:ON 2:OFF"
	::= { maMoCcu 1 }

maMoCcWarn OBJECT-TYPE
	SYNTAX INTEGER
		{
			undefined(0),
			on(1),
			off(2)
		}
	MAX-ACCESS read-only
	STATUS current
	DESCRIPTION
		"Central control unit warning State : 0:Undefined 1:ON 2:OFF"
	::= { maMoCcu 2 }

maMoConditions OBJECT-IDENTITY
	STATUS current
	DESCRIPTION
		"Working conditions"
	::= { maMonitoring 3 }

maMoCoMeas OBJECT-IDENTITY
	STATUS current
	DESCRIPTION
		"Conditions measurements"
	::= { maMoConditions 1 }

maMoCoMeAmb OBJECT-TYPE
	SYNTAX Integer32(-125..125)
	UNITS "Celsius Degrees"
	MAX-ACCESS read-only
	STATUS current
	DESCRIPTION
		"Ambient temperature measurement."
	::= { maMoCoMeas 1 }

maMoCoMeLoad1InputTemp OBJECT-TYPE
	SYNTAX Integer32(-999..999)
	UNITS "Celsius Degrees"
	MAX-ACCESS read-only
	STATUS current
	DESCRIPTION
		"Load1 input temperature measurement."
	::= { maMoCoMeas 2 }

maMoCoMeLoad1HeatsinkTemp OBJECT-TYPE
	SYNTAX Integer32(-999..999)
	UNITS "Celsius Degrees"
	MAX-ACCESS read-only
	STATUS current
	DESCRIPTION
		"Load1 heatsink temperature measurement."
	::= { maMoCoMeas 3 }

maMoCoMeLoad2InputTemp OBJECT-TYPE
	SYNTAX Integer32(-999..999)
	UNITS "Celsius Degrees"
	MAX-ACCESS read-only
	STATUS current
	DESCRIPTION
		"Load1 input temperature measurement."
	::= { maMoCoMeas 4 }

maMoCoMeLoad2HeatsinkTemp OBJECT-TYPE
	SYNTAX Integer32(-999..999)
	UNITS "Celsius Degrees"
	MAX-ACCESS read-only
	STATUS current
	DESCRIPTION
		"Load1 heatsink temperature measurement."
	::= { maMoCoMeas 5 }

maMoCoMePressure OBJECT-TYPE
	SYNTAX Gauge32(0..2000)
	UNITS "Celsius Degrees"
	MAX-ACCESS read-only
	STATUS current
	DESCRIPTION
		"Atmospheric pressure measurement."
	::= { maMoCoMeas 6 }

maMoCoMeHeat1 OBJECT-TYPE
	SYNTAX Integer32(-125..125)
	UNITS "Celsius Degrees"
	MAX-ACCESS read-only
	STATUS current
	DESCRIPTION
		"Heatsink 1 temperature measurement."
	::= { maMoCoMeas 7 }

maMoCoMeHeat2 OBJECT-TYPE
	SYNTAX Integer32(-125..125)
	UNITS "Celsius Degrees"
	MAX-ACCESS read-only
	STATUS current
	DESCRIPTION
		"Heatsink 2 temperature measurement."
	::= { maMoCoMeas 8 }

maMoCoMePsuTemp OBJECT-TYPE
	SYNTAX Integer32(-125..125)
	UNITS "Celsius Degrees"
	MAX-ACCESS read-only
	STATUS current
	DESCRIPTION
		"PSU temperature measurement."
	::= { maMoCoMeas 9 }

maMoCoMeIntTemp OBJECT-TYPE
	SYNTAX Gauge32(0..999)
	UNITS "Celsius Degrees"
	MAX-ACCESS read-only
	STATUS current
	DESCRIPTION
		"Int temperature measurement."
	::= { maMoCoMeas 10 }

maMoCoMeExcTemp OBJECT-TYPE
	SYNTAX Integer32(-125..125)
	UNITS "Celsius Degrees"
	MAX-ACCESS read-only
	STATUS current
	DESCRIPTION
		"Exciter temperature measurement."
	::= { maMoCoMeas 11 }


maMoCoAlarms OBJECT-IDENTITY
	STATUS current
	DESCRIPTION
		"Conditions alarms"
	::= { maMoConditions 2 }

maMoCoAlAmb OBJECT-TYPE
	SYNTAX INTEGER
		{
			undefined(0),
			on(1),
			off(2)
		}
	MAX-ACCESS read-only
	STATUS current
	DESCRIPTION
		"Ambient temperature alarm state : 0:Undefined 1:ON 2:OFF"
	::= { maMoCoAlarms 1 }

maMoCoAlLoad1Heatsink OBJECT-TYPE
	SYNTAX INTEGER
		{
			undefined(0),
			on(1),
			off(2)
		}
	MAX-ACCESS read-only
	STATUS current
	DESCRIPTION
		"Load1 heatsink temperature alarm state : 0:Undefined 1:ON 2:OFF"
	::= { maMoCoAlarms 2 }

maMoCoAlLoad2Heatsink OBJECT-TYPE
	SYNTAX INTEGER
		{
			undefined(0),
			on(1),
			off(2)
		}
	MAX-ACCESS read-only
	STATUS current
	DESCRIPTION
		"Load2 heatsink temperature alarm state : 0:Undefined 1:ON 2:OFF"
	::= { maMoCoAlarms 3 }


maMoCoAlPressure OBJECT-TYPE
	SYNTAX INTEGER
		{
			undefined(0),
			on(1),
			off(2)
		}
	MAX-ACCESS read-only
	STATUS current
	DESCRIPTION
		"Atmospheric pressure alarm state : 0:Undefined 1:ON 2:OFF"
	::= { maMoCoAlarms 4 }

maMoCoAlHeat1 OBJECT-TYPE
	SYNTAX INTEGER
		{
			undefined(0),
			on(1),
			off(2)
		}
	MAX-ACCESS read-only
	STATUS current
	DESCRIPTION
		"Heatsink 1 temperature alarm."
	::= { maMoCoAlarms 5 }

maMoCoAlHeat2 OBJECT-TYPE
	SYNTAX INTEGER
		{
			undefined(0),
			on(1),
			off(2)
		}
	MAX-ACCESS read-only
	STATUS current
	DESCRIPTION
		"Heatsink 2 temperature alarm."
	::= { maMoCoAlarms 6 }

maMoCoAlTemp1 OBJECT-TYPE
	SYNTAX INTEGER
		{
			undefined(0),
			on(1),
			off(2)
		}
	MAX-ACCESS read-only
	STATUS current
	DESCRIPTION
		"Temp 1 temperature alarm."
	::= { maMoCoAlarms 7 }

maMoCoAlTemp2 OBJECT-TYPE
	SYNTAX INTEGER
		{
			undefined(0),
			on(1),
			off(2)
		}
	MAX-ACCESS read-only
	STATUS current
	DESCRIPTION
		"Temp 2 temperature alarm."
	::= { maMoCoAlarms 8 }

maMoCoAlPsuTemp OBJECT-TYPE
	SYNTAX INTEGER
		{
			undefined(0),
			on(1),
			off(2)
		}
	MAX-ACCESS read-only
	STATUS current
	DESCRIPTION
		"PSU temperature alarm."
	::= { maMoCoAlarms 9 }

maMoCoAlIntTemp OBJECT-TYPE
	SYNTAX INTEGER
		{
			undefined(0),
			on(1),
			off(2)
		}
	MAX-ACCESS read-only
	STATUS current
	DESCRIPTION
		"Int temperature alarm."
	::= { maMoCoAlarms 10 }

maMoCoAlExcTemp OBJECT-TYPE
	SYNTAX INTEGER
		{
			undefined(0),
			on(1),
			off(2)
		}
	MAX-ACCESS read-only
	STATUS current
	DESCRIPTION
		"Exciter temperature alarm."
	::= { maMoCoAlarms 11 }


maMoAuxVolt OBJECT-IDENTITY
	STATUS current
	DESCRIPTION
		"Auxiliary power supplies"
	::= { maMonitoring 4 }

maMoAuMeas OBJECT-IDENTITY
	STATUS current
	DESCRIPTION
		"Auxiliary power supplies measurements"
	::= { maMoAuxVolt 1 }

maMoAuMe5V OBJECT-TYPE
	SYNTAX Gauge32(0..9999)
	UNITS "Volt/100"
	MAX-ACCESS read-only
	STATUS current
	DESCRIPTION
		"Internal 5V measurement."
	::= { maMoAuMeas 1 }

maMoAuMe12V OBJECT-TYPE
	SYNTAX Gauge32(0..9999)
	UNITS "Volt/100"
	MAX-ACCESS read-only
	STATUS current
	DESCRIPTION
		"Internal 12V measurement."
	::= { maMoAuMeas 2 }

maMoAuMeN12V OBJECT-TYPE
	SYNTAX Integer32(-9999..0)
	UNITS "Volt/100"
	MAX-ACCESS read-only
	STATUS current
	DESCRIPTION
		"Internal minus 12V measurement."
	::= { maMoAuMeas 3 }

maMoAuMe24V OBJECT-TYPE
	SYNTAX Gauge32(0..9999)
	UNITS "Volt/100"
	MAX-ACCESS read-only
	STATUS current
	DESCRIPTION
		"Internal 24V measurement."
	::= { maMoAuMeas 4 }

maMoAuAlarms OBJECT-IDENTITY
	STATUS current
	DESCRIPTION
		"Auxiliary power supplies alarms"
	::= { maMoAuxVolt 2 }

maMoAuAlVoltAux OBJECT-TYPE
	SYNTAX INTEGER
		{
			undefined(0),
			on(1),
			off(2)
		}
	MAX-ACCESS read-only
	STATUS current
	DESCRIPTION
		"Auxiliary voltage (5V,12V,-12V) alarm state : 0:Undefined 1:ON 2:OFF"
	::= { maMoAuAlarms 1 }

maMoAuAl24V OBJECT-TYPE
	SYNTAX INTEGER
		{
			undefined(0),
			on(1),
			off(2)
		}
	MAX-ACCESS read-only
	STATUS current
	DESCRIPTION
		"Auxiliary voltage 24V alarm state : 0:Undefined 1:ON 2:OFF"
	::= { maMoAuAlarms 2 }

maMoFanTable OBJECT-TYPE
	SYNTAX SEQUENCE OF MaMoFanEntry
	MAX-ACCESS not-accessible
	STATUS current
	DESCRIPTION
		"Fan table"
	::= { maMonitoring 5 }

maMoFanEntry OBJECT-TYPE
	SYNTAX MaMoFanEntry
	MAX-ACCESS not-accessible
	STATUS current
	DESCRIPTION
		"An entry of the maMoFan table"
	INDEX { maMoFanIndex }
	::= { maMoFanTable 1 }

MaMoFanEntry ::=	SEQUENCE {
	maMoFanIndex		Integer32,
	maMoFanSpeed		Gauge32,
	maMoFanAlarms		Integer32
}

maMoFanIndex OBJECT-TYPE
	SYNTAX Integer32 (0..2147483647)
	MAX-ACCESS not-accessible
	STATUS current
	DESCRIPTION
		"maMoFanMeTable index"
	::= { maMoFanEntry 1 }

maMoFanSpeed OBJECT-TYPE
	SYNTAX Gauge32(0..99999)
	UNITS "Rpm"
	MAX-ACCESS read-only
	STATUS current
	DESCRIPTION
		"Fan speed measurement."
	::= { maMoFanEntry 2 }

maMoFanAlarms OBJECT-TYPE
	SYNTAX INTEGER
	{
		undefined(0),
		on(1),
		off(2)
	}
	MAX-ACCESS read-only
	STATUS current
	DESCRIPTION
		"Fan speed alarm state : 0:Undefined 1:ON 2:OFF"
	::= { maMoFanEntry 3 }


maMoMeas OBJECT-IDENTITY
	STATUS current
	DESCRIPTION
		"Monitoring Measurements"
	::= { maMonitoring 6 }

maMoMeVolt1 OBJECT-TYPE
	SYNTAX Gauge32(0..999)
	UNITS "V/10"
	MAX-ACCESS read-only
	STATUS current
	DESCRIPTION
		"Volt1 voltage measurement."
	::= { maMoMeas 1 }

maMoMeVolt2 OBJECT-TYPE
	SYNTAX Gauge32(0..999)
	UNITS "V/10"
	MAX-ACCESS read-only
	STATUS current
	DESCRIPTION
		"Volt2 voltage measurement."
	::= { maMoMeas 2 }

maMoMeCur1 OBJECT-TYPE
	SYNTAX Gauge32(0..999)
	UNITS "A/10"
	MAX-ACCESS read-only
	STATUS current
	DESCRIPTION
		"Cur1 current measurement."
	::= { maMoMeas 3 }

maMoMeCur2 OBJECT-TYPE
	SYNTAX Gauge32(0..999)
	UNITS "A/10"
	MAX-ACCESS read-only
	STATUS current
	DESCRIPTION
		"Cur2 current measurement."
	::= { maMoMeas 4 }

maMoMePin OBJECT-TYPE
	SYNTAX Gauge32(0..999)
	UNITS "W/10"
	MAX-ACCESS read-only
	STATUS current
	DESCRIPTION
		"Input power measurement."
	::= { maMoMeas 5 }

maMoMeVolt3 OBJECT-TYPE
	SYNTAX Gauge32(0..999)
	UNITS "mV"
	MAX-ACCESS read-only
	STATUS current
	DESCRIPTION
		"Volt3 voltage measurement."
	::= { maMoMeas 6 }

maMoMeCur3 OBJECT-TYPE
	SYNTAX Gauge32(0..99999)
	UNITS "mA"
	MAX-ACCESS read-only
	STATUS current
	DESCRIPTION
		"Cur3 current measurement."
	::= { maMoMeas 7 }


maMoAlarm OBJECT-IDENTITY
	STATUS current
	DESCRIPTION
		"Monitoring Alarms"
	::= { maMonitoring 7 }

maMoAlVolt1 OBJECT-TYPE
	SYNTAX INTEGER
		{
			undefined(0),
			on(1),
			off(2)
		}
	MAX-ACCESS read-only
	STATUS current
	DESCRIPTION
		"Volt1 voltage alarm."
	::= { maMoAlarm 1 }

maMoAlVolt2 OBJECT-TYPE
	SYNTAX INTEGER
		{
			undefined(0),
			on(1),
			off(2)
		}
	MAX-ACCESS read-only
	STATUS current
	DESCRIPTION
		"Volt2 voltage alarm."
	::= { maMoAlarm 2 }

maMoAlCur1 OBJECT-TYPE
	SYNTAX INTEGER
		{
			undefined(0),
			on(1),
			off(2)
		}
	MAX-ACCESS read-only
	STATUS current
	DESCRIPTION
		"Cur1 current alarm."
	::= { maMoAlarm 3 }

maMoAlCur2 OBJECT-TYPE
	SYNTAX INTEGER
		{
			undefined(0),
			on(1),
			off(2)
		}
	MAX-ACCESS read-only
	STATUS current
	DESCRIPTION
		"Cur2 current alarm."
	::= { maMoAlarm 4 }

maMoAlPin OBJECT-TYPE
	SYNTAX INTEGER
		{
			undefined(0),
			on(1),
			off(2)
		}
	MAX-ACCESS read-only
	STATUS current
	DESCRIPTION
		"Input power alarm."
	::= { maMoAlarm 5 }

maMoAlSecPref OBJECT-TYPE
	SYNTAX INTEGER
		{
			undefined(0),
			on(1),
			off(2)
		}
	MAX-ACCESS read-only
	STATUS current
	DESCRIPTION
		"SecPref alarm."
	::= { maMoAlarm 6 }

maMoAlCur3 OBJECT-TYPE
	SYNTAX INTEGER
		{
			undefined(0),
			on(1),
			off(2)
		}
	MAX-ACCESS read-only
	STATUS current
	DESCRIPTION
		"Cur3 current alarm."
	::= { maMoAlarm 7 }


maDrive OBJECT-IDENTITY
	STATUS current
	DESCRIPTION
		"Drivers informations"
	::= { maintenance 2 }

maDrTable  OBJECT-TYPE
	SYNTAX SEQUENCE OF MaDrEntry
	MAX-ACCESS not-accessible
	STATUS current
	DESCRIPTION
		"Driver table"
	::= { maDrive 1 }

maDrEntry OBJECT-TYPE
	SYNTAX MaDrEntry
	MAX-ACCESS not-accessible
	STATUS current
	DESCRIPTION
		"An entry of the maDrive table"
	INDEX { maDrIndex }
	::= { maDrTable 1 }

MaDrEntry ::=	SEQUENCE {
	maDrIndex		Integer32,
	maDrCommunication		Integer32,
	maDrFault		Integer32,
	maDrWarning		Integer32,
	maDrForwardPower		Gauge32,
	maDrReflectedPower	Gauge32,
	maDrHeatsink		Integer32,
	maDrFanSpeed		Gauge32
}

maDrIndex OBJECT-TYPE
	SYNTAX Integer32 (0..2147483647)
	MAX-ACCESS not-accessible
	STATUS current
	DESCRIPTION
		"maDrTable index"
	::= { maDrEntry 1 }

maDrCommunication OBJECT-TYPE
	SYNTAX INTEGER
	{
		undefined(0),
		on(1),
		off(2)
	}
	MAX-ACCESS read-only
	STATUS current
	DESCRIPTION
		"Driver communication state : 0:Undefined 1:ON 2:OFF"
	::= { maDrEntry 2 }

maDrFault OBJECT-TYPE
	SYNTAX INTEGER
	{
		undefined(0),
		on(1),
		off(2)
	}
	MAX-ACCESS read-only
	STATUS current
	DESCRIPTION
		"Driver alarm fault state : 0:Undefined 1:ON 2:OFF"
	::= { maDrEntry 3 }

maDrWarning OBJECT-TYPE
	SYNTAX INTEGER
	{
		undefined(0),
		on(1),
		off(2)
	}
	MAX-ACCESS read-only
	STATUS current
	DESCRIPTION
		"Driver alarm warning state : 0:Undefined 1:ON 2:OFF"
	::= { maDrEntry 4 }

maDrForwardPower OBJECT-TYPE
	SYNTAX Gauge32(0..99999)
	UNITS "W"
	MAX-ACCESS read-only
	STATUS current
	DESCRIPTION
		"Driver forward Power (W)"
	::= { maDrEntry 5 }

maDrReflectedPower OBJECT-TYPE
	SYNTAX Gauge32(0..99999)
	UNITS "W"
	MAX-ACCESS read-only
	STATUS current
	DESCRIPTION
		"Driver reflected Power (W)"
	::= { maDrEntry 6 }

maDrHeatsink OBJECT-TYPE
	SYNTAX Integer32(-125..125)
	UNITS "Celsius Degrees"
	MAX-ACCESS read-only
	STATUS current
	DESCRIPTION
		"Driver heatsink temperature measurement."
	::= { maDrEntry 7 }

maDrFanSpeed OBJECT-TYPE
	SYNTAX Gauge32(0..99999)
	UNITS "Rpm"
	MAX-ACCESS read-only
	STATUS current
	DESCRIPTION
		"Driver fan speed measurement."
	::= { maDrEntry 8 }

maPa OBJECT-IDENTITY
	STATUS current
	DESCRIPTION
		"Power amplifiers informations"
	::= { maintenance 3 }

maPaTable  OBJECT-TYPE
	SYNTAX SEQUENCE OF MaPaEntry
	MAX-ACCESS not-accessible
	STATUS current
	DESCRIPTION
		"Power amplifiers table"
	::= { maPa 1 }

maPaEntry OBJECT-TYPE
	SYNTAX MaPaEntry
	MAX-ACCESS not-accessible
	STATUS current
	DESCRIPTION
		"An entry of the maPa table"
	INDEX { maPaIndex }
	::= { maPaTable 1 }

MaPaEntry ::=	SEQUENCE {
	maPaIndex			Integer32,
	maPaCommunication		Integer32,
	maPaFault			Integer32,
	maPaWarning			Integer32,
	maPaForwardPower		Gauge32,
	maPaReflectedPower		Gauge32,
	maPaEfficiency		Gauge32,
	maPaCurrent			Gauge32,
	maPaHeatMax			Integer32,
	maPaAlrCur			Integer32,
	maPaVoltage			Gauge32,
	maPaAlrVolt			Integer32,
	maPaAmbTemp			Integer32,
	maPaAlrHeat			Integer32,
	maPaAlrTemp			Integer32
}

maPaIndex OBJECT-TYPE
	SYNTAX Integer32 (0..2147483647)
	MAX-ACCESS not-accessible
	STATUS current
	DESCRIPTION
		"maPaTable index"
	::= { maPaEntry 1 }

maPaCommunication OBJECT-TYPE
	SYNTAX INTEGER
	{
		undefined(0),
		on(1),
		off(2)
	}
	MAX-ACCESS read-only
	STATUS current
	DESCRIPTION
		"Power amplifier communication state : 0:Undefined 1:ON 2:OFF"
	::= { maPaEntry 2 }

maPaFault OBJECT-TYPE
	SYNTAX INTEGER
	{
		undefined(0),
		on(1),
		off(2)
	}
	MAX-ACCESS read-only
	STATUS current
	DESCRIPTION
		"Power amplifier alarm fault state : 0:Undefined 1:ON 2:OFF"
	::= { maPaEntry 3 }

maPaWarning OBJECT-TYPE
	SYNTAX INTEGER
	{
		undefined(0),
		on(1),
		off(2)
	}
	MAX-ACCESS read-only
	STATUS current
	DESCRIPTION
		"Power amplifier alarm warning state : 0:Undefined 1:ON 2:OFF"
	::= { maPaEntry 4 }

maPaForwardPower OBJECT-TYPE
	SYNTAX Gauge32(0..99999)
	UNITS "W"
	MAX-ACCESS read-only
	STATUS current
	DESCRIPTION
		"Power amplifier forward Power (W)"
	::= { maPaEntry 5 }

maPaReflectedPower OBJECT-TYPE
	SYNTAX Gauge32(0..99999)
	UNITS "W"
	MAX-ACCESS read-only
	STATUS current
	DESCRIPTION
		"Power amplifier reflected Power (W)"
	::= { maPaEntry 6 }

maPaEfficiency OBJECT-TYPE
	SYNTAX Gauge32(0..100)
	UNITS "percent"
	MAX-ACCESS read-only
	STATUS current
	DESCRIPTION
		"Power amplifier efficiency measurement."
	::= { maPaEntry 7 }

maPaCurrent OBJECT-TYPE
	SYNTAX Gauge32(0..99999)
	UNITS "Ampere/100"
	MAX-ACCESS read-only
	STATUS current
	DESCRIPTION
		"Power amplifier output current measurement."
	::= { maPaEntry 8 }

maPaHeatMax OBJECT-TYPE
	SYNTAX Integer32(-125..125)
	UNITS "Celsius Degrees"
	MAX-ACCESS read-only
	STATUS current
	DESCRIPTION
		"Power amplifier heat maximum measurement."
	::= { maPaEntry 9 }

maPaAlrCur OBJECT-TYPE
	SYNTAX INTEGER
	{
		undefined(0),
		on(1),
		off(2)
	}
	MAX-ACCESS read-only
	STATUS current
	DESCRIPTION
		"Power amplifier alarm current state : 0:Undefined 1:ON 2:OFF"
	::= { maPaEntry 10 }

maPaVoltage	OBJECT-TYPE
	SYNTAX Gauge32(0..99999)
	UNITS "mV"
	MAX-ACCESS read-only
	STATUS current
	DESCRIPTION
		"Power amplifier input voltage measurement."
	::= { maPaEntry 11 }

maPaAlrVolt OBJECT-TYPE
	SYNTAX INTEGER
	{
		undefined(0),
		on(1),
		off(2)
	}
	MAX-ACCESS read-only
	STATUS current
	DESCRIPTION
		"Power amplifier alarm voltage state : 0:Undefined 1:ON 2:OFF"
	::= { maPaEntry 12 }

maPaAmbTemp	OBJECT-TYPE
	SYNTAX Integer32(-125..125)
	UNITS "Celsius Degrees"
	MAX-ACCESS read-only
	STATUS current
	DESCRIPTION
		"Power amplifier ambiant temperature measurement."
	::= { maPaEntry 13 }

maPaAlrHeat OBJECT-TYPE
	SYNTAX INTEGER
	{
		undefined(0),
		on(1),
		off(2)
	}
	MAX-ACCESS read-only
	STATUS current
	DESCRIPTION
		"Power amplifier heat alarm state : 0:Undefined 1:ON 2:OFF"
	::= { maPaEntry 14 }

maPaAlrTemp OBJECT-TYPE
	SYNTAX INTEGER
	{
		undefined(0),
		on(1),
		off(2)
	}
	MAX-ACCESS read-only
	STATUS current
	DESCRIPTION
		"Power amplifier temperature alarm state : 0:Undefined 1:ON 2:OFF"
	::= { maPaEntry 15 }


maPsu OBJECT-IDENTITY
	STATUS current
	DESCRIPTION
		"Power supplies informations"
	::= { maintenance 4 }

maPsVoltageInput OBJECT-TYPE
	SYNTAX Gauge32(0..99999)
	UNITS "Volt/100"
	MAX-ACCESS read-only
	STATUS current
	DESCRIPTION
		"Power supplies input voltage measurement."
	::= { maPsu 1}

maPsCurrentInput OBJECT-TYPE
	SYNTAX Gauge32(0..99999)
	UNITS "Ampere/100"
	MAX-ACCESS read-only
	STATUS current
	DESCRIPTION
		"Power supplies input current measurement."
	::= { maPsu 2}

maPsPowerInput OBJECT-TYPE
	SYNTAX Gauge32(0..99999)
	UNITS "W"
	MAX-ACCESS read-only
	STATUS current
	DESCRIPTION
		"Power supplies input power measurement."
	::= { maPsu 3}

maPsVoltageOutput OBJECT-TYPE
	SYNTAX Gauge32(0..99999)
	UNITS "Volt/100"
	MAX-ACCESS read-only
	STATUS current
	DESCRIPTION
		"Power supplies Output voltage measurement."
	::= { maPsu 4}

maPsCurrentOutput OBJECT-TYPE
	SYNTAX Gauge32(0..99999)
	UNITS "Ampere/100"
	MAX-ACCESS read-only
	STATUS current
	DESCRIPTION
		"Power supplies Output current measurement."
	::= { maPsu 5}

maPsPowerOutput OBJECT-TYPE
	SYNTAX Gauge32(0..99999)
	UNITS "W"
	MAX-ACCESS read-only
	STATUS current
	DESCRIPTION
		"Power supplies Output power measurement."
	::= { maPsu 6}

maPsTable  OBJECT-TYPE
	SYNTAX SEQUENCE OF MaPsEntry
	MAX-ACCESS not-accessible
	STATUS current
	DESCRIPTION
		"Power supply table"
	::= { maPsu 7 }

maPsEntry OBJECT-TYPE
	SYNTAX MaPsEntry
	MAX-ACCESS not-accessible
	STATUS current
	DESCRIPTION
		"An entry of the maPs table"
	INDEX { maPsIndex }
	::= { maPsTable 1 }

MaPsEntry ::=	SEQUENCE {
	maPsIndex			Integer32,
	maPsCommunication		Integer32,
	maPsFault			Integer32,
	maPsWarning			Integer32,
	maPsEfficiency		Gauge32,
	maPsOutputPower		Gauge32,
	maPsInputPower		Gauge32,
	maPsMissing			Integer32,
	maPsInputCurrent		Gauge32,
	maPsInputCurAlr		Integer32,
	maPsInputVoltage		Gauge32,
	maPsInputVoltAlr		Integer32,
	maPsOutputCurrent		Gauge32,
	maPsOutputCurAlr		Integer32,
	maPsOutputVoltage		Gauge32,
	maPsOutputVoltAlr		Integer32,
	maPsAmbTemp			Integer32,
	maPsAmbAlr			Integer32,
	maPsHeat1Temp		Integer32,
	maPsHeat1Alr			Integer32,
	maPsFan1Speed		Gauge32,
	maPsFan1Alr			Integer32,
	maPsSerial			DisplayString,
	maPsSoftRel			DisplayString
}

maPsIndex OBJECT-TYPE
	SYNTAX Integer32 (0..2147483647)
	MAX-ACCESS not-accessible
	STATUS current
	DESCRIPTION
		"maPsTable index"
	::= { maPsEntry 1 }

maPsCommunication OBJECT-TYPE
	SYNTAX INTEGER
	{
		undefined(0),
		on(1),
		off(2)
	}
	MAX-ACCESS read-only
	STATUS current
	DESCRIPTION
		"Power supply communication state : 0:Undefined 1:ON 2:OFF"
	::= { maPsEntry 2 }

maPsFault OBJECT-TYPE
	SYNTAX INTEGER
	{
		undefined(0),
		on(1),
		off(2)
	}
	MAX-ACCESS read-only
	STATUS current
	DESCRIPTION
		"Power supply alarm fault state : 0:Undefined 1:ON 2:OFF"
	::= { maPsEntry 3 }

maPsWarning OBJECT-TYPE
	SYNTAX INTEGER
	{
		undefined(0),
		on(1),
		off(2)
	}
	MAX-ACCESS read-only
	STATUS current
	DESCRIPTION
		"Power supply alarm warning state : 0:Undefined 1:ON 2:OFF"
	::= { maPsEntry 4 }

maPsEfficiency OBJECT-TYPE
	SYNTAX Gauge32(0..100)
	UNITS "percent"
	MAX-ACCESS read-only
	STATUS current
	DESCRIPTION
		"Power supply efficiency measurement."
	::= { maPsEntry 5 }

maPsOutputPower OBJECT-TYPE
	SYNTAX Gauge32(0..99999)
	UNITS "W"
	MAX-ACCESS read-only
	STATUS current
	DESCRIPTION
		"Power supply output Power (W)"
	::= { maPsEntry 6 }

maPsInputPower OBJECT-TYPE
	SYNTAX Gauge32(0..99999)
	UNITS "W"
	MAX-ACCESS read-only
	STATUS current
	DESCRIPTION
		"Power supply input Power (W)"
	::= { maPsEntry 7 }

maPsMissing OBJECT-TYPE
	SYNTAX INTEGER
	{
		undefined(0),
		on(1),
		off(2)
	}
	MAX-ACCESS read-only
	STATUS current
	DESCRIPTION
		"Power supply missing alarm : 0:Undefined 1:ON 2:OFF"
	::= { maPsEntry 8 }

maPsInputCurrent OBJECT-TYPE
	SYNTAX Gauge32(0..99999)
	UNITS "mA"
	MAX-ACCESS read-only
	STATUS current
	DESCRIPTION
		"Power supply input Current (mA)"
	::= { maPsEntry 9 }

maPsInputCurAlr OBJECT-TYPE
	SYNTAX INTEGER
	{
		undefined(0),
		on(1),
		off(2)
	}
	MAX-ACCESS read-only
	STATUS current
	DESCRIPTION
		"Power supply input current alarm : 0:Undefined 1:ON 2:OFF"
	::= { maPsEntry 10 }

maPsInputVoltage OBJECT-TYPE
	SYNTAX Gauge32(0..999999)
	UNITS "mV"
	MAX-ACCESS read-only
	STATUS current
	DESCRIPTION
		"Power supply input voltage (mV)"
	::= { maPsEntry 11 }

maPsInputVoltAlr OBJECT-TYPE
	SYNTAX INTEGER
	{
		undefined(0),
		on(1),
		off(2)
	}
	MAX-ACCESS read-only
	STATUS current
	DESCRIPTION
		"Power supply input voltage alarm : 0:Undefined 1:ON 2:OFF"
	::= { maPsEntry 12 }

maPsOutputCurrent OBJECT-TYPE
	SYNTAX Gauge32(0..99999)
	UNITS "mA"
	MAX-ACCESS read-only
	STATUS current
	DESCRIPTION
		"Power supply output Current (mA)"
	::= { maPsEntry 13 }

maPsOutputCurAlr OBJECT-TYPE
	SYNTAX INTEGER
	{
		undefined(0),
		on(1),
		off(2)
	}
	MAX-ACCESS read-only
	STATUS current
	DESCRIPTION
		"Power supply output current alarm : 0:Undefined 1:ON 2:OFF"
	::= { maPsEntry 14 }

maPsOutputVoltage OBJECT-TYPE
	SYNTAX Gauge32(0..99999)
	UNITS "mV"
	MAX-ACCESS read-only
	STATUS current
	DESCRIPTION
		"Power supply output voltage (mV)"
	::= { maPsEntry 15 }

maPsOutputVoltAlr OBJECT-TYPE
	SYNTAX INTEGER
	{
		undefined(0),
		on(1),
		off(2)
	}
	MAX-ACCESS read-only
	STATUS current
	DESCRIPTION
		"Power supply output voltage alarm : 0:Undefined 1:ON 2:OFF"
	::= { maPsEntry 16 }

maPsAmbTemp OBJECT-TYPE
	SYNTAX Integer32(-125..125)
	UNITS "Celsius Degrees"
	MAX-ACCESS read-only
	STATUS current
	DESCRIPTION
		"Power supply ambiant temperature."
	::= { maPsEntry 17 }

maPsAmbAlr OBJECT-TYPE
	SYNTAX INTEGER
	{
		undefined(0),
		on(1),
		off(2)
	}
	MAX-ACCESS read-only
	STATUS current
	DESCRIPTION
		"Power supply ambiant temperature alarm : 0:Undefined 1:ON 2:OFF"
	::= { maPsEntry 18 }

maPsHeat1Temp OBJECT-TYPE
	SYNTAX Integer32(-125..125)
	UNITS "Celsius Degrees"
	MAX-ACCESS read-only
	STATUS current
	DESCRIPTION
		"Power supply heatsink1 temperature."
	::= { maPsEntry 19 }

maPsHeat1Alr OBJECT-TYPE
	SYNTAX INTEGER
	{
		undefined(0),
		on(1),
		off(2)
	}
	MAX-ACCESS read-only
	STATUS current
	DESCRIPTION
		"Power supply heatsink1 temperature alarm : 0:Undefined 1:ON 2:OFF"
	::= { maPsEntry 20 }

maPsFan1Speed OBJECT-TYPE
	SYNTAX Gauge32(0..99999)
	UNITS "rpm"
	MAX-ACCESS read-only
	STATUS current
	DESCRIPTION
		"Power supply fan1 speed."
	::= { maPsEntry 21 }

maPsFan1Alr OBJECT-TYPE
	SYNTAX INTEGER
	{
		undefined(0),
		on(1),
		off(2)
	}
	MAX-ACCESS read-only
	STATUS current
	DESCRIPTION
		"Power supply fan1 speed alarm : 0:Undefined 1:ON 2:OFF"
	::= { maPsEntry 22 }

maPsSerial OBJECT-TYPE
	SYNTAX DisplayString(SIZE(0..18))
	MAX-ACCESS read-only
	STATUS current
	DESCRIPTION
		"Power supply serial number."
	::= { maPsEntry 23 }

maPsSoftRel OBJECT-TYPE
	SYNTAX DisplayString(SIZE(0..32))
	MAX-ACCESS read-only
	STATUS current
	DESCRIPTION
		"Power supply software release."
	::= { maPsEntry 24 }



events OBJECT-IDENTITY
	STATUS current
	DESCRIPTION
		"No description"
	::= { transmitter 0 }

eventBindings OBJECT-IDENTITY
	STATUS current
	DESCRIPTION
		"No description"
	::= { transmitter 1 }

eventTxLocalModeBindings OBJECT-IDENTITY
	STATUS current
	DESCRIPTION
		"No description"
	::= { eventBindings 1 }

eventTimeStampTxLocalMode OBJECT-TYPE
	SYNTAX DateAndTime
	MAX-ACCESS accessible-for-notify
	STATUS current
	DESCRIPTION
		"No description"
	::= { eventTxLocalModeBindings 1 }

eventTxLocalMode NOTIFICATION-TYPE
		OBJECTS {
			sysDescr, sysName, sysLocation, eventTimeStampTxLocalMode, syGeSerial, 
			eventTxLocalModePriority, syGeTrapCounter, txGnGlLocalMode 
		}
	STATUS current
	DESCRIPTION
		"TxLocalMode notification"
	::= { events 1 }

eventTxAl3dBBindings OBJECT-IDENTITY
	STATUS current
	DESCRIPTION
		"No description"
	::= { eventBindings 2 }

eventTimeStampTxAl3dB OBJECT-TYPE
	SYNTAX DateAndTime
	MAX-ACCESS accessible-for-notify
	STATUS current
	DESCRIPTION
		"No description"
	::= { eventTxAl3dBBindings 1 }

eventTxAl3dB NOTIFICATION-TYPE
		OBJECTS {
			sysDescr, sysName, sysLocation, eventTimeStampTxAl3dB, syGeSerial, 
			eventTxAl3dBPriority, syGeTrapCounter, txGnAl3dB 
		}
	STATUS current
	DESCRIPTION
		"TxAl3dB notification"
	::= { events 2 }

eventTxAlFaultBindings OBJECT-IDENTITY
	STATUS current
	DESCRIPTION
		"No description"
	::= { eventBindings 3 }

eventTimeStampTxAlFault OBJECT-TYPE
	SYNTAX DateAndTime
	MAX-ACCESS accessible-for-notify
	STATUS current
	DESCRIPTION
		"No description"
	::= { eventTxAlFaultBindings 1 }

eventTxAlFault NOTIFICATION-TYPE
		OBJECTS {
			sysDescr, sysName, sysLocation, eventTimeStampTxAlFault, syGeSerial, 
			eventTxAlFaultPriority, syGeTrapCounter, txGnAlFault 
		}
	STATUS current
	DESCRIPTION
		"TxAlFault notification"
	::= { events 3 }

eventTxAlWarningBindings OBJECT-IDENTITY
	STATUS current
	DESCRIPTION
		"No description"
	::= { eventBindings 4 }

eventTimeStampTxAlWarning OBJECT-TYPE
	SYNTAX DateAndTime
	MAX-ACCESS accessible-for-notify
	STATUS current
	DESCRIPTION
		"No description"
	::= { eventTxAlWarningBindings 1 }

eventTxAlWarning NOTIFICATION-TYPE
		OBJECTS {
			sysDescr, sysName, sysLocation, eventTimeStampTxAlWarning, syGeSerial, 
			eventTxAlWarningPriority, syGeTrapCounter, txGnAlWarning 
		}
	STATUS current
	DESCRIPTION
		"TxAlWarning notification"
	::= { events 4 }

eventTxAlVSWRBindings OBJECT-IDENTITY
	STATUS current
	DESCRIPTION
		"No description"
	::= { eventBindings 5 }

eventTimeStampTxAlVSWR OBJECT-TYPE
	SYNTAX DateAndTime
	MAX-ACCESS accessible-for-notify
	STATUS current
	DESCRIPTION
		"No description"
	::= { eventTxAlVSWRBindings 1 }

eventTxAlVSWR NOTIFICATION-TYPE
		OBJECTS {
			sysDescr, sysName, sysLocation, eventTimeStampTxAlVSWR, syGeSerial, 
			eventTxAlVSWRPriority, syGeTrapCounter, txGnAlVSWR 
		}
	STATUS current
	DESCRIPTION
		"TxAlVSWR notification"
	::= { events 5 }

eventTxAlInterlockAntBindings OBJECT-IDENTITY
	STATUS current
	DESCRIPTION
		"No description"
	::= { eventBindings 6 }

eventTimeStampTxAlInterlockAnt OBJECT-TYPE
	SYNTAX DateAndTime
	MAX-ACCESS accessible-for-notify
	STATUS current
	DESCRIPTION
		"No description"
	::= { eventTxAlInterlockAntBindings 1 }

eventTxAlInterlockAnt NOTIFICATION-TYPE
		OBJECTS {
			sysDescr, sysName, sysLocation, eventTimeStampTxAlInterlockAnt, syGeSerial, 
			eventTxAlInterlockAntPriority, syGeTrapCounter, txGnAlInterlockAnt 
		}
	STATUS current
	DESCRIPTION
		"TxAlInterlockAnt notification"
	::= { events 6 }

eventTxAlInterlockLoadBindings OBJECT-IDENTITY
	STATUS obsolete
	DESCRIPTION
		"No description"
	::= { eventBindings 7 }

eventTimeStampTxAlInterlockLoad OBJECT-TYPE
	SYNTAX DateAndTime
	MAX-ACCESS accessible-for-notify
	STATUS obsolete
	DESCRIPTION
		"No description"
	::= { eventTxAlInterlockLoadBindings 1 }

eventTxAlInterlockLoad NOTIFICATION-TYPE
		OBJECTS {
			sysDescr, sysName, sysLocation, eventTimeStampTxAlInterlockLoad, syGeSerial, 
			eventTxAlInterlockLoadPriority, syGeTrapCounter, txGnAlInterlockLoad 
		}
	STATUS obsolete
	DESCRIPTION
		"TxAlInterlockLoad notification"
	::= { events 7 }

eventTxRfOpmodeBindings OBJECT-IDENTITY
	STATUS current
	DESCRIPTION
		"No description"
	::= { eventBindings 8 }

eventTimeStampTxRfOpmode OBJECT-TYPE
	SYNTAX DateAndTime
	MAX-ACCESS accessible-for-notify
	STATUS current
	DESCRIPTION
		"No description"
	::= { eventTxRfOpmodeBindings 1 }

eventTxRfOpmode NOTIFICATION-TYPE
		OBJECTS {
			sysDescr, sysName, sysLocation, eventTimeStampTxRfOpmode, syGeSerial, 
			eventTxRfOpmodePriority, syGeTrapCounter, txGnRfOpmode 
		}
	STATUS current
	DESCRIPTION
		"TxRfOpmode notification"
	::= { events 8 }

eventTxRfRFPresentBindings OBJECT-IDENTITY
	STATUS current
	DESCRIPTION
		"No description"
	::= { eventBindings 9 }

eventTimeStampTxRfRFPresent OBJECT-TYPE
	SYNTAX DateAndTime
	MAX-ACCESS accessible-for-notify
	STATUS current
	DESCRIPTION
		"No description"
	::= { eventTxRfRFPresentBindings 1 }

eventTxRfRFPresent NOTIFICATION-TYPE
		OBJECTS {
			sysDescr, sysName, sysLocation, eventTimeStampTxRfRFPresent, syGeSerial, 
			eventTxRfRFPresentPriority, syGeTrapCounter, txGnRfRFPresent 
		}
	STATUS current
	DESCRIPTION
		"TxRfRFPresent notification"
	::= { events 9 }

eventAcReserveControlBindings OBJECT-IDENTITY
	STATUS current
	DESCRIPTION
		"No description"
	::= { eventBindings 10 }

eventTimeStampAcReserveControl OBJECT-TYPE
	SYNTAX DateAndTime
	MAX-ACCESS accessible-for-notify
	STATUS current
	DESCRIPTION
		"No description"
	::= { eventAcReserveControlBindings 1 }

eventAcReserveControl NOTIFICATION-TYPE
		OBJECTS {
			sysDescr, sysName, sysLocation, eventTimeStampAcReserveControl, syGeSerial, 
			eventAcReserveControlPriority, syGeTrapCounter, acGnGlReserveControl 
		}
	STATUS current
	DESCRIPTION
		"AcReserveControl notification"
	::= { events 10 }

eventAcLocalModeBindings OBJECT-IDENTITY
	STATUS current
	DESCRIPTION
		"No description"
	::= { eventBindings 11 }

eventTimeStampAcLocalMode OBJECT-TYPE
	SYNTAX DateAndTime
	MAX-ACCESS accessible-for-notify
	STATUS current
	DESCRIPTION
		"No description"
	::= { eventAcLocalModeBindings 1 }

eventAcLocalMode NOTIFICATION-TYPE
		OBJECTS {
			sysDescr, sysName, sysLocation, eventTimeStampAcLocalMode, syGeSerial, 
			eventAcLocalModePriority, syGeTrapCounter, acGnGlLocalMode 
		}
	STATUS current
	DESCRIPTION
		"AcLocalMode notification"
	::= { events 11 }

eventAcFaultBindings OBJECT-IDENTITY
	STATUS current
	DESCRIPTION
		"No description"
	::= { eventBindings 12 }

eventTimeStampAcFault OBJECT-TYPE
	SYNTAX DateAndTime
	MAX-ACCESS accessible-for-notify
	STATUS current
	DESCRIPTION
		"No description"
	::= { eventAcFaultBindings 1 }

eventAcFault NOTIFICATION-TYPE
		OBJECTS {
			sysDescr, sysName, sysLocation, eventTimeStampAcFault, syGeSerial, 
			eventAcFaultPriority, syGeTrapCounter, acGnAlFault 
		}
	STATUS current
	DESCRIPTION
		"AcFault notification"
	::= { events 12 }

eventAcSwitchOverBindings OBJECT-IDENTITY
	STATUS current
	DESCRIPTION
		"No description"
	::= { eventBindings 13 }

eventTimeStampAcSwitchOver OBJECT-TYPE
	SYNTAX DateAndTime
	MAX-ACCESS accessible-for-notify
	STATUS current
	DESCRIPTION
		"No description"
	::= { eventAcSwitchOverBindings 1 }

eventAcSwitchOver NOTIFICATION-TYPE
		OBJECTS {
			sysDescr, sysName, sysLocation, eventTimeStampAcSwitchOver, syGeSerial, 
			eventAcSwitchOverPriority, syGeTrapCounter, acGnAlSwitchOver 
		}
	STATUS current
	DESCRIPTION
		"AcSwitchOver notification"
	::= { events 13 }

eventSysWarningBindings OBJECT-IDENTITY
	STATUS current
	DESCRIPTION
		"No description"
	::= { eventBindings 14 }

eventTimeStampSysWarning OBJECT-TYPE
	SYNTAX DateAndTime
	MAX-ACCESS accessible-for-notify
	STATUS current
	DESCRIPTION
		"No description"
	::= { eventSysWarningBindings 1 }

eventSysWarning NOTIFICATION-TYPE
		OBJECTS {
			sysDescr, sysName, sysLocation, eventTimeStampSysWarning, syGeSerial, 
			eventSysWarningPriority, syGeTrapCounter, syAlWarning 
		}
	STATUS current
	DESCRIPTION
		"SysWarning notification"
	::= { events 14 }

eventSysFaultBindings OBJECT-IDENTITY
	STATUS current
	DESCRIPTION
		"No description"
	::= { eventBindings 15 }

eventTimeStampSysFault OBJECT-TYPE
	SYNTAX DateAndTime
	MAX-ACCESS accessible-for-notify
	STATUS current
	DESCRIPTION
		"No description"
	::= { eventSysFaultBindings 1 }

eventSysFault NOTIFICATION-TYPE
		OBJECTS {
			sysDescr, sysName, sysLocation, eventTimeStampSysFault, syGeSerial, 
			eventSysFaultPriority, syGeTrapCounter, syAlFault 
		}
	STATUS current
	DESCRIPTION
		"SysFault notification"
	::= { events 15 }

eventSysAlAmbBindings OBJECT-IDENTITY
	STATUS current
	DESCRIPTION
		"No description"
	::= { eventBindings 16 }

eventTimeStampSysAlAmb OBJECT-TYPE
	SYNTAX DateAndTime
	MAX-ACCESS accessible-for-notify
	STATUS current
	DESCRIPTION
		"No description"
	::= { eventSysAlAmbBindings 1 }

eventSysAlAmb NOTIFICATION-TYPE
		OBJECTS {
			sysDescr, sysName, sysLocation, eventTimeStampSysAlAmb, syGeSerial, 
			eventSysAlAmbPriority, syGeTrapCounter, syAlAmb 
		}
	STATUS current
	DESCRIPTION
		"SysAlAmb notification"
	::= { events 16 }

eventSysAlVoltAuxBindings OBJECT-IDENTITY
	STATUS current
	DESCRIPTION
		"No description"
	::= { eventBindings 17 }

eventTimeStampSysAlVoltAux OBJECT-TYPE
	SYNTAX DateAndTime
	MAX-ACCESS accessible-for-notify
	STATUS current
	DESCRIPTION
		"No description"
	::= { eventSysAlVoltAuxBindings 1 }

eventSysAlVoltAux NOTIFICATION-TYPE
		OBJECTS {
			sysDescr, sysName, sysLocation, eventTimeStampSysAlVoltAux, syGeSerial, 
			eventSysAlVoltAuxPriority, syGeTrapCounter, syAlVoltAux 
		}
	STATUS current
	DESCRIPTION
		"SysAlVoltAux notification"
	::= { events 17 }

eventSysAlRelayBindings OBJECT-IDENTITY
	STATUS current
	DESCRIPTION
		"No description"
	::= { eventBindings 18 }

eventTimeStampSysAlRelay OBJECT-TYPE
	SYNTAX DateAndTime
	MAX-ACCESS accessible-for-notify
	STATUS current
	DESCRIPTION
		"No description"
	::= { eventSysAlRelayBindings 1 }

eventSysAlRelay NOTIFICATION-TYPE
		OBJECTS {
			sysDescr, sysName, sysLocation, eventTimeStampSysAlRelay, syGeSerial, 
			eventSysAlRelayPriority, syGeTrapCounter, syAlRelay 
		}
	STATUS current
	DESCRIPTION
		"SysAlRelay notification"
	::= { events 18 }

eventSysAlReserveBindings OBJECT-IDENTITY
	STATUS current
	DESCRIPTION
		"No description"
	::= { eventBindings 19 }

eventTimeStampSysAlReserve OBJECT-TYPE
	SYNTAX DateAndTime
	MAX-ACCESS accessible-for-notify
	STATUS current
	DESCRIPTION
		"No description"
	::= { eventSysAlReserveBindings 1 }

eventSysAlReserve NOTIFICATION-TYPE
		OBJECTS {
			sysDescr, sysName, sysLocation, eventTimeStampSysAlReserve, syGeSerial, 
			eventSysAlReservePriority, syGeTrapCounter, syAlReserve 
		}
	STATUS current
	DESCRIPTION
		"SysAlReserve notification"
	::= { events 19 }

eventInSeAlrInputSwitchBindings OBJECT-IDENTITY
	STATUS current
	DESCRIPTION
		"No description"
	::= { eventBindings 20 }

eventTimeStampInSeAlrInputSwitch OBJECT-TYPE
	SYNTAX DateAndTime
	MAX-ACCESS accessible-for-notify
	STATUS current
	DESCRIPTION
		"No description"
	::= { eventInSeAlrInputSwitchBindings 1 }

eventInSeAlrInputSwitch NOTIFICATION-TYPE
		OBJECTS {
			sysDescr, sysName, sysLocation, eventTimeStampInSeAlrInputSwitch, syGeSerial, 
			eventInSeAlrInputSwitchPriority, syGeTrapCounter, inSeAlrInputSwitch 
		}
	STATUS current
	DESCRIPTION
		"inSeAlrInputSwitch notification"
	::= { events 20 }

eventTxAl1dBBindings OBJECT-IDENTITY
	STATUS current
	DESCRIPTION
		"No description"
	::= { eventBindings 21 }

eventTimeStampTxAl1dB OBJECT-TYPE
	SYNTAX DateAndTime
	MAX-ACCESS accessible-for-notify
	STATUS current
	DESCRIPTION
		"No description"
	::= { eventTxAl1dBBindings 1 }

eventTxAl1dB NOTIFICATION-TYPE
		OBJECTS {
			sysDescr, sysName, sysLocation, eventTimeStampTxAl1dB, syGeSerial, 
			eventTxAl1dBPriority, syGeTrapCounter, txGnAl1dB 
		}
	STATUS current
	DESCRIPTION
		"TxAl1dB notification"
	::= { events 21 }

eventTxGnGlStandbyBindings OBJECT-IDENTITY
	STATUS current
	DESCRIPTION
		"No description"
	::= { eventBindings 22 }

eventTimeStampTxGnGlStandby OBJECT-TYPE
	SYNTAX DateAndTime
	MAX-ACCESS accessible-for-notify
	STATUS current
	DESCRIPTION
		"No description"
	::= { eventTxGnGlStandbyBindings 1 }

eventTxGnGlStandby NOTIFICATION-TYPE
		OBJECTS {
			sysDescr, sysName, sysLocation, eventTimeStampTxGnGlStandby, syGeSerial, 
			eventTxGnGlStandbyPriority, syGeTrapCounter, txGnGlStandby 
		}
	STATUS current
	DESCRIPTION
		"TxGnGlStandby notification"
	::= { events 22 }

eventInAlLine1Bindings OBJECT-IDENTITY
	STATUS current
	DESCRIPTION
		"No description"
	::= { eventBindings 23 }

eventTimeStampInAlLine1 OBJECT-TYPE
	SYNTAX DateAndTime
	MAX-ACCESS accessible-for-notify
	STATUS current
	DESCRIPTION
		"No description"
	::= { eventInAlLine1Bindings 1 }

eventInAlLine1 NOTIFICATION-TYPE
		OBJECTS {
			sysDescr, sysName, sysLocation, eventTimeStampInAlLine1, syGeSerial, 
			eventInAlLine1Priority, syGeTrapCounter, inAlLine1
		}
	STATUS current
	DESCRIPTION
		"InAlLine1 notification"
	::= { events 23 }

eventInAlLine2Bindings OBJECT-IDENTITY
	STATUS current
	DESCRIPTION
		"No description"
	::= { eventBindings 24 }

eventTimeStampInAlLine2 OBJECT-TYPE
	SYNTAX DateAndTime
	MAX-ACCESS accessible-for-notify
	STATUS current
	DESCRIPTION
		"No description"
	::= { eventInAlLine2Bindings 1 }

eventInAlLine2 NOTIFICATION-TYPE
		OBJECTS {
			sysDescr, sysName, sysLocation, eventTimeStampInAlLine2, syGeSerial, 
			eventInAlLine2Priority, syGeTrapCounter, inAlLine2
		}
	STATUS current
	DESCRIPTION
		"InAlLine2 notification"
	::= { events 24 }

eventInAlMpx1Bindings OBJECT-IDENTITY
	STATUS current
	DESCRIPTION
		"No description"
	::= { eventBindings 25 }

eventTimeStampInAlMpx1 OBJECT-TYPE
	SYNTAX DateAndTime
	MAX-ACCESS accessible-for-notify
	STATUS current
	DESCRIPTION
		"No description"
	::= { eventInAlMpx1Bindings 1 }

eventInAlMpx1 NOTIFICATION-TYPE
		OBJECTS {
			sysDescr, sysName, sysLocation, eventTimeStampInAlMpx1, syGeSerial, 
			eventInAlMpx1Priority, syGeTrapCounter, inAlMpx1
		}
	STATUS current
	DESCRIPTION
		"InAlMpx1 notification"
	::= { events 25 }

eventInAlMpx2Bindings OBJECT-IDENTITY
	STATUS current
	DESCRIPTION
		"No description"
	::= { eventBindings 26 }

eventTimeStampInAlMpx2 OBJECT-TYPE
	SYNTAX DateAndTime
	MAX-ACCESS accessible-for-notify
	STATUS current
	DESCRIPTION
		"No description"
	::= { eventInAlMpx2Bindings 1 }

eventInAlMpx2 NOTIFICATION-TYPE
		OBJECTS {
			sysDescr, sysName, sysLocation, eventTimeStampInAlMpx2, syGeSerial, 
			eventInAlMpx2Priority, syGeTrapCounter, inAlMpx2
		}
	STATUS current
	DESCRIPTION
		"InAlMpx2 notification"
	::= { events 26 }

eventInAlPlayerBindings OBJECT-IDENTITY
	STATUS current
	DESCRIPTION
		"No description"
	::= { eventBindings 27 }

eventTimeStampInAlPlayer OBJECT-TYPE
	SYNTAX DateAndTime
	MAX-ACCESS accessible-for-notify
	STATUS current
	DESCRIPTION
		"No description"
	::= { eventInAlPlayerBindings 1 }

eventInAlPlayer NOTIFICATION-TYPE
		OBJECTS {
			sysDescr, sysName, sysLocation, eventTimeStampInAlPlayer, syGeSerial, 
			eventInAlPlayerPriority, syGeTrapCounter, inAlPlayer
		}
	STATUS current
	DESCRIPTION
		"InAlPlayer notification"
	::= { events 27 }

eventSysAlInvalidDataBindings OBJECT-IDENTITY
	STATUS current
	DESCRIPTION
		"No description"
	::= { eventBindings 28 }

eventTimeStampSysAlInvalidData OBJECT-TYPE
	SYNTAX DateAndTime
	MAX-ACCESS accessible-for-notify
	STATUS current
	DESCRIPTION
		"No description"
	::= { eventSysAlInvalidDataBindings 1 }

eventSysAlInvalidData NOTIFICATION-TYPE
		OBJECTS {
			sysDescr, sysName, sysLocation, eventTimeStampSysAlInvalidData, syGeSerial, 
			eventSysAlInvalidDataPriority, syGeTrapCounter, syAlInvalidData
		}
	STATUS current
	DESCRIPTION
		"SysAlInvalidData notification"
	::= { events 28 }

eventAcGnAlInterlockAntBindings OBJECT-IDENTITY
	STATUS current
	DESCRIPTION
		"No description"
	::= { eventBindings 29 }

eventTimeStampAcGnAlInterlockAnt OBJECT-TYPE
	SYNTAX DateAndTime
	MAX-ACCESS accessible-for-notify
	STATUS current
	DESCRIPTION
		"No description"
	::= { eventAcGnAlInterlockAntBindings 1 }

eventAcGnAlInterlockAnt NOTIFICATION-TYPE
		OBJECTS {
			sysDescr, sysName, sysLocation, eventTimeStampAcGnAlInterlockAnt, syGeSerial, 
			eventAcGnAlInterlockAntPriority, syGeTrapCounter, acGnAlInterlockAnt
		}
	STATUS current
	DESCRIPTION
		"AcGnAlInterlockAnt notification"
	::= { events 29 }

eventAcGnAlInterlockLoadBindings OBJECT-IDENTITY
	STATUS current
	DESCRIPTION
		"No description"
	::= { eventBindings 30 }

eventTimeStampAcGnAlInterlockLoad OBJECT-TYPE
	SYNTAX DateAndTime
	MAX-ACCESS accessible-for-notify
	STATUS current
	DESCRIPTION
		"No description"
	::= { eventAcGnAlInterlockLoadBindings 1 }

eventAcGnAlInterlockLoad NOTIFICATION-TYPE
		OBJECTS {
			sysDescr, sysName, sysLocation, eventTimeStampAcGnAlInterlockLoad, syGeSerial, 
			eventAcGnAlInterlockLoadPriority, syGeTrapCounter, acGnAlInterlockLoad
		}
	STATUS current
	DESCRIPTION
		"AcGnAlInterlockLoad notification"
	::= { events 30 }

eventSysAl24vBindings OBJECT-IDENTITY
	STATUS current
	DESCRIPTION
		"No description"
	::= { eventBindings 31 }

eventTimeStampSysAl24v OBJECT-TYPE
	SYNTAX DateAndTime
	MAX-ACCESS accessible-for-notify
	STATUS current
	DESCRIPTION
		"No description"
	::= { eventSysAl24vBindings 1 }

eventSysAl24v NOTIFICATION-TYPE
		OBJECTS {
			sysDescr, sysName, sysLocation, eventTimeStampSysAl24v, syGeSerial, 
			eventSysAl24vPriority, syGeTrapCounter, syAl24v
		}
	STATUS current
	DESCRIPTION
		"SysAl24v notification"
	::= { events 31 }

eventSysAlCommBindings OBJECT-IDENTITY
	STATUS current
	DESCRIPTION
		"No description"
	::= { eventBindings 32 }

eventTimeStampSysAlComm OBJECT-TYPE
	SYNTAX DateAndTime
	MAX-ACCESS accessible-for-notify
	STATUS current
	DESCRIPTION
		"No description"
	::= { eventSysAlCommBindings 1 }

eventSysAlComm NOTIFICATION-TYPE
		OBJECTS {
			sysDescr, sysName, sysLocation, eventTimeStampSysAlComm, syGeSerial, 
			eventSysAlCommPriority, syGeTrapCounter, syAlComm
		}
	STATUS current
	DESCRIPTION
		"syAlComm notification"
	::= { events 32 }

eventEquipmentOnBindings OBJECT-IDENTITY
	STATUS current
	DESCRIPTION
		"No description"
	::= { eventBindings 33 }

eventTimeStampEquipmentOn OBJECT-TYPE
	SYNTAX DateAndTime
	MAX-ACCESS accessible-for-notify
	STATUS current
	DESCRIPTION
		"No description"
	::= { eventEquipmentOnBindings 1 }

eventEquipmentOnDownTime OBJECT-TYPE
	SYNTAX Integer32
	MAX-ACCESS accessible-for-notify
	STATUS current
	DESCRIPTION
		"No description"
	::= { eventEquipmentOnBindings 2 }

eventEquipmentOn NOTIFICATION-TYPE
		OBJECTS {
			sysDescr, sysName, sysLocation, eventTimeStampEquipmentOn, syGeSerial, 
			eventEquipmentOnPriority, syGeTrapCounter, eventEquipmentOnDownTime
		}
	STATUS current
	DESCRIPTION
		"equipmentOn notification"
	::= { events 33 }

eventHeartBeatBindings OBJECT-IDENTITY
	STATUS current
	DESCRIPTION
		"No description"
	::= { eventBindings 34 }

eventTimeStampHeartBeat OBJECT-TYPE
	SYNTAX DateAndTime
	MAX-ACCESS accessible-for-notify
	STATUS current
	DESCRIPTION
		"No description"
	::= { eventHeartBeatBindings 1 }

eventHeartBeat NOTIFICATION-TYPE
		OBJECTS {
			sysDescr, sysName, sysLocation, eventTimeStampHeartBeat, syGeSerial, 
			eventHeartBeatPriority, syGeTrapCounter
		}
	STATUS current
	DESCRIPTION
		"heartBeat notification"
	::= { events 34 }

eventConfigChangedBindings OBJECT-IDENTITY
	STATUS current
	DESCRIPTION
		"No description"
	::= { eventBindings 35 }

eventTimeStampConfigChanged OBJECT-TYPE
	SYNTAX DateAndTime
	MAX-ACCESS accessible-for-notify
	STATUS current
	DESCRIPTION
		"No description"
	::= { eventConfigChangedBindings 1 }

eventConfigChanged NOTIFICATION-TYPE
		OBJECTS {
			sysDescr, sysName, sysLocation, eventTimeStampConfigChanged, syGeSerial, 
			eventConfigChangedPriority, syGeTrapCounter
		}
	STATUS current
	DESCRIPTION
		"configChanged notification"
	::= { events 35 }

eventEquipmentFaultBindings OBJECT-IDENTITY
	STATUS obsolete
	DESCRIPTION
		"No description"
	::= { eventBindings 36 }

eventTimeStampEquipmentFault OBJECT-TYPE
	SYNTAX DateAndTime
	MAX-ACCESS accessible-for-notify
	STATUS obsolete
	DESCRIPTION
		"No description"
	::= { eventEquipmentFaultBindings 1 }

eventEquipmentFaultError OBJECT-TYPE
	SYNTAX DisplayString(SIZE(0..255))
	MAX-ACCESS accessible-for-notify
	STATUS obsolete
	DESCRIPTION
		"error message"
	::= { eventEquipmentFaultBindings 2 }

eventEquipmentFault NOTIFICATION-TYPE
		OBJECTS {
			sysDescr, sysName, sysLocation, eventTimeStampEquipmentFault, syGeSerial, 
			eventEquipmentFaultPriority, syGeTrapCounter, eventEquipmentFaultError
		}
	STATUS obsolete
	DESCRIPTION
		"equipmentFault notification"
	::= { events 36 }

eventInAlFaultBindings OBJECT-IDENTITY
	STATUS current
	DESCRIPTION
		"No description"
	::= { eventBindings 37 }

eventTimeStampInAlFault OBJECT-TYPE
	SYNTAX DateAndTime
	MAX-ACCESS accessible-for-notify
	STATUS current
	DESCRIPTION
		"No description"
	::= { eventInAlFaultBindings 1 }

eventInAlFault NOTIFICATION-TYPE
		OBJECTS {
			sysDescr, sysName, sysLocation, eventTimeStampInAlFault, syGeSerial, 
			eventInAlFaultPriority, syGeTrapCounter, inAlFault
		}
	STATUS current
	DESCRIPTION
		"inAlFault notification"
	::= { events 37 }

eventMoSfAlarmBindings OBJECT-IDENTITY
	STATUS current
	DESCRIPTION
		"No description"
	::= { eventBindings 38 }

eventTimeStampMoSfAlarm OBJECT-TYPE
	SYNTAX DateAndTime
	MAX-ACCESS accessible-for-notify
	STATUS current
	DESCRIPTION
		"No description"
	::= { eventMoSfAlarmBindings 1 }

eventMoSfAlarm NOTIFICATION-TYPE
		OBJECTS {
			sysDescr, sysName, sysLocation, eventTimeStampMoSfAlarm, syGeSerial, 
			eventMoSfAlarmPriority, syGeTrapCounter, moSfAlarm
		}
	STATUS current
	DESCRIPTION
		"moSfAlarm notification"
	::= { events 38 }

eventMoSfSwitch10MAlarmBindings OBJECT-IDENTITY
	STATUS current
	DESCRIPTION
		"No description"
	::= { eventBindings 39 }

eventTimeStampMoSfSwitch10MAlarm OBJECT-TYPE
	SYNTAX DateAndTime
	MAX-ACCESS accessible-for-notify
	STATUS current
	DESCRIPTION
		"No description"
	::= { eventMoSfSwitch10MAlarmBindings 1 }

eventMoSfSwitch10MAlarm NOTIFICATION-TYPE
		OBJECTS {
			sysDescr, sysName, sysLocation, eventTimeStampMoSfSwitch10MAlarm, syGeSerial, 
			eventMoSfAlarmPriority, syGeTrapCounter, moSfSwitch10MAlarm
		}
	STATUS current
	DESCRIPTION
		"moSfSwitch10MAlarm notification"
	::= { events 39 }



eventSyAlLoggingBindings OBJECT-IDENTITY
	STATUS current
	DESCRIPTION
		"No description"
	::= { eventBindings 40 }

eventTimeStampSyAlLogging OBJECT-TYPE
	SYNTAX DateAndTime
	MAX-ACCESS accessible-for-notify
	STATUS current
	DESCRIPTION
		"No description"
	::= { eventSyAlLoggingBindings 1 }

eventSyAlLogging NOTIFICATION-TYPE
		OBJECTS {
			sysDescr, sysName, sysLocation, eventTimeStampSyAlLogging, syGeSerial, 
			eventSyAlLoggingPriority, syGeTrapCounter, syAlLogging
		}
	STATUS current
	DESCRIPTION
		"syAlLogging notification"
	::= { events 40 }


eventInAlMpx3Bindings OBJECT-IDENTITY
	STATUS current
	DESCRIPTION
		"No description"
	::= { eventBindings 41 }

eventTimeStampInAlMpx3 OBJECT-TYPE
	SYNTAX DateAndTime
	MAX-ACCESS accessible-for-notify
	STATUS current
	DESCRIPTION
		"No description"
	::= { eventInAlMpx3Bindings 1 }

eventInAlMpx3 NOTIFICATION-TYPE
		OBJECTS {
			sysDescr, sysName, sysLocation, eventTimeStampInAlMpx3, syGeSerial, 
			eventInAlMpx3Priority, syGeTrapCounter, inAlMpx3
		}
	STATUS current
	DESCRIPTION
		"InAlMpx3 notification"
	::= { events 41 }


eventInAlMpx4Bindings OBJECT-IDENTITY
	STATUS current
	DESCRIPTION
		"No description"
	::= { eventBindings 42 }

eventTimeStampInAlMpx4 OBJECT-TYPE
	SYNTAX DateAndTime
	MAX-ACCESS accessible-for-notify
	STATUS current
	DESCRIPTION
		"No description"
	::= { eventInAlMpx4Bindings 1 }

eventInAlMpx4 NOTIFICATION-TYPE
		OBJECTS {
			sysDescr, sysName, sysLocation, eventTimeStampInAlMpx4, syGeSerial, 
			eventInAlMpx4Priority, syGeTrapCounter, inAlMpx4
		}
	STATUS current
	DESCRIPTION
		"InAlMpx4 notification"
	::= { events 42 }


eventTxSfStActBindings OBJECT-IDENTITY
	STATUS current
	DESCRIPTION
		"No description"
	::= { eventBindings 43 }

eventTimeStampTxSfStAct OBJECT-TYPE
	SYNTAX DateAndTime
	MAX-ACCESS accessible-for-notify
	STATUS current
	DESCRIPTION
		"No description"
	::= { eventTxSfStActBindings 1 }

eventTxSfStAct NOTIFICATION-TYPE
		OBJECTS {
			sysDescr, sysName, sysLocation, eventTimeStampTxSfStAct, syGeSerial, 
			eventTxSfStActPriority, syGeTrapCounter, txSfStAct
		}
	STATUS current
	DESCRIPTION
		"TxSfStAct notification"
	::= { events 43 }


eventTxSfStAlarmBindings OBJECT-IDENTITY
	STATUS current
	DESCRIPTION
		"No description"
	::= { eventBindings 44 }

eventTimeStampTxSfStAlarm OBJECT-TYPE
	SYNTAX DateAndTime
	MAX-ACCESS accessible-for-notify
	STATUS current
	DESCRIPTION
		"No description"
	::= { eventTxSfStAlarmBindings 1 }

eventTxSfStAlarm NOTIFICATION-TYPE
		OBJECTS {
			sysDescr, sysName, sysLocation, eventTimeStampTxSfStAlarm, syGeSerial, 
			eventTxSfStAlarmPriority, syGeTrapCounter, txSfStAlarm
		}
	STATUS current
	DESCRIPTION
		"TxSfStAlarm notification"
	::= { events 44 }


eventSyLiAlRdsBindings OBJECT-IDENTITY
	STATUS current
	DESCRIPTION
		"No description"
	::= { eventBindings 45 }

eventTimeStampSyLiAlRds OBJECT-TYPE
	SYNTAX DateAndTime
	MAX-ACCESS accessible-for-notify
	STATUS current
	DESCRIPTION
		"No description"
	::= { eventSyLiAlRdsBindings 1 }

eventSyLiAlRds NOTIFICATION-TYPE
		OBJECTS {
			sysDescr, sysName, sysLocation, eventTimeStampSyLiAlRds, syGeSerial, 
			eventSyLiAlRdsPriority, syGeTrapCounter, syLiAlRds
		}
	STATUS current
	DESCRIPTION
		"SyLiAlRds notification"
	::= { events 45 }


eventSyLiAlSoundProcBindings OBJECT-IDENTITY
	STATUS current
	DESCRIPTION
		"No description"
	::= { eventBindings 46 }

eventTimeStampSyLiAlSoundProc OBJECT-TYPE
	SYNTAX DateAndTime
	MAX-ACCESS accessible-for-notify
	STATUS current
	DESCRIPTION
		"No description"
	::= { eventSyLiAlSoundProcBindings 1 }

eventSyLiAlSoundProc NOTIFICATION-TYPE
		OBJECTS {
			sysDescr, sysName, sysLocation, eventTimeStampSyLiAlSoundProc, syGeSerial, 
			eventSyLiAlSoundProcPriority, syGeTrapCounter, syLiAlSoundProc
		}
	STATUS current
	DESCRIPTION
		"SyLiAlSoundProc notification"
	::= { events 46 }


eventSyLiAlSfmBindings OBJECT-IDENTITY
	STATUS current
	DESCRIPTION
		"No description"
	::= { eventBindings 47 }

eventTimeStampSyLiAlSfm OBJECT-TYPE
	SYNTAX DateAndTime
	MAX-ACCESS accessible-for-notify
	STATUS current
	DESCRIPTION
		"No description"
	::= { eventSyLiAlSfmBindings 1 }

eventSyLiAlSfm NOTIFICATION-TYPE
		OBJECTS {
			sysDescr, sysName, sysLocation, eventTimeStampSyLiAlSfm, syGeSerial, 
			eventSyLiAlSfmPriority, syGeTrapCounter, syLiAlSfm
		}
	STATUS current
	DESCRIPTION
		"SyLiAlSfm notification"
	::= { events 47 }


eventSyLiAlActivationBindings OBJECT-IDENTITY
	STATUS current
	DESCRIPTION
		"No description"
	::= { eventBindings 48 }

eventTimeStampSyLiAlActivation OBJECT-TYPE
	SYNTAX DateAndTime
	MAX-ACCESS accessible-for-notify
	STATUS current
	DESCRIPTION
		"No description"
	::= { eventSyLiAlActivationBindings 1 }

eventSyLiAlActivation NOTIFICATION-TYPE
		OBJECTS {
			sysDescr, sysName, sysLocation, eventTimeStampSyLiAlActivation, syGeSerial, 
			eventSyLiAlActivationPriority, syGeTrapCounter, syLiAlActivation
		}
	STATUS current
	DESCRIPTION
		"SyLiAlActivation notification"
	::= { events 48 }


eventInAlAes1Bindings OBJECT-IDENTITY
	STATUS current
	DESCRIPTION
		"No description"
	::= { eventBindings 49 }

eventTimeStampInAlAes1 OBJECT-TYPE
	SYNTAX DateAndTime
	MAX-ACCESS accessible-for-notify
	STATUS current
	DESCRIPTION
		"No description"
	::= { eventInAlAes1Bindings 1 }

eventInAlAes1 NOTIFICATION-TYPE
		OBJECTS {
			sysDescr, sysName, sysLocation, eventTimeStampInAlAes1, syGeSerial, 
			eventInAlAes1Priority, syGeTrapCounter, inAlAes1
		}
	STATUS current
	DESCRIPTION
		"InAlAes1 notification"
	::= { events 49 }


eventInAlAes2Bindings OBJECT-IDENTITY
	STATUS current
	DESCRIPTION
		"No description"
	::= { eventBindings 50 }

eventTimeStampInAlAes2 OBJECT-TYPE
	SYNTAX DateAndTime
	MAX-ACCESS accessible-for-notify
	STATUS current
	DESCRIPTION
		"No description"
	::= { eventInAlAes2Bindings 1 }

eventInAlAes2 NOTIFICATION-TYPE
		OBJECTS {
			sysDescr, sysName, sysLocation, eventTimeStampInAlAes2, syGeSerial, 
			eventInAlAes2Priority, syGeTrapCounter, inAlAes2
		}
	STATUS current
	DESCRIPTION
		"InAlAes2 notification"
	::= { events 50 }


eventInAlAes3Bindings OBJECT-IDENTITY
	STATUS current
	DESCRIPTION
		"No description"
	::= { eventBindings 51 }

eventTimeStampInAlAes3 OBJECT-TYPE
	SYNTAX DateAndTime
	MAX-ACCESS accessible-for-notify
	STATUS current
	DESCRIPTION
		"No description"
	::= { eventInAlAes3Bindings 1 }

eventInAlAes3 NOTIFICATION-TYPE
		OBJECTS {
			sysDescr, sysName, sysLocation, eventTimeStampInAlAes3, syGeSerial, 
			eventInAlAes3Priority, syGeTrapCounter, inAlAes3
		}
	STATUS current
	DESCRIPTION
		"InAlAes3 notification"
	::= { events 51 }


eventInAlAna1Bindings OBJECT-IDENTITY
	STATUS current
	DESCRIPTION
		"No description"
	::= { eventBindings 52 }

eventTimeStampInAlAna1 OBJECT-TYPE
	SYNTAX DateAndTime
	MAX-ACCESS accessible-for-notify
	STATUS current
	DESCRIPTION
		"No description"
	::= { eventInAlAna1Bindings 1 }

eventInAlAna1 NOTIFICATION-TYPE
		OBJECTS {
			sysDescr, sysName, sysLocation, eventTimeStampInAlAna1, syGeSerial, 
			eventInAlAna1Priority, syGeTrapCounter, inAlAna1
		}
	STATUS current
	DESCRIPTION
		"InAlAna1 notification"
	::= { events 52 }


eventInAlAoipBindings OBJECT-IDENTITY
	STATUS current
	DESCRIPTION
		"No description"
	::= { eventBindings 53 }

eventTimeStampInAlAoip OBJECT-TYPE
	SYNTAX DateAndTime
	MAX-ACCESS accessible-for-notify
	STATUS current
	DESCRIPTION
		"No description"
	::= { eventInAlAoipBindings 1 }

eventInAlAoip NOTIFICATION-TYPE
		OBJECTS {
			sysDescr, sysName, sysLocation, eventTimeStampInAlAoip, syGeSerial, 
			eventInAlAoipPriority, syGeTrapCounter, inAlAoip
		}
	STATUS current
	DESCRIPTION
		"InAlAoip notification"
	::= { events 53 }


eventLossOfEth0Bindings OBJECT-IDENTITY
	STATUS current
	DESCRIPTION
		"No description"
	::= { eventBindings 54 }

eventTimeStampLossOfEth0 OBJECT-TYPE
	SYNTAX DateAndTime
	MAX-ACCESS accessible-for-notify
	STATUS current
	DESCRIPTION
		"No description"
	::= { eventLossOfEth0Bindings 1 }

eventLossOfEth0 NOTIFICATION-TYPE
		OBJECTS {
			sysDescr, sysName, sysLocation, eventTimeStampLossOfEth0, syGeSerial, 
			eventLossOfEth0Priority, syGeTrapCounter, syLossOfEth0
		}
	STATUS current
	DESCRIPTION
		"syLossOfEth0 notification"
	::= { events 54 }


eventLossOfEth1Bindings OBJECT-IDENTITY
	STATUS current
	DESCRIPTION
		"No description"
	::= { eventBindings 55 }

eventTimeStampLossOfEth1 OBJECT-TYPE
	SYNTAX DateAndTime
	MAX-ACCESS accessible-for-notify
	STATUS current
	DESCRIPTION
		"No description"
	::= { eventLossOfEth1Bindings 1 }

eventLossOfEth1 NOTIFICATION-TYPE
		OBJECTS {
			sysDescr, sysName, sysLocation, eventTimeStampLossOfEth1, syGeSerial, 
			eventLossOfEth1Priority, syGeTrapCounter, syLossOfEth1
		}
	STATUS current
	DESCRIPTION
		"syLossOfEth1 notification"
	::= { events 55 }


eventSyLiAlAoipdecoderBindings OBJECT-IDENTITY
	STATUS current
	DESCRIPTION
		"No description"
	::= { eventBindings 56 }

eventTimeStampSyLiAlAoipdecoder OBJECT-TYPE
	SYNTAX DateAndTime
	MAX-ACCESS accessible-for-notify
	STATUS current
	DESCRIPTION
		"No description"
	::= { eventSyLiAlAoipdecoderBindings 1 }

eventSyLiAlAoipdecoder NOTIFICATION-TYPE
		OBJECTS {
			sysDescr, sysName, sysLocation, eventTimeStampSyLiAlAoipdecoder, syGeSerial, 
			eventSyLiAlAoipdecoderPriority, syGeTrapCounter, syLiAlAoipdecoder
		}
	STATUS current
	DESCRIPTION
		"syLiAlAoipdecoder notification"
	::= { events 56 }


eventSyLiAlMpxoipdecoderBindings OBJECT-IDENTITY
	STATUS current
	DESCRIPTION
		"No description"
	::= { eventBindings 57 }

eventTimeStampSyLiAlMpxoipdecoder OBJECT-TYPE
	SYNTAX DateAndTime
	MAX-ACCESS accessible-for-notify
	STATUS current
	DESCRIPTION
		"No description"
	::= { eventSyLiAlMpxoipdecoderBindings 1 }

eventSyLiAlMpxoipdecoder NOTIFICATION-TYPE
		OBJECTS {
			sysDescr, sysName, sysLocation, eventTimeStampSyLiAlMpxoipdecoder, syGeSerial, 
			eventSyLiAlMpxoipdecoderPriority, syGeTrapCounter, syLiAlMpxoipdecoder
		}
	STATUS current
	DESCRIPTION
		"syLiAlMpxoipdecoder notification"
	::= { events 57 }


eventSyLiAlSurestreamBindings OBJECT-IDENTITY
	STATUS current
	DESCRIPTION
		"No description"
	::= { eventBindings 58 }

eventTimeStampSyLiAlSurestream OBJECT-TYPE
	SYNTAX DateAndTime
	MAX-ACCESS accessible-for-notify
	STATUS current
	DESCRIPTION
		"No description"
	::= { eventSyLiAlSurestreamBindings 1 }

eventSyLiAlSurestream NOTIFICATION-TYPE
		OBJECTS {
			sysDescr, sysName, sysLocation, eventTimeStampSyLiAlSurestream, syGeSerial, 
			eventSyLiAlSurestreamPriority, syGeTrapCounter, syLiAlSurestream
		}
	STATUS current
	DESCRIPTION
		"syLiAlSurestream notification"
	::= { events 58 }


eventSyLiAlSynchrostreamBindings OBJECT-IDENTITY
	STATUS current
	DESCRIPTION
		"No description"
	::= { eventBindings 59 }

eventTimeStampSyLiAlSynchrostream OBJECT-TYPE
	SYNTAX DateAndTime
	MAX-ACCESS accessible-for-notify
	STATUS current
	DESCRIPTION
		"No description"
	::= { eventSyLiAlSynchrostreamBindings 1 }

eventSyLiAlSynchrostream NOTIFICATION-TYPE
		OBJECTS {
			sysDescr, sysName, sysLocation, eventTimeStampSyLiAlSynchrostream, syGeSerial, 
			eventSyLiAlSynchrostreamPriority, syGeTrapCounter, syLiAlSynchrostream
		}
	STATUS current
	DESCRIPTION
		"syLiAlSynchrostream notification"
	::= { events 59 }



groups OBJECT-IDENTITY
	STATUS current
	DESCRIPTION
		"No description"
	::= { transmitter 2 }

	objectGroup OBJECT-GROUP
		OBJECTS {
			eventTxLocalModePriority, eventTxLocalModeEnable, txLocalModeSignalSuppression, eventTxAl3dBPriority, eventTxAl3dBEnable, 
			eventTxAlFaultPriority, eventTxAlFaultEnable, eventTxAlWarningPriority, eventTxAlWarningEnable, eventTxAlVSWRPriority, 
			eventTxAlVSWREnable, eventTxAlInterlockAntPriority, eventTxAlInterlockAntEnable,  
			eventTxRfOpmodePriority, eventTxRfOpmodeEnable, eventTxRfRFPresentPriority, eventTxRfRFPresentEnable, eventAcReserveControlPriority, 
			eventInAlLine1Priority, eventInAlLine1Enable, eventInAlLine2Priority, eventInAlLine2Enable, 
			eventInAlMpx1Priority, eventInAlMpx1Enable, eventInAlMpx2Priority, eventInAlMpx2Enable,eventInAlPlayerPriority, eventInAlPlayerEnable,
			eventAcReserveControlEnable, eventAcLocalModePriority, eventAcLocalModeEnable, acLocalModeSignalSuppression, eventAcFaultPriority, 
			eventAcFaultEnable, eventAcSwitchOverPriority, eventAcSwitchOverEnable, eventSysWarningPriority, eventSysWarningEnable, 
			eventSysFaultPriority, eventSysFaultEnable, eventSysAlAmbPriority, eventSysAlAmbEnable, eventSysAlVoltAuxPriority, 
			eventSysAlVoltAuxEnable, eventSysAlRelayPriority, eventSysAlRelayEnable, eventSysAlReservePriority, eventSysAlReserveEnable, 
			eventInSeAlrInputSwitchPriority, eventInSeAlrInputSwitchEnable, eventTxAl1dBPriority, eventTxAl1dBEnable, eventTxGnGlStandbyPriority, 
			eventTxGnGlStandbyEnable, eventSysAlInvalidDataPriority, eventSysAlInvalidDataEnable, eventAcGnAlInterlockAntPriority, eventAcGnAlInterlockAntEnable, 
			eventAcGnAlInterlockLoadPriority, eventAcGnAlInterlockLoadEnable, eventSysAl24vPriority, eventSysAl24vEnable, 
			eventSysAlCommPriority, eventSysAlCommEnable, eventEquipmentOnPriority, eventEquipmentOnEnable, 
			eventHeartBeatPriority, eventHeartBeatEnable, eventConfigChangedPriority, eventConfigChangedEnable, eventInAlFaultEnable, 
			eventMoSfAlarmPriority, eventMoSfAlarmEnable, eventMoSfSwitch10MAlarmPriority, eventMoSfSwitch10MAlarmEnable, 
			eventSyAlLoggingPriority, eventSyAlLoggingEnable, eventInAlMpx3Priority, eventInAlMpx3Enable, 
			eventInAlMpx4Priority, eventInAlMpx4Enable, eventInAlAoipPriority, eventInAlAoipEnable, 
			eventTxSfStActPriority, eventTxSfStActEnable, eventTxSfStAlarmPriority, eventTxSfStAlarmEnable, 
			eventSyLiAlRdsPriority, eventSyLiAlRdsEnable, eventSyLiAlSoundProcPriority, eventSyLiAlSoundProcEnable, 
			eventSyLiAlSfmPriority, eventSyLiAlSfmEnable, eventSyLiAlActivationPriority, eventSyLiAlActivationEnable, 
			eventInAlAes1Priority, eventInAlAes1Enable, eventInAlAes2Priority, eventInAlAes2Enable, eventInAlAes3Priority, eventInAlAes3Enable, 
			eventInAlAna1Priority, eventInAlAna1Enable, 
			eventLossOfEth0Priority, eventLossOfEth0Enable, eventLossOfEth1Priority, eventLossOfEth1Enable, 
			eventSyLiAlAoipdecoderPriority, eventSyLiAlAoipdecoderEnable, eventSyLiAlMpxoipdecoderPriority, eventSyLiAlMpxoipdecoderEnable, 
			eventSyLiAlSurestreamPriority, eventSyLiAlSurestreamEnable, eventSyLiAlSynchrostreamPriority, eventSyLiAlSynchrostreamEnable, 
			inSoL1Presence, inSoL1Type, inSoL1LeftPeakMax, inSoL1RightPeakMax, inSoL1LeftPeak, inSoL1RightPeak, 
			inSoL1Level, inSoL1Drive, inSoL1Trim, inSoL1Filter, inSoL1Preacc, inSoL1Lost, inSoL1AlarmTrig,
			inSoL2Presence, inSoL2Type, inSoL2LeftPeakMax, inSoL2RightPeakMax, inSoL2LeftPeak, inSoL2RightPeak, 
			inSoL2Level, inSoL2Drive, inSoL2Trim, inSoL2Filter, inSoL2Preacc, inSoL2Lost, inSoL2AlarmTrig, inSoM1Presence, inSoM1PeakMax, 
			inSoAes1Presence, inSoAes1LeftPeakMax, inSoAes1RightPeakMax, inSoAes1LeftPeak, inSoAes1RightPeak, inSoAes1PeakMax, inSoAes1Peak, 
			inSoAes1Level, inSoAes1Drive, inSoAes1Trim, inSoAes1Filter, inSoAes1Preacc, inSoAes1Lost, inSoAes1AlarmTrig, 
			inSoAes2Presence, inSoAes2LeftPeakMax, inSoAes2RightPeakMax, inSoAes2LeftPeak, inSoAes2RightPeak, inSoAes2PeakMax, inSoAes2Peak, 
			inSoAes2Level, inSoAes2Drive, inSoAes2Trim, inSoAes2Filter, inSoAes2Preacc, inSoAes2Lost, inSoAes2AlarmTrig, 
			inSoAes3Presence, inSoAes3LeftPeakMax, inSoAes3RightPeakMax, inSoAes3LeftPeak, inSoAes3RightPeak, inSoAes3PeakMax, inSoAes3Peak, 
			inSoAes3Level, inSoAes3Drive, inSoAes3Trim, inSoAes3Filter, inSoAes3Preacc, inSoAes3Lost, inSoAes3AlarmTrig, 
			inSoAna1Presence, inSoAna1LeftPeakMax, inSoAna1RightPeakMax, inSoAna1LeftPeak, inSoAna1RightPeak, 
			inSoAna1Level, inSoAna1Drive, inSoAna1Trim, inSoAna1Filter, inSoAna1Preacc, inSoAna1Lost, inSoAna1AlarmTrig, 
			inSoTySlot1, inSoTySlot2, inSoTySlot3, 
			inSoAoipPresence, inSoAoipLeftPeakMax, inSoAoipRightPeakMax, inSoAoipLeftPeak, inSoAoipRightPeak, inSoAoipPeakMax, 
			inSoAoipPeak, inSoAoipLevel, inSoAoipDrive, inSoAoipTrim, inSoAoipFilter, inSoAoipPreacc, inSoAoipLost, inSoAoipAlarmTrig, 
			inSoM1Peak, inSoM1Level, inSoM1Drive, inSoM1Lost, inSoM1AlarmTrig, moSfSwitch10MAlarm, 
			inSoM2Presence, inSoM2PeakMax, inSoM2Peak, inSoM2Level, inSoM2Drive, inSoM2Lost, inSoM2AlarmTrig,
			inSoPlPresence, inSoPlLeftPeakMax, inSoPlRightPeakMax, inSoPlLeftPeak, inSoPlRightPeak, inSoPlLevel, 
			inSoPlDrive, inSoPlTrim, inSoPlFilter, inSoPlPreacc, inSoPlSampling, inSoPlLost, inSoPlAlarmTrig, inSoGeState, 
			inSoGeLevel1, inSoGeLevel2, inSoGeFreq1, inSoGeFreq2, inSoGePreacc, 
			inSoM3Presence, inSoM3PeakMax, inSoM3Peak, inSoM3Level, inSoM3Drive, inSoM3Lost, inSoM3AlarmTrig, 
			inSoM4Presence, inSoM4PeakMax, inSoM4Peak, inSoM4Level, inSoM4Drive, inSoM4Lost, inSoM4AlarmTrig, 
			inSeLine1Prio, inSeLine2Prio, inSeMpx1Prio, inSeMpx2Prio, inSePlayerPrio, inSeMpx3Prio, inSeMpx4Prio, 
			inSeCrossfade, inSeSelectAudio, inSeCurrentAudio, inSeAuBackupMode, 
			inSeAlrInputSwitch, inSeFadein, inSeThLine1Th, inSeThLine1Sil, inSeThLine2Th, inSeThLine2Sil, 
			inSeThPlayerTh, inSeThPlayerSil, inSeThMpx1Th, inSeThMpx2Th, inSeThMpx3Th, inSeThMpx4Th, 
			inSeThAes1Th, inSeThAes1Sil, inSeThAes2Th, inSeThAes2Sil, inSeThAes3Th, inSeThAes3Sil, inSeThAna1Th, inSeThAna1Sil, 
			inSeThAoipTh, inSeThAoipSil, 
			inSeDeLine1BackDelay, inSeDeLine1Delay, inSeDeLine2BackDelay, 
			inSeDeLine2Delay, inSeDePlayerBackDelay, inSeDePlayerDelay, inSeDeMpxBackDelay, inSeDeMpxDelay, 
			inSeDeMpx34BackDelay, inSeDeMpx34Delay, inSeDeAes1BackDelay, inSeDeAes1Delay, inSeDeAes2BackDelay, inSeDeAes2Delay, 
			inSeDeAes3BackDelay, inSeDeAes3Delay, inSeDeAna1BackDelay, inSeDeAna1Delay, 
			inSeDeMpx1BackDelay, inSeDeMpx1Delay, inSeDeMpx2BackDelay, inSeDeMpx2Delay, 
			inSeDeAoipBackDelay, inSeDeAoipDelay, 
			inSeSyLine1, inSeSyLine2, inSeSyPlayer, inSeSyMpx34, inSeSyAes1, inSeSyAes2, inSeSyAes3, inSeSyAoip, 
			inSeSaLine1, inSeSaLine2, inSeSaPlayer, inSeSaMpx1, inSeSaMpx2, inSeSaMpx3, inSeSaMpx4, 
			inSeBackupsSource, 
			inAlLine1, inAlLine2, inAlMpx1, inAlMpx2, inAlPlayer, inAlFault, inAlMpx3, inAlMpx4, inAlAes1, inAlAes2, inAlAes3, inAlAna1, inAlAoip, 
			rdSeDsn, rdSeMainId, rdSeAltId, rdSeCtEnable, rdSeCtOffset, rdMaPi, rdMaPs, rdMaPty, rdMaMs, rdMaDi, rdMaAf, rdMaRt, rdMaPtyn, 
			rdMaGs, rdMaTa, rdMaTp, rdAtPi, rdAtPs, rdAtPty, rdAtMs, rdAtDi, rdAtAf, rdAtRt, rdAtPtyn, rdAtGs, rdAtTa, rdAtTp, 
			rdPsScrollText, rdPsScrollRepetition, rdPsScrollEnable, rdPsScrollCenter, rdPsScrollTrunc, rdPsScrollIncrement, rdPsScrollDelay, 
			rdSeCurrentPs, rdSeCurrentRt, 
			moDevMpx, moDevAudio, moDevPilot, moDevRds, moDevSca, moDevRmsMeas, moDevPeakMeas, moDevPeakMaxMeas, moDevMPeakMaxMeas,moDevSPeakMaxMeas, 
			moSeCoder, 
			moSeCoderRdsSelect, moSeCoderScaSelect, moSeCoderRdsBackup, moSeCoderCurrentRds, moSeCoderCurrentSca,
			moSeCoder19kOutLevel, moSeCoderAlrRdsSwitch, moSeCoderRdsPhase, moSeCoderRdsSelectBackup, 
			moSpClState, moSpClVal, moSpClMeas, moSpMpState, moSpMpTarget, moSpMpMeas1m, moSpMpMeas10s, moSpMpMeasAtt, moSpPrNum, moSpPrBypass,
 			moSpPrTableName, 
			moSfConfDelay, moSfConfState, moSfMeasDelay, moSfAlarm, moSfConfOp10M, moSfState10M, moSfClockSource, moSfState1PPS, 
			txGnGlName, txGnGlPcap, txGnGlType, txGnGlStandby, txGnGlLocalMode, txGnGlReserveType, 
			txGnAl3dB, txGnAlFault, txGnAlWarning, txGnAlVSWR, txGnAlInterlockAnt, txGnAlLink, txGnAlVswrTrip, 
			txGnAl1dB, 
			txGnMsForwardPower, txGnMsReflectedPower, txGnMsVSWR, txGnMsVswrTrip, 
			txGnRfFrequency,txGnRfThreshold3dB, txGnRfAutomatic3dBThreshold, txGnRfThresholdVSWR, txGnRfOpmode, 
			txGnRfPower, txGnRfVswrTrip, txGnRfRFPresent, txGnRfThreshold1dB, txGnRfMaxPower, txGnRfRfPresentMin, txGnRfVswrTrig, 
			txGnPrCurrent, txGnPrGpioMode, txGnPrPresetsFreq, txGnPrPresetsPower,
			txGnPrPresetsName, txGnPrPresetsThreshold3dB, txGnPrPresetsThreshold1dB, txGnPrPresetsRfPresentMin, txGnPrPresetsAuto3dB, 
			txSfMeRangeMin, txSfMeRangeMax, txSfMeCurrentValue, txSfMePwr, txSfMeCurSavings, txSfMeCurBoost, txSfMePcons, txSfMePconsNoSfm, 
			txSfCoState, txSfCoMode, txSfCoRdsCor, txSfCoKwhCost, 
			txSfStAct, txSfStAlarm, txSfLiSavings, txSfLiBoost, txSfLiCredits, 
			acGnGlDelay, acGnGlIterConf, acGnGlOperation, acGnGlPreselection, 
			acGnGlVSWRInhibit, acGnGlReserveControl, acGnGlCurrentMain, acGnGlLocalMode, acGnGlMainOpmode, acGnGlManSwLoc,
			acGnGlDelaySwitch, acGnGlDelayStart, acGnGlSwOnFault, acGnGlSwNoComm, 
			acGnAlFault, acGnAlSwitchOver, acGnAlInterlockAnt, acGnAlInterlockLoad, acGnMsIter, acGnMsPos, acGnMsSwitchLast, 
			acTx1GlLocalMode, acTx1AlFault, acTx1AlWarning, acTx1AlCom, acTx1RfRFPresent, acTx2GlLocalMode, 
			acTx2AlFault, acTx2AlWarning, acTx2AlCom, acTx2RfRFPresent, syGeType, syGeDate, 
			syGeTime, syGeName, syGeHardRel, syGeSoftRel, syGeDateCode, syGeContact, syGeUnit, 
			syGeSerial, syGeUptime, syGeOptList, syGeLocation, syGeDigMPX, syGeDigMPX2, syGeDigMPX3, syGeAOIPMpx, syAlWarning, syAlFault, 
			syAlAmb, syAlVoltAux, syAlRelay, syAlReserve, syAlInvalidData, syAl24v, eventTimeStampTxLocalMode, syAlComm, syAlLogging, syLossOfEth0, syLossOfEth1, 
			syGeTrapCounter, 
			maMoMaEffTrans, maMoMaEffPa, maMoMaEffPsu, maMoMaEffSys, maMoCcFault, maMoCcWarn, maMoCoMeAmb, maMoCoMeLoad1InputTemp, maMoCoMeLoad1HeatsinkTemp,
 			maMoCoMeLoad2InputTemp, maMoCoMeLoad2HeatsinkTemp, maMoCoMePressure, 
			maMoCoMeHeat1, maMoCoMeHeat2, maMoCoMePsuTemp, maMoCoMeIntTemp, maMoCoMeExcTemp, 
			maMoCoAlAmb, maMoCoAlLoad1Heatsink, maMoCoAlLoad2Heatsink, maMoCoAlPressure, 
			maMoCoAlHeat1, maMoCoAlHeat2, maMoCoAlTemp1, maMoCoAlTemp2, maMoCoAlPsuTemp, maMoCoAlIntTemp, maMoCoAlExcTemp, maMoAlSecPref, 
 			maMoAuMe5V, maMoAuMe12V, maMoAuMeN12V, maMoAuMe24V, maMoAuAlVoltAux, maMoAuAl24V,
 			maMoFanSpeed, maMoFanAlarms, 
			maMoMeVolt1, maMoMeVolt2, maMoMeCur1, maMoMeCur2, maMoMeCur3, maMoMeVolt3, maMoMePin, maMoAlVolt1, maMoAlVolt2, maMoAlCur1, maMoAlCur2, maMoAlCur3, maMoAlPin, 
			maDrCommunication, maDrFault, maDrWarning, maDrForwardPower, maDrReflectedPower, maDrHeatsink, maDrFanSpeed,
 			maPaCommunication, maPaFault, maPaWarning, maPaForwardPower, maPaReflectedPower, maPaEfficiency, maPaCurrent, maPaHeatMax,
			maPaAlrCur, maPaVoltage, maPaAlrVolt, maPaAmbTemp, maPaAlrHeat, maPaAlrTemp, 
 			maPsVoltageInput, maPsCurrentInput, maPsPowerInput, maPsVoltageOutput, maPsCurrentOutput, maPsPowerOutput, maPsCommunication, maPsFault,
 			maPsWarning, maPsEfficiency, maPsOutputPower, maPsInputPower, maPsMissing, maPsInputCurrent, maPsInputCurAlr, maPsInputVoltage, maPsInputVoltAlr,
			maPsOutputCurrent, maPsOutputCurAlr, maPsOutputVoltage, maPsOutputVoltAlr, maPsAmbTemp, maPsAmbAlr, maPsHeat1Temp, maPsHeat1Alr,
			maPsFan1Speed, maPsFan1Alr, maPsSerial, maPsSoftRel,
			syLiPrRds, syLiPrSoundProc, syLiPrSfm, syLiPrActivation, syLiPrAoipdecoder, syLiPrMpxoipdecoder, syLiPrSurestream, syLiPrSynchrostream, 
			syLiReRds, syLiReSoundProc, syLiReSfm, syLiReActivation, syLiReAoipdecoder, syLiReMpxoipdecoder, syLiReSurestream, syLiReSynchrostream, 
			syLiAlRds, syLiAlSoundProc, syLiAlSfm, syLiAlActivation, syLiAlAoipdecoder, syLiAlMpxoipdecoder, syLiAlSurestream, syLiAlSynchrostream, 
			eventTimeStampTxAl3dB, eventTimeStampTxAlFault, eventTimeStampTxAlWarning, eventTimeStampTxAlVSWR, eventTimeStampTxAlInterlockAnt, 
			eventTimeStampTxRfOpmode, eventTimeStampTxRfRFPresent, eventTimeStampAcReserveControl, eventTimeStampAcLocalMode, 
			eventTimeStampAcFault, eventTimeStampAcSwitchOver, eventTimeStampSysWarning, eventTimeStampSysFault, eventTimeStampSysAlAmb, 
			eventTimeStampSysAlVoltAux, eventTimeStampSysAlRelay, eventTimeStampSysAlReserve, eventTimeStampInSeAlrInputSwitch, 
			eventTimeStampTxAl1dB, eventTimeStampTxGnGlStandby, eventTimeStampInAlLine1, eventTimeStampInAlLine2, eventTimeStampInAlMpx1,
			eventTimeStampInAlMpx2, eventTimeStampInAlPlayer, eventTimeStampSysAlInvalidData, eventTimeStampAcGnAlInterlockAnt, 
			eventTimeStampAcGnAlInterlockLoad, eventTimeStampSysAl24v, eventTimeStampSysAlComm, eventTimeStampEquipmentOn, 
			eventEquipmentOnDownTime, eventTimeStampHeartBeat, eventTimeStampConfigChanged,  
			eventTimeStampInAlFault, eventTimeStampMoSfAlarm, eventTimeStampMoSfSwitch10MAlarm,
			eventTimeStampSyAlLogging, eventTimeStampInAlMpx3, eventTimeStampInAlMpx4, 
			eventTimeStampInAlAes1, eventTimeStampInAlAes2, eventTimeStampInAlAes3, eventTimeStampInAlAna1, 
			eventTimeStampTxSfStAct, eventTimeStampTxSfStAlarm, 
			eventTimeStampSyLiAlRds, eventTimeStampSyLiAlSoundProc, eventTimeStampSyLiAlSfm, eventTimeStampSyLiAlActivation, 
			eventTimeStampInAlAoip, eventTimeStampLossOfEth0, eventTimeStampLossOfEth1, 
			eventTimeStampSyLiAlAoipdecoder, eventTimeStampSyLiAlMpxoipdecoder, 
			eventTimeStampSyLiAlSurestream, eventTimeStampSyLiAlSynchrostream
		}
	STATUS current
	DESCRIPTION
		"All current objects"
	::= { groups 1 }

	objectObsoleteGroup OBJECT-GROUP
		OBJECTS {
			eventTxAlInterlockLoadPriority, eventTxAlInterlockLoadEnable, txGnAlInterlockLoad, eventTimeStampTxAlInterlockLoad,
			inSeThMpxTh, eventEquipmentFaultPriority, eventEquipmentFaultEnable, eventInAlFaultPriority, eventTimeStampEquipmentFault, 
			eventEquipmentFaultError, moSpAgState, moSpAgDrive, moSpAgAtt, 
			moSpAgRel, moSpAgThr, moSpAgMeas, moSpLimState, moSpLimVal, moSpLimDrive, moSpLimMeas, moSpLimPreset, 
			moMaMeVolt1, moMaMeVolt2, moMaMeCur1, moMaMeCur2, moMaMeEffSys, moMaMeEffTrans, moMaMePin, moMainAlVolt1, moMainAlVolt2, 
			moMainAlCur1, moMainAlCur2, moMainAlPin, moCoMeAmb, moCoMeHeat1, moCoMeHeat2, moCoMePsuTemp, moCoMeIntTemp, moCoMePressure, 
			moCoMeExcTemp, moCoAlHeat1, moCoAlHeat2, moCoAlTemp1,
			moCoAlTemp2, moCoAlPsuTemp, moCoAlIntTemp, moCoAlExcTemp, moCoAlPressure, 
			moAuMe5V, moAuMe12V, moAuMeN12V, moFanMeFan1Speed, moFanMeFan2Speed, moFanAlFan1Alarm, moFanAlFan2Alarm
		}
	STATUS obsolete
	DESCRIPTION
		"All obsolete objects"
	::= { groups 2 }

	eventGroup NOTIFICATION-GROUP
		NOTIFICATIONS {
			eventTxLocalMode, eventTxAl3dB, eventTxAlFault, eventTxAlWarning, eventTxAlVSWR, 
			eventTxAlInterlockAnt, eventTxRfOpmode, eventTxRfRFPresent, eventAcReserveControl, 
			eventAcLocalMode, eventAcFault, eventAcSwitchOver, eventSysWarning, eventSysFault, 
			eventSysAlAmb, eventSysAlVoltAux, eventSysAlRelay, eventSysAlReserve,  eventInSeAlrInputSwitch, 
			eventTxAl1dB, eventTxGnGlStandby, eventInAlLine1, eventInAlLine2, eventInAlMpx1, eventInAlMpx2, eventInAlPlayer, 
			eventInAlAes1, eventInAlAes2, eventInAlAes3, eventInAlAna1, 
			eventSysAlInvalidData, eventAcGnAlInterlockAnt, eventAcGnAlInterlockLoad, eventSysAl24v, eventSysAlComm,
			eventEquipmentOn, eventHeartBeat, eventConfigChanged, eventInAlFault, eventMoSfAlarm, 
			eventMoSfSwitch10MAlarm, eventSyAlLogging, eventLossOfEth0, eventLossOfEth1, eventInAlMpx3, eventInAlMpx4, 
			eventTxSfStAct, eventTxSfStAlarm, eventInAlAoip, 
			eventSyLiAlRds, eventSyLiAlSoundProc, eventSyLiAlSfm, eventSyLiAlActivation, 
			eventSyLiAlAoipdecoder, eventSyLiAlMpxoipdecoder, eventSyLiAlSurestream, eventSyLiAlSynchrostream
		}
	STATUS current
	DESCRIPTION
		"All current events"
	::= { groups 3 }

	eventObsoleteGroup NOTIFICATION-GROUP
		NOTIFICATIONS {
			eventTxAlInterlockLoad, eventEquipmentFault
		}
	STATUS obsolete
	DESCRIPTION
		"All obsolete events"
	::= { groups 4 }

END
