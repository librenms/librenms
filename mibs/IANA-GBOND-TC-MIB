IANA-GBOND-TC-MIB DEFINITIONS ::= BEGIN

  IMPORTS
    MODULE-IDENTITY,
    mib-2
      FROM SNMPv2-SMI
    TEXTUAL-CONVENTION
      FROM SNMPv2-TC
    ;
------------------------------------------------------------------------
   ianaGBondTcMIB MODULE-IDENTITY
    LAST-UPDATED "201706230000Z"  -- 23 June 2017
    ORGANIZATION "IANA"
    CONTACT-INFO "        Internet Assigned Numbers Authority

                    Postal: ICANN
                            12025 Waterfront Drive, Suite 300
                            Los Angeles, CA 90094-2536

                        Tel: +1-310-301-5800
                      EMail: iana&iana.org"

    DESCRIPTION
        "This MIB module defines IANAgBondScheme and IANAgBondSchemeList
        TEXTUAL-CONVENTIONs, specifying enumerated values of the
        gBondPortConfAdminScheme, gBondPortConfPeerAdminScheme,
        gBondPortStatOperScheme, gBondPortStatPeerOperScheme,
        gBondPortCapSchemesSupported, and gBondPortCapPeerSchemesSupported
        objects, respectively, as defined in the GBOND-MIB.

        It is intended that each new bonding scheme defined by the
        ITU-T Q4/SG15 working group and approved for publication in a
        revision of the ITU-T G.998 specification will be added to this
        MIB module, provided that it is suitable for being managed by the
        base objects in the GBOND-MIB.  An Expert Review, as defined in
        RFC 8126, is REQUIRED for such additions.

        The following references are used throughout this MIB module:

        [G.998.1] refers to:
          ITU-T Recommendation G.998.1: 'ATM-based multi-pair bonding',
          January 2005.

        [G.998.2] refers to:
          ITU-T Recommendation G.998.2: 'Ethernet-based multi-pair
          bonding', January 2005.

        [G.998.3] refers to:
          ITU-T Recommendation G.998.3: 'Multi-pair bonding using
          time-division inverse multiplexing', January 2005.

        Naming Conventions:
          BCE   - Bonding Channel Entity
          GBS   - Generic Bonding Sub-layer

        These references should be updated as appropriate when a new
        bonding scheme is added to this MIB module.

        Copyright (c) 2013 IETF Trust and the persons identified as
        authors of the code.  All rights reserved.

        Redistribution and use in source and binary forms, with or without
        modification, is permitted pursuant to, and subject to the license
        terms contained in, the Simplified BSD License set forth in
        Section 4.c of the IETF Trust's Legal Provisions Relating to IETF
        Documents (http://trustee.ietf.org/license-info)."

      REVISION    "201302200000Z"  -- 20 February 2013
      DESCRIPTION "Initial version, published as RFC 6765."

      ::= { mib-2 215 }

    -- Textual Conventions

    IANAgBondSchemeList ::= TEXTUAL-CONVENTION
      STATUS      current
      DESCRIPTION
        "This textual convention defines a bitmap of possible ITU-T
        G.998 (G.Bond) bonding schemes.  Currently, the following values
        are defined for the corresponding bonding schemes:
          g9981(1) - G.998.1 (G.Bond/ATM; see the G9981-MIB)
          g9982(2) - G.998.2 (G.Bond/Ethernet; see the G9982-MIB)
          g9983(3) - G.998.3 (G.Bond/TDIM; see the G9983-MIB)
        An additional value of none(0) can be returned as a result
        of a GET operation when a value of the object cannot be
        determined (for example, a peer GBS cannot be reached), the port
        does not support any kind of bonding, or when a single-BCE
        G.998.2 GBS supports bonding (frame fragmentation/reassembly)
        bypass."

      SYNTAX      BITS {
        none(0),
        g9981(1),
        g9982(2),
        g9983(3)
      }

    IANAgBondScheme ::= TEXTUAL-CONVENTION
      STATUS      current
      DESCRIPTION
        "This textual convention defines ITU-T G.998 bonding scheme
        values.  Possible values are:
          none(0)    - no bonding (e.g., on a single-BCE G.998.2 GBS)
                       or unknown
          g9981(1)   - G.998.1 (G.Bond/ATM)
          g9982(2)   - G.998.2 (G.Bond/Ethernet)
          g9983(3)   - G.998.3 (G.Bond/TDIM)"
      SYNTAX      INTEGER {
        none(0),
        g9981(1),
        g9982(2),
        g9983(3)
      }

END
