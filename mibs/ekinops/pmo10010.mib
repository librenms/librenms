-- *****************************************************************
-- EKINOPS-Pmo10010.TXT:  MIB
--
--MIB Part Number:3MI00039AAAA
--MIB Version:04
--
-- Copyright (c) 2016 by Ekinops
-- All rights reserved.
-- 
-- *****************************************************************

EKINOPS-Pmo10010-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePmo10010 MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201601120000Z"
	DESCRIPTION
	  "Creation for PMO10010 (OTN)"
	REVISION "201605200000Z"
	DESCRIPTION
	  "New AlarmType – synthesisAlarm (12)"
	REVISION "201606020000Z"
	DESCRIPTION
	  "Capabilities objects of Table 5"
        ::= { ekinops 76 }



--- *****************************************************
---     LEAF LEVEL 2
--- *****************************************************


pmo10010alarms OBJECT IDENTIFIER ::= { modulePmo10010 2 }	
pmo10010AlmOther OBJECT IDENTIFIER ::= { pmo10010alarms 1 }
pmo10010AlmOtherNurg OBJECT IDENTIFIER ::= { pmo10010AlmOther 1 }
pmo10010AlmOtherUrg OBJECT IDENTIFIER ::= { pmo10010AlmOther 2 }
pmo10010AlmOtherCrit OBJECT IDENTIFIER ::= { pmo10010AlmOther 3 }

pmo10010AlmClient OBJECT IDENTIFIER ::= { pmo10010alarms 2 }
pmo10010AlmClientNurg OBJECT IDENTIFIER ::= { pmo10010AlmClient 1 }
pmo10010AlmClientUrg OBJECT IDENTIFIER ::= { pmo10010AlmClient 2 }
pmo10010AlmClientCrit OBJECT IDENTIFIER ::= { pmo10010AlmClient 3 }
	
pmo10010AlmLine OBJECT IDENTIFIER ::= { pmo10010alarms 3 }
pmo10010AlmLineNurg OBJECT IDENTIFIER ::= { pmo10010AlmLine 1 }
pmo10010AlmLineUrg OBJECT IDENTIFIER ::= { pmo10010AlmLine 2 }
pmo10010AlmLineCrit OBJECT IDENTIFIER ::= { pmo10010AlmLine 3 }





pmo10010measures OBJECT IDENTIFIER ::= { modulePmo10010 3 }	
pmo10010MesrOther OBJECT IDENTIFIER ::= { pmo10010measures 1 }	
pmo10010MesrClient OBJECT IDENTIFIER ::= { pmo10010measures 2 }	
pmo10010MesrLine OBJECT IDENTIFIER ::= { pmo10010measures 3 }	




pmo10010counters OBJECT IDENTIFIER ::= { modulePmo10010 4 }
pmo10010CntOther OBJECT IDENTIFIER ::= { pmo10010counters 1 }
pmo10010CntClient OBJECT IDENTIFIER ::= { pmo10010counters 2 }
pmo10010CntLine OBJECT IDENTIFIER ::= { pmo10010counters 3 }


pmo10010controlsWrite OBJECT IDENTIFIER ::= { modulePmo10010 6 }
pmo10010CtrlOther OBJECT IDENTIFIER ::= { pmo10010controlsWrite 1 }
pmo10010CtrlClient OBJECT IDENTIFIER ::= { pmo10010controlsWrite 2 }
pmo10010CtrlLine OBJECT IDENTIFIER ::= { pmo10010controlsWrite 3 }

pmo10010ri OBJECT IDENTIFIER ::= { modulePmo10010 7 }
pmo10010riTable OBJECT IDENTIFIER ::= { pmo10010ri 1 }

pmo10010download OBJECT IDENTIFIER ::= { modulePmo10010 8 }
pmo10010DwlOther OBJECT IDENTIFIER ::= { pmo10010download 1 }
pmo10010DwlClient OBJECT IDENTIFIER ::= { pmo10010download 2 }
pmo10010DwlLine OBJECT IDENTIFIER ::= { pmo10010download 3 }


pmo10010Config OBJECT IDENTIFIER ::= { modulePmo10010 9 }

pmo10010traps OBJECT IDENTIFIER ::= { modulePmo10010 10 }



pmo10010Monitoring OBJECT IDENTIFIER ::= { modulePmo10010 11}

pmo10010MonOther OBJECT IDENTIFIER ::= { pmo10010Monitoring 1 }
pmo10010MonRmon OBJECT IDENTIFIER ::= { pmo10010MonOther 3 }

pmo10010MonClient OBJECT IDENTIFIER ::= { pmo10010Monitoring 2 }
pmo10010MonClientRmonCounter OBJECT IDENTIFIER ::= { pmo10010MonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pmo10010MultiRate ::= TEXTUAL-CONVENTION
    STATUS      current
    DESCRIPTION "different rate for a client port"
    SYNTAX INTEGER {
		rate100Mhz(0),
		rate250Mhz(1),
		rate500Mhz(2),
		rate1Ghz(3)
           }

Pmo10010OtxMode ::= TEXTUAL-CONVENTION
    STATUS      current
    DESCRIPTION "Different modes on OTX-TLH on client and line ports"
    SYNTAX INTEGER {
		otx80mode(1),
		otx60mode(2),
		otxadjustmode(4)
           }

Pmo10010OtxGrid ::= TEXTUAL-CONVENTION
    STATUS      current
    DESCRIPTION "Different grids on OTX-TLH on client and line ports"
    SYNTAX INTEGER {
		otxgrid200(200),
		otxgrid100(100),
		otxgrid50(50)
           }

Pmo10010AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pmo10010ClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pmo10010ProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pmo10010OtxChannel ::= TEXTUAL-CONVENTION
    STATUS      current
    DESCRIPTION "Channel selection on transceiver Tx line ports"
    SYNTAX INTEGER

Pmo10010OrxChannel ::= TEXTUAL-CONVENTION
    STATUS      current
    DESCRIPTION "Channel selection on transceiver Rx line ports"
    SYNTAX INTEGER


Pmo10010Odu2SapiMode ::= TEXTUAL-CONVENTION
    STATUS      current
    DESCRIPTION "Mode for SAPI-DAPI"
    SYNTAX INTEGER {
		off(0),
		sapi(1)
		dapi(2)
		sapidapi(3),
           }

Pmo10010Otu4SapiMode ::= TEXTUAL-CONVENTION
    STATUS      current
    DESCRIPTION "Mode for SAPI-DAPI"
    SYNTAX INTEGER {
		off(0),
		sapi(1)
		dapi(2)
		sapidapi(3),
           }


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmo10010RinvReloadInventory OBJECT-TYPE
  SYNTAX EkiOnOff
  MAX-ACCESS read-write
  STATUS current
  DESCRIPTION
        "Reload the inventory: This OID triggers an 
         inventory reload."
  ::= { pmo10010ri 2 }

pmo10010RinvHwPlatform OBJECT-TYPE
  SYNTAX DisplayString
  MAX-ACCESS read-only
  STATUS current
  DESCRIPTION
        "HW platform description: This OID contains the 
         description of the Hardware platform."
  ::= { pmo10010ri 3 }
  
pmo10010RinvModulePlatform OBJECT-TYPE
  SYNTAX DisplayString
  MAX-ACCESS read-only
  STATUS current
  DESCRIPTION
        "Module platform description: This OID contains the 
         description of the Module."
  ::= { pmo10010ri 4 }
  
pmo10010RinvSwPlatform OBJECT-TYPE
  SYNTAX DisplayString
  MAX-ACCESS read-only
  STATUS current
  DESCRIPTION
        "SW platform description: This OID contains the 
         description of the Software platform."
  ::= { pmo10010ri 5 }
  
pmo10010RinvGwPlatform OBJECT-TYPE
  SYNTAX DisplayString
  MAX-ACCESS read-only
  STATUS current
  DESCRIPTION
        "GW platform desciption: This OID contains the 
         description of the Gateware platform."
  ::= { pmo10010ri 6 }


pmo10010RinvSfpTable OBJECT-TYPE
      SYNTAX  SEQUENCE OF Pmo10010RinvSfpEntry
      MAX-ACCESS  not-accessible
      STATUS  current
      DESCRIPTION
              "List of the SFPs on the selected module"
      ::= { pmo10010riTable 1 }

pmo10010RinvSfpEntry OBJECT-TYPE
        SYNTAX  Pmo10010RinvSfpEntry
        MAX-ACCESS  not-accessible
        STATUS  current
        DESCRIPTION
              "Row definition for the SFP table"
        INDEX   { pmo10010RinvSfpIndex }
        ::= { pmo10010RinvSfpTable 1 }
    


Pmo10010RinvSfpEntry::=
        SEQUENCE {
          pmo10010RinvSfpIndex 
              Integer32,
          pmo10010Rinvsfp
              DisplayString
        }


    pmo10010RinvSfpIndex OBJECT-TYPE
        SYNTAX  Integer32(1..16)
        MAX-ACCESS  read-only
        STATUS  current
        DESCRIPTION
              "Index for SFP table"
        ::= { pmo10010RinvSfpEntry 1 }


    pmo10010Rinvsfp OBJECT-TYPE
        SYNTAX  DisplayString
        MAX-ACCESS  read-only
        STATUS  current
        DESCRIPTION
              "Inventory for the SFP: This OID contains the inventory for the SFP"
        ::= { pmo10010RinvSfpEntry 2 }




pmo10010RinvLineTable OBJECT-TYPE
      SYNTAX  SEQUENCE OF Pmo10010RinvLineEntry
      MAX-ACCESS  not-accessible
      STATUS  current
      DESCRIPTION
              "List of the XFPs on the selected module"
      ::= { pmo10010riTable 2 }

pmo10010RinvLineEntry OBJECT-TYPE
        SYNTAX  Pmo10010RinvLineEntry
        MAX-ACCESS  not-accessible
        STATUS  current
        DESCRIPTION
              "Row definition for the XFP table"
        INDEX   { pmo10010RinvLineIndex }
        ::= { pmo10010RinvLineTable 1 }
    


Pmo10010RinvLineEntry::=
        SEQUENCE {
          pmo10010RinvLineIndex 
              Integer32,
          pmo10010RinvxfpLine
              DisplayString
        }


    pmo10010RinvLineIndex OBJECT-TYPE
        SYNTAX  Integer32(1..16)
        MAX-ACCESS  read-only
        STATUS  current
        DESCRIPTION
              "Index for XFP table"
        ::= { pmo10010RinvLineEntry 1 }


    pmo10010RinvxfpLine OBJECT-TYPE
        SYNTAX  DisplayString
        MAX-ACCESS  read-only
        STATUS  current
        DESCRIPTION
              "Inventory for the XFP: This OID contains the inventory for the XFP"
        ::= { pmo10010RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmo10010AlmsynthAlm0 OBJECT IDENTIFIER ::= { pmo10010AlmOtherCrit 0 }




pmo10010AlmDefFuseB OBJECT-TYPE
	  SYNTAX EkiOnOff
	  MAX-ACCESS read-only
	  STATUS current
	  DESCRIPTION
        "
        Fuse B Fail :This OID indicates 
        that the fuse of the power input 
        B is in fail condition <Help> Status 
        of the Fuse B <Condtype> DEF_FUSE_B 
        <Probcause> powerProblem (36) <Alarmtype> 
        equipmentAlarm (5) <Polarity> (2) 
        "
	  ::= { pmo10010AlmsynthAlm0 16 }



pmo10010AlmDefFuseA OBJECT-TYPE
	  SYNTAX EkiOnOff
	  MAX-ACCESS read-only
	  STATUS current
	  DESCRIPTION
        "
        Fuse A Fail :This OID indicates 
        that the fuse of the power input 
        A is in fail condition <Help> Status 
        of the Fuse A <Condtype> DEF_FUSE_A 
        <Probcause> powerProblem (36) <Alarmtype> 
        equipmentAlarm (5) <Polarity> (2) 
        "
	  ::= { pmo10010AlmsynthAlm0 15 }



pmo10010AlmModGlobFail OBJECT-TYPE
	  SYNTAX EkiOnOff
	  MAX-ACCESS read-only
	  STATUS current
	  DESCRIPTION
        "
        Module Failure :This OID is set 
        on detection of a failure originating 
        from the RM <Help> This alarm is 
        set on detection of a failure originating 
        from the equipment <Condtype> MOD_GLOB_FAIL 
        <Probcause> other (1) <Alarmtype> 
        synthesisAlarm (12)  <Polarity> 
        (2) 
        "
	  ::= { pmo10010AlmsynthAlm0 9 }



pmo10010AlmFailFan OBJECT-TYPE
	  SYNTAX EkiOnOff
	  MAX-ACCESS read-only
	  STATUS current
	  DESCRIPTION
        "
        Fan Fail :This OID is at 1 when 
        any fail occurs on the fan tray 
        <Help> This alarm indicates that 
        the Fan tray module is in a failure 
        condition <Condtype> FAIL_FAN <Probcause> 
        equipmentMalfunction (16) <Alarmtype> 
        equipmentAlarm (5) <Polarity> (2) 
        "
	  ::= { pmo10010AlmsynthAlm0 2 }



--- *****************************************************
---     LEAF for the synthAlm2 article
--- *****************************************************
pmo10010AlmsynthAlm2 OBJECT IDENTIFIER ::= { pmo10010AlmOtherNurg 2 }




pmo10010AlmMaintenanceOn OBJECT-TYPE
	  SYNTAX EkiOnOff
	  MAX-ACCESS read-only
	  STATUS current
	  DESCRIPTION
        "
        Maintenance Mode :This OID indicates 
        that the RM is in maintenance mode. 
        <Help> This alarm indicates that 
        the maintenance mode is enabled 
        on the PM <Condtype> MAINTENANCE_ON 
        <Probcause> informationalStatus(1000) 
        <Alarmtype> other (1) <Polarity> 
        (2) 
        "
	  ::= { pmo10010AlmsynthAlm2 5 }



pmo10010AlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> informationalStatus(1000) 
        <Alarmtype> other (1) <Polarity> 
        (2) 
        "
	  ::= { pmo10010AlmsynthAlm2 4 }



pmo10010AlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> informationalStatus(1000) 
        <Alarmtype> other (1) <Polarity> 
        (2) 
        "
	  ::= { pmo10010AlmsynthAlm2 3 }



pmo10010AlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> informationalStatus(1000) 
        <Alarmtype> other (1) <Polarity> 
        (2) 
        "
	  ::= { pmo10010AlmsynthAlm2 2 }



pmo10010AlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> informationalStatus(1000) 
        <Alarmtype> other (1) <Polarity> 
        (2) 
        "
	  ::= { pmo10010AlmsynthAlm2 1 }



--- *********************************************************
---     TABLE for the pmo10010AlmsynthAlmPort articles
--- *********************************************************

pmo10010AlmsynthAlmPortTable OBJECT-TYPE
	SYNTAX  SEQUENCE OF Pmo10010AlmsynthAlmPortEntry
	MAX-ACCESS not-accessible
	STATUS current
	DESCRIPTION
        "
        List of pmo10010AlmsynthAlmPort 
        Article
        "
	::= { pmo10010AlmClientCrit 8 }


pmo10010AlmsynthAlmPortEntry OBJECT-TYPE
	SYNTAX Pmo10010AlmsynthAlmPortEntry
	MAX-ACCESS not-accessible
	STATUS current
	DESCRIPTION
        "
        Row definition for the pmo10010AlmsynthAlmPort 
        table
        "
	INDEX   { pmo10010AlmsynthAlmPortIndex }
	::= { pmo10010AlmsynthAlmPortTable 1 }


Pmo10010AlmsynthAlmPortEntry ::=
	SEQUENCE {
	pmo10010AlmsynthAlmPortIndex
		INTEGER,
	pmo10010AlmUpCsfPortn
		EkiOnOff,
	pmo10010AlmFailAccPortn
		EkiOnOff,
	pmo10010AlmSfpDdmAlmPortn
		EkiOnOff,
	pmo10010AlmSfpDdmWarningPortn
		EkiOnOff,
	pmo10010AlmDwCaisPortn
		EkiOnOff,
	pmo10010AlmClientRemoteOosPortn
		EkiOnOff,
	pmo10010AlmClientLocalOosPortn
		EkiOnOff,
	pmo10010AlmDwLsdPortn
		EkiOnOff,
	pmo10010AlmHwFailAccPortn
		EkiOnOff,
	pmo10010AlmDdmAbsentPortn
		EkiOnOff,
	pmo10010AlmSfpAbsentPortn
		EkiOnOff
	}


pmo10010AlmsynthAlmPortIndex OBJECT-TYPE
	SYNTAX  INTEGER(0..128)
	MAX-ACCESS  read-only
	STATUS current
	DESCRIPTION
        "
        Index definition for the pmo10010AlmsynthAlmPort 
        table
        "
	::= { pmo10010AlmsynthAlmPortEntry 1 }


pmo10010AlmUpCsfPortn OBJECT-TYPE
	SYNTAX  EkiOnOff
	MAX-ACCESS read-only
	STATUS current
	DESCRIPTION
        "
        Client Signal Fail Inserted :This 
        OID indicates a CSF has been inserted 
        in the upstream client port. <Help> 
        This status indicates if a Client 
        Signal Fail is currently inserted 
        on the line signal for this client 
        port <Condtype> UP_CSF_1 <Probcause> 
        informationalStatus(1000) <Alarmtype> 
        other (1) <Polarity> (2) 
        "
	::= { pmo10010AlmsynthAlmPortEntry 17 }


pmo10010AlmFailAccPortn OBJECT-TYPE
	SYNTAX  EkiOnOff
	MAX-ACCESS read-only
	STATUS current
	DESCRIPTION
        "
        Client Access Fail :This OID indicates 
        a failure on the Client port <Help> 
        This alarm indicates a failure
         on the Client port <Condtype>
         FAIL_ACC_1 <Probcause> equipmentMalfunction 
        (16) <Alarmtype> synthesisAlarm 
        (12)  <Polarity> (2) 
        "
	::= { pmo10010AlmsynthAlmPortEntry 13 }


pmo10010AlmSfpDdmAlmPortn OBJECT-TYPE
	SYNTAX  EkiOnOff
	MAX-ACCESS read-only
	STATUS current
	DESCRIPTION
        "
        Alarm On Client Trscv DDM :This 
        OID indicates an alarm is being 
        received from the Client Transceiver 
        DDM <Help> This alarm indicates 
        if a DDM Alarm has been detected 
        on the client transceiver <Condtype> 
        SFP_DDM_ALM_1 <Probcause> inputOutputDeviceError 
        (24) <Alarmtype> synthesisAlarm 
        (12)  <Polarity> (2) 
        "
	::= { pmo10010AlmsynthAlmPortEntry 11 }


pmo10010AlmSfpDdmWarningPortn OBJECT-TYPE
	SYNTAX  EkiOnOff
	MAX-ACCESS read-only
	STATUS current
	DESCRIPTION
        "
        Warning On Client Trscv DDM :This 
        OID indicates a warning is being 
        received from the Client Transceiver 
        DDM <Help> This alarm indicates 
        if a DDM Warning has been detected 
        on the client transceiver <Condtype> 
        SFP_DDM_WARNING_1 <Probcause> inputOutputDeviceError 
        (24) <Alarmtype> synthesisAlarm 
        (12)  <Polarity> (2) 
        "
	::= { pmo10010AlmsynthAlmPortEntry 10 }


pmo10010AlmDwCaisPortn OBJECT-TYPE
	SYNTAX  EkiOnOff
	MAX-ACCESS read-only
	STATUS current
	DESCRIPTION
        "
        Client AIS Inserted :This OID
         indicates a CAIS has been inserted 
        on the output client port. <Help> 
        This status indicates if a Client 
        Alarm Indication Signal is currently 
        inserted on the client interface 
        <Condtype> DW_CAIS_1 <Probcause> 
        informationalStatus(1000) <Alarmtype> 
        other (1) <Polarity> (2) 
        "
	::= { pmo10010AlmsynthAlmPortEntry 9 }


pmo10010AlmClientRemoteOosPortn OBJECT-TYPE
	SYNTAX  EkiOnOff
	MAX-ACCESS read-only
	STATUS current
	DESCRIPTION
        "
        Remote Client Port In Service
         :This OID indicates that the remote 
        Client port is In Service (1) or 
        Out of Service (2) <Help> This
         status indicates if the remote 
        client port is in service <Condtype> 
        CLIENT_REMOTE_OOS <Probcause> informationalStatus(1000) 
        <Alarmtype> other (1) <Polarity> 
        (2) 
        "
	::= { pmo10010AlmsynthAlmPortEntry 8 }


pmo10010AlmClientLocalOosPortn OBJECT-TYPE
	SYNTAX  EkiOnOff
	MAX-ACCESS read-only
	STATUS current
	DESCRIPTION
        "
        Local Client Port In Service :This 
        OID indicates that the local Client 
        port is In Service (1) or Out of 
        Service (2) <Help> This status
         indicates if the local client
         port is in service <Condtype>
         CLIENT_LOCAL_OOS <Probcause> informationalStatus(1000) 
        <Alarmtype> other (1) <Polarity> 
        (2) 
        "
	::= { pmo10010AlmsynthAlmPortEntry 7 }


pmo10010AlmDwLsdPortn OBJECT-TYPE
	SYNTAX  EkiOnOff
	MAX-ACCESS read-only
	STATUS current
	DESCRIPTION
        "
        Client Trscv Laser Shutdown :This 
        OID indicates the Client transceiver 
        laser is shutdown <Help> This status 
        indicates if the client transceiver 
        laser is shutdown <Condtype> DW_LSD_1 
        <Probcause> other (1) <Alarmtype> 
        equipmentAlarm (5) <Polarity> (2) 
        "
	::= { pmo10010AlmsynthAlmPortEntry 6 }


pmo10010AlmHwFailAccPortn OBJECT-TYPE
	SYNTAX  EkiOnOff
	MAX-ACCESS read-only
	STATUS current
	DESCRIPTION
        "
        Client HW Fail :This OID indicates 
        a failure on client port, most
         probably caused by a HW issue. 
        <Help> This alarm indicates a failure 
        on client port, most probably caused 
        by a HW issue. <Condtype> HW_FAIL_ACC_1 
        <Probcause> equipmentMalfunction 
        (16) <Alarmtype> synthesisAlarm 
        (12)  <Polarity> (2) 
        "
	::= { pmo10010AlmsynthAlmPortEntry 5 }


pmo10010AlmDdmAbsentPortn OBJECT-TYPE
	SYNTAX  EkiOnOff
	MAX-ACCESS read-only
	STATUS current
	DESCRIPTION
        "
        DDM Supported On Client Trscv
         :This OID indicates that the Client 
        transceiver supports the Digital 
        Diagnostic Monitoring function
         <Help> This status indicates if 
        the client transceiver includes 
        the DDM feature <Condtype> DDM_ABSENT_1 
        <Probcause> informationalStatus(1000) 
        <Alarmtype> other (1) <Polarity> 
        (2) 
        "
	::= { pmo10010AlmsynthAlmPortEntry 3 }


pmo10010AlmSfpAbsentPortn OBJECT-TYPE
	SYNTAX  EkiOnOff
	MAX-ACCESS read-only
	STATUS current
	DESCRIPTION
        "
        Client Optical Module Absent :This 
        OID indicates that the Transceiver 
        is not present in the client port. 
        <Help> This alarm indicates if
         the client transceiver is not
         plugged <Condtype> SFP_ABSENT_1 
        <Probcause> inputOutputDeviceError 
        (24) <Alarmtype> equipmentAlarm 
        (5) <Polarity> (2) <Event> ObjectCDINV
        "
	::= { pmo10010AlmsynthAlmPortEntry 2 }


--- *********************************************************
---     TABLE for the pmo10010AlmsynthAlmLine articles
--- *********************************************************

pmo10010AlmsynthAlmLineTable OBJECT-TYPE
	SYNTAX  SEQUENCE OF Pmo10010AlmsynthAlmLineEntry
	MAX-ACCESS not-accessible
	STATUS current
	DESCRIPTION
        "
        List of pmo10010AlmsynthAlmLine 
        Article
        "
	::= { pmo10010AlmLineCrit 24 }


pmo10010AlmsynthAlmLineEntry OBJECT-TYPE
	SYNTAX Pmo10010AlmsynthAlmLineEntry
	MAX-ACCESS not-accessible
	STATUS current
	DESCRIPTION
        "
        Row definition for the pmo10010AlmsynthAlmLine 
        table
        "
	INDEX   { pmo10010AlmsynthAlmLineIndex }
	::= { pmo10010AlmsynthAlmLineTable 1 }


Pmo10010AlmsynthAlmLineEntry ::=
	SEQUENCE {
	pmo10010AlmsynthAlmLineIndex
		INTEGER,
	pmo10010AlmLineActivePortn
		EkiOnOff,
	pmo10010AlmLineFailPortn
		EkiOnOff,
	pmo10010AlmLineDdmAlmPortn
		EkiOnOff,
	pmo10010AlmLineDdmWarningPortn
		EkiOnOff,
	pmo10010AlmUpRdiInsPortn
		EkiOnOff,
	pmo10010AlmLineLocalOosPortn
		EkiOnOff,
	pmo10010AlmXfpTxOffPortn
		EkiOnOff,
	pmo10010AlmLineHwFailPortn
		EkiOnOff,
	pmo10010AlmXfpInitNotComplPortn
		EkiOnOff,
	pmo10010AlmXfpAbsentPortn
		EkiOnOff
	}


pmo10010AlmsynthAlmLineIndex OBJECT-TYPE
	SYNTAX  INTEGER(0..128)
	MAX-ACCESS  read-only
	STATUS current
	DESCRIPTION
        "
        Index definition for the pmo10010AlmsynthAlmLine 
        table
        "
	::= { pmo10010AlmsynthAlmLineEntry 1 }


pmo10010AlmLineActivePortn OBJECT-TYPE
	SYNTAX  EkiOnOff
	MAX-ACCESS read-only
	STATUS current
	DESCRIPTION
        "
        Line Active :This OID indicates 
        whether the line is active or standby. 
        <Help> This status indicates whether 
        the line is active or standby.
         <Condtype> LINE_ACTIVE <Probcause> 
        informationalStatus(1000) <Alarmtype> 
        other (1) <Polarity> (2) 
        "
	::= { pmo10010AlmsynthAlmLineEntry 17 }


pmo10010AlmLineFailPortn OBJECT-TYPE
	SYNTAX  EkiOnOff
	MAX-ACCESS read-only
	STATUS current
	DESCRIPTION
        "
        Line Port Failure :This OID indicates 
        a failure on the line port <Help> 
        This alarm indicates a failure
         on the line port <Condtype> LINE_FAIL 
        <Probcause> equipmentMalfunction 
        (16) <Alarmtype> synthesisAlarm 
        (12)  <Polarity> (2) 
        "
	::= { pmo10010AlmsynthAlmLineEntry 13 }


pmo10010AlmLineDdmAlmPortn OBJECT-TYPE
	SYNTAX  EkiOnOff
	MAX-ACCESS read-only
	STATUS current
	DESCRIPTION
        "
        Alarm On Line Optical Module DDM 
        :This OID indicates an alarm is 
        present coming out of Line transceiver 
        DDM <Help> This alarm indicates 
        if a DDM Alarm has been detected 
        on the line transceiver <Condtype> 
        LINE_DDM_ALM <Probcause> inputOutputDeviceError 
        (24) <Alarmtype> synthesisAlarm 
        (12)  <Polarity> (2) 
        "
	::= { pmo10010AlmsynthAlmLineEntry 11 }


pmo10010AlmLineDdmWarningPortn OBJECT-TYPE
	SYNTAX  EkiOnOff
	MAX-ACCESS read-only
	STATUS current
	DESCRIPTION
        "
        Warning On Line Optical Module 
        DDM :This OID indicates a warning 
        is present coming out of Line transceiver 
        DDM <Help> This alarm indicates 
        if a DDM Warning has been detected 
        on the line transceiver <Condtype> 
        LINE_DDM_WARNING <Probcause> inputOutputDeviceError 
        (24) <Alarmtype> synthesisAlarm 
        (12)  <Polarity> (2) 
        "
	::= { pmo10010AlmsynthAlmLineEntry 10 }


pmo10010AlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal. <Help> This status indicates 
        if a MS-RDI/L-RDI is currently
         inserted on the line interface. 
        <Condtype> UP_RDI_INS <Probcause> 
        informationalStatus(1000) <Alarmtype> 
        other (1) <Polarity> (2) 
        "
	::= { pmo10010AlmsynthAlmLineEntry 9 }


pmo10010AlmLineLocalOosPortn OBJECT-TYPE
	SYNTAX  EkiOnOff
	MAX-ACCESS read-only
	STATUS current
	DESCRIPTION
        "
        Line Port In Service :This OID 
        indicates that the Line port is 
        In Service (1) of Out or Service 
        (2) <Help> This status indicates 
        if the line port is in service
         <Condtype> LINE_LOCAL_OOS <Probcause> 
        informationalStatus(1000) <Alarmtype> 
        other (1) <Polarity> (2) 
        "
	::= { pmo10010AlmsynthAlmLineEntry 7 }


pmo10010AlmXfpTxOffPortn OBJECT-TYPE
	SYNTAX  EkiOnOff
	MAX-ACCESS read-only
	STATUS current
	DESCRIPTION
        "
        Line Trscv Laser Shutdown :This 
        OID indicates the Line transceiver 
        laser is shutdown <Help> This status 
        indicates if the Line transceiver 
        laser is shutdown <Condtype> XFP_TX_OFF 
        <Probcause> other (1) <Alarmtype> 
        equipmentAlarm (5) <Polarity> (2) 
        "
	::= { pmo10010AlmsynthAlmLineEntry 6 }


pmo10010AlmLineHwFailPortn OBJECT-TYPE
	SYNTAX  EkiOnOff
	MAX-ACCESS read-only
	STATUS current
	DESCRIPTION
        "
        Line Port HW Failure :This OID 
        indicates a failure on line port, 
        most probably caused by a HW issue 
        <Help> This alarm indicates a failure 
        on line port, most probably caused 
        by a HW issue <Condtype> LINE_HW_FAIL 
        <Probcause> equipmentMalfunction 
        (16) <Alarmtype> synthesisAlarm 
        (12)  <Polarity> (2) 
        "
	::= { pmo10010AlmsynthAlmLineEntry 5 }


pmo10010AlmXfpInitNotComplPortn OBJECT-TYPE
	SYNTAX  EkiOnOff
	MAX-ACCESS read-only
	STATUS current
	DESCRIPTION
        "
        Line Optical Module Ready :This 
        OID indicates that the optical
         interface is not operational.
         <Help> This status indicates if 
        the line transceiver has been correctly 
        initialized <Condtype> XFP_INIT_NOT_COMPL 
        <Probcause> equipmentMalfunction 
        (16) <Alarmtype> equipmentAlarm 
        (5) <Polarity> (2) <Event> ObjectCDINV
        "
	::= { pmo10010AlmsynthAlmLineEntry 3 }


pmo10010AlmXfpAbsentPortn OBJECT-TYPE
	SYNTAX  EkiOnOff
	MAX-ACCESS read-only
	STATUS current
	DESCRIPTION
        "
        Line Optical Module Absent :This 
        OID indicates that the line optical 
        interface is not present. <Help> 
        This alarm indicates if the line 
        transceiver is not plugged <Condtype> 
        XFP_ABSENT <Probcause> inputOutputDeviceError 
        (24) <Alarmtype> equipmentAlarm 
        (5) <Polarity> (2)  <Event> ObjectCDINV
        "
	::= { pmo10010AlmsynthAlmLineEntry 2 }


--- *****************************************************
---     LEAF for the clientModuleState article
--- *****************************************************
pmo10010AlmclientModuleState OBJECT IDENTIFIER ::= { pmo10010AlmOtherCrit 40 }




pmo10010AlmCfpHighPowerDown OBJECT-TYPE
	  SYNTAX EkiOnOff
	  MAX-ACCESS read-only
	  STATUS current
	  DESCRIPTION
        "
        Client Trscv High Power Down :This 
        OID indicates the Client Trscv
         is entering Low Power state <Help> 
        Status indicating the Client Trscv 
        is entering Low Power state <Condtype> 
        CFP_HIGH_POWER_DOWN <Probcause> 
        informationalStatus(1000) <Alarmtype> 
        other (1) <Polarity> (2) 
        "
	  ::= { pmo10010AlmclientModuleState 9 }



pmo10010AlmCfpTxTurnOff OBJECT-TYPE
	  SYNTAX EkiOnOff
	  MAX-ACCESS read-only
	  STATUS current
	  DESCRIPTION
        "
        Client Trscv Laser Turn Off :This 
        OID indicates the Client Trscv
         is turning off its laser <Help> 
        Status indicating the Client Trscv 
        is turning off its laser <Condtype> 
        CFP_TX_TURN_OFF <Probcause> informationalStatus(1000) 
        <Alarmtype> other (1) <Polarity> 
        (2) 
        "
	  ::= { pmo10010AlmclientModuleState 8 }



pmo10010AlmCfpFault OBJECT-TYPE
	  SYNTAX EkiOnOff
	  MAX-ACCESS read-only
	  STATUS current
	  DESCRIPTION
        "
        Client Trscv Fault :This OID indicates 
        the Client Trscv is in Fault state 
        <Help> Status indicating the Client 
        Trscv is in Fault state <Condtype> 
        CFP_FAULT <Probcause> informationalStatus(1000) 
        <Alarmtype> other (1) <Polarity> 
        (2) 
        "
	  ::= { pmo10010AlmclientModuleState 7 }



pmo10010AlmCfpReady OBJECT-TYPE
	  SYNTAX EkiOnOff
	  MAX-ACCESS read-only
	  STATUS current
	  DESCRIPTION
        "
        Client Trscv Ready :This OID indicates 
        the Client Trscv is ready to operate 
        <Help> Status indicating the Client 
        Trscv is ready to operate <Condtype> 
        CFP_READY <Probcause> informationalStatus(1000) 
        <Alarmtype> other (1) <Polarity> 
        (2) 
        "
	  ::= { pmo10010AlmclientModuleState 6 }



pmo10010AlmCfpTxTurnOn OBJECT-TYPE
	  SYNTAX EkiOnOff
	  MAX-ACCESS read-only
	  STATUS current
	  DESCRIPTION
        "
        Client Trscv Laser Turn On :This 
        OID indicates the Client Trscv
         is turning on its laser <Help> 
        Status indicating the Client Trscv 
        is turning on its laser <Condtype> 
        CFP_TX_TURN_ON <Probcause> informationalStatus(1000) 
        <Alarmtype> other (1) <Polarity> 
        (2) 
        "
	  ::= { pmo10010AlmclientModuleState 5 }



pmo10010AlmCfpTxOff OBJECT-TYPE
	  SYNTAX EkiOnOff
	  MAX-ACCESS read-only
	  STATUS current
	  DESCRIPTION
        "
        Client Trscv Laser Shutdown :This 
        OID indicates the Client Trscv
         Laser is OFF <Help> Status indicating 
        the Client Trscv Laser is OFF <Condtype> 
        CFP_TX_OFF <Probcause> informationalStatus(1000) 
        <Alarmtype> other (1) <Polarity> 
        (2) 
        "
	  ::= { pmo10010AlmclientModuleState 4 }



pmo10010AlmCfpHighPowerUp OBJECT-TYPE
	  SYNTAX EkiOnOff
	  MAX-ACCESS read-only
	  STATUS current
	  DESCRIPTION
        "
        Client Trscv High Power Up :This 
        OID indicates the Client Trscv
         is leaving Low Power state <Help> 
        Status indicating the Client Trscv 
        is leaving Low Power state <Condtype> 
        CFP_HIGH_POWER_UP <Probcause> informationalStatus(1000) 
        <Alarmtype> other (1) <Polarity> 
        (2) 
        "
	  ::= { pmo10010AlmclientModuleState 3 }



pmo10010AlmCfpLowPower OBJECT-TYPE
	  SYNTAX EkiOnOff
	  MAX-ACCESS read-only
	  STATUS current
	  DESCRIPTION
        "
        Client Trscv Low Power :This OID 
        indicates the Client Trscv is in 
        low power state <Help> Status indicating 
        the Client Trscv is in low power 
        state <Condtype> CFP_LOW_POWER
         <Probcause> informationalStatus(1000) 
        <Alarmtype> other (1) <Polarity> 
        (2) 
        "
	  ::= { pmo10010AlmclientModuleState 2 }



pmo10010AlmCfpInitialize OBJECT-TYPE
	  SYNTAX EkiOnOff
	  MAX-ACCESS read-only
	  STATUS current
	  DESCRIPTION
        "
        Client Trscv Initialize :This
         OID indicates the Client Trscv 
        initialization is in progress <Help> 
        Status indicating the Client Trscv 
        initialization is in progress <Condtype> 
        CFP_INITIALIZE <Probcause> informationalStatus(1000) 
        <Alarmtype> other (1) <Polarity> 
        (2) 
        "
	  ::= { pmo10010AlmclientModuleState 1 }



--- *****************************************************
---     LEAF for the clientModuleGeneralStatus article
--- *****************************************************
pmo10010AlmclientModuleGeneralStatus OBJECT IDENTIFIER ::= { pmo10010AlmOtherCrit 41 }




pmo10010AlmCfpHwInterlock OBJECT-TYPE
	  SYNTAX EkiOnOff
	  MAX-ACCESS read-only
	  STATUS current
	  DESCRIPTION
        "
        Client Trscv Hardware Interlock 
        :This OID indicates the Client
         Trscv power is higher than the 
        cooling capacity <Help> Alarm indicating 
        the Client Trscv power is higher 
        than the cooling capacity <Condtype> 
        CFP_HW_INTERLOCK <Probcause> temperatureUnacceptable 
        (51) <Alarmtype> equipmentAlarm 
        (5) <Polarity> (2) 
        "
	  ::= { pmo10010AlmclientModuleGeneralStatus 14 }



pmo10010AlmCfpLossOfRefclk OBJECT-TYPE
	  SYNTAX EkiOnOff
	  MAX-ACCESS read-only
	  STATUS current
	  DESCRIPTION
        "
        Client Trscv Loss Of Ref Clock 
        :This OID indicates a Loss of Reference 
        clock is detected on the Client 
        Trscv <Help> Alarm indicating a 
        Loss of Reference clock is detected 
        on the Client Trscv <Condtype>
         CFP_LOSS_OF_REFCLK <Probcause> 
        inputOutputDeviceError (24) <Alarmtype> 
        equipmentAlarm (5) <Polarity> (2) 
        "
	  ::= { pmo10010AlmclientModuleGeneralStatus 11 }



pmo10010AlmCfpTxJitterPllLol OBJECT-TYPE
	  SYNTAX EkiOnOff
	  MAX-ACCESS read-only
	  STATUS current
	  DESCRIPTION
        "
        Client Trscv Tx Jitter PLL Loss 
        Of Lock :This OID indicates a Tx 
        Jitter PLL Loss of Lock is dtected 
        on the Client Trscv <Help> Alarm 
        indicating a Tx Jitter PLL Loss 
        of Lock is dtected on the Client 
        Trscv <Condtype> CFP_TX_JITTER_PLL_LOL 
        <Probcause> inputOutputDeviceError 
        (24) <Alarmtype> equipmentAlarm 
        (5) <Polarity> (2) 
        "
	  ::= { pmo10010AlmclientModuleGeneralStatus 10 }



pmo10010AlmCfpTxCmuLol OBJECT-TYPE
	  SYNTAX EkiOnOff
	  MAX-ACCESS read-only
	  STATUS current
	  DESCRIPTION
        "
        Client Trscv CMU Loss Of Lock
         :This OID indicates a Clock Multiplier 
        Unit Loss of Lock is detected on 
        the Client Trscv <Help> Alarm indicating 
        a Clock Multiplier Unit Loss of 
        Lock is detected on the Client
         Trscv <Condtype> CFP_TX_CMU_LOL 
        <Probcause> inputOutputDeviceError 
        (24) <Alarmtype> equipmentAlarm 
        (5) <Polarity> (2) 
        "
	  ::= { pmo10010AlmclientModuleGeneralStatus 9 }



pmo10010AlmCfpTxLosf OBJECT-TYPE
	  SYNTAX EkiOnOff
	  MAX-ACCESS read-only
	  STATUS current
	  DESCRIPTION
        "
        Client Trscv Loss Of Signal Functionality 
        :This OID indicates a Loss of Signal 
        functionality is detected on the 
        Client Trscv <Help> Alarm indicating 
        a Loss of Signal functionality
         is detected on the Client Trscv 
        <Condtype> CFP_TX_LOSF <Probcause> 
        lossOfSignal (30) <Alarmtype> equipmentAlarm 
        (5) <Polarity> (2) 
        "
	  ::= { pmo10010AlmclientModuleGeneralStatus 8 }



pmo10010AlmCfpTxHostLol OBJECT-TYPE
	  SYNTAX EkiOnOff
	  MAX-ACCESS read-only
	  STATUS current
	  DESCRIPTION
        "
        Client Trscv Tx Host Loss Of Lock 
        :This OID indicates of Loss of
         Lock is detected on the Client 
        Trscv Tx Host interface <Help>
         Alarm indicating of Loss of Lock 
        is detected on the Client Trscv 
        Tx Host interface <Condtype> CFP_TX_HOST_LOL 
        <Probcause> receiverFailure (42) 
        <Alarmtype> equipmentAlarm (5)
         <Polarity> (2) 
        "
	  ::= { pmo10010AlmclientModuleGeneralStatus 7 }



pmo10010AlmCfpRxLos OBJECT-TYPE
	  SYNTAX EkiOnOff
	  MAX-ACCESS read-only
	  STATUS current
	  DESCRIPTION
        "
        Client Trscv Loss Of Signal :This 
        OID indicates a Loss of Signal
         is detected on the Client Trscv 
        <Help> Alarm indicating a Loss
         of Signal is detected on the Client 
        Trscv <Condtype> CFP_RX_LOS <Probcause> 
        lossOfSignal (30) <Alarmtype> equipmentAlarm 
        (5) <Polarity> (2) 
        "
	  ::= { pmo10010AlmclientModuleGeneralStatus 6 }



pmo10010AlmCfpRxNetworkLol OBJECT-TYPE
	  SYNTAX EkiOnOff
	  MAX-ACCESS read-only
	  STATUS current
	  DESCRIPTION
        "
        Client Trscv Rx Network Loss Of 
        Lock :This OID indicates of Loss 
        of Lock is dected on the Client 
        Trscv Rx Network interface <Help> 
        Alarm indicating of Loss of Lock 
        is dected on the Client Trscv Rx 
        Network interface <Condtype> CFP_RX_NETWORK_LOL 
        <Probcause> receiverFailure (42) 
        <Alarmtype> equipmentAlarm (5)
         <Polarity> (2) 
        "
	  ::= { pmo10010AlmclientModuleGeneralStatus 5 }



pmo10010AlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating 
        an Out of alignment on the Client 
        Trscv Host Interface <Condtype> 
        CFP_OUT_OF_ALIGNMENT <Probcause> 
        receiverFailure (42) <Alarmtype> 
        equipmentAlarm (5) <Polarity> (2) 
        "
	  ::= { pmo10010AlmclientModuleGeneralStatus 4 }



--- *****************************************************
---     LEAF for the clientGlobalAlarmSummary article
--- *****************************************************
pmo10010AlmclientGlobalAlarmSummary OBJECT IDENTIFIER ::= { pmo10010AlmOtherCrit 42 }




pmo10010AlmCfpGlobAlarmAssertion  OBJECT-TYPE
	  SYNTAX EkiOnOff
	  MAX-ACCESS read-only
	  STATUS current
	  DESCRIPTION
        "
        Client Trscv Global Alarm :This 
        OID indicates at least one  Fault 
        or Status is detected on the Client 
        Trscv module <Help> Synthesis alarm 
        indicating at least one Alarm,
         Warning, Fault or Status is detected 
        on the Client Trscv module <Condtype> 
        CFP_GLOB_ALARM_ASSERTION  <Probcause> 
        informationalStatus(1000) <Alarmtype> 
        other (1) <Polarity> (2) 
        "
	  ::= { pmo10010AlmclientGlobalAlarmSummary 16 }



pmo10010AlmCfpHostLaneFaultStatus  OBJECT-TYPE
	  SYNTAX EkiOnOff
	  MAX-ACCESS read-only
	  STATUS current
	  DESCRIPTION
        "
        Client Trscv Host Fault And Status 
        :This OID indicates at least one 
        Fault or Status is detected on
         the Client Trscv Host Interface 
        <Help> Synthesis alarm indicating 
        at least one Fault or Status is 
        detected on the Client Trscv Host 
        Interface <Condtype> CFP_HOST_LANE_FAULT_STATUS 
         <Probcause> informationalStatus(1000) 
        <Alarmtype> other (1) <Polarity> 
        (2) 
        "
	  ::= { pmo10010AlmclientGlobalAlarmSummary 15 }



pmo10010AlmCfpNetworkLaneFaultStatus  OBJECT-TYPE
	  SYNTAX EkiOnOff
	  MAX-ACCESS read-only
	  STATUS current
	  DESCRIPTION
        "
        Client Trscv Network Fault And 
        Status :This OID indicates at least 
        one Fault or Status is detected 
        on the Client Trscv Network Interface 
        <Help> Synthesis alarm indicating 
        at least one Fault or Status is 
        detected on the Client Trscv Network 
        Interface <Condtype> CFP_NETWORK_LANE_FAULT_STATUS 
         <Probcause> informationalStatus(1000) 
        <Alarmtype> other (1) <Polarity> 
        (2) 
        "
	  ::= { pmo10010AlmclientGlobalAlarmSummary 14 }



pmo10010AlmCfpNetworkLaneAlarmWarning1 OBJECT-TYPE
	  SYNTAX EkiOnOff
	  MAX-ACCESS read-only
	  STATUS current
	  DESCRIPTION
        "
        Client Trscv Network Alarm And 
        Warning 1 :This OID indicates at 
        least one DDM  is detected on the 
        Client Trscv Network Interface
         <Help> Synthesis alarm indicating 
        at least one DDM Alarm or DDM Warning 
        is detected on the Client Trscv 
        Network Interface <Condtype> CFP_NETWORK_LANE_ALARM_WARNING_1 
        <Probcause> informationalStatus(1000) 
        <Alarmtype> other (1) <Polarity> 
        (2) 
        "
	  ::= { pmo10010AlmclientGlobalAlarmSummary 13 }



pmo10010AlmCfpModuleAlarmWarning2 OBJECT-TYPE
	  SYNTAX EkiOnOff
	  MAX-ACCESS read-only
	  STATUS current
	  DESCRIPTION
        "
        Client Trscv Module Alarm And
         Warning 2 :This OID indicates
         at least one DDM is detected on 
        the Client Trscv module <Help>
         Synthesis alarm indicating at
         least one DDM Alarm or DDM Warning 
        is detected on the Client Trscv 
        module <Condtype> CFP_MODULE_ALARM_WARNING_2 
        <Probcause> informationalStatus(1000) 
        <Alarmtype> other (1) <Polarity> 
        (2) 
        "
	  ::= { pmo10010AlmclientGlobalAlarmSummary 12 }



pmo10010AlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module 
        <Help> Synthesis alarm indicating 
        at least one DDM Alarm or DDM Warning 
        is detected on the Client Trscv 
        module <Condtype> CFP_MODULE_ALARM_WARNING_1 
         <Probcause> informationalStatus(1000) 
        <Alarmtype> other (1) <Polarity> 
        (2) 
        "
	  ::= { pmo10010AlmclientGlobalAlarmSummary 11 }



pmo10010AlmCfpModuleFault  OBJECT-TYPE
	  SYNTAX EkiOnOff
	  MAX-ACCESS read-only
	  STATUS current
	  DESCRIPTION
        "
        Client Trscv Module Fault :This 
        OID indicates at least one Fault 
        is detected on the Client Trscv 
        module <Help> Synthesis alarm indicating 
        at least one Fault is detected
         on the Client Trscv module <Condtype> 
        CFP_MODULE_FAULT  <Probcause> informationalStatus(1000) 
        <Alarmtype> other (1) <Polarity> 
        (2) 
        "
	  ::= { pmo10010AlmclientGlobalAlarmSummary 10 }



pmo10010AlmCfpModuleGeneralStatus  OBJECT-TYPE
	  SYNTAX EkiOnOff
	  MAX-ACCESS read-only
	  STATUS current
	  DESCRIPTION
        "
        Client Trscv General Status :This 
        OID indicates the Client Trscv
         module general status <Help> Synthesis 
        alarm indicating the Client Trscv 
        module general status <Condtype> 
        CFP_MODULE_GENERAL_STATUS  <Probcause> 
        informationalStatus(1000) <Alarmtype> 
        other (1) <Polarity> (2) 
        "
	  ::= { pmo10010AlmclientGlobalAlarmSummary 9 }



pmo10010AlmCfpModuleState  OBJECT-TYPE
	  SYNTAX EkiOnOff
	  MAX-ACCESS read-only
	  STATUS current
	  DESCRIPTION
        "
        Client Trscv Module State :This 
        OID indicates the Client Trscv
         module state <Help> Synthesis
         alarm indicating the Client Trscv 
        module state <Condtype> CFP_MODULE_STATE 
         <Probcause> informationalStatus(1000) 
        <Alarmtype> other (1) <Polarity> 
        (2) 
        "
	  ::= { pmo10010AlmclientGlobalAlarmSummary 8 }



pmo10010AlmCfpNetworkLaneAlarmWarning2 OBJECT-TYPE
	  SYNTAX EkiOnOff
	  MAX-ACCESS read-only
	  STATUS current
	  DESCRIPTION
        "
        Client Trscv Network Alarm And 
        Warning 2 :This OID indicates at 
        least one DDM is detected on the 
        Client Trscv Network Interface
         <Help> Synthesis alarm indicating 
        at least one DDM Alarm or DDM Warning 
        is detected on the Client Trscv 
        Network Interface <Condtype> CFP_NETWORK_LANE_ALARM_WARNING_2 
        <Probcause> informationalStatus(1000) 
        <Alarmtype> other (1) <Polarity> 
        (2) 
        "
	  ::= { pmo10010AlmclientGlobalAlarmSummary 7 }



pmo10010AlmCfpSoftGlobAlarmTest  OBJECT-TYPE
	  SYNTAX EkiOnOff
	  MAX-ACCESS read-only
	  STATUS current
	  DESCRIPTION
        "
        Client Trscv Global Alarm SW Test 
        :This OID indicates the Client
         Trscv Global Alarm This OID is 
        raised by SW request for test purpose 
        <Help> Status indicating the Client 
        Trscv Global Alarm is raised by 
        SW request for test purpose <Condtype> 
        CFP_SOFT_GLOB_ALARM_TEST  <Probcause> 
        informationalStatus(1000) <Alarmtype> 
        other (1) <Polarity> (2) 
        "
	  ::= { pmo10010AlmclientGlobalAlarmSummary 1 }



--- *****************************************************
---     LEAF for the msaModuleState article
--- *****************************************************
pmo10010AlmmsaModuleState OBJECT IDENTIFIER ::= { pmo10010AlmOtherCrit 46 }




pmo10010AlmMsaHighPowerDown OBJECT-TYPE
	  SYNTAX EkiOnOff
	  MAX-ACCESS read-only
	  STATUS current
	  DESCRIPTION
        "
        Line Trscv High Power Down :This 
        OID indicates the Line Trscv is 
        entering Low Power state <Help> 
        Status indicating the Line Trscv 
        is entering Low Power state <Condtype> 
        MSA_HIGH_POWER_DOWN <Probcause> 
        informationalStatus(1000) <Alarmtype> 
        other (1) <Polarity> (2) 
        "
	  ::= { pmo10010AlmmsaModuleState 9 }



pmo10010AlmMsaTxTurnOff OBJECT-TYPE
	  SYNTAX EkiOnOff
	  MAX-ACCESS read-only
	  STATUS current
	  DESCRIPTION
        "
        Line Trscv Laser Turn Off :This 
        OID indicates the Line Trscv is 
        turning off its laser <Help> Status 
        indicating the Line Trscv is turning 
        off its laser <Condtype> MSA_TX_TURN_OFF 
        <Probcause> informationalStatus(1000) 
        <Alarmtype> other (1) <Polarity> 
        (2) 
        "
	  ::= { pmo10010AlmmsaModuleState 8 }



pmo10010AlmMsaFault OBJECT-TYPE
	  SYNTAX EkiOnOff
	  MAX-ACCESS read-only
	  STATUS current
	  DESCRIPTION
        "
        Line Trscv Fault :This OID indicates 
        the Line Trscv is in Fault state 
        <Help> Status indicating the Line 
        Trscv is in Fault state <Condtype> 
        MSA_FAULT <Probcause> informationalStatus(1000) 
        <Alarmtype> other (1) <Polarity> 
        (2) 
        "
	  ::= { pmo10010AlmmsaModuleState 7 }



pmo10010AlmMsaReady OBJECT-TYPE
	  SYNTAX EkiOnOff
	  MAX-ACCESS read-only
	  STATUS current
	  DESCRIPTION
        "
        Line Trscv Ready :This OID indicates 
        the Line Trscv is ready to operate 
        <Help> Status indicating the Line 
        Trscv is ready to operate <Condtype> 
        MSA_READY <Probcause> informationalStatus(1000) 
        <Alarmtype> other (1) <Polarity> 
        (2) 
        "
	  ::= { pmo10010AlmmsaModuleState 6 }



pmo10010AlmMsaTxTurnOn OBJECT-TYPE
	  SYNTAX EkiOnOff
	  MAX-ACCESS read-only
	  STATUS current
	  DESCRIPTION
        "
        Line Trscv Laser Turn On :This 
        OID indicates the Line Trscv is 
        turning on its laser <Help> Status 
        indicating the Line Trscv is turning 
        on its laser <Condtype> MSA_TX_TURN_ON 
        <Probcause> informationalStatus(1000) 
        <Alarmtype> other (1) <Polarity> 
        (2) 
        "
	  ::= { pmo10010AlmmsaModuleState 5 }



pmo10010AlmMsaTxOff OBJECT-TYPE
	  SYNTAX EkiOnOff
	  MAX-ACCESS read-only
	  STATUS current
	  DESCRIPTION
        "
        Line Trscv Laser Shutdown :This 
        OID indicates the Line Trscv Laser 
        is OFF <Help> Status indicating 
        the Line Trscv Laser is OFF <Condtype> 
        MSA_TX_OFF <Probcause> informationalStatus(1000) 
        <Alarmtype> other (1) <Polarity> 
        (2) 
        "
	  ::= { pmo10010AlmmsaModuleState 4 }



pmo10010AlmMsaHighPowerUp OBJECT-TYPE
	  SYNTAX EkiOnOff
	  MAX-ACCESS read-only
	  STATUS current
	  DESCRIPTION
        "
        Line Trscv High Power Up :This 
        OID indicates the Line Trscv is 
        leaving Low Power state <Help>
         Status indicating the Line Trscv 
        is leaving Low Power state <Condtype> 
        MSA_HIGH_POWER_UP <Probcause> informationalStatus(1000) 
        <Alarmtype> other (1) <Polarity> 
        (2) 
        "
	  ::= { pmo10010AlmmsaModuleState 3 }



pmo10010AlmMsaLowPower OBJECT-TYPE
	  SYNTAX EkiOnOff
	  MAX-ACCESS read-only
	  STATUS current
	  DESCRIPTION
        "
        Line Trscv Low Power :This OID 
        indicates the Line Trscv is in
         low power state <Help> Status
         indicating the Line Trscv is in 
        low power state <Condtype> MSA_LOW_POWER 
        <Probcause> informationalStatus(1000) 
        <Alarmtype> other (1) <Polarity> 
        (2) 
        "
	  ::= { pmo10010AlmmsaModuleState 2 }



pmo10010AlmMsaInitialize OBJECT-TYPE
	  SYNTAX EkiOnOff
	  MAX-ACCESS read-only
	  STATUS current
	  DESCRIPTION
        "
        Line Trscv Initialize :This OID 
        indicates the Line Trscv initialization 
        is in progress <Help> Status indicating 
        the Line Trscv initialization is 
        in progress <Condtype> MSA_INITIALIZE 
        <Probcause> informationalStatus(1000) 
        <Alarmtype> other (1) <Polarity> 
        (2) 
        "
	  ::= { pmo10010AlmmsaModuleState 1 }



--- *****************************************************
---     LEAF for the msaModuleGeneralStatus article
--- *****************************************************
pmo10010AlmmsaModuleGeneralStatus OBJECT IDENTIFIER ::= { pmo10010AlmOtherCrit 47 }




pmo10010AlmMsaHwInterlock OBJECT-TYPE
	  SYNTAX EkiOnOff
	  MAX-ACCESS read-only
	  STATUS current
	  DESCRIPTION
        "
        Line Trscv Hardware Interlock
         :This OID indicates the Line Trscv 
        power is higher than the cooling 
        capacity <Help> Alarm indicating 
        the Line Trscv power is higher
         than the cooling capacity <Condtype> 
        MSA_HW_INTERLOCK <Probcause> temperatureUnacceptable 
        (51) <Alarmtype> equipmentAlarm 
        (5) <Polarity> (2) 
        "
	  ::= { pmo10010AlmmsaModuleGeneralStatus 14 }



pmo10010AlmMsaLossOfRefclk OBJECT-TYPE
	  SYNTAX EkiOnOff
	  MAX-ACCESS read-only
	  STATUS current
	  DESCRIPTION
        "
        Line Trscv Loss Of Ref Clock :This 
        OID indicates a Loss of Reference 
        clock is detected on the Line Trscv 
        <Help> Alarm indicating a Loss
         of Reference clock is detected 
        on the Line Trscv <Condtype> MSA_LOSS_OF_REFCLK 
        <Probcause> inputOutputDeviceError 
        (24) <Alarmtype> equipmentAlarm 
        (5) <Polarity> (2) 
        "
	  ::= { pmo10010AlmmsaModuleGeneralStatus 11 }



pmo10010AlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help> 
        Alarm indicating a Tx Jitter PLL 
        Loss of Lock is detected on the 
        Line Trscv <Condtype> MSA_TX_JITTER_PLL_LOL 
        <Probcause> inputOutputDeviceError 
        (24) <Alarmtype> equipmentAlarm 
        (5) <Polarity> (2) 
        "
	  ::= { pmo10010AlmmsaModuleGeneralStatus 10 }



pmo10010AlmMsaTxCmuLol OBJECT-TYPE
	  SYNTAX EkiOnOff
	  MAX-ACCESS read-only
	  STATUS current
	  DESCRIPTION
        "
        Line Trscv CMU Loss Of Lock :This 
        OID indicates a Clock Multiplier 
        Unit Loss of Lock is detected on 
        the Line Trscv <Help> Alarm indicating 
        a Clock Multiplier Unit Loss of 
        Lock is detected on the Line Trscv 
        <Condtype> MSA_TX_CMU_LOL <Probcause> 
        inputOutputDeviceError (24) <Alarmtype> 
        equipmentAlarm (5) <Polarity> (2) 
        "
	  ::= { pmo10010AlmmsaModuleGeneralStatus 9 }



pmo10010AlmMsaTxLosf OBJECT-TYPE
	  SYNTAX EkiOnOff
	  MAX-ACCESS read-only
	  STATUS current
	  DESCRIPTION
        "
        Line Trscv Loss Of Signal Functionality 
        :This OID indicates a Loss of Signal 
        functionality is detected on the 
        Line Trscv <Help> Alarm indicating 
        a Loss of Signal functionality
         is detected on the Line Trscv
         <Condtype> MSA_TX_LOSF <Probcause> 
        lossOfSignal (30) <Alarmtype> equipmentAlarm 
        (5) <Polarity> (2) 
        "
	  ::= { pmo10010AlmmsaModuleGeneralStatus 8 }



pmo10010AlmMsaTxHostLol OBJECT-TYPE
	  SYNTAX EkiOnOff
	  MAX-ACCESS read-only
	  STATUS current
	  DESCRIPTION
        "
        Line Trscv Tx Host Loss Of Lock 
        :This OID indicates of Loss of
         Lock is detected on the Line Trscv 
        Tx Host interface <Help> Alarm
         indicating of Loss of Lock is
         detected on the Line Trscv Tx
         Host interface <Condtype> MSA_TX_HOST_LOL 
        <Probcause> receiverFailure (42) 
        <Alarmtype> equipmentAlarm (5)
         <Polarity> (2) 
        "
	  ::= { pmo10010AlmmsaModuleGeneralStatus 7 }



pmo10010AlmMsaRxLos OBJECT-TYPE
	  SYNTAX EkiOnOff
	  MAX-ACCESS read-only
	  STATUS current
	  DESCRIPTION
        "
        Line Trscv Loss Of Signal :This 
        OID indicates a Loss of Signal
         is detected on the Line Trscv
         <Help> Alarm indicating a Loss 
        of Signal is detected on the Line 
        Trscv <Condtype> MSA_RX_LOS <Probcause> 
        lossOfSignal (30) <Alarmtype> equipmentAlarm 
        (5) <Polarity> (2) 
        "
	  ::= { pmo10010AlmmsaModuleGeneralStatus 6 }



pmo10010AlmMsaRxNetworkLol OBJECT-TYPE
	  SYNTAX EkiOnOff
	  MAX-ACCESS read-only
	  STATUS current
	  DESCRIPTION
        "
        Line Trscv Rx Network Loss Of
         Lock :This OID indicates of Loss 
        of Lock is detected on the Line 
        Trscv Rx Network interface <Help> 
        Alarm indicating of Loss of Lock 
        is detected on the Line Trscv Rx 
        Network interface <Condtype> MSA_RX_NETWORK_LOL 
        <Probcause> receiverFailure (42) 
        <Alarmtype> equipmentAlarm (5)
         <Polarity> (2) 
        "
	  ::= { pmo10010AlmmsaModuleGeneralStatus 5 }



pmo10010AlmMsaOutOfAlignment OBJECT-TYPE
	  SYNTAX EkiOnOff
	  MAX-ACCESS read-only
	  STATUS current
	  DESCRIPTION
        "
        Line Trscv Out Of Alignment :This 
        OID indicates an Out of alignment 
        on the Line Trscv Host Interface 
        <Help> Alarm indicating an Out
         of alignment on the Line Trscv 
        Host Interface <Condtype> MSA_OUT_OF_ALIGNMENT 
        <Probcause> receiverFailure (42) 
        <Alarmtype> equipmentAlarm (5)
         <Polarity> (2) 
        "
	  ::= { pmo10010AlmmsaModuleGeneralStatus 4 }



--- *****************************************************
---     LEAF for the msaGlobalAlarmSummary article
--- *****************************************************
pmo10010AlmmsaGlobalAlarmSummary OBJECT IDENTIFIER ::= { pmo10010AlmOtherCrit 48 }




pmo10010AlmMsaGlobAlarmAssertion  OBJECT-TYPE
	  SYNTAX EkiOnOff
	  MAX-ACCESS read-only
	  STATUS current
	  DESCRIPTION
        "
        Line Trscv Global Alarm :This
         OID indicates at least one Fault 
        or Status is detected on the Line 
        Trscv module <Help> Synthesis alarm 
        indicating at least one Alarm,
         Warning, Fault or Status is detected 
        on the Line Trscv module <Condtype> 
        MSA_GLOB_ALARM_ASSERTION  <Probcause> 
        informationalStatus(1000) <Alarmtype> 
        other (1) <Polarity> (2) 
        "
	  ::= { pmo10010AlmmsaGlobalAlarmSummary 16 }



pmo10010AlmMsaHostLaneFaultStatus  OBJECT-TYPE
	  SYNTAX EkiOnOff
	  MAX-ACCESS read-only
	  STATUS current
	  DESCRIPTION
        "
        Line Trscv Host Fault And Status 
        :This OID indicates at least one 
        Fault or Status is detected on
         the Line Trscv Host Interface
         <Help> Synthesis alarm indicating 
        at least one Fault or Status is 
        detected on the Line Trscv Host 
        Interface <Condtype> MSA_HOST_LANE_FAULT_STATUS 
         <Probcause> informationalStatus(1000) 
        <Alarmtype> other (1) <Polarity> 
        (2) 
        "
	  ::= { pmo10010AlmmsaGlobalAlarmSummary 15 }



pmo10010AlmMsaNetworkLaneFaultStatus  OBJECT-TYPE
	  SYNTAX EkiOnOff
	  MAX-ACCESS read-only
	  STATUS current
	  DESCRIPTION
        "
        Line Trscv Network Fault And Status 
        :This OID indicates at least one 
        Fault or Status is detected on
         the Line Trscv Network Interface 
        <Help> Synthesis alarm indicating 
        at least one Fault or Status is 
        detected on the Line Trscv Network 
        Interface <Condtype> MSA_NETWORK_LANE_FAULT_STATUS 
         <Probcause> informationalStatus(1000) 
        <Alarmtype> other (1) <Polarity> 
        (2) 
        "
	  ::= { pmo10010AlmmsaGlobalAlarmSummary 14 }



pmo10010AlmMsaNetworkLaneAlarmWarning1 OBJECT-TYPE
	  SYNTAX EkiOnOff
	  MAX-ACCESS read-only
	  STATUS current
	  DESCRIPTION
        "
        Line Trscv Network Alarm And Warning 
        1 :This OID indicates at least
         one DDM is detected on the Line 
        Trscv Network Interface <Help>
         Synthesis alarm indicating at
         least one DDM Alarm or DDM Warning 
        is detected on the Line Trscv Network 
        Interface <Condtype> MSA_NETWORK_LANE_ALARM_WARNING_1 
        <Probcause> informationalStatus(1000) 
        <Alarmtype> other (1) <Polarity> 
        (2) 
        "
	  ::= { pmo10010AlmmsaGlobalAlarmSummary 13 }



pmo10010AlmMsaModuleAlarmWarning2 OBJECT-TYPE
	  SYNTAX EkiOnOff
	  MAX-ACCESS read-only
	  STATUS current
	  DESCRIPTION
        "
        Line Trscv Module Alarm And Warning 
        2 :This OID indicates at least
         one DDM is detected on the Line 
        Trscv module <Help> Synthesis alarm 
        indicating at least one DDM Alarm 
        or DDM Warning is detected on the 
        Line Trscv module <Condtype> MSA_MODULE_ALARM_WARNING_2 
        <Probcause> informationalStatus(1000) 
        <Alarmtype> other (1) <Polarity> 
        (2) 
        "
	  ::= { pmo10010AlmmsaGlobalAlarmSummary 12 }



pmo10010AlmMsaModuleAlarmWarning1  OBJECT-TYPE
	  SYNTAX EkiOnOff
	  MAX-ACCESS read-only
	  STATUS current
	  DESCRIPTION
        "
        Line Trscv Module Alarm And Warning 
        1 :This OID indicates at least
         one DDM is detected on the Line 
        Trscv module <Help> Synthesis alarm 
        indicating at least one DDM Alarm 
        or DDM Warning is detected on the 
        Line Trscv module <Condtype> MSA_MODULE_ALARM_WARNING_1 
         <Probcause> informationalStatus(1000) 
        <Alarmtype> other (1) <Polarity> 
        (2) 
        "
	  ::= { pmo10010AlmmsaGlobalAlarmSummary 11 }



pmo10010AlmModuleFault  OBJECT-TYPE
	  SYNTAX EkiOnOff
	  MAX-ACCESS read-only
	  STATUS current
	  DESCRIPTION
        "
        Line Trscv Module Fault :This
         OID indicates at least one Fault 
        is detected on the Line Trscv module 
        <Help> Synthesis alarm indicating 
        at least one Fault is detected
         on the Line Trscv module <Condtype> 
        MODULE_FAULT  <Probcause> informationalStatus(1000) 
        <Alarmtype> other (1) <Polarity> 
        (2) 
        "
	  ::= { pmo10010AlmmsaGlobalAlarmSummary 10 }



pmo10010AlmMsaModuleGeneralStatus  OBJECT-TYPE
	  SYNTAX EkiOnOff
	  MAX-ACCESS read-only
	  STATUS current
	  DESCRIPTION
        "
        Line Trscv General Status :This 
        OID indicates the Line Trscv module 
        general <Help> Synthesis alarm
         indicating the Line Trscv module 
        general status <Condtype> MSA_MODULE_GENERAL_STATUS 
         <Probcause> informationalStatus(1000) 
        <Alarmtype> other (1) <Polarity> 
        (2) 
        "
	  ::= { pmo10010AlmmsaGlobalAlarmSummary 9 }



pmo10010AlmMsaModuleState  OBJECT-TYPE
	  SYNTAX EkiOnOff
	  MAX-ACCESS read-only
	  STATUS current
	  DESCRIPTION
        "
        Line Trscv Module State :This
         OID indicates the Line Trscv module 
        state <Help> Synthesis alarm indicating 
        the Line Trscv module state <Condtype> 
        MSA_MODULE_STATE  <Probcause> informationalStatus(1000) 
        <Alarmtype> other (1) <Polarity> 
        (2) 
        "
	  ::= { pmo10010AlmmsaGlobalAlarmSummary 8 }



pmo10010AlmMsaNetworkLaneAlarmWarning2 OBJECT-TYPE
	  SYNTAX EkiOnOff
	  MAX-ACCESS read-only
	  STATUS current
	  DESCRIPTION
        "
        Line Trscv Network Alarm And Warning 
        2 :This OID indicates at least
         one DDM This OID is detected on 
        the Line Trscv Network Interface 
        <Help> Synthesis alarm indicating 
        at least one DDM Alarm or DDM Warning 
        is detected on the Line Trscv Network 
        Interface <Condtype> MSA_NETWORK_LANE_ALARM_WARNING_2 
        <Probcause> informationalStatus(1000) 
        <Alarmtype> other (1) <Polarity> 
        (2) 
        "
	  ::= { pmo10010AlmmsaGlobalAlarmSummary 7 }



pmo10010AlmMsaNetworkHostAlarmStatus OBJECT-TYPE
	  SYNTAX EkiOnOff
	  MAX-ACCESS read-only
	  STATUS current
	  DESCRIPTION
        "
        Line Trscv Network/Host Alarm
         Status :This OID indicates the 
        state of the Network and Host interface 
        of the Line Trscv <Help> Synthesis 
        alarm indicating the alarm state 
        of the Network and Host interface 
        of the Line Trscv <Condtype> MSA_NETWORK_HOST_ALARM_STATUS 
        <Probcause> informationalStatus(1000) 
        <Alarmtype> other (1) <Polarity> 
        (2) 
        "
	  ::= { pmo10010AlmmsaGlobalAlarmSummary 6 }



pmo10010AlmMsaSoftGlobAlarmTest  OBJECT-TYPE
	  SYNTAX EkiOnOff
	  MAX-ACCESS read-only
	  STATUS current
	  DESCRIPTION
        "
        Line Trscv Global Alarm SW Test 
        :This OID indicates the Line Trscv 
        Global alarm This OID is raised 
        by SW request for test purpose
         <Help> Status indicating the Line 
        Trscv Global Alarm is raised by 
        SW request for test purpose <Condtype> 
        MSA_SOFT_GLOB_ALARM_TEST  <Probcause> 
        informationalStatus(1000) <Alarmtype> 
        other (1) <Polarity> (2) 
        "
	  ::= { pmo10010AlmmsaGlobalAlarmSummary 1 }



--- *****************************************************
---     LEAF for the msaNetworkTxAlignment article
--- *****************************************************
pmo10010AlmmsaNetworkTxAlignment OBJECT IDENTIFIER ::= { pmo10010AlmOtherCrit 49 }




pmo10010AlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected 
        on the Line Trscv Network interface 
        <Help> Alarm indicating a Tx Loss 
        of Alignment is detected on the 
        Line Trscv Network interface <Condtype> 
        NET_TX_LOSS_OF_ALIGNMENT <Probcause> 
        transmitterFailure (56) <Alarmtype> 
        equipmentAlarm (5) <Polarity> (2) 
        "
	  ::= { pmo10010AlmmsaNetworkTxAlignment 16 }



pmo10010AlmNetTxOutOfAlignment OBJECT-TYPE
	  SYNTAX EkiOnOff
	  MAX-ACCESS read-only
	  STATUS current
	  DESCRIPTION
        "
        Line Trscv Network Tx Out Of Alignment 
        :This OID indicates a Tx Out of 
        Alignment is detected on the Line 
        Trscv Network interface <Help>
         Alarm indicating a Tx Out of Alignment 
        is detected on the Line Trscv Network 
        interface <Condtype> NET_TX_OUT_OF_ALIGNMENT 
        <Probcause> transmitterFailure
         (56) <Alarmtype> equipmentAlarm 
        (5) <Polarity> (2) 
        "
	  ::= { pmo10010AlmmsaNetworkTxAlignment 15 }



pmo10010AlmNetTxCmuLockFault OBJECT-TYPE
	  SYNTAX EkiOnOff
	  MAX-ACCESS read-only
	  STATUS current
	  DESCRIPTION
        "
        Line Trscv Network Tx CMU Lock 
        Fault :This OID indicates a Tx
         Clock Multiplier Unit Lock Fault 
        is detected on the Line Trscv Network 
        interface <Help> Alarm indicating 
        a Tx Clock Multiplier Unit Lock 
        Fault is detected on the Line Trscv 
        Network interface <Condtype> NET_TX_CMU_LOCK_FAULT 
        <Probcause> transmitterFailure
         (56) <Alarmtype> equipmentAlarm 
        (5) <Polarity> (2) 
        "
	  ::= { pmo10010AlmmsaNetworkTxAlignment 14 }



pmo10010AlmNetTxReferenceClockFault OBJECT-TYPE
	  SYNTAX EkiOnOff
	  MAX-ACCESS read-only
	  STATUS current
	  DESCRIPTION
        "
        Line Trscv Network Tx Ref Clock 
        Fault :This OID indicates a Tx
         Reference Clock Fault is detected 
        on the Line Trscv Network interface 
        <Help> Alarm indicating a Tx Reference 
        Clock Fault is detected on the
         Line Trscv Network interface <Condtype> 
        NET_TX_REFERENCE_CLOCK_FAULT <Probcause> 
        transmitterFailure (56) <Alarmtype> 
        equipmentAlarm (5) <Polarity> (2) 
        "
	  ::= { pmo10010AlmmsaNetworkTxAlignment 13 }



pmo10010AlmNetTxTimingFault OBJECT-TYPE
	  SYNTAX EkiOnOff
	  MAX-ACCESS read-only
	  STATUS current
	  DESCRIPTION
        "
        Line Trscv Network Tx Timing Fault 
        :This OID indicates a Tx Timing 
        Fault is detected on the Line Trscv 
        Network interface <Help> Alarm
         indicating a Tx Timing Fault is 
        detected on the Line Trscv Network 
        interface <Condtype> NET_TX_TIMING_FAULT 
        <Probcause> transmitterFailure
         (56) <Alarmtype> equipmentAlarm 
        (5) <Polarity> (2) 
        "
	  ::= { pmo10010AlmmsaNetworkTxAlignment 12 }



--- *****************************************************
---     LEAF for the msaNetworkRxAlignment article
--- *****************************************************
pmo10010AlmmsaNetworkRxAlignment OBJECT IDENTIFIER ::= { pmo10010AlmOtherCrit 50 }




pmo10010AlmNetRxModemSyncDetectFault OBJECT-TYPE
	  SYNTAX EkiOnOff
	  MAX-ACCESS read-only
	  STATUS current
	  DESCRIPTION
        "
        Line Trscv Network Rx Modem Sync 
        Detect Fault :This OID indicates 
        a Rx Modem Synchronisation Detection 
        Fault is detected on the Line Trscv 
        Network interface <Help> Alarm
         indicating a Rx Modem Synchronisation 
        Detection Fault is detected on
         the Line Trscv Network interface 
        <Condtype> NET_RX_MODEM_SYNC_DETECT_FAULT 
        <Probcause> receiverFailure (42) 
        <Alarmtype> equipmentAlarm (5)
         <Polarity> (2) 
        "
	  ::= { pmo10010AlmmsaNetworkRxAlignment 16 }



pmo10010AlmNetRxModemLockFault OBJECT-TYPE
	  SYNTAX EkiOnOff
	  MAX-ACCESS read-only
	  STATUS current
	  DESCRIPTION
        "
        Line Trscv Network Rx Modem Lock 
        Fault :This OID indicates a Rx
         Modem Lock Fault is detected on 
        the Line Trscv Network interface 
        <Help> Alarm indicating a Rx Modem 
        Lock Fault is detected on the Line 
        Trscv Network interface <Condtype> 
        NET_RX_MODEM_LOCK_FAULT <Probcause> 
        receiverFailure (42) <Alarmtype> 
        equipmentAlarm (5) <Polarity> (2) 
        "
	  ::= { pmo10010AlmmsaNetworkRxAlignment 15 }



pmo10010AlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected 
        on the Line Trscv Network interface 
        <Help> Alarm indicating a Rx Loss 
        of Alignment is detected on the 
        Line Trscv Network interface <Condtype> 
        NET_RX_LOSS_OF_ALIGNMENT <Probcause> 
        receiverFailure (42) <Alarmtype> 
        equipmentAlarm (5) <Polarity> (2) 
        "
	  ::= { pmo10010AlmmsaNetworkRxAlignment 14 }



pmo10010AlmNetRxOutOfAlignment OBJECT-TYPE
	  SYNTAX EkiOnOff
	  MAX-ACCESS read-only
	  STATUS current
	  DESCRIPTION
        "
        Line Trscv Network Rx Out Of Alignment 
        :This OID indicates a Rx Out of 
        Alignment is detected on the Line 
        Trscv Network interface <Help>
         Alarm indicating a Rx Out of Alignment 
        is detected on the Line Trscv Network 
        interface <Condtype> NET_RX_OUT_OF_ALIGNMENT 
        <Probcause> receiverFailure (42) 
        <Alarmtype> equipmentAlarm (5)
         <Polarity> (2) 
        "
	  ::= { pmo10010AlmmsaNetworkRxAlignment 13 }



pmo10010AlmNetRxTimingFault OBJECT-TYPE
	  SYNTAX EkiOnOff
	  MAX-ACCESS read-only
	  STATUS current
	  DESCRIPTION
        "
        Line Trscv Network Rx Timing Fault 
        :This OID indicates a Rx Timing 
        Fault is detected on the Line Trscv 
        Network interface <Help> Alarm
         indicating a Rx Timing Fault is 
        detected on the Line Trscv Network 
        interface <Condtype> NET_RX_TIMING_FAULT 
        <Probcause> receiverFailure (42) 
        <Alarmtype> equipmentAlarm (5)
         <Polarity> (2) 
        "
	  ::= { pmo10010AlmmsaNetworkRxAlignment 12 }



--- *****************************************************
---     LEAF for the msaNetworkHostNetworkAlarmSummary article
--- *****************************************************
pmo10010AlmmsaNetworkHostNetworkAlarmSummary OBJECT IDENTIFIER ::= { pmo10010AlmOtherCrit 51 }




pmo10010AlmHostTxOtnStatus OBJECT-TYPE
	  SYNTAX EkiOnOff
	  MAX-ACCESS read-only
	  STATUS current
	  DESCRIPTION
        "
        Line Trscv Host Tx OTN :This OID 
        indicates a Tx OTN Fault is detected 
        on the Line Trscv Host interface 
        <Help> Synthesis Alarm indicating 
        a Tx OTN Fault is detected on the 
        Line Trscv Host interface <Condtype> 
        HOST_TX_OTN_STATUS <Probcause>
         informationalStatus(1000) <Alarmtype> 
        other (1) <Polarity> (2) 
        "
	  ::= { pmo10010AlmmsaNetworkHostNetworkAlarmSummary 16 }



pmo10010AlmHostTxAlignment OBJECT-TYPE
	  SYNTAX EkiOnOff
	  MAX-ACCESS read-only
	  STATUS current
	  DESCRIPTION
        "
        Line Trscv Host Tx Alignment :This 
        OID indicates a Tx Alignment Fault 
        is detected on the Line Trscv Host 
        interface <Help> Synthesis Alarm 
        indicating a Tx Alignment Fault 
        is detected on the Line Trscv Host 
        interface <Condtype> HOST_TX_ALIGNMENT 
        <Probcause> informationalStatus(1000) 
        <Alarmtype> other (1) <Polarity> 
        (2) 
        "
	  ::= { pmo10010AlmmsaNetworkHostNetworkAlarmSummary 15 }



pmo10010AlmHostRxAlignment OBJECT-TYPE
	  SYNTAX EkiOnOff
	  MAX-ACCESS read-only
	  STATUS current
	  DESCRIPTION
        "
        Line Trscv Host Rx Alignment :This 
        OID indicates a Rx Alignment Fault 
        is detected on the Line Trscv Host 
        interface <Help> Synthesis Alarm 
        indicating a Rx Alignment Fault 
        is detected on the Line Trscv Host 
        interface <Condtype> HOST_RX_ALIGNMENT 
        <Probcause> informationalStatus(1000) 
        <Alarmtype> other (1) <Polarity> 
        (2) 
        "
	  ::= { pmo10010AlmmsaNetworkHostNetworkAlarmSummary 14 }



pmo10010AlmNetworkRxOtn OBJECT-TYPE
	  SYNTAX EkiOnOff
	  MAX-ACCESS read-only
	  STATUS current
	  DESCRIPTION
        "
        Line Trscv Network Rx OTN :This 
        OID indicates a Rx OTN Fault is 
        detected on the Line Trscv Network 
        interface <Help> Synthesis Alarm 
        indicating a Rx OTN Fault is detected 
        on the Line Trscv Network interface 
        <Condtype> NETWORK_RX_OTN <Probcause> 
        informationalStatus(1000) <Alarmtype> 
        other (1) <Polarity> (2) 
        "
	  ::= { pmo10010AlmmsaNetworkHostNetworkAlarmSummary 13 }



pmo10010AlmNetworkRxAlignment OBJECT-TYPE
	  SYNTAX EkiOnOff
	  MAX-ACCESS read-only
	  STATUS current
	  DESCRIPTION
        "
        Line Trscv Network Rx Alignment 
        :This OID indicates a Rx Alignment 
        Fault is detected on the Line Trscv 
        Network interface <Help> Synthesis 
        Alarm indicating a Rx Alignment 
        Fault is detected on the Line Trscv 
        Network interface <Condtype> NETWORK_RX_ALIGNMENT 
        <Probcause> informationalStatus(1000) 
        <Alarmtype> other (1) <Polarity> 
        (2) 
        "
	  ::= { pmo10010AlmmsaNetworkHostNetworkAlarmSummary 12 }



pmo10010AlmNetworkTxAlignment OBJECT-TYPE
	  SYNTAX EkiOnOff
	  MAX-ACCESS read-only
	  STATUS current
	  DESCRIPTION
        "
        Line Trscv Network Tx Alignment 
        :This OID indicates a Tx Alignment 
        Fault is detected on the Line Trscv 
        Network interface <Help> Synthesis 
        Alarm indicating a Tx Alignment 
        Fault is detected on the Line Trscv 
        Network interface <Condtype> NETWORK_TX_ALIGNMENT 
        <Probcause> informationalStatus(1000) 
        <Alarmtype> other (1) <Polarity> 
        (2) 
        "
	  ::= { pmo10010AlmmsaNetworkHostNetworkAlarmSummary 11 }



--- *****************************************************
---     LEAF for the msaHostTxAlignment article
--- *****************************************************
pmo10010AlmmsaHostTxAlignment OBJECT IDENTIFIER ::= { pmo10010AlmOtherCrit 52 }




pmo10010AlmHostTxCdrLockFault OBJECT-TYPE
	  SYNTAX EkiOnOff
	  MAX-ACCESS read-only
	  STATUS current
	  DESCRIPTION
        "
        Line Trscv Host Tx CDR Lock Fault 
        :This OID indicates a Tx Clock
         Data Recovery Lock Fault is detected 
        on the Line Trscv Host interface 
        <Help> Alarm indicating a Tx Clock 
        Data Recovery Lock Fault is detected 
        on the Line Trscv Host interface 
        <Condtype> HOST_TX_CDR_LOCK_FAULT 
        <Probcause> receiverFailure (42) 
        <Alarmtype> equipmentAlarm (5)
         <Polarity> (2) 
        "
	  ::= { pmo10010AlmmsaHostTxAlignment 16 }



pmo10010AlmHostTxLossOfAlignment OBJECT-TYPE
	  SYNTAX EkiOnOff
	  MAX-ACCESS read-only
	  STATUS current
	  DESCRIPTION
        "
        Line Trscv Host Tx Loss Of Alignment 
        :This OID indicates a Tx Loss of 
        Alignment is detected on the Line 
        Trscv Host interface <Help> Alarm 
        indicating a Tx Loss of Alignment 
        is detected on the Line Trscv Host 
        interface <Condtype> HOST_TX_LOSS_OF_ALIGNMENT 
        <Probcause> receiverFailure (42) 
        <Alarmtype> equipmentAlarm (5)
         <Polarity> (2) 
        "
	  ::= { pmo10010AlmmsaHostTxAlignment 15 }



pmo10010AlmHostTxOutOfAlignment OBJECT-TYPE
	  SYNTAX EkiOnOff
	  MAX-ACCESS read-only
	  STATUS current
	  DESCRIPTION
        "
        Line Trscv Host Tx Out Of Alignment 
        :This OID indicates a Tx Out of 
        Alignment is detected on the Line 
        Trscv Host interface <Help> Alarm 
        indicating a Tx Out of Alignment 
        is detected on the Line Trscv Host 
        interface <Condtype> HOST_TX_OUT_OF_ALIGNMENT 
        <Probcause> receiverFailure (42) 
        <Alarmtype> equipmentAlarm (5)
         <Polarity> (2) 
        "
	  ::= { pmo10010AlmmsaHostTxAlignment 14 }



pmo10010AlmHostTxDeskewLockFault OBJECT-TYPE
	  SYNTAX EkiOnOff
	  MAX-ACCESS read-only
	  STATUS current
	  DESCRIPTION
        "
        Line Trscv Host Tx Deskew Lock 
        Fault :This OID indicates a Tx
         Deskew Lock Fault is detected
         on  the Line Trscv Host interface 
        <Help> Alarm indicating a Tx Deskew 
        Lock Fault is detected on  the
         Line Trscv Host interface <Condtype> 
        HOST_TX_DESKEW_LOCK_FAULT <Probcause> 
        receiverFailure (42) <Alarmtype> 
        equipmentAlarm (5) <Polarity> (2) 
        "
	  ::= { pmo10010AlmmsaHostTxAlignment 13 }



--- *****************************************************
---     LEAF for the msaHostRxAlignment article
--- *****************************************************
pmo10010AlmmsaHostRxAlignment OBJECT IDENTIFIER ::= { pmo10010AlmOtherCrit 53 }




pmo10010AlmHostRxLossOfAlignment OBJECT-TYPE
	  SYNTAX EkiOnOff
	  MAX-ACCESS read-only
	  STATUS current
	  DESCRIPTION
        "
        Line Trscv Host Rx Loss Of Alignment 
        :This OID indicates a Rx Loss of 
        Alignment is detected on the Line 
        Trscv Host interface <Help> Alarm 
        indicating a Rx Loss of Alignment 
        is detected on the Line Trscv Host 
        interface <Condtype> HOST_RX_LOSS_OF_ALIGNMENT 
        <Probcause> transmitterFailure
         (56) <Alarmtype> equipmentAlarm 
        (5) <Polarity> (2) 
        "
	  ::= { pmo10010AlmmsaHostRxAlignment 16 }



pmo10010AlmHostRxOutOfAlignment OBJECT-TYPE
	  SYNTAX EkiOnOff
	  MAX-ACCESS read-only
	  STATUS current
	  DESCRIPTION
        "
        Line Trscv Host Rx Out Of Alignment 
        :This OID indicates a Rx Out of 
        Alignment is detected on the Line 
        Trscv Host interface <Help> Alarm 
        indicating a Rx Out of Alignment 
        is detected on the Line Trscv Host 
        interface <Condtype> HOST_RX_OUT_OF_ALIGNMENT 
        <Probcause> transmitterFailure
         (56) <Alarmtype> equipmentAlarm 
        (5) <Polarity> (2) 
        "
	  ::= { pmo10010AlmmsaHostRxAlignment 15 }



pmo10010AlmHostRxCmuLockFault OBJECT-TYPE
	  SYNTAX EkiOnOff
	  MAX-ACCESS read-only
	  STATUS current
	  DESCRIPTION
        "
        Line Trscv Host Rx CMU Lock Fault 
        :This OID indicates a Rx Clock
         Multiplier Unit Lock Fault is
         detected on the Line Trscv Host 
        interface <Help> Alarm indicating 
        a Rx Clock Multiplier Unit Lock 
        Fault is detected on the Line Trscv 
        Host interface <Condtype> HOST_RX_CMU_LOCK_FAULT 
        <Probcause> transmitterFailure
         (56) <Alarmtype> equipmentAlarm 
        (5) <Polarity> (2) 
        "
	  ::= { pmo10010AlmmsaHostRxAlignment 14 }



--- *********************************************************
---     TABLE for the pmo10010AlmclientNetworkLaneAlarmWarning articles
--- *********************************************************

pmo10010AlmclientNetworkLaneAlarmWarningTable OBJECT-TYPE
	SYNTAX  SEQUENCE OF Pmo10010AlmclientNetworkLaneAlarmWarningEntry
	MAX-ACCESS not-accessible
	STATUS current
	DESCRIPTION
        "
        List of pmo10010AlmclientNetworkLaneAlarmWarning 
        Article
        "
	::= { pmo10010AlmClientNurg 56 }


pmo10010AlmclientNetworkLaneAlarmWarningEntry OBJECT-TYPE
	SYNTAX Pmo10010AlmclientNetworkLaneAlarmWarningEntry
	MAX-ACCESS not-accessible
	STATUS current
	DESCRIPTION
        "
        Row definition for the pmo10010AlmclientNetworkLaneAlarmWarning 
        table
        "
	INDEX   { pmo10010AlmclientNetworkLaneAlarmWarningIndex }
	::= { pmo10010AlmclientNetworkLaneAlarmWarningTable 1 }


Pmo10010AlmclientNetworkLaneAlarmWarningEntry ::=
	SEQUENCE {
	pmo10010AlmclientNetworkLaneAlarmWarningIndex
		INTEGER,
	pmo10010AlmClientBiasHighAlarmPortn
		EkiOnOff,
	pmo10010AlmClientBiasHighWarningPortn
		EkiOnOff,
	pmo10010AlmClientBiasLowWarningPortn
		EkiOnOff,
	pmo10010AlmClientBiasLowAlarmPortn
		EkiOnOff,
	pmo10010AlmClientTxPowerHighAlarmPortn
		EkiOnOff,
	pmo10010AlmClientTxPowerHighWarningPortn
		EkiOnOff,
	pmo10010AlmClientTxPowerLowWarningPortn
		EkiOnOff,
	pmo10010AlmClientTxPowerLowAlarmPortn
		EkiOnOff,
	pmo10010AlmClientLaserTempHighAlarmPortn
		EkiOnOff,
	pmo10010AlmClientLaserTempHighWarningPortn
		EkiOnOff,
	pmo10010AlmClientLaserTempLowWarningPortn
		EkiOnOff,
	pmo10010AlmLaserTempLowAlarmPortn
		EkiOnOff,
	pmo10010AlmClientRxPowerHighAlarmPortn
		EkiOnOff,
	pmo10010AlmClientRxPowerHighWarningPortn
		EkiOnOff,
	pmo10010AlmClientRxPowerLowWarningPortn
		EkiOnOff,
	pmo10010AlmClientRxPowerLowAlarmPortn
		EkiOnOff
	}


pmo10010AlmclientNetworkLaneAlarmWarningIndex OBJECT-TYPE
	SYNTAX  INTEGER(0..128)
	MAX-ACCESS  read-only
	STATUS current
	DESCRIPTION
        "
        Index definition for the pmo10010AlmclientNetworkLaneAlarmWarning 
        table
        "
	::= { pmo10010AlmclientNetworkLaneAlarmWarningEntry 1 }


pmo10010AlmClientBiasHighAlarmPortn OBJECT-TYPE
	SYNTAX  EkiOnOff
	MAX-ACCESS read-only
	STATUS current
	DESCRIPTION
        "
        Client Trscv Bias High Alarm :This 
        OID indicates that the Trscv laser 
        bias current is higher than the 
        threshold value written in the
         Trscv EEPROM <Help> Alarm indicating 
        that the Trscv laser bias current 
        is higher than the threshold value 
        written in the Trscv EEPROM <Condtype> 
        CLIENT_BIAS_HIGH_ALARM <Probcause> 
        transmitterFailure (56) <Alarmtype> 
        equipmentAlarm (5) <Polarity> (2) 
        "
	::= { pmo10010AlmclientNetworkLaneAlarmWarningEntry 17 }


pmo10010AlmClientBiasHighWarningPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> CLIENT_BIAS_HIGH_WARNING 
        <Probcause> transmitterFailure
         (56) <Alarmtype> equipmentAlarm 
        (5) <Polarity> (2) 
        "
	::= { pmo10010AlmclientNetworkLaneAlarmWarningEntry 16 }


pmo10010AlmClientBiasLowWarningPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> CLIENT_BIAS_LOW_WARNING 
        <Probcause> transmitterFailure
         (56) <Alarmtype> equipmentAlarm 
        (5) <Polarity> (2) 
        "
	::= { pmo10010AlmclientNetworkLaneAlarmWarningEntry 15 }


pmo10010AlmClientBiasLowAlarmPortn OBJECT-TYPE
	SYNTAX  EkiOnOff
	MAX-ACCESS read-only
	STATUS current
	DESCRIPTION
        "
        Client Trscv Bias Low Alarm :This 
        OID indicates that the Trscv laser 
        bias current is lower than the
         threshold value written in the 
        Trscv EEPROM <Help> Alarm indicating 
        that the Trscv laser bias current 
        is lower than the threshold value 
        written in the Trscv EEPROM <Condtype> 
        CLIENT_BIAS_LOW_ALARM <Probcause> 
        transmitterFailure (56) <Alarmtype> 
        equipmentAlarm (5) <Polarity> (2) 
        "
	::= { pmo10010AlmclientNetworkLaneAlarmWarningEntry 14 }


pmo10010AlmClientTxPowerHighAlarmPortn OBJECT-TYPE
	SYNTAX  EkiOnOff
	MAX-ACCESS read-only
	STATUS current
	DESCRIPTION
        "
        Client Trscv Tx Power High Alarm 
        :This OID indicates that the Trscv 
        output power is higher than the 
        threshold value written in the
         Trscv EEPROM <Help> Alarm indicating 
        that the Trscv output power is
         higher than the threshold value 
        written in the Trscv EEPROM <Condtype> 
        CLIENT_TX_POWER_HIGH_ALARM <Probcause> 
        transmitterFailure (56) <Alarmtype> 
        equipmentAlarm (5) <Polarity> (2) 
        "
	::= { pmo10010AlmclientNetworkLaneAlarmWarningEntry 13 }


pmo10010AlmClientTxPowerHighWarningPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        CLIENT_TX_POWER_HIGH_WARNING <Probcause> 
        transmitterFailure (56) <Alarmtype> 
        equipmentAlarm (5) <Polarity> (2) 
        "
	::= { pmo10010AlmclientNetworkLaneAlarmWarningEntry 12 }


pmo10010AlmClientTxPowerLowWarningPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        CLIENT_TX_POWER_LOW_WARNING <Probcause> 
        transmitterFailure (56) <Alarmtype> 
        equipmentAlarm (5) <Polarity> (2) 
        "
	::= { pmo10010AlmclientNetworkLaneAlarmWarningEntry 11 }


pmo10010AlmClientTxPowerLowAlarmPortn OBJECT-TYPE
	SYNTAX  EkiOnOff
	MAX-ACCESS read-only
	STATUS current
	DESCRIPTION
        "
        Client Trscv Tx Power Low Alarm 
        :This OID indicates that the Trscv 
        output power is lower than the
         threshold value written in the 
        Trscv EEPROM <Help> Alarm indicating 
        that the Trscv output power is
         lower than the threshold value 
        written in the Trscv EEPROM <Condtype> 
        CLIENT_TX_POWER_LOW_ALARM <Probcause> 
        transmitterFailure (56) <Alarmtype> 
        equipmentAlarm (5) <Polarity> (2) 
        "
	::= { pmo10010AlmclientNetworkLaneAlarmWarningEntry 10 }


pmo10010AlmClientLaserTempHighAlarmPortn OBJECT-TYPE
	SYNTAX  EkiOnOff
	MAX-ACCESS read-only
	STATUS current
	DESCRIPTION
        "
        Client Trscv Laser Temp High Alarm 
        :This OID indicates that the Trscv 
        Laser Temperature is higher than 
        the threshold value written in
         the Trscv EEPROM <Help> Alarm
         indicating that the Trscv Laser 
        Temperature is higher than the
         threshold value written in the 
        Trscv EEPROM <Condtype> CLIENT_LASER_TEMP_HIGH_ALARM 
        <Probcause> temperatureUnacceptable 
        (51) <Alarmtype> equipmentAlarm 
        (5) <Polarity> (2) 
        "
	::= { pmo10010AlmclientNetworkLaneAlarmWarningEntry 9 }


pmo10010AlmClientLaserTempHighWarningPortn OBJECT-TYPE
	SYNTAX  EkiOnOff
	MAX-ACCESS read-only
	STATUS current
	DESCRIPTION
        "
        Client Trscv Laser Temp High Warning 
        :This OID indicates that the Trscv 
        Laser Temperature is higher than 
        the threshold value written in
         the Trscv EEPROM <Help> Warning 
        indicating that the Trscv Laser 
        Temperature is higher than the
         threshold value written in the 
        Trscv EEPROM <Condtype> CLIENT_LASER_TEMP_HIGH_WARNING 
        <Probcause> temperatureUnacceptable 
        (51) <Alarmtype> equipmentAlarm 
        (5) <Polarity> (2) 
        "
	::= { pmo10010AlmclientNetworkLaneAlarmWarningEntry 8 }


pmo10010AlmClientLaserTempLowWarningPortn OBJECT-TYPE
	SYNTAX  EkiOnOff
	MAX-ACCESS read-only
	STATUS current
	DESCRIPTION
        "
        Client Trscv Laser Temp Low Warning 
        :This OID indicates that the Trscv 
        Laser Temperature is lower than 
        the threshold value written in
         the Trscv EEPROM <Help> Warning 
        indicating that the Trscv Laser 
        Temperature is lower than the threshold 
        value written in the Trscv EEPROM 
        <Condtype> CLIENT_LASER_TEMP_LOW_WARNING 
        <Probcause> temperatureUnacceptable 
        (51) <Alarmtype> equipmentAlarm 
        (5) <Polarity> (2) 
        "
	::= { pmo10010AlmclientNetworkLaneAlarmWarningEntry 7 }


pmo10010AlmLaserTempLowAlarmPortn OBJECT-TYPE
	SYNTAX  EkiOnOff
	MAX-ACCESS read-only
	STATUS current
	DESCRIPTION
        "
        Client Trscv Laser Temp Low Alarm 
        :This OID indicates that the Trscv 
        Laser Temperature is lower than 
        the threshold value written in
         the Trscv EEPROM <Help> Alarm
         indicating that the Trscv Laser 
        Temperature is lower than the threshold 
        value written in the Trscv EEPROM 
        <Condtype> LASER_TEMP_LOW_ALARM 
        <Probcause> temperatureUnacceptable 
        (51) <Alarmtype> equipmentAlarm 
        (5) <Polarity> (2) 
        "
	::= { pmo10010AlmclientNetworkLaneAlarmWarningEntry 6 }


pmo10010AlmClientRxPowerHighAlarmPortn OBJECT-TYPE
	SYNTAX  EkiOnOff
	MAX-ACCESS read-only
	STATUS current
	DESCRIPTION
        "
        Client Trscv Rx Power High Alarm 
        :This OID indicates that the Trscv 
        input power is higher than the
         threshold value written in the 
        Trscv EEPROM <Help> Alarm indicating 
        that the Trscv input power is higher 
        than the threshold value written 
        in the Trscv EEPROM <Condtype>
         CLIENT_RX_POWER_HIGH_ALARM <Probcause> 
        receiveFailure (41) <Alarmtype> 
        equipmentAlarm (5) <Polarity> (2) 
        "
	::= { pmo10010AlmclientNetworkLaneAlarmWarningEntry 5 }


pmo10010AlmClientRxPowerHighWarningPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         CLIENT_RX_POWER_HIGH_WARNING <Probcause> 
        receiveFailure (41) <Alarmtype> 
        equipmentAlarm (5) <Polarity> (2) 
        "
	::= { pmo10010AlmclientNetworkLaneAlarmWarningEntry 4 }


pmo10010AlmClientRxPowerLowWarningPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         CLIENT_RX_POWER_LOW_WARNING <Probcause> 
        receiveFailure (41) <Alarmtype> 
        equipmentAlarm (5) <Polarity> (2) 
        "
	::= { pmo10010AlmclientNetworkLaneAlarmWarningEntry 3 }


pmo10010AlmClientRxPowerLowAlarmPortn OBJECT-TYPE
	SYNTAX  EkiOnOff
	MAX-ACCESS read-only
	STATUS current
	DESCRIPTION
        "
        Client Trscv Rx Power Low Alarm 
        :This OID indicates that the Trscv 
        input power is lower than the threshold 
        value written in the Trscv EEPROM 
        <Help> Alarm indicating that the 
        Trscv input power is lower than 
        the threshold value written in
         the Trscv EEPROM <Condtype> CLIENT_RX_POWER_LOW_ALARM 
        <Probcause> receiveFailure (41) 
        <Alarmtype> equipmentAlarm (5)
         <Polarity> (2) 
        "
	::= { pmo10010AlmclientNetworkLaneAlarmWarningEntry 2 }


--- *********************************************************
---     TABLE for the pmo10010AlmclientNetworkLaneFault articles
--- *********************************************************

pmo10010AlmclientNetworkLaneFaultTable OBJECT-TYPE
	SYNTAX  SEQUENCE OF Pmo10010AlmclientNetworkLaneFaultEntry
	MAX-ACCESS not-accessible
	STATUS current
	DESCRIPTION
        "
        List of pmo10010AlmclientNetworkLaneFault 
        Article
        "
	::= { pmo10010AlmClientUrg 72 }


pmo10010AlmclientNetworkLaneFaultEntry OBJECT-TYPE
	SYNTAX Pmo10010AlmclientNetworkLaneFaultEntry
	MAX-ACCESS not-accessible
	STATUS current
	DESCRIPTION
        "
        Row definition for the pmo10010AlmclientNetworkLaneFault 
        table
        "
	INDEX   { pmo10010AlmclientNetworkLaneFaultIndex }
	::= { pmo10010AlmclientNetworkLaneFaultTable 1 }


Pmo10010AlmclientNetworkLaneFaultEntry ::=
	SEQUENCE {
	pmo10010AlmclientNetworkLaneFaultIndex
		INTEGER,
	pmo10010AlmClientLaneTecFaultPortn
		EkiOnOff,
	pmo10010AlmClientLaneWavelengthUnlockedPortn
		EkiOnOff,
	pmo10010AlmClientLaneApdPowerSupplyPortn
		EkiOnOff,
	pmo10010AlmClientLaneTxLosfPortn
		EkiOnOff,
	pmo10010AlmClientLaneTxLolPortn
		EkiOnOff,
	pmo10010AlmClientLaneRxLosPortn
		EkiOnOff,
	pmo10010AlmClientLaneRxLolPortn
		EkiOnOff,
	pmo10010AlmClientLaneRxFifoErrorPortn
		EkiOnOff
	}


pmo10010AlmclientNetworkLaneFaultIndex OBJECT-TYPE
	SYNTAX  INTEGER(0..128)
	MAX-ACCESS  read-only
	STATUS current
	DESCRIPTION
        "
        Index definition for the pmo10010AlmclientNetworkLaneFault 
        table
        "
	::= { pmo10010AlmclientNetworkLaneFaultEntry 1 }


pmo10010AlmClientLaneTecFaultPortn OBJECT-TYPE
	SYNTAX  EkiOnOff
	MAX-ACCESS read-only
	STATUS current
	DESCRIPTION
        "
        Client Network Lane TEC Fault
         :This OID indicates a TEC Fault 
        on the Client Trscv Network Lane 
        <Help> Alarm indicating a TEC Fault 
        on the Client Trscv Network Lane 
        <Condtype> CLIENT_LANE_TEC_FAULT 
        <Probcause> transmitterFailure
         (56) <Alarmtype> equipmentAlarm 
        (5) <Polarity> (2) 
        "
	::= { pmo10010AlmclientNetworkLaneFaultEntry 17 }


pmo10010AlmClientLaneWavelengthUnlockedPortn OBJECT-TYPE
	SYNTAX  EkiOnOff
	MAX-ACCESS read-only
	STATUS current
	DESCRIPTION
        "
        Client Network Lane Wavelength 
        Unlock :This OID indicates a Wavelength 
        unlock on the Client Trscv Network 
        Lane <Help> Alarm indicating a
         Wavelength unlock on the Client 
        Trscv Network Lane <Condtype> CLIENT_LANE_WAVELENGTH_UNLOCKED 
        <Probcause> transmitterFailure
         (56) <Alarmtype> equipmentAlarm 
        (5) <Polarity> (2) 
        "
	::= { pmo10010AlmclientNetworkLaneFaultEntry 16 }


pmo10010AlmClientLaneApdPowerSupplyPortn OBJECT-TYPE
	SYNTAX  EkiOnOff
	MAX-ACCESS read-only
	STATUS current
	DESCRIPTION
        "
        Client Network Lane APD Power
         Supply :This OID indicates an
         APD Power supply failure on the 
        Client Trscv Network Lane <Help> 
        Alarm indicating an APD Power supply 
        failure on the Client Trscv Network 
        Lane <Condtype> CLIENT_LANE_APD_POWER_SUPPLY 
        <Probcause> transmitterFailure
         (56) <Alarmtype> equipmentAlarm 
        (5) <Polarity> (2) 
        "
	::= { pmo10010AlmclientNetworkLaneFaultEntry 15 }


pmo10010AlmClientLaneTxLosfPortn OBJECT-TYPE
	SYNTAX  EkiOnOff
	MAX-ACCESS read-only
	STATUS current
	DESCRIPTION
        "
        Client Network Lane Tx Loss Of 
        Signal Functionality :This OID
         indicates a Tx Loss of Signal
         Functionality on the Client Trscv 
        Network Lane <Help> Alarm indicating 
        a Tx Loss of Signal Functionality 
        on the Client Trscv Network Lane 
        <Condtype> CLIENT_LANE_TX_LOSF
         <Probcause> transmitterFailure 
        (56) <Alarmtype> equipmentAlarm 
        (5) <Polarity> (2) 
        "
	::= { pmo10010AlmclientNetworkLaneFaultEntry 9 }


pmo10010AlmClientLaneTxLolPortn OBJECT-TYPE
	SYNTAX  EkiOnOff
	MAX-ACCESS read-only
	STATUS current
	DESCRIPTION
        "
        Client Network Lane Tx Loss Of 
        Lock :This OID indicates a Tx Loss 
        of Lock on the Client Trscv Network 
        Lane <Help> Alarm indicating a
         Tx Loss of Lock on the Client
         Trscv Network Lane <Condtype>
         CLIENT_LANE_TX_LOL <Probcause> 
        transmitterFailure (56) <Alarmtype> 
        equipmentAlarm (5) <Polarity> (2) 
        "
	::= { pmo10010AlmclientNetworkLaneFaultEntry 8 }


pmo10010AlmClientLaneRxLosPortn OBJECT-TYPE
	SYNTAX  EkiOnOff
	MAX-ACCESS read-only
	STATUS current
	DESCRIPTION
        "
        Client Network Lane Rx Loss Of 
        Signal :This OID indicates a Rx 
        Loss of Signal on the Client Trscv 
        Network Lane <Help> Alarm indicating 
        a Rx Loss of Signal on the Client 
        Trscv Network Lane <Condtype> CLIENT_LANE_RX_LOS 
        <Probcause> receiveFailure (41) 
        <Alarmtype> physicalViolation (9) 
        <Polarity> (2) 
        "
	::= { pmo10010AlmclientNetworkLaneFaultEntry 6 }


pmo10010AlmClientLaneRxLolPortn OBJECT-TYPE
	SYNTAX  EkiOnOff
	MAX-ACCESS read-only
	STATUS current
	DESCRIPTION
        "
        Client Network Lane Rx Loss Of 
        Lock :This OID indicates a Rx Loss 
        of Lock on the Client Trscv Network 
        Lane <Help> Alarm indicating a
         Rx Loss of Lock on the Client
         Trscv Network Lane <Condtype>
         CLIENT_LANE_RX_LOL <Probcause> 
        receiverFailure (42) <Alarmtype> 
        equipmentAlarm (5) <Polarity> (2) 
        "
	::= { pmo10010AlmclientNetworkLaneFaultEntry 5 }


pmo10010AlmClientLaneRxFifoErrorPortn OBJECT-TYPE
	SYNTAX  EkiOnOff
	MAX-ACCESS read-only
	STATUS current
	DESCRIPTION
        "
        Client Network Lane Rx FIFO Error 
        :This OID indicates a Rx FIFO Error 
        on the Client Trscv Network Lane 
        <Help> Alarm indicating a Rx FIFO 
        Error on the Client Trscv Network 
        Lane <Condtype> CLIENT_LANE_RX_FIFO_ERROR 
        <Probcause> receiverFailure (42) 
        <Alarmtype> equipmentAlarm (5)
         <Polarity> (2) 
        "
	::= { pmo10010AlmclientNetworkLaneFaultEntry 4 }


--- *********************************************************
---     TABLE for the pmo10010AlmclientHostLaneFault articles
--- *********************************************************

pmo10010AlmclientHostLaneFaultTable OBJECT-TYPE
	SYNTAX  SEQUENCE OF Pmo10010AlmclientHostLaneFaultEntry
	MAX-ACCESS not-accessible
	STATUS current
	DESCRIPTION
        "
        List of pmo10010AlmclientHostLaneFault 
        Article
        "
	::= { pmo10010AlmClientUrg 88 }


pmo10010AlmclientHostLaneFaultEntry OBJECT-TYPE
	SYNTAX Pmo10010AlmclientHostLaneFaultEntry
	MAX-ACCESS not-accessible
	STATUS current
	DESCRIPTION
        "
        Row definition for the pmo10010AlmclientHostLaneFault 
        table
        "
	INDEX   { pmo10010AlmclientHostLaneFaultIndex }
	::= { pmo10010AlmclientHostLaneFaultTable 1 }


Pmo10010AlmclientHostLaneFaultEntry ::=
	SEQUENCE {
	pmo10010AlmclientHostLaneFaultIndex
		INTEGER,
	pmo10010AlmClientTxLossOfSyncPortn
		EkiOnOff,
	pmo10010AlmTxRemoteFaultDetectedPortn
		EkiOnOff,
	pmo10010AlmTxLocalFaultDetectedPortn
		EkiOnOff,
	pmo10010AlmRxRemoteFaultDetectedPortn
		EkiOnOff,
	pmo10010AlmRxLocalFaultDetectedPortn
		EkiOnOff,
	pmo10010AlmClientLaneTxFifoErrorPortn
		EkiOnOff,
	pmo10010AlmClientTxHostLolPortn
		EkiOnOff,
	pmo10010AlmClientCsfDetectedPortn
		EkiOnOff,
	pmo10010AlmClientLanesNotAlignedPortn
		EkiOnOff,
	pmo10010AlmClientLanes6466UnlockPortn
		EkiOnOff,
	pmo10010AlmClientLanesMarkerUnlockPortn
		EkiOnOff,
	pmo10010AlmClientInputLossOfSigPortn
		EkiOnOff,
	pmo10010AlmClientRxLossOfSyncPortn
		EkiOnOff
	}


pmo10010AlmclientHostLaneFaultIndex OBJECT-TYPE
	SYNTAX  INTEGER(0..128)
	MAX-ACCESS  read-only
	STATUS current
	DESCRIPTION
        "
        Index definition for the pmo10010AlmclientHostLaneFault 
        table
        "
	::= { pmo10010AlmclientHostLaneFaultEntry 1 }


pmo10010AlmClientTxLossOfSyncPortn OBJECT-TYPE
	SYNTAX  EkiOnOff
	MAX-ACCESS read-only
	STATUS current
	DESCRIPTION
        "
        Client Tx Frame Alignment Loss 
        :This OID indicates the module
         is not aligned with the Tx incoming 
        Client signal<Help> Alarm indicating 
        the module is not aligned with
         the incoming client signal from 
        the line side <Condtype> CLIENT_TX_LOSS_OF_SYNC 
        <Probcause> receiveFailure (41) 
        <Alarmtype> equipmentAlarm (5)
         <Polarity> (2) 
        "
	::= { pmo10010AlmclientHostLaneFaultEntry 16 }


pmo10010AlmTxRemoteFaultDetectedPortn OBJECT-TYPE
	SYNTAX  EkiOnOff
	MAX-ACCESS read-only
	STATUS current
	DESCRIPTION
        "
        Tx Remote Fault Signal Detected 
        :This OID indicates a Remote Fault 
        Signal is coming on the client
         port from the line side<Help>
         This alarm indicates a Remote
         Fault Signal is coming on the
         client input port from the line 
        side <Condtype> TX_REMOTE_FAULT_DETECTED 
        <Probcause> receiverFailure (42) 
        <Alarmtype> equipmentAlarm (5)
         <Polarity> (2) 
        "
	::= { pmo10010AlmclientHostLaneFaultEntry 15 }


pmo10010AlmTxLocalFaultDetectedPortn OBJECT-TYPE
	SYNTAX  EkiOnOff
	MAX-ACCESS read-only
	STATUS current
	DESCRIPTION
        "
        Tx Local Fault Signal Detected 
        :This OID indicates a Local Fault 
        Signal is coming on the client
         port from the line side<Help>
         This alarm indicates a Local Fault 
        Signal is coming on the client
         input port from the line side
         <Condtype> TX_LOCAL_FAULT_DETECTED 
        <Probcause> receiverFailure (42) 
        <Alarmtype> equipmentAlarm (5)
         <Polarity> (2) 
        "
	::= { pmo10010AlmclientHostLaneFaultEntry 14 }


pmo10010AlmRxRemoteFaultDetectedPortn OBJECT-TYPE
	SYNTAX  EkiOnOff
	MAX-ACCESS read-only
	STATUS current
	DESCRIPTION
        "
        Rx Remote Fault Signal Detected 
        :This OID indicates a Remote Fault 
        Signal is detected on the client 
        input port<Help> This alarm indicates 
        a Remote Fault Signal is detected 
        on the client input port <Condtype> 
        RX_REMOTE_FAULT_DETECTED <Probcause> 
        receiverFailure (42) <Alarmtype> 
        equipmentAlarm (5) <Polarity> (2) 
        "
	::= { pmo10010AlmclientHostLaneFaultEntry 13 }


pmo10010AlmRxLocalFaultDetectedPortn OBJECT-TYPE
	SYNTAX  EkiOnOff
	MAX-ACCESS read-only
	STATUS current
	DESCRIPTION
        "
        Rx Local Fault Signal Detected 
        :This OID indicates a Local Fault 
        Signal is detected on the client 
        input port<Help> This alarm indicates 
        a Local Fault Signal is detected 
        on the client input port <Condtype> 
        RX_LOCAL_FAULT_DETECTED <Probcause> 
        receiverFailure (42) <Alarmtype> 
        equipmentAlarm (5) <Polarity> (2) 
        "
	::= { pmo10010AlmclientHostLaneFaultEntry 12 }


pmo10010AlmClientLaneTxFifoErrorPortn OBJECT-TYPE
	SYNTAX  EkiOnOff
	MAX-ACCESS read-only
	STATUS current
	DESCRIPTION
        "
        Client Host Lane Tx FIFO Error 
        :This OID indicates a Tx FIFO Error 
        on the Client Trscv Host Lane <Help> 
        Alarm indicating a Tx FIFO Error 
        on the Client Trscv Host Lane <Condtype> 
        CLIENT_LANE_TX_FIFO_ERROR <Probcause> 
        receiverFailure (42) <Alarmtype> 
        equipmentAlarm (5) <Polarity> (2) 
        "
	::= { pmo10010AlmclientHostLaneFaultEntry 11 }


pmo10010AlmClientTxHostLolPortn OBJECT-TYPE
	SYNTAX  EkiOnOff
	MAX-ACCESS read-only
	STATUS current
	DESCRIPTION
        "
        Client Host Lane Tx Loss Of Lock 
        :This OID indicates a Tx Loss of 
        Lock on the Client Trscv Host Lane 
        <Help> Alarm indicating a Tx Loss 
        of Lock on the Client Trscv Host 
        Lane <Condtype> CLIENT_TX_HOST_LOL 
        <Probcause> receiverFailure (42) 
        <Alarmtype> equipmentAlarm (5)
         <Polarity> (2) 
        "
	::= { pmo10010AlmclientHostLaneFaultEntry 10 }


pmo10010AlmClientCsfDetectedPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> CLIENT_CSF_DETECTED 
        <Probcause> receiveFailure (41) 
        <Alarmtype> other(1) <Polarity> 
        (2)
        "
	::= { pmo10010AlmclientHostLaneFaultEntry 7 }


pmo10010AlmClientLanesNotAlignedPortn OBJECT-TYPE
	SYNTAX  EkiOnOff
	MAX-ACCESS read-only
	STATUS current
	DESCRIPTION
        "
        Client Lanes Not Aligned :This 
        OID indicates the Client lanes
         are not aligned <Help> Alarm indicating 
        the Client lanes are not aligned 
        <Condtype> CLIENT_LANES_NOT_ALIGNED 
        <Probcause> receiveFailure (41) 
        <Alarmtype> integrityViolation
         (7) <Polarity> (2) 
        "
	::= { pmo10010AlmclientHostLaneFaultEntry 6 }


pmo10010AlmClientLanes6466UnlockPortn OBJECT-TYPE
	SYNTAX  EkiOnOff
	MAX-ACCESS read-only
	STATUS current
	DESCRIPTION
        "
        Client Lanes 64/66b Unlock :This 
        OID indicates the Client 64/66b 
        decoder is not lock <Help> Alarm 
        indicating the Client 64/66b decoder 
        is not lock <Condtype> CLIENT_LANES_64_66_UNLOCK 
        <Probcause> receiveFailure (41) 
        <Alarmtype> integrityViolation
         (7) <Polarity> (2) 
        "
	::= { pmo10010AlmclientHostLaneFaultEntry 5 }


pmo10010AlmClientLanesMarkerUnlockPortn OBJECT-TYPE
	SYNTAX  EkiOnOff
	MAX-ACCESS read-only
	STATUS current
	DESCRIPTION
        "
        Client Lanes Marker Unlock :This 
        OID indicates the Client lanes
         marker alignment is not lock <Help> 
        Alarm indicating the Client lanes 
        marker alignment is not lock <Condtype> 
        CLIENT_LANES_MARKER_UNLOCK <Probcause> 
        receiveFailure (41) <Alarmtype> 
        integrityViolation (7) <Polarity> 
        (2) 
        "
	::= { pmo10010AlmclientHostLaneFaultEntry 4 }


pmo10010AlmClientInputLossOfSigPortn OBJECT-TYPE
	SYNTAX  EkiOnOff
	MAX-ACCESS read-only
	STATUS current
	DESCRIPTION
        "
        Client Input Loss Of Signal :This 
        OID indicates a Loss of Signal
         is detected on the Client Trscv 
        <Help> Alarm indicating a Loss
         of Signal is detected on the Client 
        Trscv <Condtype> CLIENT_INPUT_LOSS_OF_SIG 
        <Probcause> receiveFailure (41) 
        <Alarmtype> physicalViolation (9) 
        <Polarity> (2) 
        "
	::= { pmo10010AlmclientHostLaneFaultEntry 3 }


pmo10010AlmClientRxLossOfSyncPortn OBJECT-TYPE
	SYNTAX  EkiOnOff
	MAX-ACCESS read-only
	STATUS current
	DESCRIPTION
        "
        Client Rx Frame Alignment Loss 
        :This OID indicates the module
         is not aligned with the Rx incoming 
        Client signal <Help> Alarm indicating 
        the module is not aligned with
         the incoming client signal <Condtype> 
        CLIENT_RX_LOSS_OF_SYNC <Probcause> 
        receiveFailure (41) <Alarmtype> 
        integrityViolation (7) <Polarity> 
        (2) 
        "
	::= { pmo10010AlmclientHostLaneFaultEntry 2 }


--- *********************************************************
---     TABLE for the pmo10010AlmlineNetworkLaneAlarmWarning1 articles
--- *********************************************************

pmo10010AlmlineNetworkLaneAlarmWarning1Table OBJECT-TYPE
	SYNTAX  SEQUENCE OF Pmo10010AlmlineNetworkLaneAlarmWarning1Entry
	MAX-ACCESS not-accessible
	STATUS current
	DESCRIPTION
        "
        List of pmo10010AlmlineNetworkLaneAlarmWarning1 
        Article
        "
	::= { pmo10010AlmLineNurg 104 }


pmo10010AlmlineNetworkLaneAlarmWarning1Entry OBJECT-TYPE
	SYNTAX Pmo10010AlmlineNetworkLaneAlarmWarning1Entry
	MAX-ACCESS not-accessible
	STATUS current
	DESCRIPTION
        "
        Row definition for the pmo10010AlmlineNetworkLaneAlarmWarning1 
        table
        "
	INDEX   { pmo10010AlmlineNetworkLaneAlarmWarning1Index }
	::= { pmo10010AlmlineNetworkLaneAlarmWarning1Table 1 }


Pmo10010AlmlineNetworkLaneAlarmWarning1Entry ::=
	SEQUENCE {
	pmo10010AlmlineNetworkLaneAlarmWarning1Index
		INTEGER,
	pmo10010AlmLineBiasHighAlarmPortn
		EkiOnOff,
	pmo10010AlmLineBiasHighWarningPortn
		EkiOnOff,
	pmo10010AlmLineBiasLowWarningPortn
		EkiOnOff,
	pmo10010AlmLineBiasLowAlarmPortn
		EkiOnOff,
	pmo10010AlmLineTxPowerHighAlarmPortn
		EkiOnOff,
	pmo10010AlmLineTxPowerHighWarningPortn
		EkiOnOff,
	pmo10010AlmLineTxPowerLowWarningPortn
		EkiOnOff,
	pmo10010AlmLineTxPowerLowAlarmPortn
		EkiOnOff,
	pmo10010AlmLineLaserTempHighAlarmPortn
		EkiOnOff,
	pmo10010AlmLineLaserTempHighWarningPortn
		EkiOnOff,
	pmo10010AlmLineLaserTempLowWarningPortn
		EkiOnOff,
	pmo10010AlmLineLaserTempLowAlarmPortn
		EkiOnOff,
	pmo10010AlmLineRxPowerHighAlarmPortn
		EkiOnOff,
	pmo10010AlmLineRxPowerHighWarningPortn
		EkiOnOff,
	pmo10010AlmLineRxPowerLowWarningPortn
		EkiOnOff,
	pmo10010AlmLineRxPowerLowAlarmPortn
		EkiOnOff
	}


pmo10010AlmlineNetworkLaneAlarmWarning1Index OBJECT-TYPE
	SYNTAX  INTEGER(0..128)
	MAX-ACCESS  read-only
	STATUS current
	DESCRIPTION
        "
        Index definition for the pmo10010AlmlineNetworkLaneAlarmWarning1 
        table
        "
	::= { pmo10010AlmlineNetworkLaneAlarmWarning1Entry 1 }


pmo10010AlmLineBiasHighAlarmPortn OBJECT-TYPE
	SYNTAX  EkiOnOff
	MAX-ACCESS read-only
	STATUS current
	DESCRIPTION
        "
        Line Trscv Tx Bias High Alarm
         :This OID indicates that the Trscv 
        laser bias current is higher than 
        the threshold value written in
         the Trscv EEPROM <Help> Alarm
         indicating that the Trscv laser 
        bias current is higher than the 
        threshold value written in the
         Trscv EEPROM <Condtype> LINE_BIAS_HIGH_ALARM 
        <Probcause> transmitterFailure
         (56) <Alarmtype> equipmentAlarm 
        (5) <Polarity> (2) 
        "
	::= { pmo10010AlmlineNetworkLaneAlarmWarning1Entry 17 }


pmo10010AlmLineBiasHighWarningPortn OBJECT-TYPE
	SYNTAX  EkiOnOff
	MAX-ACCESS read-only
	STATUS current
	DESCRIPTION
        "
        Line Trscv Tx Bias High Warning 
        :This OID indicates that the Trscv 
        laser bias current is higher than 
        the threshold value written in
         the Trscv EEPROM <Help> Warning 
        indicating that the Trscv laser 
        bias current is higher than the 
        threshold value written in the
         Trscv EEPROM <Condtype> LINE_BIAS_HIGH_WARNING 
        <Probcause> transmitterFailure
         (56) <Alarmtype> equipmentAlarm 
        (5) <Polarity> (2) 
        "
	::= { pmo10010AlmlineNetworkLaneAlarmWarning1Entry 16 }


pmo10010AlmLineBiasLowWarningPortn OBJECT-TYPE
	SYNTAX  EkiOnOff
	MAX-ACCESS read-only
	STATUS current
	DESCRIPTION
        "
        Line Trscv Tx Bias Low Warning 
        :This OID indicates that the Trscv 
        laser bias current is lower than 
        the threshold value written in
         the Trscv EEPROM <Help> Warning 
        indicating that the Trscv laser 
        bias current is lower than the
         threshold value written in the 
        Trscv EEPROM <Condtype> LINE_BIAS_LOW_WARNING 
        <Probcause> transmitterFailure
         (56) <Alarmtype> equipmentAlarm 
        (5) <Polarity> (2) 
        "
	::= { pmo10010AlmlineNetworkLaneAlarmWarning1Entry 15 }


pmo10010AlmLineBiasLowAlarmPortn OBJECT-TYPE
	SYNTAX  EkiOnOff
	MAX-ACCESS read-only
	STATUS current
	DESCRIPTION
        "
        Line Trscv Tx Bias Low Alarm :This 
        OID indicates that the Trscv laser 
        bias current is lower than the
         threshold value written in the 
        Trscv EEPROM <Help> Alarm indicating 
        that the Trscv laser bias current 
        is lower than the threshold value 
        written in the Trscv EEPROM <Condtype> 
        LINE_BIAS_LOW_ALARM <Probcause> 
        transmitterFailure (56) <Alarmtype> 
        equipmentAlarm (5) <Polarity> (2) 
        "
	::= { pmo10010AlmlineNetworkLaneAlarmWarning1Entry 14 }


pmo10010AlmLineTxPowerHighAlarmPortn OBJECT-TYPE
	SYNTAX  EkiOnOff
	MAX-ACCESS read-only
	STATUS current
	DESCRIPTION
        "
        Line Trscv Tx Power High Alarm 
        :This OID indicates that the Trscv 
        output power is higher than the 
        threshold value written in the
         Trscv EEPROM <Help> Alarm indicating 
        that the Trscv output power is
         higher than the threshold value 
        written in the Trscv EEPROM <Condtype> 
        LINE_TX_POWER_HIGH_ALARM <Probcause> 
        transmitterFailure (56) <Alarmtype> 
        equipmentAlarm (5) <Polarity> (2) 
        "
	::= { pmo10010AlmlineNetworkLaneAlarmWarning1Entry 13 }


pmo10010AlmLineTxPowerHighWarningPortn OBJECT-TYPE
	SYNTAX  EkiOnOff
	MAX-ACCESS read-only
	STATUS current
	DESCRIPTION
        "
        Line Trscv Tx Power High Warning 
        :This OID indicates that the Trscv 
        output power is higher than the 
        threshold value written in the
         Trscv EEPROM <Help> Warning indicating 
        that the Trscv output power is
         higher than the threshold value 
        written in the Trscv EEPROM <Condtype> 
        LINE_TX_POWER_HIGH_WARNING <Probcause> 
        transmitterFailure (56) <Alarmtype> 
        equipmentAlarm (5) <Polarity> (2) 
        "
	::= { pmo10010AlmlineNetworkLaneAlarmWarning1Entry 12 }


pmo10010AlmLineTxPowerLowWarningPortn OBJECT-TYPE
	SYNTAX  EkiOnOff
	MAX-ACCESS read-only
	STATUS current
	DESCRIPTION
        "
        Line Trscv Tx Power Low Warning 
        :This OID indicates that the Trscv 
        output power is lower than the
         threshold value written in the 
        Trscv EEPROM <Help> Warning indicating 
        that the Trscv output power is
         lower than the threshold value 
        written in the Trscv EEPROM <Condtype> 
        LINE_TX_POWER_LOW_WARNING <Probcause> 
        transmitterFailure (56) <Alarmtype> 
        equipmentAlarm (5) <Polarity> (2) 
        "
	::= { pmo10010AlmlineNetworkLaneAlarmWarning1Entry 11 }


pmo10010AlmLineTxPowerLowAlarmPortn OBJECT-TYPE
	SYNTAX  EkiOnOff
	MAX-ACCESS read-only
	STATUS current
	DESCRIPTION
        "
        Line Trscv Tx Power Low Alarm
         :This OID indicates that the Trscv 
        output power is lower than the
         threshold value written in the 
        Trscv EEPROM <Help> Alarm indicating 
        that the Trscv output power is
         lower than the threshold value 
        written in the Trscv EEPROM <Condtype> 
        LINE_TX_POWER_LOW_ALARM <Probcause> 
        transmitterFailure (56) <Alarmtype> 
        equipmentAlarm (5) <Polarity> (2) 
        "
	::= { pmo10010AlmlineNetworkLaneAlarmWarning1Entry 10 }


pmo10010AlmLineLaserTempHighAlarmPortn OBJECT-TYPE
	SYNTAX  EkiOnOff
	MAX-ACCESS read-only
	STATUS current
	DESCRIPTION
        "
        Line Trscv Tx Laser Temp High
         Alarm :This OID indicates that 
        the Trscv Tx Laser Temperature
         is higher than the threshold value 
        written in the Trscv EEPROM <Help> 
        Alarm indicating that the Trscv 
        Tx Laser Temperature is higher
         than the threshold value written 
        in the Trscv EEPROM <Condtype>
         LINE_LASER_TEMP_HIGH_ALARM <Probcause> 
        temperatureUnacceptable (51) <Alarmtype> 
        equipmentAlarm (5) <Polarity> (2) 
        "
	::= { pmo10010AlmlineNetworkLaneAlarmWarning1Entry 9 }


pmo10010AlmLineLaserTempHighWarningPortn OBJECT-TYPE
	SYNTAX  EkiOnOff
	MAX-ACCESS read-only
	STATUS current
	DESCRIPTION
        "
        Line Trscv Tx Laser Temp High
         Warning :This OID indicates that 
        the Trscv Tx Laser Temperature
         is higher than the threshold value 
        written in the Trscv EEPROM <Help> 
        Warning indicating that the Trscv 
        Tx Laser Temperature is higher
         than the threshold value written 
        in the Trscv EEPROM <Condtype>
         LINE_LASER_TEMP_HIGH_WARNING <Probcause> 
        temperatureUnacceptable (51) <Alarmtype> 
        equipmentAlarm (5) <Polarity> (2) 
        "
	::= { pmo10010AlmlineNetworkLaneAlarmWarning1Entry 8 }


pmo10010AlmLineLaserTempLowWarningPortn OBJECT-TYPE
	SYNTAX  EkiOnOff
	MAX-ACCESS read-only
	STATUS current
	DESCRIPTION
        "
        Line Trscv Tx Laser Temp Low Warning 
        :This OID indicates that the Trscv 
        Tx Laser Temperature is lower than 
        the threshold value written in
         the Trscv EEPROM <Help> Warning 
        indicating that the Trscv Tx Laser 
        Temperature is lower than the threshold 
        value written in the Trscv EEPROM 
        <Condtype> LINE_LASER_TEMP_LOW_WARNING 
        <Probcause> temperatureUnacceptable 
        (51) <Alarmtype> equipmentAlarm 
        (5) <Polarity> (2) 
        "
	::= { pmo10010AlmlineNetworkLaneAlarmWarning1Entry 7 }


pmo10010AlmLineLaserTempLowAlarmPortn OBJECT-TYPE
	SYNTAX  EkiOnOff
	MAX-ACCESS read-only
	STATUS current
	DESCRIPTION
        "
        Line Trscv Tx Laser Temp Low Alarm 
        :This OID indicates that the Trscv 
        Tx Laser Temperature is lower than 
        the threshold value written in
         the Trscv EEPROM <Help> Alarm
         indicating that the Trscv Tx Laser 
        Temperature is lower than the threshold 
        value written in the Trscv EEPROM 
        <Condtype> LINE_LASER_TEMP_LOW_ALARM 
        <Probcause> temperatureUnacceptable 
        (51) <Alarmtype> equipmentAlarm 
        (5) <Polarity> (2) 
        "
	::= { pmo10010AlmlineNetworkLaneAlarmWarning1Entry 6 }


pmo10010AlmLineRxPowerHighAlarmPortn OBJECT-TYPE
	SYNTAX  EkiOnOff
	MAX-ACCESS read-only
	STATUS current
	DESCRIPTION
        "
        Line Trscv Rx Power High Alarm 
        :This OID indicates that the Trscv 
        input power is higher than the
         threshold value written in the 
        Trscv EEPROM <Help> Alarm indicating 
        that the Trscv input power is higher 
        than the threshold value written 
        in the Trscv EEPROM <Condtype>
         LINE_RX_POWER_HIGH_ALARM <Probcause> 
        receiveFailure (41) <Alarmtype> 
        equipmentAlarm (5) <Polarity> (2) 
        "
	::= { pmo10010AlmlineNetworkLaneAlarmWarning1Entry 5 }


pmo10010AlmLineRxPowerHighWarningPortn OBJECT-TYPE
	SYNTAX  EkiOnOff
	MAX-ACCESS read-only
	STATUS current
	DESCRIPTION
        "
        Line Trscv Rx Power High Warning 
        :This OID indicates that the Trscv 
        input power is higher than the
         threshold value written in the 
        Trscv EEPROM <Help> Warning indicating 
        that the Trscv input power is higher 
        than the threshold value written 
        in the Trscv EEPROM <Condtype>
         LINE_RX_POWER_HIGH_WARNING <Probcause> 
        receiveFailure (41) <Alarmtype> 
        equipmentAlarm (5) <Polarity> (2) 
        "
	::= { pmo10010AlmlineNetworkLaneAlarmWarning1Entry 4 }


pmo10010AlmLineRxPowerLowWarningPortn OBJECT-TYPE
	SYNTAX  EkiOnOff
	MAX-ACCESS read-only
	STATUS current
	DESCRIPTION
        "
        Line Trscv Rx Power Low Warning 
        :This OID indicates that the Trscv 
        input power is lower than the threshold 
        value written in the Trscv EEPROM 
        <Help> Warning indicating that
         the Trscv input power is lower 
        than the threshold value written 
        in the Trscv EEPROM <Condtype>
         LINE_RX_POWER_LOW_WARNING <Probcause> 
        receiveFailure (41) <Alarmtype> 
        equipmentAlarm (5) <Polarity> (2) 
        "
	::= { pmo10010AlmlineNetworkLaneAlarmWarning1Entry 3 }


pmo10010AlmLineRxPowerLowAlarmPortn OBJECT-TYPE
	SYNTAX  EkiOnOff
	MAX-ACCESS read-only
	STATUS current
	DESCRIPTION
        "
        Line Trscv Rx Power Low Alarm
         :This OID indicates that the Trscv 
        input power is lower than the threshold 
        value written in the Trscv EEPROM 
        <Help> Alarm indicating that the 
        Trscv input power is lower than 
        the threshold value written in
         the Trscv EEPROM <Condtype> LINE_RX_POWER_LOW_ALARM 
        <Probcause> receiveFailure (41) 
        <Alarmtype> equipmentAlarm (5)
         <Polarity> (2) 
        "
	::= { pmo10010AlmlineNetworkLaneAlarmWarning1Entry 2 }


--- *********************************************************
---     TABLE for the pmo10010AlmlineNetworkLaneAlarmWarning2 articles
--- *********************************************************

pmo10010AlmlineNetworkLaneAlarmWarning2Table OBJECT-TYPE
	SYNTAX  SEQUENCE OF Pmo10010AlmlineNetworkLaneAlarmWarning2Entry
	MAX-ACCESS not-accessible
	STATUS current
	DESCRIPTION
        "
        List of pmo10010AlmlineNetworkLaneAlarmWarning2 
        Article
        "
	::= { pmo10010AlmLineNurg 120 }


pmo10010AlmlineNetworkLaneAlarmWarning2Entry OBJECT-TYPE
	SYNTAX Pmo10010AlmlineNetworkLaneAlarmWarning2Entry
	MAX-ACCESS not-accessible
	STATUS current
	DESCRIPTION
        "
        Row definition for the pmo10010AlmlineNetworkLaneAlarmWarning2 
        table
        "
	INDEX   { pmo10010AlmlineNetworkLaneAlarmWarning2Index }
	::= { pmo10010AlmlineNetworkLaneAlarmWarning2Table 1 }


Pmo10010AlmlineNetworkLaneAlarmWarning2Entry ::=
	SEQUENCE {
	pmo10010AlmlineNetworkLaneAlarmWarning2Index
		INTEGER,
	pmo10010AlmRxLaserBiasHighAlarmPortn
		EkiOnOff,
	pmo10010AlmRxLaserBiasHighWarningPortn
		EkiOnOff,
	pmo10010AlmRxLaserBiasLowWarningPortn
		EkiOnOff,
	pmo10010AlmRxLaserBiasLowAlarmPortn
		EkiOnOff,
	pmo10010AlmRxLaserOutputHighAlarmPortn
		EkiOnOff,
	pmo10010AlmRxLaserOutputHighWarningPortn
		EkiOnOff,
	pmo10010AlmRxLaserOutputLowWarningPortn
		EkiOnOff,
	pmo10010AlmRxLaserOutputLowAlarmPortn
		EkiOnOff,
	pmo10010AlmRxLaserTempHighAlarmPortn
		EkiOnOff,
	pmo10010AlmRxLaserTempHighWarningPortn
		EkiOnOff,
	pmo10010AlmRxLaserTempLowWarningPortn
		EkiOnOff,
	pmo10010AlmRxLaserTempLowAlarmPortn
		EkiOnOff,
	pmo10010AlmTxModulatorBiasHighAlarmPortn
		EkiOnOff,
	pmo10010AlmTxModulatorBiasHighWarningPortn
		EkiOnOff,
	pmo10010AlmTxModulatorBiasLowWarningPortn
		EkiOnOff,
	pmo10010AlmTxModulatorBiasLowAlarmPortn
		EkiOnOff
	}


pmo10010AlmlineNetworkLaneAlarmWarning2Index OBJECT-TYPE
	SYNTAX  INTEGER(0..128)
	MAX-ACCESS  read-only
	STATUS current
	DESCRIPTION
        "
        Index definition for the pmo10010AlmlineNetworkLaneAlarmWarning2 
        table
        "
	::= { pmo10010AlmlineNetworkLaneAlarmWarning2Entry 1 }


pmo10010AlmRxLaserBiasHighAlarmPortn OBJECT-TYPE
	SYNTAX  EkiOnOff
	MAX-ACCESS read-only
	STATUS current
	DESCRIPTION
        "
        Line Trscv Rx Bias High Alarm
         :This OID indicates that the Trscv 
        Rx laser bias current is higher 
        than the threshold value written 
        in the Trscv EEPROM <Help> Alarm 
        indicating that the Trscv Rx laser 
        bias current is higher than the 
        threshold value written in the
         Trscv EEPROM <Condtype> RX_LASER_BIAS_HIGH_ALARM 
        <Probcause> receiveFailure (41) 
        <Alarmtype> equipmentAlarm (5)
         <Polarity> (2) 
        "
	::= { pmo10010AlmlineNetworkLaneAlarmWarning2Entry 17 }


pmo10010AlmRxLaserBiasHighWarningPortn OBJECT-TYPE
	SYNTAX  EkiOnOff
	MAX-ACCESS read-only
	STATUS current
	DESCRIPTION
        "
        Line Trscv Rx Bias High Warning 
        :This OID indicates that the Trscv 
        Rx laser bias current is higher 
        than the threshold value written 
        in the Trscv EEPROM <Help> Warning 
        indicating that the Trscv Rx laser 
        bias current is higher than the 
        threshold value written in the
         Trscv EEPROM <Condtype> RX_LASER_BIAS_HIGH_WARNING 
        <Probcause> receiveFailure (41) 
        <Alarmtype> equipmentAlarm (5)
         <Polarity> (2) 
        "
	::= { pmo10010AlmlineNetworkLaneAlarmWarning2Entry 16 }


pmo10010AlmRxLaserBiasLowWarningPortn OBJECT-TYPE
	SYNTAX  EkiOnOff
	MAX-ACCESS read-only
	STATUS current
	DESCRIPTION
        "
        Line Trscv Rx Bias Low Warning 
        :This OID indicates that the Trscv 
        Rx laser bias current is lower
         than the threshold value written 
        in the Trscv EEPROM <Help> Warning 
        indicating that the Trscv Rx laser 
        bias current is lower than the
         threshold value written in the 
        Trscv EEPROM <Condtype> RX_LASER_BIAS_LOW_WARNING 
        <Probcause> receiveFailure (41) 
        <Alarmtype> equipmentAlarm (5)
         <Polarity> (2) 
        "
	::= { pmo10010AlmlineNetworkLaneAlarmWarning2Entry 15 }


pmo10010AlmRxLaserBiasLowAlarmPortn OBJECT-TYPE
	SYNTAX  EkiOnOff
	MAX-ACCESS read-only
	STATUS current
	DESCRIPTION
        "
        Line Trscv Rx Bias Low Alarm :This 
        OID indicates that the Trscv Rx 
        laser bias current is lower than 
        the threshold value written in
         the Trscv EEPROM <Help> Alarm
         indicating that the Trscv Rx laser 
        bias current is lower than the
         threshold value written in the 
        Trscv EEPROM <Condtype> RX_LASER_BIAS_LOW_ALARM 
        <Probcause> receiveFailure (41) 
        <Alarmtype> equipmentAlarm (5)
         <Polarity> (2) 
        "
	::= { pmo10010AlmlineNetworkLaneAlarmWarning2Entry 14 }


pmo10010AlmRxLaserOutputHighAlarmPortn OBJECT-TYPE
	SYNTAX  EkiOnOff
	MAX-ACCESS read-only
	STATUS current
	DESCRIPTION
        "
        Line Trscv Rx Output Power High 
        Alarm :This OID indicates that
         the Trscv Rx output power is higher 
        than the threshold value written 
        in the Trscv EEPROM <Help> Alarm 
        indicating that the Trscv Rx output 
        power is higher than the threshold 
        value written in the Trscv EEPROM 
        <Condtype> RX_LASER_OUTPUT_HIGH_ALARM 
        <Probcause> receiveFailure (41) 
        <Alarmtype> equipmentAlarm (5)
         <Polarity> (2) 
        "
	::= { pmo10010AlmlineNetworkLaneAlarmWarning2Entry 13 }


pmo10010AlmRxLaserOutputHighWarningPortn OBJECT-TYPE
	SYNTAX  EkiOnOff
	MAX-ACCESS read-only
	STATUS current
	DESCRIPTION
        "
        Line Trscv Rx Output Power High 
        Warning :This OID indicates that 
        the Trscv Rx output power is higher 
        than the threshold value written 
        in the Trscv EEPROM <Help> Warning 
        indicating that the Trscv Rx output 
        power is higher than the threshold 
        value written in the Trscv EEPROM 
        <Condtype> RX_LASER_OUTPUT_HIGH_WARNING 
        <Probcause> receiveFailure (41) 
        <Alarmtype> equipmentAlarm (5)
         <Polarity> (2) 
        "
	::= { pmo10010AlmlineNetworkLaneAlarmWarning2Entry 12 }


pmo10010AlmRxLaserOutputLowWarningPortn OBJECT-TYPE
	SYNTAX  EkiOnOff
	MAX-ACCESS read-only
	STATUS current
	DESCRIPTION
        "
        Line Trscv Rx Output Power Low 
        Warning :This OID indicates that 
        the Trscv Rx output power is lower 
        than the threshold value written 
        in the Trscv EEPROM <Help> Warning 
        indicating that the Trscv Rx output 
        power is lower than the threshold 
        value written in the Trscv EEPROM 
        <Condtype> RX_LASER_OUTPUT_LOW_WARNING 
        <Probcause> receiveFailure (41) 
        <Alarmtype> equipmentAlarm (5)
         <Polarity> (2) 
        "
	::= { pmo10010AlmlineNetworkLaneAlarmWarning2Entry 11 }


pmo10010AlmRxLaserOutputLowAlarmPortn OBJECT-TYPE
	SYNTAX  EkiOnOff
	MAX-ACCESS read-only
	STATUS current
	DESCRIPTION
        "
        Line Trscv Rx Output Power Low 
        Alarm :This OID indicates that
         the Trscv Rx output power is lower 
        than the threshold value written 
        in the Trscv EEPROM <Help> Alarm 
        indicating that the Trscv Rx output 
        power is lower than the threshold 
        value written in the Trscv EEPROM 
        <Condtype> RX_LASER_OUTPUT_LOW_ALARM 
        <Probcause> receiveFailure (41) 
        <Alarmtype> equipmentAlarm (5)
         <Polarity> (2) 
        "
	::= { pmo10010AlmlineNetworkLaneAlarmWarning2Entry 10 }


pmo10010AlmRxLaserTempHighAlarmPortn OBJECT-TYPE
	SYNTAX  EkiOnOff
	MAX-ACCESS read-only
	STATUS current
	DESCRIPTION
        "
        Line Trscv Rx Laser Temp High
         Alarm :This OID indicates that 
        the Trscv Rx Laser Temperature
         is higher than the threshold value 
        written in the Trscv EEPROM <Help> 
        Alarm indicating that the Trscv 
        Rx Laser Temperature is higher
         than the threshold value written 
        in the Trscv EEPROM <Condtype>
         RX_LASER_TEMP_HIGH_ALARM <Probcause> 
        temperatureUnacceptable (51) <Alarmtype> 
        equipmentAlarm (5) <Polarity> (2) 
        "
	::= { pmo10010AlmlineNetworkLaneAlarmWarning2Entry 9 }


pmo10010AlmRxLaserTempHighWarningPortn OBJECT-TYPE
	SYNTAX  EkiOnOff
	MAX-ACCESS read-only
	STATUS current
	DESCRIPTION
        "
        Line Trscv Rx Laser Temp High
         Warning :This OID indicates that 
        the Trscv Rx Laser Temperature
         is higher than the threshold value 
        written in the Trscv EEPROM <Help> 
        Warning indicating that the Trscv 
        Rx Laser Temperature is higher
         than the threshold value written 
        in the Trscv EEPROM <Condtype>
         RX_LASER_TEMP_HIGH_WARNING <Probcause> 
        temperatureUnacceptable (51) <Alarmtype> 
        equipmentAlarm (5) <Polarity> (2) 
        "
	::= { pmo10010AlmlineNetworkLaneAlarmWarning2Entry 8 }


pmo10010AlmRxLaserTempLowWarningPortn OBJECT-TYPE
	SYNTAX  EkiOnOff
	MAX-ACCESS read-only
	STATUS current
	DESCRIPTION
        "
        Line Trscv Rx Laser Temp Low Warning 
        :This OID indicates that the Trscv 
        Rx Laser Temperature is lower than 
        the threshold value written in
         the Trscv EEPROM <Help> Warning 
        indicating that the Trscv Rx Laser 
        Temperature is lower than the threshold 
        value written in the Trscv EEPROM 
        <Condtype> RX_LASER_TEMP_LOW_WARNING 
        <Probcause> temperatureUnacceptable 
        (51) <Alarmtype> equipmentAlarm 
        (5) <Polarity> (2) 
        "
	::= { pmo10010AlmlineNetworkLaneAlarmWarning2Entry 7 }


pmo10010AlmRxLaserTempLowAlarmPortn OBJECT-TYPE
	SYNTAX  EkiOnOff
	MAX-ACCESS read-only
	STATUS current
	DESCRIPTION
        "
        Line Trscv Rx Laser Temp Low Alarm 
        :This OID indicates that the Trscv 
        Rx Laser Temperature is lower than 
        the threshold value written in
         the Trscv EEPROM <Help> Alarm
         indicating that the Trscv Rx Laser 
        Temperature is lower than the threshold 
        value written in the Trscv EEPROM 
        <Condtype> RX_LASER_TEMP_LOW_ALARM 
        <Probcause> temperatureUnacceptable 
        (51) <Alarmtype> equipmentAlarm 
        (5) <Polarity> (2) 
        "
	::= { pmo10010AlmlineNetworkLaneAlarmWarning2Entry 6 }


pmo10010AlmTxModulatorBiasHighAlarmPortn OBJECT-TYPE
	SYNTAX  EkiOnOff
	MAX-ACCESS read-only
	STATUS current
	DESCRIPTION
        "
        Line Trscv Tx Modulator Bias High 
        Alarm :This OID indicates that
         the Trscv Tx modulator bias current 
        is higher than the threshold value 
        written in the Trscv EEPROM <Help> 
        Alarm indicating that the Trscv 
        Tx modulator bias current is higher 
        than the threshold value written 
        in the Trscv EEPROM <Condtype>
         TX_MODULATOR_BIAS_HIGH_ALARM <Probcause> 
        transmitterFailure (56) <Alarmtype> 
        equipmentAlarm (5) <Polarity> (2) 
        "
	::= { pmo10010AlmlineNetworkLaneAlarmWarning2Entry 5 }


pmo10010AlmTxModulatorBiasHighWarningPortn OBJECT-TYPE
	SYNTAX  EkiOnOff
	MAX-ACCESS read-only
	STATUS current
	DESCRIPTION
        "
        Line Trscv Tx Modulator Bias High 
        Warning :This OID indicates that 
        the Trscv Tx modulator bias current 
        is higher than the threshold value 
        written in the Trscv EEPROM <Help> 
        Warning indicating that the Trscv 
        Tx modulator bias current is higher 
        than the threshold value written 
        in the Trscv EEPROM <Condtype>
         TX_MODULATOR_BIAS_HIGH_WARNING 
        <Probcause> transmitterFailure
         (56) <Alarmtype> equipmentAlarm 
        (5) <Polarity> (2) 
        "
	::= { pmo10010AlmlineNetworkLaneAlarmWarning2Entry 4 }


pmo10010AlmTxModulatorBiasLowWarningPortn OBJECT-TYPE
	SYNTAX  EkiOnOff
	MAX-ACCESS read-only
	STATUS current
	DESCRIPTION
        "
        Line Trscv Tx Modulator Bias Low 
        Warning :This OID indicates that 
        the Trscv Tx modulator bias current 
        is lower than the threshold value 
        written in the Trscv EEPROM <Help> 
        Warning indicating that the Trscv 
        Tx modulator bias current is lower 
        than the threshold value written 
        in the Trscv EEPROM <Condtype>
         TX_MODULATOR_BIAS_LOW_WARNING
         <Probcause> transmitterFailure 
        (56) <Alarmtype> equipmentAlarm 
        (5) <Polarity> (2) 
        "
	::= { pmo10010AlmlineNetworkLaneAlarmWarning2Entry 3 }


pmo10010AlmTxModulatorBiasLowAlarmPortn OBJECT-TYPE
	SYNTAX  EkiOnOff
	MAX-ACCESS read-only
	STATUS current
	DESCRIPTION
        "
        Line Trscv Tx Modulator Bias Low 
        Alarm :This OID indicates that
         the Trscv Tx modulator bias current 
        is lower than the threshold value 
        written in the Trscv EEPROM <Help> 
        Alarm indicating that the Trscv 
        Tx modulator bias current is lower 
        than the threshold value written 
        in the Trscv EEPROM <Condtype>
         TX_MODULATOR_BIAS_LOW_ALARM <Probcause> 
        transmitterFailure (56) <Alarmtype> 
        equipmentAlarm (5) <Polarity> (2) 
        "
	::= { pmo10010AlmlineNetworkLaneAlarmWarning2Entry 2 }


--- *********************************************************
---     TABLE for the pmo10010AlmlineNetworkLaneFault articles
--- *********************************************************

pmo10010AlmlineNetworkLaneFaultTable OBJECT-TYPE
	SYNTAX  SEQUENCE OF Pmo10010AlmlineNetworkLaneFaultEntry
	MAX-ACCESS not-accessible
	STATUS current
	DESCRIPTION
        "
        List of pmo10010AlmlineNetworkLaneFault 
        Article
        "
	::= { pmo10010AlmLineUrg 136 }


pmo10010AlmlineNetworkLaneFaultEntry OBJECT-TYPE
	SYNTAX Pmo10010AlmlineNetworkLaneFaultEntry
	MAX-ACCESS not-accessible
	STATUS current
	DESCRIPTION
        "
        Row definition for the pmo10010AlmlineNetworkLaneFault 
        table
        "
	INDEX   { pmo10010AlmlineNetworkLaneFaultIndex }
	::= { pmo10010AlmlineNetworkLaneFaultTable 1 }


Pmo10010AlmlineNetworkLaneFaultEntry ::=
	SEQUENCE {
	pmo10010AlmlineNetworkLaneFaultIndex
		INTEGER,
	pmo10010AlmLineLaneTecFaultPortn
		EkiOnOff,
	pmo10010AlmLineLaneWavelengthUnlockedPortn
		EkiOnOff,
	pmo10010AlmLineLaneApdPowerSupplyPortn
		EkiOnOff,
	pmo10010AlmLineLaneTxLosfPortn
		EkiOnOff,
	pmo10010AlmLineLaneTxLolPortn
		EkiOnOff,
	pmo10010AlmLineLaneRxLosPortn
		EkiOnOff,
	pmo10010AlmLineLaneRxLolPortn
		EkiOnOff,
	pmo10010AlmLineLaneRxFifoErrorPortn
		EkiOnOff,
	pmo10010AlmLineLaneRxTecFaultPortn
		EkiOnOff
	}


pmo10010AlmlineNetworkLaneFaultIndex OBJECT-TYPE
	SYNTAX  INTEGER(0..128)
	MAX-ACCESS  read-only
	STATUS current
	DESCRIPTION
        "
        Index definition for the pmo10010AlmlineNetworkLaneFault 
        table
        "
	::= { pmo10010AlmlineNetworkLaneFaultEntry 1 }


pmo10010AlmLineLaneTecFaultPortn OBJECT-TYPE
	SYNTAX  EkiOnOff
	MAX-ACCESS read-only
	STATUS current
	DESCRIPTION
        "
        Line Network Lane TEC Fault :This 
        OID indicates a Tx TEC Fault on 
        the Line Trscv Network Lane <Help> 
        Alarm indicating a Tx TEC Fault 
        on the Line Trscv Network Lane
         <Condtype> LINE_LANE_TEC_FAULT 
        <Probcause> transmitterFailure
         (56) <Alarmtype> equipmentAlarm 
        (5) <Polarity> (2) 
        "
	::= { pmo10010AlmlineNetworkLaneFaultEntry 17 }


pmo10010AlmLineLaneWavelengthUnlockedPortn OBJECT-TYPE
	SYNTAX  EkiOnOff
	MAX-ACCESS read-only
	STATUS current
	DESCRIPTION
        "
        Line Network Lane Wavelength Unlock 
        :This OID indicates a Wavelength 
        unlock on the Line Trscv Network 
        Lane <Help> Alarm indicating a
         Wavelength unlock on the Line
         Trscv Network Lane <Condtype>
         LINE_LANE_WAVELENGTH_UNLOCKED
         <Probcause> transmitterFailure 
        (56) <Alarmtype> equipmentAlarm 
        (5) <Polarity> (2) 
        "
	::= { pmo10010AlmlineNetworkLaneFaultEntry 16 }


pmo10010AlmLineLaneApdPowerSupplyPortn OBJECT-TYPE
	SYNTAX  EkiOnOff
	MAX-ACCESS read-only
	STATUS current
	DESCRIPTION
        "
        Line Network Lane APD Power Supply 
        :This OID indicates an APD Power 
        supply failure on the Line Trscv 
        Network Lane <Help> Alarm indicating 
        an APD Power supply failure on
         the Line Trscv Network Lane <Condtype> 
        LINE_LANE_APD_POWER_SUPPLY <Probcause> 
        transmitterFailure (56) <Alarmtype> 
        equipmentAlarm (5) <Polarity> (2) 
        "
	::= { pmo10010AlmlineNetworkLaneFaultEntry 15 }


pmo10010AlmLineLaneTxLosfPortn OBJECT-TYPE
	SYNTAX  EkiOnOff
	MAX-ACCESS read-only
	STATUS current
	DESCRIPTION
        "
        Line Network Lane Tx Loss Of Signal 
        Functionality :This OID indicates 
        a Tx Loss of Signal Functionality 
        on the Line Trscv Network Lane
         <Help> Alarm indicating a Tx Loss 
        of Signal Functionality on the
         Line Trscv Network Lane <Condtype> 
        LINE_LANE_TX_LOSF <Probcause> transmitterFailure 
        (56) <Alarmtype> equipmentAlarm 
        (5) <Polarity> (2) 
        "
	::= { pmo10010AlmlineNetworkLaneFaultEntry 9 }


pmo10010AlmLineLaneTxLolPortn OBJECT-TYPE
	SYNTAX  EkiOnOff
	MAX-ACCESS read-only
	STATUS current
	DESCRIPTION
        "
        Line Network Lane Tx Loss Of Lock 
        :This OID indicates a Tx Loss of 
        Lock on the Line Trscv Network
         Lane <Help> Alarm indicating a 
        Tx Loss of Lock on the Line Trscv 
        Network Lane <Condtype> LINE_LANE_TX_LOL 
        <Probcause> transmitterFailure
         (56) <Alarmtype> equipmentAlarm 
        (5) <Polarity> (2) 
        "
	::= { pmo10010AlmlineNetworkLaneFaultEntry 8 }


pmo10010AlmLineLaneRxLosPortn OBJECT-TYPE
	SYNTAX  EkiOnOff
	MAX-ACCESS read-only
	STATUS current
	DESCRIPTION
        "
        Line Network Lane Rx Loss Of Signal 
        :This OID indicates a Rx Loss of 
        Signal on the Line Trscv Network 
        Lane <Help> Alarm indicating a
         Rx Loss of Signal on the Line
         Trscv Network Lane <Condtype>
         LINE_LANE_RX_LOS <Probcause> receiveFailure 
        (41) <Alarmtype> physicalViolation 
        (9) <Polarity> (2) 
        "
	::= { pmo10010AlmlineNetworkLaneFaultEntry 6 }


pmo10010AlmLineLaneRxLolPortn OBJECT-TYPE
	SYNTAX  EkiOnOff
	MAX-ACCESS read-only
	STATUS current
	DESCRIPTION
        "
        Line Network Lane Rx Loss Of Lock 
        :This OID indicates a Rx Loss of 
        Lock on the Line Trscv Network
         Lane <Help> Alarm indicating a 
        Rx Loss of Lock on the Line Trscv 
        Network Lane <Condtype> LINE_LANE_RX_LOL 
        <Probcause> receiverFailure (42) 
        <Alarmtype> equipmentAlarm (5)
         <Polarity> (2) 
        "
	::= { pmo10010AlmlineNetworkLaneFaultEntry 5 }


pmo10010AlmLineLaneRxFifoErrorPortn OBJECT-TYPE
	SYNTAX  EkiOnOff
	MAX-ACCESS read-only
	STATUS current
	DESCRIPTION
        "
        Line Network Lane Rx FIFO Error 
        :This OID indicates a Rx FIFO Error 
        on the Line Trscv Network Lane
         <Help> Alarm indicating a Rx FIFO 
        Error on the Line Trscv Network 
        Lane <Condtype> LINE_LANE_RX_FIFO_ERROR 
        <Probcause> receiverFailure (42) 
        <Alarmtype> equipmentAlarm (5)
         <Polarity> (2) 
        "
	::= { pmo10010AlmlineNetworkLaneFaultEntry 4 }


pmo10010AlmLineLaneRxTecFaultPortn OBJECT-TYPE
	SYNTAX  EkiOnOff
	MAX-ACCESS read-only
	STATUS current
	DESCRIPTION
        "
        Line Network Lane Rx TEC Fault 
        :This OID indicates a Rx TEC Fault 
        on the Line Trscv Network Lane
         <Help> Alarm indicating a Rx TEC 
        Fault on the Line Trscv Network 
        Lane <Condtype> LINE_LANE_RX_TEC_FAULT 
        <Probcause> receiverFailure (42) 
        <Alarmtype> equipmentAlarm (5)
         <Polarity> (2) 
        "
	::= { pmo10010AlmlineNetworkLaneFaultEntry 3 }


--- *********************************************************
---     TABLE for the pmo10010AlmlineOtu4Alarm articles
--- *********************************************************

pmo10010AlmlineOtu4AlarmTable OBJECT-TYPE
	SYNTAX  SEQUENCE OF Pmo10010AlmlineOtu4AlarmEntry
	MAX-ACCESS not-accessible
	STATUS current
	DESCRIPTION
        "
        List of pmo10010AlmlineOtu4Alarm 
        Article
        "
	::= { pmo10010AlmLineUrg 152 }


pmo10010AlmlineOtu4AlarmEntry OBJECT-TYPE
	SYNTAX Pmo10010AlmlineOtu4AlarmEntry
	MAX-ACCESS not-accessible
	STATUS current
	DESCRIPTION
        "
        Row definition for the pmo10010AlmlineOtu4Alarm 
        table
        "
	INDEX   { pmo10010AlmlineOtu4AlarmIndex }
	::= { pmo10010AlmlineOtu4AlarmTable 1 }


Pmo10010AlmlineOtu4AlarmEntry ::=
	SEQUENCE {
	pmo10010AlmlineOtu4AlarmIndex
		INTEGER,
	pmo10010AlmLineOtu4DlomPortn
		EkiOnOff,
	pmo10010AlmLineOtu4DssfPortn
		EkiOnOff,
	pmo10010AlmLineOchr4DlosPPortn
		EkiOnOff,
	pmo10010AlmLineLaneTxFifoErrorPortn
		EkiOnOff,
	pmo10010AlmLineTxHostLolPortn
		EkiOnOff,
	pmo10010AlmClientOtu4DtimPortn
		EkiOnOff,
	pmo10010AlmOtu4DdegPortn
		EkiOnOff,
	pmo10010AlmLineSmIaeDetectedPortn
		EkiOnOff,
	pmo10010AlmLineSmIaeInsertedPortn
		EkiOnOff,
	pmo10010AlmLineSmBdiDetectedPortn
		EkiOnOff,
	pmo10010AlmLineSmBdiInsertedPortn
		EkiOnOff,
	pmo10010AlmLineLossOfFramePortn
		EkiOnOff,
	pmo10010AlmLineInputLossOfSignalPortn
		EkiOnOff
	}


pmo10010AlmlineOtu4AlarmIndex OBJECT-TYPE
	SYNTAX  INTEGER(0..128)
	MAX-ACCESS  read-only
	STATUS current
	DESCRIPTION
        "
        Index definition for the pmo10010AlmlineOtu4Alarm 
        table
        "
	::= { pmo10010AlmlineOtu4AlarmEntry 1 }


pmo10010AlmLineOtu4DlomPortn OBJECT-TYPE
	SYNTAX  EkiOnOff
	MAX-ACCESS read-only
	STATUS current
	DESCRIPTION
        "
        OTU4 DLOM :This OID indicates
         that a Loss Of Multiframe has
         been detected on line port <Help> 
         This alarm indicates if a Loss 
        Of Multiframe has been detected 
        on the line port <Condtype> LINE_OTU4_DLOM 
        <Probcause> equipmentMalfunction(16) 
        <Alarmtype> equipmentAlarm (5)
         <Polarity> (2) 
        "
	::= { pmo10010AlmlineOtu4AlarmEntry 17 }


pmo10010AlmLineOtu4DssfPortn OBJECT-TYPE
	SYNTAX  EkiOnOff
	MAX-ACCESS read-only
	STATUS current
	DESCRIPTION
        "
        OTU4 DSSF :This OID indicates
         that a Server Signal failure has 
        been detected on line port <Help> 
         This alarm indicates if a Server 
        Signal Failure has been detected 
        on the line port <Condtype> LINE_OTU4_DSSF 
        <Probcause> other(1) <Alarmtype> 
        equipmentAlarm (5) <Polarity> (2) 
        "
	::= { pmo10010AlmlineOtu4AlarmEntry 16 }


pmo10010AlmLineOchr4DlosPPortn OBJECT-TYPE
	SYNTAX  EkiOnOff
	MAX-ACCESS read-only
	STATUS current
	DESCRIPTION
        "
        Ochr4 - DLOS-P :This OID indicates 
        that a Transmitter failure has
         been detected on line port <Help> 
         This alarm indicates if a Transmitter 
        Failure has been detected on the 
        line port <Condtype> LINE_OCHR4_DLOS_P 
        <Probcause> equipmentMalfunction(16) 
        <Alarmtype> other (1) <Polarity> 
        (2) 
        "
	::= { pmo10010AlmlineOtu4AlarmEntry 12 }


pmo10010AlmLineLaneTxFifoErrorPortn OBJECT-TYPE
	SYNTAX  EkiOnOff
	MAX-ACCESS read-only
	STATUS current
	DESCRIPTION
        "
        Line Host Lane Tx FIFO Error :This 
        OID indicates a Tx FIFO Error on 
        the Line Trscv Host Lane <Help> 
        Alarm indicating a Tx FIFO Error 
        on the Line Trscv Host Lane <Condtype> 
        LINE_LANE_TX_FIFO_ERROR <Probcause> 
        receiverFailure (42) <Alarmtype> 
        equipmentAlarm (5) <Polarity> (2) 
        "
	::= { pmo10010AlmlineOtu4AlarmEntry 11 }


pmo10010AlmLineTxHostLolPortn OBJECT-TYPE
	SYNTAX  EkiOnOff
	MAX-ACCESS read-only
	STATUS current
	DESCRIPTION
        "
        Line Host Lane Tx Loss Of Lock 
        :This OID indicates a Tx Loss of 
        Lock on the Line Trscv Host Lane 
        <Help> Alarm indicating a Tx Loss 
        of Lock on the Line Trscv Host
         Lane <Condtype> LINE_TX_HOST_LOL 
        <Probcause> receiverFailure (42) 
        <Alarmtype> equipmentAlarm (5)
         <Polarity> (2) 
        "
	::= { pmo10010AlmlineOtu4AlarmEntry 10 }


pmo10010AlmClientOtu4DtimPortn OBJECT-TYPE
	SYNTAX  EkiOnOff
	MAX-ACCESS read-only
	STATUS current
	DESCRIPTION
        "
        OTU4 DTIM :This OID indicates
         that a Trace Identifier Mismatch 
        has been detected on line port
         <Help>  This alarm indicates if 
        a Trace Identifier Mismatch has 
        been detected on the line port
         <Condtype> CLIENT_OTU4_DTIM <Probcause> 
        other(1) <Alarmtype> other (1)
         <Polarity> (2) 
        "
	::= { pmo10010AlmlineOtu4AlarmEntry 9 }


pmo10010AlmOtu4DdegPortn OBJECT-TYPE
	SYNTAX  EkiOnOff
	MAX-ACCESS read-only
	STATUS current
	DESCRIPTION
        "
        OTU4 DDEG :This OID indicates
         that a Signal Degrade has been 
        detected on line port <Help>  This 
        alarm indicates if a Signal Degrade 
        has been detected upon threshold 
        and confirmation parameters on
         the line port <Condtype> OTU4_DDEG 
        <Probcause> degradedSignal(13)
         <Alarmtype> other (1) <Polarity> 
        (2) 
        "
	::= { pmo10010AlmlineOtu4AlarmEntry 8 }


pmo10010AlmLineSmIaeDetectedPortn OBJECT-TYPE
	SYNTAX  EkiOnOff
	MAX-ACCESS read-only
	STATUS current
	DESCRIPTION
        "
        Line SM IAE Detected :This OID 
        indicates a SM Incoming Alignment 
        Error is detected on the incoming 
        Line signal <Help> Alarm indicating 
        a SM Incoming Alignment Error is 
        detected on the incoming Line signal 
        <Condtype> LINE_SM_IAE_DETECTED 
        <Probcause> receiveFailure (41) 
        <Alarmtype> equipmentAlarm (5)
         <Polarity> (2) 
        "
	::= { pmo10010AlmlineOtu4AlarmEntry 7 }


pmo10010AlmLineSmIaeInsertedPortn OBJECT-TYPE
	SYNTAX  EkiOnOff
	MAX-ACCESS read-only
	STATUS current
	DESCRIPTION
        "
        Line SM IAE Inserted :This OID 
        indicates a SM Incoming Alignment 
        Error is inserted on the outgoing 
        Line signal <Help> Status indicating 
        a SM Incoming Alignment Error is 
        inserted on the outgoing Line signal 
        <Condtype> LINE_SM_IAE_INSERTED 
        <Probcause> informationalStatus(1000) 
        <Alarmtype> equipmentAlarm (5)
         <Polarity> (2) 
        "
	::= { pmo10010AlmlineOtu4AlarmEntry 6 }


pmo10010AlmLineSmBdiDetectedPortn OBJECT-TYPE
	SYNTAX  EkiOnOff
	MAX-ACCESS read-only
	STATUS current
	DESCRIPTION
        "
        OTU4 DBDI :This OID indicates
         a SM Backward Defect Indication 
        is detected on the incoming Line 
        signal <Help> Alarm indicating
         a SM Backward Defect Indication 
        is detected on the incoming Line 
        signal <Condtype> LINE_SM_BDI_DETECTED 
        <Probcause> receiveFailure (41) 
        <Alarmtype> equipmentAlarm (5)
         <Polarity> (2) 
        "
	::= { pmo10010AlmlineOtu4AlarmEntry 5 }


pmo10010AlmLineSmBdiInsertedPortn OBJECT-TYPE
	SYNTAX  EkiOnOff
	MAX-ACCESS read-only
	STATUS current
	DESCRIPTION
        "
        OTU4 IBDI :This OID indicates
         a SM Backward Defect Indication 
        is inserted on the outgoing Line 
        signal <Help> Status indicating 
        a SM Backward Defect Indication 
        is inserted on the outgoing Line 
        signal <Condtype> LINE_SM_BDI_INSERTED 
        <Probcause> informationalStatus(1000) 
        <Alarmtype> equipmentAlarm (5)
         <Polarity> (2) 
        "
	::= { pmo10010AlmlineOtu4AlarmEntry 4 }


pmo10010AlmLineLossOfFramePortn OBJECT-TYPE
	SYNTAX  EkiOnOff
	MAX-ACCESS read-only
	STATUS current
	DESCRIPTION
        "
        OTU4 - DLOF :This OID indicates 
        the module is not aligned with
         the incoming Line signal <Help> 
        Alarm indicating the module is
         not aligned with the incoming
         Line signal <Condtype> LINE_LOSS_OF_FRAME 
        <Probcause> receiveFailure (41) 
        <Alarmtype> other (1) <Polarity> 
        (2) 
        "
	::= { pmo10010AlmlineOtu4AlarmEntry 3 }


pmo10010AlmLineInputLossOfSignalPortn OBJECT-TYPE
	SYNTAX  EkiOnOff
	MAX-ACCESS read-only
	STATUS current
	DESCRIPTION
        "
        OPS4 DLOS-P :This OID indicates 
        a Loss of Signal is detected on 
        the Line Trscv <Help> Alarm indicating 
        a Loss of Signal is detected on 
        the Line Trscv <Condtype> LINE_INPUT_LOSS_OF_SIGNAL 
        <Probcause> receiveFailure (41) 
        <Alarmtype> other (1) <Polarity> 
        (2) 
        "
	::= { pmo10010AlmlineOtu4AlarmEntry 2 }


--- *********************************************************
---     TABLE for the pmo10010AlmlineNetworkLaneRxOtn articles
--- *********************************************************

pmo10010AlmlineNetworkLaneRxOtnTable OBJECT-TYPE
	SYNTAX  SEQUENCE OF Pmo10010AlmlineNetworkLaneRxOtnEntry
	MAX-ACCESS not-accessible
	STATUS current
	DESCRIPTION
        "
        List of pmo10010AlmlineNetworkLaneRxOtn 
        Article
        "
	::= { pmo10010AlmLineUrg 168 }


pmo10010AlmlineNetworkLaneRxOtnEntry OBJECT-TYPE
	SYNTAX Pmo10010AlmlineNetworkLaneRxOtnEntry
	MAX-ACCESS not-accessible
	STATUS current
	DESCRIPTION
        "
        Row definition for the pmo10010AlmlineNetworkLaneRxOtn 
        table
        "
	INDEX   { pmo10010AlmlineNetworkLaneRxOtnIndex }
	::= { pmo10010AlmlineNetworkLaneRxOtnTable 1 }


Pmo10010AlmlineNetworkLaneRxOtnEntry ::=
	SEQUENCE {
	pmo10010AlmlineNetworkLaneRxOtnIndex
		INTEGER,
	pmo10010AlmLineRxOtnLofPortn
		EkiOnOff,
	pmo10010AlmLineRxOtnOofPortn
		EkiOnOff,
	pmo10010AlmLineRxOtnLomPortn
		EkiOnOff,
	pmo10010AlmLineRxOtnOomPortn
		EkiOnOff,
	pmo10010AlmLineRxOtnIaePortn
		EkiOnOff,
	pmo10010AlmLineRxSmBdiPortn
		EkiOnOff,
	pmo10010AlmLineRxOtnOtuAisPortn
		EkiOnOff,
	pmo10010AlmLineRxOtnOduAisPortn
		EkiOnOff
	}


pmo10010AlmlineNetworkLaneRxOtnIndex OBJECT-TYPE
	SYNTAX  INTEGER(0..128)
	MAX-ACCESS  read-only
	STATUS current
	DESCRIPTION
        "
        Index definition for the pmo10010AlmlineNetworkLaneRxOtn 
        table
        "
	::= { pmo10010AlmlineNetworkLaneRxOtnEntry 1 }


pmo10010AlmLineRxOtnLofPortn OBJECT-TYPE
	SYNTAX  EkiOnOff
	MAX-ACCESS read-only
	STATUS current
	DESCRIPTION
        "
        Line Network Rx LOF :This OID
         indicates a Loss of Frame is detected 
        on the Rx Network interface of
         the Line Trscv <Help> Alarm indicating 
        a Loss of Frame is detected on
         the Rx Network interface of the 
        Line Trscv <Condtype> LINE_RX_OTN_LOF 
        <Probcause> receiveFailure (41) 
        <Alarmtype> equipmentAlarm (5)
         <Polarity> (2) 
        "
	::= { pmo10010AlmlineNetworkLaneRxOtnEntry 17 }


pmo10010AlmLineRxOtnOofPortn OBJECT-TYPE
	SYNTAX  EkiOnOff
	MAX-ACCESS read-only
	STATUS current
	DESCRIPTION
        "
        Line Network Rx OOF :This OID
         indicates an Out of Frame is detected 
        on the Rx Network interface of
         the Line Trscv <Help> Alarm indicating 
        an Out of Frame is detected on
         the Rx Network interface of the 
        Line Trscv <Condtype> LINE_RX_OTN_OOF 
        <Probcause> receiveFailure (41) 
        <Alarmtype> equipmentAlarm (5)
         <Polarity> (2) 
        "
	::= { pmo10010AlmlineNetworkLaneRxOtnEntry 16 }


pmo10010AlmLineRxOtnLomPortn OBJECT-TYPE
	SYNTAX  EkiOnOff
	MAX-ACCESS read-only
	STATUS current
	DESCRIPTION
        "
        Line Network Rx LOM :This OID
         indicates a Loss of Multiframe 
        is detected on the Rx Network interface 
        of the Line Trscv <Help> Alarm
         indicating a Loss of Multiframe 
        is detected on the Rx Network interface 
        of the Line Trscv <Condtype> LINE_RX_OTN_LOM 
        <Probcause> receiveFailure (41) 
        <Alarmtype> equipmentAlarm (5)
         <Polarity> (2) 
        "
	::= { pmo10010AlmlineNetworkLaneRxOtnEntry 15 }


pmo10010AlmLineRxOtnOomPortn OBJECT-TYPE
	SYNTAX  EkiOnOff
	MAX-ACCESS read-only
	STATUS current
	DESCRIPTION
        "
        Line Network Rx OOM :This OID
         indicates an Out of Multiframe 
        is detected on the Rx Network interface 
        of the Line Trscv <Help> Alarm
         indicating an Out of Multiframe 
        is detected on the Rx Network interface 
        of the Line Trscv <Condtype> LINE_RX_OTN_OOM 
        <Probcause> receiveFailure (41) 
        <Alarmtype> equipmentAlarm (5)
         <Polarity> (2) 
        "
	::= { pmo10010AlmlineNetworkLaneRxOtnEntry 14 }


pmo10010AlmLineRxOtnIaePortn OBJECT-TYPE
	SYNTAX  EkiOnOff
	MAX-ACCESS read-only
	STATUS current
	DESCRIPTION
        "
        Line Network Rx IAE :This OID
         indicates an Incoming Alignment 
        Error is detected on the Rx Network 
        interface of the Line Trscv <Help> 
        Alarm indicating an Incoming Alignment 
        Error is detected on the Rx Network 
        interface of the Line Trscv <Condtype> 
        LINE_RX_OTN_IAE <Probcause> receiveFailure 
        (41) <Alarmtype> equipmentAlarm 
        (5) <Polarity> (2) 
        "
	::= { pmo10010AlmlineNetworkLaneRxOtnEntry 13 }


pmo10010AlmLineRxSmBdiPortn OBJECT-TYPE
	SYNTAX  EkiOnOff
	MAX-ACCESS read-only
	STATUS current
	DESCRIPTION
        "
        Line Network Rx SM BDI :This OID 
        indicates an SM Backward Defect 
        Indication is detected on the Rx 
        Network interface of the Line Trscv 
        <Help> Alarm indicating an SM Backward 
        Defect Indication is detected on 
        the Rx Network interface of the 
        Line Trscv <Condtype> LINE_RX_SM_BDI 
        <Probcause> informationalStatus(1000) 
        <Alarmtype> other (1) <Polarity> 
        (2) 
        "
	::= { pmo10010AlmlineNetworkLaneRxOtnEntry 12 }


pmo10010AlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of 
        the Line Trscv <Help> Alarm indicating 
        an OTU Alarm Indication Signal
         is detected on the Rx Network
         interface of the Line Trscv <Condtype> 
        LINE_RX_OTN_OTU_AIS <Probcause> 
        receiveFailure (41) <Alarmtype> 
        equipmentAlarm (5) <Polarity> (2) 
        "
	::= { pmo10010AlmlineNetworkLaneRxOtnEntry 11 }


pmo10010AlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of 
        the Line Trscv <Help> Alarm indicating 
        an ODU Alarm Indication Signal
         is detected on the Rx Network
         interface of the Line Trscv <Condtype> 
        LINE_RX_OTN_ODU_AIS <Probcause> 
        receiveFailure (41) <Alarmtype> 
        equipmentAlarm (5) <Polarity> (2) 
        "
	::= { pmo10010AlmlineNetworkLaneRxOtnEntry 10 }


--- *********************************************************
---     TABLE for the pmo10010AlmlineHostLaneTxOtn articles
--- *********************************************************

pmo10010AlmlineHostLaneTxOtnTable OBJECT-TYPE
	SYNTAX  SEQUENCE OF Pmo10010AlmlineHostLaneTxOtnEntry
	MAX-ACCESS not-accessible
	STATUS current
	DESCRIPTION
        "
        List of pmo10010AlmlineHostLaneTxOtn 
        Article
        "
	::= { pmo10010AlmLineUrg 184 }


pmo10010AlmlineHostLaneTxOtnEntry OBJECT-TYPE
	SYNTAX Pmo10010AlmlineHostLaneTxOtnEntry
	MAX-ACCESS not-accessible
	STATUS current
	DESCRIPTION
        "
        Row definition for the pmo10010AlmlineHostLaneTxOtn 
        table
        "
	INDEX   { pmo10010AlmlineHostLaneTxOtnIndex }
	::= { pmo10010AlmlineHostLaneTxOtnTable 1 }


Pmo10010AlmlineHostLaneTxOtnEntry ::=
	SEQUENCE {
	pmo10010AlmlineHostLaneTxOtnIndex
		INTEGER,
	pmo10010AlmLineTxOtnLofPortn
		EkiOnOff,
	pmo10010AlmLineTxOtnOofPortn
		EkiOnOff,
	pmo10010AlmLineTxOtnLomPortn
		EkiOnOff,
	pmo10010AlmLineTxOtnOomPortn
		EkiOnOff,
	pmo10010AlmLineTxOtnIaePortn
		EkiOnOff,
	pmo10010AlmLineTxSmBdiPortn
		EkiOnOff,
	pmo10010AlmLineTxOtnOtuAisPortn
		EkiOnOff,
	pmo10010AlmLineTxOtnOduAisPortn
		EkiOnOff
	}


pmo10010AlmlineHostLaneTxOtnIndex OBJECT-TYPE
	SYNTAX  INTEGER(0..128)
	MAX-ACCESS  read-only
	STATUS current
	DESCRIPTION
        "
        Index definition for the pmo10010AlmlineHostLaneTxOtn 
        table
        "
	::= { pmo10010AlmlineHostLaneTxOtnEntry 1 }


pmo10010AlmLineTxOtnLofPortn OBJECT-TYPE
	SYNTAX  EkiOnOff
	MAX-ACCESS read-only
	STATUS current
	DESCRIPTION
        "
        Line Host Tx LOF :This OID indicates 
        a Loss of Frame is detected on
         the Tx Host interface of the Line 
        Trscv <Help> Alarm indicating a 
        Loss of Frame is detected on the 
        Tx Host interface of the Line Trscv 
        <Condtype> LINE_TX_OTN_LOF <Probcause> 
        receiveFailure (41) <Alarmtype> 
        equipmentAlarm (5) <Polarity> (2) 
        "
	::= { pmo10010AlmlineHostLaneTxOtnEntry 17 }


pmo10010AlmLineTxOtnOofPortn OBJECT-TYPE
	SYNTAX  EkiOnOff
	MAX-ACCESS read-only
	STATUS current
	DESCRIPTION
        "
        Line Host Tx OOF :This OID indicates 
        an Out of Frame is detected on
         the Tx Host interface of the Line 
        Trscv <Help> Alarm indicating an 
        Out of Frame is detected on the 
        Tx Host interface of the Line Trscv 
        <Condtype> LINE_TX_OTN_OOF <Probcause> 
        receiveFailure (41) <Alarmtype> 
        equipmentAlarm (5) <Polarity> (2) 
        "
	::= { pmo10010AlmlineHostLaneTxOtnEntry 16 }


pmo10010AlmLineTxOtnLomPortn OBJECT-TYPE
	SYNTAX  EkiOnOff
	MAX-ACCESS read-only
	STATUS current
	DESCRIPTION
        "
        Line Host Tx LOM :This OID indicates 
        a Loss of Multiframe is detected 
        on the Tx Host interface of the 
        Line Trscv <Help> Alarm indicating 
        a Loss of Multiframe is detected 
        on the Tx Host interface of the 
        Line Trscv <Condtype> LINE_TX_OTN_LOM 
        <Probcause> receiveFailure (41) 
        <Alarmtype> equipmentAlarm (5)
         <Polarity> (2) 
        "
	::= { pmo10010AlmlineHostLaneTxOtnEntry 15 }


pmo10010AlmLineTxOtnOomPortn OBJECT-TYPE
	SYNTAX  EkiOnOff
	MAX-ACCESS read-only
	STATUS current
	DESCRIPTION
        "
        Line Host Tx OOM :This OID indicates 
        an Out of Multiframe is detected 
        on the Tx Host interface of the 
        Line Trscv <Help> Alarm indicating 
        an Out of Multiframe is detected 
        on the Tx Host interface of the 
        Line Trscv <Condtype> LINE_TX_OTN_OOM 
        <Probcause> receiveFailure (41) 
        <Alarmtype> equipmentAlarm (5)
         <Polarity> (2) 
        "
	::= { pmo10010AlmlineHostLaneTxOtnEntry 14 }


pmo10010AlmLineTxOtnIaePortn OBJECT-TYPE
	SYNTAX  EkiOnOff
	MAX-ACCESS read-only
	STATUS current
	DESCRIPTION
        "
        Line Host Tx IAE :This OID indicates 
        an Incoming Alignment Error is
         detected on the Tx Host interface 
        of the Line Trscv <Help> Alarm
         indicating an Incoming Alignment 
        Error is detected on the Tx Host 
        interface of the Line Trscv <Condtype> 
        LINE_TX_OTN_IAE <Probcause> receiveFailure 
        (41) <Alarmtype> equipmentAlarm 
        (5) <Polarity> (2) 
        "
	::= { pmo10010AlmlineHostLaneTxOtnEntry 13 }


pmo10010AlmLineTxSmBdiPortn OBJECT-TYPE
	SYNTAX  EkiOnOff
	MAX-ACCESS read-only
	STATUS current
	DESCRIPTION
        "
        Line Host Tx SM BDI :This OID
         indicates an SM Backward Defect 
        Indication is detected on the Tx 
        Host interface of the Line Trscv 
        <Help> Alarm indicating an SM Backward 
        Defect Indication is detected on 
        the Tx Host interface of the Line 
        Trscv <Condtype> LINE_TX_SM_BDI 
        <Probcause> informationalStatus(1000) 
        <Alarmtype> other (1) <Polarity> 
        (2) 
        "
	::= { pmo10010AlmlineHostLaneTxOtnEntry 12 }


pmo10010AlmLineTxOtnOtuAisPortn OBJECT-TYPE
	SYNTAX  EkiOnOff
	MAX-ACCESS read-only
	STATUS current
	DESCRIPTION
        "
        Line Host Tx OTU AIS :This OID 
        indicates an OTU This OID Indication 
        Signal is detected on the Tx Host 
        interface of the Line Trscv <Help> 
        Alarm indicating an OTU Alarm Indication 
        Signal is detected on the Tx Host 
        interface of the Line Trscv <Condtype> 
        LINE_TX_OTN_OTU_AIS <Probcause> 
        receiveFailure (41) <Alarmtype> 
        equipmentAlarm (5) <Polarity> (2) 
        "
	::= { pmo10010AlmlineHostLaneTxOtnEntry 11 }


pmo10010AlmLineTxOtnOduAisPortn OBJECT-TYPE
	SYNTAX  EkiOnOff
	MAX-ACCESS read-only
	STATUS current
	DESCRIPTION
        "
        Line Host Tx ODU AIS :This OID 
        indicates an ODU This OID Indication 
        Signal is detected on the Tx Host 
        interface of the Line Trscv <Help> 
        Alarm indicating an ODU Alarm Indication 
        Signal is detected on the Tx Host 
        interface of the Line Trscv <Condtype> 
        LINE_TX_OTN_ODU_AIS <Probcause> 
        receiveFailure (41) <Alarmtype> 
        equipmentAlarm (5) <Polarity> (2) 
        "
	::= { pmo10010AlmlineHostLaneTxOtnEntry 10 }


--- *********************************************************
---     TABLE for the pmo10010AlmclientOtnAlm articles
--- *********************************************************

pmo10010AlmclientOtnAlmTable OBJECT-TYPE
	SYNTAX  SEQUENCE OF Pmo10010AlmclientOtnAlmEntry
	MAX-ACCESS not-accessible
	STATUS current
	DESCRIPTION
        "
        List of pmo10010AlmclientOtnAlm 
        Article
        "
	::= { pmo10010AlmClientUrg 200 }


pmo10010AlmclientOtnAlmEntry OBJECT-TYPE
	SYNTAX Pmo10010AlmclientOtnAlmEntry
	MAX-ACCESS not-accessible
	STATUS current
	DESCRIPTION
        "
        Row definition for the pmo10010AlmclientOtnAlm 
        table
        "
	INDEX   { pmo10010AlmclientOtnAlmIndex }
	::= { pmo10010AlmclientOtnAlmTable 1 }


Pmo10010AlmclientOtnAlmEntry ::=
	SEQUENCE {
	pmo10010AlmclientOtnAlmIndex
		INTEGER,
	pmo10010AlmClientOdu2eDlckPortn
		EkiOnOff,
	pmo10010AlmClientOdu2eIlckPortn
		EkiOnOff,
	pmo10010AlmClientOdu2eDbdiPortn
		EkiOnOff,
	pmo10010AlmClientOdu2eIbdiPortn
		EkiOnOff,
	pmo10010AlmClientOdu2eDociPortn
		EkiOnOff,
	pmo10010AlmClientOdu2eIociPortn
		EkiOnOff,
	pmo10010AlmClientOdu2eDaisPortn
		EkiOnOff,
	pmo10010AlmClientOdu2eDtimPortn
		EkiOnOff,
	pmo10010AlmClientOdu2eIaisPortn
		EkiOnOff,
	pmo10010AlmClientCsfDetectedOtnPortn
		EkiOnOff,
	pmo10010AlmClientOdu2eDdegPortn
		EkiOnOff,
	pmo10010AlmClientOdu2eDplmPortn
		EkiOnOff,
	pmo10010AlmClientOtu2eDlofPortn
		EkiOnOff,
	pmo10010AlmClientOtu2eDlomPortn
		EkiOnOff
	}


pmo10010AlmclientOtnAlmIndex OBJECT-TYPE
	SYNTAX  INTEGER(0..128)
	MAX-ACCESS  read-only
	STATUS current
	DESCRIPTION
        "
        Index definition for the pmo10010AlmclientOtnAlm 
        table
        "
	::= { pmo10010AlmclientOtnAlmEntry 1 }


pmo10010AlmClientOdu2eDlckPortn OBJECT-TYPE
	SYNTAX  EkiOnOff
	MAX-ACCESS read-only
	STATUS current
	DESCRIPTION
        "
        ODU2e DLCK :This OID indicates 
        that a Locked Indication has been 
        detected on client port <Help>
          This alarm indicates if a Locked 
        Indication has been detected on 
        the client port <Condtype> CLIENT_ODU2E_DLCK 
        <Probcause> other(1) <Alarmtype> 
        other(1) <Polarity> (2)
        "
	::= { pmo10010AlmclientOtnAlmEntry 17 }


pmo10010AlmClientOdu2eIlckPortn OBJECT-TYPE
	SYNTAX  EkiOnOff
	MAX-ACCESS read-only
	STATUS current
	DESCRIPTION
        "
        ODU2e ILCK :This OID indicates 
        that a Locked Indication has been 
        inserted on client port <Help>
          This alarm indicates if a Locked 
        Indication has been inserted on 
        the client port <Condtype> CLIENT_ODU2E_ILCK 
        <Probcause> other(1) <Alarmtype> 
        other(1) <Polarity> (2)
        "
	::= { pmo10010AlmclientOtnAlmEntry 16 }


pmo10010AlmClientOdu2eDbdiPortn OBJECT-TYPE
	SYNTAX  EkiOnOff
	MAX-ACCESS read-only
	STATUS current
	DESCRIPTION
        "
        ODU2e DBDI :This OID indicates 
        that a Backward Defect Indication 
        has been detected on client port<Help> 
         This alarm indicates if a Backward 
        Defect Indication has been detected 
        on the client port <Condtype> CLIENT_ODU2E_DBDI 
        <Probcause> other(1) <Alarmtype> 
        other(1) <Polarity> (2)
        "
	::= { pmo10010AlmclientOtnAlmEntry 15 }


pmo10010AlmClientOdu2eIbdiPortn OBJECT-TYPE
	SYNTAX  EkiOnOff
	MAX-ACCESS read-only
	STATUS current
	DESCRIPTION
        "
        ODU2e IBDI :This OID indicates 
        that a Backward Defect Indication 
        has been inserted on client port 
        <Help>  This alarm indicates if 
        a Backward Defect Indication has 
        been inserted on the client port 
        <Condtype> CLIENT_ODU2E_IBDI <Probcause> 
        other(1) <Alarmtype> other(1) <Polarity> 
        (2)
        "
	::= { pmo10010AlmclientOtnAlmEntry 14 }


pmo10010AlmClientOdu2eDociPortn OBJECT-TYPE
	SYNTAX  EkiOnOff
	MAX-ACCESS read-only
	STATUS current
	DESCRIPTION
        "
        ODU2e DOCI :This OID indicates 
        that a Open Connection has been 
        detected on client port <Help>
          This alarm indicates if an Open 
        Connection Indication has been
         detected on the client port <Condtype> 
        CLIENT_ODU2E_DOCI <Probcause> other(1) 
        <Alarmtype> other(1) <Polarity> 
        (2)
        "
	::= { pmo10010AlmclientOtnAlmEntry 13 }


pmo10010AlmClientOdu2eIociPortn OBJECT-TYPE
	SYNTAX  EkiOnOff
	MAX-ACCESS read-only
	STATUS current
	DESCRIPTION
        "
        ODU2e IOCI :This OID indicates 
        that an Open Connection has been 
        inserted on client port <Help>
          This alarm indicates if an Open 
        Connection Indication has been
         inserted on the client port <Condtype> 
        CLIENT_ODU2E_IOCI <Probcause> other(1) 
        <Alarmtype> other(1) <Polarity> 
        (2)
        "
	::= { pmo10010AlmclientOtnAlmEntry 12 }


pmo10010AlmClientOdu2eDaisPortn OBJECT-TYPE
	SYNTAX  EkiOnOff
	MAX-ACCESS read-only
	STATUS current
	DESCRIPTION
        "
        ODU2e DAIS :This OID indicates 
        that a Alarm Indication SIgnal
         has been detected on client port<Help> 
         This alarm indicates if an Alarm 
        Indication Signal has been detected 
        on the client port <Condtype> CLIENT_ODU2E_DAIS 
        <Probcause> equipmentMalfunction(16) 
        <Alarmtype> equipmentAlarm (5)
         <Polarity> (2) 
        "
	::= { pmo10010AlmclientOtnAlmEntry 10 }


pmo10010AlmClientOdu2eDtimPortn OBJECT-TYPE
	SYNTAX  EkiOnOff
	MAX-ACCESS read-only
	STATUS current
	DESCRIPTION
        "
        ODU2e DTIM :This OID indicates 
        that a Trace Identifier Mismatch 
        has been detected on client port<Help> 
         This alarm indicates if an Trace 
        Identifier Mismatch has been detected 
        on the client port <Condtype> CLIENT_ODU2E_DTIM 
        <Probcause> equipmentMalfunction(16) 
        <Alarmtype> equipmentAlarm (5)
         <Polarity> (2) 
        "
	::= { pmo10010AlmclientOtnAlmEntry 9 }


pmo10010AlmClientOdu2eIaisPortn OBJECT-TYPE
	SYNTAX  EkiOnOff
	MAX-ACCESS read-only
	STATUS current
	DESCRIPTION
        "
        ODU2e IAIS :This OID indicates 
        that an Alarm Indication Signal 
        has been inserted on client port 
        <Help>  This alarm indicates if 
        an Alarm Indication Signal has
         been inserted on the client port 
        <Condtype> CLIENT_ODU2E_IAIS <Probcause> 
        equipmentMalfunction(16) <Alarmtype> 
        equipmentAlarm (5) <Polarity> (2) 
        "
	::= { pmo10010AlmclientOtnAlmEntry 8 }


pmo10010AlmClientCsfDetectedOtnPortn OBJECT-TYPE
	SYNTAX  EkiOnOff
	MAX-ACCESS read-only
	STATUS current
	DESCRIPTION
        "
        ETH DCSF :This OID indicates that 
        a CSF has been detected on client 
        port in the downstream direction 
          <Help>  This alarm indicates
         if a Client Signal Fail has been 
        detected in the incoming line frame 
        for this client port <Condtype> 
        CLIENT_CSF_DETECTED_OTN <Probcause> 
        equipmentMalfunction(16) <Alarmtype> 
        equipmentAlarm (5) <Polarity> (2) 
        "
	::= { pmo10010AlmclientOtnAlmEntry 7 }


pmo10010AlmClientOdu2eDdegPortn OBJECT-TYPE
	SYNTAX  EkiOnOff
	MAX-ACCESS read-only
	STATUS current
	DESCRIPTION
        "
        ODU2e DDEG :This OID indicates 
        that a Signal Degrade has been
         detected on client port<Help>
         Alarm indicating a Signal Degrade 
        upon threshold and confirmation 
        parameters <Condtype> CLIENT_ODU2E_DDEG 
        <Probcause> degradedSignal(13)
         <Alarmtype> other(1) <Polarity> 
        (2)
        "
	::= { pmo10010AlmclientOtnAlmEntry 6 }


pmo10010AlmClientOdu2eDplmPortn OBJECT-TYPE
	SYNTAX  EkiOnOff
	MAX-ACCESS read-only
	STATUS current
	DESCRIPTION
        "
        ODU2e DPLM :This OID indicates 
        a Payload Mismatch is detected
         on the Client port<Help> Alarm 
        indicating a Payload Mismatch <Condtype> 
        CLIENT_ODU2E_DPLM <Probcause> receiveFailure 
        (41) <Alarmtype> equipmentAlarm 
        (5) <Polarity> (2) 
        "
	::= { pmo10010AlmclientOtnAlmEntry 4 }


pmo10010AlmClientOtu2eDlofPortn OBJECT-TYPE
	SYNTAX  EkiOnOff
	MAX-ACCESS read-only
	STATUS current
	DESCRIPTION
        "
        OTU2e_DLOF :This OID indicates 
        the module is not aligned with
         the incoming Line signal<Help> 
        Alarm indicating the module is
         not aligned with the incoming
         client signal <Condtype> CLIENT_OTU2E_DLOF 
        <Probcause> receiveFailure (41) 
        <Alarmtype> equipmentAlarm (5)
         <Polarity> (2) 
        "
	::= { pmo10010AlmclientOtnAlmEntry 3 }


pmo10010AlmClientOtu2eDlomPortn OBJECT-TYPE
	SYNTAX  EkiOnOff
	MAX-ACCESS read-only
	STATUS current
	DESCRIPTION
        "
        OTU2e_DLOM :This OID indicates 
        that a Loss Of Multiframe has been 
        detected on client port<Help> 
         This alarm indicates if a Loss 
        Of Multiframe has been detected 
        on the client port <Condtype> CLIENT_OTU2E_DLOM 
        <Probcause> receiveFailure (41) 
        <Alarmtype> equipmentAlarm (5)
         <Polarity> (2) 
        "
	::= { pmo10010AlmclientOtnAlmEntry 2 }


--- *********************************************************
---     TABLE for the pmo10010AlmclientSfpAlmDdm articles
--- *********************************************************

pmo10010AlmclientSfpAlmDdmTable OBJECT-TYPE
	SYNTAX  SEQUENCE OF Pmo10010AlmclientSfpAlmDdmEntry
	MAX-ACCESS not-accessible
	STATUS current
	DESCRIPTION
        "
        List of pmo10010AlmclientSfpAlmDdm 
        Article
        "
	::= { pmo10010AlmClientUrg 216 }


pmo10010AlmclientSfpAlmDdmEntry OBJECT-TYPE
	SYNTAX Pmo10010AlmclientSfpAlmDdmEntry
	MAX-ACCESS not-accessible
	STATUS current
	DESCRIPTION
        "
        Row definition for the pmo10010AlmclientSfpAlmDdm 
        table
        "
	INDEX   { pmo10010AlmclientSfpAlmDdmIndex }
	::= { pmo10010AlmclientSfpAlmDdmTable 1 }


Pmo10010AlmclientSfpAlmDdmEntry ::=
	SEQUENCE {
	pmo10010AlmclientSfpAlmDdmIndex
		INTEGER,
	pmo10010AlmRxPwrHighAlaPortn
		EkiOnOff,
	pmo10010AlmRxPwrLowAlaPortn
		EkiOnOff,
	pmo10010AlmTempHighAlaPortn
		EkiOnOff,
	pmo10010AlmTempLowAlaPortn
		EkiOnOff,
	pmo10010AlmVccHighAlaPortn
		EkiOnOff,
	pmo10010AlmVccLowAlaPortn
		EkiOnOff,
	pmo10010AlmTxBiasHighAlaPortn
		EkiOnOff,
	pmo10010AlmTxBiasLowAlaPortn
		EkiOnOff,
	pmo10010AlmTxPwrHighAlaPortn
		EkiOnOff,
	pmo10010AlmTxPwrLowAlaPortn
		EkiOnOff
	}


pmo10010AlmclientSfpAlmDdmIndex OBJECT-TYPE
	SYNTAX  INTEGER(0..128)
	MAX-ACCESS  read-only
	STATUS current
	DESCRIPTION
        "
        Index definition for the pmo10010AlmclientSfpAlmDdm 
        table
        "
	::= { pmo10010AlmclientSfpAlmDdmEntry 1 }


pmo10010AlmRxPwrHighAlaPortn OBJECT-TYPE
	SYNTAX  EkiOnOff
	MAX-ACCESS read-only
	STATUS current
	DESCRIPTION
        "
        Client Trscv Rx Power High :This 
        OID indicates that the Trscv input 
        power of port is higher than the 
        threshold value written in the
         Trscv EEPROM <Help> Alarm indicating 
        that the Trscv input power of port 
        is higher than the threshold value 
        written in the Trscv EEPROM <Condtype> 
        RX_PWR_HIGH_ALA_1 <Probcause> receiveFailure 
        (41) <Alarmtype> equipmentAlarm 
        (5) <Polarity> (2) 
        "
	::= { pmo10010AlmclientSfpAlmDdmEntry 17 }


pmo10010AlmRxPwrLowAlaPortn OBJECT-TYPE
	SYNTAX  EkiOnOff
	MAX-ACCESS read-only
	STATUS current
	DESCRIPTION
        "
        Client Trscv Rx Power Low :This 
        OID indicates that the Trscv input 
        power of port is lower than the 
        threshold value written in the
         Trscv EEPROM <Help> Alarm indicating 
        that the Trscv input power of port 
        is lower than the threshold value 
        written in the Trscv EEPROM <Condtype> 
        RX_PWR_LOW_ALA_1 <Probcause> receiveFailure 
        (41) <Alarmtype> equipmentAlarm 
        (5) <Polarity> (2) 
        "
	::= { pmo10010AlmclientSfpAlmDdmEntry 16 }


pmo10010AlmTempHighAlaPortn OBJECT-TYPE
	SYNTAX  EkiOnOff
	MAX-ACCESS read-only
	STATUS current
	DESCRIPTION
        "
        Client Trscv Temp High :This OID 
        indicates that the Trscv temperature 
        of port is higher than the threshold 
        value written in the Trscv EEPROM 
        <Help> Alarm indicating that the 
        Trscv temperature of port is higher 
        than the threshold value written 
        in the Trscv EEPROM <Condtype>
         TEMP_HIGH_ALA_1 <Probcause> temperatureUnacceptable 
        (51) <Alarmtype> equipmentAlarm 
        (5) <Polarity> (2) 
        "
	::= { pmo10010AlmclientSfpAlmDdmEntry 9 }


pmo10010AlmTempLowAlaPortn OBJECT-TYPE
	SYNTAX  EkiOnOff
	MAX-ACCESS read-only
	STATUS current
	DESCRIPTION
        "
        Client Trscv Temp Low :This OID 
        indicates that the Trscv temperature 
        of port is lower than the threshold 
        value written in the Trscv EEPROM 
        <Help> Alarm indicating that the 
        Trscv temperature of port is lower 
        than the threshold value written 
        in the Trscv EEPROM <Condtype>
         TEMP_LOW_ALA_1 <Probcause> temperatureUnacceptable 
        (51) <Alarmtype> equipmentAlarm 
        (5) <Polarity> (2) 
        "
	::= { pmo10010AlmclientSfpAlmDdmEntry 8 }


pmo10010AlmVccHighAlaPortn OBJECT-TYPE
	SYNTAX  EkiOnOff
	MAX-ACCESS read-only
	STATUS current
	DESCRIPTION
        "
        Client Trscv Power Supply High 
        :This OID indicates that the Trscv 
        power supply of port is higher
         than the threshold value written 
        in the Trscv EEPROM <Help> Alarm 
        indicating that the Trscv power 
        supply of port is higher than the 
        threshold value written in the
         Trscv EEPROM <Condtype> VCC_HIGH_ALA_1 
        <Probcause> powerProblem (36) <Alarmtype> 
        equipmentAlarm (5) <Polarity> (2) 
        "
	::= { pmo10010AlmclientSfpAlmDdmEntry 7 }


pmo10010AlmVccLowAlaPortn OBJECT-TYPE
	SYNTAX  EkiOnOff
	MAX-ACCESS read-only
	STATUS current
	DESCRIPTION
        "
        Client Trscv Power Supply Low
         :This OID indicates that the Trscv 
        power supply of port is lower than 
        the threshold value written in
         the Trscv EEPROM <Help> Alarm
         indicating that the Trscv power 
        supply of port is lower than the 
        threshold value written in the
         Trscv EEPROM <Condtype> VCC_LOW_ALA_1 
        <Probcause> powerProblem (36) <Alarmtype> 
        equipmentAlarm (5) <Polarity> (2) 
        "
	::= { pmo10010AlmclientSfpAlmDdmEntry 6 }


pmo10010AlmTxBiasHighAlaPortn OBJECT-TYPE
	SYNTAX  EkiOnOff
	MAX-ACCESS read-only
	STATUS current
	DESCRIPTION
        "
        Client Trscv Bias High :This OID 
        indicates that the Trscv laser
         bias current of port is higher 
        than the threshold value written 
        in the Trscv EEPROM <Help> Alarm 
        indicating that the Trscv laser 
        bias current of port is higher
         than the threshold value written 
        in the Trscv EEPROM <Condtype>
         TX_BIAS_HIGH_ALA_1 <Probcause> 
        transmitterFailure (56) <Alarmtype> 
        equipmentAlarm (5) <Polarity> (2) 
        "
	::= { pmo10010AlmclientSfpAlmDdmEntry 5 }


pmo10010AlmTxBiasLowAlaPortn OBJECT-TYPE
	SYNTAX  EkiOnOff
	MAX-ACCESS read-only
	STATUS current
	DESCRIPTION
        "
        Client Trscv Bias Low :This OID 
        indicates that the Trscv laser
         bias current of port is lower
         than the threshold value written 
        in the Trscv EEPROM <Help> Alarm 
        indicating that the Trscv laser 
        bias current of port is lower than 
        the threshold value written in
         the Trscv EEPROM <Condtype> TX_BIAS_LOW_ALA_1 
        <Probcause> transmitterFailure
         (56) <Alarmtype> equipmentAlarm 
        (5) <Polarity> (2) 
        "
	::= { pmo10010AlmclientSfpAlmDdmEntry 4 }


pmo10010AlmTxPwrHighAlaPortn OBJECT-TYPE
	SYNTAX  EkiOnOff
	MAX-ACCESS read-only
	STATUS current
	DESCRIPTION
        "
        Client Trscv Tx Power High :This 
        OID indicates that the Trscv output 
        power of port is higher than the 
        threshold value written in the
         Trscv EEPROM <Help> Alarm indicating 
        that the Trscv output power of
         port is higher than the threshold 
        value written in the Trscv EEPROM 
        <Condtype> TX_PWR_HIGH_ALA_1 <Probcause> 
        transmitterFailure (56) <Alarmtype> 
        equipmentAlarm (5) <Polarity> (2) 
        "
	::= { pmo10010AlmclientSfpAlmDdmEntry 3 }


pmo10010AlmTxPwrLowAlaPortn OBJECT-TYPE
	SYNTAX  EkiOnOff
	MAX-ACCESS read-only
	STATUS current
	DESCRIPTION
        "
        Client Trscv Tx Power Low :This 
        OID indicates that the Trscv output 
        power of port is lower than the 
        threshold value written in the
         Trscv EEPROM <Help> Alarm indicating 
        that the Trscv output power of
         port is lower than the threshold 
        value written in the Trscv EEPROM 
        <Condtype> TX_PWR_LOW_ALA_1 <Probcause> 
        transmitterFailure (56) <Alarmtype> 
        equipmentAlarm (5) <Polarity> (2) 
        "
	::= { pmo10010AlmclientSfpAlmDdmEntry 2 }


--- *********************************************************
---     TABLE for the pmo10010AlmclientSfpWarnDdm articles
--- *********************************************************

pmo10010AlmclientSfpWarnDdmTable OBJECT-TYPE
	SYNTAX  SEQUENCE OF Pmo10010AlmclientSfpWarnDdmEntry
	MAX-ACCESS not-accessible
	STATUS current
	DESCRIPTION
        "
        List of pmo10010AlmclientSfpWarnDdm 
        Article
        "
	::= { pmo10010AlmClientNurg 232 }


pmo10010AlmclientSfpWarnDdmEntry OBJECT-TYPE
	SYNTAX Pmo10010AlmclientSfpWarnDdmEntry
	MAX-ACCESS not-accessible
	STATUS current
	DESCRIPTION
        "
        Row definition for the pmo10010AlmclientSfpWarnDdm 
        table
        "
	INDEX   { pmo10010AlmclientSfpWarnDdmIndex }
	::= { pmo10010AlmclientSfpWarnDdmTable 1 }


Pmo10010AlmclientSfpWarnDdmEntry ::=
	SEQUENCE {
	pmo10010AlmclientSfpWarnDdmIndex
		INTEGER,
	pmo10010AlmRxPwrHighWngPortn
		EkiOnOff,
	pmo10010AlmRxPwrLowWngPortn
		EkiOnOff,
	pmo10010AlmTempHighWngPortn
		EkiOnOff,
	pmo10010AlmTempLowWngPortn
		EkiOnOff,
	pmo10010AlmVccHighWngPortn
		EkiOnOff,
	pmo10010AlmVccLowWngPortn
		EkiOnOff,
	pmo10010AlmTxBiasHighWngPortn
		EkiOnOff,
	pmo10010AlmTxBiasLowWngPortn
		EkiOnOff,
	pmo10010AlmTxPwrHighWngPortn
		EkiOnOff,
	pmo10010AlmTxPwLowWngPortn
		EkiOnOff
	}


pmo10010AlmclientSfpWarnDdmIndex OBJECT-TYPE
	SYNTAX  INTEGER(0..128)
	MAX-ACCESS  read-only
	STATUS current
	DESCRIPTION
        "
        Index definition for the pmo10010AlmclientSfpWarnDdm 
        table
        "
	::= { pmo10010AlmclientSfpWarnDdmEntry 1 }


pmo10010AlmRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         RX_PWR_HIGH_WNG_1 <Probcause>
         receiveFailure (41) <Alarmtype> 
        equipmentAlarm (5) <Polarity> (2) 
        "
	::= { pmo10010AlmclientSfpWarnDdmEntry 17 }


pmo10010AlmRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         RX_PWR_LOW_WNG_1 <Probcause> receiveFailure 
        (41) <Alarmtype> equipmentAlarm 
        (5) <Polarity> (2) 
        "
	::= { pmo10010AlmclientSfpWarnDdmEntry 16 }


pmo10010AlmTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         TEMP_HIGH_WNG_1 <Probcause> temperatureUnacceptable 
        (51) <Alarmtype> equipmentAlarm 
        (5) <Polarity> (2) 
        "
	::= { pmo10010AlmclientSfpWarnDdmEntry 9 }


pmo10010AlmTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         TEMP_LOW_WNG_1 <Probcause> temperatureUnacceptable 
        (51) <Alarmtype> equipmentAlarm 
        (5) <Polarity> (2) 
        "
	::= { pmo10010AlmclientSfpWarnDdmEntry 8 }


pmo10010AlmVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> VCC_HIGH_WNG_1 <Probcause> 
        powerProblem (36) <Alarmtype> equipmentAlarm 
        (5) <Polarity> (2) 
        "
	::= { pmo10010AlmclientSfpWarnDdmEntry 7 }


pmo10010AlmVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> VCC_LOW_WNG_1 <Probcause> 
        powerProblem (36) <Alarmtype> equipmentAlarm 
        (5) <Polarity> (2) 
        "
	::= { pmo10010AlmclientSfpWarnDdmEntry 6 }


pmo10010AlmTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> TX_BIAS_HIGH_WNG_1 
        <Probcause> transmitterFailure
         (56) <Alarmtype> equipmentAlarm 
        (5) <Polarity> (2) 
        "
	::= { pmo10010AlmclientSfpWarnDdmEntry 5 }


pmo10010AlmTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> TX_BIAS_LOW_WNG_1 
        <Probcause> transmitterFailure
         (56) <Alarmtype> equipmentAlarm 
        (5) <Polarity> (2) 
        "
	::= { pmo10010AlmclientSfpWarnDdmEntry 4 }


pmo10010AlmTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        TX_PWR_HIGH_WNG_1 <Probcause> transmitterFailure 
        (56) <Alarmtype> equipmentAlarm 
        (5) <Polarity> (2) 
        "
	::= { pmo10010AlmclientSfpWarnDdmEntry 3 }


pmo10010AlmTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        TX_PW_LOW_WNG_1 <Probcause> transmitterFailure 
        (56) <Alarmtype> equipmentAlarm 
        (5) <Polarity> (2) 
        "
	::= { pmo10010AlmclientSfpWarnDdmEntry 2 }


--- *********************************************************
---     TABLE for the pmo10010AlmlineOdu4Alm articles
--- *********************************************************

pmo10010AlmlineOdu4AlmTable OBJECT-TYPE
	SYNTAX  SEQUENCE OF Pmo10010AlmlineOdu4AlmEntry
	MAX-ACCESS not-accessible
	STATUS current
	DESCRIPTION
        "
        List of pmo10010AlmlineOdu4Alm 
        Article
        "
	::= { pmo10010AlmLineUrg 256 }


pmo10010AlmlineOdu4AlmEntry OBJECT-TYPE
	SYNTAX Pmo10010AlmlineOdu4AlmEntry
	MAX-ACCESS not-accessible
	STATUS current
	DESCRIPTION
        "
        Row definition for the pmo10010AlmlineOdu4Alm 
        table
        "
	INDEX   { pmo10010AlmlineOdu4AlmIndex }
	::= { pmo10010AlmlineOdu4AlmTable 1 }


Pmo10010AlmlineOdu4AlmEntry ::=
	SEQUENCE {
	pmo10010AlmlineOdu4AlmIndex
		INTEGER,
	pmo10010AlmLineOdu4DlckPortn
		EkiOnOff,
	pmo10010AlmLineOdu4IlckPortn
		EkiOnOff,
	pmo10010AlmLineOdu4DbdiPortn
		EkiOnOff,
	pmo10010AlmLineOdu4IbdiPortn
		EkiOnOff,
	pmo10010AlmLineOdu4DociPortn
		EkiOnOff,
	pmo10010AlmLineOdu4IociPortn
		EkiOnOff,
	pmo10010AlmLineOdu4DaisPortn
		EkiOnOff,
	pmo10010AlmLineOdu4DtimPortn
		EkiOnOff,
	pmo10010AlmLineOdu4IaisPortn
		EkiOnOff,
	pmo10010AlmLineOdu4DdegPortn
		EkiOnOff,
	pmo10010AlmLineOdu4DplmPortn
		EkiOnOff
	}


pmo10010AlmlineOdu4AlmIndex OBJECT-TYPE
	SYNTAX  INTEGER(0..128)
	MAX-ACCESS  read-only
	STATUS current
	DESCRIPTION
        "
        Index definition for the pmo10010AlmlineOdu4Alm 
        table
        "
	::= { pmo10010AlmlineOdu4AlmEntry 1 }


pmo10010AlmLineOdu4DlckPortn OBJECT-TYPE
	SYNTAX  EkiOnOff
	MAX-ACCESS read-only
	STATUS current
	DESCRIPTION
        "
        ODU4 DLCK :This OID indicates
         that a Locked Indication has been 
        detected on line port <Help>  This 
        alarm indicates if a Locked Indication 
        has been detected on the line port 
        <Condtype> LINE_ODU4_DLCK <Probcause> 
        other(1) <Alarmtype> other(1) <Polarity> 
        (2)
        "
	::= { pmo10010AlmlineOdu4AlmEntry 17 }


pmo10010AlmLineOdu4IlckPortn OBJECT-TYPE
	SYNTAX  EkiOnOff
	MAX-ACCESS read-only
	STATUS current
	DESCRIPTION
        "
        ODU4 ILCK :This OID indicates
         that a Locked Indication has been 
        inserted on line port <Help>  This 
        alarm indicates if a Locked Indication 
        has been inserted on the line port 
        <Condtype> LINE_ODU4_ILCK <Probcause> 
        other(1) <Alarmtype> other(1) <Polarity> 
        (2)
        "
	::= { pmo10010AlmlineOdu4AlmEntry 16 }


pmo10010AlmLineOdu4DbdiPortn OBJECT-TYPE
	SYNTAX  EkiOnOff
	MAX-ACCESS read-only
	STATUS current
	DESCRIPTION
        "
        ODU4 DBDI :This OID indicates
         that a Backward Defect Indication 
        has been detected on line port<Help> 
         This alarm indicates if a Backward 
        Defect Indication has been detected 
        on the line port <Condtype> LINE_ODU4_DBDI 
        <Probcause> other(1) <Alarmtype> 
        other(1) <Polarity> (2)
        "
	::= { pmo10010AlmlineOdu4AlmEntry 15 }


pmo10010AlmLineOdu4IbdiPortn OBJECT-TYPE
	SYNTAX  EkiOnOff
	MAX-ACCESS read-only
	STATUS current
	DESCRIPTION
        "
        ODU4 IBDI :This OID indicates
         that a Backward Defect Indication 
        has been inserted on line port
         <Help>  This alarm indicates if 
        a Backward Defect Indication has 
        been inserted on the line port
         <Condtype> LINE_ODU4_IBDI <Probcause> 
        other(1) <Alarmtype> other(1) <Polarity> 
        (2)
        "
	::= { pmo10010AlmlineOdu4AlmEntry 14 }


pmo10010AlmLineOdu4DociPortn OBJECT-TYPE
	SYNTAX  EkiOnOff
	MAX-ACCESS read-only
	STATUS current
	DESCRIPTION
        "
        ODU4 DOCI :This OID indicates
         that a Open Connection has been 
        detected on line port <Help>  This 
        alarm indicates if an Open Connection 
        Indication has been detected on 
        the line port <Condtype> LINE_ODU4_DOCI 
        <Probcause> other(1) <Alarmtype> 
        other(1) <Polarity> (2)
        "
	::= { pmo10010AlmlineOdu4AlmEntry 13 }


pmo10010AlmLineOdu4IociPortn OBJECT-TYPE
	SYNTAX  EkiOnOff
	MAX-ACCESS read-only
	STATUS current
	DESCRIPTION
        "
        ODU4 IOCI :This OID indicates
         that an Open Connection has been 
        inserted on line port <Help>  This 
        alarm indicates if an Open Connection 
        Indication has been inserted on 
        the line port <Condtype> LINE_ODU4_IOCI 
        <Probcause> other(1) <Alarmtype> 
        other(1) <Polarity> (2)
        "
	::= { pmo10010AlmlineOdu4AlmEntry 12 }


pmo10010AlmLineOdu4DaisPortn OBJECT-TYPE
	SYNTAX  EkiOnOff
	MAX-ACCESS read-only
	STATUS current
	DESCRIPTION
        "
        ODU4 DAIS :This OID indicates
         that a Alarm Indication SIgnal 
        has been detected on line port<Help> 
         This alarm indicates if an Alarm 
        Indication Signal has been detected 
        on the line port <Condtype> LINE_ODU4_DAIS 
        <Probcause> equipmentMalfunction(16) 
        <Alarmtype> equipmentAlarm (5)
         <Polarity> (2) 
        "
	::= { pmo10010AlmlineOdu4AlmEntry 10 }


pmo10010AlmLineOdu4DtimPortn OBJECT-TYPE
	SYNTAX  EkiOnOff
	MAX-ACCESS read-only
	STATUS current
	DESCRIPTION
        "
        ODU4 DTIM :This OID indicates
         that a Trace Identifier Mismatch 
        has been detected on line port<Help> 
         This alarm indicates if an Trace 
        Identifier Mismatch has been detected 
        on the line port <Condtype> LINE_ODU4_DTIM 
        <Probcause> equipmentMalfunction(16) 
        <Alarmtype> equipmentAlarm (5)
         <Polarity> (2) 
        "
	::= { pmo10010AlmlineOdu4AlmEntry 9 }


pmo10010AlmLineOdu4IaisPortn OBJECT-TYPE
	SYNTAX  EkiOnOff
	MAX-ACCESS read-only
	STATUS current
	DESCRIPTION
        "
        ODU4 IAIS :This OID indicates
         that an Alarm Indication Signal 
        has been inserted on line port
         <Help>  This alarm indicates if 
        an Alarm Indication Signal has
         been inserted on the line port 
        <Condtype> LINE_ODU4_IAIS <Probcause> 
        equipmentMalfunction(16) <Alarmtype> 
        equipmentAlarm (5) <Polarity> (2) 
        "
	::= { pmo10010AlmlineOdu4AlmEntry 8 }


pmo10010AlmLineOdu4DdegPortn OBJECT-TYPE
	SYNTAX  EkiOnOff
	MAX-ACCESS read-only
	STATUS current
	DESCRIPTION
        "
        ODU4 DDEG :This OID indicates
         that a Signal Degrade has been 
        detected on line port<Help> Alarm 
        indicating a Signal Degrade upon 
        threshold and confirmation parameters 
        <Condtype> LINE_ODU4_DDEG <Probcause> 
        degradedSignal(13) <Alarmtype>
         other(1) <Polarity> (2)
        "
	::= { pmo10010AlmlineOdu4AlmEntry 6 }


pmo10010AlmLineOdu4DplmPortn OBJECT-TYPE
	SYNTAX  EkiOnOff
	MAX-ACCESS read-only
	STATUS current
	DESCRIPTION
        "
        ODU4 DPLM :This OID indicates
         a Payload Mismatch is detected 
        on the line port<Help> Alarm indicating 
        a Payload Mismatch <Condtype> LINE_ODU4_DPLM 
        <Probcause> receiveFailure (41) 
        <Alarmtype> equipmentAlarm (5)
         <Polarity> (2) 
        "
	::= { pmo10010AlmlineOdu4AlmEntry 4 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmo10010CtrlconfMgnt1 OBJECT IDENTIFIER ::= { pmo10010CtrlOther 1 }




pmo10010CtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pmo10010CtrlconfMgnt1 14 }



pmo10010CtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pmo10010CtrlconfMgnt1 10 }



pmo10010CtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pmo10010CtrlconfMgnt1 2 }



pmo10010CtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pmo10010CtrlconfMgnt1 1 }



--- *****************************************************
---     LEAF for the synth4 article
--- *****************************************************
pmo10010Ctrlsynth4 OBJECT IDENTIFIER ::= { pmo10010CtrlOther 4 }




pmo10010CtrlCorrelatOff OBJECT-TYPE
	  SYNTAX EkiOnOff
	  MAX-ACCESS read-write
	  STATUS current
	  DESCRIPTION
        "
        Disable Alarm Correlation :This 
        OID disables the alarm correlation 
        in the PM.
        "
	  ::= { pmo10010Ctrlsynth4 2 }



pmo10010CtrlCorrelatOn OBJECT-TYPE
	  SYNTAX EkiOnOff
	  MAX-ACCESS read-write
	  STATUS current
	  DESCRIPTION
        "
        Enable Alarm Correlation :This 
        OID enables the alarm correlation 
        in the PM.
        "
	  ::= { pmo10010Ctrlsynth4 1 }



--- *****************************************************
---     LEAF for the swMgnt article
--- *****************************************************
pmo10010CtrlswMgnt OBJECT IDENTIFIER ::= { pmo10010CtrlOther 5 }




pmo10010CtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pmo10010CtrlswMgnt 6 }



pmo10010CtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pmo10010CtrlswMgnt 5 }



pmo10010CtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pmo10010CtrlswMgnt 3 }



pmo10010CtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pmo10010CtrlswMgnt 2 }



--- *****************************************************
---     LEAF for the gwMgnt article
--- *****************************************************
pmo10010CtrlgwMgnt OBJECT IDENTIFIER ::= { pmo10010CtrlOther 6 }




pmo10010CtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pmo10010CtrlgwMgnt 8 }



pmo10010CtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pmo10010CtrlgwMgnt 7 }



pmo10010CtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pmo10010CtrlgwMgnt 6 }



pmo10010CtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pmo10010CtrlgwMgnt 5 }



pmo10010CtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pmo10010CtrlgwMgnt 1 }



--- *********************************************************
---     TABLE for the pmo10010CtrlaccessLoop articles
--- *********************************************************

pmo10010CtrlaccessLoopTable OBJECT-TYPE
	SYNTAX  SEQUENCE OF Pmo10010CtrlaccessLoopEntry
	MAX-ACCESS not-accessible
	STATUS current
	DESCRIPTION
        "
        List of pmo10010CtrlaccessLoop 
        Article
        "
	::= { pmo10010CtrlClient 16 }


pmo10010CtrlaccessLoopEntry OBJECT-TYPE
	SYNTAX Pmo10010CtrlaccessLoopEntry
	MAX-ACCESS not-accessible
	STATUS current
	DESCRIPTION
        "
        Row definition for the pmo10010CtrlaccessLoop 
        table
        "
	INDEX   { pmo10010CtrlaccessLoopIndex }
	::= { pmo10010CtrlaccessLoopTable 1 }


Pmo10010CtrlaccessLoopEntry ::=
	SEQUENCE {
	pmo10010CtrlaccessLoopIndex
		INTEGER,
	pmo10010CtrlaccessLoopPortn
		EkiState
	}


pmo10010CtrlaccessLoopIndex OBJECT-TYPE
	SYNTAX  INTEGER(0..128)
	MAX-ACCESS  read-only
	STATUS current
	DESCRIPTION
        "
        Index definition for the pmo10010CtrlaccessLoop 
        table
        "
	::= { pmo10010CtrlaccessLoopEntry 1 }


pmo10010CtrlaccessLoopPortn OBJECT-TYPE
	SYNTAX  EkiState
	MAX-ACCESS read-write
	STATUS current
	DESCRIPTION
        "
        Client Facility Loopback :This 
        OID, when set at '1' puts the client 
        port in loopback, looping the received 
        10 Gb/s signal on the transmit
         10 Gb/s output.  <Help> This control 
        enables the Out Loopback on the 
        client port, looping the client 
        input signal on the client output
        "
	::= { pmo10010CtrlaccessLoopEntry 2 }


--- *********************************************************
---     TABLE for the pmo10010CtrlclientLoopToLine articles
--- *********************************************************

pmo10010CtrlclientLoopToLineTable OBJECT-TYPE
	SYNTAX  SEQUENCE OF Pmo10010CtrlclientLoopToLineEntry
	MAX-ACCESS not-accessible
	STATUS current
	DESCRIPTION
        "
        List of pmo10010CtrlclientLoopToLine 
        Article
        "
	::= { pmo10010CtrlClient 17 }


pmo10010CtrlclientLoopToLineEntry OBJECT-TYPE
	SYNTAX Pmo10010CtrlclientLoopToLineEntry
	MAX-ACCESS not-accessible
	STATUS current
	DESCRIPTION
        "
        Row definition for the pmo10010CtrlclientLoopToLine 
        table
        "
	INDEX   { pmo10010CtrlclientLoopToLineIndex }
	::= { pmo10010CtrlclientLoopToLineTable 1 }


Pmo10010CtrlclientLoopToLineEntry ::=
	SEQUENCE {
	pmo10010CtrlclientLoopToLineIndex
		INTEGER,
	pmo10010CtrlclientLoopToLinePortn
		EkiState
	}


pmo10010CtrlclientLoopToLineIndex OBJECT-TYPE
	SYNTAX  INTEGER(0..128)
	MAX-ACCESS  read-only
	STATUS current
	DESCRIPTION
        "
        Index definition for the pmo10010CtrlclientLoopToLine 
        table
        "
	::= { pmo10010CtrlclientLoopToLineEntry 1 }


pmo10010CtrlclientLoopToLinePortn OBJECT-TYPE
	SYNTAX  EkiState
	MAX-ACCESS read-write
	STATUS current
	DESCRIPTION
        "
        Client Terminal Loopback :This 
        OID, when set, puts the client
         port in loop back, looping the 
        10 Gb/s output signal on the 10 
        Gb/s input.<Help> This control
         enables the In Loopback on the 
        client port, looping the client 
        output signal on the client input
        "
	::= { pmo10010CtrlclientLoopToLineEntry 2 }


--- *********************************************************
---     TABLE for the pmo10010CtrlcsfUpIns articles
--- *********************************************************

pmo10010CtrlcsfUpInsTable OBJECT-TYPE
	SYNTAX  SEQUENCE OF Pmo10010CtrlcsfUpInsEntry
	MAX-ACCESS not-accessible
	STATUS current
	DESCRIPTION
        "
        List of pmo10010CtrlcsfUpIns Article
        "
	::= { pmo10010CtrlClient 21 }


pmo10010CtrlcsfUpInsEntry OBJECT-TYPE
	SYNTAX Pmo10010CtrlcsfUpInsEntry
	MAX-ACCESS not-accessible
	STATUS current
	DESCRIPTION
        "
        Row definition for the pmo10010CtrlcsfUpIns 
        table
        "
	INDEX   { pmo10010CtrlcsfUpInsIndex }
	::= { pmo10010CtrlcsfUpInsTable 1 }


Pmo10010CtrlcsfUpInsEntry ::=
	SEQUENCE {
	pmo10010CtrlcsfUpInsIndex
		INTEGER,
	pmo10010CtrlcsfUpInsPortn
		EkiState
	}


pmo10010CtrlcsfUpInsIndex OBJECT-TYPE
	SYNTAX  INTEGER(0..128)
	MAX-ACCESS  read-only
	STATUS current
	DESCRIPTION
        "
        Index definition for the pmo10010CtrlcsfUpIns 
        table
        "
	::= { pmo10010CtrlcsfUpInsEntry 1 }


pmo10010CtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pmo10010CtrlcsfUpInsEntry 2 }


--- *********************************************************
---     TABLE for the pmo10010CtrlcaisDwIns articles
--- *********************************************************

pmo10010CtrlcaisDwInsTable OBJECT-TYPE
	SYNTAX  SEQUENCE OF Pmo10010CtrlcaisDwInsEntry
	MAX-ACCESS not-accessible
	STATUS current
	DESCRIPTION
        "
        List of pmo10010CtrlcaisDwIns
         Article
        "
	::= { pmo10010CtrlClient 22 }


pmo10010CtrlcaisDwInsEntry OBJECT-TYPE
	SYNTAX Pmo10010CtrlcaisDwInsEntry
	MAX-ACCESS not-accessible
	STATUS current
	DESCRIPTION
        "
        Row definition for the pmo10010CtrlcaisDwIns 
        table
        "
	INDEX   { pmo10010CtrlcaisDwInsIndex }
	::= { pmo10010CtrlcaisDwInsTable 1 }


Pmo10010CtrlcaisDwInsEntry ::=
	SEQUENCE {
	pmo10010CtrlcaisDwInsIndex
		INTEGER,
	pmo10010CtrlcaisDwInsPortn
		EkiState
	}


pmo10010CtrlcaisDwInsIndex OBJECT-TYPE
	SYNTAX  INTEGER(0..128)
	MAX-ACCESS  read-only
	STATUS current
	DESCRIPTION
        "
        Index definition for the pmo10010CtrlcaisDwIns 
        table
        "
	::= { pmo10010CtrlcaisDwInsEntry 1 }


pmo10010CtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pmo10010CtrlcaisDwInsEntry 2 }


--- *********************************************************
---     TABLE for the pmo10010CtrlcommAccessLoop articles
--- *********************************************************

pmo10010CtrlcommAccessLoopTable OBJECT-TYPE
	SYNTAX  SEQUENCE OF Pmo10010CtrlcommAccessLoopEntry
	MAX-ACCESS not-accessible
	STATUS current
	DESCRIPTION
        "
        List of pmo10010CtrlcommAccessLoop 
        Article
        "
	::= { pmo10010CtrlLine 64 }


pmo10010CtrlcommAccessLoopEntry OBJECT-TYPE
	SYNTAX Pmo10010CtrlcommAccessLoopEntry
	MAX-ACCESS not-accessible
	STATUS current
	DESCRIPTION
        "
        Row definition for the pmo10010CtrlcommAccessLoop 
        table
        "
	INDEX   { pmo10010CtrlcommAccessLoopIndex }
	::= { pmo10010CtrlcommAccessLoopTable 1 }


Pmo10010CtrlcommAccessLoopEntry ::=
	SEQUENCE {
	pmo10010CtrlcommAccessLoopIndex
		INTEGER,
	pmo10010CtrlcommAccessLoopPortn
		EkiState
	}


pmo10010CtrlcommAccessLoopIndex OBJECT-TYPE
	SYNTAX  INTEGER(0..128)
	MAX-ACCESS  read-only
	STATUS current
	DESCRIPTION
        "
        Index definition for the pmo10010CtrlcommAccessLoop 
        table
        "
	::= { pmo10010CtrlcommAccessLoopEntry 1 }


pmo10010CtrlcommAccessLoopPortn OBJECT-TYPE
	SYNTAX  EkiState
	MAX-ACCESS read-write
	STATUS current
	DESCRIPTION
        "
        Line Terminal Loopback :This OID, 
        when set, puts the module in common 
        access loop back, looping the 100 
        Gb/s output signal on the 100 Gb/s 
        input.<Help> This control enables 
        the In Loopback on the line port, 
        looping the 100 Gb/s output signal 
        on the 100 Gb/s input
        "
	::= { pmo10010CtrlcommAccessLoopEntry 2 }


--- *********************************************************
---     TABLE for the pmo10010CtrllineLoop articles
--- *********************************************************

pmo10010CtrllineLoopTable OBJECT-TYPE
	SYNTAX  SEQUENCE OF Pmo10010CtrllineLoopEntry
	MAX-ACCESS not-accessible
	STATUS current
	DESCRIPTION
        "
        List of pmo10010CtrllineLoop Article
        "
	::= { pmo10010CtrlLine 66 }


pmo10010CtrllineLoopEntry OBJECT-TYPE
	SYNTAX Pmo10010CtrllineLoopEntry
	MAX-ACCESS not-accessible
	STATUS current
	DESCRIPTION
        "
        Row definition for the pmo10010CtrllineLoop 
        table
        "
	INDEX   { pmo10010CtrllineLoopIndex }
	::= { pmo10010CtrllineLoopTable 1 }


Pmo10010CtrllineLoopEntry ::=
	SEQUENCE {
	pmo10010CtrllineLoopIndex
		INTEGER,
	pmo10010CtrllineLoopPortn
		EkiState
	}


pmo10010CtrllineLoopIndex OBJECT-TYPE
	SYNTAX  INTEGER(0..128)
	MAX-ACCESS  read-only
	STATUS current
	DESCRIPTION
        "
        Index definition for the pmo10010CtrllineLoop 
        table
        "
	::= { pmo10010CtrllineLoopEntry 1 }


pmo10010CtrllineLoopPortn OBJECT-TYPE
	SYNTAX  EkiState
	MAX-ACCESS read-write
	STATUS current
	DESCRIPTION
        "
        Line Facility Loopback :This OID, 
        when set at '1' puts the module 
        in line loopback mode, looping
         the received 100 Gb/s signal on 
        the transmit 100 Gb/s output. The 
        Upstream part of the module is
         timed on the 100 Gb/s recovered 
        clock in that case.<Help> This
         control enables the Out Loopback 
        on the line port, looping the 100 
        Gb/s input signal on the 100 Gb/s 
        output
        "
	::= { pmo10010CtrllineLoopEntry 2 }


--- *********************************************************
---     TABLE for the pmo10010CtrlfecDisable articles
--- *********************************************************

pmo10010CtrlfecDisableTable OBJECT-TYPE
	SYNTAX  SEQUENCE OF Pmo10010CtrlfecDisableEntry
	MAX-ACCESS not-accessible
	STATUS current
	DESCRIPTION
        "
        List of pmo10010CtrlfecDisable 
        Article
        "
	::= { pmo10010CtrlLine 69 }


pmo10010CtrlfecDisableEntry OBJECT-TYPE
	SYNTAX Pmo10010CtrlfecDisableEntry
	MAX-ACCESS not-accessible
	STATUS current
	DESCRIPTION
        "
        Row definition for the pmo10010CtrlfecDisable 
        table
        "
	INDEX   { pmo10010CtrlfecDisableIndex }
	::= { pmo10010CtrlfecDisableTable 1 }


Pmo10010CtrlfecDisableEntry ::=
	SEQUENCE {
	pmo10010CtrlfecDisableIndex
		INTEGER,
	pmo10010CtrlfecDisablePortn
		EkiState
	}


pmo10010CtrlfecDisableIndex OBJECT-TYPE
	SYNTAX  INTEGER(0..128)
	MAX-ACCESS  read-only
	STATUS current
	DESCRIPTION
        "
        Index definition for the pmo10010CtrlfecDisable 
        table
        "
	::= { pmo10010CtrlfecDisableEntry 1 }


pmo10010CtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pmo10010CtrlfecDisableEntry 2 }


--- *****************************************************
---     LEAF for the ledTest article
--- *****************************************************
pmo10010CtrlledTest OBJECT IDENTIFIER ::= { pmo10010CtrlOther 192 }




pmo10010CtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pmo10010CtrlledTest 3 }



pmo10010CtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pmo10010CtrlledTest 2 }



pmo10010CtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pmo10010CtrlledTest 1 }



--- *****************************************************
---     LEAF for the initSwitchMarvell article
--- *****************************************************
pmo10010CtrlinitSwitchMarvell OBJECT IDENTIFIER ::= { pmo10010CtrlOther 201 }




pmo10010CtrlInitSwitchMarvell OBJECT-TYPE
	  SYNTAX EkiOnOff
	  MAX-ACCESS read-write
	  STATUS current
	  DESCRIPTION
        "
        Switch Initialization :This OID 
        operates an initialization of the 
        switch managed through the module 
         <Help>  This control activates 
        an initialization of the switch 
        managed through the module
        "
	  ::= { pmo10010CtrlinitSwitchMarvell 1 }



--- *********************************************************
---     TABLE for the pmo10010CtrlmsaLineLoop articles
--- *********************************************************

pmo10010CtrlmsaLineLoopTable OBJECT-TYPE
	SYNTAX  SEQUENCE OF Pmo10010CtrlmsaLineLoopEntry
	MAX-ACCESS not-accessible
	STATUS current
	DESCRIPTION
        "
        List of pmo10010CtrlmsaLineLoop 
        Article
        "
	::= { pmo10010CtrlLine 209 }


pmo10010CtrlmsaLineLoopEntry OBJECT-TYPE
	SYNTAX Pmo10010CtrlmsaLineLoopEntry
	MAX-ACCESS not-accessible
	STATUS current
	DESCRIPTION
        "
        Row definition for the pmo10010CtrlmsaLineLoop 
        table
        "
	INDEX   { pmo10010CtrlmsaLineLoopIndex }
	::= { pmo10010CtrlmsaLineLoopTable 1 }


Pmo10010CtrlmsaLineLoopEntry ::=
	SEQUENCE {
	pmo10010CtrlmsaLineLoopIndex
		INTEGER,
	pmo10010CtrlmsaLineLoopPortn
		EkiState
	}


pmo10010CtrlmsaLineLoopIndex OBJECT-TYPE
	SYNTAX  INTEGER(0..128)
	MAX-ACCESS  read-only
	STATUS current
	DESCRIPTION
        "
        Index definition for the pmo10010CtrlmsaLineLoop 
        table
        "
	::= { pmo10010CtrlmsaLineLoopEntry 1 }


pmo10010CtrlmsaLineLoopPortn OBJECT-TYPE
	SYNTAX  EkiState
	MAX-ACCESS read-write
	STATUS current
	DESCRIPTION
        "
        MSA Line Loop :This OID operates 
        a line loopback on the MSA Line 
         <Help>  This control defines the 
        line loop back of the line transceiver
        "
	::= { pmo10010CtrlmsaLineLoopEntry 2 }


--- *********************************************************
---     TABLE for the pmo10010CtrlmsaTxReset articles
--- *********************************************************

pmo10010CtrlmsaTxResetTable OBJECT-TYPE
	SYNTAX  SEQUENCE OF Pmo10010CtrlmsaTxResetEntry
	MAX-ACCESS not-accessible
	STATUS current
	DESCRIPTION
        "
        List of pmo10010CtrlmsaTxReset 
        Article
        "
	::= { pmo10010CtrlLine 210 }


pmo10010CtrlmsaTxResetEntry OBJECT-TYPE
	SYNTAX Pmo10010CtrlmsaTxResetEntry
	MAX-ACCESS not-accessible
	STATUS current
	DESCRIPTION
        "
        Row definition for the pmo10010CtrlmsaTxReset 
        table
        "
	INDEX   { pmo10010CtrlmsaTxResetIndex }
	::= { pmo10010CtrlmsaTxResetTable 1 }


Pmo10010CtrlmsaTxResetEntry ::=
	SEQUENCE {
	pmo10010CtrlmsaTxResetIndex
		INTEGER,
	pmo10010CtrlmsaTxResetPortn
		EkiState
	}


pmo10010CtrlmsaTxResetIndex OBJECT-TYPE
	SYNTAX  INTEGER(0..128)
	MAX-ACCESS  read-only
	STATUS current
	DESCRIPTION
        "
        Index definition for the pmo10010CtrlmsaTxReset 
        table
        "
	::= { pmo10010CtrlmsaTxResetEntry 1 }


pmo10010CtrlmsaTxResetPortn OBJECT-TYPE
	SYNTAX  EkiState
	MAX-ACCESS read-write
	STATUS current
	DESCRIPTION
        "
        Line MSA TX Reset :This OID resets 
        the TX portion of the MSA line
         module  <Help > This control 
         initiates a reset of the transmitting 
        side
        "
	::= { pmo10010CtrlmsaTxResetEntry 2 }


--- *********************************************************
---     TABLE for the pmo10010CtrlmsaRxReset articles
--- *********************************************************

pmo10010CtrlmsaRxResetTable OBJECT-TYPE
	SYNTAX  SEQUENCE OF Pmo10010CtrlmsaRxResetEntry
	MAX-ACCESS not-accessible
	STATUS current
	DESCRIPTION
        "
        List of pmo10010CtrlmsaRxReset 
        Article
        "
	::= { pmo10010CtrlLine 211 }


pmo10010CtrlmsaRxResetEntry OBJECT-TYPE
	SYNTAX Pmo10010CtrlmsaRxResetEntry
	MAX-ACCESS not-accessible
	STATUS current
	DESCRIPTION
        "
        Row definition for the pmo10010CtrlmsaRxReset 
        table
        "
	INDEX   { pmo10010CtrlmsaRxResetIndex }
	::= { pmo10010CtrlmsaRxResetTable 1 }


Pmo10010CtrlmsaRxResetEntry ::=
	SEQUENCE {
	pmo10010CtrlmsaRxResetIndex
		INTEGER,
	pmo10010CtrlmsaRxResetPortn
		EkiState
	}


pmo10010CtrlmsaRxResetIndex OBJECT-TYPE
	SYNTAX  INTEGER(0..128)
	MAX-ACCESS  read-only
	STATUS current
	DESCRIPTION
        "
        Index definition for the pmo10010CtrlmsaRxReset 
        table
        "
	::= { pmo10010CtrlmsaRxResetEntry 1 }


pmo10010CtrlmsaRxResetPortn OBJECT-TYPE
	SYNTAX  EkiState
	MAX-ACCESS read-write
	STATUS current
	DESCRIPTION
        "
        Line MSA RX Reset :This OID resets 
        the RX portion of the MSA line
         module  <Help > This control 
         initiates a reset of the receiving 
        side
        "
	::= { pmo10010CtrlmsaRxResetEntry 2 }


--- *********************************************************
---     TABLE for the pmo10010CtrlmsaShutdown articles
--- *********************************************************

pmo10010CtrlmsaShutdownTable OBJECT-TYPE
	SYNTAX  SEQUENCE OF Pmo10010CtrlmsaShutdownEntry
	MAX-ACCESS not-accessible
	STATUS current
	DESCRIPTION
        "
        List of pmo10010CtrlmsaShutdown 
        Article
        "
	::= { pmo10010CtrlLine 212 }


pmo10010CtrlmsaShutdownEntry OBJECT-TYPE
	SYNTAX Pmo10010CtrlmsaShutdownEntry
	MAX-ACCESS not-accessible
	STATUS current
	DESCRIPTION
        "
        Row definition for the pmo10010CtrlmsaShutdown 
        table
        "
	INDEX   { pmo10010CtrlmsaShutdownIndex }
	::= { pmo10010CtrlmsaShutdownTable 1 }


Pmo10010CtrlmsaShutdownEntry ::=
	SEQUENCE {
	pmo10010CtrlmsaShutdownIndex
		INTEGER,
	pmo10010CtrlmsaShutdownPortn
		EkiState
	}


pmo10010CtrlmsaShutdownIndex OBJECT-TYPE
	SYNTAX  INTEGER(0..128)
	MAX-ACCESS  read-only
	STATUS current
	DESCRIPTION
        "
        Index definition for the pmo10010CtrlmsaShutdown 
        table
        "
	::= { pmo10010CtrlmsaShutdownEntry 1 }


pmo10010CtrlmsaShutdownPortn OBJECT-TYPE
	SYNTAX  EkiState
	MAX-ACCESS read-write
	STATUS current
	DESCRIPTION
        "
        Line MSA Shutdown :This OID enters 
        a process to shutdown the MSA line 
        module  <Help > This control  initiates 
        a shutdown of the module
        "
	::= { pmo10010CtrlmsaShutdownEntry 2 }


--- *****************************************************
---     LEAF for the resetCount article
--- *****************************************************
pmo10010CtrlresetCount OBJECT IDENTIFIER ::= { pmo10010CtrlOther 259 }




pmo10010CtrlResetcount OBJECT-TYPE
	  SYNTAX EkiOnOff
	  MAX-ACCESS read-write
	  STATUS current
	  DESCRIPTION
        "
        Module Count Global Reset :This 
        OID resets all the errors counters 
        on the module  <Help > This control 
         initiates a reset of the errors 
        counters on the module
        "
	  ::= { pmo10010CtrlresetCount 1 }



--- *****************************************************
---     LEAF for the resetRmon article
--- *****************************************************
pmo10010CtrlresetRmon OBJECT IDENTIFIER ::= { pmo10010CtrlOther 260 }




pmo10010CtrlResetrmon OBJECT-TYPE
	  SYNTAX EkiOnOff
	  MAX-ACCESS read-write
	  STATUS current
	  DESCRIPTION
        "
        Module Rmon Global Reset :This 
        OID resets all the Rmon counters 
        on the module  <Help > This control 
         initiates a reset of the Rmon
         counters on the module
        "
	  ::= { pmo10010CtrlresetRmon 1 }



--- *****************************************************
---     LEAF for the resetMeasurements article
--- *****************************************************
pmo10010CtrlresetMeasurements OBJECT IDENTIFIER ::= { pmo10010CtrlOther 261 }




pmo10010CtrlResetmeasurements OBJECT-TYPE
	  SYNTAX EkiOnOff
	  MAX-ACCESS read-write
	  STATUS current
	  DESCRIPTION
        "
        Management Meas Global Reset :This 
        OID resets some measurements on 
        the management  <Help > This control 
         initiates a reset of some measurements 
        on the management
        "
	  ::= { pmo10010CtrlresetMeasurements 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pmo10010CntclientInputErrorCounterLaneOne articles
--- *********************************************************

pmo10010CntclientInputErrorCounterLaneOneTable OBJECT-TYPE
	SYNTAX  SEQUENCE OF Pmo10010CntclientInputErrorCounterLaneOneEntry
	MAX-ACCESS not-accessible
	STATUS current
	DESCRIPTION
        "
        List of pmo10010CntclientInputErrorCounterLaneOne 
        Article
        "
	::= { pmo10010CntClient 16 }


pmo10010CntclientInputErrorCounterLaneOneEntry OBJECT-TYPE
	SYNTAX Pmo10010CntclientInputErrorCounterLaneOneEntry
	MAX-ACCESS not-accessible
	STATUS current
	DESCRIPTION
        "
        Row definition for the pmo10010CntclientInputErrorCounterLaneOne 
        table
        "
	INDEX   { pmo10010CntclientInputErrorCounterLaneOneIndex }
	::= { pmo10010CntclientInputErrorCounterLaneOneTable 1 }


Pmo10010CntclientInputErrorCounterLaneOneEntry ::=
	SEQUENCE {
	pmo10010CntclientInputErrorCounterLaneOneIndex
		INTEGER,
	pmo10010CntclientInputErrorCounterLaneOneValuePortn
		Counter32,
	pmo10010CntclientInputErrorCounterLaneOneErrorPortn
		EkiOnOff,
	pmo10010CntclientInputErrorCounterLaneOneOverloadPortn
		EkiOnOff
	}


pmo10010CntclientInputErrorCounterLaneOneIndex OBJECT-TYPE
	SYNTAX  INTEGER(0..128)
	MAX-ACCESS  read-only
	STATUS current
	DESCRIPTION
        "
        Index definition for the pmo10010CntclientInputErrorCounterLaneOne 
        table
        "
	::= { pmo10010CntclientInputErrorCounterLaneOneEntry 1 }


pmo10010CntclientInputErrorCounterLaneOneValuePortn OBJECT-TYPE
	SYNTAX  Counter32
	MAX-ACCESS read-only
	STATUS current
	DESCRIPTION
        "
        Client_Input_Error_Counter_Lane1 
        :This counter is incremented each 
        time a coding violation is detected 
        on the host lane of the client
         transceiver <Help> This counter 
        is incremented each time a coding 
        violation is detected on the host 
        lane of the client transceiver
        "
	::= { pmo10010CntclientInputErrorCounterLaneOneEntry 2 }


pmo10010CntclientInputErrorCounterLaneOneErrorPortn OBJECT-TYPE
	SYNTAX  EkiOnOff
	MAX-ACCESS read-only
	STATUS current
	DESCRIPTION
        "
        Client Input Counter Error :This 
        OID when set indicates the rate 
        adaptation removal counter value 
        is invalid on Port
        "
	::= { pmo10010CntclientInputErrorCounterLaneOneEntry 3 }


pmo10010CntclientInputErrorCounterLaneOneOverloadPortn OBJECT-TYPE
	SYNTAX  EkiOnOff
	MAX-ACCESS read-only
	STATUS current
	DESCRIPTION
        "
        Client Input Counter Overload
         :This OID when set indicates a 
        rate adaptation removal counter 
        overload on Port
        "
	::= { pmo10010CntclientInputErrorCounterLaneOneEntry 4 }


--- *********************************************************
---     TABLE for the pmo10010CntclientInputErrorCounterLaneTwo articles
--- *********************************************************

pmo10010CntclientInputErrorCounterLaneTwoTable OBJECT-TYPE
	SYNTAX  SEQUENCE OF Pmo10010CntclientInputErrorCounterLaneTwoEntry
	MAX-ACCESS not-accessible
	STATUS current
	DESCRIPTION
        "
        List of pmo10010CntclientInputErrorCounterLaneTwo 
        Article
        "
	::= { pmo10010CntClient 32 }


pmo10010CntclientInputErrorCounterLaneTwoEntry OBJECT-TYPE
	SYNTAX Pmo10010CntclientInputErrorCounterLaneTwoEntry
	MAX-ACCESS not-accessible
	STATUS current
	DESCRIPTION
        "
        Row definition for the pmo10010CntclientInputErrorCounterLaneTwo 
        table
        "
	INDEX   { pmo10010CntclientInputErrorCounterLaneTwoIndex }
	::= { pmo10010CntclientInputErrorCounterLaneTwoTable 1 }


Pmo10010CntclientInputErrorCounterLaneTwoEntry ::=
	SEQUENCE {
	pmo10010CntclientInputErrorCounterLaneTwoIndex
		INTEGER,
	pmo10010CntclientInputErrorCounterLaneTwoValuePortn
		Counter32,
	pmo10010CntclientInputErrorCounterLaneTwoErrorPortn
		EkiOnOff,
	pmo10010CntclientInputErrorCounterLaneTwoOverloadPortn
		EkiOnOff
	}


pmo10010CntclientInputErrorCounterLaneTwoIndex OBJECT-TYPE
	SYNTAX  INTEGER(0..128)
	MAX-ACCESS  read-only
	STATUS current
	DESCRIPTION
        "
        Index definition for the pmo10010CntclientInputErrorCounterLaneTwo 
        table
        "
	::= { pmo10010CntclientInputErrorCounterLaneTwoEntry 1 }


pmo10010CntclientInputErrorCounterLaneTwoValuePortn OBJECT-TYPE
	SYNTAX  Counter32
	MAX-ACCESS read-only
	STATUS current
	DESCRIPTION
        "
        Client_Input_Error_Counter_Lane2 
        :This counter is incremented each 
        time a coding violation is detected 
        on the host lane of the client
         transceiver <Help> This counter 
        is incremented each time a coding 
        violation is detected on the host 
        lane of the client transceiver
        "
	::= { pmo10010CntclientInputErrorCounterLaneTwoEntry 2 }


pmo10010CntclientInputErrorCounterLaneTwoErrorPortn OBJECT-TYPE
	SYNTAX  EkiOnOff
	MAX-ACCESS read-only
	STATUS current
	DESCRIPTION
        "
        Client Input Counter Error :This 
        OID when set indicates the client 
        error counter value is invalid
         on Port
        "
	::= { pmo10010CntclientInputErrorCounterLaneTwoEntry 3 }


pmo10010CntclientInputErrorCounterLaneTwoOverloadPortn OBJECT-TYPE
	SYNTAX  EkiOnOff
	MAX-ACCESS read-only
	STATUS current
	DESCRIPTION
        "
        Client Input Counter Overload
         :This OID when set indicates a 
        client input error counter overload 
        on Port
        "
	::= { pmo10010CntclientInputErrorCounterLaneTwoEntry 4 }


--- *********************************************************
---     TABLE for the pmo10010CntclientInputErrorCounter articles
--- *********************************************************

pmo10010CntclientInputErrorCounterTable OBJECT-TYPE
	SYNTAX  SEQUENCE OF Pmo10010CntclientInputErrorCounterEntry
	MAX-ACCESS not-accessible
	STATUS current
	DESCRIPTION
        "
        List of pmo10010CntclientInputErrorCounter 
        Article
        "
	::= { pmo10010CntClient 80 }


pmo10010CntclientInputErrorCounterEntry OBJECT-TYPE
	SYNTAX Pmo10010CntclientInputErrorCounterEntry
	MAX-ACCESS not-accessible
	STATUS current
	DESCRIPTION
        "
        Row definition for the pmo10010CntclientInputErrorCounter 
        table
        "
	INDEX   { pmo10010CntclientInputErrorCounterIndex }
	::= { pmo10010CntclientInputErrorCounterTable 1 }


Pmo10010CntclientInputErrorCounterEntry ::=
	SEQUENCE {
	pmo10010CntclientInputErrorCounterIndex
		INTEGER,
	pmo10010CntclientInputErrorCounterValuePortn
		Counter32,
	pmo10010CntclientInputErrorCounterErrorPortn
		EkiOnOff,
	pmo10010CntclientInputErrorCounterOverloadPortn
		EkiOnOff
	}


pmo10010CntclientInputErrorCounterIndex OBJECT-TYPE
	SYNTAX  INTEGER(0..128)
	MAX-ACCESS  read-only
	STATUS current
	DESCRIPTION
        "
        Index definition for the pmo10010CntclientInputErrorCounter 
        table
        "
	::= { pmo10010CntclientInputErrorCounterEntry 1 }


pmo10010CntclientInputErrorCounterValuePortn OBJECT-TYPE
	SYNTAX  Counter32
	MAX-ACCESS read-only
	STATUS current
	DESCRIPTION
        "
        Client Input Errors :This counter 
        is increased each time an error 
        is detected on the Client input 
        stream  <Help>  This counter gives 
        the number of CBIP errors (at 100G) 
        on the client port
        "
	::= { pmo10010CntclientInputErrorCounterEntry 2 }


pmo10010CntclientInputErrorCounterErrorPortn OBJECT-TYPE
	SYNTAX  EkiOnOff
	MAX-ACCESS read-only
	STATUS current
	DESCRIPTION
        "
        Client Counter Error :This OID 
        when set indicates the client error 
        counter value is invalid on Port
        "
	::= { pmo10010CntclientInputErrorCounterEntry 3 }


pmo10010CntclientInputErrorCounterOverloadPortn OBJECT-TYPE
	SYNTAX  EkiOnOff
	MAX-ACCESS read-only
	STATUS current
	DESCRIPTION
        "
        Client Counter Overload :This
         OID when set indicates a client 
        input error counter overload on 
        Port
        "
	::= { pmo10010CntclientInputErrorCounterEntry 4 }


--- *********************************************************
---     TABLE for the pmo10010CntclientOutputErrorCounter articles
--- *********************************************************

pmo10010CntclientOutputErrorCounterTable OBJECT-TYPE
	SYNTAX  SEQUENCE OF Pmo10010CntclientOutputErrorCounterEntry
	MAX-ACCESS not-accessible
	STATUS current
	DESCRIPTION
        "
        List of pmo10010CntclientOutputErrorCounter 
        Article
        "
	::= { pmo10010CntClient 96 }


pmo10010CntclientOutputErrorCounterEntry OBJECT-TYPE
	SYNTAX Pmo10010CntclientOutputErrorCounterEntry
	MAX-ACCESS not-accessible
	STATUS current
	DESCRIPTION
        "
        Row definition for the pmo10010CntclientOutputErrorCounter 
        table
        "
	INDEX   { pmo10010CntclientOutputErrorCounterIndex }
	::= { pmo10010CntclientOutputErrorCounterTable 1 }


Pmo10010CntclientOutputErrorCounterEntry ::=
	SEQUENCE {
	pmo10010CntclientOutputErrorCounterIndex
		INTEGER,
	pmo10010CntclientOutputErrorCounterValuePortn
		Counter32,
	pmo10010CntclientOutputErrorCounterErrorPortn
		EkiOnOff,
	pmo10010CntclientOutputErrorCounterOverloadPortn
		EkiOnOff
	}


pmo10010CntclientOutputErrorCounterIndex OBJECT-TYPE
	SYNTAX  INTEGER(0..128)
	MAX-ACCESS  read-only
	STATUS current
	DESCRIPTION
        "
        Index definition for the pmo10010CntclientOutputErrorCounter 
        table
        "
	::= { pmo10010CntclientOutputErrorCounterEntry 1 }


pmo10010CntclientOutputErrorCounterValuePortn OBJECT-TYPE
	SYNTAX  Counter32
	MAX-ACCESS read-only
	STATUS current
	DESCRIPTION
        "
        Client Output Errors :This counter 
        is increased each time an error 
        is detected on the Client output 
        stream  <Help>  This counter gives 
        the number of CBIP errors (at 100G) 
        or ODU2 BIP-8 errors (at 10G) on 
        the client port
        "
	::= { pmo10010CntclientOutputErrorCounterEntry 2 }


pmo10010CntclientOutputErrorCounterErrorPortn OBJECT-TYPE
	SYNTAX  EkiOnOff
	MAX-ACCESS read-only
	STATUS current
	DESCRIPTION
        "
        Client Counter Error :This OID 
        when set indicates the client error 
        counter value is invalid on Port
        "
	::= { pmo10010CntclientOutputErrorCounterEntry 3 }


pmo10010CntclientOutputErrorCounterOverloadPortn OBJECT-TYPE
	SYNTAX  EkiOnOff
	MAX-ACCESS read-only
	STATUS current
	DESCRIPTION
        "
        Client Counter Overload :This
         OID when set indicates a client 
        input error counter overload on 
        Port
        "
	::= { pmo10010CntclientOutputErrorCounterEntry 4 }


--- *********************************************************
---     TABLE for the pmo10010CntlocalLineSmBlockErrorCounter articles
--- *********************************************************

pmo10010CntlocalLineSmBlockErrorCounterTable OBJECT-TYPE
	SYNTAX  SEQUENCE OF Pmo10010CntlocalLineSmBlockErrorCounterEntry
	MAX-ACCESS not-accessible
	STATUS current
	DESCRIPTION
        "
        List of pmo10010CntlocalLineSmBlockErrorCounter 
        Article
        "
	::= { pmo10010CntLine 192 }


pmo10010CntlocalLineSmBlockErrorCounterEntry OBJECT-TYPE
	SYNTAX Pmo10010CntlocalLineSmBlockErrorCounterEntry
	MAX-ACCESS not-accessible
	STATUS current
	DESCRIPTION
        "
        Row definition for the pmo10010CntlocalLineSmBlockErrorCounter 
        table
        "
	INDEX   { pmo10010CntlocalLineSmBlockErrorCounterIndex }
	::= { pmo10010CntlocalLineSmBlockErrorCounterTable 1 }


Pmo10010CntlocalLineSmBlockErrorCounterEntry ::=
	SEQUENCE {
	pmo10010CntlocalLineSmBlockErrorCounterIndex
		INTEGER,
	pmo10010CntlocalLineSmBlockErrorCounterValuePortn
		Counter64,
	pmo10010CntlocalLineSmBlockErrorCounterErrorPortn
		EkiOnOff,
	pmo10010CntlocalLineSmBlockErrorCounterOverloadPortn
		EkiOnOff
	}


pmo10010CntlocalLineSmBlockErrorCounterIndex OBJECT-TYPE
	SYNTAX  INTEGER(0..128)
	MAX-ACCESS  read-only
	STATUS current
	DESCRIPTION
        "
        Index definition for the pmo10010CntlocalLineSmBlockErrorCounter 
        table
        "
	::= { pmo10010CntlocalLineSmBlockErrorCounterEntry 1 }


pmo10010CntlocalLineSmBlockErrorCounterValuePortn OBJECT-TYPE
	SYNTAX  Counter64
	MAX-ACCESS read-only
	STATUS current
	DESCRIPTION
        "
        Line Input SM-Block Errors :This 
        OID gives the current Bit Error 
        Rate (residual SM-BIP8 error) after 
        FEC   <Help> This counter gives 
        the current Bit Error Rate (residual 
        SM-BIP8 error) after FEC
        "
	::= { pmo10010CntlocalLineSmBlockErrorCounterEntry 2 }


pmo10010CntlocalLineSmBlockErrorCounterErrorPortn OBJECT-TYPE
	SYNTAX  EkiOnOff
	MAX-ACCESS read-only
	STATUS current
	DESCRIPTION
        "
        Line Counter Error :This OID when 
        set indicates the B1 error counter 
        value is invalid on Port
        "
	::= { pmo10010CntlocalLineSmBlockErrorCounterEntry 3 }


pmo10010CntlocalLineSmBlockErrorCounterOverloadPortn OBJECT-TYPE
	SYNTAX  EkiOnOff
	MAX-ACCESS read-only
	STATUS current
	DESCRIPTION
        "
        Line Counter Overload :This OID 
        when set indicates a B1 error counter 
        overload on Port
        "
	::= { pmo10010CntlocalLineSmBlockErrorCounterEntry 4 }


--- *********************************************************
---     TABLE for the pmo10010CntlocalLineFecCorrectedErrorsCounter articles
--- *********************************************************

pmo10010CntlocalLineFecCorrectedErrorsCounterTable OBJECT-TYPE
	SYNTAX  SEQUENCE OF Pmo10010CntlocalLineFecCorrectedErrorsCounterEntry
	MAX-ACCESS not-accessible
	STATUS current
	DESCRIPTION
        "
        List of pmo10010CntlocalLineFecCorrectedErrorsCounter 
        Article
        "
	::= { pmo10010CntLine 193 }


pmo10010CntlocalLineFecCorrectedErrorsCounterEntry OBJECT-TYPE
	SYNTAX Pmo10010CntlocalLineFecCorrectedErrorsCounterEntry
	MAX-ACCESS not-accessible
	STATUS current
	DESCRIPTION
        "
        Row definition for the pmo10010CntlocalLineFecCorrectedErrorsCounter 
        table
        "
	INDEX   { pmo10010CntlocalLineFecCorrectedErrorsCounterIndex }
	::= { pmo10010CntlocalLineFecCorrectedErrorsCounterTable 1 }


Pmo10010CntlocalLineFecCorrectedErrorsCounterEntry ::=
	SEQUENCE {
	pmo10010CntlocalLineFecCorrectedErrorsCounterIndex
		INTEGER,
	pmo10010CntlocalLineFecCorrectedErrorsCounterValuePortn
		Counter64,
	pmo10010CntlocalLineFecCorrectedErrorsCounterErrorPortn
		EkiOnOff,
	pmo10010CntlocalLineFecCorrectedErrorsCounterOverloadPortn
		EkiOnOff
	}


pmo10010CntlocalLineFecCorrectedErrorsCounterIndex OBJECT-TYPE
	SYNTAX  INTEGER(0..128)
	MAX-ACCESS  read-only
	STATUS current
	DESCRIPTION
        "
        Index definition for the pmo10010CntlocalLineFecCorrectedErrorsCounter 
        table
        "
	::= { pmo10010CntlocalLineFecCorrectedErrorsCounterEntry 1 }


pmo10010CntlocalLineFecCorrectedErrorsCounterValuePortn OBJECT-TYPE
	SYNTAX  Counter64
	MAX-ACCESS read-only
	STATUS current
	DESCRIPTION
        "
        Line Input FEC Corrected Errors 
        :This OID gives the current Bit 
        Error Rate before the Hard Decision 
        FEC  <Help> This counter gives
         the current Bit Error Rate before 
        the Hard Decision FEC
        "
	::= { pmo10010CntlocalLineFecCorrectedErrorsCounterEntry 2 }


pmo10010CntlocalLineFecCorrectedErrorsCounterErrorPortn OBJECT-TYPE
	SYNTAX  EkiOnOff
	MAX-ACCESS read-only
	STATUS current
	DESCRIPTION
        "
        FEC Counter Error :This bit when 
        set indicates the FEC corrected 
        errors counter value is invalid 
        on Line
        "
	::= { pmo10010CntlocalLineFecCorrectedErrorsCounterEntry 3 }


pmo10010CntlocalLineFecCorrectedErrorsCounterOverloadPortn OBJECT-TYPE
	SYNTAX  EkiOnOff
	MAX-ACCESS read-only
	STATUS current
	DESCRIPTION
        "
        FEC Counter Overload :This bit 
        when set indicates a FEC corrected 
        errors counter overload on Line
        "
	::= { pmo10010CntlocalLineFecCorrectedErrorsCounterEntry 4 }


--- *********************************************************
---     TABLE for the pmo10010CntremoteLineSmBlockErrorCounter articles
--- *********************************************************

pmo10010CntremoteLineSmBlockErrorCounterTable OBJECT-TYPE
	SYNTAX  SEQUENCE OF Pmo10010CntremoteLineSmBlockErrorCounterEntry
	MAX-ACCESS not-accessible
	STATUS current
	DESCRIPTION
        "
        List of pmo10010CntremoteLineSmBlockErrorCounter 
        Article
        "
	::= { pmo10010CntLine 194 }


pmo10010CntremoteLineSmBlockErrorCounterEntry OBJECT-TYPE
	SYNTAX Pmo10010CntremoteLineSmBlockErrorCounterEntry
	MAX-ACCESS not-accessible
	STATUS current
	DESCRIPTION
        "
        Row definition for the pmo10010CntremoteLineSmBlockErrorCounter 
        table
        "
	INDEX   { pmo10010CntremoteLineSmBlockErrorCounterIndex }
	::= { pmo10010CntremoteLineSmBlockErrorCounterTable 1 }


Pmo10010CntremoteLineSmBlockErrorCounterEntry ::=
	SEQUENCE {
	pmo10010CntremoteLineSmBlockErrorCounterIndex
		INTEGER,
	pmo10010CntremoteLineSmBlockErrorCounterValuePortn
		Counter64,
	pmo10010CntremoteLineSmBlockErrorCounterErrorPortn
		EkiOnOff,
	pmo10010CntremoteLineSmBlockErrorCounterOverloadPortn
		EkiOnOff
	}


pmo10010CntremoteLineSmBlockErrorCounterIndex OBJECT-TYPE
	SYNTAX  INTEGER(0..128)
	MAX-ACCESS  read-only
	STATUS current
	DESCRIPTION
        "
        Index definition for the pmo10010CntremoteLineSmBlockErrorCounter 
        table
        "
	::= { pmo10010CntremoteLineSmBlockErrorCounterEntry 1 }


pmo10010CntremoteLineSmBlockErrorCounterValuePortn OBJECT-TYPE
	SYNTAX  Counter64
	MAX-ACCESS read-only
	STATUS current
	DESCRIPTION
        "
        Remote SM Block Errors :This OID 
        gives the current Bit Error Rate 
        (residual SM-BIP8 error) after
         FEC on the remote side  <Help> 
        This counter gives the current
         Bit Error Rate (residual SM-BIP8 
        error) after FEC on the remote
         side
        "
	::= { pmo10010CntremoteLineSmBlockErrorCounterEntry 2 }


pmo10010CntremoteLineSmBlockErrorCounterErrorPortn OBJECT-TYPE
	SYNTAX  EkiOnOff
	MAX-ACCESS read-only
	STATUS current
	DESCRIPTION
        "
        Remote Counter Error :This bit 
        when set indicates the FEC corrected 
        errors counter value is invalid 
        on Line
        "
	::= { pmo10010CntremoteLineSmBlockErrorCounterEntry 3 }


pmo10010CntremoteLineSmBlockErrorCounterOverloadPortn OBJECT-TYPE
	SYNTAX  EkiOnOff
	MAX-ACCESS read-only
	STATUS current
	DESCRIPTION
        "
        Remote Counter Overload :This
         bit when set indicates a FEC corrected 
        errors counter overload on Line
        "
	::= { pmo10010CntremoteLineSmBlockErrorCounterEntry 4 }


--- *********************************************************
---     TABLE for the pmo10010CntlineDfrmTimCnt articles
--- *********************************************************

pmo10010CntlineDfrmTimCntTable OBJECT-TYPE
	SYNTAX  SEQUENCE OF Pmo10010CntlineDfrmTimCntEntry
	MAX-ACCESS not-accessible
	STATUS current
	DESCRIPTION
        "
        List of pmo10010CntlineDfrmTimCnt 
        Article
        "
	::= { pmo10010CntLine 195 }


pmo10010CntlineDfrmTimCntEntry OBJECT-TYPE
	SYNTAX Pmo10010CntlineDfrmTimCntEntry
	MAX-ACCESS not-accessible
	STATUS current
	DESCRIPTION
        "
        Row definition for the pmo10010CntlineDfrmTimCnt 
        table
        "
	INDEX   { pmo10010CntlineDfrmTimCntIndex }
	::= { pmo10010CntlineDfrmTimCntTable 1 }


Pmo10010CntlineDfrmTimCntEntry ::=
	SEQUENCE {
	pmo10010CntlineDfrmTimCntIndex
		INTEGER,
	pmo10010CntlineDfrmTimCntValuePortn
		Counter64,
	pmo10010CntlineDfrmTimCntErrorPortn
		EkiOnOff,
	pmo10010CntlineDfrmTimCntOverloadPortn
		EkiOnOff
	}


pmo10010CntlineDfrmTimCntIndex OBJECT-TYPE
	SYNTAX  INTEGER(0..128)
	MAX-ACCESS  read-only
	STATUS current
	DESCRIPTION
        "
        Index definition for the pmo10010CntlineDfrmTimCnt 
        table
        "
	::= { pmo10010CntlineDfrmTimCntEntry 1 }


pmo10010CntlineDfrmTimCntValuePortn OBJECT-TYPE
	SYNTAX  Counter64
	MAX-ACCESS read-only
	STATUS current
	DESCRIPTION
        "
        Line Timer Counter :
        "
	::= { pmo10010CntlineDfrmTimCntEntry 2 }


pmo10010CntlineDfrmTimCntErrorPortn OBJECT-TYPE
	SYNTAX  EkiOnOff
	MAX-ACCESS read-only
	STATUS current
	DESCRIPTION
        "
        Line Counter Error :This OID when 
        set indicates the deframer timer 
        counter value is invalid on Port
        "
	::= { pmo10010CntlineDfrmTimCntEntry 3 }


pmo10010CntlineDfrmTimCntOverloadPortn OBJECT-TYPE
	SYNTAX  EkiOnOff
	MAX-ACCESS read-only
	STATUS current
	DESCRIPTION
        "
        Line Counter Overload :This OID 
        when set indicates a deframer timer 
        counter overload on Port
        "
	::= { pmo10010CntlineDfrmTimCntEntry 4 }


--- *********************************************************
---     TABLE for the pmo10010CntlocalLineTrscvFecCorrectedErrorCounter articles
--- *********************************************************

pmo10010CntlocalLineTrscvFecCorrectedErrorCounterTable OBJECT-TYPE
	SYNTAX  SEQUENCE OF Pmo10010CntlocalLineTrscvFecCorrectedErrorCounterEntry
	MAX-ACCESS not-accessible
	STATUS current
	DESCRIPTION
        "
        List of pmo10010CntlocalLineTrscvFecCorrectedErrorCounter 
        Article
        "
	::= { pmo10010CntLine 196 }


pmo10010CntlocalLineTrscvFecCorrectedErrorCounterEntry OBJECT-TYPE
	SYNTAX Pmo10010CntlocalLineTrscvFecCorrectedErrorCounterEntry
	MAX-ACCESS not-accessible
	STATUS current
	DESCRIPTION
        "
        Row definition for the pmo10010CntlocalLineTrscvFecCorrectedErrorCounter 
        table
        "
	INDEX   { pmo10010CntlocalLineTrscvFecCorrectedErrorCounterIndex }
	::= { pmo10010CntlocalLineTrscvFecCorrectedErrorCounterTable 1 }


Pmo10010CntlocalLineTrscvFecCorrectedErrorCounterEntry ::=
	SEQUENCE {
	pmo10010CntlocalLineTrscvFecCorrectedErrorCounterIndex
		INTEGER,
	pmo10010CntlocalLineTrscvFecCorrectedErrorCounterValuePortn
		Counter64,
	pmo10010CntlocalLineTrscvFecCorrectedErrorCounterErrorPortn
		EkiOnOff,
	pmo10010CntlocalLineTrscvFecCorrectedErrorCounterOverloadPortn
		EkiOnOff
	}


pmo10010CntlocalLineTrscvFecCorrectedErrorCounterIndex OBJECT-TYPE
	SYNTAX  INTEGER(0..128)
	MAX-ACCESS  read-only
	STATUS current
	DESCRIPTION
        "
        Index definition for the pmo10010CntlocalLineTrscvFecCorrectedErrorCounter 
        table
        "
	::= { pmo10010CntlocalLineTrscvFecCorrectedErrorCounterEntry 1 }


pmo10010CntlocalLineTrscvFecCorrectedErrorCounterValuePortn OBJECT-TYPE
	SYNTAX  Counter64
	MAX-ACCESS read-only
	STATUS current
	DESCRIPTION
        "
        Line Input SD FEC Corrected Errors 
        :This OID gives the current Bit 
        Error Rate before the Soft Decision 
        FEC  <Help> This counter gives
         the current Bit Error Rate before 
        the Soft Decision FEC
        "
	::= { pmo10010CntlocalLineTrscvFecCorrectedErrorCounterEntry 2 }


pmo10010CntlocalLineTrscvFecCorrectedErrorCounterErrorPortn OBJECT-TYPE
	SYNTAX  EkiOnOff
	MAX-ACCESS read-only
	STATUS current
	DESCRIPTION
        "
        Line Counter Error :This OID when 
        set indicates the deframer timer 
        counter value is invalid on Port
        "
	::= { pmo10010CntlocalLineTrscvFecCorrectedErrorCounterEntry 3 }


pmo10010CntlocalLineTrscvFecCorrectedErrorCounterOverloadPortn OBJECT-TYPE
	SYNTAX  EkiOnOff
	MAX-ACCESS read-only
	STATUS current
	DESCRIPTION
        "
        Line Counter Overload :This OID 
        when set indicates a deframer timer 
        counter overload on Port
        "
	::= { pmo10010CntlocalLineTrscvFecCorrectedErrorCounterEntry 4 }


--- *********************************************************
---     TABLE for the pmo10010CntlocalLineTrscvFecUncorrectedErrorCounter articles
--- *********************************************************

pmo10010CntlocalLineTrscvFecUncorrectedErrorCounterTable OBJECT-TYPE
	SYNTAX  SEQUENCE OF Pmo10010CntlocalLineTrscvFecUncorrectedErrorCounterEntry
	MAX-ACCESS not-accessible
	STATUS current
	DESCRIPTION
        "
        List of pmo10010CntlocalLineTrscvFecUncorrectedErrorCounter 
        Article
        "
	::= { pmo10010CntLine 197 }


pmo10010CntlocalLineTrscvFecUncorrectedErrorCounterEntry OBJECT-TYPE
	SYNTAX Pmo10010CntlocalLineTrscvFecUncorrectedErrorCounterEntry
	MAX-ACCESS not-accessible
	STATUS current
	DESCRIPTION
        "
        Row definition for the pmo10010CntlocalLineTrscvFecUncorrectedErrorCounter 
        table
        "
	INDEX   { pmo10010CntlocalLineTrscvFecUncorrectedErrorCounterIndex }
	::= { pmo10010CntlocalLineTrscvFecUncorrectedErrorCounterTable 1 }


Pmo10010CntlocalLineTrscvFecUncorrectedErrorCounterEntry ::=
	SEQUENCE {
	pmo10010CntlocalLineTrscvFecUncorrectedErrorCounterIndex
		INTEGER,
	pmo10010CntlocalLineTrscvFecUncorrectedErrorCounterValuePortn
		Counter64,
	pmo10010CntlocalLineTrscvFecUncorrectedErrorCounterErrorPortn
		EkiOnOff,
	pmo10010CntlocalLineTrscvFecUncorrectedErrorCounterOverloadPortn
		EkiOnOff
	}


pmo10010CntlocalLineTrscvFecUncorrectedErrorCounterIndex OBJECT-TYPE
	SYNTAX  INTEGER(0..128)
	MAX-ACCESS  read-only
	STATUS current
	DESCRIPTION
        "
        Index definition for the pmo10010CntlocalLineTrscvFecUncorrectedErrorCounter 
        table
        "
	::= { pmo10010CntlocalLineTrscvFecUncorrectedErrorCounterEntry 1 }


pmo10010CntlocalLineTrscvFecUncorrectedErrorCounterValuePortn OBJECT-TYPE
	SYNTAX  Counter64
	MAX-ACCESS read-only
	STATUS current
	DESCRIPTION
        "
        SD Uncorrected :This OID gives 
        the current Bit Error Rate after 
        the Soft Decision FEC (residual) 
         <Help> This counter gives the
         current Bit Error Rate after the 
        Soft Decision FEC (residual)
        "
	::= { pmo10010CntlocalLineTrscvFecUncorrectedErrorCounterEntry 2 }


pmo10010CntlocalLineTrscvFecUncorrectedErrorCounterErrorPortn OBJECT-TYPE
	SYNTAX  EkiOnOff
	MAX-ACCESS read-only
	STATUS current
	DESCRIPTION
        "
        Line Counter Error :This OID when 
        set indicates the deframer timer 
        counter value is invalid on Port
        "
	::= { pmo10010CntlocalLineTrscvFecUncorrectedErrorCounterEntry 3 }


pmo10010CntlocalLineTrscvFecUncorrectedErrorCounterOverloadPortn OBJECT-TYPE
	SYNTAX  EkiOnOff
	MAX-ACCESS read-only
	STATUS current
	DESCRIPTION
        "
        Line Counter Overload :This OID 
        when set indicates a deframer timer 
        counter overload on Port
        "
	::= { pmo10010CntlocalLineTrscvFecUncorrectedErrorCounterEntry 4 }


--- *********************************************************
---     TABLE for the pmo10010CntlocalLinePmBlockErrorCounter articles
--- *********************************************************

pmo10010CntlocalLinePmBlockErrorCounterTable OBJECT-TYPE
	SYNTAX  SEQUENCE OF Pmo10010CntlocalLinePmBlockErrorCounterEntry
	MAX-ACCESS not-accessible
	STATUS current
	DESCRIPTION
        "
        List of pmo10010CntlocalLinePmBlockErrorCounter 
        Article
        "
	::= { pmo10010CntLine 200 }


pmo10010CntlocalLinePmBlockErrorCounterEntry OBJECT-TYPE
	SYNTAX Pmo10010CntlocalLinePmBlockErrorCounterEntry
	MAX-ACCESS not-accessible
	STATUS current
	DESCRIPTION
        "
        Row definition for the pmo10010CntlocalLinePmBlockErrorCounter 
        table
        "
	INDEX   { pmo10010CntlocalLinePmBlockErrorCounterIndex }
	::= { pmo10010CntlocalLinePmBlockErrorCounterTable 1 }


Pmo10010CntlocalLinePmBlockErrorCounterEntry ::=
	SEQUENCE {
	pmo10010CntlocalLinePmBlockErrorCounterIndex
		INTEGER,
	pmo10010CntlocalLinePmBlockErrorCounterValuePortn
		Counter64,
	pmo10010CntlocalLinePmBlockErrorCounterErrorPortn
		EkiOnOff,
	pmo10010CntlocalLinePmBlockErrorCounterOverloadPortn
		EkiOnOff
	}


pmo10010CntlocalLinePmBlockErrorCounterIndex OBJECT-TYPE
	SYNTAX  INTEGER(0..128)
	MAX-ACCESS  read-only
	STATUS current
	DESCRIPTION
        "
        Index definition for the pmo10010CntlocalLinePmBlockErrorCounter 
        table
        "
	::= { pmo10010CntlocalLinePmBlockErrorCounterEntry 1 }


pmo10010CntlocalLinePmBlockErrorCounterValuePortn OBJECT-TYPE
	SYNTAX  Counter64
	MAX-ACCESS read-only
	STATUS current
	DESCRIPTION
        "
        Line Input PM Block Errors :This 
        OID gives the PM B1 errors counted 
        as block errors <Help> This counter 
        gives the PM B1 errors counted
         as block errors
        "
	::= { pmo10010CntlocalLinePmBlockErrorCounterEntry 2 }


pmo10010CntlocalLinePmBlockErrorCounterErrorPortn OBJECT-TYPE
	SYNTAX  EkiOnOff
	MAX-ACCESS read-only
	STATUS current
	DESCRIPTION
        "
        Line Counter Error :This OID when 
        set indicates the deframer timer 
        counter value is invalid on Port
        "
	::= { pmo10010CntlocalLinePmBlockErrorCounterEntry 3 }


pmo10010CntlocalLinePmBlockErrorCounterOverloadPortn OBJECT-TYPE
	SYNTAX  EkiOnOff
	MAX-ACCESS read-only
	STATUS current
	DESCRIPTION
        "
        Line Counter Overload :This OID 
        when set indicates a deframer timer 
        counter overload on Port
        "
	::= { pmo10010CntlocalLinePmBlockErrorCounterEntry 4 }


--- *********************************************************
---     TABLE for the pmo10010CntremoteLinePmBlockErrorCounter articles
--- *********************************************************

pmo10010CntremoteLinePmBlockErrorCounterTable OBJECT-TYPE
	SYNTAX  SEQUENCE OF Pmo10010CntremoteLinePmBlockErrorCounterEntry
	MAX-ACCESS not-accessible
	STATUS current
	DESCRIPTION
        "
        List of pmo10010CntremoteLinePmBlockErrorCounter 
        Article
        "
	::= { pmo10010CntLine 201 }


pmo10010CntremoteLinePmBlockErrorCounterEntry OBJECT-TYPE
	SYNTAX Pmo10010CntremoteLinePmBlockErrorCounterEntry
	MAX-ACCESS not-accessible
	STATUS current
	DESCRIPTION
        "
        Row definition for the pmo10010CntremoteLinePmBlockErrorCounter 
        table
        "
	INDEX   { pmo10010CntremoteLinePmBlockErrorCounterIndex }
	::= { pmo10010CntremoteLinePmBlockErrorCounterTable 1 }


Pmo10010CntremoteLinePmBlockErrorCounterEntry ::=
	SEQUENCE {
	pmo10010CntremoteLinePmBlockErrorCounterIndex
		INTEGER,
	pmo10010CntremoteLinePmBlockErrorCounterValuePortn
		Counter64,
	pmo10010CntremoteLinePmBlockErrorCounterErrorPortn
		EkiOnOff,
	pmo10010CntremoteLinePmBlockErrorCounterOverloadPortn
		EkiOnOff
	}


pmo10010CntremoteLinePmBlockErrorCounterIndex OBJECT-TYPE
	SYNTAX  INTEGER(0..128)
	MAX-ACCESS  read-only
	STATUS current
	DESCRIPTION
        "
        Index definition for the pmo10010CntremoteLinePmBlockErrorCounter 
        table
        "
	::= { pmo10010CntremoteLinePmBlockErrorCounterEntry 1 }


pmo10010CntremoteLinePmBlockErrorCounterValuePortn OBJECT-TYPE
	SYNTAX  Counter64
	MAX-ACCESS read-only
	STATUS current
	DESCRIPTION
        "
        Remote PM Block Errors :This OID 
        gives the PM Remote Error Indication 
        counted as block errorsPM Remote 
        Error Indication counted as block 
        errors
        "
	::= { pmo10010CntremoteLinePmBlockErrorCounterEntry 2 }


pmo10010CntremoteLinePmBlockErrorCounterErrorPortn OBJECT-TYPE
	SYNTAX  EkiOnOff
	MAX-ACCESS read-only
	STATUS current
	DESCRIPTION
        "
        Remote Counter Error :This OID 
        when set indicates the deframer 
        timer counter value is invalid
         on Port
        "
	::= { pmo10010CntremoteLinePmBlockErrorCounterEntry 3 }


pmo10010CntremoteLinePmBlockErrorCounterOverloadPortn OBJECT-TYPE
	SYNTAX  EkiOnOff
	MAX-ACCESS read-only
	STATUS current
	DESCRIPTION
        "
        Remote Counter Overload :This
         OID when set indicates a deframer 
        timer counter overload on Port
        "
	::= { pmo10010CntremoteLinePmBlockErrorCounterEntry 4 }







--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pmo10010MonupRmonBytesCounterClientInput articles
--- *********************************************************

pmo10010MonupRmonBytesCounterClientInputTable OBJECT-TYPE
	SYNTAX  SEQUENCE OF Pmo10010MonupRmonBytesCounterClientInputEntry
	MAX-ACCESS not-accessible
	STATUS current
	DESCRIPTION
        "
        List of pmo10010MonupRmonBytesCounterClientInput 
        Article
        "
	::= { pmo10010MonClientRmonCounter 16 }


pmo10010MonupRmonBytesCounterClientInputEntry OBJECT-TYPE
	SYNTAX Pmo10010MonupRmonBytesCounterClientInputEntry
	MAX-ACCESS not-accessible
	STATUS current
	DESCRIPTION
        "
        Row definition for the pmo10010MonupRmonBytesCounterClientInput 
        table
        "
	INDEX   { pmo10010MonupRmonBytesCounterClientInputIndex }
	::= { pmo10010MonupRmonBytesCounterClientInputTable 1 }


Pmo10010MonupRmonBytesCounterClientInputEntry ::=
	SEQUENCE {
	pmo10010MonupRmonBytesCounterClientInputIndex
		INTEGER,
	pmo10010MonupRmonBytesCounterClientInputValuePortn
		Counter64,
	pmo10010MonupRmonBytesCounterClientInputErrorPortn
		EkiOnOff,
	pmo10010MonupRmonBytesCounterClientInputOverloadPortn
		EkiOnOff
	}


pmo10010MonupRmonBytesCounterClientInputIndex OBJECT-TYPE
	SYNTAX  INTEGER(0..128)
	MAX-ACCESS  read-only
	STATUS current
	DESCRIPTION
        "
        Index definition for the pmo10010MonupRmonBytesCounterClientInput 
        table
        "
	::= { pmo10010MonupRmonBytesCounterClientInputEntry 1 }


pmo10010MonupRmonBytesCounterClientInputValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pmo10010MonupRmonBytesCounterClientInputEntry 2 }


pmo10010MonupRmonBytesCounterClientInputErrorPortn OBJECT-TYPE
	SYNTAX  EkiOnOff
	MAX-ACCESS read-only
	STATUS current
	DESCRIPTION
        "
        Bytes Counter Error :This OID
         when set indicates the Bytes counter 
        value is invalid on client port
        "
	::= { pmo10010MonupRmonBytesCounterClientInputEntry 3 }


pmo10010MonupRmonBytesCounterClientInputOverloadPortn OBJECT-TYPE
	SYNTAX  EkiOnOff
	MAX-ACCESS read-only
	STATUS current
	DESCRIPTION
        "
        Bytes Counter Overload :This OID 
        when set indicates a Bytes counter 
        overload on client port
        "
	::= { pmo10010MonupRmonBytesCounterClientInputEntry 4 }


--- *********************************************************
---     TABLE for the pmo10010MonupRmonFcsErrorsCounterClientInput articles
--- *********************************************************

pmo10010MonupRmonFcsErrorsCounterClientInputTable OBJECT-TYPE
	SYNTAX  SEQUENCE OF Pmo10010MonupRmonFcsErrorsCounterClientInputEntry
	MAX-ACCESS not-accessible
	STATUS current
	DESCRIPTION
        "
        List of pmo10010MonupRmonFcsErrorsCounterClientInput 
        Article
        "
	::= { pmo10010MonClientRmonCounter 32 }


pmo10010MonupRmonFcsErrorsCounterClientInputEntry OBJECT-TYPE
	SYNTAX Pmo10010MonupRmonFcsErrorsCounterClientInputEntry
	MAX-ACCESS not-accessible
	STATUS current
	DESCRIPTION
        "
        Row definition for the pmo10010MonupRmonFcsErrorsCounterClientInput 
        table
        "
	INDEX   { pmo10010MonupRmonFcsErrorsCounterClientInputIndex }
	::= { pmo10010MonupRmonFcsErrorsCounterClientInputTable 1 }


Pmo10010MonupRmonFcsErrorsCounterClientInputEntry ::=
	SEQUENCE {
	pmo10010MonupRmonFcsErrorsCounterClientInputIndex
		INTEGER,
	pmo10010MonupRmonFcsErrorsCounterClientInputValuePortn
		Counter64,
	pmo10010MonupRmonFcsErrorsCounterClientInputErrorPortn
		EkiOnOff,
	pmo10010MonupRmonFcsErrorsCounterClientInputOverloadPortn
		EkiOnOff
	}


pmo10010MonupRmonFcsErrorsCounterClientInputIndex OBJECT-TYPE
	SYNTAX  INTEGER(0..128)
	MAX-ACCESS  read-only
	STATUS current
	DESCRIPTION
        "
        Index definition for the pmo10010MonupRmonFcsErrorsCounterClientInput 
        table
        "
	::= { pmo10010MonupRmonFcsErrorsCounterClientInputEntry 1 }


pmo10010MonupRmonFcsErrorsCounterClientInputValuePortn OBJECT-TYPE
	SYNTAX  Counter64
	MAX-ACCESS read-only
	STATUS current
	DESCRIPTION
        "
        Client Input FCS Errors :This
         counter is increased each time 
        a FCS error is detected on the
         client port  <Help>  This counter 
        gives the number of FCS Errors
         received on the client port
        "
	::= { pmo10010MonupRmonFcsErrorsCounterClientInputEntry 2 }


pmo10010MonupRmonFcsErrorsCounterClientInputErrorPortn OBJECT-TYPE
	SYNTAX  EkiOnOff
	MAX-ACCESS read-only
	STATUS current
	DESCRIPTION
        "
        FCS Errors Counter Error :This 
        OID when set indicates the FCS
         Errors counter value is invalid 
        on client port
        "
	::= { pmo10010MonupRmonFcsErrorsCounterClientInputEntry 3 }


pmo10010MonupRmonFcsErrorsCounterClientInputOverloadPortn OBJECT-TYPE
	SYNTAX  EkiOnOff
	MAX-ACCESS read-only
	STATUS current
	DESCRIPTION
        "
        FCS Errors Counter Overload :This 
        OID when set indicates a FCS Errors 
        counter overload on client port
        "
	::= { pmo10010MonupRmonFcsErrorsCounterClientInputEntry 4 }


--- *********************************************************
---     TABLE for the pmo10010MonupRmonPacketsCounterClientInput articles
--- *********************************************************

pmo10010MonupRmonPacketsCounterClientInputTable OBJECT-TYPE
	SYNTAX  SEQUENCE OF Pmo10010MonupRmonPacketsCounterClientInputEntry
	MAX-ACCESS not-accessible
	STATUS current
	DESCRIPTION
        "
        List of pmo10010MonupRmonPacketsCounterClientInput 
        Article
        "
	::= { pmo10010MonClientRmonCounter 48 }


pmo10010MonupRmonPacketsCounterClientInputEntry OBJECT-TYPE
	SYNTAX Pmo10010MonupRmonPacketsCounterClientInputEntry
	MAX-ACCESS not-accessible
	STATUS current
	DESCRIPTION
        "
        Row definition for the pmo10010MonupRmonPacketsCounterClientInput 
        table
        "
	INDEX   { pmo10010MonupRmonPacketsCounterClientInputIndex }
	::= { pmo10010MonupRmonPacketsCounterClientInputTable 1 }


Pmo10010MonupRmonPacketsCounterClientInputEntry ::=
	SEQUENCE {
	pmo10010MonupRmonPacketsCounterClientInputIndex
		INTEGER,
	pmo10010MonupRmonPacketsCounterClientInputValuePortn
		Counter64,
	pmo10010MonupRmonPacketsCounterClientInputErrorPortn
		EkiOnOff,
	pmo10010MonupRmonPacketsCounterClientInputOverloadPortn
		EkiOnOff
	}


pmo10010MonupRmonPacketsCounterClientInputIndex OBJECT-TYPE
	SYNTAX  INTEGER(0..128)
	MAX-ACCESS  read-only
	STATUS current
	DESCRIPTION
        "
        Index definition for the pmo10010MonupRmonPacketsCounterClientInput 
        table
        "
	::= { pmo10010MonupRmonPacketsCounterClientInputEntry 1 }


pmo10010MonupRmonPacketsCounterClientInputValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pmo10010MonupRmonPacketsCounterClientInputEntry 2 }


pmo10010MonupRmonPacketsCounterClientInputErrorPortn OBJECT-TYPE
	SYNTAX  EkiOnOff
	MAX-ACCESS read-only
	STATUS current
	DESCRIPTION
        "
        Packets Counter Error :This OID 
        when set indicates the Packets
         counter value is invalid on client 
        port
        "
	::= { pmo10010MonupRmonPacketsCounterClientInputEntry 3 }


pmo10010MonupRmonPacketsCounterClientInputOverloadPortn OBJECT-TYPE
	SYNTAX  EkiOnOff
	MAX-ACCESS read-only
	STATUS current
	DESCRIPTION
        "
        Packets Counter Overload :This 
        OID when set indicates a Packets 
        counter overload on client port
        "
	::= { pmo10010MonupRmonPacketsCounterClientInputEntry 4 }


--- *********************************************************
---     TABLE for the pmo10010MonupRmonBroadcastCounterClientInput articles
--- *********************************************************

pmo10010MonupRmonBroadcastCounterClientInputTable OBJECT-TYPE
	SYNTAX  SEQUENCE OF Pmo10010MonupRmonBroadcastCounterClientInputEntry
	MAX-ACCESS not-accessible
	STATUS current
	DESCRIPTION
        "
        List of pmo10010MonupRmonBroadcastCounterClientInput 
        Article
        "
	::= { pmo10010MonClientRmonCounter 64 }


pmo10010MonupRmonBroadcastCounterClientInputEntry OBJECT-TYPE
	SYNTAX Pmo10010MonupRmonBroadcastCounterClientInputEntry
	MAX-ACCESS not-accessible
	STATUS current
	DESCRIPTION
        "
        Row definition for the pmo10010MonupRmonBroadcastCounterClientInput 
        table
        "
	INDEX   { pmo10010MonupRmonBroadcastCounterClientInputIndex }
	::= { pmo10010MonupRmonBroadcastCounterClientInputTable 1 }


Pmo10010MonupRmonBroadcastCounterClientInputEntry ::=
	SEQUENCE {
	pmo10010MonupRmonBroadcastCounterClientInputIndex
		INTEGER,
	pmo10010MonupRmonBroadcastCounterClientInputValuePortn
		Counter64,
	pmo10010MonupRmonBroadcastCounterClientInputErrorPortn
		EkiOnOff,
	pmo10010MonupRmonBroadcastCounterClientInputOverloadPortn
		EkiOnOff
	}


pmo10010MonupRmonBroadcastCounterClientInputIndex OBJECT-TYPE
	SYNTAX  INTEGER(0..128)
	MAX-ACCESS  read-only
	STATUS current
	DESCRIPTION
        "
        Index definition for the pmo10010MonupRmonBroadcastCounterClientInput 
        table
        "
	::= { pmo10010MonupRmonBroadcastCounterClientInputEntry 1 }


pmo10010MonupRmonBroadcastCounterClientInputValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pmo10010MonupRmonBroadcastCounterClientInputEntry 2 }


pmo10010MonupRmonBroadcastCounterClientInputErrorPortn OBJECT-TYPE
	SYNTAX  EkiOnOff
	MAX-ACCESS read-only
	STATUS current
	DESCRIPTION
        "
        Broadcast Counter Error :This
         OID when set indicates the Broadcast 
        counter value is invalid on client 
        port
        "
	::= { pmo10010MonupRmonBroadcastCounterClientInputEntry 3 }


pmo10010MonupRmonBroadcastCounterClientInputOverloadPortn OBJECT-TYPE
	SYNTAX  EkiOnOff
	MAX-ACCESS read-only
	STATUS current
	DESCRIPTION
        "
        Broadcast Counter Overload :This 
        OID when set indicates a Broadcast 
        counter overload on client port
        "
	::= { pmo10010MonupRmonBroadcastCounterClientInputEntry 4 }


--- *********************************************************
---     TABLE for the pmo10010MonupRmonMulticastCounterClientInput articles
--- *********************************************************

pmo10010MonupRmonMulticastCounterClientInputTable OBJECT-TYPE
	SYNTAX  SEQUENCE OF Pmo10010MonupRmonMulticastCounterClientInputEntry
	MAX-ACCESS not-accessible
	STATUS current
	DESCRIPTION
        "
        List of pmo10010MonupRmonMulticastCounterClientInput 
        Article
        "
	::= { pmo10010MonClientRmonCounter 80 }


pmo10010MonupRmonMulticastCounterClientInputEntry OBJECT-TYPE
	SYNTAX Pmo10010MonupRmonMulticastCounterClientInputEntry
	MAX-ACCESS not-accessible
	STATUS current
	DESCRIPTION
        "
        Row definition for the pmo10010MonupRmonMulticastCounterClientInput 
        table
        "
	INDEX   { pmo10010MonupRmonMulticastCounterClientInputIndex }
	::= { pmo10010MonupRmonMulticastCounterClientInputTable 1 }


Pmo10010MonupRmonMulticastCounterClientInputEntry ::=
	SEQUENCE {
	pmo10010MonupRmonMulticastCounterClientInputIndex
		INTEGER,
	pmo10010MonupRmonMulticastCounterClientInputValuePortn
		Counter64,
	pmo10010MonupRmonMulticastCounterClientInputErrorPortn
		EkiOnOff,
	pmo10010MonupRmonMulticastCounterClientInputOverloadPortn
		EkiOnOff
	}


pmo10010MonupRmonMulticastCounterClientInputIndex OBJECT-TYPE
	SYNTAX  INTEGER(0..128)
	MAX-ACCESS  read-only
	STATUS current
	DESCRIPTION
        "
        Index definition for the pmo10010MonupRmonMulticastCounterClientInput 
        table
        "
	::= { pmo10010MonupRmonMulticastCounterClientInputEntry 1 }


pmo10010MonupRmonMulticastCounterClientInputValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pmo10010MonupRmonMulticastCounterClientInputEntry 2 }


pmo10010MonupRmonMulticastCounterClientInputErrorPortn OBJECT-TYPE
	SYNTAX  EkiOnOff
	MAX-ACCESS read-only
	STATUS current
	DESCRIPTION
        "
        Multicast Counter Error :This
         OID when set indicates the Multicast 
        counter value is invalid on client 
        port
        "
	::= { pmo10010MonupRmonMulticastCounterClientInputEntry 3 }


pmo10010MonupRmonMulticastCounterClientInputOverloadPortn OBJECT-TYPE
	SYNTAX  EkiOnOff
	MAX-ACCESS read-only
	STATUS current
	DESCRIPTION
        "
        Multicast Counter Overload :This 
        OID when set indicates a Multicast 
        counter overload on client port
        "
	::= { pmo10010MonupRmonMulticastCounterClientInputEntry 4 }


--- *********************************************************
---     TABLE for the pmo10010MonupRmonPauseFrameCounterClientInput articles
--- *********************************************************

pmo10010MonupRmonPauseFrameCounterClientInputTable OBJECT-TYPE
	SYNTAX  SEQUENCE OF Pmo10010MonupRmonPauseFrameCounterClientInputEntry
	MAX-ACCESS not-accessible
	STATUS current
	DESCRIPTION
        "
        List of pmo10010MonupRmonPauseFrameCounterClientInput 
        Article
        "
	::= { pmo10010MonClientRmonCounter 96 }


pmo10010MonupRmonPauseFrameCounterClientInputEntry OBJECT-TYPE
	SYNTAX Pmo10010MonupRmonPauseFrameCounterClientInputEntry
	MAX-ACCESS not-accessible
	STATUS current
	DESCRIPTION
        "
        Row definition for the pmo10010MonupRmonPauseFrameCounterClientInput 
        table
        "
	INDEX   { pmo10010MonupRmonPauseFrameCounterClientInputIndex }
	::= { pmo10010MonupRmonPauseFrameCounterClientInputTable 1 }


Pmo10010MonupRmonPauseFrameCounterClientInputEntry ::=
	SEQUENCE {
	pmo10010MonupRmonPauseFrameCounterClientInputIndex
		INTEGER,
	pmo10010MonupRmonPauseFrameCounterClientInputValuePortn
		Counter64,
	pmo10010MonupRmonPauseFrameCounterClientInputErrorPortn
		EkiOnOff,
	pmo10010MonupRmonPauseFrameCounterClientInputOverloadPortn
		EkiOnOff
	}


pmo10010MonupRmonPauseFrameCounterClientInputIndex OBJECT-TYPE
	SYNTAX  INTEGER(0..128)
	MAX-ACCESS  read-only
	STATUS current
	DESCRIPTION
        "
        Index definition for the pmo10010MonupRmonPauseFrameCounterClientInput 
        table
        "
	::= { pmo10010MonupRmonPauseFrameCounterClientInputEntry 1 }


pmo10010MonupRmonPauseFrameCounterClientInputValuePortn OBJECT-TYPE
	SYNTAX  Counter64
	MAX-ACCESS read-only
	STATUS current
	DESCRIPTION
        "
        Client Input Pause Frames :This 
        counter is increased each time
         a Pause frame is received on the 
        client port  <Help>  This counter 
        gives the number of Pause frames 
        received on the client port
        "
	::= { pmo10010MonupRmonPauseFrameCounterClientInputEntry 2 }


pmo10010MonupRmonPauseFrameCounterClientInputErrorPortn OBJECT-TYPE
	SYNTAX  EkiOnOff
	MAX-ACCESS read-only
	STATUS current
	DESCRIPTION
        "
        Pause Counter Error :This OID
         when set indicates the Pause counter 
        value is invalid on client port
        "
	::= { pmo10010MonupRmonPauseFrameCounterClientInputEntry 3 }


pmo10010MonupRmonPauseFrameCounterClientInputOverloadPortn OBJECT-TYPE
	SYNTAX  EkiOnOff
	MAX-ACCESS read-only
	STATUS current
	DESCRIPTION
        "
        Pause Counter Overload :This OID 
        when set indicates a Pause counter 
        overload on client port
        "
	::= { pmo10010MonupRmonPauseFrameCounterClientInputEntry 4 }


--- *********************************************************
---     TABLE for the pmo10010MonupRmonUnicastCounterClientInput articles
--- *********************************************************

pmo10010MonupRmonUnicastCounterClientInputTable OBJECT-TYPE
	SYNTAX  SEQUENCE OF Pmo10010MonupRmonUnicastCounterClientInputEntry
	MAX-ACCESS not-accessible
	STATUS current
	DESCRIPTION
        "
        List of pmo10010MonupRmonUnicastCounterClientInput 
        Article
        "
	::= { pmo10010MonClientRmonCounter 160 }


pmo10010MonupRmonUnicastCounterClientInputEntry OBJECT-TYPE
	SYNTAX Pmo10010MonupRmonUnicastCounterClientInputEntry
	MAX-ACCESS not-accessible
	STATUS current
	DESCRIPTION
        "
        Row definition for the pmo10010MonupRmonUnicastCounterClientInput 
        table
        "
	INDEX   { pmo10010MonupRmonUnicastCounterClientInputIndex }
	::= { pmo10010MonupRmonUnicastCounterClientInputTable 1 }


Pmo10010MonupRmonUnicastCounterClientInputEntry ::=
	SEQUENCE {
	pmo10010MonupRmonUnicastCounterClientInputIndex
		INTEGER,
	pmo10010MonupRmonUnicastCounterClientInputValuePortn
		Counter64,
	pmo10010MonupRmonUnicastCounterClientInputErrorPortn
		EkiOnOff,
	pmo10010MonupRmonUnicastCounterClientInputOverloadPortn
		EkiOnOff
	}


pmo10010MonupRmonUnicastCounterClientInputIndex OBJECT-TYPE
	SYNTAX  INTEGER(0..128)
	MAX-ACCESS  read-only
	STATUS current
	DESCRIPTION
        "
        Index definition for the pmo10010MonupRmonUnicastCounterClientInput 
        table
        "
	::= { pmo10010MonupRmonUnicastCounterClientInputEntry 1 }


pmo10010MonupRmonUnicastCounterClientInputValuePortn OBJECT-TYPE
	SYNTAX  Counter64
	MAX-ACCESS read-only
	STATUS current
	DESCRIPTION
        "
        Client Input Unicast Packets :This 
        counter is increased each time
         a Unicast packet is received on 
        the client port  <Help>  This counter 
        gives the number of Unicast packets 
        received on the client port
        "
	::= { pmo10010MonupRmonUnicastCounterClientInputEntry 2 }


pmo10010MonupRmonUnicastCounterClientInputErrorPortn OBJECT-TYPE
	SYNTAX  EkiOnOff
	MAX-ACCESS read-only
	STATUS current
	DESCRIPTION
        "
        Unicast Counter Error :This OID 
        when set indicates the Unicast
         counter value is invalid on client 
        port
        "
	::= { pmo10010MonupRmonUnicastCounterClientInputEntry 3 }


pmo10010MonupRmonUnicastCounterClientInputOverloadPortn OBJECT-TYPE
	SYNTAX  EkiOnOff
	MAX-ACCESS read-only
	STATUS current
	DESCRIPTION
        "
        Unicast Counter Overload :This 
        OID when set indicates a Unicast 
        counter overload on client port
        "
	::= { pmo10010MonupRmonUnicastCounterClientInputEntry 4 }


--- *********************************************************
---     TABLE for the pmo10010MonupRmonNonunicastCounterClientInput articles
--- *********************************************************

pmo10010MonupRmonNonunicastCounterClientInputTable OBJECT-TYPE
	SYNTAX  SEQUENCE OF Pmo10010MonupRmonNonunicastCounterClientInputEntry
	MAX-ACCESS not-accessible
	STATUS current
	DESCRIPTION
        "
        List of pmo10010MonupRmonNonunicastCounterClientInput 
        Article
        "
	::= { pmo10010MonClientRmonCounter 176 }


pmo10010MonupRmonNonunicastCounterClientInputEntry OBJECT-TYPE
	SYNTAX Pmo10010MonupRmonNonunicastCounterClientInputEntry
	MAX-ACCESS not-accessible
	STATUS current
	DESCRIPTION
        "
        Row definition for the pmo10010MonupRmonNonunicastCounterClientInput 
        table
        "
	INDEX   { pmo10010MonupRmonNonunicastCounterClientInputIndex }
	::= { pmo10010MonupRmonNonunicastCounterClientInputTable 1 }


Pmo10010MonupRmonNonunicastCounterClientInputEntry ::=
	SEQUENCE {
	pmo10010MonupRmonNonunicastCounterClientInputIndex
		INTEGER,
	pmo10010MonupRmonNonunicastCounterClientInputValuePortn
		Counter64,
	pmo10010MonupRmonNonunicastCounterClientInputErrorPortn
		EkiOnOff,
	pmo10010MonupRmonNonunicastCounterClientInputOverloadPortn
		EkiOnOff
	}


pmo10010MonupRmonNonunicastCounterClientInputIndex OBJECT-TYPE
	SYNTAX  INTEGER(0..128)
	MAX-ACCESS  read-only
	STATUS current
	DESCRIPTION
        "
        Index definition for the pmo10010MonupRmonNonunicastCounterClientInput 
        table
        "
	::= { pmo10010MonupRmonNonunicastCounterClientInputEntry 1 }


pmo10010MonupRmonNonunicastCounterClientInputValuePortn OBJECT-TYPE
	SYNTAX  Counter64
	MAX-ACCESS read-only
	STATUS current
	DESCRIPTION
        "
        Client Input Non Unicast Packets 
        :This counter is increased each 
        time a Non-Unicast packet is received 
        on the client port  <Help>  This 
        counter gives the number of Non-Unicast 
        packets received on the client
         port
        "
	::= { pmo10010MonupRmonNonunicastCounterClientInputEntry 2 }


pmo10010MonupRmonNonunicastCounterClientInputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pmo10010MonupRmonNonunicastCounterClientInputEntry 3 }


pmo10010MonupRmonNonunicastCounterClientInputOverloadPortn OBJECT-TYPE
	SYNTAX  EkiOnOff
	MAX-ACCESS read-only
	STATUS current
	DESCRIPTION
        "
        Non Unicast Counter Overload :This 
        OID when set indicates a Non-Unicast 
        counter overload on client port
        "
	::= { pmo10010MonupRmonNonunicastCounterClientInputEntry 4 }


--- *********************************************************
---     TABLE for the pmo10010MondownRmonBytesCounterClientOutput articles
--- *********************************************************

pmo10010MondownRmonBytesCounterClientOutputTable OBJECT-TYPE
	SYNTAX  SEQUENCE OF Pmo10010MondownRmonBytesCounterClientOutputEntry
	MAX-ACCESS not-accessible
	STATUS current
	DESCRIPTION
        "
        List of pmo10010MondownRmonBytesCounterClientOutput 
        Article
        "
	::= { pmo10010MonClientRmonCounter 208 }


pmo10010MondownRmonBytesCounterClientOutputEntry OBJECT-TYPE
	SYNTAX Pmo10010MondownRmonBytesCounterClientOutputEntry
	MAX-ACCESS not-accessible
	STATUS current
	DESCRIPTION
        "
        Row definition for the pmo10010MondownRmonBytesCounterClientOutput 
        table
        "
	INDEX   { pmo10010MondownRmonBytesCounterClientOutputIndex }
	::= { pmo10010MondownRmonBytesCounterClientOutputTable 1 }


Pmo10010MondownRmonBytesCounterClientOutputEntry ::=
	SEQUENCE {
	pmo10010MondownRmonBytesCounterClientOutputIndex
		INTEGER,
	pmo10010MondownRmonBytesCounterClientOutputValuePortn
		Counter64,
	pmo10010MondownRmonBytesCounterClientOutputErrorPortn
		EkiOnOff,
	pmo10010MondownRmonBytesCounterClientOutputOverloadPortn
		EkiOnOff
	}


pmo10010MondownRmonBytesCounterClientOutputIndex OBJECT-TYPE
	SYNTAX  INTEGER(0..128)
	MAX-ACCESS  read-only
	STATUS current
	DESCRIPTION
        "
        Index definition for the pmo10010MondownRmonBytesCounterClientOutput 
        table
        "
	::= { pmo10010MondownRmonBytesCounterClientOutputEntry 1 }


pmo10010MondownRmonBytesCounterClientOutputValuePortn OBJECT-TYPE
	SYNTAX  Counter64
	MAX-ACCESS read-only
	STATUS current
	DESCRIPTION
        "
        Client Output Bytes :This counter 
        is increased each time a data byte 
        is transmitted on the client port 
         <Help>  This counter gives the 
        number of bytes transmitted on
         the client port
        "
	::= { pmo10010MondownRmonBytesCounterClientOutputEntry 2 }


pmo10010MondownRmonBytesCounterClientOutputErrorPortn OBJECT-TYPE
	SYNTAX  EkiOnOff
	MAX-ACCESS read-only
	STATUS current
	DESCRIPTION
        "
        Bytes Counter Error :This OID
         when set indicates the Bytes counter 
        value is invalid on client port
        "
	::= { pmo10010MondownRmonBytesCounterClientOutputEntry 3 }


pmo10010MondownRmonBytesCounterClientOutputOverloadPortn OBJECT-TYPE
	SYNTAX  EkiOnOff
	MAX-ACCESS read-only
	STATUS current
	DESCRIPTION
        "
        Bytes Counter Overload :This OID 
        when set indicates a Bytes counter 
        overload on client port
        "
	::= { pmo10010MondownRmonBytesCounterClientOutputEntry 4 }


--- *********************************************************
---     TABLE for the pmo10010MondownRmonFcsErrorsCounterClientOutput articles
--- *********************************************************

pmo10010MondownRmonFcsErrorsCounterClientOutputTable OBJECT-TYPE
	SYNTAX  SEQUENCE OF Pmo10010MondownRmonFcsErrorsCounterClientOutputEntry
	MAX-ACCESS not-accessible
	STATUS current
	DESCRIPTION
        "
        List of pmo10010MondownRmonFcsErrorsCounterClientOutput 
        Article
        "
	::= { pmo10010MonClientRmonCounter 224 }


pmo10010MondownRmonFcsErrorsCounterClientOutputEntry OBJECT-TYPE
	SYNTAX Pmo10010MondownRmonFcsErrorsCounterClientOutputEntry
	MAX-ACCESS not-accessible
	STATUS current
	DESCRIPTION
        "
        Row definition for the pmo10010MondownRmonFcsErrorsCounterClientOutput 
        table
        "
	INDEX   { pmo10010MondownRmonFcsErrorsCounterClientOutputIndex }
	::= { pmo10010MondownRmonFcsErrorsCounterClientOutputTable 1 }


Pmo10010MondownRmonFcsErrorsCounterClientOutputEntry ::=
	SEQUENCE {
	pmo10010MondownRmonFcsErrorsCounterClientOutputIndex
		INTEGER,
	pmo10010MondownRmonFcsErrorsCounterClientOutputValuePortn
		Counter64,
	pmo10010MondownRmonFcsErrorsCounterClientOutputErrorPortn
		EkiOnOff,
	pmo10010MondownRmonFcsErrorsCounterClientOutputOverloadPortn
		EkiOnOff
	}


pmo10010MondownRmonFcsErrorsCounterClientOutputIndex OBJECT-TYPE
	SYNTAX  INTEGER(0..128)
	MAX-ACCESS  read-only
	STATUS current
	DESCRIPTION
        "
        Index definition for the pmo10010MondownRmonFcsErrorsCounterClientOutput 
        table
        "
	::= { pmo10010MondownRmonFcsErrorsCounterClientOutputEntry 1 }


pmo10010MondownRmonFcsErrorsCounterClientOutputValuePortn OBJECT-TYPE
	SYNTAX  Counter64
	MAX-ACCESS read-only
	STATUS current
	DESCRIPTION
        "
        Client Output FCS Errors :This 
        counter is increased each time
         a FCS error is detected on the 
        transmit client port  <Help>  This 
        counter gives the number of FCS 
        Errors transmitted on the client 
        port
        "
	::= { pmo10010MondownRmonFcsErrorsCounterClientOutputEntry 2 }


pmo10010MondownRmonFcsErrorsCounterClientOutputErrorPortn OBJECT-TYPE
	SYNTAX  EkiOnOff
	MAX-ACCESS read-only
	STATUS current
	DESCRIPTION
        "
        FCS Errors Counter Error :This 
        OID when set indicates the FCS
         Errors counter value is invalid 
        on client port
        "
	::= { pmo10010MondownRmonFcsErrorsCounterClientOutputEntry 3 }


pmo10010MondownRmonFcsErrorsCounterClientOutputOverloadPortn OBJECT-TYPE
	SYNTAX  EkiOnOff
	MAX-ACCESS read-only
	STATUS current
	DESCRIPTION
        "
        FCS Errors Counter Overload :This 
        OID when set indicates a FCS Errors 
        counter overload on client port
        "
	::= { pmo10010MondownRmonFcsErrorsCounterClientOutputEntry 4 }


--- *********************************************************
---     TABLE for the pmo10010MondownRmonPacketsCounterClientOutput articles
--- *********************************************************

pmo10010MondownRmonPacketsCounterClientOutputTable OBJECT-TYPE
	SYNTAX  SEQUENCE OF Pmo10010MondownRmonPacketsCounterClientOutputEntry
	MAX-ACCESS not-accessible
	STATUS current
	DESCRIPTION
        "
        List of pmo10010MondownRmonPacketsCounterClientOutput 
        Article
        "
	::= { pmo10010MonClientRmonCounter 240 }


pmo10010MondownRmonPacketsCounterClientOutputEntry OBJECT-TYPE
	SYNTAX Pmo10010MondownRmonPacketsCounterClientOutputEntry
	MAX-ACCESS not-accessible
	STATUS current
	DESCRIPTION
        "
        Row definition for the pmo10010MondownRmonPacketsCounterClientOutput 
        table
        "
	INDEX   { pmo10010MondownRmonPacketsCounterClientOutputIndex }
	::= { pmo10010MondownRmonPacketsCounterClientOutputTable 1 }


Pmo10010MondownRmonPacketsCounterClientOutputEntry ::=
	SEQUENCE {
	pmo10010MondownRmonPacketsCounterClientOutputIndex
		INTEGER,
	pmo10010MondownRmonPacketsCounterClientOutputValuePortn
		Counter64,
	pmo10010MondownRmonPacketsCounterClientOutputErrorPortn
		EkiOnOff,
	pmo10010MondownRmonPacketsCounterClientOutputOverloadPortn
		EkiOnOff
	}


pmo10010MondownRmonPacketsCounterClientOutputIndex OBJECT-TYPE
	SYNTAX  INTEGER(0..128)
	MAX-ACCESS  read-only
	STATUS current
	DESCRIPTION
        "
        Index definition for the pmo10010MondownRmonPacketsCounterClientOutput 
        table
        "
	::= { pmo10010MondownRmonPacketsCounterClientOutputEntry 1 }


pmo10010MondownRmonPacketsCounterClientOutputValuePortn OBJECT-TYPE
	SYNTAX  Counter64
	MAX-ACCESS read-only
	STATUS current
	DESCRIPTION
        "
        Client Output Packets :This counter 
        is increased each time a packet 
        is transmitted on the client port 
         <Help>  This counter gives the 
        number of packets transmitted on 
        the client port
        "
	::= { pmo10010MondownRmonPacketsCounterClientOutputEntry 2 }


pmo10010MondownRmonPacketsCounterClientOutputErrorPortn OBJECT-TYPE
	SYNTAX  EkiOnOff
	MAX-ACCESS read-only
	STATUS current
	DESCRIPTION
        "
        Packets Counter Error :This OID 
        when set indicates the Packets
         counter value is invalid on client 
        port
        "
	::= { pmo10010MondownRmonPacketsCounterClientOutputEntry 3 }


pmo10010MondownRmonPacketsCounterClientOutputOverloadPortn OBJECT-TYPE
	SYNTAX  EkiOnOff
	MAX-ACCESS read-only
	STATUS current
	DESCRIPTION
        "
        Packets Counter Overload :This 
        OID when set indicates a Packets 
        counter overload on client port
        "
	::= { pmo10010MondownRmonPacketsCounterClientOutputEntry 4 }


--- *********************************************************
---     TABLE for the pmo10010MondownRmonBroadcastCounterClientOutput articles
--- *********************************************************

pmo10010MondownRmonBroadcastCounterClientOutputTable OBJECT-TYPE
	SYNTAX  SEQUENCE OF Pmo10010MondownRmonBroadcastCounterClientOutputEntry
	MAX-ACCESS not-accessible
	STATUS current
	DESCRIPTION
        "
        List of pmo10010MondownRmonBroadcastCounterClientOutput 
        Article
        "
	::= { pmo10010MonClientRmonCounter 256 }


pmo10010MondownRmonBroadcastCounterClientOutputEntry OBJECT-TYPE
	SYNTAX Pmo10010MondownRmonBroadcastCounterClientOutputEntry
	MAX-ACCESS not-accessible
	STATUS current
	DESCRIPTION
        "
        Row definition for the pmo10010MondownRmonBroadcastCounterClientOutput 
        table
        "
	INDEX   { pmo10010MondownRmonBroadcastCounterClientOutputIndex }
	::= { pmo10010MondownRmonBroadcastCounterClientOutputTable 1 }


Pmo10010MondownRmonBroadcastCounterClientOutputEntry ::=
	SEQUENCE {
	pmo10010MondownRmonBroadcastCounterClientOutputIndex
		INTEGER,
	pmo10010MondownRmonBroadcastCounterClientOutputValuePortn
		Counter64,
	pmo10010MondownRmonBroadcastCounterClientOutputErrorPortn
		EkiOnOff,
	pmo10010MondownRmonBroadcastCounterClientOutputOverloadPortn
		EkiOnOff
	}


pmo10010MondownRmonBroadcastCounterClientOutputIndex OBJECT-TYPE
	SYNTAX  INTEGER(0..128)
	MAX-ACCESS  read-only
	STATUS current
	DESCRIPTION
        "
        Index definition for the pmo10010MondownRmonBroadcastCounterClientOutput 
        table
        "
	::= { pmo10010MondownRmonBroadcastCounterClientOutputEntry 1 }


pmo10010MondownRmonBroadcastCounterClientOutputValuePortn OBJECT-TYPE
	SYNTAX  Counter64
	MAX-ACCESS read-only
	STATUS current
	DESCRIPTION
        "
        Client Output Broadcast Packets 
        :This counter is increased each 
        time a broadcast packet is transmitted 
        on the client port  <Help>  This 
        counter gives the number of Broadcast 
        packets transmitted on the client 
        port
        "
	::= { pmo10010MondownRmonBroadcastCounterClientOutputEntry 2 }


pmo10010MondownRmonBroadcastCounterClientOutputErrorPortn OBJECT-TYPE
	SYNTAX  EkiOnOff
	MAX-ACCESS read-only
	STATUS current
	DESCRIPTION
        "
        Broadcast Counter Error :This
         OID when set indicates the Broadcast 
        counter value is invalid on client 
        port
        "
	::= { pmo10010MondownRmonBroadcastCounterClientOutputEntry 3 }


pmo10010MondownRmonBroadcastCounterClientOutputOverloadPortn OBJECT-TYPE
	SYNTAX  EkiOnOff
	MAX-ACCESS read-only
	STATUS current
	DESCRIPTION
        "
        Broadcast Counter Overload :This 
        OID when set indicates a Broadcast 
        counter overload on client port
        "
	::= { pmo10010MondownRmonBroadcastCounterClientOutputEntry 4 }


--- *********************************************************
---     TABLE for the pmo10010MondownRmonMulticastCounterClientOutput articles
--- *********************************************************

pmo10010MondownRmonMulticastCounterClientOutputTable OBJECT-TYPE
	SYNTAX  SEQUENCE OF Pmo10010MondownRmonMulticastCounterClientOutputEntry
	MAX-ACCESS not-accessible
	STATUS current
	DESCRIPTION
        "
        List of pmo10010MondownRmonMulticastCounterClientOutput 
        Article
        "
	::= { pmo10010MonClientRmonCounter 272 }


pmo10010MondownRmonMulticastCounterClientOutputEntry OBJECT-TYPE
	SYNTAX Pmo10010MondownRmonMulticastCounterClientOutputEntry
	MAX-ACCESS not-accessible
	STATUS current
	DESCRIPTION
        "
        Row definition for the pmo10010MondownRmonMulticastCounterClientOutput 
        table
        "
	INDEX   { pmo10010MondownRmonMulticastCounterClientOutputIndex }
	::= { pmo10010MondownRmonMulticastCounterClientOutputTable 1 }


Pmo10010MondownRmonMulticastCounterClientOutputEntry ::=
	SEQUENCE {
	pmo10010MondownRmonMulticastCounterClientOutputIndex
		INTEGER,
	pmo10010MondownRmonMulticastCounterClientOutputValuePortn
		Counter64,
	pmo10010MondownRmonMulticastCounterClientOutputErrorPortn
		EkiOnOff,
	pmo10010MondownRmonMulticastCounterClientOutputOverloadPortn
		EkiOnOff
	}


pmo10010MondownRmonMulticastCounterClientOutputIndex OBJECT-TYPE
	SYNTAX  INTEGER(0..128)
	MAX-ACCESS  read-only
	STATUS current
	DESCRIPTION
        "
        Index definition for the pmo10010MondownRmonMulticastCounterClientOutput 
        table
        "
	::= { pmo10010MondownRmonMulticastCounterClientOutputEntry 1 }


pmo10010MondownRmonMulticastCounterClientOutputValuePortn OBJECT-TYPE
	SYNTAX  Counter64
	MAX-ACCESS read-only
	STATUS current
	DESCRIPTION
        "
        Client Output Multicast Packets 
        :This counter is increased each 
        time a Multicast packet is transmitted 
        on the client port  <Help>  This 
        counter gives the number of Multicast 
        packets transmitted on the client 
        port
        "
	::= { pmo10010MondownRmonMulticastCounterClientOutputEntry 2 }


pmo10010MondownRmonMulticastCounterClientOutputErrorPortn OBJECT-TYPE
	SYNTAX  EkiOnOff
	MAX-ACCESS read-only
	STATUS current
	DESCRIPTION
        "
        Multicast Counter Error :This
         OID when set indicates the Multicast 
        counter value is invalid on client 
        port
        "
	::= { pmo10010MondownRmonMulticastCounterClientOutputEntry 3 }


pmo10010MondownRmonMulticastCounterClientOutputOverloadPortn OBJECT-TYPE
	SYNTAX  EkiOnOff
	MAX-ACCESS read-only
	STATUS current
	DESCRIPTION
        "
        Multicast Counter Overload :This 
        OID when set indicates a Multicast 
        counter overload on client port
        "
	::= { pmo10010MondownRmonMulticastCounterClientOutputEntry 4 }


--- *********************************************************
---     TABLE for the pmo10010MondownRmonPauseFrameCounterClientOutput articles
--- *********************************************************

pmo10010MondownRmonPauseFrameCounterClientOutputTable OBJECT-TYPE
	SYNTAX  SEQUENCE OF Pmo10010MondownRmonPauseFrameCounterClientOutputEntry
	MAX-ACCESS not-accessible
	STATUS current
	DESCRIPTION
        "
        List of pmo10010MondownRmonPauseFrameCounterClientOutput 
        Article
        "
	::= { pmo10010MonClientRmonCounter 288 }


pmo10010MondownRmonPauseFrameCounterClientOutputEntry OBJECT-TYPE
	SYNTAX Pmo10010MondownRmonPauseFrameCounterClientOutputEntry
	MAX-ACCESS not-accessible
	STATUS current
	DESCRIPTION
        "
        Row definition for the pmo10010MondownRmonPauseFrameCounterClientOutput 
        table
        "
	INDEX   { pmo10010MondownRmonPauseFrameCounterClientOutputIndex }
	::= { pmo10010MondownRmonPauseFrameCounterClientOutputTable 1 }


Pmo10010MondownRmonPauseFrameCounterClientOutputEntry ::=
	SEQUENCE {
	pmo10010MondownRmonPauseFrameCounterClientOutputIndex
		INTEGER,
	pmo10010MondownRmonPauseFrameCounterClientOutputValuePortn
		Counter64,
	pmo10010MondownRmonPauseFrameCounterClientOutputErrorPortn
		EkiOnOff,
	pmo10010MondownRmonPauseFrameCounterClientOutputOverloadPortn
		EkiOnOff
	}


pmo10010MondownRmonPauseFrameCounterClientOutputIndex OBJECT-TYPE
	SYNTAX  INTEGER(0..128)
	MAX-ACCESS  read-only
	STATUS current
	DESCRIPTION
        "
        Index definition for the pmo10010MondownRmonPauseFrameCounterClientOutput 
        table
        "
	::= { pmo10010MondownRmonPauseFrameCounterClientOutputEntry 1 }


pmo10010MondownRmonPauseFrameCounterClientOutputValuePortn OBJECT-TYPE
	SYNTAX  Counter64
	MAX-ACCESS read-only
	STATUS current
	DESCRIPTION
        "
        Client Output Pause Frames :This 
        counter is increased each time
         a Pause frame is transmitted on 
        the client port  <Help>  This counter 
        gives the number of Pause frames 
        transmitted on the client port
        "
	::= { pmo10010MondownRmonPauseFrameCounterClientOutputEntry 2 }


pmo10010MondownRmonPauseFrameCounterClientOutputErrorPortn OBJECT-TYPE
	SYNTAX  EkiOnOff
	MAX-ACCESS read-only
	STATUS current
	DESCRIPTION
        "
        Pause Counter Error :This OID
         when set indicates the Pause counter 
        value is invalid on client port
        "
	::= { pmo10010MondownRmonPauseFrameCounterClientOutputEntry 3 }


pmo10010MondownRmonPauseFrameCounterClientOutputOverloadPortn OBJECT-TYPE
	SYNTAX  EkiOnOff
	MAX-ACCESS read-only
	STATUS current
	DESCRIPTION
        "
        Pause Counter Overload :This OID 
        when set indicates a Pause counter 
        overload on client port
        "
	::= { pmo10010MondownRmonPauseFrameCounterClientOutputEntry 4 }


--- *********************************************************
---     TABLE for the pmo10010MondownRmonUnicastCounterClientOutput articles
--- *********************************************************

pmo10010MondownRmonUnicastCounterClientOutputTable OBJECT-TYPE
	SYNTAX  SEQUENCE OF Pmo10010MondownRmonUnicastCounterClientOutputEntry
	MAX-ACCESS not-accessible
	STATUS current
	DESCRIPTION
        "
        List of pmo10010MondownRmonUnicastCounterClientOutput 
        Article
        "
	::= { pmo10010MonClientRmonCounter 352 }


pmo10010MondownRmonUnicastCounterClientOutputEntry OBJECT-TYPE
	SYNTAX Pmo10010MondownRmonUnicastCounterClientOutputEntry
	MAX-ACCESS not-accessible
	STATUS current
	DESCRIPTION
        "
        Row definition for the pmo10010MondownRmonUnicastCounterClientOutput 
        table
        "
	INDEX   { pmo10010MondownRmonUnicastCounterClientOutputIndex }
	::= { pmo10010MondownRmonUnicastCounterClientOutputTable 1 }


Pmo10010MondownRmonUnicastCounterClientOutputEntry ::=
	SEQUENCE {
	pmo10010MondownRmonUnicastCounterClientOutputIndex
		INTEGER,
	pmo10010MondownRmonUnicastCounterClientOutputValuePortn
		Counter64,
	pmo10010MondownRmonUnicastCounterClientOutputErrorPortn
		EkiOnOff,
	pmo10010MondownRmonUnicastCounterClientOutputOverloadPortn
		EkiOnOff
	}


pmo10010MondownRmonUnicastCounterClientOutputIndex OBJECT-TYPE
	SYNTAX  INTEGER(0..128)
	MAX-ACCESS  read-only
	STATUS current
	DESCRIPTION
        "
        Index definition for the pmo10010MondownRmonUnicastCounterClientOutput 
        table
        "
	::= { pmo10010MondownRmonUnicastCounterClientOutputEntry 1 }


pmo10010MondownRmonUnicastCounterClientOutputValuePortn OBJECT-TYPE
	SYNTAX  Counter64
	MAX-ACCESS read-only
	STATUS current
	DESCRIPTION
        "
        Client Output Unicast Packets
         :This counter is increased each 
        time a Unicast packet is transmitted 
        on the client port  <Help>  This 
        counter gives the number of Unicast 
        packets transmitted on the client 
        port
        "
	::= { pmo10010MondownRmonUnicastCounterClientOutputEntry 2 }


pmo10010MondownRmonUnicastCounterClientOutputErrorPortn OBJECT-TYPE
	SYNTAX  EkiOnOff
	MAX-ACCESS read-only
	STATUS current
	DESCRIPTION
        "
        Unicast Counter Error :This OID 
        when set indicates the Unicast
         counter value is invalid on client 
        port
        "
	::= { pmo10010MondownRmonUnicastCounterClientOutputEntry 3 }


pmo10010MondownRmonUnicastCounterClientOutputOverloadPortn OBJECT-TYPE
	SYNTAX  EkiOnOff
	MAX-ACCESS read-only
	STATUS current
	DESCRIPTION
        "
        Unicast Counter Overload :This 
        OID when set indicates a Unicast 
        counter overload on client port
        "
	::= { pmo10010MondownRmonUnicastCounterClientOutputEntry 4 }


--- *********************************************************
---     TABLE for the pmo10010MondownRmonNonunicastCounterClientOutput articles
--- *********************************************************

pmo10010MondownRmonNonunicastCounterClientOutputTable OBJECT-TYPE
	SYNTAX  SEQUENCE OF Pmo10010MondownRmonNonunicastCounterClientOutputEntry
	MAX-ACCESS not-accessible
	STATUS current
	DESCRIPTION
        "
        List of pmo10010MondownRmonNonunicastCounterClientOutput 
        Article
        "
	::= { pmo10010MonClientRmonCounter 368 }


pmo10010MondownRmonNonunicastCounterClientOutputEntry OBJECT-TYPE
	SYNTAX Pmo10010MondownRmonNonunicastCounterClientOutputEntry
	MAX-ACCESS not-accessible
	STATUS current
	DESCRIPTION
        "
        Row definition for the pmo10010MondownRmonNonunicastCounterClientOutput 
        table
        "
	INDEX   { pmo10010MondownRmonNonunicastCounterClientOutputIndex }
	::= { pmo10010MondownRmonNonunicastCounterClientOutputTable 1 }


Pmo10010MondownRmonNonunicastCounterClientOutputEntry ::=
	SEQUENCE {
	pmo10010MondownRmonNonunicastCounterClientOutputIndex
		INTEGER,
	pmo10010MondownRmonNonunicastCounterClientOutputValuePortn
		Counter64,
	pmo10010MondownRmonNonunicastCounterClientOutputErrorPortn
		EkiOnOff,
	pmo10010MondownRmonNonunicastCounterClientOutputOverloadPortn
		EkiOnOff
	}


pmo10010MondownRmonNonunicastCounterClientOutputIndex OBJECT-TYPE
	SYNTAX  INTEGER(0..128)
	MAX-ACCESS  read-only
	STATUS current
	DESCRIPTION
        "
        Index definition for the pmo10010MondownRmonNonunicastCounterClientOutput 
        table
        "
	::= { pmo10010MondownRmonNonunicastCounterClientOutputEntry 1 }


pmo10010MondownRmonNonunicastCounterClientOutputValuePortn OBJECT-TYPE
	SYNTAX  Counter64
	MAX-ACCESS read-only
	STATUS current
	DESCRIPTION
        "
        Client Output Non Unicast Packets 
        :This counter is increased each 
        time a Non-Unicast packet is transmitted 
        on the client port  <Help>  This 
        counter gives the number of Non-Unicast 
        packets transmitted on the client 
        port
        "
	::= { pmo10010MondownRmonNonunicastCounterClientOutputEntry 2 }


pmo10010MondownRmonNonunicastCounterClientOutputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pmo10010MondownRmonNonunicastCounterClientOutputEntry 3 }


pmo10010MondownRmonNonunicastCounterClientOutputOverloadPortn OBJECT-TYPE
	SYNTAX  EkiOnOff
	MAX-ACCESS read-only
	STATUS current
	DESCRIPTION
        "
        Non Unicast Counter Overload :This 
        OID when set indicates a Non-Unicast 
        counter overload on client port
        "
	::= { pmo10010MondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pmo10010Mesrsynth0 OBJECT-TYPE
	  SYNTAX EkiMeasureType
	  MAX-ACCESS read-only
	  STATUS deprecated
	  DESCRIPTION
        "
        Not Used :
        "
	  ::= { pmo10010MesrOther 0 }



pmo10010Mesrsynth1 OBJECT-TYPE
	  SYNTAX EkiMeasureType
	  MAX-ACCESS read-only
	  STATUS deprecated
	  DESCRIPTION
        "
        Not Used :
        "
	  ::= { pmo10010MesrOther 1 }



--- *****************************************************
---     LEAF for the pmIntervalNumber article
--- *****************************************************

pmo10010MesrpmIntervalNumber OBJECT-TYPE
	  SYNTAX Unsigned32 (0..65535)
	  MAX-ACCESS read-only
	  STATUS current
	  DESCRIPTION
        "
        PM Interval Counter :
        "
	  ::= { pmo10010MesrOther 7 }



--- *****************************************************
---     LEAF for the clientCfpTemp article
--- *****************************************************

pmo10010MesrclientCfpTemp OBJECT-TYPE
	  SYNTAX Unsigned32 (0..65535)
	  MAX-ACCESS read-only
	  STATUS current
	  DESCRIPTION
        "
        Client Trscv Temperature :This 
        OID gives the temperature value 
        of the Client Transceiver, read 
        from the DDM (Digital Diagnostic 
        Monitoring) (Temperature = AV/256) 
        (Unit = C) <Help> This Measure
         gives the temperature value of 
        the Client Transceiver
        "
	  ::= { pmo10010MesrClient 8 }



--- *****************************************************
---     LEAF for the clientCfp3v3Voltage article
--- *****************************************************

pmo10010MesrclientCfp3v3Voltage OBJECT-TYPE
	  SYNTAX Unsigned32 (0..65535)
	  MAX-ACCESS read-only
	  STATUS current
	  DESCRIPTION
        "
        Client Trscv Voltage :This OID 
        gives the 3V3 voltage value of
         the Client Transceiver, read from 
        the DDM (Digital Diagnostic Monitoring) 
         (Voltage = AV/1000) (Unit = V) 
        <Help> This Measure gives the 3V3 
        voltage value of the Client Transceiver
        "
	  ::= { pmo10010MesrClient 9 }



--- *****************************************************
---     LEAF for the clientSoaBiasCurrent article
--- *****************************************************

pmo10010MesrclientSoaBiasCurrent OBJECT-TYPE
	  SYNTAX Unsigned32 (0..65535)
	  MAX-ACCESS read-only
	  STATUS current
	  DESCRIPTION
        "
        Client Trscv SOA Bias :This OID 
        gives the SOA bias value of the 
        Client Transceiver, read from the 
        DDM (Digital Diagnostic Monitoring) 
         (Bias = AV/500) (Unit = mA) <Help> 
        This Measure gives the SOA bias 
        value of the Client Transceiver
        "
	  ::= { pmo10010MesrClient 10 }



--- *****************************************************
---     LEAF for the lineMsaTemp article
--- *****************************************************

pmo10010MesrlineMsaTemp OBJECT-TYPE
	  SYNTAX Unsigned32 (0..65535)
	  MAX-ACCESS read-only
	  STATUS current
	  DESCRIPTION
        "
        Line Trscv Temperature :This OID 
        gives the temperature value of
         the Line Transceiver, read from 
        the DDM (Digital Diagnostic Monitoring) 
         (Temperature = AV/256) (Unit = 
        C) <Help> This Measure gives the 
        temperature value of the Line Transceiver.This 
        temperature must remain below 95°C 
        for proper operation
        "
	  ::= { pmo10010MesrLine 12 }



--- *****************************************************
---     LEAF for the lineMsa3v3Voltage article
--- *****************************************************

pmo10010MesrlineMsa3v3Voltage OBJECT-TYPE
	  SYNTAX Unsigned32 (0..65535)
	  MAX-ACCESS read-only
	  STATUS current
	  DESCRIPTION
        "
        Line Trscv Voltage :This OID gives 
        the 3V3 voltage value of the Line 
        Transceiver, read from the DDM
         (Digital Diagnostic Monitoring) 
        (Voltage = AV/1000) (Unit = V)
         <Help> This Measure gives the
         3V3 voltage value of the Line
         Transceiver
        "
	  ::= { pmo10010MesrLine 13 }



--- *****************************************************
---     LEAF for the lineSoaBiasCurrent article
--- *****************************************************

pmo10010MesrlineSoaBiasCurrent OBJECT-TYPE
	  SYNTAX Unsigned32 (0..65535)
	  MAX-ACCESS read-only
	  STATUS current
	  DESCRIPTION
        "
        Line Trscv SOA Bias :This OID
         gives the SOA bias value of the 
        Line Transceiver,read from the
         DDM (Digital Diagnostic Monitoring) 
         (Bias = AV/500) (Unit = mA) <Help> 
        This Measure gives the SOA bias 
        value of the Line Transceiver
        "
	  ::= { pmo10010MesrLine 14 }



--- *********************************************************
---     TABLE for the pmo10010MesrclientNetTxTemp articles
--- *********************************************************

pmo10010MesrclientNetTxTempTable OBJECT-TYPE
	SYNTAX  SEQUENCE OF Pmo10010MesrclientNetTxTempEntry
	MAX-ACCESS not-accessible
	STATUS current
	DESCRIPTION
        "
        List of pmo10010MesrclientNetTxTemp 
        Article
        "
	::= { pmo10010MesrClient 16 }


pmo10010MesrclientNetTxTempEntry OBJECT-TYPE
	SYNTAX Pmo10010MesrclientNetTxTempEntry
	MAX-ACCESS not-accessible
	STATUS current
	DESCRIPTION
        "
        Row definition for the pmo10010MesrclientNetTxTemp 
        table
        "
	INDEX   { pmo10010MesrclientNetTxTempIndex }
	::= { pmo10010MesrclientNetTxTempTable 1 }


Pmo10010MesrclientNetTxTempEntry ::=
	SEQUENCE {
	pmo10010MesrclientNetTxTempIndex
		INTEGER,
	pmo10010MesrclientNetTxTempPortn
		INTEGER 
	}


pmo10010MesrclientNetTxTempIndex OBJECT-TYPE
	SYNTAX  INTEGER(0..128)
	MAX-ACCESS  read-only
	STATUS current
	DESCRIPTION
        "
        Index definition for the pmo10010MesrclientNetTxTemp 
        table
        "
	::= { pmo10010MesrclientNetTxTempEntry 1 }


pmo10010MesrclientNetTxTempPortn OBJECT-TYPE
	SYNTAX  INTEGER (0..65535)
	MAX-ACCESS read-only
	STATUS current
	DESCRIPTION
        "
        Client Trscv Temperature :This 
        OID gives the Laser temperature 
        value of the Client Transceiver, 
        read from the DDM (Digital Diagnostic 
        Monitoring) (Temperature = AV/256) 
        (Unit = C) <Help> This Measure
         gives the Laser temperature value 
        of the Client Transceiver
        "
	::= { pmo10010MesrclientNetTxTempEntry 2 }


--- *********************************************************
---     TABLE for the pmo10010MesrclientNetTxBias articles
--- *********************************************************

pmo10010MesrclientNetTxBiasTable OBJECT-TYPE
	SYNTAX  SEQUENCE OF Pmo10010MesrclientNetTxBiasEntry
	MAX-ACCESS not-accessible
	STATUS current
	DESCRIPTION
        "
        List of pmo10010MesrclientNetTxBias 
        Article
        "
	::= { pmo10010MesrClient 32 }


pmo10010MesrclientNetTxBiasEntry OBJECT-TYPE
	SYNTAX Pmo10010MesrclientNetTxBiasEntry
	MAX-ACCESS not-accessible
	STATUS current
	DESCRIPTION
        "
        Row definition for the pmo10010MesrclientNetTxBias 
        table
        "
	INDEX   { pmo10010MesrclientNetTxBiasIndex }
	::= { pmo10010MesrclientNetTxBiasTable 1 }


Pmo10010MesrclientNetTxBiasEntry ::=
	SEQUENCE {
	pmo10010MesrclientNetTxBiasIndex
		INTEGER,
	pmo10010MesrclientNetTxBiasPortn
		INTEGER 
	}


pmo10010MesrclientNetTxBiasIndex OBJECT-TYPE
	SYNTAX  INTEGER(0..128)
	MAX-ACCESS  read-only
	STATUS current
	DESCRIPTION
        "
        Index definition for the pmo10010MesrclientNetTxBias 
        table
        "
	::= { pmo10010MesrclientNetTxBiasEntry 1 }


pmo10010MesrclientNetTxBiasPortn OBJECT-TYPE
	SYNTAX  INTEGER (0..65535)
	MAX-ACCESS read-only
	STATUS current
	DESCRIPTION
        "
        Client Trscv Laser Bias :This
         OID gives the Laser bias value 
        of the Client Transceiver, read 
        from the DDM (Digital Diagnostic 
        Monitoring) (Bias = AV/500) (Unit 
        = mA) <Help> This Measure gives 
        the Laser bias value of the Client 
        Transceiver
        "
	::= { pmo10010MesrclientNetTxBiasEntry 2 }


--- *********************************************************
---     TABLE for the pmo10010MesrclientNetTxPwr articles
--- *********************************************************

pmo10010MesrclientNetTxPwrTable OBJECT-TYPE
	SYNTAX  SEQUENCE OF Pmo10010MesrclientNetTxPwrEntry
	MAX-ACCESS not-accessible
	STATUS current
	DESCRIPTION
        "
        List of pmo10010MesrclientNetTxPwr 
        Article
        "
	::= { pmo10010MesrClient 48 }


pmo10010MesrclientNetTxPwrEntry OBJECT-TYPE
	SYNTAX Pmo10010MesrclientNetTxPwrEntry
	MAX-ACCESS not-accessible
	STATUS current
	DESCRIPTION
        "
        Row definition for the pmo10010MesrclientNetTxPwr 
        table
        "
	INDEX   { pmo10010MesrclientNetTxPwrIndex }
	::= { pmo10010MesrclientNetTxPwrTable 1 }


Pmo10010MesrclientNetTxPwrEntry ::=
	SEQUENCE {
	pmo10010MesrclientNetTxPwrIndex
		INTEGER,
	pmo10010MesrclientNetTxPwrPortn
		INTEGER 
	}


pmo10010MesrclientNetTxPwrIndex OBJECT-TYPE
	SYNTAX  INTEGER(0..128)
	MAX-ACCESS  read-only
	STATUS current
	DESCRIPTION
        "
        Index definition for the pmo10010MesrclientNetTxPwr 
        table
        "
	::= { pmo10010MesrclientNetTxPwrEntry 1 }


pmo10010MesrclientNetTxPwrPortn OBJECT-TYPE
	SYNTAX  INTEGER (0..65535)
	MAX-ACCESS read-only
	STATUS current
	DESCRIPTION
        "
        Client Trscv Tx Power :This OID 
        gives the transmit power value
         of the Client Transceiver, read 
        from the DDM (Digital Diagnostic 
        Monitoring) (Power = 10*log(AV)-40) 
        (Unit = dBm) <Help> This Measure 
        gives the transmit power value
         of the Client Transceiver
        "
	::= { pmo10010MesrclientNetTxPwrEntry 2 }


--- *********************************************************
---     TABLE for the pmo10010MesrclientNetRxPwr articles
--- *********************************************************

pmo10010MesrclientNetRxPwrTable OBJECT-TYPE
	SYNTAX  SEQUENCE OF Pmo10010MesrclientNetRxPwrEntry
	MAX-ACCESS not-accessible
	STATUS current
	DESCRIPTION
        "
        List of pmo10010MesrclientNetRxPwr 
        Article
        "
	::= { pmo10010MesrClient 64 }


pmo10010MesrclientNetRxPwrEntry OBJECT-TYPE
	SYNTAX Pmo10010MesrclientNetRxPwrEntry
	MAX-ACCESS not-accessible
	STATUS current
	DESCRIPTION
        "
        Row definition for the pmo10010MesrclientNetRxPwr 
        table
        "
	INDEX   { pmo10010MesrclientNetRxPwrIndex }
	::= { pmo10010MesrclientNetRxPwrTable 1 }


Pmo10010MesrclientNetRxPwrEntry ::=
	SEQUENCE {
	pmo10010MesrclientNetRxPwrIndex
		INTEGER,
	pmo10010MesrclientNetRxPwrPortn
		INTEGER 
	}


pmo10010MesrclientNetRxPwrIndex OBJECT-TYPE
	SYNTAX  INTEGER(0..128)
	MAX-ACCESS  read-only
	STATUS current
	DESCRIPTION
        "
        Index definition for the pmo10010MesrclientNetRxPwr 
        table
        "
	::= { pmo10010MesrclientNetRxPwrEntry 1 }


pmo10010MesrclientNetRxPwrPortn OBJECT-TYPE
	SYNTAX  INTEGER (0..65535)
	MAX-ACCESS read-only
	STATUS current
	DESCRIPTION
        "
        Client Trscv Rx Power :This OID 
        gives the receive power value of 
        the Client Transceiver, read in 
        the DDM (Digital Diagnostic Monitoring) 
        (Power = 10*log(AV)-40) (Unit = 
        dBm) <Help> This Measure gives
         the receive power value of the 
        Client Transceiver
        "
	::= { pmo10010MesrclientNetRxPwrEntry 2 }


--- *********************************************************
---     TABLE for the pmo10010MesrlineNetTxLaserOutputPwr articles
--- *********************************************************

pmo10010MesrlineNetTxLaserOutputPwrTable OBJECT-TYPE
	SYNTAX  SEQUENCE OF Pmo10010MesrlineNetTxLaserOutputPwrEntry
	MAX-ACCESS not-accessible
	STATUS current
	DESCRIPTION
        "
        List of pmo10010MesrlineNetTxLaserOutputPwr 
        Article
        "
	::= { pmo10010MesrLine 80 }


pmo10010MesrlineNetTxLaserOutputPwrEntry OBJECT-TYPE
	SYNTAX Pmo10010MesrlineNetTxLaserOutputPwrEntry
	MAX-ACCESS not-accessible
	STATUS current
	DESCRIPTION
        "
        Row definition for the pmo10010MesrlineNetTxLaserOutputPwr 
        table
        "
	INDEX   { pmo10010MesrlineNetTxLaserOutputPwrIndex }
	::= { pmo10010MesrlineNetTxLaserOutputPwrTable 1 }


Pmo10010MesrlineNetTxLaserOutputPwrEntry ::=
	SEQUENCE {
	pmo10010MesrlineNetTxLaserOutputPwrIndex
		INTEGER,
	pmo10010MesrlineNetTxLaserOutputPwrPortn
		INTEGER 
	}


pmo10010MesrlineNetTxLaserOutputPwrIndex OBJECT-TYPE
	SYNTAX  INTEGER(0..128)
	MAX-ACCESS  read-only
	STATUS current
	DESCRIPTION
        "
        Index definition for the pmo10010MesrlineNetTxLaserOutputPwr 
        table
        "
	::= { pmo10010MesrlineNetTxLaserOutputPwrEntry 1 }


pmo10010MesrlineNetTxLaserOutputPwrPortn OBJECT-TYPE
	SYNTAX  INTEGER (0..65535)
	MAX-ACCESS read-only
	STATUS current
	DESCRIPTION
        "
        Current Line Trscv Tx Power :This 
        OID gives the Tx Laser transmit 
        power value of the Line Transceiver, 
        read in the DDM (Digital Diagnostic 
        Monitoring) (Power = AV/100) (Unit 
        = dBm) <Help> This Measure gives 
        the Tx Laser transmit power value 
        of the Line Transceiver
        "
	::= { pmo10010MesrlineNetTxLaserOutputPwrEntry 2 }


--- *********************************************************
---     TABLE for the pmo10010MesrlineNetTxLaserTemp articles
--- *********************************************************

pmo10010MesrlineNetTxLaserTempTable OBJECT-TYPE
	SYNTAX  SEQUENCE OF Pmo10010MesrlineNetTxLaserTempEntry
	MAX-ACCESS not-accessible
	STATUS current
	DESCRIPTION
        "
        List of pmo10010MesrlineNetTxLaserTemp 
        Article
        "
	::= { pmo10010MesrLine 96 }


pmo10010MesrlineNetTxLaserTempEntry OBJECT-TYPE
	SYNTAX Pmo10010MesrlineNetTxLaserTempEntry
	MAX-ACCESS not-accessible
	STATUS current
	DESCRIPTION
        "
        Row definition for the pmo10010MesrlineNetTxLaserTemp 
        table
        "
	INDEX   { pmo10010MesrlineNetTxLaserTempIndex }
	::= { pmo10010MesrlineNetTxLaserTempTable 1 }


Pmo10010MesrlineNetTxLaserTempEntry ::=
	SEQUENCE {
	pmo10010MesrlineNetTxLaserTempIndex
		INTEGER,
	pmo10010MesrlineNetTxLaserTempPortn
		INTEGER 
	}


pmo10010MesrlineNetTxLaserTempIndex OBJECT-TYPE
	SYNTAX  INTEGER(0..128)
	MAX-ACCESS  read-only
	STATUS current
	DESCRIPTION
        "
        Index definition for the pmo10010MesrlineNetTxLaserTemp 
        table
        "
	::= { pmo10010MesrlineNetTxLaserTempEntry 1 }


pmo10010MesrlineNetTxLaserTempPortn OBJECT-TYPE
	SYNTAX  INTEGER (0..65535)
	MAX-ACCESS read-only
	STATUS current
	DESCRIPTION
        "
        Current Line Trscv Tx Laser Temperature 
        :This OID gives the Tx Laser Temperature 
        value of the Line Transceiver,
         read from the DDM (Digital Diagnostic 
        Monitoring) (Temperature = AV/256) 
        (Unit = C) <Help> This Measure
         gives the Tx Laser Temperature 
        value of the Line Transceiver
        "
	::= { pmo10010MesrlineNetTxLaserTempEntry 2 }


--- *********************************************************
---     TABLE for the pmo10010MesrlineNetTxBiasCurrent articles
--- *********************************************************

pmo10010MesrlineNetTxBiasCurrentTable OBJECT-TYPE
	SYNTAX  SEQUENCE OF Pmo10010MesrlineNetTxBiasCurrentEntry
	MAX-ACCESS not-accessible
	STATUS current
	DESCRIPTION
        "
        List of pmo10010MesrlineNetTxBiasCurrent 
        Article
        "
	::= { pmo10010MesrLine 112 }


pmo10010MesrlineNetTxBiasCurrentEntry OBJECT-TYPE
	SYNTAX Pmo10010MesrlineNetTxBiasCurrentEntry
	MAX-ACCESS not-accessible
	STATUS current
	DESCRIPTION
        "
        Row definition for the pmo10010MesrlineNetTxBiasCurrent 
        table
        "
	INDEX   { pmo10010MesrlineNetTxBiasCurrentIndex }
	::= { pmo10010MesrlineNetTxBiasCurrentTable 1 }


Pmo10010MesrlineNetTxBiasCurrentEntry ::=
	SEQUENCE {
	pmo10010MesrlineNetTxBiasCurrentIndex
		INTEGER,
	pmo10010MesrlineNetTxBiasCurrentPortn
		INTEGER 
	}


pmo10010MesrlineNetTxBiasCurrentIndex OBJECT-TYPE
	SYNTAX  INTEGER(0..128)
	MAX-ACCESS  read-only
	STATUS current
	DESCRIPTION
        "
        Index definition for the pmo10010MesrlineNetTxBiasCurrent 
        table
        "
	::= { pmo10010MesrlineNetTxBiasCurrentEntry 1 }


pmo10010MesrlineNetTxBiasCurrentPortn OBJECT-TYPE
	SYNTAX  INTEGER (0..65535)
	MAX-ACCESS read-only
	STATUS current
	DESCRIPTION
        "
        Current Line Trscv Tx Laser Bias 
        :This OID gives the Tx Laser Bias 
        value of the Line Transceiver,
         read from the DDM (Digital Diagnostic 
        Monitoring) (Bias = AV/10) (Unit 
        = mA) <Help> This Measure gives 
        the Tx Laser Bias value of the
         Line Transceiver
        "
	::= { pmo10010MesrlineNetTxBiasCurrentEntry 2 }


--- *********************************************************
---     TABLE for the pmo10010MesrlineNetRxInputPwr articles
--- *********************************************************

pmo10010MesrlineNetRxInputPwrTable OBJECT-TYPE
	SYNTAX  SEQUENCE OF Pmo10010MesrlineNetRxInputPwrEntry
	MAX-ACCESS not-accessible
	STATUS current
	DESCRIPTION
        "
        List of pmo10010MesrlineNetRxInputPwr 
        Article
        "
	::= { pmo10010MesrLine 128 }


pmo10010MesrlineNetRxInputPwrEntry OBJECT-TYPE
	SYNTAX Pmo10010MesrlineNetRxInputPwrEntry
	MAX-ACCESS not-accessible
	STATUS current
	DESCRIPTION
        "
        Row definition for the pmo10010MesrlineNetRxInputPwr 
        table
        "
	INDEX   { pmo10010MesrlineNetRxInputPwrIndex }
	::= { pmo10010MesrlineNetRxInputPwrTable 1 }


Pmo10010MesrlineNetRxInputPwrEntry ::=
	SEQUENCE {
	pmo10010MesrlineNetRxInputPwrIndex
		INTEGER,
	pmo10010MesrlineNetRxInputPwrPortn
		INTEGER 
	}


pmo10010MesrlineNetRxInputPwrIndex OBJECT-TYPE
	SYNTAX  INTEGER(0..128)
	MAX-ACCESS  read-only
	STATUS current
	DESCRIPTION
        "
        Index definition for the pmo10010MesrlineNetRxInputPwr 
        table
        "
	::= { pmo10010MesrlineNetRxInputPwrEntry 1 }


pmo10010MesrlineNetRxInputPwrPortn OBJECT-TYPE
	SYNTAX  INTEGER (0..65535)
	MAX-ACCESS read-only
	STATUS current
	DESCRIPTION
        "
        Current Line Trscv Rx Power :This 
        OID gives the Receive power value 
        of the Line Transceiver, read in 
        the DDM (Digital Diagnostic Monitoring) 
        (Power = AV/100) (Unit = dBm) <Help> 
        This Measure gives the Receive
         power value of the Line Transceiver
        "
	::= { pmo10010MesrlineNetRxInputPwrEntry 2 }


--- *********************************************************
---     TABLE for the pmo10010MesrlineResidualChromaticDisp articles
--- *********************************************************

pmo10010MesrlineResidualChromaticDispTable OBJECT-TYPE
	SYNTAX  SEQUENCE OF Pmo10010MesrlineResidualChromaticDispEntry
	MAX-ACCESS not-accessible
	STATUS current
	DESCRIPTION
        "
        List of pmo10010MesrlineResidualChromaticDisp 
        Article
        "
	::= { pmo10010MesrLine 144 }


pmo10010MesrlineResidualChromaticDispEntry OBJECT-TYPE
	SYNTAX Pmo10010MesrlineResidualChromaticDispEntry
	MAX-ACCESS not-accessible
	STATUS current
	DESCRIPTION
        "
        Row definition for the pmo10010MesrlineResidualChromaticDisp 
        table
        "
	INDEX   { pmo10010MesrlineResidualChromaticDispIndex }
	::= { pmo10010MesrlineResidualChromaticDispTable 1 }


Pmo10010MesrlineResidualChromaticDispEntry ::=
	SEQUENCE {
	pmo10010MesrlineResidualChromaticDispIndex
		INTEGER,
	pmo10010MesrlineResidualChromaticDispPortn
		INTEGER 
	}


pmo10010MesrlineResidualChromaticDispIndex OBJECT-TYPE
	SYNTAX  INTEGER(0..128)
	MAX-ACCESS  read-only
	STATUS current
	DESCRIPTION
        "
        Index definition for the pmo10010MesrlineResidualChromaticDisp 
        table
        "
	::= { pmo10010MesrlineResidualChromaticDispEntry 1 }


pmo10010MesrlineResidualChromaticDispPortn OBJECT-TYPE
	SYNTAX  INTEGER (0..65535)
	MAX-ACCESS read-only
	STATUS current
	DESCRIPTION
        "
        Current Residual Chromatic Dispersion 
        :This OID gives the current Residual 
        Chromatic Dispersion on the Line 
        interface  (Unit = ps/nm)<Help> 
        This measure gives the current
         Residual Chromatic Dispersion
         on the Line interface.
        "
	::= { pmo10010MesrlineResidualChromaticDispEntry 2 }


--- *********************************************************
---     TABLE for the pmo10010MesrlineDiffGroupDelay articles
--- *********************************************************

pmo10010MesrlineDiffGroupDelayTable OBJECT-TYPE
	SYNTAX  SEQUENCE OF Pmo10010MesrlineDiffGroupDelayEntry
	MAX-ACCESS not-accessible
	STATUS current
	DESCRIPTION
        "
        List of pmo10010MesrlineDiffGroupDelay 
        Article
        "
	::= { pmo10010MesrLine 148 }


pmo10010MesrlineDiffGroupDelayEntry OBJECT-TYPE
	SYNTAX Pmo10010MesrlineDiffGroupDelayEntry
	MAX-ACCESS not-accessible
	STATUS current
	DESCRIPTION
        "
        Row definition for the pmo10010MesrlineDiffGroupDelay 
        table
        "
	INDEX   { pmo10010MesrlineDiffGroupDelayIndex }
	::= { pmo10010MesrlineDiffGroupDelayTable 1 }


Pmo10010MesrlineDiffGroupDelayEntry ::=
	SEQUENCE {
	pmo10010MesrlineDiffGroupDelayIndex
		INTEGER,
	pmo10010MesrlineDiffGroupDelayPortn
		INTEGER 
	}


pmo10010MesrlineDiffGroupDelayIndex OBJECT-TYPE
	SYNTAX  INTEGER(0..128)
	MAX-ACCESS  read-only
	STATUS current
	DESCRIPTION
        "
        Index definition for the pmo10010MesrlineDiffGroupDelay 
        table
        "
	::= { pmo10010MesrlineDiffGroupDelayEntry 1 }


pmo10010MesrlineDiffGroupDelayPortn OBJECT-TYPE
	SYNTAX  INTEGER (0..65535)
	MAX-ACCESS read-only
	STATUS current
	DESCRIPTION
        "
        Current Differential Group Delay 
        :This OID gives the current Differential 
        Group Delay on the Line interface 
          (Unit = ps)<Help> This measure 
        gives the current Differential
         Group Delay on the Line interface.
        "
	::= { pmo10010MesrlineDiffGroupDelayEntry 2 }


--- *********************************************************
---     TABLE for the pmo10010MesrlineQFactor articles
--- *********************************************************

pmo10010MesrlineQFactorTable OBJECT-TYPE
	SYNTAX  SEQUENCE OF Pmo10010MesrlineQFactorEntry
	MAX-ACCESS not-accessible
	STATUS current
	DESCRIPTION
        "
        List of pmo10010MesrlineQFactor 
        Article
        "
	::= { pmo10010MesrLine 152 }


pmo10010MesrlineQFactorEntry OBJECT-TYPE
	SYNTAX Pmo10010MesrlineQFactorEntry
	MAX-ACCESS not-accessible
	STATUS current
	DESCRIPTION
        "
        Row definition for the pmo10010MesrlineQFactor 
        table
        "
	INDEX   { pmo10010MesrlineQFactorIndex }
	::= { pmo10010MesrlineQFactorTable 1 }


Pmo10010MesrlineQFactorEntry ::=
	SEQUENCE {
	pmo10010MesrlineQFactorIndex
		INTEGER,
	pmo10010MesrlineQFactorPortn
		INTEGER 
	}


pmo10010MesrlineQFactorIndex OBJECT-TYPE
	SYNTAX  INTEGER(0..128)
	MAX-ACCESS  read-only
	STATUS current
	DESCRIPTION
        "
        Index definition for the pmo10010MesrlineQFactor 
        table
        "
	::= { pmo10010MesrlineQFactorEntry 1 }


pmo10010MesrlineQFactorPortn OBJECT-TYPE
	SYNTAX  INTEGER (0..65535)
	MAX-ACCESS read-only
	STATUS current
	DESCRIPTION
        "
        Current Q Factor :This OID gives 
        the current Q Factor on the Line 
        interface   (Unit = dB) <Help>
         This measure gives the current 
        Q Factor on the Line interface.
        "
	::= { pmo10010MesrlineQFactorEntry 2 }


--- *********************************************************
---     TABLE for the pmo10010MesrlineCarrierFreqOffset articles
--- *********************************************************

pmo10010MesrlineCarrierFreqOffsetTable OBJECT-TYPE
	SYNTAX  SEQUENCE OF Pmo10010MesrlineCarrierFreqOffsetEntry
	MAX-ACCESS not-accessible
	STATUS current
	DESCRIPTION
        "
        List of pmo10010MesrlineCarrierFreqOffset 
        Article
        "
	::= { pmo10010MesrLine 156 }


pmo10010MesrlineCarrierFreqOffsetEntry OBJECT-TYPE
	SYNTAX Pmo10010MesrlineCarrierFreqOffsetEntry
	MAX-ACCESS not-accessible
	STATUS current
	DESCRIPTION
        "
        Row definition for the pmo10010MesrlineCarrierFreqOffset 
        table
        "
	INDEX   { pmo10010MesrlineCarrierFreqOffsetIndex }
	::= { pmo10010MesrlineCarrierFreqOffsetTable 1 }


Pmo10010MesrlineCarrierFreqOffsetEntry ::=
	SEQUENCE {
	pmo10010MesrlineCarrierFreqOffsetIndex
		INTEGER,
	pmo10010MesrlineCarrierFreqOffsetPortn
		INTEGER 
	}


pmo10010MesrlineCarrierFreqOffsetIndex OBJECT-TYPE
	SYNTAX  INTEGER(0..128)
	MAX-ACCESS  read-only
	STATUS current
	DESCRIPTION
        "
        Index definition for the pmo10010MesrlineCarrierFreqOffset 
        table
        "
	::= { pmo10010MesrlineCarrierFreqOffsetEntry 1 }


pmo10010MesrlineCarrierFreqOffsetPortn OBJECT-TYPE
	SYNTAX  INTEGER (0..65535)
	MAX-ACCESS read-only
	STATUS current
	DESCRIPTION
        "
        Current Carrier Frequency Offset 
        :This OID gives the current Carrier 
        Frequency Offset on the Line interface 
          (Unit = Mhz)<Help> This measure 
        gives the current Carrier Frequency 
        Offset on the Line interface.
        "
	::= { pmo10010MesrlineCarrierFreqOffsetEntry 2 }


--- *********************************************************
---     TABLE for the pmo10010MesrlineOsnr articles
--- *********************************************************

pmo10010MesrlineOsnrTable OBJECT-TYPE
	SYNTAX  SEQUENCE OF Pmo10010MesrlineOsnrEntry
	MAX-ACCESS not-accessible
	STATUS current
	DESCRIPTION
        "
        List of pmo10010MesrlineOsnr Article
        "
	::= { pmo10010MesrLine 160 }


pmo10010MesrlineOsnrEntry OBJECT-TYPE
	SYNTAX Pmo10010MesrlineOsnrEntry
	MAX-ACCESS not-accessible
	STATUS current
	DESCRIPTION
        "
        Row definition for the pmo10010MesrlineOsnr 
        table
        "
	INDEX   { pmo10010MesrlineOsnrIndex }
	::= { pmo10010MesrlineOsnrTable 1 }


Pmo10010MesrlineOsnrEntry ::=
	SEQUENCE {
	pmo10010MesrlineOsnrIndex
		INTEGER,
	pmo10010MesrlineOsnrPortn
		INTEGER 
	}


pmo10010MesrlineOsnrIndex OBJECT-TYPE
	SYNTAX  INTEGER(0..128)
	MAX-ACCESS  read-only
	STATUS current
	DESCRIPTION
        "
        Index definition for the pmo10010MesrlineOsnr 
        table
        "
	::= { pmo10010MesrlineOsnrEntry 1 }


pmo10010MesrlineOsnrPortn OBJECT-TYPE
	SYNTAX  INTEGER (0..65535)
	MAX-ACCESS read-only
	STATUS current
	DESCRIPTION
        "
        Current OSNR :This OID gives the 
        current OSNR on the Line interface 
          (OSNR = AV/10) (Unit = dB)<Help> 
        This measure gives the current
         OSNR on the Line interface.
        "
	::= { pmo10010MesrlineOsnrEntry 2 }


--- *****************************************************
---     LEAF for the lineNetTxLaserOutputPwrAverage article
--- *****************************************************

pmo10010MesrlineNetTxLaserOutputPwrAverage OBJECT-TYPE
	  SYNTAX Unsigned32 (0..65535)
	  MAX-ACCESS read-only
	  STATUS current
	  DESCRIPTION
        "
        Average Line Trscv Tx Power :This 
        OID gives the average Tx Laser
         transmit power value among the 
        network lanes of the Line Transceiver, 
        read in the DDM (Digital Diagnostic 
        Monitoring)  (Power = AV/100) (Unit 
        = dBm) (Unit = dBm) <Help> This 
        Measure gives the average Tx Laser 
        transmit power value among the
         network lanes of the Line Transceiver
        "
	  ::= { pmo10010MesrOther 180 }



--- *****************************************************
---     LEAF for the lineNetTxLaserTempAverage article
--- *****************************************************

pmo10010MesrlineNetTxLaserTempAverage OBJECT-TYPE
	  SYNTAX Unsigned32 (0..65535)
	  MAX-ACCESS read-only
	  STATUS current
	  DESCRIPTION
        "
        Average Line Trscv Tx Laser Temperature 
        :This OID gives the average Tx
         Laser Temperature value among
         the network lanes of the Line
         Transceiver, read from the DDM 
        (Digital Diagnostic Monitoring) 
        (Temperature = AV/256) (Unit =
         C) <Help> This Measure gives the 
        average Tx Laser Temperature value 
        among the network lanes of the
         Line Transceiver
        "
	  ::= { pmo10010MesrOther 181 }



--- *****************************************************
---     LEAF for the lineNetTxBiasCurrentAverage article
--- *****************************************************

pmo10010MesrlineNetTxBiasCurrentAverage OBJECT-TYPE
	  SYNTAX Unsigned32 (0..65535)
	  MAX-ACCESS read-only
	  STATUS current
	  DESCRIPTION
        "
        Average Line Trscv Tx Laser Bias 
        :This OID gives the average Tx
         Laser Bias value among the network 
        lanes of the Line Transceiver,
         read from the DDM (Digital Diagnostic 
        Monitoring) (Bias = AV/10) (Unit 
        = mA) <Help> This Measure gives 
        the average Tx Laser Bias value 
        among the network lanes of the
         Line Transceiver
        "
	  ::= { pmo10010MesrOther 182 }



--- *****************************************************
---     LEAF for the lineNetRxInputPwrAverage article
--- *****************************************************

pmo10010MesrlineNetRxInputPwrAverage OBJECT-TYPE
	  SYNTAX Unsigned32 (0..65535)
	  MAX-ACCESS read-only
	  STATUS current
	  DESCRIPTION
        "
        Average Line Trscv Rx Power :This 
        OID gives the average Receive power 
        value among the network lanes of 
        the Line Transceiver, read in the 
        DDM (Digital Diagnostic Monitoring) 
        (Power = AV/100) (Unit = dBm) <Help> 
        This Measure gives the average
         Receive power value among the
         network lanes of the Line Transceiver
        "
	  ::= { pmo10010MesrOther 183 }



--- *****************************************************
---     LEAF for the lineResidualChromaticDispAverage article
--- *****************************************************

pmo10010MesrlineResidualChromaticDispAverage OBJECT-TYPE
	  SYNTAX Unsigned32 (0..65535)
	  MAX-ACCESS read-only
	  STATUS current
	  DESCRIPTION
        "
        Average Residual Chromatic Dispersion 
        :This OID gives the average Residual 
        Chromatic Dispersion on the Line 
        interface since the last measure 
        reset <Help> This measure gives 
        the average Residual Chromatic
         Dispersion on the Line interface 
        since the last measure reset.
        "
	  ::= { pmo10010MesrOther 184 }



--- *****************************************************
---     LEAF for the lineDiffGroupDelayAverage article
--- *****************************************************

pmo10010MesrlineDiffGroupDelayAverage OBJECT-TYPE
	  SYNTAX Unsigned32 (0..65535)
	  MAX-ACCESS read-only
	  STATUS current
	  DESCRIPTION
        "
        Average Differential Group Delay 
        :This OID gives the average Group 
        Delay on the Line interface since 
        the last measure reset <Help> This 
        measure gives the average Differential 
        Group Delay on the Line interface 
        since the last measure reset.
        "
	  ::= { pmo10010MesrOther 185 }



--- *****************************************************
---     LEAF for the lineQFactorAverage article
--- *****************************************************

pmo10010MesrlineQFactorAverage OBJECT-TYPE
	  SYNTAX Unsigned32 (0..65535)
	  MAX-ACCESS read-only
	  STATUS current
	  DESCRIPTION
        "
        Average Q Factor :This OID gives 
        the average Q Factor on the Line 
        interface since the last measure 
        reset <Help> This measure gives 
        the average Q Factor on the Line 
        interface since the last measure 
        reset.
        "
	  ::= { pmo10010MesrOther 186 }



--- *****************************************************
---     LEAF for the lineCarrierFreqOffsetAverage article
--- *****************************************************

pmo10010MesrlineCarrierFreqOffsetAverage OBJECT-TYPE
	  SYNTAX Unsigned32 (0..65535)
	  MAX-ACCESS read-only
	  STATUS current
	  DESCRIPTION
        "
        Average Carrier Frequency Offset 
        :This OID gives the average Carrier 
        Frequency Offset on the Line interface 
        since the last measure reset <Help> 
        This measure gives the average
         Carrier Frequency Offset on the 
        Line interface since the last measure 
        reset
        "
	  ::= { pmo10010MesrOther 187 }



--- *****************************************************
---     LEAF for the lineOsnrAverage article
--- *****************************************************

pmo10010MesrlineOsnrAverage OBJECT-TYPE
	  SYNTAX Unsigned32 (0..65535)
	  MAX-ACCESS read-only
	  STATUS current
	  DESCRIPTION
        "
        Average OSNR :This OID gives the 
        average OSNR on the Line interface 
        since the last measure reset <Help> 
        This measure gives the average
         OSNR on the Line interface since 
        the last measure reset.
        "
	  ::= { pmo10010MesrOther 188 }



--- *****************************************************
---     LEAF for the clientNetTxTempMin article
--- *****************************************************

pmo10010MesrclientNetTxTempMin OBJECT-TYPE
	  SYNTAX Unsigned32 (0..65535)
	  MAX-ACCESS read-only
	  STATUS current
	  DESCRIPTION
        "
        Min Client Trscv Laser Temperature 
        :This OID gives the minimum Laser 
        temperature value among the network 
        lanes of the Client Transceiver, 
        read from the DDM (Digital Diagnostic 
        Monitoring) (Temperature = AV/256) 
        (Unit = C) <Help> This Measure
         gives the minimum Laser temperature 
        value among the network lanes of 
        the Client Transceiver
        "
	  ::= { pmo10010MesrOther 192 }



--- *****************************************************
---     LEAF for the clientNetTxBiasMin article
--- *****************************************************

pmo10010MesrclientNetTxBiasMin OBJECT-TYPE
	  SYNTAX Unsigned32 (0..65535)
	  MAX-ACCESS read-only
	  STATUS current
	  DESCRIPTION
        "
        Min Client Trscv Laser Bias :This 
        OID gives the minimum Laser bias 
        value among the network lanes of 
        the Client Transceiver, read from 
        the DDM (Digital Diagnostic Monitoring) 
        (Bias = AV/500) (Unit = mA) <Help> 
        This Measure gives the minimum
         Laser bias value among the network 
        lanes of the Client Transceiver
        "
	  ::= { pmo10010MesrOther 193 }



--- *****************************************************
---     LEAF for the clientNetTxPwrMin article
--- *****************************************************

pmo10010MesrclientNetTxPwrMin OBJECT-TYPE
	  SYNTAX Unsigned32 (0..65535)
	  MAX-ACCESS read-only
	  STATUS current
	  DESCRIPTION
        "
        Min Client Trscv Tx Power :This 
        OID gives the minimum transmit
         power value among the network
         lanes of the Client Transceiver, 
        read from the DDM (Digital Diagnostic 
        Monitoring) (Power = 10*log(AV)-40) 
        (Unit = dBm) <Help> This Measure 
        gives the minimum transmit power 
        value among the network lanes of 
        the Client Transceiver
        "
	  ::= { pmo10010MesrOther 194 }



--- *****************************************************
---     LEAF for the clientNetRxPwrMin article
--- *****************************************************

pmo10010MesrclientNetRxPwrMin OBJECT-TYPE
	  SYNTAX Unsigned32 (0..65535)
	  MAX-ACCESS read-only
	  STATUS current
	  DESCRIPTION
        "
        Min Client Trscv Rx Power :This 
        OID gives the minimum receive power 
        value among the network lanes of 
        the Client Transceiver, read in 
        the DDM (Digital Diagnostic Monitoring) 
        (Power = 10*log(AV)-40) (Unit = 
        dBm) <Help> This Measure gives
         the minimum receive power value 
        among the network lanes of the
         Client Transceiver
        "
	  ::= { pmo10010MesrOther 195 }



--- *****************************************************
---     LEAF for the lineNetTxLaserOutputPwrMin article
--- *****************************************************

pmo10010MesrlineNetTxLaserOutputPwrMin OBJECT-TYPE
	  SYNTAX Unsigned32 (0..65535)
	  MAX-ACCESS read-only
	  STATUS current
	  DESCRIPTION
        "
        Min Line Trscv Tx Power :This
         OID gives the minimum Tx Laser 
        transmit power value among the
         network lanes of the Line Transceiver, 
        read in the DDM (Digital Diagnostic 
        Monitoring)  (Power = AV/100) (Unit 
        = dBm) (Unit = dBm) <Help> This 
        Measure gives the minimum Tx Laser 
        transmit power value among the
         network lanes of the Line Transceiver
        "
	  ::= { pmo10010MesrOther 196 }



--- *****************************************************
---     LEAF for the lineNetTxLaserTempMin article
--- *****************************************************

pmo10010MesrlineNetTxLaserTempMin OBJECT-TYPE
	  SYNTAX Unsigned32 (0..65535)
	  MAX-ACCESS read-only
	  STATUS current
	  DESCRIPTION
        "
        Min Line Trscv Tx Laser Temperature 
        :This OID gives the minimum Tx
         Laser Temperature value among
         the network lanes of the Line
         Transceiver, read from the DDM 
        (Digital Diagnostic Monitoring) 
        (Temperature = AV/256) (Unit =
         C) <Help> This Measure gives the 
        minimum Tx Laser Temperature value 
        among the network lanes of the
         Line Transceiver
        "
	  ::= { pmo10010MesrOther 197 }



--- *****************************************************
---     LEAF for the lineNetTxBiasCurrentMin article
--- *****************************************************

pmo10010MesrlineNetTxBiasCurrentMin OBJECT-TYPE
	  SYNTAX Unsigned32 (0..65535)
	  MAX-ACCESS read-only
	  STATUS current
	  DESCRIPTION
        "
        Min Line Trscv Tx Laser Bias :This 
        OID gives the minimum Tx Laser
         Bias value among the network lanes 
        of the Line Transceiver, read from 
        the DDM (Digital Diagnostic Monitoring) 
        (Bias = AV/10) (Unit = mA) <Help> 
        This Measure gives the minimum
         Tx Laser Bias value among the
         network lanes of the Line Transceiver
        "
	  ::= { pmo10010MesrOther 198 }



--- *****************************************************
---     LEAF for the lineNetRxInputPwrMin article
--- *****************************************************

pmo10010MesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver, 
        read in the DDM (Digital Diagnostic 
        Monitoring) (Power = AV/100) (Unit 
        = dBm) <Help> This Measure gives 
        the minimum Receive power value 
        among the network lanes of the
         Line Transceiver
        "
	  ::= { pmo10010MesrOther 199 }



--- *****************************************************
---     LEAF for the lineResidualChromaticDispMin article
--- *****************************************************

pmo10010MesrlineResidualChromaticDispMin OBJECT-TYPE
	  SYNTAX Unsigned32 (0..65535)
	  MAX-ACCESS read-only
	  STATUS current
	  DESCRIPTION
        "
        Min Residual Chromatic Dispersion 
        :This OID gives the minimum Residual 
        Chromatic Dispersion on the Line 
        interface since the last measure 
        reset  (Unit = ps/nm)<Help> This 
        measure gives the minimum Residual 
        Chromatic Dispersion on the Line 
        interface since the last measure 
        reset.
        "
	  ::= { pmo10010MesrOther 200 }



--- *****************************************************
---     LEAF for the lineDiffGroupDelayMin article
--- *****************************************************

pmo10010MesrlineDiffGroupDelayMin OBJECT-TYPE
	  SYNTAX Unsigned32 (0..65535)
	  MAX-ACCESS read-only
	  STATUS current
	  DESCRIPTION
        "
        Min Differential Group Delay :This 
        OID gives the minimum Differential 
        Group Delay  on the Line interface 
        since the last measure reset  (Unit 
        = ps)<Help> This measure gives
         the minimum Differential Group 
        Delay on the Line interface since 
        the last measure reset.
        "
	  ::= { pmo10010MesrOther 201 }



--- *****************************************************
---     LEAF for the lineQFactorMin article
--- *****************************************************

pmo10010MesrlineQFactorMin OBJECT-TYPE
	  SYNTAX Unsigned32 (0..65535)
	  MAX-ACCESS read-only
	  STATUS current
	  DESCRIPTION
        "
        Min Q Factor :This OID gives the 
        minimum Q Factor on the Line interface 
        since the last measure reset  (Unit 
        = dB)<Help> This measure gives
         the minimum Q Factor on the Line 
        interface since the last measure 
        reset.
        "
	  ::= { pmo10010MesrOther 202 }



--- *****************************************************
---     LEAF for the lineCarrierFreqOffsetMin article
--- *****************************************************

pmo10010MesrlineCarrierFreqOffsetMin OBJECT-TYPE
	  SYNTAX Unsigned32 (0..65535)
	  MAX-ACCESS read-only
	  STATUS current
	  DESCRIPTION
        "
        Min Carrier Frequency Offset :This 
        OID gives the minimum Carrier Frequency 
        Offset on the Line interface since 
        the last measure reset  (Unit = 
        Mhz)<Help> This measure gives the 
        minimum Carrier Frequency Offset 
        on the Line interface since the 
        last measure reset
        "
	  ::= { pmo10010MesrOther 203 }



--- *****************************************************
---     LEAF for the lineOsnrMin article
--- *****************************************************

pmo10010MesrlineOsnrMin OBJECT-TYPE
	  SYNTAX Unsigned32 (0..65535)
	  MAX-ACCESS read-only
	  STATUS current
	  DESCRIPTION
        "
        Min OSNR :This OID gives the minimum 
        OSNR on the Line interface since 
        the last measure reset  (OSNR = 
        AV/10) (Unit = dB)<Help> This measure 
        gives the minimum OSNR on the Line 
        interface since the last measure 
        reset.
        "
	  ::= { pmo10010MesrOther 204 }



--- *****************************************************
---     LEAF for the clientNetTxTempMax article
--- *****************************************************

pmo10010MesrclientNetTxTempMax OBJECT-TYPE
	  SYNTAX Unsigned32 (0..65535)
	  MAX-ACCESS read-only
	  STATUS current
	  DESCRIPTION
        "
        Max Client Trscv Laser Temperature 
        :This OID gives the maximum Laser 
        temperature value among the network 
        lanes of the Client Transceiver, 
        read from the DDM (Digital Diagnostic 
        Monitoring) (Temperature = AV/256) 
        (Unit = C) <Help> This Measure
         gives the maximum Laser temperature 
        value among the network lanes of 
        the Client Transceiver
        "
	  ::= { pmo10010MesrOther 208 }



--- *****************************************************
---     LEAF for the clientNetTxBiasMax article
--- *****************************************************

pmo10010MesrclientNetTxBiasMax OBJECT-TYPE
	  SYNTAX Unsigned32 (0..65535)
	  MAX-ACCESS read-only
	  STATUS current
	  DESCRIPTION
        "
        Max Client Trscv Laser Bias :This 
        OID gives the maximum Laser bias 
        value among the network lanes of 
        the Client Transceiver, read from 
        the DDM (Digital Diagnostic Monitoring) 
        (Bias = AV/500) (Unit = mA) <Help> 
        This Measure gives the maximum
         Laser bias value among the network 
        lanes of the Client Transceiver
        "
	  ::= { pmo10010MesrOther 209 }



--- *****************************************************
---     LEAF for the clientNetTxPwrMax article
--- *****************************************************

pmo10010MesrclientNetTxPwrMax OBJECT-TYPE
	  SYNTAX Unsigned32 (0..65535)
	  MAX-ACCESS read-only
	  STATUS current
	  DESCRIPTION
        "
        Max Client Trscv Tx Power :This 
        OID gives the maximum transmit
         power value among the network
         lanes of the Client Transceiver, 
        read from the DDM (Digital Diagnostic 
        Monitoring) (Power = 10*log(AV)-40) 
        (Unit = dBm) <Help> This Measure 
        gives the maximum transmit power 
        value among the network lanes of 
        the Client Transceiver
        "
	  ::= { pmo10010MesrOther 210 }



--- *****************************************************
---     LEAF for the clientNetRxPwrMax article
--- *****************************************************

pmo10010MesrclientNetRxPwrMax OBJECT-TYPE
	  SYNTAX Unsigned32 (0..65535)
	  MAX-ACCESS read-only
	  STATUS current
	  DESCRIPTION
        "
        Max Client Trscv Rx Power :This 
        OID gives the maximum receive power 
        value among the network lanes of 
        the Client Transceiver, read in 
        the DDM (Digital Diagnostic Monitoring) 
        (Power = 10*log(AV)-40) (Unit = 
        dBm) <Help> This Measure gives
         the maximum receive power value 
        among the network lanes of the
         Client Transceiver
        "
	  ::= { pmo10010MesrOther 211 }



--- *****************************************************
---     LEAF for the lineNetTxLaserOutputPwrMax article
--- *****************************************************

pmo10010MesrlineNetTxLaserOutputPwrMax OBJECT-TYPE
	  SYNTAX Unsigned32 (0..65535)
	  MAX-ACCESS read-only
	  STATUS current
	  DESCRIPTION
        "
        Max Line Trscv Tx Power :This
         OID gives the maximum Tx Laser 
        transmit power value among the
         network lanes of the Line Transceiver, 
        read in the DDM (Digital Diagnostic 
        Monitoring) (Power = 10*log(AV)-40) 
        (Unit = dBm) <Help> This Measure 
        gives the maximum Tx Laser transmit 
        power value among the network lanes 
        of the Line Transceiver
        "
	  ::= { pmo10010MesrOther 212 }



--- *****************************************************
---     LEAF for the lineNetTxLaserTempMax article
--- *****************************************************

pmo10010MesrlineNetTxLaserTempMax OBJECT-TYPE
	  SYNTAX Unsigned32 (0..65535)
	  MAX-ACCESS read-only
	  STATUS current
	  DESCRIPTION
        "
        Max Line Trscv Tx Laser Temperature 
        :This OID gives the maximum Tx
         Laser Temperature value among
         the network lanes of the Line
         Transceiver, read from the DDM 
        (Digital Diagnostic Monitoring) 
        (Temperature = AV/256) (Unit =
         C) <Help> This Measure gives the 
        maximum Tx Laser Temperature value 
        among the network lanes of the
         Line Transceiver
        "
	  ::= { pmo10010MesrOther 213 }



--- *****************************************************
---     LEAF for the lineNetTxBiasCurrentMax article
--- *****************************************************

pmo10010MesrlineNetTxBiasCurrentMax OBJECT-TYPE
	  SYNTAX Unsigned32 (0..65535)
	  MAX-ACCESS read-only
	  STATUS current
	  DESCRIPTION
        "
        Max Line Trscv Tx Laser Bias :This 
        OID gives the maximum Tx Laser
         Bias value among the network lanes 
        of the Line Transceiver, read from 
        the DDM (Digital Diagnostic Monitoring) 
        (Bias = AV/10) (Unit = mA) <Help> 
        This Measure gives the maximum
         Tx Laser Bias value among the
         network lanes of the Line Transceiver
        "
	  ::= { pmo10010MesrOther 214 }



--- *****************************************************
---     LEAF for the lineNetRxInputPwrMax article
--- *****************************************************

pmo10010MesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver, 
        read in the DDM (Digital Diagnostic 
        Monitoring) (Power = 10*log(AV)-40) 
        (Unit = dBm) <Help> This Measure 
        gives the maximum Receive power 
        value among the network lanes of 
        the Line Transceiver
        "
	  ::= { pmo10010MesrOther 215 }



--- *****************************************************
---     LEAF for the lineResidualChromaticDispMax article
--- *****************************************************

pmo10010MesrlineResidualChromaticDispMax OBJECT-TYPE
	  SYNTAX Unsigned32 (0..65535)
	  MAX-ACCESS read-only
	  STATUS current
	  DESCRIPTION
        "
        Max Residual Chromatic Dispersion 
        :This OID gives the maximum Residual 
        Chromatic Dispersion on the Line 
        interface since the last measure 
        reset  (Unit = ps/nm)<Help> This 
        measure gives the maximum Residual 
        Chromatic Dispersion on the Line 
        interface since the last measure 
        reset.
        "
	  ::= { pmo10010MesrOther 216 }



--- *****************************************************
---     LEAF for the lineDiffGroupDelayMax article
--- *****************************************************

pmo10010MesrlineDiffGroupDelayMax OBJECT-TYPE
	  SYNTAX Unsigned32 (0..65535)
	  MAX-ACCESS read-only
	  STATUS current
	  DESCRIPTION
        "
        Max Differential Group Delay :This 
        OID gives the maximum Differential 
        Group Delay  on the Line interface 
        since the last measure reset  
         (Unit = ps)<Help> This measure 
        gives the maximum Differential
         Group Delay on the Line interface 
        since the last measure reset.
        "
	  ::= { pmo10010MesrOther 217 }



--- *****************************************************
---     LEAF for the lineQFactorMax article
--- *****************************************************

pmo10010MesrlineQFactorMax OBJECT-TYPE
	  SYNTAX Unsigned32 (0..65535)
	  MAX-ACCESS read-only
	  STATUS current
	  DESCRIPTION
        "
        Max Q Factor :This OID gives the 
        maximum Q Factor on the Line interface 
        since the last measure reset  (Unit 
        = dB)<Help> This measure gives
         the maximum Q Factor on the Line 
        interface since the last measure 
        reset.
        "
	  ::= { pmo10010MesrOther 218 }



--- *****************************************************
---     LEAF for the lineCarrierFreqOffsetMax article
--- *****************************************************

pmo10010MesrlineCarrierFreqOffsetMax OBJECT-TYPE
	  SYNTAX Unsigned32 (0..65535)
	  MAX-ACCESS read-only
	  STATUS current
	  DESCRIPTION
        "
        Max Carrier Frequency Offset :This 
        OID gives the maximum Carrier Frequency 
        Offset on the Line interface since 
        the last measure reset   (Unit
         = Mhz)<Help> This measure gives 
        the maximum Carrier Frequency Offset 
        on the Line interface since the 
        last measure reset.
        "
	  ::= { pmo10010MesrOther 219 }



--- *****************************************************
---     LEAF for the lineOsnrMax article
--- *****************************************************

pmo10010MesrlineOsnrMax OBJECT-TYPE
	  SYNTAX Unsigned32 (0..65535)
	  MAX-ACCESS read-only
	  STATUS current
	  DESCRIPTION
        "
        Max OSNR :This OID gives the maximum 
        OSNR on the Line interface since 
        the last measure reset  (OSNR = 
        AV/10) (Unit = dB)<Help> This measure 
        gives the maximum OSNR on the Line 
        interface since the last measure 
        reset
        "
	  ::= { pmo10010MesrOther 220 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmo10010DwlrestartProcess OBJECT IDENTIFIER ::= { pmo10010DwlOther 0 }




pmo10010DwlColdRestartProcessed OBJECT-TYPE
	  SYNTAX EkiOnOff
	  MAX-ACCESS read-only
	  STATUS current
	  DESCRIPTION
        "
        Cold Restart :This OID indicates 
        that the module last restart was 
        a Cold RESTART
        "
	  ::= { pmo10010DwlrestartProcess 2 }



pmo10010DwlWarmRestartProcessed OBJECT-TYPE
	  SYNTAX EkiOnOff
	  MAX-ACCESS read-only
	  STATUS current
	  DESCRIPTION
        "
        Warm Restart :This OID indicates 
        that the module last restart was 
        a Warm RESTART
        "
	  ::= { pmo10010DwlrestartProcess 1 }



--- *****************************************************
---     LEAF for the swBanksUsed article
--- *****************************************************
pmo10010DwlswBanksUsed OBJECT IDENTIFIER ::= { pmo10010DwlOther 1 }




pmo10010DwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pmo10010DwlswBanksUsed 6 }



pmo10010DwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pmo10010DwlswBanksUsed 5 }



pmo10010DwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pmo10010DwlswBanksUsed 2 }



pmo10010DwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pmo10010DwlswBanksUsed 1 }



--- *****************************************************
---     LEAF for the gwBanksUsed article
--- *****************************************************
pmo10010DwlgwBanksUsed OBJECT IDENTIFIER ::= { pmo10010DwlOther 2 }




pmo10010DwlGwBank4Notempty OBJECT-TYPE
	  SYNTAX EkiOnOff
	  MAX-ACCESS read-only
	  STATUS current
	  DESCRIPTION
        "
        GW bank 4 loaded :This OID indicates 
        a gateware is loaded in GW bank 
        4
        "
	  ::= { pmo10010DwlgwBanksUsed 8 }



pmo10010DwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pmo10010DwlgwBanksUsed 7 }



pmo10010DwlGwBank2Notempty OBJECT-TYPE
	  SYNTAX EkiOnOff
	  MAX-ACCESS read-only
	  STATUS current
	  DESCRIPTION
        "
        GW bank 2 loaded :This OID indicates 
        a gateware is loaded in GW bank 
        2
        "
	  ::= { pmo10010DwlgwBanksUsed 6 }



pmo10010DwlGwBank1Notempty OBJECT-TYPE
	  SYNTAX EkiOnOff
	  MAX-ACCESS read-only
	  STATUS current
	  DESCRIPTION
        "
        GW bank 1 loaded :This OID indicates 
        a gateware is loaded in GW bank 
        1  <Help>  This status indicates 
        if the GW bank 1 contains GW package
        "
	  ::= { pmo10010DwlgwBanksUsed 5 }



pmo10010DwlGwBank4Used OBJECT-TYPE
	  SYNTAX EkiOnOff
	  MAX-ACCESS read-only
	  STATUS current
	  DESCRIPTION
        "
        GW bank 4 active :This OID indicates 
        the module is working on GW bank 
        4
        "
	  ::= { pmo10010DwlgwBanksUsed 4 }



pmo10010DwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pmo10010DwlgwBanksUsed 3 }



pmo10010DwlGwBank2Used OBJECT-TYPE
	  SYNTAX EkiOnOff
	  MAX-ACCESS read-only
	  STATUS current
	  DESCRIPTION
        "
        GW bank 2 active :This OID indicates 
        the module is working on GW bank 
        2
        "
	  ::= { pmo10010DwlgwBanksUsed 2 }



pmo10010DwlGwBank1Used OBJECT-TYPE
	  SYNTAX EkiOnOff
	  MAX-ACCESS read-only
	  STATUS current
	  DESCRIPTION
        "
        GW bank 1 active :This OID indicates 
        the module is working on GW bank 
        1  <Help>  This status indicates 
        if the GW bank 1 is active or standby
        "
	  ::= { pmo10010DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pmo10010CfgAccessCAisCsf OBJECT IDENTIFIER ::= { pmo10010Config 1 }



--- *****************************************************
---     LEAF for the table 0012
--- *****************************************************

pmo10010CfgClientcaiscsfTable OBJECT-TYPE
	SYNTAX  SEQUENCE OF Pmo10010CfgClientcaiscsfEntry
	MAX-ACCESS not-accessible
	STATUS current
	DESCRIPTION
        "
        List of  Article
        "
	::= { pmo10010CfgAccessCAisCsf 1 }


pmo10010CfgClientcaiscsfEntry OBJECT-TYPE
	SYNTAX Pmo10010CfgClientcaiscsfEntry
	MAX-ACCESS not-accessible
	STATUS current
	DESCRIPTION
        "
        Row definition for the accessCAisCsf 
        table
        "
	INDEX   { pmo10010CfgClientcaiscsfIndex }
	::= { pmo10010CfgClientcaiscsfTable 1 }


Pmo10010CfgClientcaiscsfEntry ::=
	SEQUENCE {
	pmo10010CfgClientcaiscsfIndex
		INTEGER,
	pmo10010CfgReservePortn
		Unsigned32
	}


pmo10010CfgClientcaiscsfIndex OBJECT-TYPE
	SYNTAX  INTEGER(0..128)
	MAX-ACCESS  read-only
	STATUS current
	DESCRIPTION
        "
        Index definition for the clientcaiscsf 
        table
        "
	::= { pmo10010CfgClientcaiscsfEntry 1 }


pmo10010CfgReservePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pmo10010CfgClientcaiscsfEntry 3 }


--- *****************************************************
---     LEAF for the table Group startup
--- *****************************************************

pmo10010CfgStartup OBJECT IDENTIFIER ::= { pmo10010Config 2 }



--- *****************************************************
---     LEAF for the table 2110
--- *****************************************************

pmo10010CfgClientStartupTable OBJECT-TYPE
	SYNTAX  SEQUENCE OF Pmo10010CfgClientStartupEntry
	MAX-ACCESS not-accessible
	STATUS current
	DESCRIPTION
        "
        List of  Article
        "
	::= { pmo10010CfgStartup 1 }


pmo10010CfgClientStartupEntry OBJECT-TYPE
	SYNTAX Pmo10010CfgClientStartupEntry
	MAX-ACCESS not-accessible
	STATUS current
	DESCRIPTION
        "
        Row definition for the startup 
        table
        "
	INDEX   { pmo10010CfgClientStartupIndex }
	::= { pmo10010CfgClientStartupTable 1 }


Pmo10010CfgClientStartupEntry ::=
	SEQUENCE {
	pmo10010CfgClientStartupIndex
		INTEGER,
	pmo10010CfgSystConfPortPortn
		Unsigned32,
	pmo10010CfgNetConfPortPortn
		Unsigned32,
	pmo10010CfgOptionsPortPortn
		Unsigned32
	}


pmo10010CfgClientStartupIndex OBJECT-TYPE
	SYNTAX  INTEGER(0..128)
	MAX-ACCESS  read-only
	STATUS current
	DESCRIPTION
        "
        Index definition for the clientStartup 
        table
        "
	::= { pmo10010CfgClientStartupEntry 1 }


pmo10010CfgSystConfPortPortn OBJECT-TYPE
	SYNTAX  Unsigned32 (0..65536)
	MAX-ACCESS read-write
	STATUS current
	DESCRIPTION
        "
        Default Settings on Client Port 
        :This  register configures the
         default initialisation settings 
        on the port.
        "
	::= { pmo10010CfgClientStartupEntry 3 }


pmo10010CfgNetConfPortPortn OBJECT-TYPE
	SYNTAX  Unsigned32 (0..65536)
	MAX-ACCESS read-write
	STATUS current
	DESCRIPTION
        "
        Default Settings on Client Port 
        :This  register configures the
         default initialisation settings 
        on the port.
        "
	::= { pmo10010CfgClientStartupEntry 4 }


pmo10010CfgOptionsPortPortn OBJECT-TYPE
	SYNTAX  Unsigned32 (0..65536)
	MAX-ACCESS read-write
	STATUS current
	DESCRIPTION
        "
        Default Options on Client Port 
        :This register configures the default 
        options on the port.
        "
	::= { pmo10010CfgClientStartupEntry 14 }


--- *****************************************************
---     LEAF for the table 2190
--- *****************************************************

pmo10010CfgLineStartupTable OBJECT-TYPE
	SYNTAX  SEQUENCE OF Pmo10010CfgLineStartupEntry
	MAX-ACCESS not-accessible
	STATUS current
	DESCRIPTION
        "
        List of  Article
        "
	::= { pmo10010CfgStartup 2 }


pmo10010CfgLineStartupEntry OBJECT-TYPE
	SYNTAX Pmo10010CfgLineStartupEntry
	MAX-ACCESS not-accessible
	STATUS current
	DESCRIPTION
        "
        Row definition for the startup 
        table
        "
	INDEX   { pmo10010CfgLineStartupIndex }
	::= { pmo10010CfgLineStartupTable 1 }


Pmo10010CfgLineStartupEntry ::=
	SEQUENCE {
	pmo10010CfgLineStartupIndex
		INTEGER,
	pmo10010CfgSystConfLinePortn
		Unsigned32,
	pmo10010CfgOptionsLinePortn
		Unsigned32
	}


pmo10010CfgLineStartupIndex OBJECT-TYPE
	SYNTAX  INTEGER(0..128)
	MAX-ACCESS  read-only
	STATUS current
	DESCRIPTION
        "
        Index definition for the lineStartup 
        table
        "
	::= { pmo10010CfgLineStartupEntry 1 }


pmo10010CfgSystConfLinePortn OBJECT-TYPE
	SYNTAX  Unsigned32 (0..65536)
	MAX-ACCESS read-write
	STATUS current
	DESCRIPTION
        "
        Default Settings on Line :This 
        register configures the default 
        initialisation settings on Line
        "
	::= { pmo10010CfgLineStartupEntry 3 }


pmo10010CfgOptionsLinePortn OBJECT-TYPE
	SYNTAX  Unsigned32 (0..65536)
	MAX-ACCESS read-write
	STATUS current
	DESCRIPTION
        "
        Default Options on Line :This
         register configures the default 
        options on the line
        "
	::= { pmo10010CfgLineStartupEntry 14 }


--- *****************************************************
---     LEAF for the table 21AB
--- *****************************************************

pmo10010CfgXfpTable OBJECT-TYPE
	SYNTAX  SEQUENCE OF Pmo10010CfgXfpEntry
	MAX-ACCESS not-accessible
	STATUS current
	DESCRIPTION
        "
        List of  Article
        "
	::= { pmo10010CfgStartup 3 }


pmo10010CfgXfpEntry OBJECT-TYPE
	SYNTAX Pmo10010CfgXfpEntry
	MAX-ACCESS not-accessible
	STATUS current
	DESCRIPTION
        "
        Row definition for the startup 
        table
        "
	INDEX   { pmo10010CfgXfpIndex }
	::= { pmo10010CfgXfpTable 1 }


Pmo10010CfgXfpEntry ::=
	SEQUENCE {
	pmo10010CfgXfpIndex
		INTEGER,
	pmo10010CfgSystConfMsaLinePortn
		Unsigned32
	}


pmo10010CfgXfpIndex OBJECT-TYPE
	SYNTAX  INTEGER(0..128)
	MAX-ACCESS  read-only
	STATUS current
	DESCRIPTION
        "
        Index definition for the xfp table
        "
	::= { pmo10010CfgXfpEntry 1 }


pmo10010CfgSystConfMsaLinePortn OBJECT-TYPE
	SYNTAX  Unsigned32 (0..65536)
	MAX-ACCESS read-write
	STATUS current
	DESCRIPTION
        "
        Default settings on MSA :This
         register configures the default 
        initialisation settings on MSA
        "
	::= { pmo10010CfgXfpEntry 3 }


--- *****************************************************
---     LEAF for the table 2610
--- *****************************************************

pmo10010CfgClientOtxtlhTable OBJECT-TYPE
	SYNTAX  SEQUENCE OF Pmo10010CfgClientOtxtlhEntry
	MAX-ACCESS not-accessible
	STATUS current
	DESCRIPTION
        "
        List of  Article
        "
	::= { pmo10010CfgStartup 4 }


pmo10010CfgClientOtxtlhEntry OBJECT-TYPE
	SYNTAX Pmo10010CfgClientOtxtlhEntry
	MAX-ACCESS not-accessible
	STATUS current
	DESCRIPTION
        "
        Row definition for the startup 
        table
        "
	INDEX   { pmo10010CfgClientOtxtlhIndex }
	::= { pmo10010CfgClientOtxtlhTable 1 }


Pmo10010CfgClientOtxtlhEntry ::=
	SEQUENCE {
	pmo10010CfgClientOtxtlhIndex
		INTEGER,
	pmo10010CfgControlsPortn
		Unsigned32,
	pmo10010CfgClientPwrLaserPortn
		Unsigned32,
	pmo10010CfgClientFCurrentPortn
		Unsigned32,
	pmo10010CfgClientGridCurrentPortn
		Unsigned32,
	pmo10010CfgClientFoPortn
		Unsigned32
	}


pmo10010CfgClientOtxtlhIndex OBJECT-TYPE
	SYNTAX  INTEGER(0..128)
	MAX-ACCESS  read-only
	STATUS current
	DESCRIPTION
        "
        Index definition for the clientOtxtlh 
        table
        "
	::= { pmo10010CfgClientOtxtlhEntry 1 }


pmo10010CfgControlsPortn OBJECT-TYPE
	SYNTAX  Unsigned32 (0..65536)
	MAX-ACCESS read-write
	STATUS deprecated
	DESCRIPTION
        "
        Defaut Client settings :This register 
        configures the start-up settings 
        on the ports
        "
	::= { pmo10010CfgClientOtxtlhEntry 3 }


pmo10010CfgClientPwrLaserPortn OBJECT-TYPE
	SYNTAX  Unsigned32 (0..65536)
	MAX-ACCESS read-write
	STATUS current
	DESCRIPTION
        "
        Defaut Client output Power :This 
        register configures the start-up 
        output power of the client transceiver 
         (Unit = dBm)
        "
	::= { pmo10010CfgClientOtxtlhEntry 6 }


pmo10010CfgClientFCurrentPortn OBJECT-TYPE
	SYNTAX  Unsigned32 (0..65536)
	MAX-ACCESS read-write
	STATUS current
	DESCRIPTION
        "
        Default Client transceiver Channel 
        :This register configures the start-up 
        laser channel of the client  transceiver
        "
	::= { pmo10010CfgClientOtxtlhEntry 7 }


pmo10010CfgClientGridCurrentPortn OBJECT-TYPE
	SYNTAX  Unsigned32 (0..65536)
	MAX-ACCESS read-write
	STATUS current
	DESCRIPTION
        "
        Default Client transceiver Grid 
        :This register configures the start-up 
        laser grid of the client transceiver
        "
	::= { pmo10010CfgClientOtxtlhEntry 8 }


pmo10010CfgClientFoPortn OBJECT-TYPE
	SYNTAX  Unsigned32 (0..65536)
	MAX-ACCESS read-write
	STATUS current
	DESCRIPTION
        "
        Default Client first Frequency 
        :This register configures the start-up 
        first frequency of the client transceiver
        "
	::= { pmo10010CfgClientOtxtlhEntry 9 }


--- *****************************************************
---     LEAF for the table Group labels
--- *****************************************************

pmo10010CfgLabels OBJECT IDENTIFIER ::= { pmo10010Config 3 }



--- *****************************************************
---     LEAF for the table 0003
--- *****************************************************

pmo10010CfgLabelclientTable OBJECT-TYPE
	SYNTAX  SEQUENCE OF Pmo10010CfgLabelclientEntry
	MAX-ACCESS not-accessible
	STATUS current
	DESCRIPTION
        "
        List of  Article
        "
	::= { pmo10010CfgLabels 1 }


pmo10010CfgLabelclientEntry OBJECT-TYPE
	SYNTAX Pmo10010CfgLabelclientEntry
	MAX-ACCESS not-accessible
	STATUS current
	DESCRIPTION
        "
        Row definition for the labels
         table
        "
	INDEX   { pmo10010CfgLabelclientIndex }
	::= { pmo10010CfgLabelclientTable 1 }


Pmo10010CfgLabelclientEntry ::=
	SEQUENCE {
	pmo10010CfgLabelclientIndex
		INTEGER,
	pmo10010CfgLabelclientPortn
		DisplayString
	}


pmo10010CfgLabelclientIndex OBJECT-TYPE
	SYNTAX  INTEGER(0..128)
	MAX-ACCESS  read-only
	STATUS current
	DESCRIPTION
        "
        Index definition for the labelclient 
        table
        "
	::= { pmo10010CfgLabelclientEntry 1 }


pmo10010CfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pmo10010CfgLabelclientEntry 3 }


--- *****************************************************
---     LEAF for the table 0004
--- *****************************************************

pmo10010CfgLabellineTable OBJECT-TYPE
	SYNTAX  SEQUENCE OF Pmo10010CfgLabellineEntry
	MAX-ACCESS not-accessible
	STATUS current
	DESCRIPTION
        "
        List of  Article
        "
	::= { pmo10010CfgLabels 2 }


pmo10010CfgLabellineEntry OBJECT-TYPE
	SYNTAX Pmo10010CfgLabellineEntry
	MAX-ACCESS not-accessible
	STATUS current
	DESCRIPTION
        "
        Row definition for the labels
         table
        "
	INDEX   { pmo10010CfgLabellineIndex }
	::= { pmo10010CfgLabellineTable 1 }


Pmo10010CfgLabellineEntry ::=
	SEQUENCE {
	pmo10010CfgLabellineIndex
		INTEGER,
	pmo10010CfgLabellinePortn
		DisplayString
	}


pmo10010CfgLabellineIndex OBJECT-TYPE
	SYNTAX  INTEGER(0..128)
	MAX-ACCESS  read-only
	STATUS current
	DESCRIPTION
        "
        Index definition for the labelline 
        table
        "
	::= { pmo10010CfgLabellineEntry 1 }


pmo10010CfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pmo10010CfgLabellineEntry 3 }


--- *****************************************************
---     LEAF for the table Group startuptlh
--- *****************************************************

pmo10010CfgStartuptlh OBJECT IDENTIFIER ::= { pmo10010Config 4 }



--- *****************************************************
---     LEAF for the table 25AB
--- *****************************************************

pmo10010CfgOtxtlhTable OBJECT-TYPE
	SYNTAX  SEQUENCE OF Pmo10010CfgOtxtlhEntry
	MAX-ACCESS not-accessible
	STATUS current
	DESCRIPTION
        "
        List of  Article
        "
	::= { pmo10010CfgStartuptlh 1 }


pmo10010CfgOtxtlhEntry OBJECT-TYPE
	SYNTAX Pmo10010CfgOtxtlhEntry
	MAX-ACCESS not-accessible
	STATUS current
	DESCRIPTION
        "
        Row definition for the startuptlh 
        table
        "
	INDEX   { pmo10010CfgOtxtlhIndex }
	::= { pmo10010CfgOtxtlhTable 1 }


Pmo10010CfgOtxtlhEntry ::=
	SEQUENCE {
	pmo10010CfgOtxtlhIndex
		INTEGER,
	pmo10010CfgLinePwrLaserPortn
		Unsigned32,
	pmo10010CfgLineFCurrentPortn
		Unsigned32,
	pmo10010CfgLineGridCurrentPortn
		Unsigned32,
	pmo10010CfgFPortn
		Unsigned32,
	pmo10010CfgRxLineFCurrentPortn
		Unsigned32
	}


pmo10010CfgOtxtlhIndex OBJECT-TYPE
	SYNTAX  INTEGER(0..128)
	MAX-ACCESS  read-only
	STATUS current
	DESCRIPTION
        "
        Index definition for the otxtlh 
        table
        "
	::= { pmo10010CfgOtxtlhEntry 1 }


pmo10010CfgLinePwrLaserPortn OBJECT-TYPE
	SYNTAX  Unsigned32 (0..65536)
	MAX-ACCESS read-write
	STATUS current
	DESCRIPTION
        "
        Defaut Line output Power :This 
        register configures the start-up 
        output power of the Line tranceiver 
         (Unit = dBm)
        "
	::= { pmo10010CfgOtxtlhEntry 6 }


pmo10010CfgLineFCurrentPortn OBJECT-TYPE
	SYNTAX  Unsigned32 (0..65536)
	MAX-ACCESS read-write
	STATUS current
	DESCRIPTION
        "
        Default Line transceiver Tx Channel 
        :This register configures the start-up 
        laser channel of the Line Tx transceiver
        "
	::= { pmo10010CfgOtxtlhEntry 7 }


pmo10010CfgLineGridCurrentPortn OBJECT-TYPE
	SYNTAX  Unsigned32 (0..65536)
	MAX-ACCESS read-write
	STATUS current
	DESCRIPTION
        "
        Default Line transceiver Grid
         :This register configures the
         start-up laser grid of the Line 
        transceiver
        "
	::= { pmo10010CfgOtxtlhEntry 8 }


pmo10010CfgFPortn OBJECT-TYPE
	SYNTAX  Unsigned32 (0..65536)
	MAX-ACCESS read-write
	STATUS current
	DESCRIPTION
        "
        Default Line TRX lowest Freq :This 
        register configures the start-up 
        lowest frequency of the Line transceiver
        "
	::= { pmo10010CfgOtxtlhEntry 9 }


pmo10010CfgRxLineFCurrentPortn OBJECT-TYPE
	SYNTAX  Unsigned32 (0..65536)
	MAX-ACCESS read-write
	STATUS current
	DESCRIPTION
        "
        Default Line transceiver Rx Channel 
        :This register configures the start-up 
        laser channel of the Line Rx transceiver
        "
	::= { pmo10010CfgOtxtlhEntry 10 }


--- *****************************************************
---     LEAF for the table Group other
--- *****************************************************

pmo10010CfgOther OBJECT IDENTIFIER ::= { pmo10010Config 5 }



--- *****************************************************
---     LEAF for the table 2300
--- *****************************************************

pmo10010tablemoduleOther OBJECT IDENTIFIER ::= { pmo10010CfgOther 1 }



pmo10010Cfgmode OBJECT-TYPE
	  SYNTAX Unsigned32 (0..65536)
	  MAX-ACCESS read-write
	  STATUS current
	  DESCRIPTION
        "
        Default settings on Module :This 
        register selects the configuration 
        mode of the module
        "
	  ::= { pmo10010tablemoduleOther 2 }



pmo10010CfgfanLowSpeedThreshold OBJECT-TYPE
	  SYNTAX Unsigned32 (0..65536)
	  MAX-ACCESS read-write
	  STATUS current
	  DESCRIPTION
        "
        Default settings on Module :This 
        register selects the speed threshold 
        of the fan's
        "
	  ::= { pmo10010tablemoduleOther 3 }



pmo10010CfgfanHighSpeedThreshold OBJECT-TYPE
	  SYNTAX Unsigned32 (0..65536)
	  MAX-ACCESS read-write
	  STATUS current
	  DESCRIPTION
        "
        Default settings on Module :This 
        register selects the speed threshold 
        of the fan's
        "
	  ::= { pmo10010tablemoduleOther 4 }



--- *****************************************************
---     LEAF for the table Group odu2Clienta
--- *****************************************************

pmo10010CfgOdu2Clienta OBJECT IDENTIFIER ::= { pmo10010Config 6 }



--- *****************************************************
---     LEAF for the table 29C0
--- *****************************************************

pmo10010CfgClientStartupOduTable OBJECT-TYPE
	SYNTAX  SEQUENCE OF Pmo10010CfgClientStartupOduEntry
	MAX-ACCESS not-accessible
	STATUS current
	DESCRIPTION
        "
        List of  Article
        "
	::= { pmo10010CfgOdu2Clienta 1 }


pmo10010CfgClientStartupOduEntry OBJECT-TYPE
	SYNTAX Pmo10010CfgClientStartupOduEntry
	MAX-ACCESS not-accessible
	STATUS current
	DESCRIPTION
        "
        Row definition for the odu2Clienta 
        table
        "
	INDEX   { pmo10010CfgClientStartupOduIndex }
	::= { pmo10010CfgClientStartupOduTable 1 }


Pmo10010CfgClientStartupOduEntry ::=
	SEQUENCE {
	pmo10010CfgClientStartupOduIndex
		INTEGER,
	pmo10010CfgOdu2ReserveLsbPortn
		Unsigned32,
	pmo10010CfgOdu2DegthresholdMsbPortn
		Unsigned32,
	pmo10010CfgOdu2DegmPortn
		Unsigned32,
	pmo10010CfgOdu2SettingsPortn
		Unsigned32
	}


pmo10010CfgClientStartupOduIndex OBJECT-TYPE
	SYNTAX  INTEGER(0..128)
	MAX-ACCESS  read-only
	STATUS current
	DESCRIPTION
        "
        Index definition for the clientStartupOdu 
        table
        "
	::= { pmo10010CfgClientStartupOduEntry 1 }


pmo10010CfgOdu2ReserveLsbPortn OBJECT-TYPE
	SYNTAX  Unsigned32 (0..65536)
	MAX-ACCESS read-write
	STATUS current
	DESCRIPTION
        "
        :
        "
	::= { pmo10010CfgClientStartupOduEntry 3 }


pmo10010CfgOdu2DegthresholdMsbPortn OBJECT-TYPE
	SYNTAX  Unsigned32 (0..65536)
	MAX-ACCESS read-write
	STATUS current
	DESCRIPTION
        "
        ODU2 Degrade Threshold :
        "
	::= { pmo10010CfgClientStartupOduEntry 4 }


pmo10010CfgOdu2DegmPortn OBJECT-TYPE
	SYNTAX  Unsigned32 (0..65536)
	MAX-ACCESS read-write
	STATUS current
	DESCRIPTION
        "
        ODU2 Degrade Confirmation :
        "
	::= { pmo10010CfgClientStartupOduEntry 5 }


pmo10010CfgOdu2SettingsPortn OBJECT-TYPE
	SYNTAX  Unsigned32 (0..65536)
	MAX-ACCESS read-write
	STATUS current
	DESCRIPTION
        "
        ODU2 Settings :
        "
	::= { pmo10010CfgClientStartupOduEntry 6 }


--- *****************************************************
---     LEAF for the table Group otu4Line
--- *****************************************************

pmo10010CfgOtu4Line OBJECT IDENTIFIER ::= { pmo10010Config 7 }



--- *****************************************************
---     LEAF for the table 29E0
--- *****************************************************

pmo10010CfgLinexStartupOtuTable OBJECT-TYPE
	SYNTAX  SEQUENCE OF Pmo10010CfgLinexStartupOtuEntry
	MAX-ACCESS not-accessible
	STATUS current
	DESCRIPTION
        "
        List of  Article
        "
	::= { pmo10010CfgOtu4Line 1 }


pmo10010CfgLinexStartupOtuEntry OBJECT-TYPE
	SYNTAX Pmo10010CfgLinexStartupOtuEntry
	MAX-ACCESS not-accessible
	STATUS current
	DESCRIPTION
        "
        Row definition for the otu4Line 
        table
        "
	INDEX   { pmo10010CfgLinexStartupOtuIndex }
	::= { pmo10010CfgLinexStartupOtuTable 1 }


Pmo10010CfgLinexStartupOtuEntry ::=
	SEQUENCE {
	pmo10010CfgLinexStartupOtuIndex
		INTEGER,
	pmo10010CfgOtu4ReserveLsbPortn
		Unsigned32,
	pmo10010CfgOtu4DegthresholdMsbPortn
		Unsigned32,
	pmo10010CfgOtu4DegmPortn
		Unsigned32,
	pmo10010CfgOtu4SettingsPortn
		Unsigned32
	}


pmo10010CfgLinexStartupOtuIndex OBJECT-TYPE
	SYNTAX  INTEGER(0..128)
	MAX-ACCESS  read-only
	STATUS current
	DESCRIPTION
        "
        Index definition for the linexStartupOtu 
        table
        "
	::= { pmo10010CfgLinexStartupOtuEntry 1 }


pmo10010CfgOtu4ReserveLsbPortn OBJECT-TYPE
	SYNTAX  Unsigned32 (0..65536)
	MAX-ACCESS read-write
	STATUS current
	DESCRIPTION
        "
        :
        "
	::= { pmo10010CfgLinexStartupOtuEntry 3 }


pmo10010CfgOtu4DegthresholdMsbPortn OBJECT-TYPE
	SYNTAX  Unsigned32 (0..65536)
	MAX-ACCESS read-write
	STATUS current
	DESCRIPTION
        "
        OTU4 Degrade Threshold :
        "
	::= { pmo10010CfgLinexStartupOtuEntry 4 }


pmo10010CfgOtu4DegmPortn OBJECT-TYPE
	SYNTAX  Unsigned32 (0..65536)
	MAX-ACCESS read-write
	STATUS current
	DESCRIPTION
        "
        OTU4 Degrade Confirmation :
        "
	::= { pmo10010CfgLinexStartupOtuEntry 5 }


pmo10010CfgOtu4SettingsPortn OBJECT-TYPE
	SYNTAX  Unsigned32 (0..65536)
	MAX-ACCESS read-write
	STATUS current
	DESCRIPTION
        "
        OTU4 Settings :
        "
	::= { pmo10010CfgLinexStartupOtuEntry 6 }


--- *****************************************************
---     LEAF for the table Group odu4Line
--- *****************************************************

pmo10010CfgOdu4Line OBJECT IDENTIFIER ::= { pmo10010Config 8 }



--- *****************************************************
---     LEAF for the table 29F4
--- *****************************************************

pmo10010CfgLinexStartupOduTable OBJECT-TYPE
	SYNTAX  SEQUENCE OF Pmo10010CfgLinexStartupOduEntry
	MAX-ACCESS not-accessible
	STATUS current
	DESCRIPTION
        "
        List of  Article
        "
	::= { pmo10010CfgOdu4Line 1 }


pmo10010CfgLinexStartupOduEntry OBJECT-TYPE
	SYNTAX Pmo10010CfgLinexStartupOduEntry
	MAX-ACCESS not-accessible
	STATUS current
	DESCRIPTION
        "
        Row definition for the odu4Line 
        table
        "
	INDEX   { pmo10010CfgLinexStartupOduIndex }
	::= { pmo10010CfgLinexStartupOduTable 1 }


Pmo10010CfgLinexStartupOduEntry ::=
	SEQUENCE {
	pmo10010CfgLinexStartupOduIndex
		INTEGER,
	pmo10010CfgOdu4ReserveLsbPortn
		Unsigned32,
	pmo10010CfgOdu4DegthresholdMsbPortn
		Unsigned32,
	pmo10010CfgOdu4DegmPortn
		Unsigned32,
	pmo10010CfgOdu4SettingsPortn
		Unsigned32
	}


pmo10010CfgLinexStartupOduIndex OBJECT-TYPE
	SYNTAX  INTEGER(0..128)
	MAX-ACCESS  read-only
	STATUS current
	DESCRIPTION
        "
        Index definition for the linexStartupOdu 
        table
        "
	::= { pmo10010CfgLinexStartupOduEntry 1 }


pmo10010CfgOdu4ReserveLsbPortn OBJECT-TYPE
	SYNTAX  Unsigned32 (0..65536)
	MAX-ACCESS read-write
	STATUS current
	DESCRIPTION
        "
        :
        "
	::= { pmo10010CfgLinexStartupOduEntry 3 }


pmo10010CfgOdu4DegthresholdMsbPortn OBJECT-TYPE
	SYNTAX  Unsigned32 (0..65536)
	MAX-ACCESS read-write
	STATUS current
	DESCRIPTION
        "
        ODU4 Degrade Threshold :
        "
	::= { pmo10010CfgLinexStartupOduEntry 4 }


pmo10010CfgOdu4DegmPortn OBJECT-TYPE
	SYNTAX  Unsigned32 (0..65536)
	MAX-ACCESS read-write
	STATUS current
	DESCRIPTION
        "
        ODU4 Degrade Confirmation :
        "
	::= { pmo10010CfgLinexStartupOduEntry 5 }


pmo10010CfgOdu4SettingsPortn OBJECT-TYPE
	SYNTAX  Unsigned32 (0..65536)
	MAX-ACCESS read-write
	STATUS current
	DESCRIPTION
        "
        ODU4 Settings :
        "
	::= { pmo10010CfgLinexStartupOduEntry 6 }


--- *****************************************************
---     LEAF for the table Group sapiTxClient
--- *****************************************************

pmo10010CfgSapiTxClient OBJECT IDENTIFIER ::= { pmo10010Config 9 }



--- *****************************************************
---     LEAF for the table 2A10
--- *****************************************************

pmo10010CfgClientSapiTxOduTable OBJECT-TYPE
	SYNTAX  SEQUENCE OF Pmo10010CfgClientSapiTxOduEntry
	MAX-ACCESS not-accessible
	STATUS current
	DESCRIPTION
        "
        List of  Article
        "
	::= { pmo10010CfgSapiTxClient 1 }


pmo10010CfgClientSapiTxOduEntry OBJECT-TYPE
	SYNTAX Pmo10010CfgClientSapiTxOduEntry
	MAX-ACCESS not-accessible
	STATUS current
	DESCRIPTION
        "
        Row definition for the sapiTxClient 
        table
        "
	INDEX   { pmo10010CfgClientSapiTxOduIndex }
	::= { pmo10010CfgClientSapiTxOduTable 1 }


Pmo10010CfgClientSapiTxOduEntry ::=
	SEQUENCE {
	pmo10010CfgClientSapiTxOduIndex
		INTEGER,
	pmo10010CfgClientSapiTxSetupPortn
		DisplayString
	}


pmo10010CfgClientSapiTxOduIndex OBJECT-TYPE
	SYNTAX  INTEGER(0..128)
	MAX-ACCESS  read-only
	STATUS current
	DESCRIPTION
        "
        Index definition for the clientSapiTxOdu 
        table
        "
	::= { pmo10010CfgClientSapiTxOduEntry 1 }


pmo10010CfgClientSapiTxSetupPortn OBJECT-TYPE
	SYNTAX  DisplayString( SIZE(1..16))
	MAX-ACCESS read-write
	STATUS current
	DESCRIPTION
        "
        Client Transmitted SAPI :This
         register defines the value of
         the transmitted Trace Identifier 
        on the line output
        "
	::= { pmo10010CfgClientSapiTxOduEntry 3 }


--- *****************************************************
---     LEAF for the table Group sapiExpClient
--- *****************************************************

pmo10010CfgSapiExpClient OBJECT IDENTIFIER ::= { pmo10010Config 10 }



--- *****************************************************
---     LEAF for the table 2A30
--- *****************************************************

pmo10010CfgClientSapiExpOduTable OBJECT-TYPE
	SYNTAX  SEQUENCE OF Pmo10010CfgClientSapiExpOduEntry
	MAX-ACCESS not-accessible
	STATUS current
	DESCRIPTION
        "
        List of  Article
        "
	::= { pmo10010CfgSapiExpClient 1 }


pmo10010CfgClientSapiExpOduEntry OBJECT-TYPE
	SYNTAX Pmo10010CfgClientSapiExpOduEntry
	MAX-ACCESS not-accessible
	STATUS current
	DESCRIPTION
        "
        Row definition for the sapiExpClient 
        table
        "
	INDEX   { pmo10010CfgClientSapiExpOduIndex }
	::= { pmo10010CfgClientSapiExpOduTable 1 }


Pmo10010CfgClientSapiExpOduEntry ::=
	SEQUENCE {
	pmo10010CfgClientSapiExpOduIndex
		INTEGER,
	pmo10010CfgClientSapiExpSetupPortn
		DisplayString
	}


pmo10010CfgClientSapiExpOduIndex OBJECT-TYPE
	SYNTAX  INTEGER(0..128)
	MAX-ACCESS  read-only
	STATUS current
	DESCRIPTION
        "
        Index definition for the clientSapiExpOdu 
        table
        "
	::= { pmo10010CfgClientSapiExpOduEntry 1 }


pmo10010CfgClientSapiExpSetupPortn OBJECT-TYPE
	SYNTAX  DisplayString( SIZE(1..16))
	MAX-ACCESS read-write
	STATUS current
	DESCRIPTION
        "
        Client Expected SAPI :This register 
        defines the value of the expected 
        Trace Identifier on the line input
        "
	::= { pmo10010CfgClientSapiExpOduEntry 3 }


--- *****************************************************
---     LEAF for the table Group sapiAccClient
--- *****************************************************

pmo10010CfgSapiAccClient OBJECT IDENTIFIER ::= { pmo10010Config 11 }



--- *****************************************************
---     LEAF for the table 2A50
--- *****************************************************

pmo10010CfgClientSapiAccOduTable OBJECT-TYPE
	SYNTAX  SEQUENCE OF Pmo10010CfgClientSapiAccOduEntry
	MAX-ACCESS not-accessible
	STATUS current
	DESCRIPTION
        "
        List of  Article
        "
	::= { pmo10010CfgSapiAccClient 1 }


pmo10010CfgClientSapiAccOduEntry OBJECT-TYPE
	SYNTAX Pmo10010CfgClientSapiAccOduEntry
	MAX-ACCESS not-accessible
	STATUS current
	DESCRIPTION
        "
        Row definition for the sapiAccClient 
        table
        "
	INDEX   { pmo10010CfgClientSapiAccOduIndex }
	::= { pmo10010CfgClientSapiAccOduTable 1 }


Pmo10010CfgClientSapiAccOduEntry ::=
	SEQUENCE {
	pmo10010CfgClientSapiAccOduIndex
		INTEGER,
	pmo10010CfgClientSapiAccSetupPortn
		DisplayString
	}


pmo10010CfgClientSapiAccOduIndex OBJECT-TYPE
	SYNTAX  INTEGER(0..128)
	MAX-ACCESS  read-only
	STATUS current
	DESCRIPTION
        "
        Index definition for the clientSapiAccOdu 
        table
        "
	::= { pmo10010CfgClientSapiAccOduEntry 1 }


pmo10010CfgClientSapiAccSetupPortn OBJECT-TYPE
	SYNTAX  DisplayString( SIZE(1..16))
	MAX-ACCESS read-write
	STATUS deprecated
	DESCRIPTION
        "
        Client Accepted SAPI :This register 
        defines the value of the accepted 
        Trace Identifier on the line input
        "
	::= { pmo10010CfgClientSapiAccOduEntry 3 }


--- *****************************************************
---     LEAF for the table Group dapiTxClient
--- *****************************************************

pmo10010CfgDapiTxClient OBJECT IDENTIFIER ::= { pmo10010Config 12 }



--- *****************************************************
---     LEAF for the table 2A90
--- *****************************************************

pmo10010CfgClientDapiTxOduTable OBJECT-TYPE
	SYNTAX  SEQUENCE OF Pmo10010CfgClientDapiTxOduEntry
	MAX-ACCESS not-accessible
	STATUS current
	DESCRIPTION
        "
        List of  Article
        "
	::= { pmo10010CfgDapiTxClient 1 }


pmo10010CfgClientDapiTxOduEntry OBJECT-TYPE
	SYNTAX Pmo10010CfgClientDapiTxOduEntry
	MAX-ACCESS not-accessible
	STATUS current
	DESCRIPTION
        "
        Row definition for the dapiTxClient 
        table
        "
	INDEX   { pmo10010CfgClientDapiTxOduIndex }
	::= { pmo10010CfgClientDapiTxOduTable 1 }


Pmo10010CfgClientDapiTxOduEntry ::=
	SEQUENCE {
	pmo10010CfgClientDapiTxOduIndex
		INTEGER,
	pmo10010CfgClientDapiTxSetupPortn
		DisplayString
	}


pmo10010CfgClientDapiTxOduIndex OBJECT-TYPE
	SYNTAX  INTEGER(0..128)
	MAX-ACCESS  read-only
	STATUS current
	DESCRIPTION
        "
        Index definition for the clientDapiTxOdu 
        table
        "
	::= { pmo10010CfgClientDapiTxOduEntry 1 }


pmo10010CfgClientDapiTxSetupPortn OBJECT-TYPE
	SYNTAX  DisplayString( SIZE(1..16))
	MAX-ACCESS read-write
	STATUS current
	DESCRIPTION
        "
        Client Transmitted DAPI :This
         register defines the value of
         the transmitted Trace Identifier 
        on the line output
        "
	::= { pmo10010CfgClientDapiTxOduEntry 3 }


--- *****************************************************
---     LEAF for the table Group dapiExpClient
--- *****************************************************

pmo10010CfgDapiExpClient OBJECT IDENTIFIER ::= { pmo10010Config 13 }



--- *****************************************************
---     LEAF for the table 2AB0
--- *****************************************************

pmo10010CfgClientDapiExpOduTable OBJECT-TYPE
	SYNTAX  SEQUENCE OF Pmo10010CfgClientDapiExpOduEntry
	MAX-ACCESS not-accessible
	STATUS current
	DESCRIPTION
        "
        List of  Article
        "
	::= { pmo10010CfgDapiExpClient 1 }


pmo10010CfgClientDapiExpOduEntry OBJECT-TYPE
	SYNTAX Pmo10010CfgClientDapiExpOduEntry
	MAX-ACCESS not-accessible
	STATUS current
	DESCRIPTION
        "
        Row definition for the dapiExpClient 
        table
        "
	INDEX   { pmo10010CfgClientDapiExpOduIndex }
	::= { pmo10010CfgClientDapiExpOduTable 1 }


Pmo10010CfgClientDapiExpOduEntry ::=
	SEQUENCE {
	pmo10010CfgClientDapiExpOduIndex
		INTEGER,
	pmo10010CfgClientDapiExpSetupPortn
		DisplayString
	}


pmo10010CfgClientDapiExpOduIndex OBJECT-TYPE
	SYNTAX  INTEGER(0..128)
	MAX-ACCESS  read-only
	STATUS current
	DESCRIPTION
        "
        Index definition for the clientDapiExpOdu 
        table
        "
	::= { pmo10010CfgClientDapiExpOduEntry 1 }


pmo10010CfgClientDapiExpSetupPortn OBJECT-TYPE
	SYNTAX  DisplayString( SIZE(1..16))
	MAX-ACCESS read-write
	STATUS current
	DESCRIPTION
        "
        Client Expected DAPI :This register 
        defines the value of the expected 
        Trace Identifier on the line input
        "
	::= { pmo10010CfgClientDapiExpOduEntry 3 }


--- *****************************************************
---     LEAF for the table Group dapiAccClient
--- *****************************************************

pmo10010CfgDapiAccClient OBJECT IDENTIFIER ::= { pmo10010Config 14 }



--- *****************************************************
---     LEAF for the table 2AD0
--- *****************************************************

pmo10010CfgClientDapiAccOduTable OBJECT-TYPE
	SYNTAX  SEQUENCE OF Pmo10010CfgClientDapiAccOduEntry
	MAX-ACCESS not-accessible
	STATUS current
	DESCRIPTION
        "
        List of  Article
        "
	::= { pmo10010CfgDapiAccClient 1 }


pmo10010CfgClientDapiAccOduEntry OBJECT-TYPE
	SYNTAX Pmo10010CfgClientDapiAccOduEntry
	MAX-ACCESS not-accessible
	STATUS current
	DESCRIPTION
        "
        Row definition for the dapiAccClient 
        table
        "
	INDEX   { pmo10010CfgClientDapiAccOduIndex }
	::= { pmo10010CfgClientDapiAccOduTable 1 }


Pmo10010CfgClientDapiAccOduEntry ::=
	SEQUENCE {
	pmo10010CfgClientDapiAccOduIndex
		INTEGER,
	pmo10010CfgClientDapiAccSetupPortn
		DisplayString
	}


pmo10010CfgClientDapiAccOduIndex OBJECT-TYPE
	SYNTAX  INTEGER(0..128)
	MAX-ACCESS  read-only
	STATUS current
	DESCRIPTION
        "
        Index definition for the clientDapiAccOdu 
        table
        "
	::= { pmo10010CfgClientDapiAccOduEntry 1 }


pmo10010CfgClientDapiAccSetupPortn OBJECT-TYPE
	SYNTAX  DisplayString( SIZE(1..16))
	MAX-ACCESS read-write
	STATUS deprecated
	DESCRIPTION
        "
        Client Accepted DAPI :This register 
        defines the value of the accepted 
        Trace Identifier on the line input
        "
	::= { pmo10010CfgClientDapiAccOduEntry 3 }


--- *****************************************************
---     LEAF for the table Group sapiTxLineOtu4
--- *****************************************************

pmo10010CfgSapiTxLineOtu4 OBJECT IDENTIFIER ::= { pmo10010Config 15 }



--- *****************************************************
---     LEAF for the table 2B10
--- *****************************************************

pmo10010CfgLineSapiTxOtuTable OBJECT-TYPE
	SYNTAX  SEQUENCE OF Pmo10010CfgLineSapiTxOtuEntry
	MAX-ACCESS not-accessible
	STATUS current
	DESCRIPTION
        "
        List of  Article
        "
	::= { pmo10010CfgSapiTxLineOtu4 1 }


pmo10010CfgLineSapiTxOtuEntry OBJECT-TYPE
	SYNTAX Pmo10010CfgLineSapiTxOtuEntry
	MAX-ACCESS not-accessible
	STATUS current
	DESCRIPTION
        "
        Row definition for the sapiTxLineOtu4 
        table
        "
	INDEX   { pmo10010CfgLineSapiTxOtuIndex }
	::= { pmo10010CfgLineSapiTxOtuTable 1 }


Pmo10010CfgLineSapiTxOtuEntry ::=
	SEQUENCE {
	pmo10010CfgLineSapiTxOtuIndex
		INTEGER,
	pmo10010CfgLineSapiTxSetupOtuPortn
		DisplayString
	}


pmo10010CfgLineSapiTxOtuIndex OBJECT-TYPE
	SYNTAX  INTEGER(0..128)
	MAX-ACCESS  read-only
	STATUS current
	DESCRIPTION
        "
        Index definition for the lineSapiTxOtu 
        table
        "
	::= { pmo10010CfgLineSapiTxOtuEntry 1 }


pmo10010CfgLineSapiTxSetupOtuPortn OBJECT-TYPE
	SYNTAX  DisplayString( SIZE(1..16))
	MAX-ACCESS read-write
	STATUS current
	DESCRIPTION
        "
        OTU4 Line Transmitted SAPI :This 
        register defines the value of the 
        transmitted Trace Identifier on 
        the line output
        "
	::= { pmo10010CfgLineSapiTxOtuEntry 3 }


--- *****************************************************
---     LEAF for the table Group sapiExpLineOtu4
--- *****************************************************

pmo10010CfgSapiExpLineOtu4 OBJECT IDENTIFIER ::= { pmo10010Config 16 }



--- *****************************************************
---     LEAF for the table 2B30
--- *****************************************************

pmo10010CfgLineSapiExpOtuTable OBJECT-TYPE
	SYNTAX  SEQUENCE OF Pmo10010CfgLineSapiExpOtuEntry
	MAX-ACCESS not-accessible
	STATUS current
	DESCRIPTION
        "
        List of  Article
        "
	::= { pmo10010CfgSapiExpLineOtu4 1 }


pmo10010CfgLineSapiExpOtuEntry OBJECT-TYPE
	SYNTAX Pmo10010CfgLineSapiExpOtuEntry
	MAX-ACCESS not-accessible
	STATUS current
	DESCRIPTION
        "
        Row definition for the sapiExpLineOtu4 
        table
        "
	INDEX   { pmo10010CfgLineSapiExpOtuIndex }
	::= { pmo10010CfgLineSapiExpOtuTable 1 }


Pmo10010CfgLineSapiExpOtuEntry ::=
	SEQUENCE {
	pmo10010CfgLineSapiExpOtuIndex
		INTEGER,
	pmo10010CfgLineSapiExpSetupOtuPortn
		DisplayString
	}


pmo10010CfgLineSapiExpOtuIndex OBJECT-TYPE
	SYNTAX  INTEGER(0..128)
	MAX-ACCESS  read-only
	STATUS current
	DESCRIPTION
        "
        Index definition for the lineSapiExpOtu 
        table
        "
	::= { pmo10010CfgLineSapiExpOtuEntry 1 }


pmo10010CfgLineSapiExpSetupOtuPortn OBJECT-TYPE
	SYNTAX  DisplayString( SIZE(1..16))
	MAX-ACCESS read-write
	STATUS current
	DESCRIPTION
        "
        OTU4 Line Expected SAPI :This
         register defines the value of
         the expected Trace Identifier
         on the line input
        "
	::= { pmo10010CfgLineSapiExpOtuEntry 3 }


--- *****************************************************
---     LEAF for the table Group sapiAccLineOtu4
--- *****************************************************

pmo10010CfgSapiAccLineOtu4 OBJECT IDENTIFIER ::= { pmo10010Config 17 }



--- *****************************************************
---     LEAF for the table 2B50
--- *****************************************************

pmo10010CfgLineSapiAccOtuTable OBJECT-TYPE
	SYNTAX  SEQUENCE OF Pmo10010CfgLineSapiAccOtuEntry
	MAX-ACCESS not-accessible
	STATUS current
	DESCRIPTION
        "
        List of  Article
        "
	::= { pmo10010CfgSapiAccLineOtu4 1 }


pmo10010CfgLineSapiAccOtuEntry OBJECT-TYPE
	SYNTAX Pmo10010CfgLineSapiAccOtuEntry
	MAX-ACCESS not-accessible
	STATUS current
	DESCRIPTION
        "
        Row definition for the sapiAccLineOtu4 
        table
        "
	INDEX   { pmo10010CfgLineSapiAccOtuIndex }
	::= { pmo10010CfgLineSapiAccOtuTable 1 }


Pmo10010CfgLineSapiAccOtuEntry ::=
	SEQUENCE {
	pmo10010CfgLineSapiAccOtuIndex
		INTEGER,
	pmo10010CfgLineSapiAccSetupOtuPortn
		DisplayString
	}


pmo10010CfgLineSapiAccOtuIndex OBJECT-TYPE
	SYNTAX  INTEGER(0..128)
	MAX-ACCESS  read-only
	STATUS current
	DESCRIPTION
        "
        Index definition for the lineSapiAccOtu 
        table
        "
	::= { pmo10010CfgLineSapiAccOtuEntry 1 }


pmo10010CfgLineSapiAccSetupOtuPortn OBJECT-TYPE
	SYNTAX  DisplayString( SIZE(1..16))
	MAX-ACCESS read-write
	STATUS deprecated
	DESCRIPTION
        "
        OTU4 Line Accepted SAPI :This
         register defines the value of
         the accepted Trace Identifier
         on the line input
        "
	::= { pmo10010CfgLineSapiAccOtuEntry 3 }


--- *****************************************************
---     LEAF for the table Group dapiTxLineOtu4
--- *****************************************************

pmo10010CfgDapiTxLineOtu4 OBJECT IDENTIFIER ::= { pmo10010Config 18 }



--- *****************************************************
---     LEAF for the table 2B90
--- *****************************************************

pmo10010CfgLineDapiTxOtuTable OBJECT-TYPE
	SYNTAX  SEQUENCE OF Pmo10010CfgLineDapiTxOtuEntry
	MAX-ACCESS not-accessible
	STATUS current
	DESCRIPTION
        "
        List of  Article
        "
	::= { pmo10010CfgDapiTxLineOtu4 1 }


pmo10010CfgLineDapiTxOtuEntry OBJECT-TYPE
	SYNTAX Pmo10010CfgLineDapiTxOtuEntry
	MAX-ACCESS not-accessible
	STATUS current
	DESCRIPTION
        "
        Row definition for the dapiTxLineOtu4 
        table
        "
	INDEX   { pmo10010CfgLineDapiTxOtuIndex }
	::= { pmo10010CfgLineDapiTxOtuTable 1 }


Pmo10010CfgLineDapiTxOtuEntry ::=
	SEQUENCE {
	pmo10010CfgLineDapiTxOtuIndex
		INTEGER,
	pmo10010CfgLineDapiTxSetupOtuPortn
		DisplayString
	}


pmo10010CfgLineDapiTxOtuIndex OBJECT-TYPE
	SYNTAX  INTEGER(0..128)
	MAX-ACCESS  read-only
	STATUS current
	DESCRIPTION
        "
        Index definition for the lineDapiTxOtu 
        table
        "
	::= { pmo10010CfgLineDapiTxOtuEntry 1 }


pmo10010CfgLineDapiTxSetupOtuPortn OBJECT-TYPE
	SYNTAX  DisplayString( SIZE(1..16))
	MAX-ACCESS read-write
	STATUS current
	DESCRIPTION
        "
        OTU4 Line Transmitted DAPI :This 
        register defines the value of the 
        transmitted Trace Identifier on 
        the line output
        "
	::= { pmo10010CfgLineDapiTxOtuEntry 3 }


--- *****************************************************
---     LEAF for the table Group dapiExpLineOtu4
--- *****************************************************

pmo10010CfgDapiExpLineOtu4 OBJECT IDENTIFIER ::= { pmo10010Config 19 }



--- *****************************************************
---     LEAF for the table 2BB0
--- *****************************************************

pmo10010CfgLineDapiExpOtuTable OBJECT-TYPE
	SYNTAX  SEQUENCE OF Pmo10010CfgLineDapiExpOtuEntry
	MAX-ACCESS not-accessible
	STATUS current
	DESCRIPTION
        "
        List of  Article
        "
	::= { pmo10010CfgDapiExpLineOtu4 1 }


pmo10010CfgLineDapiExpOtuEntry OBJECT-TYPE
	SYNTAX Pmo10010CfgLineDapiExpOtuEntry
	MAX-ACCESS not-accessible
	STATUS current
	DESCRIPTION
        "
        Row definition for the dapiExpLineOtu4 
        table
        "
	INDEX   { pmo10010CfgLineDapiExpOtuIndex }
	::= { pmo10010CfgLineDapiExpOtuTable 1 }


Pmo10010CfgLineDapiExpOtuEntry ::=
	SEQUENCE {
	pmo10010CfgLineDapiExpOtuIndex
		INTEGER,
	pmo10010CfgLineDapiExpSetupOtuPortn
		DisplayString
	}


pmo10010CfgLineDapiExpOtuIndex OBJECT-TYPE
	SYNTAX  INTEGER(0..128)
	MAX-ACCESS  read-only
	STATUS current
	DESCRIPTION
        "
        Index definition for the lineDapiExpOtu 
        table
        "
	::= { pmo10010CfgLineDapiExpOtuEntry 1 }


pmo10010CfgLineDapiExpSetupOtuPortn OBJECT-TYPE
	SYNTAX  DisplayString( SIZE(1..16))
	MAX-ACCESS read-write
	STATUS current
	DESCRIPTION
        "
        OTU4 Line Expected DAPI :This
         register defines the value of
         the expected Trace Identifier
         on the line input
        "
	::= { pmo10010CfgLineDapiExpOtuEntry 3 }


--- *****************************************************
---     LEAF for the table Group dapiAccLineOtu4
--- *****************************************************

pmo10010CfgDapiAccLineOtu4 OBJECT IDENTIFIER ::= { pmo10010Config 20 }



--- *****************************************************
---     LEAF for the table 2BD0
--- *****************************************************

pmo10010CfgLineDapiAccOtuTable OBJECT-TYPE
	SYNTAX  SEQUENCE OF Pmo10010CfgLineDapiAccOtuEntry
	MAX-ACCESS not-accessible
	STATUS current
	DESCRIPTION
        "
        List of  Article
        "
	::= { pmo10010CfgDapiAccLineOtu4 1 }


pmo10010CfgLineDapiAccOtuEntry OBJECT-TYPE
	SYNTAX Pmo10010CfgLineDapiAccOtuEntry
	MAX-ACCESS not-accessible
	STATUS current
	DESCRIPTION
        "
        Row definition for the dapiAccLineOtu4 
        table
        "
	INDEX   { pmo10010CfgLineDapiAccOtuIndex }
	::= { pmo10010CfgLineDapiAccOtuTable 1 }


Pmo10010CfgLineDapiAccOtuEntry ::=
	SEQUENCE {
	pmo10010CfgLineDapiAccOtuIndex
		INTEGER,
	pmo10010CfgLineDapiAccSetupOtuPortn
		DisplayString
	}


pmo10010CfgLineDapiAccOtuIndex OBJECT-TYPE
	SYNTAX  INTEGER(0..128)
	MAX-ACCESS  read-only
	STATUS current
	DESCRIPTION
        "
        Index definition for the lineDapiAccOtu 
        table
        "
	::= { pmo10010CfgLineDapiAccOtuEntry 1 }


pmo10010CfgLineDapiAccSetupOtuPortn OBJECT-TYPE
	SYNTAX  DisplayString( SIZE(1..16))
	MAX-ACCESS read-write
	STATUS deprecated
	DESCRIPTION
        "
        OTU4 Line Accepted DAPI :This
         register defines the value of
         the accepted Trace Identifier
         on the line input
        "
	::= { pmo10010CfgLineDapiAccOtuEntry 3 }


--- *****************************************************
---     LEAF for the table Group sapiTxLineOdu4
--- *****************************************************

pmo10010CfgSapiTxLineOdu4 OBJECT IDENTIFIER ::= { pmo10010Config 21 }



--- *****************************************************
---     LEAF for the table 2B24
--- *****************************************************

pmo10010CfgLineSapiTxOduTable OBJECT-TYPE
	SYNTAX  SEQUENCE OF Pmo10010CfgLineSapiTxOduEntry
	MAX-ACCESS not-accessible
	STATUS current
	DESCRIPTION
        "
        List of  Article
        "
	::= { pmo10010CfgSapiTxLineOdu4 1 }


pmo10010CfgLineSapiTxOduEntry OBJECT-TYPE
	SYNTAX Pmo10010CfgLineSapiTxOduEntry
	MAX-ACCESS not-accessible
	STATUS current
	DESCRIPTION
        "
        Row definition for the sapiTxLineOdu4 
        table
        "
	INDEX   { pmo10010CfgLineSapiTxOduIndex }
	::= { pmo10010CfgLineSapiTxOduTable 1 }


Pmo10010CfgLineSapiTxOduEntry ::=
	SEQUENCE {
	pmo10010CfgLineSapiTxOduIndex
		INTEGER,
	pmo10010CfgLineSapiTxSetupOduPortn
		DisplayString
	}


pmo10010CfgLineSapiTxOduIndex OBJECT-TYPE
	SYNTAX  INTEGER(0..128)
	MAX-ACCESS  read-only
	STATUS current
	DESCRIPTION
        "
        Index definition for the lineSapiTxOdu 
        table
        "
	::= { pmo10010CfgLineSapiTxOduEntry 1 }


pmo10010CfgLineSapiTxSetupOduPortn OBJECT-TYPE
	SYNTAX  DisplayString( SIZE(1..16))
	MAX-ACCESS read-write
	STATUS current
	DESCRIPTION
        "
        ODU4 Line Transmitted SAPI :This 
        register defines the value of the 
        transmitted Trace Identifier on 
        the line output
        "
	::= { pmo10010CfgLineSapiTxOduEntry 3 }


--- *****************************************************
---     LEAF for the table Group sapiExpLineOdu4
--- *****************************************************

pmo10010CfgSapiExpLineOdu4 OBJECT IDENTIFIER ::= { pmo10010Config 22 }



--- *****************************************************
---     LEAF for the table 2B44
--- *****************************************************

pmo10010CfgLineSapiExpOduTable OBJECT-TYPE
	SYNTAX  SEQUENCE OF Pmo10010CfgLineSapiExpOduEntry
	MAX-ACCESS not-accessible
	STATUS current
	DESCRIPTION
        "
        List of  Article
        "
	::= { pmo10010CfgSapiExpLineOdu4 1 }


pmo10010CfgLineSapiExpOduEntry OBJECT-TYPE
	SYNTAX Pmo10010CfgLineSapiExpOduEntry
	MAX-ACCESS not-accessible
	STATUS current
	DESCRIPTION
        "
        Row definition for the sapiExpLineOdu4 
        table
        "
	INDEX   { pmo10010CfgLineSapiExpOduIndex }
	::= { pmo10010CfgLineSapiExpOduTable 1 }


Pmo10010CfgLineSapiExpOduEntry ::=
	SEQUENCE {
	pmo10010CfgLineSapiExpOduIndex
		INTEGER,
	pmo10010CfgLineSapiExpSetupOduPortn
		DisplayString
	}


pmo10010CfgLineSapiExpOduIndex OBJECT-TYPE
	SYNTAX  INTEGER(0..128)
	MAX-ACCESS  read-only
	STATUS current
	DESCRIPTION
        "
        Index definition for the lineSapiExpOdu 
        table
        "
	::= { pmo10010CfgLineSapiExpOduEntry 1 }


pmo10010CfgLineSapiExpSetupOduPortn OBJECT-TYPE
	SYNTAX  DisplayString( SIZE(1..16))
	MAX-ACCESS read-write
	STATUS current
	DESCRIPTION
        "
        ODU4 Line Expected SAPI :This
         register defines the value of
         the expected Trace Identifier
         on the line input
        "
	::= { pmo10010CfgLineSapiExpOduEntry 3 }


--- *****************************************************
---     LEAF for the table Group sapiAccLineOdu4
--- *****************************************************

pmo10010CfgSapiAccLineOdu4 OBJECT IDENTIFIER ::= { pmo10010Config 23 }



--- *****************************************************
---     LEAF for the table 2B64
--- *****************************************************

pmo10010CfgLineSapiAccOduTable OBJECT-TYPE
	SYNTAX  SEQUENCE OF Pmo10010CfgLineSapiAccOduEntry
	MAX-ACCESS not-accessible
	STATUS current
	DESCRIPTION
        "
        List of  Article
        "
	::= { pmo10010CfgSapiAccLineOdu4 1 }


pmo10010CfgLineSapiAccOduEntry OBJECT-TYPE
	SYNTAX Pmo10010CfgLineSapiAccOduEntry
	MAX-ACCESS not-accessible
	STATUS current
	DESCRIPTION
        "
        Row definition for the sapiAccLineOdu4 
        table
        "
	INDEX   { pmo10010CfgLineSapiAccOduIndex }
	::= { pmo10010CfgLineSapiAccOduTable 1 }


Pmo10010CfgLineSapiAccOduEntry ::=
	SEQUENCE {
	pmo10010CfgLineSapiAccOduIndex
		INTEGER,
	pmo10010CfgLineSapiAccSetupOduPortn
		DisplayString
	}


pmo10010CfgLineSapiAccOduIndex OBJECT-TYPE
	SYNTAX  INTEGER(0..128)
	MAX-ACCESS  read-only
	STATUS current
	DESCRIPTION
        "
        Index definition for the lineSapiAccOdu 
        table
        "
	::= { pmo10010CfgLineSapiAccOduEntry 1 }


pmo10010CfgLineSapiAccSetupOduPortn OBJECT-TYPE
	SYNTAX  DisplayString( SIZE(1..16))
	MAX-ACCESS read-write
	STATUS deprecated
	DESCRIPTION
        "
        ODU4 Line Accepted SAPI :This
         register defines the value of
         the accepted Trace Identifier
         on the line input
        "
	::= { pmo10010CfgLineSapiAccOduEntry 3 }


--- *****************************************************
---     LEAF for the table Group dapiTxLineOdu4
--- *****************************************************

pmo10010CfgDapiTxLineOdu4 OBJECT IDENTIFIER ::= { pmo10010Config 24 }



--- *****************************************************
---     LEAF for the table 2BA4
--- *****************************************************

pmo10010CfgLineDapiTxOduTable OBJECT-TYPE
	SYNTAX  SEQUENCE OF Pmo10010CfgLineDapiTxOduEntry
	MAX-ACCESS not-accessible
	STATUS current
	DESCRIPTION
        "
        List of  Article
        "
	::= { pmo10010CfgDapiTxLineOdu4 1 }


pmo10010CfgLineDapiTxOduEntry OBJECT-TYPE
	SYNTAX Pmo10010CfgLineDapiTxOduEntry
	MAX-ACCESS not-accessible
	STATUS current
	DESCRIPTION
        "
        Row definition for the dapiTxLineOdu4 
        table
        "
	INDEX   { pmo10010CfgLineDapiTxOduIndex }
	::= { pmo10010CfgLineDapiTxOduTable 1 }


Pmo10010CfgLineDapiTxOduEntry ::=
	SEQUENCE {
	pmo10010CfgLineDapiTxOduIndex
		INTEGER,
	pmo10010CfgLineDapiTxSetupOduPortn
		DisplayString
	}


pmo10010CfgLineDapiTxOduIndex OBJECT-TYPE
	SYNTAX  INTEGER(0..128)
	MAX-ACCESS  read-only
	STATUS current
	DESCRIPTION
        "
        Index definition for the lineDapiTxOdu 
        table
        "
	::= { pmo10010CfgLineDapiTxOduEntry 1 }


pmo10010CfgLineDapiTxSetupOduPortn OBJECT-TYPE
	SYNTAX  DisplayString( SIZE(1..16))
	MAX-ACCESS read-write
	STATUS current
	DESCRIPTION
        "
        ODU4 Line Transmitted DAPI :This 
        register defines the value of the 
        transmitted Trace Identifier on 
        the line output
        "
	::= { pmo10010CfgLineDapiTxOduEntry 3 }


--- *****************************************************
---     LEAF for the table Group dapiExpLineOdu4
--- *****************************************************

pmo10010CfgDapiExpLineOdu4 OBJECT IDENTIFIER ::= { pmo10010Config 25 }



--- *****************************************************
---     LEAF for the table 2BC4
--- *****************************************************

pmo10010CfgLineDapiExpOduTable OBJECT-TYPE
	SYNTAX  SEQUENCE OF Pmo10010CfgLineDapiExpOduEntry
	MAX-ACCESS not-accessible
	STATUS current
	DESCRIPTION
        "
        List of  Article
        "
	::= { pmo10010CfgDapiExpLineOdu4 1 }


pmo10010CfgLineDapiExpOduEntry OBJECT-TYPE
	SYNTAX Pmo10010CfgLineDapiExpOduEntry
	MAX-ACCESS not-accessible
	STATUS current
	DESCRIPTION
        "
        Row definition for the dapiExpLineOdu4 
        table
        "
	INDEX   { pmo10010CfgLineDapiExpOduIndex }
	::= { pmo10010CfgLineDapiExpOduTable 1 }


Pmo10010CfgLineDapiExpOduEntry ::=
	SEQUENCE {
	pmo10010CfgLineDapiExpOduIndex
		INTEGER,
	pmo10010CfgLineDapiExpSetupOduPortn
		DisplayString
	}


pmo10010CfgLineDapiExpOduIndex OBJECT-TYPE
	SYNTAX  INTEGER(0..128)
	MAX-ACCESS  read-only
	STATUS current
	DESCRIPTION
        "
        Index definition for the lineDapiExpOdu 
        table
        "
	::= { pmo10010CfgLineDapiExpOduEntry 1 }


pmo10010CfgLineDapiExpSetupOduPortn OBJECT-TYPE
	SYNTAX  DisplayString( SIZE(1..16))
	MAX-ACCESS read-write
	STATUS current
	DESCRIPTION
        "
        ODU4 Line Expected DAPI :This
         register defines the value of
         the expected Trace Identifier
         on the line input
        "
	::= { pmo10010CfgLineDapiExpOduEntry 3 }


--- *****************************************************
---     LEAF for the table Group dapiAccLineOdu4
--- *****************************************************

pmo10010CfgDapiAccLineOdu4 OBJECT IDENTIFIER ::= { pmo10010Config 26 }



--- *****************************************************
---     LEAF for the table 2BE4
--- *****************************************************

pmo10010CfgLineDapiAccOduTable OBJECT-TYPE
	SYNTAX  SEQUENCE OF Pmo10010CfgLineDapiAccOduEntry
	MAX-ACCESS not-accessible
	STATUS current
	DESCRIPTION
        "
        List of  Article
        "
	::= { pmo10010CfgDapiAccLineOdu4 1 }


pmo10010CfgLineDapiAccOduEntry OBJECT-TYPE
	SYNTAX Pmo10010CfgLineDapiAccOduEntry
	MAX-ACCESS not-accessible
	STATUS current
	DESCRIPTION
        "
        Row definition for the dapiAccLineOdu4 
        table
        "
	INDEX   { pmo10010CfgLineDapiAccOduIndex }
	::= { pmo10010CfgLineDapiAccOduTable 1 }


Pmo10010CfgLineDapiAccOduEntry ::=
	SEQUENCE {
	pmo10010CfgLineDapiAccOduIndex
		INTEGER,
	pmo10010CfgLineDapiAccSetupOduPortn
		DisplayString
	}


pmo10010CfgLineDapiAccOduIndex OBJECT-TYPE
	SYNTAX  INTEGER(0..128)
	MAX-ACCESS  read-only
	STATUS current
	DESCRIPTION
        "
        Index definition for the lineDapiAccOdu 
        table
        "
	::= { pmo10010CfgLineDapiAccOduEntry 1 }


pmo10010CfgLineDapiAccSetupOduPortn OBJECT-TYPE
	SYNTAX  DisplayString( SIZE(1..16))
	MAX-ACCESS read-write
	STATUS deprecated
	DESCRIPTION
        "
        ODU4 Line Accepted DAPI :This
         register defines the value of
         the accepted Trace Identifier
         on the line input
        "
	::= { pmo10010CfgLineDapiAccOduEntry 3 }


--- *****************************************************
---     LEAF for the table Group startuptablefive
--- *****************************************************

pmo10010CfgStartuptablefive OBJECT IDENTIFIER ::= { pmo10010Config 27 }



--- *****************************************************
---     LEAF for the table 0005
--- *****************************************************

pmo10010CfgOtxtlhcapabilitiesTable OBJECT-TYPE
	SYNTAX  SEQUENCE OF Pmo10010CfgOtxtlhcapabilitiesEntry
	MAX-ACCESS not-accessible
	STATUS current
	DESCRIPTION
        "
        List of  Article
        "
	::= { pmo10010CfgStartuptablefive 1 }


pmo10010CfgOtxtlhcapabilitiesEntry OBJECT-TYPE
	SYNTAX Pmo10010CfgOtxtlhcapabilitiesEntry
	MAX-ACCESS not-accessible
	STATUS current
	DESCRIPTION
        "
        Row definition for the startuptablefive 
        table
        "
	INDEX   { pmo10010CfgOtxtlhcapabilitiesIndex }
	::= { pmo10010CfgOtxtlhcapabilitiesTable 1 }


Pmo10010CfgOtxtlhcapabilitiesEntry ::=
	SEQUENCE {
	pmo10010CfgOtxtlhcapabilitiesIndex
		INTEGER,
	pmo10010CfgComponentTypePortn
		Unsigned32,
	pmo10010CfgMiscellaneousPortn
		Unsigned32,
	pmo10010CfgFirstChannelPortn
		Unsigned32,
	pmo10010CfgLastChannelPortn
		Unsigned32,
	pmo10010CfgGridPortn
		Unsigned32
	}


pmo10010CfgOtxtlhcapabilitiesIndex OBJECT-TYPE
	SYNTAX  INTEGER(0..128)
	MAX-ACCESS  read-only
	STATUS current
	DESCRIPTION
        "
        Index definition for the otxtlhcapabilities 
        table
        "
	::= { pmo10010CfgOtxtlhcapabilitiesEntry 1 }


pmo10010CfgComponentTypePortn OBJECT-TYPE
	SYNTAX  Unsigned32 (0..65536)
	MAX-ACCESS read-only
	STATUS current
	DESCRIPTION
        "
        Component parameters :This OID 
        defines the component parameters
        "
	::= { pmo10010CfgOtxtlhcapabilitiesEntry 3 }


pmo10010CfgMiscellaneousPortn OBJECT-TYPE
	SYNTAX  Unsigned32 (0..65536)
	MAX-ACCESS read-only
	STATUS current
	DESCRIPTION
        "
        Miscellaneous default settings 
        :This OID defines the miscellaneous 
        parameters
        "
	::= { pmo10010CfgOtxtlhcapabilitiesEntry 4 }


pmo10010CfgFirstChannelPortn OBJECT-TYPE
	SYNTAX  Unsigned32 (0..65536)
	MAX-ACCESS read-only
	STATUS current
	DESCRIPTION
        "
        Number of the first channel of 
        the component :This OID defines 
        the first channel number of the 
        PM
        "
	::= { pmo10010CfgOtxtlhcapabilitiesEntry 5 }


pmo10010CfgLastChannelPortn OBJECT-TYPE
	SYNTAX  Unsigned32 (0..65536)
	MAX-ACCESS read-only
	STATUS current
	DESCRIPTION
        "
        Number of the last channel of
         the component :This OID defines 
        the last channel number of the
         PM
        "
	::= { pmo10010CfgOtxtlhcapabilitiesEntry 6 }


pmo10010CfgGridPortn OBJECT-TYPE
	SYNTAX  Unsigned32 (0..65536)
	MAX-ACCESS read-only
	STATUS current
	DESCRIPTION
        "
        Grid value of the component :This 
        OID defines the grid of the PM
        "
	::= { pmo10010CfgOtxtlhcapabilitiesEntry 7 }



pmo10010CfgWriteConfiguration  OBJECT-TYPE
	SYNTAX EkiOnOff
	MAX-ACCESS read-write
	STATUS current
	DESCRIPTION
	"Write configuration to module:This OID 
	 writes the complete configuration to the module"
	::= { pmo10010Config 257 }






--- *****************************************************
---     TRAP OBJECTS
--- *****************************************************

pmo10010trapPortNumber OBJECT-TYPE
	SYNTAX INTEGER(1..64)
	MAX-ACCESS read-only
	STATUS current
	DESCRIPTION
	"Last port which generates a trap"
	::= { pmo10010traps 2 }

pmo10010trapLineNumber OBJECT-TYPE
	SYNTAX INTEGER(1..64)
	MAX-ACCESS read-only
	STATUS current
	DESCRIPTION
	"Last Line which generates a trap"
	::= { pmo10010traps 3 }

pmo10010trapBoardNumber OBJECT-TYPE
	SYNTAX INTEGER(1..64)
	MAX-ACCESS read-only
	STATUS current
	DESCRIPTION
	"Last module which generates a trap"
	::= { pmo10010traps 4 }







--- *****************************************************
---     LINE TRAPS
--- *****************************************************

pmo10010LineTrapNotUrgentGoesOn NOTIFICATION-TYPE
	OBJECTS {pmo10010AlmLineDdmWarningPortn, pmo10010trapLineNumber, pmo10010trapBoardNumber}
	STATUS current
	--&FILTNAME    "PMO10010 Line Not Urgent ON"
	--&ACTIONS     { log, minor }
	--&MATCH       { pmo10010AlmLineDdmWarningPortn "on", pmo10010trapLineNumber "$2", pmo10010trapBoardNumber "$3"}
	--&MESG        "DDM Warning appears on Line Port $2 of PMO10010 in Slot $3 ($A)"
	DESCRIPTION "Not urgent Line default is activated"
	::= { pmo10010traps 30 }

pmo10010LineTrapNotUrgentGoesOff NOTIFICATION-TYPE
	OBJECTS {pmo10010AlmLineDdmWarningPortn, pmo10010trapLineNumber, pmo10010trapBoardNumber}
	STATUS current
	--&FILTNAME    "PMO10010 Line Not Urgent OFF"
	--&ACTIONS     { log, normal }
	--&CLEARS      { "PMO10010 Line Not Urgent ON" }
	--&MATCH       { pmo10010AlmLineDdmWarningPortn "on", pmo10010trapLineNumber "$2", pmo10010trapBoardNumber "$3"}
	--&MESG        "DDM Warning disappears on Line Port $2 of PMO10010 in Slot $3 ($A)"
	DESCRIPTION "Not urgent Line default disappeared"
	::= { pmo10010traps 31 }

pmo10010LineTrapUrgentGoesOn NOTIFICATION-TYPE
	OBJECTS {pmo10010AlmLineDdmAlmPortn, pmo10010trapLineNumber, pmo10010trapBoardNumber}
	STATUS current
	--&FILTNAME    "PMO10010 Line Urgent ON"
	--&ACTIONS     { log, major }
	--&MATCH       { pmo10010AlmLineDdmAlmPortn "on", pmo10010trapLineNumber "$2", pmo10010trapBoardNumber "$3"}
	--&MESG        "DDM Alarm appears on Line Port $2 of PMO10010 in Slot $3 ($A)"
	DESCRIPTION "Urgent Line default is activated"
	::= { pmo10010traps 32 }

pmo10010LineTrapUrgentGoesOff NOTIFICATION-TYPE
	OBJECTS {pmo10010AlmLineDdmAlmPortn, pmo10010trapLineNumber, pmo10010trapBoardNumber}
	STATUS current
	--&FILTNAME    "PMO10010 Line Urgent OFF"
	--&ACTIONS     { log, normal }
	--&CLEARS      { "PMO10010 Line Urgent ON" }
	--&MATCH       { pmo10010AlmLineDdmAlmPortn "on", pmo10010trapLineNumber "$2", pmo10010trapBoardNumber "$3"}
	--&MESG        "DDM Alarm disappears on Line Port $2 of PMO10010 in Slot $3 ($A)"
	DESCRIPTION "Urgent Line default disappeared"
	::= { pmo10010traps 33 }

pmo10010LineTrapCritGoesOn NOTIFICATION-TYPE
	OBJECTS {pmo10010AlmLineFailPortn , pmo10010AlmLineHwFailPortn , pmo10010trapLineNumber, pmo10010trapBoardNumber}
	STATUS current
	--&FILTNAME    "PMO10010 Line Fail ON"
	--&ACTIONS     { log, critical }
	--&MATCH       { pmo10010AlmLineFailPortn "on", pmo10010AlmLineHwFailPortn "*", pmo10010trapLineNumber "$3", pmo10010trapBoardNumber "$4"}
	--&MESG        "Line Port $3 Down on PMO10010 in Slot $4 ($A)"
	
	--&FILTNAME    "PMO10010 Line HW Fail ON (Hidden)"
	--&ACTIONS     { info }
	--&MATCH       { pmo10010AlmLineFailPortn "*", pmo10010AlmLineHwFailPortn "on", pmo10010trapLineNumber "$3", pmo10010trapBoardNumber "$4"}
	--&MESG        "Line Port $3 Down on PMO10010 in Slot $4 ($A)"
	DESCRIPTION "Critical Line default is activated"
	::= { pmo10010traps 34 }

pmo10010LineTrapCritGoesOff NOTIFICATION-TYPE
	OBJECTS {pmo10010AlmLineFailPortn , pmo10010AlmLineHwFailPortn , pmo10010trapLineNumber, pmo10010trapBoardNumber}
	STATUS current
	--&FILTNAME    "PMO10010 Line Fail OFF"
	--&ACTIONS     { log,  normal }
	--&CLEARS      { "PMO10010 Line Fail ON" }
	--&MATCH       { pmo10010AlmLineFailPortn "on", pmo10010AlmLineHwFailPortn "*", pmo10010trapLineNumber "$3", pmo10010trapBoardNumber "$4"}
	--&MESG        "Line Port $3 Up on PMO10010 in Slot $4 ($A)"

	--&FILTNAME    "PMO10010 Line HW Fail OFF (Hidden)"
	--&ACTIONS     { info }
	--&MATCH       { pmo10010AlmLineFailPortn "*", pmo10010AlmLineHwFailPortn "on", pmo10010trapLineNumber "$3", pmo10010trapBoardNumber "$4"}
	--&MESG        "Line Port $3 Up on PMO10010 in Slot $4 ($A)"
	DESCRIPTION "Critical Line default disappeared"
	::= { pmo10010traps 35 }






--- *****************************************************
---     CLIENT TRAPS
--- *****************************************************

pmo10010ClientTrapNotUrgentGoesOn NOTIFICATION-TYPE
	OBJECTS {pmo10010AlmSfpDdmWarningPortn, pmo10010trapPortNumber, pmo10010trapBoardNumber}
	STATUS current
		--&FILTNAME    "PMO10010 Client Not Urgent ON"
		--&ACTIONS     { log, minor }
		--&MATCH       { pmo10010AlmSfpDdmWarningPortn "on", pmo10010trapPortNumber "$2", pmo10010trapBoardNumber "$3"}
		--&MESG        "DDM Warning appears on Client Port $2 of PMO10010 in Slot $3 ($A)"
	DESCRIPTION "Not urgent client default is activated"
	::= { pmo10010traps 40 }

pmo10010ClientTrapNotUrgentGoesOff NOTIFICATION-TYPE
	OBJECTS {pmo10010AlmSfpDdmWarningPortn, pmo10010trapPortNumber, pmo10010trapBoardNumber}
	STATUS current
		--&FILTNAME    "PMO10010 Client Not Urgent OFF"
		--&ACTIONS     { log, normal }
		--&CLEARS      { "PMO10010 Client Not Urgent ON" }
		--&MATCH       { pmo10010AlmSfpDdmWarningPortn "on", pmo10010trapPortNumber "$2", pmo10010trapBoardNumber "$3"}
		--&MESG        "DDM Warning appears on Client Port $2 of PMO10010 in Slot $3 ($A)"
	DESCRIPTION "Not urgent client default disappeared"
	::= { pmo10010traps 41 }

pmo10010ClientTrapUrgentGoesOn NOTIFICATION-TYPE
	OBJECTS {pmo10010AlmSfpDdmAlmPortn, pmo10010trapPortNumber, pmo10010trapBoardNumber}
	STATUS current
		--&FILTNAME    "PMO10010 Client Urgent ON"
		--&ACTIONS     { log, major }
		--&MATCH       { pmo10010AlmSfpDdmAlmPortn "on", pmo10010trapPortNumber "$2", pmo10010trapBoardNumber "$3"}
		--&MESG        "DDM Alarm appears on Client Port $2 of PMO10010 in Slot $3 ($A)"
	DESCRIPTION "Urgent client default is activated"
	::= { pmo10010traps 42 }

pmo10010ClientTrapUrgentGoesOff NOTIFICATION-TYPE
	OBJECTS {pmo10010AlmSfpDdmAlmPortn, pmo10010trapPortNumber, pmo10010trapBoardNumber}
	STATUS current
		--&FILTNAME    "PMO10010 Client Urgent OFF"
		--&ACTIONS     { log, normal }
		--&CLEARS      { "PMO10010 Client Urgent ON" }
		--&MATCH       { pmo10010AlmSfpDdmAlmPortn "on", pmo10010trapPortNumber "$2", pmo10010trapBoardNumber "$3"}
		--&MESG        "DDM Alarm disappears on Client Port $2 of PMO10010 in Slot $3 ($A)"
	DESCRIPTION "Urgent client default disappeared"
	::= { pmo10010traps 43 }

pmo10010ClientTrapCritGoesOn NOTIFICATION-TYPE
	OBJECTS {pmo10010AlmFailAccPortn, pmo10010AlmHwFailAccPortn, pmo10010trapPortNumber, pmo10010trapBoardNumber}
	STATUS current
		--&FILTNAME    "PMO10010 Client Fail ON"
		--&ACTIONS     { log, critical }
		--&MATCH       { pmo10010AlmFailAccPortn "on", pmo10010AlmHwFailAccPortn "*", pmo10010trapPortNumber "$3", pmo10010trapBoardNumber "$4"}
		--&MESG        "Client Port $3 Down on PMO10010 in Slot $4 ($A)"
		
		--&FILTNAME    "PMO10010 Client HW Fail ON (Hidden)"
		--&ACTIONS     { info }
		--&MATCH       { pmo10010AlmFailAccPortn "*", pmo10010AlmHwFailAccPortn "on", pmo10010trapPortNumber "$3", pmo10010trapBoardNumber "$4"}
		--&MESG        "Client Port $3 Down on PMO10010 in Slot $4 ($A)"
	DESCRIPTION "Critical client default is activated"
	::= { pmo10010traps 44 }

pmo10010ClientTrapCritGoesOff NOTIFICATION-TYPE
	OBJECTS {pmo10010AlmFailAccPortn, pmo10010AlmHwFailAccPortn, pmo10010trapPortNumber, pmo10010trapBoardNumber}
	STATUS current
		--&FILTNAME    "PMO10010 Client Fail OFF"
		--&ACTIONS     { log, normal }
		--&CLEARS      { "PMO10010 Client Fail ON" }
		--&MATCH       { pmo10010AlmFailAccPortn "on", pmo10010AlmHwFailAccPortn "*", pmo10010trapPortNumber "$3", pmo10010trapBoardNumber "$4"}
		--&MESG        "Client Port $3 Up on PMO10010 in Slot $4 ($A)"
		
		--&FILTNAME    "PMO10010 Client HW Fail OFF (Hidden)"
		--&ACTIONS     { info }
		--&MATCH       { pmo10010AlmFailAccPortn "*", pmo10010AlmHwFailAccPortn "on", pmo10010trapPortNumber "$3", pmo10010trapBoardNumber "$4"}
		--&MESG        "Client Port $3 Up on PMO10010 in Slot $4 ($A)"
	DESCRIPTION "Critical client default disappeared"
	::= { pmo10010traps 45 }






--- *****************************************************
---     HW TRAPS
--- *****************************************************

pmo10010PowerTrapUrgentGoesOn NOTIFICATION-TYPE
	OBJECTS {pmo10010AlmDefFuseB, pmo10010AlmDefFuseA , pmo10010trapBoardNumber}
	STATUS current
		--&FILTNAME    "PMO10010 Fuse A Fail ON"
		--&ACTIONS     { log, major }
		--&MATCH       { pmo10010AlmDefFuseB "*", pmo10010AlmDefFuseA "on", pmo10010trapBoardNumber "$3"}
		--&MESG        "Power Input A Fail on PMO10010 in Slot $3 ($A)"
	
		--&FILTNAME    "PMO10010 Fuse B Fail ON"
		--&ACTIONS     { log, major }
		--&MATCH       { pmo10010AlmDefFuseB "on", pmo10010AlmDefFuseA "*", pmo10010trapBoardNumber "$3"}
		--&MESG        "Power Input B Fail on PMO10010 in Slot $3 ($A)"
	DESCRIPTION "Urgent power supply default is activated"
	::= { pmo10010traps 50 }

pmo10010PowerTrapUrgentGoesOff NOTIFICATION-TYPE
	OBJECTS {pmo10010AlmDefFuseB, pmo10010AlmDefFuseA , pmo10010trapBoardNumber}
	STATUS current
		--&FILTNAME    "PMO10010 Fuse A&B Fail OFF"
		--&ACTIONS     { log, normal}
		--&CLEARS      { "PMO10010 Fuse A Fail ON", "PMO10010 Fuse B Fail ON" }
		--&MATCH       { pmo10010AlmDefFuseB "on", pmo10010AlmDefFuseA "on", pmo10010trapBoardNumber "$3"}
		--&MESG        "Power Inputs A and B Present on PMO10010 in Slot $3 ($A)"
	DESCRIPTION "Urgent power supply default disappeared"
	::= { pmo10010traps 51 }






END
