-- *****************************************************************
-- EKINOPS-Pmc1008MP.TXT:  MIB
--
--MIB Part Number:3MI00024ADAF
--MIB Version:02
--
-- Copyright (c) 2016 by Ekinops
-- All rights reserved.
-- 
-- *****************************************************************

EKINOPS-Pmc1008MP-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePmc1008mp MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.net"
        DESCRIPTION
          "MIB for managing Ekinops modules with PM1008MP software"
	REVISION "201005250000Z"
	DESCRIPTION
	  "Création"
	REVISION "201011090000Z"
	DESCRIPTION
	  "Reset on Perf"
	REVISION "201101060000Z"
	DESCRIPTION
	  "Formulas and Event on XFP init"
	REVISION "201101130000Z"
	DESCRIPTION
	  "WB mode"
	REVISION "201207030000Z"
	DESCRIPTION
	  "Minor cosmetic updates"
	REVISION "201304030000Z"
	DESCRIPTION
	  "S1,K1,K2 suppress"
	REVISION "201403270000Z"
	DESCRIPTION
	  "Probcause,AlarmType - NMS completion"
	REVISION "201501140000Z"
	DESCRIPTION
	  "Add Loopback objects"
	REVISION "201501140000Z"
	DESCRIPTION
	  "Labels cosmetic updates"
	REVISION "201605190000Z"
	DESCRIPTION
	  "New AlarmType - synthesisAlarm(12)"
	REVISION "201606020000Z"
	DESCRIPTION
	  "Capabilities objects of Table 5"
        ::= { ekinops 47 }



--- *****************************************************
---     LEAF LEVEL 2
--- *****************************************************


pmc1008mpalarms OBJECT IDENTIFIER ::= { modulePmc1008mp 2 }	
pmc1008mpAlmOther OBJECT IDENTIFIER ::= { pmc1008mpalarms 1 }
pmc1008mpAlmOtherNurg OBJECT IDENTIFIER ::= { pmc1008mpAlmOther 1 }
pmc1008mpAlmOtherUrg OBJECT IDENTIFIER ::= { pmc1008mpAlmOther 2 }
pmc1008mpAlmOtherCrit OBJECT IDENTIFIER ::= { pmc1008mpAlmOther 3 }

pmc1008mpAlmClient OBJECT IDENTIFIER ::= { pmc1008mpalarms 2 }
pmc1008mpAlmClientNurg OBJECT IDENTIFIER ::= { pmc1008mpAlmClient 1 }
pmc1008mpAlmClientUrg OBJECT IDENTIFIER ::= { pmc1008mpAlmClient 2 }
pmc1008mpAlmClientCrit OBJECT IDENTIFIER ::= { pmc1008mpAlmClient 3 }
	
pmc1008mpAlmLine OBJECT IDENTIFIER ::= { pmc1008mpalarms 3 }
pmc1008mpAlmLineNurg OBJECT IDENTIFIER ::= { pmc1008mpAlmLine 1 }
pmc1008mpAlmLineUrg OBJECT IDENTIFIER ::= { pmc1008mpAlmLine 2 }
pmc1008mpAlmLineCrit OBJECT IDENTIFIER ::= { pmc1008mpAlmLine 3 }





pmc1008mpmeasures OBJECT IDENTIFIER ::= { modulePmc1008mp 3 }	
pmc1008mpMesrOther OBJECT IDENTIFIER ::= { pmc1008mpmeasures 1 }	
pmc1008mpMesrClient OBJECT IDENTIFIER ::= { pmc1008mpmeasures 2 }	
pmc1008mpMesrLine OBJECT IDENTIFIER ::= { pmc1008mpmeasures 3 }	




pmc1008mpcounters OBJECT IDENTIFIER ::= { modulePmc1008mp 4 }
pmc1008mpCntOther OBJECT IDENTIFIER ::= { pmc1008mpcounters 1 }
pmc1008mpCntClient OBJECT IDENTIFIER ::= { pmc1008mpcounters 2 }
pmc1008mpCntLine OBJECT IDENTIFIER ::= { pmc1008mpcounters 3 }


pmc1008mpcontrolsWrite OBJECT IDENTIFIER ::= { modulePmc1008mp 6 }
pmc1008mpCtrlOther OBJECT IDENTIFIER ::= { pmc1008mpcontrolsWrite 1 }
pmc1008mpCtrlClient OBJECT IDENTIFIER ::= { pmc1008mpcontrolsWrite 2 }
pmc1008mpCtrlLine OBJECT IDENTIFIER ::= { pmc1008mpcontrolsWrite 3 }

pmc1008mpri OBJECT IDENTIFIER ::= { modulePmc1008mp 7 }
pmc1008mpriTable OBJECT IDENTIFIER ::= { pmc1008mpri 1 }

pmc1008mpdownload OBJECT IDENTIFIER ::= { modulePmc1008mp 8 }
pmc1008mpDwlOther OBJECT IDENTIFIER ::= { pmc1008mpdownload 1 }
pmc1008mpDwlClient OBJECT IDENTIFIER ::= { pmc1008mpdownload 2 }
pmc1008mpDwlLine OBJECT IDENTIFIER ::= { pmc1008mpdownload 3 }


pmc1008mpConfig OBJECT IDENTIFIER ::= { modulePmc1008mp 9 }

pmc1008mptraps OBJECT IDENTIFIER ::= { modulePmc1008mp 10 }



pmc1008mpMonitoring OBJECT IDENTIFIER ::= { modulePmc1008mp 11}

pmc1008mpMonOther OBJECT IDENTIFIER ::= { pmc1008mpMonitoring 1 }
pmc1008mpMonSync OBJECT IDENTIFIER ::= { pmc1008mpMonOther 1 }
pmc1008mpMonTimeStamp OBJECT IDENTIFIER ::= { pmc1008mpMonOther 2 }

pmc1008mpMonRmon OBJECT IDENTIFIER ::= { pmc1008mpMonOther 3 }

pmc1008mpMonClient OBJECT IDENTIFIER ::= { pmc1008mpMonitoring 2 }
pmc1008mpMonClientRmonCounter OBJECT IDENTIFIER ::= { pmc1008mpMonClient 4 }
pmc1008mpMonLine OBJECT IDENTIFIER ::= { pmc1008mpMonitoring 3 }

--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pmc1008mpModeTimeSlot ::= TEXTUAL-CONVENTION
    STATUS      current
    DESCRIPTION "different mode for time slot"
    SYNTAX INTEGER {
		dualPassThrough(1),
		addDropTsA(2),
		addDropTsB(4),
		splitSelectTsA(8),
		splitSelectTsB(16),
		splitSelectTsATsB(32)
           }

Pmc1008mpModeAddDropA ::= TEXTUAL-CONVENTION
    STATUS      current
    DESCRIPTION "different mode for client A"
    SYNTAX INTEGER {
		passThroughA(1),
		addDropTsA(2),
		splitSelectTsA(4)
           }

Pmc1008mpModeAddDrop ::= TEXTUAL-CONVENTION
    STATUS      current
    DESCRIPTION "different mode for client B"
    SYNTAX INTEGER {
		dualPassThrough(1),
		addDropTsA(2),
		addDropTsB(4),
		splitSelectTsA(8),
		splitSelectTsB(16),
		splitSelectTsATsB(32)
           }


Pmc1008mpProtectionTimeSlot ::= TEXTUAL-CONVENTION
    STATUS      current
    DESCRIPTION "protection for control"
    SYNTAX INTEGER {
		auto(0),
		manualX1Line1(257),
		manualX2Line2(513)
           }

Pmc1008mpProtectionStartUp ::= TEXTUAL-CONVENTION
    STATUS      current
    DESCRIPTION "protection for startup"
    SYNTAX INTEGER {
		auto(2),
		manualX2Line2(0),
		manualX1Line1(1)
           }


Pmc1008mpDccMode ::= TEXTUAL-CONVENTION
    STATUS      current
    DESCRIPTION "Mode for DCC"
    SYNTAX INTEGER {
		dccNo(0),
		dcctermLine1(1),
		dcctermLine2(2),
		dcctermLines12(3),
		dccmaster(4),
		dccslaveLine12(7)
           }

Pmc1008mpOtxMode ::= TEXTUAL-CONVENTION
    STATUS      current
    DESCRIPTION "Different modes on OTX-TLH on client and line ports"
    SYNTAX INTEGER {
		otx80mode(1),
		otx60mode(2),
		otxadjustmode(4)
           }

Pmc1008mpOtxGrid ::= TEXTUAL-CONVENTION
    STATUS      current
    DESCRIPTION "Different grids on OTX-TLH on client and line ports"
    SYNTAX INTEGER {
		otxgrid200(200),
		otxgrid100(100),
		otxgrid50(50)
           }

Pmc1008mpAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pmc1008mpOtxChannel ::= TEXTUAL-CONVENTION
    STATUS      current
    DESCRIPTION "Channel selection on OTX-TLH on client and line ports"
    SYNTAX INTEGER 


--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pmc1008mpRinvReloadInventory OBJECT-TYPE
  SYNTAX EkiOnOff
  MAX-ACCESS read-write
  STATUS current
  DESCRIPTION
        "Reload the inventory: This OID triggers an 
         inventory reload."
  ::= { pmc1008mpri 2 }

pmc1008mpRinvHwPlatform OBJECT-TYPE
  SYNTAX DisplayString
  MAX-ACCESS read-only
  STATUS current
  DESCRIPTION
        "HW platform description: This OID contains the 
         description of the Hardware platform."
  ::= { pmc1008mpri 3 }
  
pmc1008mpRinvModulePlatform OBJECT-TYPE
  SYNTAX DisplayString
  MAX-ACCESS read-only
  STATUS current
  DESCRIPTION
        "Module platform description: This OID contains the 
         description of the Module."
  ::= { pmc1008mpri 4 }
  
pmc1008mpRinvSwPlatform OBJECT-TYPE
  SYNTAX DisplayString
  MAX-ACCESS read-only
  STATUS current
  DESCRIPTION
        "SW platform description: This OID contains the 
         description of the Software platform."
  ::= { pmc1008mpri 5 }
  
pmc1008mpRinvGwPlatform OBJECT-TYPE
  SYNTAX DisplayString
  MAX-ACCESS read-only
  STATUS current
  DESCRIPTION
        "GW platform desciption: This OID contains the 
         description of the Gateware platform."
  ::= { pmc1008mpri 6 }


pmc1008mpRinvSfpTable OBJECT-TYPE
      SYNTAX  SEQUENCE OF Pmc1008mpRinvSfpEntry
      MAX-ACCESS  not-accessible
      STATUS  current
      DESCRIPTION
              "List of the SFPs on the selected module"
      ::= { pmc1008mpriTable 1 }

pmc1008mpRinvSfpEntry OBJECT-TYPE
        SYNTAX  Pmc1008mpRinvSfpEntry
        MAX-ACCESS  not-accessible
        STATUS  current
        DESCRIPTION
              "Row definition for the SFP table"
        INDEX   { pmc1008mpRinvSfpIndex }
        ::= { pmc1008mpRinvSfpTable 1 }
    


Pmc1008mpRinvSfpEntry::=
        SEQUENCE {
          pmc1008mpRinvSfpIndex 
              Integer32,
          pmc1008mpRinvsfp
              DisplayString
        }


    pmc1008mpRinvSfpIndex OBJECT-TYPE
        SYNTAX  Integer32(1..16)
        MAX-ACCESS  read-only
        STATUS  current
        DESCRIPTION
              "Index for SFP table"
        ::= { pmc1008mpRinvSfpEntry 1 }


    pmc1008mpRinvsfp OBJECT-TYPE
        SYNTAX  DisplayString
        MAX-ACCESS  read-only
        STATUS  current
        DESCRIPTION
              "Inventory for the SFP: This OID contains the inventory for the SFP"
        ::= { pmc1008mpRinvSfpEntry 2 }




pmc1008mpRinvLineTable OBJECT-TYPE
      SYNTAX  SEQUENCE OF Pmc1008mpRinvLineEntry
      MAX-ACCESS  not-accessible
      STATUS  current
      DESCRIPTION
              "List of the XFPs on the selected module"
      ::= { pmc1008mpriTable 2 }

pmc1008mpRinvLineEntry OBJECT-TYPE
        SYNTAX  Pmc1008mpRinvLineEntry
        MAX-ACCESS  not-accessible
        STATUS  current
        DESCRIPTION
              "Row definition for the XFP table"
        INDEX   { pmc1008mpRinvLineIndex }
        ::= { pmc1008mpRinvLineTable 1 }
    


Pmc1008mpRinvLineEntry::=
        SEQUENCE {
          pmc1008mpRinvLineIndex 
              Integer32,
          pmc1008mpRinvxfpLine
              DisplayString
        }


    pmc1008mpRinvLineIndex OBJECT-TYPE
        SYNTAX  Integer32(1..16)
        MAX-ACCESS  read-only
        STATUS  current
        DESCRIPTION
              "Index for XFP table"
        ::= { pmc1008mpRinvLineEntry 1 }


    pmc1008mpRinvxfpLine OBJECT-TYPE
        SYNTAX  DisplayString
        MAX-ACCESS  read-only
        STATUS  current
        DESCRIPTION
              "Inventory for the XFP: This OID contains the inventory for the XFP"
        ::= { pmc1008mpRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pmc1008mpAlmsynthAlm0 OBJECT IDENTIFIER ::= { pmc1008mpAlmOtherCrit 0 }




pmc1008mpAlmDefFuseB OBJECT-TYPE
	  SYNTAX EkiOnOff
	  MAX-ACCESS read-only
	  STATUS current
	  DESCRIPTION
        "
        Fuse B Fail :This OID indicates 
        that the fuse of the power input 
        B is in fail condition  <Help>
          Status of the Fuse B <Condtype> 
        DEF_FUSE_B <Probcause> powerProblem 
        (36) <Alarmtype> equipmentAlarm 
        (5) <Polarity> (2) 
        "
	  ::= { pmc1008mpAlmsynthAlm0 16 }



pmc1008mpAlmDefFuseA OBJECT-TYPE
	  SYNTAX EkiOnOff
	  MAX-ACCESS read-only
	  STATUS current
	  DESCRIPTION
        "
        Fuse A Fail :This OID indicates 
        that the fuse of the power input 
        A is in fail condition  <Help>
          Status of the Fuse A <Condtype> 
        DEF_FUSE_A <Probcause> powerProblem 
        (36) <Alarmtype> equipmentAlarm 
        (5) <Polarity> (2) 
        "
	  ::= { pmc1008mpAlmsynthAlm0 15 }



pmc1008mpAlmModGlobFail OBJECT-TYPE
	  SYNTAX EkiOnOff
	  MAX-ACCESS read-only
	  STATUS current
	  DESCRIPTION
        "
        Module Failure :This OID is set 
        on detection of a failure originating 
        from the PM <Condtype> MOD_GLOB_FAIL 
        <Probcause> equipmentMalfunction 
        (16) <Alarmtype> synthesisAlarm 
        (12)  <Polarity> (2) 
        "
	  ::= { pmc1008mpAlmsynthAlm0 9 }



--- *****************************************************
---     LEAF for the synthAlm2 article
--- *****************************************************
pmc1008mpAlmsynthAlm2 OBJECT IDENTIFIER ::= { pmc1008mpAlmOtherNurg 2 }




pmc1008mpAlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> other
         (1) <Alarmtype> other (1) <Polarity> 
        (2) 
        "
	  ::= { pmc1008mpAlmsynthAlm2 4 }



pmc1008mpAlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> other (1) <Alarmtype> 
        other (1) <Polarity> (2) 
        "
	  ::= { pmc1008mpAlmsynthAlm2 3 }



pmc1008mpAlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> other (1) 
        <Alarmtype> other (1) <Polarity> 
        (2) 
        "
	  ::= { pmc1008mpAlmsynthAlm2 2 }



pmc1008mpAlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> other 
        (1) <Alarmtype> other (1) <Polarity> 
        (2) 
        "
	  ::= { pmc1008mpAlmsynthAlm2 1 }



--- *********************************************************
---     TABLE for the pmc1008mpAlmsynthAlmLine articles
--- *********************************************************

pmc1008mpAlmsynthAlmLineTable OBJECT-TYPE
	SYNTAX  SEQUENCE OF Pmc1008mpAlmsynthAlmLineEntry
	MAX-ACCESS not-accessible
	STATUS current
	DESCRIPTION
        "
        List of pmc1008mpAlmsynthAlmLine 
        Article
        "
	::= { pmc1008mpAlmLineCrit 7 }


pmc1008mpAlmsynthAlmLineEntry OBJECT-TYPE
	SYNTAX Pmc1008mpAlmsynthAlmLineEntry
	MAX-ACCESS not-accessible
	STATUS current
	DESCRIPTION
        "
        Row definition for the pmc1008mpAlmsynthAlmLine 
        table
        "
	INDEX   { pmc1008mpAlmsynthAlmLineIndex }
	::= { pmc1008mpAlmsynthAlmLineTable 1 }


Pmc1008mpAlmsynthAlmLineEntry ::=
	SEQUENCE {
	pmc1008mpAlmsynthAlmLineIndex
		INTEGER,
	pmc1008mpAlmLineActivePortn
		EkiOnOff,
	pmc1008mpAlmLineFailPortn
		EkiOnOff,
	pmc1008mpAlmLineDdmAlmPortn
		EkiOnOff,
	pmc1008mpAlmLineDdmWarningPortn
		EkiOnOff,
	pmc1008mpAlmUpRdiInsPortn
		EkiOnOff,
	pmc1008mpAlmLineLocalOosPortn
		EkiOnOff,
	pmc1008mpAlmXfpTxOffPortn
		EkiOnOff,
	pmc1008mpAlmLineHwFailPortn
		EkiOnOff,
	pmc1008mpAlmXfpInitNotComplPortn
		EkiOnOff,
	pmc1008mpAlmXfpAbsentPortn
		EkiOnOff
	}


pmc1008mpAlmsynthAlmLineIndex OBJECT-TYPE
	SYNTAX  INTEGER(0..128)
	MAX-ACCESS  read-only
	STATUS current
	DESCRIPTION
        "
        Index definition for the pmc1008mpAlmsynthAlmLine 
        table
        "
	::= { pmc1008mpAlmsynthAlmLineEntry 1 }


pmc1008mpAlmLineActivePortn OBJECT-TYPE
	SYNTAX  EkiOnOff
	MAX-ACCESS read-only
	STATUS current
	DESCRIPTION
        "
        Line Active :This bit indicates 
        the line #n is active on receive 
        side  <Help>  This status indicates 
        whether the line is active or standby. 
        <Condtype> LINE_ACTIVE <Probcause> 
        informationalStatus(1000) <Alarmtype> 
        other(1) <Polarity> (2) 
        "
	::= { pmc1008mpAlmsynthAlmLineEntry 17 }


pmc1008mpAlmLineFailPortn OBJECT-TYPE
	SYNTAX  EkiOnOff
	MAX-ACCESS read-only
	STATUS current
	DESCRIPTION
        "
        Line Port Failure :This OID indicates 
        a failure on the line port <Condtype> 
        LINE_FAIL <Probcause> equipmentMalfunction 
        (16) <Alarmtype> synthesisAlarm 
        (12)  <Polarity> (2) 
        "
	::= { pmc1008mpAlmsynthAlmLineEntry 13 }


pmc1008mpAlmLineDdmAlmPortn OBJECT-TYPE
	SYNTAX  EkiOnOff
	MAX-ACCESS read-only
	STATUS current
	DESCRIPTION
        "
        Alarm On Line Optical Module DDM 
        :This OID indicates an alarm is 
        present coming out of Line optical 
        interface DDM  <Help>  This alarm 
        indicates if a DDM Alarm has been 
        detected on the line transceiver 
        <Condtype> LINE_DDM_ALM <Probcause> 
        equipmentMalfunction (16) <Alarmtype> 
        synthesisAlarm (12)  <Polarity> 
        (2) 
        "
	::= { pmc1008mpAlmsynthAlmLineEntry 11 }


pmc1008mpAlmLineDdmWarningPortn OBJECT-TYPE
	SYNTAX  EkiOnOff
	MAX-ACCESS read-only
	STATUS current
	DESCRIPTION
        "
        Warning On Line Optical Module 
        DDM :This OID indicates a warning 
        is present coming out of Line optical 
        interface DDM  <Help>  This alarm 
        indicates if a DDM Warning has
         been detected on the line transceiver 
        <Condtype> LINE_DDM_WARNING <Probcause> 
        equipmentMalfunction (16) <Alarmtype> 
        synthesisAlarm (12)  <Polarity> 
        (2) 
        "
	::= { pmc1008mpAlmsynthAlmLineEntry 10 }


pmc1008mpAlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal.   <Help>  This status indicates 
        if a MS-RDI/L-RDI is currently
         inserted on the line interface. 
        <Condtype> UP_RDI_INS <Probcause> 
        informationalStatus(1000) <Alarmtype> 
        other (1) <Polarity> (2) 
        "
	::= { pmc1008mpAlmsynthAlmLineEntry 9 }


pmc1008mpAlmLineLocalOosPortn OBJECT-TYPE
	SYNTAX  EkiOnOff
	MAX-ACCESS read-only
	STATUS current
	DESCRIPTION
        "
        Line Port In Service :This OID 
        indicates that the Line port is 
        In Service (1) of Out or Service 
        (2)  <Help>  This status indicates 
        if the line port is in service
         <Condtype> LINE_LOCAL_OOS <Probcause> 
        informationalStatus(1000) <Alarmtype> 
        other (1) <Polarity> (2) 
        "
	::= { pmc1008mpAlmsynthAlmLineEntry 7 }


pmc1008mpAlmXfpTxOffPortn OBJECT-TYPE
	SYNTAX  EkiOnOff
	MAX-ACCESS read-only
	STATUS current
	DESCRIPTION
        "
        Line Optical Module Laser Shutdown 
        :This OID indicates the line optical 
        output power is on  <Help>  This 
        status indicates if the line transceiver 
        laser is ON or OFF <Condtype> XFP_TX_OFF 
        <Probcause> other (1) <Alarmtype> 
        equipmentAlarm (5) <Polarity> (2) 
        "
	::= { pmc1008mpAlmsynthAlmLineEntry 6 }


pmc1008mpAlmLineHwFailPortn OBJECT-TYPE
	SYNTAX  EkiOnOff
	MAX-ACCESS read-only
	STATUS current
	DESCRIPTION
        "
        Line Port HW Failure :This OID 
        indicates a failure on line port, 
        most probably caused by a HW issue 
        <Condtype> LINE_HW_FAIL <Probcause> 
        equipmentMalfunction (16) <Alarmtype> 
        synthesisAlarm (12)  <Polarity> 
        (2) 
        "
	::= { pmc1008mpAlmsynthAlmLineEntry 5 }


pmc1008mpAlmXfpInitNotComplPortn OBJECT-TYPE
	SYNTAX  EkiOnOff
	MAX-ACCESS read-only
	STATUS current
	DESCRIPTION
        "
        Line Optical Module Ready :This 
        OID indicates that the optical
         interface (XFP or OTX) is not
         operational.  <Help>  This status 
        indicates if the line transceiver 
        has been correctly initialized
         <Condtype> XFP_INIT_NOT_COMPL
         <Probcause> equipmentMalfunction 
        (16) <Alarmtype> equipmentAlarm 
        (5) <Polarity> (2) <Event> ObjectCDINV
        "
	::= { pmc1008mpAlmsynthAlmLineEntry 3 }


pmc1008mpAlmXfpAbsentPortn OBJECT-TYPE
	SYNTAX  EkiOnOff
	MAX-ACCESS read-only
	STATUS current
	DESCRIPTION
        "
        Line Optical Module Absent :This 
        OID indicates that the line optical 
        interface (XFP or OTX) is not plugged 
        in.  <Help>  This alarm indicates 
        if the line transceiver is present. 
        <Condtype> XFP_ABSENT <Probcause> 
        inputOutputDeviceError (24) <Alarmtype> 
        equipmentAlarm (5) <Polarity> (2) 
        <Event> ObjectCDINV
        "
	::= { pmc1008mpAlmsynthAlmLineEntry 2 }


--- *********************************************************
---     TABLE for the pmc1008mpAlmsynthAlmPort articles
--- *********************************************************

pmc1008mpAlmsynthAlmPortTable OBJECT-TYPE
	SYNTAX  SEQUENCE OF Pmc1008mpAlmsynthAlmPortEntry
	MAX-ACCESS not-accessible
	STATUS current
	DESCRIPTION
        "
        List of pmc1008mpAlmsynthAlmPort 
        Article
        "
	::= { pmc1008mpAlmClientCrit 8 }


pmc1008mpAlmsynthAlmPortEntry OBJECT-TYPE
	SYNTAX Pmc1008mpAlmsynthAlmPortEntry
	MAX-ACCESS not-accessible
	STATUS current
	DESCRIPTION
        "
        Row definition for the pmc1008mpAlmsynthAlmPort 
        table
        "
	INDEX   { pmc1008mpAlmsynthAlmPortIndex }
	::= { pmc1008mpAlmsynthAlmPortTable 1 }


Pmc1008mpAlmsynthAlmPortEntry ::=
	SEQUENCE {
	pmc1008mpAlmsynthAlmPortIndex
		INTEGER,
	pmc1008mpAlmUpCsfPortn
		EkiOnOff,
	pmc1008mpAlmClientActivePortn
		EkiOnOff,
	pmc1008mpAlmFailAccPortn
		EkiOnOff,
	pmc1008mpAlmSfpDdmAlmPortn
		EkiOnOff,
	pmc1008mpAlmSfpDdmWarningPortn
		EkiOnOff,
	pmc1008mpAlmDwCaisPortn
		EkiOnOff,
	pmc1008mpAlmClientRemoteOosPortn
		EkiOnOff,
	pmc1008mpAlmClientLocalOosPortn
		EkiOnOff,
	pmc1008mpAlmDwLsdPortn
		EkiOnOff,
	pmc1008mpAlmHwFailAccPortn
		EkiOnOff,
	pmc1008mpAlmDdmAbsentPortn
		EkiOnOff,
	pmc1008mpAlmSfpAbsentPortn
		EkiOnOff
	}


pmc1008mpAlmsynthAlmPortIndex OBJECT-TYPE
	SYNTAX  INTEGER(0..128)
	MAX-ACCESS  read-only
	STATUS current
	DESCRIPTION
        "
        Index definition for the pmc1008mpAlmsynthAlmPort 
        table
        "
	::= { pmc1008mpAlmsynthAlmPortEntry 1 }


pmc1008mpAlmUpCsfPortn OBJECT-TYPE
	SYNTAX  EkiOnOff
	MAX-ACCESS read-only
	STATUS current
	DESCRIPTION
        "
        Client Signal Fail Inserted :This 
        OID indicates a CSF has been inserted 
        in the upstream client port.  <Help> 
         This status indicates if a Client 
        Signal Fail is currently inserted 
        on the line signal for this client 
        port <Condtype> UP_CSF_1 <Probcause> 
        other (1) <Alarmtype> other(1)
         <Polarity> (2) 
        "
	::= { pmc1008mpAlmsynthAlmPortEntry 17 }


pmc1008mpAlmClientActivePortn OBJECT-TYPE
	SYNTAX  EkiOnOff
	MAX-ACCESS read-only
	STATUS current
	DESCRIPTION
        "
        Client Sink (Line1 Or Line2) :This 
        bit indicates the Client #n is
         active on receive side  <Help> 
         This status indicates whether
         the Client is extracted from Line 
        1 or Line 2. <Condtype> CLIENT_ACTIVE 
        <Probcause> informationalStatus(1000) 
        <Alarmtype> other(1) <Polarity> 
        (2) 
        "
	::= { pmc1008mpAlmsynthAlmPortEntry 16 }


pmc1008mpAlmFailAccPortn OBJECT-TYPE
	SYNTAX  EkiOnOff
	MAX-ACCESS read-only
	STATUS current
	DESCRIPTION
        "
        Client Access Fail :This OID indicates 
        a failure on the Client port <Condtype> 
        FAIL_ACC_1 <Probcause> equipmentMalfunction 
        (16) <Alarmtype> synthesisAlarm 
        (12)  <Polarity> (2) 
        "
	::= { pmc1008mpAlmsynthAlmPortEntry 13 }


pmc1008mpAlmSfpDdmAlmPortn OBJECT-TYPE
	SYNTAX  EkiOnOff
	MAX-ACCESS read-only
	STATUS current
	DESCRIPTION
        "
        Alarm On Client SFP DDM :This
         OID indicates an alarm is being 
        received from the Client SFP DDM 
         <Help>  This alarm indicates if 
        a DDM Alarm has been detected on 
        the client transceiver <Condtype> 
        SFP_DDM_ALM_1 <Probcause> equipmentMalfunction 
        (16) <Alarmtype> synthesisAlarm 
        (12)  <Polarity> (2) 
        "
	::= { pmc1008mpAlmsynthAlmPortEntry 11 }


pmc1008mpAlmSfpDdmWarningPortn OBJECT-TYPE
	SYNTAX  EkiOnOff
	MAX-ACCESS read-only
	STATUS current
	DESCRIPTION
        "
        Warning On Client SFP DDM :This 
        OID indicates a warning is being 
        received from the Client SFP DDM 
         <Help>  This alarm indicates if 
        a DDM Warning has been detected 
        on the client transceiver <Condtype> 
        SFP_DDM_WARNING_1 <Probcause> equipmentMalfunction 
        (16) <Alarmtype> synthesisAlarm 
        (12)  <Polarity> (2) 
        "
	::= { pmc1008mpAlmsynthAlmPortEntry 10 }


pmc1008mpAlmDwCaisPortn OBJECT-TYPE
	SYNTAX  EkiOnOff
	MAX-ACCESS read-only
	STATUS current
	DESCRIPTION
        "
        Client AIS Inserted :This OID
         indicates a CAIS has been inserted 
        on the output client port.  <Help> 
         This status indicates if a Client 
        Alarm Indication Signal is currently 
        inserted on the client interface 
        <Condtype> DW_CAIS_1 <Probcause> 
        informationalStatus(1000) <Alarmtype> 
        other (1) <Polarity> (2) 
        "
	::= { pmc1008mpAlmsynthAlmPortEntry 9 }


pmc1008mpAlmClientRemoteOosPortn OBJECT-TYPE
	SYNTAX  EkiOnOff
	MAX-ACCESS read-only
	STATUS current
	DESCRIPTION
        "
        Remote Client Port In Service
         :This OID indicates that the remote 
        Client port is In Service (1) or 
        Out of Service (2)  <Help>  This 
        status indicates if the remote
         client port is in service <Condtype> 
        CLIENT_REMOTE_OOS <Probcause> informationalStatus(1000) 
        <Alarmtype> other (1) <Polarity> 
        (2) 
        "
	::= { pmc1008mpAlmsynthAlmPortEntry 8 }


pmc1008mpAlmClientLocalOosPortn OBJECT-TYPE
	SYNTAX  EkiOnOff
	MAX-ACCESS read-only
	STATUS current
	DESCRIPTION
        "
        Local Client Port In Service :This 
        OID indicates that the local Client 
        port is In Service (1) or Out of 
        Service (2)  <Help>  This status 
        indicates if the local client port 
        is in service <Condtype> CLIENT_LOCAL_OOS 
        <Probcause> informationalStatus(1000) 
        <Alarmtype> other (1) <Polarity> 
        (2) 
        "
	::= { pmc1008mpAlmsynthAlmPortEntry 7 }


pmc1008mpAlmDwLsdPortn OBJECT-TYPE
	SYNTAX  EkiOnOff
	MAX-ACCESS read-only
	STATUS current
	DESCRIPTION
        "
        Client SFP Laser Shutdown :This 
        OID indicates the Client SFP transmitter 
        output is ON.   <Help>  This status 
        indicates if the client transceiver 
        laser is ON or OFF <Condtype> DW_LSD_1 
        <Probcause> other (1) <Alarmtype> 
        equipmentAlarm (5) <Polarity> (2) 
        "
	::= { pmc1008mpAlmsynthAlmPortEntry 6 }


pmc1008mpAlmHwFailAccPortn OBJECT-TYPE
	SYNTAX  EkiOnOff
	MAX-ACCESS read-only
	STATUS current
	DESCRIPTION
        "
        Client HW Fail :This OID indicates 
        a failure on client port, most
         probably caused by a HW issue. 
        <Condtype> HW_FAIL_ACC_1 <Probcause> 
        equipmentMalfunction (16) <Alarmtype> 
        synthesisAlarm (12)  <Polarity> 
        (2) 
        "
	::= { pmc1008mpAlmsynthAlmPortEntry 5 }


pmc1008mpAlmDdmAbsentPortn OBJECT-TYPE
	SYNTAX  EkiOnOff
	MAX-ACCESS read-only
	STATUS current
	DESCRIPTION
        "
        DDM Supported On Client SFP :This 
        OID indicates that the Client SFP 
        module supports the Digital Diagnostic 
        Monitoring function  <Help>  This 
        status indicates if the client
         transceiver includes the DDM feature 
        <Condtype> DDM_ABSENT_1 <Probcause> 
        informationalStatus(1000) <Alarmtype> 
        other (1) <Polarity> (2) 
        "
	::= { pmc1008mpAlmsynthAlmPortEntry 3 }


pmc1008mpAlmSfpAbsentPortn OBJECT-TYPE
	SYNTAX  EkiOnOff
	MAX-ACCESS read-only
	STATUS current
	DESCRIPTION
        "
        Client SFP Absent :This OID indicates 
        that the SFP module is not present 
        in the client port.  <Help>  This 
        alarm indicates if the client transceiver 
        is present. <Condtype> SFP_ABSENT_1 
        <Probcause> inputOutputDeviceError 
        (24) <Alarmtype> equipmentAlarm 
        (5) <Polarity> (2) <Event> ObjectCDINV
        "
	::= { pmc1008mpAlmsynthAlmPortEntry 2 }


--- *********************************************************
---     TABLE for the pmc1008mpAlmaccessioAlm articles
--- *********************************************************

pmc1008mpAlmaccessioAlmTable OBJECT-TYPE
	SYNTAX  SEQUENCE OF Pmc1008mpAlmaccessioAlmEntry
	MAX-ACCESS not-accessible
	STATUS current
	DESCRIPTION
        "
        List of pmc1008mpAlmaccessioAlm 
        Article
        "
	::= { pmc1008mpAlmClientCrit 16 }


pmc1008mpAlmaccessioAlmEntry OBJECT-TYPE
	SYNTAX Pmc1008mpAlmaccessioAlmEntry
	MAX-ACCESS not-accessible
	STATUS current
	DESCRIPTION
        "
        Row definition for the pmc1008mpAlmaccessioAlm 
        table
        "
	INDEX   { pmc1008mpAlmaccessioAlmIndex }
	::= { pmc1008mpAlmaccessioAlmTable 1 }


Pmc1008mpAlmaccessioAlmEntry ::=
	SEQUENCE {
	pmc1008mpAlmaccessioAlmIndex
		INTEGER,
	pmc1008mpAlmUpLosPortn
		EkiOnOff,
	pmc1008mpAlmDwLasFailPortn
		EkiOnOff
	}


pmc1008mpAlmaccessioAlmIndex OBJECT-TYPE
	SYNTAX  INTEGER(0..128)
	MAX-ACCESS  read-only
	STATUS current
	DESCRIPTION
        "
        Index definition for the pmc1008mpAlmaccessioAlm 
        table
        "
	::= { pmc1008mpAlmaccessioAlmEntry 1 }


pmc1008mpAlmUpLosPortn OBJECT-TYPE
	SYNTAX  EkiOnOff
	MAX-ACCESS read-only
	STATUS current
	DESCRIPTION
        "
        Client Input Loss Of Signal :This 
        OID indicates that no signal is 
        present on the SFP of the client 
        port  <Help>  This alarm indicates 
        if an optical signal is detected 
        on the client transceiver input 
        <Condtype> UP_LOS_1 <Probcause> 
        receiveFailure (41) <Alarmtype> 
        physicalViolation (9) <Polarity> 
        (2) 
        "
	::= { pmc1008mpAlmaccessioAlmEntry 5 }


pmc1008mpAlmDwLasFailPortn OBJECT-TYPE
	SYNTAX  EkiOnOff
	MAX-ACCESS read-only
	STATUS current
	DESCRIPTION
        "
        Client SFP Tx Failed :This OID 
        indicates that the transmitter
         fails for the SFP plugged into 
        the client port (this alarm reports 
        the transmitter failure alarm generated 
        by the SFPs)  <Help>  This alarm 
        indicates if the laser of the client 
        transceiver is in fail condition 
        <Condtype> DW_LAS_FAIL_1 <Probcause> 
        transmitterFailure (56) <Alarmtype> 
        equipmentAlarm (5) <Polarity> (2) 
        "
	::= { pmc1008mpAlmaccessioAlmEntry 2 }


--- *********************************************************
---     TABLE for the pmc1008mpAlmsfpAlmDdm articles
--- *********************************************************

pmc1008mpAlmsfpAlmDdmTable OBJECT-TYPE
	SYNTAX  SEQUENCE OF Pmc1008mpAlmsfpAlmDdmEntry
	MAX-ACCESS not-accessible
	STATUS current
	DESCRIPTION
        "
        List of pmc1008mpAlmsfpAlmDdm
         Article
        "
	::= { pmc1008mpAlmClientUrg 32 }


pmc1008mpAlmsfpAlmDdmEntry OBJECT-TYPE
	SYNTAX Pmc1008mpAlmsfpAlmDdmEntry
	MAX-ACCESS not-accessible
	STATUS current
	DESCRIPTION
        "
        Row definition for the pmc1008mpAlmsfpAlmDdm 
        table
        "
	INDEX   { pmc1008mpAlmsfpAlmDdmIndex }
	::= { pmc1008mpAlmsfpAlmDdmTable 1 }


Pmc1008mpAlmsfpAlmDdmEntry ::=
	SEQUENCE {
	pmc1008mpAlmsfpAlmDdmIndex
		INTEGER,
	pmc1008mpAlmRxPwrHighAlaPortn
		EkiOnOff,
	pmc1008mpAlmRxPwrLowAlaPortn
		EkiOnOff,
	pmc1008mpAlmTempHighAlaPortn
		EkiOnOff,
	pmc1008mpAlmTempLowAlaPortn
		EkiOnOff,
	pmc1008mpAlmVccHighAlaPortn
		EkiOnOff,
	pmc1008mpAlmVccLowAlaPortn
		EkiOnOff,
	pmc1008mpAlmTxBiasHighAlaPortn
		EkiOnOff,
	pmc1008mpAlmTxBiasLowAlaPortn
		EkiOnOff,
	pmc1008mpAlmTxPwrHighAlaPortn
		EkiOnOff,
	pmc1008mpAlmTxPwrLowAlaPortn
		EkiOnOff
	}


pmc1008mpAlmsfpAlmDdmIndex OBJECT-TYPE
	SYNTAX  INTEGER(0..128)
	MAX-ACCESS  read-only
	STATUS current
	DESCRIPTION
        "
        Index definition for the pmc1008mpAlmsfpAlmDdm 
        table
        "
	::= { pmc1008mpAlmsfpAlmDdmEntry 1 }


pmc1008mpAlmRxPwrHighAlaPortn OBJECT-TYPE
	SYNTAX  EkiOnOff
	MAX-ACCESS read-only
	STATUS current
	DESCRIPTION
        "
        Client SFP Rx Power High :Alarm 
        indicating that the SFP input power 
        of port is higher than the threshold 
        value written in the SFP EEPROM 
        <Condtype> RX_PWR_HIGH_ALA_1 <Probcause> 
        receiveFailure (41) <Alarmtype> 
        equipmentAlarm (5) <Polarity> (2) 
        "
	::= { pmc1008mpAlmsfpAlmDdmEntry 17 }


pmc1008mpAlmRxPwrLowAlaPortn OBJECT-TYPE
	SYNTAX  EkiOnOff
	MAX-ACCESS read-only
	STATUS current
	DESCRIPTION
        "
        Client SFP Rx Power Low :Alarm 
        indicating that the SFP input power 
        of port is lower than the threshold 
        value written in the SFP EEPROM 
        <Condtype> RX_PWR_LOW_ALA_1 <Probcause> 
        receiveFailure (41) <Alarmtype> 
        equipmentAlarm (5) <Polarity> (2) 
        "
	::= { pmc1008mpAlmsfpAlmDdmEntry 16 }


pmc1008mpAlmTempHighAlaPortn OBJECT-TYPE
	SYNTAX  EkiOnOff
	MAX-ACCESS read-only
	STATUS current
	DESCRIPTION
        "
        Client SFP Temp High :Alarm indicating 
        that the SFP temperature of port 
        is higher than the threshold value 
        written in the SFP EEPROM <Condtype> 
        TEMP_HIGH_ALA_1 <Probcause> temperatureUnacceptable 
        (51) <Alarmtype> equipmentAlarm 
        (5) <Polarity> (2) 
        "
	::= { pmc1008mpAlmsfpAlmDdmEntry 9 }


pmc1008mpAlmTempLowAlaPortn OBJECT-TYPE
	SYNTAX  EkiOnOff
	MAX-ACCESS read-only
	STATUS current
	DESCRIPTION
        "
        Client SFP Temp Low :Alarm indicating 
        that the SFP temperature of port 
        is lower than the threshold value 
        written in the SFP EEPROM <Condtype> 
        TEMP_LOW_ALA_1 <Probcause> temperatureUnacceptable 
        (51) <Alarmtype> equipmentAlarm 
        (5) <Polarity> (2) 
        "
	::= { pmc1008mpAlmsfpAlmDdmEntry 8 }


pmc1008mpAlmVccHighAlaPortn OBJECT-TYPE
	SYNTAX  EkiOnOff
	MAX-ACCESS read-only
	STATUS current
	DESCRIPTION
        "
        Client SFP Power Supply High :Alarm 
        indicating that the SFP power supply 
        of port is higher than the threshold 
        value written in the SFP EEPROM 
         <Condtype> VCC_HIGH_ALA_1 <Probcause> 
        powerProblem (36) <Alarmtype> equipmentAlarm 
        (5) <Polarity> (2) 
        "
	::= { pmc1008mpAlmsfpAlmDdmEntry 7 }


pmc1008mpAlmVccLowAlaPortn OBJECT-TYPE
	SYNTAX  EkiOnOff
	MAX-ACCESS read-only
	STATUS current
	DESCRIPTION
        "
        Client SFP Power Supply Low :Alarm 
        indicating that the SFP power supply 
        of port is lower than the threshold 
        value written in the SFP EEPROM 
         <Condtype> VCC_LOW_ALA_1 <Probcause> 
        powerProblem (36) <Alarmtype> equipmentAlarm 
        (5) <Polarity> (2) 
        "
	::= { pmc1008mpAlmsfpAlmDdmEntry 6 }


pmc1008mpAlmTxBiasHighAlaPortn OBJECT-TYPE
	SYNTAX  EkiOnOff
	MAX-ACCESS read-only
	STATUS current
	DESCRIPTION
        "
        Client SFP Bias High :Alarm indicating 
        that the SFP laser bias current 
        of port is higher than the threshold 
        value written in the SFP EEPROM 
        <Condtype> TX_BIAS_HIGH_ALA_1 <Probcause> 
        transmitterFailure (56) <Alarmtype> 
        equipmentAlarm (5) <Polarity> (2) 
        "
	::= { pmc1008mpAlmsfpAlmDdmEntry 5 }


pmc1008mpAlmTxBiasLowAlaPortn OBJECT-TYPE
	SYNTAX  EkiOnOff
	MAX-ACCESS read-only
	STATUS current
	DESCRIPTION
        "
        Client SFP Bias Low :Alarm indicating 
        that the SFP laser bias current 
        of port is lower than the threshold 
        value written in the SFP EEPROM 
        <Condtype> TX_BIAS_LOW_ALA_1 <Probcause> 
        transmitterFailure (56) <Alarmtype> 
        equipmentAlarm (5) <Polarity> (2) 
        "
	::= { pmc1008mpAlmsfpAlmDdmEntry 4 }


pmc1008mpAlmTxPwrHighAlaPortn OBJECT-TYPE
	SYNTAX  EkiOnOff
	MAX-ACCESS read-only
	STATUS current
	DESCRIPTION
        "
        Client SFP Tx Power High :Alarm 
        indicating that the SFP output
         power of port is higher than the 
        threshold value written in the
         SFP EEPROM <Condtype> TX_PWR_HIGH_ALA_1 
        <Probcause> transmitterFailure
         (56) <Alarmtype> equipmentAlarm 
        (5) <Polarity> (2) 
        "
	::= { pmc1008mpAlmsfpAlmDdmEntry 3 }


pmc1008mpAlmTxPwrLowAlaPortn OBJECT-TYPE
	SYNTAX  EkiOnOff
	MAX-ACCESS read-only
	STATUS current
	DESCRIPTION
        "
        Client SFP Tx Power Low :Alarm 
        indicating that the SFP output
         power of port is lower than the 
        threshold value written in the
         SFP EEPROM <Condtype> TX_PWR_LOW_ALA_1 
        <Probcause> transmitterFailure
         (56) <Alarmtype> equipmentAlarm 
        (5) <Polarity> (2) 
        "
	::= { pmc1008mpAlmsfpAlmDdmEntry 2 }


--- *********************************************************
---     TABLE for the pmc1008mpAlmsfpWarnDdm articles
--- *********************************************************

pmc1008mpAlmsfpWarnDdmTable OBJECT-TYPE
	SYNTAX  SEQUENCE OF Pmc1008mpAlmsfpWarnDdmEntry
	MAX-ACCESS not-accessible
	STATUS current
	DESCRIPTION
        "
        List of pmc1008mpAlmsfpWarnDdm 
        Article
        "
	::= { pmc1008mpAlmClientNurg 48 }


pmc1008mpAlmsfpWarnDdmEntry OBJECT-TYPE
	SYNTAX Pmc1008mpAlmsfpWarnDdmEntry
	MAX-ACCESS not-accessible
	STATUS current
	DESCRIPTION
        "
        Row definition for the pmc1008mpAlmsfpWarnDdm 
        table
        "
	INDEX   { pmc1008mpAlmsfpWarnDdmIndex }
	::= { pmc1008mpAlmsfpWarnDdmTable 1 }


Pmc1008mpAlmsfpWarnDdmEntry ::=
	SEQUENCE {
	pmc1008mpAlmsfpWarnDdmIndex
		INTEGER,
	pmc1008mpAlmRxPwrHighWngPortn
		EkiOnOff,
	pmc1008mpAlmRxPwrLowWngPortn
		EkiOnOff,
	pmc1008mpAlmTempHighWngPortn
		EkiOnOff,
	pmc1008mpAlmTempLowWngPortn
		EkiOnOff,
	pmc1008mpAlmVccHighWngPortn
		EkiOnOff,
	pmc1008mpAlmVccLowWngPortn
		EkiOnOff,
	pmc1008mpAlmTxBiasHighWngPortn
		EkiOnOff,
	pmc1008mpAlmTxBiasLowWngPortn
		EkiOnOff,
	pmc1008mpAlmTxPwrHighWngPortn
		EkiOnOff,
	pmc1008mpAlmTxPwLowWngPortn
		EkiOnOff
	}


pmc1008mpAlmsfpWarnDdmIndex OBJECT-TYPE
	SYNTAX  INTEGER(0..128)
	MAX-ACCESS  read-only
	STATUS current
	DESCRIPTION
        "
        Index definition for the pmc1008mpAlmsfpWarnDdm 
        table
        "
	::= { pmc1008mpAlmsfpWarnDdmEntry 1 }


pmc1008mpAlmRxPwrHighWngPortn OBJECT-TYPE
	SYNTAX  EkiOnOff
	MAX-ACCESS read-only
	STATUS current
	DESCRIPTION
        "
        Client SFP Rx Power High Warning 
        :Warning indicating that the SFP 
        input power of port is higher than 
        the threshold value written in
         the SFP EEPROM <Condtype> RX_PWR_HIGH_WNG_1 
        <Probcause> receiveFailure (41) 
        <Alarmtype> equipmentAlarm (5)
         <Polarity> (2) 
        "
	::= { pmc1008mpAlmsfpWarnDdmEntry 17 }


pmc1008mpAlmRxPwrLowWngPortn OBJECT-TYPE
	SYNTAX  EkiOnOff
	MAX-ACCESS read-only
	STATUS current
	DESCRIPTION
        "
        Client SFP Rx Power Low Warning 
        :Warning indicating that the SFP 
        input power of port is lower than 
        the threshold value written in
         the SFP EEPROM <Condtype> RX_PWR_LOW_WNG_1 
        <Probcause> receiveFailure (41) 
        <Alarmtype> equipmentAlarm (5)
         <Polarity> (2) 
        "
	::= { pmc1008mpAlmsfpWarnDdmEntry 16 }


pmc1008mpAlmTempHighWngPortn OBJECT-TYPE
	SYNTAX  EkiOnOff
	MAX-ACCESS read-only
	STATUS current
	DESCRIPTION
        "
        Client SFP Temp High Warning :Warning 
        indicating that the SFP temperature 
        of port is higher than the threshold 
        value written in the SFP EEPROM 
        <Condtype> TEMP_HIGH_WNG_1 <Probcause> 
        temperatureUnacceptable (51) <Alarmtype> 
        equipmentAlarm (5) <Polarity> (2) 
        "
	::= { pmc1008mpAlmsfpWarnDdmEntry 9 }


pmc1008mpAlmTempLowWngPortn OBJECT-TYPE
	SYNTAX  EkiOnOff
	MAX-ACCESS read-only
	STATUS current
	DESCRIPTION
        "
        Client SFP Temp Low Warning :Warning 
        indicating that the SFP temperature 
        of port is lower than the threshold 
        value written in the SFP EEPROM 
        <Condtype> TEMP_LOW_WNG_1 <Probcause> 
        temperatureUnacceptable (51) <Alarmtype> 
        equipmentAlarm (5) <Polarity> (2) 
        "
	::= { pmc1008mpAlmsfpWarnDdmEntry 8 }


pmc1008mpAlmVccHighWngPortn OBJECT-TYPE
	SYNTAX  EkiOnOff
	MAX-ACCESS read-only
	STATUS current
	DESCRIPTION
        "
        Client SFP Power Supply High Warning 
        :Warning indicating that the SFP 
        power supply of port is higher
         than the threshold value written 
        in the SFP EEPROM  <Condtype> VCC_HIGH_WNG_1 
        <Probcause> powerProblem (36) <Alarmtype> 
        equipmentAlarm (5) <Polarity> (2) 
        "
	::= { pmc1008mpAlmsfpWarnDdmEntry 7 }


pmc1008mpAlmVccLowWngPortn OBJECT-TYPE
	SYNTAX  EkiOnOff
	MAX-ACCESS read-only
	STATUS current
	DESCRIPTION
        "
        Client SFP Power Supply Low Warning 
        :Warning indicating that the SFP 
        power supply of port is lower than 
        the threshold value written in
         the SFP EEPROM  <Condtype> VCC_LOW_WNG_1 
        <Probcause> powerProblem (36) <Alarmtype> 
        equipmentAlarm (5) <Polarity> (2) 
        "
	::= { pmc1008mpAlmsfpWarnDdmEntry 6 }


pmc1008mpAlmTxBiasHighWngPortn OBJECT-TYPE
	SYNTAX  EkiOnOff
	MAX-ACCESS read-only
	STATUS current
	DESCRIPTION
        "
        Client SFP Bias High Warning :Warning 
        indicating that the SFP laser bias 
        current of port is higher than
         the threshold value written in 
        the SFP EEPROM <Condtype> TX_BIAS_HIGH_WNG_1 
        <Probcause> transmitterFailure
         (56) <Alarmtype> equipmentAlarm 
        (5) <Polarity> (2) 
        "
	::= { pmc1008mpAlmsfpWarnDdmEntry 5 }


pmc1008mpAlmTxBiasLowWngPortn OBJECT-TYPE
	SYNTAX  EkiOnOff
	MAX-ACCESS read-only
	STATUS current
	DESCRIPTION
        "
        Client SFP Bias Low Warning :Warning 
        indicating that the SFP laser bias 
        current of port is lower than the 
        threshold value written in the
         SFP EEPROM <Condtype> TX_BIAS_LOW_WNG_1 
        <Probcause> transmitterFailure
         (56) <Alarmtype> equipmentAlarm 
        (5) <Polarity> (2) 
        "
	::= { pmc1008mpAlmsfpWarnDdmEntry 4 }


pmc1008mpAlmTxPwrHighWngPortn OBJECT-TYPE
	SYNTAX  EkiOnOff
	MAX-ACCESS read-only
	STATUS current
	DESCRIPTION
        "
        Client SFP Tx Power High Warning 
        :Warning indicating that the SFP 
        output power of port is higher
         than the threshold value written 
        in the SFP EEPROM <Condtype> TX_PWR_HIGH_WNG_1 
        <Probcause> transmitterFailure
         (56) <Alarmtype> equipmentAlarm 
        (5) <Polarity> (2) 
        "
	::= { pmc1008mpAlmsfpWarnDdmEntry 3 }


pmc1008mpAlmTxPwLowWngPortn OBJECT-TYPE
	SYNTAX  EkiOnOff
	MAX-ACCESS read-only
	STATUS current
	DESCRIPTION
        "
        Client SFP Tx Power Low Warning 
        :Warning indicating that the SFP 
        output power of port is lower than 
        the threshold value written in
         the SFP EEPROM <Condtype> TX_PW_LOW_WNG_1 
        <Probcause> transmitterFailure
         (56) <Alarmtype> equipmentAlarm 
        (5) <Polarity> (2) 
        "
	::= { pmc1008mpAlmsfpWarnDdmEntry 2 }


--- *********************************************************
---     TABLE for the pmc1008mpAlmmapperDeAlm articles
--- *********************************************************

pmc1008mpAlmmapperDeAlmTable OBJECT-TYPE
	SYNTAX  SEQUENCE OF Pmc1008mpAlmmapperDeAlmEntry
	MAX-ACCESS not-accessible
	STATUS current
	DESCRIPTION
        "
        List of pmc1008mpAlmmapperDeAlm 
        Article
        "
	::= { pmc1008mpAlmClientCrit 72 }


pmc1008mpAlmmapperDeAlmEntry OBJECT-TYPE
	SYNTAX Pmc1008mpAlmmapperDeAlmEntry
	MAX-ACCESS not-accessible
	STATUS current
	DESCRIPTION
        "
        Row definition for the pmc1008mpAlmmapperDeAlm 
        table
        "
	INDEX   { pmc1008mpAlmmapperDeAlmIndex }
	::= { pmc1008mpAlmmapperDeAlmTable 1 }


Pmc1008mpAlmmapperDeAlmEntry ::=
	SEQUENCE {
	pmc1008mpAlmmapperDeAlmIndex
		INTEGER,
	pmc1008mpAlmDwBufferOvlPortn
		EkiOnOff,
	pmc1008mpAlmDwCsfDetPortn
		EkiOnOff,
	pmc1008mpAlmUpBufferOvlPortn
		EkiOnOff,
	pmc1008mpAlmUpAccOosPortn
		EkiOnOff
	}


pmc1008mpAlmmapperDeAlmIndex OBJECT-TYPE
	SYNTAX  INTEGER(0..128)
	MAX-ACCESS  read-only
	STATUS current
	DESCRIPTION
        "
        Index definition for the pmc1008mpAlmmapperDeAlm 
        table
        "
	::= { pmc1008mpAlmmapperDeAlmEntry 1 }


pmc1008mpAlmDwBufferOvlPortn OBJECT-TYPE
	SYNTAX  EkiOnOff
	MAX-ACCESS read-only
	STATUS current
	DESCRIPTION
        "
        Client Downstream Buffer Overload 
        :This OID indicates that the de-mapper 
        buffer for client port is in overload. 
         <Help>  This alarm indicates if 
        there is a downstream FIFO overload 
        for this client port <Condtype> 
        DW_BUFFER_OVL_1 <Probcause> equipmentMalfunction 
        (16) <Alarmtype> equipmentAlarm 
        (5) <Polarity> (2) 
        "
	::= { pmc1008mpAlmmapperDeAlmEntry 15 }


pmc1008mpAlmDwCsfDetPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> DW_CSF_DET_1 
        <Probcause> receiveFailure (41) 
        <Alarmtype> other (1) <Polarity> 
        (2) 
        "
	::= { pmc1008mpAlmmapperDeAlmEntry 12 }


pmc1008mpAlmUpBufferOvlPortn OBJECT-TYPE
	SYNTAX  EkiOnOff
	MAX-ACCESS read-only
	STATUS current
	DESCRIPTION
        "
        Client Upstream Buffer Overload 
        :This OID indicates that the rate 
        adaptation buffer for client port 
        is in overload.  <Help>  This alarm 
        indicates if there is a upstream 
        FIFO overload for this client port 
        <Condtype> UP_BUFFER_OVL_1 <Probcause> 
        receiveFailure (41) <Alarmtype> 
        integrityViolation (7) <Polarity> 
        (2) 
        "
	::= { pmc1008mpAlmmapperDeAlmEntry 11 }


pmc1008mpAlmUpAccOosPortn OBJECT-TYPE
	SYNTAX  EkiOnOff
	MAX-ACCESS read-only
	STATUS current
	DESCRIPTION
        "
        Client Loss Of Synchro :This OID 
        indicates the upstream client input 
        port has lost synchronization on 
        its decoder  <Help>  This alarms 
        indicates if the input client signal 
        is correctly synchronized with
         the decoder <Condtype> UP_ACC_OOS_1 
        <Probcause> receiveFailure (41) 
        <Alarmtype> integrityViolation
         (7) <Polarity> (2) 
        "
	::= { pmc1008mpAlmmapperDeAlmEntry 2 }


--- *********************************************************
---     TABLE for the pmc1008mpAlmdfrmAlm articles
--- *********************************************************

pmc1008mpAlmdfrmAlmTable OBJECT-TYPE
	SYNTAX  SEQUENCE OF Pmc1008mpAlmdfrmAlmEntry
	MAX-ACCESS not-accessible
	STATUS current
	DESCRIPTION
        "
        List of pmc1008mpAlmdfrmAlm Article
        "
	::= { pmc1008mpAlmLineCrit 128 }


pmc1008mpAlmdfrmAlmEntry OBJECT-TYPE
	SYNTAX Pmc1008mpAlmdfrmAlmEntry
	MAX-ACCESS not-accessible
	STATUS current
	DESCRIPTION
        "
        Row definition for the pmc1008mpAlmdfrmAlm 
        table
        "
	INDEX   { pmc1008mpAlmdfrmAlmIndex }
	::= { pmc1008mpAlmdfrmAlmTable 1 }


Pmc1008mpAlmdfrmAlmEntry ::=
	SEQUENCE {
	pmc1008mpAlmdfrmAlmIndex
		INTEGER,
	pmc1008mpAlmDwLofPortn
		EkiOnOff,
	pmc1008mpAlmDwOofPortn
		EkiOnOff,
	pmc1008mpAlmDwRdiDetPortn
		EkiOnOff,
	pmc1008mpAlmDwAisDetPortn
		EkiOnOff
	}


pmc1008mpAlmdfrmAlmIndex OBJECT-TYPE
	SYNTAX  INTEGER(0..128)
	MAX-ACCESS  read-only
	STATUS current
	DESCRIPTION
        "
        Index definition for the pmc1008mpAlmdfrmAlm 
        table
        "
	::= { pmc1008mpAlmdfrmAlmEntry 1 }


pmc1008mpAlmDwLofPortn OBJECT-TYPE
	SYNTAX  EkiOnOff
	MAX-ACCESS read-only
	STATUS current
	DESCRIPTION
        "
        SONET/SDH Line Loss Of Frame :This 
        OID indicates that a Loss Of Frame 
        has been detected on incoming 
         OC-48c/STM-16c input signal  <Help> 
         This alarm indicates if there
         is a Loss of Frame is detected 
        on the line input signal <Condtype> 
        DW_LOF_1 <Probcause> receiveFailure 
        (41) <Alarmtype> integrityViolation 
        (7) <Polarity> (2) 
        "
	::= { pmc1008mpAlmdfrmAlmEntry 5 }


pmc1008mpAlmDwOofPortn OBJECT-TYPE
	SYNTAX  EkiOnOff
	MAX-ACCESS read-only
	STATUS current
	DESCRIPTION
        "
        SONET/SDH Line Out Of Frame :This 
        OID indicates that an Out Of Frame 
        has been detected on incoming 
         OC-48c/STM-16c input signal  <Help> 
         This alarm indicates if there
         is a Out of Frame is detected
         on the line input signal <Condtype> 
        DW_OOF_1 <Probcause> receiveFailure 
        (41) <Alarmtype> integrityViolation 
        (7) <Polarity> (2) 
        "
	::= { pmc1008mpAlmdfrmAlmEntry 4 }


pmc1008mpAlmDwRdiDetPortn OBJECT-TYPE
	SYNTAX  EkiOnOff
	MAX-ACCESS read-only
	STATUS current
	DESCRIPTION
        "
        MS-RDI/L-RDI Detected On Line
         Input :This OID indicates that 
        an MS-RDI has been detected on
         incoming  OC-48c/STM-16c input 
        signal  <Help>  This alarm indicates 
        if there is a MS-RDI/L-RDI is detected 
        on the line input signal <Condtype> 
        DW_RDI_DET_1 <Probcause> remoteNodeTransmissionError 
        (43) <Alarmtype> other (1) <Polarity> 
        (2) 
        "
	::= { pmc1008mpAlmdfrmAlmEntry 3 }


pmc1008mpAlmDwAisDetPortn OBJECT-TYPE
	SYNTAX  EkiOnOff
	MAX-ACCESS read-only
	STATUS current
	DESCRIPTION
        "
        MS-AIS/L-AIS Detected On Line
         Input :This OID indicates that 
        an MS-AIS has been detected on
         incoming  OC-48c/STM-16c input 
        signal  <Help>  This alarm indicates 
        if there is a MS-AIS/L-AIS is detected 
        on the line input signal <Condtype> 
        DW_AIS_DET_1 <Probcause> receiveFailure 
        (41) <Alarmtype> operationalViolation 
        (8) <Polarity> (2) 
        "
	::= { pmc1008mpAlmdfrmAlmEntry 2 }


--- *********************************************************
---     TABLE for the pmc1008mpAlmdfrmBer articles
--- *********************************************************

pmc1008mpAlmdfrmBerTable OBJECT-TYPE
	SYNTAX  SEQUENCE OF Pmc1008mpAlmdfrmBerEntry
	MAX-ACCESS not-accessible
	STATUS current
	DESCRIPTION
        "
        List of pmc1008mpAlmdfrmBer Article
        "
	::= { pmc1008mpAlmLineUrg 129 }


pmc1008mpAlmdfrmBerEntry OBJECT-TYPE
	SYNTAX Pmc1008mpAlmdfrmBerEntry
	MAX-ACCESS not-accessible
	STATUS current
	DESCRIPTION
        "
        Row definition for the pmc1008mpAlmdfrmBer 
        table
        "
	INDEX   { pmc1008mpAlmdfrmBerIndex }
	::= { pmc1008mpAlmdfrmBerTable 1 }


Pmc1008mpAlmdfrmBerEntry ::=
	SEQUENCE {
	pmc1008mpAlmdfrmBerIndex
		INTEGER,
	pmc1008mpAlmLineDegradePortn
		EkiOnOff,
	pmc1008mpAlmLineSignalFailPortn
		EkiOnOff,
	pmc1008mpAlmLineSignalDegradePortn
		EkiOnOff
	}


pmc1008mpAlmdfrmBerIndex OBJECT-TYPE
	SYNTAX  INTEGER(0..128)
	MAX-ACCESS  read-only
	STATUS current
	DESCRIPTION
        "
        Index definition for the pmc1008mpAlmdfrmBer 
        table
        "
	::= { pmc1008mpAlmdfrmBerEntry 1 }


pmc1008mpAlmLineDegradePortn OBJECT-TYPE
	SYNTAX  EkiOnOff
	MAX-ACCESS read-only
	STATUS current
	DESCRIPTION
        "
        Fixed Line Signal Degrade :This 
        OID indicates that the line input 
        signal is DEGRADE. The assetion 
        hysteresis is fixed to 10-8 (assertion) 
        and 10-9 (de-assertion) <Condtype> 
        LINE_DEGRADE_1 <Probcause> degradedSignal 
        (13) <Alarmtype> qualityOfServiceAlarm 
        (3) <Polarity> (2) 
        "
	::= { pmc1008mpAlmdfrmBerEntry 6 }


pmc1008mpAlmLineSignalFailPortn OBJECT-TYPE
	SYNTAX  EkiOnOff
	MAX-ACCESS read-only
	STATUS current
	DESCRIPTION
        "
        Custom Line Signal Fail :This
         OID indicates that the line input 
        signal is FAIL. The assertion hysteresis 
        can be customized by the host <Condtype> 
        LINE_SIGNAL_FAIL_1 <Probcause>
         receiveFailure (41) <Alarmtype> 
        integrityViolation (7) <Polarity> 
        (2) 
        "
	::= { pmc1008mpAlmdfrmBerEntry 3 }


pmc1008mpAlmLineSignalDegradePortn OBJECT-TYPE
	SYNTAX  EkiOnOff
	MAX-ACCESS read-only
	STATUS current
	DESCRIPTION
        "
        Custom Line Signal Degrade :This 
        OID indicates that the line input 
        signal is DEGRADE. The assertion 
        hysteresis can customized by the 
        host <Condtype> LINE_SIGNAL_DEGRADE_1 
        <Probcause> degradedSignal (13) 
        <Alarmtype> qualityOfServiceAlarm 
        (3) <Polarity> (2) 
        "
	::= { pmc1008mpAlmdfrmBerEntry 2 }


--- *********************************************************
---     TABLE for the pmc1008mpAlmlineSyncAlarms articles
--- *********************************************************

pmc1008mpAlmlineSyncAlarmsTable OBJECT-TYPE
	SYNTAX  SEQUENCE OF Pmc1008mpAlmlineSyncAlarmsEntry
	MAX-ACCESS not-accessible
	STATUS current
	DESCRIPTION
        "
        List of pmc1008mpAlmlineSyncAlarms 
        Article
        "
	::= { pmc1008mpAlmLineCrit 133 }


pmc1008mpAlmlineSyncAlarmsEntry OBJECT-TYPE
	SYNTAX Pmc1008mpAlmlineSyncAlarmsEntry
	MAX-ACCESS not-accessible
	STATUS current
	DESCRIPTION
        "
        Row definition for the pmc1008mpAlmlineSyncAlarms 
        table
        "
	INDEX   { pmc1008mpAlmlineSyncAlarmsIndex }
	::= { pmc1008mpAlmlineSyncAlarmsTable 1 }


Pmc1008mpAlmlineSyncAlarmsEntry ::=
	SEQUENCE {
	pmc1008mpAlmlineSyncAlarmsIndex
		INTEGER,
	pmc1008mpAlmDwLosPortn
		EkiOnOff,
	pmc1008mpAlmUpLockerrPortn
		EkiOnOff,
	pmc1008mpAlmDwLockerrPortn
		EkiOnOff
	}


pmc1008mpAlmlineSyncAlarmsIndex OBJECT-TYPE
	SYNTAX  INTEGER(0..128)
	MAX-ACCESS  read-only
	STATUS current
	DESCRIPTION
        "
        Index definition for the pmc1008mpAlmlineSyncAlarms 
        table
        "
	::= { pmc1008mpAlmlineSyncAlarmsEntry 1 }


pmc1008mpAlmDwLosPortn OBJECT-TYPE
	SYNTAX  EkiOnOff
	MAX-ACCESS read-only
	STATUS current
	DESCRIPTION
        "
        Line Input Loss Of Signal :This 
        OID indicates a loss of signal
         on the 10 Gb/s input.  <Help>
          This alarm indicates if an optical 
        signal is detected on the line
         transceiver input <Condtype> DW_LOS 
        <Probcause> receiveFailure (41) 
        <Alarmtype> physicalViolation (9) 
        <Polarity> (2) 
        "
	::= { pmc1008mpAlmlineSyncAlarmsEntry 17 }


pmc1008mpAlmUpLockerrPortn OBJECT-TYPE
	SYNTAX  EkiOnOff
	MAX-ACCESS read-only
	STATUS current
	DESCRIPTION
        "
        Upstream Clock Lock Error :This 
        OID indicates that the serializer 
        output 10 Gb/s clock multiplier 
        unit is not locked. <Condtype>
         UP_LOCKERR <Probcause> receiveFailure 
        (41) <Alarmtype> equipmentAlarm 
        (5) <Polarity> (2) 
        "
	::= { pmc1008mpAlmlineSyncAlarmsEntry 14 }


pmc1008mpAlmDwLockerrPortn OBJECT-TYPE
	SYNTAX  EkiOnOff
	MAX-ACCESS read-only
	STATUS current
	DESCRIPTION
        "
        Downstream Clock Lock Error :This 
        OID indicates that the deserializer 
        input 10 Gb/s clock recovery is 
        not locked. <Condtype> DW_LOCKERR 
        <Probcause> receiveFailure (41) 
        <Alarmtype> equipmentAlarm (5)
         <Polarity> (2) 
        "
	::= { pmc1008mpAlmlineSyncAlarmsEntry 13 }


--- *****************************************************
---     LEAF for the modInitFailLevel2 article
--- *****************************************************
pmc1008mpAlmmodInitFailLevel2 OBJECT IDENTIFIER ::= { pmc1008mpAlmOtherUrg 194 }




pmc1008mpAlmSwInitFail OBJECT-TYPE
	  SYNTAX EkiOnOff
	  MAX-ACCESS read-only
	  STATUS current
	  DESCRIPTION
        "
        SW Init Fail :This OID indicates 
        that the SW intialization has caused 
        unknown intial conditions  <Help> 
         This alarm indicates if the SW 
        module is correctly initialized 
        <Condtype> SW_INIT_FAIL <Probcause> 
        softwareError (47) <Alarmtype>
         processingErrorAlarm (4) <Polarity> 
        (2) 
        "
	  ::= { pmc1008mpAlmmodInitFailLevel2 5 }



pmc1008mpAlmResetHwInitFail OBJECT-TYPE
	  SYNTAX EkiOnOff
	  MAX-ACCESS read-only
	  STATUS current
	  DESCRIPTION
        "
        Reset HW Init Fail :This OID indicates 
        that the HW intialization has caused 
        unknown intial conditions  <Help> 
         This alarm indicates if the HW 
        has been correctly initialized
         <Condtype> RESET_HW_INIT_FAIL
         <Probcause> softwareError (47) 
        <Alarmtype> processingErrorAlarm 
        (4) <Polarity> (2) 
        "
	  ::= { pmc1008mpAlmmodInitFailLevel2 4 }



pmc1008mpAlmBootUndone OBJECT-TYPE
	  SYNTAX EkiOnOff
	  MAX-ACCESS read-only
	  STATUS current
	  DESCRIPTION
        "
        Boot Undone :This OID indicates 
        that the boot has not been correctly 
        achieved  <Help>  This alarm indicates 
        if the module has correctly boot 
        <Condtype> BOOT_UNDONE <Probcause> 
        softwareError (47) <Alarmtype>
         processingErrorAlarm (4) <Polarity> 
        (2) 
        "
	  ::= { pmc1008mpAlmmodInitFailLevel2 3 }



pmc1008mpAlmNextColdBootForced OBJECT-TYPE
	  SYNTAX EkiOnOff
	  MAX-ACCESS read-only
	  STATUS current
	  DESCRIPTION
        "
        Next Cold Boot Forced :This OID 
        indicates that the next Reset will 
        be forced Cold  <Help>  This alarm 
        indicates that the next reset of 
        the module will be forced to cold 
        reset <Condtype> NEXT_COLD_BOOT_FORCED 
        <Probcause> informationalStatus(1000) 
        <Alarmtype> other (1) <Polarity> 
        (2) 
        "
	  ::= { pmc1008mpAlmmodInitFailLevel2 2 }



pmc1008mpAlmLedFail OBJECT-TYPE
	  SYNTAX EkiOnOff
	  MAX-ACCESS read-only
	  STATUS current
	  DESCRIPTION
        "
        Led Fail :This OID indicates that 
        Led register has not been correctly 
        initalized  <Help>  This alarm
         indicates if the module LEDs are 
        correctly initialized <Condtype> 
        LED_FAIL <Probcause> softwareError 
        (47) <Alarmtype> processingErrorAlarm 
        (4) <Polarity> (2) 
        "
	  ::= { pmc1008mpAlmmodInitFailLevel2 1 }



--- *****************************************************
---     LEAF for the modInitFailLevel3 article
--- *****************************************************
pmc1008mpAlmmodInitFailLevel3 OBJECT IDENTIFIER ::= { pmc1008mpAlmOtherUrg 195 }




pmc1008mpAlmClient8InitFail OBJECT-TYPE
	  SYNTAX EkiOnOff
	  MAX-ACCESS read-only
	  STATUS current
	  DESCRIPTION
        "
        Client8 Init Fail :This OID indicates 
        that Client 8 registers subset
         has not been correctly initialized 
         <Help>  This alarm indicates if 
        the client port 8 is correctly
         initialized <Condtype> CLIENT8_INIT_FAIL 
        <Probcause> softwareError (47)
         <Alarmtype> processingErrorAlarm 
        (4) <Polarity> (2) 
        "
	  ::= { pmc1008mpAlmmodInitFailLevel3 16 }



pmc1008mpAlmClient7InitFail OBJECT-TYPE
	  SYNTAX EkiOnOff
	  MAX-ACCESS read-only
	  STATUS current
	  DESCRIPTION
        "
        Client7 Init Fail :This OID indicates 
        that Client 7 registers subset
         has not been correctly initialized 
         <Help>  This alarm indicates if 
        the client port 7 is correctly
         initialized <Condtype> CLIENT7_INIT_FAIL 
        <Probcause> softwareError (47)
         <Alarmtype> processingErrorAlarm 
        (4) <Polarity> (2) 
        "
	  ::= { pmc1008mpAlmmodInitFailLevel3 15 }



pmc1008mpAlmClient6InitFail OBJECT-TYPE
	  SYNTAX EkiOnOff
	  MAX-ACCESS read-only
	  STATUS current
	  DESCRIPTION
        "
        Client6 Init Fail :This OID indicates 
        that Client 6 registers subset
         has not been correctly initialized 
         <Help>  This alarm indicates if 
        the client port 6 is correctly
         initialized <Condtype> CLIENT6_INIT_FAIL 
        <Probcause> softwareError (47)
         <Alarmtype> processingErrorAlarm 
        (4) <Polarity> (2) 
        "
	  ::= { pmc1008mpAlmmodInitFailLevel3 14 }



pmc1008mpAlmClient5InitFail OBJECT-TYPE
	  SYNTAX EkiOnOff
	  MAX-ACCESS read-only
	  STATUS current
	  DESCRIPTION
        "
        Client5 Init Fail :This OID indicates 
        that Client 5 registers subset
         has not been correctly initialized 
         <Help>  This alarm indicates if 
        the client port 5 is correctly
         initialized <Condtype> CLIENT5_INIT_FAIL 
        <Probcause> softwareError (47)
         <Alarmtype> processingErrorAlarm 
        (4) <Polarity> (2) 
        "
	  ::= { pmc1008mpAlmmodInitFailLevel3 13 }



pmc1008mpAlmClient4InitFail OBJECT-TYPE
	  SYNTAX EkiOnOff
	  MAX-ACCESS read-only
	  STATUS current
	  DESCRIPTION
        "
        Client4 Init Fail :This OID indicates 
        that Client 4 registers subset
         has not been correctly initialized 
         <Help>  This alarm indicates if 
        the client port 4 is correctly
         initialized <Condtype> CLIENT4_INIT_FAIL 
        <Probcause> softwareError (47)
         <Alarmtype> processingErrorAlarm 
        (4) <Polarity> (2) 
        "
	  ::= { pmc1008mpAlmmodInitFailLevel3 12 }



pmc1008mpAlmClient3InitFail OBJECT-TYPE
	  SYNTAX EkiOnOff
	  MAX-ACCESS read-only
	  STATUS current
	  DESCRIPTION
        "
        Client3 Init Fail :This OID indicates 
        that Client 3 registers subset
         has not been correctly initialized 
         <Help>  This alarm indicates if 
        the client port 3 is correctly
         initialized <Condtype> CLIENT3_INIT_FAIL 
        <Probcause> softwareError (47)
         <Alarmtype> processingErrorAlarm 
        (4) <Polarity> (2) 
        "
	  ::= { pmc1008mpAlmmodInitFailLevel3 11 }



pmc1008mpAlmClient2InitFail OBJECT-TYPE
	  SYNTAX EkiOnOff
	  MAX-ACCESS read-only
	  STATUS current
	  DESCRIPTION
        "
        Client2 Init Fail :This OID indicates 
        that Client 2 registers subset
         has not been correctly initialized 
         <Help>  This alarm indicates if 
        the client port 2 is correctly
         initialized <Condtype> CLIENT2_INIT_FAIL 
        <Probcause> softwareError (47)
         <Alarmtype> processingErrorAlarm 
        (4) <Polarity> (2) 
        "
	  ::= { pmc1008mpAlmmodInitFailLevel3 10 }



pmc1008mpAlmClient1InitFail OBJECT-TYPE
	  SYNTAX EkiOnOff
	  MAX-ACCESS read-only
	  STATUS current
	  DESCRIPTION
        "
        Client1 Init Fail :This OID indicates 
        that Client 1 registers subset
         has not been correctly initialized 
         <Help>  This alarm indicates if 
        the client port 1 is correctly
         initialized <Condtype> CLIENT1_INIT_FAIL 
        <Probcause> softwareError (47)
         <Alarmtype> processingErrorAlarm 
        (4) <Polarity> (2) 
        "
	  ::= { pmc1008mpAlmmodInitFailLevel3 9 }



pmc1008mpAlmLine2InitFail OBJECT-TYPE
	  SYNTAX EkiOnOff
	  MAX-ACCESS read-only
	  STATUS current
	  DESCRIPTION
        "
        Line2 Init Fail :This OID indicates 
        that the Line register subset has 
        not been correctly initialized
          <Help>  This alarm indicates
         if the line port 2 is correctly 
        initialized <Condtype> LINE2_INIT_FAIL 
        <Probcause> softwareError (47)
         <Alarmtype> processingErrorAlarm 
        (4) <Polarity> (2) 
        "
	  ::= { pmc1008mpAlmmodInitFailLevel3 8 }



pmc1008mpAlmLine1InitFail OBJECT-TYPE
	  SYNTAX EkiOnOff
	  MAX-ACCESS read-only
	  STATUS current
	  DESCRIPTION
        "
        Line1 Init Fail :This OID indicates 
        that the Line registersvsubset
         has not been correctly initialized 
         <Help>  This alarm indicates if 
        the line port 1 is correctly initialized 
        <Condtype> LINE1_INIT_FAIL <Probcause> 
        softwareError (47) <Alarmtype>
         processingErrorAlarm (4) <Polarity> 
        (2) 
        "
	  ::= { pmc1008mpAlmmodInitFailLevel3 7 }



pmc1008mpAlmXfp2InitFail OBJECT-TYPE
	  SYNTAX EkiOnOff
	  MAX-ACCESS read-only
	  STATUS current
	  DESCRIPTION
        "
        XFP2 Init Fail :This OID indicates 
        that the XFP has not been correctly 
        initialized  <Help>  This alarm 
        indicates if the line transceiver 
        2 is correctly initialized <Condtype> 
        XFP2_INIT_FAIL <Probcause> softwareError 
        (47) <Alarmtype> processingErrorAlarm 
        (4) <Polarity> (2) 
        "
	  ::= { pmc1008mpAlmmodInitFailLevel3 6 }



pmc1008mpAlmXfp1InitFail OBJECT-TYPE
	  SYNTAX EkiOnOff
	  MAX-ACCESS read-only
	  STATUS current
	  DESCRIPTION
        "
        XFP1 Init Fail :This OID indicates 
        that the XFP has not been correctly 
        initialized  <Help>  This alarm 
        indicates if the line transceiver 
        1 is correctly initialized <Condtype> 
        XFP1_INIT_FAIL <Probcause> softwareError 
        (47) <Alarmtype> processingErrorAlarm 
        (4) <Polarity> (2) 
        "
	  ::= { pmc1008mpAlmmodInitFailLevel3 5 }



pmc1008mpAlmInitModuleFail OBJECT-TYPE
	  SYNTAX EkiOnOff
	  MAX-ACCESS read-only
	  STATUS current
	  DESCRIPTION
        "
        Init Module Fail :This OID indicates 
        that the Module has not been correctly 
        initialized  <Help>  This alarm 
        indicates if the SW module is correctly 
        initialized <Condtype> INIT_MODULE_FAIL 
        <Probcause> softwareError (47)
         <Alarmtype> processingErrorAlarm 
        (4) <Polarity> (2) 
        "
	  ::= { pmc1008mpAlmmodInitFailLevel3 3 }



pmc1008mpAlmObmTypeReadFail OBJECT-TYPE
	  SYNTAX EkiOnOff
	  MAX-ACCESS read-only
	  STATUS current
	  DESCRIPTION
        "
        OBM Type Read Fail :This OID indicates 
        that OBM type has not been recognized 
         <Help>  This alarm indicates if 
        the OBM board has been correctly 
        identified <Condtype> OBM_TYPE_READ_FAIL 
        <Probcause> softwareError (47)
         <Alarmtype> processingErrorAlarm 
        (4) <Polarity> (2) 
        "
	  ::= { pmc1008mpAlmmodInitFailLevel3 2 }



pmc1008mpAlmGwIdentFail OBJECT-TYPE
	  SYNTAX EkiOnOff
	  MAX-ACCESS read-only
	  STATUS current
	  DESCRIPTION
        "
        GW Ident Fail :This OID indicates 
        that GW identification has not
         been read  <Help>  This alarm
         indicates if the GW has been correctly 
        identified <Condtype> GW_IDENT_FAIL 
        <Probcause> softwareError (47)
         <Alarmtype> processingErrorAlarm 
        (4) <Polarity> (2) 
        "
	  ::= { pmc1008mpAlmmodInitFailLevel3 1 }



--- *****************************************************
---     LEAF for the adddropTsClientRxProt article
--- *****************************************************
pmc1008mpAlmadddropTsClientRxProt OBJECT IDENTIFIER ::= { pmc1008mpAlmOtherUrg 198 }




pmc1008mpAlmAdddropClient8East OBJECT-TYPE
	  SYNTAX EkiOnOff
	  MAX-ACCESS read-only
	  STATUS current
	  DESCRIPTION
        "
        Client 8 East Rx Side Active :This 
        OID indicates the Client #8 is
         active on East receiving side
         <Condtype> ADDDROP_CLIENT8_EAST 
        <Probcause> other (1) <Alarmtype> 
        other (1) <Polarity> (2) 
        "
	  ::= { pmc1008mpAlmadddropTsClientRxProt 16 }



pmc1008mpAlmAdddropClient7East OBJECT-TYPE
	  SYNTAX EkiOnOff
	  MAX-ACCESS read-only
	  STATUS current
	  DESCRIPTION
        "
        Client 7 East Rx Side Active :This 
        OID indicates the Client #7 is
         active on East receiving side
         <Condtype> ADDDROP_CLIENT7_EAST 
        <Probcause> other (1) <Alarmtype> 
        other (1) <Polarity> (2) 
        "
	  ::= { pmc1008mpAlmadddropTsClientRxProt 15 }



pmc1008mpAlmAdddropClient6East OBJECT-TYPE
	  SYNTAX EkiOnOff
	  MAX-ACCESS read-only
	  STATUS current
	  DESCRIPTION
        "
        Client 6 East Rx Side Active :This 
        OID indicates the Client #6 is
         active on East receiving side
         <Condtype> ADDDROP_CLIENT6_EAST 
        <Probcause> other (1) <Alarmtype> 
        other (1) <Polarity> (2) 
        "
	  ::= { pmc1008mpAlmadddropTsClientRxProt 14 }



pmc1008mpAlmAdddropClient5East OBJECT-TYPE
	  SYNTAX EkiOnOff
	  MAX-ACCESS read-only
	  STATUS current
	  DESCRIPTION
        "
        Client 5 East Rx Side Active :This 
        OID indicates the Client #5 is
         active on East receiving side
         <Condtype> ADDDROP_CLIENT5_EAST 
        <Probcause> other (1) <Alarmtype> 
        other (1) <Polarity> (2) 
        "
	  ::= { pmc1008mpAlmadddropTsClientRxProt 13 }



pmc1008mpAlmAdddropClient4East OBJECT-TYPE
	  SYNTAX EkiOnOff
	  MAX-ACCESS read-only
	  STATUS current
	  DESCRIPTION
        "
        Client 4 East Rx Side Active :This 
        OID indicates the Client #4 is
         active on East receiving side
         <Condtype> ADDDROP_CLIENT4_EAST 
        <Probcause> other (1) <Alarmtype> 
        other (1) <Polarity> (2) 
        "
	  ::= { pmc1008mpAlmadddropTsClientRxProt 12 }



pmc1008mpAlmAdddropClient3East OBJECT-TYPE
	  SYNTAX EkiOnOff
	  MAX-ACCESS read-only
	  STATUS current
	  DESCRIPTION
        "
        Client 3 East Rx Side Active :This 
        OID indicates the Client #3 is
         active on East receiving side
         <Condtype> ADDDROP_CLIENT3_EAST 
        <Probcause> other (1) <Alarmtype> 
        other (1) <Polarity> (2) 
        "
	  ::= { pmc1008mpAlmadddropTsClientRxProt 11 }



pmc1008mpAlmAdddropClient2East OBJECT-TYPE
	  SYNTAX EkiOnOff
	  MAX-ACCESS read-only
	  STATUS current
	  DESCRIPTION
        "
        Client 2 East Rx Side Active :This 
        OID indicates the Client #2 is
         active on East receiving side
         <Condtype> ADDDROP_CLIENT2_EAST 
        <Probcause> other (1) <Alarmtype> 
        other (1) <Polarity> (2) 
        "
	  ::= { pmc1008mpAlmadddropTsClientRxProt 10 }



pmc1008mpAlmAdddropClient1East OBJECT-TYPE
	  SYNTAX EkiOnOff
	  MAX-ACCESS read-only
	  STATUS current
	  DESCRIPTION
        "
        Client 1 East Rx Side Active :This 
        OID indicates the Client #1 is
         active on East receiving side
         <Condtype> ADDDROP_CLIENT1_EAST 
        <Probcause> other (1) <Alarmtype> 
        other (1) <Polarity> (2) 
        "
	  ::= { pmc1008mpAlmadddropTsClientRxProt 9 }



pmc1008mpAlmAdddropClient8West OBJECT-TYPE
	  SYNTAX EkiOnOff
	  MAX-ACCESS read-only
	  STATUS current
	  DESCRIPTION
        "
        Client 8 West Rx Side Active :This 
        OID indicates the Client #8 is
         active on West receiving side
         <Condtype> ADDDROP_CLIENT8_WEST 
        <Probcause> other (1) <Alarmtype> 
        other (1) <Polarity> (2) 
        "
	  ::= { pmc1008mpAlmadddropTsClientRxProt 8 }



pmc1008mpAlmAdddropClient7West OBJECT-TYPE
	  SYNTAX EkiOnOff
	  MAX-ACCESS read-only
	  STATUS current
	  DESCRIPTION
        "
        Client 7 West Rx Side Active :This 
        OID indicates the Client #7 is
         active on West receiving side
         <Condtype> ADDDROP_CLIENT7_WEST 
        <Probcause> other (1) <Alarmtype> 
        other (1) <Polarity> (2) 
        "
	  ::= { pmc1008mpAlmadddropTsClientRxProt 7 }



pmc1008mpAlmAdddropClient6West OBJECT-TYPE
	  SYNTAX EkiOnOff
	  MAX-ACCESS read-only
	  STATUS current
	  DESCRIPTION
        "
        Client 6 West Rx Side Active :This 
        OID indicates the Client #6 is
         active on West receiving side
         <Condtype> ADDDROP_CLIENT6_WEST 
        <Probcause> other (1) <Alarmtype> 
        other (1) <Polarity> (2) 
        "
	  ::= { pmc1008mpAlmadddropTsClientRxProt 6 }



pmc1008mpAlmAdddropClient5West OBJECT-TYPE
	  SYNTAX EkiOnOff
	  MAX-ACCESS read-only
	  STATUS current
	  DESCRIPTION
        "
        Client 5 West Rx Side Active :This 
        OID indicates the Client #5 is
         active on West receiving side
         <Condtype> ADDDROP_CLIENT5_WEST 
        <Probcause> other (1) <Alarmtype> 
        other (1) <Polarity> (2) 
        "
	  ::= { pmc1008mpAlmadddropTsClientRxProt 5 }



pmc1008mpAlmAdddropClient4West OBJECT-TYPE
	  SYNTAX EkiOnOff
	  MAX-ACCESS read-only
	  STATUS current
	  DESCRIPTION
        "
        Client 4 West Rx Side Active :This 
        OID indicates the Client #4 is
         active on West receiving side
         <Condtype> ADDDROP_CLIENT4_WEST 
        <Probcause> other (1) <Alarmtype> 
        other (1) <Polarity> (2) 
        "
	  ::= { pmc1008mpAlmadddropTsClientRxProt 4 }



pmc1008mpAlmAdddropClient3West OBJECT-TYPE
	  SYNTAX EkiOnOff
	  MAX-ACCESS read-only
	  STATUS current
	  DESCRIPTION
        "
        Client 3 West Rx Side Active :This 
        OID indicates the Client #3 is
         active on West receiving side
         <Condtype> ADDDROP_CLIENT3_WEST 
        <Probcause> other (1) <Alarmtype> 
        other (1) <Polarity> (2) 
        "
	  ::= { pmc1008mpAlmadddropTsClientRxProt 3 }



pmc1008mpAlmAdddropClient2West OBJECT-TYPE
	  SYNTAX EkiOnOff
	  MAX-ACCESS read-only
	  STATUS current
	  DESCRIPTION
        "
        Client 2 West Rx Side Active :This 
        OID indicates the Client #2 is
         active on West receiving side
         <Condtype> ADDDROP_CLIENT2_WEST 
        <Probcause> other (1) <Alarmtype> 
        other (1) <Polarity> (2) 
        "
	  ::= { pmc1008mpAlmadddropTsClientRxProt 2 }



pmc1008mpAlmAdddropClient1West OBJECT-TYPE
	  SYNTAX EkiOnOff
	  MAX-ACCESS read-only
	  STATUS current
	  DESCRIPTION
        "
        Client 1 West Rx Side Active :This 
        OID indicates the Client #1 is
         active on West receiving side
         <Condtype> ADDDROP_CLIENT1_WEST 
        <Probcause> other (1) <Alarmtype> 
        other (1) <Polarity> (2) 
        "
	  ::= { pmc1008mpAlmadddropTsClientRxProt 1 }



--- *********************************************************
---     TABLE for the pmc1008mpAlmlineXfp1Alarm articles
--- *********************************************************

pmc1008mpAlmlineXfp1AlarmTable OBJECT-TYPE
	SYNTAX  SEQUENCE OF Pmc1008mpAlmlineXfp1AlarmEntry
	MAX-ACCESS not-accessible
	STATUS current
	DESCRIPTION
        "
        List of pmc1008mpAlmlineXfp1Alarm 
        Article
        "
	::= { pmc1008mpAlmLineUrg 208 }


pmc1008mpAlmlineXfp1AlarmEntry OBJECT-TYPE
	SYNTAX Pmc1008mpAlmlineXfp1AlarmEntry
	MAX-ACCESS not-accessible
	STATUS current
	DESCRIPTION
        "
        Row definition for the pmc1008mpAlmlineXfp1Alarm 
        table
        "
	INDEX   { pmc1008mpAlmlineXfp1AlarmIndex }
	::= { pmc1008mpAlmlineXfp1AlarmTable 1 }


Pmc1008mpAlmlineXfp1AlarmEntry ::=
	SEQUENCE {
	pmc1008mpAlmlineXfp1AlarmIndex
		INTEGER,
	pmc1008mpAlmRxPowerHighAlarmPortn
		EkiOnOff,
	pmc1008mpAlmRxPowerLowAlarmPortn
		EkiOnOff,
	pmc1008mpAlmTempHighAlarmPortn
		EkiOnOff,
	pmc1008mpAlmTempLowAlarmPortn
		EkiOnOff,
	pmc1008mpAlmTxBiasHighAlarmPortn
		EkiOnOff,
	pmc1008mpAlmTxBiasLowAlarmPortn
		EkiOnOff,
	pmc1008mpAlmTxPowerHighAlarmPortn
		EkiOnOff,
	pmc1008mpAlmTxPowerLowAlarmPortn
		EkiOnOff
	}


pmc1008mpAlmlineXfp1AlarmIndex OBJECT-TYPE
	SYNTAX  INTEGER(0..128)
	MAX-ACCESS  read-only
	STATUS current
	DESCRIPTION
        "
        Index definition for the pmc1008mpAlmlineXfp1Alarm 
        table
        "
	::= { pmc1008mpAlmlineXfp1AlarmEntry 1 }


pmc1008mpAlmRxPowerHighAlarmPortn OBJECT-TYPE
	SYNTAX  EkiOnOff
	MAX-ACCESS read-only
	STATUS current
	DESCRIPTION
        "
        Line Optical Rx Power High :Alarm 
        indicating that the XFP received 
        optical power is higher than the 
        threshold value written in the
         XFP EEPROM <Condtype> RX_POWER_HIGH_ALARM_1 
        <Probcause> receiveFailure (41) 
        <Alarmtype> equipmentAlarm (5)
         <Polarity> (2) 
        "
	::= { pmc1008mpAlmlineXfp1AlarmEntry 17 }


pmc1008mpAlmRxPowerLowAlarmPortn OBJECT-TYPE
	SYNTAX  EkiOnOff
	MAX-ACCESS read-only
	STATUS current
	DESCRIPTION
        "
        Line Optical Rx Power Low :Alarm 
        indicating that the XFP received 
        optical power is lower than the 
        threshold value written in the
         XFP EEPROM  <Condtype> RX_POWER_LOW_ALARM_1 
        <Probcause> receiveFailure (41) 
        <Alarmtype> equipmentAlarm (5)
         <Polarity> (2) 
        "
	::= { pmc1008mpAlmlineXfp1AlarmEntry 16 }


pmc1008mpAlmTempHighAlarmPortn OBJECT-TYPE
	SYNTAX  EkiOnOff
	MAX-ACCESS read-only
	STATUS current
	DESCRIPTION
        "
        Line Transceiver Temp High :Alarm 
        indicating that the XFP/OTX temperature 
        is higher than the threshold value 
        written in the XFP EEPROM <Condtype> 
        TEMP_HIGH_ALARM_1 <Probcause> temperatureUnacceptable 
        (51) <Alarmtype> equipmentAlarm 
        (5) <Polarity> (2) 
        "
	::= { pmc1008mpAlmlineXfp1AlarmEntry 9 }


pmc1008mpAlmTempLowAlarmPortn OBJECT-TYPE
	SYNTAX  EkiOnOff
	MAX-ACCESS read-only
	STATUS current
	DESCRIPTION
        "
        Line Transceiver Temp Low :Alarm 
        indicating that the XFP/OTX temperature 
        is lower than the threshold value 
        written in the XFP/OTX EEPROM <Condtype> 
        TEMP_LOW_ALARM_1 <Probcause> temperatureUnacceptable 
        (51) <Alarmtype> equipmentAlarm 
        (5) <Polarity> (2) 
        "
	::= { pmc1008mpAlmlineXfp1AlarmEntry 8 }


pmc1008mpAlmTxBiasHighAlarmPortn OBJECT-TYPE
	SYNTAX  EkiOnOff
	MAX-ACCESS read-only
	STATUS current
	DESCRIPTION
        "
        Line Transceiver Bias High :Alarm 
        indicating that the XFP/OTX transmitter 
        laser bias current is higher than 
        the threshold value written in
         the XFP EEPROM <Condtype> TX_BIAS_HIGH_ALARM_1 
        <Probcause> transmitterFailure
         (56) <Alarmtype> equipmentAlarm 
        (5) <Polarity> (2) 
        "
	::= { pmc1008mpAlmlineXfp1AlarmEntry 5 }


pmc1008mpAlmTxBiasLowAlarmPortn OBJECT-TYPE
	SYNTAX  EkiOnOff
	MAX-ACCESS read-only
	STATUS current
	DESCRIPTION
        "
        Line Transceiver Bias Low :Alarm 
        indicating that the XFP/OTX transmitter 
        laser bias current is lower than 
        the threshold value written in
         the XFP/OTX EEPROM <Condtype>
         TX_BIAS_LOW_ALARM_1 <Probcause> 
        transmitterFailure (56) <Alarmtype> 
        equipmentAlarm (5) <Polarity> (2) 
        "
	::= { pmc1008mpAlmlineXfp1AlarmEntry 4 }


pmc1008mpAlmTxPowerHighAlarmPortn OBJECT-TYPE
	SYNTAX  EkiOnOff
	MAX-ACCESS read-only
	STATUS current
	DESCRIPTION
        "
        Line Optical Tx Power High :Alarm 
        indicating that the XFP/OTX transmitter 
        transmitter output power is higher 
        than the threshold value written 
        in the XFP EEPROM <Condtype> TX_POWER_HIGH_ALARM_1 
        <Probcause> transmitterFailure
         (56) <Alarmtype> equipmentAlarm 
        (5) <Polarity> (2) 
        "
	::= { pmc1008mpAlmlineXfp1AlarmEntry 3 }


pmc1008mpAlmTxPowerLowAlarmPortn OBJECT-TYPE
	SYNTAX  EkiOnOff
	MAX-ACCESS read-only
	STATUS current
	DESCRIPTION
        "
        Line Optical Tx Power Low :Alarm 
        indicating that the XFP/OTX transmitter 
        transmitter output power is lower 
        than the threshold value written 
        in the XFP/OTX EEPROM <Condtype> 
        TX_POWER_LOW_ALARM_1 <Probcause> 
        transmitterFailure (56) <Alarmtype> 
        equipmentAlarm (5) <Polarity> (2) 
        "
	::= { pmc1008mpAlmlineXfp1AlarmEntry 2 }


--- *********************************************************
---     TABLE for the pmc1008mpAlmlineXfp1Warnings articles
--- *********************************************************

pmc1008mpAlmlineXfp1WarningsTable OBJECT-TYPE
	SYNTAX  SEQUENCE OF Pmc1008mpAlmlineXfp1WarningsEntry
	MAX-ACCESS not-accessible
	STATUS current
	DESCRIPTION
        "
        List of pmc1008mpAlmlineXfp1Warnings 
        Article
        "
	::= { pmc1008mpAlmLineNurg 209 }


pmc1008mpAlmlineXfp1WarningsEntry OBJECT-TYPE
	SYNTAX Pmc1008mpAlmlineXfp1WarningsEntry
	MAX-ACCESS not-accessible
	STATUS current
	DESCRIPTION
        "
        Row definition for the pmc1008mpAlmlineXfp1Warnings 
        table
        "
	INDEX   { pmc1008mpAlmlineXfp1WarningsIndex }
	::= { pmc1008mpAlmlineXfp1WarningsTable 1 }


Pmc1008mpAlmlineXfp1WarningsEntry ::=
	SEQUENCE {
	pmc1008mpAlmlineXfp1WarningsIndex
		INTEGER,
	pmc1008mpAlmRxPowerHighWarningPortn
		EkiOnOff,
	pmc1008mpAlmRxPowerLowWarningPortn
		EkiOnOff,
	pmc1008mpAlmTempHighWarningPortn
		EkiOnOff,
	pmc1008mpAlmTempLowWarningPortn
		EkiOnOff,
	pmc1008mpAlmTxBiasHighWarningPortn
		EkiOnOff,
	pmc1008mpAlmTxBiasLowWarningPortn
		EkiOnOff,
	pmc1008mpAlmTxPowerHighWarningPortn
		EkiOnOff,
	pmc1008mpAlmTxPowerLowWarningPortn
		EkiOnOff
	}


pmc1008mpAlmlineXfp1WarningsIndex OBJECT-TYPE
	SYNTAX  INTEGER(0..128)
	MAX-ACCESS  read-only
	STATUS current
	DESCRIPTION
        "
        Index definition for the pmc1008mpAlmlineXfp1Warnings 
        table
        "
	::= { pmc1008mpAlmlineXfp1WarningsEntry 1 }


pmc1008mpAlmRxPowerHighWarningPortn OBJECT-TYPE
	SYNTAX  EkiOnOff
	MAX-ACCESS read-only
	STATUS current
	DESCRIPTION
        "
        Line Optical Rx Power High Warning 
        :Warning indicating that the XFP 
        received optical power is higher 
        than the threshold value written 
        in the XFP EEPROM <Condtype> RX_POWER_HIGH_WARNING_1 
        <Probcause> receiveFailure (41) 
        <Alarmtype> equipmentAlarm (5)
         <Polarity> (2) 
        "
	::= { pmc1008mpAlmlineXfp1WarningsEntry 17 }


pmc1008mpAlmRxPowerLowWarningPortn OBJECT-TYPE
	SYNTAX  EkiOnOff
	MAX-ACCESS read-only
	STATUS current
	DESCRIPTION
        "
        Line Optical Rx Power Low Warning 
        :Warning indicating that the XFP 
        received optical power is lower 
        than the threshold value written 
        in the XFP EEPROM  <Condtype> RX_POWER_LOW_WARNING_1 
        <Probcause> receiveFailure (41) 
        <Alarmtype> equipmentAlarm (5)
         <Polarity> (2) 
        "
	::= { pmc1008mpAlmlineXfp1WarningsEntry 16 }


pmc1008mpAlmTempHighWarningPortn OBJECT-TYPE
	SYNTAX  EkiOnOff
	MAX-ACCESS read-only
	STATUS current
	DESCRIPTION
        "
        Line Transceiver Temp High Warning 
        :Warning indicating that the XFP/OTX 
        temperature is higher than the
         threshold value written in the 
        XFP EEPROM <Condtype> TEMP_HIGH_WARNING_1 
        <Probcause> temperatureUnacceptable 
        (51) <Alarmtype> equipmentAlarm 
        (5) <Polarity> (2) 
        "
	::= { pmc1008mpAlmlineXfp1WarningsEntry 9 }


pmc1008mpAlmTempLowWarningPortn OBJECT-TYPE
	SYNTAX  EkiOnOff
	MAX-ACCESS read-only
	STATUS current
	DESCRIPTION
        "
        Line Transceiver Temp Low Warning 
        :Warning indicating that the XFP/OTX 
        temperature is lower than the threshold 
        value written in the XFP/OTX EEPROM 
        <Condtype> TEMP_LOW_WARNING_1 <Probcause> 
        temperatureUnacceptable (51) <Alarmtype> 
        equipmentAlarm (5) <Polarity> (2) 
        "
	::= { pmc1008mpAlmlineXfp1WarningsEntry 8 }


pmc1008mpAlmTxBiasHighWarningPortn OBJECT-TYPE
	SYNTAX  EkiOnOff
	MAX-ACCESS read-only
	STATUS current
	DESCRIPTION
        "
        Line Transceiver Bias High Warning 
        :Warning indicating that the XFP/OTX 
        transmitter laser bias current
         is higher than the threshold value 
        written in the XFP EEPROM <Condtype> 
        TX_BIAS_HIGH_WARNING_1 <Probcause> 
        transmitterFailure (56) <Alarmtype> 
        equipmentAlarm (5) <Polarity> (2) 
        "
	::= { pmc1008mpAlmlineXfp1WarningsEntry 5 }


pmc1008mpAlmTxBiasLowWarningPortn OBJECT-TYPE
	SYNTAX  EkiOnOff
	MAX-ACCESS read-only
	STATUS current
	DESCRIPTION
        "
        Line Transceiver Bias Low Warning 
        :Warning indicating that the XFP/OTX 
        transmitter laser bias current
         is lower than the threshold value 
        written in the XFP/OTX EEPROM <Condtype> 
        TX_BIAS_LOW_WARNING_1 <Probcause> 
        transmitterFailure (56) <Alarmtype> 
        equipmentAlarm (5) <Polarity> (2) 
        "
	::= { pmc1008mpAlmlineXfp1WarningsEntry 4 }


pmc1008mpAlmTxPowerHighWarningPortn OBJECT-TYPE
	SYNTAX  EkiOnOff
	MAX-ACCESS read-only
	STATUS current
	DESCRIPTION
        "
        Line Optical Tx Power High Warning 
        :Warning indicating that the XFP/OTX 
        transmitter transmitter output
         power is higher than the threshold 
        value written in the XFP EEPROM 
        <Condtype> TX_POWER_HIGH_WARNING_1 
        <Probcause> transmitterFailure
         (56) <Alarmtype> equipmentAlarm 
        (5) <Polarity> (2) 
        "
	::= { pmc1008mpAlmlineXfp1WarningsEntry 3 }


pmc1008mpAlmTxPowerLowWarningPortn OBJECT-TYPE
	SYNTAX  EkiOnOff
	MAX-ACCESS read-only
	STATUS current
	DESCRIPTION
        "
        Line Optical Tx Power Low Warning 
        :Warning indicating that the XFP/OTX 
        transmitter transmitter output
         power is lower than the threshold 
        value written in the XFP/OTX EEPROM 
        <Condtype> TX_POWER_LOW_WARNING_1 
        <Probcause> transmitterFailure
         (56) <Alarmtype> equipmentAlarm 
        (5) <Polarity> (2) 
        "
	::= { pmc1008mpAlmlineXfp1WarningsEntry 2 }


--- *********************************************************
---     TABLE for the pmc1008mpAlmlineXfp1Alarms articles
--- *********************************************************

pmc1008mpAlmlineXfp1AlarmsTable OBJECT-TYPE
	SYNTAX  SEQUENCE OF Pmc1008mpAlmlineXfp1AlarmsEntry
	MAX-ACCESS not-accessible
	STATUS current
	DESCRIPTION
        "
        List of pmc1008mpAlmlineXfp1Alarms 
        Article
        "
	::= { pmc1008mpAlmLineCrit 211 }


pmc1008mpAlmlineXfp1AlarmsEntry OBJECT-TYPE
	SYNTAX Pmc1008mpAlmlineXfp1AlarmsEntry
	MAX-ACCESS not-accessible
	STATUS current
	DESCRIPTION
        "
        Row definition for the pmc1008mpAlmlineXfp1Alarms 
        table
        "
	INDEX   { pmc1008mpAlmlineXfp1AlarmsIndex }
	::= { pmc1008mpAlmlineXfp1AlarmsTable 1 }


Pmc1008mpAlmlineXfp1AlarmsEntry ::=
	SEQUENCE {
	pmc1008mpAlmlineXfp1AlarmsIndex
		INTEGER,
	pmc1008mpAlmApdSupplyFaultPortn
		EkiOnOff,
	pmc1008mpAlmTecFaultPortn
		EkiOnOff,
	pmc1008mpAlmWavelengthUnlockedPortn
		EkiOnOff,
	pmc1008mpAlmChannelNotAcquiredPortn
		EkiOnOff,
	pmc1008mpAlmTxNrPortn
		EkiOnOff,
	pmc1008mpAlmTxFaultPortn
		EkiOnOff,
	pmc1008mpAlmTxCdrNotLockedPortn
		EkiOnOff,
	pmc1008mpAlmRxNrPortn
		EkiOnOff,
	pmc1008mpAlmRxCdrNotLockedPortn
		EkiOnOff,
	pmc1008mpAlmModNrPortn
		EkiOnOff
	}


pmc1008mpAlmlineXfp1AlarmsIndex OBJECT-TYPE
	SYNTAX  INTEGER(0..128)
	MAX-ACCESS  read-only
	STATUS current
	DESCRIPTION
        "
        Index definition for the pmc1008mpAlmlineXfp1Alarms 
        table
        "
	::= { pmc1008mpAlmlineXfp1AlarmsEntry 1 }


pmc1008mpAlmApdSupplyFaultPortn OBJECT-TYPE
	SYNTAX  EkiOnOff
	MAX-ACCESS read-only
	STATUS current
	DESCRIPTION
        "
        Line Rx Photodiode Power Failed 
        :This OID indicates a failure on 
        the APD power supply  <Help>  This 
        alarm indicates if the APD power 
        supply is in fail condition <Condtype> 
        APD_SUPPLY_FAULT_1 <Probcause>
         receiverFailure (42) <Alarmtype> 
        equipmentAlarm (5) <Polarity> (2) 
        "
	::= { pmc1008mpAlmlineXfp1AlarmsEntry 17 }


pmc1008mpAlmTecFaultPortn OBJECT-TYPE
	SYNTAX  EkiOnOff
	MAX-ACCESS read-only
	STATUS current
	DESCRIPTION
        "
        Line Optical Tx Temp Regul Failed 
        :This OID indicates a failure on 
        the TEC module  <Help>  This alarm 
        indicates if the TEC of the line 
        transceiver is in fail condition 
        <Condtype> TEC_FAULT_1 <Probcause> 
        transmitterFailure (56) <Alarmtype> 
        equipmentAlarm (5) <Polarity> (2) 
        "
	::= { pmc1008mpAlmlineXfp1AlarmsEntry 16 }


pmc1008mpAlmWavelengthUnlockedPortn OBJECT-TYPE
	SYNTAX  EkiOnOff
	MAX-ACCESS read-only
	STATUS current
	DESCRIPTION
        "
        Line Optical Tx Wavelength Unlocked 
        :This OID indicates that the wavelength 
        error is exceeding the manufacturer 
        tolerance  <Help>  This alarm indicates 
        if the wavelenght of the line transceiver 
        is locked <Condtype> WAVELENGTH_UNLOCKED_1 
        <Probcause> transmitterFailure
         (56) <Alarmtype> equipmentAlarm 
        (5) <Polarity> (2) 
        "
	::= { pmc1008mpAlmlineXfp1AlarmsEntry 15 }


pmc1008mpAlmChannelNotAcquiredPortn OBJECT-TYPE
	SYNTAX  EkiOnOff
	MAX-ACCESS read-only
	STATUS current
	DESCRIPTION
        "
        DWDM Channel Not Acquired :This 
        OID indicates the transceiver didn't 
        tune the DWDM Channel succesfully. 
         <Help>  This status indicates
         the transceiver has not tuned
         the DWDM Channel succesfully.
         <Condtype> CHANNEL_NOT_ACQUIRED_1 
        <Probcause> equipmentMalfunction 
        (16) <Alarmtype> equipmentAlarm 
        (5) <Polarity> (2) 
        "
	::= { pmc1008mpAlmlineXfp1AlarmsEntry 11 }


pmc1008mpAlmTxNrPortn OBJECT-TYPE
	SYNTAX  EkiOnOff
	MAX-ACCESS read-only
	STATUS current
	DESCRIPTION
        "
        Line Optical Tx Not Ready :This 
        OID indicates a condition has arisen 
        leading to invalid data on the
         transmitting side  <Help>  This 
        alarm indicates if the Tx part
         of the line transceiver is ready 
        <Condtype> TX_NR_1 <Probcause>
         transmitterFailure (56) <Alarmtype> 
        equipmentAlarm (5) <Polarity> (2) 
        "
	::= { pmc1008mpAlmlineXfp1AlarmsEntry 9 }


pmc1008mpAlmTxFaultPortn OBJECT-TYPE
	SYNTAX  EkiOnOff
	MAX-ACCESS read-only
	STATUS current
	DESCRIPTION
        "
        Line Optical Tx Failure :This
         OID indicates a fault condition 
        on the laser detected by the safety 
        syste  <Help>  This alarm indicates 
        if the laser of the line transceiver 
        is in fail condition <Condtype> 
        TX_FAULT_1 <Probcause> transmitterFailure 
        (56) <Alarmtype> equipmentAlarm 
        (5) <Polarity> (2) 
        "
	::= { pmc1008mpAlmlineXfp1AlarmsEntry 8 }


pmc1008mpAlmTxCdrNotLockedPortn OBJECT-TYPE
	SYNTAX  EkiOnOff
	MAX-ACCESS read-only
	STATUS current
	DESCRIPTION
        "
        Line Optical Tx CDR Unlocked :This 
        OID indicates a loss of lock on 
        the transmitting side CDR has been 
        detected.  <Help>  This alarm indicates 
        if the Tx CDR is locked in the
         line transceiver <Condtype> TX_CDR_NOT_LOCKED1_1 
        <Probcause> transmitterFailure
         (56) <Alarmtype> equipmentAlarm 
        (5) <Polarity> (2) 
        "
	::= { pmc1008mpAlmlineXfp1AlarmsEntry 7 }


pmc1008mpAlmRxNrPortn OBJECT-TYPE
	SYNTAX  EkiOnOff
	MAX-ACCESS read-only
	STATUS current
	DESCRIPTION
        "
        Line Optical Rx Not Ready :This 
        OID indicates that a condition
         has arisen leading to invalid
         data on the receiving side.  <Help> 
         This alarm indicates if the Rx 
        part of the line transceiver is 
        ready <Condtype> RX_NR_1 <Probcause> 
        receiveFailure (41) <Alarmtype> 
        equipmentAlarm (5) <Polarity> (2) 
        "
	::= { pmc1008mpAlmlineXfp1AlarmsEntry 6 }


pmc1008mpAlmRxCdrNotLockedPortn OBJECT-TYPE
	SYNTAX  EkiOnOff
	MAX-ACCESS read-only
	STATUS current
	DESCRIPTION
        "
        Line Optical Rx CDR Unlocked :This 
        OID indicates that a loss of lock 
        on the receiving side CDR has been 
        detected  <Help>  This alarm indicates 
        if the Rx CDR is locked in the
         line transceiver <Condtype> RX_CDR_NOT_LOCKED1_1 
        <Probcause> receiveFailure (41) 
        <Alarmtype> equipmentAlarm (5)
         <Polarity> (2) 
        "
	::= { pmc1008mpAlmlineXfp1AlarmsEntry 4 }


pmc1008mpAlmModNrPortn OBJECT-TYPE
	SYNTAX  EkiOnOff
	MAX-ACCESS read-only
	STATUS current
	DESCRIPTION
        "
        Line Optical Module Not Ready
         :This OID indicates that the module 
        is unable to determine correct
         data.  <Help>  This alarm indicates 
        if the line transceiver is ready 
        <Condtype> MOD_NR_1 <Probcause> 
        receiveFailure (41) <Alarmtype> 
        equipmentAlarm (5) <Polarity> (2) 
        "
	::= { pmc1008mpAlmlineXfp1AlarmsEntry 3 }


--- *********************************************************
---     TABLE for the pmc1008mpAlmlineXfp1SupplyAlarm articles
--- *********************************************************

pmc1008mpAlmlineXfp1SupplyAlarmTable OBJECT-TYPE
	SYNTAX  SEQUENCE OF Pmc1008mpAlmlineXfp1SupplyAlarmEntry
	MAX-ACCESS not-accessible
	STATUS current
	DESCRIPTION
        "
        List of pmc1008mpAlmlineXfp1SupplyAlarm 
        Article
        "
	::= { pmc1008mpAlmLineUrg 212 }


pmc1008mpAlmlineXfp1SupplyAlarmEntry OBJECT-TYPE
	SYNTAX Pmc1008mpAlmlineXfp1SupplyAlarmEntry
	MAX-ACCESS not-accessible
	STATUS current
	DESCRIPTION
        "
        Row definition for the pmc1008mpAlmlineXfp1SupplyAlarm 
        table
        "
	INDEX   { pmc1008mpAlmlineXfp1SupplyAlarmIndex }
	::= { pmc1008mpAlmlineXfp1SupplyAlarmTable 1 }


Pmc1008mpAlmlineXfp1SupplyAlarmEntry ::=
	SEQUENCE {
	pmc1008mpAlmlineXfp1SupplyAlarmIndex
		INTEGER,
	pmc1008mpAlmVcc5HighWarningPortn
		EkiOnOff,
	pmc1008mpAlmVcc5LowWarningPortn
		EkiOnOff,
	pmc1008mpAlmVcc3HighWarningPortn
		EkiOnOff,
	pmc1008mpAlmVcc3LowWarningPortn
		EkiOnOff,
	pmc1008mpAlmVcc2HighWarningPortn
		EkiOnOff,
	pmc1008mpAlmVcc2LowWarningPortn
		EkiOnOff,
	pmc1008mpAlmVee5HighWarningPortn
		EkiOnOff,
	pmc1008mpAlmVee5LowWarningPortn
		EkiOnOff,
	pmc1008mpAlmVcc5HighAlarmPortn
		EkiOnOff,
	pmc1008mpAlmVcc5LowAlarmPortn
		EkiOnOff,
	pmc1008mpAlmVcc3HighAlarmPortn
		EkiOnOff,
	pmc1008mpAlmVcc3LowAlarmPortn
		EkiOnOff,
	pmc1008mpAlmVcc2HighAlarmPortn
		EkiOnOff,
	pmc1008mpAlmVcc2LowAlarmPortn
		EkiOnOff,
	pmc1008mpAlmVee5HighAlarmPortn
		EkiOnOff,
	pmc1008mpAlmVee5LowAlarmPortn
		EkiOnOff
	}


pmc1008mpAlmlineXfp1SupplyAlarmIndex OBJECT-TYPE
	SYNTAX  INTEGER(0..128)
	MAX-ACCESS  read-only
	STATUS current
	DESCRIPTION
        "
        Index definition for the pmc1008mpAlmlineXfp1SupplyAlarm 
        table
        "
	::= { pmc1008mpAlmlineXfp1SupplyAlarmEntry 1 }


pmc1008mpAlmVcc5HighWarningPortn OBJECT-TYPE
	SYNTAX  EkiOnOff
	MAX-ACCESS read-only
	STATUS current
	DESCRIPTION
        "
        VCC5 Power Supply High Warning 
        :Warning indicating the XFP/OTX 
        VCC5 power supply is higher than 
        the threshold written in the EEPROM 
        <Condtype> VCC5_HIGH_WARNING_1
         <Probcause> powerProblem (36)
         <Alarmtype> equipmentAlarm (5) 
        <Polarity> (2) 
        "
	::= { pmc1008mpAlmlineXfp1SupplyAlarmEntry 17 }


pmc1008mpAlmVcc5LowWarningPortn OBJECT-TYPE
	SYNTAX  EkiOnOff
	MAX-ACCESS read-only
	STATUS current
	DESCRIPTION
        "
        VCC5 Power Supply Low Warning
         :Warning indicating the XFP/OTX 
        VCC5 power supply is lower than 
        the threshold written in the EEPROM 
        <Condtype> VCC5_LOW_WARNING_1 <Probcause> 
        powerProblem (36) <Alarmtype> equipmentAlarm 
        (5) <Polarity> (2) 
        "
	::= { pmc1008mpAlmlineXfp1SupplyAlarmEntry 16 }


pmc1008mpAlmVcc3HighWarningPortn OBJECT-TYPE
	SYNTAX  EkiOnOff
	MAX-ACCESS read-only
	STATUS current
	DESCRIPTION
        "
        VCC3 Power Supply High Warning 
        :Warning indicating the XFP/OTX 
        VCC3 power supply is higher than 
        the threshold written in the EEPROM 
        <Condtype> VCC3_HIGH_WARNING_1
         <Probcause> powerProblem (36)
         <Alarmtype> equipmentAlarm (5) 
        <Polarity> (2) 
        "
	::= { pmc1008mpAlmlineXfp1SupplyAlarmEntry 15 }


pmc1008mpAlmVcc3LowWarningPortn OBJECT-TYPE
	SYNTAX  EkiOnOff
	MAX-ACCESS read-only
	STATUS current
	DESCRIPTION
        "
        VCC3 Power Supply Low Warning
         :Warning indicating the XFP/OTX 
        VCC3 power supply is lower than 
        the threshold written in the EEPROM 
        <Condtype> VCC3_LOW_WARNING_1 <Probcause> 
        powerProblem (36) <Alarmtype> equipmentAlarm 
        (5) <Polarity> (2) 
        "
	::= { pmc1008mpAlmlineXfp1SupplyAlarmEntry 14 }


pmc1008mpAlmVcc2HighWarningPortn OBJECT-TYPE
	SYNTAX  EkiOnOff
	MAX-ACCESS read-only
	STATUS current
	DESCRIPTION
        "
        VCC2 Power Supply High Warning 
        :Warning indicating the XFP/OTX 
        VCC2 power supply is higher than 
        the threshold written in the EEPROM 
        <Condtype> VCC2_HIGH_WARNING_1
         <Probcause> powerProblem (36)
         <Alarmtype> equipmentAlarm (5) 
        <Polarity> (2) 
        "
	::= { pmc1008mpAlmlineXfp1SupplyAlarmEntry 13 }


pmc1008mpAlmVcc2LowWarningPortn OBJECT-TYPE
	SYNTAX  EkiOnOff
	MAX-ACCESS read-only
	STATUS current
	DESCRIPTION
        "
        VCC2 Power Supply Low Warning
         :Warning indicating the XFP/OTX 
        VCC2 power supply is lower than 
        the threshold written in the EEPROM 
        <Condtype> VCC2_LOW_WARNING_1 <Probcause> 
        powerProblem (36) <Alarmtype> equipmentAlarm 
        (5) <Polarity> (2) 
        "
	::= { pmc1008mpAlmlineXfp1SupplyAlarmEntry 12 }


pmc1008mpAlmVee5HighWarningPortn OBJECT-TYPE
	SYNTAX  EkiOnOff
	MAX-ACCESS read-only
	STATUS current
	DESCRIPTION
        "
        VEE5 Power Supply High Warning 
        :Warning indicating the XFP/OTX 
        VEE5 power supply is higher than 
        the threshold written in the EEPROM 
        <Condtype> VEE5_HIGH_WARNING_1
         <Probcause> powerProblem (36)
         <Alarmtype> equipmentAlarm (5) 
        <Polarity> (2) 
        "
	::= { pmc1008mpAlmlineXfp1SupplyAlarmEntry 11 }


pmc1008mpAlmVee5LowWarningPortn OBJECT-TYPE
	SYNTAX  EkiOnOff
	MAX-ACCESS read-only
	STATUS current
	DESCRIPTION
        "
        VEE5 Power Supply Low Warning
         :Warning indicating the XFP/OTX 
        VEE5 power supply is lower than 
        the threshold written in the EEPROM 
        <Condtype> VEE5_LOW_WARNING_1 <Probcause> 
        powerProblem (36) <Alarmtype> equipmentAlarm 
        (5) <Polarity> (2) 
        "
	::= { pmc1008mpAlmlineXfp1SupplyAlarmEntry 10 }


pmc1008mpAlmVcc5HighAlarmPortn OBJECT-TYPE
	SYNTAX  EkiOnOff
	MAX-ACCESS read-only
	STATUS current
	DESCRIPTION
        "
        VCC5 Power Supply High :Alarm
         indicating the XFP/OTX VCC5 power 
        supply is higher than the threshold 
        written in the EEPROM <Condtype> 
        VCC5_HIGH_ALARM_1 <Probcause> powerProblem 
        (36) <Alarmtype> equipmentAlarm 
        (5) <Polarity> (2) 
        "
	::= { pmc1008mpAlmlineXfp1SupplyAlarmEntry 9 }


pmc1008mpAlmVcc5LowAlarmPortn OBJECT-TYPE
	SYNTAX  EkiOnOff
	MAX-ACCESS read-only
	STATUS current
	DESCRIPTION
        "
        VCC5 Power Supply Low :Alarm indicating 
        the XFP/OTX VCC5 power supply is 
        lower than the threshold written 
        in the EEPROM <Condtype> VCC5_LOW_ALARM_1 
        <Probcause> powerProblem (36) <Alarmtype> 
        equipmentAlarm (5) <Polarity> (2) 
        "
	::= { pmc1008mpAlmlineXfp1SupplyAlarmEntry 8 }


pmc1008mpAlmVcc3HighAlarmPortn OBJECT-TYPE
	SYNTAX  EkiOnOff
	MAX-ACCESS read-only
	STATUS current
	DESCRIPTION
        "
        VCC3 Power Supply High :Alarm
         indicating the XFP/OTX VCC3 power 
        supply is higher than the threshold 
        written in the EEPROM <Condtype> 
        VCC3_HIGH_ALARM_1 <Probcause> powerProblem 
        (36) <Alarmtype> equipmentAlarm 
        (5) <Polarity> (2) 
        "
	::= { pmc1008mpAlmlineXfp1SupplyAlarmEntry 7 }


pmc1008mpAlmVcc3LowAlarmPortn OBJECT-TYPE
	SYNTAX  EkiOnOff
	MAX-ACCESS read-only
	STATUS current
	DESCRIPTION
        "
        VCC3 Power Supply Low :Alarm indicating 
        the XFP/OTX VCC3 power supply is 
        lower than the threshold written 
        in the EEPROM <Condtype> VCC3_LOW_ALARM_1 
        <Probcause> powerProblem (36) <Alarmtype> 
        equipmentAlarm (5) <Polarity> (2) 
        "
	::= { pmc1008mpAlmlineXfp1SupplyAlarmEntry 6 }


pmc1008mpAlmVcc2HighAlarmPortn OBJECT-TYPE
	SYNTAX  EkiOnOff
	MAX-ACCESS read-only
	STATUS current
	DESCRIPTION
        "
        VCC2 Power Supply High :Alarm
         indicating the XFP/OTX VCC2 power 
        supply is higher than the threshold 
        written in the EEPROM <Condtype> 
        VCC2_HIGH_ALARM_1 <Probcause> powerProblem 
        (36) <Alarmtype> equipmentAlarm 
        (5) <Polarity> (2) 
        "
	::= { pmc1008mpAlmlineXfp1SupplyAlarmEntry 5 }


pmc1008mpAlmVcc2LowAlarmPortn OBJECT-TYPE
	SYNTAX  EkiOnOff
	MAX-ACCESS read-only
	STATUS current
	DESCRIPTION
        "
        VCC2 Power Supply Low :Alarm indicating 
        the XFP/OTX VCC2 power supply is 
        lower than the threshold written 
        in the EEPROM <Condtype> VCC2_LOW_ALARM_1 
        <Probcause> powerProblem (36) <Alarmtype> 
        equipmentAlarm (5) <Polarity> (2) 
        "
	::= { pmc1008mpAlmlineXfp1SupplyAlarmEntry 4 }


pmc1008mpAlmVee5HighAlarmPortn OBJECT-TYPE
	SYNTAX  EkiOnOff
	MAX-ACCESS read-only
	STATUS current
	DESCRIPTION
        "
        VEE5 Power Supply High :Alarm
         indicating the XFP/OTX VEE5 power 
        supply is higher than the threshold 
        written in the EEPROM <Condtype> 
        VEE5_HIGH_ALARM_1 <Probcause> powerProblem 
        (36) <Alarmtype> equipmentAlarm 
        (5) <Polarity> (2) 
        "
	::= { pmc1008mpAlmlineXfp1SupplyAlarmEntry 3 }


pmc1008mpAlmVee5LowAlarmPortn OBJECT-TYPE
	SYNTAX  EkiOnOff
	MAX-ACCESS read-only
	STATUS current
	DESCRIPTION
        "
        VEE5 Power Supply Low :Alarm indicating 
        the XFP/OTX VEE5 power supply is 
        lower than the threshold written 
        in the EEPROM <Condtype> VEE5_LOW_ALARM_1 
        <Probcause> powerProblem (36) <Alarmtype> 
        equipmentAlarm (5) <Polarity> (2) 
        "
	::= { pmc1008mpAlmlineXfp1SupplyAlarmEntry 2 }


--- *********************************************************
---     TABLE for the pmc1008mpAlmlineOtx1TlhAlarms articles
--- *********************************************************

pmc1008mpAlmlineOtx1TlhAlarmsTable OBJECT-TYPE
	SYNTAX  SEQUENCE OF Pmc1008mpAlmlineOtx1TlhAlarmsEntry
	MAX-ACCESS not-accessible
	STATUS current
	DESCRIPTION
        "
        List of pmc1008mpAlmlineOtx1TlhAlarms 
        Article
        "
	::= { pmc1008mpAlmLineUrg 224 }


pmc1008mpAlmlineOtx1TlhAlarmsEntry OBJECT-TYPE
	SYNTAX Pmc1008mpAlmlineOtx1TlhAlarmsEntry
	MAX-ACCESS not-accessible
	STATUS current
	DESCRIPTION
        "
        Row definition for the pmc1008mpAlmlineOtx1TlhAlarms 
        table
        "
	INDEX   { pmc1008mpAlmlineOtx1TlhAlarmsIndex }
	::= { pmc1008mpAlmlineOtx1TlhAlarmsTable 1 }


Pmc1008mpAlmlineOtx1TlhAlarmsEntry ::=
	SEQUENCE {
	pmc1008mpAlmlineOtx1TlhAlarmsIndex
		INTEGER,
	pmc1008mpAlmLineLaserTempHighAlaPortn
		EkiOnOff,
	pmc1008mpAlmLineFreqDevHighAlaPortn
		EkiOnOff,
	pmc1008mpAlmLineCdrNotReadyPortn
		EkiOnOff,
	pmc1008mpAlmLineAgingHighAlaPortn
		EkiOnOff,
	pmc1008mpAlmLineModulatorAgingHighAlaPortn
		EkiOnOff
	}


pmc1008mpAlmlineOtx1TlhAlarmsIndex OBJECT-TYPE
	SYNTAX  INTEGER(0..128)
	MAX-ACCESS  read-only
	STATUS current
	DESCRIPTION
        "
        Index definition for the pmc1008mpAlmlineOtx1TlhAlarms 
        table
        "
	::= { pmc1008mpAlmlineOtx1TlhAlarmsEntry 1 }


pmc1008mpAlmLineLaserTempHighAlaPortn OBJECT-TYPE
	SYNTAX  EkiOnOff
	MAX-ACCESS read-only
	STATUS current
	DESCRIPTION
        "
        Line Laser Temp. High Alarm :Alarm 
        indicating the Line OTX TLH laser 
        temperature is higher than the
         threshold written in the EEPROM 
        <Condtype> LINE_LASER_TEMP_HIGH_ALA_1 
        <Probcause> temperatureUnacceptable 
        (51) <Alarmtype> equipmentAlarm 
        (5) <Polarity> (2) 
        "
	::= { pmc1008mpAlmlineOtx1TlhAlarmsEntry 15 }


pmc1008mpAlmLineFreqDevHighAlaPortn OBJECT-TYPE
	SYNTAX  EkiOnOff
	MAX-ACCESS read-only
	STATUS current
	DESCRIPTION
        "
        Line Freq. Deviation High Alarm 
        :Alarm indicating the Line OTX
         TLH frequency deviation is higher 
        than the threshold written in the 
        EEPROM <Condtype> LINE_FREQ_DEV_HIGH_ALA_1 
        <Probcause> transmitterFailure
         (56) <Alarmtype> equipmentAlarm 
        (5) <Polarity> (2) 
        "
	::= { pmc1008mpAlmlineOtx1TlhAlarmsEntry 13 }


pmc1008mpAlmLineCdrNotReadyPortn OBJECT-TYPE
	SYNTAX  EkiOnOff
	MAX-ACCESS read-only
	STATUS current
	DESCRIPTION
        "
        CDR Not Ready :This OID indicates 
        the Clock Data Recovery unit is 
        not yet initialized.   <Help> 
         This alarm indicates the Clock 
        Data Recovery unit is not yet initialized. 
        <Condtype> LINE_CDR_NOT_READY_1 
        <Probcause> transmitterFailure
         (56) <Alarmtype> equipmentAlarm 
        (5) <Polarity> (2) 
        "
	::= { pmc1008mpAlmlineOtx1TlhAlarmsEntry 10 }


pmc1008mpAlmLineAgingHighAlaPortn OBJECT-TYPE
	SYNTAX  EkiOnOff
	MAX-ACCESS read-only
	STATUS current
	DESCRIPTION
        "
        Line OTX TLH Aging High Alarm
         :Alarm indicating the Line OTX 
        TLH aging is higher than the threshold 
        written in the EEPROM <Condtype> 
        LINE_AGING_HIGH_ALA_1 <Probcause> 
        transmitterFailure (56) <Alarmtype> 
        equipmentAlarm (5) <Polarity> (2) 
        "
	::= { pmc1008mpAlmlineOtx1TlhAlarmsEntry 7 }


pmc1008mpAlmLineModulatorAgingHighAlaPortn OBJECT-TYPE
	SYNTAX  EkiOnOff
	MAX-ACCESS read-only
	STATUS current
	DESCRIPTION
        "
        Line Modulator Aging High Alarm 
        :Alarm indicating the Line OTX
         TLH modulator aging is higher
         than the threshold written in
         the EEPROM <Condtype> LINE_MODULATOR_AGING_HIGH_ALA_1 
        <Probcause> transmitterFailure
         (56) <Alarmtype> equipmentAlarm 
        (5) <Polarity> (2) 
        "
	::= { pmc1008mpAlmlineOtx1TlhAlarmsEntry 6 }


--- *********************************************************
---     TABLE for the pmc1008mpAlmlineOtx1TlhWarnings articles
--- *********************************************************

pmc1008mpAlmlineOtx1TlhWarningsTable OBJECT-TYPE
	SYNTAX  SEQUENCE OF Pmc1008mpAlmlineOtx1TlhWarningsEntry
	MAX-ACCESS not-accessible
	STATUS current
	DESCRIPTION
        "
        List of pmc1008mpAlmlineOtx1TlhWarnings 
        Article
        "
	::= { pmc1008mpAlmLineNurg 225 }


pmc1008mpAlmlineOtx1TlhWarningsEntry OBJECT-TYPE
	SYNTAX Pmc1008mpAlmlineOtx1TlhWarningsEntry
	MAX-ACCESS not-accessible
	STATUS current
	DESCRIPTION
        "
        Row definition for the pmc1008mpAlmlineOtx1TlhWarnings 
        table
        "
	INDEX   { pmc1008mpAlmlineOtx1TlhWarningsIndex }
	::= { pmc1008mpAlmlineOtx1TlhWarningsTable 1 }


Pmc1008mpAlmlineOtx1TlhWarningsEntry ::=
	SEQUENCE {
	pmc1008mpAlmlineOtx1TlhWarningsIndex
		INTEGER,
	pmc1008mpAlmLineLaserTempHighWarningPortn
		EkiOnOff,
	pmc1008mpAlmLineFreqDevHighWarningPortn
		EkiOnOff,
	pmc1008mpAlmLineAgingHighWarningPortn
		EkiOnOff,
	pmc1008mpAlmLineModulatorAgingHighWarningPortn
		EkiOnOff
	}


pmc1008mpAlmlineOtx1TlhWarningsIndex OBJECT-TYPE
	SYNTAX  INTEGER(0..128)
	MAX-ACCESS  read-only
	STATUS current
	DESCRIPTION
        "
        Index definition for the pmc1008mpAlmlineOtx1TlhWarnings 
        table
        "
	::= { pmc1008mpAlmlineOtx1TlhWarningsEntry 1 }


pmc1008mpAlmLineLaserTempHighWarningPortn OBJECT-TYPE
	SYNTAX  EkiOnOff
	MAX-ACCESS read-only
	STATUS current
	DESCRIPTION
        "
        Line Laser Temp. High Warning
         :Warning indicating the Line OTX 
        TLH laser temperature is higher 
        than the threshold written in the 
        EEPROM <Condtype> LINE_LASER_TEMP_HIGH_WARNING_1 
        <Probcause> temperatureUnacceptable 
        (51) <Alarmtype> equipmentAlarm 
        (5) <Polarity> (2) 
        "
	::= { pmc1008mpAlmlineOtx1TlhWarningsEntry 15 }


pmc1008mpAlmLineFreqDevHighWarningPortn OBJECT-TYPE
	SYNTAX  EkiOnOff
	MAX-ACCESS read-only
	STATUS current
	DESCRIPTION
        "
        Line Freq. Deviation High Warning 
        :Warning indicating the Line OTX 
        TLH frequency deviation is higher 
        than the threshold written in the 
        EEPROM <Condtype> LINE_FREQ_DEV_HIGH_WARNING_1 
        <Probcause> transmitterFailure
         (56) <Alarmtype> equipmentAlarm 
        (5) <Polarity> (2) 
        "
	::= { pmc1008mpAlmlineOtx1TlhWarningsEntry 13 }


pmc1008mpAlmLineAgingHighWarningPortn OBJECT-TYPE
	SYNTAX  EkiOnOff
	MAX-ACCESS read-only
	STATUS current
	DESCRIPTION
        "
        Line OTX TLH Aging High Warning 
        :Warning indicating the Line OTX 
        TLH aging is higher than the threshold 
        written in the EEPROM <Condtype> 
        LINE_AGING_HIGH_WARNING_1 <Probcause> 
        transmitterFailure (56) <Alarmtype> 
        equipmentAlarm (5) <Polarity> (2) 
        "
	::= { pmc1008mpAlmlineOtx1TlhWarningsEntry 7 }


pmc1008mpAlmLineModulatorAgingHighWarningPortn OBJECT-TYPE
	SYNTAX  EkiOnOff
	MAX-ACCESS read-only
	STATUS current
	DESCRIPTION
        "
        Line Modulator Aging High Warning 
        :Warning indicating the Line OTX 
        TLH modulator aging is higher than 
        the threshold written in the EEPROM 
        <Condtype> LINE_MODULATOR_AGING_HIGH_WARNING_1 
        <Probcause> transmitterFailure
         (56) <Alarmtype> equipmentAlarm 
        (5) <Polarity> (2) 
        "
	::= { pmc1008mpAlmlineOtx1TlhWarningsEntry 6 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pmc1008mpCtrlconfMgnt1 OBJECT IDENTIFIER ::= { pmc1008mpCtrlOther 1 }




pmc1008mpCtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pmc1008mpCtrlconfMgnt1 14 }



pmc1008mpCtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pmc1008mpCtrlconfMgnt1 10 }



pmc1008mpCtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pmc1008mpCtrlconfMgnt1 2 }



pmc1008mpCtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pmc1008mpCtrlconfMgnt1 1 }



--- *****************************************************
---     LEAF for the synth4 article
--- *****************************************************
pmc1008mpCtrlsynth4 OBJECT IDENTIFIER ::= { pmc1008mpCtrlOther 4 }




pmc1008mpCtrlCorrelatOff OBJECT-TYPE
	  SYNTAX EkiOnOff
	  MAX-ACCESS read-write
	  STATUS current
	  DESCRIPTION
        "
        Disable Alarm Correlation :This 
        OID disables the alarm correlation 
        in the PM.
        "
	  ::= { pmc1008mpCtrlsynth4 2 }



pmc1008mpCtrlCorrelatOn OBJECT-TYPE
	  SYNTAX EkiOnOff
	  MAX-ACCESS read-write
	  STATUS current
	  DESCRIPTION
        "
        Enable Alarm Correlation :This 
        OID enables the alarm correlation 
        in the PM.
        "
	  ::= { pmc1008mpCtrlsynth4 1 }



--- *****************************************************
---     LEAF for the swMgnt article
--- *****************************************************
pmc1008mpCtrlswMgnt OBJECT IDENTIFIER ::= { pmc1008mpCtrlOther 5 }




pmc1008mpCtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pmc1008mpCtrlswMgnt 6 }



pmc1008mpCtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pmc1008mpCtrlswMgnt 5 }



pmc1008mpCtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pmc1008mpCtrlswMgnt 3 }



pmc1008mpCtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pmc1008mpCtrlswMgnt 2 }



--- *****************************************************
---     LEAF for the gwMgnt article
--- *****************************************************
pmc1008mpCtrlgwMgnt OBJECT IDENTIFIER ::= { pmc1008mpCtrlOther 6 }




pmc1008mpCtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pmc1008mpCtrlgwMgnt 8 }



pmc1008mpCtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pmc1008mpCtrlgwMgnt 7 }



pmc1008mpCtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pmc1008mpCtrlgwMgnt 6 }



pmc1008mpCtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pmc1008mpCtrlgwMgnt 5 }



pmc1008mpCtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pmc1008mpCtrlgwMgnt 1 }



--- *********************************************************
---     TABLE for the pmc1008mpCtrlaccessLoop articles
--- *********************************************************

pmc1008mpCtrlaccessLoopTable OBJECT-TYPE
	SYNTAX  SEQUENCE OF Pmc1008mpCtrlaccessLoopEntry
	MAX-ACCESS not-accessible
	STATUS current
	DESCRIPTION
        "
        List of pmc1008mpCtrlaccessLoop 
        Article
        "
	::= { pmc1008mpCtrlClient 16 }


pmc1008mpCtrlaccessLoopEntry OBJECT-TYPE
	SYNTAX Pmc1008mpCtrlaccessLoopEntry
	MAX-ACCESS not-accessible
	STATUS current
	DESCRIPTION
        "
        Row definition for the pmc1008mpCtrlaccessLoop 
        table
        "
	INDEX   { pmc1008mpCtrlaccessLoopIndex }
	::= { pmc1008mpCtrlaccessLoopTable 1 }


Pmc1008mpCtrlaccessLoopEntry ::=
	SEQUENCE {
	pmc1008mpCtrlaccessLoopIndex
		INTEGER,
	pmc1008mpCtrlaccessLoopPortn
		EkiState
	}


pmc1008mpCtrlaccessLoopIndex OBJECT-TYPE
	SYNTAX  INTEGER(0..128)
	MAX-ACCESS  read-only
	STATUS current
	DESCRIPTION
        "
        Index definition for the pmc1008mpCtrlaccessLoop 
        table
        "
	::= { pmc1008mpCtrlaccessLoopEntry 1 }


pmc1008mpCtrlaccessLoopPortn OBJECT-TYPE
	SYNTAX  EkiState
	MAX-ACCESS read-write
	STATUS current
	DESCRIPTION
        "
        Client Facility Loopback :This 
        OID operates a Client Facility
         Loopback, looping client input 
        signal on the client output port. 
        The loop is located on the client 
        transceiver  <Help> This maintenance 
        parameter operates a Client Facility 
        Loopback, looping client input
         signal on the client output port. 
        The loop is located on the client 
        transceiver 
        "
	::= { pmc1008mpCtrlaccessLoopEntry 2 }


--- *********************************************************
---     TABLE for the pmc1008mpCtrlportOosMode articles
--- *********************************************************

pmc1008mpCtrlportOosModeTable OBJECT-TYPE
	SYNTAX  SEQUENCE OF Pmc1008mpCtrlportOosModeEntry
	MAX-ACCESS not-accessible
	STATUS current
	DESCRIPTION
        "
        List of pmc1008mpCtrlportOosMode 
        Article
        "
	::= { pmc1008mpCtrlClient 18 }


pmc1008mpCtrlportOosModeEntry OBJECT-TYPE
	SYNTAX Pmc1008mpCtrlportOosModeEntry
	MAX-ACCESS not-accessible
	STATUS current
	DESCRIPTION
        "
        Row definition for the pmc1008mpCtrlportOosMode 
        table
        "
	INDEX   { pmc1008mpCtrlportOosModeIndex }
	::= { pmc1008mpCtrlportOosModeTable 1 }


Pmc1008mpCtrlportOosModeEntry ::=
	SEQUENCE {
	pmc1008mpCtrlportOosModeIndex
		INTEGER,
	pmc1008mpCtrlportOosModePortn
		EkiState
	}


pmc1008mpCtrlportOosModeIndex OBJECT-TYPE
	SYNTAX  INTEGER(0..128)
	MAX-ACCESS  read-only
	STATUS current
	DESCRIPTION
        "
        Index definition for the pmc1008mpCtrlportOosMode 
        table
        "
	::= { pmc1008mpCtrlportOosModeEntry 1 }


pmc1008mpCtrlportOosModePortn OBJECT-TYPE
	SYNTAX  EkiState
	MAX-ACCESS read-write
	STATUS current
	DESCRIPTION
        "
        Client Port Out Of Service :This 
        OID sets the client port Out Of 
        Service  <Help>  This controls
         defines the service state of the 
        client port
        "
	::= { pmc1008mpCtrlportOosModeEntry 2 }


--- *********************************************************
---     TABLE for the pmc1008mpCtrlsfpOnCtrl articles
--- *********************************************************

pmc1008mpCtrlsfpOnCtrlTable OBJECT-TYPE
	SYNTAX  SEQUENCE OF Pmc1008mpCtrlsfpOnCtrlEntry
	MAX-ACCESS not-accessible
	STATUS current
	DESCRIPTION
        "
        List of pmc1008mpCtrlsfpOnCtrl 
        Article
        "
	::= { pmc1008mpCtrlClient 19 }


pmc1008mpCtrlsfpOnCtrlEntry OBJECT-TYPE
	SYNTAX Pmc1008mpCtrlsfpOnCtrlEntry
	MAX-ACCESS not-accessible
	STATUS current
	DESCRIPTION
        "
        Row definition for the pmc1008mpCtrlsfpOnCtrl 
        table
        "
	INDEX   { pmc1008mpCtrlsfpOnCtrlIndex }
	::= { pmc1008mpCtrlsfpOnCtrlTable 1 }


Pmc1008mpCtrlsfpOnCtrlEntry ::=
	SEQUENCE {
	pmc1008mpCtrlsfpOnCtrlIndex
		INTEGER,
	pmc1008mpCtrlsfpOnCtrlPortn
		EkiState
	}


pmc1008mpCtrlsfpOnCtrlIndex OBJECT-TYPE
	SYNTAX  INTEGER(0..128)
	MAX-ACCESS  read-only
	STATUS current
	DESCRIPTION
        "
        Index definition for the pmc1008mpCtrlsfpOnCtrl 
        table
        "
	::= { pmc1008mpCtrlsfpOnCtrlEntry 1 }


pmc1008mpCtrlsfpOnCtrlPortn OBJECT-TYPE
	SYNTAX  EkiState
	MAX-ACCESS read-write
	STATUS current
	DESCRIPTION
        "
        Client SFP Optical Laser ON :This 
        OID switches on the SFP.
        "
	::= { pmc1008mpCtrlsfpOnCtrlEntry 2 }


--- *********************************************************
---     TABLE for the pmc1008mpCtrlsfpOffCtrl articles
--- *********************************************************

pmc1008mpCtrlsfpOffCtrlTable OBJECT-TYPE
	SYNTAX  SEQUENCE OF Pmc1008mpCtrlsfpOffCtrlEntry
	MAX-ACCESS not-accessible
	STATUS current
	DESCRIPTION
        "
        List of pmc1008mpCtrlsfpOffCtrl 
        Article
        "
	::= { pmc1008mpCtrlClient 20 }


pmc1008mpCtrlsfpOffCtrlEntry OBJECT-TYPE
	SYNTAX Pmc1008mpCtrlsfpOffCtrlEntry
	MAX-ACCESS not-accessible
	STATUS current
	DESCRIPTION
        "
        Row definition for the pmc1008mpCtrlsfpOffCtrl 
        table
        "
	INDEX   { pmc1008mpCtrlsfpOffCtrlIndex }
	::= { pmc1008mpCtrlsfpOffCtrlTable 1 }


Pmc1008mpCtrlsfpOffCtrlEntry ::=
	SEQUENCE {
	pmc1008mpCtrlsfpOffCtrlIndex
		INTEGER,
	pmc1008mpCtrlsfpOffCtrlPortn
		EkiState
	}


pmc1008mpCtrlsfpOffCtrlIndex OBJECT-TYPE
	SYNTAX  INTEGER(0..128)
	MAX-ACCESS  read-only
	STATUS current
	DESCRIPTION
        "
        Index definition for the pmc1008mpCtrlsfpOffCtrl 
        table
        "
	::= { pmc1008mpCtrlsfpOffCtrlEntry 1 }


pmc1008mpCtrlsfpOffCtrlPortn OBJECT-TYPE
	SYNTAX  EkiState
	MAX-ACCESS read-write
	STATUS current
	DESCRIPTION
        "
        Client SFP Optical Laser OFF :This 
        OID switches off the SFP.  <Help> 
         This control defines the laser 
        state of the client transceiver
        "
	::= { pmc1008mpCtrlsfpOffCtrlEntry 2 }


--- *********************************************************
---     TABLE for the pmc1008mpCtrlcsfUpIns articles
--- *********************************************************

pmc1008mpCtrlcsfUpInsTable OBJECT-TYPE
	SYNTAX  SEQUENCE OF Pmc1008mpCtrlcsfUpInsEntry
	MAX-ACCESS not-accessible
	STATUS current
	DESCRIPTION
        "
        List of pmc1008mpCtrlcsfUpIns
         Article
        "
	::= { pmc1008mpCtrlClient 21 }


pmc1008mpCtrlcsfUpInsEntry OBJECT-TYPE
	SYNTAX Pmc1008mpCtrlcsfUpInsEntry
	MAX-ACCESS not-accessible
	STATUS current
	DESCRIPTION
        "
        Row definition for the pmc1008mpCtrlcsfUpIns 
        table
        "
	INDEX   { pmc1008mpCtrlcsfUpInsIndex }
	::= { pmc1008mpCtrlcsfUpInsTable 1 }


Pmc1008mpCtrlcsfUpInsEntry ::=
	SEQUENCE {
	pmc1008mpCtrlcsfUpInsIndex
		INTEGER,
	pmc1008mpCtrlcsfUpInsPortn
		EkiState
	}


pmc1008mpCtrlcsfUpInsIndex OBJECT-TYPE
	SYNTAX  INTEGER(0..128)
	MAX-ACCESS  read-only
	STATUS current
	DESCRIPTION
        "
        Index definition for the pmc1008mpCtrlcsfUpIns 
        table
        "
	::= { pmc1008mpCtrlcsfUpInsEntry 1 }


pmc1008mpCtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pmc1008mpCtrlcsfUpInsEntry 2 }


--- *********************************************************
---     TABLE for the pmc1008mpCtrlcaisDwIns articles
--- *********************************************************

pmc1008mpCtrlcaisDwInsTable OBJECT-TYPE
	SYNTAX  SEQUENCE OF Pmc1008mpCtrlcaisDwInsEntry
	MAX-ACCESS not-accessible
	STATUS current
	DESCRIPTION
        "
        List of pmc1008mpCtrlcaisDwIns 
        Article
        "
	::= { pmc1008mpCtrlClient 22 }


pmc1008mpCtrlcaisDwInsEntry OBJECT-TYPE
	SYNTAX Pmc1008mpCtrlcaisDwInsEntry
	MAX-ACCESS not-accessible
	STATUS current
	DESCRIPTION
        "
        Row definition for the pmc1008mpCtrlcaisDwIns 
        table
        "
	INDEX   { pmc1008mpCtrlcaisDwInsIndex }
	::= { pmc1008mpCtrlcaisDwInsTable 1 }


Pmc1008mpCtrlcaisDwInsEntry ::=
	SEQUENCE {
	pmc1008mpCtrlcaisDwInsIndex
		INTEGER,
	pmc1008mpCtrlcaisDwInsPortn
		EkiState
	}


pmc1008mpCtrlcaisDwInsIndex OBJECT-TYPE
	SYNTAX  INTEGER(0..128)
	MAX-ACCESS  read-only
	STATUS current
	DESCRIPTION
        "
        Index definition for the pmc1008mpCtrlcaisDwIns 
        table
        "
	::= { pmc1008mpCtrlcaisDwInsEntry 1 }


pmc1008mpCtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pmc1008mpCtrlcaisDwInsEntry 2 }


--- *********************************************************
---     TABLE for the pmc1008mpCtrlclientAccessTermLoop articles
--- *********************************************************

pmc1008mpCtrlclientAccessTermLoopTable OBJECT-TYPE
	SYNTAX  SEQUENCE OF Pmc1008mpCtrlclientAccessTermLoopEntry
	MAX-ACCESS not-accessible
	STATUS current
	DESCRIPTION
        "
        List of pmc1008mpCtrlclientAccessTermLoop 
        Article
        "
	::= { pmc1008mpCtrlClient 26 }


pmc1008mpCtrlclientAccessTermLoopEntry OBJECT-TYPE
	SYNTAX Pmc1008mpCtrlclientAccessTermLoopEntry
	MAX-ACCESS not-accessible
	STATUS current
	DESCRIPTION
        "
        Row definition for the pmc1008mpCtrlclientAccessTermLoop 
        table
        "
	INDEX   { pmc1008mpCtrlclientAccessTermLoopIndex }
	::= { pmc1008mpCtrlclientAccessTermLoopTable 1 }


Pmc1008mpCtrlclientAccessTermLoopEntry ::=
	SEQUENCE {
	pmc1008mpCtrlclientAccessTermLoopIndex
		INTEGER,
	pmc1008mpCtrlclientAccessTermLoopPortn
		EkiState
	}


pmc1008mpCtrlclientAccessTermLoopIndex OBJECT-TYPE
	SYNTAX  INTEGER(0..128)
	MAX-ACCESS  read-only
	STATUS current
	DESCRIPTION
        "
        Index definition for the pmc1008mpCtrlclientAccessTermLoop 
        table
        "
	::= { pmc1008mpCtrlclientAccessTermLoopEntry 1 }


pmc1008mpCtrlclientAccessTermLoopPortn OBJECT-TYPE
	SYNTAX  EkiState
	MAX-ACCESS read-write
	STATUS current
	DESCRIPTION
        "
        Client Terminal Loopback :This 
        OID operates a Client Terminal
         Loopback, looping client input 
        signal on the client output port. 
        The loop is located on the line 
        transceiver  <Help> This maintenance 
        parameter operates a Client Terminal 
        Loopback, looping client input
         signal on the client output port. 
        The loop is located on the line 
        transceiver
        "
	::= { pmc1008mpCtrlclientAccessTermLoopEntry 2 }


--- *********************************************************
---     TABLE for the pmc1008mpCtrlprotocol articles
--- *********************************************************

pmc1008mpCtrlprotocolTable OBJECT-TYPE
	SYNTAX  SEQUENCE OF Pmc1008mpCtrlprotocolEntry
	MAX-ACCESS not-accessible
	STATUS current
	DESCRIPTION
        "
        List of pmc1008mpCtrlprotocol
         Article
        "
	::= { pmc1008mpCtrlClient 48 }


pmc1008mpCtrlprotocolEntry OBJECT-TYPE
	SYNTAX Pmc1008mpCtrlprotocolEntry
	MAX-ACCESS not-accessible
	STATUS current
	DESCRIPTION
        "
        Row definition for the pmc1008mpCtrlprotocol 
        table
        "
	INDEX   { pmc1008mpCtrlprotocolIndex }
	::= { pmc1008mpCtrlprotocolTable 1 }


Pmc1008mpCtrlprotocolEntry ::=
	SEQUENCE {
	pmc1008mpCtrlprotocolIndex
		INTEGER,
	pmc1008mpCtrlprotocolPortn
		EkiProtocol
	}


pmc1008mpCtrlprotocolIndex OBJECT-TYPE
	SYNTAX  INTEGER(0..128)
	MAX-ACCESS  read-only
	STATUS current
	DESCRIPTION
        "
        Index definition for the pmc1008mpCtrlprotocol 
        table
        "
	::= { pmc1008mpCtrlprotocolEntry 1 }


pmc1008mpCtrlprotocolPortn OBJECT-TYPE
	SYNTAX  EkiProtocol
	MAX-ACCESS read-write
	STATUS current
	DESCRIPTION
        "
        Protocol used for client port: 
        This OID sets the protocol of the 
        Client port.
        "
	::= { pmc1008mpCtrlprotocolEntry 2 }


--- *****************************************************
---     LEAF for the commAccessLoop article
--- *****************************************************
pmc1008mpCtrlcommAccessLoop OBJECT IDENTIFIER ::= { pmc1008mpCtrlLine 64 }




pmc1008mpCtrlCommAccessloop OBJECT-TYPE
	  SYNTAX EkiOnOff
	  MAX-ACCESS read-write
	  STATUS deprecated
	  DESCRIPTION
        "
        PM Full Access Loop Mode :This 
        OID, when set, puts the module
         in common access loop back, looping 
        the 10 Gb/s output signal on the 
        10 Gb/s input.
        "
	  ::= { pmc1008mpCtrlcommAccessLoop 1 }



--- *****************************************************
---     LEAF for the lineLoop article
--- *****************************************************
pmc1008mpCtrllineLoop OBJECT IDENTIFIER ::= { pmc1008mpCtrlLine 66 }




pmc1008mpCtrlLineLoop OBJECT-TYPE
	  SYNTAX EkiOnOff
	  MAX-ACCESS read-write
	  STATUS deprecated
	  DESCRIPTION
        "
        PM Line Loop Mode :This OID, when 
        set at '1' puts the module in line 
        loopback mode, looping the received 
        10 Gb/s signal on the transmit
         10 Gb/s output. The Upstream part 
        of the module is timed on the 10 
        Gb/s recovered clock in that case.
        "
	  ::= { pmc1008mpCtrllineLoop 1 }



--- *****************************************************
---     LEAF for the msAis article
--- *****************************************************
pmc1008mpCtrlmsAis OBJECT IDENTIFIER ::= { pmc1008mpCtrlLine 67 }




pmc1008mpCtrlMsAis OBJECT-TYPE
	  SYNTAX EkiOnOff
	  MAX-ACCESS read-write
	  STATUS current
	  DESCRIPTION
        "
        Insert MS-AIS/L-AIS On Line Output 
        :This OID, when set, inserts an 
        MS-AIS/L-AIS in the outgoing STM-64/OC-192 
        signal.
        "
	  ::= { pmc1008mpCtrlmsAis 1 }



--- *********************************************************
---     TABLE for the pmc1008mpCtrlfecDisable articles
--- *********************************************************

pmc1008mpCtrlfecDisableTable OBJECT-TYPE
	SYNTAX  SEQUENCE OF Pmc1008mpCtrlfecDisableEntry
	MAX-ACCESS not-accessible
	STATUS current
	DESCRIPTION
        "
        List of pmc1008mpCtrlfecDisable 
        Article
        "
	::= { pmc1008mpCtrlLine 69 }


pmc1008mpCtrlfecDisableEntry OBJECT-TYPE
	SYNTAX Pmc1008mpCtrlfecDisableEntry
	MAX-ACCESS not-accessible
	STATUS current
	DESCRIPTION
        "
        Row definition for the pmc1008mpCtrlfecDisable 
        table
        "
	INDEX   { pmc1008mpCtrlfecDisableIndex }
	::= { pmc1008mpCtrlfecDisableTable 1 }


Pmc1008mpCtrlfecDisableEntry ::=
	SEQUENCE {
	pmc1008mpCtrlfecDisableIndex
		INTEGER,
	pmc1008mpCtrlfecDisablePortn
		EkiState
	}


pmc1008mpCtrlfecDisableIndex OBJECT-TYPE
	SYNTAX  INTEGER(0..128)
	MAX-ACCESS  read-only
	STATUS current
	DESCRIPTION
        "
        Index definition for the pmc1008mpCtrlfecDisable 
        table
        "
	::= { pmc1008mpCtrlfecDisableEntry 1 }


pmc1008mpCtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pmc1008mpCtrlfecDisableEntry 2 }


--- *********************************************************
---     TABLE for the pmc1008mpCtrllineOosMode articles
--- *********************************************************

pmc1008mpCtrllineOosModeTable OBJECT-TYPE
	SYNTAX  SEQUENCE OF Pmc1008mpCtrllineOosModeEntry
	MAX-ACCESS not-accessible
	STATUS current
	DESCRIPTION
        "
        List of pmc1008mpCtrllineOosMode 
        Article
        "
	::= { pmc1008mpCtrlLine 74 }


pmc1008mpCtrllineOosModeEntry OBJECT-TYPE
	SYNTAX Pmc1008mpCtrllineOosModeEntry
	MAX-ACCESS not-accessible
	STATUS current
	DESCRIPTION
        "
        Row definition for the pmc1008mpCtrllineOosMode 
        table
        "
	INDEX   { pmc1008mpCtrllineOosModeIndex }
	::= { pmc1008mpCtrllineOosModeTable 1 }


Pmc1008mpCtrllineOosModeEntry ::=
	SEQUENCE {
	pmc1008mpCtrllineOosModeIndex
		INTEGER,
	pmc1008mpCtrllineOosModePortn
		EkiState
	}


pmc1008mpCtrllineOosModeIndex OBJECT-TYPE
	SYNTAX  INTEGER(0..128)
	MAX-ACCESS  read-only
	STATUS current
	DESCRIPTION
        "
        Index definition for the pmc1008mpCtrllineOosMode 
        table
        "
	::= { pmc1008mpCtrllineOosModeEntry 1 }


pmc1008mpCtrllineOosModePortn OBJECT-TYPE
	SYNTAX  EkiState
	MAX-ACCESS read-write
	STATUS current
	DESCRIPTION
        "
        Line Port Out Of Service :This 
        OID sets the line port Out Of Service 
         <Help>  This control defines the 
        service state of the line port
        "
	::= { pmc1008mpCtrllineOosModeEntry 2 }


--- *********************************************************
---     TABLE for the pmc1008mpCtrladddropTsClientARxProtect articles
--- *********************************************************

pmc1008mpCtrladddropTsClientARxProtectTable OBJECT-TYPE
	SYNTAX  SEQUENCE OF Pmc1008mpCtrladddropTsClientARxProtectEntry
	MAX-ACCESS not-accessible
	STATUS current
	DESCRIPTION
        "
        List of pmc1008mpCtrladddropTsClientARxProtect 
        Article
        "
	::= { pmc1008mpCtrlClient 128 }


pmc1008mpCtrladddropTsClientARxProtectEntry OBJECT-TYPE
	SYNTAX Pmc1008mpCtrladddropTsClientARxProtectEntry
	MAX-ACCESS not-accessible
	STATUS current
	DESCRIPTION
        "
        Row definition for the pmc1008mpCtrladddropTsClientARxProtect 
        table
        "
	INDEX   { pmc1008mpCtrladddropTsClientARxProtectIndex }
	::= { pmc1008mpCtrladddropTsClientARxProtectTable 1 }


Pmc1008mpCtrladddropTsClientARxProtectEntry ::=
	SEQUENCE {
	pmc1008mpCtrladddropTsClientARxProtectIndex
		INTEGER,
	pmc1008mpCtrladddropTsClientARxProtectPortn
		Pmc1008mpProtectionTimeSlot
	}


pmc1008mpCtrladddropTsClientARxProtectIndex OBJECT-TYPE
	SYNTAX  INTEGER(0..128)
	MAX-ACCESS  read-only
	STATUS current
	DESCRIPTION
        "
        Index definition for the pmc1008mpCtrladddropTsClientARxProtect 
        table
        "
	::= { pmc1008mpCtrladddropTsClientARxProtectEntry 1 }


pmc1008mpCtrladddropTsClientARxProtectPortn OBJECT-TYPE
	SYNTAX  Pmc1008mpProtectionTimeSlot
	MAX-ACCESS read-write
	STATUS current
	DESCRIPTION
        "
        Client A Switch Mode :This bit 
        selects the manual (1) or automatic 
        (0) switch method  <Help>  This 
        control defines the protection
         switch mode on the client interface
        "
	::= { pmc1008mpCtrladddropTsClientARxProtectEntry 2 }


--- *********************************************************
---     TABLE for the pmc1008mpCtrladddropTsPairMode articles
--- *********************************************************

pmc1008mpCtrladddropTsPairModeTable OBJECT-TYPE
	SYNTAX  SEQUENCE OF Pmc1008mpCtrladddropTsPairModeEntry
	MAX-ACCESS not-accessible
	STATUS current
	DESCRIPTION
        "
        List of pmc1008mpCtrladddropTsPairMode 
        Article
        "
	::= { pmc1008mpCtrlClient 136 }


pmc1008mpCtrladddropTsPairModeEntry OBJECT-TYPE
	SYNTAX Pmc1008mpCtrladddropTsPairModeEntry
	MAX-ACCESS not-accessible
	STATUS current
	DESCRIPTION
        "
        Row definition for the pmc1008mpCtrladddropTsPairMode 
        table
        "
	INDEX   { pmc1008mpCtrladddropTsPairModeIndex }
	::= { pmc1008mpCtrladddropTsPairModeTable 1 }


Pmc1008mpCtrladddropTsPairModeEntry ::=
	SEQUENCE {
	pmc1008mpCtrladddropTsPairModeIndex
		INTEGER,
	pmc1008mpCtrladddropTsPairModePortn
		Pmc1008mpModeTimeSlot
	}


pmc1008mpCtrladddropTsPairModeIndex OBJECT-TYPE
	SYNTAX  INTEGER(0..128)
	MAX-ACCESS  read-only
	STATUS current
	DESCRIPTION
        "
        Index definition for the pmc1008mpCtrladddropTsPairMode 
        table
        "
	::= { pmc1008mpCtrladddropTsPairModeEntry 1 }


pmc1008mpCtrladddropTsPairModePortn OBJECT-TYPE
	SYNTAX  Pmc1008mpModeTimeSlot
	MAX-ACCESS read-write
	STATUS current
	DESCRIPTION
        "
        TS Group Mode :This OID selects 
        the mode on the group of clients 
         <Help>   This control defines
         the mode (Add/Drop or Split&Select) 
        of two consecutive Client (1/2
         , 3/4 , 5/6 , 7/8)
        "
	::= { pmc1008mpCtrladddropTsPairModeEntry 2 }


--- *****************************************************
---     LEAF for the ledTest article
--- *****************************************************
pmc1008mpCtrlledTest OBJECT IDENTIFIER ::= { pmc1008mpCtrlOther 192 }




pmc1008mpCtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pmc1008mpCtrlledTest 3 }



pmc1008mpCtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pmc1008mpCtrlledTest 2 }



pmc1008mpCtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pmc1008mpCtrlledTest 1 }



--- *****************************************************
---     LEAF for the moduleOosMode article
--- *****************************************************
pmc1008mpCtrlmoduleOosMode OBJECT IDENTIFIER ::= { pmc1008mpCtrlOther 193 }




pmc1008mpCtrlModuleOosMode OBJECT-TYPE
	  SYNTAX EkiOnOff
	  MAX-ACCESS read-write
	  STATUS current
	  DESCRIPTION
        "
        PM Out Of Service :This OID sets 
        the PM Out Of Service  <Help> 
         This control defines the service 
        state of the complete module
        "
	  ::= { pmc1008mpCtrlmoduleOosMode 1 }



--- *****************************************************
---     LEAF for the moduleDccMgnt article
--- *****************************************************

pmc1008mpCtrlmoduleDccMgnt OBJECT-TYPE
	  SYNTAX Pmc1008mpDccMode
	  MAX-ACCESS read-write
	  STATUS current
	  DESCRIPTION
        "
        DCC Mode :This OID defines the 
        DCC mode of the PM (No DCC, Master, 
        Slave Line 1&2, Terminal Line 1, 
        Terminal Line 2, Terminal Line
         1&2)   <Help>  This control defines 
        the DCC mode of the PM (No DCC, 
        Master, Slave Line 1&2, Terminal 
        Line 1, Terminal Line 2 or Terminal 
        Line 1&2)

        "
	  ::= { pmc1008mpCtrlOther 196 }



--- *****************************************************
---     LEAF for the maintenanceMode article
--- *****************************************************
pmc1008mpCtrlmaintenanceMode OBJECT IDENTIFIER ::= { pmc1008mpCtrlOther 197 }




pmc1008mpCtrlMaintenanceMode OBJECT-TYPE
	  SYNTAX EkiOnOff
	  MAX-ACCESS read-write
	  STATUS current
	  DESCRIPTION
        "
        Enable Maintenance :This OID enables 
        the maintenance mode on the PM. 
         <Help>  This control enables the 
        maintenance mode on the PM.
        "
	  ::= { pmc1008mpCtrlmaintenanceMode 1 }



--- *********************************************************
---     TABLE for the pmc1008mpCtrlxfpOnoff articles
--- *********************************************************

pmc1008mpCtrlxfpOnoffTable OBJECT-TYPE
	SYNTAX  SEQUENCE OF Pmc1008mpCtrlxfpOnoffEntry
	MAX-ACCESS not-accessible
	STATUS current
	DESCRIPTION
        "
        List of pmc1008mpCtrlxfpOnoff
         Article
        "
	::= { pmc1008mpCtrlLine 208 }


pmc1008mpCtrlxfpOnoffEntry OBJECT-TYPE
	SYNTAX Pmc1008mpCtrlxfpOnoffEntry
	MAX-ACCESS not-accessible
	STATUS current
	DESCRIPTION
        "
        Row definition for the pmc1008mpCtrlxfpOnoff 
        table
        "
	INDEX   { pmc1008mpCtrlxfpOnoffIndex }
	::= { pmc1008mpCtrlxfpOnoffTable 1 }


Pmc1008mpCtrlxfpOnoffEntry ::=
	SEQUENCE {
	pmc1008mpCtrlxfpOnoffIndex
		INTEGER,
	pmc1008mpCtrlxfpOnoffPortn
		EkiState
	}


pmc1008mpCtrlxfpOnoffIndex OBJECT-TYPE
	SYNTAX  INTEGER(0..128)
	MAX-ACCESS  read-only
	STATUS current
	DESCRIPTION
        "
        Index definition for the pmc1008mpCtrlxfpOnoff 
        table
        "
	::= { pmc1008mpCtrlxfpOnoffEntry 1 }


pmc1008mpCtrlxfpOnoffPortn OBJECT-TYPE
	SYNTAX  EkiState
	MAX-ACCESS read-write
	STATUS current
	DESCRIPTION
        "
        XFP/OTX Optical Laser OFF :This 
        OID switches off the XFP or the 
        OTX  <Help>  This control defines 
        the laser state of the line transceiver
        "
	::= { pmc1008mpCtrlxfpOnoffEntry 2 }


--- *********************************************************
---     TABLE for the pmc1008mpCtrlxfpLineLoop articles
--- *********************************************************

pmc1008mpCtrlxfpLineLoopTable OBJECT-TYPE
	SYNTAX  SEQUENCE OF Pmc1008mpCtrlxfpLineLoopEntry
	MAX-ACCESS not-accessible
	STATUS current
	DESCRIPTION
        "
        List of pmc1008mpCtrlxfpLineLoop 
        Article
        "
	::= { pmc1008mpCtrlLine 209 }


pmc1008mpCtrlxfpLineLoopEntry OBJECT-TYPE
	SYNTAX Pmc1008mpCtrlxfpLineLoopEntry
	MAX-ACCESS not-accessible
	STATUS current
	DESCRIPTION
        "
        Row definition for the pmc1008mpCtrlxfpLineLoop 
        table
        "
	INDEX   { pmc1008mpCtrlxfpLineLoopIndex }
	::= { pmc1008mpCtrlxfpLineLoopTable 1 }


Pmc1008mpCtrlxfpLineLoopEntry ::=
	SEQUENCE {
	pmc1008mpCtrlxfpLineLoopIndex
		INTEGER,
	pmc1008mpCtrlxfpLineLoopPortn
		EkiState
	}


pmc1008mpCtrlxfpLineLoopIndex OBJECT-TYPE
	SYNTAX  INTEGER(0..128)
	MAX-ACCESS  read-only
	STATUS current
	DESCRIPTION
        "
        Index definition for the pmc1008mpCtrlxfpLineLoop 
        table
        "
	::= { pmc1008mpCtrlxfpLineLoopEntry 1 }


pmc1008mpCtrlxfpLineLoopPortn OBJECT-TYPE
	SYNTAX  EkiState
	MAX-ACCESS read-write
	STATUS current
	DESCRIPTION
        "
        Line XFP/OTX Loop :This OID operates 
        a line loopback on the XFP or the 
        OTX  <Help>  This control defines 
        the line loop back of the line
         transceiver
        "
	::= { pmc1008mpCtrlxfpLineLoopEntry 2 }


--- *********************************************************
---     TABLE for the pmc1008mpCtrlxfpXfiLoop articles
--- *********************************************************

pmc1008mpCtrlxfpXfiLoopTable OBJECT-TYPE
	SYNTAX  SEQUENCE OF Pmc1008mpCtrlxfpXfiLoopEntry
	MAX-ACCESS not-accessible
	STATUS current
	DESCRIPTION
        "
        List of pmc1008mpCtrlxfpXfiLoop 
        Article
        "
	::= { pmc1008mpCtrlLine 210 }


pmc1008mpCtrlxfpXfiLoopEntry OBJECT-TYPE
	SYNTAX Pmc1008mpCtrlxfpXfiLoopEntry
	MAX-ACCESS not-accessible
	STATUS current
	DESCRIPTION
        "
        Row definition for the pmc1008mpCtrlxfpXfiLoop 
        table
        "
	INDEX   { pmc1008mpCtrlxfpXfiLoopIndex }
	::= { pmc1008mpCtrlxfpXfiLoopTable 1 }


Pmc1008mpCtrlxfpXfiLoopEntry ::=
	SEQUENCE {
	pmc1008mpCtrlxfpXfiLoopIndex
		INTEGER,
	pmc1008mpCtrlxfpXfiLoopPortn
		EkiState
	}


pmc1008mpCtrlxfpXfiLoopIndex OBJECT-TYPE
	SYNTAX  INTEGER(0..128)
	MAX-ACCESS  read-only
	STATUS current
	DESCRIPTION
        "
        Index definition for the pmc1008mpCtrlxfpXfiLoop 
        table
        "
	::= { pmc1008mpCtrlxfpXfiLoopEntry 1 }


pmc1008mpCtrlxfpXfiLoopPortn OBJECT-TYPE
	SYNTAX  EkiState
	MAX-ACCESS read-write
	STATUS current
	DESCRIPTION
        "
        Line XFP/OTX XFI Loop :This OID 
        operates a XFI loopback on the
         XFP or the OTX   <Help>  This
         control defines the XFI loop back 
        of the line transceiver
        "
	::= { pmc1008mpCtrlxfpXfiLoopEntry 2 }


--- *********************************************************
---     TABLE for the pmc1008mpCtrllineTunableChannel articles
--- *********************************************************

pmc1008mpCtrllineTunableChannelTable OBJECT-TYPE
	SYNTAX  SEQUENCE OF Pmc1008mpCtrllineTunableChannelEntry
	MAX-ACCESS not-accessible
	STATUS current
	DESCRIPTION
        "
        List of pmc1008mpCtrllineTunableChannel 
        Article
        "
	::= { pmc1008mpCtrlLine 212 }


pmc1008mpCtrllineTunableChannelEntry OBJECT-TYPE
	SYNTAX Pmc1008mpCtrllineTunableChannelEntry
	MAX-ACCESS not-accessible
	STATUS current
	DESCRIPTION
        "
        Row definition for the pmc1008mpCtrllineTunableChannel 
        table
        "
	INDEX   { pmc1008mpCtrllineTunableChannelIndex }
	::= { pmc1008mpCtrllineTunableChannelTable 1 }


Pmc1008mpCtrllineTunableChannelEntry ::=
	SEQUENCE {
	pmc1008mpCtrllineTunableChannelIndex
		INTEGER,
	pmc1008mpCtrllineTunableChannelPortn
		Pmc1008mpOtxChannel
	}


pmc1008mpCtrllineTunableChannelIndex OBJECT-TYPE
	SYNTAX  INTEGER(0..128)
	MAX-ACCESS  read-only
	STATUS current
	DESCRIPTION
        "
        Index definition for the pmc1008mpCtrllineTunableChannel 
        table
        "
	::= { pmc1008mpCtrllineTunableChannelEntry 1 }


pmc1008mpCtrllineTunableChannelPortn OBJECT-TYPE
	SYNTAX  Pmc1008mpOtxChannel
	MAX-ACCESS read-write
	STATUS current
	DESCRIPTION
        "
        ITU Channel :This OID selects
         the ITU channel of the Line OTX 
        TLH Laser  <Help>   This control 
        defines the ITU channel of the
         Line OTX TLH Laser
        "
	::= { pmc1008mpCtrllineTunableChannelEntry 2 }


--- *********************************************************
---     TABLE for the pmc1008mpCtrllinePhotodiodeMode articles
--- *********************************************************

pmc1008mpCtrllinePhotodiodeModeTable OBJECT-TYPE
	SYNTAX  SEQUENCE OF Pmc1008mpCtrllinePhotodiodeModeEntry
	MAX-ACCESS not-accessible
	STATUS current
	DESCRIPTION
        "
        List of pmc1008mpCtrllinePhotodiodeMode 
        Article
        "
	::= { pmc1008mpCtrlLine 213 }


pmc1008mpCtrllinePhotodiodeModeEntry OBJECT-TYPE
	SYNTAX Pmc1008mpCtrllinePhotodiodeModeEntry
	MAX-ACCESS not-accessible
	STATUS current
	DESCRIPTION
        "
        Row definition for the pmc1008mpCtrllinePhotodiodeMode 
        table
        "
	INDEX   { pmc1008mpCtrllinePhotodiodeModeIndex }
	::= { pmc1008mpCtrllinePhotodiodeModeTable 1 }


Pmc1008mpCtrllinePhotodiodeModeEntry ::=
	SEQUENCE {
	pmc1008mpCtrllinePhotodiodeModeIndex
		INTEGER,
	pmc1008mpCtrllinePhotodiodeModePortn
		Pmc1008mpOtxMode
	}


pmc1008mpCtrllinePhotodiodeModeIndex OBJECT-TYPE
	SYNTAX  INTEGER(0..128)
	MAX-ACCESS  read-only
	STATUS current
	DESCRIPTION
        "
        Index definition for the pmc1008mpCtrllinePhotodiodeMode 
        table
        "
	::= { pmc1008mpCtrllinePhotodiodeModeEntry 1 }


pmc1008mpCtrllinePhotodiodeModePortn OBJECT-TYPE
	SYNTAX  Pmc1008mpOtxMode
	MAX-ACCESS read-write
	STATUS current
	DESCRIPTION
        "
        OTX TLH Rx Sens. Mode :This OID 
        defines the Rx sensiblity mode
         of the Line OTX TLH  <Help>  
         This control defines the receiver 
        sensibility mode of the Line OTX 
        TLH Laser (OTX60, OTX80 or Custom)
        "
	::= { pmc1008mpCtrllinePhotodiodeModeEntry 2 }


--- *********************************************************
---     TABLE for the pmc1008mpCtrllinePhotodiodeValue articles
--- *********************************************************

pmc1008mpCtrllinePhotodiodeValueTable OBJECT-TYPE
	SYNTAX  SEQUENCE OF Pmc1008mpCtrllinePhotodiodeValueEntry
	MAX-ACCESS not-accessible
	STATUS current
	DESCRIPTION
        "
        List of pmc1008mpCtrllinePhotodiodeValue 
        Article
        "
	::= { pmc1008mpCtrlLine 214 }


pmc1008mpCtrllinePhotodiodeValueEntry OBJECT-TYPE
	SYNTAX Pmc1008mpCtrllinePhotodiodeValueEntry
	MAX-ACCESS not-accessible
	STATUS current
	DESCRIPTION
        "
        Row definition for the pmc1008mpCtrllinePhotodiodeValue 
        table
        "
	INDEX   { pmc1008mpCtrllinePhotodiodeValueIndex }
	::= { pmc1008mpCtrllinePhotodiodeValueTable 1 }


Pmc1008mpCtrllinePhotodiodeValueEntry ::=
	SEQUENCE {
	pmc1008mpCtrllinePhotodiodeValueIndex
		INTEGER,
	pmc1008mpCtrllinePhotodiodeValuePortn
		Pmc1008mpAdjustValue
	}


pmc1008mpCtrllinePhotodiodeValueIndex OBJECT-TYPE
	SYNTAX  INTEGER(0..128)
	MAX-ACCESS  read-only
	STATUS current
	DESCRIPTION
        "
        Index definition for the pmc1008mpCtrllinePhotodiodeValue 
        table
        "
	::= { pmc1008mpCtrllinePhotodiodeValueEntry 1 }


pmc1008mpCtrllinePhotodiodeValuePortn OBJECT-TYPE
	SYNTAX  Pmc1008mpAdjustValue
	MAX-ACCESS read-write
	STATUS current
	DESCRIPTION
        "
        OTX TLH Rx Sensibility :This OID 
        sets the Rx sensibility of the
         Line OTX TLH (custom mode only) 
         <Help>   This control defines
         the receiver sensibility value 
        (only in Custom mode) of the Line 
        OTX TLH Laser
        "
	::= { pmc1008mpCtrllinePhotodiodeValueEntry 2 }


--- *********************************************************
---     TABLE for the pmc1008mpCtrllinePowerLaser articles
--- *********************************************************

pmc1008mpCtrllinePowerLaserTable OBJECT-TYPE
	SYNTAX  SEQUENCE OF Pmc1008mpCtrllinePowerLaserEntry
	MAX-ACCESS not-accessible
	STATUS current
	DESCRIPTION
        "
        List of pmc1008mpCtrllinePowerLaser 
        Article
        "
	::= { pmc1008mpCtrlLine 215 }


pmc1008mpCtrllinePowerLaserEntry OBJECT-TYPE
	SYNTAX Pmc1008mpCtrllinePowerLaserEntry
	MAX-ACCESS not-accessible
	STATUS current
	DESCRIPTION
        "
        Row definition for the pmc1008mpCtrllinePowerLaser 
        table
        "
	INDEX   { pmc1008mpCtrllinePowerLaserIndex }
	::= { pmc1008mpCtrllinePowerLaserTable 1 }


Pmc1008mpCtrllinePowerLaserEntry ::=
	SEQUENCE {
	pmc1008mpCtrllinePowerLaserIndex
		INTEGER,
	pmc1008mpCtrllinePowerLaserPortn
		INTEGER 
	}


pmc1008mpCtrllinePowerLaserIndex OBJECT-TYPE
	SYNTAX  INTEGER(0..128)
	MAX-ACCESS  read-only
	STATUS current
	DESCRIPTION
        "
        Index definition for the pmc1008mpCtrllinePowerLaser 
        table
        "
	::= { pmc1008mpCtrllinePowerLaserEntry 1 }


pmc1008mpCtrllinePowerLaserPortn OBJECT-TYPE
	SYNTAX  INTEGER (0..255)
	MAX-ACCESS read-write
	STATUS current
	DESCRIPTION
        "
        Laser Output Power [3-5] :This 
        OID sets the output power value 
        on the laser of the Line OTX TLH 
         (Unit = dBm)  <Help>   This control 
        defines the start-up output power 
        of the Line OTX TLH
        "
	::= { pmc1008mpCtrllinePowerLaserEntry 2 }


--- *********************************************************
---     TABLE for the pmc1008mpCtrlotxVlhReset articles
--- *********************************************************

pmc1008mpCtrlotxVlhResetTable OBJECT-TYPE
	SYNTAX  SEQUENCE OF Pmc1008mpCtrlotxVlhResetEntry
	MAX-ACCESS not-accessible
	STATUS current
	DESCRIPTION
        "
        List of pmc1008mpCtrlotxVlhReset 
        Article
        "
	::= { pmc1008mpCtrlLine 216 }


pmc1008mpCtrlotxVlhResetEntry OBJECT-TYPE
	SYNTAX Pmc1008mpCtrlotxVlhResetEntry
	MAX-ACCESS not-accessible
	STATUS current
	DESCRIPTION
        "
        Row definition for the pmc1008mpCtrlotxVlhReset 
        table
        "
	INDEX   { pmc1008mpCtrlotxVlhResetIndex }
	::= { pmc1008mpCtrlotxVlhResetTable 1 }


Pmc1008mpCtrlotxVlhResetEntry ::=
	SEQUENCE {
	pmc1008mpCtrlotxVlhResetIndex
		INTEGER,
	pmc1008mpCtrlOtxVlhResetPortn
		EkiOnOff
	}


pmc1008mpCtrlotxVlhResetIndex OBJECT-TYPE
	SYNTAX  INTEGER(0..128)
	MAX-ACCESS  read-only
	STATUS current
	DESCRIPTION
        "
        Index definition for the pmc1008mpCtrlotxVlhReset 
        table
        "
	::= { pmc1008mpCtrlotxVlhResetEntry 1 }


pmc1008mpCtrlOtxVlhResetPortn OBJECT-TYPE
	SYNTAX  EkiOnOff
	MAX-ACCESS read-write
	STATUS current
	DESCRIPTION
        "
        OTX-VLH Reset :This OID resets 
        the OTX-VLH module  <Help>  This 
        control resets the OTX-VLH and
         its parameters  
        "
	::= { pmc1008mpCtrlotxVlhResetEntry 2 }


--- *********************************************************
---     TABLE for the pmc1008mpCtrllineAccessLoop articles
--- *********************************************************

pmc1008mpCtrllineAccessLoopTable OBJECT-TYPE
	SYNTAX  SEQUENCE OF Pmc1008mpCtrllineAccessLoopEntry
	MAX-ACCESS not-accessible
	STATUS current
	DESCRIPTION
        "
        List of pmc1008mpCtrllineAccessLoop 
        Article
        "
	::= { pmc1008mpCtrlLine 217 }


pmc1008mpCtrllineAccessLoopEntry OBJECT-TYPE
	SYNTAX Pmc1008mpCtrllineAccessLoopEntry
	MAX-ACCESS not-accessible
	STATUS current
	DESCRIPTION
        "
        Row definition for the pmc1008mpCtrllineAccessLoop 
        table
        "
	INDEX   { pmc1008mpCtrllineAccessLoopIndex }
	::= { pmc1008mpCtrllineAccessLoopTable 1 }


Pmc1008mpCtrllineAccessLoopEntry ::=
	SEQUENCE {
	pmc1008mpCtrllineAccessLoopIndex
		INTEGER,
	pmc1008mpCtrllineAccessLoopPortn
		EkiState
	}


pmc1008mpCtrllineAccessLoopIndex OBJECT-TYPE
	SYNTAX  INTEGER(0..128)
	MAX-ACCESS  read-only
	STATUS current
	DESCRIPTION
        "
        Index definition for the pmc1008mpCtrllineAccessLoop 
        table
        "
	::= { pmc1008mpCtrllineAccessLoopEntry 1 }


pmc1008mpCtrllineAccessLoopPortn OBJECT-TYPE
	SYNTAX  EkiState
	MAX-ACCESS read-write
	STATUS current
	DESCRIPTION
        "
        Line Facility Loopback :This OID 
        operates a Line Facility Loopback, 
        looping line input signal on the 
        line output port. The loop is located 
        on the line transceiver. If the 
        Line signal carries DCC, the management 
        network is impacted  <Help> This 
        maintenance parameter operates
         a Line Facility Loopback, looping 
        line input signal on the line output 
        port. The loop is located on the 
        line transceiver. If the Line signal 
        carries DCC, the management network 
        is impacted
        "
	::= { pmc1008mpCtrllineAccessLoopEntry 2 }


--- *********************************************************
---     TABLE for the pmc1008mpCtrllineLoopTransceiver articles
--- *********************************************************

pmc1008mpCtrllineLoopTransceiverTable OBJECT-TYPE
	SYNTAX  SEQUENCE OF Pmc1008mpCtrllineLoopTransceiverEntry
	MAX-ACCESS not-accessible
	STATUS current
	DESCRIPTION
        "
        List of pmc1008mpCtrllineLoopTransceiver 
        Article
        "
	::= { pmc1008mpCtrlLine 218 }


pmc1008mpCtrllineLoopTransceiverEntry OBJECT-TYPE
	SYNTAX Pmc1008mpCtrllineLoopTransceiverEntry
	MAX-ACCESS not-accessible
	STATUS current
	DESCRIPTION
        "
        Row definition for the pmc1008mpCtrllineLoopTransceiver 
        table
        "
	INDEX   { pmc1008mpCtrllineLoopTransceiverIndex }
	::= { pmc1008mpCtrllineLoopTransceiverTable 1 }


Pmc1008mpCtrllineLoopTransceiverEntry ::=
	SEQUENCE {
	pmc1008mpCtrllineLoopTransceiverIndex
		INTEGER,
	pmc1008mpCtrllineLoopTransceiverPortn
		EkiState
	}


pmc1008mpCtrllineLoopTransceiverIndex OBJECT-TYPE
	SYNTAX  INTEGER(0..128)
	MAX-ACCESS  read-only
	STATUS current
	DESCRIPTION
        "
        Index definition for the pmc1008mpCtrllineLoopTransceiver 
        table
        "
	::= { pmc1008mpCtrllineLoopTransceiverEntry 1 }


pmc1008mpCtrllineLoopTransceiverPortn OBJECT-TYPE
	SYNTAX  EkiState
	MAX-ACCESS read-write
	STATUS current
	DESCRIPTION
        "
        Line Terminal Loopback :This OID 
        operates a Line Terminal Loopback, 
        looping line input signal on the 
        line output port. The loop is located 
        on all client transceivers  <Help> 
        This maintenance parameter operates 
        a Line Terminal Loopback, looping 
        line input signal on the line output 
        port. The loop is located on all 
        client transceivers.
        "
	::= { pmc1008mpCtrllineLoopTransceiverEntry 2 }


--- *********************************************************
---     TABLE for the pmc1008mpCtrlclientResetAllCount articles
--- *********************************************************

pmc1008mpCtrlclientResetAllCountTable OBJECT-TYPE
	SYNTAX  SEQUENCE OF Pmc1008mpCtrlclientResetAllCountEntry
	MAX-ACCESS not-accessible
	STATUS current
	DESCRIPTION
        "
        List of pmc1008mpCtrlclientResetAllCount 
        Article
        "
	::= { pmc1008mpCtrlClient 271 }


pmc1008mpCtrlclientResetAllCountEntry OBJECT-TYPE
	SYNTAX Pmc1008mpCtrlclientResetAllCountEntry
	MAX-ACCESS not-accessible
	STATUS current
	DESCRIPTION
        "
        Row definition for the pmc1008mpCtrlclientResetAllCount 
        table
        "
	INDEX   { pmc1008mpCtrlclientResetAllCountIndex }
	::= { pmc1008mpCtrlclientResetAllCountTable 1 }


Pmc1008mpCtrlclientResetAllCountEntry ::=
	SEQUENCE {
	pmc1008mpCtrlclientResetAllCountIndex
		INTEGER,
	pmc1008mpCtrlclientResetAllCountsPortn
		EkiState
	}


pmc1008mpCtrlclientResetAllCountIndex OBJECT-TYPE
	SYNTAX  INTEGER(0..128)
	MAX-ACCESS  read-only
	STATUS current
	DESCRIPTION
        "
        Index definition for the pmc1008mpCtrlclientResetAllCount 
        table
        "
	::= { pmc1008mpCtrlclientResetAllCountEntry 1 }


pmc1008mpCtrlclientResetAllCountsPortn OBJECT-TYPE
	SYNTAX  EkiState
	MAX-ACCESS read-write
	STATUS current
	DESCRIPTION
        "
        Client Counters Reset :This OID 
        resets every counter on the client 
        port  <Help>   This control operates 
        a reset on the statistics current 
        ,previous and history client port 
        counters  
        "
	::= { pmc1008mpCtrlclientResetAllCountEntry 2 }


--- *********************************************************
---     TABLE for the pmc1008mpCtrllineResetAllCount articles
--- *********************************************************

pmc1008mpCtrllineResetAllCountTable OBJECT-TYPE
	SYNTAX  SEQUENCE OF Pmc1008mpCtrllineResetAllCountEntry
	MAX-ACCESS not-accessible
	STATUS current
	DESCRIPTION
        "
        List of pmc1008mpCtrllineResetAllCount 
        Article
        "
	::= { pmc1008mpCtrlLine 335 }


pmc1008mpCtrllineResetAllCountEntry OBJECT-TYPE
	SYNTAX Pmc1008mpCtrllineResetAllCountEntry
	MAX-ACCESS not-accessible
	STATUS current
	DESCRIPTION
        "
        Row definition for the pmc1008mpCtrllineResetAllCount 
        table
        "
	INDEX   { pmc1008mpCtrllineResetAllCountIndex }
	::= { pmc1008mpCtrllineResetAllCountTable 1 }


Pmc1008mpCtrllineResetAllCountEntry ::=
	SEQUENCE {
	pmc1008mpCtrllineResetAllCountIndex
		INTEGER,
	pmc1008mpCtrllineResetAllCountsPortn
		EkiState
	}


pmc1008mpCtrllineResetAllCountIndex OBJECT-TYPE
	SYNTAX  INTEGER(0..128)
	MAX-ACCESS  read-only
	STATUS current
	DESCRIPTION
        "
        Index definition for the pmc1008mpCtrllineResetAllCount 
        table
        "
	::= { pmc1008mpCtrllineResetAllCountEntry 1 }


pmc1008mpCtrllineResetAllCountsPortn OBJECT-TYPE
	SYNTAX  EkiState
	MAX-ACCESS read-write
	STATUS current
	DESCRIPTION
        "
        Line Counters Reset :This OID
         resets every counter on the line 
        port  <Help>   This control operates 
        a reset on the statistics current 
        ,previous and history line port 
        counters  
        "
	::= { pmc1008mpCtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pmc1008mpCntupRaRemCnt articles
--- *********************************************************

pmc1008mpCntupRaRemCntTable OBJECT-TYPE
	SYNTAX  SEQUENCE OF Pmc1008mpCntupRaRemCntEntry
	MAX-ACCESS not-accessible
	STATUS current
	DESCRIPTION
        "
        List of pmc1008mpCntupRaRemCnt 
        Article
        "
	::= { pmc1008mpCntClient 16 }


pmc1008mpCntupRaRemCntEntry OBJECT-TYPE
	SYNTAX Pmc1008mpCntupRaRemCntEntry
	MAX-ACCESS not-accessible
	STATUS current
	DESCRIPTION
        "
        Row definition for the pmc1008mpCntupRaRemCnt 
        table
        "
	INDEX   { pmc1008mpCntupRaRemCntIndex }
	::= { pmc1008mpCntupRaRemCntTable 1 }


Pmc1008mpCntupRaRemCntEntry ::=
	SEQUENCE {
	pmc1008mpCntupRaRemCntIndex
		INTEGER,
	pmc1008mpCntupRaRemCntValuePortn
		Counter32,
	pmc1008mpCntupRaRemCntErrorPortn
		EkiOnOff,
	pmc1008mpCntupRaRemCntOverloadPortn
		EkiOnOff
	}


pmc1008mpCntupRaRemCntIndex OBJECT-TYPE
	SYNTAX  INTEGER(0..128)
	MAX-ACCESS  read-only
	STATUS current
	DESCRIPTION
        "
        Index definition for the pmc1008mpCntupRaRemCnt 
        table
        "
	::= { pmc1008mpCntupRaRemCntEntry 1 }


pmc1008mpCntupRaRemCntValuePortn OBJECT-TYPE
	SYNTAX  Counter32
	MAX-ACCESS read-only
	STATUS current
	DESCRIPTION
        "
        Client Rate Adapt. Words Removal 
        :This counter is incremented each 
        time a rate adaptation 10B word 
        is removed from the Client input 
        stream
        "
	::= { pmc1008mpCntupRaRemCntEntry 2 }


pmc1008mpCntupRaRemCntErrorPortn OBJECT-TYPE
	SYNTAX  EkiOnOff
	MAX-ACCESS read-only
	STATUS current
	DESCRIPTION
        "
        Client Counter Error :This OID 
        when set indicates the rate adaptation 
        removal counter value is invalid 
        on Port
        "
	::= { pmc1008mpCntupRaRemCntEntry 3 }


pmc1008mpCntupRaRemCntOverloadPortn OBJECT-TYPE
	SYNTAX  EkiOnOff
	MAX-ACCESS read-only
	STATUS current
	DESCRIPTION
        "
        Client Counter Overload :This
         OID when set indicates a rate
         adaptation removal counter overload 
        on Port
        "
	::= { pmc1008mpCntupRaRemCntEntry 4 }


--- *********************************************************
---     TABLE for the pmc1008mpCntupRaInsCnt articles
--- *********************************************************

pmc1008mpCntupRaInsCntTable OBJECT-TYPE
	SYNTAX  SEQUENCE OF Pmc1008mpCntupRaInsCntEntry
	MAX-ACCESS not-accessible
	STATUS current
	DESCRIPTION
        "
        List of pmc1008mpCntupRaInsCnt 
        Article
        "
	::= { pmc1008mpCntClient 24 }


pmc1008mpCntupRaInsCntEntry OBJECT-TYPE
	SYNTAX Pmc1008mpCntupRaInsCntEntry
	MAX-ACCESS not-accessible
	STATUS current
	DESCRIPTION
        "
        Row definition for the pmc1008mpCntupRaInsCnt 
        table
        "
	INDEX   { pmc1008mpCntupRaInsCntIndex }
	::= { pmc1008mpCntupRaInsCntTable 1 }


Pmc1008mpCntupRaInsCntEntry ::=
	SEQUENCE {
	pmc1008mpCntupRaInsCntIndex
		INTEGER,
	pmc1008mpCntupRaInsCntValuePortn
		Counter32,
	pmc1008mpCntupRaInsCntErrorPortn
		EkiOnOff,
	pmc1008mpCntupRaInsCntOverloadPortn
		EkiOnOff
	}


pmc1008mpCntupRaInsCntIndex OBJECT-TYPE
	SYNTAX  INTEGER(0..128)
	MAX-ACCESS  read-only
	STATUS current
	DESCRIPTION
        "
        Index definition for the pmc1008mpCntupRaInsCnt 
        table
        "
	::= { pmc1008mpCntupRaInsCntEntry 1 }


pmc1008mpCntupRaInsCntValuePortn OBJECT-TYPE
	SYNTAX  Counter32
	MAX-ACCESS read-only
	STATUS current
	DESCRIPTION
        "
        Client Rate Adapt. Words Insertion 
        :This counter is incremented each 
        time a rate adaptation 10B word 
        is inserted in the Client input 
        stream
        "
	::= { pmc1008mpCntupRaInsCntEntry 2 }


pmc1008mpCntupRaInsCntErrorPortn OBJECT-TYPE
	SYNTAX  EkiOnOff
	MAX-ACCESS read-only
	STATUS current
	DESCRIPTION
        "
        Client Counter Error :This OID 
        when set indicates the rate adaptation 
        insertion counter value is invalid 
        on Port
        "
	::= { pmc1008mpCntupRaInsCntEntry 3 }


pmc1008mpCntupRaInsCntOverloadPortn OBJECT-TYPE
	SYNTAX  EkiOnOff
	MAX-ACCESS read-only
	STATUS current
	DESCRIPTION
        "
        Client Counter Overload :This
         OID when set indicates a rate
         adaptation insertion counter overload 
        on Port
        "
	::= { pmc1008mpCntupRaInsCntEntry 4 }


--- *********************************************************
---     TABLE for the pmc1008mpCntupRdErrCnt articles
--- *********************************************************

pmc1008mpCntupRdErrCntTable OBJECT-TYPE
	SYNTAX  SEQUENCE OF Pmc1008mpCntupRdErrCntEntry
	MAX-ACCESS not-accessible
	STATUS current
	DESCRIPTION
        "
        List of pmc1008mpCntupRdErrCnt 
        Article
        "
	::= { pmc1008mpCntClient 32 }


pmc1008mpCntupRdErrCntEntry OBJECT-TYPE
	SYNTAX Pmc1008mpCntupRdErrCntEntry
	MAX-ACCESS not-accessible
	STATUS current
	DESCRIPTION
        "
        Row definition for the pmc1008mpCntupRdErrCnt 
        table
        "
	INDEX   { pmc1008mpCntupRdErrCntIndex }
	::= { pmc1008mpCntupRdErrCntTable 1 }


Pmc1008mpCntupRdErrCntEntry ::=
	SEQUENCE {
	pmc1008mpCntupRdErrCntIndex
		INTEGER,
	pmc1008mpCntupRdErrCntValuePortn
		Counter32,
	pmc1008mpCntupRdErrCntErrorPortn
		EkiOnOff,
	pmc1008mpCntupRdErrCntOverloadPortn
		EkiOnOff
	}


pmc1008mpCntupRdErrCntIndex OBJECT-TYPE
	SYNTAX  INTEGER(0..128)
	MAX-ACCESS  read-only
	STATUS current
	DESCRIPTION
        "
        Index definition for the pmc1008mpCntupRdErrCnt 
        table
        "
	::= { pmc1008mpCntupRdErrCntEntry 1 }


pmc1008mpCntupRdErrCntValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of 10b/8b running disparity errors 
        on the client port
        "
	::= { pmc1008mpCntupRdErrCntEntry 2 }


pmc1008mpCntupRdErrCntErrorPortn OBJECT-TYPE
	SYNTAX  EkiOnOff
	MAX-ACCESS read-only
	STATUS current
	DESCRIPTION
        "
        Client Counter Error :This OID 
        when set indicates the client error 
        counter value is invalid on Port
        "
	::= { pmc1008mpCntupRdErrCntEntry 3 }


pmc1008mpCntupRdErrCntOverloadPortn OBJECT-TYPE
	SYNTAX  EkiOnOff
	MAX-ACCESS read-only
	STATUS current
	DESCRIPTION
        "
        Client Counter Overload :This
         OID when set indicates a client 
        input error counter overload on 
        Port
        "
	::= { pmc1008mpCntupRdErrCntEntry 4 }


--- *********************************************************
---     TABLE for the pmc1008mpCntupTimCnt articles
--- *********************************************************

pmc1008mpCntupTimCntTable OBJECT-TYPE
	SYNTAX  SEQUENCE OF Pmc1008mpCntupTimCntEntry
	MAX-ACCESS not-accessible
	STATUS current
	DESCRIPTION
        "
        List of pmc1008mpCntupTimCnt Article
        "
	::= { pmc1008mpCntClient 40 }


pmc1008mpCntupTimCntEntry OBJECT-TYPE
	SYNTAX Pmc1008mpCntupTimCntEntry
	MAX-ACCESS not-accessible
	STATUS current
	DESCRIPTION
        "
        Row definition for the pmc1008mpCntupTimCnt 
        table
        "
	INDEX   { pmc1008mpCntupTimCntIndex }
	::= { pmc1008mpCntupTimCntTable 1 }


Pmc1008mpCntupTimCntEntry ::=
	SEQUENCE {
	pmc1008mpCntupTimCntIndex
		INTEGER,
	pmc1008mpCntupTimCntValuePortn
		Counter32,
	pmc1008mpCntupTimCntErrorPortn
		EkiOnOff,
	pmc1008mpCntupTimCntOverloadPortn
		EkiOnOff
	}


pmc1008mpCntupTimCntIndex OBJECT-TYPE
	SYNTAX  INTEGER(0..128)
	MAX-ACCESS  read-only
	STATUS current
	DESCRIPTION
        "
        Index definition for the pmc1008mpCntupTimCnt 
        table
        "
	::= { pmc1008mpCntupTimCntEntry 1 }


pmc1008mpCntupTimCntValuePortn OBJECT-TYPE
	SYNTAX  Counter32
	MAX-ACCESS read-only
	STATUS current
	DESCRIPTION
        "
        Client Upstream Timer Counter
         :This is the timing counter dedicated 
        to the upstream access counters. 
        It is incremented every 125 us.
        "
	::= { pmc1008mpCntupTimCntEntry 2 }


pmc1008mpCntupTimCntErrorPortn OBJECT-TYPE
	SYNTAX  EkiOnOff
	MAX-ACCESS read-only
	STATUS current
	DESCRIPTION
        "
        Client Counter Error :This OID 
        when set indicates the upstream 
        timing counter value is invalid 
        on Port
        "
	::= { pmc1008mpCntupTimCntEntry 3 }


pmc1008mpCntupTimCntOverloadPortn OBJECT-TYPE
	SYNTAX  EkiOnOff
	MAX-ACCESS read-only
	STATUS current
	DESCRIPTION
        "
        Client Counter Overload :This
         OID when set indicates a upstream 
        timing counter overload on Port
        "
	::= { pmc1008mpCntupTimCntEntry 4 }


--- *********************************************************
---     TABLE for the pmc1008mpCntupCvErrCnt articles
--- *********************************************************

pmc1008mpCntupCvErrCntTable OBJECT-TYPE
	SYNTAX  SEQUENCE OF Pmc1008mpCntupCvErrCntEntry
	MAX-ACCESS not-accessible
	STATUS current
	DESCRIPTION
        "
        List of pmc1008mpCntupCvErrCnt 
        Article
        "
	::= { pmc1008mpCntClient 48 }


pmc1008mpCntupCvErrCntEntry OBJECT-TYPE
	SYNTAX Pmc1008mpCntupCvErrCntEntry
	MAX-ACCESS not-accessible
	STATUS current
	DESCRIPTION
        "
        Row definition for the pmc1008mpCntupCvErrCnt 
        table
        "
	INDEX   { pmc1008mpCntupCvErrCntIndex }
	::= { pmc1008mpCntupCvErrCntTable 1 }


Pmc1008mpCntupCvErrCntEntry ::=
	SEQUENCE {
	pmc1008mpCntupCvErrCntIndex
		INTEGER,
	pmc1008mpCntupCvErrCntValuePortn
		Counter32,
	pmc1008mpCntupCvErrCntErrorPortn
		EkiOnOff,
	pmc1008mpCntupCvErrCntOverloadPortn
		EkiOnOff
	}


pmc1008mpCntupCvErrCntIndex OBJECT-TYPE
	SYNTAX  INTEGER(0..128)
	MAX-ACCESS  read-only
	STATUS current
	DESCRIPTION
        "
        Index definition for the pmc1008mpCntupCvErrCnt 
        table
        "
	::= { pmc1008mpCntupCvErrCntEntry 1 }


pmc1008mpCntupCvErrCntValuePortn OBJECT-TYPE
	SYNTAX  Counter32
	MAX-ACCESS read-only
	STATUS current
	DESCRIPTION
        "
        Client Coding Violation Counter 
        :This counter is increased each 
        time a 10b/8b coding violation
         is detected on the Client input 
        stream
        "
	::= { pmc1008mpCntupCvErrCntEntry 2 }


pmc1008mpCntupCvErrCntErrorPortn OBJECT-TYPE
	SYNTAX  EkiOnOff
	MAX-ACCESS read-only
	STATUS current
	DESCRIPTION
        "
        Client Counter Error :This OID 
        when set indicates the coding violation 
        counter value is invalid on Port
        "
	::= { pmc1008mpCntupCvErrCntEntry 3 }


pmc1008mpCntupCvErrCntOverloadPortn OBJECT-TYPE
	SYNTAX  EkiOnOff
	MAX-ACCESS read-only
	STATUS current
	DESCRIPTION
        "
        Client Counter Overload :This
         OID when set indicates a coding 
        violation counter overload on Port
        "
	::= { pmc1008mpCntupCvErrCntEntry 4 }


--- *********************************************************
---     TABLE for the pmc1008mpCntdwCbipCnt articles
--- *********************************************************

pmc1008mpCntdwCbipCntTable OBJECT-TYPE
	SYNTAX  SEQUENCE OF Pmc1008mpCntdwCbipCntEntry
	MAX-ACCESS not-accessible
	STATUS current
	DESCRIPTION
        "
        List of pmc1008mpCntdwCbipCnt
         Article
        "
	::= { pmc1008mpCntClient 64 }


pmc1008mpCntdwCbipCntEntry OBJECT-TYPE
	SYNTAX Pmc1008mpCntdwCbipCntEntry
	MAX-ACCESS not-accessible
	STATUS current
	DESCRIPTION
        "
        Row definition for the pmc1008mpCntdwCbipCnt 
        table
        "
	INDEX   { pmc1008mpCntdwCbipCntIndex }
	::= { pmc1008mpCntdwCbipCntTable 1 }


Pmc1008mpCntdwCbipCntEntry ::=
	SEQUENCE {
	pmc1008mpCntdwCbipCntIndex
		INTEGER,
	pmc1008mpCntdwCbipCntValuePortn
		Counter32,
	pmc1008mpCntdwCbipCntErrorPortn
		EkiOnOff,
	pmc1008mpCntdwCbipCntOverloadPortn
		EkiOnOff
	}


pmc1008mpCntdwCbipCntIndex OBJECT-TYPE
	SYNTAX  INTEGER(0..128)
	MAX-ACCESS  read-only
	STATUS current
	DESCRIPTION
        "
        Index definition for the pmc1008mpCntdwCbipCnt 
        table
        "
	::= { pmc1008mpCntdwCbipCntEntry 1 }


pmc1008mpCntdwCbipCntValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of CBIP 
        errors on the client port
        "
	::= { pmc1008mpCntdwCbipCntEntry 2 }


pmc1008mpCntdwCbipCntErrorPortn OBJECT-TYPE
	SYNTAX  EkiOnOff
	MAX-ACCESS read-only
	STATUS current
	DESCRIPTION
        "
        Client Counter Error :This OID 
        when set indicates the CBIP error 
        counter value is invalid on Port
        "
	::= { pmc1008mpCntdwCbipCntEntry 3 }


pmc1008mpCntdwCbipCntOverloadPortn OBJECT-TYPE
	SYNTAX  EkiOnOff
	MAX-ACCESS read-only
	STATUS current
	DESCRIPTION
        "
        Client CBIP Counter Overload :This 
        OID when set indicates a CBIP error 
        counter overload on Port
        "
	::= { pmc1008mpCntdwCbipCntEntry 4 }


--- *********************************************************
---     TABLE for the pmc1008mpCntdwTimCnt articles
--- *********************************************************

pmc1008mpCntdwTimCntTable OBJECT-TYPE
	SYNTAX  SEQUENCE OF Pmc1008mpCntdwTimCntEntry
	MAX-ACCESS not-accessible
	STATUS current
	DESCRIPTION
        "
        List of pmc1008mpCntdwTimCnt Article
        "
	::= { pmc1008mpCntClient 72 }


pmc1008mpCntdwTimCntEntry OBJECT-TYPE
	SYNTAX Pmc1008mpCntdwTimCntEntry
	MAX-ACCESS not-accessible
	STATUS current
	DESCRIPTION
        "
        Row definition for the pmc1008mpCntdwTimCnt 
        table
        "
	INDEX   { pmc1008mpCntdwTimCntIndex }
	::= { pmc1008mpCntdwTimCntTable 1 }


Pmc1008mpCntdwTimCntEntry ::=
	SEQUENCE {
	pmc1008mpCntdwTimCntIndex
		INTEGER,
	pmc1008mpCntdwTimCntValuePortn
		Counter32,
	pmc1008mpCntdwTimCntErrorPortn
		EkiOnOff,
	pmc1008mpCntdwTimCntOverloadPortn
		EkiOnOff
	}


pmc1008mpCntdwTimCntIndex OBJECT-TYPE
	SYNTAX  INTEGER(0..128)
	MAX-ACCESS  read-only
	STATUS current
	DESCRIPTION
        "
        Index definition for the pmc1008mpCntdwTimCnt 
        table
        "
	::= { pmc1008mpCntdwTimCntEntry 1 }


pmc1008mpCntdwTimCntValuePortn OBJECT-TYPE
	SYNTAX  Counter32
	MAX-ACCESS read-only
	STATUS current
	DESCRIPTION
        "
        Client Downstream Timer Counter 
        :This is the timing counter dedicated 
        to the downstream access counters. 
        It is incremented every 125 us.
        "
	::= { pmc1008mpCntdwTimCntEntry 2 }


pmc1008mpCntdwTimCntErrorPortn OBJECT-TYPE
	SYNTAX  EkiOnOff
	MAX-ACCESS read-only
	STATUS current
	DESCRIPTION
        "
        Client Counter Error :This OID 
        when set indicates the downstream 
        timer counter value is invalid
         on Port
        "
	::= { pmc1008mpCntdwTimCntEntry 3 }


pmc1008mpCntdwTimCntOverloadPortn OBJECT-TYPE
	SYNTAX  EkiOnOff
	MAX-ACCESS read-only
	STATUS current
	DESCRIPTION
        "
        Client Counter Overload :This
         OID when set indicates a downstream 
        timer counter overload on Port
        "
	::= { pmc1008mpCntdwTimCntEntry 4 }


--- *********************************************************
---     TABLE for the pmc1008mpCntdfrmB1ErrCnt articles
--- *********************************************************

pmc1008mpCntdfrmB1ErrCntTable OBJECT-TYPE
	SYNTAX  SEQUENCE OF Pmc1008mpCntdfrmB1ErrCntEntry
	MAX-ACCESS not-accessible
	STATUS current
	DESCRIPTION
        "
        List of pmc1008mpCntdfrmB1ErrCnt 
        Article
        "
	::= { pmc1008mpCntLine 152 }


pmc1008mpCntdfrmB1ErrCntEntry OBJECT-TYPE
	SYNTAX Pmc1008mpCntdfrmB1ErrCntEntry
	MAX-ACCESS not-accessible
	STATUS current
	DESCRIPTION
        "
        Row definition for the pmc1008mpCntdfrmB1ErrCnt 
        table
        "
	INDEX   { pmc1008mpCntdfrmB1ErrCntIndex }
	::= { pmc1008mpCntdfrmB1ErrCntTable 1 }


Pmc1008mpCntdfrmB1ErrCntEntry ::=
	SEQUENCE {
	pmc1008mpCntdfrmB1ErrCntIndex
		INTEGER,
	pmc1008mpCntdfrmB1ErrCntValuePortn
		Counter32,
	pmc1008mpCntdfrmB1ErrCntErrorPortn
		EkiOnOff,
	pmc1008mpCntdfrmB1ErrCntOverloadPortn
		EkiOnOff
	}


pmc1008mpCntdfrmB1ErrCntIndex OBJECT-TYPE
	SYNTAX  INTEGER(0..128)
	MAX-ACCESS  read-only
	STATUS current
	DESCRIPTION
        "
        Index definition for the pmc1008mpCntdfrmB1ErrCnt 
        table
        "
	::= { pmc1008mpCntdfrmB1ErrCntEntry 1 }


pmc1008mpCntdfrmB1ErrCntValuePortn OBJECT-TYPE
	SYNTAX  Counter32
	MAX-ACCESS read-only
	STATUS current
	DESCRIPTION
        "
        Line Input B1 Errors :This counter 
        is incremented each time a B1 error 
        is detected on the Deframer input 
        stream.  <Help>  This counter gives 
        the number of B1 errors on the
         line port
        "
	::= { pmc1008mpCntdfrmB1ErrCntEntry 2 }


pmc1008mpCntdfrmB1ErrCntErrorPortn OBJECT-TYPE
	SYNTAX  EkiOnOff
	MAX-ACCESS read-only
	STATUS current
	DESCRIPTION
        "
        Line Counter Error :This OID when 
        set indicates the B1 error counter 
        value is invalid on Port
        "
	::= { pmc1008mpCntdfrmB1ErrCntEntry 3 }


pmc1008mpCntdfrmB1ErrCntOverloadPortn OBJECT-TYPE
	SYNTAX  EkiOnOff
	MAX-ACCESS read-only
	STATUS current
	DESCRIPTION
        "
        Line Counter Overload :This OID 
        when set indicates a B1 error counter 
        overload on Port
        "
	::= { pmc1008mpCntdfrmB1ErrCntEntry 4 }


--- *********************************************************
---     TABLE for the pmc1008mpCntdfrmTimCnt articles
--- *********************************************************

pmc1008mpCntdfrmTimCntTable OBJECT-TYPE
	SYNTAX  SEQUENCE OF Pmc1008mpCntdfrmTimCntEntry
	MAX-ACCESS not-accessible
	STATUS current
	DESCRIPTION
        "
        List of pmc1008mpCntdfrmTimCnt 
        Article
        "
	::= { pmc1008mpCntLine 153 }


pmc1008mpCntdfrmTimCntEntry OBJECT-TYPE
	SYNTAX Pmc1008mpCntdfrmTimCntEntry
	MAX-ACCESS not-accessible
	STATUS current
	DESCRIPTION
        "
        Row definition for the pmc1008mpCntdfrmTimCnt 
        table
        "
	INDEX   { pmc1008mpCntdfrmTimCntIndex }
	::= { pmc1008mpCntdfrmTimCntTable 1 }


Pmc1008mpCntdfrmTimCntEntry ::=
	SEQUENCE {
	pmc1008mpCntdfrmTimCntIndex
		INTEGER,
	pmc1008mpCntdfrmTimCntValuePortn
		Counter32,
	pmc1008mpCntdfrmTimCntErrorPortn
		EkiOnOff,
	pmc1008mpCntdfrmTimCntOverloadPortn
		EkiOnOff
	}


pmc1008mpCntdfrmTimCntIndex OBJECT-TYPE
	SYNTAX  INTEGER(0..128)
	MAX-ACCESS  read-only
	STATUS current
	DESCRIPTION
        "
        Index definition for the pmc1008mpCntdfrmTimCnt 
        table
        "
	::= { pmc1008mpCntdfrmTimCntEntry 1 }


pmc1008mpCntdfrmTimCntValuePortn OBJECT-TYPE
	SYNTAX  Counter32
	MAX-ACCESS read-only
	STATUS current
	DESCRIPTION
        "
        Line Timer Counter :This is the 
        timing counter dedicated to the 
        downstream deframer counters. It 
        is incremented every 125 us.
        "
	::= { pmc1008mpCntdfrmTimCntEntry 2 }


pmc1008mpCntdfrmTimCntErrorPortn OBJECT-TYPE
	SYNTAX  EkiOnOff
	MAX-ACCESS read-only
	STATUS current
	DESCRIPTION
        "
        Line Counter Error :This OID when 
        set indicates the deframer timer 
        counter value is invalid on Port
        "
	::= { pmc1008mpCntdfrmTimCntEntry 3 }


pmc1008mpCntdfrmTimCntOverloadPortn OBJECT-TYPE
	SYNTAX  EkiOnOff
	MAX-ACCESS read-only
	STATUS current
	DESCRIPTION
        "
        Line Counter Overload :This OID 
        when set indicates a deframer timer 
        counter overload on Port
        "
	::= { pmc1008mpCntdfrmTimCntEntry 4 }


--- *********************************************************
---     TABLE for the pmc1008mpCntdfrmPrimLineErrCnt articles
--- *********************************************************

pmc1008mpCntdfrmPrimLineErrCntTable OBJECT-TYPE
	SYNTAX  SEQUENCE OF Pmc1008mpCntdfrmPrimLineErrCntEntry
	MAX-ACCESS not-accessible
	STATUS current
	DESCRIPTION
        "
        List of pmc1008mpCntdfrmPrimLineErrCnt 
        Article
        "
	::= { pmc1008mpCntLine 154 }


pmc1008mpCntdfrmPrimLineErrCntEntry OBJECT-TYPE
	SYNTAX Pmc1008mpCntdfrmPrimLineErrCntEntry
	MAX-ACCESS not-accessible
	STATUS current
	DESCRIPTION
        "
        Row definition for the pmc1008mpCntdfrmPrimLineErrCnt 
        table
        "
	INDEX   { pmc1008mpCntdfrmPrimLineErrCntIndex }
	::= { pmc1008mpCntdfrmPrimLineErrCntTable 1 }


Pmc1008mpCntdfrmPrimLineErrCntEntry ::=
	SEQUENCE {
	pmc1008mpCntdfrmPrimLineErrCntIndex
		INTEGER,
	pmc1008mpCntdfrmPrimLineErrCntValuePortn
		Counter32,
	pmc1008mpCntdfrmPrimLineErrCntErrorPortn
		EkiOnOff,
	pmc1008mpCntdfrmPrimLineErrCntOverloadPortn
		EkiOnOff
	}


pmc1008mpCntdfrmPrimLineErrCntIndex OBJECT-TYPE
	SYNTAX  INTEGER(0..128)
	MAX-ACCESS  read-only
	STATUS current
	DESCRIPTION
        "
        Index definition for the pmc1008mpCntdfrmPrimLineErrCnt 
        table
        "
	::= { pmc1008mpCntdfrmPrimLineErrCntEntry 1 }


pmc1008mpCntdfrmPrimLineErrCntValuePortn OBJECT-TYPE
	SYNTAX  Counter32
	MAX-ACCESS read-only
	STATUS current
	DESCRIPTION
        "
        Line Input FEC Corrected Errors 
        :This counter is incremented each 
        time the FEC is correcting an error 
        on the line input stream.  <Help> 
         This counter gives the number
         of errors corrected by the FEC 
        on the line port
        "
	::= { pmc1008mpCntdfrmPrimLineErrCntEntry 2 }


pmc1008mpCntdfrmPrimLineErrCntErrorPortn OBJECT-TYPE
	SYNTAX  EkiOnOff
	MAX-ACCESS read-only
	STATUS current
	DESCRIPTION
        "
        FEC Counter Error :This bit when 
        set indicates the FEC corrected 
        errors counter value is invalid 
        on Line
        "
	::= { pmc1008mpCntdfrmPrimLineErrCntEntry 3 }


pmc1008mpCntdfrmPrimLineErrCntOverloadPortn OBJECT-TYPE
	SYNTAX  EkiOnOff
	MAX-ACCESS read-only
	STATUS current
	DESCRIPTION
        "
        FEC Counter Overload :This bit 
        when set indicates a FEC corrected 
        errors counter overload on Line
        "
	::= { pmc1008mpCntdfrmPrimLineErrCntEntry 4 }


pmc1008mpCntCountersReset  OBJECT-TYPE
	SYNTAX EkiOnOff
	MAX-ACCESS read-write
	STATUS current
	DESCRIPTION
	"Counters Reset:This OID resets and restarts all the counters"
	::= { pmc1008mpcounters  259 }

pmc1008mpCntCountersStop  OBJECT-TYPE
	SYNTAX EkiOnOff
	MAX-ACCESS read-write
	STATUS current
	DESCRIPTION
	"Counters stop:This OID stops all the counters"
	::= { pmc1008mpcounters 260 }






--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pmc1008mpMonupRmonByteCnt articles
--- *********************************************************

pmc1008mpMonupRmonByteCntTable OBJECT-TYPE
	SYNTAX  SEQUENCE OF Pmc1008mpMonupRmonByteCntEntry
	MAX-ACCESS not-accessible
	STATUS current
	DESCRIPTION
        "
        List of pmc1008mpMonupRmonByteCnt 
        Article
        "
	::= { pmc1008mpMonClientRmonCounter 16 }


pmc1008mpMonupRmonByteCntEntry OBJECT-TYPE
	SYNTAX Pmc1008mpMonupRmonByteCntEntry
	MAX-ACCESS not-accessible
	STATUS current
	DESCRIPTION
        "
        Row definition for the pmc1008mpMonupRmonByteCnt 
        table
        "
	INDEX   { pmc1008mpMonupRmonByteCntIndex }
	::= { pmc1008mpMonupRmonByteCntTable 1 }


Pmc1008mpMonupRmonByteCntEntry ::=
	SEQUENCE {
	pmc1008mpMonupRmonByteCntIndex
		INTEGER,
	pmc1008mpMonupRmonByteCntValuePortn
		Counter64,
	pmc1008mpMonupRmonByteCntErrorPortn
		EkiOnOff,
	pmc1008mpMonupRmonByteCntOverloadPortn
		EkiOnOff
	}


pmc1008mpMonupRmonByteCntIndex OBJECT-TYPE
	SYNTAX  INTEGER(0..128)
	MAX-ACCESS  read-only
	STATUS current
	DESCRIPTION
        "
        Index definition for the pmc1008mpMonupRmonByteCnt 
        table
        "
	::= { pmc1008mpMonupRmonByteCntEntry 1 }


pmc1008mpMonupRmonByteCntValuePortn OBJECT-TYPE
	SYNTAX  Counter64
	MAX-ACCESS read-only
	STATUS current
	DESCRIPTION
        "
        Bytes Counter On Client Input
         :This counter is increased each 
        time a data byte is received on 
        the client port  <Help>  This counter 
        gives the number of bytes received 
        on the client port
        "
	::= { pmc1008mpMonupRmonByteCntEntry 2 }


pmc1008mpMonupRmonByteCntErrorPortn OBJECT-TYPE
	SYNTAX  EkiOnOff
	MAX-ACCESS read-only
	STATUS current
	DESCRIPTION
        "
        Bytes Counter Error :This OID
         when set indicates the Bytes counter 
        value is invalid on clinet port
        "
	::= { pmc1008mpMonupRmonByteCntEntry 3 }


pmc1008mpMonupRmonByteCntOverloadPortn OBJECT-TYPE
	SYNTAX  EkiOnOff
	MAX-ACCESS read-only
	STATUS current
	DESCRIPTION
        "
        Bytes Counter Overload :This OID 
        when set indicates a Bytes counter 
        overload on client port
        "
	::= { pmc1008mpMonupRmonByteCntEntry 4 }


--- *********************************************************
---     TABLE for the pmc1008mpMonupRmonCrcErrorCnt articles
--- *********************************************************

pmc1008mpMonupRmonCrcErrorCntTable OBJECT-TYPE
	SYNTAX  SEQUENCE OF Pmc1008mpMonupRmonCrcErrorCntEntry
	MAX-ACCESS not-accessible
	STATUS current
	DESCRIPTION
        "
        List of pmc1008mpMonupRmonCrcErrorCnt 
        Article
        "
	::= { pmc1008mpMonClientRmonCounter 24 }


pmc1008mpMonupRmonCrcErrorCntEntry OBJECT-TYPE
	SYNTAX Pmc1008mpMonupRmonCrcErrorCntEntry
	MAX-ACCESS not-accessible
	STATUS current
	DESCRIPTION
        "
        Row definition for the pmc1008mpMonupRmonCrcErrorCnt 
        table
        "
	INDEX   { pmc1008mpMonupRmonCrcErrorCntIndex }
	::= { pmc1008mpMonupRmonCrcErrorCntTable 1 }


Pmc1008mpMonupRmonCrcErrorCntEntry ::=
	SEQUENCE {
	pmc1008mpMonupRmonCrcErrorCntIndex
		INTEGER,
	pmc1008mpMonupRmonCrcErrorCntValuePortn
		Counter64,
	pmc1008mpMonupRmonCrcErrorCntErrorPortn
		EkiOnOff,
	pmc1008mpMonupRmonCrcErrorCntOverloadPortn
		EkiOnOff
	}


pmc1008mpMonupRmonCrcErrorCntIndex OBJECT-TYPE
	SYNTAX  INTEGER(0..128)
	MAX-ACCESS  read-only
	STATUS current
	DESCRIPTION
        "
        Index definition for the pmc1008mpMonupRmonCrcErrorCnt 
        table
        "
	::= { pmc1008mpMonupRmonCrcErrorCntEntry 1 }


pmc1008mpMonupRmonCrcErrorCntValuePortn OBJECT-TYPE
	SYNTAX  Counter64
	MAX-ACCESS read-only
	STATUS current
	DESCRIPTION
        "
        CRC Errors Counter On Client Input 
        :This counter is increased each 
        time a CRC error is detected on 
        the client port  <Help>  This counter 
        gives the number of CRC Errors
         received on the client port
        "
	::= { pmc1008mpMonupRmonCrcErrorCntEntry 2 }


pmc1008mpMonupRmonCrcErrorCntErrorPortn OBJECT-TYPE
	SYNTAX  EkiOnOff
	MAX-ACCESS read-only
	STATUS current
	DESCRIPTION
        "
        CRC Errors Counter Error :This 
        OID when set indicates the CRC
         Errors counter value is invalid 
        on clinet port
        "
	::= { pmc1008mpMonupRmonCrcErrorCntEntry 3 }


pmc1008mpMonupRmonCrcErrorCntOverloadPortn OBJECT-TYPE
	SYNTAX  EkiOnOff
	MAX-ACCESS read-only
	STATUS current
	DESCRIPTION
        "
        CRC Errors Counter Overload :This 
        OID when set indicates a CRC Errors 
        counter overload on client port
        "
	::= { pmc1008mpMonupRmonCrcErrorCntEntry 4 }


--- *********************************************************
---     TABLE for the pmc1008mpMonupRmonPacketsCnt articles
--- *********************************************************

pmc1008mpMonupRmonPacketsCntTable OBJECT-TYPE
	SYNTAX  SEQUENCE OF Pmc1008mpMonupRmonPacketsCntEntry
	MAX-ACCESS not-accessible
	STATUS current
	DESCRIPTION
        "
        List of pmc1008mpMonupRmonPacketsCnt 
        Article
        "
	::= { pmc1008mpMonClientRmonCounter 32 }


pmc1008mpMonupRmonPacketsCntEntry OBJECT-TYPE
	SYNTAX Pmc1008mpMonupRmonPacketsCntEntry
	MAX-ACCESS not-accessible
	STATUS current
	DESCRIPTION
        "
        Row definition for the pmc1008mpMonupRmonPacketsCnt 
        table
        "
	INDEX   { pmc1008mpMonupRmonPacketsCntIndex }
	::= { pmc1008mpMonupRmonPacketsCntTable 1 }


Pmc1008mpMonupRmonPacketsCntEntry ::=
	SEQUENCE {
	pmc1008mpMonupRmonPacketsCntIndex
		INTEGER,
	pmc1008mpMonupRmonPacketsCntValuePortn
		Counter64,
	pmc1008mpMonupRmonPacketsCntErrorPortn
		EkiOnOff,
	pmc1008mpMonupRmonPacketsCntOverloadPortn
		EkiOnOff
	}


pmc1008mpMonupRmonPacketsCntIndex OBJECT-TYPE
	SYNTAX  INTEGER(0..128)
	MAX-ACCESS  read-only
	STATUS current
	DESCRIPTION
        "
        Index definition for the pmc1008mpMonupRmonPacketsCnt 
        table
        "
	::= { pmc1008mpMonupRmonPacketsCntEntry 1 }


pmc1008mpMonupRmonPacketsCntValuePortn OBJECT-TYPE
	SYNTAX  Counter64
	MAX-ACCESS read-only
	STATUS current
	DESCRIPTION
        "
        Packets Counter On Client Input 
        :This counter is increased each 
        time a packet is received on the 
        client port  <Help>  This counter 
        gives the number of packets received 
        on the client port
        "
	::= { pmc1008mpMonupRmonPacketsCntEntry 2 }


pmc1008mpMonupRmonPacketsCntErrorPortn OBJECT-TYPE
	SYNTAX  EkiOnOff
	MAX-ACCESS read-only
	STATUS current
	DESCRIPTION
        "
        Packets Counter Error :This OID 
        when set indicates the Packets
         counter value is invalid on clinet 
        port
        "
	::= { pmc1008mpMonupRmonPacketsCntEntry 3 }


pmc1008mpMonupRmonPacketsCntOverloadPortn OBJECT-TYPE
	SYNTAX  EkiOnOff
	MAX-ACCESS read-only
	STATUS current
	DESCRIPTION
        "
        Packets Counter Overload :This 
        OID when set indicates a Packets 
        counter overload on client port
        "
	::= { pmc1008mpMonupRmonPacketsCntEntry 4 }


--- *********************************************************
---     TABLE for the pmc1008mpMonupRmonBroadcastCnt articles
--- *********************************************************

pmc1008mpMonupRmonBroadcastCntTable OBJECT-TYPE
	SYNTAX  SEQUENCE OF Pmc1008mpMonupRmonBroadcastCntEntry
	MAX-ACCESS not-accessible
	STATUS current
	DESCRIPTION
        "
        List of pmc1008mpMonupRmonBroadcastCnt 
        Article
        "
	::= { pmc1008mpMonClientRmonCounter 40 }


pmc1008mpMonupRmonBroadcastCntEntry OBJECT-TYPE
	SYNTAX Pmc1008mpMonupRmonBroadcastCntEntry
	MAX-ACCESS not-accessible
	STATUS current
	DESCRIPTION
        "
        Row definition for the pmc1008mpMonupRmonBroadcastCnt 
        table
        "
	INDEX   { pmc1008mpMonupRmonBroadcastCntIndex }
	::= { pmc1008mpMonupRmonBroadcastCntTable 1 }


Pmc1008mpMonupRmonBroadcastCntEntry ::=
	SEQUENCE {
	pmc1008mpMonupRmonBroadcastCntIndex
		INTEGER,
	pmc1008mpMonupRmonBroadcastCntValuePortn
		Counter64,
	pmc1008mpMonupRmonBroadcastCntErrorPortn
		EkiOnOff,
	pmc1008mpMonupRmonBroadcastCntOverloadPortn
		EkiOnOff
	}


pmc1008mpMonupRmonBroadcastCntIndex OBJECT-TYPE
	SYNTAX  INTEGER(0..128)
	MAX-ACCESS  read-only
	STATUS current
	DESCRIPTION
        "
        Index definition for the pmc1008mpMonupRmonBroadcastCnt 
        table
        "
	::= { pmc1008mpMonupRmonBroadcastCntEntry 1 }


pmc1008mpMonupRmonBroadcastCntValuePortn OBJECT-TYPE
	SYNTAX  Counter64
	MAX-ACCESS read-only
	STATUS current
	DESCRIPTION
        "
        Broadcast Counter On Client Input 
        :This counter is increased each 
        time a broadcast packet is received 
        on the client port  <Help>  This 
        counter gives the number of Broadcast 
        packets received on the client
         port
        "
	::= { pmc1008mpMonupRmonBroadcastCntEntry 2 }


pmc1008mpMonupRmonBroadcastCntErrorPortn OBJECT-TYPE
	SYNTAX  EkiOnOff
	MAX-ACCESS read-only
	STATUS current
	DESCRIPTION
        "
        Broadcast Counter Error :This
         OID when set indicates the Broadcast 
        counter value is invalid on clinet 
        port
        "
	::= { pmc1008mpMonupRmonBroadcastCntEntry 3 }


pmc1008mpMonupRmonBroadcastCntOverloadPortn OBJECT-TYPE
	SYNTAX  EkiOnOff
	MAX-ACCESS read-only
	STATUS current
	DESCRIPTION
        "
        Broadcast Counter Overload :This 
        OID when set indicates a Broadcast 
        counter overload on client port
        "
	::= { pmc1008mpMonupRmonBroadcastCntEntry 4 }


--- *********************************************************
---     TABLE for the pmc1008mpMonupRmonMulticastCnt articles
--- *********************************************************

pmc1008mpMonupRmonMulticastCntTable OBJECT-TYPE
	SYNTAX  SEQUENCE OF Pmc1008mpMonupRmonMulticastCntEntry
	MAX-ACCESS not-accessible
	STATUS current
	DESCRIPTION
        "
        List of pmc1008mpMonupRmonMulticastCnt 
        Article
        "
	::= { pmc1008mpMonClientRmonCounter 48 }


pmc1008mpMonupRmonMulticastCntEntry OBJECT-TYPE
	SYNTAX Pmc1008mpMonupRmonMulticastCntEntry
	MAX-ACCESS not-accessible
	STATUS current
	DESCRIPTION
        "
        Row definition for the pmc1008mpMonupRmonMulticastCnt 
        table
        "
	INDEX   { pmc1008mpMonupRmonMulticastCntIndex }
	::= { pmc1008mpMonupRmonMulticastCntTable 1 }


Pmc1008mpMonupRmonMulticastCntEntry ::=
	SEQUENCE {
	pmc1008mpMonupRmonMulticastCntIndex
		INTEGER,
	pmc1008mpMonupRmonMulticastCntValuePortn
		Counter64,
	pmc1008mpMonupRmonMulticastCntErrorPortn
		EkiOnOff,
	pmc1008mpMonupRmonMulticastCntOverloadPortn
		EkiOnOff
	}


pmc1008mpMonupRmonMulticastCntIndex OBJECT-TYPE
	SYNTAX  INTEGER(0..128)
	MAX-ACCESS  read-only
	STATUS current
	DESCRIPTION
        "
        Index definition for the pmc1008mpMonupRmonMulticastCnt 
        table
        "
	::= { pmc1008mpMonupRmonMulticastCntEntry 1 }


pmc1008mpMonupRmonMulticastCntValuePortn OBJECT-TYPE
	SYNTAX  Counter64
	MAX-ACCESS read-only
	STATUS current
	DESCRIPTION
        "
        Multicast Counter On Client Input 
        :This counter is increased each 
        time a Multicast packet is received 
        on the client port  <Help>  This 
        counter gives the number of Multicast 
        packets received on the client
         port
        "
	::= { pmc1008mpMonupRmonMulticastCntEntry 2 }


pmc1008mpMonupRmonMulticastCntErrorPortn OBJECT-TYPE
	SYNTAX  EkiOnOff
	MAX-ACCESS read-only
	STATUS current
	DESCRIPTION
        "
        Multicast Counter Error :This
         OID when set indicates the Multicast 
        counter value is invalid on clinet 
        port
        "
	::= { pmc1008mpMonupRmonMulticastCntEntry 3 }


pmc1008mpMonupRmonMulticastCntOverloadPortn OBJECT-TYPE
	SYNTAX  EkiOnOff
	MAX-ACCESS read-only
	STATUS current
	DESCRIPTION
        "
        Multicast Counter Overload :This 
        OID when set indicates a Multicast 
        counter overload on client port
        "
	::= { pmc1008mpMonupRmonMulticastCntEntry 4 }


pmc1008mpMonCountersReset  OBJECT-TYPE
	SYNTAX EkiOnOff
	MAX-ACCESS read-write
	STATUS current
	DESCRIPTION
	"RMON Counters Reset:This OID resets and restarts all the RMON counters"
	::= { pmc1008mpMonRmon   359 }

pmc1008mpMonCountersStop  OBJECT-TYPE
	SYNTAX EkiOnOff
	MAX-ACCESS read-write
	STATUS current
	DESCRIPTION
	"RMON Counters stop:This OID stops all the RMON counters"
	::= { pmc1008mpMonRmon  360 }






--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pmc1008mpMesrsynth0 OBJECT-TYPE
	  SYNTAX EkiMeasureType
	  MAX-ACCESS read-only
	  STATUS deprecated
	  DESCRIPTION
        "
        Not Used :This OID gives the unit 
        used on AUX1 measurement of XFP#1 
         (Unit = )
        "
	  ::= { pmc1008mpMesrOther 0 }



pmc1008mpMesrsynth1 OBJECT-TYPE
	  SYNTAX EkiMeasureType
	  MAX-ACCESS read-only
	  STATUS deprecated
	  DESCRIPTION
        "
        Not Used :This OID gives the unit 
        used on AUX2 measurement of XFP#1 
         (Unit = )
        "
	  ::= { pmc1008mpMesrOther 1 }



--- *********************************************************
---     TABLE for the pmc1008mpMesrtempMeas articles
--- *********************************************************

pmc1008mpMesrtempMeasTable OBJECT-TYPE
	SYNTAX  SEQUENCE OF Pmc1008mpMesrtempMeasEntry
	MAX-ACCESS not-accessible
	STATUS current
	DESCRIPTION
        "
        List of pmc1008mpMesrtempMeas
         Article
        "
	::= { pmc1008mpMesrClient 16 }


pmc1008mpMesrtempMeasEntry OBJECT-TYPE
	SYNTAX Pmc1008mpMesrtempMeasEntry
	MAX-ACCESS not-accessible
	STATUS current
	DESCRIPTION
        "
        Row definition for the pmc1008mpMesrtempMeas 
        table
        "
	INDEX   { pmc1008mpMesrtempMeasIndex }
	::= { pmc1008mpMesrtempMeasTable 1 }


Pmc1008mpMesrtempMeasEntry ::=
	SEQUENCE {
	pmc1008mpMesrtempMeasIndex
		INTEGER,
	pmc1008mpMesrtempMeasPortn
		INTEGER 
	}


pmc1008mpMesrtempMeasIndex OBJECT-TYPE
	SYNTAX  INTEGER(0..128)
	MAX-ACCESS  read-only
	STATUS current
	DESCRIPTION
        "
        Index definition for the pmc1008mpMesrtempMeas 
        table
        "
	::= { pmc1008mpMesrtempMeasEntry 1 }


pmc1008mpMesrtempMeasPortn OBJECT-TYPE
	SYNTAX  INTEGER (0..65535)
	MAX-ACCESS read-only
	STATUS current
	DESCRIPTION
        "
        Client SFP Temperature :This OID 
        gives the temperature value of
         the SFP plugged in port, read
         from the DDM (Digital Diagnostic 
        Monitoring) (Temperature = AV/256) 
        (Unit = C)  <Help>  This measure 
        gives the temperature of the client 
        transceiver
        "
	::= { pmc1008mpMesrtempMeasEntry 2 }


--- *********************************************************
---     TABLE for the pmc1008mpMesrvoltMeas articles
--- *********************************************************

pmc1008mpMesrvoltMeasTable OBJECT-TYPE
	SYNTAX  SEQUENCE OF Pmc1008mpMesrvoltMeasEntry
	MAX-ACCESS not-accessible
	STATUS current
	DESCRIPTION
        "
        List of pmc1008mpMesrvoltMeas
         Article
        "
	::= { pmc1008mpMesrClient 24 }


pmc1008mpMesrvoltMeasEntry OBJECT-TYPE
	SYNTAX Pmc1008mpMesrvoltMeasEntry
	MAX-ACCESS not-accessible
	STATUS current
	DESCRIPTION
        "
        Row definition for the pmc1008mpMesrvoltMeas 
        table
        "
	INDEX   { pmc1008mpMesrvoltMeasIndex }
	::= { pmc1008mpMesrvoltMeasTable 1 }


Pmc1008mpMesrvoltMeasEntry ::=
	SEQUENCE {
	pmc1008mpMesrvoltMeasIndex
		INTEGER,
	pmc1008mpMesrvoltMeasPortn
		INTEGER 
	}


pmc1008mpMesrvoltMeasIndex OBJECT-TYPE
	SYNTAX  INTEGER(0..128)
	MAX-ACCESS  read-only
	STATUS current
	DESCRIPTION
        "
        Index definition for the pmc1008mpMesrvoltMeas 
        table
        "
	::= { pmc1008mpMesrvoltMeasEntry 1 }


pmc1008mpMesrvoltMeasPortn OBJECT-TYPE
	SYNTAX  INTEGER (0..65535)
	MAX-ACCESS read-only
	STATUS current
	DESCRIPTION
        "
        Client SFP Power Supply :This
         OID gives the 3V3 voltage value 
        of the SFP plugged into port, read 
        from the DDM (Digital Diagnostic 
        Monitoring) (Voltage = AV/10000) 
        (Unit = V)  <Help>  This measure 
        gives the 3V3 voltage of the client 
        transceiver
        "
	::= { pmc1008mpMesrvoltMeasEntry 2 }


--- *********************************************************
---     TABLE for the pmc1008mpMesrbiasMeas articles
--- *********************************************************

pmc1008mpMesrbiasMeasTable OBJECT-TYPE
	SYNTAX  SEQUENCE OF Pmc1008mpMesrbiasMeasEntry
	MAX-ACCESS not-accessible
	STATUS current
	DESCRIPTION
        "
        List of pmc1008mpMesrbiasMeas
         Article
        "
	::= { pmc1008mpMesrClient 32 }


pmc1008mpMesrbiasMeasEntry OBJECT-TYPE
	SYNTAX Pmc1008mpMesrbiasMeasEntry
	MAX-ACCESS not-accessible
	STATUS current
	DESCRIPTION
        "
        Row definition for the pmc1008mpMesrbiasMeas 
        table
        "
	INDEX   { pmc1008mpMesrbiasMeasIndex }
	::= { pmc1008mpMesrbiasMeasTable 1 }


Pmc1008mpMesrbiasMeasEntry ::=
	SEQUENCE {
	pmc1008mpMesrbiasMeasIndex
		INTEGER,
	pmc1008mpMesrbiasMeasPortn
		INTEGER 
	}


pmc1008mpMesrbiasMeasIndex OBJECT-TYPE
	SYNTAX  INTEGER(0..128)
	MAX-ACCESS  read-only
	STATUS current
	DESCRIPTION
        "
        Index definition for the pmc1008mpMesrbiasMeas 
        table
        "
	::= { pmc1008mpMesrbiasMeasEntry 1 }


pmc1008mpMesrbiasMeasPortn OBJECT-TYPE
	SYNTAX  INTEGER (0..65535)
	MAX-ACCESS read-only
	STATUS current
	DESCRIPTION
        "
        Client SFP Laser Bias :This OID 
        gives the bias value of the SFP 
        plugged into port, read from the 
        DDM (Digital Diagnostic Monitoring) 
        (Bias = AV/500)  (Unit = mA)  <Help> 
         This measure gives the bias of 
        the client transceiver
        "
	::= { pmc1008mpMesrbiasMeasEntry 2 }


--- *********************************************************
---     TABLE for the pmc1008mpMesrtxpwrMeas articles
--- *********************************************************

pmc1008mpMesrtxpwrMeasTable OBJECT-TYPE
	SYNTAX  SEQUENCE OF Pmc1008mpMesrtxpwrMeasEntry
	MAX-ACCESS not-accessible
	STATUS current
	DESCRIPTION
        "
        List of pmc1008mpMesrtxpwrMeas 
        Article
        "
	::= { pmc1008mpMesrClient 40 }


pmc1008mpMesrtxpwrMeasEntry OBJECT-TYPE
	SYNTAX Pmc1008mpMesrtxpwrMeasEntry
	MAX-ACCESS not-accessible
	STATUS current
	DESCRIPTION
        "
        Row definition for the pmc1008mpMesrtxpwrMeas 
        table
        "
	INDEX   { pmc1008mpMesrtxpwrMeasIndex }
	::= { pmc1008mpMesrtxpwrMeasTable 1 }


Pmc1008mpMesrtxpwrMeasEntry ::=
	SEQUENCE {
	pmc1008mpMesrtxpwrMeasIndex
		INTEGER,
	pmc1008mpMesrtxpwrMeasPortn
		INTEGER 
	}


pmc1008mpMesrtxpwrMeasIndex OBJECT-TYPE
	SYNTAX  INTEGER(0..128)
	MAX-ACCESS  read-only
	STATUS current
	DESCRIPTION
        "
        Index definition for the pmc1008mpMesrtxpwrMeas 
        table
        "
	::= { pmc1008mpMesrtxpwrMeasEntry 1 }


pmc1008mpMesrtxpwrMeasPortn OBJECT-TYPE
	SYNTAX  INTEGER (0..65535)
	MAX-ACCESS read-only
	STATUS current
	DESCRIPTION
        "
        Client SFP Tx Power :This OID
         gives the transmit power value 
        of the SFP plugged into port, read 
        from the DDM (Digital Diagnostic 
        Monitoring)  (Power = 10*log(AV)-40) 
        (Unit = dBm)  <Help>  This measure 
        gives the Tx optical power of the 
        client transceiver
        "
	::= { pmc1008mpMesrtxpwrMeasEntry 2 }


--- *********************************************************
---     TABLE for the pmc1008mpMesrrxpwrMeas articles
--- *********************************************************

pmc1008mpMesrrxpwrMeasTable OBJECT-TYPE
	SYNTAX  SEQUENCE OF Pmc1008mpMesrrxpwrMeasEntry
	MAX-ACCESS not-accessible
	STATUS current
	DESCRIPTION
        "
        List of pmc1008mpMesrrxpwrMeas 
        Article
        "
	::= { pmc1008mpMesrClient 48 }


pmc1008mpMesrrxpwrMeasEntry OBJECT-TYPE
	SYNTAX Pmc1008mpMesrrxpwrMeasEntry
	MAX-ACCESS not-accessible
	STATUS current
	DESCRIPTION
        "
        Row definition for the pmc1008mpMesrrxpwrMeas 
        table
        "
	INDEX   { pmc1008mpMesrrxpwrMeasIndex }
	::= { pmc1008mpMesrrxpwrMeasTable 1 }


Pmc1008mpMesrrxpwrMeasEntry ::=
	SEQUENCE {
	pmc1008mpMesrrxpwrMeasIndex
		INTEGER,
	pmc1008mpMesrrxpwrMeasPortn
		INTEGER 
	}


pmc1008mpMesrrxpwrMeasIndex OBJECT-TYPE
	SYNTAX  INTEGER(0..128)
	MAX-ACCESS  read-only
	STATUS current
	DESCRIPTION
        "
        Index definition for the pmc1008mpMesrrxpwrMeas 
        table
        "
	::= { pmc1008mpMesrrxpwrMeasEntry 1 }


pmc1008mpMesrrxpwrMeasPortn OBJECT-TYPE
	SYNTAX  INTEGER (0..65535)
	MAX-ACCESS read-only
	STATUS current
	DESCRIPTION
        "
        Client SFP Rx Power :This OID
         gives the receive power value
         of the SFP plugged into port,
         read in the DDM (Digital Diagnostic 
        Monitoring)  (Power = 10*log(AV)-40) 
        (Unit = dBm)  <Help>  This measure 
        gives the Rx optical power of the 
        client transceiver
        "
	::= { pmc1008mpMesrrxpwrMeasEntry 2 }


--- *********************************************************
---     TABLE for the pmc1008mpMesrxfp1LxModTempMeas articles
--- *********************************************************

pmc1008mpMesrxfp1LxModTempMeasTable OBJECT-TYPE
	SYNTAX  SEQUENCE OF Pmc1008mpMesrxfp1LxModTempMeasEntry
	MAX-ACCESS not-accessible
	STATUS current
	DESCRIPTION
        "
        List of pmc1008mpMesrxfp1LxModTempMeas 
        Article
        "
	::= { pmc1008mpMesrLine 208 }


pmc1008mpMesrxfp1LxModTempMeasEntry OBJECT-TYPE
	SYNTAX Pmc1008mpMesrxfp1LxModTempMeasEntry
	MAX-ACCESS not-accessible
	STATUS current
	DESCRIPTION
        "
        Row definition for the pmc1008mpMesrxfp1LxModTempMeas 
        table
        "
	INDEX   { pmc1008mpMesrxfp1LxModTempMeasIndex }
	::= { pmc1008mpMesrxfp1LxModTempMeasTable 1 }


Pmc1008mpMesrxfp1LxModTempMeasEntry ::=
	SEQUENCE {
	pmc1008mpMesrxfp1LxModTempMeasIndex
		INTEGER,
	pmc1008mpMesrxfp1LxModTempMeasPortn
		INTEGER 
	}


pmc1008mpMesrxfp1LxModTempMeasIndex OBJECT-TYPE
	SYNTAX  INTEGER(0..128)
	MAX-ACCESS  read-only
	STATUS current
	DESCRIPTION
        "
        Index definition for the pmc1008mpMesrxfp1LxModTempMeas 
        table
        "
	::= { pmc1008mpMesrxfp1LxModTempMeasEntry 1 }


pmc1008mpMesrxfp1LxModTempMeasPortn OBJECT-TYPE
	SYNTAX  INTEGER (0..65535)
	MAX-ACCESS read-only
	STATUS current
	DESCRIPTION
        "
        Line Optical Module Temperature 
        :This OID gives the temperature 
        of the XFP or OTX plugged in line#n, 
        read from the DDM (Digital Diagnostic 
        Monitoring)  (Temperature = AV/256) 
        (Unit = C)  <Help>  This measure 
        gives the temperature of the line 
        transceiver
        "
	::= { pmc1008mpMesrxfp1LxModTempMeasEntry 2 }


--- *********************************************************
---     TABLE for the pmc1008mpMesrxfp1Reserved articles
--- *********************************************************

pmc1008mpMesrxfp1ReservedTable OBJECT-TYPE
	SYNTAX  SEQUENCE OF Pmc1008mpMesrxfp1ReservedEntry
	MAX-ACCESS not-accessible
	STATUS deprecated
	DESCRIPTION
        "
        List of pmc1008mpMesrxfp1Reserved 
        Article
        "
	::= { pmc1008mpMesrLine 209 }


pmc1008mpMesrxfp1ReservedEntry OBJECT-TYPE
	SYNTAX Pmc1008mpMesrxfp1ReservedEntry
	MAX-ACCESS not-accessible
	STATUS deprecated
	DESCRIPTION
        "
        Row definition for the pmc1008mpMesrxfp1Reserved 
        table
        "
	INDEX   { pmc1008mpMesrxfp1ReservedIndex }
	::= { pmc1008mpMesrxfp1ReservedTable 1 }


Pmc1008mpMesrxfp1ReservedEntry ::=
	SEQUENCE {
	pmc1008mpMesrxfp1ReservedIndex
		INTEGER,
	pmc1008mpMesrxfp1ReservedPortn
		INTEGER 
	}


pmc1008mpMesrxfp1ReservedIndex OBJECT-TYPE
	SYNTAX  INTEGER(0..128)
	MAX-ACCESS  read-only
	STATUS deprecated
	DESCRIPTION
        "
        Index definition for the pmc1008mpMesrxfp1Reserved 
        table
        "
	::= { pmc1008mpMesrxfp1ReservedEntry 1 }


pmc1008mpMesrxfp1ReservedPortn OBJECT-TYPE
	SYNTAX  INTEGER (0..65535)
	MAX-ACCESS read-only
	STATUS deprecated
	DESCRIPTION
        "
        Not Used :Reserved
        "
	::= { pmc1008mpMesrxfp1ReservedEntry 2 }


--- *********************************************************
---     TABLE for the pmc1008mpMesrxfp1LoBiasCurrentMeas articles
--- *********************************************************

pmc1008mpMesrxfp1LoBiasCurrentMeasTable OBJECT-TYPE
	SYNTAX  SEQUENCE OF Pmc1008mpMesrxfp1LoBiasCurrentMeasEntry
	MAX-ACCESS not-accessible
	STATUS current
	DESCRIPTION
        "
        List of pmc1008mpMesrxfp1LoBiasCurrentMeas 
        Article
        "
	::= { pmc1008mpMesrLine 210 }


pmc1008mpMesrxfp1LoBiasCurrentMeasEntry OBJECT-TYPE
	SYNTAX Pmc1008mpMesrxfp1LoBiasCurrentMeasEntry
	MAX-ACCESS not-accessible
	STATUS current
	DESCRIPTION
        "
        Row definition for the pmc1008mpMesrxfp1LoBiasCurrentMeas 
        table
        "
	INDEX   { pmc1008mpMesrxfp1LoBiasCurrentMeasIndex }
	::= { pmc1008mpMesrxfp1LoBiasCurrentMeasTable 1 }


Pmc1008mpMesrxfp1LoBiasCurrentMeasEntry ::=
	SEQUENCE {
	pmc1008mpMesrxfp1LoBiasCurrentMeasIndex
		INTEGER,
	pmc1008mpMesrxfp1LoBiasCurrentMeasPortn
		INTEGER 
	}


pmc1008mpMesrxfp1LoBiasCurrentMeasIndex OBJECT-TYPE
	SYNTAX  INTEGER(0..128)
	MAX-ACCESS  read-only
	STATUS current
	DESCRIPTION
        "
        Index definition for the pmc1008mpMesrxfp1LoBiasCurrentMeas 
        table
        "
	::= { pmc1008mpMesrxfp1LoBiasCurrentMeasEntry 1 }


pmc1008mpMesrxfp1LoBiasCurrentMeasPortn OBJECT-TYPE
	SYNTAX  INTEGER (0..65535)
	MAX-ACCESS read-only
	STATUS current
	DESCRIPTION
        "
        Line Optical Module Laser Bias 
        :This OID gives the bias value
         of the XFP or OTX plugged in line 
        #n, read from the DDM (Digital
         Diagnostic Monitoring) (Bias = 
        AV/500) (Unit = mA)  <Help>  This 
        measure gives the bias of the line 
        transceiver
        "
	::= { pmc1008mpMesrxfp1LoBiasCurrentMeasEntry 2 }


--- *********************************************************
---     TABLE for the pmc1008mpMesrxfp1LoTxPowerMeas articles
--- *********************************************************

pmc1008mpMesrxfp1LoTxPowerMeasTable OBJECT-TYPE
	SYNTAX  SEQUENCE OF Pmc1008mpMesrxfp1LoTxPowerMeasEntry
	MAX-ACCESS not-accessible
	STATUS current
	DESCRIPTION
        "
        List of pmc1008mpMesrxfp1LoTxPowerMeas 
        Article
        "
	::= { pmc1008mpMesrLine 211 }


pmc1008mpMesrxfp1LoTxPowerMeasEntry OBJECT-TYPE
	SYNTAX Pmc1008mpMesrxfp1LoTxPowerMeasEntry
	MAX-ACCESS not-accessible
	STATUS current
	DESCRIPTION
        "
        Row definition for the pmc1008mpMesrxfp1LoTxPowerMeas 
        table
        "
	INDEX   { pmc1008mpMesrxfp1LoTxPowerMeasIndex }
	::= { pmc1008mpMesrxfp1LoTxPowerMeasTable 1 }


Pmc1008mpMesrxfp1LoTxPowerMeasEntry ::=
	SEQUENCE {
	pmc1008mpMesrxfp1LoTxPowerMeasIndex
		INTEGER,
	pmc1008mpMesrxfp1LoTxPowerMeasPortn
		INTEGER 
	}


pmc1008mpMesrxfp1LoTxPowerMeasIndex OBJECT-TYPE
	SYNTAX  INTEGER(0..128)
	MAX-ACCESS  read-only
	STATUS current
	DESCRIPTION
        "
        Index definition for the pmc1008mpMesrxfp1LoTxPowerMeas 
        table
        "
	::= { pmc1008mpMesrxfp1LoTxPowerMeasEntry 1 }


pmc1008mpMesrxfp1LoTxPowerMeasPortn OBJECT-TYPE
	SYNTAX  INTEGER (0..65535)
	MAX-ACCESS read-only
	STATUS current
	DESCRIPTION
        "
        Line Optical Module Tx Power :This 
        OID gives the transmit power value 
        of the XFP or OTX plugged in line 
        #n, read from the DDM (Digital
           Diagnostic Monitoring) (Power 
        = 10*log(AV)-40) (Unit = dBm) 
         <Help>  This measure gives the 
        Tx optical power of the line transceiver
        "
	::= { pmc1008mpMesrxfp1LoTxPowerMeasEntry 2 }


--- *********************************************************
---     TABLE for the pmc1008mpMesrxfp1LiRxPowerMeas articles
--- *********************************************************

pmc1008mpMesrxfp1LiRxPowerMeasTable OBJECT-TYPE
	SYNTAX  SEQUENCE OF Pmc1008mpMesrxfp1LiRxPowerMeasEntry
	MAX-ACCESS not-accessible
	STATUS current
	DESCRIPTION
        "
        List of pmc1008mpMesrxfp1LiRxPowerMeas 
        Article
        "
	::= { pmc1008mpMesrLine 212 }


pmc1008mpMesrxfp1LiRxPowerMeasEntry OBJECT-TYPE
	SYNTAX Pmc1008mpMesrxfp1LiRxPowerMeasEntry
	MAX-ACCESS not-accessible
	STATUS current
	DESCRIPTION
        "
        Row definition for the pmc1008mpMesrxfp1LiRxPowerMeas 
        table
        "
	INDEX   { pmc1008mpMesrxfp1LiRxPowerMeasIndex }
	::= { pmc1008mpMesrxfp1LiRxPowerMeasTable 1 }


Pmc1008mpMesrxfp1LiRxPowerMeasEntry ::=
	SEQUENCE {
	pmc1008mpMesrxfp1LiRxPowerMeasIndex
		INTEGER,
	pmc1008mpMesrxfp1LiRxPowerMeasPortn
		INTEGER 
	}


pmc1008mpMesrxfp1LiRxPowerMeasIndex OBJECT-TYPE
	SYNTAX  INTEGER(0..128)
	MAX-ACCESS  read-only
	STATUS current
	DESCRIPTION
        "
        Index definition for the pmc1008mpMesrxfp1LiRxPowerMeas 
        table
        "
	::= { pmc1008mpMesrxfp1LiRxPowerMeasEntry 1 }


pmc1008mpMesrxfp1LiRxPowerMeasPortn OBJECT-TYPE
	SYNTAX  INTEGER (0..65535)
	MAX-ACCESS read-only
	STATUS current
	DESCRIPTION
        "
        Line Optical Module Rx Power :This 
        OID gives the receive power value 
        of the XFP or OTX plugged in line 
        #n, read from the DDM (Digital
         Diagnostic Monitoring) (Power
         = 10*log(AV)-40)  (Unit = dBm) 
         <Help>  This measure gives the 
        Rx optical power of the line transceiver
        "
	::= { pmc1008mpMesrxfp1LiRxPowerMeasEntry 2 }


--- *********************************************************
---     TABLE for the pmc1008mpMesrxfp1LxAux1Meas articles
--- *********************************************************

pmc1008mpMesrxfp1LxAux1MeasTable OBJECT-TYPE
	SYNTAX  SEQUENCE OF Pmc1008mpMesrxfp1LxAux1MeasEntry
	MAX-ACCESS not-accessible
	STATUS deprecated
	DESCRIPTION
        "
        List of pmc1008mpMesrxfp1LxAux1Meas 
        Article
        "
	::= { pmc1008mpMesrLine 213 }


pmc1008mpMesrxfp1LxAux1MeasEntry OBJECT-TYPE
	SYNTAX Pmc1008mpMesrxfp1LxAux1MeasEntry
	MAX-ACCESS not-accessible
	STATUS deprecated
	DESCRIPTION
        "
        Row definition for the pmc1008mpMesrxfp1LxAux1Meas 
        table
        "
	INDEX   { pmc1008mpMesrxfp1LxAux1MeasIndex }
	::= { pmc1008mpMesrxfp1LxAux1MeasTable 1 }


Pmc1008mpMesrxfp1LxAux1MeasEntry ::=
	SEQUENCE {
	pmc1008mpMesrxfp1LxAux1MeasIndex
		INTEGER,
	pmc1008mpMesrxfp1LxAux1MeasPortn
		INTEGER 
	}


pmc1008mpMesrxfp1LxAux1MeasIndex OBJECT-TYPE
	SYNTAX  INTEGER(0..128)
	MAX-ACCESS  read-only
	STATUS deprecated
	DESCRIPTION
        "
        Index definition for the pmc1008mpMesrxfp1LxAux1Meas 
        table
        "
	::= { pmc1008mpMesrxfp1LxAux1MeasEntry 1 }


pmc1008mpMesrxfp1LxAux1MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line #n (Unit 
        = ?)
        "
	::= { pmc1008mpMesrxfp1LxAux1MeasEntry 2 }


--- *********************************************************
---     TABLE for the pmc1008mpMesrxfp1LxAux2Meas articles
--- *********************************************************

pmc1008mpMesrxfp1LxAux2MeasTable OBJECT-TYPE
	SYNTAX  SEQUENCE OF Pmc1008mpMesrxfp1LxAux2MeasEntry
	MAX-ACCESS not-accessible
	STATUS deprecated
	DESCRIPTION
        "
        List of pmc1008mpMesrxfp1LxAux2Meas 
        Article
        "
	::= { pmc1008mpMesrLine 214 }


pmc1008mpMesrxfp1LxAux2MeasEntry OBJECT-TYPE
	SYNTAX Pmc1008mpMesrxfp1LxAux2MeasEntry
	MAX-ACCESS not-accessible
	STATUS deprecated
	DESCRIPTION
        "
        Row definition for the pmc1008mpMesrxfp1LxAux2Meas 
        table
        "
	INDEX   { pmc1008mpMesrxfp1LxAux2MeasIndex }
	::= { pmc1008mpMesrxfp1LxAux2MeasTable 1 }


Pmc1008mpMesrxfp1LxAux2MeasEntry ::=
	SEQUENCE {
	pmc1008mpMesrxfp1LxAux2MeasIndex
		INTEGER,
	pmc1008mpMesrxfp1LxAux2MeasPortn
		INTEGER 
	}


pmc1008mpMesrxfp1LxAux2MeasIndex OBJECT-TYPE
	SYNTAX  INTEGER(0..128)
	MAX-ACCESS  read-only
	STATUS deprecated
	DESCRIPTION
        "
        Index definition for the pmc1008mpMesrxfp1LxAux2Meas 
        table
        "
	::= { pmc1008mpMesrxfp1LxAux2MeasEntry 1 }


pmc1008mpMesrxfp1LxAux2MeasPortn OBJECT-TYPE
	SYNTAX  INTEGER (0..65535)
	MAX-ACCESS read-only
	STATUS deprecated
	DESCRIPTION
        "
        Not Used :This OID gives the receive 
        power value read in the DDM (Digital 
        Diagnostic Monitoring) of the XFP 
        or OTX plugged in line #n (Unit 
        = ?)
        "
	::= { pmc1008mpMesrxfp1LxAux2MeasEntry 2 }


--- *********************************************************
---     TABLE for the pmc1008mpMesrotx1Aging articles
--- *********************************************************

pmc1008mpMesrotx1AgingTable OBJECT-TYPE
	SYNTAX  SEQUENCE OF Pmc1008mpMesrotx1AgingEntry
	MAX-ACCESS not-accessible
	STATUS current
	DESCRIPTION
        "
        List of pmc1008mpMesrotx1Aging 
        Article
        "
	::= { pmc1008mpMesrLine 224 }


pmc1008mpMesrotx1AgingEntry OBJECT-TYPE
	SYNTAX Pmc1008mpMesrotx1AgingEntry
	MAX-ACCESS not-accessible
	STATUS current
	DESCRIPTION
        "
        Row definition for the pmc1008mpMesrotx1Aging 
        table
        "
	INDEX   { pmc1008mpMesrotx1AgingIndex }
	::= { pmc1008mpMesrotx1AgingTable 1 }


Pmc1008mpMesrotx1AgingEntry ::=
	SEQUENCE {
	pmc1008mpMesrotx1AgingIndex
		INTEGER,
	pmc1008mpMesrotx1AgingPortn
		INTEGER 
	}


pmc1008mpMesrotx1AgingIndex OBJECT-TYPE
	SYNTAX  INTEGER(0..128)
	MAX-ACCESS  read-only
	STATUS current
	DESCRIPTION
        "
        Index definition for the pmc1008mpMesrotx1Aging 
        table
        "
	::= { pmc1008mpMesrotx1AgingEntry 1 }


pmc1008mpMesrotx1AgingPortn OBJECT-TYPE
	SYNTAX  INTEGER (0..65535)
	MAX-ACCESS read-only
	STATUS current
	DESCRIPTION
        "
        Line OTX TLH Aging :This OID gives 
        the aging of the Line OTX TLH,
         read from the DDM (Digital Diagnostic 
        Monitoring)  (Aging = AV) (Unit 
        = %)  <Help>  This measure gives 
        the aging of the Line OTX TLH
        "
	::= { pmc1008mpMesrotx1AgingEntry 2 }


--- *********************************************************
---     TABLE for the pmc1008mpMesrotx1LaserTemperature articles
--- *********************************************************

pmc1008mpMesrotx1LaserTemperatureTable OBJECT-TYPE
	SYNTAX  SEQUENCE OF Pmc1008mpMesrotx1LaserTemperatureEntry
	MAX-ACCESS not-accessible
	STATUS deprecated
	DESCRIPTION
        "
        List of pmc1008mpMesrotx1LaserTemperature 
        Article
        "
	::= { pmc1008mpMesrLine 225 }


pmc1008mpMesrotx1LaserTemperatureEntry OBJECT-TYPE
	SYNTAX Pmc1008mpMesrotx1LaserTemperatureEntry
	MAX-ACCESS not-accessible
	STATUS deprecated
	DESCRIPTION
        "
        Row definition for the pmc1008mpMesrotx1LaserTemperature 
        table
        "
	INDEX   { pmc1008mpMesrotx1LaserTemperatureIndex }
	::= { pmc1008mpMesrotx1LaserTemperatureTable 1 }


Pmc1008mpMesrotx1LaserTemperatureEntry ::=
	SEQUENCE {
	pmc1008mpMesrotx1LaserTemperatureIndex
		INTEGER,
	pmc1008mpMesrotx1LaserTemperaturePortn
		INTEGER 
	}


pmc1008mpMesrotx1LaserTemperatureIndex OBJECT-TYPE
	SYNTAX  INTEGER(0..128)
	MAX-ACCESS  read-only
	STATUS deprecated
	DESCRIPTION
        "
        Index definition for the pmc1008mpMesrotx1LaserTemperature 
        table
        "
	::= { pmc1008mpMesrotx1LaserTemperatureEntry 1 }


pmc1008mpMesrotx1LaserTemperaturePortn OBJECT-TYPE
	SYNTAX  INTEGER (0..65535)
	MAX-ACCESS read-only
	STATUS deprecated
	DESCRIPTION
        "
        Line OTX TLH Laser Temperature 
        :This OID gives the laser temperature 
        of the Line OTX TLH, read from
         the DDM (Digital Diagnostic Monitoring) 
        (Temperature = AV/256) (Unit =
         C)  <Help>  This measure gives 
        the laser temperature of the Line 
        OTX TLH
        "
	::= { pmc1008mpMesrotx1LaserTemperatureEntry 2 }


--- *********************************************************
---     TABLE for the pmc1008mpMesrotx1FreqDeviation articles
--- *********************************************************

pmc1008mpMesrotx1FreqDeviationTable OBJECT-TYPE
	SYNTAX  SEQUENCE OF Pmc1008mpMesrotx1FreqDeviationEntry
	MAX-ACCESS not-accessible
	STATUS current
	DESCRIPTION
        "
        List of pmc1008mpMesrotx1FreqDeviation 
        Article
        "
	::= { pmc1008mpMesrLine 226 }


pmc1008mpMesrotx1FreqDeviationEntry OBJECT-TYPE
	SYNTAX Pmc1008mpMesrotx1FreqDeviationEntry
	MAX-ACCESS not-accessible
	STATUS current
	DESCRIPTION
        "
        Row definition for the pmc1008mpMesrotx1FreqDeviation 
        table
        "
	INDEX   { pmc1008mpMesrotx1FreqDeviationIndex }
	::= { pmc1008mpMesrotx1FreqDeviationTable 1 }


Pmc1008mpMesrotx1FreqDeviationEntry ::=
	SEQUENCE {
	pmc1008mpMesrotx1FreqDeviationIndex
		INTEGER,
	pmc1008mpMesrotx1FreqDeviationPortn
		INTEGER 
	}


pmc1008mpMesrotx1FreqDeviationIndex OBJECT-TYPE
	SYNTAX  INTEGER(0..128)
	MAX-ACCESS  read-only
	STATUS current
	DESCRIPTION
        "
        Index definition for the pmc1008mpMesrotx1FreqDeviation 
        table
        "
	::= { pmc1008mpMesrotx1FreqDeviationEntry 1 }


pmc1008mpMesrotx1FreqDeviationPortn OBJECT-TYPE
	SYNTAX  INTEGER (0..65535)
	MAX-ACCESS read-only
	STATUS current
	DESCRIPTION
        "
        Line OTX TLH Frequency Deviation 
        :This OID gives the frequency deviation 
        of the Line OTX TLH, read from
         the DDM (Digital Diagnostic Monitoring) 
        (Deviation = (AV-32768)*100) (Unit 
        = MHz)  <Help>  This measure gives 
        the frequency deviation of the
         Line OTX TLH
        "
	::= { pmc1008mpMesrotx1FreqDeviationEntry 2 }


--- *********************************************************
---     TABLE for the pmc1008mpMesrotx1LaserWvlength articles
--- *********************************************************

pmc1008mpMesrotx1LaserWvlengthTable OBJECT-TYPE
	SYNTAX  SEQUENCE OF Pmc1008mpMesrotx1LaserWvlengthEntry
	MAX-ACCESS not-accessible
	STATUS current
	DESCRIPTION
        "
        List of pmc1008mpMesrotx1LaserWvlength 
        Article
        "
	::= { pmc1008mpMesrLine 227 }


pmc1008mpMesrotx1LaserWvlengthEntry OBJECT-TYPE
	SYNTAX Pmc1008mpMesrotx1LaserWvlengthEntry
	MAX-ACCESS not-accessible
	STATUS current
	DESCRIPTION
        "
        Row definition for the pmc1008mpMesrotx1LaserWvlength 
        table
        "
	INDEX   { pmc1008mpMesrotx1LaserWvlengthIndex }
	::= { pmc1008mpMesrotx1LaserWvlengthTable 1 }


Pmc1008mpMesrotx1LaserWvlengthEntry ::=
	SEQUENCE {
	pmc1008mpMesrotx1LaserWvlengthIndex
		INTEGER,
	pmc1008mpMesrotx1LaserWvlengthPortn
		INTEGER 
	}


pmc1008mpMesrotx1LaserWvlengthIndex OBJECT-TYPE
	SYNTAX  INTEGER(0..128)
	MAX-ACCESS  read-only
	STATUS current
	DESCRIPTION
        "
        Index definition for the pmc1008mpMesrotx1LaserWvlength 
        table
        "
	::= { pmc1008mpMesrotx1LaserWvlengthEntry 1 }


pmc1008mpMesrotx1LaserWvlengthPortn OBJECT-TYPE
	SYNTAX  INTEGER (0..65535)
	MAX-ACCESS read-only
	STATUS current
	DESCRIPTION
        "
        Line Optical Module Wavelength 
        :This OID gives the laser wavelength 
        of the Line OTX TLH, read from
         the DDM (Digital Diagnostic Monitoring) 
        (Wavelength=299792458/((193,100+(AV-32768 
        )*12,5)*10 3)) (Unit = nm)  <Help> 
         This measure gives the laser wavelength 
        of the Line OTX TLH
        "
	::= { pmc1008mpMesrotx1LaserWvlengthEntry 2 }







--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomClientCurrent15Stat
--- *****************************************************
--- *********************************************************
---     TABLE for the pmc1008mpPerfTelecomClientCurrent15Stat articles
--- *********************************************************

pmc1008mpPerfTelecomClientCurrent15StatTable OBJECT-TYPE
	SYNTAX  SEQUENCE OF Pmc1008mpPerfTelecomClientCurrent15StatEntry
	MAX-ACCESS not-accessible
	STATUS current
	DESCRIPTION
        "
        List of pmc1008mpPerfTelecomClientCurrent15Stat 
        Article
        "
	::= { pmc1008mpMonClient 16 }


pmc1008mpPerfTelecomClientCurrent15StatEntry OBJECT-TYPE
	SYNTAX Pmc1008mpPerfTelecomClientCurrent15StatEntry
	MAX-ACCESS not-accessible
	STATUS current
	DESCRIPTION
        "
        Row definition for the pmc1008mpPerfTelecomClientCurrent15Stat 
        table
        "
	INDEX   { pmc1008mpPerfTelecomClientCurrent15StatIndex }
	::= { pmc1008mpPerfTelecomClientCurrent15StatTable 1 }


Pmc1008mpPerfTelecomClientCurrent15StatEntry ::=
	SEQUENCE {
	pmc1008mpPerfTelecomClientCurrent15StatIndex
		INTEGER,
	pmc1008mpPerfTelecomClientCurrent15StatInvCvPortn
		EkiOnOff,
	pmc1008mpPerfTelecomClientCurrent15StatCvValuePortn
		Unsigned32,
	pmc1008mpPerfTelecomClientCurrent15StatInvEsPortn
		EkiOnOff,
	pmc1008mpPerfTelecomClientCurrent15StatEsValuePortn
		Unsigned32,
	pmc1008mpPerfTelecomClientCurrent15StatInvSesPortn
		EkiOnOff,
	pmc1008mpPerfTelecomClientCurrent15StatSesValuePortn
		Unsigned32,
	pmc1008mpPerfTelecomClientCurrent15StatInvSefsPortn
		EkiOnOff,
	pmc1008mpPerfTelecomClientCurrent15StatSefsValuePortn
		Unsigned32,
	pmc1008mpPerfTelecomClientCurrent15StatInvUasPortn
		EkiOnOff,
	pmc1008mpPerfTelecomClientCurrent15StatUasValuePortn
		Unsigned32
	}


pmc1008mpPerfTelecomClientCurrent15StatIndex OBJECT-TYPE
	SYNTAX  INTEGER(0..128)
	MAX-ACCESS  read-only
	STATUS current
	DESCRIPTION
        "
        Index definition for the pmc1008mpPerfTelecomClientCurrent15Stat 
        table
        "
	::= { pmc1008mpPerfTelecomClientCurrent15StatEntry 1 }


pmc1008mpPerfTelecomClientCurrent15StatInvCvPortn OBJECT-TYPE
	SYNTAX  EkiOnOff
	MAX-ACCESS read-only
	STATUS current
	DESCRIPTION
        "
        Current 15-min CV counter inv. 
        :This OID indicates that the current 
        15-min Coding Violation counter 
        is invalid
        "
	::= { pmc1008mpPerfTelecomClientCurrent15StatEntry 2 }


pmc1008mpPerfTelecomClientCurrent15StatCvValuePortn OBJECT-TYPE
	SYNTAX  Unsigned32
	MAX-ACCESS read-only
	STATUS current
	DESCRIPTION
        "
        Current 15-min CV counter :This 
        OID gives the current 15-min Coding 
        Violation counter value
        "
	::= { pmc1008mpPerfTelecomClientCurrent15StatEntry 3 }


pmc1008mpPerfTelecomClientCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pmc1008mpPerfTelecomClientCurrent15StatEntry 4 }


pmc1008mpPerfTelecomClientCurrent15StatEsValuePortn OBJECT-TYPE
	SYNTAX  Unsigned32
	MAX-ACCESS read-only
	STATUS current
	DESCRIPTION
        "
        Current 15-min ES counter :This 
        OID gives the current 15-min Errored 
        Second counter value
        "
	::= { pmc1008mpPerfTelecomClientCurrent15StatEntry 5 }


pmc1008mpPerfTelecomClientCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pmc1008mpPerfTelecomClientCurrent15StatEntry 6 }


pmc1008mpPerfTelecomClientCurrent15StatSesValuePortn OBJECT-TYPE
	SYNTAX  Unsigned32
	MAX-ACCESS read-only
	STATUS current
	DESCRIPTION
        "
        Current 15-min SES counter :This 
        OID gives the current 15-min severely 
        Errored Second counter value
        "
	::= { pmc1008mpPerfTelecomClientCurrent15StatEntry 7 }


pmc1008mpPerfTelecomClientCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pmc1008mpPerfTelecomClientCurrent15StatEntry 8 }


pmc1008mpPerfTelecomClientCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pmc1008mpPerfTelecomClientCurrent15StatEntry 9 }


pmc1008mpPerfTelecomClientCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pmc1008mpPerfTelecomClientCurrent15StatEntry 10 }


pmc1008mpPerfTelecomClientCurrent15StatUasValuePortn OBJECT-TYPE
	SYNTAX  Unsigned32
	MAX-ACCESS read-only
	STATUS current
	DESCRIPTION
        "
        Current 15-min UAS counter :This 
        OID gives the current 15-min UnAvailable 
        Second counter value
        "
	::= { pmc1008mpPerfTelecomClientCurrent15StatEntry 11 }


--- *****************************************************
---     Leaf of the telecomClientPast15Stat
--- *****************************************************
--- *********************************************************
---     TABLE for the pmc1008mpPerfTelecomClientPast15StatHistory articles
--- *********************************************************

pmc1008mpPerfTelecomClientPast15StatHistoryPort1Table OBJECT-TYPE
	SYNTAX  SEQUENCE OF Pmc1008mpPerfTelecomClientPast15StatHistoryPort1Entry
	MAX-ACCESS not-accessible
	STATUS current
	DESCRIPTION
        "
        List of pmc1008mpPerfTelecomClientPast15StatHistory 
        Article
        "
	::= { pmc1008mpMonClient 24 }


pmc1008mpPerfTelecomClientPast15StatHistoryPort1Entry OBJECT-TYPE
	SYNTAX Pmc1008mpPerfTelecomClientPast15StatHistoryPort1Entry
	MAX-ACCESS not-accessible
	STATUS current
	DESCRIPTION
        "
        Row definition for the pmc1008mpPerfTelecomClientPast15StatHistory 
        table
        "
	INDEX   { pmc1008mpPerfTelecomClientPast15StatHistoryPort1Index }
	::= { pmc1008mpPerfTelecomClientPast15StatHistoryPort1Table 1 }


Pmc1008mpPerfTelecomClientPast15StatHistoryPort1Entry ::=
	SEQUENCE {
	pmc1008mpPerfTelecomClientPast15StatHistoryPort1Index
		INTEGER,
	pmc1008mpPerfTelecomClientPast15StatHistoryInvCvPort1
		EkiOnOff,
	pmc1008mpPerfTelecomClientPast15StatHistoryCvValuePort1
		Unsigned32,
	pmc1008mpPerfTelecomClientPast15StatHistoryInvEsPort1
		EkiOnOff,
	pmc1008mpPerfTelecomClientPast15StatHistoryEsValuePort1
		Unsigned32,
	pmc1008mpPerfTelecomClientPast15StatHistoryInvSesPort1
		EkiOnOff,
	pmc1008mpPerfTelecomClientPast15StatHistorySesValuePort1
		Unsigned32,
	pmc1008mpPerfTelecomClientPast15StatHistoryInvSefsPort1
		EkiOnOff,
	pmc1008mpPerfTelecomClientPast15StatHistorySefsValuePort1
		Unsigned32,
	pmc1008mpPerfTelecomClientPast15StatHistoryInvUasPort1
		EkiOnOff,
	pmc1008mpPerfTelecomClientPast15StatHistoryUasValuePort1
		Unsigned32
	}


pmc1008mpPerfTelecomClientPast15StatHistoryPort1Index OBJECT-TYPE
	SYNTAX  INTEGER(0..128)
	MAX-ACCESS  read-only
	STATUS current
	DESCRIPTION
        "
        Index definition for the pmc1008mpPerfTelecomClientPast15StatHistory 
        table
        "
	::= { pmc1008mpPerfTelecomClientPast15StatHistoryPort1Entry 1 }


pmc1008mpPerfTelecomClientPast15StatHistoryInvCvPort1 OBJECT-TYPE
	SYNTAX  EkiOnOff
	MAX-ACCESS read-only
	STATUS current
	DESCRIPTION
        "
        Previous 15-min CV counter inv. 
        :This OID indicates that the previous 
        15-min Coding Violation counter 
        is invalid
        "
	::= { pmc1008mpPerfTelecomClientPast15StatHistoryPort1Entry 2 }


pmc1008mpPerfTelecomClientPast15StatHistoryCvValuePort1 OBJECT-TYPE
	SYNTAX  Unsigned32
	MAX-ACCESS read-only
	STATUS current
	DESCRIPTION
        "
        Previous 15-min CV counter :This 
        OID gives the previous 15-min Coding 
        Violation counter value
        "
	::= { pmc1008mpPerfTelecomClientPast15StatHistoryPort1Entry 3 }


pmc1008mpPerfTelecomClientPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pmc1008mpPerfTelecomClientPast15StatHistoryPort1Entry 4 }


pmc1008mpPerfTelecomClientPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pmc1008mpPerfTelecomClientPast15StatHistoryPort1Entry 5 }


pmc1008mpPerfTelecomClientPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pmc1008mpPerfTelecomClientPast15StatHistoryPort1Entry 6 }


pmc1008mpPerfTelecomClientPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pmc1008mpPerfTelecomClientPast15StatHistoryPort1Entry 7 }


pmc1008mpPerfTelecomClientPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pmc1008mpPerfTelecomClientPast15StatHistoryPort1Entry 8 }


pmc1008mpPerfTelecomClientPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pmc1008mpPerfTelecomClientPast15StatHistoryPort1Entry 9 }


pmc1008mpPerfTelecomClientPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pmc1008mpPerfTelecomClientPast15StatHistoryPort1Entry 10 }


pmc1008mpPerfTelecomClientPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pmc1008mpPerfTelecomClientPast15StatHistoryPort1Entry 11 }


--- *****************************************************
---     Leaf of the telecomClientCurrent24Stat
--- *****************************************************
--- *********************************************************
---     TABLE for the pmc1008mpPerfTelecomClientCurrent24Stat articles
--- *********************************************************

pmc1008mpPerfTelecomClientCurrent24StatTable OBJECT-TYPE
	SYNTAX  SEQUENCE OF Pmc1008mpPerfTelecomClientCurrent24StatEntry
	MAX-ACCESS not-accessible
	STATUS current
	DESCRIPTION
        "
        List of pmc1008mpPerfTelecomClientCurrent24Stat 
        Article
        "
	::= { pmc1008mpMonClient 32 }


pmc1008mpPerfTelecomClientCurrent24StatEntry OBJECT-TYPE
	SYNTAX Pmc1008mpPerfTelecomClientCurrent24StatEntry
	MAX-ACCESS not-accessible
	STATUS current
	DESCRIPTION
        "
        Row definition for the pmc1008mpPerfTelecomClientCurrent24Stat 
        table
        "
	INDEX   { pmc1008mpPerfTelecomClientCurrent24StatIndex }
	::= { pmc1008mpPerfTelecomClientCurrent24StatTable 1 }


Pmc1008mpPerfTelecomClientCurrent24StatEntry ::=
	SEQUENCE {
	pmc1008mpPerfTelecomClientCurrent24StatIndex
		INTEGER,
	pmc1008mpPerfTelecomClientCurrent24StatInvCvPortn
		EkiOnOff,
	pmc1008mpPerfTelecomClientCurrent24StatCvValuePortn
		Unsigned32,
	pmc1008mpPerfTelecomClientCurrent24StatInvEsPortn
		EkiOnOff,
	pmc1008mpPerfTelecomClientCurrent24StatEsValuePortn
		Unsigned32,
	pmc1008mpPerfTelecomClientCurrent24StatInvSesPortn
		EkiOnOff,
	pmc1008mpPerfTelecomClientCurrent24StatSesValuePortn
		Unsigned32,
	pmc1008mpPerfTelecomClientCurrent24StatInvSefsPortn
		EkiOnOff,
	pmc1008mpPerfTelecomClientCurrent24StatSefsValuePortn
		Unsigned32,
	pmc1008mpPerfTelecomClientCurrent24StatInvUasPortn
		EkiOnOff,
	pmc1008mpPerfTelecomClientCurrent24StatUasValuePortn
		Unsigned32
	}


pmc1008mpPerfTelecomClientCurrent24StatIndex OBJECT-TYPE
	SYNTAX  INTEGER(0..128)
	MAX-ACCESS  read-only
	STATUS current
	DESCRIPTION
        "
        Index definition for the pmc1008mpPerfTelecomClientCurrent24Stat 
        table
        "
	::= { pmc1008mpPerfTelecomClientCurrent24StatEntry 1 }


pmc1008mpPerfTelecomClientCurrent24StatInvCvPortn OBJECT-TYPE
	SYNTAX  EkiOnOff
	MAX-ACCESS read-only
	STATUS current
	DESCRIPTION
        "
        Current 24-hours CV counter inv. 
        :This OID indicates that the current 
        24-hours Coding Violation counter 
        is invalid
        "
	::= { pmc1008mpPerfTelecomClientCurrent24StatEntry 2 }


pmc1008mpPerfTelecomClientCurrent24StatCvValuePortn OBJECT-TYPE
	SYNTAX  Unsigned32
	MAX-ACCESS read-only
	STATUS current
	DESCRIPTION
        "
        Current 24-hours CV counter :This 
        OID gives the current 24-hours
         Coding Violation counter value
        "
	::= { pmc1008mpPerfTelecomClientCurrent24StatEntry 3 }


pmc1008mpPerfTelecomClientCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pmc1008mpPerfTelecomClientCurrent24StatEntry 4 }


pmc1008mpPerfTelecomClientCurrent24StatEsValuePortn OBJECT-TYPE
	SYNTAX  Unsigned32
	MAX-ACCESS read-only
	STATUS current
	DESCRIPTION
        "
        Current 24-hours ES counter :This 
        OID gives the current 24-hours
         Errored Second counter value
        "
	::= { pmc1008mpPerfTelecomClientCurrent24StatEntry 5 }


pmc1008mpPerfTelecomClientCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pmc1008mpPerfTelecomClientCurrent24StatEntry 6 }


pmc1008mpPerfTelecomClientCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pmc1008mpPerfTelecomClientCurrent24StatEntry 7 }


pmc1008mpPerfTelecomClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pmc1008mpPerfTelecomClientCurrent24StatEntry 8 }


pmc1008mpPerfTelecomClientCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pmc1008mpPerfTelecomClientCurrent24StatEntry 9 }


pmc1008mpPerfTelecomClientCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pmc1008mpPerfTelecomClientCurrent24StatEntry 10 }


pmc1008mpPerfTelecomClientCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pmc1008mpPerfTelecomClientCurrent24StatEntry 11 }


--- *****************************************************
---     Leaf of the telecomClientPast24Stat
--- *****************************************************
--- *********************************************************
---     TABLE for the pmc1008mpPerfTelecomClientPast24StatHistory articles
--- *********************************************************

pmc1008mpPerfTelecomClientPast24StatHistoryPort1Table OBJECT-TYPE
	SYNTAX  SEQUENCE OF Pmc1008mpPerfTelecomClientPast24StatHistoryPort1Entry
	MAX-ACCESS not-accessible
	STATUS current
	DESCRIPTION
        "
        List of pmc1008mpPerfTelecomClientPast24StatHistory 
        Article
        "
	::= { pmc1008mpMonClient 40 }


pmc1008mpPerfTelecomClientPast24StatHistoryPort1Entry OBJECT-TYPE
	SYNTAX Pmc1008mpPerfTelecomClientPast24StatHistoryPort1Entry
	MAX-ACCESS not-accessible
	STATUS current
	DESCRIPTION
        "
        Row definition for the pmc1008mpPerfTelecomClientPast24StatHistory 
        table
        "
	INDEX   { pmc1008mpPerfTelecomClientPast24StatHistoryPort1Index }
	::= { pmc1008mpPerfTelecomClientPast24StatHistoryPort1Table 1 }


Pmc1008mpPerfTelecomClientPast24StatHistoryPort1Entry ::=
	SEQUENCE {
	pmc1008mpPerfTelecomClientPast24StatHistoryPort1Index
		INTEGER,
	pmc1008mpPerfTelecomClientPast24StatHistoryInvCvPort1
		EkiOnOff,
	pmc1008mpPerfTelecomClientPast24StatHistoryCvValuePort1
		Unsigned32,
	pmc1008mpPerfTelecomClientPast24StatHistoryInvEsPort1
		EkiOnOff,
	pmc1008mpPerfTelecomClientPast24StatHistoryEsValuePort1
		Unsigned32,
	pmc1008mpPerfTelecomClientPast24StatHistoryInvSesPort1
		EkiOnOff,
	pmc1008mpPerfTelecomClientPast24StatHistorySesValuePort1
		Unsigned32,
	pmc1008mpPerfTelecomClientPast24StatHistoryInvSefsPort1
		EkiOnOff,
	pmc1008mpPerfTelecomClientPast24StatHistorySefsValuePort1
		Unsigned32,
	pmc1008mpPerfTelecomClientPast24StatHistoryInvUasPort1
		EkiOnOff,
	pmc1008mpPerfTelecomClientPast24StatHistoryUasValuePort1
		Unsigned32
	}


pmc1008mpPerfTelecomClientPast24StatHistoryPort1Index OBJECT-TYPE
	SYNTAX  INTEGER(0..128)
	MAX-ACCESS  read-only
	STATUS current
	DESCRIPTION
        "
        Index definition for the pmc1008mpPerfTelecomClientPast24StatHistory 
        table
        "
	::= { pmc1008mpPerfTelecomClientPast24StatHistoryPort1Entry 1 }


pmc1008mpPerfTelecomClientPast24StatHistoryInvCvPort1 OBJECT-TYPE
	SYNTAX  EkiOnOff
	MAX-ACCESS read-only
	STATUS current
	DESCRIPTION
        "
        Previous 24-hours CV counter inv. 
        :This OID indicates that the previous 
        24-hours Coding Violation counter 
        is invalid
        "
	::= { pmc1008mpPerfTelecomClientPast24StatHistoryPort1Entry 2 }


pmc1008mpPerfTelecomClientPast24StatHistoryCvValuePort1 OBJECT-TYPE
	SYNTAX  Unsigned32
	MAX-ACCESS read-only
	STATUS current
	DESCRIPTION
        "
        Previous 24-hours CV counter :This 
        OID gives the previous 24-hours 
        Coding Violation counter value
        "
	::= { pmc1008mpPerfTelecomClientPast24StatHistoryPort1Entry 3 }


pmc1008mpPerfTelecomClientPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pmc1008mpPerfTelecomClientPast24StatHistoryPort1Entry 4 }


pmc1008mpPerfTelecomClientPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pmc1008mpPerfTelecomClientPast24StatHistoryPort1Entry 5 }


pmc1008mpPerfTelecomClientPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pmc1008mpPerfTelecomClientPast24StatHistoryPort1Entry 6 }


pmc1008mpPerfTelecomClientPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pmc1008mpPerfTelecomClientPast24StatHistoryPort1Entry 7 }


pmc1008mpPerfTelecomClientPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pmc1008mpPerfTelecomClientPast24StatHistoryPort1Entry 8 }


pmc1008mpPerfTelecomClientPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pmc1008mpPerfTelecomClientPast24StatHistoryPort1Entry 9 }


pmc1008mpPerfTelecomClientPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pmc1008mpPerfTelecomClientPast24StatHistoryPort1Entry 10 }


pmc1008mpPerfTelecomClientPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pmc1008mpPerfTelecomClientPast24StatHistoryPort1Entry 11 }


--- *****************************************************
---     Leaf of the telecomLineCurrent15Stat
--- *****************************************************
--- *********************************************************
---     TABLE for the pmc1008mpPerfTelecomLineCurrent15Stat articles
--- *********************************************************

pmc1008mpPerfTelecomLineCurrent15StatTable OBJECT-TYPE
	SYNTAX  SEQUENCE OF Pmc1008mpPerfTelecomLineCurrent15StatEntry
	MAX-ACCESS not-accessible
	STATUS current
	DESCRIPTION
        "
        List of pmc1008mpPerfTelecomLineCurrent15Stat 
        Article
        "
	::= { pmc1008mpMonLine 128 }


pmc1008mpPerfTelecomLineCurrent15StatEntry OBJECT-TYPE
	SYNTAX Pmc1008mpPerfTelecomLineCurrent15StatEntry
	MAX-ACCESS not-accessible
	STATUS current
	DESCRIPTION
        "
        Row definition for the pmc1008mpPerfTelecomLineCurrent15Stat 
        table
        "
	INDEX   { pmc1008mpPerfTelecomLineCurrent15StatIndex }
	::= { pmc1008mpPerfTelecomLineCurrent15StatTable 1 }


Pmc1008mpPerfTelecomLineCurrent15StatEntry ::=
	SEQUENCE {
	pmc1008mpPerfTelecomLineCurrent15StatIndex
		INTEGER,
	pmc1008mpPerfTelecomLineCurrent15StatInvCvPortn
		EkiOnOff,
	pmc1008mpPerfTelecomLineCurrent15StatCvValuePortn
		Unsigned32,
	pmc1008mpPerfTelecomLineCurrent15StatInvEsPortn
		EkiOnOff,
	pmc1008mpPerfTelecomLineCurrent15StatEsValuePortn
		Unsigned32,
	pmc1008mpPerfTelecomLineCurrent15StatInvSesPortn
		EkiOnOff,
	pmc1008mpPerfTelecomLineCurrent15StatSesValuePortn
		Unsigned32,
	pmc1008mpPerfTelecomLineCurrent15StatInvSefsPortn
		EkiOnOff,
	pmc1008mpPerfTelecomLineCurrent15StatSefsValuePortn
		Unsigned32,
	pmc1008mpPerfTelecomLineCurrent15StatInvUasPortn
		EkiOnOff,
	pmc1008mpPerfTelecomLineCurrent15StatUasValuePortn
		Unsigned32
	}


pmc1008mpPerfTelecomLineCurrent15StatIndex OBJECT-TYPE
	SYNTAX  INTEGER(0..128)
	MAX-ACCESS  read-only
	STATUS current
	DESCRIPTION
        "
        Index definition for the pmc1008mpPerfTelecomLineCurrent15Stat 
        table
        "
	::= { pmc1008mpPerfTelecomLineCurrent15StatEntry 1 }


pmc1008mpPerfTelecomLineCurrent15StatInvCvPortn OBJECT-TYPE
	SYNTAX  EkiOnOff
	MAX-ACCESS read-only
	STATUS current
	DESCRIPTION
        "
        Current 15-min CV counter inv. 
        :This OID indicates that the current 
        15-min Coding Violation counter 
        is invalid
        "
	::= { pmc1008mpPerfTelecomLineCurrent15StatEntry 2 }


pmc1008mpPerfTelecomLineCurrent15StatCvValuePortn OBJECT-TYPE
	SYNTAX  Unsigned32
	MAX-ACCESS read-only
	STATUS current
	DESCRIPTION
        "
        Current 15-min CV counter :This 
        OID gives the current 15-min Coding 
        Violation counter value
        "
	::= { pmc1008mpPerfTelecomLineCurrent15StatEntry 3 }


pmc1008mpPerfTelecomLineCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pmc1008mpPerfTelecomLineCurrent15StatEntry 4 }


pmc1008mpPerfTelecomLineCurrent15StatEsValuePortn OBJECT-TYPE
	SYNTAX  Unsigned32
	MAX-ACCESS read-only
	STATUS current
	DESCRIPTION
        "
        Current 15-min ES counter :This 
        OID gives the current 15-min Errored 
        Second counter value
        "
	::= { pmc1008mpPerfTelecomLineCurrent15StatEntry 5 }


pmc1008mpPerfTelecomLineCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pmc1008mpPerfTelecomLineCurrent15StatEntry 6 }


pmc1008mpPerfTelecomLineCurrent15StatSesValuePortn OBJECT-TYPE
	SYNTAX  Unsigned32
	MAX-ACCESS read-only
	STATUS current
	DESCRIPTION
        "
        Current 15-min SES counter :This 
        OID gives the current 15-min severely 
        Errored Second counter value
        "
	::= { pmc1008mpPerfTelecomLineCurrent15StatEntry 7 }


pmc1008mpPerfTelecomLineCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pmc1008mpPerfTelecomLineCurrent15StatEntry 8 }


pmc1008mpPerfTelecomLineCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pmc1008mpPerfTelecomLineCurrent15StatEntry 9 }


pmc1008mpPerfTelecomLineCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pmc1008mpPerfTelecomLineCurrent15StatEntry 10 }


pmc1008mpPerfTelecomLineCurrent15StatUasValuePortn OBJECT-TYPE
	SYNTAX  Unsigned32
	MAX-ACCESS read-only
	STATUS current
	DESCRIPTION
        "
        Current 15-min UAS counter :This 
        OID gives the current 15-min UnAvailable 
        Second counter value
        "
	::= { pmc1008mpPerfTelecomLineCurrent15StatEntry 11 }


--- *****************************************************
---     Leaf of the telecomLinePast15Stat
--- *****************************************************
--- *********************************************************
---     TABLE for the pmc1008mpPerfTelecomLinePast15StatHistory articles
--- *********************************************************

pmc1008mpPerfTelecomLinePast15StatHistoryPort1Table OBJECT-TYPE
	SYNTAX  SEQUENCE OF Pmc1008mpPerfTelecomLinePast15StatHistoryPort1Entry
	MAX-ACCESS not-accessible
	STATUS current
	DESCRIPTION
        "
        List of pmc1008mpPerfTelecomLinePast15StatHistory 
        Article
        "
	::= { pmc1008mpMonLine 129 }


pmc1008mpPerfTelecomLinePast15StatHistoryPort1Entry OBJECT-TYPE
	SYNTAX Pmc1008mpPerfTelecomLinePast15StatHistoryPort1Entry
	MAX-ACCESS not-accessible
	STATUS current
	DESCRIPTION
        "
        Row definition for the pmc1008mpPerfTelecomLinePast15StatHistory 
        table
        "
	INDEX   { pmc1008mpPerfTelecomLinePast15StatHistoryPort1Index }
	::= { pmc1008mpPerfTelecomLinePast15StatHistoryPort1Table 1 }


Pmc1008mpPerfTelecomLinePast15StatHistoryPort1Entry ::=
	SEQUENCE {
	pmc1008mpPerfTelecomLinePast15StatHistoryPort1Index
		INTEGER,
	pmc1008mpPerfTelecomLinePast15StatHistoryInvCvPort1
		EkiOnOff,
	pmc1008mpPerfTelecomLinePast15StatHistoryCvValuePort1
		Unsigned32,
	pmc1008mpPerfTelecomLinePast15StatHistoryInvEsPort1
		EkiOnOff,
	pmc1008mpPerfTelecomLinePast15StatHistoryEsValuePort1
		Unsigned32,
	pmc1008mpPerfTelecomLinePast15StatHistoryInvSesPort1
		EkiOnOff,
	pmc1008mpPerfTelecomLinePast15StatHistorySesValuePort1
		Unsigned32,
	pmc1008mpPerfTelecomLinePast15StatHistoryInvSefsPort1
		EkiOnOff,
	pmc1008mpPerfTelecomLinePast15StatHistorySefsValuePort1
		Unsigned32,
	pmc1008mpPerfTelecomLinePast15StatHistoryInvUasPort1
		EkiOnOff,
	pmc1008mpPerfTelecomLinePast15StatHistoryUasValuePort1
		Unsigned32
	}


pmc1008mpPerfTelecomLinePast15StatHistoryPort1Index OBJECT-TYPE
	SYNTAX  INTEGER(0..128)
	MAX-ACCESS  read-only
	STATUS current
	DESCRIPTION
        "
        Index definition for the pmc1008mpPerfTelecomLinePast15StatHistory 
        table
        "
	::= { pmc1008mpPerfTelecomLinePast15StatHistoryPort1Entry 1 }


pmc1008mpPerfTelecomLinePast15StatHistoryInvCvPort1 OBJECT-TYPE
	SYNTAX  EkiOnOff
	MAX-ACCESS read-only
	STATUS current
	DESCRIPTION
        "
        Previous 15-min CV counter inv. 
        :This OID indicates that the previous 
        15-min Coding Violation counter 
        is invalid
        "
	::= { pmc1008mpPerfTelecomLinePast15StatHistoryPort1Entry 2 }


pmc1008mpPerfTelecomLinePast15StatHistoryCvValuePort1 OBJECT-TYPE
	SYNTAX  Unsigned32
	MAX-ACCESS read-only
	STATUS current
	DESCRIPTION
        "
        Previous 15-min CV counter :This 
        OID gives the previous 15-min Coding 
        Violation counter value
        "
	::= { pmc1008mpPerfTelecomLinePast15StatHistoryPort1Entry 3 }


pmc1008mpPerfTelecomLinePast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pmc1008mpPerfTelecomLinePast15StatHistoryPort1Entry 4 }


pmc1008mpPerfTelecomLinePast15StatHistoryEsValuePort1 OBJECT-TYPE
	SYNTAX  Unsigned32
	MAX-ACCESS read-only
	STATUS current
	DESCRIPTION
        "
        Previous 15-min ES counter :This 
        OID gives the previous 15-min Errored 
        Second counter value
        "
	::= { pmc1008mpPerfTelecomLinePast15StatHistoryPort1Entry 5 }


pmc1008mpPerfTelecomLinePast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pmc1008mpPerfTelecomLinePast15StatHistoryPort1Entry 6 }


pmc1008mpPerfTelecomLinePast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pmc1008mpPerfTelecomLinePast15StatHistoryPort1Entry 7 }


pmc1008mpPerfTelecomLinePast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pmc1008mpPerfTelecomLinePast15StatHistoryPort1Entry 8 }


pmc1008mpPerfTelecomLinePast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pmc1008mpPerfTelecomLinePast15StatHistoryPort1Entry 9 }


pmc1008mpPerfTelecomLinePast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pmc1008mpPerfTelecomLinePast15StatHistoryPort1Entry 10 }


pmc1008mpPerfTelecomLinePast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pmc1008mpPerfTelecomLinePast15StatHistoryPort1Entry 11 }


--- *****************************************************
---     Leaf of the telecomLineCurrent24Stat
--- *****************************************************
--- *********************************************************
---     TABLE for the pmc1008mpPerfTelecomLineCurrent24Stat articles
--- *********************************************************

pmc1008mpPerfTelecomLineCurrent24StatTable OBJECT-TYPE
	SYNTAX  SEQUENCE OF Pmc1008mpPerfTelecomLineCurrent24StatEntry
	MAX-ACCESS not-accessible
	STATUS current
	DESCRIPTION
        "
        List of pmc1008mpPerfTelecomLineCurrent24Stat 
        Article
        "
	::= { pmc1008mpMonLine 130 }


pmc1008mpPerfTelecomLineCurrent24StatEntry OBJECT-TYPE
	SYNTAX Pmc1008mpPerfTelecomLineCurrent24StatEntry
	MAX-ACCESS not-accessible
	STATUS current
	DESCRIPTION
        "
        Row definition for the pmc1008mpPerfTelecomLineCurrent24Stat 
        table
        "
	INDEX   { pmc1008mpPerfTelecomLineCurrent24StatIndex }
	::= { pmc1008mpPerfTelecomLineCurrent24StatTable 1 }


Pmc1008mpPerfTelecomLineCurrent24StatEntry ::=
	SEQUENCE {
	pmc1008mpPerfTelecomLineCurrent24StatIndex
		INTEGER,
	pmc1008mpPerfTelecomLineCurrent24StatInvCvPortn
		EkiOnOff,
	pmc1008mpPerfTelecomLineCurrent24StatCvValuePortn
		Unsigned32,
	pmc1008mpPerfTelecomLineCurrent24StatInvEsPortn
		EkiOnOff,
	pmc1008mpPerfTelecomLineCurrent24StatEsValuePortn
		Unsigned32,
	pmc1008mpPerfTelecomLineCurrent24StatInvSesPortn
		EkiOnOff,
	pmc1008mpPerfTelecomLineCurrent24StatSesValuePortn
		Unsigned32,
	pmc1008mpPerfTelecomLineCurrent24StatInvSefsPortn
		EkiOnOff,
	pmc1008mpPerfTelecomLineCurrent24StatSefsValuePortn
		Unsigned32,
	pmc1008mpPerfTelecomLineCurrent24StatInvUasPortn
		EkiOnOff,
	pmc1008mpPerfTelecomLineCurrent24StatUasValuePortn
		Unsigned32
	}


pmc1008mpPerfTelecomLineCurrent24StatIndex OBJECT-TYPE
	SYNTAX  INTEGER(0..128)
	MAX-ACCESS  read-only
	STATUS current
	DESCRIPTION
        "
        Index definition for the pmc1008mpPerfTelecomLineCurrent24Stat 
        table
        "
	::= { pmc1008mpPerfTelecomLineCurrent24StatEntry 1 }


pmc1008mpPerfTelecomLineCurrent24StatInvCvPortn OBJECT-TYPE
	SYNTAX  EkiOnOff
	MAX-ACCESS read-only
	STATUS current
	DESCRIPTION
        "
        Current 24-hours CV counter inv. 
        :This OID indicates that the current 
        24-hours Coding Violation counter 
        is invalid
        "
	::= { pmc1008mpPerfTelecomLineCurrent24StatEntry 2 }


pmc1008mpPerfTelecomLineCurrent24StatCvValuePortn OBJECT-TYPE
	SYNTAX  Unsigned32
	MAX-ACCESS read-only
	STATUS current
	DESCRIPTION
        "
        Current 24-hours CV counter :This 
        OID gives the current 24-hours
         Coding Violation counter value
        "
	::= { pmc1008mpPerfTelecomLineCurrent24StatEntry 3 }


pmc1008mpPerfTelecomLineCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pmc1008mpPerfTelecomLineCurrent24StatEntry 4 }


pmc1008mpPerfTelecomLineCurrent24StatEsValuePortn OBJECT-TYPE
	SYNTAX  Unsigned32
	MAX-ACCESS read-only
	STATUS current
	DESCRIPTION
        "
        Current 24-hours ES counter :This 
        OID gives the current 24-hours
         Errored Second counter value
        "
	::= { pmc1008mpPerfTelecomLineCurrent24StatEntry 5 }


pmc1008mpPerfTelecomLineCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pmc1008mpPerfTelecomLineCurrent24StatEntry 6 }


pmc1008mpPerfTelecomLineCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pmc1008mpPerfTelecomLineCurrent24StatEntry 7 }


pmc1008mpPerfTelecomLineCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pmc1008mpPerfTelecomLineCurrent24StatEntry 8 }


pmc1008mpPerfTelecomLineCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pmc1008mpPerfTelecomLineCurrent24StatEntry 9 }


pmc1008mpPerfTelecomLineCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pmc1008mpPerfTelecomLineCurrent24StatEntry 10 }


pmc1008mpPerfTelecomLineCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pmc1008mpPerfTelecomLineCurrent24StatEntry 11 }


--- *****************************************************
---     Leaf of the telecomLinePast24Stat
--- *****************************************************
--- *********************************************************
---     TABLE for the pmc1008mpPerfTelecomLinePast24StatHistory articles
--- *********************************************************

pmc1008mpPerfTelecomLinePast24StatHistoryPort1Table OBJECT-TYPE
	SYNTAX  SEQUENCE OF Pmc1008mpPerfTelecomLinePast24StatHistoryPort1Entry
	MAX-ACCESS not-accessible
	STATUS current
	DESCRIPTION
        "
        List of pmc1008mpPerfTelecomLinePast24StatHistory 
        Article
        "
	::= { pmc1008mpMonLine 131 }


pmc1008mpPerfTelecomLinePast24StatHistoryPort1Entry OBJECT-TYPE
	SYNTAX Pmc1008mpPerfTelecomLinePast24StatHistoryPort1Entry
	MAX-ACCESS not-accessible
	STATUS current
	DESCRIPTION
        "
        Row definition for the pmc1008mpPerfTelecomLinePast24StatHistory 
        table
        "
	INDEX   { pmc1008mpPerfTelecomLinePast24StatHistoryPort1Index }
	::= { pmc1008mpPerfTelecomLinePast24StatHistoryPort1Table 1 }


Pmc1008mpPerfTelecomLinePast24StatHistoryPort1Entry ::=
	SEQUENCE {
	pmc1008mpPerfTelecomLinePast24StatHistoryPort1Index
		INTEGER,
	pmc1008mpPerfTelecomLinePast24StatHistoryInvCvPort1
		EkiOnOff,
	pmc1008mpPerfTelecomLinePast24StatHistoryCvValuePort1
		Unsigned32,
	pmc1008mpPerfTelecomLinePast24StatHistoryInvEsPort1
		EkiOnOff,
	pmc1008mpPerfTelecomLinePast24StatHistoryEsValuePort1
		Unsigned32,
	pmc1008mpPerfTelecomLinePast24StatHistoryInvSesPort1
		EkiOnOff,
	pmc1008mpPerfTelecomLinePast24StatHistorySesValuePort1
		Unsigned32,
	pmc1008mpPerfTelecomLinePast24StatHistoryInvSefsPort1
		EkiOnOff,
	pmc1008mpPerfTelecomLinePast24StatHistorySefsValuePort1
		Unsigned32,
	pmc1008mpPerfTelecomLinePast24StatHistoryInvUasPort1
		EkiOnOff,
	pmc1008mpPerfTelecomLinePast24StatHistoryUasValuePort1
		Unsigned32
	}


pmc1008mpPerfTelecomLinePast24StatHistoryPort1Index OBJECT-TYPE
	SYNTAX  INTEGER(0..128)
	MAX-ACCESS  read-only
	STATUS current
	DESCRIPTION
        "
        Index definition for the pmc1008mpPerfTelecomLinePast24StatHistory 
        table
        "
	::= { pmc1008mpPerfTelecomLinePast24StatHistoryPort1Entry 1 }


pmc1008mpPerfTelecomLinePast24StatHistoryInvCvPort1 OBJECT-TYPE
	SYNTAX  EkiOnOff
	MAX-ACCESS read-only
	STATUS current
	DESCRIPTION
        "
        Previous 24-hours CV counter inv. 
        :This OID indicates that the previous 
        24-hours Coding Violation counter 
        is invalid
        "
	::= { pmc1008mpPerfTelecomLinePast24StatHistoryPort1Entry 2 }


pmc1008mpPerfTelecomLinePast24StatHistoryCvValuePort1 OBJECT-TYPE
	SYNTAX  Unsigned32
	MAX-ACCESS read-only
	STATUS current
	DESCRIPTION
        "
        Previous 24-hours CV counter :This 
        OID gives the previous 24-hours 
        Coding Violation counter value
        "
	::= { pmc1008mpPerfTelecomLinePast24StatHistoryPort1Entry 3 }


pmc1008mpPerfTelecomLinePast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pmc1008mpPerfTelecomLinePast24StatHistoryPort1Entry 4 }


pmc1008mpPerfTelecomLinePast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pmc1008mpPerfTelecomLinePast24StatHistoryPort1Entry 5 }


pmc1008mpPerfTelecomLinePast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pmc1008mpPerfTelecomLinePast24StatHistoryPort1Entry 6 }


pmc1008mpPerfTelecomLinePast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pmc1008mpPerfTelecomLinePast24StatHistoryPort1Entry 7 }


pmc1008mpPerfTelecomLinePast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pmc1008mpPerfTelecomLinePast24StatHistoryPort1Entry 8 }


pmc1008mpPerfTelecomLinePast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pmc1008mpPerfTelecomLinePast24StatHistoryPort1Entry 9 }


pmc1008mpPerfTelecomLinePast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pmc1008mpPerfTelecomLinePast24StatHistoryPort1Entry 10 }


pmc1008mpPerfTelecomLinePast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pmc1008mpPerfTelecomLinePast24StatHistoryPort1Entry 11 }


--- *****************************************************
---     Leaf of the datacomClientCurrent15Stat
--- *****************************************************
--- *********************************************************
---     TABLE for the pmc1008mpPerfDatacomClientCurrent15Stat articles
--- *********************************************************

pmc1008mpPerfDatacomClientCurrent15StatTable OBJECT-TYPE
	SYNTAX  SEQUENCE OF Pmc1008mpPerfDatacomClientCurrent15StatEntry
	MAX-ACCESS not-accessible
	STATUS current
	DESCRIPTION
        "
        List of pmc1008mpPerfDatacomClientCurrent15Stat 
        Article
        "
	::= { pmc1008mpMonClient 256 }


pmc1008mpPerfDatacomClientCurrent15StatEntry OBJECT-TYPE
	SYNTAX Pmc1008mpPerfDatacomClientCurrent15StatEntry
	MAX-ACCESS not-accessible
	STATUS current
	DESCRIPTION
        "
        Row definition for the pmc1008mpPerfDatacomClientCurrent15Stat 
        table
        "
	INDEX   { pmc1008mpPerfDatacomClientCurrent15StatIndex }
	::= { pmc1008mpPerfDatacomClientCurrent15StatTable 1 }


Pmc1008mpPerfDatacomClientCurrent15StatEntry ::=
	SEQUENCE {
	pmc1008mpPerfDatacomClientCurrent15StatIndex
		INTEGER,
	pmc1008mpperfdatacomclientCurrent15StatOutNonunicastCountInvPortn
		EkiOnOff,
	pmc1008mpperfdatacomclientCurrent15StatOutNonunicastCountPortn
		Counter64,
	pmc1008mpperfdatacomclientCurrent15StatOutUnicastCountInvPortn
		EkiOnOff,
	pmc1008mpperfdatacomclientCurrent15StatOutUnicastCountPortn
		Counter64,
	pmc1008mpperfdatacomclientCurrent15StatOutMulticastCountInvPortn
		EkiOnOff,
	pmc1008mpperfdatacomclientCurrent15StatOutMulticastCountPortn
		Counter64,
	pmc1008mpperfdatacomclientCurrent15StatOutBroadcastCountInvPortn
		EkiOnOff,
	pmc1008mpperfdatacomclientCurrent15StatOutBroadcastCountPortn
		Counter64,
	pmc1008mpperfdatacomclientCurrent15StatOutBytesCountInvPortn
		EkiOnOff,
	pmc1008mpperfdatacomclientCurrent15StatOutBytesCountPortn
		Counter64,
	pmc1008mpperfdatacomclientCurrent15StatInNonunicastCountInvPortn
		EkiOnOff,
	pmc1008mpperfdatacomclientCurrent15StatInNonunicastCountPortn
		Counter64,
	pmc1008mpperfdatacomclientCurrent15StatInUnicastCountInvPortn
		EkiOnOff,
	pmc1008mpperfdatacomclientCurrent15StatInUnicastCountPortn
		Counter64,
	pmc1008mpperfdatacomclientCurrent15StatInMulticastCountInvPortn
		EkiOnOff,
	pmc1008mpperfdatacomclientCurrent15StatInMulticastCountPortn
		Counter64,
	pmc1008mpperfdatacomclientCurrent15StatInBroadcastCountInvPortn
		EkiOnOff,
	pmc1008mpperfdatacomclientCurrent15StatInBroadcastCountPortn
		Counter64,
	pmc1008mpperfdatacomclientCurrent15StatInCrcCountInvPortn
		EkiOnOff,
	pmc1008mpperfdatacomclientCurrent15StatInCrcCountPortn
		Counter64,
	pmc1008mpperfdatacomclientCurrent15StatInBytesCountInvPortn
		EkiOnOff,
	pmc1008mpperfdatacomclientCurrent15StatInBytesCountPortn
		Counter64
	}


pmc1008mpPerfDatacomClientCurrent15StatIndex OBJECT-TYPE
	SYNTAX  INTEGER(0..128)
	MAX-ACCESS  read-only
	STATUS current
	DESCRIPTION
        "
        Index definition for the pmc1008mpPerfDatacomClientCurrent15Stat 
        table
        "
	::= { pmc1008mpPerfDatacomClientCurrent15StatEntry 1 }


pmc1008mpperfdatacomclientCurrent15StatOutNonunicastCountInvPortn OBJECT-TYPE
	SYNTAX  EkiOnOff
	MAX-ACCESS read-only
	STATUS current
	DESCRIPTION
        "
        Client Current 15-min Output Non 
        Unicast counter inv. :This OID
         indicates that the current 15-min 
        Non Unicast counter is invalid
        "
	::= { pmc1008mpPerfDatacomClientCurrent15StatEntry 44 }


pmc1008mpperfdatacomclientCurrent15StatOutNonunicastCountPortn OBJECT-TYPE
	SYNTAX  Counter64
	MAX-ACCESS read-only
	STATUS current
	DESCRIPTION
        "
        Client Current 15-min Output Non 
        Unicast counter :This OID gives 
        the current 15-min Non Unicast
         counter value
        "
	::= { pmc1008mpPerfDatacomClientCurrent15StatEntry 45 }


pmc1008mpperfdatacomclientCurrent15StatOutUnicastCountInvPortn OBJECT-TYPE
	SYNTAX  EkiOnOff
	MAX-ACCESS read-only
	STATUS current
	DESCRIPTION
        "
        Client Current 15-min Output Unicast 
        counter inv. :This OID indicates 
        that the current 15-min Unicast 
        counter is invalid
        "
	::= { pmc1008mpPerfDatacomClientCurrent15StatEntry 42 }


pmc1008mpperfdatacomclientCurrent15StatOutUnicastCountPortn OBJECT-TYPE
	SYNTAX  Counter64
	MAX-ACCESS read-only
	STATUS current
	DESCRIPTION
        "
        Client Current 15-min Output Unicast 
        counter :This OID gives the current 
        15-min Unicast counter value
        "
	::= { pmc1008mpPerfDatacomClientCurrent15StatEntry 43 }


pmc1008mpperfdatacomclientCurrent15StatOutMulticastCountInvPortn OBJECT-TYPE
	SYNTAX  EkiOnOff
	MAX-ACCESS read-only
	STATUS current
	DESCRIPTION
        "
        Client Current 15-min Output Multicast 
        counter inv. :This OID indicates 
        that the current 15-min Multicast 
        counter is invalid
        "
	::= { pmc1008mpPerfDatacomClientCurrent15StatEntry 34 }


pmc1008mpperfdatacomclientCurrent15StatOutMulticastCountPortn OBJECT-TYPE
	SYNTAX  Counter64
	MAX-ACCESS read-only
	STATUS current
	DESCRIPTION
        "
        Client Current 15-min Output Multicast 
        counter :This OID gives the current 
        15-min Multicast counter value
        "
	::= { pmc1008mpPerfDatacomClientCurrent15StatEntry 35 }


pmc1008mpperfdatacomclientCurrent15StatOutBroadcastCountInvPortn OBJECT-TYPE
	SYNTAX  EkiOnOff
	MAX-ACCESS read-only
	STATUS current
	DESCRIPTION
        "
        Client Current 15-min Output Broadcast 
        counter inv. :This OID indicates 
        that the current 15-min Broadcast 
        counter is invalid
        "
	::= { pmc1008mpPerfDatacomClientCurrent15StatEntry 32 }


pmc1008mpperfdatacomclientCurrent15StatOutBroadcastCountPortn OBJECT-TYPE
	SYNTAX  Counter64
	MAX-ACCESS read-only
	STATUS current
	DESCRIPTION
        "
        Client Current 15-min Output Broadcast 
        counter :This OID gives the current 
        15-min Broadcast counter value
        "
	::= { pmc1008mpPerfDatacomClientCurrent15StatEntry 33 }


pmc1008mpperfdatacomclientCurrent15StatOutBytesCountInvPortn OBJECT-TYPE
	SYNTAX  EkiOnOff
	MAX-ACCESS read-only
	STATUS current
	DESCRIPTION
        "
        Client Current 15-min Output Bytes 
        counter inv. :This OID indicates 
        that the current 15-min Bytes counter 
        is invalid
        "
	::= { pmc1008mpPerfDatacomClientCurrent15StatEntry 26 }


pmc1008mpperfdatacomclientCurrent15StatOutBytesCountPortn OBJECT-TYPE
	SYNTAX  Counter64
	MAX-ACCESS read-only
	STATUS current
	DESCRIPTION
        "
        Client Current 15-min Output Bytes 
        counter :This OID gives the current 
        15-min Bytes counter value
        "
	::= { pmc1008mpPerfDatacomClientCurrent15StatEntry 27 }


pmc1008mpperfdatacomclientCurrent15StatInNonunicastCountInvPortn OBJECT-TYPE
	SYNTAX  EkiOnOff
	MAX-ACCESS read-only
	STATUS current
	DESCRIPTION
        "
        Client Current 15-min Input Non 
        Unicast counter inv. :This OID
         indicates that the current 15-min 
        Non unicast counter is invalid
        "
	::= { pmc1008mpPerfDatacomClientCurrent15StatEntry 22 }


pmc1008mpperfdatacomclientCurrent15StatInNonunicastCountPortn OBJECT-TYPE
	SYNTAX  Counter64
	MAX-ACCESS read-only
	STATUS current
	DESCRIPTION
        "
        Client Current 15-min Input Non 
        Unicast counter :This OID gives 
        the current 15-min Non Unicast
         counter value
        "
	::= { pmc1008mpPerfDatacomClientCurrent15StatEntry 23 }


pmc1008mpperfdatacomclientCurrent15StatInUnicastCountInvPortn OBJECT-TYPE
	SYNTAX  EkiOnOff
	MAX-ACCESS read-only
	STATUS current
	DESCRIPTION
        "
        Client Current 15-min Input Unicast 
        counter inv. :This OID indicates 
        that the current 15-min Unicast 
        counter is invalid
        "
	::= { pmc1008mpPerfDatacomClientCurrent15StatEntry 20 }


pmc1008mpperfdatacomclientCurrent15StatInUnicastCountPortn OBJECT-TYPE
	SYNTAX  Counter64
	MAX-ACCESS read-only
	STATUS current
	DESCRIPTION
        "
        Client Current 15-min Input Unicast 
        counter :This OID gives the current 
        15-min Unicast counter value
        "
	::= { pmc1008mpPerfDatacomClientCurrent15StatEntry 21 }


pmc1008mpperfdatacomclientCurrent15StatInMulticastCountInvPortn OBJECT-TYPE
	SYNTAX  EkiOnOff
	MAX-ACCESS read-only
	STATUS current
	DESCRIPTION
        "
        Client Current 15-min Input Multicast 
        counter inv. :This OID indicates 
        that the current 15-min Multicast 
        counter is invalid
        "
	::= { pmc1008mpPerfDatacomClientCurrent15StatEntry 10 }


pmc1008mpperfdatacomclientCurrent15StatInMulticastCountPortn OBJECT-TYPE
	SYNTAX  Counter64
	MAX-ACCESS read-only
	STATUS current
	DESCRIPTION
        "
        Client Current 15-min Input Multicast 
        counter :This OID gives the current 
        15-min Multicast counter value
        "
	::= { pmc1008mpPerfDatacomClientCurrent15StatEntry 11 }


pmc1008mpperfdatacomclientCurrent15StatInBroadcastCountInvPortn OBJECT-TYPE
	SYNTAX  EkiOnOff
	MAX-ACCESS read-only
	STATUS current
	DESCRIPTION
        "
        Client Current 15-min Input Broadcast 
        counter inv. :This OID indicates 
        that the current 15-min Broadcast 
        counter is invalid
        "
	::= { pmc1008mpPerfDatacomClientCurrent15StatEntry 8 }


pmc1008mpperfdatacomclientCurrent15StatInBroadcastCountPortn OBJECT-TYPE
	SYNTAX  Counter64
	MAX-ACCESS read-only
	STATUS current
	DESCRIPTION
        "
        Client Current 15-min Input Broadcast 
        counter :This OID gives the current 
        15-min Broadcast counter value
        "
	::= { pmc1008mpPerfDatacomClientCurrent15StatEntry 9 }


pmc1008mpperfdatacomclientCurrent15StatInCrcCountInvPortn OBJECT-TYPE
	SYNTAX  EkiOnOff
	MAX-ACCESS read-only
	STATUS current
	DESCRIPTION
        "
        Client Current 15-min Input CRC 
        counter inv. :This OID indicates 
        that the current 15-min CRC counter 
        is invalid
        "
	::= { pmc1008mpPerfDatacomClientCurrent15StatEntry 4 }


pmc1008mpperfdatacomclientCurrent15StatInCrcCountPortn OBJECT-TYPE
	SYNTAX  Counter64
	MAX-ACCESS read-only
	STATUS current
	DESCRIPTION
        "
        Client Current 15-min Input CRC 
        counter :This OID gives the current 
        15-min CRC counter value
        "
	::= { pmc1008mpPerfDatacomClientCurrent15StatEntry 5 }


pmc1008mpperfdatacomclientCurrent15StatInBytesCountInvPortn OBJECT-TYPE
	SYNTAX  EkiOnOff
	MAX-ACCESS read-only
	STATUS current
	DESCRIPTION
        "
        Client Current 15-min Input Bytes 
        counter inv. :This OID indicates 
        that the current 15-min Bytes counter 
        is invalid
        "
	::= { pmc1008mpPerfDatacomClientCurrent15StatEntry 2 }


pmc1008mpperfdatacomclientCurrent15StatInBytesCountPortn OBJECT-TYPE
	SYNTAX  Counter64
	MAX-ACCESS read-only
	STATUS current
	DESCRIPTION
        "
        Client Current 15-min Input Bytes 
        counter :This OID gives the current 
        15-min Bytes counter value
        "
	::= { pmc1008mpPerfDatacomClientCurrent15StatEntry 3 }


--- *****************************************************
---     Leaf of the datacomClientPast15Stat
--- *****************************************************
--- *********************************************************
---     TABLE for the pmc1008mpPerfDatacomClientPast15StatHistory articles
--- *********************************************************

pmc1008mpPerfDatacomClientPast15StatHistoryPort1Table OBJECT-TYPE
	SYNTAX  SEQUENCE OF Pmc1008mpPerfDatacomClientPast15StatHistoryPort1Entry
	MAX-ACCESS not-accessible
	STATUS current
	DESCRIPTION
        "
        List of pmc1008mpPerfDatacomClientPast15StatHistory 
        Article
        "
	::= { pmc1008mpMonClient 264 }


pmc1008mpPerfDatacomClientPast15StatHistoryPort1Entry OBJECT-TYPE
	SYNTAX Pmc1008mpPerfDatacomClientPast15StatHistoryPort1Entry
	MAX-ACCESS not-accessible
	STATUS current
	DESCRIPTION
        "
        Row definition for the pmc1008mpPerfDatacomClientPast15StatHistory 
        table
        "
	INDEX   { pmc1008mpPerfDatacomClientPast15StatHistoryPort1Index }
	::= { pmc1008mpPerfDatacomClientPast15StatHistoryPort1Table 1 }


Pmc1008mpPerfDatacomClientPast15StatHistoryPort1Entry ::=
	SEQUENCE {
	pmc1008mpPerfDatacomClientPast15StatHistoryPort1Index
		INTEGER,
	pmc1008mpperfdatacomclientPast15StatOutNonunicastCountInvPort1
		EkiOnOff,
	pmc1008mpperfdatacomclientPast15StatOutNonunicastCountPort1
		Counter64,
	pmc1008mpperfdatacomclientPast15StatOutUnicastCountInvPort1
		EkiOnOff,
	pmc1008mpperfdatacomclientPast15StatOutUnicastCountPort1
		Counter64,
	pmc1008mpperfdatacomclientPast15StatOutMulticastCountInvPort1
		EkiOnOff,
	pmc1008mpperfdatacomclientPast15StatOutMulticastCountPort1
		Counter64,
	pmc1008mpperfdatacomclientPast15StatOutBroadcastCountInvPort1
		EkiOnOff,
	pmc1008mpperfdatacomclientPast15StatOutBroadcastCountPort1
		Counter64,
	pmc1008mpperfdatacomclientPast15StatOutBytesCountInvPort1
		EkiOnOff,
	pmc1008mpperfdatacomclientPast15StatOutBytesCountPort1
		Counter64,
	pmc1008mpperfdatacomclientPast15StatInNonunicastCountInvPort1
		EkiOnOff,
	pmc1008mpperfdatacomclientPast15StatInNonunicastCountPort1
		Counter64,
	pmc1008mpperfdatacomclientPast15StatInUnicastCountInvPort1
		EkiOnOff,
	pmc1008mpperfdatacomclientPast15StatInUnicastCountPort1
		Counter64,
	pmc1008mpperfdatacomclientPast15StatInMulticastCountInvPort1
		EkiOnOff,
	pmc1008mpperfdatacomclientPast15StatInMulticastCountPort1
		Counter64,
	pmc1008mpperfdatacomclientPast15StatInBroadcastCountInvPort1
		EkiOnOff,
	pmc1008mpperfdatacomclientPast15StatInBroadcastCountPort1
		Counter64,
	pmc1008mpperfdatacomclientPast15StatInCrcCountInvPort1
		EkiOnOff,
	pmc1008mpperfdatacomclientPast15StatInCrcCountPort1
		Counter64,
	pmc1008mpperfdatacomclientPast15StatInBytesCountInvPort1
		EkiOnOff,
	pmc1008mpperfdatacomclientPast15StatInBytesCountPort1
		Counter64
	}


pmc1008mpPerfDatacomClientPast15StatHistoryPort1Index OBJECT-TYPE
	SYNTAX  INTEGER(0..128)
	MAX-ACCESS  read-only
	STATUS current
	DESCRIPTION
        "
        Index definition for the pmc1008mpPerfDatacomClientPast15StatHistory 
        table
        "
	::= { pmc1008mpPerfDatacomClientPast15StatHistoryPort1Entry 1 }


pmc1008mpperfdatacomclientPast15StatOutNonunicastCountInvPort1 OBJECT-TYPE
	SYNTAX  EkiOnOff
	MAX-ACCESS read-only
	STATUS current
	DESCRIPTION
        "
        Client Past 15-min Output Non
         Unicast counter inv. :This OID 
        indicates that the past 15-min
         Non Unicast counter is invalid
        "
	::= { pmc1008mpPerfDatacomClientPast15StatHistoryPort1Entry 44 }


pmc1008mpperfdatacomclientPast15StatOutNonunicastCountPort1 OBJECT-TYPE
	SYNTAX  Counter64
	MAX-ACCESS read-only
	STATUS current
	DESCRIPTION
        "
        Client Past 15-min Output Non
         Unicast counter :This OID gives 
        the past 15-min Non Unicast counter 
        value
        "
	::= { pmc1008mpPerfDatacomClientPast15StatHistoryPort1Entry 45 }


pmc1008mpperfdatacomclientPast15StatOutUnicastCountInvPort1 OBJECT-TYPE
	SYNTAX  EkiOnOff
	MAX-ACCESS read-only
	STATUS current
	DESCRIPTION
        "
        Client Past 15-min Output Unicast 
        counter inv. :This OID indicates 
        that the past 15-min Unicast counter 
        is invalid
        "
	::= { pmc1008mpPerfDatacomClientPast15StatHistoryPort1Entry 42 }


pmc1008mpperfdatacomclientPast15StatOutUnicastCountPort1 OBJECT-TYPE
	SYNTAX  Counter64
	MAX-ACCESS read-only
	STATUS current
	DESCRIPTION
        "
        Client Past 15-min Output Unicast 
        counter :This OID gives the past 
        15-min Unicast counter value
        "
	::= { pmc1008mpPerfDatacomClientPast15StatHistoryPort1Entry 43 }


pmc1008mpperfdatacomclientPast15StatOutMulticastCountInvPort1 OBJECT-TYPE
	SYNTAX  EkiOnOff
	MAX-ACCESS read-only
	STATUS current
	DESCRIPTION
        "
        Client Past 15-min Output Multicast 
        counter inv. :This OID indicates 
        that the past 15-min Multicast
         counter is invalid
        "
	::= { pmc1008mpPerfDatacomClientPast15StatHistoryPort1Entry 34 }


pmc1008mpperfdatacomclientPast15StatOutMulticastCountPort1 OBJECT-TYPE
	SYNTAX  Counter64
	MAX-ACCESS read-only
	STATUS current
	DESCRIPTION
        "
        Client Past 15-min Output Multicast 
        counter :This OID gives the past 
        15-min Multicast counter value
        "
	::= { pmc1008mpPerfDatacomClientPast15StatHistoryPort1Entry 35 }


pmc1008mpperfdatacomclientPast15StatOutBroadcastCountInvPort1 OBJECT-TYPE
	SYNTAX  EkiOnOff
	MAX-ACCESS read-only
	STATUS current
	DESCRIPTION
        "
        Client Past 15-min Output Broadcast 
        counter inv. :This OID indicates 
        that the past 15-min Broadcast
         counter is invalid
        "
	::= { pmc1008mpPerfDatacomClientPast15StatHistoryPort1Entry 32 }


pmc1008mpperfdatacomclientPast15StatOutBroadcastCountPort1 OBJECT-TYPE
	SYNTAX  Counter64
	MAX-ACCESS read-only
	STATUS current
	DESCRIPTION
        "
        Client Past 15-min Output Broadcast 
        counter :This OID gives the past 
        15-min Broadcast counter value
        "
	::= { pmc1008mpPerfDatacomClientPast15StatHistoryPort1Entry 33 }


pmc1008mpperfdatacomclientPast15StatOutBytesCountInvPort1 OBJECT-TYPE
	SYNTAX  EkiOnOff
	MAX-ACCESS read-only
	STATUS current
	DESCRIPTION
        "
        Client Past 15-min Output Bytes 
        counter inv. :This OID indicates 
        that the past 15-min Bytes counter 
        is invalid
        "
	::= { pmc1008mpPerfDatacomClientPast15StatHistoryPort1Entry 26 }


pmc1008mpperfdatacomclientPast15StatOutBytesCountPort1 OBJECT-TYPE
	SYNTAX  Counter64
	MAX-ACCESS read-only
	STATUS current
	DESCRIPTION
        "
        Client Past 15-min Output Bytes 
        counter :This OID gives the past 
        15-min Bytes counter value
        "
	::= { pmc1008mpPerfDatacomClientPast15StatHistoryPort1Entry 27 }


pmc1008mpperfdatacomclientPast15StatInNonunicastCountInvPort1 OBJECT-TYPE
	SYNTAX  EkiOnOff
	MAX-ACCESS read-only
	STATUS current
	DESCRIPTION
        "
        Client Past 15-min Input Non Unicast 
        counter inv. :This OID indicates 
        that the past 15-min Non unicast 
        counter is invalid
        "
	::= { pmc1008mpPerfDatacomClientPast15StatHistoryPort1Entry 22 }


pmc1008mpperfdatacomclientPast15StatInNonunicastCountPort1 OBJECT-TYPE
	SYNTAX  Counter64
	MAX-ACCESS read-only
	STATUS current
	DESCRIPTION
        "
        Client Past 15-min Input Non Unicast 
        counter :This OID gives the past 
        15-min Non Unicast counter value
        "
	::= { pmc1008mpPerfDatacomClientPast15StatHistoryPort1Entry 23 }


pmc1008mpperfdatacomclientPast15StatInUnicastCountInvPort1 OBJECT-TYPE
	SYNTAX  EkiOnOff
	MAX-ACCESS read-only
	STATUS current
	DESCRIPTION
        "
        Client Past 15-min Input Unicast 
        counter inv. :This OID indicates 
        that the past 15-min Unicast counter 
        is invalid
        "
	::= { pmc1008mpPerfDatacomClientPast15StatHistoryPort1Entry 20 }


pmc1008mpperfdatacomclientPast15StatInUnicastCountPort1 OBJECT-TYPE
	SYNTAX  Counter64
	MAX-ACCESS read-only
	STATUS current
	DESCRIPTION
        "
        Client Past 15-min Input Unicast 
        counter :This OID gives the past 
        15-min Unicast counter value
        "
	::= { pmc1008mpPerfDatacomClientPast15StatHistoryPort1Entry 21 }


pmc1008mpperfdatacomclientPast15StatInMulticastCountInvPort1 OBJECT-TYPE
	SYNTAX  EkiOnOff
	MAX-ACCESS read-only
	STATUS current
	DESCRIPTION
        "
        Client Past 15-min Input Multicast 
        counter inv. :This OID indicates 
        that the past 15-min Multicast
         counter is invalid
        "
	::= { pmc1008mpPerfDatacomClientPast15StatHistoryPort1Entry 10 }


pmc1008mpperfdatacomclientPast15StatInMulticastCountPort1 OBJECT-TYPE
	SYNTAX  Counter64
	MAX-ACCESS read-only
	STATUS current
	DESCRIPTION
        "
        Client Past 15-min Input Multicast 
        counter :This OID gives the past 
        15-min Multicast counter value
        "
	::= { pmc1008mpPerfDatacomClientPast15StatHistoryPort1Entry 11 }


pmc1008mpperfdatacomclientPast15StatInBroadcastCountInvPort1 OBJECT-TYPE
	SYNTAX  EkiOnOff
	MAX-ACCESS read-only
	STATUS current
	DESCRIPTION
        "
        Client Past 15-min Input Broadcast 
        counter inv. :This OID indicates 
        that the past 15-min Broadcast
         counter is invalid
        "
	::= { pmc1008mpPerfDatacomClientPast15StatHistoryPort1Entry 8 }


pmc1008mpperfdatacomclientPast15StatInBroadcastCountPort1 OBJECT-TYPE
	SYNTAX  Counter64
	MAX-ACCESS read-only
	STATUS current
	DESCRIPTION
        "
        Client Past 15-min Input Broadcast 
        counter :This OID gives the past 
        15-min Broadcast counter value
        "
	::= { pmc1008mpPerfDatacomClientPast15StatHistoryPort1Entry 9 }


pmc1008mpperfdatacomclientPast15StatInCrcCountInvPort1 OBJECT-TYPE
	SYNTAX  EkiOnOff
	MAX-ACCESS read-only
	STATUS current
	DESCRIPTION
        "
        Client Past 15-min Input CRC counter 
        inv. :This OID indicates that the 
        past 15-min CRC counter is invalid
        "
	::= { pmc1008mpPerfDatacomClientPast15StatHistoryPort1Entry 4 }


pmc1008mpperfdatacomclientPast15StatInCrcCountPort1 OBJECT-TYPE
	SYNTAX  Counter64
	MAX-ACCESS read-only
	STATUS current
	DESCRIPTION
        "
        Client Past 15-min Input CRC counter 
        :This OID gives the past 15-min 
        CRC counter value
        "
	::= { pmc1008mpPerfDatacomClientPast15StatHistoryPort1Entry 5 }


pmc1008mpperfdatacomclientPast15StatInBytesCountInvPort1 OBJECT-TYPE
	SYNTAX  EkiOnOff
	MAX-ACCESS read-only
	STATUS current
	DESCRIPTION
        "
        Client Past 15-min Input Bytes 
        counter inv. :This OID indicates 
        that the past 15-min Bytes counter 
        is invalid
        "
	::= { pmc1008mpPerfDatacomClientPast15StatHistoryPort1Entry 2 }


pmc1008mpperfdatacomclientPast15StatInBytesCountPort1 OBJECT-TYPE
	SYNTAX  Counter64
	MAX-ACCESS read-only
	STATUS current
	DESCRIPTION
        "
        Client Past 15-min Input Bytes 
        counter :This OID gives the past 
        15-min Bytes counter value
        "
	::= { pmc1008mpPerfDatacomClientPast15StatHistoryPort1Entry 3 }


--- *****************************************************
---     Leaf of the datacomClientCurrent24Stat
--- *****************************************************
--- *********************************************************
---     TABLE for the pmc1008mpPerfDatacomClientCurrent24Stat articles
--- *********************************************************

pmc1008mpPerfDatacomClientCurrent24StatTable OBJECT-TYPE
	SYNTAX  SEQUENCE OF Pmc1008mpPerfDatacomClientCurrent24StatEntry
	MAX-ACCESS not-accessible
	STATUS current
	DESCRIPTION
        "
        List of pmc1008mpPerfDatacomClientCurrent24Stat 
        Article
        "
	::= { pmc1008mpMonClient 272 }


pmc1008mpPerfDatacomClientCurrent24StatEntry OBJECT-TYPE
	SYNTAX Pmc1008mpPerfDatacomClientCurrent24StatEntry
	MAX-ACCESS not-accessible
	STATUS current
	DESCRIPTION
        "
        Row definition for the pmc1008mpPerfDatacomClientCurrent24Stat 
        table
        "
	INDEX   { pmc1008mpPerfDatacomClientCurrent24StatIndex }
	::= { pmc1008mpPerfDatacomClientCurrent24StatTable 1 }


Pmc1008mpPerfDatacomClientCurrent24StatEntry ::=
	SEQUENCE {
	pmc1008mpPerfDatacomClientCurrent24StatIndex
		INTEGER,
	pmc1008mpperfdatacomclientCurrent24StatOutNonunicastCountInvPortn
		EkiOnOff,
	pmc1008mpperfdatacomclientCurrent24StatOutNonunicastCountPortn
		Counter64,
	pmc1008mpperfdatacomclientCurrent24StatOutUnicastCountInvPortn
		EkiOnOff,
	pmc1008mpperfdatacomclientCurrent24StatOutUnicastCountPortn
		Counter64,
	pmc1008mpperfdatacomclientCurrent24StatOutMulticastCountInvPortn
		EkiOnOff,
	pmc1008mpperfdatacomclientCurrent24StatOutMulticastCountPortn
		Counter64,
	pmc1008mpperfdatacomclientCurrent24StatOutBroadcastCountInvPortn
		EkiOnOff,
	pmc1008mpperfdatacomclientCurrent24StatOutBroadcastCountPortn
		Counter64,
	pmc1008mpperfdatacomclientCurrent24StatOutBytesCountInvPortn
		EkiOnOff,
	pmc1008mpperfdatacomclientCurrent24StatOutBytesCountPortn
		Counter64,
	pmc1008mpperfdatacomclientCurrent24StatInNonunicastCountInvPortn
		EkiOnOff,
	pmc1008mpperfdatacomclientCurrent24StatInNonunicastCountPortn
		Counter64,
	pmc1008mpperfdatacomclientCurrent24StatInUnicastCountInvPortn
		EkiOnOff,
	pmc1008mpperfdatacomclientCurrent24StatInUnicastCountPortn
		Counter64,
	pmc1008mpperfdatacomclientCurrent24StatInMulticastCountInvPortn
		EkiOnOff,
	pmc1008mpperfdatacomclientCurrent24StatInMulticastCountPortn
		Counter64,
	pmc1008mpperfdatacomclientCurrent24StatInBroadcastCountInvPortn
		EkiOnOff,
	pmc1008mpperfdatacomclientCurrent24StatInBroadcastCountPortn
		Counter64,
	pmc1008mpperfdatacomclientCurrent24StatInCrcCountInvPortn
		EkiOnOff,
	pmc1008mpperfdatacomclientCurrent24StatInCrcCountPortn
		Counter64,
	pmc1008mpperfdatacomclientCurrent24StatInBytesCountInvPortn
		EkiOnOff,
	pmc1008mpperfdatacomclientCurrent24StatInBytesCountPortn
		Counter64
	}


pmc1008mpPerfDatacomClientCurrent24StatIndex OBJECT-TYPE
	SYNTAX  INTEGER(0..128)
	MAX-ACCESS  read-only
	STATUS current
	DESCRIPTION
        "
        Index definition for the pmc1008mpPerfDatacomClientCurrent24Stat 
        table
        "
	::= { pmc1008mpPerfDatacomClientCurrent24StatEntry 1 }


pmc1008mpperfdatacomclientCurrent24StatOutNonunicastCountInvPortn OBJECT-TYPE
	SYNTAX  EkiOnOff
	MAX-ACCESS read-only
	STATUS current
	DESCRIPTION
        "
        Client Current 24-hours Output 
        Non Unicast counter inv. :This
         OID indicates that the current 
        24-hours Non Unicast counter is 
        invalid
        "
	::= { pmc1008mpPerfDatacomClientCurrent24StatEntry 44 }


pmc1008mpperfdatacomclientCurrent24StatOutNonunicastCountPortn OBJECT-TYPE
	SYNTAX  Counter64
	MAX-ACCESS read-only
	STATUS current
	DESCRIPTION
        "
        Client Current 24-hours Output 
        Non Unicast counter :This OID gives 
        the current 24-hours Non Unicast 
        counter value
        "
	::= { pmc1008mpPerfDatacomClientCurrent24StatEntry 45 }


pmc1008mpperfdatacomclientCurrent24StatOutUnicastCountInvPortn OBJECT-TYPE
	SYNTAX  EkiOnOff
	MAX-ACCESS read-only
	STATUS current
	DESCRIPTION
        "
        Client Current 24-hours Output 
        Unicast counter inv. :This OID
         indicates that the current 24-hours 
        Unicast counter is invalid
        "
	::= { pmc1008mpPerfDatacomClientCurrent24StatEntry 42 }


pmc1008mpperfdatacomclientCurrent24StatOutUnicastCountPortn OBJECT-TYPE
	SYNTAX  Counter64
	MAX-ACCESS read-only
	STATUS current
	DESCRIPTION
        "
        Client Current 24-hours Output 
        Unicast counter :This OID gives 
        the current 24-hours Unicast counter 
        value
        "
	::= { pmc1008mpPerfDatacomClientCurrent24StatEntry 43 }


pmc1008mpperfdatacomclientCurrent24StatOutMulticastCountInvPortn OBJECT-TYPE
	SYNTAX  EkiOnOff
	MAX-ACCESS read-only
	STATUS current
	DESCRIPTION
        "
        Client Current 24-hours Output 
        Multicast counter inv. :This OID 
        indicates that the current 24-hours 
        Multicast counter is invalid
        "
	::= { pmc1008mpPerfDatacomClientCurrent24StatEntry 34 }


pmc1008mpperfdatacomclientCurrent24StatOutMulticastCountPortn OBJECT-TYPE
	SYNTAX  Counter64
	MAX-ACCESS read-only
	STATUS current
	DESCRIPTION
        "
        Client Current 24-hours Output 
        Multicast counter :This OID gives 
        the current 24-hours Multicast
         counter value
        "
	::= { pmc1008mpPerfDatacomClientCurrent24StatEntry 35 }


pmc1008mpperfdatacomclientCurrent24StatOutBroadcastCountInvPortn OBJECT-TYPE
	SYNTAX  EkiOnOff
	MAX-ACCESS read-only
	STATUS current
	DESCRIPTION
        "
        Client Current 24-hours Output 
        Broadcast counter inv. :This OID 
        indicates that the current 24-hours 
        Broadcast counter is invalid
        "
	::= { pmc1008mpPerfDatacomClientCurrent24StatEntry 32 }


pmc1008mpperfdatacomclientCurrent24StatOutBroadcastCountPortn OBJECT-TYPE
	SYNTAX  Counter64
	MAX-ACCESS read-only
	STATUS current
	DESCRIPTION
        "
        Client Current 24-hours Output 
        Broadcast counter :This OID gives 
        the current 24-hours Broadcast
         counter value
        "
	::= { pmc1008mpPerfDatacomClientCurrent24StatEntry 33 }


pmc1008mpperfdatacomclientCurrent24StatOutBytesCountInvPortn OBJECT-TYPE
	SYNTAX  EkiOnOff
	MAX-ACCESS read-only
	STATUS current
	DESCRIPTION
        "
        Client Current 24-hours Output 
        Bytes counter inv. :This OID indicates 
        that the current 24-hours Bytes 
        counter is invalid
        "
	::= { pmc1008mpPerfDatacomClientCurrent24StatEntry 26 }


pmc1008mpperfdatacomclientCurrent24StatOutBytesCountPortn OBJECT-TYPE
	SYNTAX  Counter64
	MAX-ACCESS read-only
	STATUS current
	DESCRIPTION
        "
        Client Current 24-hours Output 
        Bytes counter :This OID gives the 
        current 24-hours Bytes counter
         value
        "
	::= { pmc1008mpPerfDatacomClientCurrent24StatEntry 27 }


pmc1008mpperfdatacomclientCurrent24StatInNonunicastCountInvPortn OBJECT-TYPE
	SYNTAX  EkiOnOff
	MAX-ACCESS read-only
	STATUS current
	DESCRIPTION
        "
        Client Current 24-hours Input
         Non Unicast counter inv. :This 
        OID indicates that the current
         24-hours Non unicast counter is 
        invalid
        "
	::= { pmc1008mpPerfDatacomClientCurrent24StatEntry 22 }


pmc1008mpperfdatacomclientCurrent24StatInNonunicastCountPortn OBJECT-TYPE
	SYNTAX  Counter64
	MAX-ACCESS read-only
	STATUS current
	DESCRIPTION
        "
        Client Current 24-hours Input
         Non Unicast counter :This OID
         gives the current 24-hours Non 
        Unicast counter value
        "
	::= { pmc1008mpPerfDatacomClientCurrent24StatEntry 23 }


pmc1008mpperfdatacomclientCurrent24StatInUnicastCountInvPortn OBJECT-TYPE
	SYNTAX  EkiOnOff
	MAX-ACCESS read-only
	STATUS current
	DESCRIPTION
        "
        Client Current 24-hours Input
         Unicast counter inv. :This OID 
        indicates that the current 24-hours 
        Unicast counter is invalid
        "
	::= { pmc1008mpPerfDatacomClientCurrent24StatEntry 20 }


pmc1008mpperfdatacomclientCurrent24StatInUnicastCountPortn OBJECT-TYPE
	SYNTAX  Counter64
	MAX-ACCESS read-only
	STATUS current
	DESCRIPTION
        "
        Client Current 24-hours Input
         Unicast counter :This OID gives 
        the current 24-hours Unicast counter 
        value
        "
	::= { pmc1008mpPerfDatacomClientCurrent24StatEntry 21 }


pmc1008mpperfdatacomclientCurrent24StatInMulticastCountInvPortn OBJECT-TYPE
	SYNTAX  EkiOnOff
	MAX-ACCESS read-only
	STATUS current
	DESCRIPTION
        "
        Client Current 24-hours Input
         Multicast counter inv. :This OID 
        indicates that the current 24-hours 
        Multicast counter is invalid
        "
	::= { pmc1008mpPerfDatacomClientCurrent24StatEntry 10 }


pmc1008mpperfdatacomclientCurrent24StatInMulticastCountPortn OBJECT-TYPE
	SYNTAX  Counter64
	MAX-ACCESS read-only
	STATUS current
	DESCRIPTION
        "
        Client Current 24-hours Input
         Multicast counter :This OID gives 
        the current 24-hours Multicast
         counter value
        "
	::= { pmc1008mpPerfDatacomClientCurrent24StatEntry 11 }


pmc1008mpperfdatacomclientCurrent24StatInBroadcastCountInvPortn OBJECT-TYPE
	SYNTAX  EkiOnOff
	MAX-ACCESS read-only
	STATUS current
	DESCRIPTION
        "
        Client Current 24-hours Input
         Broadcast counter inv. :This OID 
        indicates that the current 24-hours 
        Broadcast counter is invalid
        "
	::= { pmc1008mpPerfDatacomClientCurrent24StatEntry 8 }


pmc1008mpperfdatacomclientCurrent24StatInBroadcastCountPortn OBJECT-TYPE
	SYNTAX  Counter64
	MAX-ACCESS read-only
	STATUS current
	DESCRIPTION
        "
        Client Current 24-hours Input
         Broadcast counter :This OID gives 
        the current 24-hours Broadcast
         counter value
        "
	::= { pmc1008mpPerfDatacomClientCurrent24StatEntry 9 }


pmc1008mpperfdatacomclientCurrent24StatInCrcCountInvPortn OBJECT-TYPE
	SYNTAX  EkiOnOff
	MAX-ACCESS read-only
	STATUS current
	DESCRIPTION
        "
        Client Current 24-hours Input
         CRC counter inv. :This OID indicates 
        that the current 24-hours CRC counter 
        is invalid
        "
	::= { pmc1008mpPerfDatacomClientCurrent24StatEntry 4 }


pmc1008mpperfdatacomclientCurrent24StatInCrcCountPortn OBJECT-TYPE
	SYNTAX  Counter64
	MAX-ACCESS read-only
	STATUS current
	DESCRIPTION
        "
        Client Current 24-hours Input
         CRC counter :This OID gives the 
        current 24-hours CRC counter value
        "
	::= { pmc1008mpPerfDatacomClientCurrent24StatEntry 5 }


pmc1008mpperfdatacomclientCurrent24StatInBytesCountInvPortn OBJECT-TYPE
	SYNTAX  EkiOnOff
	MAX-ACCESS read-only
	STATUS current
	DESCRIPTION
        "
        Client Current 24-hours Input
         Bytes counter inv. :This OID indicates 
        that the current 24-hours Bytes 
        counter is invalid
        "
	::= { pmc1008mpPerfDatacomClientCurrent24StatEntry 2 }


pmc1008mpperfdatacomclientCurrent24StatInBytesCountPortn OBJECT-TYPE
	SYNTAX  Counter64
	MAX-ACCESS read-only
	STATUS current
	DESCRIPTION
        "
        Client Current 24-hours Input
         Bytes counter :This OID gives
         the current 24-hours Bytes counter 
        value
        "
	::= { pmc1008mpPerfDatacomClientCurrent24StatEntry 3 }


--- *****************************************************
---     Leaf of the datacomClientPast24Stat
--- *****************************************************
--- *********************************************************
---     TABLE for the pmc1008mpPerfDatacomClientPast24StatHistory articles
--- *********************************************************

pmc1008mpPerfDatacomClientPast24StatHistoryPort1Table OBJECT-TYPE
	SYNTAX  SEQUENCE OF Pmc1008mpPerfDatacomClientPast24StatHistoryPort1Entry
	MAX-ACCESS not-accessible
	STATUS current
	DESCRIPTION
        "
        List of pmc1008mpPerfDatacomClientPast24StatHistory 
        Article
        "
	::= { pmc1008mpMonClient 280 }


pmc1008mpPerfDatacomClientPast24StatHistoryPort1Entry OBJECT-TYPE
	SYNTAX Pmc1008mpPerfDatacomClientPast24StatHistoryPort1Entry
	MAX-ACCESS not-accessible
	STATUS current
	DESCRIPTION
        "
        Row definition for the pmc1008mpPerfDatacomClientPast24StatHistory 
        table
        "
	INDEX   { pmc1008mpPerfDatacomClientPast24StatHistoryPort1Index }
	::= { pmc1008mpPerfDatacomClientPast24StatHistoryPort1Table 1 }


Pmc1008mpPerfDatacomClientPast24StatHistoryPort1Entry ::=
	SEQUENCE {
	pmc1008mpPerfDatacomClientPast24StatHistoryPort1Index
		INTEGER,
	pmc1008mpperfdatacomclientPast24StatOutNonunicastCountInvPort1
		EkiOnOff,
	pmc1008mpperfdatacomclientPast24StatOutNonunicastCountPort1
		Counter64,
	pmc1008mpperfdatacomclientPast24StatOutUnicastCountInvPort1
		EkiOnOff,
	pmc1008mpperfdatacomclientPast24StatOutUnicastCountPort1
		Counter64,
	pmc1008mpperfdatacomclientPast24StatOutMulticastCountInvPort1
		EkiOnOff,
	pmc1008mpperfdatacomclientPast24StatOutMulticastCountPort1
		Counter64,
	pmc1008mpperfdatacomclientPast24StatOutBroadcastCountInvPort1
		EkiOnOff,
	pmc1008mpperfdatacomclientPast24StatOutBroadcastCountPort1
		Counter64,
	pmc1008mpperfdatacomclientPast24StatOutBytesCountInvPort1
		EkiOnOff,
	pmc1008mpperfdatacomclientPast24StatOutBytesCountPort1
		Counter64,
	pmc1008mpperfdatacomclientPast24StatInNonunicastCountInvPort1
		EkiOnOff,
	pmc1008mpperfdatacomclientPast24StatInNonunicastCountPort1
		Counter64,
	pmc1008mpperfdatacomclientPast24StatInUnicastCountInvPort1
		EkiOnOff,
	pmc1008mpperfdatacomclientPast24StatInUnicastCountPort1
		Counter64,
	pmc1008mpperfdatacomclientPast24StatInMulticastCountInvPort1
		EkiOnOff,
	pmc1008mpperfdatacomclientPast24StatInMulticastCountPort1
		Counter64,
	pmc1008mpperfdatacomclientPast24StatInBroadcastCountInvPort1
		EkiOnOff,
	pmc1008mpperfdatacomclientPast24StatInBroadcastCountPort1
		Counter64,
	pmc1008mpperfdatacomclientPast24StatInCrcCountInvPort1
		EkiOnOff,
	pmc1008mpperfdatacomclientPast24StatInCrcCountPort1
		Counter64,
	pmc1008mpperfdatacomclientPast24StatInBytesCountInvPort1
		EkiOnOff,
	pmc1008mpperfdatacomclientPast24StatInBytesCountPort1
		Counter64
	}


pmc1008mpPerfDatacomClientPast24StatHistoryPort1Index OBJECT-TYPE
	SYNTAX  INTEGER(0..128)
	MAX-ACCESS  read-only
	STATUS current
	DESCRIPTION
        "
        Index definition for the pmc1008mpPerfDatacomClientPast24StatHistory 
        table
        "
	::= { pmc1008mpPerfDatacomClientPast24StatHistoryPort1Entry 1 }


pmc1008mpperfdatacomclientPast24StatOutNonunicastCountInvPort1 OBJECT-TYPE
	SYNTAX  EkiOnOff
	MAX-ACCESS read-only
	STATUS current
	DESCRIPTION
        "
        Client Past 24-hours Output Non 
        Unicast counter inv. :This OID
         indicates that the past 24-hours 
        Non Unicast counter is invalid
        "
	::= { pmc1008mpPerfDatacomClientPast24StatHistoryPort1Entry 44 }


pmc1008mpperfdatacomclientPast24StatOutNonunicastCountPort1 OBJECT-TYPE
	SYNTAX  Counter64
	MAX-ACCESS read-only
	STATUS current
	DESCRIPTION
        "
        Client Past 24-hours Output Non 
        Unicast counter :This OID gives 
        the past 24-hours Non Unicast counter 
        value
        "
	::= { pmc1008mpPerfDatacomClientPast24StatHistoryPort1Entry 45 }


pmc1008mpperfdatacomclientPast24StatOutUnicastCountInvPort1 OBJECT-TYPE
	SYNTAX  EkiOnOff
	MAX-ACCESS read-only
	STATUS current
	DESCRIPTION
        "
        Client Past 24-hours Output Unicast 
        counter inv. :This OID indicates 
        that the past 24-hours Unicast
         counter is invalid
        "
	::= { pmc1008mpPerfDatacomClientPast24StatHistoryPort1Entry 42 }


pmc1008mpperfdatacomclientPast24StatOutUnicastCountPort1 OBJECT-TYPE
	SYNTAX  Counter64
	MAX-ACCESS read-only
	STATUS current
	DESCRIPTION
        "
        Client Past 24-hours Output Unicast 
        counter :This OID gives the past 
        24-hours Unicast counter value
        "
	::= { pmc1008mpPerfDatacomClientPast24StatHistoryPort1Entry 43 }


pmc1008mpperfdatacomclientPast24StatOutMulticastCountInvPort1 OBJECT-TYPE
	SYNTAX  EkiOnOff
	MAX-ACCESS read-only
	STATUS current
	DESCRIPTION
        "
        Client Past 24-hours Output Multicast 
        counter inv. :This OID indicates 
        that the past 24-hours Multicast 
        counter is invalid
        "
	::= { pmc1008mpPerfDatacomClientPast24StatHistoryPort1Entry 34 }


pmc1008mpperfdatacomclientPast24StatOutMulticastCountPort1 OBJECT-TYPE
	SYNTAX  Counter64
	MAX-ACCESS read-only
	STATUS current
	DESCRIPTION
        "
        Client Past 24-hours Output Multicast 
        counter :This OID gives the past 
        24-hours Multicast counter value
        "
	::= { pmc1008mpPerfDatacomClientPast24StatHistoryPort1Entry 35 }


pmc1008mpperfdatacomclientPast24StatOutBroadcastCountInvPort1 OBJECT-TYPE
	SYNTAX  EkiOnOff
	MAX-ACCESS read-only
	STATUS current
	DESCRIPTION
        "
        Client Past 24-hours Output Broadcast 
        counter inv. :This OID indicates 
        that the past 24-hours Broadcast 
        counter is invalid
        "
	::= { pmc1008mpPerfDatacomClientPast24StatHistoryPort1Entry 32 }


pmc1008mpperfdatacomclientPast24StatOutBroadcastCountPort1 OBJECT-TYPE
	SYNTAX  Counter64
	MAX-ACCESS read-only
	STATUS current
	DESCRIPTION
        "
        Client Past 24-hours Output Broadcast 
        counter :This OID gives the past 
        24-hours Broadcast counter value
        "
	::= { pmc1008mpPerfDatacomClientPast24StatHistoryPort1Entry 33 }


pmc1008mpperfdatacomclientPast24StatOutBytesCountInvPort1 OBJECT-TYPE
	SYNTAX  EkiOnOff
	MAX-ACCESS read-only
	STATUS current
	DESCRIPTION
        "
        Client Past 24-hours Output Bytes 
        counter inv. :This OID indicates 
        that the past 24-hours Bytes counter 
        is invalid
        "
	::= { pmc1008mpPerfDatacomClientPast24StatHistoryPort1Entry 26 }


pmc1008mpperfdatacomclientPast24StatOutBytesCountPort1 OBJECT-TYPE
	SYNTAX  Counter64
	MAX-ACCESS read-only
	STATUS current
	DESCRIPTION
        "
        Client Past 24-hours Output Bytes 
        counter :This OID gives the past 
        24-hours Bytes counter value
        "
	::= { pmc1008mpPerfDatacomClientPast24StatHistoryPort1Entry 27 }


pmc1008mpperfdatacomclientPast24StatInNonunicastCountInvPort1 OBJECT-TYPE
	SYNTAX  EkiOnOff
	MAX-ACCESS read-only
	STATUS current
	DESCRIPTION
        "
        Client Past 24-hours Input Non 
        Unicast counter inv. :This OID
         indicates that the past 24-hours 
        Non unicast counter is invalid
        "
	::= { pmc1008mpPerfDatacomClientPast24StatHistoryPort1Entry 22 }


pmc1008mpperfdatacomclientPast24StatInNonunicastCountPort1 OBJECT-TYPE
	SYNTAX  Counter64
	MAX-ACCESS read-only
	STATUS current
	DESCRIPTION
        "
        Client Past 24-hours Input Non 
        Unicast counter :This OID gives 
        the past 24-hours Non Unicast counter 
        value
        "
	::= { pmc1008mpPerfDatacomClientPast24StatHistoryPort1Entry 23 }


pmc1008mpperfdatacomclientPast24StatInUnicastCountInvPort1 OBJECT-TYPE
	SYNTAX  EkiOnOff
	MAX-ACCESS read-only
	STATUS current
	DESCRIPTION
        "
        Client Past 24-hours Input Unicast 
        counter inv. :This OID indicates 
        that the past 24-hours Unicast
         counter is invalid
        "
	::= { pmc1008mpPerfDatacomClientPast24StatHistoryPort1Entry 20 }


pmc1008mpperfdatacomclientPast24StatInUnicastCountPort1 OBJECT-TYPE
	SYNTAX  Counter64
	MAX-ACCESS read-only
	STATUS current
	DESCRIPTION
        "
        Client Past 24-hours Input Unicast 
        counter :This OID gives the past 
        24-hours Unicast counter value
        "
	::= { pmc1008mpPerfDatacomClientPast24StatHistoryPort1Entry 21 }


pmc1008mpperfdatacomclientPast24StatInMulticastCountInvPort1 OBJECT-TYPE
	SYNTAX  EkiOnOff
	MAX-ACCESS read-only
	STATUS current
	DESCRIPTION
        "
        Client Past 24-hours Input Multicast 
        counter inv. :This OID indicates 
        that the past 24-hours Multicast 
        counter is invalid
        "
	::= { pmc1008mpPerfDatacomClientPast24StatHistoryPort1Entry 10 }


pmc1008mpperfdatacomclientPast24StatInMulticastCountPort1 OBJECT-TYPE
	SYNTAX  Counter64
	MAX-ACCESS read-only
	STATUS current
	DESCRIPTION
        "
        Client Past 24-hours Input Multicast 
        counter :This OID gives the past 
        24-hours Multicast counter value
        "
	::= { pmc1008mpPerfDatacomClientPast24StatHistoryPort1Entry 11 }


pmc1008mpperfdatacomclientPast24StatInBroadcastCountInvPort1 OBJECT-TYPE
	SYNTAX  EkiOnOff
	MAX-ACCESS read-only
	STATUS current
	DESCRIPTION
        "
        Client Past 24-hours Input Broadcast 
        counter inv. :This OID indicates 
        that the past 24-hours Broadcast 
        counter is invalid
        "
	::= { pmc1008mpPerfDatacomClientPast24StatHistoryPort1Entry 8 }


pmc1008mpperfdatacomclientPast24StatInBroadcastCountPort1 OBJECT-TYPE
	SYNTAX  Counter64
	MAX-ACCESS read-only
	STATUS current
	DESCRIPTION
        "
        Client Past 24-hours Input Broadcast 
        counter :This OID gives the past 
        24-hours Broadcast counter value
        "
	::= { pmc1008mpPerfDatacomClientPast24StatHistoryPort1Entry 9 }


pmc1008mpperfdatacomclientPast24StatInCrcCountInvPort1 OBJECT-TYPE
	SYNTAX  EkiOnOff
	MAX-ACCESS read-only
	STATUS current
	DESCRIPTION
        "
        Client Past 24-hours Input CRC 
        counter inv. :This OID indicates 
        that the past 24-hours CRC counter 
        is invalid
        "
	::= { pmc1008mpPerfDatacomClientPast24StatHistoryPort1Entry 4 }


pmc1008mpperfdatacomclientPast24StatInCrcCountPort1 OBJECT-TYPE
	SYNTAX  Counter64
	MAX-ACCESS read-only
	STATUS current
	DESCRIPTION
        "
        Client Past 24-hours Input CRC 
        counter :This OID gives the past 
        24-hours CRC counter value
        "
	::= { pmc1008mpPerfDatacomClientPast24StatHistoryPort1Entry 5 }


pmc1008mpperfdatacomclientPast24StatInBytesCountInvPort1 OBJECT-TYPE
	SYNTAX  EkiOnOff
	MAX-ACCESS read-only
	STATUS current
	DESCRIPTION
        "
        Client Past 24-hours Input Bytes 
        counter inv. :This OID indicates 
        that the past 24-hours Bytes counter 
        is invalid
        "
	::= { pmc1008mpPerfDatacomClientPast24StatHistoryPort1Entry 2 }


pmc1008mpperfdatacomclientPast24StatInBytesCountPort1 OBJECT-TYPE
	SYNTAX  Counter64
	MAX-ACCESS read-only
	STATUS current
	DESCRIPTION
        "
        Client Past 24-hours Input Bytes 
        counter :This OID gives the past 
        24-hours Bytes counter value
        "
	::= { pmc1008mpPerfDatacomClientPast24StatHistoryPort1Entry 3 }



pmc1008mpPerfEnable OBJECT-TYPE
	SYNTAX EkiOnOff
	MAX-ACCESS read-write
	STATUS current
	DESCRIPTION
        "
        Perf. Mon. Enable :This OID enables 
        the Performance Monitoring application
        "
	::= { pmc1008mpMonSync 257 }


pmc1008mpPerf15minSync OBJECT-TYPE
	SYNTAX EkiOnOff
	MAX-ACCESS read-write
	STATUS current
	DESCRIPTION
        "
        Perf. Mon. 15-min sync. :This
         OID must be used in external synchronisation 
        mode only to send a 15-min synchronisation 
        command
        "
	::= { pmc1008mpMonSync 259 }


pmc1008mpPerf24hSync OBJECT-TYPE
	SYNTAX EkiOnOff
	MAX-ACCESS read-write
	STATUS current
	DESCRIPTION
        "
        Perf. Mon. 24-hours sync. :This 
        OID must be used in external synchronisation 
        mode only to send a 24-hours synchronisation 
        command
        "
	::= { pmc1008mpMonSync 260 }


pmc1008mpPerf15MinShort OBJECT-TYPE
	SYNTAX EkiOnOff
	MAX-ACCESS read-write
	STATUS current
	DESCRIPTION
        "
        15-min period is short :This OID 
        indicates that the 15-min period 
        lasts less than 890 seconds
        "
	::= { pmc1008mpMonTimeStamp 1 }


pmc1008mpPerf15MinLong OBJECT-TYPE
	SYNTAX EkiOnOff
	MAX-ACCESS read-write
	STATUS current
	DESCRIPTION
        "
        15-min period is long :This OID 
        indicates that the 15-min period 
        lasts more than 910 seconds
        "
	::= { pmc1008mpMonTimeStamp 2 }


pmc1008mpPerf24HoursShort OBJECT-TYPE
	SYNTAX Counter32
	MAX-ACCESS read-write
	STATUS current
	DESCRIPTION
        "
        24-hours period is short :This 
        OID indicates that 24-hours period 
        lasts less than 86390 seconds
        "
	::= { pmc1008mpMonTimeStamp 5 }


pmc1008mpPerf24HoursLong OBJECT-TYPE
	SYNTAX Counter32
	MAX-ACCESS read-write
	STATUS current
	DESCRIPTION
        "
        24-hours period is long :This
         OID indicates that 24-hours period 
        lasts more than 86410 seconds
        "
	::= { pmc1008mpMonTimeStamp 6 }


pmc1008mpPerfCurrent15MinElapsedTime OBJECT-TYPE
	SYNTAX Counter32
	MAX-ACCESS read-write
	STATUS current
	DESCRIPTION
        "
        Current 15min period Elapsed Time 
         :This OID gives the number of
         seconds elapsed in the current 
        15-minutes period
        "
	::= { pmc1008mpMonTimeStamp 7 }


pmc1008mpPerfCurrent24HoursElapsedTime OBJECT-TYPE
	SYNTAX Counter32
	MAX-ACCESS read-write
	STATUS current
	DESCRIPTION
        "
        Current 24hours period Elapsed 
        Time :This OID gives the number 
        of seconds elapsed in the current 
        24-hours period
        "
	::= { pmc1008mpMonTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pmc1008mpDwlrestartProcess OBJECT IDENTIFIER ::= { pmc1008mpDwlOther 0 }




pmc1008mpDwlColdRestartProcessed OBJECT-TYPE
	  SYNTAX EkiOnOff
	  MAX-ACCESS read-only
	  STATUS current
	  DESCRIPTION
        "
        Cold Restart :This OID indicates 
        that the module last restart was 
        a Cold RESTART
        "
	  ::= { pmc1008mpDwlrestartProcess 2 }



pmc1008mpDwlWarmRestartProcessed OBJECT-TYPE
	  SYNTAX EkiOnOff
	  MAX-ACCESS read-only
	  STATUS current
	  DESCRIPTION
        "
        Warm Restart :This OID indicates 
        that the module last restart was 
        a Warm RESTART
        "
	  ::= { pmc1008mpDwlrestartProcess 1 }



--- *****************************************************
---     LEAF for the swBanksUsed article
--- *****************************************************
pmc1008mpDwlswBanksUsed OBJECT IDENTIFIER ::= { pmc1008mpDwlOther 1 }




pmc1008mpDwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pmc1008mpDwlswBanksUsed 6 }



pmc1008mpDwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pmc1008mpDwlswBanksUsed 5 }



pmc1008mpDwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pmc1008mpDwlswBanksUsed 2 }



pmc1008mpDwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pmc1008mpDwlswBanksUsed 1 }



--- *****************************************************
---     LEAF for the gwBanksUsed article
--- *****************************************************
pmc1008mpDwlgwBanksUsed OBJECT IDENTIFIER ::= { pmc1008mpDwlOther 2 }




pmc1008mpDwlGwBank4Notempty OBJECT-TYPE
	  SYNTAX EkiOnOff
	  MAX-ACCESS read-only
	  STATUS current
	  DESCRIPTION
        "
        GW bank 4 loaded :This OID indicates 
        a gateware is loaded in GW bank 
        4
        "
	  ::= { pmc1008mpDwlgwBanksUsed 8 }



pmc1008mpDwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pmc1008mpDwlgwBanksUsed 7 }



pmc1008mpDwlGwBank2Notempty OBJECT-TYPE
	  SYNTAX EkiOnOff
	  MAX-ACCESS read-only
	  STATUS current
	  DESCRIPTION
        "
        GW bank 2 loaded :This OID indicates 
        a gateware is loaded in GW bank 
        2
        "
	  ::= { pmc1008mpDwlgwBanksUsed 6 }



pmc1008mpDwlGwBank1Notempty OBJECT-TYPE
	  SYNTAX EkiOnOff
	  MAX-ACCESS read-only
	  STATUS current
	  DESCRIPTION
        "
        GW bank 1 loaded  :This OID indicates 
        a gateware is loaded in GW bank 
        1  <Help>  This status indicates 
        if the GW bank 1 contains GW package
        "
	  ::= { pmc1008mpDwlgwBanksUsed 5 }



pmc1008mpDwlGwBank4Used OBJECT-TYPE
	  SYNTAX EkiOnOff
	  MAX-ACCESS read-only
	  STATUS current
	  DESCRIPTION
        "
        GW bank 4 active  :This OID indicates 
        the module is working on GW bank 
        4
        "
	  ::= { pmc1008mpDwlgwBanksUsed 4 }



pmc1008mpDwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pmc1008mpDwlgwBanksUsed 3 }



pmc1008mpDwlGwBank2Used OBJECT-TYPE
	  SYNTAX EkiOnOff
	  MAX-ACCESS read-only
	  STATUS current
	  DESCRIPTION
        "
        GW bank 2 active :This OID indicates 
        the module is working on GW bank 
        2
        "
	  ::= { pmc1008mpDwlgwBanksUsed 2 }



pmc1008mpDwlGwBank1Used OBJECT-TYPE
	  SYNTAX EkiOnOff
	  MAX-ACCESS read-only
	  STATUS current
	  DESCRIPTION
        "
        GW bank 1 active  :This OID indicates 
        the module is working on GW bank 
        1  <Help>  This status indicates 
        if the GW bank 1 is active or standby
        "
	  ::= { pmc1008mpDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pmc1008mpCfgAccessCAisCsf OBJECT IDENTIFIER ::= { pmc1008mpConfig 1 }



--- *****************************************************
---     LEAF for the table 0012
--- *****************************************************

pmc1008mpCfgClientcaiscsfTable OBJECT-TYPE
	SYNTAX  SEQUENCE OF Pmc1008mpCfgClientcaiscsfEntry
	MAX-ACCESS not-accessible
	STATUS current
	DESCRIPTION
        "
        List of  Article
        "
	::= { pmc1008mpCfgAccessCAisCsf 1 }


pmc1008mpCfgClientcaiscsfEntry OBJECT-TYPE
	SYNTAX Pmc1008mpCfgClientcaiscsfEntry
	MAX-ACCESS not-accessible
	STATUS current
	DESCRIPTION
        "
        Row definition for the accessCAisCsf 
        table
        "
	INDEX   { pmc1008mpCfgClientcaiscsfIndex }
	::= { pmc1008mpCfgClientcaiscsfTable 1 }


Pmc1008mpCfgClientcaiscsfEntry ::=
	SEQUENCE {
	pmc1008mpCfgClientcaiscsfIndex
		INTEGER,
	pmc1008mpCfgCAisModePortn
		Unsigned32,
	pmc1008mpCfgUpAccessioAlmPortn
		Unsigned32,
	pmc1008mpCfgUpMapperDeAlmPortn
		Unsigned32,
	pmc1008mpCfgDownAccessioAlmPortn
		Unsigned32,
	pmc1008mpCfgDownMapperDeAlmPortn
		Unsigned32,
	pmc1008mpCfgDownDfrmAlmPortn
		Unsigned32,
	pmc1008mpCfgDownLineSyncAlarmsPortn
		Unsigned32
	}


pmc1008mpCfgClientcaiscsfIndex OBJECT-TYPE
	SYNTAX  INTEGER(0..128)
	MAX-ACCESS  read-only
	STATUS current
	DESCRIPTION
        "
        Index definition for the clientcaiscsf 
        table
        "
	::= { pmc1008mpCfgClientcaiscsfEntry 1 }


pmc1008mpCfgCAisModePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pmc1008mpCfgClientcaiscsfEntry 3 }


pmc1008mpCfgUpAccessioAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pmc1008mpCfgClientcaiscsfEntry 9 }


pmc1008mpCfgUpMapperDeAlmPortn OBJECT-TYPE
	SYNTAX  Unsigned32 (0..65536)
	MAX-ACCESS read-write
	STATUS current
	DESCRIPTION
        "
        CSF contributors on Client Port 
        :This register configures the contributors 
        to upstream CSF insertion on the 
        port.
        "
	::= { pmc1008mpCfgClientcaiscsfEntry 10 }


pmc1008mpCfgDownAccessioAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pmc1008mpCfgClientcaiscsfEntry 17 }


pmc1008mpCfgDownMapperDeAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pmc1008mpCfgClientcaiscsfEntry 18 }


pmc1008mpCfgDownDfrmAlmPortn OBJECT-TYPE
	SYNTAX  Unsigned32 (0..65536)
	MAX-ACCESS read-write
	STATUS current
	DESCRIPTION
        "
        CAIS contributors on Client Port 
        :This register configures the contributors 
        to downstream CAIS insertion on 
         port.
        "
	::= { pmc1008mpCfgClientcaiscsfEntry 19 }


pmc1008mpCfgDownLineSyncAlarmsPortn OBJECT-TYPE
	SYNTAX  Unsigned32 (0..65536)
	MAX-ACCESS read-write
	STATUS deprecated
	DESCRIPTION
        "
        CAIS contributors on Client Port 
        :This register configures the contributors 
        to downstream CAIS insertion on 
         port.
        "
	::= { pmc1008mpCfgClientcaiscsfEntry 20 }


--- *****************************************************
---     LEAF for the table Group startup
--- *****************************************************

pmc1008mpCfgStartup OBJECT IDENTIFIER ::= { pmc1008mpConfig 2 }



--- *****************************************************
---     LEAF for the table 2111
--- *****************************************************

pmc1008mpCfgClientStartupTable OBJECT-TYPE
	SYNTAX  SEQUENCE OF Pmc1008mpCfgClientStartupEntry
	MAX-ACCESS not-accessible
	STATUS current
	DESCRIPTION
        "
        List of  Article
        "
	::= { pmc1008mpCfgStartup 1 }


pmc1008mpCfgClientStartupEntry OBJECT-TYPE
	SYNTAX Pmc1008mpCfgClientStartupEntry
	MAX-ACCESS not-accessible
	STATUS current
	DESCRIPTION
        "
        Row definition for the startup 
        table
        "
	INDEX   { pmc1008mpCfgClientStartupIndex }
	::= { pmc1008mpCfgClientStartupTable 1 }


Pmc1008mpCfgClientStartupEntry ::=
	SEQUENCE {
	pmc1008mpCfgClientStartupIndex
		INTEGER,
	pmc1008mpCfgSystConfPortPortn
		Unsigned32,
	pmc1008mpCfgNetConfPortPortn
		Unsigned32,
	pmc1008mpCfgAdddropConfPortPortn
		Unsigned32
	}


pmc1008mpCfgClientStartupIndex OBJECT-TYPE
	SYNTAX  INTEGER(0..128)
	MAX-ACCESS  read-only
	STATUS current
	DESCRIPTION
        "
        Index definition for the clientStartup 
        table
        "
	::= { pmc1008mpCfgClientStartupEntry 1 }


pmc1008mpCfgSystConfPortPortn OBJECT-TYPE
	SYNTAX  Unsigned32 (0..65536)
	MAX-ACCESS read-write
	STATUS current
	DESCRIPTION
        "
        Default Settings on Client Port 
        :This  register configures the
         default initialisation settings 
        on the port.
        "
	::= { pmc1008mpCfgClientStartupEntry 3 }


pmc1008mpCfgNetConfPortPortn OBJECT-TYPE
	SYNTAX  Unsigned32 (0..65536)
	MAX-ACCESS read-write
	STATUS current
	DESCRIPTION
        "
        Default Protocol on Client Port 
        :This register configures the default 
        initialisation protocol on the
         port.
        "
	::= { pmc1008mpCfgClientStartupEntry 4 }


pmc1008mpCfgAdddropConfPortPortn OBJECT-TYPE
	SYNTAX  Unsigned32 (0..65536)
	MAX-ACCESS read-write
	STATUS deprecated
	DESCRIPTION
        "
        Default Add&Drop mode on Client 
        Port :This register configures
         the default Add&Drop mode on the 
        port.
        "
	::= { pmc1008mpCfgClientStartupEntry 5 }


--- *****************************************************
---     LEAF for the table 2191
--- *****************************************************

pmc1008mptablelineStartup OBJECT IDENTIFIER ::= { pmc1008mpCfgStartup 2 }



pmc1008mpCfgsystConfLine1 OBJECT-TYPE
	  SYNTAX Unsigned32 (0..65536)
	  MAX-ACCESS read-write
	  STATUS current
	  DESCRIPTION
        "
        Default Settings on Line 1 :This 
        register configures the default 
        initialisation settings on Line 
        port 1.
        "
	  ::= { pmc1008mptablelineStartup 2 }



pmc1008mpCfglineOptions1 OBJECT-TYPE
	  SYNTAX Unsigned32 (0..65536)
	  MAX-ACCESS read-write
	  STATUS current
	  DESCRIPTION
        "
        Default Options on Active Line 
        Port :This register configures
         the default options on the active 
        line port
        "
	  ::= { pmc1008mptablelineStartup 5 }



pmc1008mpCfgsystConfLine2 OBJECT-TYPE
	  SYNTAX Unsigned32 (0..65536)
	  MAX-ACCESS read-write
	  STATUS current
	  DESCRIPTION
        "
        Default Settings on Line 2 :This 
        register configures the default 
        initialisation settings on Line 
        port 2.
        "
	  ::= { pmc1008mptablelineStartup 6 }



pmc1008mpCfglineSelection OBJECT-TYPE
	  SYNTAX Unsigned32 (0..65536)
	  MAX-ACCESS read-write
	  STATUS current
	  DESCRIPTION
        "
        Default Settings of active line 
        :This  register configures the
         start up active line.
        "
	  ::= { pmc1008mptablelineStartup 7 }



pmc1008mpCfglineOptions2 OBJECT-TYPE
	  SYNTAX Unsigned32 (0..65536)
	  MAX-ACCESS read-write
	  STATUS deprecated
	  DESCRIPTION
        "
        Default Options on Active Line 
        Port :This register configures
         the default options on the active 
        line port
        "
	  ::= { pmc1008mptablelineStartup 9 }



--- *****************************************************
---     LEAF for the table 21AB
--- *****************************************************

pmc1008mpCfgXfpTable OBJECT-TYPE
	SYNTAX  SEQUENCE OF Pmc1008mpCfgXfpEntry
	MAX-ACCESS not-accessible
	STATUS current
	DESCRIPTION
        "
        List of  Article
        "
	::= { pmc1008mpCfgStartup 3 }


pmc1008mpCfgXfpEntry OBJECT-TYPE
	SYNTAX Pmc1008mpCfgXfpEntry
	MAX-ACCESS not-accessible
	STATUS current
	DESCRIPTION
        "
        Row definition for the startup 
        table
        "
	INDEX   { pmc1008mpCfgXfpIndex }
	::= { pmc1008mpCfgXfpTable 1 }


Pmc1008mpCfgXfpEntry ::=
	SEQUENCE {
	pmc1008mpCfgXfpIndex
		INTEGER,
	pmc1008mpCfgSystConfXfpPortn
		Unsigned32,
	pmc1008mpCfgDataRateConfXfpPortn
		Unsigned32
	}


pmc1008mpCfgXfpIndex OBJECT-TYPE
	SYNTAX  INTEGER(0..128)
	MAX-ACCESS  read-only
	STATUS current
	DESCRIPTION
        "
        Index definition for the xfp table
        "
	::= { pmc1008mpCfgXfpEntry 1 }


pmc1008mpCfgSystConfXfpPortn OBJECT-TYPE
	SYNTAX  Unsigned32 (0..65536)
	MAX-ACCESS read-write
	STATUS current
	DESCRIPTION
        "
        Default settings on XFP Port :This 
        register configures the default 
        initialisation settings on XFP
         port.
        "
	::= { pmc1008mpCfgXfpEntry 3 }


pmc1008mpCfgDataRateConfXfpPortn OBJECT-TYPE
	SYNTAX  Unsigned32 (0..65536)
	MAX-ACCESS read-write
	STATUS deprecated
	DESCRIPTION
        "
        :
        "
	::= { pmc1008mpCfgXfpEntry 4 }


--- *****************************************************
---     LEAF for the table 25A8
--- *****************************************************

pmc1008mpCfgOtxtlhTable OBJECT-TYPE
	SYNTAX  SEQUENCE OF Pmc1008mpCfgOtxtlhEntry
	MAX-ACCESS not-accessible
	STATUS current
	DESCRIPTION
        "
        List of  Article
        "
	::= { pmc1008mpCfgStartup 4 }


pmc1008mpCfgOtxtlhEntry OBJECT-TYPE
	SYNTAX Pmc1008mpCfgOtxtlhEntry
	MAX-ACCESS not-accessible
	STATUS current
	DESCRIPTION
        "
        Row definition for the startup 
        table
        "
	INDEX   { pmc1008mpCfgOtxtlhIndex }
	::= { pmc1008mpCfgOtxtlhTable 1 }


Pmc1008mpCfgOtxtlhEntry ::=
	SEQUENCE {
	pmc1008mpCfgOtxtlhIndex
		INTEGER,
	pmc1008mpCfgLineOtxMiscPortn
		Unsigned32,
	pmc1008mpCfgLineDitherRatePortn
		Unsigned32,
	pmc1008mpCfgLineDitherFhzPortn
		Unsigned32,
	pmc1008mpCfgLinePwrLaserPortn
		Unsigned32,
	pmc1008mpCfgLineFCurrentPortn
		Unsigned32,
	pmc1008mpCfgLineGridCurrentPortn
		Unsigned32,
	pmc1008mpCfgFPortn
		Unsigned32,
	pmc1008mpCfgReservedPortn
		Unsigned32,
	pmc1008mpCfgLinePhotodiodeModePortn
		Unsigned32,
	pmc1008mpCfgLinePhotodiodeValuePortn
		Unsigned32
	}


pmc1008mpCfgOtxtlhIndex OBJECT-TYPE
	SYNTAX  INTEGER(0..128)
	MAX-ACCESS  read-only
	STATUS current
	DESCRIPTION
        "
        Index definition for the otxtlh 
        table
        "
	::= { pmc1008mpCfgOtxtlhEntry 1 }


pmc1008mpCfgLineOtxMiscPortn OBJECT-TYPE
	SYNTAX  Unsigned32 (0..65536)
	MAX-ACCESS read-write
	STATUS current
	DESCRIPTION
        "
        Default Line OTX TLH miscellaneous 
        :This register configures the start-up 
        miscellaneous mode of the Line
         OTX TLH
        "
	::= { pmc1008mpCfgOtxtlhEntry 3 }


pmc1008mpCfgLineDitherRatePortn OBJECT-TYPE
	SYNTAX  Unsigned32 (0..65536)
	MAX-ACCESS read-write
	STATUS current
	DESCRIPTION
        "
        Default Line OTX TLH FM amplitude 
        :This register configures the start-up 
        width of the frequency modulation 
        of the Line OTX TLH
        "
	::= { pmc1008mpCfgOtxtlhEntry 4 }


pmc1008mpCfgLineDitherFhzPortn OBJECT-TYPE
	SYNTAX  Unsigned32 (0..65536)
	MAX-ACCESS read-write
	STATUS current
	DESCRIPTION
        "
        Default Line OTX TLH FM frequency 
        :This register configures the start-up 
        frequency of the frequency modulation 
        of the Line OTX TLH
        "
	::= { pmc1008mpCfgOtxtlhEntry 5 }


pmc1008mpCfgLinePwrLaserPortn OBJECT-TYPE
	SYNTAX  Unsigned32 (0..65536)
	MAX-ACCESS read-write
	STATUS current
	DESCRIPTION
        "
        Defaut Line OTX TLH output Power 
        :This register configures the start-up 
        output power of the Line OTX TLH 
         (Unit = dBm)
        "
	::= { pmc1008mpCfgOtxtlhEntry 6 }


pmc1008mpCfgLineFCurrentPortn OBJECT-TYPE
	SYNTAX  Unsigned32 (0..65536)
	MAX-ACCESS read-write
	STATUS current
	DESCRIPTION
        "
        Default Line OTX TLH Channel :This 
        register configures the start-up 
        laser channel of the Line OTX TLH
        "
	::= { pmc1008mpCfgOtxtlhEntry 7 }


pmc1008mpCfgLineGridCurrentPortn OBJECT-TYPE
	SYNTAX  Unsigned32 (0..65536)
	MAX-ACCESS read-write
	STATUS current
	DESCRIPTION
        "
        Default Line OTX TLH Grid :This 
        register configures the start-up 
        laser grid of the Line OTX TLH
        "
	::= { pmc1008mpCfgOtxtlhEntry 8 }


pmc1008mpCfgFPortn OBJECT-TYPE
	SYNTAX  Unsigned32 (0..65536)
	MAX-ACCESS read-write
	STATUS current
	DESCRIPTION
        "
        Default Line OTX TLH lowest Freq 
        :This register configures the start-up 
        lowest frequency supported on the 
        Line OTX TLH
        "
	::= { pmc1008mpCfgOtxtlhEntry 9 }


pmc1008mpCfgReservedPortn OBJECT-TYPE
	SYNTAX  Unsigned32 (0..65536)
	MAX-ACCESS read-write
	STATUS deprecated
	DESCRIPTION
        "
        :
        "
	::= { pmc1008mpCfgOtxtlhEntry 10 }


pmc1008mpCfgLinePhotodiodeModePortn OBJECT-TYPE
	SYNTAX  Unsigned32 (0..65536)
	MAX-ACCESS read-write
	STATUS current
	DESCRIPTION
        "
        Default Line OTX TLH APD mode
         :This register configures the
         start-up APD mode of the Line
         OTX TLH
        "
	::= { pmc1008mpCfgOtxtlhEntry 11 }


pmc1008mpCfgLinePhotodiodeValuePortn OBJECT-TYPE
	SYNTAX  Unsigned32 (0..65536)
	MAX-ACCESS read-write
	STATUS current
	DESCRIPTION
        "
        Default Line OTX TLH APD atten. 
        :This register configures the start-up 
        APD attenuation on the Line OTX 
        TLH
        "
	::= { pmc1008mpCfgOtxtlhEntry 12 }


--- *****************************************************
---     LEAF for the table Group other
--- *****************************************************

pmc1008mpCfgOther OBJECT IDENTIFIER ::= { pmc1008mpConfig 3 }



--- *****************************************************
---     LEAF for the table 2300
--- *****************************************************

pmc1008mptablemoduleOther OBJECT IDENTIFIER ::= { pmc1008mpCfgOther 1 }



pmc1008mpCfgmode OBJECT-TYPE
	  SYNTAX Unsigned32 (0..65536)
	  MAX-ACCESS read-write
	  STATUS current
	  DESCRIPTION
        "
        Default settings on Module :This 
        register selects the DCC  configuration 
        of the PM
        "
	  ::= { pmc1008mptablemoduleOther 2 }



--- *****************************************************
---     LEAF for the table Group labels
--- *****************************************************

pmc1008mpCfgLabels OBJECT IDENTIFIER ::= { pmc1008mpConfig 4 }



--- *****************************************************
---     LEAF for the table NO_VALUE
--- *****************************************************

pmc1008mpCfgLabelclientTable OBJECT-TYPE
	SYNTAX  SEQUENCE OF Pmc1008mpCfgLabelclientEntry
	MAX-ACCESS not-accessible
	STATUS current
	DESCRIPTION
        "
        List of  Article
        "
	::= { pmc1008mpCfgLabels 1 }


pmc1008mpCfgLabelclientEntry OBJECT-TYPE
	SYNTAX Pmc1008mpCfgLabelclientEntry
	MAX-ACCESS not-accessible
	STATUS current
	DESCRIPTION
        "
        Row definition for the labels
         table
        "
	INDEX   { pmc1008mpCfgLabelclientIndex }
	::= { pmc1008mpCfgLabelclientTable 1 }


Pmc1008mpCfgLabelclientEntry ::=
	SEQUENCE {
	pmc1008mpCfgLabelclientIndex
		INTEGER,
	pmc1008mpCfgLabelclientPortn
		DisplayString
	}


pmc1008mpCfgLabelclientIndex OBJECT-TYPE
	SYNTAX  INTEGER(0..128)
	MAX-ACCESS  read-only
	STATUS current
	DESCRIPTION
        "
        Index definition for the labelclient 
        table
        "
	::= { pmc1008mpCfgLabelclientEntry 1 }


pmc1008mpCfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pmc1008mpCfgLabelclientEntry 3 }


--- *****************************************************
---     LEAF for the table NO_VALUE
--- *****************************************************

pmc1008mpCfgLabellineTable OBJECT-TYPE
	SYNTAX  SEQUENCE OF Pmc1008mpCfgLabellineEntry
	MAX-ACCESS not-accessible
	STATUS current
	DESCRIPTION
        "
        List of  Article
        "
	::= { pmc1008mpCfgLabels 2 }


pmc1008mpCfgLabellineEntry OBJECT-TYPE
	SYNTAX Pmc1008mpCfgLabellineEntry
	MAX-ACCESS not-accessible
	STATUS current
	DESCRIPTION
        "
        Row definition for the labels
         table
        "
	INDEX   { pmc1008mpCfgLabellineIndex }
	::= { pmc1008mpCfgLabellineTable 1 }


Pmc1008mpCfgLabellineEntry ::=
	SEQUENCE {
	pmc1008mpCfgLabellineIndex
		INTEGER,
	pmc1008mpCfgLabellinePortn
		DisplayString
	}


pmc1008mpCfgLabellineIndex OBJECT-TYPE
	SYNTAX  INTEGER(0..128)
	MAX-ACCESS  read-only
	STATUS current
	DESCRIPTION
        "
        Index definition for the labelline 
        table
        "
	::= { pmc1008mpCfgLabellineEntry 1 }


pmc1008mpCfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pmc1008mpCfgLabellineEntry 3 }


--- *****************************************************
---     LEAF for the table Group startuptimeslotsline1
--- *****************************************************

pmc1008mpCfgStartuptimeslotsline1 OBJECT IDENTIFIER ::= { pmc1008mpConfig 5 }



--- *****************************************************
---     LEAF for the table 2910
--- *****************************************************

pmc1008mpCfgTimeslotsportsline1Table OBJECT-TYPE
	SYNTAX  SEQUENCE OF Pmc1008mpCfgTimeslotsportsline1Entry
	MAX-ACCESS not-accessible
	STATUS current
	DESCRIPTION
        "
        List of  Article
        "
	::= { pmc1008mpCfgStartuptimeslotsline1 1 }


pmc1008mpCfgTimeslotsportsline1Entry OBJECT-TYPE
	SYNTAX Pmc1008mpCfgTimeslotsportsline1Entry
	MAX-ACCESS not-accessible
	STATUS current
	DESCRIPTION
        "
        Row definition for the startuptimeslotsline1 
        table
        "
	INDEX   { pmc1008mpCfgTimeslotsportsline1Index }
	::= { pmc1008mpCfgTimeslotsportsline1Table 1 }


Pmc1008mpCfgTimeslotsportsline1Entry ::=
	SEQUENCE {
	pmc1008mpCfgTimeslotsportsline1Index
		INTEGER,
	pmc1008mpCfgLine1Timeslotb2PortPortn
		Unsigned32,
	pmc1008mpCfgLine1Timeslotb1PortPortn
		Unsigned32,
	pmc1008mpCfgLine1ProtocolPortPortn
		Unsigned32
	}


pmc1008mpCfgTimeslotsportsline1Index OBJECT-TYPE
	SYNTAX  INTEGER(0..128)
	MAX-ACCESS  read-only
	STATUS current
	DESCRIPTION
        "
        Index definition for the timeslotsportsline1 
        table
        "
	::= { pmc1008mpCfgTimeslotsportsline1Entry 1 }


pmc1008mpCfgLine1Timeslotb2PortPortn OBJECT-TYPE
	SYNTAX  Unsigned32 (0..65536)
	MAX-ACCESS read-write
	STATUS current
	DESCRIPTION
        "
        Port Defaut Time Slot allocation 
        (MSB) on Line1 :This register configures 
        the start-up timeslots allocation 
        on the port (MSB)
        "
	::= { pmc1008mpCfgTimeslotsportsline1Entry 3 }


pmc1008mpCfgLine1Timeslotb1PortPortn OBJECT-TYPE
	SYNTAX  Unsigned32 (0..65536)
	MAX-ACCESS read-write
	STATUS current
	DESCRIPTION
        "
        Port Defaut Time Slot allocation 
        (LSB) on Line1 :This register configures 
        the start-up timeslots allocation 
        on the port (LSB)
        "
	::= { pmc1008mpCfgTimeslotsportsline1Entry 4 }


pmc1008mpCfgLine1ProtocolPortPortn OBJECT-TYPE
	SYNTAX  Unsigned32 (0..65536)
	MAX-ACCESS read-write
	STATUS current
	DESCRIPTION
        "
        Port Defaut Protocol on Line1
         :This register configures the
         start-up protocol on the port
        "
	::= { pmc1008mpCfgTimeslotsportsline1Entry 5 }


--- *****************************************************
---     LEAF for the table Group startuptimeslotsline2
--- *****************************************************

pmc1008mpCfgStartuptimeslotsline2 OBJECT IDENTIFIER ::= { pmc1008mpConfig 6 }



--- *****************************************************
---     LEAF for the table 2910
--- *****************************************************

pmc1008mpCfgTimeslotsportsline2Table OBJECT-TYPE
	SYNTAX  SEQUENCE OF Pmc1008mpCfgTimeslotsportsline2Entry
	MAX-ACCESS not-accessible
	STATUS current
	DESCRIPTION
        "
        List of  Article
        "
	::= { pmc1008mpCfgStartuptimeslotsline2 1 }


pmc1008mpCfgTimeslotsportsline2Entry OBJECT-TYPE
	SYNTAX Pmc1008mpCfgTimeslotsportsline2Entry
	MAX-ACCESS not-accessible
	STATUS current
	DESCRIPTION
        "
        Row definition for the startuptimeslotsline2 
        table
        "
	INDEX   { pmc1008mpCfgTimeslotsportsline2Index }
	::= { pmc1008mpCfgTimeslotsportsline2Table 1 }


Pmc1008mpCfgTimeslotsportsline2Entry ::=
	SEQUENCE {
	pmc1008mpCfgTimeslotsportsline2Index
		INTEGER,
	pmc1008mpCfgLine2Timeslotb2PortPortn
		Unsigned32,
	pmc1008mpCfgLine2Timeslotb1PortPortn
		Unsigned32,
	pmc1008mpCfgLine2ProtocolPortPortn
		Unsigned32
	}


pmc1008mpCfgTimeslotsportsline2Index OBJECT-TYPE
	SYNTAX  INTEGER(0..128)
	MAX-ACCESS  read-only
	STATUS current
	DESCRIPTION
        "
        Index definition for the timeslotsportsline2 
        table
        "
	::= { pmc1008mpCfgTimeslotsportsline2Entry 1 }


pmc1008mpCfgLine2Timeslotb2PortPortn OBJECT-TYPE
	SYNTAX  Unsigned32 (0..65536)
	MAX-ACCESS read-write
	STATUS current
	DESCRIPTION
        "
        Port Defaut Time Slot allocation 
        (MSB) on Line2 :This register configures 
        the start-up timeslots allocation 
        on the port (MSB)
        "
	::= { pmc1008mpCfgTimeslotsportsline2Entry 3 }


pmc1008mpCfgLine2Timeslotb1PortPortn OBJECT-TYPE
	SYNTAX  Unsigned32 (0..65536)
	MAX-ACCESS read-write
	STATUS current
	DESCRIPTION
        "
        Port Defaut Time Slot allocation 
        (LSB) on Line2 :This register configures 
        the start-up timeslots allocation 
        on the port (LSB)
        "
	::= { pmc1008mpCfgTimeslotsportsline2Entry 4 }


pmc1008mpCfgLine2ProtocolPortPortn OBJECT-TYPE
	SYNTAX  Unsigned32 (0..65536)
	MAX-ACCESS read-write
	STATUS current
	DESCRIPTION
        "
        Port Defaut Protocol on Line2
         :This register configures the
         start-up protocol on the port
        "
	::= { pmc1008mpCfgTimeslotsportsline2Entry 5 }


--- *****************************************************
---     LEAF for the table Group startuptimeslotspassthroughline1
--- *****************************************************

pmc1008mpCfgStartuptimeslotspassthroughline1 OBJECT IDENTIFIER ::= { pmc1008mpConfig 7 }



--- *****************************************************
---     LEAF for the table 2910
--- *****************************************************

pmc1008mpCfgTimeslotspassthroughline1Table OBJECT-TYPE
	SYNTAX  SEQUENCE OF Pmc1008mpCfgTimeslotspassthroughline1Entry
	MAX-ACCESS not-accessible
	STATUS current
	DESCRIPTION
        "
        List of  Article
        "
	::= { pmc1008mpCfgStartuptimeslotspassthroughline1 1 }


pmc1008mpCfgTimeslotspassthroughline1Entry OBJECT-TYPE
	SYNTAX Pmc1008mpCfgTimeslotspassthroughline1Entry
	MAX-ACCESS not-accessible
	STATUS current
	DESCRIPTION
        "
        Row definition for the startuptimeslotspassthroughline1 
        table
        "
	INDEX   { pmc1008mpCfgTimeslotspassthroughline1Index }
	::= { pmc1008mpCfgTimeslotspassthroughline1Table 1 }


Pmc1008mpCfgTimeslotspassthroughline1Entry ::=
	SEQUENCE {
	pmc1008mpCfgTimeslotspassthroughline1Index
		INTEGER,
	pmc1008mpCfgLine1Timeslotb2PassthroughPortn
		Unsigned32,
	pmc1008mpCfgLine1Timeslotb1PassthroughPortn
		Unsigned32,
	pmc1008mpCfgLine1ProtocolPassthroughPortn
		Unsigned32
	}


pmc1008mpCfgTimeslotspassthroughline1Index OBJECT-TYPE
	SYNTAX  INTEGER(0..128)
	MAX-ACCESS  read-only
	STATUS current
	DESCRIPTION
        "
        Index definition for the timeslotspassthroughline1 
        table
        "
	::= { pmc1008mpCfgTimeslotspassthroughline1Entry 1 }


pmc1008mpCfgLine1Timeslotb2PassthroughPortn OBJECT-TYPE
	SYNTAX  Unsigned32 (0..65536)
	MAX-ACCESS read-write
	STATUS current
	DESCRIPTION
        "
        Port Defaut PassThrough Time Slot 
        allocation (MSB) on Line1 :This 
        register configures the start-up 
        timeslots allocation on the port 
        (MSB)
        "
	::= { pmc1008mpCfgTimeslotspassthroughline1Entry 3 }


pmc1008mpCfgLine1Timeslotb1PassthroughPortn OBJECT-TYPE
	SYNTAX  Unsigned32 (0..65536)
	MAX-ACCESS read-write
	STATUS current
	DESCRIPTION
        "
        Port Defaut PassThroughTime Slot 
        allocation (LSB) on Line1 :This 
        register configures the start-up 
        timeslots allocation on the port 
        (LSB)
        "
	::= { pmc1008mpCfgTimeslotspassthroughline1Entry 4 }


pmc1008mpCfgLine1ProtocolPassthroughPortn OBJECT-TYPE
	SYNTAX  Unsigned32 (0..65536)
	MAX-ACCESS read-write
	STATUS current
	DESCRIPTION
        "
        Port Defaut PassThrough Protocol 
        on Line1 :This register configures 
        the start-up protocol on the port
        "
	::= { pmc1008mpCfgTimeslotspassthroughline1Entry 5 }


--- *****************************************************
---     LEAF for the table Group startuptimeslotspassthroughline2
--- *****************************************************

pmc1008mpCfgStartuptimeslotspassthroughline2 OBJECT IDENTIFIER ::= { pmc1008mpConfig 8 }



--- *****************************************************
---     LEAF for the table 2910
--- *****************************************************

pmc1008mpCfgTimeslotspassthroughline2Table OBJECT-TYPE
	SYNTAX  SEQUENCE OF Pmc1008mpCfgTimeslotspassthroughline2Entry
	MAX-ACCESS not-accessible
	STATUS current
	DESCRIPTION
        "
        List of  Article
        "
	::= { pmc1008mpCfgStartuptimeslotspassthroughline2 1 }


pmc1008mpCfgTimeslotspassthroughline2Entry OBJECT-TYPE
	SYNTAX Pmc1008mpCfgTimeslotspassthroughline2Entry
	MAX-ACCESS not-accessible
	STATUS current
	DESCRIPTION
        "
        Row definition for the startuptimeslotspassthroughline2 
        table
        "
	INDEX   { pmc1008mpCfgTimeslotspassthroughline2Index }
	::= { pmc1008mpCfgTimeslotspassthroughline2Table 1 }


Pmc1008mpCfgTimeslotspassthroughline2Entry ::=
	SEQUENCE {
	pmc1008mpCfgTimeslotspassthroughline2Index
		INTEGER,
	pmc1008mpCfgLine2Timeslotb2PassthroughPortn
		Unsigned32,
	pmc1008mpCfgLine2Timeslotb1PassthroughPortn
		Unsigned32,
	pmc1008mpCfgLine2ProtocolPassthroughPortn
		Unsigned32
	}


pmc1008mpCfgTimeslotspassthroughline2Index OBJECT-TYPE
	SYNTAX  INTEGER(0..128)
	MAX-ACCESS  read-only
	STATUS current
	DESCRIPTION
        "
        Index definition for the timeslotspassthroughline2 
        table
        "
	::= { pmc1008mpCfgTimeslotspassthroughline2Entry 1 }


pmc1008mpCfgLine2Timeslotb2PassthroughPortn OBJECT-TYPE
	SYNTAX  Unsigned32 (0..65536)
	MAX-ACCESS read-write
	STATUS current
	DESCRIPTION
        "
        Port Defaut PassThrough Time Slot 
        allocation (MSB) on Line2 :This 
        register configures the start-up 
        timeslots allocation on the port 
        (MSB)
        "
	::= { pmc1008mpCfgTimeslotspassthroughline2Entry 3 }


pmc1008mpCfgLine2Timeslotb1PassthroughPortn OBJECT-TYPE
	SYNTAX  Unsigned32 (0..65536)
	MAX-ACCESS read-write
	STATUS current
	DESCRIPTION
        "
        Port Defaut PassThroughTime Slot 
        allocation (LSB) on Line2 :This 
        register configures the start-up 
        timeslots allocation on the port 
        (LSB)
        "
	::= { pmc1008mpCfgTimeslotspassthroughline2Entry 4 }


pmc1008mpCfgLine2ProtocolPassthroughPortn OBJECT-TYPE
	SYNTAX  Unsigned32 (0..65536)
	MAX-ACCESS read-write
	STATUS current
	DESCRIPTION
        "
        Port Defaut PassThrough Protocol 
        on Line2 :This register configures 
        the start-up protocol on the port
        "
	::= { pmc1008mpCfgTimeslotspassthroughline2Entry 5 }


--- *****************************************************
---     LEAF for the table Group startuptablefive
--- *****************************************************

pmc1008mpCfgStartuptablefive OBJECT IDENTIFIER ::= { pmc1008mpConfig 9 }



--- *****************************************************
---     LEAF for the table 0005
--- *****************************************************

pmc1008mpCfgOtxtlhcapabilitiesTable OBJECT-TYPE
	SYNTAX  SEQUENCE OF Pmc1008mpCfgOtxtlhcapabilitiesEntry
	MAX-ACCESS not-accessible
	STATUS current
	DESCRIPTION
        "
        List of  Article
        "
	::= { pmc1008mpCfgStartuptablefive 1 }


pmc1008mpCfgOtxtlhcapabilitiesEntry OBJECT-TYPE
	SYNTAX Pmc1008mpCfgOtxtlhcapabilitiesEntry
	MAX-ACCESS not-accessible
	STATUS current
	DESCRIPTION
        "
        Row definition for the startuptablefive 
        table
        "
	INDEX   { pmc1008mpCfgOtxtlhcapabilitiesIndex }
	::= { pmc1008mpCfgOtxtlhcapabilitiesTable 1 }


Pmc1008mpCfgOtxtlhcapabilitiesEntry ::=
	SEQUENCE {
	pmc1008mpCfgOtxtlhcapabilitiesIndex
		INTEGER,
	pmc1008mpCfgComponentTypePortn
		Unsigned32,
	pmc1008mpCfgMiscellaneousPortn
		Unsigned32,
	pmc1008mpCfgFirstChannelPortn
		Unsigned32,
	pmc1008mpCfgLastChannelPortn
		Unsigned32,
	pmc1008mpCfgGridPortn
		Unsigned32
	}


pmc1008mpCfgOtxtlhcapabilitiesIndex OBJECT-TYPE
	SYNTAX  INTEGER(0..128)
	MAX-ACCESS  read-only
	STATUS current
	DESCRIPTION
        "
        Index definition for the otxtlhcapabilities 
        table
        "
	::= { pmc1008mpCfgOtxtlhcapabilitiesEntry 1 }


pmc1008mpCfgComponentTypePortn OBJECT-TYPE
	SYNTAX  Unsigned32 (0..65536)
	MAX-ACCESS read-only
	STATUS current
	DESCRIPTION
        "
        Component parameters :This OID 
        defines the component parameters
        "
	::= { pmc1008mpCfgOtxtlhcapabilitiesEntry 3 }


pmc1008mpCfgMiscellaneousPortn OBJECT-TYPE
	SYNTAX  Unsigned32 (0..65536)
	MAX-ACCESS read-only
	STATUS current
	DESCRIPTION
        "
        Miscellaneous default settings 
        :This OID defines the miscellaneous 
        parameters
        "
	::= { pmc1008mpCfgOtxtlhcapabilitiesEntry 4 }


pmc1008mpCfgFirstChannelPortn OBJECT-TYPE
	SYNTAX  Unsigned32 (0..65536)
	MAX-ACCESS read-only
	STATUS current
	DESCRIPTION
        "
        Number of the first channel of 
        the component :This OID defines 
        the first channel number of the 
        PM
        "
	::= { pmc1008mpCfgOtxtlhcapabilitiesEntry 5 }


pmc1008mpCfgLastChannelPortn OBJECT-TYPE
	SYNTAX  Unsigned32 (0..65536)
	MAX-ACCESS read-only
	STATUS current
	DESCRIPTION
        "
        Number of the last channel of
         the component :This OID defines 
        the last channel number of the
         PM
        "
	::= { pmc1008mpCfgOtxtlhcapabilitiesEntry 6 }


pmc1008mpCfgGridPortn OBJECT-TYPE
	SYNTAX  Unsigned32 (0..65536)
	MAX-ACCESS read-only
	STATUS current
	DESCRIPTION
        "
        Grid value of the component :This 
        OID defines the grid of the PM
        "
	::= { pmc1008mpCfgOtxtlhcapabilitiesEntry 7 }



pmc1008mpCfgWriteConfiguration  OBJECT-TYPE
	SYNTAX EkiOnOff
	MAX-ACCESS read-write
	STATUS current
	DESCRIPTION
	"Write configuration to module:This OID 
	 writes the complete configuration to the module"
	::= { pmc1008mpConfig 257 }






--- *****************************************************
---     TRAP OBJECTS
--- *****************************************************

pmc1008mptrapPortNumber OBJECT-TYPE
	SYNTAX INTEGER(1..64)
	MAX-ACCESS read-only
	STATUS current
	DESCRIPTION
	"Last port which generates a trap"
	::= { pmc1008mptraps 2 }

pmc1008mptrapLineNumber OBJECT-TYPE
	SYNTAX INTEGER(1..64)
	MAX-ACCESS read-only
	STATUS current
	DESCRIPTION
	"Last Line which generates a trap"
	::= { pmc1008mptraps 3 }

pmc1008mptrapBoardNumber OBJECT-TYPE
	SYNTAX INTEGER(1..64)
	MAX-ACCESS read-only
	STATUS current
	DESCRIPTION
	"Last module which generates a trap"
	::= { pmc1008mptraps 4 }







--- *****************************************************
---     LINE TRAPS
--- *****************************************************

pmc1008mpLineTrapNotUrgentGoesOn NOTIFICATION-TYPE
	OBJECTS {pmc1008mpAlmLineDdmWarningPortn, pmc1008mptrapLineNumber, pmc1008mptrapBoardNumber}
	STATUS current
	--&FILTNAME    "PMC1008MP Line Not Urgent ON"
	--&ACTIONS     { log, minor }
	--&MATCH       { pmc1008mpAlmLineDdmWarningPortn "on", pmc1008mptrapLineNumber "$2", pmc1008mptrapBoardNumber "$3"}
	--&MESG        "DDM Warning appears on Line Port $2 of PMC1008MP in Slot $3 ($A)"
	DESCRIPTION "Not urgent Line default is activated"
	::= { pmc1008mptraps 30 }

pmc1008mpLineTrapNotUrgentGoesOff NOTIFICATION-TYPE
	OBJECTS {pmc1008mpAlmLineDdmWarningPortn, pmc1008mptrapLineNumber, pmc1008mptrapBoardNumber}
	STATUS current
	--&FILTNAME    "PMC1008MP Line Not Urgent OFF"
	--&ACTIONS     { log, normal }
	--&CLEARS      { "PMC1008MP Line Not Urgent ON" }
	--&MATCH       { pmc1008mpAlmLineDdmWarningPortn "on", pmc1008mptrapLineNumber "$2", pmc1008mptrapBoardNumber "$3"}
	--&MESG        "DDM Warning disappears on Line Port $2 of PMC1008MP in Slot $3 ($A)"
	DESCRIPTION "Not urgent Line default disappeared"
	::= { pmc1008mptraps 31 }

pmc1008mpLineTrapUrgentGoesOn NOTIFICATION-TYPE
	OBJECTS {pmc1008mpAlmLineDdmAlmPortn, pmc1008mptrapLineNumber, pmc1008mptrapBoardNumber}
	STATUS current
	--&FILTNAME    "PMC1008MP Line Urgent ON"
	--&ACTIONS     { log, major }
	--&MATCH       { pmc1008mpAlmLineDdmAlmPortn "on", pmc1008mptrapLineNumber "$2", pmc1008mptrapBoardNumber "$3"}
	--&MESG        "DDM Alarm appears on Line Port $2 of PMC1008MP in Slot $3 ($A)"
	DESCRIPTION "Urgent Line default is activated"
	::= { pmc1008mptraps 32 }

pmc1008mpLineTrapUrgentGoesOff NOTIFICATION-TYPE
	OBJECTS {pmc1008mpAlmLineDdmAlmPortn, pmc1008mptrapLineNumber, pmc1008mptrapBoardNumber}
	STATUS current
	--&FILTNAME    "PMC1008MP Line Urgent OFF"
	--&ACTIONS     { log, normal }
	--&CLEARS      { "PMC1008MP Line Urgent ON" }
	--&MATCH       { pmc1008mpAlmLineDdmAlmPortn "on", pmc1008mptrapLineNumber "$2", pmc1008mptrapBoardNumber "$3"}
	--&MESG        "DDM Alarm disappears on Line Port $2 of PMC1008MP in Slot $3 ($A)"
	DESCRIPTION "Urgent Line default disappeared"
	::= { pmc1008mptraps 33 }

pmc1008mpLineTrapCritGoesOn NOTIFICATION-TYPE
	OBJECTS {pmc1008mpAlmLineFailPortn , pmc1008mpAlmLineHwFailPortn , pmc1008mptrapLineNumber, pmc1008mptrapBoardNumber}
	STATUS current
	--&FILTNAME    "PMC1008MP Line Fail ON"
	--&ACTIONS     { log, critical }
	--&MATCH       { pmc1008mpAlmLineFailPortn "on", pmc1008mpAlmLineHwFailPortn "*", pmc1008mptrapLineNumber "$3", pmc1008mptrapBoardNumber "$4"}
	--&MESG        "Line Port $3 Down on PMC1008MP in Slot $4 ($A)"
	
	--&FILTNAME    "PMC1008MP Line HW Fail ON (Hidden)"
	--&ACTIONS     { info }
	--&MATCH       { pmc1008mpAlmLineFailPortn "*", pmc1008mpAlmLineHwFailPortn "on", pmc1008mptrapLineNumber "$3", pmc1008mptrapBoardNumber "$4"}
	--&MESG        "Line Port $3 Down on PMC1008MP in Slot $4 ($A)"
	DESCRIPTION "Critical Line default is activated"
	::= { pmc1008mptraps 34 }

pmc1008mpLineTrapCritGoesOff NOTIFICATION-TYPE
	OBJECTS {pmc1008mpAlmLineFailPortn , pmc1008mpAlmLineHwFailPortn , pmc1008mptrapLineNumber, pmc1008mptrapBoardNumber}
	STATUS current
	--&FILTNAME    "PMC1008MP Line Fail OFF"
	--&ACTIONS     { log,  normal }
	--&CLEARS      { "PMC1008MP Line Fail ON" }
	--&MATCH       { pmc1008mpAlmLineFailPortn "on", pmc1008mpAlmLineHwFailPortn "*", pmc1008mptrapLineNumber "$3", pmc1008mptrapBoardNumber "$4"}
	--&MESG        "Line Port $3 Up on PMC1008MP in Slot $4 ($A)"

	--&FILTNAME    "PMC1008MP Line HW Fail OFF (Hidden)"
	--&ACTIONS     { info }
	--&MATCH       { pmc1008mpAlmLineFailPortn "*", pmc1008mpAlmLineHwFailPortn "on", pmc1008mptrapLineNumber "$3", pmc1008mptrapBoardNumber "$4"}
	--&MESG        "Line Port $3 Up on PMC1008MP in Slot $4 ($A)"
	DESCRIPTION "Critical Line default disappeared"
	::= { pmc1008mptraps 35 }






--- *****************************************************
---     CLIENT TRAPS
--- *****************************************************

pmc1008mpClientTrapNotUrgentGoesOn NOTIFICATION-TYPE
	OBJECTS {pmc1008mpAlmSfpDdmWarningPortn, pmc1008mptrapPortNumber, pmc1008mptrapBoardNumber}
	STATUS current
	--&FILTNAME    "PMC1008MP Client Not Urgent ON"
	--&ACTIONS     { log, minor }
	--&MATCH       { pmc1008mpAlmSfpDdmWarningPortn "on", pmc1008mptrapPortNumber "$2", pmc1008mptrapBoardNumber "$3"}
	--&MESG        "DDM Warning appears on Client Port $2 of PMC1008MP in Slot $3 ($A)"
	DESCRIPTION "Not urgent client default is activated"
	::= { pmc1008mptraps 40 }

pmc1008mpClientTrapNotUrgentGoesOff NOTIFICATION-TYPE
	OBJECTS {pmc1008mpAlmSfpDdmWarningPortn, pmc1008mptrapPortNumber, pmc1008mptrapBoardNumber}
	STATUS current
	--&FILTNAME    "PMC1008MP Client Not Urgent OFF"
	--&ACTIONS     { log, normal }
	--&CLEARS      { "PMC1008MP Client Not Urgent ON" }
	--&MATCH       { pmc1008mpAlmSfpDdmWarningPortn "on", pmc1008mptrapPortNumber "$2", pmc1008mptrapBoardNumber "$3"}
	--&MESG        "DDM Warning appears on Client Port $2 of PMC1008MP in Slot $3 ($A)"
	DESCRIPTION "Not urgent client default disappeared"
	::= { pmc1008mptraps 41 }

pmc1008mpClientTrapUrgentGoesOn NOTIFICATION-TYPE
	OBJECTS {pmc1008mpAlmSfpDdmAlmPortn, pmc1008mptrapPortNumber, pmc1008mptrapBoardNumber}
	STATUS current
	--&FILTNAME    "PMC1008MP Client Urgent ON"
	--&ACTIONS     { log, major }
	--&MATCH       { pmc1008mpAlmSfpDdmAlmPortn "on", pmc1008mptrapPortNumber "$2", pmc1008mptrapBoardNumber "$3"}
	--&MESG        "DDM Alarm appears on Client Port $2 of PMC1008MP in Slot $3 ($A)"
	DESCRIPTION "Urgent client default is activated"
	::= { pmc1008mptraps 42 }

pmc1008mpClientTrapUrgentGoesOff NOTIFICATION-TYPE
	OBJECTS {pmc1008mpAlmSfpDdmAlmPortn, pmc1008mptrapPortNumber, pmc1008mptrapBoardNumber}
	STATUS current
	--&FILTNAME    "PMC1008MP Client Urgent OFF"
	--&ACTIONS     { log, normal }
	--&CLEARS      { "PMC1008MP Client Urgent ON" }
	--&MATCH       { pmc1008mpAlmSfpDdmAlmPortn "on", pmc1008mptrapPortNumber "$2", pmc1008mptrapBoardNumber "$3"}
	--&MESG        "DDM Alarm disappears on Client Port $2 of PMC1008MP in Slot $3 ($A)"
	DESCRIPTION "Urgent client default disappeared"
	::= { pmc1008mptraps 43 }

pmc1008mpClientTrapCritGoesOn NOTIFICATION-TYPE
	OBJECTS {pmc1008mpAlmFailAccPortn, pmc1008mpAlmHwFailAccPortn, pmc1008mptrapPortNumber, pmc1008mptrapBoardNumber}
	STATUS current
	--&FILTNAME    "PMC1008MP Client Fail ON"
	--&ACTIONS     { log, critical }
	--&MATCH       { pmc1008mpAlmFailAccPortn "on", pmc1008mpAlmHwFailAccPortn "*", pmc1008mptrapPortNumber "$3", pmc1008mptrapBoardNumber "$4"}
	--&MESG        "Client Port $3 Down on PMC1008MP in Slot $4 ($A)"
	
	--&FILTNAME    "PMC1008MP Client HW Fail ON (Hidden)"
	--&ACTIONS     { info }
	--&MATCH       { pmc1008mpAlmFailAccPortn "*", pmc1008mpAlmHwFailAccPortn "on", pmc1008mptrapPortNumber "$3", pmc1008mptrapBoardNumber "$4"}
	--&MESG        "Client Port $3 Down on PMC1008MP in Slot $4 ($A)"
	DESCRIPTION "Critical client default is activated"
	::= { pmc1008mptraps 44 }

pmc1008mpClientTrapCritGoesOff NOTIFICATION-TYPE
	OBJECTS {pmc1008mpAlmFailAccPortn, pmc1008mpAlmHwFailAccPortn, pmc1008mptrapPortNumber, pmc1008mptrapBoardNumber}
	STATUS current
	--&FILTNAME    "PMC1008MP Client Fail OFF"
	--&ACTIONS     { log, normal }
	--&CLEARS      { "PMC1008MP Client Fail ON" }
	--&MATCH       { pmc1008mpAlmFailAccPortn "on", pmc1008mpAlmHwFailAccPortn "*", pmc1008mptrapPortNumber "$3", pmc1008mptrapBoardNumber "$4"}
	--&MESG        "Client Port $3 Up on PMC1008MP in Slot $4 ($A)"
	
	--&FILTNAME    "PMC1008MP Client HW Fail OFF (Hidden)"
	--&ACTIONS     { info }
	--&MATCH       { pmc1008mpAlmFailAccPortn "*", pmc1008mpAlmHwFailAccPortn "on", pmc1008mptrapPortNumber "$3", pmc1008mptrapBoardNumber "$4"}
	--&MESG        "Client Port $3 Up on PMC1008MP in Slot $4 ($A)"
	DESCRIPTION "Critical client default disappeared"
	::= { pmc1008mptraps 45 }






--- *****************************************************
---     HW TRAPS
--- *****************************************************

pmc1008mpPowerTrapUrgentGoesOn NOTIFICATION-TYPE
	OBJECTS {pmc1008mpAlmDefFuseB, pmc1008mpAlmDefFuseA , pmc1008mptrapBoardNumber}
	STATUS current
	--&FILTNAME    "PMC1008MP Fuse A Fail ON"
	--&ACTIONS     { log, major }
	--&MATCH       { pmc1008mpAlmDefFuseB "*", pmc1008mpAlmDefFuseA "on", pmc1008mptrapBoardNumber "$3"}
	--&MESG        "Power Input A Fail on PMC1008MP in Slot $3 ($A)"

	--&FILTNAME    "PMC1008MP Fuse B Fail ON"
	--&ACTIONS     { log, major }
	--&MATCH       { pmc1008mpAlmDefFuseB "on", pmc1008mpAlmDefFuseA "*", pmc1008mptrapBoardNumber "$3"}
	--&MESG        "Power Input B Fail on PMC1008MP in Slot $3 ($A)"
	DESCRIPTION "Urgent power supply default is activated"
	::= { pmc1008mptraps 50 }

pmc1008mpPowerTrapUrgentGoesOff NOTIFICATION-TYPE
	OBJECTS {pmc1008mpAlmDefFuseB, pmc1008mpAlmDefFuseA , pmc1008mptrapBoardNumber}
	STATUS current
	--&FILTNAME    "PMC1008MP Fuse A&B Fail OFF"
	--&ACTIONS     { log, normal}
	--&CLEARS      { "PMC1008MP Fuse A Fail ON", "PMC1008MP Fuse B Fail ON" }
	--&MATCH       { pmc1008mpAlmDefFuseB "on", pmc1008mpAlmDefFuseA "on", pmc1008mptrapBoardNumber "$3"}
	--&MESG        "Power Inputs A and B Present on PMC1008MP in Slot $3 ($A)"
	DESCRIPTION "Urgent power supply default disappeared"
	::= { pmc1008mptraps 51 }






END
