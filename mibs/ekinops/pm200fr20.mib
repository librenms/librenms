-- *****************************************************************
-- EKINOPS-Pm200fr20.TXT:  MIB
--
--MIB Part Number:3MI00047AAAD
--MIB Version:01
--
-- Copyright (c) 2018 by Ekinops
-- All rights reserved.
-- 
-- *****************************************************************

EKINOPS-Pm200fr20-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm200fr20 MODULE-IDENTITY
        LAST-UPDATED "201804130000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."


	REVISION "201705110000Z"
	DESCRIPTION
	  "Creation for PM200FR20 module"
	REVISION "201802090000Z"
	DESCRIPTION
	  "Rmon Labels modification"
	REVISION "201803010000Z"
	DESCRIPTION
	  "Line Temp object added"
	REVISION "201804130000Z"
	DESCRIPTION
	  "Alarm Type modification"
        ::= { ekinops 87 }



--- *****************************************************
---     LEAF LEVEL 2
--- *****************************************************


pm200fr20alarms OBJECT IDENTIFIER ::= { modulePm200fr20 2 }	
pm200fr20AlmOther OBJECT IDENTIFIER ::= { pm200fr20alarms 1 }
pm200fr20AlmOtherNurg OBJECT IDENTIFIER ::= { pm200fr20AlmOther 1 }
pm200fr20AlmOtherUrg OBJECT IDENTIFIER ::= { pm200fr20AlmOther 2 }
pm200fr20AlmOtherCrit OBJECT IDENTIFIER ::= { pm200fr20AlmOther 3 }

pm200fr20AlmClient OBJECT IDENTIFIER ::= { pm200fr20alarms 2 }
pm200fr20AlmClientNurg OBJECT IDENTIFIER ::= { pm200fr20AlmClient 1 }
pm200fr20AlmClientUrg OBJECT IDENTIFIER ::= { pm200fr20AlmClient 2 }
pm200fr20AlmClientCrit OBJECT IDENTIFIER ::= { pm200fr20AlmClient 3 }
	
pm200fr20AlmLine OBJECT IDENTIFIER ::= { pm200fr20alarms 3 }
pm200fr20AlmLineNurg OBJECT IDENTIFIER ::= { pm200fr20AlmLine 1 }
pm200fr20AlmLineUrg OBJECT IDENTIFIER ::= { pm200fr20AlmLine 2 }
pm200fr20AlmLineCrit OBJECT IDENTIFIER ::= { pm200fr20AlmLine 3 }





pm200fr20measures OBJECT IDENTIFIER ::= { modulePm200fr20 3 }	
pm200fr20MesrOther OBJECT IDENTIFIER ::= { pm200fr20measures 1 }	
pm200fr20MesrClient OBJECT IDENTIFIER ::= { pm200fr20measures 2 }	
pm200fr20MesrLine OBJECT IDENTIFIER ::= { pm200fr20measures 3 }	




pm200fr20counters OBJECT IDENTIFIER ::= { modulePm200fr20 4 }
pm200fr20CntOther OBJECT IDENTIFIER ::= { pm200fr20counters 1 }
pm200fr20CntClient OBJECT IDENTIFIER ::= { pm200fr20counters 2 }
pm200fr20CntLine OBJECT IDENTIFIER ::= { pm200fr20counters 3 }


pm200fr20controlsWrite OBJECT IDENTIFIER ::= { modulePm200fr20 6 }
pm200fr20CtrlOther OBJECT IDENTIFIER ::= { pm200fr20controlsWrite 1 }
pm200fr20CtrlClient OBJECT IDENTIFIER ::= { pm200fr20controlsWrite 2 }
pm200fr20CtrlLine OBJECT IDENTIFIER ::= { pm200fr20controlsWrite 3 }

pm200fr20ri OBJECT IDENTIFIER ::= { modulePm200fr20 7 }
pm200fr20riTable OBJECT IDENTIFIER ::= { pm200fr20ri 1 }

pm200fr20download OBJECT IDENTIFIER ::= { modulePm200fr20 8 }
pm200fr20DwlOther OBJECT IDENTIFIER ::= { pm200fr20download 1 }
pm200fr20DwlClient OBJECT IDENTIFIER ::= { pm200fr20download 2 }
pm200fr20DwlLine OBJECT IDENTIFIER ::= { pm200fr20download 3 }


pm200fr20Config OBJECT IDENTIFIER ::= { modulePm200fr20 9 }

pm200fr20traps OBJECT IDENTIFIER ::= { modulePm200fr20 10 }



pm200fr20Monitoring OBJECT IDENTIFIER ::= { modulePm200fr20 11}

pm200fr20MonOther OBJECT IDENTIFIER ::= { pm200fr20Monitoring 1 }
pm200fr20MonRmon OBJECT IDENTIFIER ::= { pm200fr20MonOther 3 }

pm200fr20MonClient OBJECT IDENTIFIER ::= { pm200fr20Monitoring 2 }
pm200fr20MonClientRmonCounter OBJECT IDENTIFIER ::= { pm200fr20MonClient 4 }


pm200fr20MonPerfOther OBJECT IDENTIFIER ::= { pm200fr20Monitoring 5 }
pm200fr20MonPerfSync OBJECT IDENTIFIER ::= { pm200fr20MonPerfOther 1 }
pm200fr20MonPerfTimeStamp OBJECT IDENTIFIER ::= { pm200fr20MonPerfOther 2 }


pm200fr20MonPerfClient OBJECT IDENTIFIER ::= { pm200fr20Monitoring 6 }

pm200fr20MonPerfLine OBJECT IDENTIFIER ::= { pm200fr20Monitoring 7 }



--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************



Pm200fr20OtxGrid ::= TEXTUAL-CONVENTION
    STATUS      current
    DESCRIPTION "Different grids on OTX-TLH on client and line ports"
    SYNTAX INTEGER {
		otxgrid200(200),
		otxgrid100(100),
		otxgrid50(50)
           }


Pm200fr20ClientProtocolA ::= TEXTUAL-CONVENTION
    STATUS      current
    DESCRIPTION "Different values on the protocol on the client ports"
    SYNTAX INTEGER {
		protocolclientvalue0A(1),
		protocolclientvalue1A(2),
		protocolclientvalue2A(3)
           }


Pm200fr20ClientProtocolB ::= TEXTUAL-CONVENTION
    STATUS      current
    DESCRIPTION "Different values on the protocol on the client ports"
    SYNTAX INTEGER {
		protocolclientvalue0B(1),
		protocolclientvalue1B(2),
		protocolclientvalue2B(3),
		protocolclientvalue3B(4),
		protocolclientvalue4B(5)
           }


Pm200fr20ClientProtocolC ::= TEXTUAL-CONVENTION
    STATUS      current
    DESCRIPTION "Different values on the protocol on the client ports"
    SYNTAX INTEGER {
		protocolclientvalue0C(1)
           }


Pm200fr20ProtocolMode ::= TEXTUAL-CONVENTION
    STATUS      current
    DESCRIPTION "Different values on the protocol mode"
    SYNTAX INTEGER {
		protocolmodevalue0(1),
		protocolmodevalue1(2),
		protocolmodevalue2(3)
           }

Pm200fr20OtxChannel ::= TEXTUAL-CONVENTION
    STATUS      current
    DESCRIPTION "Channel selection on transceiver Tx line ports"
    SYNTAX INTEGER

Pm200fr20OrxChannel ::= TEXTUAL-CONVENTION
    STATUS      current
    DESCRIPTION "Channel selection on transceiver Rx line ports"
    SYNTAX INTEGER

Pm200fr20DccMode ::= TEXTUAL-CONVENTION
    STATUS      current
    DESCRIPTION "Mode for DCC"
    SYNTAX INTEGER {
		dccNo(0),
		dccLine1(1),
		dccLine2(2)
           }





--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm200fr20RinvReloadInventory OBJECT-TYPE
  SYNTAX EkiOnOff
  MAX-ACCESS read-write
  STATUS current
  DESCRIPTION
        "Reload the inventory: This OID triggers an 
         inventory reload."
  ::= { pm200fr20ri 2 }

pm200fr20RinvHwPlatform OBJECT-TYPE
  SYNTAX DisplayString
  MAX-ACCESS read-only
  STATUS current
  DESCRIPTION
        "HW platform description: This OID contains the 
         description of the Hardware platform."
  ::= { pm200fr20ri 3 }
  
pm200fr20RinvModulePlatform OBJECT-TYPE
  SYNTAX DisplayString
  MAX-ACCESS read-only
  STATUS current
  DESCRIPTION
        "Module platform description: This OID contains the 
         description of the Module."
  ::= { pm200fr20ri 4 }
  
pm200fr20RinvSwPlatform OBJECT-TYPE
  SYNTAX DisplayString
  MAX-ACCESS read-only
  STATUS current
  DESCRIPTION
        "SW platform description: This OID contains the 
         description of the Software platform."
  ::= { pm200fr20ri 5 }
  
pm200fr20RinvGwPlatform OBJECT-TYPE
  SYNTAX DisplayString
  MAX-ACCESS read-only
  STATUS current
  DESCRIPTION
        "GW platform description: This OID contains the 
         description of the Gateware platform."
  ::= { pm200fr20ri 6 }


pm200fr20RinvSfpTable OBJECT-TYPE
      SYNTAX  SEQUENCE OF Pm200fr20RinvSfpEntry
      MAX-ACCESS  not-accessible
      STATUS  current
      DESCRIPTION
              "List of the SFPs on the selected module"
      ::= { pm200fr20riTable 1 }

pm200fr20RinvSfpEntry OBJECT-TYPE
        SYNTAX  Pm200fr20RinvSfpEntry
        MAX-ACCESS  not-accessible
        STATUS  current
        DESCRIPTION
              "Row definition for the SFP table"
        INDEX   { pm200fr20RinvSfpIndex }
        ::= { pm200fr20RinvSfpTable 1 }
    


Pm200fr20RinvSfpEntry::=
        SEQUENCE {
          pm200fr20RinvSfpIndex 
              Integer32,
          pm200fr20Rinvsfp
              DisplayString
        }


    pm200fr20RinvSfpIndex OBJECT-TYPE
        SYNTAX  Integer32(1..16)
        MAX-ACCESS  read-only
        STATUS  current
        DESCRIPTION
              "Index for SFP table"
        ::= { pm200fr20RinvSfpEntry 1 }


    pm200fr20Rinvsfp OBJECT-TYPE
        SYNTAX  DisplayString
        MAX-ACCESS  read-only
        STATUS  current
        DESCRIPTION
              "Inventory for the SFP: This OID contains the inventory for the SFP"
        ::= { pm200fr20RinvSfpEntry 2 }




pm200fr20RinvLineTable OBJECT-TYPE
      SYNTAX  SEQUENCE OF Pm200fr20RinvLineEntry
      MAX-ACCESS  not-accessible
      STATUS  current
      DESCRIPTION
              "List of the XFPs on the selected module"
      ::= { pm200fr20riTable 2 }

pm200fr20RinvLineEntry OBJECT-TYPE
        SYNTAX  Pm200fr20RinvLineEntry
        MAX-ACCESS  not-accessible
        STATUS  current
        DESCRIPTION
              "Row definition for the XFP table"
        INDEX   { pm200fr20RinvLineIndex }
        ::= { pm200fr20RinvLineTable 1 }
    


Pm200fr20RinvLineEntry::=
        SEQUENCE {
          pm200fr20RinvLineIndex 
              Integer32,
          pm200fr20RinvxfpLine
              DisplayString
        }


    pm200fr20RinvLineIndex OBJECT-TYPE
        SYNTAX  Integer32(1..16)
        MAX-ACCESS  read-only
        STATUS  current
        DESCRIPTION
              "Index for XFP table"
        ::= { pm200fr20RinvLineEntry 1 }


    pm200fr20RinvxfpLine OBJECT-TYPE
        SYNTAX  DisplayString
        MAX-ACCESS  read-only
        STATUS  current
        DESCRIPTION
              "Inventory for the XFP: This OID contains the inventory for the XFP"
        ::= { pm200fr20RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm200fr20AlmsynthAlm0 OBJECT IDENTIFIER ::= { pm200fr20AlmOtherCrit 0 }




pm200fr20AlmDefFuseB OBJECT-TYPE
	  SYNTAX EkiOnOff
	  MAX-ACCESS read-only
	  STATUS current
	  DESCRIPTION
        "
        Fuse B Fail :This OID indicates 
        that the fuse of the power input 
        B is in fail condition <Help> Status 
        of the Fuse B <Condtype> DEF_FUSE_B 
        <Probcause> powerProblem (36) <Alarmtype> 
        equipmentAlarm (5) <Polarity> (2) 
        "
	  ::= { pm200fr20AlmsynthAlm0 16 }



pm200fr20AlmDefFuseA OBJECT-TYPE
	  SYNTAX EkiOnOff
	  MAX-ACCESS read-only
	  STATUS current
	  DESCRIPTION
        "
        Fuse A Fail :This OID indicates 
        that the fuse of the power input 
        A is in fail condition <Help> Status 
        of the Fuse A <Condtype> DEF_FUSE_A 
        <Probcause> powerProblem (36) <Alarmtype> 
        equipmentAlarm (5) <Polarity> (2) 
        "
	  ::= { pm200fr20AlmsynthAlm0 15 }



pm200fr20AlmModGlobFail OBJECT-TYPE
	  SYNTAX EkiOnOff
	  MAX-ACCESS read-only
	  STATUS current
	  DESCRIPTION
        "
        Module Failure :This OID is set 
        on detection of a failure originating 
        from the RM <Help> This alarm is 
        set on detection of a failure originating 
        from the equipment <Condtype> MOD_GLOB_FAIL 
        <Probcause> other (1) <Alarmtype> 
        synthesisAlarm (12)  <Polarity> 
        (2) 
        "
	  ::= { pm200fr20AlmsynthAlm0 9 }



pm200fr20AlmFailFan OBJECT-TYPE
	  SYNTAX EkiOnOff
	  MAX-ACCESS read-only
	  STATUS current
	  DESCRIPTION
        "
        Fan Fail :This OID is at 1 when 
        any fail occurs on the fan tray 
        <Help> This alarm indicates that 
        the Fan tray module is in a failure 
        condition <Condtype> FAIL_FAN <Probcause> 
        equipmentMalfunction (16) <Alarmtype> 
        equipmentAlarm (5) <Polarity> (2) 
        "
	  ::= { pm200fr20AlmsynthAlm0 2 }



--- *****************************************************
---     LEAF for the synthAlm2 article
--- *****************************************************
pm200fr20AlmsynthAlm2 OBJECT IDENTIFIER ::= { pm200fr20AlmOtherNurg 2 }




pm200fr20AlmMaintenanceOn OBJECT-TYPE
	  SYNTAX EkiOnOff
	  MAX-ACCESS read-only
	  STATUS current
	  DESCRIPTION
        "
        Maintenance Mode :This OID indicates 
        that the RM is in maintenance mode. 
        <Help> This alarm indicates that 
        the maintenance mode is enabled 
        on the PM <Condtype> MAINTENANCE_ON 
        <Probcause> informationalStatus(1000) 
        <Alarmtype> other (1) <Polarity> 
        (2) 
        "
	  ::= { pm200fr20AlmsynthAlm2 5 }



pm200fr20AlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> informationalStatus(1000) 
        <Alarmtype> other (1) <Polarity> 
        (2) 
        "
	  ::= { pm200fr20AlmsynthAlm2 4 }



pm200fr20AlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> informationalStatus(1000) 
        <Alarmtype> other (1) <Polarity> 
        (2) 
        "
	  ::= { pm200fr20AlmsynthAlm2 3 }



pm200fr20AlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> informationalStatus(1000) 
        <Alarmtype> other (1) <Polarity> 
        (2) 
        "
	  ::= { pm200fr20AlmsynthAlm2 2 }



pm200fr20AlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> informationalStatus(1000) 
        <Alarmtype> other (1) <Polarity> 
        (2) 
        "
	  ::= { pm200fr20AlmsynthAlm2 1 }



--- *********************************************************
---     TABLE for the pm200fr20AlmsynthAlmPort articles
--- *********************************************************

pm200fr20AlmsynthAlmPortTable OBJECT-TYPE
	SYNTAX  SEQUENCE OF Pm200fr20AlmsynthAlmPortEntry
	MAX-ACCESS not-accessible
	STATUS current
	DESCRIPTION
        "
        List of pm200fr20AlmsynthAlmPort 
        Article
        "
	::= { pm200fr20AlmClientCrit 8 }


pm200fr20AlmsynthAlmPortEntry OBJECT-TYPE
	SYNTAX Pm200fr20AlmsynthAlmPortEntry
	MAX-ACCESS not-accessible
	STATUS current
	DESCRIPTION
        "
        Row definition for the pm200fr20AlmsynthAlmPort 
        table
        "
	INDEX   { pm200fr20AlmsynthAlmPortIndex }
	::= { pm200fr20AlmsynthAlmPortTable 1 }


Pm200fr20AlmsynthAlmPortEntry ::=
	SEQUENCE {
	pm200fr20AlmsynthAlmPortIndex
		INTEGER,
	pm200fr20AlmUpCsfPortn
		EkiOnOff,
	pm200fr20AlmFailAccPortn
		EkiOnOff,
	pm200fr20AlmSfpDdmAlmPortn
		EkiOnOff,
	pm200fr20AlmSfpDdmWarningPortn
		EkiOnOff,
	pm200fr20AlmDwCaisPortn
		EkiOnOff,
	pm200fr20AlmClientRemoteOosPortn
		EkiOnOff,
	pm200fr20AlmClientLocalOosPortn
		EkiOnOff,
	pm200fr20AlmDwLsdPortn
		EkiOnOff,
	pm200fr20AlmHwFailAccPortn
		EkiOnOff,
	pm200fr20AlmDdmAbsentPortn
		EkiOnOff,
	pm200fr20AlmSfpAbsentPortn
		EkiOnOff
	}


pm200fr20AlmsynthAlmPortIndex OBJECT-TYPE
	SYNTAX  INTEGER(0..128)
	MAX-ACCESS  read-only
	STATUS current
	DESCRIPTION
        "
        Index definition for the pm200fr20AlmsynthAlmPort 
        table
        "
	::= { pm200fr20AlmsynthAlmPortEntry 1 }


pm200fr20AlmUpCsfPortn OBJECT-TYPE
	SYNTAX  EkiOnOff
	MAX-ACCESS read-only
	STATUS current
	DESCRIPTION
        "
        Client Signal Fail Inserted :This 
        OID indicates a CSF has been inserted 
        in the upstream client port. <Help> 
        This status indicates if a Client 
        Signal Fail is currently inserted 
        on the line signal for this client 
        port <Condtype> UP_CSF_1 <Probcause> 
        informationalStatus(1000) <Alarmtype> 
        other (1) <Polarity> (2) 
        "
	::= { pm200fr20AlmsynthAlmPortEntry 17 }


pm200fr20AlmFailAccPortn OBJECT-TYPE
	SYNTAX  EkiOnOff
	MAX-ACCESS read-only
	STATUS current
	DESCRIPTION
        "
        Client Access Fail :This OID indicates 
        a failure on the Client port <Help> 
        This alarm indicates a failure
         on the Client port <Condtype>
         FAIL_ACC_1 <Probcause> equipmentMalfunction 
        (16) <Alarmtype> synthesisAlarm 
        (12)  <Polarity> (2) 
        "
	::= { pm200fr20AlmsynthAlmPortEntry 13 }


pm200fr20AlmSfpDdmAlmPortn OBJECT-TYPE
	SYNTAX  EkiOnOff
	MAX-ACCESS read-only
	STATUS current
	DESCRIPTION
        "
        Alarm On Client Trscv DDM :This 
        OID indicates an alarm is being 
        received from the Client Transceiver 
        DDM <Help> This alarm indicates 
        if a DDM Alarm has been detected 
        on the client transceiver <Condtype> 
        SFP_DDM_ALM_1 <Probcause> inputOutputDeviceError 
        (24) <Alarmtype> synthesisAlarm 
        (12)  <Polarity> (2) 
        "
	::= { pm200fr20AlmsynthAlmPortEntry 11 }


pm200fr20AlmSfpDdmWarningPortn OBJECT-TYPE
	SYNTAX  EkiOnOff
	MAX-ACCESS read-only
	STATUS current
	DESCRIPTION
        "
        Warning On Client Trscv DDM :This 
        OID indicates a warning is being 
        received from the Client Transceiver 
        DDM <Help> This alarm indicates 
        if a DDM Warning has been detected 
        on the client transceiver <Condtype> 
        SFP_DDM_WARNING_1 <Probcause> inputOutputDeviceError 
        (24) <Alarmtype> synthesisAlarm 
        (12)  <Polarity> (2) 
        "
	::= { pm200fr20AlmsynthAlmPortEntry 10 }


pm200fr20AlmDwCaisPortn OBJECT-TYPE
	SYNTAX  EkiOnOff
	MAX-ACCESS read-only
	STATUS current
	DESCRIPTION
        "
        Client AIS Inserted :This OID
         indicates a CAIS has been inserted 
        on the output client port. <Help> 
        This status indicates if a Client 
        Alarm Indication Signal is currently 
        inserted on the client interface 
        <Condtype> DW_CAIS_1 <Probcause> 
        informationalStatus(1000) <Alarmtype> 
        other (1) <Polarity> (2) 
        "
	::= { pm200fr20AlmsynthAlmPortEntry 9 }


pm200fr20AlmClientRemoteOosPortn OBJECT-TYPE
	SYNTAX  EkiOnOff
	MAX-ACCESS read-only
	STATUS current
	DESCRIPTION
        "
        Remote Client Port In Service
         :This OID indicates that the remote 
        Client port is In Service (1) or 
        Out of Service (2) <Help> This
         status indicates if the remote 
        client port is in service <Condtype> 
        CLIENT_REMOTE_OOS <Probcause> informationalStatus(1000) 
        <Alarmtype> other (1) <Polarity> 
        (2) 
        "
	::= { pm200fr20AlmsynthAlmPortEntry 8 }


pm200fr20AlmClientLocalOosPortn OBJECT-TYPE
	SYNTAX  EkiOnOff
	MAX-ACCESS read-only
	STATUS current
	DESCRIPTION
        "
        Local Client Port In Service :This 
        OID indicates that the local Client 
        port is In Service (1) or Out of 
        Service (2) <Help> This status
         indicates if the local client
         port is in service <Condtype>
         CLIENT_LOCAL_OOS <Probcause> informationalStatus(1000) 
        <Alarmtype> other (1) <Polarity> 
        (2)
        "
	::= { pm200fr20AlmsynthAlmPortEntry 7 }


pm200fr20AlmDwLsdPortn OBJECT-TYPE
	SYNTAX  EkiOnOff
	MAX-ACCESS read-only
	STATUS current
	DESCRIPTION
        "
        Client Trscv Laser Shutdown :This 
        OID indicates the Client transceiver 
        laser is shutdown <Help> This status 
        indicates if the client transceiver 
        laser is shutdown <Condtype> DW_LSD_1 
        <Probcause> other (1) <Alarmtype> 
        equipmentAlarm (5) <Polarity> (2) 
        "
	::= { pm200fr20AlmsynthAlmPortEntry 6 }


pm200fr20AlmHwFailAccPortn OBJECT-TYPE
	SYNTAX  EkiOnOff
	MAX-ACCESS read-only
	STATUS current
	DESCRIPTION
        "
        Client HW Fail :This OID indicates 
        a failure on client port, most
         probably caused by a HW issue. 
        <Help> This alarm indicates a failure 
        on client port, most probably caused 
        by a HW issue. <Condtype> HW_FAIL_ACC_1 
        <Probcause> equipmentMalfunction 
        (16) <Alarmtype> synthesisAlarm 
        (12)  <Polarity> (2) 
        "
	::= { pm200fr20AlmsynthAlmPortEntry 5 }


pm200fr20AlmDdmAbsentPortn OBJECT-TYPE
	SYNTAX  EkiOnOff
	MAX-ACCESS read-only
	STATUS current
	DESCRIPTION
        "
        DDM Supported On Client Trscv
         :This OID indicates that the Client 
        transceiver supports the Digital 
        Diagnostic Monitoring function
         <Help> This status indicates if 
        the client transceiver includes 
        the DDM feature <Condtype> DDM_ABSENT_1 
        <Probcause> informationalStatus(1000) 
        <Alarmtype> other (1) <Polarity> 
        (2) 
        "
	::= { pm200fr20AlmsynthAlmPortEntry 3 }


pm200fr20AlmSfpAbsentPortn OBJECT-TYPE
	SYNTAX  EkiOnOff
	MAX-ACCESS read-only
	STATUS current
	DESCRIPTION
        "
        Client Optical Module Absent :This 
        OID indicates that the Transceiver 
        is not present in the client port. 
        <Help> This alarm indicates if
         the client transceiver is not
         plugged <Condtype> SFP_ABSENT_1 
        <Probcause> inputOutputDeviceError 
        (24) <Alarmtype> equipmentAlarm 
        (5) <Polarity> (2) <Event> ObjectCDSingleClientInv
        "
	::= { pm200fr20AlmsynthAlmPortEntry 2 }


--- *********************************************************
---     TABLE for the pm200fr20AlmsynthAlmLine articles
--- *********************************************************

pm200fr20AlmsynthAlmLineTable OBJECT-TYPE
	SYNTAX  SEQUENCE OF Pm200fr20AlmsynthAlmLineEntry
	MAX-ACCESS not-accessible
	STATUS current
	DESCRIPTION
        "
        List of pm200fr20AlmsynthAlmLine 
        Article
        "
	::= { pm200fr20AlmLineCrit 40 }


pm200fr20AlmsynthAlmLineEntry OBJECT-TYPE
	SYNTAX Pm200fr20AlmsynthAlmLineEntry
	MAX-ACCESS not-accessible
	STATUS current
	DESCRIPTION
        "
        Row definition for the pm200fr20AlmsynthAlmLine 
        table
        "
	INDEX   { pm200fr20AlmsynthAlmLineIndex }
	::= { pm200fr20AlmsynthAlmLineTable 1 }


Pm200fr20AlmsynthAlmLineEntry ::=
	SEQUENCE {
	pm200fr20AlmsynthAlmLineIndex
		INTEGER,
	pm200fr20AlmLineFailPortn
		EkiOnOff,
	pm200fr20AlmLineDdmAlmPortn
		EkiOnOff,
	pm200fr20AlmLineDdmWarningPortn
		EkiOnOff,
	pm200fr20AlmUpRdiInsPortn
		EkiOnOff,
	pm200fr20AlmLineLocalOosPortn
		EkiOnOff,
	pm200fr20AlmXfpTxOffPortn
		EkiOnOff,
	pm200fr20AlmLineHwFailPortn
		EkiOnOff,
	pm200fr20AlmXfpInitNotComplPortn
		EkiOnOff,
	pm200fr20AlmXfpAbsentPortn
		EkiOnOff
	}


pm200fr20AlmsynthAlmLineIndex OBJECT-TYPE
	SYNTAX  INTEGER(0..128)
	MAX-ACCESS  read-only
	STATUS current
	DESCRIPTION
        "
        Index definition for the pm200fr20AlmsynthAlmLine 
        table
        "
	::= { pm200fr20AlmsynthAlmLineEntry 1 }


pm200fr20AlmLineFailPortn OBJECT-TYPE
	SYNTAX  EkiOnOff
	MAX-ACCESS read-only
	STATUS current
	DESCRIPTION
        "
        Line Port Failure :This OID indicates 
        a failure on the line port <Help> 
        This alarm indicates a failure
         on the line port <Condtype> LINE_FAIL 
        <Probcause> equipmentMalfunction 
        (16) <Alarmtype> synthesisAlarm 
        (12)  <Polarity> (2) 
        "
	::= { pm200fr20AlmsynthAlmLineEntry 13 }


pm200fr20AlmLineDdmAlmPortn OBJECT-TYPE
	SYNTAX  EkiOnOff
	MAX-ACCESS read-only
	STATUS current
	DESCRIPTION
        "
        Alarm On Line Optical Module DDM 
        :This OID indicates an alarm is 
        present coming out of Line transceiver 
        DDM <Help> This alarm indicates 
        if a DDM Alarm has been detected 
        on the line transceiver <Condtype> 
        LINE_DDM_ALM <Probcause> inputOutputDeviceError 
        (24) <Alarmtype> equipmentAlarm 
        (5) <Polarity> (2) 
        "
	::= { pm200fr20AlmsynthAlmLineEntry 11 }


pm200fr20AlmLineDdmWarningPortn OBJECT-TYPE
	SYNTAX  EkiOnOff
	MAX-ACCESS read-only
	STATUS current
	DESCRIPTION
        "
        Warning On Line Optical Module 
        DDM :This OID indicates a warning 
        is present coming out of Line transceiver 
        DDM <Help> This alarm indicates 
        if a DDM Warning has been detected 
        on the line transceiver <Condtype> 
        LINE_DDM_WARNING <Probcause> inputOutputDeviceError 
        (24) <Alarmtype> equipmentAlarm 
        (5) <Polarity> (2) 
        "
	::= { pm200fr20AlmsynthAlmLineEntry 10 }


pm200fr20AlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal. <Help> This status indicates 
        if a MS-RDI/L-RDI is currently
         inserted on the line interface. 
        <Condtype> UP_RDI_INS <Probcause> 
        informationalStatus(1000) <Alarmtype> 
        other (1) <Polarity> (2) 
        "
	::= { pm200fr20AlmsynthAlmLineEntry 9 }


pm200fr20AlmLineLocalOosPortn OBJECT-TYPE
	SYNTAX  EkiOnOff
	MAX-ACCESS read-only
	STATUS current
	DESCRIPTION
        "
        Line Port In Service :This OID 
        indicates that the Line port is 
        In Service (1) of Out or Service 
        (2) <Help> This status indicates 
        if the line port is in service
         <Condtype> LINE_LOCAL_OOS <Probcause> 
        informationalStatus(1000) <Alarmtype> 
        other (1) <Polarity> (2) 
        "
	::= { pm200fr20AlmsynthAlmLineEntry 7 }


pm200fr20AlmXfpTxOffPortn OBJECT-TYPE
	SYNTAX  EkiOnOff
	MAX-ACCESS read-only
	STATUS current
	DESCRIPTION
        "
        Line Trscv Laser Shutdown :This 
        OID indicates the Line transceiver 
        laser is shutdown <Help> This status 
        indicates if the Line transceiver 
        laser is shutdown <Condtype> XFP_TX_OFF 
        <Probcause> other (1) <Alarmtype> 
        equipmentAlarm (5) <Polarity> (2) 
        "
	::= { pm200fr20AlmsynthAlmLineEntry 6 }


pm200fr20AlmLineHwFailPortn OBJECT-TYPE
	SYNTAX  EkiOnOff
	MAX-ACCESS read-only
	STATUS current
	DESCRIPTION
        "
        Line Port HW Failure :This OID 
        indicates a failure on line port, 
        most probably caused by a HW issue 
        <Help> This alarm indicates a failure 
        on line port, most probably caused 
        by a HW issue <Condtype> LINE_HW_FAIL 
        <Probcause> equipmentMalfunction 
        (16) <Alarmtype> synthesisAlarm 
        (12)  <Polarity> (2) 
        "
	::= { pm200fr20AlmsynthAlmLineEntry 5 }


pm200fr20AlmXfpInitNotComplPortn OBJECT-TYPE
	SYNTAX  EkiOnOff
	MAX-ACCESS read-only
	STATUS current
	DESCRIPTION
        "
        Line Optical Module Ready :This 
        OID indicates that the optical
         interface is not operational.
         <Help> This status indicates if 
        the line transceiver has been correctly 
        initialized <Condtype> XFP_INIT_NOT_COMPL 
        <Probcause> equipmentMalfunction 
        (16) <Alarmtype> equipmentAlarm 
        (5) <Polarity> (2) 
        "
	::= { pm200fr20AlmsynthAlmLineEntry 3 }


pm200fr20AlmXfpAbsentPortn OBJECT-TYPE
	SYNTAX  EkiOnOff
	MAX-ACCESS read-only
	STATUS current
	DESCRIPTION
        "
        Line Optical Module Absent :This 
        OID indicates that the line optical 
        interface is not present. <Help> 
        This alarm indicates if the line 
        transceiver is not plugged <Condtype> 
        XFP_ABSENT <Probcause> inputOutputDeviceError 
        (24) <Alarmtype> equipmentAlarm 
        (5) <Polarity> (2) <Event> ObjectCDINV
        "
	::= { pm200fr20AlmsynthAlmLineEntry 2 }


--- *****************************************************
---     LEAF for the msaModuleState article
--- *****************************************************
pm200fr20AlmmsaModuleState OBJECT IDENTIFIER ::= { pm200fr20AlmOtherCrit 78 }




pm200fr20AlmMsaFault OBJECT-TYPE
	  SYNTAX EkiOnOff
	  MAX-ACCESS read-only
	  STATUS current
	  DESCRIPTION
        "
        Line Trscv Fault :This OID indicates 
        the Line Trscv is in Fault state 
        <Help> Status indicating the Line 
        Trscv is in Fault state <Condtype> 
        MSA_FAULT <Probcause> informationalStatus(1000) 
        <Alarmtype> other (1) <Polarity> 
        (2) 
        "
	  ::= { pm200fr20AlmmsaModuleState 7 }



pm200fr20AlmMsaReady OBJECT-TYPE
	  SYNTAX EkiOnOff
	  MAX-ACCESS read-only
	  STATUS current
	  DESCRIPTION
        "
        Line Trscv Ready :This OID indicates 
        the Line Trscv is ready to operate 
        <Help> Status indicating the Line 
        Trscv is ready to operate <Condtype> 
        MSA_READY <Probcause> informationalStatus(1000) 
        <Alarmtype> other (1) <Polarity> 
        (2) 
        "
	  ::= { pm200fr20AlmmsaModuleState 6 }



--- *********************************************************
---     TABLE for the pm200fr20AlmlineQsfpWarnDdm articles
--- *********************************************************

pm200fr20AlmlineQsfpWarnDdmTable OBJECT-TYPE
	SYNTAX  SEQUENCE OF Pm200fr20AlmlineQsfpWarnDdmEntry
	MAX-ACCESS not-accessible
	STATUS current
	DESCRIPTION
        "
        List of pm200fr20AlmlineQsfpWarnDdm 
        Article
        "
	::= { pm200fr20AlmLineNurg 104 }


pm200fr20AlmlineQsfpWarnDdmEntry OBJECT-TYPE
	SYNTAX Pm200fr20AlmlineQsfpWarnDdmEntry
	MAX-ACCESS not-accessible
	STATUS current
	DESCRIPTION
        "
        Row definition for the pm200fr20AlmlineQsfpWarnDdm 
        table
        "
	INDEX   { pm200fr20AlmlineQsfpWarnDdmIndex }
	::= { pm200fr20AlmlineQsfpWarnDdmTable 1 }


Pm200fr20AlmlineQsfpWarnDdmEntry ::=
	SEQUENCE {
	pm200fr20AlmlineQsfpWarnDdmIndex
		INTEGER,
	pm200fr20AlmLineRxPwrHighWngPortn
		EkiOnOff,
	pm200fr20AlmLineRxPwrLowWngPortn
		EkiOnOff,
	pm200fr20AlmLineTempHighWngPortn
		EkiOnOff,
	pm200fr20AlmLineTempLowWngPortn
		EkiOnOff,
	pm200fr20AlmLineVccHighWngPortn
		EkiOnOff,
	pm200fr20AlmLineVccLowWngPortn
		EkiOnOff,
	pm200fr20AlmLineTxBiasHighWngPortn
		EkiOnOff,
	pm200fr20AlmLineTxBiasLowWngPortn
		EkiOnOff,
	pm200fr20AlmLineTxPwrHighWngPortn
		EkiOnOff,
	pm200fr20AlmLineTxPwLowWngPortn
		EkiOnOff
	}


pm200fr20AlmlineQsfpWarnDdmIndex OBJECT-TYPE
	SYNTAX  INTEGER(0..128)
	MAX-ACCESS  read-only
	STATUS current
	DESCRIPTION
        "
        Index definition for the pm200fr20AlmlineQsfpWarnDdm 
        table
        "
	::= { pm200fr20AlmlineQsfpWarnDdmEntry 1 }


pm200fr20AlmLineRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         LINE_RX_PWR_HIGH_WNG_1 <Probcause> 
        receiveFailure (41) <Alarmtype> 
        equipmentAlarm (5) <Polarity> (2) 
        "
	::= { pm200fr20AlmlineQsfpWarnDdmEntry 17 }


pm200fr20AlmLineRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         LINE_RX_PWR_LOW_WNG_1 <Probcause> 
        receiveFailure (41) <Alarmtype> 
        equipmentAlarm (5) <Polarity> (2) 
        "
	::= { pm200fr20AlmlineQsfpWarnDdmEntry 16 }


pm200fr20AlmLineTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         LINE_TEMP_HIGH_WNG_1 <Probcause> 
        temperatureUnacceptable (51) <Alarmtype> 
        equipmentAlarm (5) <Polarity> (2) 
        "
	::= { pm200fr20AlmlineQsfpWarnDdmEntry 9 }


pm200fr20AlmLineTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         LINE_TEMP_LOW_WNG_1 <Probcause> 
        temperatureUnacceptable (51) <Alarmtype> 
        equipmentAlarm (5) <Polarity> (2) 
        "
	::= { pm200fr20AlmlineQsfpWarnDdmEntry 8 }


pm200fr20AlmLineVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> LINE_VCC_HIGH_WNG_1
         <Probcause> powerProblem (36)
         <Alarmtype> equipmentAlarm (5) 
        <Polarity> (2) 
        "
	::= { pm200fr20AlmlineQsfpWarnDdmEntry 7 }


pm200fr20AlmLineVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> LINE_VCC_LOW_WNG_1 <Probcause> 
        powerProblem (36) <Alarmtype> equipmentAlarm 
        (5) <Polarity> (2) 
        "
	::= { pm200fr20AlmlineQsfpWarnDdmEntry 6 }


pm200fr20AlmLineTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> LINE_TX_BIAS_HIGH_WNG_1 
        <Probcause> transmitterFailure
         (56) <Alarmtype> equipmentAlarm 
        (5) <Polarity> (2) 
        "
	::= { pm200fr20AlmlineQsfpWarnDdmEntry 5 }


pm200fr20AlmLineTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> LINE_TX_BIAS_LOW_WNG_1 
        <Probcause> transmitterFailure
         (56) <Alarmtype> equipmentAlarm 
        (5) <Polarity> (2) 
        "
	::= { pm200fr20AlmlineQsfpWarnDdmEntry 4 }


pm200fr20AlmLineTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        LINE_TX_PWR_HIGH_WNG_1 <Probcause> 
        transmitterFailure (56) <Alarmtype> 
        equipmentAlarm (5) <Polarity> (2) 
        "
	::= { pm200fr20AlmlineQsfpWarnDdmEntry 3 }


pm200fr20AlmLineTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        LINE_TX_PW_LOW_WNG_1 <Probcause> 
        transmitterFailure (56) <Alarmtype> 
        equipmentAlarm (5) <Polarity> (2) 
        "
	::= { pm200fr20AlmlineQsfpWarnDdmEntry 2 }


--- *********************************************************
---     TABLE for the pm200fr20AlmclientHostLaneFault articles
--- *********************************************************

pm200fr20AlmclientHostLaneFaultTable OBJECT-TYPE
	SYNTAX  SEQUENCE OF Pm200fr20AlmclientHostLaneFaultEntry
	MAX-ACCESS not-accessible
	STATUS current
	DESCRIPTION
        "
        List of pm200fr20AlmclientHostLaneFault 
        Article
        "
	::= { pm200fr20AlmClientUrg 152 }


pm200fr20AlmclientHostLaneFaultEntry OBJECT-TYPE
	SYNTAX Pm200fr20AlmclientHostLaneFaultEntry
	MAX-ACCESS not-accessible
	STATUS current
	DESCRIPTION
        "
        Row definition for the pm200fr20AlmclientHostLaneFault 
        table
        "
	INDEX   { pm200fr20AlmclientHostLaneFaultIndex }
	::= { pm200fr20AlmclientHostLaneFaultTable 1 }


Pm200fr20AlmclientHostLaneFaultEntry ::=
	SEQUENCE {
	pm200fr20AlmclientHostLaneFaultIndex
		INTEGER,
	pm200fr20AlmOtu2eProtocDetectedPortn
		EkiOnOff,
	pm200fr20AlmOtu2ProtocDetectedPortn
		EkiOnOff,
	pm200fr20Alm10gbeProtocDetectedPortn
		EkiOnOff,
	pm200fr20AlmStm64ProtocDetectedPortn
		EkiOnOff,
	pm200fr20AlmRfDetectedPortn
		EkiOnOff,
	pm200fr20AlmLfDetectedPortn
		EkiOnOff,
	pm200fr20AlmClientLaneTxFifoErrorPortn
		EkiOnOff,
	pm200fr20AlmClientTxHostLolPortn
		EkiOnOff,
	pm200fr20AlmClientCsfDetectedPortn
		EkiOnOff,
	pm200fr20AlmClientLanesNotAlignedPortn
		EkiOnOff,
	pm200fr20AlmClientLanes6466UnlockPortn
		EkiOnOff,
	pm200fr20AlmClientLanesMarkerUnlockPortn
		EkiOnOff,
	pm200fr20AlmClientInputLossOfSigPortn
		EkiOnOff,
	pm200fr20AlmClientLossOfSyncPortn
		EkiOnOff
	}


pm200fr20AlmclientHostLaneFaultIndex OBJECT-TYPE
	SYNTAX  INTEGER(0..128)
	MAX-ACCESS  read-only
	STATUS current
	DESCRIPTION
        "
        Index definition for the pm200fr20AlmclientHostLaneFault 
        table
        "
	::= { pm200fr20AlmclientHostLaneFaultEntry 1 }


pm200fr20AlmOtu2eProtocDetectedPortn OBJECT-TYPE
	SYNTAX  EkiOnOff
	MAX-ACCESS read-only
	STATUS current
	DESCRIPTION
        "
        OTU2e Protocol Detected :This
         OID indicates an OTU2e  Protocol 
        detected on the Client Port <Help> 
        Status indicating a OTU2e protocol 
        received on the Client side <Condtype> 
        OTU2E_PROTOC_DETECTED <Probcause> 
        informationalStatus(1000) <Alarmtype> 
        other(1) <Polarity> (2)
        "
	::= { pm200fr20AlmclientHostLaneFaultEntry 17 }


pm200fr20AlmOtu2ProtocDetectedPortn OBJECT-TYPE
	SYNTAX  EkiOnOff
	MAX-ACCESS read-only
	STATUS current
	DESCRIPTION
        "
        OTU2 Protocol Detected :This OID 
        indicates an OTU2  Protocol detected 
        on the Client Port <Help> Status 
        indicating a OTU2 protocol received 
        on the Client side <Condtype> OTU2_PROTOC_DETECTED 
        <Probcause> informationalStatus(1000) 
        <Alarmtype> other(1) <Polarity> 
        (2)
        "
	::= { pm200fr20AlmclientHostLaneFaultEntry 16 }


pm200fr20Alm10gbeProtocDetectedPortn OBJECT-TYPE
	SYNTAX  EkiOnOff
	MAX-ACCESS read-only
	STATUS current
	DESCRIPTION
        "
        10GbE Protocol Detected :This
         OID indicates a 10GbE Protocol 
        detected on the Client Port <Help> 
        Status indicating a 10GbE protocol 
        received on the Client side <Condtype> 
        10GBE_PROTOC_DETECTED <Probcause> 
        informationalStatus(1000) <Alarmtype> 
        other(1) <Polarity> (2)
        "
	::= { pm200fr20AlmclientHostLaneFaultEntry 15 }


pm200fr20AlmStm64ProtocDetectedPortn OBJECT-TYPE
	SYNTAX  EkiOnOff
	MAX-ACCESS read-only
	STATUS current
	DESCRIPTION
        "
        STM64 Protocol Detected :This
         OID indicates a STM64 Protocol 
        detected on the Client Port <Help> 
        Status indicating a STM64 protocol 
        received on the Client side <Condtype> 
        STM64_PROTOC_DETECTED <Probcause> 
        informationalStatus(1000) <Alarmtype> 
        other(1) <Polarity> (2)
        "
	::= { pm200fr20AlmclientHostLaneFaultEntry 14 }


pm200fr20AlmRfDetectedPortn OBJECT-TYPE
	SYNTAX  EkiOnOff
	MAX-ACCESS read-only
	STATUS current
	DESCRIPTION
        "
        Remote Fault Signal Detected :This 
        OID indicates a Remote Fault Signal 
        is detected on the client input 
        port<Help> This alarm indicates 
        a Remote Fault Signal is detected 
        on the client input port <Condtype> 
        RF_DETECTED <Probcause> receiverFailure 
        (42) <Alarmtype> equipmentAlarm 
        (5) <Polarity> (2)
        "
	::= { pm200fr20AlmclientHostLaneFaultEntry 13 }


pm200fr20AlmLfDetectedPortn OBJECT-TYPE
	SYNTAX  EkiOnOff
	MAX-ACCESS read-only
	STATUS current
	DESCRIPTION
        "
        Local Fault Signal Detected :This 
        OID indicates a Local Fault Signal 
        is detected on the client input 
        port<Help> This alarm indicates 
        a Local Fault Signal is detected 
        on the client input port <Condtype> 
        LF_DETECTED <Probcause> receiverFailure 
        (42) <Alarmtype> equipmentAlarm 
        (5) <Polarity> (2)
        "
	::= { pm200fr20AlmclientHostLaneFaultEntry 12 }


pm200fr20AlmClientLaneTxFifoErrorPortn OBJECT-TYPE
	SYNTAX  EkiOnOff
	MAX-ACCESS read-only
	STATUS current
	DESCRIPTION
        "
        Client Host Lane Tx FIFO Error 
        :This OID indicates a Tx FIFO Error 
        on the Client Trscv Host Lane <Help> 
        Alarm indicating a Tx FIFO Error 
        on the Client Trscv Host Lane <Condtype> 
        CLIENT_LANE_TX_FIFO_ERROR <Probcause> 
        receiverFailure (42) <Alarmtype> 
        equipmentAlarm (5) <Polarity> (2) 
        "
	::= { pm200fr20AlmclientHostLaneFaultEntry 11 }


pm200fr20AlmClientTxHostLolPortn OBJECT-TYPE
	SYNTAX  EkiOnOff
	MAX-ACCESS read-only
	STATUS current
	DESCRIPTION
        "
        Client Host Lane Tx Loss Of Lock 
        :This OID indicates a Tx Loss of 
        Lock on the Client Trscv Host Lane 
        <Help> Alarm indicating a Tx Loss 
        of Lock on the Client Trscv Host 
        Lane <Condtype> CLIENT_TX_HOST_LOL 
        <Probcause> receiverFailure (42) 
        <Alarmtype> equipmentAlarm (5)
         <Polarity> (2) 
        "
	::= { pm200fr20AlmclientHostLaneFaultEntry 10 }


pm200fr20AlmClientCsfDetectedPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> CLIENT_CSF_DETECTED 
        <Probcause> receiveFailure (41) 
        <Alarmtype> other(1) <Polarity> 
        (2)
        "
	::= { pm200fr20AlmclientHostLaneFaultEntry 7 }


pm200fr20AlmClientLanesNotAlignedPortn OBJECT-TYPE
	SYNTAX  EkiOnOff
	MAX-ACCESS read-only
	STATUS current
	DESCRIPTION
        "
        Client Lanes Not Aligned :This 
        OID indicates the Client lanes
         are not aligned <Help> Alarm indicating 
        the Client lanes are not aligned 
        <Condtype> CLIENT_LANES_NOT_ALIGNED 
        <Probcause> receiveFailure (41) 
        <Alarmtype> integrityViolation
         (7) <Polarity> (2) 
        "
	::= { pm200fr20AlmclientHostLaneFaultEntry 6 }


pm200fr20AlmClientLanes6466UnlockPortn OBJECT-TYPE
	SYNTAX  EkiOnOff
	MAX-ACCESS read-only
	STATUS current
	DESCRIPTION
        "
        Client Lanes 64/66b Unlock :This 
        OID indicates the Client 64/66b 
        decoder is not lock <Help> Alarm 
        indicating the Client 64/66b decoder 
        is not lock <Condtype> CLIENT_LANES_64_66_UNLOCK 
        <Probcause> receiveFailure (41) 
        <Alarmtype> integrityViolation
         (7) <Polarity> (2) 
        "
	::= { pm200fr20AlmclientHostLaneFaultEntry 5 }


pm200fr20AlmClientLanesMarkerUnlockPortn OBJECT-TYPE
	SYNTAX  EkiOnOff
	MAX-ACCESS read-only
	STATUS current
	DESCRIPTION
        "
        Client Lanes Marker Unlock :This 
        OID indicates the Client lanes
         marker alignment is not lock <Help> 
        Alarm indicating the Client lanes 
        marker alignment is not lock <Condtype> 
        CLIENT_LANES_MARKER_UNLOCK <Probcause> 
        receiveFailure (41) <Alarmtype> 
        integrityViolation (7) <Polarity> 
        (2) 
        "
	::= { pm200fr20AlmclientHostLaneFaultEntry 4 }


pm200fr20AlmClientInputLossOfSigPortn OBJECT-TYPE
	SYNTAX  EkiOnOff
	MAX-ACCESS read-only
	STATUS current
	DESCRIPTION
        "
        Client Input Loss Of Signal :This 
        OID indicates a Loss of Signal
         is detected on the Client Trscv 
        <Help> Alarm indicating a Loss
         of Signal is detected on the Client 
        Trscv <Condtype> CLIENT_INPUT_LOSS_OF_SIG 
        <Probcause> receiveFailure (41) 
        <Alarmtype> physicalViolation (9) 
        <Polarity> (2) 
        "
	::= { pm200fr20AlmclientHostLaneFaultEntry 3 }


pm200fr20AlmClientLossOfSyncPortn OBJECT-TYPE
	SYNTAX  EkiOnOff
	MAX-ACCESS read-only
	STATUS current
	DESCRIPTION
        "
        Client Frame Alignment Loss :This 
        OID indicates the module is not 
        aligned with the incoming Client 
        signal <Help> Alarm indicating
         the module is not aligned with 
        the incoming client signal <Condtype> 
        CLIENT_LOSS_OF_SYNC <Probcause> 
        receiveFailure (41) <Alarmtype> 
        integrityViolation (7) <Polarity> 
        (2) 
        "
	::= { pm200fr20AlmclientHostLaneFaultEntry 2 }


--- *********************************************************
---     TABLE for the pm200fr20AlmlineHostLaneFault articles
--- *********************************************************

pm200fr20AlmlineHostLaneFaultTable OBJECT-TYPE
	SYNTAX  SEQUENCE OF Pm200fr20AlmlineHostLaneFaultEntry
	MAX-ACCESS not-accessible
	STATUS current
	DESCRIPTION
        "
        List of pm200fr20AlmlineHostLaneFault 
        Article
        "
	::= { pm200fr20AlmLineUrg 196 }


pm200fr20AlmlineHostLaneFaultEntry OBJECT-TYPE
	SYNTAX Pm200fr20AlmlineHostLaneFaultEntry
	MAX-ACCESS not-accessible
	STATUS current
	DESCRIPTION
        "
        Row definition for the pm200fr20AlmlineHostLaneFault 
        table
        "
	INDEX   { pm200fr20AlmlineHostLaneFaultIndex }
	::= { pm200fr20AlmlineHostLaneFaultTable 1 }


Pm200fr20AlmlineHostLaneFaultEntry ::=
	SEQUENCE {
	pm200fr20AlmlineHostLaneFaultIndex
		INTEGER,
	pm200fr20AlmLineOtu4DlomPortn
		EkiOnOff,
	pm200fr20AlmLineOchr4DlosPPortn
		EkiOnOff,
	pm200fr20AlmClientOtu4DtimPortn
		EkiOnOff,
	pm200fr20AlmOtu4DdegPortn
		EkiOnOff,
	pm200fr20AlmLineSmIaeDetectedPortn
		EkiOnOff,
	pm200fr20AlmLineSmIaeInsertedPortn
		EkiOnOff,
	pm200fr20AlmLineSmBdiDetectedPortn
		EkiOnOff,
	pm200fr20AlmLineSmBdiInsertedPortn
		EkiOnOff,
	pm200fr20AlmLineLossOfFramePortn
		EkiOnOff,
	pm200fr20AlmLineInputLossOfSignalPortn
		EkiOnOff
	}


pm200fr20AlmlineHostLaneFaultIndex OBJECT-TYPE
	SYNTAX  INTEGER(0..128)
	MAX-ACCESS  read-only
	STATUS current
	DESCRIPTION
        "
        Index definition for the pm200fr20AlmlineHostLaneFault 
        table
        "
	::= { pm200fr20AlmlineHostLaneFaultEntry 1 }


pm200fr20AlmLineOtu4DlomPortn OBJECT-TYPE
	SYNTAX  EkiOnOff
	MAX-ACCESS read-only
	STATUS current
	DESCRIPTION
        "
        OTU4 DLOM :This OID indicates
         that a Loss Of Multiframe has
         been detected on line port <Help> 
         This alarm indicates if a Loss 
        Of Multiframe has been detected 
        on the line port <Condtype> LINE_OTU4_DLOM 
        <Probcause> equipmentMalfunction(16) 
        <Alarmtype> equipmentAlarm (5)
         <Polarity> (2) 
        "
	::= { pm200fr20AlmlineHostLaneFaultEntry 17 }


pm200fr20AlmLineOchr4DlosPPortn OBJECT-TYPE
	SYNTAX  EkiOnOff
	MAX-ACCESS read-only
	STATUS current
	DESCRIPTION
        "
        Ochr4 - DLOS-P :This OID indicates 
        that a Transmitter failure has
         been detected on line port <Help> 
         This alarm indicates if a Transmitter 
        Failure has been detected on the 
        line port <Condtype> LINE_OCHR4_DLOS_P 
        <Probcause> equipmentMalfunction(16) 
        <Alarmtype> other (1) <Polarity> 
        (2) 
        "
	::= { pm200fr20AlmlineHostLaneFaultEntry 12 }


pm200fr20AlmClientOtu4DtimPortn OBJECT-TYPE
	SYNTAX  EkiOnOff
	MAX-ACCESS read-only
	STATUS current
	DESCRIPTION
        "
        OTU4 DTIM :This OID indicates
         that a Trace Identifier Mismatch 
        has been detected on line port
         <Help>  This alarm indicates if 
        a Trace Identifier Mismatch has 
        been detected on the line port
         <Condtype> CLIENT_OTU4_DTIM <Probcause> 
        other(1) <Alarmtype> other (1)
         <Polarity> (2) 
        "
	::= { pm200fr20AlmlineHostLaneFaultEntry 9 }


pm200fr20AlmOtu4DdegPortn OBJECT-TYPE
	SYNTAX  EkiOnOff
	MAX-ACCESS read-only
	STATUS current
	DESCRIPTION
        "
        OTU4 DDEG :This OID indicates
         that a Signal Degrade has been 
        detected on line port <Help>  This 
        alarm indicates if a Signal Degrade 
        has been detected upon threshold 
        and confirmation parameters on
         the line port <Condtype> OTU4_DDEG 
        <Probcause> degradedSignal(13)
         <Alarmtype> other (1) <Polarity> 
        (2) 
        "
	::= { pm200fr20AlmlineHostLaneFaultEntry 8 }


pm200fr20AlmLineSmIaeDetectedPortn OBJECT-TYPE
	SYNTAX  EkiOnOff
	MAX-ACCESS read-only
	STATUS current
	DESCRIPTION
        "
        Line SM IAE Detected :This OID 
        indicates a SM Incoming Alignment 
        Error is detected on the incoming 
        Line signal <Help> Alarm indicating 
        a SM Incoming Alignment Error is 
        detected on the incoming Line signal 
        <Condtype> LINE_SM_IAE_DETECTED 
        <Probcause> receiveFailure (41) 
        <Alarmtype> integrityViolation
         (7) <Polarity> (2) 
        "
	::= { pm200fr20AlmlineHostLaneFaultEntry 7 }


pm200fr20AlmLineSmIaeInsertedPortn OBJECT-TYPE
	SYNTAX  EkiOnOff
	MAX-ACCESS read-only
	STATUS current
	DESCRIPTION
        "
        Line SM IAE Inserted :This OID 
        indicates a SM Incoming Alignment 
        Error is inserted on the outgoing 
        Line signal <Help> Status indicating 
        a SM Incoming Alignment Error is 
        inserted on the outgoing Line signal 
        <Condtype> LINE_SM_IAE_INSERTED 
        <Probcause> informationalStatus(1000) 
        <Alarmtype> other (1) <Polarity> 
        (2) 
        "
	::= { pm200fr20AlmlineHostLaneFaultEntry 6 }


pm200fr20AlmLineSmBdiDetectedPortn OBJECT-TYPE
	SYNTAX  EkiOnOff
	MAX-ACCESS read-only
	STATUS current
	DESCRIPTION
        "
        Line SM BDI Detected :This OID 
        indicates a SM Backward Defect
         Indication is detected on the
         incoming Line signal <Help> Alarm 
        indicating a SM Backward Defect 
        Indication is detected on the incoming 
        Line signal <Condtype> LINE_SM_BDI_DETECTED 
        <Probcause> receiveFailure (41) 
        <Alarmtype> integrityViolation
         (7) <Polarity> (2) 
        "
	::= { pm200fr20AlmlineHostLaneFaultEntry 5 }


pm200fr20AlmLineSmBdiInsertedPortn OBJECT-TYPE
	SYNTAX  EkiOnOff
	MAX-ACCESS read-only
	STATUS current
	DESCRIPTION
        "
        Line SM BDI Inserted :This OID 
        indicates a SM Backward Defect
         Indication is inserted on the
         outgoing Line signal <Help> Status 
        indicating a SM Backward Defect 
        Indication is inserted on the outgoing 
        Line signal <Condtype> LINE_SM_BDI_INSERTED 
        <Probcause> informationalStatus(1000) 
        <Alarmtype> other (1) <Polarity> 
        (2) 
        "
	::= { pm200fr20AlmlineHostLaneFaultEntry 4 }


pm200fr20AlmLineLossOfFramePortn OBJECT-TYPE
	SYNTAX  EkiOnOff
	MAX-ACCESS read-only
	STATUS current
	DESCRIPTION
        "
        Line Loss Of Frame :This OID indicates 
        the module is not aligned with
         the incoming Line signal <Help> 
        Alarm indicating the module is
         not aligned with the incoming
         Line signal <Condtype> LINE_LOSS_OF_FRAME 
        <Probcause> receiveFailure (41) 
        <Alarmtype> integrityViolation
         (7) <Polarity> (2) 
        "
	::= { pm200fr20AlmlineHostLaneFaultEntry 3 }


pm200fr20AlmLineInputLossOfSignalPortn OBJECT-TYPE
	SYNTAX  EkiOnOff
	MAX-ACCESS read-only
	STATUS current
	DESCRIPTION
        "
        Line Input Loss Of Signal :This 
        OID indicates a Loss of Signal
         is detected on the Line Trscv
         <Help> Alarm indicating a Loss 
        of Signal is detected on the Line 
        Trscv <Condtype> LINE_INPUT_LOSS_OF_SIGNAL 
        <Probcause> receiveFailure (41) 
        <Alarmtype> physicalViolation (9) 
        <Polarity> (2) 
        "
	::= { pm200fr20AlmlineHostLaneFaultEntry 2 }


--- *********************************************************
---     TABLE for the pm200fr20AlmlineOdu4Alm articles
--- *********************************************************

pm200fr20AlmlineOdu4AlmTable OBJECT-TYPE
	SYNTAX  SEQUENCE OF Pm200fr20AlmlineOdu4AlmEntry
	MAX-ACCESS not-accessible
	STATUS current
	DESCRIPTION
        "
        List of pm200fr20AlmlineOdu4Alm 
        Article
        "
	::= { pm200fr20AlmLineUrg 208 }


pm200fr20AlmlineOdu4AlmEntry OBJECT-TYPE
	SYNTAX Pm200fr20AlmlineOdu4AlmEntry
	MAX-ACCESS not-accessible
	STATUS current
	DESCRIPTION
        "
        Row definition for the pm200fr20AlmlineOdu4Alm 
        table
        "
	INDEX   { pm200fr20AlmlineOdu4AlmIndex }
	::= { pm200fr20AlmlineOdu4AlmTable 1 }


Pm200fr20AlmlineOdu4AlmEntry ::=
	SEQUENCE {
	pm200fr20AlmlineOdu4AlmIndex
		INTEGER,
	pm200fr20AlmLineOdu4DlckPortn
		EkiOnOff,
	pm200fr20AlmLineOdu4IlckPortn
		EkiOnOff,
	pm200fr20AlmLineOdu4DbdiPortn
		EkiOnOff,
	pm200fr20AlmLineOdu4IbdiPortn
		EkiOnOff,
	pm200fr20AlmLineOdu4DociPortn
		EkiOnOff,
	pm200fr20AlmLineOdu4IociPortn
		EkiOnOff,
	pm200fr20AlmLineOdu4DaisPortn
		EkiOnOff,
	pm200fr20AlmLineOdu4DtimPortn
		EkiOnOff,
	pm200fr20AlmLineOdu4IaisPortn
		EkiOnOff,
	pm200fr20AlmLineOdu4DdegPortn
		EkiOnOff,
	pm200fr20AlmLineOdu4DplmPortn
		EkiOnOff
	}


pm200fr20AlmlineOdu4AlmIndex OBJECT-TYPE
	SYNTAX  INTEGER(0..128)
	MAX-ACCESS  read-only
	STATUS current
	DESCRIPTION
        "
        Index definition for the pm200fr20AlmlineOdu4Alm 
        table
        "
	::= { pm200fr20AlmlineOdu4AlmEntry 1 }


pm200fr20AlmLineOdu4DlckPortn OBJECT-TYPE
	SYNTAX  EkiOnOff
	MAX-ACCESS read-only
	STATUS current
	DESCRIPTION
        "
        ODU4 DLCK :This OID indicates
         that a Locked Indication has been 
        detected on line port <Help>  This 
        alarm indicates if a Locked Indication 
        has been detected on the line port 
        <Condtype> LINE_ODU4_DLCK <Probcause> 
        other(1) <Alarmtype> other(1) <Polarity> 
        (2)
        "
	::= { pm200fr20AlmlineOdu4AlmEntry 17 }


pm200fr20AlmLineOdu4IlckPortn OBJECT-TYPE
	SYNTAX  EkiOnOff
	MAX-ACCESS read-only
	STATUS current
	DESCRIPTION
        "
        ODU4 ILCK :This OID indicates
         that a Locked Indication has been 
        inserted on line port <Help>  This 
        alarm indicates if a Locked Indication 
        has been inserted on the line port 
        <Condtype> LINE_ODU4_ILCK <Probcause> 
        other(1) <Alarmtype> other(1) <Polarity> 
        (2)
        "
	::= { pm200fr20AlmlineOdu4AlmEntry 16 }


pm200fr20AlmLineOdu4DbdiPortn OBJECT-TYPE
	SYNTAX  EkiOnOff
	MAX-ACCESS read-only
	STATUS current
	DESCRIPTION
        "
        ODU4 DBDI :This OID indicates
         that a Backward Defect Indication 
        has been detected on line port<Help> 
         This alarm indicates if a Backward 
        Defect Indication has been detected 
        on the line port <Condtype> LINE_ODU4_DBDI 
        <Probcause> other(1) <Alarmtype> 
        other(1) <Polarity> (2)
        "
	::= { pm200fr20AlmlineOdu4AlmEntry 15 }


pm200fr20AlmLineOdu4IbdiPortn OBJECT-TYPE
	SYNTAX  EkiOnOff
	MAX-ACCESS read-only
	STATUS current
	DESCRIPTION
        "
        ODU4 IBDI :This OID indicates
         that a Backward Defect Indication 
        has been inserted on line port
         <Help>  This alarm indicates if 
        a Backward Defect Indication has 
        been inserted on the line port
         <Condtype> LINE_ODU4_IBDI <Probcause> 
        other(1) <Alarmtype> other(1) <Polarity> 
        (2)
        "
	::= { pm200fr20AlmlineOdu4AlmEntry 14 }


pm200fr20AlmLineOdu4DociPortn OBJECT-TYPE
	SYNTAX  EkiOnOff
	MAX-ACCESS read-only
	STATUS current
	DESCRIPTION
        "
        ODU4 DOCI :This OID indicates
         that a Open Connection has been 
        detected on line port <Help>  This 
        alarm indicates if an Open Connection 
        Indication has been detected on 
        the line port <Condtype> LINE_ODU4_DOCI 
        <Probcause> other(1) <Alarmtype> 
        other(1) <Polarity> (2)
        "
	::= { pm200fr20AlmlineOdu4AlmEntry 13 }


pm200fr20AlmLineOdu4IociPortn OBJECT-TYPE
	SYNTAX  EkiOnOff
	MAX-ACCESS read-only
	STATUS current
	DESCRIPTION
        "
        ODU4 IOCI :This OID indicates
         that an Open Connection has been 
        inserted on line port <Help>  This 
        alarm indicates if an Open Connection 
        Indication has been inserted on 
        the line port <Condtype> LINE_ODU4_IOCI 
        <Probcause> other(1) <Alarmtype> 
        other(1) <Polarity> (2)
        "
	::= { pm200fr20AlmlineOdu4AlmEntry 12 }


pm200fr20AlmLineOdu4DaisPortn OBJECT-TYPE
	SYNTAX  EkiOnOff
	MAX-ACCESS read-only
	STATUS current
	DESCRIPTION
        "
        ODU4 DAIS :This OID indicates
         that a Alarm Indication SIgnal 
        has been detected on line port<Help> 
         This alarm indicates if an Alarm 
        Indication Signal has been detected 
        on the line port <Condtype> LINE_ODU4_DAIS 
        <Probcause> equipmentMalfunction(16) 
        <Alarmtype> equipmentAlarm (5)
         <Polarity> (2) 
        "
	::= { pm200fr20AlmlineOdu4AlmEntry 10 }


pm200fr20AlmLineOdu4DtimPortn OBJECT-TYPE
	SYNTAX  EkiOnOff
	MAX-ACCESS read-only
	STATUS current
	DESCRIPTION
        "
        ODU4 DTIM :This OID indicates
         that a Trace Identifier Mismatch 
        has been detected on line port<Help> 
         This alarm indicates if an Trace 
        Identifier Mismatch has been detected 
        on the line port <Condtype> LINE_ODU4_DTIM 
        <Probcause> equipmentMalfunction(16) 
        <Alarmtype> equipmentAlarm (5)
         <Polarity> (2) 
        "
	::= { pm200fr20AlmlineOdu4AlmEntry 9 }


pm200fr20AlmLineOdu4IaisPortn OBJECT-TYPE
	SYNTAX  EkiOnOff
	MAX-ACCESS read-only
	STATUS current
	DESCRIPTION
        "
        ODU4 IAIS :This OID indicates
         that an Alarm Indication Signal 
        has been inserted on line port
         <Help>  This alarm indicates if 
        an Alarm Indication Signal has
         been inserted on the line port 
        <Condtype> LINE_ODU4_IAIS <Probcause> 
        equipmentMalfunction(16) <Alarmtype> 
        equipmentAlarm (5) <Polarity> (2) 
        "
	::= { pm200fr20AlmlineOdu4AlmEntry 8 }


pm200fr20AlmLineOdu4DdegPortn OBJECT-TYPE
	SYNTAX  EkiOnOff
	MAX-ACCESS read-only
	STATUS current
	DESCRIPTION
        "
        ODU4 DDEG :This OID indicates
         that a Signal Degrade has been 
        detected on line port<Help> Alarm 
        indicating a Signal Degrade upon 
        threshold and confirmation parameters 
        <Condtype> LINE_ODU4_DDEG <Probcause> 
        degradedSignal(13) <Alarmtype>
         other(1) <Polarity> (2)
        "
	::= { pm200fr20AlmlineOdu4AlmEntry 6 }


pm200fr20AlmLineOdu4DplmPortn OBJECT-TYPE
	SYNTAX  EkiOnOff
	MAX-ACCESS read-only
	STATUS current
	DESCRIPTION
        "
        ODU4 DPLM :This OID indicates
         a Payload Mismatch is detected 
        on the line port<Help> Alarm indicating 
        a Payload Mismatch <Condtype> LINE_ODU4_DPLM 
        <Probcause> receiveFailure (41) 
        <Alarmtype> equipmentAlarm (5)
         <Polarity> (2) 
        "
	::= { pm200fr20AlmlineOdu4AlmEntry 4 }


--- *********************************************************
---     TABLE for the pm200fr20AlmclientSfpAlmDdm articles
--- *********************************************************

pm200fr20AlmclientSfpAlmDdmTable OBJECT-TYPE
	SYNTAX  SEQUENCE OF Pm200fr20AlmclientSfpAlmDdmEntry
	MAX-ACCESS not-accessible
	STATUS current
	DESCRIPTION
        "
        List of pm200fr20AlmclientSfpAlmDdm 
        Article
        "
	::= { pm200fr20AlmClientUrg 240 }


pm200fr20AlmclientSfpAlmDdmEntry OBJECT-TYPE
	SYNTAX Pm200fr20AlmclientSfpAlmDdmEntry
	MAX-ACCESS not-accessible
	STATUS current
	DESCRIPTION
        "
        Row definition for the pm200fr20AlmclientSfpAlmDdm 
        table
        "
	INDEX   { pm200fr20AlmclientSfpAlmDdmIndex }
	::= { pm200fr20AlmclientSfpAlmDdmTable 1 }


Pm200fr20AlmclientSfpAlmDdmEntry ::=
	SEQUENCE {
	pm200fr20AlmclientSfpAlmDdmIndex
		INTEGER,
	pm200fr20AlmRxPwrHighAlaPortn
		EkiOnOff,
	pm200fr20AlmRxPwrLowAlaPortn
		EkiOnOff,
	pm200fr20AlmTempHighAlaPortn
		EkiOnOff,
	pm200fr20AlmTempLowAlaPortn
		EkiOnOff,
	pm200fr20AlmVccHighAlaPortn
		EkiOnOff,
	pm200fr20AlmVccLowAlaPortn
		EkiOnOff,
	pm200fr20AlmTxBiasHighAlaPortn
		EkiOnOff,
	pm200fr20AlmTxBiasLowAlaPortn
		EkiOnOff,
	pm200fr20AlmTxPwrHighAlaPortn
		EkiOnOff,
	pm200fr20AlmTxPwrLowAlaPortn
		EkiOnOff
	}


pm200fr20AlmclientSfpAlmDdmIndex OBJECT-TYPE
	SYNTAX  INTEGER(0..128)
	MAX-ACCESS  read-only
	STATUS current
	DESCRIPTION
        "
        Index definition for the pm200fr20AlmclientSfpAlmDdm 
        table
        "
	::= { pm200fr20AlmclientSfpAlmDdmEntry 1 }


pm200fr20AlmRxPwrHighAlaPortn OBJECT-TYPE
	SYNTAX  EkiOnOff
	MAX-ACCESS read-only
	STATUS current
	DESCRIPTION
        "
        Client Trscv Rx Power High :This 
        OID indicates that the Trscv input 
        power of port is higher than the 
        threshold value written in the
         Trscv EEPROM <Help> Alarm indicating 
        that the Trscv input power of port 
        is higher than the threshold value 
        written in the Trscv EEPROM <Condtype> 
        RX_PWR_HIGH_ALA_1 <Probcause> receiveFailure 
        (41) <Alarmtype> equipmentAlarm 
        (5) <Polarity> (2) 
        "
	::= { pm200fr20AlmclientSfpAlmDdmEntry 17 }


pm200fr20AlmRxPwrLowAlaPortn OBJECT-TYPE
	SYNTAX  EkiOnOff
	MAX-ACCESS read-only
	STATUS current
	DESCRIPTION
        "
        Client Trscv Rx Power Low :This 
        OID indicates that the Trscv input 
        power of port is lower than the 
        threshold value written in the
         Trscv EEPROM <Help> Alarm indicating 
        that the Trscv input power of port 
        is lower than the threshold value 
        written in the Trscv EEPROM <Condtype> 
        RX_PWR_LOW_ALA_1 <Probcause> receiveFailure 
        (41) <Alarmtype> equipmentAlarm 
        (5) <Polarity> (2) 
        "
	::= { pm200fr20AlmclientSfpAlmDdmEntry 16 }


pm200fr20AlmTempHighAlaPortn OBJECT-TYPE
	SYNTAX  EkiOnOff
	MAX-ACCESS read-only
	STATUS current
	DESCRIPTION
        "
        Client Trscv Temp High :This OID 
        indicates that the Trscv temperature 
        of port is higher than the threshold 
        value written in the Trscv EEPROM 
        <Help> Alarm indicating that the 
        Trscv temperature of port is higher 
        than the threshold value written 
        in the Trscv EEPROM <Condtype>
         TEMP_HIGH_ALA_1 <Probcause> temperatureUnacceptable 
        (51) <Alarmtype> equipmentAlarm 
        (5) <Polarity> (2) 
        "
	::= { pm200fr20AlmclientSfpAlmDdmEntry 9 }


pm200fr20AlmTempLowAlaPortn OBJECT-TYPE
	SYNTAX  EkiOnOff
	MAX-ACCESS read-only
	STATUS current
	DESCRIPTION
        "
        Client Trscv Temp Low :This OID 
        indicates that the Trscv temperature 
        of port is lower than the threshold 
        value written in the Trscv EEPROM 
        <Help> Alarm indicating that the 
        Trscv temperature of port is lower 
        than the threshold value written 
        in the Trscv EEPROM <Condtype>
         TEMP_LOW_ALA_1 <Probcause> temperatureUnacceptable 
        (51) <Alarmtype> equipmentAlarm 
        (5) <Polarity> (2) 
        "
	::= { pm200fr20AlmclientSfpAlmDdmEntry 8 }


pm200fr20AlmVccHighAlaPortn OBJECT-TYPE
	SYNTAX  EkiOnOff
	MAX-ACCESS read-only
	STATUS current
	DESCRIPTION
        "
        Client Trscv Power Supply High 
        :This OID indicates that the Trscv 
        power supply of port is higher
         than the threshold value written 
        in the Trscv EEPROM <Help> Alarm 
        indicating that the Trscv power 
        supply of port is higher than the 
        threshold value written in the
         Trscv EEPROM <Condtype> VCC_HIGH_ALA_1 
        <Probcause> powerProblem (36) <Alarmtype> 
        equipmentAlarm (5) <Polarity> (2) 
        "
	::= { pm200fr20AlmclientSfpAlmDdmEntry 7 }


pm200fr20AlmVccLowAlaPortn OBJECT-TYPE
	SYNTAX  EkiOnOff
	MAX-ACCESS read-only
	STATUS current
	DESCRIPTION
        "
        Client Trscv Power Supply Low
         :This OID indicates that the Trscv 
        power supply of port is lower than 
        the threshold value written in
         the Trscv EEPROM <Help> Alarm
         indicating that the Trscv power 
        supply of port is lower than the 
        threshold value written in the
         Trscv EEPROM <Condtype> VCC_LOW_ALA_1 
        <Probcause> powerProblem (36) <Alarmtype> 
        equipmentAlarm (5) <Polarity> (2) 
        "
	::= { pm200fr20AlmclientSfpAlmDdmEntry 6 }


pm200fr20AlmTxBiasHighAlaPortn OBJECT-TYPE
	SYNTAX  EkiOnOff
	MAX-ACCESS read-only
	STATUS current
	DESCRIPTION
        "
        Client Trscv Bias High :This OID 
        indicates that the Trscv laser
         bias current of port is higher 
        than the threshold value written 
        in the Trscv EEPROM <Help> Alarm 
        indicating that the Trscv laser 
        bias current of port is higher
         than the threshold value written 
        in the Trscv EEPROM <Condtype>
         TX_BIAS_HIGH_ALA_1 <Probcause> 
        transmitterFailure (56) <Alarmtype> 
        equipmentAlarm (5) <Polarity> (2) 
        "
	::= { pm200fr20AlmclientSfpAlmDdmEntry 5 }


pm200fr20AlmTxBiasLowAlaPortn OBJECT-TYPE
	SYNTAX  EkiOnOff
	MAX-ACCESS read-only
	STATUS current
	DESCRIPTION
        "
        Client Trscv Bias Low :This OID 
        indicates that the Trscv laser
         bias current of port is lower
         than the threshold value written 
        in the Trscv EEPROM <Help> Alarm 
        indicating that the Trscv laser 
        bias current of port is lower than 
        the threshold value written in
         the Trscv EEPROM <Condtype> TX_BIAS_LOW_ALA_1 
        <Probcause> transmitterFailure
         (56) <Alarmtype> equipmentAlarm 
        (5) <Polarity> (2) 
        "
	::= { pm200fr20AlmclientSfpAlmDdmEntry 4 }


pm200fr20AlmTxPwrHighAlaPortn OBJECT-TYPE
	SYNTAX  EkiOnOff
	MAX-ACCESS read-only
	STATUS current
	DESCRIPTION
        "
        Client Trscv Tx Power High :This 
        OID indicates that the Trscv output 
        power of port is higher than the 
        threshold value written in the
         Trscv EEPROM <Help> Alarm indicating 
        that the Trscv output power of
         port is higher than the threshold 
        value written in the Trscv EEPROM 
        <Condtype> TX_PWR_HIGH_ALA_1 <Probcause> 
        transmitterFailure (56) <Alarmtype> 
        equipmentAlarm (5) <Polarity> (2) 
        "
	::= { pm200fr20AlmclientSfpAlmDdmEntry 3 }


pm200fr20AlmTxPwrLowAlaPortn OBJECT-TYPE
	SYNTAX  EkiOnOff
	MAX-ACCESS read-only
	STATUS current
	DESCRIPTION
        "
        Client Trscv Tx Power Low :This 
        OID indicates that the Trscv output 
        power of port is lower than the 
        threshold value written in the
         Trscv EEPROM <Help> Alarm indicating 
        that the Trscv output power of
         port is lower than the threshold 
        value written in the Trscv EEPROM 
        <Condtype> TX_PWR_LOW_ALA_1 <Probcause> 
        transmitterFailure (56) <Alarmtype> 
        equipmentAlarm (5) <Polarity> (2) 
        "
	::= { pm200fr20AlmclientSfpAlmDdmEntry 2 }


--- *********************************************************
---     TABLE for the pm200fr20AlmclientSfpWarnDdm articles
--- *********************************************************

pm200fr20AlmclientSfpWarnDdmTable OBJECT-TYPE
	SYNTAX  SEQUENCE OF Pm200fr20AlmclientSfpWarnDdmEntry
	MAX-ACCESS not-accessible
	STATUS current
	DESCRIPTION
        "
        List of pm200fr20AlmclientSfpWarnDdm 
        Article
        "
	::= { pm200fr20AlmClientNurg 272 }


pm200fr20AlmclientSfpWarnDdmEntry OBJECT-TYPE
	SYNTAX Pm200fr20AlmclientSfpWarnDdmEntry
	MAX-ACCESS not-accessible
	STATUS current
	DESCRIPTION
        "
        Row definition for the pm200fr20AlmclientSfpWarnDdm 
        table
        "
	INDEX   { pm200fr20AlmclientSfpWarnDdmIndex }
	::= { pm200fr20AlmclientSfpWarnDdmTable 1 }


Pm200fr20AlmclientSfpWarnDdmEntry ::=
	SEQUENCE {
	pm200fr20AlmclientSfpWarnDdmIndex
		INTEGER,
	pm200fr20AlmRxPwrHighWngPortn
		EkiOnOff,
	pm200fr20AlmRxPwrLowWngPortn
		EkiOnOff,
	pm200fr20AlmTempHighWngPortn
		EkiOnOff,
	pm200fr20AlmTempLowWngPortn
		EkiOnOff,
	pm200fr20AlmVccHighWngPortn
		EkiOnOff,
	pm200fr20AlmVccLowWngPortn
		EkiOnOff,
	pm200fr20AlmTxBiasHighWngPortn
		EkiOnOff,
	pm200fr20AlmTxBiasLowWngPortn
		EkiOnOff,
	pm200fr20AlmTxPwrHighWngPortn
		EkiOnOff,
	pm200fr20AlmTxPwLowWngPortn
		EkiOnOff
	}


pm200fr20AlmclientSfpWarnDdmIndex OBJECT-TYPE
	SYNTAX  INTEGER(0..128)
	MAX-ACCESS  read-only
	STATUS current
	DESCRIPTION
        "
        Index definition for the pm200fr20AlmclientSfpWarnDdm 
        table
        "
	::= { pm200fr20AlmclientSfpWarnDdmEntry 1 }


pm200fr20AlmRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         RX_PWR_HIGH_WNG_1 <Probcause>
         receiveFailure (41) <Alarmtype> 
        equipmentAlarm (5) <Polarity> (2) 
        "
	::= { pm200fr20AlmclientSfpWarnDdmEntry 17 }


pm200fr20AlmRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         RX_PWR_LOW_WNG_1 <Probcause> receiveFailure 
        (41) <Alarmtype> equipmentAlarm 
        (5) <Polarity> (2) 
        "
	::= { pm200fr20AlmclientSfpWarnDdmEntry 16 }


pm200fr20AlmTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         TEMP_HIGH_WNG_1 <Probcause> temperatureUnacceptable 
        (51) <Alarmtype> equipmentAlarm 
        (5) <Polarity> (2) 
        "
	::= { pm200fr20AlmclientSfpWarnDdmEntry 9 }


pm200fr20AlmTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         TEMP_LOW_WNG_1 <Probcause> temperatureUnacceptable 
        (51) <Alarmtype> equipmentAlarm 
        (5) <Polarity> (2) 
        "
	::= { pm200fr20AlmclientSfpWarnDdmEntry 8 }


pm200fr20AlmVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> VCC_HIGH_WNG_1 <Probcause> 
        powerProblem (36) <Alarmtype> equipmentAlarm 
        (5) <Polarity> (2) 
        "
	::= { pm200fr20AlmclientSfpWarnDdmEntry 7 }


pm200fr20AlmVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> VCC_LOW_WNG_1 <Probcause> 
        powerProblem (36) <Alarmtype> equipmentAlarm 
        (5) <Polarity> (2) 
        "
	::= { pm200fr20AlmclientSfpWarnDdmEntry 6 }


pm200fr20AlmTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> TX_BIAS_HIGH_WNG_1 
        <Probcause> transmitterFailure
         (56) <Alarmtype> equipmentAlarm 
        (5) <Polarity> (2) 
        "
	::= { pm200fr20AlmclientSfpWarnDdmEntry 5 }


pm200fr20AlmTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> TX_BIAS_LOW_WNG_1 
        <Probcause> transmitterFailure
         (56) <Alarmtype> equipmentAlarm 
        (5) <Polarity> (2) 
        "
	::= { pm200fr20AlmclientSfpWarnDdmEntry 4 }


pm200fr20AlmTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        TX_PWR_HIGH_WNG_1 <Probcause> transmitterFailure 
        (56) <Alarmtype> equipmentAlarm 
        (5) <Polarity> (2) 
        "
	::= { pm200fr20AlmclientSfpWarnDdmEntry 3 }


pm200fr20AlmTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        TX_PW_LOW_WNG_1 <Probcause> transmitterFailure 
        (56) <Alarmtype> equipmentAlarm 
        (5) <Polarity> (2) 
        "
	::= { pm200fr20AlmclientSfpWarnDdmEntry 2 }


--- *********************************************************
---     TABLE for the pm200fr20AlmclientOtnAlm articles
--- *********************************************************

pm200fr20AlmclientOtnAlmTable OBJECT-TYPE
	SYNTAX  SEQUENCE OF Pm200fr20AlmclientOtnAlmEntry
	MAX-ACCESS not-accessible
	STATUS current
	DESCRIPTION
        "
        List of pm200fr20AlmclientOtnAlm 
        Article
        "
	::= { pm200fr20AlmClientUrg 304 }


pm200fr20AlmclientOtnAlmEntry OBJECT-TYPE
	SYNTAX Pm200fr20AlmclientOtnAlmEntry
	MAX-ACCESS not-accessible
	STATUS current
	DESCRIPTION
        "
        Row definition for the pm200fr20AlmclientOtnAlm 
        table
        "
	INDEX   { pm200fr20AlmclientOtnAlmIndex }
	::= { pm200fr20AlmclientOtnAlmTable 1 }


Pm200fr20AlmclientOtnAlmEntry ::=
	SEQUENCE {
	pm200fr20AlmclientOtnAlmIndex
		INTEGER,
	pm200fr20AlmClientOtu2eDlomPortn
		EkiOnOff
	}


pm200fr20AlmclientOtnAlmIndex OBJECT-TYPE
	SYNTAX  INTEGER(0..128)
	MAX-ACCESS  read-only
	STATUS current
	DESCRIPTION
        "
        Index definition for the pm200fr20AlmclientOtnAlm 
        table
        "
	::= { pm200fr20AlmclientOtnAlmEntry 1 }


pm200fr20AlmClientOtu2eDlomPortn OBJECT-TYPE
	SYNTAX  EkiOnOff
	MAX-ACCESS read-only
	STATUS current
	DESCRIPTION
        "
        DLOM :This OID indicates that
         a Loss Of Multiframe has been
         detected on client port<Help>
          This alarm indicates if a Loss 
        Of Multiframe has been detected 
        on the client port <Condtype> CLIENT_OTU2E_DLOM 
        <Probcause> receiveFailure (41) 
        <Alarmtype> equipmentAlarm (5)
         <Polarity> (2) 
        "
	::= { pm200fr20AlmclientOtnAlmEntry 2 }


--- *****************************************************
---     LEAF for the modFanFail article
--- *****************************************************
pm200fr20AlmmodFanFail OBJECT IDENTIFIER ::= { pm200fr20AlmOtherUrg 336 }




pm200fr20AlmFanHighSpeed OBJECT-TYPE
	  SYNTAX EkiOnOff
	  MAX-ACCESS read-only
	  STATUS current
	  DESCRIPTION
        "
        Fan High Speed :This OID indicates 
        the fan is blowing at high speed 
        <Help> This alarm indicates the 
        fan is blowing at high speed <Condtype> 
        FAN_HIGH_SPEED <Probcause> other 
        (1) <Alarmtype> other (1) <Polarity> 
        (2) 
        "
	  ::= { pm200fr20AlmmodFanFail 2 }



pm200fr20AlmFanFail OBJECT-TYPE
	  SYNTAX EkiOnOff
	  MAX-ACCESS read-only
	  STATUS current
	  DESCRIPTION
        "
        Fan Module Failure :This OID indicates 
        that the FAN unit inside the module 
        is in fail condition  <Help>  This 
        alarm indicates that the FAN is 
        in a fail condition. <Condtype> 
        FAN_FAIL <Probcause> heatingVentCoolingSystemProblem 
        (22) <Alarmtype> equipmentAlarm 
        (5) <Polarity> (2) 
        "
	  ::= { pm200fr20AlmmodFanFail 1 }








--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm200fr20CtrlconfMgnt1 OBJECT IDENTIFIER ::= { pm200fr20CtrlOther 1 }




pm200fr20CtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm200fr20CtrlconfMgnt1 14 }



pm200fr20CtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm200fr20CtrlconfMgnt1 10 }



pm200fr20CtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm200fr20CtrlconfMgnt1 2 }



pm200fr20CtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm200fr20CtrlconfMgnt1 1 }



--- *****************************************************
---     LEAF for the synth4 article
--- *****************************************************
pm200fr20Ctrlsynth4 OBJECT IDENTIFIER ::= { pm200fr20CtrlOther 4 }




pm200fr20CtrlCorrelatOff OBJECT-TYPE
	  SYNTAX EkiOnOff
	  MAX-ACCESS read-write
	  STATUS current
	  DESCRIPTION
        "
        Disable Alarm Correlation :This 
        OID disables the alarm correlation 
        in the PM.
        "
	  ::= { pm200fr20Ctrlsynth4 2 }



pm200fr20CtrlCorrelatOn OBJECT-TYPE
	  SYNTAX EkiOnOff
	  MAX-ACCESS read-write
	  STATUS current
	  DESCRIPTION
        "
        Enable Alarm Correlation :This 
        OID enables the alarm correlation 
        in the PM.
        "
	  ::= { pm200fr20Ctrlsynth4 1 }



--- *****************************************************
---     LEAF for the swMgnt article
--- *****************************************************
pm200fr20CtrlswMgnt OBJECT IDENTIFIER ::= { pm200fr20CtrlOther 5 }




pm200fr20CtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm200fr20CtrlswMgnt 6 }



pm200fr20CtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm200fr20CtrlswMgnt 5 }



pm200fr20CtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm200fr20CtrlswMgnt 3 }



pm200fr20CtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm200fr20CtrlswMgnt 2 }



--- *****************************************************
---     LEAF for the gwMgnt article
--- *****************************************************
pm200fr20CtrlgwMgnt OBJECT IDENTIFIER ::= { pm200fr20CtrlOther 6 }




pm200fr20CtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm200fr20CtrlgwMgnt 8 }



pm200fr20CtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm200fr20CtrlgwMgnt 7 }



pm200fr20CtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm200fr20CtrlgwMgnt 6 }



pm200fr20CtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm200fr20CtrlgwMgnt 5 }



pm200fr20CtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm200fr20CtrlgwMgnt 1 }



--- *********************************************************
---     TABLE for the pm200fr20CtrlaccessLoop articles
--- *********************************************************

pm200fr20CtrlaccessLoopTable OBJECT-TYPE
	SYNTAX  SEQUENCE OF Pm200fr20CtrlaccessLoopEntry
	MAX-ACCESS not-accessible
	STATUS current
	DESCRIPTION
        "
        List of pm200fr20CtrlaccessLoop 
        Article
        "
	::= { pm200fr20CtrlClient 16 }


pm200fr20CtrlaccessLoopEntry OBJECT-TYPE
	SYNTAX Pm200fr20CtrlaccessLoopEntry
	MAX-ACCESS not-accessible
	STATUS current
	DESCRIPTION
        "
        Row definition for the pm200fr20CtrlaccessLoop 
        table
        "
	INDEX   { pm200fr20CtrlaccessLoopIndex }
	::= { pm200fr20CtrlaccessLoopTable 1 }


Pm200fr20CtrlaccessLoopEntry ::=
	SEQUENCE {
	pm200fr20CtrlaccessLoopIndex
		INTEGER,
	pm200fr20CtrlaccessLoopPortn
		EkiState
	}


pm200fr20CtrlaccessLoopIndex OBJECT-TYPE
	SYNTAX  INTEGER(0..128)
	MAX-ACCESS  read-only
	STATUS current
	DESCRIPTION
        "
        Index definition for the pm200fr20CtrlaccessLoop 
        table
        "
	::= { pm200fr20CtrlaccessLoopEntry 1 }


pm200fr20CtrlaccessLoopPortn OBJECT-TYPE
	SYNTAX  EkiState
	MAX-ACCESS read-write
	STATUS current
	DESCRIPTION
        "
        Client Facility Loopback :This 
        OID, when set at '1' puts the client 
        port in loopback, looping the received 
        10 Gb/s signal on the transmit
         10 Gb/s output.  <Help> This control 
        enables the Out Loopback on the 
        client port, looping the client 
        input signal on the client output
        "
	::= { pm200fr20CtrlaccessLoopEntry 2 }


--- *********************************************************
---     TABLE for the pm200fr20CtrlclientLoopToLine articles
--- *********************************************************

pm200fr20CtrlclientLoopToLineTable OBJECT-TYPE
	SYNTAX  SEQUENCE OF Pm200fr20CtrlclientLoopToLineEntry
	MAX-ACCESS not-accessible
	STATUS current
	DESCRIPTION
        "
        List of pm200fr20CtrlclientLoopToLine 
        Article
        "
	::= { pm200fr20CtrlClient 17 }


pm200fr20CtrlclientLoopToLineEntry OBJECT-TYPE
	SYNTAX Pm200fr20CtrlclientLoopToLineEntry
	MAX-ACCESS not-accessible
	STATUS current
	DESCRIPTION
        "
        Row definition for the pm200fr20CtrlclientLoopToLine 
        table
        "
	INDEX   { pm200fr20CtrlclientLoopToLineIndex }
	::= { pm200fr20CtrlclientLoopToLineTable 1 }


Pm200fr20CtrlclientLoopToLineEntry ::=
	SEQUENCE {
	pm200fr20CtrlclientLoopToLineIndex
		INTEGER,
	pm200fr20CtrlclientLoopToLinePortn
		EkiState
	}


pm200fr20CtrlclientLoopToLineIndex OBJECT-TYPE
	SYNTAX  INTEGER(0..128)
	MAX-ACCESS  read-only
	STATUS current
	DESCRIPTION
        "
        Index definition for the pm200fr20CtrlclientLoopToLine 
        table
        "
	::= { pm200fr20CtrlclientLoopToLineEntry 1 }


pm200fr20CtrlclientLoopToLinePortn OBJECT-TYPE
	SYNTAX  EkiState
	MAX-ACCESS read-write
	STATUS current
	DESCRIPTION
        "
        Client Terminal Loopback :This 
        OID, when set, puts the client
         port in loop back, looping the 
        10 Gb/s output signal on the 10 
        Gb/s input.<Help> This control
         enables the In Loopback on the 
        client port, looping the client 
        output signal on the client input
        "
	::= { pm200fr20CtrlclientLoopToLineEntry 2 }


--- *********************************************************
---     TABLE for the pm200fr20CtrlcsfUpIns articles
--- *********************************************************

pm200fr20CtrlcsfUpInsTable OBJECT-TYPE
	SYNTAX  SEQUENCE OF Pm200fr20CtrlcsfUpInsEntry
	MAX-ACCESS not-accessible
	STATUS current
	DESCRIPTION
        "
        List of pm200fr20CtrlcsfUpIns
         Article
        "
	::= { pm200fr20CtrlClient 21 }


pm200fr20CtrlcsfUpInsEntry OBJECT-TYPE
	SYNTAX Pm200fr20CtrlcsfUpInsEntry
	MAX-ACCESS not-accessible
	STATUS current
	DESCRIPTION
        "
        Row definition for the pm200fr20CtrlcsfUpIns 
        table
        "
	INDEX   { pm200fr20CtrlcsfUpInsIndex }
	::= { pm200fr20CtrlcsfUpInsTable 1 }


Pm200fr20CtrlcsfUpInsEntry ::=
	SEQUENCE {
	pm200fr20CtrlcsfUpInsIndex
		INTEGER,
	pm200fr20CtrlcsfUpInsPortn
		EkiState
	}


pm200fr20CtrlcsfUpInsIndex OBJECT-TYPE
	SYNTAX  INTEGER(0..128)
	MAX-ACCESS  read-only
	STATUS current
	DESCRIPTION
        "
        Index definition for the pm200fr20CtrlcsfUpIns 
        table
        "
	::= { pm200fr20CtrlcsfUpInsEntry 1 }


pm200fr20CtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm200fr20CtrlcsfUpInsEntry 2 }


--- *********************************************************
---     TABLE for the pm200fr20CtrlcaisDwIns articles
--- *********************************************************

pm200fr20CtrlcaisDwInsTable OBJECT-TYPE
	SYNTAX  SEQUENCE OF Pm200fr20CtrlcaisDwInsEntry
	MAX-ACCESS not-accessible
	STATUS current
	DESCRIPTION
        "
        List of pm200fr20CtrlcaisDwIns 
        Article
        "
	::= { pm200fr20CtrlClient 22 }


pm200fr20CtrlcaisDwInsEntry OBJECT-TYPE
	SYNTAX Pm200fr20CtrlcaisDwInsEntry
	MAX-ACCESS not-accessible
	STATUS current
	DESCRIPTION
        "
        Row definition for the pm200fr20CtrlcaisDwIns 
        table
        "
	INDEX   { pm200fr20CtrlcaisDwInsIndex }
	::= { pm200fr20CtrlcaisDwInsTable 1 }


Pm200fr20CtrlcaisDwInsEntry ::=
	SEQUENCE {
	pm200fr20CtrlcaisDwInsIndex
		INTEGER,
	pm200fr20CtrlcaisDwInsPortn
		EkiState
	}


pm200fr20CtrlcaisDwInsIndex OBJECT-TYPE
	SYNTAX  INTEGER(0..128)
	MAX-ACCESS  read-only
	STATUS current
	DESCRIPTION
        "
        Index definition for the pm200fr20CtrlcaisDwIns 
        table
        "
	::= { pm200fr20CtrlcaisDwInsEntry 1 }


pm200fr20CtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm200fr20CtrlcaisDwInsEntry 2 }


--- *********************************************************
---     TABLE for the pm200fr20CtrlcommAccessLoop articles
--- *********************************************************

pm200fr20CtrlcommAccessLoopTable OBJECT-TYPE
	SYNTAX  SEQUENCE OF Pm200fr20CtrlcommAccessLoopEntry
	MAX-ACCESS not-accessible
	STATUS current
	DESCRIPTION
        "
        List of pm200fr20CtrlcommAccessLoop 
        Article
        "
	::= { pm200fr20CtrlLine 64 }


pm200fr20CtrlcommAccessLoopEntry OBJECT-TYPE
	SYNTAX Pm200fr20CtrlcommAccessLoopEntry
	MAX-ACCESS not-accessible
	STATUS current
	DESCRIPTION
        "
        Row definition for the pm200fr20CtrlcommAccessLoop 
        table
        "
	INDEX   { pm200fr20CtrlcommAccessLoopIndex }
	::= { pm200fr20CtrlcommAccessLoopTable 1 }


Pm200fr20CtrlcommAccessLoopEntry ::=
	SEQUENCE {
	pm200fr20CtrlcommAccessLoopIndex
		INTEGER,
	pm200fr20CtrlcommAccessLoopPortn
		EkiState
	}


pm200fr20CtrlcommAccessLoopIndex OBJECT-TYPE
	SYNTAX  INTEGER(0..128)
	MAX-ACCESS  read-only
	STATUS current
	DESCRIPTION
        "
        Index definition for the pm200fr20CtrlcommAccessLoop 
        table
        "
	::= { pm200fr20CtrlcommAccessLoopEntry 1 }


pm200fr20CtrlcommAccessLoopPortn OBJECT-TYPE
	SYNTAX  EkiState
	MAX-ACCESS read-write
	STATUS current
	DESCRIPTION
        "
        Line Terminal Loopback :This OID, 
        when set, puts the module in common 
        access loop back, looping the 200 
        Gb/s output signal on the 200 Gb/s 
        input.<Help> This control enables 
        the In Loopback on the line port, 
        looping the 200 Gb/s output signal 
        on the 200 Gb/s input
        "
	::= { pm200fr20CtrlcommAccessLoopEntry 2 }


--- *********************************************************
---     TABLE for the pm200fr20CtrllineLoop articles
--- *********************************************************

pm200fr20CtrllineLoopTable OBJECT-TYPE
	SYNTAX  SEQUENCE OF Pm200fr20CtrllineLoopEntry
	MAX-ACCESS not-accessible
	STATUS current
	DESCRIPTION
        "
        List of pm200fr20CtrllineLoop
         Article
        "
	::= { pm200fr20CtrlLine 66 }


pm200fr20CtrllineLoopEntry OBJECT-TYPE
	SYNTAX Pm200fr20CtrllineLoopEntry
	MAX-ACCESS not-accessible
	STATUS current
	DESCRIPTION
        "
        Row definition for the pm200fr20CtrllineLoop 
        table
        "
	INDEX   { pm200fr20CtrllineLoopIndex }
	::= { pm200fr20CtrllineLoopTable 1 }


Pm200fr20CtrllineLoopEntry ::=
	SEQUENCE {
	pm200fr20CtrllineLoopIndex
		INTEGER,
	pm200fr20CtrllineLoopPortn
		EkiState
	}


pm200fr20CtrllineLoopIndex OBJECT-TYPE
	SYNTAX  INTEGER(0..128)
	MAX-ACCESS  read-only
	STATUS current
	DESCRIPTION
        "
        Index definition for the pm200fr20CtrllineLoop 
        table
        "
	::= { pm200fr20CtrllineLoopEntry 1 }


pm200fr20CtrllineLoopPortn OBJECT-TYPE
	SYNTAX  EkiState
	MAX-ACCESS read-write
	STATUS current
	DESCRIPTION
        "
        Line Facility Loopback :This OID, 
        when set at '1' puts the module 
        in line loopback mode, looping
         the received 200 Gb/s signal on 
        the transmit 200 Gb/s output. The 
        Upstream part of the module is
         timed on the 200 Gb/s recovered 
        clock in that case.<Help> This
         control enables the Out Loopback 
        on the line port, looping the 200 
        Gb/s input signal on the 200 Gb/s 
        output
        "
	::= { pm200fr20CtrllineLoopEntry 2 }


--- *********************************************************
---     TABLE for the pm200fr20CtrlfecDisable articles
--- *********************************************************

pm200fr20CtrlfecDisableTable OBJECT-TYPE
	SYNTAX  SEQUENCE OF Pm200fr20CtrlfecDisableEntry
	MAX-ACCESS not-accessible
	STATUS current
	DESCRIPTION
        "
        List of pm200fr20CtrlfecDisable 
        Article
        "
	::= { pm200fr20CtrlLine 69 }


pm200fr20CtrlfecDisableEntry OBJECT-TYPE
	SYNTAX Pm200fr20CtrlfecDisableEntry
	MAX-ACCESS not-accessible
	STATUS current
	DESCRIPTION
        "
        Row definition for the pm200fr20CtrlfecDisable 
        table
        "
	INDEX   { pm200fr20CtrlfecDisableIndex }
	::= { pm200fr20CtrlfecDisableTable 1 }


Pm200fr20CtrlfecDisableEntry ::=
	SEQUENCE {
	pm200fr20CtrlfecDisableIndex
		INTEGER,
	pm200fr20CtrlfecDisablePortn
		EkiState
	}


pm200fr20CtrlfecDisableIndex OBJECT-TYPE
	SYNTAX  INTEGER(0..128)
	MAX-ACCESS  read-only
	STATUS current
	DESCRIPTION
        "
        Index definition for the pm200fr20CtrlfecDisable 
        table
        "
	::= { pm200fr20CtrlfecDisableEntry 1 }


pm200fr20CtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pm200fr20CtrlfecDisableEntry 2 }


--- *****************************************************
---     LEAF for the ledTest article
--- *****************************************************
pm200fr20CtrlledTest OBJECT IDENTIFIER ::= { pm200fr20CtrlOther 192 }




pm200fr20CtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm200fr20CtrlledTest 3 }



pm200fr20CtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm200fr20CtrlledTest 2 }



pm200fr20CtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm200fr20CtrlledTest 1 }



--- *****************************************************
---     LEAF for the initSwitchMarvell article
--- *****************************************************
pm200fr20CtrlinitSwitchMarvell OBJECT IDENTIFIER ::= { pm200fr20CtrlOther 201 }




pm200fr20CtrlInitSwitchMarvell OBJECT-TYPE
	  SYNTAX EkiOnOff
	  MAX-ACCESS read-write
	  STATUS current
	  DESCRIPTION
        "
        Switch Initialization :This OID 
        operates an initialization of the 
        switch managed through the module 
         <Help>  This control activates 
        an initialization of the switch 
        managed through the module
        "
	  ::= { pm200fr20CtrlinitSwitchMarvell 1 }



--- *********************************************************
---     TABLE for the pm200fr20CtrlmsaLineLoop articles
--- *********************************************************

pm200fr20CtrlmsaLineLoopTable OBJECT-TYPE
	SYNTAX  SEQUENCE OF Pm200fr20CtrlmsaLineLoopEntry
	MAX-ACCESS not-accessible
	STATUS current
	DESCRIPTION
        "
        List of pm200fr20CtrlmsaLineLoop 
        Article
        "
	::= { pm200fr20CtrlLine 209 }


pm200fr20CtrlmsaLineLoopEntry OBJECT-TYPE
	SYNTAX Pm200fr20CtrlmsaLineLoopEntry
	MAX-ACCESS not-accessible
	STATUS current
	DESCRIPTION
        "
        Row definition for the pm200fr20CtrlmsaLineLoop 
        table
        "
	INDEX   { pm200fr20CtrlmsaLineLoopIndex }
	::= { pm200fr20CtrlmsaLineLoopTable 1 }


Pm200fr20CtrlmsaLineLoopEntry ::=
	SEQUENCE {
	pm200fr20CtrlmsaLineLoopIndex
		INTEGER,
	pm200fr20CtrlmsaLineLoopPortn
		EkiState
	}


pm200fr20CtrlmsaLineLoopIndex OBJECT-TYPE
	SYNTAX  INTEGER(0..128)
	MAX-ACCESS  read-only
	STATUS current
	DESCRIPTION
        "
        Index definition for the pm200fr20CtrlmsaLineLoop 
        table
        "
	::= { pm200fr20CtrlmsaLineLoopEntry 1 }


pm200fr20CtrlmsaLineLoopPortn OBJECT-TYPE
	SYNTAX  EkiState
	MAX-ACCESS read-write
	STATUS current
	DESCRIPTION
        "
        MSA Line Loop :This OID operates 
        a line loopback on the MSA Line 
         <Help>  This control defines the 
        line loop back of the line transceiver
        "
	::= { pm200fr20CtrlmsaLineLoopEntry 2 }


--- *********************************************************
---     TABLE for the pm200fr20CtrlmsaTxReset articles
--- *********************************************************

pm200fr20CtrlmsaTxResetTable OBJECT-TYPE
	SYNTAX  SEQUENCE OF Pm200fr20CtrlmsaTxResetEntry
	MAX-ACCESS not-accessible
	STATUS current
	DESCRIPTION
        "
        List of pm200fr20CtrlmsaTxReset 
        Article
        "
	::= { pm200fr20CtrlLine 210 }


pm200fr20CtrlmsaTxResetEntry OBJECT-TYPE
	SYNTAX Pm200fr20CtrlmsaTxResetEntry
	MAX-ACCESS not-accessible
	STATUS current
	DESCRIPTION
        "
        Row definition for the pm200fr20CtrlmsaTxReset 
        table
        "
	INDEX   { pm200fr20CtrlmsaTxResetIndex }
	::= { pm200fr20CtrlmsaTxResetTable 1 }


Pm200fr20CtrlmsaTxResetEntry ::=
	SEQUENCE {
	pm200fr20CtrlmsaTxResetIndex
		INTEGER,
	pm200fr20CtrlmsaTxResetPortn
		EkiState
	}


pm200fr20CtrlmsaTxResetIndex OBJECT-TYPE
	SYNTAX  INTEGER(0..128)
	MAX-ACCESS  read-only
	STATUS current
	DESCRIPTION
        "
        Index definition for the pm200fr20CtrlmsaTxReset 
        table
        "
	::= { pm200fr20CtrlmsaTxResetEntry 1 }


pm200fr20CtrlmsaTxResetPortn OBJECT-TYPE
	SYNTAX  EkiState
	MAX-ACCESS read-write
	STATUS current
	DESCRIPTION
        "
        Line MSA TX Reset :This OID resets 
        the TX portion of the MSA line
         module  <Help > This control 
         initiates a reset of the transmitting 
        side
        "
	::= { pm200fr20CtrlmsaTxResetEntry 2 }


--- *********************************************************
---     TABLE for the pm200fr20CtrlmsaRxReset articles
--- *********************************************************

pm200fr20CtrlmsaRxResetTable OBJECT-TYPE
	SYNTAX  SEQUENCE OF Pm200fr20CtrlmsaRxResetEntry
	MAX-ACCESS not-accessible
	STATUS current
	DESCRIPTION
        "
        List of pm200fr20CtrlmsaRxReset 
        Article
        "
	::= { pm200fr20CtrlLine 211 }


pm200fr20CtrlmsaRxResetEntry OBJECT-TYPE
	SYNTAX Pm200fr20CtrlmsaRxResetEntry
	MAX-ACCESS not-accessible
	STATUS current
	DESCRIPTION
        "
        Row definition for the pm200fr20CtrlmsaRxReset 
        table
        "
	INDEX   { pm200fr20CtrlmsaRxResetIndex }
	::= { pm200fr20CtrlmsaRxResetTable 1 }


Pm200fr20CtrlmsaRxResetEntry ::=
	SEQUENCE {
	pm200fr20CtrlmsaRxResetIndex
		INTEGER,
	pm200fr20CtrlmsaRxResetPortn
		EkiState
	}


pm200fr20CtrlmsaRxResetIndex OBJECT-TYPE
	SYNTAX  INTEGER(0..128)
	MAX-ACCESS  read-only
	STATUS current
	DESCRIPTION
        "
        Index definition for the pm200fr20CtrlmsaRxReset 
        table
        "
	::= { pm200fr20CtrlmsaRxResetEntry 1 }


pm200fr20CtrlmsaRxResetPortn OBJECT-TYPE
	SYNTAX  EkiState
	MAX-ACCESS read-write
	STATUS current
	DESCRIPTION
        "
        Line MSA RX Reset :This OID resets 
        the RX portion of the MSA line
         module  <Help > This control 
         initiates a reset of the receiving 
        side
        "
	::= { pm200fr20CtrlmsaRxResetEntry 2 }


--- *********************************************************
---     TABLE for the pm200fr20CtrlmsaShutdown articles
--- *********************************************************

pm200fr20CtrlmsaShutdownTable OBJECT-TYPE
	SYNTAX  SEQUENCE OF Pm200fr20CtrlmsaShutdownEntry
	MAX-ACCESS not-accessible
	STATUS current
	DESCRIPTION
        "
        List of pm200fr20CtrlmsaShutdown 
        Article
        "
	::= { pm200fr20CtrlLine 212 }


pm200fr20CtrlmsaShutdownEntry OBJECT-TYPE
	SYNTAX Pm200fr20CtrlmsaShutdownEntry
	MAX-ACCESS not-accessible
	STATUS current
	DESCRIPTION
        "
        Row definition for the pm200fr20CtrlmsaShutdown 
        table
        "
	INDEX   { pm200fr20CtrlmsaShutdownIndex }
	::= { pm200fr20CtrlmsaShutdownTable 1 }


Pm200fr20CtrlmsaShutdownEntry ::=
	SEQUENCE {
	pm200fr20CtrlmsaShutdownIndex
		INTEGER,
	pm200fr20CtrlmsaShutdownPortn
		EkiState
	}


pm200fr20CtrlmsaShutdownIndex OBJECT-TYPE
	SYNTAX  INTEGER(0..128)
	MAX-ACCESS  read-only
	STATUS current
	DESCRIPTION
        "
        Index definition for the pm200fr20CtrlmsaShutdown 
        table
        "
	::= { pm200fr20CtrlmsaShutdownEntry 1 }


pm200fr20CtrlmsaShutdownPortn OBJECT-TYPE
	SYNTAX  EkiState
	MAX-ACCESS read-write
	STATUS current
	DESCRIPTION
        "
        Line MSA Shutdown :This OID enters 
        a process to shutdown the MSA line 
        module  <Help > This control  initiates 
        a shutdown of the module
        "
	::= { pm200fr20CtrlmsaShutdownEntry 2 }


--- *****************************************************
---     LEAF for the resetCount article
--- *****************************************************
pm200fr20CtrlresetCount OBJECT IDENTIFIER ::= { pm200fr20CtrlOther 259 }




pm200fr20CtrlResetcount OBJECT-TYPE
	  SYNTAX EkiOnOff
	  MAX-ACCESS read-write
	  STATUS current
	  DESCRIPTION
        "
        Module Count Global Reset :This 
        OID resets all the errors counters 
        on the module  <Help > This control 
         initiates a reset of the errors 
        counters on the module
        "
	  ::= { pm200fr20CtrlresetCount 1 }



--- *****************************************************
---     LEAF for the resetRmon article
--- *****************************************************
pm200fr20CtrlresetRmon OBJECT IDENTIFIER ::= { pm200fr20CtrlOther 260 }




pm200fr20CtrlResetrmon OBJECT-TYPE
	  SYNTAX EkiOnOff
	  MAX-ACCESS read-write
	  STATUS current
	  DESCRIPTION
        "
        Module Rmon Global Reset :This 
        OID resets all the Rmon counters 
        on the module  <Help > This control 
         initiates a reset of the Rmon
         counters on the module
        "
	  ::= { pm200fr20CtrlresetRmon 1 }



--- *****************************************************
---     LEAF for the resetMeasurements article
--- *****************************************************
pm200fr20CtrlresetMeasurements OBJECT IDENTIFIER ::= { pm200fr20CtrlOther 261 }




pm200fr20CtrlResetmeasurements OBJECT-TYPE
	  SYNTAX EkiOnOff
	  MAX-ACCESS read-write
	  STATUS current
	  DESCRIPTION
        "
        Management Meas Global Reset :This 
        OID resets some measurements on 
        the management  <Help > This control 
         initiates a reset of some measurements 
        on the management
        "
	  ::= { pm200fr20CtrlresetMeasurements 1 }



--- *********************************************************
---     TABLE for the pm200fr20CtrlclientResetAllCount articles
--- *********************************************************

pm200fr20CtrlclientResetAllCountTable OBJECT-TYPE
	SYNTAX  SEQUENCE OF Pm200fr20CtrlclientResetAllCountEntry
	MAX-ACCESS not-accessible
	STATUS current
	DESCRIPTION
        "
        List of pm200fr20CtrlclientResetAllCount 
        Article
        "
	::= { pm200fr20CtrlClient 262 }


pm200fr20CtrlclientResetAllCountEntry OBJECT-TYPE
	SYNTAX Pm200fr20CtrlclientResetAllCountEntry
	MAX-ACCESS not-accessible
	STATUS current
	DESCRIPTION
        "
        Row definition for the pm200fr20CtrlclientResetAllCount 
        table
        "
	INDEX   { pm200fr20CtrlclientResetAllCountIndex }
	::= { pm200fr20CtrlclientResetAllCountTable 1 }


Pm200fr20CtrlclientResetAllCountEntry ::=
	SEQUENCE {
	pm200fr20CtrlclientResetAllCountIndex
		INTEGER,
	pm200fr20CtrlclientResetAllCountsPortn
		EkiState
	}


pm200fr20CtrlclientResetAllCountIndex OBJECT-TYPE
	SYNTAX  INTEGER(0..128)
	MAX-ACCESS  read-only
	STATUS current
	DESCRIPTION
        "
        Index definition for the pm200fr20CtrlclientResetAllCount 
        table
        "
	::= { pm200fr20CtrlclientResetAllCountEntry 1 }


pm200fr20CtrlclientResetAllCountsPortn OBJECT-TYPE
	SYNTAX  EkiState
	MAX-ACCESS read-write
	STATUS current
	DESCRIPTION
        "
        Client Counters Reset :This OID 
        resets every counter on the client 
        port  <Help>   This control operates 
        a reset on the statistics current 
        ,previous and history client port 
        counters  
        "
	::= { pm200fr20CtrlclientResetAllCountEntry 2 }


--- *********************************************************
---     TABLE for the pm200fr20CtrllineResetAllCount articles
--- *********************************************************

pm200fr20CtrllineResetAllCountTable OBJECT-TYPE
	SYNTAX  SEQUENCE OF Pm200fr20CtrllineResetAllCountEntry
	MAX-ACCESS not-accessible
	STATUS current
	DESCRIPTION
        "
        List of pm200fr20CtrllineResetAllCount 
        Article
        "
	::= { pm200fr20CtrlLine 263 }


pm200fr20CtrllineResetAllCountEntry OBJECT-TYPE
	SYNTAX Pm200fr20CtrllineResetAllCountEntry
	MAX-ACCESS not-accessible
	STATUS current
	DESCRIPTION
        "
        Row definition for the pm200fr20CtrllineResetAllCount 
        table
        "
	INDEX   { pm200fr20CtrllineResetAllCountIndex }
	::= { pm200fr20CtrllineResetAllCountTable 1 }


Pm200fr20CtrllineResetAllCountEntry ::=
	SEQUENCE {
	pm200fr20CtrllineResetAllCountIndex
		INTEGER,
	pm200fr20CtrllineResetAllCountsPortn
		EkiState
	}


pm200fr20CtrllineResetAllCountIndex OBJECT-TYPE
	SYNTAX  INTEGER(0..128)
	MAX-ACCESS  read-only
	STATUS current
	DESCRIPTION
        "
        Index definition for the pm200fr20CtrllineResetAllCount 
        table
        "
	::= { pm200fr20CtrllineResetAllCountEntry 1 }


pm200fr20CtrllineResetAllCountsPortn OBJECT-TYPE
	SYNTAX  EkiState
	MAX-ACCESS read-write
	STATUS current
	DESCRIPTION
        "
        Line Counters Reset :This OID
         resets every counter on the line 
        port  <Help>   This control operates 
        a reset on the statistics current 
        ,previous and history line port 
        counters  
        "
	::= { pm200fr20CtrllineResetAllCountEntry 2 }







--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm200fr20CntclientInputErrorCounter articles
--- *********************************************************

pm200fr20CntclientInputErrorCounterTable OBJECT-TYPE
	SYNTAX  SEQUENCE OF Pm200fr20CntclientInputErrorCounterEntry
	MAX-ACCESS not-accessible
	STATUS current
	DESCRIPTION
        "
        List of pm200fr20CntclientInputErrorCounter 
        Article
        "
	::= { pm200fr20CntClient 112 }


pm200fr20CntclientInputErrorCounterEntry OBJECT-TYPE
	SYNTAX Pm200fr20CntclientInputErrorCounterEntry
	MAX-ACCESS not-accessible
	STATUS current
	DESCRIPTION
        "
        Row definition for the pm200fr20CntclientInputErrorCounter 
        table
        "
	INDEX   { pm200fr20CntclientInputErrorCounterIndex }
	::= { pm200fr20CntclientInputErrorCounterTable 1 }


Pm200fr20CntclientInputErrorCounterEntry ::=
	SEQUENCE {
	pm200fr20CntclientInputErrorCounterIndex
		INTEGER,
	pm200fr20CntclientInputErrorCounterValuePortn
		Counter32,
	pm200fr20CntclientInputErrorCounterErrorPortn
		EkiOnOff,
	pm200fr20CntclientInputErrorCounterOverloadPortn
		EkiOnOff
	}


pm200fr20CntclientInputErrorCounterIndex OBJECT-TYPE
	SYNTAX  INTEGER(0..128)
	MAX-ACCESS  read-only
	STATUS current
	DESCRIPTION
        "
        Index definition for the pm200fr20CntclientInputErrorCounter 
        table
        "
	::= { pm200fr20CntclientInputErrorCounterEntry 1 }


pm200fr20CntclientInputErrorCounterValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of errors on the client port (FCS 
        errors for 10GbE and BIP8 errors 
        for STM64,OTU2,OTU2e)
        "
	::= { pm200fr20CntclientInputErrorCounterEntry 2 }


pm200fr20CntclientInputErrorCounterErrorPortn OBJECT-TYPE
	SYNTAX  EkiOnOff
	MAX-ACCESS read-only
	STATUS current
	DESCRIPTION
        "
        Client Counter Error :This OID 
        when set indicates the client error 
        counter value is invalid on Port
        "
	::= { pm200fr20CntclientInputErrorCounterEntry 3 }


pm200fr20CntclientInputErrorCounterOverloadPortn OBJECT-TYPE
	SYNTAX  EkiOnOff
	MAX-ACCESS read-only
	STATUS current
	DESCRIPTION
        "
        Client Counter Overload :This
         OID when set indicates a client 
        input error counter overload on 
        Port
        "
	::= { pm200fr20CntclientInputErrorCounterEntry 4 }


--- *********************************************************
---     TABLE for the pm200fr20CntclientCbipCounter articles
--- *********************************************************

pm200fr20CntclientCbipCounterTable OBJECT-TYPE
	SYNTAX  SEQUENCE OF Pm200fr20CntclientCbipCounterEntry
	MAX-ACCESS not-accessible
	STATUS current
	DESCRIPTION
        "
        List of pm200fr20CntclientCbipCounter 
        Article
        "
	::= { pm200fr20CntClient 144 }


pm200fr20CntclientCbipCounterEntry OBJECT-TYPE
	SYNTAX Pm200fr20CntclientCbipCounterEntry
	MAX-ACCESS not-accessible
	STATUS current
	DESCRIPTION
        "
        Row definition for the pm200fr20CntclientCbipCounter 
        table
        "
	INDEX   { pm200fr20CntclientCbipCounterIndex }
	::= { pm200fr20CntclientCbipCounterTable 1 }


Pm200fr20CntclientCbipCounterEntry ::=
	SEQUENCE {
	pm200fr20CntclientCbipCounterIndex
		INTEGER,
	pm200fr20CntclientCbipCounterValuePortn
		Counter32,
	pm200fr20CntclientCbipCounterErrorPortn
		EkiOnOff,
	pm200fr20CntclientCbipCounterOverloadPortn
		EkiOnOff
	}


pm200fr20CntclientCbipCounterIndex OBJECT-TYPE
	SYNTAX  INTEGER(0..128)
	MAX-ACCESS  read-only
	STATUS current
	DESCRIPTION
        "
        Index definition for the pm200fr20CntclientCbipCounter 
        table
        "
	::= { pm200fr20CntclientCbipCounterEntry 1 }


pm200fr20CntclientCbipCounterValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of errors 
        on the client port (FCS errors
         for 10GbE and BIP8 errors for
         STM64,OTU2,OTU2e)
        "
	::= { pm200fr20CntclientCbipCounterEntry 2 }


pm200fr20CntclientCbipCounterErrorPortn OBJECT-TYPE
	SYNTAX  EkiOnOff
	MAX-ACCESS read-only
	STATUS current
	DESCRIPTION
        "
        Client Counter Error :This OID 
        when set indicates the CBIP error 
        counter value is invalid on Port
        "
	::= { pm200fr20CntclientCbipCounterEntry 3 }


pm200fr20CntclientCbipCounterOverloadPortn OBJECT-TYPE
	SYNTAX  EkiOnOff
	MAX-ACCESS read-only
	STATUS current
	DESCRIPTION
        "
        Client CBIP Counter Overload :This 
        OID when set indicates a CBIP error 
        counter overload on Port
        "
	::= { pm200fr20CntclientCbipCounterEntry 4 }


--- *********************************************************
---     TABLE for the pm200fr20CntlocalLineSmBip8ErrorCounter articles
--- *********************************************************

pm200fr20CntlocalLineSmBip8ErrorCounterTable OBJECT-TYPE
	SYNTAX  SEQUENCE OF Pm200fr20CntlocalLineSmBip8ErrorCounterEntry
	MAX-ACCESS not-accessible
	STATUS current
	DESCRIPTION
        "
        List of pm200fr20CntlocalLineSmBip8ErrorCounter 
        Article
        "
	::= { pm200fr20CntLine 192 }


pm200fr20CntlocalLineSmBip8ErrorCounterEntry OBJECT-TYPE
	SYNTAX Pm200fr20CntlocalLineSmBip8ErrorCounterEntry
	MAX-ACCESS not-accessible
	STATUS current
	DESCRIPTION
        "
        Row definition for the pm200fr20CntlocalLineSmBip8ErrorCounter 
        table
        "
	INDEX   { pm200fr20CntlocalLineSmBip8ErrorCounterIndex }
	::= { pm200fr20CntlocalLineSmBip8ErrorCounterTable 1 }


Pm200fr20CntlocalLineSmBip8ErrorCounterEntry ::=
	SEQUENCE {
	pm200fr20CntlocalLineSmBip8ErrorCounterIndex
		INTEGER,
	pm200fr20CntlocalLineSmBip8ErrorCounterValuePortn
		Counter64,
	pm200fr20CntlocalLineSmBip8ErrorCounterErrorPortn
		EkiOnOff,
	pm200fr20CntlocalLineSmBip8ErrorCounterOverloadPortn
		EkiOnOff
	}


pm200fr20CntlocalLineSmBip8ErrorCounterIndex OBJECT-TYPE
	SYNTAX  INTEGER(0..128)
	MAX-ACCESS  read-only
	STATUS current
	DESCRIPTION
        "
        Index definition for the pm200fr20CntlocalLineSmBip8ErrorCounter 
        table
        "
	::= { pm200fr20CntlocalLineSmBip8ErrorCounterEntry 1 }


pm200fr20CntlocalLineSmBip8ErrorCounterValuePortn OBJECT-TYPE
	SYNTAX  Counter64
	MAX-ACCESS read-only
	STATUS current
	DESCRIPTION
        "
        Uncorrected SD FEC Errors :This 
        OID gives the current Bit Error 
        Rate after the Soft Decision FEC 
        (residual)  <Help> This counter 
        gives the current Bit Error Rate 
        after the Soft Decision FEC (residual)
        "
	::= { pm200fr20CntlocalLineSmBip8ErrorCounterEntry 2 }


pm200fr20CntlocalLineSmBip8ErrorCounterErrorPortn OBJECT-TYPE
	SYNTAX  EkiOnOff
	MAX-ACCESS read-only
	STATUS current
	DESCRIPTION
        "
        Line Counter Error :This OID when 
        set indicates the B1 error counter 
        value is invalid on Port
        "
	::= { pm200fr20CntlocalLineSmBip8ErrorCounterEntry 3 }


pm200fr20CntlocalLineSmBip8ErrorCounterOverloadPortn OBJECT-TYPE
	SYNTAX  EkiOnOff
	MAX-ACCESS read-only
	STATUS current
	DESCRIPTION
        "
        Line Counter Overload :This OID 
        when set indicates a B1 error counter 
        overload on Port
        "
	::= { pm200fr20CntlocalLineSmBip8ErrorCounterEntry 4 }


--- *********************************************************
---     TABLE for the pm200fr20CntlocalLineFecCorrectedErrorsCounter articles
--- *********************************************************

pm200fr20CntlocalLineFecCorrectedErrorsCounterTable OBJECT-TYPE
	SYNTAX  SEQUENCE OF Pm200fr20CntlocalLineFecCorrectedErrorsCounterEntry
	MAX-ACCESS not-accessible
	STATUS current
	DESCRIPTION
        "
        List of pm200fr20CntlocalLineFecCorrectedErrorsCounter 
        Article
        "
	::= { pm200fr20CntLine 193 }


pm200fr20CntlocalLineFecCorrectedErrorsCounterEntry OBJECT-TYPE
	SYNTAX Pm200fr20CntlocalLineFecCorrectedErrorsCounterEntry
	MAX-ACCESS not-accessible
	STATUS current
	DESCRIPTION
        "
        Row definition for the pm200fr20CntlocalLineFecCorrectedErrorsCounter 
        table
        "
	INDEX   { pm200fr20CntlocalLineFecCorrectedErrorsCounterIndex }
	::= { pm200fr20CntlocalLineFecCorrectedErrorsCounterTable 1 }


Pm200fr20CntlocalLineFecCorrectedErrorsCounterEntry ::=
	SEQUENCE {
	pm200fr20CntlocalLineFecCorrectedErrorsCounterIndex
		INTEGER,
	pm200fr20CntlocalLineFecCorrectedErrorsCounterValuePortn
		Counter64,
	pm200fr20CntlocalLineFecCorrectedErrorsCounterErrorPortn
		EkiOnOff,
	pm200fr20CntlocalLineFecCorrectedErrorsCounterOverloadPortn
		EkiOnOff
	}


pm200fr20CntlocalLineFecCorrectedErrorsCounterIndex OBJECT-TYPE
	SYNTAX  INTEGER(0..128)
	MAX-ACCESS  read-only
	STATUS current
	DESCRIPTION
        "
        Index definition for the pm200fr20CntlocalLineFecCorrectedErrorsCounter 
        table
        "
	::= { pm200fr20CntlocalLineFecCorrectedErrorsCounterEntry 1 }


pm200fr20CntlocalLineFecCorrectedErrorsCounterValuePortn OBJECT-TYPE
	SYNTAX  Counter64
	MAX-ACCESS read-only
	STATUS current
	DESCRIPTION
        "
        Line Input HD FEC Corrected Errors 
        :This OID gives the current Bit 
        Error Rate before the Hard Decision 
        FEC  <Help> This counter gives
         the current Bit Error Rate before 
        the Hard Decision FEC
        "
	::= { pm200fr20CntlocalLineFecCorrectedErrorsCounterEntry 2 }


pm200fr20CntlocalLineFecCorrectedErrorsCounterErrorPortn OBJECT-TYPE
	SYNTAX  EkiOnOff
	MAX-ACCESS read-only
	STATUS current
	DESCRIPTION
        "
        FEC Counter Error :This bit when 
        set indicates the FEC corrected 
        errors counter value is invalid 
        on Line
        "
	::= { pm200fr20CntlocalLineFecCorrectedErrorsCounterEntry 3 }


pm200fr20CntlocalLineFecCorrectedErrorsCounterOverloadPortn OBJECT-TYPE
	SYNTAX  EkiOnOff
	MAX-ACCESS read-only
	STATUS current
	DESCRIPTION
        "
        FEC Counter Overload :This bit 
        when set indicates a FEC corrected 
        errors counter overload on Line
        "
	::= { pm200fr20CntlocalLineFecCorrectedErrorsCounterEntry 4 }


--- *********************************************************
---     TABLE for the pm200fr20CntremoteLineSmBip8ErrorCounter articles
--- *********************************************************

pm200fr20CntremoteLineSmBip8ErrorCounterTable OBJECT-TYPE
	SYNTAX  SEQUENCE OF Pm200fr20CntremoteLineSmBip8ErrorCounterEntry
	MAX-ACCESS not-accessible
	STATUS current
	DESCRIPTION
        "
        List of pm200fr20CntremoteLineSmBip8ErrorCounter 
        Article
        "
	::= { pm200fr20CntLine 194 }


pm200fr20CntremoteLineSmBip8ErrorCounterEntry OBJECT-TYPE
	SYNTAX Pm200fr20CntremoteLineSmBip8ErrorCounterEntry
	MAX-ACCESS not-accessible
	STATUS current
	DESCRIPTION
        "
        Row definition for the pm200fr20CntremoteLineSmBip8ErrorCounter 
        table
        "
	INDEX   { pm200fr20CntremoteLineSmBip8ErrorCounterIndex }
	::= { pm200fr20CntremoteLineSmBip8ErrorCounterTable 1 }


Pm200fr20CntremoteLineSmBip8ErrorCounterEntry ::=
	SEQUENCE {
	pm200fr20CntremoteLineSmBip8ErrorCounterIndex
		INTEGER,
	pm200fr20CntremoteLineSmBip8ErrorCounterValuePortn
		Counter64,
	pm200fr20CntremoteLineSmBip8ErrorCounterErrorPortn
		EkiOnOff,
	pm200fr20CntremoteLineSmBip8ErrorCounterOverloadPortn
		EkiOnOff
	}


pm200fr20CntremoteLineSmBip8ErrorCounterIndex OBJECT-TYPE
	SYNTAX  INTEGER(0..128)
	MAX-ACCESS  read-only
	STATUS current
	DESCRIPTION
        "
        Index definition for the pm200fr20CntremoteLineSmBip8ErrorCounter 
        table
        "
	::= { pm200fr20CntremoteLineSmBip8ErrorCounterEntry 1 }


pm200fr20CntremoteLineSmBip8ErrorCounterValuePortn OBJECT-TYPE
	SYNTAX  Counter64
	MAX-ACCESS read-only
	STATUS current
	DESCRIPTION
        "
        Remote SM BIP8 :This OID gives 
        the current Bit Error Rate (residual 
        SM-BIP8 error) after FEC on the 
        remote side  <Help> This counter 
        gives the current Bit Error Rate 
        (residual SM-BIP8 error) after
         FEC on the remote side
        "
	::= { pm200fr20CntremoteLineSmBip8ErrorCounterEntry 2 }


pm200fr20CntremoteLineSmBip8ErrorCounterErrorPortn OBJECT-TYPE
	SYNTAX  EkiOnOff
	MAX-ACCESS read-only
	STATUS current
	DESCRIPTION
        "
        Remote Counter Error :
        "
	::= { pm200fr20CntremoteLineSmBip8ErrorCounterEntry 3 }


pm200fr20CntremoteLineSmBip8ErrorCounterOverloadPortn OBJECT-TYPE
	SYNTAX  EkiOnOff
	MAX-ACCESS read-only
	STATUS current
	DESCRIPTION
        "
        Remote Counter Overload :
        "
	::= { pm200fr20CntremoteLineSmBip8ErrorCounterEntry 4 }


--- *********************************************************
---     TABLE for the pm200fr20CntlineDfrmTimCnt articles
--- *********************************************************

pm200fr20CntlineDfrmTimCntTable OBJECT-TYPE
	SYNTAX  SEQUENCE OF Pm200fr20CntlineDfrmTimCntEntry
	MAX-ACCESS not-accessible
	STATUS current
	DESCRIPTION
        "
        List of pm200fr20CntlineDfrmTimCnt 
        Article
        "
	::= { pm200fr20CntLine 195 }


pm200fr20CntlineDfrmTimCntEntry OBJECT-TYPE
	SYNTAX Pm200fr20CntlineDfrmTimCntEntry
	MAX-ACCESS not-accessible
	STATUS current
	DESCRIPTION
        "
        Row definition for the pm200fr20CntlineDfrmTimCnt 
        table
        "
	INDEX   { pm200fr20CntlineDfrmTimCntIndex }
	::= { pm200fr20CntlineDfrmTimCntTable 1 }


Pm200fr20CntlineDfrmTimCntEntry ::=
	SEQUENCE {
	pm200fr20CntlineDfrmTimCntIndex
		INTEGER,
	pm200fr20CntlineDfrmTimCntValuePortn
		Counter64,
	pm200fr20CntlineDfrmTimCntErrorPortn
		EkiOnOff,
	pm200fr20CntlineDfrmTimCntOverloadPortn
		EkiOnOff
	}


pm200fr20CntlineDfrmTimCntIndex OBJECT-TYPE
	SYNTAX  INTEGER(0..128)
	MAX-ACCESS  read-only
	STATUS current
	DESCRIPTION
        "
        Index definition for the pm200fr20CntlineDfrmTimCnt 
        table
        "
	::= { pm200fr20CntlineDfrmTimCntEntry 1 }


pm200fr20CntlineDfrmTimCntValuePortn OBJECT-TYPE
	SYNTAX  Counter64
	MAX-ACCESS read-only
	STATUS current
	DESCRIPTION
        "
        Line Timer Counter :
        "
	::= { pm200fr20CntlineDfrmTimCntEntry 2 }


pm200fr20CntlineDfrmTimCntErrorPortn OBJECT-TYPE
	SYNTAX  EkiOnOff
	MAX-ACCESS read-only
	STATUS current
	DESCRIPTION
        "
        Line Counter Error :This OID when 
        set indicates the deframer timer 
        counter value is invalid on Port
        "
	::= { pm200fr20CntlineDfrmTimCntEntry 3 }


pm200fr20CntlineDfrmTimCntOverloadPortn OBJECT-TYPE
	SYNTAX  EkiOnOff
	MAX-ACCESS read-only
	STATUS current
	DESCRIPTION
        "
        Line Counter Overload :This OID 
        when set indicates a deframer timer 
        counter overload on Port
        "
	::= { pm200fr20CntlineDfrmTimCntEntry 4 }


--- *********************************************************
---     TABLE for the pm200fr20CntlocalLineTrscvPreSdFecErrorCounter articles
--- *********************************************************

pm200fr20CntlocalLineTrscvPreSdFecErrorCounterTable OBJECT-TYPE
	SYNTAX  SEQUENCE OF Pm200fr20CntlocalLineTrscvPreSdFecErrorCounterEntry
	MAX-ACCESS not-accessible
	STATUS current
	DESCRIPTION
        "
        List of pm200fr20CntlocalLineTrscvPreSdFecErrorCounter 
        Article
        "
	::= { pm200fr20CntLine 196 }


pm200fr20CntlocalLineTrscvPreSdFecErrorCounterEntry OBJECT-TYPE
	SYNTAX Pm200fr20CntlocalLineTrscvPreSdFecErrorCounterEntry
	MAX-ACCESS not-accessible
	STATUS current
	DESCRIPTION
        "
        Row definition for the pm200fr20CntlocalLineTrscvPreSdFecErrorCounter 
        table
        "
	INDEX   { pm200fr20CntlocalLineTrscvPreSdFecErrorCounterIndex }
	::= { pm200fr20CntlocalLineTrscvPreSdFecErrorCounterTable 1 }


Pm200fr20CntlocalLineTrscvPreSdFecErrorCounterEntry ::=
	SEQUENCE {
	pm200fr20CntlocalLineTrscvPreSdFecErrorCounterIndex
		INTEGER,
	pm200fr20CntlocalLineTrscvPreSdFecErrorCounterValuePortn
		Counter64,
	pm200fr20CntlocalLineTrscvPreSdFecErrorCounterErrorPortn
		EkiOnOff,
	pm200fr20CntlocalLineTrscvPreSdFecErrorCounterOverloadPortn
		EkiOnOff
	}


pm200fr20CntlocalLineTrscvPreSdFecErrorCounterIndex OBJECT-TYPE
	SYNTAX  INTEGER(0..128)
	MAX-ACCESS  read-only
	STATUS current
	DESCRIPTION
        "
        Index definition for the pm200fr20CntlocalLineTrscvPreSdFecErrorCounter 
        table
        "
	::= { pm200fr20CntlocalLineTrscvPreSdFecErrorCounterEntry 1 }


pm200fr20CntlocalLineTrscvPreSdFecErrorCounterValuePortn OBJECT-TYPE
	SYNTAX  Counter64
	MAX-ACCESS read-only
	STATUS current
	DESCRIPTION
        "
        Pre-SD FEC Errors :This OID gives 
        the current Bit Error Rate before 
        the Soft Decision FEC  <Help> This 
        counter gives the current Bit Error 
        Rate before the Soft Decision FEC
        "
	::= { pm200fr20CntlocalLineTrscvPreSdFecErrorCounterEntry 2 }


pm200fr20CntlocalLineTrscvPreSdFecErrorCounterErrorPortn OBJECT-TYPE
	SYNTAX  EkiOnOff
	MAX-ACCESS read-only
	STATUS current
	DESCRIPTION
        "
        Line Counter Error :This OID when 
        set indicates the deframer timer 
        counter value is invalid on Port
        "
	::= { pm200fr20CntlocalLineTrscvPreSdFecErrorCounterEntry 3 }


pm200fr20CntlocalLineTrscvPreSdFecErrorCounterOverloadPortn OBJECT-TYPE
	SYNTAX  EkiOnOff
	MAX-ACCESS read-only
	STATUS current
	DESCRIPTION
        "
        Line Counter Overload :This OID 
        when set indicates a deframer timer 
        counter overload on Port
        "
	::= { pm200fr20CntlocalLineTrscvPreSdFecErrorCounterEntry 4 }


--- *********************************************************
---     TABLE for the pm200fr20CntlocalLineTrscvUncorrectedSdFecErrorCounter articles
--- *********************************************************

pm200fr20CntlocalLineTrscvUncorrectedSdFecErrorCounterTable OBJECT-TYPE
	SYNTAX  SEQUENCE OF Pm200fr20CntlocalLineTrscvUncorrectedSdFecErrorCounterEntry
	MAX-ACCESS not-accessible
	STATUS current
	DESCRIPTION
        "
        List of pm200fr20CntlocalLineTrscvUncorrectedSdFecErrorCounter 
        Article
        "
	::= { pm200fr20CntLine 197 }


pm200fr20CntlocalLineTrscvUncorrectedSdFecErrorCounterEntry OBJECT-TYPE
	SYNTAX Pm200fr20CntlocalLineTrscvUncorrectedSdFecErrorCounterEntry
	MAX-ACCESS not-accessible
	STATUS current
	DESCRIPTION
        "
        Row definition for the pm200fr20CntlocalLineTrscvUncorrectedSdFecErrorCounter 
        table
        "
	INDEX   { pm200fr20CntlocalLineTrscvUncorrectedSdFecErrorCounterIndex }
	::= { pm200fr20CntlocalLineTrscvUncorrectedSdFecErrorCounterTable 1 }


Pm200fr20CntlocalLineTrscvUncorrectedSdFecErrorCounterEntry ::=
	SEQUENCE {
	pm200fr20CntlocalLineTrscvUncorrectedSdFecErrorCounterIndex
		INTEGER,
	pm200fr20CntlocalLineTrscvUncorrectedSdFecErrorCounterValuePortn
		Counter64,
	pm200fr20CntlocalLineTrscvUncorrectedSdFecErrorCounterErrorPortn
		EkiOnOff,
	pm200fr20CntlocalLineTrscvUncorrectedSdFecErrorCounterOverloadPortn
		EkiOnOff
	}


pm200fr20CntlocalLineTrscvUncorrectedSdFecErrorCounterIndex OBJECT-TYPE
	SYNTAX  INTEGER(0..128)
	MAX-ACCESS  read-only
	STATUS current
	DESCRIPTION
        "
        Index definition for the pm200fr20CntlocalLineTrscvUncorrectedSdFecErrorCounter 
        table
        "
	::= { pm200fr20CntlocalLineTrscvUncorrectedSdFecErrorCounterEntry 1 }


pm200fr20CntlocalLineTrscvUncorrectedSdFecErrorCounterValuePortn OBJECT-TYPE
	SYNTAX  Counter64
	MAX-ACCESS read-only
	STATUS current
	DESCRIPTION
        "
        Uncorrected SD FEC Errors :This 
        OID gives the current Bit Error 
        Rate after the Soft Decision FEC 
        (residual)  <Help> This counter 
        gives the current Bit Error Rate 
        after the Soft Decision FEC (residual)
        "
	::= { pm200fr20CntlocalLineTrscvUncorrectedSdFecErrorCounterEntry 2 }


pm200fr20CntlocalLineTrscvUncorrectedSdFecErrorCounterErrorPortn OBJECT-TYPE
	SYNTAX  EkiOnOff
	MAX-ACCESS read-only
	STATUS current
	DESCRIPTION
        "
        Line Counter Error :This OID when 
        set indicates the deframer timer 
        counter value is invalid on Port
        "
	::= { pm200fr20CntlocalLineTrscvUncorrectedSdFecErrorCounterEntry 3 }


pm200fr20CntlocalLineTrscvUncorrectedSdFecErrorCounterOverloadPortn OBJECT-TYPE
	SYNTAX  EkiOnOff
	MAX-ACCESS read-only
	STATUS current
	DESCRIPTION
        "
        Line Counter Overload :This OID 
        when set indicates a deframer timer 
        counter overload on Port
        "
	::= { pm200fr20CntlocalLineTrscvUncorrectedSdFecErrorCounterEntry 4 }


--- *********************************************************
---     TABLE for the pm200fr20CntlocalLineTrscvPreSdFecBitCounter articles
--- *********************************************************

pm200fr20CntlocalLineTrscvPreSdFecBitCounterTable OBJECT-TYPE
	SYNTAX  SEQUENCE OF Pm200fr20CntlocalLineTrscvPreSdFecBitCounterEntry
	MAX-ACCESS not-accessible
	STATUS current
	DESCRIPTION
        "
        List of pm200fr20CntlocalLineTrscvPreSdFecBitCounter 
        Article
        "
	::= { pm200fr20CntLine 198 }


pm200fr20CntlocalLineTrscvPreSdFecBitCounterEntry OBJECT-TYPE
	SYNTAX Pm200fr20CntlocalLineTrscvPreSdFecBitCounterEntry
	MAX-ACCESS not-accessible
	STATUS current
	DESCRIPTION
        "
        Row definition for the pm200fr20CntlocalLineTrscvPreSdFecBitCounter 
        table
        "
	INDEX   { pm200fr20CntlocalLineTrscvPreSdFecBitCounterIndex }
	::= { pm200fr20CntlocalLineTrscvPreSdFecBitCounterTable 1 }


Pm200fr20CntlocalLineTrscvPreSdFecBitCounterEntry ::=
	SEQUENCE {
	pm200fr20CntlocalLineTrscvPreSdFecBitCounterIndex
		INTEGER,
	pm200fr20CntlocalLineTrscvPreSdFecBitCounterValuePortn
		Counter64,
	pm200fr20CntlocalLineTrscvPreSdFecBitCounterErrorPortn
		EkiOnOff,
	pm200fr20CntlocalLineTrscvPreSdFecBitCounterOverloadPortn
		EkiOnOff
	}


pm200fr20CntlocalLineTrscvPreSdFecBitCounterIndex OBJECT-TYPE
	SYNTAX  INTEGER(0..128)
	MAX-ACCESS  read-only
	STATUS current
	DESCRIPTION
        "
        Index definition for the pm200fr20CntlocalLineTrscvPreSdFecBitCounter 
        table
        "
	::= { pm200fr20CntlocalLineTrscvPreSdFecBitCounterEntry 1 }


pm200fr20CntlocalLineTrscvPreSdFecBitCounterValuePortn OBJECT-TYPE
	SYNTAX  Counter64
	MAX-ACCESS read-only
	STATUS current
	DESCRIPTION
        "
        Pre-SD FEC Bit Counter :This OID 
        gives the current Bit count before 
        the Soft Decision FEC  <Help> This 
        counter gives the current Bit Count 
        before the Soft Decision FEC
        "
	::= { pm200fr20CntlocalLineTrscvPreSdFecBitCounterEntry 2 }


pm200fr20CntlocalLineTrscvPreSdFecBitCounterErrorPortn OBJECT-TYPE
	SYNTAX  EkiOnOff
	MAX-ACCESS read-only
	STATUS current
	DESCRIPTION
        "
        Line Counter Error :This OID when 
        set indicates the deframer timer 
        counter value is invalid on Port
        "
	::= { pm200fr20CntlocalLineTrscvPreSdFecBitCounterEntry 3 }


pm200fr20CntlocalLineTrscvPreSdFecBitCounterOverloadPortn OBJECT-TYPE
	SYNTAX  EkiOnOff
	MAX-ACCESS read-only
	STATUS current
	DESCRIPTION
        "
        Line Counter Overload :This OID 
        when set indicates a deframer timer 
        counter overload on Port
        "
	::= { pm200fr20CntlocalLineTrscvPreSdFecBitCounterEntry 4 }


--- *********************************************************
---     TABLE for the pm200fr20CntlocalLineTrscvUncorrectedSdFecBitCounter articles
--- *********************************************************

pm200fr20CntlocalLineTrscvUncorrectedSdFecBitCounterTable OBJECT-TYPE
	SYNTAX  SEQUENCE OF Pm200fr20CntlocalLineTrscvUncorrectedSdFecBitCounterEntry
	MAX-ACCESS not-accessible
	STATUS current
	DESCRIPTION
        "
        List of pm200fr20CntlocalLineTrscvUncorrectedSdFecBitCounter 
        Article
        "
	::= { pm200fr20CntLine 199 }


pm200fr20CntlocalLineTrscvUncorrectedSdFecBitCounterEntry OBJECT-TYPE
	SYNTAX Pm200fr20CntlocalLineTrscvUncorrectedSdFecBitCounterEntry
	MAX-ACCESS not-accessible
	STATUS current
	DESCRIPTION
        "
        Row definition for the pm200fr20CntlocalLineTrscvUncorrectedSdFecBitCounter 
        table
        "
	INDEX   { pm200fr20CntlocalLineTrscvUncorrectedSdFecBitCounterIndex }
	::= { pm200fr20CntlocalLineTrscvUncorrectedSdFecBitCounterTable 1 }


Pm200fr20CntlocalLineTrscvUncorrectedSdFecBitCounterEntry ::=
	SEQUENCE {
	pm200fr20CntlocalLineTrscvUncorrectedSdFecBitCounterIndex
		INTEGER,
	pm200fr20CntlocalLineTrscvUncorrectedSdFecBitCounterValuePortn
		Counter64,
	pm200fr20CntlocalLineTrscvUncorrectedSdFecBitCounterErrorPortn
		EkiOnOff,
	pm200fr20CntlocalLineTrscvUncorrectedSdFecBitCounterOverloadPortn
		EkiOnOff
	}


pm200fr20CntlocalLineTrscvUncorrectedSdFecBitCounterIndex OBJECT-TYPE
	SYNTAX  INTEGER(0..128)
	MAX-ACCESS  read-only
	STATUS current
	DESCRIPTION
        "
        Index definition for the pm200fr20CntlocalLineTrscvUncorrectedSdFecBitCounter 
        table
        "
	::= { pm200fr20CntlocalLineTrscvUncorrectedSdFecBitCounterEntry 1 }


pm200fr20CntlocalLineTrscvUncorrectedSdFecBitCounterValuePortn OBJECT-TYPE
	SYNTAX  Counter64
	MAX-ACCESS read-only
	STATUS current
	DESCRIPTION
        "
        Uncorrected SD FEC Bit Counter 
        :This OID gives the current Bit 
        count after the Soft Decision FEC 
        (residual)  <Help> This counter 
        gives the current Bit Count after 
        the Soft Decision FEC (residual)
        "
	::= { pm200fr20CntlocalLineTrscvUncorrectedSdFecBitCounterEntry 2 }


pm200fr20CntlocalLineTrscvUncorrectedSdFecBitCounterErrorPortn OBJECT-TYPE
	SYNTAX  EkiOnOff
	MAX-ACCESS read-only
	STATUS current
	DESCRIPTION
        "
        Line Counter Error :This OID when 
        set indicates the deframer timer 
        counter value is invalid on Port
        "
	::= { pm200fr20CntlocalLineTrscvUncorrectedSdFecBitCounterEntry 3 }


pm200fr20CntlocalLineTrscvUncorrectedSdFecBitCounterOverloadPortn OBJECT-TYPE
	SYNTAX  EkiOnOff
	MAX-ACCESS read-only
	STATUS current
	DESCRIPTION
        "
        Line Counter Overload :This OID 
        when set indicates a deframer timer 
        counter overload on Port
        "
	::= { pm200fr20CntlocalLineTrscvUncorrectedSdFecBitCounterEntry 4 }







--- *****************************************************
--- $$$$$$$$$$$$$$$$$$$$$$$$$$$$$$$$$$$$$$$$$$$$$$$$$$$$$
---     RMON - 64 bits COUNTERS
--- $$$$$$$$$$$$$$$$$$$$$$$$$$$$$$$$$$$$$$$$$$$$$$$$$$$$$
--- *****************************************************



--- *********************************************************
---     TABLE for the pm200fr20MonupRmonBytesCounterClientInput articles
--- *********************************************************

pm200fr20MonupRmonBytesCounterClientInputTable OBJECT-TYPE
	SYNTAX  SEQUENCE OF Pm200fr20MonupRmonBytesCounterClientInputEntry
	MAX-ACCESS not-accessible
	STATUS current
	DESCRIPTION
        "
        List of pm200fr20MonupRmonBytesCounterClientInput 
        Article
        "
	::= { pm200fr20MonClientRmonCounter 16 }


pm200fr20MonupRmonBytesCounterClientInputEntry OBJECT-TYPE
	SYNTAX Pm200fr20MonupRmonBytesCounterClientInputEntry
	MAX-ACCESS not-accessible
	STATUS current
	DESCRIPTION
        "
        Row definition for the pm200fr20MonupRmonBytesCounterClientInput 
        table
        "
	INDEX   { pm200fr20MonupRmonBytesCounterClientInputIndex }
	::= { pm200fr20MonupRmonBytesCounterClientInputTable 1 }


Pm200fr20MonupRmonBytesCounterClientInputEntry ::=
	SEQUENCE {
	pm200fr20MonupRmonBytesCounterClientInputIndex
		INTEGER,
	pm200fr20MonupRmonBytesCounterClientInputValuePortn
		Counter64,
	pm200fr20MonupRmonBytesCounterClientInputErrorPortn
		EkiOnOff,
	pm200fr20MonupRmonBytesCounterClientInputOverloadPortn
		EkiOnOff
	}


pm200fr20MonupRmonBytesCounterClientInputIndex OBJECT-TYPE
	SYNTAX  INTEGER(0..128)
	MAX-ACCESS  read-only
	STATUS current
	DESCRIPTION
        "
        Index definition for the pm200fr20MonupRmonBytesCounterClientInput 
        table
        "
	::= { pm200fr20MonupRmonBytesCounterClientInputEntry 1 }


pm200fr20MonupRmonBytesCounterClientInputValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pm200fr20MonupRmonBytesCounterClientInputEntry 2 }


pm200fr20MonupRmonBytesCounterClientInputErrorPortn OBJECT-TYPE
	SYNTAX  EkiOnOff
	MAX-ACCESS read-only
	STATUS current
	DESCRIPTION
        "
        Bytes Counter Error :This OID
         when set indicates the Bytes counter 
        value is invalid on client port
        "
	::= { pm200fr20MonupRmonBytesCounterClientInputEntry 3 }


pm200fr20MonupRmonBytesCounterClientInputOverloadPortn OBJECT-TYPE
	SYNTAX  EkiOnOff
	MAX-ACCESS read-only
	STATUS current
	DESCRIPTION
        "
        Bytes Counter Overload :This OID 
        when set indicates a Bytes counter 
        overload on client port
        "
	::= { pm200fr20MonupRmonBytesCounterClientInputEntry 4 }


--- *********************************************************
---     TABLE for the pm200fr20MonupRmonCrcErrorsCounterClientInput articles
--- *********************************************************

pm200fr20MonupRmonCrcErrorsCounterClientInputTable OBJECT-TYPE
	SYNTAX  SEQUENCE OF Pm200fr20MonupRmonCrcErrorsCounterClientInputEntry
	MAX-ACCESS not-accessible
	STATUS current
	DESCRIPTION
        "
        List of pm200fr20MonupRmonCrcErrorsCounterClientInput 
        Article
        "
	::= { pm200fr20MonClientRmonCounter 48 }


pm200fr20MonupRmonCrcErrorsCounterClientInputEntry OBJECT-TYPE
	SYNTAX Pm200fr20MonupRmonCrcErrorsCounterClientInputEntry
	MAX-ACCESS not-accessible
	STATUS current
	DESCRIPTION
        "
        Row definition for the pm200fr20MonupRmonCrcErrorsCounterClientInput 
        table
        "
	INDEX   { pm200fr20MonupRmonCrcErrorsCounterClientInputIndex }
	::= { pm200fr20MonupRmonCrcErrorsCounterClientInputTable 1 }


Pm200fr20MonupRmonCrcErrorsCounterClientInputEntry ::=
	SEQUENCE {
	pm200fr20MonupRmonCrcErrorsCounterClientInputIndex
		INTEGER,
	pm200fr20MonupRmonCrcErrorsCounterClientInputValuePortn
		Counter64,
	pm200fr20MonupRmonCrcErrorsCounterClientInputErrorPortn
		EkiOnOff,
	pm200fr20MonupRmonCrcErrorsCounterClientInputOverloadPortn
		EkiOnOff
	}


pm200fr20MonupRmonCrcErrorsCounterClientInputIndex OBJECT-TYPE
	SYNTAX  INTEGER(0..128)
	MAX-ACCESS  read-only
	STATUS current
	DESCRIPTION
        "
        Index definition for the pm200fr20MonupRmonCrcErrorsCounterClientInput 
        table
        "
	::= { pm200fr20MonupRmonCrcErrorsCounterClientInputEntry 1 }


pm200fr20MonupRmonCrcErrorsCounterClientInputValuePortn OBJECT-TYPE
	SYNTAX  Counter64
	MAX-ACCESS read-only
	STATUS current
	DESCRIPTION
        "
        Client Input Errors :This counter 
        is increased each time a CRC error 
        is detected on the client port<Help> 
         This counter gives the number
         of CRC errors for 16GFC, 10GFC, 
        10GbE and B1 errors for OC192/STM64 
        received on Client port
        "
	::= { pm200fr20MonupRmonCrcErrorsCounterClientInputEntry 2 }


pm200fr20MonupRmonCrcErrorsCounterClientInputErrorPortn OBJECT-TYPE
	SYNTAX  EkiOnOff
	MAX-ACCESS read-only
	STATUS current
	DESCRIPTION
        "
        CRC Errors Counter Error :This 
        OID when set indicates the CRC
         Errors counter value is invalid 
        on client port
        "
	::= { pm200fr20MonupRmonCrcErrorsCounterClientInputEntry 3 }


pm200fr20MonupRmonCrcErrorsCounterClientInputOverloadPortn OBJECT-TYPE
	SYNTAX  EkiOnOff
	MAX-ACCESS read-only
	STATUS current
	DESCRIPTION
        "
        CRC Errors Counter Overload :This 
        OID when set indicates a CRC Errors 
        counter overload on client port
        "
	::= { pm200fr20MonupRmonCrcErrorsCounterClientInputEntry 4 }


--- *********************************************************
---     TABLE for the pm200fr20MonupRmonPacketsCounterClientInput articles
--- *********************************************************

pm200fr20MonupRmonPacketsCounterClientInputTable OBJECT-TYPE
	SYNTAX  SEQUENCE OF Pm200fr20MonupRmonPacketsCounterClientInputEntry
	MAX-ACCESS not-accessible
	STATUS current
	DESCRIPTION
        "
        List of pm200fr20MonupRmonPacketsCounterClientInput 
        Article
        "
	::= { pm200fr20MonClientRmonCounter 80 }


pm200fr20MonupRmonPacketsCounterClientInputEntry OBJECT-TYPE
	SYNTAX Pm200fr20MonupRmonPacketsCounterClientInputEntry
	MAX-ACCESS not-accessible
	STATUS current
	DESCRIPTION
        "
        Row definition for the pm200fr20MonupRmonPacketsCounterClientInput 
        table
        "
	INDEX   { pm200fr20MonupRmonPacketsCounterClientInputIndex }
	::= { pm200fr20MonupRmonPacketsCounterClientInputTable 1 }


Pm200fr20MonupRmonPacketsCounterClientInputEntry ::=
	SEQUENCE {
	pm200fr20MonupRmonPacketsCounterClientInputIndex
		INTEGER,
	pm200fr20MonupRmonPacketsCounterClientInputValuePortn
		Counter64,
	pm200fr20MonupRmonPacketsCounterClientInputErrorPortn
		EkiOnOff,
	pm200fr20MonupRmonPacketsCounterClientInputOverloadPortn
		EkiOnOff
	}


pm200fr20MonupRmonPacketsCounterClientInputIndex OBJECT-TYPE
	SYNTAX  INTEGER(0..128)
	MAX-ACCESS  read-only
	STATUS current
	DESCRIPTION
        "
        Index definition for the pm200fr20MonupRmonPacketsCounterClientInput 
        table
        "
	::= { pm200fr20MonupRmonPacketsCounterClientInputEntry 1 }


pm200fr20MonupRmonPacketsCounterClientInputValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pm200fr20MonupRmonPacketsCounterClientInputEntry 2 }


pm200fr20MonupRmonPacketsCounterClientInputErrorPortn OBJECT-TYPE
	SYNTAX  EkiOnOff
	MAX-ACCESS read-only
	STATUS current
	DESCRIPTION
        "
        Packets Counter Error :This OID 
        when set indicates the Packets
         counter value is invalid on client 
        port
        "
	::= { pm200fr20MonupRmonPacketsCounterClientInputEntry 3 }


pm200fr20MonupRmonPacketsCounterClientInputOverloadPortn OBJECT-TYPE
	SYNTAX  EkiOnOff
	MAX-ACCESS read-only
	STATUS current
	DESCRIPTION
        "
        Packets Counter Overload :This 
        OID when set indicates a Packets 
        counter overload on client port
        "
	::= { pm200fr20MonupRmonPacketsCounterClientInputEntry 4 }


--- *********************************************************
---     TABLE for the pm200fr20MonupRmonBroadcastCounterClientInput articles
--- *********************************************************

pm200fr20MonupRmonBroadcastCounterClientInputTable OBJECT-TYPE
	SYNTAX  SEQUENCE OF Pm200fr20MonupRmonBroadcastCounterClientInputEntry
	MAX-ACCESS not-accessible
	STATUS current
	DESCRIPTION
        "
        List of pm200fr20MonupRmonBroadcastCounterClientInput 
        Article
        "
	::= { pm200fr20MonClientRmonCounter 112 }


pm200fr20MonupRmonBroadcastCounterClientInputEntry OBJECT-TYPE
	SYNTAX Pm200fr20MonupRmonBroadcastCounterClientInputEntry
	MAX-ACCESS not-accessible
	STATUS current
	DESCRIPTION
        "
        Row definition for the pm200fr20MonupRmonBroadcastCounterClientInput 
        table
        "
	INDEX   { pm200fr20MonupRmonBroadcastCounterClientInputIndex }
	::= { pm200fr20MonupRmonBroadcastCounterClientInputTable 1 }


Pm200fr20MonupRmonBroadcastCounterClientInputEntry ::=
	SEQUENCE {
	pm200fr20MonupRmonBroadcastCounterClientInputIndex
		INTEGER,
	pm200fr20MonupRmonBroadcastCounterClientInputValuePortn
		Counter64,
	pm200fr20MonupRmonBroadcastCounterClientInputErrorPortn
		EkiOnOff,
	pm200fr20MonupRmonBroadcastCounterClientInputOverloadPortn
		EkiOnOff
	}


pm200fr20MonupRmonBroadcastCounterClientInputIndex OBJECT-TYPE
	SYNTAX  INTEGER(0..128)
	MAX-ACCESS  read-only
	STATUS current
	DESCRIPTION
        "
        Index definition for the pm200fr20MonupRmonBroadcastCounterClientInput 
        table
        "
	::= { pm200fr20MonupRmonBroadcastCounterClientInputEntry 1 }


pm200fr20MonupRmonBroadcastCounterClientInputValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pm200fr20MonupRmonBroadcastCounterClientInputEntry 2 }


pm200fr20MonupRmonBroadcastCounterClientInputErrorPortn OBJECT-TYPE
	SYNTAX  EkiOnOff
	MAX-ACCESS read-only
	STATUS current
	DESCRIPTION
        "
        Broadcast Counter Error :This
         OID when set indicates the Broadcast 
        counter value is invalid on client 
        port
        "
	::= { pm200fr20MonupRmonBroadcastCounterClientInputEntry 3 }


pm200fr20MonupRmonBroadcastCounterClientInputOverloadPortn OBJECT-TYPE
	SYNTAX  EkiOnOff
	MAX-ACCESS read-only
	STATUS current
	DESCRIPTION
        "
        Broadcast Counter Overload :This 
        OID when set indicates a Broadcast 
        counter overload on client port
        "
	::= { pm200fr20MonupRmonBroadcastCounterClientInputEntry 4 }


--- *********************************************************
---     TABLE for the pm200fr20MonupRmonMulticastCounterClientInput articles
--- *********************************************************

pm200fr20MonupRmonMulticastCounterClientInputTable OBJECT-TYPE
	SYNTAX  SEQUENCE OF Pm200fr20MonupRmonMulticastCounterClientInputEntry
	MAX-ACCESS not-accessible
	STATUS current
	DESCRIPTION
        "
        List of pm200fr20MonupRmonMulticastCounterClientInput 
        Article
        "
	::= { pm200fr20MonClientRmonCounter 144 }


pm200fr20MonupRmonMulticastCounterClientInputEntry OBJECT-TYPE
	SYNTAX Pm200fr20MonupRmonMulticastCounterClientInputEntry
	MAX-ACCESS not-accessible
	STATUS current
	DESCRIPTION
        "
        Row definition for the pm200fr20MonupRmonMulticastCounterClientInput 
        table
        "
	INDEX   { pm200fr20MonupRmonMulticastCounterClientInputIndex }
	::= { pm200fr20MonupRmonMulticastCounterClientInputTable 1 }


Pm200fr20MonupRmonMulticastCounterClientInputEntry ::=
	SEQUENCE {
	pm200fr20MonupRmonMulticastCounterClientInputIndex
		INTEGER,
	pm200fr20MonupRmonMulticastCounterClientInputValuePortn
		Counter64,
	pm200fr20MonupRmonMulticastCounterClientInputErrorPortn
		EkiOnOff,
	pm200fr20MonupRmonMulticastCounterClientInputOverloadPortn
		EkiOnOff
	}


pm200fr20MonupRmonMulticastCounterClientInputIndex OBJECT-TYPE
	SYNTAX  INTEGER(0..128)
	MAX-ACCESS  read-only
	STATUS current
	DESCRIPTION
        "
        Index definition for the pm200fr20MonupRmonMulticastCounterClientInput 
        table
        "
	::= { pm200fr20MonupRmonMulticastCounterClientInputEntry 1 }


pm200fr20MonupRmonMulticastCounterClientInputValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pm200fr20MonupRmonMulticastCounterClientInputEntry 2 }


pm200fr20MonupRmonMulticastCounterClientInputErrorPortn OBJECT-TYPE
	SYNTAX  EkiOnOff
	MAX-ACCESS read-only
	STATUS current
	DESCRIPTION
        "
        Multicast Counter Error :This
         OID when set indicates the Multicast 
        counter value is invalid on client 
        port
        "
	::= { pm200fr20MonupRmonMulticastCounterClientInputEntry 3 }


pm200fr20MonupRmonMulticastCounterClientInputOverloadPortn OBJECT-TYPE
	SYNTAX  EkiOnOff
	MAX-ACCESS read-only
	STATUS current
	DESCRIPTION
        "
        Multicast Counter Overload :This 
        OID when set indicates a Multicast 
        counter overload on client port
        "
	::= { pm200fr20MonupRmonMulticastCounterClientInputEntry 4 }


--- *********************************************************
---     TABLE for the pm200fr20MonupRmonPauseFrameCounterClientInput articles
--- *********************************************************

pm200fr20MonupRmonPauseFrameCounterClientInputTable OBJECT-TYPE
	SYNTAX  SEQUENCE OF Pm200fr20MonupRmonPauseFrameCounterClientInputEntry
	MAX-ACCESS not-accessible
	STATUS current
	DESCRIPTION
        "
        List of pm200fr20MonupRmonPauseFrameCounterClientInput 
        Article
        "
	::= { pm200fr20MonClientRmonCounter 176 }


pm200fr20MonupRmonPauseFrameCounterClientInputEntry OBJECT-TYPE
	SYNTAX Pm200fr20MonupRmonPauseFrameCounterClientInputEntry
	MAX-ACCESS not-accessible
	STATUS current
	DESCRIPTION
        "
        Row definition for the pm200fr20MonupRmonPauseFrameCounterClientInput 
        table
        "
	INDEX   { pm200fr20MonupRmonPauseFrameCounterClientInputIndex }
	::= { pm200fr20MonupRmonPauseFrameCounterClientInputTable 1 }


Pm200fr20MonupRmonPauseFrameCounterClientInputEntry ::=
	SEQUENCE {
	pm200fr20MonupRmonPauseFrameCounterClientInputIndex
		INTEGER,
	pm200fr20MonupRmonPauseFrameCounterClientInputValuePortn
		Counter64,
	pm200fr20MonupRmonPauseFrameCounterClientInputErrorPortn
		EkiOnOff,
	pm200fr20MonupRmonPauseFrameCounterClientInputOverloadPortn
		EkiOnOff
	}


pm200fr20MonupRmonPauseFrameCounterClientInputIndex OBJECT-TYPE
	SYNTAX  INTEGER(0..128)
	MAX-ACCESS  read-only
	STATUS current
	DESCRIPTION
        "
        Index definition for the pm200fr20MonupRmonPauseFrameCounterClientInput 
        table
        "
	::= { pm200fr20MonupRmonPauseFrameCounterClientInputEntry 1 }


pm200fr20MonupRmonPauseFrameCounterClientInputValuePortn OBJECT-TYPE
	SYNTAX  Counter64
	MAX-ACCESS read-only
	STATUS current
	DESCRIPTION
        "
        Client Input Pause Frames :This 
        counter is increased each time
         a Pause frame is received on the 
        client port  <Help>  This counter 
        gives the number of Pause frames 
        received on the client port
        "
	::= { pm200fr20MonupRmonPauseFrameCounterClientInputEntry 2 }


pm200fr20MonupRmonPauseFrameCounterClientInputErrorPortn OBJECT-TYPE
	SYNTAX  EkiOnOff
	MAX-ACCESS read-only
	STATUS current
	DESCRIPTION
        "
        Pause Counter Error :This OID
         when set indicates the Pause counter 
        value is invalid on client port
        "
	::= { pm200fr20MonupRmonPauseFrameCounterClientInputEntry 3 }


pm200fr20MonupRmonPauseFrameCounterClientInputOverloadPortn OBJECT-TYPE
	SYNTAX  EkiOnOff
	MAX-ACCESS read-only
	STATUS current
	DESCRIPTION
        "
        Pause Counter Overload :This OID 
        when set indicates a Pause counter 
        overload on client port
        "
	::= { pm200fr20MonupRmonPauseFrameCounterClientInputEntry 4 }


--- *********************************************************
---     TABLE for the pm200fr20MonupRmonUnicastCounterClientInput articles
--- *********************************************************

pm200fr20MonupRmonUnicastCounterClientInputTable OBJECT-TYPE
	SYNTAX  SEQUENCE OF Pm200fr20MonupRmonUnicastCounterClientInputEntry
	MAX-ACCESS not-accessible
	STATUS current
	DESCRIPTION
        "
        List of pm200fr20MonupRmonUnicastCounterClientInput 
        Article
        "
	::= { pm200fr20MonClientRmonCounter 304 }


pm200fr20MonupRmonUnicastCounterClientInputEntry OBJECT-TYPE
	SYNTAX Pm200fr20MonupRmonUnicastCounterClientInputEntry
	MAX-ACCESS not-accessible
	STATUS current
	DESCRIPTION
        "
        Row definition for the pm200fr20MonupRmonUnicastCounterClientInput 
        table
        "
	INDEX   { pm200fr20MonupRmonUnicastCounterClientInputIndex }
	::= { pm200fr20MonupRmonUnicastCounterClientInputTable 1 }


Pm200fr20MonupRmonUnicastCounterClientInputEntry ::=
	SEQUENCE {
	pm200fr20MonupRmonUnicastCounterClientInputIndex
		INTEGER,
	pm200fr20MonupRmonUnicastCounterClientInputValuePortn
		Counter64,
	pm200fr20MonupRmonUnicastCounterClientInputErrorPortn
		EkiOnOff,
	pm200fr20MonupRmonUnicastCounterClientInputOverloadPortn
		EkiOnOff
	}


pm200fr20MonupRmonUnicastCounterClientInputIndex OBJECT-TYPE
	SYNTAX  INTEGER(0..128)
	MAX-ACCESS  read-only
	STATUS current
	DESCRIPTION
        "
        Index definition for the pm200fr20MonupRmonUnicastCounterClientInput 
        table
        "
	::= { pm200fr20MonupRmonUnicastCounterClientInputEntry 1 }


pm200fr20MonupRmonUnicastCounterClientInputValuePortn OBJECT-TYPE
	SYNTAX  Counter64
	MAX-ACCESS read-only
	STATUS current
	DESCRIPTION
        "
        Client Input Unicast Packets :This 
        counter is increased each time
         a Unicast packet is received on 
        the client port  <Help>  This counter 
        gives the number of Unicast packets 
        received on the client port
        "
	::= { pm200fr20MonupRmonUnicastCounterClientInputEntry 2 }


pm200fr20MonupRmonUnicastCounterClientInputErrorPortn OBJECT-TYPE
	SYNTAX  EkiOnOff
	MAX-ACCESS read-only
	STATUS current
	DESCRIPTION
        "
        Unicast Counter Error :This OID 
        when set indicates the Unicast
         counter value is invalid on client 
        port
        "
	::= { pm200fr20MonupRmonUnicastCounterClientInputEntry 3 }


pm200fr20MonupRmonUnicastCounterClientInputOverloadPortn OBJECT-TYPE
	SYNTAX  EkiOnOff
	MAX-ACCESS read-only
	STATUS current
	DESCRIPTION
        "
        Unicast Counter Overload :This 
        OID when set indicates a Unicast 
        counter overload on client port
        "
	::= { pm200fr20MonupRmonUnicastCounterClientInputEntry 4 }


--- *********************************************************
---     TABLE for the pm200fr20MonupRmonNonunicastCounterClientInput articles
--- *********************************************************

pm200fr20MonupRmonNonunicastCounterClientInputTable OBJECT-TYPE
	SYNTAX  SEQUENCE OF Pm200fr20MonupRmonNonunicastCounterClientInputEntry
	MAX-ACCESS not-accessible
	STATUS current
	DESCRIPTION
        "
        List of pm200fr20MonupRmonNonunicastCounterClientInput 
        Article
        "
	::= { pm200fr20MonClientRmonCounter 336 }


pm200fr20MonupRmonNonunicastCounterClientInputEntry OBJECT-TYPE
	SYNTAX Pm200fr20MonupRmonNonunicastCounterClientInputEntry
	MAX-ACCESS not-accessible
	STATUS current
	DESCRIPTION
        "
        Row definition for the pm200fr20MonupRmonNonunicastCounterClientInput 
        table
        "
	INDEX   { pm200fr20MonupRmonNonunicastCounterClientInputIndex }
	::= { pm200fr20MonupRmonNonunicastCounterClientInputTable 1 }


Pm200fr20MonupRmonNonunicastCounterClientInputEntry ::=
	SEQUENCE {
	pm200fr20MonupRmonNonunicastCounterClientInputIndex
		INTEGER,
	pm200fr20MonupRmonNonunicastCounterClientInputValuePortn
		Counter64,
	pm200fr20MonupRmonNonunicastCounterClientInputErrorPortn
		EkiOnOff,
	pm200fr20MonupRmonNonunicastCounterClientInputOverloadPortn
		EkiOnOff
	}


pm200fr20MonupRmonNonunicastCounterClientInputIndex OBJECT-TYPE
	SYNTAX  INTEGER(0..128)
	MAX-ACCESS  read-only
	STATUS current
	DESCRIPTION
        "
        Index definition for the pm200fr20MonupRmonNonunicastCounterClientInput 
        table
        "
	::= { pm200fr20MonupRmonNonunicastCounterClientInputEntry 1 }


pm200fr20MonupRmonNonunicastCounterClientInputValuePortn OBJECT-TYPE
	SYNTAX  Counter64
	MAX-ACCESS read-only
	STATUS current
	DESCRIPTION
        "
        Client Input Non Unicast Packets 
        :This counter is increased each 
        time a Non-Unicast packet is received 
        on the client port  <Help>  This 
        counter gives the number of Non-Unicast 
        packets received on the client
         port
        "
	::= { pm200fr20MonupRmonNonunicastCounterClientInputEntry 2 }


pm200fr20MonupRmonNonunicastCounterClientInputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pm200fr20MonupRmonNonunicastCounterClientInputEntry 3 }


pm200fr20MonupRmonNonunicastCounterClientInputOverloadPortn OBJECT-TYPE
	SYNTAX  EkiOnOff
	MAX-ACCESS read-only
	STATUS current
	DESCRIPTION
        "
        Non Unicast Counter Overload :This 
        OID when set indicates a Non-Unicast 
        counter overload on client port
        "
	::= { pm200fr20MonupRmonNonunicastCounterClientInputEntry 4 }


--- *********************************************************
---     TABLE for the pm200fr20MondownRmonBytesCounterClientOutput articles
--- *********************************************************

pm200fr20MondownRmonBytesCounterClientOutputTable OBJECT-TYPE
	SYNTAX  SEQUENCE OF Pm200fr20MondownRmonBytesCounterClientOutputEntry
	MAX-ACCESS not-accessible
	STATUS current
	DESCRIPTION
        "
        List of pm200fr20MondownRmonBytesCounterClientOutput 
        Article
        "
	::= { pm200fr20MonClientRmonCounter 400 }


pm200fr20MondownRmonBytesCounterClientOutputEntry OBJECT-TYPE
	SYNTAX Pm200fr20MondownRmonBytesCounterClientOutputEntry
	MAX-ACCESS not-accessible
	STATUS current
	DESCRIPTION
        "
        Row definition for the pm200fr20MondownRmonBytesCounterClientOutput 
        table
        "
	INDEX   { pm200fr20MondownRmonBytesCounterClientOutputIndex }
	::= { pm200fr20MondownRmonBytesCounterClientOutputTable 1 }


Pm200fr20MondownRmonBytesCounterClientOutputEntry ::=
	SEQUENCE {
	pm200fr20MondownRmonBytesCounterClientOutputIndex
		INTEGER,
	pm200fr20MondownRmonBytesCounterClientOutputValuePortn
		Counter64,
	pm200fr20MondownRmonBytesCounterClientOutputErrorPortn
		EkiOnOff,
	pm200fr20MondownRmonBytesCounterClientOutputOverloadPortn
		EkiOnOff
	}


pm200fr20MondownRmonBytesCounterClientOutputIndex OBJECT-TYPE
	SYNTAX  INTEGER(0..128)
	MAX-ACCESS  read-only
	STATUS current
	DESCRIPTION
        "
        Index definition for the pm200fr20MondownRmonBytesCounterClientOutput 
        table
        "
	::= { pm200fr20MondownRmonBytesCounterClientOutputEntry 1 }


pm200fr20MondownRmonBytesCounterClientOutputValuePortn OBJECT-TYPE
	SYNTAX  Counter64
	MAX-ACCESS read-only
	STATUS current
	DESCRIPTION
        "
        Client Output Bytes :This counter 
        is increased each time a data byte 
        is transmitted on the client port 
        <Help> This counter gives the number 
        of bytes transmitted on the client 
        port
        "
	::= { pm200fr20MondownRmonBytesCounterClientOutputEntry 2 }


pm200fr20MondownRmonBytesCounterClientOutputErrorPortn OBJECT-TYPE
	SYNTAX  EkiOnOff
	MAX-ACCESS read-only
	STATUS current
	DESCRIPTION
        "
        Bytes Counter Error :This OID
         when set indicates the Bytes counter 
        value is invalid on client port
        "
	::= { pm200fr20MondownRmonBytesCounterClientOutputEntry 3 }


pm200fr20MondownRmonBytesCounterClientOutputOverloadPortn OBJECT-TYPE
	SYNTAX  EkiOnOff
	MAX-ACCESS read-only
	STATUS current
	DESCRIPTION
        "
        Bytes Counter Overload :This OID 
        when set indicates a Bytes counter 
        overload on client port

        "
	::= { pm200fr20MondownRmonBytesCounterClientOutputEntry 4 }


--- *********************************************************
---     TABLE for the pm200fr20MondownRmonCrcErrorsCounterClientOutput articles
--- *********************************************************

pm200fr20MondownRmonCrcErrorsCounterClientOutputTable OBJECT-TYPE
	SYNTAX  SEQUENCE OF Pm200fr20MondownRmonCrcErrorsCounterClientOutputEntry
	MAX-ACCESS not-accessible
	STATUS current
	DESCRIPTION
        "
        List of pm200fr20MondownRmonCrcErrorsCounterClientOutput 
        Article
        "
	::= { pm200fr20MonClientRmonCounter 432 }


pm200fr20MondownRmonCrcErrorsCounterClientOutputEntry OBJECT-TYPE
	SYNTAX Pm200fr20MondownRmonCrcErrorsCounterClientOutputEntry
	MAX-ACCESS not-accessible
	STATUS current
	DESCRIPTION
        "
        Row definition for the pm200fr20MondownRmonCrcErrorsCounterClientOutput 
        table
        "
	INDEX   { pm200fr20MondownRmonCrcErrorsCounterClientOutputIndex }
	::= { pm200fr20MondownRmonCrcErrorsCounterClientOutputTable 1 }


Pm200fr20MondownRmonCrcErrorsCounterClientOutputEntry ::=
	SEQUENCE {
	pm200fr20MondownRmonCrcErrorsCounterClientOutputIndex
		INTEGER,
	pm200fr20MondownRmonCrcErrorsCounterClientOutputValuePortn
		Counter64,
	pm200fr20MondownRmonCrcErrorsCounterClientOutputErrorPortn
		EkiOnOff,
	pm200fr20MondownRmonCrcErrorsCounterClientOutputOverloadPortn
		EkiOnOff
	}


pm200fr20MondownRmonCrcErrorsCounterClientOutputIndex OBJECT-TYPE
	SYNTAX  INTEGER(0..128)
	MAX-ACCESS  read-only
	STATUS current
	DESCRIPTION
        "
        Index definition for the pm200fr20MondownRmonCrcErrorsCounterClientOutput 
        table
        "
	::= { pm200fr20MondownRmonCrcErrorsCounterClientOutputEntry 1 }


pm200fr20MondownRmonCrcErrorsCounterClientOutputValuePortn OBJECT-TYPE
	SYNTAX  Counter64
	MAX-ACCESS read-only
	STATUS current
	DESCRIPTION
        "
        Client Output Errors :This counter 
        is increased each time a CRC error 
        is detected on the transmit client 
        port  <Help>  This counter gives 
        the number of CRC errors for 16GFC, 
        10GFC, 10GbE and B1 errors for
         OC192/STM64 transmitted on Client 
        port
        "
	::= { pm200fr20MondownRmonCrcErrorsCounterClientOutputEntry 2 }


pm200fr20MondownRmonCrcErrorsCounterClientOutputErrorPortn OBJECT-TYPE
	SYNTAX  EkiOnOff
	MAX-ACCESS read-only
	STATUS current
	DESCRIPTION
        "
        CRC Errors Counter Error :This 
        OID when set indicates the CRC
         Errors counter value is invalid 
        on client port
        "
	::= { pm200fr20MondownRmonCrcErrorsCounterClientOutputEntry 3 }


pm200fr20MondownRmonCrcErrorsCounterClientOutputOverloadPortn OBJECT-TYPE
	SYNTAX  EkiOnOff
	MAX-ACCESS read-only
	STATUS current
	DESCRIPTION
        "
        CRC Errors Counter Overload :This 
        OID when set indicates a CRC Errors 
        counter overload on client port
        "
	::= { pm200fr20MondownRmonCrcErrorsCounterClientOutputEntry 4 }


--- *********************************************************
---     TABLE for the pm200fr20MondownRmonPacketsCounterClientOutput articles
--- *********************************************************

pm200fr20MondownRmonPacketsCounterClientOutputTable OBJECT-TYPE
	SYNTAX  SEQUENCE OF Pm200fr20MondownRmonPacketsCounterClientOutputEntry
	MAX-ACCESS not-accessible
	STATUS current
	DESCRIPTION
        "
        List of pm200fr20MondownRmonPacketsCounterClientOutput 
        Article
        "
	::= { pm200fr20MonClientRmonCounter 464 }


pm200fr20MondownRmonPacketsCounterClientOutputEntry OBJECT-TYPE
	SYNTAX Pm200fr20MondownRmonPacketsCounterClientOutputEntry
	MAX-ACCESS not-accessible
	STATUS current
	DESCRIPTION
        "
        Row definition for the pm200fr20MondownRmonPacketsCounterClientOutput 
        table
        "
	INDEX   { pm200fr20MondownRmonPacketsCounterClientOutputIndex }
	::= { pm200fr20MondownRmonPacketsCounterClientOutputTable 1 }


Pm200fr20MondownRmonPacketsCounterClientOutputEntry ::=
	SEQUENCE {
	pm200fr20MondownRmonPacketsCounterClientOutputIndex
		INTEGER,
	pm200fr20MondownRmonPacketsCounterClientOutputValuePortn
		Counter64,
	pm200fr20MondownRmonPacketsCounterClientOutputErrorPortn
		EkiOnOff,
	pm200fr20MondownRmonPacketsCounterClientOutputOverloadPortn
		EkiOnOff
	}


pm200fr20MondownRmonPacketsCounterClientOutputIndex OBJECT-TYPE
	SYNTAX  INTEGER(0..128)
	MAX-ACCESS  read-only
	STATUS current
	DESCRIPTION
        "
        Index definition for the pm200fr20MondownRmonPacketsCounterClientOutput 
        table
        "
	::= { pm200fr20MondownRmonPacketsCounterClientOutputEntry 1 }


pm200fr20MondownRmonPacketsCounterClientOutputValuePortn OBJECT-TYPE
	SYNTAX  Counter64
	MAX-ACCESS read-only
	STATUS current
	DESCRIPTION
        "
        Client Output Packets :This counter 
        is increased each time a packet 
        is transmitted on the client port 
         <Help>  This counter gives the 
        number of packets transmitted on 
        the client port
        "
	::= { pm200fr20MondownRmonPacketsCounterClientOutputEntry 2 }


pm200fr20MondownRmonPacketsCounterClientOutputErrorPortn OBJECT-TYPE
	SYNTAX  EkiOnOff
	MAX-ACCESS read-only
	STATUS current
	DESCRIPTION
        "
        Packets Counter Error :This OID 
        when set indicates the Packets
         counter value is invalid on client 
        port
        "
	::= { pm200fr20MondownRmonPacketsCounterClientOutputEntry 3 }


pm200fr20MondownRmonPacketsCounterClientOutputOverloadPortn OBJECT-TYPE
	SYNTAX  EkiOnOff
	MAX-ACCESS read-only
	STATUS current
	DESCRIPTION
        "
        Packets Counter Overload :This 
        OID when set indicates a Packets 
        counter overload on client port
        "
	::= { pm200fr20MondownRmonPacketsCounterClientOutputEntry 4 }


--- *********************************************************
---     TABLE for the pm200fr20MondownRmonBroadcastCounterClientOutput articles
--- *********************************************************

pm200fr20MondownRmonBroadcastCounterClientOutputTable OBJECT-TYPE
	SYNTAX  SEQUENCE OF Pm200fr20MondownRmonBroadcastCounterClientOutputEntry
	MAX-ACCESS not-accessible
	STATUS current
	DESCRIPTION
        "
        List of pm200fr20MondownRmonBroadcastCounterClientOutput 
        Article
        "
	::= { pm200fr20MonClientRmonCounter 496 }


pm200fr20MondownRmonBroadcastCounterClientOutputEntry OBJECT-TYPE
	SYNTAX Pm200fr20MondownRmonBroadcastCounterClientOutputEntry
	MAX-ACCESS not-accessible
	STATUS current
	DESCRIPTION
        "
        Row definition for the pm200fr20MondownRmonBroadcastCounterClientOutput 
        table
        "
	INDEX   { pm200fr20MondownRmonBroadcastCounterClientOutputIndex }
	::= { pm200fr20MondownRmonBroadcastCounterClientOutputTable 1 }


Pm200fr20MondownRmonBroadcastCounterClientOutputEntry ::=
	SEQUENCE {
	pm200fr20MondownRmonBroadcastCounterClientOutputIndex
		INTEGER,
	pm200fr20MondownRmonBroadcastCounterClientOutputValuePortn
		Counter64,
	pm200fr20MondownRmonBroadcastCounterClientOutputErrorPortn
		EkiOnOff,
	pm200fr20MondownRmonBroadcastCounterClientOutputOverloadPortn
		EkiOnOff
	}


pm200fr20MondownRmonBroadcastCounterClientOutputIndex OBJECT-TYPE
	SYNTAX  INTEGER(0..128)
	MAX-ACCESS  read-only
	STATUS current
	DESCRIPTION
        "
        Index definition for the pm200fr20MondownRmonBroadcastCounterClientOutput 
        table
        "
	::= { pm200fr20MondownRmonBroadcastCounterClientOutputEntry 1 }


pm200fr20MondownRmonBroadcastCounterClientOutputValuePortn OBJECT-TYPE
	SYNTAX  Counter64
	MAX-ACCESS read-only
	STATUS current
	DESCRIPTION
        "
        Client Output Broadcast Packets 
        :This counter is increased each 
        time a broadcast packet is transmitted 
        on the client port  <Help>  This 
        counter gives the number of Broadcast 
        packets transmitted on the client 
        port
        "
	::= { pm200fr20MondownRmonBroadcastCounterClientOutputEntry 2 }


pm200fr20MondownRmonBroadcastCounterClientOutputErrorPortn OBJECT-TYPE
	SYNTAX  EkiOnOff
	MAX-ACCESS read-only
	STATUS current
	DESCRIPTION
        "
        Broadcast Counter Error :This
         OID when set indicates the Broadcast 
        counter value is invalid on client 
        port
        "
	::= { pm200fr20MondownRmonBroadcastCounterClientOutputEntry 3 }


pm200fr20MondownRmonBroadcastCounterClientOutputOverloadPortn OBJECT-TYPE
	SYNTAX  EkiOnOff
	MAX-ACCESS read-only
	STATUS current
	DESCRIPTION
        "
        Broadcast Counter Overload :This 
        OID when set indicates a Broadcast 
        counter overload on client port
        "
	::= { pm200fr20MondownRmonBroadcastCounterClientOutputEntry 4 }


--- *********************************************************
---     TABLE for the pm200fr20MondownRmonMulticastCounterClientOutput articles
--- *********************************************************

pm200fr20MondownRmonMulticastCounterClientOutputTable OBJECT-TYPE
	SYNTAX  SEQUENCE OF Pm200fr20MondownRmonMulticastCounterClientOutputEntry
	MAX-ACCESS not-accessible
	STATUS current
	DESCRIPTION
        "
        List of pm200fr20MondownRmonMulticastCounterClientOutput 
        Article
        "
	::= { pm200fr20MonClientRmonCounter 528 }


pm200fr20MondownRmonMulticastCounterClientOutputEntry OBJECT-TYPE
	SYNTAX Pm200fr20MondownRmonMulticastCounterClientOutputEntry
	MAX-ACCESS not-accessible
	STATUS current
	DESCRIPTION
        "
        Row definition for the pm200fr20MondownRmonMulticastCounterClientOutput 
        table
        "
	INDEX   { pm200fr20MondownRmonMulticastCounterClientOutputIndex }
	::= { pm200fr20MondownRmonMulticastCounterClientOutputTable 1 }


Pm200fr20MondownRmonMulticastCounterClientOutputEntry ::=
	SEQUENCE {
	pm200fr20MondownRmonMulticastCounterClientOutputIndex
		INTEGER,
	pm200fr20MondownRmonMulticastCounterClientOutputValuePortn
		Counter64,
	pm200fr20MondownRmonMulticastCounterClientOutputErrorPortn
		EkiOnOff,
	pm200fr20MondownRmonMulticastCounterClientOutputOverloadPortn
		EkiOnOff
	}


pm200fr20MondownRmonMulticastCounterClientOutputIndex OBJECT-TYPE
	SYNTAX  INTEGER(0..128)
	MAX-ACCESS  read-only
	STATUS current
	DESCRIPTION
        "
        Index definition for the pm200fr20MondownRmonMulticastCounterClientOutput 
        table
        "
	::= { pm200fr20MondownRmonMulticastCounterClientOutputEntry 1 }


pm200fr20MondownRmonMulticastCounterClientOutputValuePortn OBJECT-TYPE
	SYNTAX  Counter64
	MAX-ACCESS read-only
	STATUS current
	DESCRIPTION
        "
        Client Output Multicast Packets 
        :This counter is increased each 
        time a Multicast packet is transmitted 
        on the client port  <Help>  This 
        counter gives the number of Multicast 
        packets transmitted on the client 
        port
        "
	::= { pm200fr20MondownRmonMulticastCounterClientOutputEntry 2 }


pm200fr20MondownRmonMulticastCounterClientOutputErrorPortn OBJECT-TYPE
	SYNTAX  EkiOnOff
	MAX-ACCESS read-only
	STATUS current
	DESCRIPTION
        "
        Multicast Counter Error :This
         OID when set indicates the Multicast 
        counter value is invalid on client 
        port
        "
	::= { pm200fr20MondownRmonMulticastCounterClientOutputEntry 3 }


pm200fr20MondownRmonMulticastCounterClientOutputOverloadPortn OBJECT-TYPE
	SYNTAX  EkiOnOff
	MAX-ACCESS read-only
	STATUS current
	DESCRIPTION
        "
        Multicast Counter Overload :This 
        OID when set indicates a Multicast 
        counter overload on client port
        "
	::= { pm200fr20MondownRmonMulticastCounterClientOutputEntry 4 }


--- *********************************************************
---     TABLE for the pm200fr20MondownRmonPauseFrameCounterClientOutput articles
--- *********************************************************

pm200fr20MondownRmonPauseFrameCounterClientOutputTable OBJECT-TYPE
	SYNTAX  SEQUENCE OF Pm200fr20MondownRmonPauseFrameCounterClientOutputEntry
	MAX-ACCESS not-accessible
	STATUS current
	DESCRIPTION
        "
        List of pm200fr20MondownRmonPauseFrameCounterClientOutput 
        Article
        "
	::= { pm200fr20MonClientRmonCounter 560 }


pm200fr20MondownRmonPauseFrameCounterClientOutputEntry OBJECT-TYPE
	SYNTAX Pm200fr20MondownRmonPauseFrameCounterClientOutputEntry
	MAX-ACCESS not-accessible
	STATUS current
	DESCRIPTION
        "
        Row definition for the pm200fr20MondownRmonPauseFrameCounterClientOutput 
        table
        "
	INDEX   { pm200fr20MondownRmonPauseFrameCounterClientOutputIndex }
	::= { pm200fr20MondownRmonPauseFrameCounterClientOutputTable 1 }


Pm200fr20MondownRmonPauseFrameCounterClientOutputEntry ::=
	SEQUENCE {
	pm200fr20MondownRmonPauseFrameCounterClientOutputIndex
		INTEGER,
	pm200fr20MondownRmonPauseFrameCounterClientOutputValuePortn
		Counter64,
	pm200fr20MondownRmonPauseFrameCounterClientOutputErrorPortn
		EkiOnOff,
	pm200fr20MondownRmonPauseFrameCounterClientOutputOverloadPortn
		EkiOnOff
	}


pm200fr20MondownRmonPauseFrameCounterClientOutputIndex OBJECT-TYPE
	SYNTAX  INTEGER(0..128)
	MAX-ACCESS  read-only
	STATUS current
	DESCRIPTION
        "
        Index definition for the pm200fr20MondownRmonPauseFrameCounterClientOutput 
        table
        "
	::= { pm200fr20MondownRmonPauseFrameCounterClientOutputEntry 1 }


pm200fr20MondownRmonPauseFrameCounterClientOutputValuePortn OBJECT-TYPE
	SYNTAX  Counter64
	MAX-ACCESS read-only
	STATUS current
	DESCRIPTION
        "
        Client Output Pause Frames :This 
        counter is increased each time
         a Pause frame is transmitted on 
        the client port  <Help>  This counter 
        gives the number of Pause frames 
        transmitted on the client port
        "
	::= { pm200fr20MondownRmonPauseFrameCounterClientOutputEntry 2 }


pm200fr20MondownRmonPauseFrameCounterClientOutputErrorPortn OBJECT-TYPE
	SYNTAX  EkiOnOff
	MAX-ACCESS read-only
	STATUS current
	DESCRIPTION
        "
        Pause Counter Error :This OID
         when set indicates the Pause counter 
        value is invalid on client port
        "
	::= { pm200fr20MondownRmonPauseFrameCounterClientOutputEntry 3 }


pm200fr20MondownRmonPauseFrameCounterClientOutputOverloadPortn OBJECT-TYPE
	SYNTAX  EkiOnOff
	MAX-ACCESS read-only
	STATUS current
	DESCRIPTION
        "
        Pause Counter Overload :This OID 
        when set indicates a Pause counter 
        overload on client port
        "
	::= { pm200fr20MondownRmonPauseFrameCounterClientOutputEntry 4 }


--- *********************************************************
---     TABLE for the pm200fr20MondownRmonUnicastCounterClientOutput articles
--- *********************************************************

pm200fr20MondownRmonUnicastCounterClientOutputTable OBJECT-TYPE
	SYNTAX  SEQUENCE OF Pm200fr20MondownRmonUnicastCounterClientOutputEntry
	MAX-ACCESS not-accessible
	STATUS current
	DESCRIPTION
        "
        List of pm200fr20MondownRmonUnicastCounterClientOutput 
        Article
        "
	::= { pm200fr20MonClientRmonCounter 688 }


pm200fr20MondownRmonUnicastCounterClientOutputEntry OBJECT-TYPE
	SYNTAX Pm200fr20MondownRmonUnicastCounterClientOutputEntry
	MAX-ACCESS not-accessible
	STATUS current
	DESCRIPTION
        "
        Row definition for the pm200fr20MondownRmonUnicastCounterClientOutput 
        table
        "
	INDEX   { pm200fr20MondownRmonUnicastCounterClientOutputIndex }
	::= { pm200fr20MondownRmonUnicastCounterClientOutputTable 1 }


Pm200fr20MondownRmonUnicastCounterClientOutputEntry ::=
	SEQUENCE {
	pm200fr20MondownRmonUnicastCounterClientOutputIndex
		INTEGER,
	pm200fr20MondownRmonUnicastCounterClientOutputValuePortn
		Counter64,
	pm200fr20MondownRmonUnicastCounterClientOutputErrorPortn
		EkiOnOff,
	pm200fr20MondownRmonUnicastCounterClientOutputOverloadPortn
		EkiOnOff
	}


pm200fr20MondownRmonUnicastCounterClientOutputIndex OBJECT-TYPE
	SYNTAX  INTEGER(0..128)
	MAX-ACCESS  read-only
	STATUS current
	DESCRIPTION
        "
        Index definition for the pm200fr20MondownRmonUnicastCounterClientOutput 
        table
        "
	::= { pm200fr20MondownRmonUnicastCounterClientOutputEntry 1 }


pm200fr20MondownRmonUnicastCounterClientOutputValuePortn OBJECT-TYPE
	SYNTAX  Counter64
	MAX-ACCESS read-only
	STATUS current
	DESCRIPTION
        "
        Client Output Unicast Packets
         :This counter is increased each 
        time a Unicast packet is transmitted 
        on the client port  <Help>  This 
        counter gives the number of Unicast 
        packets transmitted on the client 
        port
        "
	::= { pm200fr20MondownRmonUnicastCounterClientOutputEntry 2 }


pm200fr20MondownRmonUnicastCounterClientOutputErrorPortn OBJECT-TYPE
	SYNTAX  EkiOnOff
	MAX-ACCESS read-only
	STATUS current
	DESCRIPTION
        "
        Unicast Counter Error :This OID 
        when set indicates the Unicast
         counter value is invalid on client 
        port
        "
	::= { pm200fr20MondownRmonUnicastCounterClientOutputEntry 3 }


pm200fr20MondownRmonUnicastCounterClientOutputOverloadPortn OBJECT-TYPE
	SYNTAX  EkiOnOff
	MAX-ACCESS read-only
	STATUS current
	DESCRIPTION
        "
        Unicast Counter Overload :This 
        OID when set indicates a Unicast 
        counter overload on client port
        "
	::= { pm200fr20MondownRmonUnicastCounterClientOutputEntry 4 }


--- *********************************************************
---     TABLE for the pm200fr20MondownRmonNonunicastCounterClientOutput articles
--- *********************************************************

pm200fr20MondownRmonNonunicastCounterClientOutputTable OBJECT-TYPE
	SYNTAX  SEQUENCE OF Pm200fr20MondownRmonNonunicastCounterClientOutputEntry
	MAX-ACCESS not-accessible
	STATUS current
	DESCRIPTION
        "
        List of pm200fr20MondownRmonNonunicastCounterClientOutput 
        Article
        "
	::= { pm200fr20MonClientRmonCounter 720 }


pm200fr20MondownRmonNonunicastCounterClientOutputEntry OBJECT-TYPE
	SYNTAX Pm200fr20MondownRmonNonunicastCounterClientOutputEntry
	MAX-ACCESS not-accessible
	STATUS current
	DESCRIPTION
        "
        Row definition for the pm200fr20MondownRmonNonunicastCounterClientOutput 
        table
        "
	INDEX   { pm200fr20MondownRmonNonunicastCounterClientOutputIndex }
	::= { pm200fr20MondownRmonNonunicastCounterClientOutputTable 1 }


Pm200fr20MondownRmonNonunicastCounterClientOutputEntry ::=
	SEQUENCE {
	pm200fr20MondownRmonNonunicastCounterClientOutputIndex
		INTEGER,
	pm200fr20MondownRmonNonunicastCounterClientOutputValuePortn
		Counter64,
	pm200fr20MondownRmonNonunicastCounterClientOutputErrorPortn
		EkiOnOff,
	pm200fr20MondownRmonNonunicastCounterClientOutputOverloadPortn
		EkiOnOff
	}


pm200fr20MondownRmonNonunicastCounterClientOutputIndex OBJECT-TYPE
	SYNTAX  INTEGER(0..128)
	MAX-ACCESS  read-only
	STATUS current
	DESCRIPTION
        "
        Index definition for the pm200fr20MondownRmonNonunicastCounterClientOutput 
        table
        "
	::= { pm200fr20MondownRmonNonunicastCounterClientOutputEntry 1 }


pm200fr20MondownRmonNonunicastCounterClientOutputValuePortn OBJECT-TYPE
	SYNTAX  Counter64
	MAX-ACCESS read-only
	STATUS current
	DESCRIPTION
        "
        Client Output Non Unicast Packets 
        :This counter is increased each 
        time a Non-Unicast packet is transmitted 
        on the client port  <Help>  This 
        counter gives the number of Non-Unicast 
        packets transmitted on the client 
        port
        "
	::= { pm200fr20MondownRmonNonunicastCounterClientOutputEntry 2 }


pm200fr20MondownRmonNonunicastCounterClientOutputErrorPortn OBJECT-TYPE
	SYNTAX  EkiOnOff
	MAX-ACCESS read-only
	STATUS current
	DESCRIPTION
        "
        Non Unicast Counter Error :This 
        OID when set indicates the Non-Unicast 
        counter value is invalid on client 
        port
        "
	::= { pm200fr20MondownRmonNonunicastCounterClientOutputEntry 3 }


pm200fr20MondownRmonNonunicastCounterClientOutputOverloadPortn OBJECT-TYPE
	SYNTAX  EkiOnOff
	MAX-ACCESS read-only
	STATUS current
	DESCRIPTION
        "
        Non Unicast Counter Overload :This 
        OID when set indicates a Non-Unicast 
        counter overload on client port
        "
	::= { pm200fr20MondownRmonNonunicastCounterClientOutputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm200fr20Mesrsynth0 OBJECT-TYPE
	  SYNTAX EkiMeasureType
	  MAX-ACCESS read-only
	  STATUS deprecated
	  DESCRIPTION
        "
        Not Used :
        "
	  ::= { pm200fr20MesrOther 0 }



pm200fr20Mesrsynth1 OBJECT-TYPE
	  SYNTAX EkiMeasureType
	  MAX-ACCESS read-only
	  STATUS deprecated
	  DESCRIPTION
        "
        Not Used :
        "
	  ::= { pm200fr20MesrOther 1 }



--- *****************************************************
---     LEAF for the pmIntervalNumber article
--- *****************************************************

pm200fr20MesrpmIntervalNumber OBJECT-TYPE
	  SYNTAX Unsigned32 (0..65535)
	  MAX-ACCESS read-only
	  STATUS current
	  DESCRIPTION
        "
        PM Interval Counter :
        "
	  ::= { pm200fr20MesrOther 7 }



--- *****************************************************
---     LEAF for the lineMsaTemp article
--- *****************************************************

pm200fr20MesrlineMsaTemp OBJECT-TYPE
	  SYNTAX Unsigned32 (0..65535)
	  MAX-ACCESS read-only
	  STATUS current
	  DESCRIPTION
        "
        Line Trscv Temperature :This OID 
        gives the temperature value of
         the Line Transceiver, read from 
        the DDM (Digital Diagnostic Monitoring) 
         (Temperature = AV_S16/256) (Unit 
        = C) <Help> This Measure gives
         the temperature value of the Line 
        Transceiver.This temperature must 
        remain below 95 C for proper operation
        "
	  ::= { pm200fr20MesrLine 12 }



--- *********************************************************
---     TABLE for the pm200fr20MesrclientTxTemp articles
--- *********************************************************

pm200fr20MesrclientTxTempTable OBJECT-TYPE
	SYNTAX  SEQUENCE OF Pm200fr20MesrclientTxTempEntry
	MAX-ACCESS not-accessible
	STATUS current
	DESCRIPTION
        "
        List of pm200fr20MesrclientTxTemp 
        Article
        "
	::= { pm200fr20MesrClient 16 }


pm200fr20MesrclientTxTempEntry OBJECT-TYPE
	SYNTAX Pm200fr20MesrclientTxTempEntry
	MAX-ACCESS not-accessible
	STATUS current
	DESCRIPTION
        "
        Row definition for the pm200fr20MesrclientTxTemp 
        table
        "
	INDEX   { pm200fr20MesrclientTxTempIndex }
	::= { pm200fr20MesrclientTxTempTable 1 }


Pm200fr20MesrclientTxTempEntry ::=
	SEQUENCE {
	pm200fr20MesrclientTxTempIndex
		INTEGER,
	pm200fr20MesrclientTxTempPortn
		INTEGER 
	}


pm200fr20MesrclientTxTempIndex OBJECT-TYPE
	SYNTAX  INTEGER(0..128)
	MAX-ACCESS  read-only
	STATUS current
	DESCRIPTION
        "
        Index definition for the pm200fr20MesrclientTxTemp 
        table
        "
	::= { pm200fr20MesrclientTxTempEntry 1 }


pm200fr20MesrclientTxTempPortn OBJECT-TYPE
	SYNTAX  INTEGER (0..65535)
	MAX-ACCESS read-only
	STATUS current
	DESCRIPTION
        "
        Client Trscv Temperature :This 
        OID gives the Laser temperature 
        value of the Client Transceiver, 
        read from the DDM (Digital Diagnostic 
        Monitoring) (Temperature = AV_S16/256) 
        (Unit = C) <Help> This Measure
         gives the Laser temperature value 
        of the Client Transceiver
        "
	::= { pm200fr20MesrclientTxTempEntry 2 }


--- *********************************************************
---     TABLE for the pm200fr20MesrclientTxBias articles
--- *********************************************************

pm200fr20MesrclientTxBiasTable OBJECT-TYPE
	SYNTAX  SEQUENCE OF Pm200fr20MesrclientTxBiasEntry
	MAX-ACCESS not-accessible
	STATUS current
	DESCRIPTION
        "
        List of pm200fr20MesrclientTxBias 
        Article
        "
	::= { pm200fr20MesrClient 48 }


pm200fr20MesrclientTxBiasEntry OBJECT-TYPE
	SYNTAX Pm200fr20MesrclientTxBiasEntry
	MAX-ACCESS not-accessible
	STATUS current
	DESCRIPTION
        "
        Row definition for the pm200fr20MesrclientTxBias 
        table
        "
	INDEX   { pm200fr20MesrclientTxBiasIndex }
	::= { pm200fr20MesrclientTxBiasTable 1 }


Pm200fr20MesrclientTxBiasEntry ::=
	SEQUENCE {
	pm200fr20MesrclientTxBiasIndex
		INTEGER,
	pm200fr20MesrclientTxBiasPortn
		INTEGER 
	}


pm200fr20MesrclientTxBiasIndex OBJECT-TYPE
	SYNTAX  INTEGER(0..128)
	MAX-ACCESS  read-only
	STATUS current
	DESCRIPTION
        "
        Index definition for the pm200fr20MesrclientTxBias 
        table
        "
	::= { pm200fr20MesrclientTxBiasEntry 1 }


pm200fr20MesrclientTxBiasPortn OBJECT-TYPE
	SYNTAX  INTEGER (0..65535)
	MAX-ACCESS read-only
	STATUS current
	DESCRIPTION
        "
        Client Trscv Laser Bias :This
         OID gives the Laser bias value 
        of the Client Transceiver, read 
        from the DDM (Digital Diagnostic 
        Monitoring) (Bias = AV_U16/500) 
        (Unit = mA) <Help> This Measure 
        gives the Laser bias value of the 
        Client Transceiver
        "
	::= { pm200fr20MesrclientTxBiasEntry 2 }


--- *********************************************************
---     TABLE for the pm200fr20MesrclientTxPwr articles
--- *********************************************************

pm200fr20MesrclientTxPwrTable OBJECT-TYPE
	SYNTAX  SEQUENCE OF Pm200fr20MesrclientTxPwrEntry
	MAX-ACCESS not-accessible
	STATUS current
	DESCRIPTION
        "
        List of pm200fr20MesrclientTxPwr 
        Article
        "
	::= { pm200fr20MesrClient 80 }


pm200fr20MesrclientTxPwrEntry OBJECT-TYPE
	SYNTAX Pm200fr20MesrclientTxPwrEntry
	MAX-ACCESS not-accessible
	STATUS current
	DESCRIPTION
        "
        Row definition for the pm200fr20MesrclientTxPwr 
        table
        "
	INDEX   { pm200fr20MesrclientTxPwrIndex }
	::= { pm200fr20MesrclientTxPwrTable 1 }


Pm200fr20MesrclientTxPwrEntry ::=
	SEQUENCE {
	pm200fr20MesrclientTxPwrIndex
		INTEGER,
	pm200fr20MesrclientTxPwrPortn
		INTEGER 
	}


pm200fr20MesrclientTxPwrIndex OBJECT-TYPE
	SYNTAX  INTEGER(0..128)
	MAX-ACCESS  read-only
	STATUS current
	DESCRIPTION
        "
        Index definition for the pm200fr20MesrclientTxPwr 
        table
        "
	::= { pm200fr20MesrclientTxPwrEntry 1 }


pm200fr20MesrclientTxPwrPortn OBJECT-TYPE
	SYNTAX  INTEGER (0..65535)
	MAX-ACCESS read-only
	STATUS current
	DESCRIPTION
        "
        Client Trscv Tx Power :This OID 
        gives the transmit power value
         of the Client Transceiver, read 
        from the DDM (Digital Diagnostic 
        Monitoring) (Power = 10*log(AV_U16)-40) 
        (Unit = dBm) <Help> This Measure 
        gives the transmit power value
         of the Client Transceiver
        "
	::= { pm200fr20MesrclientTxPwrEntry 2 }


--- *********************************************************
---     TABLE for the pm200fr20MesrclientRxPwr articles
--- *********************************************************

pm200fr20MesrclientRxPwrTable OBJECT-TYPE
	SYNTAX  SEQUENCE OF Pm200fr20MesrclientRxPwrEntry
	MAX-ACCESS not-accessible
	STATUS current
	DESCRIPTION
        "
        List of pm200fr20MesrclientRxPwr 
        Article
        "
	::= { pm200fr20MesrClient 112 }


pm200fr20MesrclientRxPwrEntry OBJECT-TYPE
	SYNTAX Pm200fr20MesrclientRxPwrEntry
	MAX-ACCESS not-accessible
	STATUS current
	DESCRIPTION
        "
        Row definition for the pm200fr20MesrclientRxPwr 
        table
        "
	INDEX   { pm200fr20MesrclientRxPwrIndex }
	::= { pm200fr20MesrclientRxPwrTable 1 }


Pm200fr20MesrclientRxPwrEntry ::=
	SEQUENCE {
	pm200fr20MesrclientRxPwrIndex
		INTEGER,
	pm200fr20MesrclientRxPwrPortn
		INTEGER 
	}


pm200fr20MesrclientRxPwrIndex OBJECT-TYPE
	SYNTAX  INTEGER(0..128)
	MAX-ACCESS  read-only
	STATUS current
	DESCRIPTION
        "
        Index definition for the pm200fr20MesrclientRxPwr 
        table
        "
	::= { pm200fr20MesrclientRxPwrEntry 1 }


pm200fr20MesrclientRxPwrPortn OBJECT-TYPE
	SYNTAX  INTEGER (0..65535)
	MAX-ACCESS read-only
	STATUS current
	DESCRIPTION
        "
        Client Trscv Rx Power :This OID 
        gives the receive power value of 
        the Client Transceiver, read in 
        the DDM (Digital Diagnostic Monitoring) 
        (Power = 10*log(AV_U16)-40) (Unit 
        = dBm) <Help> This Measure gives 
        the receive power value of the
         Client Transceiver
        "
	::= { pm200fr20MesrclientRxPwrEntry 2 }


--- *********************************************************
---     TABLE for the pm200fr20MesrlineNetTxLaserOutputPwr articles
--- *********************************************************

pm200fr20MesrlineNetTxLaserOutputPwrTable OBJECT-TYPE
	SYNTAX  SEQUENCE OF Pm200fr20MesrlineNetTxLaserOutputPwrEntry
	MAX-ACCESS not-accessible
	STATUS current
	DESCRIPTION
        "
        List of pm200fr20MesrlineNetTxLaserOutputPwr 
        Article
        "
	::= { pm200fr20MesrLine 144 }


pm200fr20MesrlineNetTxLaserOutputPwrEntry OBJECT-TYPE
	SYNTAX Pm200fr20MesrlineNetTxLaserOutputPwrEntry
	MAX-ACCESS not-accessible
	STATUS current
	DESCRIPTION
        "
        Row definition for the pm200fr20MesrlineNetTxLaserOutputPwr 
        table
        "
	INDEX   { pm200fr20MesrlineNetTxLaserOutputPwrIndex }
	::= { pm200fr20MesrlineNetTxLaserOutputPwrTable 1 }


Pm200fr20MesrlineNetTxLaserOutputPwrEntry ::=
	SEQUENCE {
	pm200fr20MesrlineNetTxLaserOutputPwrIndex
		INTEGER,
	pm200fr20MesrlineNetTxLaserOutputPwrPortn
		INTEGER 
	}


pm200fr20MesrlineNetTxLaserOutputPwrIndex OBJECT-TYPE
	SYNTAX  INTEGER(0..128)
	MAX-ACCESS  read-only
	STATUS current
	DESCRIPTION
        "
        Index definition for the pm200fr20MesrlineNetTxLaserOutputPwr 
        table
        "
	::= { pm200fr20MesrlineNetTxLaserOutputPwrEntry 1 }


pm200fr20MesrlineNetTxLaserOutputPwrPortn OBJECT-TYPE
	SYNTAX  INTEGER (0..65535)
	MAX-ACCESS read-only
	STATUS current
	DESCRIPTION
        "
        Current Line Trscv Tx Power :This 
        OID gives the Tx Laser transmit 
        power value of the Line Transceiver, 
        read in the DDM (Digital Diagnostic 
        Monitoring) (Power = AV/100) (Unit 
        = dBm) <Help> This Measure gives 
        the Tx Laser transmit power value 
        of the Line Transceiver
        "
	::= { pm200fr20MesrlineNetTxLaserOutputPwrEntry 2 }


--- *********************************************************
---     TABLE for the pm200fr20MesrlineNetTxLaserTemp articles
--- *********************************************************

pm200fr20MesrlineNetTxLaserTempTable OBJECT-TYPE
	SYNTAX  SEQUENCE OF Pm200fr20MesrlineNetTxLaserTempEntry
	MAX-ACCESS not-accessible
	STATUS current
	DESCRIPTION
        "
        List of pm200fr20MesrlineNetTxLaserTemp 
        Article
        "
	::= { pm200fr20MesrLine 148 }


pm200fr20MesrlineNetTxLaserTempEntry OBJECT-TYPE
	SYNTAX Pm200fr20MesrlineNetTxLaserTempEntry
	MAX-ACCESS not-accessible
	STATUS current
	DESCRIPTION
        "
        Row definition for the pm200fr20MesrlineNetTxLaserTemp 
        table
        "
	INDEX   { pm200fr20MesrlineNetTxLaserTempIndex }
	::= { pm200fr20MesrlineNetTxLaserTempTable 1 }


Pm200fr20MesrlineNetTxLaserTempEntry ::=
	SEQUENCE {
	pm200fr20MesrlineNetTxLaserTempIndex
		INTEGER,
	pm200fr20MesrlineNetTxLaserTempPortn
		INTEGER 
	}


pm200fr20MesrlineNetTxLaserTempIndex OBJECT-TYPE
	SYNTAX  INTEGER(0..128)
	MAX-ACCESS  read-only
	STATUS current
	DESCRIPTION
        "
        Index definition for the pm200fr20MesrlineNetTxLaserTemp 
        table
        "
	::= { pm200fr20MesrlineNetTxLaserTempEntry 1 }


pm200fr20MesrlineNetTxLaserTempPortn OBJECT-TYPE
	SYNTAX  INTEGER (0..65535)
	MAX-ACCESS read-only
	STATUS current
	DESCRIPTION
        "
        Current Line Trscv Tx Laser Temperature 
        :This OID gives the Tx Laser Temperature 
        value of the Line Transceiver,
         read from the DDM (Digital Diagnostic 
        Monitoring) (Temperature = AV/256) 
        (Unit = C) <Help> This Measure
         gives the Tx Laser Temperature 
        value of the Line Transceiver
        "
	::= { pm200fr20MesrlineNetTxLaserTempEntry 2 }


--- *********************************************************
---     TABLE for the pm200fr20MesrlineNetTxBiasCurrent articles
--- *********************************************************

pm200fr20MesrlineNetTxBiasCurrentTable OBJECT-TYPE
	SYNTAX  SEQUENCE OF Pm200fr20MesrlineNetTxBiasCurrentEntry
	MAX-ACCESS not-accessible
	STATUS current
	DESCRIPTION
        "
        List of pm200fr20MesrlineNetTxBiasCurrent 
        Article
        "
	::= { pm200fr20MesrLine 152 }


pm200fr20MesrlineNetTxBiasCurrentEntry OBJECT-TYPE
	SYNTAX Pm200fr20MesrlineNetTxBiasCurrentEntry
	MAX-ACCESS not-accessible
	STATUS current
	DESCRIPTION
        "
        Row definition for the pm200fr20MesrlineNetTxBiasCurrent 
        table
        "
	INDEX   { pm200fr20MesrlineNetTxBiasCurrentIndex }
	::= { pm200fr20MesrlineNetTxBiasCurrentTable 1 }


Pm200fr20MesrlineNetTxBiasCurrentEntry ::=
	SEQUENCE {
	pm200fr20MesrlineNetTxBiasCurrentIndex
		INTEGER,
	pm200fr20MesrlineNetTxBiasCurrentPortn
		INTEGER 
	}


pm200fr20MesrlineNetTxBiasCurrentIndex OBJECT-TYPE
	SYNTAX  INTEGER(0..128)
	MAX-ACCESS  read-only
	STATUS current
	DESCRIPTION
        "
        Index definition for the pm200fr20MesrlineNetTxBiasCurrent 
        table
        "
	::= { pm200fr20MesrlineNetTxBiasCurrentEntry 1 }


pm200fr20MesrlineNetTxBiasCurrentPortn OBJECT-TYPE
	SYNTAX  INTEGER (0..65535)
	MAX-ACCESS read-only
	STATUS current
	DESCRIPTION
        "
        Current Line Trscv Tx Laser Bias 
        :This OID gives the Tx Laser Bias 
        value of the Line Transceiver,
         read from the DDM (Digital Diagnostic 
        Monitoring) (Bias = AV/10) (Unit 
        = mA) <Help> This Measure gives 
        the Tx Laser Bias value of the
         Line Transceiver
        "
	::= { pm200fr20MesrlineNetTxBiasCurrentEntry 2 }


--- *********************************************************
---     TABLE for the pm200fr20MesrlineNetRxInputPwr articles
--- *********************************************************

pm200fr20MesrlineNetRxInputPwrTable OBJECT-TYPE
	SYNTAX  SEQUENCE OF Pm200fr20MesrlineNetRxInputPwrEntry
	MAX-ACCESS not-accessible
	STATUS current
	DESCRIPTION
        "
        List of pm200fr20MesrlineNetRxInputPwr 
        Article
        "
	::= { pm200fr20MesrLine 156 }


pm200fr20MesrlineNetRxInputPwrEntry OBJECT-TYPE
	SYNTAX Pm200fr20MesrlineNetRxInputPwrEntry
	MAX-ACCESS not-accessible
	STATUS current
	DESCRIPTION
        "
        Row definition for the pm200fr20MesrlineNetRxInputPwr 
        table
        "
	INDEX   { pm200fr20MesrlineNetRxInputPwrIndex }
	::= { pm200fr20MesrlineNetRxInputPwrTable 1 }


Pm200fr20MesrlineNetRxInputPwrEntry ::=
	SEQUENCE {
	pm200fr20MesrlineNetRxInputPwrIndex
		INTEGER,
	pm200fr20MesrlineNetRxInputPwrPortn
		INTEGER 
	}


pm200fr20MesrlineNetRxInputPwrIndex OBJECT-TYPE
	SYNTAX  INTEGER(0..128)
	MAX-ACCESS  read-only
	STATUS current
	DESCRIPTION
        "
        Index definition for the pm200fr20MesrlineNetRxInputPwr 
        table
        "
	::= { pm200fr20MesrlineNetRxInputPwrEntry 1 }


pm200fr20MesrlineNetRxInputPwrPortn OBJECT-TYPE
	SYNTAX  INTEGER (0..65535)
	MAX-ACCESS read-only
	STATUS current
	DESCRIPTION
        "
        Current Line Trscv Rx Power :This 
        OID gives the Receive power value 
        of the Line Transceiver, read in 
        the DDM (Digital Diagnostic Monitoring) 
        (Power = AV/100) (Unit = dBm) <Help> 
        This Measure gives the Receive
         power value of the Line Transceiver
        "
	::= { pm200fr20MesrlineNetRxInputPwrEntry 2 }


--- *********************************************************
---     TABLE for the pm200fr20MesrlineResidualChromaticDisp articles
--- *********************************************************

pm200fr20MesrlineResidualChromaticDispTable OBJECT-TYPE
	SYNTAX  SEQUENCE OF Pm200fr20MesrlineResidualChromaticDispEntry
	MAX-ACCESS not-accessible
	STATUS current
	DESCRIPTION
        "
        List of pm200fr20MesrlineResidualChromaticDisp 
        Article
        "
	::= { pm200fr20MesrLine 160 }


pm200fr20MesrlineResidualChromaticDispEntry OBJECT-TYPE
	SYNTAX Pm200fr20MesrlineResidualChromaticDispEntry
	MAX-ACCESS not-accessible
	STATUS current
	DESCRIPTION
        "
        Row definition for the pm200fr20MesrlineResidualChromaticDisp 
        table
        "
	INDEX   { pm200fr20MesrlineResidualChromaticDispIndex }
	::= { pm200fr20MesrlineResidualChromaticDispTable 1 }


Pm200fr20MesrlineResidualChromaticDispEntry ::=
	SEQUENCE {
	pm200fr20MesrlineResidualChromaticDispIndex
		INTEGER,
	pm200fr20MesrlineResidualChromaticDispPortn
		INTEGER 
	}


pm200fr20MesrlineResidualChromaticDispIndex OBJECT-TYPE
	SYNTAX  INTEGER(0..128)
	MAX-ACCESS  read-only
	STATUS current
	DESCRIPTION
        "
        Index definition for the pm200fr20MesrlineResidualChromaticDisp 
        table
        "
	::= { pm200fr20MesrlineResidualChromaticDispEntry 1 }


pm200fr20MesrlineResidualChromaticDispPortn OBJECT-TYPE
	SYNTAX  INTEGER (0..65535)
	MAX-ACCESS read-only
	STATUS current
	DESCRIPTION
        "
        Current Residual Chromatic Dispersion 
        :This OID gives the current Residual 
        Chromatic Dispersion on the Line 
        interface  (Unit = ps/nm)<Help> 
        This measure gives the current
         Residual Chromatic Dispersion
         on the Line interface.
        "
	::= { pm200fr20MesrlineResidualChromaticDispEntry 2 }


--- *********************************************************
---     TABLE for the pm200fr20MesrlineDiffGroupDelay articles
--- *********************************************************

pm200fr20MesrlineDiffGroupDelayTable OBJECT-TYPE
	SYNTAX  SEQUENCE OF Pm200fr20MesrlineDiffGroupDelayEntry
	MAX-ACCESS not-accessible
	STATUS current
	DESCRIPTION
        "
        List of pm200fr20MesrlineDiffGroupDelay 
        Article
        "
	::= { pm200fr20MesrLine 164 }


pm200fr20MesrlineDiffGroupDelayEntry OBJECT-TYPE
	SYNTAX Pm200fr20MesrlineDiffGroupDelayEntry
	MAX-ACCESS not-accessible
	STATUS current
	DESCRIPTION
        "
        Row definition for the pm200fr20MesrlineDiffGroupDelay 
        table
        "
	INDEX   { pm200fr20MesrlineDiffGroupDelayIndex }
	::= { pm200fr20MesrlineDiffGroupDelayTable 1 }


Pm200fr20MesrlineDiffGroupDelayEntry ::=
	SEQUENCE {
	pm200fr20MesrlineDiffGroupDelayIndex
		INTEGER,
	pm200fr20MesrlineDiffGroupDelayPortn
		INTEGER 
	}


pm200fr20MesrlineDiffGroupDelayIndex OBJECT-TYPE
	SYNTAX  INTEGER(0..128)
	MAX-ACCESS  read-only
	STATUS current
	DESCRIPTION
        "
        Index definition for the pm200fr20MesrlineDiffGroupDelay 
        table
        "
	::= { pm200fr20MesrlineDiffGroupDelayEntry 1 }


pm200fr20MesrlineDiffGroupDelayPortn OBJECT-TYPE
	SYNTAX  INTEGER (0..65535)
	MAX-ACCESS read-only
	STATUS current
	DESCRIPTION
        "
        Current Differential Group Delay 
        :This OID gives the current Differential 
        Group Delay on the Line interface 
          (Unit = ps)<Help> This measure 
        gives the current Differential
         Group Delay on the Line interface.
        "
	::= { pm200fr20MesrlineDiffGroupDelayEntry 2 }


--- *********************************************************
---     TABLE for the pm200fr20MesrlineQFactor articles
--- *********************************************************

pm200fr20MesrlineQFactorTable OBJECT-TYPE
	SYNTAX  SEQUENCE OF Pm200fr20MesrlineQFactorEntry
	MAX-ACCESS not-accessible
	STATUS current
	DESCRIPTION
        "
        List of pm200fr20MesrlineQFactor 
        Article
        "
	::= { pm200fr20MesrLine 168 }


pm200fr20MesrlineQFactorEntry OBJECT-TYPE
	SYNTAX Pm200fr20MesrlineQFactorEntry
	MAX-ACCESS not-accessible
	STATUS current
	DESCRIPTION
        "
        Row definition for the pm200fr20MesrlineQFactor 
        table
        "
	INDEX   { pm200fr20MesrlineQFactorIndex }
	::= { pm200fr20MesrlineQFactorTable 1 }


Pm200fr20MesrlineQFactorEntry ::=
	SEQUENCE {
	pm200fr20MesrlineQFactorIndex
		INTEGER,
	pm200fr20MesrlineQFactorPortn
		INTEGER 
	}


pm200fr20MesrlineQFactorIndex OBJECT-TYPE
	SYNTAX  INTEGER(0..128)
	MAX-ACCESS  read-only
	STATUS current
	DESCRIPTION
        "
        Index definition for the pm200fr20MesrlineQFactor 
        table
        "
	::= { pm200fr20MesrlineQFactorEntry 1 }


pm200fr20MesrlineQFactorPortn OBJECT-TYPE
	SYNTAX  INTEGER (0..65535)
	MAX-ACCESS read-only
	STATUS current
	DESCRIPTION
        "
        Current Q Factor :This OID gives 
        the current Q Factor on the Line 
        interface   (Unit = dB) <Help>
         This measure gives the current 
        Q Factor on the Line interface.
        "
	::= { pm200fr20MesrlineQFactorEntry 2 }


--- *********************************************************
---     TABLE for the pm200fr20MesrlineCarrierFreqOffset articles
--- *********************************************************

pm200fr20MesrlineCarrierFreqOffsetTable OBJECT-TYPE
	SYNTAX  SEQUENCE OF Pm200fr20MesrlineCarrierFreqOffsetEntry
	MAX-ACCESS not-accessible
	STATUS current
	DESCRIPTION
        "
        List of pm200fr20MesrlineCarrierFreqOffset 
        Article
        "
	::= { pm200fr20MesrLine 172 }


pm200fr20MesrlineCarrierFreqOffsetEntry OBJECT-TYPE
	SYNTAX Pm200fr20MesrlineCarrierFreqOffsetEntry
	MAX-ACCESS not-accessible
	STATUS current
	DESCRIPTION
        "
        Row definition for the pm200fr20MesrlineCarrierFreqOffset 
        table
        "
	INDEX   { pm200fr20MesrlineCarrierFreqOffsetIndex }
	::= { pm200fr20MesrlineCarrierFreqOffsetTable 1 }


Pm200fr20MesrlineCarrierFreqOffsetEntry ::=
	SEQUENCE {
	pm200fr20MesrlineCarrierFreqOffsetIndex
		INTEGER,
	pm200fr20MesrlineCarrierFreqOffsetPortn
		INTEGER 
	}


pm200fr20MesrlineCarrierFreqOffsetIndex OBJECT-TYPE
	SYNTAX  INTEGER(0..128)
	MAX-ACCESS  read-only
	STATUS current
	DESCRIPTION
        "
        Index definition for the pm200fr20MesrlineCarrierFreqOffset 
        table
        "
	::= { pm200fr20MesrlineCarrierFreqOffsetEntry 1 }


pm200fr20MesrlineCarrierFreqOffsetPortn OBJECT-TYPE
	SYNTAX  INTEGER (0..65535)
	MAX-ACCESS read-only
	STATUS current
	DESCRIPTION
        "
        Current Carrier Frequency Offset 
        :This OID gives the current Carrier 
        Frequency Offset on the Line interface 
          (Unit = Mhz)<Help> This measure 
        gives the current Carrier Frequency 
        Offset on the Line interface.
        "
	::= { pm200fr20MesrlineCarrierFreqOffsetEntry 2 }


--- *********************************************************
---     TABLE for the pm200fr20MesrlineOsnr articles
--- *********************************************************

pm200fr20MesrlineOsnrTable OBJECT-TYPE
	SYNTAX  SEQUENCE OF Pm200fr20MesrlineOsnrEntry
	MAX-ACCESS not-accessible
	STATUS current
	DESCRIPTION
        "
        List of pm200fr20MesrlineOsnr
         Article
        "
	::= { pm200fr20MesrLine 176 }


pm200fr20MesrlineOsnrEntry OBJECT-TYPE
	SYNTAX Pm200fr20MesrlineOsnrEntry
	MAX-ACCESS not-accessible
	STATUS current
	DESCRIPTION
        "
        Row definition for the pm200fr20MesrlineOsnr 
        table
        "
	INDEX   { pm200fr20MesrlineOsnrIndex }
	::= { pm200fr20MesrlineOsnrTable 1 }


Pm200fr20MesrlineOsnrEntry ::=
	SEQUENCE {
	pm200fr20MesrlineOsnrIndex
		INTEGER,
	pm200fr20MesrlineOsnrPortn
		INTEGER 
	}


pm200fr20MesrlineOsnrIndex OBJECT-TYPE
	SYNTAX  INTEGER(0..128)
	MAX-ACCESS  read-only
	STATUS current
	DESCRIPTION
        "
        Index definition for the pm200fr20MesrlineOsnr 
        table
        "
	::= { pm200fr20MesrlineOsnrEntry 1 }


pm200fr20MesrlineOsnrPortn OBJECT-TYPE
	SYNTAX  INTEGER (0..65535)
	MAX-ACCESS read-only
	STATUS current
	DESCRIPTION
        "
        Current OSNR :This OID gives the 
        current OSNR on the Line interface 
          (OSNR = AV/10) (Unit = dB)<Help> 
        This measure gives the current
         OSNR on the Line interface.
        "
	::= { pm200fr20MesrlineOsnrEntry 2 }


--- *****************************************************
---     LEAF for the lineNetTxLaserOutputPwrAverage article
--- *****************************************************

pm200fr20MesrlineNetTxLaserOutputPwrAverage OBJECT-TYPE
	  SYNTAX Unsigned32 (0..65535)
	  MAX-ACCESS read-only
	  STATUS current
	  DESCRIPTION
        "
        Average Line Trscv Tx Power :This 
        OID gives the average Tx Laser
         transmit power value among the 
        network lanes of the Line Transceiver, 
        read in the DDM (Digital Diagnostic 
        Monitoring)  (Power = AV/100) (Unit 
        = dBm) (Unit = dBm) <Help> This 
        Measure gives the average Tx Laser 
        transmit power value among the
         network lanes of the Line Transceiver
        "
	  ::= { pm200fr20MesrOther 196 }



--- *****************************************************
---     LEAF for the lineNetTxLaserTempAverage article
--- *****************************************************

pm200fr20MesrlineNetTxLaserTempAverage OBJECT-TYPE
	  SYNTAX Unsigned32 (0..65535)
	  MAX-ACCESS read-only
	  STATUS current
	  DESCRIPTION
        "
        Average Line Trscv Tx Laser Temperature 
        :This OID gives the average Tx
         Laser Temperature value among
         the network lanes of the Line
         Transceiver, read from the DDM 
        (Digital Diagnostic Monitoring) 
        (Temperature = AV/256) (Unit =
         C) <Help> This Measure gives the 
        average Tx Laser Temperature value 
        among the network lanes of the
         Line Transceiver
        "
	  ::= { pm200fr20MesrOther 197 }



--- *****************************************************
---     LEAF for the lineNetTxBiasCurrentAverage article
--- *****************************************************

pm200fr20MesrlineNetTxBiasCurrentAverage OBJECT-TYPE
	  SYNTAX Unsigned32 (0..65535)
	  MAX-ACCESS read-only
	  STATUS current
	  DESCRIPTION
        "
        Average Line Trscv Tx Laser Bias 
        :This OID gives the average Tx
         Laser Bias value among the network 
        lanes of the Line Transceiver,
         read from the DDM (Digital Diagnostic 
        Monitoring) (Bias = AV/10) (Unit 
        = mA) <Help> This Measure gives 
        the average Tx Laser Bias value 
        among the network lanes of the
         Line Transceiver
        "
	  ::= { pm200fr20MesrOther 198 }



--- *****************************************************
---     LEAF for the lineNetRxInputPwrAverage article
--- *****************************************************

pm200fr20MesrlineNetRxInputPwrAverage OBJECT-TYPE
	  SYNTAX Unsigned32 (0..65535)
	  MAX-ACCESS read-only
	  STATUS current
	  DESCRIPTION
        "
        Average Line Trscv Rx Power :This 
        OID gives the average Receive power 
        value among the network lanes of 
        the Line Transceiver, read in the 
        DDM (Digital Diagnostic Monitoring) 
        (Power = AV/100) (Unit = dBm) <Help> 
        This Measure gives the average
         Receive power value among the
         network lanes of the Line Transceiver
        "
	  ::= { pm200fr20MesrOther 199 }



--- *****************************************************
---     LEAF for the lineResidualChromaticDispAverage article
--- *****************************************************

pm200fr20MesrlineResidualChromaticDispAverage OBJECT-TYPE
	  SYNTAX Unsigned32 (0..65535)
	  MAX-ACCESS read-only
	  STATUS current
	  DESCRIPTION
        "
        Average Residual Chromatic Dispersion 
        :This OID gives the average Residual 
        Chromatic Dispersion on the Line 
        interface since the last measure 
        reset <Help> This measure gives 
        the average Residual Chromatic
         Dispersion on the Line interface 
        since the last measure reset.
        "
	  ::= { pm200fr20MesrOther 200 }



--- *****************************************************
---     LEAF for the lineDiffGroupDelayAverage article
--- *****************************************************

pm200fr20MesrlineDiffGroupDelayAverage OBJECT-TYPE
	  SYNTAX Unsigned32 (0..65535)
	  MAX-ACCESS read-only
	  STATUS current
	  DESCRIPTION
        "
        Average Differential Group Delay 
        :This OID gives the average Group 
        Delay on the Line interface since 
        the last measure reset <Help> This 
        measure gives the average Differential 
        Group Delay on the Line interface 
        since the last measure reset.
        "
	  ::= { pm200fr20MesrOther 201 }



--- *****************************************************
---     LEAF for the lineQFactorAverage article
--- *****************************************************

pm200fr20MesrlineQFactorAverage OBJECT-TYPE
	  SYNTAX Unsigned32 (0..65535)
	  MAX-ACCESS read-only
	  STATUS current
	  DESCRIPTION
        "
        Average Q Factor :This OID gives 
        the average Q Factor on the Line 
        interface since the last measure 
        reset <Help> This measure gives 
        the average Q Factor on the Line 
        interface since the last measure 
        reset.
        "
	  ::= { pm200fr20MesrOther 202 }



--- *****************************************************
---     LEAF for the lineCarrierFreqOffsetAverage article
--- *****************************************************

pm200fr20MesrlineCarrierFreqOffsetAverage OBJECT-TYPE
	  SYNTAX Unsigned32 (0..65535)
	  MAX-ACCESS read-only
	  STATUS current
	  DESCRIPTION
        "
        Average Carrier Frequency Offset 
        :This OID gives the average Carrier 
        Frequency Offset on the Line interface 
        since the last measure reset <Help> 
        This measure gives the average
         Carrier Frequency Offset on the 
        Line interface since the last measure 
        reset
        "
	  ::= { pm200fr20MesrOther 203 }



--- *****************************************************
---     LEAF for the lineOsnrAverage article
--- *****************************************************

pm200fr20MesrlineOsnrAverage OBJECT-TYPE
	  SYNTAX Unsigned32 (0..65535)
	  MAX-ACCESS read-only
	  STATUS current
	  DESCRIPTION
        "
        Average OSNR :This OID gives the 
        average OSNR on the Line interface 
        since the last measure reset <Help> 
        This measure gives the average
         OSNR on the Line interface since 
        the last measure reset.
        "
	  ::= { pm200fr20MesrOther 204 }



--- *****************************************************
---     LEAF for the clientNetTxTempMin article
--- *****************************************************

pm200fr20MesrclientNetTxTempMin OBJECT-TYPE
	  SYNTAX Unsigned32 (0..65535)
	  MAX-ACCESS read-only
	  STATUS current
	  DESCRIPTION
        "
        Min Client Trscv Laser Temperature 
        :This OID gives the minimum Laser 
        temperature value among the network 
        lanes of the Client Transceiver, 
        read from the DDM (Digital Diagnostic 
        Monitoring) (Temperature = AV/256) 
        (Unit = C) <Help> This Measure
         gives the minimum Laser temperature 
        value among the network lanes of 
        the Client Transceiver
        "
	  ::= { pm200fr20MesrOther 208 }



--- *****************************************************
---     LEAF for the clientNetTxBiasMin article
--- *****************************************************

pm200fr20MesrclientNetTxBiasMin OBJECT-TYPE
	  SYNTAX Unsigned32 (0..65535)
	  MAX-ACCESS read-only
	  STATUS current
	  DESCRIPTION
        "
        Min Client Trscv Laser Bias :This 
        OID gives the minimum Laser bias 
        value among the network lanes of 
        the Client Transceiver, read from 
        the DDM (Digital Diagnostic Monitoring) 
        (Bias = AV/500) (Unit = mA) <Help> 
        This Measure gives the minimum
         Laser bias value among the network 
        lanes of the Client Transceiver
        "
	  ::= { pm200fr20MesrOther 209 }



--- *****************************************************
---     LEAF for the clientNetTxPwrMin article
--- *****************************************************

pm200fr20MesrclientNetTxPwrMin OBJECT-TYPE
	  SYNTAX Unsigned32 (0..65535)
	  MAX-ACCESS read-only
	  STATUS current
	  DESCRIPTION
        "
        Min Client Trscv Tx Power :This 
        OID gives the minimum transmit
         power value among the network
         lanes of the Client Transceiver, 
        read from the DDM (Digital Diagnostic 
        Monitoring) (Power = 10*log(AV)-40) 
        (Unit = dBm) <Help> This Measure 
        gives the minimum transmit power 
        value among the network lanes of 
        the Client Transceiver
        "
	  ::= { pm200fr20MesrOther 210 }



--- *****************************************************
---     LEAF for the clientNetRxPwrMin article
--- *****************************************************

pm200fr20MesrclientNetRxPwrMin OBJECT-TYPE
	  SYNTAX Unsigned32 (0..65535)
	  MAX-ACCESS read-only
	  STATUS current
	  DESCRIPTION
        "
        Min Client Trscv Rx Power :This 
        OID gives the minimum receive power 
        value among the network lanes of 
        the Client Transceiver, read in 
        the DDM (Digital Diagnostic Monitoring) 
        (Power = 10*log(AV)-40) (Unit = 
        dBm) <Help> This Measure gives
         the minimum receive power value 
        among the network lanes of the
         Client Transceiver
        "
	  ::= { pm200fr20MesrOther 211 }



--- *****************************************************
---     LEAF for the lineNetTxLaserOutputPwrMin article
--- *****************************************************

pm200fr20MesrlineNetTxLaserOutputPwrMin OBJECT-TYPE
	  SYNTAX Unsigned32 (0..65535)
	  MAX-ACCESS read-only
	  STATUS current
	  DESCRIPTION
        "
        Min Line Trscv Tx Power :This
         OID gives the minimum Tx Laser 
        transmit power value among the
         network lanes of the Line Transceiver, 
        read in the DDM (Digital Diagnostic 
        Monitoring)  (Power = AV/100) (Unit 
        = dBm) (Unit = dBm) <Help> This 
        Measure gives the minimum Tx Laser 
        transmit power value among the
         network lanes of the Line Transceiver
        "
	  ::= { pm200fr20MesrOther 212 }



--- *****************************************************
---     LEAF for the lineNetTxLaserTempMin article
--- *****************************************************

pm200fr20MesrlineNetTxLaserTempMin OBJECT-TYPE
	  SYNTAX Unsigned32 (0..65535)
	  MAX-ACCESS read-only
	  STATUS current
	  DESCRIPTION
        "
        Min Line Trscv Tx Laser Temperature 
        :This OID gives the minimum Tx
         Laser Temperature value among
         the network lanes of the Line
         Transceiver, read from the DDM 
        (Digital Diagnostic Monitoring) 
        (Temperature = AV/256) (Unit =
         C) <Help> This Measure gives the 
        minimum Tx Laser Temperature value 
        among the network lanes of the
         Line Transceiver
        "
	  ::= { pm200fr20MesrOther 213 }



--- *****************************************************
---     LEAF for the lineNetTxBiasCurrentMin article
--- *****************************************************

pm200fr20MesrlineNetTxBiasCurrentMin OBJECT-TYPE
	  SYNTAX Unsigned32 (0..65535)
	  MAX-ACCESS read-only
	  STATUS current
	  DESCRIPTION
        "
        Min Line Trscv Tx Laser Bias :This 
        OID gives the minimum Tx Laser
         Bias value among the network lanes 
        of the Line Transceiver, read from 
        the DDM (Digital Diagnostic Monitoring) 
        (Bias = AV/10) (Unit = mA) <Help> 
        This Measure gives the minimum
         Tx Laser Bias value among the
         network lanes of the Line Transceiver
        "
	  ::= { pm200fr20MesrOther 214 }



--- *****************************************************
---     LEAF for the lineNetRxInputPwrMin article
--- *****************************************************

pm200fr20MesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver, 
        read in the DDM (Digital Diagnostic 
        Monitoring) (Power = AV/100) (Unit 
        = dBm) <Help> This Measure gives 
        the minimum Receive power value 
        among the network lanes of the
         Line Transceiver
        "
	  ::= { pm200fr20MesrOther 215 }



--- *****************************************************
---     LEAF for the lineResidualChromaticDispMin article
--- *****************************************************

pm200fr20MesrlineResidualChromaticDispMin OBJECT-TYPE
	  SYNTAX Unsigned32 (0..65535)
	  MAX-ACCESS read-only
	  STATUS current
	  DESCRIPTION
        "
        Min Residual Chromatic Dispersion 
        :This OID gives the minimum Residual 
        Chromatic Dispersion on the Line 
        interface since the last measure 
        reset  (Unit = ps/nm)<Help> This 
        measure gives the minimum Residual 
        Chromatic Dispersion on the Line 
        interface since the last measure 
        reset.
        "
	  ::= { pm200fr20MesrOther 216 }



--- *****************************************************
---     LEAF for the lineDiffGroupDelayMin article
--- *****************************************************

pm200fr20MesrlineDiffGroupDelayMin OBJECT-TYPE
	  SYNTAX Unsigned32 (0..65535)
	  MAX-ACCESS read-only
	  STATUS current
	  DESCRIPTION
        "
        Min Differential Group Delay :This 
        OID gives the minimum Differential 
        Group Delay  on the Line interface 
        since the last measure reset  (Unit 
        = ps)<Help> This measure gives
         the minimum Differential Group 
        Delay on the Line interface since 
        the last measure reset.
        "
	  ::= { pm200fr20MesrOther 217 }



--- *****************************************************
---     LEAF for the lineQFactorMin article
--- *****************************************************

pm200fr20MesrlineQFactorMin OBJECT-TYPE
	  SYNTAX Unsigned32 (0..65535)
	  MAX-ACCESS read-only
	  STATUS current
	  DESCRIPTION
        "
        Min Q Factor :This OID gives the 
        minimum Q Factor on the Line interface 
        since the last measure reset  (Unit 
        = dB)<Help> This measure gives
         the minimum Q Factor on the Line 
        interface since the last measure 
        reset.
        "
	  ::= { pm200fr20MesrOther 218 }



--- *****************************************************
---     LEAF for the lineCarrierFreqOffsetMin article
--- *****************************************************

pm200fr20MesrlineCarrierFreqOffsetMin OBJECT-TYPE
	  SYNTAX Unsigned32 (0..65535)
	  MAX-ACCESS read-only
	  STATUS current
	  DESCRIPTION
        "
        Min Carrier Frequency Offset :This 
        OID gives the minimum Carrier Frequency 
        Offset on the Line interface since 
        the last measure reset  (Unit = 
        Mhz)<Help> This measure gives the 
        minimum Carrier Frequency Offset 
        on the Line interface since the 
        last measure reset
        "
	  ::= { pm200fr20MesrOther 219 }



--- *****************************************************
---     LEAF for the lineOsnrMin article
--- *****************************************************

pm200fr20MesrlineOsnrMin OBJECT-TYPE
	  SYNTAX Unsigned32 (0..65535)
	  MAX-ACCESS read-only
	  STATUS current
	  DESCRIPTION
        "
        Min OSNR :This OID gives the minimum 
        OSNR on the Line interface since 
        the last measure reset  (OSNR = 
        AV/10) (Unit = dB)<Help> This measure 
        gives the minimum OSNR on the Line 
        interface since the last measure 
        reset.
        "
	  ::= { pm200fr20MesrOther 220 }



--- *****************************************************
---     LEAF for the clientNetTxTempMax article
--- *****************************************************

pm200fr20MesrclientNetTxTempMax OBJECT-TYPE
	  SYNTAX Unsigned32 (0..65535)
	  MAX-ACCESS read-only
	  STATUS current
	  DESCRIPTION
        "
        Max Client Trscv Laser Temperature 
        :This OID gives the maximum Laser 
        temperature value among the network 
        lanes of the Client Transceiver, 
        read from the DDM (Digital Diagnostic 
        Monitoring) (Temperature = AV/256) 
        (Unit = C) <Help> This Measure
         gives the maximum Laser temperature 
        value among the network lanes of 
        the Client Transceiver
        "
	  ::= { pm200fr20MesrOther 224 }



--- *****************************************************
---     LEAF for the clientNetTxBiasMax article
--- *****************************************************

pm200fr20MesrclientNetTxBiasMax OBJECT-TYPE
	  SYNTAX Unsigned32 (0..65535)
	  MAX-ACCESS read-only
	  STATUS current
	  DESCRIPTION
        "
        Max Client Trscv Laser Bias :This 
        OID gives the maximum Laser bias 
        value among the network lanes of 
        the Client Transceiver, read from 
        the DDM (Digital Diagnostic Monitoring) 
        (Bias = AV/500) (Unit = mA) <Help> 
        This Measure gives the maximum
         Laser bias value among the network 
        lanes of the Client Transceiver
        "
	  ::= { pm200fr20MesrOther 225 }



--- *****************************************************
---     LEAF for the clientNetTxPwrMax article
--- *****************************************************

pm200fr20MesrclientNetTxPwrMax OBJECT-TYPE
	  SYNTAX Unsigned32 (0..65535)
	  MAX-ACCESS read-only
	  STATUS current
	  DESCRIPTION
        "
        Max Client Trscv Tx Power :This 
        OID gives the maximum transmit
         power value among the network
         lanes of the Client Transceiver, 
        read from the DDM (Digital Diagnostic 
        Monitoring) (Power = 10*log(AV)-40) 
        (Unit = dBm) <Help> This Measure 
        gives the maximum transmit power 
        value among the network lanes of 
        the Client Transceiver
        "
	  ::= { pm200fr20MesrOther 226 }



--- *****************************************************
---     LEAF for the clientNetRxPwrMax article
--- *****************************************************

pm200fr20MesrclientNetRxPwrMax OBJECT-TYPE
	  SYNTAX Unsigned32 (0..65535)
	  MAX-ACCESS read-only
	  STATUS current
	  DESCRIPTION
        "
        Max Client Trscv Rx Power :This 
        OID gives the maximum receive power 
        value among the network lanes of 
        the Client Transceiver, read in 
        the DDM (Digital Diagnostic Monitoring) 
        (Power = 10*log(AV)-40) (Unit = 
        dBm) <Help> This Measure gives
         the maximum receive power value 
        among the network lanes of the
         Client Transceiver
        "
	  ::= { pm200fr20MesrOther 227 }



--- *****************************************************
---     LEAF for the lineNetTxLaserOutputPwrMax article
--- *****************************************************

pm200fr20MesrlineNetTxLaserOutputPwrMax OBJECT-TYPE
	  SYNTAX Unsigned32 (0..65535)
	  MAX-ACCESS read-only
	  STATUS current
	  DESCRIPTION
        "
        Max Line Trscv Tx Power :This
         OID gives the maximum Tx Laser 
        transmit power value among the
         network lanes of the Line Transceiver, 
        read in the DDM (Digital Diagnostic 
        Monitoring) (Power = 10*log(AV)-40) 
        (Unit = dBm) <Help> This Measure 
        gives the maximum Tx Laser transmit 
        power value among the network lanes 
        of the Line Transceiver
        "
	  ::= { pm200fr20MesrOther 228 }



--- *****************************************************
---     LEAF for the lineNetTxLaserTempMax article
--- *****************************************************

pm200fr20MesrlineNetTxLaserTempMax OBJECT-TYPE
	  SYNTAX Unsigned32 (0..65535)
	  MAX-ACCESS read-only
	  STATUS current
	  DESCRIPTION
        "
        Max Line Trscv Tx Laser Temperature 
        :This OID gives the maximum Tx
         Laser Temperature value among
         the network lanes of the Line
         Transceiver, read from the DDM 
        (Digital Diagnostic Monitoring) 
        (Temperature = AV/256) (Unit =
         C) <Help> This Measure gives the 
        maximum Tx Laser Temperature value 
        among the network lanes of the
         Line Transceiver
        "
	  ::= { pm200fr20MesrOther 229 }



--- *****************************************************
---     LEAF for the lineNetTxBiasCurrentMax article
--- *****************************************************

pm200fr20MesrlineNetTxBiasCurrentMax OBJECT-TYPE
	  SYNTAX Unsigned32 (0..65535)
	  MAX-ACCESS read-only
	  STATUS current
	  DESCRIPTION
        "
        Max Line Trscv Tx Laser Bias :This 
        OID gives the maximum Tx Laser
         Bias value among the network lanes 
        of the Line Transceiver, read from 
        the DDM (Digital Diagnostic Monitoring) 
        (Bias = AV/10) (Unit = mA) <Help> 
        This Measure gives the maximum
         Tx Laser Bias value among the
         network lanes of the Line Transceiver
        "
	  ::= { pm200fr20MesrOther 230 }



--- *****************************************************
---     LEAF for the lineNetRxInputPwrMax article
--- *****************************************************

pm200fr20MesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver, 
        read in the DDM (Digital Diagnostic 
        Monitoring) (Power = 10*log(AV)-40) 
        (Unit = dBm) <Help> This Measure 
        gives the maximum Receive power 
        value among the network lanes of 
        the Line Transceiver
        "
	  ::= { pm200fr20MesrOther 231 }



--- *****************************************************
---     LEAF for the lineResidualChromaticDispMax article
--- *****************************************************

pm200fr20MesrlineResidualChromaticDispMax OBJECT-TYPE
	  SYNTAX Unsigned32 (0..65535)
	  MAX-ACCESS read-only
	  STATUS current
	  DESCRIPTION
        "
        Max Residual Chromatic Dispersion 
        :This OID gives the maximum Residual 
        Chromatic Dispersion on the Line 
        interface since the last measure 
        reset  (Unit = ps/nm)<Help> This 
        measure gives the maximum Residual 
        Chromatic Dispersion on the Line 
        interface since the last measure 
        reset.
        "
	  ::= { pm200fr20MesrOther 232 }



--- *****************************************************
---     LEAF for the lineDiffGroupDelayMax article
--- *****************************************************

pm200fr20MesrlineDiffGroupDelayMax OBJECT-TYPE
	  SYNTAX Unsigned32 (0..65535)
	  MAX-ACCESS read-only
	  STATUS current
	  DESCRIPTION
        "
        Max Differential Group Delay :This 
        OID gives the maximum Differential 
        Group Delay  on the Line interface 
        since the last measure reset  
         (Unit = ps)<Help> This measure 
        gives the maximum Differential
         Group Delay on the Line interface 
        since the last measure reset.
        "
	  ::= { pm200fr20MesrOther 233 }



--- *****************************************************
---     LEAF for the lineQFactorMax article
--- *****************************************************

pm200fr20MesrlineQFactorMax OBJECT-TYPE
	  SYNTAX Unsigned32 (0..65535)
	  MAX-ACCESS read-only
	  STATUS current
	  DESCRIPTION
        "
        Max Q Factor :This OID gives the 
        maximum Q Factor on the Line interface 
        since the last measure reset  (Unit 
        = dB)<Help> This measure gives
         the maximum Q Factor on the Line 
        interface since the last measure 
        reset.
        "
	  ::= { pm200fr20MesrOther 234 }



--- *****************************************************
---     LEAF for the lineCarrierFreqOffsetMax article
--- *****************************************************

pm200fr20MesrlineCarrierFreqOffsetMax OBJECT-TYPE
	  SYNTAX Unsigned32 (0..65535)
	  MAX-ACCESS read-only
	  STATUS current
	  DESCRIPTION
        "
        Max Carrier Frequency Offset :This 
        OID gives the maximum Carrier Frequency 
        Offset on the Line interface since 
        the last measure reset   (Unit
         = Mhz)<Help> This measure gives 
        the maximum Carrier Frequency Offset 
        on the Line interface since the 
        last measure reset.
        "
	  ::= { pm200fr20MesrOther 235 }



--- *****************************************************
---     LEAF for the lineOsnrMax article
--- *****************************************************

pm200fr20MesrlineOsnrMax OBJECT-TYPE
	  SYNTAX Unsigned32 (0..65535)
	  MAX-ACCESS read-only
	  STATUS current
	  DESCRIPTION
        "
        Max OSNR :This OID gives the maximum 
        OSNR on the Line interface since 
        the last measure reset  (OSNR = 
        AV/10) (Unit = dB) <Help> This
         measure gives the maximum OSNR 
        on the Line interface since the 
        last measure reset
        "
	  ::= { pm200fr20MesrOther 236 }



--- *****************************************************
---     LEAF for the lineTrscvTemp article
--- *****************************************************

pm200fr20MesrlineTrscvTemp OBJECT-TYPE
	  SYNTAX Unsigned32 (0..65535)
	  MAX-ACCESS read-only
	  STATUS current
	  DESCRIPTION
        "
        LineTrscv Temperature :This OID 
        gives the temperature value of
         the Transceiver, read from the 
        DDM (Digital Diagnostic Monitoring) 
        (Temperature = AV_S16/256) (Unit 
        = C) <Help> This Measure gives
         the temperature value of the Transceiver
        "
	  ::= { pm200fr20MesrOther 400 }



--- *****************************************************
---     LEAF for the lineTrscvVoltage article
--- *****************************************************

pm200fr20MesrlineTrscvVoltage OBJECT-TYPE
	  SYNTAX Unsigned32 (0..65535)
	  MAX-ACCESS read-only
	  STATUS current
	  DESCRIPTION
        "
        Line Trscv Voltage :This OID gives 
        the voltage value of the QSFP plugged 
        into the port, read from the DDM 
        (Digital Diagnostic Monitoring) 
        (Voltage = AV_U16/10000) (Unit
         = V)  <Help>  This measure gives 
        the power supply voltage of the 
        transceiver
        "
	  ::= { pm200fr20MesrOther 408 }








--- *****************************************************
--- $$$$$$$$$$$$$$$$$$$$$$$$$$$$$$$$$$$$$$$$$$$$$$$$$$$$$
---     PERFORMANCE
--- $$$$$$$$$$$$$$$$$$$$$$$$$$$$$$$$$$$$$$$$$$$$$$$$$$$$$
--- *****************************************************



--- *****************************************************
---     Leaf of the telecomInputClientCurrent15Stat
--- *****************************************************
--- *********************************************************
---     TABLE for the pm200fr20PerfTelecomInputClientCurrent15Stat articles
--- *********************************************************

pm200fr20PerfTelecomInputClientCurrent15StatTable OBJECT-TYPE
	SYNTAX  SEQUENCE OF Pm200fr20PerfTelecomInputClientCurrent15StatEntry
	MAX-ACCESS not-accessible
	STATUS current
	DESCRIPTION
        "
        List of pm200fr20PerfTelecomInputClientCurrent15Stat 
        Article
        "
	::= { pm200fr20MonPerfClient 16 }


pm200fr20PerfTelecomInputClientCurrent15StatEntry OBJECT-TYPE
	SYNTAX Pm200fr20PerfTelecomInputClientCurrent15StatEntry
	MAX-ACCESS not-accessible
	STATUS current
	DESCRIPTION
        "
        Row definition for the pm200fr20PerfTelecomInputClientCurrent15Stat 
        table
        "
	INDEX   { pm200fr20PerfTelecomInputClientCurrent15StatIndex }
	::= { pm200fr20PerfTelecomInputClientCurrent15StatTable 1 }


Pm200fr20PerfTelecomInputClientCurrent15StatEntry ::=
	SEQUENCE {
	pm200fr20PerfTelecomInputClientCurrent15StatIndex
		INTEGER,
	pm200fr20PerfTelecomInputClientCurrent15StatInvCvPortn
		EkiOnOff,
	pm200fr20PerfTelecomInputClientCurrent15StatCvValuePortn
		Unsigned32,
	pm200fr20PerfTelecomInputClientCurrent15StatInvEsPortn
		EkiOnOff,
	pm200fr20PerfTelecomInputClientCurrent15StatEsValuePortn
		Unsigned32,
	pm200fr20PerfTelecomInputClientCurrent15StatInvSesPortn
		EkiOnOff,
	pm200fr20PerfTelecomInputClientCurrent15StatSesValuePortn
		Unsigned32,
	pm200fr20PerfTelecomInputClientCurrent15StatInvSefsPortn
		EkiOnOff,
	pm200fr20PerfTelecomInputClientCurrent15StatSefsValuePortn
		Unsigned32,
	pm200fr20PerfTelecomInputClientCurrent15StatInvUasPortn
		EkiOnOff,
	pm200fr20PerfTelecomInputClientCurrent15StatUasValuePortn
		Unsigned32
	}


pm200fr20PerfTelecomInputClientCurrent15StatIndex OBJECT-TYPE
	SYNTAX  INTEGER(0..128)
	MAX-ACCESS  read-only
	STATUS current
	DESCRIPTION
        "
        Index definition for the pm200fr20PerfTelecomInputClientCurrent15Stat 
        table
        "
	::= { pm200fr20PerfTelecomInputClientCurrent15StatEntry 1 }


pm200fr20PerfTelecomInputClientCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pm200fr20PerfTelecomInputClientCurrent15StatEntry 2 }


pm200fr20PerfTelecomInputClientCurrent15StatCvValuePortn OBJECT-TYPE
	SYNTAX  Unsigned32
	MAX-ACCESS read-only
	STATUS current
	DESCRIPTION
        "
        Current 15-min EBC counter :This 
        OID gives the current 15-min Coding 
        Violation counter value
        "
	::= { pm200fr20PerfTelecomInputClientCurrent15StatEntry 3 }


pm200fr20PerfTelecomInputClientCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm200fr20PerfTelecomInputClientCurrent15StatEntry 4 }


pm200fr20PerfTelecomInputClientCurrent15StatEsValuePortn OBJECT-TYPE
	SYNTAX  Unsigned32
	MAX-ACCESS read-only
	STATUS current
	DESCRIPTION
        "
        Current 15-min ES counter :This 
        OID gives the current 15-min Errored 
        Second counter value
        "
	::= { pm200fr20PerfTelecomInputClientCurrent15StatEntry 5 }


pm200fr20PerfTelecomInputClientCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm200fr20PerfTelecomInputClientCurrent15StatEntry 6 }


pm200fr20PerfTelecomInputClientCurrent15StatSesValuePortn OBJECT-TYPE
	SYNTAX  Unsigned32
	MAX-ACCESS read-only
	STATUS current
	DESCRIPTION
        "
        Current 15-min SES counter :This 
        OID gives the current 15-min severely 
        Errored Second counter value
        "
	::= { pm200fr20PerfTelecomInputClientCurrent15StatEntry 7 }


pm200fr20PerfTelecomInputClientCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm200fr20PerfTelecomInputClientCurrent15StatEntry 8 }


pm200fr20PerfTelecomInputClientCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pm200fr20PerfTelecomInputClientCurrent15StatEntry 9 }


pm200fr20PerfTelecomInputClientCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm200fr20PerfTelecomInputClientCurrent15StatEntry 10 }


pm200fr20PerfTelecomInputClientCurrent15StatUasValuePortn OBJECT-TYPE
	SYNTAX  Unsigned32
	MAX-ACCESS read-only
	STATUS current
	DESCRIPTION
        "
        Current 15-min UAS counter :This 
        OID gives the current 15-min UnAvailable 
        Second counter value
        "
	::= { pm200fr20PerfTelecomInputClientCurrent15StatEntry 11 }


--- *****************************************************
---     Leaf of the telecomInputClientPast15Stat
--- *****************************************************
--- *********************************************************
---     TABLE for the pm200fr20PerfTelecomInputClientPast15StatHistory articles
--- *********************************************************

pm200fr20PerfTelecomInputClientPast15StatHistoryPort1Table OBJECT-TYPE
	SYNTAX  SEQUENCE OF Pm200fr20PerfTelecomInputClientPast15StatHistoryPort1Entry
	MAX-ACCESS not-accessible
	STATUS current
	DESCRIPTION
        "
        List of pm200fr20PerfTelecomInputClientPast15StatHistory 
        Article
        "
	::= { pm200fr20MonPerfClient 48 }


pm200fr20PerfTelecomInputClientPast15StatHistoryPort1Entry OBJECT-TYPE
	SYNTAX Pm200fr20PerfTelecomInputClientPast15StatHistoryPort1Entry
	MAX-ACCESS not-accessible
	STATUS current
	DESCRIPTION
        "
        Row definition for the pm200fr20PerfTelecomInputClientPast15StatHistory 
        table
        "
	INDEX   { pm200fr20PerfTelecomInputClientPast15StatHistoryPort1Index }
	::= { pm200fr20PerfTelecomInputClientPast15StatHistoryPort1Table 1 }


Pm200fr20PerfTelecomInputClientPast15StatHistoryPort1Entry ::=
	SEQUENCE {
	pm200fr20PerfTelecomInputClientPast15StatHistoryPort1Index
		INTEGER,
	pm200fr20PerfTelecomInputClientPast15StatHistoryInvCvPort1
		EkiOnOff,
	pm200fr20PerfTelecomInputClientPast15StatHistoryCvValuePort1
		Unsigned32,
	pm200fr20PerfTelecomInputClientPast15StatHistoryInvEsPort1
		EkiOnOff,
	pm200fr20PerfTelecomInputClientPast15StatHistoryEsValuePort1
		Unsigned32,
	pm200fr20PerfTelecomInputClientPast15StatHistoryInvSesPort1
		EkiOnOff,
	pm200fr20PerfTelecomInputClientPast15StatHistorySesValuePort1
		Unsigned32,
	pm200fr20PerfTelecomInputClientPast15StatHistoryInvSefsPort1
		EkiOnOff,
	pm200fr20PerfTelecomInputClientPast15StatHistorySefsValuePort1
		Unsigned32,
	pm200fr20PerfTelecomInputClientPast15StatHistoryInvUasPort1
		EkiOnOff,
	pm200fr20PerfTelecomInputClientPast15StatHistoryUasValuePort1
		Unsigned32
	}


pm200fr20PerfTelecomInputClientPast15StatHistoryPort1Index OBJECT-TYPE
	SYNTAX  INTEGER(0..128)
	MAX-ACCESS  read-only
	STATUS current
	DESCRIPTION
        "
        Index definition for the pm200fr20PerfTelecomInputClientPast15StatHistory 
        table
        "
	::= { pm200fr20PerfTelecomInputClientPast15StatHistoryPort1Entry 1 }


pm200fr20PerfTelecomInputClientPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pm200fr20PerfTelecomInputClientPast15StatHistoryPort1Entry 2 }


pm200fr20PerfTelecomInputClientPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pm200fr20PerfTelecomInputClientPast15StatHistoryPort1Entry 3 }


pm200fr20PerfTelecomInputClientPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pm200fr20PerfTelecomInputClientPast15StatHistoryPort1Entry 4 }


pm200fr20PerfTelecomInputClientPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pm200fr20PerfTelecomInputClientPast15StatHistoryPort1Entry 5 }


pm200fr20PerfTelecomInputClientPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pm200fr20PerfTelecomInputClientPast15StatHistoryPort1Entry 6 }


pm200fr20PerfTelecomInputClientPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pm200fr20PerfTelecomInputClientPast15StatHistoryPort1Entry 7 }


pm200fr20PerfTelecomInputClientPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm200fr20PerfTelecomInputClientPast15StatHistoryPort1Entry 8 }


pm200fr20PerfTelecomInputClientPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pm200fr20PerfTelecomInputClientPast15StatHistoryPort1Entry 9 }


pm200fr20PerfTelecomInputClientPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pm200fr20PerfTelecomInputClientPast15StatHistoryPort1Entry 10 }


pm200fr20PerfTelecomInputClientPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pm200fr20PerfTelecomInputClientPast15StatHistoryPort1Entry 11 }


--- *****************************************************
---     Leaf of the telecomInputClientCurrent24Stat
--- *****************************************************
--- *********************************************************
---     TABLE for the pm200fr20PerfTelecomInputClientCurrent24Stat articles
--- *********************************************************

pm200fr20PerfTelecomInputClientCurrent24StatTable OBJECT-TYPE
	SYNTAX  SEQUENCE OF Pm200fr20PerfTelecomInputClientCurrent24StatEntry
	MAX-ACCESS not-accessible
	STATUS current
	DESCRIPTION
        "
        List of pm200fr20PerfTelecomInputClientCurrent24Stat 
        Article
        "
	::= { pm200fr20MonPerfClient 80 }


pm200fr20PerfTelecomInputClientCurrent24StatEntry OBJECT-TYPE
	SYNTAX Pm200fr20PerfTelecomInputClientCurrent24StatEntry
	MAX-ACCESS not-accessible
	STATUS current
	DESCRIPTION
        "
        Row definition for the pm200fr20PerfTelecomInputClientCurrent24Stat 
        table
        "
	INDEX   { pm200fr20PerfTelecomInputClientCurrent24StatIndex }
	::= { pm200fr20PerfTelecomInputClientCurrent24StatTable 1 }


Pm200fr20PerfTelecomInputClientCurrent24StatEntry ::=
	SEQUENCE {
	pm200fr20PerfTelecomInputClientCurrent24StatIndex
		INTEGER,
	pm200fr20PerfTelecomInputClientCurrent24StatInvCvPortn
		EkiOnOff,
	pm200fr20PerfTelecomInputClientCurrent24StatCvValuePortn
		Unsigned32,
	pm200fr20PerfTelecomInputClientCurrent24StatInvEsPortn
		EkiOnOff,
	pm200fr20PerfTelecomInputClientCurrent24StatEsValuePortn
		Unsigned32,
	pm200fr20PerfTelecomInputClientCurrent24StatInvSesPortn
		EkiOnOff,
	pm200fr20PerfTelecomInputClientCurrent24StatSesValuePortn
		Unsigned32,
	pm200fr20PerfTelecomInputClientCurrent24StatInvSefsPortn
		EkiOnOff,
	pm200fr20PerfTelecomInputClientCurrent24StatSefsValuePortn
		Unsigned32,
	pm200fr20PerfTelecomInputClientCurrent24StatInvUasPortn
		EkiOnOff,
	pm200fr20PerfTelecomInputClientCurrent24StatUasValuePortn
		Unsigned32
	}


pm200fr20PerfTelecomInputClientCurrent24StatIndex OBJECT-TYPE
	SYNTAX  INTEGER(0..128)
	MAX-ACCESS  read-only
	STATUS current
	DESCRIPTION
        "
        Index definition for the pm200fr20PerfTelecomInputClientCurrent24Stat 
        table
        "
	::= { pm200fr20PerfTelecomInputClientCurrent24StatEntry 1 }


pm200fr20PerfTelecomInputClientCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pm200fr20PerfTelecomInputClientCurrent24StatEntry 2 }


pm200fr20PerfTelecomInputClientCurrent24StatCvValuePortn OBJECT-TYPE
	SYNTAX  Unsigned32
	MAX-ACCESS read-only
	STATUS current
	DESCRIPTION
        "
        Current 24-hours EBC counter :This 
        OID gives the current 24-hours
         Coding Violation counter value
        "
	::= { pm200fr20PerfTelecomInputClientCurrent24StatEntry 3 }


pm200fr20PerfTelecomInputClientCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm200fr20PerfTelecomInputClientCurrent24StatEntry 4 }


pm200fr20PerfTelecomInputClientCurrent24StatEsValuePortn OBJECT-TYPE
	SYNTAX  Unsigned32
	MAX-ACCESS read-only
	STATUS current
	DESCRIPTION
        "
        Current 24-hours ES counter :This 
        OID gives the current 24-hours
         Errored Second counter value
        "
	::= { pm200fr20PerfTelecomInputClientCurrent24StatEntry 5 }


pm200fr20PerfTelecomInputClientCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm200fr20PerfTelecomInputClientCurrent24StatEntry 6 }


pm200fr20PerfTelecomInputClientCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pm200fr20PerfTelecomInputClientCurrent24StatEntry 7 }


pm200fr20PerfTelecomInputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm200fr20PerfTelecomInputClientCurrent24StatEntry 8 }


pm200fr20PerfTelecomInputClientCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm200fr20PerfTelecomInputClientCurrent24StatEntry 9 }


pm200fr20PerfTelecomInputClientCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm200fr20PerfTelecomInputClientCurrent24StatEntry 10 }


pm200fr20PerfTelecomInputClientCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pm200fr20PerfTelecomInputClientCurrent24StatEntry 11 }


--- *****************************************************
---     Leaf of the telecomInputClientPast24Stat
--- *****************************************************
--- *********************************************************
---     TABLE for the pm200fr20PerfTelecomInputClientPast24StatHistory articles
--- *********************************************************

pm200fr20PerfTelecomInputClientPast24StatHistoryPort1Table OBJECT-TYPE
	SYNTAX  SEQUENCE OF Pm200fr20PerfTelecomInputClientPast24StatHistoryPort1Entry
	MAX-ACCESS not-accessible
	STATUS current
	DESCRIPTION
        "
        List of pm200fr20PerfTelecomInputClientPast24StatHistory 
        Article
        "
	::= { pm200fr20MonPerfClient 112 }


pm200fr20PerfTelecomInputClientPast24StatHistoryPort1Entry OBJECT-TYPE
	SYNTAX Pm200fr20PerfTelecomInputClientPast24StatHistoryPort1Entry
	MAX-ACCESS not-accessible
	STATUS current
	DESCRIPTION
        "
        Row definition for the pm200fr20PerfTelecomInputClientPast24StatHistory 
        table
        "
	INDEX   { pm200fr20PerfTelecomInputClientPast24StatHistoryPort1Index }
	::= { pm200fr20PerfTelecomInputClientPast24StatHistoryPort1Table 1 }


Pm200fr20PerfTelecomInputClientPast24StatHistoryPort1Entry ::=
	SEQUENCE {
	pm200fr20PerfTelecomInputClientPast24StatHistoryPort1Index
		INTEGER,
	pm200fr20PerfTelecomInputClientPast24StatHistoryInvCvPort1
		EkiOnOff,
	pm200fr20PerfTelecomInputClientPast24StatHistoryCvValuePort1
		Unsigned32,
	pm200fr20PerfTelecomInputClientPast24StatHistoryInvEsPort1
		EkiOnOff,
	pm200fr20PerfTelecomInputClientPast24StatHistoryEsValuePort1
		Unsigned32,
	pm200fr20PerfTelecomInputClientPast24StatHistoryInvSesPort1
		EkiOnOff,
	pm200fr20PerfTelecomInputClientPast24StatHistorySesValuePort1
		Unsigned32,
	pm200fr20PerfTelecomInputClientPast24StatHistoryInvSefsPort1
		EkiOnOff,
	pm200fr20PerfTelecomInputClientPast24StatHistorySefsValuePort1
		Unsigned32,
	pm200fr20PerfTelecomInputClientPast24StatHistoryInvUasPort1
		EkiOnOff,
	pm200fr20PerfTelecomInputClientPast24StatHistoryUasValuePort1
		Unsigned32
	}


pm200fr20PerfTelecomInputClientPast24StatHistoryPort1Index OBJECT-TYPE
	SYNTAX  INTEGER(0..128)
	MAX-ACCESS  read-only
	STATUS current
	DESCRIPTION
        "
        Index definition for the pm200fr20PerfTelecomInputClientPast24StatHistory 
        table
        "
	::= { pm200fr20PerfTelecomInputClientPast24StatHistoryPort1Entry 1 }


pm200fr20PerfTelecomInputClientPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pm200fr20PerfTelecomInputClientPast24StatHistoryPort1Entry 2 }


pm200fr20PerfTelecomInputClientPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pm200fr20PerfTelecomInputClientPast24StatHistoryPort1Entry 3 }


pm200fr20PerfTelecomInputClientPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pm200fr20PerfTelecomInputClientPast24StatHistoryPort1Entry 4 }


pm200fr20PerfTelecomInputClientPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pm200fr20PerfTelecomInputClientPast24StatHistoryPort1Entry 5 }


pm200fr20PerfTelecomInputClientPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pm200fr20PerfTelecomInputClientPast24StatHistoryPort1Entry 6 }


pm200fr20PerfTelecomInputClientPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pm200fr20PerfTelecomInputClientPast24StatHistoryPort1Entry 7 }


pm200fr20PerfTelecomInputClientPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm200fr20PerfTelecomInputClientPast24StatHistoryPort1Entry 8 }


pm200fr20PerfTelecomInputClientPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pm200fr20PerfTelecomInputClientPast24StatHistoryPort1Entry 9 }


pm200fr20PerfTelecomInputClientPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm200fr20PerfTelecomInputClientPast24StatHistoryPort1Entry 10 }


pm200fr20PerfTelecomInputClientPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pm200fr20PerfTelecomInputClientPast24StatHistoryPort1Entry 11 }


--- *****************************************************
---     Leaf of the telecomOutputClientCurrent15Stat
--- *****************************************************
--- *********************************************************
---     TABLE for the pm200fr20PerfTelecomOutputClientCurrent15Stat articles
--- *********************************************************

pm200fr20PerfTelecomOutputClientCurrent15StatTable OBJECT-TYPE
	SYNTAX  SEQUENCE OF Pm200fr20PerfTelecomOutputClientCurrent15StatEntry
	MAX-ACCESS not-accessible
	STATUS current
	DESCRIPTION
        "
        List of pm200fr20PerfTelecomOutputClientCurrent15Stat 
        Article
        "
	::= { pm200fr20MonPerfClient 144 }


pm200fr20PerfTelecomOutputClientCurrent15StatEntry OBJECT-TYPE
	SYNTAX Pm200fr20PerfTelecomOutputClientCurrent15StatEntry
	MAX-ACCESS not-accessible
	STATUS current
	DESCRIPTION
        "
        Row definition for the pm200fr20PerfTelecomOutputClientCurrent15Stat 
        table
        "
	INDEX   { pm200fr20PerfTelecomOutputClientCurrent15StatIndex }
	::= { pm200fr20PerfTelecomOutputClientCurrent15StatTable 1 }


Pm200fr20PerfTelecomOutputClientCurrent15StatEntry ::=
	SEQUENCE {
	pm200fr20PerfTelecomOutputClientCurrent15StatIndex
		INTEGER,
	pm200fr20PerfTelecomOutputClientCurrent15StatInvCvPortn
		EkiOnOff,
	pm200fr20PerfTelecomOutputClientCurrent15StatCvValuePortn
		Unsigned32,
	pm200fr20PerfTelecomOutputClientCurrent15StatInvEsPortn
		EkiOnOff,
	pm200fr20PerfTelecomOutputClientCurrent15StatEsValuePortn
		Unsigned32,
	pm200fr20PerfTelecomOutputClientCurrent15StatInvSesPortn
		EkiOnOff,
	pm200fr20PerfTelecomOutputClientCurrent15StatSesValuePortn
		Unsigned32,
	pm200fr20PerfTelecomOutputClientCurrent15StatInvSefsPortn
		EkiOnOff,
	pm200fr20PerfTelecomOutputClientCurrent15StatSefsValuePortn
		Unsigned32,
	pm200fr20PerfTelecomOutputClientCurrent15StatInvUasPortn
		EkiOnOff,
	pm200fr20PerfTelecomOutputClientCurrent15StatUasValuePortn
		Unsigned32
	}


pm200fr20PerfTelecomOutputClientCurrent15StatIndex OBJECT-TYPE
	SYNTAX  INTEGER(0..128)
	MAX-ACCESS  read-only
	STATUS current
	DESCRIPTION
        "
        Index definition for the pm200fr20PerfTelecomOutputClientCurrent15Stat 
        table
        "
	::= { pm200fr20PerfTelecomOutputClientCurrent15StatEntry 1 }


pm200fr20PerfTelecomOutputClientCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pm200fr20PerfTelecomOutputClientCurrent15StatEntry 2 }


pm200fr20PerfTelecomOutputClientCurrent15StatCvValuePortn OBJECT-TYPE
	SYNTAX  Unsigned32
	MAX-ACCESS read-only
	STATUS current
	DESCRIPTION
        "
        Current 15-min EBC counter :This 
        OID gives the current 15-min Coding 
        Violation counter value
        "
	::= { pm200fr20PerfTelecomOutputClientCurrent15StatEntry 3 }


pm200fr20PerfTelecomOutputClientCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm200fr20PerfTelecomOutputClientCurrent15StatEntry 4 }


pm200fr20PerfTelecomOutputClientCurrent15StatEsValuePortn OBJECT-TYPE
	SYNTAX  Unsigned32
	MAX-ACCESS read-only
	STATUS current
	DESCRIPTION
        "
        Current 15-min ES counter :This 
        OID gives the current 15-min Errored 
        Second counter value
        "
	::= { pm200fr20PerfTelecomOutputClientCurrent15StatEntry 5 }


pm200fr20PerfTelecomOutputClientCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm200fr20PerfTelecomOutputClientCurrent15StatEntry 6 }


pm200fr20PerfTelecomOutputClientCurrent15StatSesValuePortn OBJECT-TYPE
	SYNTAX  Unsigned32
	MAX-ACCESS read-only
	STATUS current
	DESCRIPTION
        "
        Current 15-min SES counter :This 
        OID gives the current 15-min severely 
        Errored Second counter value
        "
	::= { pm200fr20PerfTelecomOutputClientCurrent15StatEntry 7 }


pm200fr20PerfTelecomOutputClientCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm200fr20PerfTelecomOutputClientCurrent15StatEntry 8 }


pm200fr20PerfTelecomOutputClientCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pm200fr20PerfTelecomOutputClientCurrent15StatEntry 9 }


pm200fr20PerfTelecomOutputClientCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm200fr20PerfTelecomOutputClientCurrent15StatEntry 10 }


pm200fr20PerfTelecomOutputClientCurrent15StatUasValuePortn OBJECT-TYPE
	SYNTAX  Unsigned32
	MAX-ACCESS read-only
	STATUS current
	DESCRIPTION
        "
        Current 15-min UAS counter :This 
        OID gives the current 15-min UnAvailable 
        Second counter value
        "
	::= { pm200fr20PerfTelecomOutputClientCurrent15StatEntry 11 }


--- *****************************************************
---     Leaf of the telecomOutputClientPast15Stat
--- *****************************************************
--- *********************************************************
---     TABLE for the pm200fr20PerfTelecomOutputClientPast15StatHistory articles
--- *********************************************************

pm200fr20PerfTelecomOutputClientPast15StatHistoryPort1Table OBJECT-TYPE
	SYNTAX  SEQUENCE OF Pm200fr20PerfTelecomOutputClientPast15StatHistoryPort1Entry
	MAX-ACCESS not-accessible
	STATUS current
	DESCRIPTION
        "
        List of pm200fr20PerfTelecomOutputClientPast15StatHistory 
        Article
        "
	::= { pm200fr20MonPerfClient 176 }


pm200fr20PerfTelecomOutputClientPast15StatHistoryPort1Entry OBJECT-TYPE
	SYNTAX Pm200fr20PerfTelecomOutputClientPast15StatHistoryPort1Entry
	MAX-ACCESS not-accessible
	STATUS current
	DESCRIPTION
        "
        Row definition for the pm200fr20PerfTelecomOutputClientPast15StatHistory 
        table
        "
	INDEX   { pm200fr20PerfTelecomOutputClientPast15StatHistoryPort1Index }
	::= { pm200fr20PerfTelecomOutputClientPast15StatHistoryPort1Table 1 }


Pm200fr20PerfTelecomOutputClientPast15StatHistoryPort1Entry ::=
	SEQUENCE {
	pm200fr20PerfTelecomOutputClientPast15StatHistoryPort1Index
		INTEGER,
	pm200fr20PerfTelecomOutputClientPast15StatHistoryInvCvPort1
		EkiOnOff,
	pm200fr20PerfTelecomOutputClientPast15StatHistoryCvValuePort1
		Unsigned32,
	pm200fr20PerfTelecomOutputClientPast15StatHistoryInvEsPort1
		EkiOnOff,
	pm200fr20PerfTelecomOutputClientPast15StatHistoryEsValuePort1
		Unsigned32,
	pm200fr20PerfTelecomOutputClientPast15StatHistoryInvSesPort1
		EkiOnOff,
	pm200fr20PerfTelecomOutputClientPast15StatHistorySesValuePort1
		Unsigned32,
	pm200fr20PerfTelecomOutputClientPast15StatHistoryInvSefsPort1
		EkiOnOff,
	pm200fr20PerfTelecomOutputClientPast15StatHistorySefsValuePort1
		Unsigned32,
	pm200fr20PerfTelecomOutputClientPast15StatHistoryInvUasPort1
		EkiOnOff,
	pm200fr20PerfTelecomOutputClientPast15StatHistoryUasValuePort1
		Unsigned32
	}


pm200fr20PerfTelecomOutputClientPast15StatHistoryPort1Index OBJECT-TYPE
	SYNTAX  INTEGER(0..128)
	MAX-ACCESS  read-only
	STATUS current
	DESCRIPTION
        "
        Index definition for the pm200fr20PerfTelecomOutputClientPast15StatHistory 
        table
        "
	::= { pm200fr20PerfTelecomOutputClientPast15StatHistoryPort1Entry 1 }


pm200fr20PerfTelecomOutputClientPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pm200fr20PerfTelecomOutputClientPast15StatHistoryPort1Entry 2 }


pm200fr20PerfTelecomOutputClientPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pm200fr20PerfTelecomOutputClientPast15StatHistoryPort1Entry 3 }


pm200fr20PerfTelecomOutputClientPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pm200fr20PerfTelecomOutputClientPast15StatHistoryPort1Entry 4 }


pm200fr20PerfTelecomOutputClientPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pm200fr20PerfTelecomOutputClientPast15StatHistoryPort1Entry 5 }


pm200fr20PerfTelecomOutputClientPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pm200fr20PerfTelecomOutputClientPast15StatHistoryPort1Entry 6 }


pm200fr20PerfTelecomOutputClientPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pm200fr20PerfTelecomOutputClientPast15StatHistoryPort1Entry 7 }


pm200fr20PerfTelecomOutputClientPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm200fr20PerfTelecomOutputClientPast15StatHistoryPort1Entry 8 }


pm200fr20PerfTelecomOutputClientPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pm200fr20PerfTelecomOutputClientPast15StatHistoryPort1Entry 9 }


pm200fr20PerfTelecomOutputClientPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pm200fr20PerfTelecomOutputClientPast15StatHistoryPort1Entry 10 }


pm200fr20PerfTelecomOutputClientPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pm200fr20PerfTelecomOutputClientPast15StatHistoryPort1Entry 11 }


--- *****************************************************
---     Leaf of the telecomOutputClientCurrent24Stat
--- *****************************************************
--- *********************************************************
---     TABLE for the pm200fr20PerfTelecomOutputClientCurrent24Stat articles
--- *********************************************************

pm200fr20PerfTelecomOutputClientCurrent24StatTable OBJECT-TYPE
	SYNTAX  SEQUENCE OF Pm200fr20PerfTelecomOutputClientCurrent24StatEntry
	MAX-ACCESS not-accessible
	STATUS current
	DESCRIPTION
        "
        List of pm200fr20PerfTelecomOutputClientCurrent24Stat 
        Article
        "
	::= { pm200fr20MonPerfClient 208 }


pm200fr20PerfTelecomOutputClientCurrent24StatEntry OBJECT-TYPE
	SYNTAX Pm200fr20PerfTelecomOutputClientCurrent24StatEntry
	MAX-ACCESS not-accessible
	STATUS current
	DESCRIPTION
        "
        Row definition for the pm200fr20PerfTelecomOutputClientCurrent24Stat 
        table
        "
	INDEX   { pm200fr20PerfTelecomOutputClientCurrent24StatIndex }
	::= { pm200fr20PerfTelecomOutputClientCurrent24StatTable 1 }


Pm200fr20PerfTelecomOutputClientCurrent24StatEntry ::=
	SEQUENCE {
	pm200fr20PerfTelecomOutputClientCurrent24StatIndex
		INTEGER,
	pm200fr20PerfTelecomOutputClientCurrent24StatInvCvPortn
		EkiOnOff,
	pm200fr20PerfTelecomOutputClientCurrent24StatCvValuePortn
		Unsigned32,
	pm200fr20PerfTelecomOutputClientCurrent24StatInvEsPortn
		EkiOnOff,
	pm200fr20PerfTelecomOutputClientCurrent24StatEsValuePortn
		Unsigned32,
	pm200fr20PerfTelecomOutputClientCurrent24StatInvSesPortn
		EkiOnOff,
	pm200fr20PerfTelecomOutputClientCurrent24StatSesValuePortn
		Unsigned32,
	pm200fr20PerfTelecomOutputClientCurrent24StatInvSefsPortn
		EkiOnOff,
	pm200fr20PerfTelecomOutputClientCurrent24StatSefsValuePortn
		Unsigned32,
	pm200fr20PerfTelecomOutputClientCurrent24StatInvUasPortn
		EkiOnOff,
	pm200fr20PerfTelecomOutputClientCurrent24StatUasValuePortn
		Unsigned32
	}


pm200fr20PerfTelecomOutputClientCurrent24StatIndex OBJECT-TYPE
	SYNTAX  INTEGER(0..128)
	MAX-ACCESS  read-only
	STATUS current
	DESCRIPTION
        "
        Index definition for the pm200fr20PerfTelecomOutputClientCurrent24Stat 
        table
        "
	::= { pm200fr20PerfTelecomOutputClientCurrent24StatEntry 1 }


pm200fr20PerfTelecomOutputClientCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pm200fr20PerfTelecomOutputClientCurrent24StatEntry 2 }


pm200fr20PerfTelecomOutputClientCurrent24StatCvValuePortn OBJECT-TYPE
	SYNTAX  Unsigned32
	MAX-ACCESS read-only
	STATUS current
	DESCRIPTION
        "
        Current 24-hours EBC counter :This 
        OID gives the current 24-hours
         Coding Violation counter value
        "
	::= { pm200fr20PerfTelecomOutputClientCurrent24StatEntry 3 }


pm200fr20PerfTelecomOutputClientCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm200fr20PerfTelecomOutputClientCurrent24StatEntry 4 }


pm200fr20PerfTelecomOutputClientCurrent24StatEsValuePortn OBJECT-TYPE
	SYNTAX  Unsigned32
	MAX-ACCESS read-only
	STATUS current
	DESCRIPTION
        "
        Current 24-hours ES counter :This 
        OID gives the current 24-hours
         Errored Second counter value
        "
	::= { pm200fr20PerfTelecomOutputClientCurrent24StatEntry 5 }


pm200fr20PerfTelecomOutputClientCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm200fr20PerfTelecomOutputClientCurrent24StatEntry 6 }


pm200fr20PerfTelecomOutputClientCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pm200fr20PerfTelecomOutputClientCurrent24StatEntry 7 }


pm200fr20PerfTelecomOutputClientCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm200fr20PerfTelecomOutputClientCurrent24StatEntry 8 }


pm200fr20PerfTelecomOutputClientCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm200fr20PerfTelecomOutputClientCurrent24StatEntry 9 }


pm200fr20PerfTelecomOutputClientCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm200fr20PerfTelecomOutputClientCurrent24StatEntry 10 }


pm200fr20PerfTelecomOutputClientCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pm200fr20PerfTelecomOutputClientCurrent24StatEntry 11 }


--- *****************************************************
---     Leaf of the telecomOutputClientPast24Stat
--- *****************************************************
--- *********************************************************
---     TABLE for the pm200fr20PerfTelecomOutputClientPast24StatHistory articles
--- *********************************************************

pm200fr20PerfTelecomOutputClientPast24StatHistoryPort1Table OBJECT-TYPE
	SYNTAX  SEQUENCE OF Pm200fr20PerfTelecomOutputClientPast24StatHistoryPort1Entry
	MAX-ACCESS not-accessible
	STATUS current
	DESCRIPTION
        "
        List of pm200fr20PerfTelecomOutputClientPast24StatHistory 
        Article
        "
	::= { pm200fr20MonPerfClient 240 }


pm200fr20PerfTelecomOutputClientPast24StatHistoryPort1Entry OBJECT-TYPE
	SYNTAX Pm200fr20PerfTelecomOutputClientPast24StatHistoryPort1Entry
	MAX-ACCESS not-accessible
	STATUS current
	DESCRIPTION
        "
        Row definition for the pm200fr20PerfTelecomOutputClientPast24StatHistory 
        table
        "
	INDEX   { pm200fr20PerfTelecomOutputClientPast24StatHistoryPort1Index }
	::= { pm200fr20PerfTelecomOutputClientPast24StatHistoryPort1Table 1 }


Pm200fr20PerfTelecomOutputClientPast24StatHistoryPort1Entry ::=
	SEQUENCE {
	pm200fr20PerfTelecomOutputClientPast24StatHistoryPort1Index
		INTEGER,
	pm200fr20PerfTelecomOutputClientPast24StatHistoryInvCvPort1
		EkiOnOff,
	pm200fr20PerfTelecomOutputClientPast24StatHistoryCvValuePort1
		Unsigned32,
	pm200fr20PerfTelecomOutputClientPast24StatHistoryInvEsPort1
		EkiOnOff,
	pm200fr20PerfTelecomOutputClientPast24StatHistoryEsValuePort1
		Unsigned32,
	pm200fr20PerfTelecomOutputClientPast24StatHistoryInvSesPort1
		EkiOnOff,
	pm200fr20PerfTelecomOutputClientPast24StatHistorySesValuePort1
		Unsigned32,
	pm200fr20PerfTelecomOutputClientPast24StatHistoryInvSefsPort1
		EkiOnOff,
	pm200fr20PerfTelecomOutputClientPast24StatHistorySefsValuePort1
		Unsigned32,
	pm200fr20PerfTelecomOutputClientPast24StatHistoryInvUasPort1
		EkiOnOff,
	pm200fr20PerfTelecomOutputClientPast24StatHistoryUasValuePort1
		Unsigned32
	}


pm200fr20PerfTelecomOutputClientPast24StatHistoryPort1Index OBJECT-TYPE
	SYNTAX  INTEGER(0..128)
	MAX-ACCESS  read-only
	STATUS current
	DESCRIPTION
        "
        Index definition for the pm200fr20PerfTelecomOutputClientPast24StatHistory 
        table
        "
	::= { pm200fr20PerfTelecomOutputClientPast24StatHistoryPort1Entry 1 }


pm200fr20PerfTelecomOutputClientPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pm200fr20PerfTelecomOutputClientPast24StatHistoryPort1Entry 2 }


pm200fr20PerfTelecomOutputClientPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pm200fr20PerfTelecomOutputClientPast24StatHistoryPort1Entry 3 }


pm200fr20PerfTelecomOutputClientPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pm200fr20PerfTelecomOutputClientPast24StatHistoryPort1Entry 4 }


pm200fr20PerfTelecomOutputClientPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pm200fr20PerfTelecomOutputClientPast24StatHistoryPort1Entry 5 }


pm200fr20PerfTelecomOutputClientPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pm200fr20PerfTelecomOutputClientPast24StatHistoryPort1Entry 6 }


pm200fr20PerfTelecomOutputClientPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pm200fr20PerfTelecomOutputClientPast24StatHistoryPort1Entry 7 }


pm200fr20PerfTelecomOutputClientPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm200fr20PerfTelecomOutputClientPast24StatHistoryPort1Entry 8 }


pm200fr20PerfTelecomOutputClientPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pm200fr20PerfTelecomOutputClientPast24StatHistoryPort1Entry 9 }


pm200fr20PerfTelecomOutputClientPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm200fr20PerfTelecomOutputClientPast24StatHistoryPort1Entry 10 }


pm200fr20PerfTelecomOutputClientPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pm200fr20PerfTelecomOutputClientPast24StatHistoryPort1Entry 11 }


--- *****************************************************
---     Leaf of the telecomLinePostFecCurrent15Stat
--- *****************************************************
--- *********************************************************
---     TABLE for the pm200fr20PerfTelecomLinePostFecCurrent15Stat articles
--- *********************************************************

pm200fr20PerfTelecomLinePostFecCurrent15StatTable OBJECT-TYPE
	SYNTAX  SEQUENCE OF Pm200fr20PerfTelecomLinePostFecCurrent15StatEntry
	MAX-ACCESS not-accessible
	STATUS current
	DESCRIPTION
        "
        List of pm200fr20PerfTelecomLinePostFecCurrent15Stat 
        Article
        "
	::= { pm200fr20MonPerfLine 336 }


pm200fr20PerfTelecomLinePostFecCurrent15StatEntry OBJECT-TYPE
	SYNTAX Pm200fr20PerfTelecomLinePostFecCurrent15StatEntry
	MAX-ACCESS not-accessible
	STATUS current
	DESCRIPTION
        "
        Row definition for the pm200fr20PerfTelecomLinePostFecCurrent15Stat 
        table
        "
	INDEX   { pm200fr20PerfTelecomLinePostFecCurrent15StatIndex }
	::= { pm200fr20PerfTelecomLinePostFecCurrent15StatTable 1 }


Pm200fr20PerfTelecomLinePostFecCurrent15StatEntry ::=
	SEQUENCE {
	pm200fr20PerfTelecomLinePostFecCurrent15StatIndex
		INTEGER,
	pm200fr20PerfTelecomLinePostFecCurrent15StatInvCvPortn
		EkiOnOff,
	pm200fr20PerfTelecomLinePostFecCurrent15StatCvValuePortn
		Unsigned32,
	pm200fr20PerfTelecomLinePostFecCurrent15StatInvEsPortn
		EkiOnOff,
	pm200fr20PerfTelecomLinePostFecCurrent15StatEsValuePortn
		Unsigned32,
	pm200fr20PerfTelecomLinePostFecCurrent15StatInvSesPortn
		EkiOnOff,
	pm200fr20PerfTelecomLinePostFecCurrent15StatSesValuePortn
		Unsigned32,
	pm200fr20PerfTelecomLinePostFecCurrent15StatInvSefsPortn
		EkiOnOff,
	pm200fr20PerfTelecomLinePostFecCurrent15StatSefsValuePortn
		Unsigned32,
	pm200fr20PerfTelecomLinePostFecCurrent15StatInvUasPortn
		EkiOnOff,
	pm200fr20PerfTelecomLinePostFecCurrent15StatUasValuePortn
		Unsigned32
	}


pm200fr20PerfTelecomLinePostFecCurrent15StatIndex OBJECT-TYPE
	SYNTAX  INTEGER(0..128)
	MAX-ACCESS  read-only
	STATUS current
	DESCRIPTION
        "
        Index definition for the pm200fr20PerfTelecomLinePostFecCurrent15Stat 
        table
        "
	::= { pm200fr20PerfTelecomLinePostFecCurrent15StatEntry 1 }


pm200fr20PerfTelecomLinePostFecCurrent15StatInvCvPortn OBJECT-TYPE
	SYNTAX  EkiOnOff
	MAX-ACCESS read-only
	STATUS current
	DESCRIPTION
        "
        Current 15-min EBC counter inv. 
        :This OID indicates that the current 
        15-min Coding Violation counter 
        is invalid
        "
	::= { pm200fr20PerfTelecomLinePostFecCurrent15StatEntry 2 }


pm200fr20PerfTelecomLinePostFecCurrent15StatCvValuePortn OBJECT-TYPE
	SYNTAX  Unsigned32
	MAX-ACCESS read-only
	STATUS current
	DESCRIPTION
        "
        Current 15-min EBC counter :This 
        OID gives the current 15-min Coding 
        Violation counter value
        "
	::= { pm200fr20PerfTelecomLinePostFecCurrent15StatEntry 3 }


pm200fr20PerfTelecomLinePostFecCurrent15StatInvEsPortn OBJECT-TYPE
	SYNTAX  EkiOnOff
	MAX-ACCESS read-only
	STATUS current
	DESCRIPTION
        "
        Current 15-min ES counter inv. 
        :This OID indicates that the current 
        15-min Errored Second counter is 
        invalid
        "
	::= { pm200fr20PerfTelecomLinePostFecCurrent15StatEntry 4 }


pm200fr20PerfTelecomLinePostFecCurrent15StatEsValuePortn OBJECT-TYPE
	SYNTAX  Unsigned32
	MAX-ACCESS read-only
	STATUS current
	DESCRIPTION
        "
        Current 15-min ES counter :This 
        OID gives the current 15-min Errored 
        Second counter value
        "
	::= { pm200fr20PerfTelecomLinePostFecCurrent15StatEntry 5 }


pm200fr20PerfTelecomLinePostFecCurrent15StatInvSesPortn OBJECT-TYPE
	SYNTAX  EkiOnOff
	MAX-ACCESS read-only
	STATUS current
	DESCRIPTION
        "
        Current 15-min SES counter inv. 
        :This OID indicates that the current 
        15-min severely Errored Second
         counter is invalid
        "
	::= { pm200fr20PerfTelecomLinePostFecCurrent15StatEntry 6 }


pm200fr20PerfTelecomLinePostFecCurrent15StatSesValuePortn OBJECT-TYPE
	SYNTAX  Unsigned32
	MAX-ACCESS read-only
	STATUS current
	DESCRIPTION
        "
        Current 15-min SES counter :This 
        OID gives the current 15-min severely 
        Errored Second counter value
        "
	::= { pm200fr20PerfTelecomLinePostFecCurrent15StatEntry 7 }


pm200fr20PerfTelecomLinePostFecCurrent15StatInvSefsPortn OBJECT-TYPE
	SYNTAX  EkiOnOff
	MAX-ACCESS read-only
	STATUS current
	DESCRIPTION
        "
        Current 15-min SEFS counter inv. 
        :This OID indicates that the current 
        15-min severely Errored Framing 
        Second counter is invalid
        "
	::= { pm200fr20PerfTelecomLinePostFecCurrent15StatEntry 8 }


pm200fr20PerfTelecomLinePostFecCurrent15StatSefsValuePortn OBJECT-TYPE
	SYNTAX  Unsigned32
	MAX-ACCESS read-only
	STATUS current
	DESCRIPTION
        "
        Current 15-min SEFS counter :This 
        OID gives the current 15-min severely 
        Errored Framing Second counter
         value
        "
	::= { pm200fr20PerfTelecomLinePostFecCurrent15StatEntry 9 }


pm200fr20PerfTelecomLinePostFecCurrent15StatInvUasPortn OBJECT-TYPE
	SYNTAX  EkiOnOff
	MAX-ACCESS read-only
	STATUS current
	DESCRIPTION
        "
        Current 15-min UAS counter inv. 
        :This OID indicates that the current 
        15-min UnAvailable Second counter 
        is invalid
        "
	::= { pm200fr20PerfTelecomLinePostFecCurrent15StatEntry 10 }


pm200fr20PerfTelecomLinePostFecCurrent15StatUasValuePortn OBJECT-TYPE
	SYNTAX  Unsigned32
	MAX-ACCESS read-only
	STATUS current
	DESCRIPTION
        "
        Current 15-min UAS counter :This 
        OID gives the current 15-min UnAvailable 
        Second counter value
        "
	::= { pm200fr20PerfTelecomLinePostFecCurrent15StatEntry 11 }


--- *****************************************************
---     Leaf of the telecomLinePostFecPast15Stat
--- *****************************************************
--- *********************************************************
---     TABLE for the pm200fr20PerfTelecomLinePostFecPast15StatHistory articles
--- *********************************************************

pm200fr20PerfTelecomLinePostFecPast15StatHistoryPort1Table OBJECT-TYPE
	SYNTAX  SEQUENCE OF Pm200fr20PerfTelecomLinePostFecPast15StatHistoryPort1Entry
	MAX-ACCESS not-accessible
	STATUS current
	DESCRIPTION
        "
        List of pm200fr20PerfTelecomLinePostFecPast15StatHistory 
        Article
        "
	::= { pm200fr20MonPerfLine 337 }


pm200fr20PerfTelecomLinePostFecPast15StatHistoryPort1Entry OBJECT-TYPE
	SYNTAX Pm200fr20PerfTelecomLinePostFecPast15StatHistoryPort1Entry
	MAX-ACCESS not-accessible
	STATUS current
	DESCRIPTION
        "
        Row definition for the pm200fr20PerfTelecomLinePostFecPast15StatHistory 
        table
        "
	INDEX   { pm200fr20PerfTelecomLinePostFecPast15StatHistoryPort1Index }
	::= { pm200fr20PerfTelecomLinePostFecPast15StatHistoryPort1Table 1 }


Pm200fr20PerfTelecomLinePostFecPast15StatHistoryPort1Entry ::=
	SEQUENCE {
	pm200fr20PerfTelecomLinePostFecPast15StatHistoryPort1Index
		INTEGER,
	pm200fr20PerfTelecomLinePostFecPast15StatHistoryInvCvPort1
		EkiOnOff,
	pm200fr20PerfTelecomLinePostFecPast15StatHistoryCvValuePort1
		Unsigned32,
	pm200fr20PerfTelecomLinePostFecPast15StatHistoryInvEsPort1
		EkiOnOff,
	pm200fr20PerfTelecomLinePostFecPast15StatHistoryEsValuePort1
		Unsigned32,
	pm200fr20PerfTelecomLinePostFecPast15StatHistoryInvSesPort1
		EkiOnOff,
	pm200fr20PerfTelecomLinePostFecPast15StatHistorySesValuePort1
		Unsigned32,
	pm200fr20PerfTelecomLinePostFecPast15StatHistoryInvSefsPort1
		EkiOnOff,
	pm200fr20PerfTelecomLinePostFecPast15StatHistorySefsValuePort1
		Unsigned32,
	pm200fr20PerfTelecomLinePostFecPast15StatHistoryInvUasPort1
		EkiOnOff,
	pm200fr20PerfTelecomLinePostFecPast15StatHistoryUasValuePort1
		Unsigned32
	}


pm200fr20PerfTelecomLinePostFecPast15StatHistoryPort1Index OBJECT-TYPE
	SYNTAX  INTEGER(0..128)
	MAX-ACCESS  read-only
	STATUS current
	DESCRIPTION
        "
        Index definition for the pm200fr20PerfTelecomLinePostFecPast15StatHistory 
        table
        "
	::= { pm200fr20PerfTelecomLinePostFecPast15StatHistoryPort1Entry 1 }


pm200fr20PerfTelecomLinePostFecPast15StatHistoryInvCvPort1 OBJECT-TYPE
	SYNTAX  EkiOnOff
	MAX-ACCESS read-only
	STATUS current
	DESCRIPTION
        "
        Previous 15-min EBC counter inv. 
        :This OID indicates that the previous 
        15-min Coding Violation counter 
        is invalid
        "
	::= { pm200fr20PerfTelecomLinePostFecPast15StatHistoryPort1Entry 2 }


pm200fr20PerfTelecomLinePostFecPast15StatHistoryCvValuePort1 OBJECT-TYPE
	SYNTAX  Unsigned32
	MAX-ACCESS read-only
	STATUS current
	DESCRIPTION
        "
        Previous 15-min EBC counter :This 
        OID gives the previous 15-min Coding 
        Violation counter value
        "
	::= { pm200fr20PerfTelecomLinePostFecPast15StatHistoryPort1Entry 3 }


pm200fr20PerfTelecomLinePostFecPast15StatHistoryInvEsPort1 OBJECT-TYPE
	SYNTAX  EkiOnOff
	MAX-ACCESS read-only
	STATUS current
	DESCRIPTION
        "
        Previous 15-min ES counter inv. 
        :This OID indicates that the previous 
        15-min Errored Second counter is 
        invalid
        "
	::= { pm200fr20PerfTelecomLinePostFecPast15StatHistoryPort1Entry 4 }


pm200fr20PerfTelecomLinePostFecPast15StatHistoryEsValuePort1 OBJECT-TYPE
	SYNTAX  Unsigned32
	MAX-ACCESS read-only
	STATUS current
	DESCRIPTION
        "
        Previous 15-min ES counter :This 
        OID gives the previous 15-min Errored 
        Second counter value
        "
	::= { pm200fr20PerfTelecomLinePostFecPast15StatHistoryPort1Entry 5 }


pm200fr20PerfTelecomLinePostFecPast15StatHistoryInvSesPort1 OBJECT-TYPE
	SYNTAX  EkiOnOff
	MAX-ACCESS read-only
	STATUS current
	DESCRIPTION
        "
        Previous 15-min SES counter inv. 
        :This OID indicates that the previous 
        15-min severely Errored Second
         counter is invalid
        "
	::= { pm200fr20PerfTelecomLinePostFecPast15StatHistoryPort1Entry 6 }


pm200fr20PerfTelecomLinePostFecPast15StatHistorySesValuePort1 OBJECT-TYPE
	SYNTAX  Unsigned32
	MAX-ACCESS read-only
	STATUS current
	DESCRIPTION
        "
        Previous 15-min SES counter :This 
        OID gives the previous 15-min severely 
        Errored Second counter value
        "
	::= { pm200fr20PerfTelecomLinePostFecPast15StatHistoryPort1Entry 7 }


pm200fr20PerfTelecomLinePostFecPast15StatHistoryInvSefsPort1 OBJECT-TYPE
	SYNTAX  EkiOnOff
	MAX-ACCESS read-only
	STATUS current
	DESCRIPTION
        "
        Previous 15-min SEFS counter inv. 
        :This OID indicates that the previous 
        15-min severely Errored Framing 
        Second counter is invalid
        "
	::= { pm200fr20PerfTelecomLinePostFecPast15StatHistoryPort1Entry 8 }


pm200fr20PerfTelecomLinePostFecPast15StatHistorySefsValuePort1 OBJECT-TYPE
	SYNTAX  Unsigned32
	MAX-ACCESS read-only
	STATUS current
	DESCRIPTION
        "
        Previous 15-min SEFS counter :This 
        OID gives the previous 15-min severely 
        Errored Framing Second counter
         value
        "
	::= { pm200fr20PerfTelecomLinePostFecPast15StatHistoryPort1Entry 9 }


pm200fr20PerfTelecomLinePostFecPast15StatHistoryInvUasPort1 OBJECT-TYPE
	SYNTAX  EkiOnOff
	MAX-ACCESS read-only
	STATUS current
	DESCRIPTION
        "
        Previous 15-min UAS counter inv. 
        :This OID indicates that the previous 
        15-min UnAvailable Second counter 
        is invalid
        "
	::= { pm200fr20PerfTelecomLinePostFecPast15StatHistoryPort1Entry 10 }


pm200fr20PerfTelecomLinePostFecPast15StatHistoryUasValuePort1 OBJECT-TYPE
	SYNTAX  Unsigned32
	MAX-ACCESS read-only
	STATUS current
	DESCRIPTION
        "
        Previous 15-min UAS counter :This 
        OID gives the previous 15-min UnAvailable 
        Second counter value
        "
	::= { pm200fr20PerfTelecomLinePostFecPast15StatHistoryPort1Entry 11 }


--- *****************************************************
---     Leaf of the telecomLinePostFecCurrent24Stat
--- *****************************************************
--- *********************************************************
---     TABLE for the pm200fr20PerfTelecomLinePostFecCurrent24Stat articles
--- *********************************************************

pm200fr20PerfTelecomLinePostFecCurrent24StatTable OBJECT-TYPE
	SYNTAX  SEQUENCE OF Pm200fr20PerfTelecomLinePostFecCurrent24StatEntry
	MAX-ACCESS not-accessible
	STATUS current
	DESCRIPTION
        "
        List of pm200fr20PerfTelecomLinePostFecCurrent24Stat 
        Article
        "
	::= { pm200fr20MonPerfLine 338 }


pm200fr20PerfTelecomLinePostFecCurrent24StatEntry OBJECT-TYPE
	SYNTAX Pm200fr20PerfTelecomLinePostFecCurrent24StatEntry
	MAX-ACCESS not-accessible
	STATUS current
	DESCRIPTION
        "
        Row definition for the pm200fr20PerfTelecomLinePostFecCurrent24Stat 
        table
        "
	INDEX   { pm200fr20PerfTelecomLinePostFecCurrent24StatIndex }
	::= { pm200fr20PerfTelecomLinePostFecCurrent24StatTable 1 }


Pm200fr20PerfTelecomLinePostFecCurrent24StatEntry ::=
	SEQUENCE {
	pm200fr20PerfTelecomLinePostFecCurrent24StatIndex
		INTEGER,
	pm200fr20PerfTelecomLinePostFecCurrent24StatInvCvPortn
		EkiOnOff,
	pm200fr20PerfTelecomLinePostFecCurrent24StatCvValuePortn
		Unsigned32,
	pm200fr20PerfTelecomLinePostFecCurrent24StatInvEsPortn
		EkiOnOff,
	pm200fr20PerfTelecomLinePostFecCurrent24StatEsValuePortn
		Unsigned32,
	pm200fr20PerfTelecomLinePostFecCurrent24StatInvSesPortn
		EkiOnOff,
	pm200fr20PerfTelecomLinePostFecCurrent24StatSesValuePortn
		Unsigned32,
	pm200fr20PerfTelecomLinePostFecCurrent24StatInvSefsPortn
		EkiOnOff,
	pm200fr20PerfTelecomLinePostFecCurrent24StatSefsValuePortn
		Unsigned32,
	pm200fr20PerfTelecomLinePostFecCurrent24StatInvUasPortn
		EkiOnOff,
	pm200fr20PerfTelecomLinePostFecCurrent24StatUasValuePortn
		Unsigned32
	}


pm200fr20PerfTelecomLinePostFecCurrent24StatIndex OBJECT-TYPE
	SYNTAX  INTEGER(0..128)
	MAX-ACCESS  read-only
	STATUS current
	DESCRIPTION
        "
        Index definition for the pm200fr20PerfTelecomLinePostFecCurrent24Stat 
        table
        "
	::= { pm200fr20PerfTelecomLinePostFecCurrent24StatEntry 1 }


pm200fr20PerfTelecomLinePostFecCurrent24StatInvCvPortn OBJECT-TYPE
	SYNTAX  EkiOnOff
	MAX-ACCESS read-only
	STATUS current
	DESCRIPTION
        "
        Current 24-hours EBC counter inv. 
        :This OID indicates that the current 
        24-hours Coding Violation counter 
        is invalid
        "
	::= { pm200fr20PerfTelecomLinePostFecCurrent24StatEntry 2 }


pm200fr20PerfTelecomLinePostFecCurrent24StatCvValuePortn OBJECT-TYPE
	SYNTAX  Unsigned32
	MAX-ACCESS read-only
	STATUS current
	DESCRIPTION
        "
        Current 24-hours EBC counter :This 
        OID gives the current 24-hours
         Coding Violation counter value
        "
	::= { pm200fr20PerfTelecomLinePostFecCurrent24StatEntry 3 }


pm200fr20PerfTelecomLinePostFecCurrent24StatInvEsPortn OBJECT-TYPE
	SYNTAX  EkiOnOff
	MAX-ACCESS read-only
	STATUS current
	DESCRIPTION
        "
        Current 24-hours ES counter inv. 
        :This OID indicates that the current 
        24-hours Errored Second counter 
        is invalid
        "
	::= { pm200fr20PerfTelecomLinePostFecCurrent24StatEntry 4 }


pm200fr20PerfTelecomLinePostFecCurrent24StatEsValuePortn OBJECT-TYPE
	SYNTAX  Unsigned32
	MAX-ACCESS read-only
	STATUS current
	DESCRIPTION
        "
        Current 24-hours ES counter :This 
        OID gives the current 24-hours
         Errored Second counter value
        "
	::= { pm200fr20PerfTelecomLinePostFecCurrent24StatEntry 5 }


pm200fr20PerfTelecomLinePostFecCurrent24StatInvSesPortn OBJECT-TYPE
	SYNTAX  EkiOnOff
	MAX-ACCESS read-only
	STATUS current
	DESCRIPTION
        "
        Current 24-hours SES counter inv. 
        :This OID indicates that the current 
        24-hours severely Errored Second 
        counter is invalid
        "
	::= { pm200fr20PerfTelecomLinePostFecCurrent24StatEntry 6 }


pm200fr20PerfTelecomLinePostFecCurrent24StatSesValuePortn OBJECT-TYPE
	SYNTAX  Unsigned32
	MAX-ACCESS read-only
	STATUS current
	DESCRIPTION
        "
        Current 24-hours SES counter :This 
        OID gives the current 24-hours
         severely Errored Second counter 
        value
        "
	::= { pm200fr20PerfTelecomLinePostFecCurrent24StatEntry 7 }


pm200fr20PerfTelecomLinePostFecCurrent24StatInvSefsPortn OBJECT-TYPE
	SYNTAX  EkiOnOff
	MAX-ACCESS read-only
	STATUS current
	DESCRIPTION
        "
        Current 24-hours SEFS counter
         inv. :This OID indicates that
         the current 24-hours severely
         Errored Framing Second counter 
        is invalid
        "
	::= { pm200fr20PerfTelecomLinePostFecCurrent24StatEntry 8 }


pm200fr20PerfTelecomLinePostFecCurrent24StatSefsValuePortn OBJECT-TYPE
	SYNTAX  Unsigned32
	MAX-ACCESS read-only
	STATUS current
	DESCRIPTION
        "
        Current 24-hours SEFS counter
         :This OID gives the current 24-hours 
        severely Errored Framing Second 
        counter value
        "
	::= { pm200fr20PerfTelecomLinePostFecCurrent24StatEntry 9 }


pm200fr20PerfTelecomLinePostFecCurrent24StatInvUasPortn OBJECT-TYPE
	SYNTAX  EkiOnOff
	MAX-ACCESS read-only
	STATUS current
	DESCRIPTION
        "
        Current 24-hours UAS counter inv. 
        :This OID indicates that the current 
        24-hours UnAvailable Second counter 
        is invalid
        "
	::= { pm200fr20PerfTelecomLinePostFecCurrent24StatEntry 10 }


pm200fr20PerfTelecomLinePostFecCurrent24StatUasValuePortn OBJECT-TYPE
	SYNTAX  Unsigned32
	MAX-ACCESS read-only
	STATUS current
	DESCRIPTION
        "
        Current 24-hours UAS counter :This 
        OID gives the current 24-hours
         UnAvailable Second counter value
        "
	::= { pm200fr20PerfTelecomLinePostFecCurrent24StatEntry 11 }


--- *****************************************************
---     Leaf of the telecomLinePostFecPast24Stat
--- *****************************************************
--- *********************************************************
---     TABLE for the pm200fr20PerfTelecomLinePostFecPast24StatHistory articles
--- *********************************************************

pm200fr20PerfTelecomLinePostFecPast24StatHistoryPort1Table OBJECT-TYPE
	SYNTAX  SEQUENCE OF Pm200fr20PerfTelecomLinePostFecPast24StatHistoryPort1Entry
	MAX-ACCESS not-accessible
	STATUS current
	DESCRIPTION
        "
        List of pm200fr20PerfTelecomLinePostFecPast24StatHistory 
        Article
        "
	::= { pm200fr20MonPerfLine 339 }


pm200fr20PerfTelecomLinePostFecPast24StatHistoryPort1Entry OBJECT-TYPE
	SYNTAX Pm200fr20PerfTelecomLinePostFecPast24StatHistoryPort1Entry
	MAX-ACCESS not-accessible
	STATUS current
	DESCRIPTION
        "
        Row definition for the pm200fr20PerfTelecomLinePostFecPast24StatHistory 
        table
        "
	INDEX   { pm200fr20PerfTelecomLinePostFecPast24StatHistoryPort1Index }
	::= { pm200fr20PerfTelecomLinePostFecPast24StatHistoryPort1Table 1 }


Pm200fr20PerfTelecomLinePostFecPast24StatHistoryPort1Entry ::=
	SEQUENCE {
	pm200fr20PerfTelecomLinePostFecPast24StatHistoryPort1Index
		INTEGER,
	pm200fr20PerfTelecomLinePostFecPast24StatHistoryInvCvPort1
		EkiOnOff,
	pm200fr20PerfTelecomLinePostFecPast24StatHistoryCvValuePort1
		Unsigned32,
	pm200fr20PerfTelecomLinePostFecPast24StatHistoryInvEsPort1
		EkiOnOff,
	pm200fr20PerfTelecomLinePostFecPast24StatHistoryEsValuePort1
		Unsigned32,
	pm200fr20PerfTelecomLinePostFecPast24StatHistoryInvSesPort1
		EkiOnOff,
	pm200fr20PerfTelecomLinePostFecPast24StatHistorySesValuePort1
		Unsigned32,
	pm200fr20PerfTelecomLinePostFecPast24StatHistoryInvSefsPort1
		EkiOnOff,
	pm200fr20PerfTelecomLinePostFecPast24StatHistorySefsValuePort1
		Unsigned32,
	pm200fr20PerfTelecomLinePostFecPast24StatHistoryInvUasPort1
		EkiOnOff,
	pm200fr20PerfTelecomLinePostFecPast24StatHistoryUasValuePort1
		Unsigned32
	}


pm200fr20PerfTelecomLinePostFecPast24StatHistoryPort1Index OBJECT-TYPE
	SYNTAX  INTEGER(0..128)
	MAX-ACCESS  read-only
	STATUS current
	DESCRIPTION
        "
        Index definition for the pm200fr20PerfTelecomLinePostFecPast24StatHistory 
        table
        "
	::= { pm200fr20PerfTelecomLinePostFecPast24StatHistoryPort1Entry 1 }


pm200fr20PerfTelecomLinePostFecPast24StatHistoryInvCvPort1 OBJECT-TYPE
	SYNTAX  EkiOnOff
	MAX-ACCESS read-only
	STATUS current
	DESCRIPTION
        "
        Previous 24-hours EBC counter
         inv. :This OID indicates that
         the previous 24-hours Coding Violation 
        counter is invalid
        "
	::= { pm200fr20PerfTelecomLinePostFecPast24StatHistoryPort1Entry 2 }


pm200fr20PerfTelecomLinePostFecPast24StatHistoryCvValuePort1 OBJECT-TYPE
	SYNTAX  Unsigned32
	MAX-ACCESS read-only
	STATUS current
	DESCRIPTION
        "
        Previous 24-hours EBC counter
         :This OID gives the previous 24-hours 
        Coding Violation counter value
        "
	::= { pm200fr20PerfTelecomLinePostFecPast24StatHistoryPort1Entry 3 }


pm200fr20PerfTelecomLinePostFecPast24StatHistoryInvEsPort1 OBJECT-TYPE
	SYNTAX  EkiOnOff
	MAX-ACCESS read-only
	STATUS current
	DESCRIPTION
        "
        Previous 24-hours ES counter inv. 
        :This OID indicates that the previous 
        24-hours Errored Second counter 
        is invalid
        "
	::= { pm200fr20PerfTelecomLinePostFecPast24StatHistoryPort1Entry 4 }


pm200fr20PerfTelecomLinePostFecPast24StatHistoryEsValuePort1 OBJECT-TYPE
	SYNTAX  Unsigned32
	MAX-ACCESS read-only
	STATUS current
	DESCRIPTION
        "
        Previous 24-hours ES counter :This 
        OID gives the previous 24-hours 
        Errored Second counter value
        "
	::= { pm200fr20PerfTelecomLinePostFecPast24StatHistoryPort1Entry 5 }


pm200fr20PerfTelecomLinePostFecPast24StatHistoryInvSesPort1 OBJECT-TYPE
	SYNTAX  EkiOnOff
	MAX-ACCESS read-only
	STATUS current
	DESCRIPTION
        "
        Previous 24-hours SES counter
         inv. :This OID indicates that
         the previous 24-hours severely 
        Errored Second counter is invalid
        "
	::= { pm200fr20PerfTelecomLinePostFecPast24StatHistoryPort1Entry 6 }


pm200fr20PerfTelecomLinePostFecPast24StatHistorySesValuePort1 OBJECT-TYPE
	SYNTAX  Unsigned32
	MAX-ACCESS read-only
	STATUS current
	DESCRIPTION
        "
        Previous 24-hours SES counter
         :This OID gives the previous 24-hours 
        severely Errored Second counter 
        value
        "
	::= { pm200fr20PerfTelecomLinePostFecPast24StatHistoryPort1Entry 7 }


pm200fr20PerfTelecomLinePostFecPast24StatHistoryInvSefsPort1 OBJECT-TYPE
	SYNTAX  EkiOnOff
	MAX-ACCESS read-only
	STATUS current
	DESCRIPTION
        "
        Previous 24-hours SEFS counter 
        inv. :This OID indicates that the 
        previous 24-hours severely Errored 
        Framing Second counter is invalid
        "
	::= { pm200fr20PerfTelecomLinePostFecPast24StatHistoryPort1Entry 8 }


pm200fr20PerfTelecomLinePostFecPast24StatHistorySefsValuePort1 OBJECT-TYPE
	SYNTAX  Unsigned32
	MAX-ACCESS read-only
	STATUS current
	DESCRIPTION
        "
        Previous 24-hours SEFS counter 
        :This OID gives the previous 24-hours 
        severely Errored Framing Second 
        counter value
        "
	::= { pm200fr20PerfTelecomLinePostFecPast24StatHistoryPort1Entry 9 }


pm200fr20PerfTelecomLinePostFecPast24StatHistoryInvUasPort1 OBJECT-TYPE
	SYNTAX  EkiOnOff
	MAX-ACCESS read-only
	STATUS current
	DESCRIPTION
        "
        Previous 24-hours UAS counter
         inv. :This OID indicates that
         the previous 24-hours UnAvailable 
        Second counter is invalid
        "
	::= { pm200fr20PerfTelecomLinePostFecPast24StatHistoryPort1Entry 10 }


pm200fr20PerfTelecomLinePostFecPast24StatHistoryUasValuePort1 OBJECT-TYPE
	SYNTAX  Unsigned32
	MAX-ACCESS read-only
	STATUS current
	DESCRIPTION
        "
        Previous 24-hours UAS counter
         :This OID gives the previous 24-hours 
        UnAvailable Second counter value
        "
	::= { pm200fr20PerfTelecomLinePostFecPast24StatHistoryPort1Entry 11 }


--- *****************************************************
---     Leaf of the telecomBerLinePreFecCurrent15Stat
--- *****************************************************
--- *********************************************************
---     TABLE for the pm200fr20PerfTelecomBerLinePreFecCurrent15Stat articles
--- *********************************************************

pm200fr20PerfTelecomBerLinePreFecCurrent15StatTable OBJECT-TYPE
	SYNTAX  SEQUENCE OF Pm200fr20PerfTelecomBerLinePreFecCurrent15StatEntry
	MAX-ACCESS not-accessible
	STATUS current
	DESCRIPTION
        "
        List of pm200fr20PerfTelecomBerLinePreFecCurrent15Stat 
        Article
        "
	::= { pm200fr20MonPerfLine 352 }


pm200fr20PerfTelecomBerLinePreFecCurrent15StatEntry OBJECT-TYPE
	SYNTAX Pm200fr20PerfTelecomBerLinePreFecCurrent15StatEntry
	MAX-ACCESS not-accessible
	STATUS current
	DESCRIPTION
        "
        Row definition for the pm200fr20PerfTelecomBerLinePreFecCurrent15Stat 
        table
        "
	INDEX   { pm200fr20PerfTelecomBerLinePreFecCurrent15StatIndex }
	::= { pm200fr20PerfTelecomBerLinePreFecCurrent15StatTable 1 }


Pm200fr20PerfTelecomBerLinePreFecCurrent15StatEntry ::=
	SEQUENCE {
	pm200fr20PerfTelecomBerLinePreFecCurrent15StatIndex
		INTEGER,
	pm200fr20PerfTelecomBerLinePreFecCurrent15StatInvBerPortn
		EkiOnOff,
	pm200fr20PerfTelecomBerLinePreFecCurrent15StatBerValuePortn
		Unsigned32,
	pm200fr20PerfTelecomBerLinePreFecCurrent15StatInvMinBerPortn
		EkiOnOff,
	pm200fr20PerfTelecomBerLinePreFecCurrent15StatMinBerValuePortn
		Unsigned32,
	pm200fr20PerfTelecomBerLinePreFecCurrent15StatInvMaxBerPortn
		EkiOnOff,
	pm200fr20PerfTelecomBerLinePreFecCurrent15StatMaxBerValuePortn
		Unsigned32
	}


pm200fr20PerfTelecomBerLinePreFecCurrent15StatIndex OBJECT-TYPE
	SYNTAX  INTEGER(0..128)
	MAX-ACCESS  read-only
	STATUS current
	DESCRIPTION
        "
        Index definition for the pm200fr20PerfTelecomBerLinePreFecCurrent15Stat 
        table
        "
	::= { pm200fr20PerfTelecomBerLinePreFecCurrent15StatEntry 1 }


pm200fr20PerfTelecomBerLinePreFecCurrent15StatInvBerPortn OBJECT-TYPE
	SYNTAX  EkiOnOff
	MAX-ACCESS read-only
	STATUS current
	DESCRIPTION
        "
        Current 15-min BER counter inv. 
        :This OID indicates that the current 
        15-min Coding Violation counter 
        is invalid
        "
	::= { pm200fr20PerfTelecomBerLinePreFecCurrent15StatEntry 2 }


pm200fr20PerfTelecomBerLinePreFecCurrent15StatBerValuePortn OBJECT-TYPE
	SYNTAX  Unsigned32
	MAX-ACCESS read-only
	STATUS current
	DESCRIPTION
        "
        Current 15-min BER counter :This 
        OID gives the current 15-min Coding 
        Violation counter value
        "
	::= { pm200fr20PerfTelecomBerLinePreFecCurrent15StatEntry 3 }


pm200fr20PerfTelecomBerLinePreFecCurrent15StatInvMinBerPortn OBJECT-TYPE
	SYNTAX  EkiOnOff
	MAX-ACCESS read-only
	STATUS current
	DESCRIPTION
        "
        Current 15-min MinBER counter
         inv. :This OID indicates that
         the current 15-min Errored Second 
        counter is invalid
        "
	::= { pm200fr20PerfTelecomBerLinePreFecCurrent15StatEntry 4 }


pm200fr20PerfTelecomBerLinePreFecCurrent15StatMinBerValuePortn OBJECT-TYPE
	SYNTAX  Unsigned32
	MAX-ACCESS read-only
	STATUS current
	DESCRIPTION
        "
        Current 15-min MinBER counter
         :This OID gives the current 15-min 
        Errored Second counter value
        "
	::= { pm200fr20PerfTelecomBerLinePreFecCurrent15StatEntry 5 }


pm200fr20PerfTelecomBerLinePreFecCurrent15StatInvMaxBerPortn OBJECT-TYPE
	SYNTAX  EkiOnOff
	MAX-ACCESS read-only
	STATUS current
	DESCRIPTION
        "
        Current 15-min MaxBER counter
         inv. :This OID indicates that
         the current 15-min severely Errored 
        Second counter is invalid
        "
	::= { pm200fr20PerfTelecomBerLinePreFecCurrent15StatEntry 6 }


pm200fr20PerfTelecomBerLinePreFecCurrent15StatMaxBerValuePortn OBJECT-TYPE
	SYNTAX  Unsigned32
	MAX-ACCESS read-only
	STATUS current
	DESCRIPTION
        "
        Current 15-min MaxBER counter
         :This OID gives the current 15-min 
        severely Errored Second counter 
        value
        "
	::= { pm200fr20PerfTelecomBerLinePreFecCurrent15StatEntry 7 }


--- *****************************************************
---     Leaf of the telecomBerLinePreFecPast15Stat
--- *****************************************************
--- *********************************************************
---     TABLE for the pm200fr20PerfTelecomBerLinePreFecPast15StatHistory articles
--- *********************************************************

pm200fr20PerfTelecomBerLinePreFecPast15StatHistoryPort1Table OBJECT-TYPE
	SYNTAX  SEQUENCE OF Pm200fr20PerfTelecomBerLinePreFecPast15StatHistoryPort1Entry
	MAX-ACCESS not-accessible
	STATUS current
	DESCRIPTION
        "
        List of pm200fr20PerfTelecomBerLinePreFecPast15StatHistory 
        Article
        "
	::= { pm200fr20MonPerfLine 353 }


pm200fr20PerfTelecomBerLinePreFecPast15StatHistoryPort1Entry OBJECT-TYPE
	SYNTAX Pm200fr20PerfTelecomBerLinePreFecPast15StatHistoryPort1Entry
	MAX-ACCESS not-accessible
	STATUS current
	DESCRIPTION
        "
        Row definition for the pm200fr20PerfTelecomBerLinePreFecPast15StatHistory 
        table
        "
	INDEX   { pm200fr20PerfTelecomBerLinePreFecPast15StatHistoryPort1Index }
	::= { pm200fr20PerfTelecomBerLinePreFecPast15StatHistoryPort1Table 1 }


Pm200fr20PerfTelecomBerLinePreFecPast15StatHistoryPort1Entry ::=
	SEQUENCE {
	pm200fr20PerfTelecomBerLinePreFecPast15StatHistoryPort1Index
		INTEGER,
	pm200fr20PerfTelecomBerLinePreFecPast15StatHistoryInvBerPort1
		EkiOnOff,
	pm200fr20PerfTelecomBerLinePreFecPast15StatHistoryBerValuePort1
		Unsigned32,
	pm200fr20PerfTelecomBerLinePreFecPast15StatHistoryInvMinBerPort1
		EkiOnOff,
	pm200fr20PerfTelecomBerLinePreFecPast15StatHistoryMinBerValuePort1
		Unsigned32,
	pm200fr20PerfTelecomBerLinePreFecPast15StatHistoryInvMaxBerPort1
		EkiOnOff,
	pm200fr20PerfTelecomBerLinePreFecPast15StatHistoryMaxBerValuePort1
		Unsigned32
	}


pm200fr20PerfTelecomBerLinePreFecPast15StatHistoryPort1Index OBJECT-TYPE
	SYNTAX  INTEGER(0..128)
	MAX-ACCESS  read-only
	STATUS current
	DESCRIPTION
        "
        Index definition for the pm200fr20PerfTelecomBerLinePreFecPast15StatHistory 
        table
        "
	::= { pm200fr20PerfTelecomBerLinePreFecPast15StatHistoryPort1Entry 1 }


pm200fr20PerfTelecomBerLinePreFecPast15StatHistoryInvBerPort1 OBJECT-TYPE
	SYNTAX  EkiOnOff
	MAX-ACCESS read-only
	STATUS current
	DESCRIPTION
        "
        Previous 15-min BER counter inv. 
        :This OID indicates that the previous 
        15-min Coding Violation counter 
        is invalid
        "
	::= { pm200fr20PerfTelecomBerLinePreFecPast15StatHistoryPort1Entry 2 }


pm200fr20PerfTelecomBerLinePreFecPast15StatHistoryBerValuePort1 OBJECT-TYPE
	SYNTAX  Unsigned32
	MAX-ACCESS read-only
	STATUS current
	DESCRIPTION
        "
        Previous 15-min BER counter :This 
        OID gives the previous 15-min Coding 
        Violation counter value
        "
	::= { pm200fr20PerfTelecomBerLinePreFecPast15StatHistoryPort1Entry 3 }


pm200fr20PerfTelecomBerLinePreFecPast15StatHistoryInvMinBerPort1 OBJECT-TYPE
	SYNTAX  EkiOnOff
	MAX-ACCESS read-only
	STATUS current
	DESCRIPTION
        "
        Previous 15-min MinBER counter 
        inv. :This OID indicates that the 
        previous 15-min Errored Second
         counter is invalid
        "
	::= { pm200fr20PerfTelecomBerLinePreFecPast15StatHistoryPort1Entry 4 }


pm200fr20PerfTelecomBerLinePreFecPast15StatHistoryMinBerValuePort1 OBJECT-TYPE
	SYNTAX  Unsigned32
	MAX-ACCESS read-only
	STATUS current
	DESCRIPTION
        "
        Previous 15-min MinBER counter 
        :This OID gives the previous 15-min 
        Errored Second counter value
        "
	::= { pm200fr20PerfTelecomBerLinePreFecPast15StatHistoryPort1Entry 5 }


pm200fr20PerfTelecomBerLinePreFecPast15StatHistoryInvMaxBerPort1 OBJECT-TYPE
	SYNTAX  EkiOnOff
	MAX-ACCESS read-only
	STATUS current
	DESCRIPTION
        "
        Previous 15-min MaxBER counter 
        inv. :This OID indicates that the 
        previous 15-min severely Errored 
        Second counter is invalid
        "
	::= { pm200fr20PerfTelecomBerLinePreFecPast15StatHistoryPort1Entry 6 }


pm200fr20PerfTelecomBerLinePreFecPast15StatHistoryMaxBerValuePort1 OBJECT-TYPE
	SYNTAX  Unsigned32
	MAX-ACCESS read-only
	STATUS current
	DESCRIPTION
        "
        Previous 15-min MaxBER counter 
        :This OID gives the previous 15-min 
        severely Errored Second counter 
        value
        "
	::= { pm200fr20PerfTelecomBerLinePreFecPast15StatHistoryPort1Entry 7 }


--- *****************************************************
---     Leaf of the telecomBerLinePreFecCurrent24Stat
--- *****************************************************
--- *********************************************************
---     TABLE for the pm200fr20PerfTelecomBerLinePreFecCurrent24Stat articles
--- *********************************************************

pm200fr20PerfTelecomBerLinePreFecCurrent24StatTable OBJECT-TYPE
	SYNTAX  SEQUENCE OF Pm200fr20PerfTelecomBerLinePreFecCurrent24StatEntry
	MAX-ACCESS not-accessible
	STATUS current
	DESCRIPTION
        "
        List of pm200fr20PerfTelecomBerLinePreFecCurrent24Stat 
        Article
        "
	::= { pm200fr20MonPerfLine 354 }


pm200fr20PerfTelecomBerLinePreFecCurrent24StatEntry OBJECT-TYPE
	SYNTAX Pm200fr20PerfTelecomBerLinePreFecCurrent24StatEntry
	MAX-ACCESS not-accessible
	STATUS current
	DESCRIPTION
        "
        Row definition for the pm200fr20PerfTelecomBerLinePreFecCurrent24Stat 
        table
        "
	INDEX   { pm200fr20PerfTelecomBerLinePreFecCurrent24StatIndex }
	::= { pm200fr20PerfTelecomBerLinePreFecCurrent24StatTable 1 }


Pm200fr20PerfTelecomBerLinePreFecCurrent24StatEntry ::=
	SEQUENCE {
	pm200fr20PerfTelecomBerLinePreFecCurrent24StatIndex
		INTEGER,
	pm200fr20PerfTelecomBerLinePreFecCurrent24StatInvBerPortn
		EkiOnOff,
	pm200fr20PerfTelecomBerLinePreFecCurrent24StatBerValuePortn
		Unsigned32,
	pm200fr20PerfTelecomBerLinePreFecCurrent24StatInvMinBerPortn
		EkiOnOff,
	pm200fr20PerfTelecomBerLinePreFecCurrent24StatMinBerValuePortn
		Unsigned32,
	pm200fr20PerfTelecomBerLinePreFecCurrent24StatInvMaxBerPortn
		EkiOnOff,
	pm200fr20PerfTelecomBerLinePreFecCurrent24StatMaxBerValuePortn
		Unsigned32
	}


pm200fr20PerfTelecomBerLinePreFecCurrent24StatIndex OBJECT-TYPE
	SYNTAX  INTEGER(0..128)
	MAX-ACCESS  read-only
	STATUS current
	DESCRIPTION
        "
        Index definition for the pm200fr20PerfTelecomBerLinePreFecCurrent24Stat 
        table
        "
	::= { pm200fr20PerfTelecomBerLinePreFecCurrent24StatEntry 1 }


pm200fr20PerfTelecomBerLinePreFecCurrent24StatInvBerPortn OBJECT-TYPE
	SYNTAX  EkiOnOff
	MAX-ACCESS read-only
	STATUS current
	DESCRIPTION
        "
        Current 24-hours BER counter inv. 
        :This OID indicates that the current 
        24-hours Coding Violation counter 
        is invalid
        "
	::= { pm200fr20PerfTelecomBerLinePreFecCurrent24StatEntry 2 }


pm200fr20PerfTelecomBerLinePreFecCurrent24StatBerValuePortn OBJECT-TYPE
	SYNTAX  Unsigned32
	MAX-ACCESS read-only
	STATUS current
	DESCRIPTION
        "
        Current 24-hours BER counter :This 
        OID gives the current 24-hours
         Coding Violation counter value
        "
	::= { pm200fr20PerfTelecomBerLinePreFecCurrent24StatEntry 3 }


pm200fr20PerfTelecomBerLinePreFecCurrent24StatInvMinBerPortn OBJECT-TYPE
	SYNTAX  EkiOnOff
	MAX-ACCESS read-only
	STATUS current
	DESCRIPTION
        "
        Current 24-hoursMinBER counter 
        inv. :This OID indicates that the 
        current 24-hours Errored Second 
        counter is invalid
        "
	::= { pm200fr20PerfTelecomBerLinePreFecCurrent24StatEntry 4 }


pm200fr20PerfTelecomBerLinePreFecCurrent24StatMinBerValuePortn OBJECT-TYPE
	SYNTAX  Unsigned32
	MAX-ACCESS read-only
	STATUS current
	DESCRIPTION
        "
        Current 24-hours MinBER counter 
        :This OID gives the current 24-hours 
        Errored Second counter value
        "
	::= { pm200fr20PerfTelecomBerLinePreFecCurrent24StatEntry 5 }


pm200fr20PerfTelecomBerLinePreFecCurrent24StatInvMaxBerPortn OBJECT-TYPE
	SYNTAX  EkiOnOff
	MAX-ACCESS read-only
	STATUS current
	DESCRIPTION
        "
        Current 24-hours MaxBER counter 
        inv. :This OID indicates that the 
        current 24-hours severely Errored 
        Second counter is invalid
        "
	::= { pm200fr20PerfTelecomBerLinePreFecCurrent24StatEntry 6 }


pm200fr20PerfTelecomBerLinePreFecCurrent24StatMaxBerValuePortn OBJECT-TYPE
	SYNTAX  Unsigned32
	MAX-ACCESS read-only
	STATUS current
	DESCRIPTION
        "
        Current 24-hours MaxBER counter 
        :This OID gives the current 24-hours 
        severely Errored Second counter 
        value
        "
	::= { pm200fr20PerfTelecomBerLinePreFecCurrent24StatEntry 7 }


--- *****************************************************
---     Leaf of the telecomBerLinePreFecPast24Stat
--- *****************************************************
--- *********************************************************
---     TABLE for the pm200fr20PerfTelecomBerLinePreFecPast24StatHistory articles
--- *********************************************************

pm200fr20PerfTelecomBerLinePreFecPast24StatHistoryPort1Table OBJECT-TYPE
	SYNTAX  SEQUENCE OF Pm200fr20PerfTelecomBerLinePreFecPast24StatHistoryPort1Entry
	MAX-ACCESS not-accessible
	STATUS current
	DESCRIPTION
        "
        List of pm200fr20PerfTelecomBerLinePreFecPast24StatHistory 
        Article
        "
	::= { pm200fr20MonPerfLine 355 }


pm200fr20PerfTelecomBerLinePreFecPast24StatHistoryPort1Entry OBJECT-TYPE
	SYNTAX Pm200fr20PerfTelecomBerLinePreFecPast24StatHistoryPort1Entry
	MAX-ACCESS not-accessible
	STATUS current
	DESCRIPTION
        "
        Row definition for the pm200fr20PerfTelecomBerLinePreFecPast24StatHistory 
        table
        "
	INDEX   { pm200fr20PerfTelecomBerLinePreFecPast24StatHistoryPort1Index }
	::= { pm200fr20PerfTelecomBerLinePreFecPast24StatHistoryPort1Table 1 }


Pm200fr20PerfTelecomBerLinePreFecPast24StatHistoryPort1Entry ::=
	SEQUENCE {
	pm200fr20PerfTelecomBerLinePreFecPast24StatHistoryPort1Index
		INTEGER,
	pm200fr20PerfTelecomBerLinePreFecPast24StatHistoryInvBerPort1
		EkiOnOff,
	pm200fr20PerfTelecomBerLinePreFecPast24StatHistoryBerValuePort1
		Unsigned32,
	pm200fr20PerfTelecomBerLinePreFecPast24StatHistoryInvMinBerPort1
		EkiOnOff,
	pm200fr20PerfTelecomBerLinePreFecPast24StatHistoryMinBerValuePort1
		Unsigned32,
	pm200fr20PerfTelecomBerLinePreFecPast24StatHistoryInvMaxBerPort1
		EkiOnOff,
	pm200fr20PerfTelecomBerLinePreFecPast24StatHistoryMaxBerValuePort1
		Unsigned32
	}


pm200fr20PerfTelecomBerLinePreFecPast24StatHistoryPort1Index OBJECT-TYPE
	SYNTAX  INTEGER(0..128)
	MAX-ACCESS  read-only
	STATUS current
	DESCRIPTION
        "
        Index definition for the pm200fr20PerfTelecomBerLinePreFecPast24StatHistory 
        table
        "
	::= { pm200fr20PerfTelecomBerLinePreFecPast24StatHistoryPort1Entry 1 }


pm200fr20PerfTelecomBerLinePreFecPast24StatHistoryInvBerPort1 OBJECT-TYPE
	SYNTAX  EkiOnOff
	MAX-ACCESS read-only
	STATUS current
	DESCRIPTION
        "
        Previous 24-hours BER counter
         inv. :This OID indicates that
         the previous 24-hours Coding Violation 
        counter is invalid
        "
	::= { pm200fr20PerfTelecomBerLinePreFecPast24StatHistoryPort1Entry 2 }


pm200fr20PerfTelecomBerLinePreFecPast24StatHistoryBerValuePort1 OBJECT-TYPE
	SYNTAX  Unsigned32
	MAX-ACCESS read-only
	STATUS current
	DESCRIPTION
        "
        Previous 24-hours BER counter
         :This OID gives the previous 24-hours 
        Coding Violation counter value
        "
	::= { pm200fr20PerfTelecomBerLinePreFecPast24StatHistoryPort1Entry 3 }


pm200fr20PerfTelecomBerLinePreFecPast24StatHistoryInvMinBerPort1 OBJECT-TYPE
	SYNTAX  EkiOnOff
	MAX-ACCESS read-only
	STATUS current
	DESCRIPTION
        "
        Previous 24-hours MinBER counter 
        inv. :This OID indicates that the 
        previous 24-hours Errored Second 
        counter is invalid
        "
	::= { pm200fr20PerfTelecomBerLinePreFecPast24StatHistoryPort1Entry 4 }


pm200fr20PerfTelecomBerLinePreFecPast24StatHistoryMinBerValuePort1 OBJECT-TYPE
	SYNTAX  Unsigned32
	MAX-ACCESS read-only
	STATUS current
	DESCRIPTION
        "
        Previous 24-hours MinBER counter 
        :This OID gives the previous 24-hours 
        Errored Second counter value
        "
	::= { pm200fr20PerfTelecomBerLinePreFecPast24StatHistoryPort1Entry 5 }


pm200fr20PerfTelecomBerLinePreFecPast24StatHistoryInvMaxBerPort1 OBJECT-TYPE
	SYNTAX  EkiOnOff
	MAX-ACCESS read-only
	STATUS current
	DESCRIPTION
        "
        Previous 24-hours MaxBER counter 
        inv. :This OID indicates that the 
        previous 24-hours severely Errored 
        Second counter is invalid
        "
	::= { pm200fr20PerfTelecomBerLinePreFecPast24StatHistoryPort1Entry 6 }


pm200fr20PerfTelecomBerLinePreFecPast24StatHistoryMaxBerValuePort1 OBJECT-TYPE
	SYNTAX  Unsigned32
	MAX-ACCESS read-only
	STATUS current
	DESCRIPTION
        "
        Previous 24-hours MaxBER counter 
        :This OID gives the previous 24-hours 
        severely Errored Second counter 
        value
        "
	::= { pm200fr20PerfTelecomBerLinePreFecPast24StatHistoryPort1Entry 7 }


--- *****************************************************
---     Leaf of the datacomClientCurrent15Stat
--- *****************************************************
--- *********************************************************
---     TABLE for the pm200fr20PerfDatacomClientCurrent15Stat articles
--- *********************************************************

pm200fr20PerfDatacomClientCurrent15StatTable OBJECT-TYPE
	SYNTAX  SEQUENCE OF Pm200fr20PerfDatacomClientCurrent15StatEntry
	MAX-ACCESS not-accessible
	STATUS current
	DESCRIPTION
        "
        List of pm200fr20PerfDatacomClientCurrent15Stat 
        Article
        "
	::= { pm200fr20MonPerfClient 848 }


pm200fr20PerfDatacomClientCurrent15StatEntry OBJECT-TYPE
	SYNTAX Pm200fr20PerfDatacomClientCurrent15StatEntry
	MAX-ACCESS not-accessible
	STATUS current
	DESCRIPTION
        "
        Row definition for the pm200fr20PerfDatacomClientCurrent15Stat 
        table
        "
	INDEX   { pm200fr20PerfDatacomClientCurrent15StatIndex }
	::= { pm200fr20PerfDatacomClientCurrent15StatTable 1 }


Pm200fr20PerfDatacomClientCurrent15StatEntry ::=
	SEQUENCE {
	pm200fr20PerfDatacomClientCurrent15StatIndex
		INTEGER,
	pm200fr20perfdatacomclientCurrent15StatOutPacketCountInvPortn
		EkiOnOff,
	pm200fr20perfdatacomclientCurrent15StatOutPacketCountPortn
		Counter64,
	pm200fr20perfdatacomclientCurrent15StatOutCrcCountInvPortn
		EkiOnOff,
	pm200fr20perfdatacomclientCurrent15StatOutCrcCountPortn
		Counter64,
	pm200fr20perfdatacomclientCurrent15StatInPacketCountInvPortn
		EkiOnOff,
	pm200fr20perfdatacomclientCurrent15StatInPacketCountPortn
		Counter64,
	pm200fr20perfdatacomclientCurrent15StatInCrcCountInvPortn
		EkiOnOff,
	pm200fr20perfdatacomclientCurrent15StatInCrcCountPortn
		Counter64
	}


pm200fr20PerfDatacomClientCurrent15StatIndex OBJECT-TYPE
	SYNTAX  INTEGER(0..128)
	MAX-ACCESS  read-only
	STATUS current
	DESCRIPTION
        "
        Index definition for the pm200fr20PerfDatacomClientCurrent15Stat 
        table
        "
	::= { pm200fr20PerfDatacomClientCurrent15StatEntry 1 }


pm200fr20perfdatacomclientCurrent15StatOutPacketCountInvPortn OBJECT-TYPE
	SYNTAX  EkiOnOff
	MAX-ACCESS read-only
	STATUS current
	DESCRIPTION
        "
        Client Current 15-min Output Packet 
        counter inv. :This OID indicates 
        that the current 15-min Output
         Packets counter is invalid
        "
	::= { pm200fr20PerfDatacomClientCurrent15StatEntry 30 }


pm200fr20perfdatacomclientCurrent15StatOutPacketCountPortn OBJECT-TYPE
	SYNTAX  Counter64
	MAX-ACCESS read-only
	STATUS current
	DESCRIPTION
        "
        Client Current 15-min Output Packet 
        counter :This OID gives the current 
        15-min Output Packets counter value
        "
	::= { pm200fr20PerfDatacomClientCurrent15StatEntry 31 }


pm200fr20perfdatacomclientCurrent15StatOutCrcCountInvPortn OBJECT-TYPE
	SYNTAX  EkiOnOff
	MAX-ACCESS read-only
	STATUS current
	DESCRIPTION
        "
        Client Current 15-min Output CRC 
        counter inv. :This OID indicates 
        that the current 15-min Output
         CRC counter is invalid
        "
	::= { pm200fr20PerfDatacomClientCurrent15StatEntry 28 }


pm200fr20perfdatacomclientCurrent15StatOutCrcCountPortn OBJECT-TYPE
	SYNTAX  Counter64
	MAX-ACCESS read-only
	STATUS current
	DESCRIPTION
        "
        Client Current 15-min Output CRC 
        counter :This OID gives the current 
        15-min Output CRC counter value
        "
	::= { pm200fr20PerfDatacomClientCurrent15StatEntry 29 }


pm200fr20perfdatacomclientCurrent15StatInPacketCountInvPortn OBJECT-TYPE
	SYNTAX  EkiOnOff
	MAX-ACCESS read-only
	STATUS current
	DESCRIPTION
        "
        Client Current 15-min Input Packet 
        counter inv. :This OID indicates 
        that the current 15-min Input Packet 
        counter is invalid
        "
	::= { pm200fr20PerfDatacomClientCurrent15StatEntry 6 }


pm200fr20perfdatacomclientCurrent15StatInPacketCountPortn OBJECT-TYPE
	SYNTAX  Counter64
	MAX-ACCESS read-only
	STATUS current
	DESCRIPTION
        "
        Client Current 15-min Input Packet 
        counter :This OID gives the current 
        15-min Input Packet counter value
        "
	::= { pm200fr20PerfDatacomClientCurrent15StatEntry 7 }


pm200fr20perfdatacomclientCurrent15StatInCrcCountInvPortn OBJECT-TYPE
	SYNTAX  EkiOnOff
	MAX-ACCESS read-only
	STATUS current
	DESCRIPTION
        "
        Client Current 15-min Input CRC 
        counter inv. :This OID indicates 
        that the current 15-min Input CRC 
        counter is invalid
        "
	::= { pm200fr20PerfDatacomClientCurrent15StatEntry 4 }


pm200fr20perfdatacomclientCurrent15StatInCrcCountPortn OBJECT-TYPE
	SYNTAX  Counter64
	MAX-ACCESS read-only
	STATUS current
	DESCRIPTION
        "
        Client Current 15-min Input CRC 
        counter :This OID gives the current 
        15-min Input CRC counter value
        "
	::= { pm200fr20PerfDatacomClientCurrent15StatEntry 5 }


--- *****************************************************
---     Leaf of the datacomClientPast15Stat
--- *****************************************************
--- *********************************************************
---     TABLE for the pm200fr20PerfDatacomClientPast15StatHistory articles
--- *********************************************************

pm200fr20PerfDatacomClientPast15StatHistoryPort1Table OBJECT-TYPE
	SYNTAX  SEQUENCE OF Pm200fr20PerfDatacomClientPast15StatHistoryPort1Entry
	MAX-ACCESS not-accessible
	STATUS current
	DESCRIPTION
        "
        List of pm200fr20PerfDatacomClientPast15StatHistory 
        Article
        "
	::= { pm200fr20MonPerfClient 880 }


pm200fr20PerfDatacomClientPast15StatHistoryPort1Entry OBJECT-TYPE
	SYNTAX Pm200fr20PerfDatacomClientPast15StatHistoryPort1Entry
	MAX-ACCESS not-accessible
	STATUS current
	DESCRIPTION
        "
        Row definition for the pm200fr20PerfDatacomClientPast15StatHistory 
        table
        "
	INDEX   { pm200fr20PerfDatacomClientPast15StatHistoryPort1Index }
	::= { pm200fr20PerfDatacomClientPast15StatHistoryPort1Table 1 }


Pm200fr20PerfDatacomClientPast15StatHistoryPort1Entry ::=
	SEQUENCE {
	pm200fr20PerfDatacomClientPast15StatHistoryPort1Index
		INTEGER,
	pm200fr20perfdatacomclientPast15StatOutPacketCountInvPort1
		EkiOnOff,
	pm200fr20perfdatacomclientPast15StatOutPacketCountPort1
		Counter64,
	pm200fr20perfdatacomclientPast15StatOutCrcCountInvPort1
		EkiOnOff,
	pm200fr20perfdatacomclientPast15StatOutCrcCountPort1
		Counter64,
	pm200fr20perfdatacomclientPast15StatInPacketCountInvPort1
		EkiOnOff,
	pm200fr20perfdatacomclientPast15StatInPacketCountPort1
		Counter64,
	pm200fr20perfdatacomclientPast15StatInCrcCountInvPort1
		EkiOnOff,
	pm200fr20perfdatacomclientPast15StatInCrcCountPort1
		Counter64
	}


pm200fr20PerfDatacomClientPast15StatHistoryPort1Index OBJECT-TYPE
	SYNTAX  INTEGER(0..128)
	MAX-ACCESS  read-only
	STATUS current
	DESCRIPTION
        "
        Index definition for the pm200fr20PerfDatacomClientPast15StatHistory 
        table
        "
	::= { pm200fr20PerfDatacomClientPast15StatHistoryPort1Entry 1 }


pm200fr20perfdatacomclientPast15StatOutPacketCountInvPort1 OBJECT-TYPE
	SYNTAX  EkiOnOff
	MAX-ACCESS read-only
	STATUS current
	DESCRIPTION
        "
        Client Past 15-min Output Packet 
        counter inv. :This OID indicates 
        that the past 15-min Output Packets 
        counter is invalid
        "
	::= { pm200fr20PerfDatacomClientPast15StatHistoryPort1Entry 30 }


pm200fr20perfdatacomclientPast15StatOutPacketCountPort1 OBJECT-TYPE
	SYNTAX  Counter64
	MAX-ACCESS read-only
	STATUS current
	DESCRIPTION
        "
        Client Past 15-min Output Packet 
        counter :This OID gives the past 
        15-min Output Packets counter value
        "
	::= { pm200fr20PerfDatacomClientPast15StatHistoryPort1Entry 31 }


pm200fr20perfdatacomclientPast15StatOutCrcCountInvPort1 OBJECT-TYPE
	SYNTAX  EkiOnOff
	MAX-ACCESS read-only
	STATUS current
	DESCRIPTION
        "
        Client Past 15-min Output CRC
         counter inv. :This OID indicates 
        that the past 15-min Output CRC 
        counter is invalid
        "
	::= { pm200fr20PerfDatacomClientPast15StatHistoryPort1Entry 28 }


pm200fr20perfdatacomclientPast15StatOutCrcCountPort1 OBJECT-TYPE
	SYNTAX  Counter64
	MAX-ACCESS read-only
	STATUS current
	DESCRIPTION
        "
        Client Past 15-min Output CRC
         counter :This OID gives the past 
        15-min Output CRC counter value
        "
	::= { pm200fr20PerfDatacomClientPast15StatHistoryPort1Entry 29 }


pm200fr20perfdatacomclientPast15StatInPacketCountInvPort1 OBJECT-TYPE
	SYNTAX  EkiOnOff
	MAX-ACCESS read-only
	STATUS current
	DESCRIPTION
        "
        Client Past 15-min Input Packet 
        counter inv. :This OID indicates 
        that the past 15-min Input Packet 
        counter is invalid
        "
	::= { pm200fr20PerfDatacomClientPast15StatHistoryPort1Entry 6 }


pm200fr20perfdatacomclientPast15StatInPacketCountPort1 OBJECT-TYPE
	SYNTAX  Counter64
	MAX-ACCESS read-only
	STATUS current
	DESCRIPTION
        "
        Client Past 15-min Input Packet 
        counter :This OID gives the past 
        15-min Input Packet counter value
        "
	::= { pm200fr20PerfDatacomClientPast15StatHistoryPort1Entry 7 }


pm200fr20perfdatacomclientPast15StatInCrcCountInvPort1 OBJECT-TYPE
	SYNTAX  EkiOnOff
	MAX-ACCESS read-only
	STATUS current
	DESCRIPTION
        "
        Client Past 15-min Input CRC counter 
        inv. :This OID indicates that the 
        past 15-min Input CRC counter is 
        invalid
        "
	::= { pm200fr20PerfDatacomClientPast15StatHistoryPort1Entry 4 }


pm200fr20perfdatacomclientPast15StatInCrcCountPort1 OBJECT-TYPE
	SYNTAX  Counter64
	MAX-ACCESS read-only
	STATUS current
	DESCRIPTION
        "
        Client Past 15-min Input CRC counter 
        :This OID gives the past 15-min 
        Input CRC counter value
        "
	::= { pm200fr20PerfDatacomClientPast15StatHistoryPort1Entry 5 }


--- *****************************************************
---     Leaf of the datacomClientCurrent24Stat
--- *****************************************************
--- *********************************************************
---     TABLE for the pm200fr20PerfDatacomClientCurrent24Stat articles
--- *********************************************************

pm200fr20PerfDatacomClientCurrent24StatTable OBJECT-TYPE
	SYNTAX  SEQUENCE OF Pm200fr20PerfDatacomClientCurrent24StatEntry
	MAX-ACCESS not-accessible
	STATUS current
	DESCRIPTION
        "
        List of pm200fr20PerfDatacomClientCurrent24Stat 
        Article
        "
	::= { pm200fr20MonPerfClient 912 }


pm200fr20PerfDatacomClientCurrent24StatEntry OBJECT-TYPE
	SYNTAX Pm200fr20PerfDatacomClientCurrent24StatEntry
	MAX-ACCESS not-accessible
	STATUS current
	DESCRIPTION
        "
        Row definition for the pm200fr20PerfDatacomClientCurrent24Stat 
        table
        "
	INDEX   { pm200fr20PerfDatacomClientCurrent24StatIndex }
	::= { pm200fr20PerfDatacomClientCurrent24StatTable 1 }


Pm200fr20PerfDatacomClientCurrent24StatEntry ::=
	SEQUENCE {
	pm200fr20PerfDatacomClientCurrent24StatIndex
		INTEGER,
	pm200fr20perfdatacomclientCurrent24StatOutPacketCountInvPortn
		EkiOnOff,
	pm200fr20perfdatacomclientCurrent24StatOutPacketCountPortn
		Counter64,
	pm200fr20perfdatacomclientCurrent24StatOutCrcCountInvPortn
		EkiOnOff,
	pm200fr20perfdatacomclientCurrent24StatOutCrcCountPortn
		Counter64,
	pm200fr20perfdatacomclientCurrent24StatInPacketCountInvPortn
		EkiOnOff,
	pm200fr20perfdatacomclientCurrent24StatInPacketCountPortn
		Counter64,
	pm200fr20perfdatacomclientCurrent24StatInCrcCountInvPortn
		EkiOnOff,
	pm200fr20perfdatacomclientCurrent24StatInCrcCountPortn
		Counter64
	}


pm200fr20PerfDatacomClientCurrent24StatIndex OBJECT-TYPE
	SYNTAX  INTEGER(0..128)
	MAX-ACCESS  read-only
	STATUS current
	DESCRIPTION
        "
        Index definition for the pm200fr20PerfDatacomClientCurrent24Stat 
        table
        "
	::= { pm200fr20PerfDatacomClientCurrent24StatEntry 1 }


pm200fr20perfdatacomclientCurrent24StatOutPacketCountInvPortn OBJECT-TYPE
	SYNTAX  EkiOnOff
	MAX-ACCESS read-only
	STATUS current
	DESCRIPTION
        "
        Client Current 24-hours Output 
        Packet counter inv. :This OID indicates 
        that the current 24-hours Output 
        Packets counter is invalid
        "
	::= { pm200fr20PerfDatacomClientCurrent24StatEntry 30 }


pm200fr20perfdatacomclientCurrent24StatOutPacketCountPortn OBJECT-TYPE
	SYNTAX  Counter64
	MAX-ACCESS read-only
	STATUS current
	DESCRIPTION
        "
        Client Current 24-hours Output 
        Packet counter :This OID gives
         the current 24-hours Output Packets 
        counter value
        "
	::= { pm200fr20PerfDatacomClientCurrent24StatEntry 31 }


pm200fr20perfdatacomclientCurrent24StatOutCrcCountInvPortn OBJECT-TYPE
	SYNTAX  EkiOnOff
	MAX-ACCESS read-only
	STATUS current
	DESCRIPTION
        "
        Client Current 24-hours Output 
        CRC counter inv. :This OID indicates 
        that the current 24-hours Output 
        CRC counter is invalid
        "
	::= { pm200fr20PerfDatacomClientCurrent24StatEntry 28 }


pm200fr20perfdatacomclientCurrent24StatOutCrcCountPortn OBJECT-TYPE
	SYNTAX  Counter64
	MAX-ACCESS read-only
	STATUS current
	DESCRIPTION
        "
        Client Current 24-hours Output 
        CRC counter :This OID gives the 
        current 24-hours Output CRC counter 
        value
        "
	::= { pm200fr20PerfDatacomClientCurrent24StatEntry 29 }


pm200fr20perfdatacomclientCurrent24StatInPacketCountInvPortn OBJECT-TYPE
	SYNTAX  EkiOnOff
	MAX-ACCESS read-only
	STATUS current
	DESCRIPTION
        "
        Client Current 24-hours Input
         Packet counter inv. :This OID
         indicates that the current 24-hours 
        Input Packet counter is invalid
        "
	::= { pm200fr20PerfDatacomClientCurrent24StatEntry 6 }


pm200fr20perfdatacomclientCurrent24StatInPacketCountPortn OBJECT-TYPE
	SYNTAX  Counter64
	MAX-ACCESS read-only
	STATUS current
	DESCRIPTION
        "
        Client Current 24-hours Input
         Packet counter :This OID gives 
        the current 24-hours Input Packet 
        counter value
        "
	::= { pm200fr20PerfDatacomClientCurrent24StatEntry 7 }


pm200fr20perfdatacomclientCurrent24StatInCrcCountInvPortn OBJECT-TYPE
	SYNTAX  EkiOnOff
	MAX-ACCESS read-only
	STATUS current
	DESCRIPTION
        "
        Client Current 24-hours Input
         CRC counter inv. :This OID indicates 
        that the current 24-hours Input 
        CRC counter is invalid
        "
	::= { pm200fr20PerfDatacomClientCurrent24StatEntry 4 }


pm200fr20perfdatacomclientCurrent24StatInCrcCountPortn OBJECT-TYPE
	SYNTAX  Counter64
	MAX-ACCESS read-only
	STATUS current
	DESCRIPTION
        "
        Client Current 24-hours Input
         CRC counter :This OID gives the 
        current 24-hours Input CRC counter 
        value
        "
	::= { pm200fr20PerfDatacomClientCurrent24StatEntry 5 }


--- *****************************************************
---     Leaf of the datacomClientPast24Stat
--- *****************************************************
--- *********************************************************
---     TABLE for the pm200fr20PerfDatacomClientPast24StatHistory articles
--- *********************************************************

pm200fr20PerfDatacomClientPast24StatHistoryPort1Table OBJECT-TYPE
	SYNTAX  SEQUENCE OF Pm200fr20PerfDatacomClientPast24StatHistoryPort1Entry
	MAX-ACCESS not-accessible
	STATUS current
	DESCRIPTION
        "
        List of pm200fr20PerfDatacomClientPast24StatHistory 
        Article
        "
	::= { pm200fr20MonPerfClient 944 }


pm200fr20PerfDatacomClientPast24StatHistoryPort1Entry OBJECT-TYPE
	SYNTAX Pm200fr20PerfDatacomClientPast24StatHistoryPort1Entry
	MAX-ACCESS not-accessible
	STATUS current
	DESCRIPTION
        "
        Row definition for the pm200fr20PerfDatacomClientPast24StatHistory 
        table
        "
	INDEX   { pm200fr20PerfDatacomClientPast24StatHistoryPort1Index }
	::= { pm200fr20PerfDatacomClientPast24StatHistoryPort1Table 1 }


Pm200fr20PerfDatacomClientPast24StatHistoryPort1Entry ::=
	SEQUENCE {
	pm200fr20PerfDatacomClientPast24StatHistoryPort1Index
		INTEGER,
	pm200fr20perfdatacomclientPast24StatOutPacketCountInvPort1
		EkiOnOff,
	pm200fr20perfdatacomclientPast24StatOutPacketCountPort1
		Counter64,
	pm200fr20perfdatacomclientPast24StatOutCrcCountInvPort1
		EkiOnOff,
	pm200fr20perfdatacomclientPast24StatOutCrcCountPort1
		Counter64,
	pm200fr20perfdatacomclientPast24StatInPacketCountInvPort1
		EkiOnOff,
	pm200fr20perfdatacomclientPast24StatInPacketCountPort1
		Counter64,
	pm200fr20perfdatacomclientPast24StatInCrcCountInvPort1
		EkiOnOff,
	pm200fr20perfdatacomclientPast24StatInCrcCountPort1
		Counter64
	}


pm200fr20PerfDatacomClientPast24StatHistoryPort1Index OBJECT-TYPE
	SYNTAX  INTEGER(0..128)
	MAX-ACCESS  read-only
	STATUS current
	DESCRIPTION
        "
        Index definition for the pm200fr20PerfDatacomClientPast24StatHistory 
        table
        "
	::= { pm200fr20PerfDatacomClientPast24StatHistoryPort1Entry 1 }


pm200fr20perfdatacomclientPast24StatOutPacketCountInvPort1 OBJECT-TYPE
	SYNTAX  EkiOnOff
	MAX-ACCESS read-only
	STATUS current
	DESCRIPTION
        "
        Client Past 24-hours Output Packet 
        counter inv. :This OID indicates 
        that the past 24-hours Output Packets 
        counter is invalid
        "
	::= { pm200fr20PerfDatacomClientPast24StatHistoryPort1Entry 30 }


pm200fr20perfdatacomclientPast24StatOutPacketCountPort1 OBJECT-TYPE
	SYNTAX  Counter64
	MAX-ACCESS read-only
	STATUS current
	DESCRIPTION
        "
        Client Past 24-hours Output Packet 
        counter :This OID gives the past 
        24-hours Output Packets counter 
        value
        "
	::= { pm200fr20PerfDatacomClientPast24StatHistoryPort1Entry 31 }


pm200fr20perfdatacomclientPast24StatOutCrcCountInvPort1 OBJECT-TYPE
	SYNTAX  EkiOnOff
	MAX-ACCESS read-only
	STATUS current
	DESCRIPTION
        "
        Client Past 24-hours Output CRC 
        counter inv. :This OID indicates 
        that the past 24-hours Output CRC 
        counter is invalid
        "
	::= { pm200fr20PerfDatacomClientPast24StatHistoryPort1Entry 28 }


pm200fr20perfdatacomclientPast24StatOutCrcCountPort1 OBJECT-TYPE
	SYNTAX  Counter64
	MAX-ACCESS read-only
	STATUS current
	DESCRIPTION
        "
        Client Past 24-hours Output CRC 
        counter :This OID gives the past 
        24-hours Output CRC counter value
        "
	::= { pm200fr20PerfDatacomClientPast24StatHistoryPort1Entry 29 }


pm200fr20perfdatacomclientPast24StatInPacketCountInvPort1 OBJECT-TYPE
	SYNTAX  EkiOnOff
	MAX-ACCESS read-only
	STATUS current
	DESCRIPTION
        "
        Client Past 24-hours Input Packet 
        counter inv. :This OID indicates 
        that the past 24-hours Input Packet 
        counter is invalid
        "
	::= { pm200fr20PerfDatacomClientPast24StatHistoryPort1Entry 6 }


pm200fr20perfdatacomclientPast24StatInPacketCountPort1 OBJECT-TYPE
	SYNTAX  Counter64
	MAX-ACCESS read-only
	STATUS current
	DESCRIPTION
        "
        Client Past 24-hours Input Packet 
        counter :This OID gives the past 
        24-hours Input Packet counter value
        "
	::= { pm200fr20PerfDatacomClientPast24StatHistoryPort1Entry 7 }


pm200fr20perfdatacomclientPast24StatInCrcCountInvPort1 OBJECT-TYPE
	SYNTAX  EkiOnOff
	MAX-ACCESS read-only
	STATUS current
	DESCRIPTION
        "
        Client Past 24-hours Input CRC 
        counter inv. :This OID indicates 
        that the past 24-hours Input CRC 
        counter is invalid
        "
	::= { pm200fr20PerfDatacomClientPast24StatHistoryPort1Entry 4 }


pm200fr20perfdatacomclientPast24StatInCrcCountPort1 OBJECT-TYPE
	SYNTAX  Counter64
	MAX-ACCESS read-only
	STATUS current
	DESCRIPTION
        "
        Client Past 24-hours Input CRC 
        counter :This OID gives the past 
        24-hours Input CRC counter value
        "
	::= { pm200fr20PerfDatacomClientPast24StatHistoryPort1Entry 5 }



pm200fr20PerfEnable OBJECT-TYPE
	SYNTAX EkiOnOff
	MAX-ACCESS read-write
	STATUS current
	DESCRIPTION
        "
        Perf. Mon. Enable :This OID enables 
        the Performance Monitoring application
        "
	::= { pm200fr20MonPerfSync 257 }


pm200fr20Perf15minSync OBJECT-TYPE
	SYNTAX EkiOnOff
	MAX-ACCESS read-write
	STATUS current
	DESCRIPTION
        "
        Perf. Mon. 15-min sync. :This
         OID must be used in external synchronisation 
        mode only to send a 15-min synchronisation 
        command
        "
	::= { pm200fr20MonPerfSync 259 }


pm200fr20Perf24hSync OBJECT-TYPE
	SYNTAX EkiOnOff
	MAX-ACCESS read-write
	STATUS current
	DESCRIPTION
        "
        Perf. Mon. 24-hours sync. :This 
        OID must be used in external synchronisation 
        mode only to send a 24-hours synchronisation 
        command
        "
	::= { pm200fr20MonPerfSync 260 }


pm200fr20Perf15MinShort OBJECT-TYPE
	SYNTAX EkiOnOff
	MAX-ACCESS read-write
	STATUS current
	DESCRIPTION
        "
        15-min period is short :This OID 
        indicates that the 15-min period 
        lasts less than 890 seconds
        "
	::= { pm200fr20MonPerfTimeStamp 1 }


pm200fr20Perf15MinLong OBJECT-TYPE
	SYNTAX EkiOnOff
	MAX-ACCESS read-write
	STATUS current
	DESCRIPTION
        "
        15-min period is long :This OID 
        indicates that the 15-min period 
        lasts more than 910 seconds
        "
	::= { pm200fr20MonPerfTimeStamp 2 }


pm200fr20Perf24HoursShort OBJECT-TYPE
	SYNTAX Counter32
	MAX-ACCESS read-write
	STATUS current
	DESCRIPTION
        "
        24-hours period is short :This 
        OID indicates that 24-hours period 
        lasts less than 86390 seconds
        "
	::= { pm200fr20MonPerfTimeStamp 5 }


pm200fr20Perf24HoursLong OBJECT-TYPE
	SYNTAX Counter32
	MAX-ACCESS read-write
	STATUS current
	DESCRIPTION
        "
        24-hours period is long :This
         OID indicates that 24-hours period 
        lasts more than 86410 seconds
        "
	::= { pm200fr20MonPerfTimeStamp 6 }


pm200fr20PerfCurrent15MinElapsedTime OBJECT-TYPE
	SYNTAX Counter32
	MAX-ACCESS read-write
	STATUS current
	DESCRIPTION
        "
        Current 15min period Elapsed Time 
         :This OID gives the number of
         seconds elapsed in the current 
        15-minutes period
        "
	::= { pm200fr20MonPerfTimeStamp 7 }


pm200fr20PerfCurrent24HoursElapsedTime OBJECT-TYPE
	SYNTAX Counter32
	MAX-ACCESS read-write
	STATUS current
	DESCRIPTION
        "
        Current 24hours period Elapsed 
        Time :This OID gives the number 
        of seconds elapsed in the current 
        24-hours period
        "
	::= { pm200fr20MonPerfTimeStamp 8 }






--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm200fr20DwlrestartProcess OBJECT IDENTIFIER ::= { pm200fr20DwlOther 0 }




pm200fr20DwlColdRestartProcessed OBJECT-TYPE
	  SYNTAX EkiOnOff
	  MAX-ACCESS read-only
	  STATUS current
	  DESCRIPTION
        "
        Cold Restart :This OID indicates 
        that the module last restart was 
        a Cold RESTART
        "
	  ::= { pm200fr20DwlrestartProcess 2 }



pm200fr20DwlWarmRestartProcessed OBJECT-TYPE
	  SYNTAX EkiOnOff
	  MAX-ACCESS read-only
	  STATUS current
	  DESCRIPTION
        "
        Warm Restart :This OID indicates 
        that the module last restart was 
        a Warm RESTART
        "
	  ::= { pm200fr20DwlrestartProcess 1 }



--- *****************************************************
---     LEAF for the swBanksUsed article
--- *****************************************************
pm200fr20DwlswBanksUsed OBJECT IDENTIFIER ::= { pm200fr20DwlOther 1 }




pm200fr20DwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pm200fr20DwlswBanksUsed 6 }



pm200fr20DwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pm200fr20DwlswBanksUsed 5 }



pm200fr20DwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pm200fr20DwlswBanksUsed 2 }



pm200fr20DwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pm200fr20DwlswBanksUsed 1 }



--- *****************************************************
---     LEAF for the gwBanksUsed article
--- *****************************************************
pm200fr20DwlgwBanksUsed OBJECT IDENTIFIER ::= { pm200fr20DwlOther 2 }




pm200fr20DwlGwBank4Notempty OBJECT-TYPE
	  SYNTAX EkiOnOff
	  MAX-ACCESS read-only
	  STATUS current
	  DESCRIPTION
        "
        GW bank 4 loaded :This OID indicates 
        a gateware is loaded in GW bank 
        4
        "
	  ::= { pm200fr20DwlgwBanksUsed 8 }



pm200fr20DwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pm200fr20DwlgwBanksUsed 7 }



pm200fr20DwlGwBank2Notempty OBJECT-TYPE
	  SYNTAX EkiOnOff
	  MAX-ACCESS read-only
	  STATUS current
	  DESCRIPTION
        "
        GW bank 2 loaded :This OID indicates 
        a gateware is loaded in GW bank 
        2
        "
	  ::= { pm200fr20DwlgwBanksUsed 6 }



pm200fr20DwlGwBank1Notempty OBJECT-TYPE
	  SYNTAX EkiOnOff
	  MAX-ACCESS read-only
	  STATUS current
	  DESCRIPTION
        "
        GW bank 1 loaded :This OID indicates 
        a gateware is loaded in GW bank 
        1  <Help>  This status indicates 
        if the GW bank 1 contains GW package
        "
	  ::= { pm200fr20DwlgwBanksUsed 5 }



pm200fr20DwlGwBank4Used OBJECT-TYPE
	  SYNTAX EkiOnOff
	  MAX-ACCESS read-only
	  STATUS current
	  DESCRIPTION
        "
        GW bank 4 active :This OID indicates 
        the module is working on GW bank 
        4
        "
	  ::= { pm200fr20DwlgwBanksUsed 4 }



pm200fr20DwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pm200fr20DwlgwBanksUsed 3 }



pm200fr20DwlGwBank2Used OBJECT-TYPE
	  SYNTAX EkiOnOff
	  MAX-ACCESS read-only
	  STATUS current
	  DESCRIPTION
        "
        GW bank 2 active :This OID indicates 
        the module is working on GW bank 
        2
        "
	  ::= { pm200fr20DwlgwBanksUsed 2 }



pm200fr20DwlGwBank1Used OBJECT-TYPE
	  SYNTAX EkiOnOff
	  MAX-ACCESS read-only
	  STATUS current
	  DESCRIPTION
        "
        GW bank 1 active :This OID indicates 
        the module is working on GW bank 
        1  <Help>  This status indicates 
        if the GW bank 1 is active or standby
        "
	  ::= { pm200fr20DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm200fr20CfgAccessCAisCsf OBJECT IDENTIFIER ::= { pm200fr20Config 1 }



--- *****************************************************
---     LEAF for the table 0012
--- *****************************************************

pm200fr20CfgClientcaiscsfTable OBJECT-TYPE
	SYNTAX  SEQUENCE OF Pm200fr20CfgClientcaiscsfEntry
	MAX-ACCESS not-accessible
	STATUS current
	DESCRIPTION
        "
        List of  Article
        "
	::= { pm200fr20CfgAccessCAisCsf 1 }


pm200fr20CfgClientcaiscsfEntry OBJECT-TYPE
	SYNTAX Pm200fr20CfgClientcaiscsfEntry
	MAX-ACCESS not-accessible
	STATUS current
	DESCRIPTION
        "
        Row definition for the accessCAisCsf 
        table
        "
	INDEX   { pm200fr20CfgClientcaiscsfIndex }
	::= { pm200fr20CfgClientcaiscsfTable 1 }


Pm200fr20CfgClientcaiscsfEntry ::=
	SEQUENCE {
	pm200fr20CfgClientcaiscsfIndex
		INTEGER,
	pm200fr20CfgReservePortn
		Unsigned32
	}


pm200fr20CfgClientcaiscsfIndex OBJECT-TYPE
	SYNTAX  INTEGER(0..128)
	MAX-ACCESS  read-only
	STATUS current
	DESCRIPTION
        "
        Index definition for the clientcaiscsf 
        table
        "
	::= { pm200fr20CfgClientcaiscsfEntry 1 }


pm200fr20CfgReservePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm200fr20CfgClientcaiscsfEntry 3 }


--- *****************************************************
---     LEAF for the table Group startup
--- *****************************************************

pm200fr20CfgStartup OBJECT IDENTIFIER ::= { pm200fr20Config 2 }



--- *****************************************************
---     LEAF for the table 2110
--- *****************************************************

pm200fr20CfgClientStartupTable OBJECT-TYPE
	SYNTAX  SEQUENCE OF Pm200fr20CfgClientStartupEntry
	MAX-ACCESS not-accessible
	STATUS current
	DESCRIPTION
        "
        List of  Article
        "
	::= { pm200fr20CfgStartup 1 }


pm200fr20CfgClientStartupEntry OBJECT-TYPE
	SYNTAX Pm200fr20CfgClientStartupEntry
	MAX-ACCESS not-accessible
	STATUS current
	DESCRIPTION
        "
        Row definition for the startup 
        table
        "
	INDEX   { pm200fr20CfgClientStartupIndex }
	::= { pm200fr20CfgClientStartupTable 1 }


Pm200fr20CfgClientStartupEntry ::=
	SEQUENCE {
	pm200fr20CfgClientStartupIndex
		INTEGER,
	pm200fr20CfgSystConfPortPortn
		Unsigned32,
	pm200fr20CfgNetConfPortPortn
		Unsigned32,
	pm200fr20CfgOptionsPortPortn
		Unsigned32
	}


pm200fr20CfgClientStartupIndex OBJECT-TYPE
	SYNTAX  INTEGER(0..128)
	MAX-ACCESS  read-only
	STATUS current
	DESCRIPTION
        "
        Index definition for the clientStartup 
        table
        "
	::= { pm200fr20CfgClientStartupEntry 1 }


pm200fr20CfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm200fr20CfgClientStartupEntry 3 }


pm200fr20CfgNetConfPortPortn OBJECT-TYPE
	SYNTAX  Unsigned32 (0..65536)
	MAX-ACCESS read-write
	STATUS current
	DESCRIPTION
        "
        Default Settings on Client Port 
        :This  register configures the
         default initialisation settings 
        on the port.
        "
	::= { pm200fr20CfgClientStartupEntry 4 }


pm200fr20CfgOptionsPortPortn OBJECT-TYPE
	SYNTAX  Unsigned32 (0..65536)
	MAX-ACCESS read-write
	STATUS current
	DESCRIPTION
        "
        Default Options on Client Port 
        :This register configures the default 
        options on the port.
        "
	::= { pm200fr20CfgClientStartupEntry 14 }


--- *****************************************************
---     LEAF for the table 2190
--- *****************************************************

pm200fr20CfgLineStartupTable OBJECT-TYPE
	SYNTAX  SEQUENCE OF Pm200fr20CfgLineStartupEntry
	MAX-ACCESS not-accessible
	STATUS current
	DESCRIPTION
        "
        List of  Article
        "
	::= { pm200fr20CfgStartup 2 }


pm200fr20CfgLineStartupEntry OBJECT-TYPE
	SYNTAX Pm200fr20CfgLineStartupEntry
	MAX-ACCESS not-accessible
	STATUS current
	DESCRIPTION
        "
        Row definition for the startup 
        table
        "
	INDEX   { pm200fr20CfgLineStartupIndex }
	::= { pm200fr20CfgLineStartupTable 1 }


Pm200fr20CfgLineStartupEntry ::=
	SEQUENCE {
	pm200fr20CfgLineStartupIndex
		INTEGER,
	pm200fr20CfgSystConfLinePortn
		Unsigned32,
	pm200fr20CfgOptionsLinePortn
		Unsigned32
	}


pm200fr20CfgLineStartupIndex OBJECT-TYPE
	SYNTAX  INTEGER(0..128)
	MAX-ACCESS  read-only
	STATUS current
	DESCRIPTION
        "
        Index definition for the lineStartup 
        table
        "
	::= { pm200fr20CfgLineStartupEntry 1 }


pm200fr20CfgSystConfLinePortn OBJECT-TYPE
	SYNTAX  Unsigned32 (0..65536)
	MAX-ACCESS read-write
	STATUS current
	DESCRIPTION
        "
        Default Settings on Line :This 
        register configures the default 
        initialisation settings on Line
        "
	::= { pm200fr20CfgLineStartupEntry 3 }


pm200fr20CfgOptionsLinePortn OBJECT-TYPE
	SYNTAX  Unsigned32 (0..65536)
	MAX-ACCESS read-write
	STATUS current
	DESCRIPTION
        "
        Default Options on Line :This
         register configures the default 
        options on the line
        "
	::= { pm200fr20CfgLineStartupEntry 14 }


--- *****************************************************
---     LEAF for the table 21AB
--- *****************************************************

pm200fr20CfgXfpTable OBJECT-TYPE
	SYNTAX  SEQUENCE OF Pm200fr20CfgXfpEntry
	MAX-ACCESS not-accessible
	STATUS current
	DESCRIPTION
        "
        List of  Article
        "
	::= { pm200fr20CfgStartup 3 }


pm200fr20CfgXfpEntry OBJECT-TYPE
	SYNTAX Pm200fr20CfgXfpEntry
	MAX-ACCESS not-accessible
	STATUS current
	DESCRIPTION
        "
        Row definition for the startup 
        table
        "
	INDEX   { pm200fr20CfgXfpIndex }
	::= { pm200fr20CfgXfpTable 1 }


Pm200fr20CfgXfpEntry ::=
	SEQUENCE {
	pm200fr20CfgXfpIndex
		INTEGER,
	pm200fr20CfgSystConfMsaLinePortn
		Unsigned32
	}


pm200fr20CfgXfpIndex OBJECT-TYPE
	SYNTAX  INTEGER(0..128)
	MAX-ACCESS  read-only
	STATUS current
	DESCRIPTION
        "
        Index definition for the xfp table
        "
	::= { pm200fr20CfgXfpEntry 1 }


pm200fr20CfgSystConfMsaLinePortn OBJECT-TYPE
	SYNTAX  Unsigned32 (0..65536)
	MAX-ACCESS read-write
	STATUS current
	DESCRIPTION
        "
        Default settings on MSA :This
         register configures the default 
        initialisation settings on MSA
        "
	::= { pm200fr20CfgXfpEntry 3 }


--- *****************************************************
---     LEAF for the table Group labels
--- *****************************************************

pm200fr20CfgLabels OBJECT IDENTIFIER ::= { pm200fr20Config 3 }



--- *****************************************************
---     LEAF for the table 0003
--- *****************************************************

pm200fr20CfgLabelclientTable OBJECT-TYPE
	SYNTAX  SEQUENCE OF Pm200fr20CfgLabelclientEntry
	MAX-ACCESS not-accessible
	STATUS current
	DESCRIPTION
        "
        List of  Article
        "
	::= { pm200fr20CfgLabels 1 }


pm200fr20CfgLabelclientEntry OBJECT-TYPE
	SYNTAX Pm200fr20CfgLabelclientEntry
	MAX-ACCESS not-accessible
	STATUS current
	DESCRIPTION
        "
        Row definition for the labels
         table
        "
	INDEX   { pm200fr20CfgLabelclientIndex }
	::= { pm200fr20CfgLabelclientTable 1 }


Pm200fr20CfgLabelclientEntry ::=
	SEQUENCE {
	pm200fr20CfgLabelclientIndex
		INTEGER,
	pm200fr20CfgLabelclientPortn
		DisplayString
	}


pm200fr20CfgLabelclientIndex OBJECT-TYPE
	SYNTAX  INTEGER(0..128)
	MAX-ACCESS  read-only
	STATUS current
	DESCRIPTION
        "
        Index definition for the labelclient 
        table
        "
	::= { pm200fr20CfgLabelclientEntry 1 }


pm200fr20CfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm200fr20CfgLabelclientEntry 3 }


--- *****************************************************
---     LEAF for the table 0004
--- *****************************************************

pm200fr20CfgLabellineTable OBJECT-TYPE
	SYNTAX  SEQUENCE OF Pm200fr20CfgLabellineEntry
	MAX-ACCESS not-accessible
	STATUS current
	DESCRIPTION
        "
        List of  Article
        "
	::= { pm200fr20CfgLabels 2 }


pm200fr20CfgLabellineEntry OBJECT-TYPE
	SYNTAX Pm200fr20CfgLabellineEntry
	MAX-ACCESS not-accessible
	STATUS current
	DESCRIPTION
        "
        Row definition for the labels
         table
        "
	INDEX   { pm200fr20CfgLabellineIndex }
	::= { pm200fr20CfgLabellineTable 1 }


Pm200fr20CfgLabellineEntry ::=
	SEQUENCE {
	pm200fr20CfgLabellineIndex
		INTEGER,
	pm200fr20CfgLabellinePortn
		DisplayString
	}


pm200fr20CfgLabellineIndex OBJECT-TYPE
	SYNTAX  INTEGER(0..128)
	MAX-ACCESS  read-only
	STATUS current
	DESCRIPTION
        "
        Index definition for the labelline 
        table
        "
	::= { pm200fr20CfgLabellineEntry 1 }


pm200fr20CfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm200fr20CfgLabellineEntry 3 }


--- *****************************************************
---     LEAF for the table Group startuptlh
--- *****************************************************

pm200fr20CfgStartuptlh OBJECT IDENTIFIER ::= { pm200fr20Config 4 }



--- *****************************************************
---     LEAF for the table 25AB
--- *****************************************************

pm200fr20CfgOtxtlhTable OBJECT-TYPE
	SYNTAX  SEQUENCE OF Pm200fr20CfgOtxtlhEntry
	MAX-ACCESS not-accessible
	STATUS current
	DESCRIPTION
        "
        List of  Article
        "
	::= { pm200fr20CfgStartuptlh 1 }


pm200fr20CfgOtxtlhEntry OBJECT-TYPE
	SYNTAX Pm200fr20CfgOtxtlhEntry
	MAX-ACCESS not-accessible
	STATUS current
	DESCRIPTION
        "
        Row definition for the startuptlh 
        table
        "
	INDEX   { pm200fr20CfgOtxtlhIndex }
	::= { pm200fr20CfgOtxtlhTable 1 }


Pm200fr20CfgOtxtlhEntry ::=
	SEQUENCE {
	pm200fr20CfgOtxtlhIndex
		INTEGER,
	pm200fr20CfgLinePwrLaserPortn
		Unsigned32,
	pm200fr20CfgLineFCurrentPortn
		Unsigned32,
	pm200fr20CfgLineGridCurrentPortn
		Unsigned32,
	pm200fr20CfgFPortn
		Unsigned32,
	pm200fr20CfgRxLineFCurrentPortn
		Unsigned32
	}


pm200fr20CfgOtxtlhIndex OBJECT-TYPE
	SYNTAX  INTEGER(0..128)
	MAX-ACCESS  read-only
	STATUS current
	DESCRIPTION
        "
        Index definition for the otxtlh 
        table
        "
	::= { pm200fr20CfgOtxtlhEntry 1 }


pm200fr20CfgLinePwrLaserPortn OBJECT-TYPE
	SYNTAX  Unsigned32 (0..65536)
	MAX-ACCESS read-write
	STATUS current
	DESCRIPTION
        "
        Defaut Line output Power :This 
        register configures the start-up 
        output power of the Line tranceiver 
         (Unit = dBm)
        "
	::= { pm200fr20CfgOtxtlhEntry 6 }


pm200fr20CfgLineFCurrentPortn OBJECT-TYPE
	SYNTAX  Unsigned32 (0..65536)
	MAX-ACCESS read-write
	STATUS current
	DESCRIPTION
        "
        Default Line transceiver Tx Channel 
        :This register configures the start-up 
        laser channel of the Line Tx transceiver
        "
	::= { pm200fr20CfgOtxtlhEntry 7 }


pm200fr20CfgLineGridCurrentPortn OBJECT-TYPE
	SYNTAX  Unsigned32 (0..65536)
	MAX-ACCESS read-write
	STATUS current
	DESCRIPTION
        "
        Default Line transceiver Grid
         :This register configures the
         start-up laser grid of the Line 
        transceiver
        "
	::= { pm200fr20CfgOtxtlhEntry 8 }


pm200fr20CfgFPortn OBJECT-TYPE
	SYNTAX  Unsigned32 (0..65536)
	MAX-ACCESS read-write
	STATUS current
	DESCRIPTION
        "
        Default Line TRX lowest Freq :This 
        register configures the start-up 
        lowest frequency of the Line transceiver
        "
	::= { pm200fr20CfgOtxtlhEntry 9 }


pm200fr20CfgRxLineFCurrentPortn OBJECT-TYPE
	SYNTAX  Unsigned32 (0..65536)
	MAX-ACCESS read-write
	STATUS current
	DESCRIPTION
        "
        Default Line transceiver Rx Channel 
        :This register configures the start-up 
        laser channel of the Line Rx transceiver
        "
	::= { pm200fr20CfgOtxtlhEntry 10 }


--- *****************************************************
---     LEAF for the table Group other
--- *****************************************************

pm200fr20CfgOther OBJECT IDENTIFIER ::= { pm200fr20Config 5 }



--- *****************************************************
---     LEAF for the table 2300
--- *****************************************************

pm200fr20tablemoduleOther OBJECT IDENTIFIER ::= { pm200fr20CfgOther 1 }



pm200fr20Cfgmode OBJECT-TYPE
	  SYNTAX Unsigned32 (0..65536)
	  MAX-ACCESS read-write
	  STATUS current
	  DESCRIPTION
        "
        Default settings on Module :This 
        register selects the configuration 
        mode of the module
        "
	  ::= { pm200fr20tablemoduleOther 2 }



pm200fr20CfgfanLowSpeedThreshold OBJECT-TYPE
	  SYNTAX Unsigned32 (0..65536)
	  MAX-ACCESS read-write
	  STATUS current
	  DESCRIPTION
        "
        Default settings on Module :This 
        register selects the speed threshold 
        of the fan's
        "
	  ::= { pm200fr20tablemoduleOther 3 }



pm200fr20CfgfanHighSpeedThreshold OBJECT-TYPE
	  SYNTAX Unsigned32 (0..65536)
	  MAX-ACCESS read-write
	  STATUS current
	  DESCRIPTION
        "
        Default settings on Module :This 
        register selects the speed threshold 
        of the fan's
        "
	  ::= { pm200fr20tablemoduleOther 4 }



pm200fr20CfgprotocolMode OBJECT-TYPE
	  SYNTAX Unsigned32 (0..65536)
	  MAX-ACCESS read-write
	  STATUS current
	  DESCRIPTION
        "
        Default settings on Module :This 
        register selects the configuration 
        mode of the module
        "
	  ::= { pm200fr20tablemoduleOther 5 }



--- *****************************************************
---     LEAF for the table Group startuptablefive
--- *****************************************************

pm200fr20CfgStartuptablefive OBJECT IDENTIFIER ::= { pm200fr20Config 6 }



--- *****************************************************
---     LEAF for the table 0005
--- *****************************************************

pm200fr20CfgOtxtlhcapabilitiesTable OBJECT-TYPE
	SYNTAX  SEQUENCE OF Pm200fr20CfgOtxtlhcapabilitiesEntry
	MAX-ACCESS not-accessible
	STATUS current
	DESCRIPTION
        "
        List of  Article
        "
	::= { pm200fr20CfgStartuptablefive 1 }


pm200fr20CfgOtxtlhcapabilitiesEntry OBJECT-TYPE
	SYNTAX Pm200fr20CfgOtxtlhcapabilitiesEntry
	MAX-ACCESS not-accessible
	STATUS current
	DESCRIPTION
        "
        Row definition for the startuptablefive 
        table
        "
	INDEX   { pm200fr20CfgOtxtlhcapabilitiesIndex }
	::= { pm200fr20CfgOtxtlhcapabilitiesTable 1 }


Pm200fr20CfgOtxtlhcapabilitiesEntry ::=
	SEQUENCE {
	pm200fr20CfgOtxtlhcapabilitiesIndex
		INTEGER,
	pm200fr20CfgComponentTypePortn
		Unsigned32,
	pm200fr20CfgMiscellaneousPortn
		Unsigned32,
	pm200fr20CfgFirstChannelPortn
		Unsigned32,
	pm200fr20CfgLastChannelPortn
		Unsigned32,
	pm200fr20CfgGridPortn
		Unsigned32
	}


pm200fr20CfgOtxtlhcapabilitiesIndex OBJECT-TYPE
	SYNTAX  INTEGER(0..128)
	MAX-ACCESS  read-only
	STATUS current
	DESCRIPTION
        "
        Index definition for the otxtlhcapabilities 
        table
        "
	::= { pm200fr20CfgOtxtlhcapabilitiesEntry 1 }


pm200fr20CfgComponentTypePortn OBJECT-TYPE
	SYNTAX  Unsigned32 (0..65536)
	MAX-ACCESS read-only
	STATUS current
	DESCRIPTION
        "
        Component parameters :This OID 
        defines the component parameters
        "
	::= { pm200fr20CfgOtxtlhcapabilitiesEntry 3 }


pm200fr20CfgMiscellaneousPortn OBJECT-TYPE
	SYNTAX  Unsigned32 (0..65536)
	MAX-ACCESS read-only
	STATUS current
	DESCRIPTION
        "
        Miscellaneous default settings 
        :This OID defines the miscellaneous 
        parameters
        "
	::= { pm200fr20CfgOtxtlhcapabilitiesEntry 4 }


pm200fr20CfgFirstChannelPortn OBJECT-TYPE
	SYNTAX  Unsigned32 (0..65536)
	MAX-ACCESS read-only
	STATUS current
	DESCRIPTION
        "
        Number of the first channel of 
        the component :This OID defines 
        the first channel number of the 
        PM
        "
	::= { pm200fr20CfgOtxtlhcapabilitiesEntry 5 }


pm200fr20CfgLastChannelPortn OBJECT-TYPE
	SYNTAX  Unsigned32 (0..65536)
	MAX-ACCESS read-only
	STATUS current
	DESCRIPTION
        "
        Number of the last channel of
         the component :This OID defines 
        the last channel number of the
         PM
        "
	::= { pm200fr20CfgOtxtlhcapabilitiesEntry 6 }


pm200fr20CfgGridPortn OBJECT-TYPE
	SYNTAX  Unsigned32 (0..65536)
	MAX-ACCESS read-only
	STATUS current
	DESCRIPTION
        "
        Grid value of the component :This 
        OID defines the grid of the PM
        "
	::= { pm200fr20CfgOtxtlhcapabilitiesEntry 7 }



pm200fr20CfgWriteConfiguration  OBJECT-TYPE
	SYNTAX EkiOnOff
	MAX-ACCESS read-write
	STATUS current
	DESCRIPTION
	"Write configuration to module:This OID 
	 writes the complete configuration to the module"
	::= { pm200fr20Config 257 }






--- *****************************************************
---     TRAP OBJECTS
--- *****************************************************

pm200fr20trapPortNumber OBJECT-TYPE
	SYNTAX INTEGER(1..64)
	MAX-ACCESS read-only
	STATUS current
	DESCRIPTION
	"Last port which generates a trap"
	::= { pm200fr20traps 2 }

pm200fr20trapLineNumber OBJECT-TYPE
	SYNTAX INTEGER(1..64)
	MAX-ACCESS read-only
	STATUS current
	DESCRIPTION
	"Last Line which generates a trap"
	::= { pm200fr20traps 3 }

pm200fr20trapBoardNumber OBJECT-TYPE
	SYNTAX INTEGER(1..64)
	MAX-ACCESS read-only
	STATUS current
	DESCRIPTION
	"Last module which generates a trap"
	::= { pm200fr20traps 4 }







--- *****************************************************
---     LINE TRAPS
--- *****************************************************

pm200fr20LineTrapNotUrgentGoesOn NOTIFICATION-TYPE
	OBJECTS {pm200fr20AlmLineDdmWarningPortn, pm200fr20trapLineNumber, pm200fr20trapBoardNumber}
	STATUS current
	DESCRIPTION "Not urgent Line default is activated"
	::= { pm200fr20traps 30 }

pm200fr20LineTrapNotUrgentGoesOff NOTIFICATION-TYPE
	OBJECTS {pm200fr20AlmLineDdmWarningPortn, pm200fr20trapLineNumber, pm200fr20trapBoardNumber}
	STATUS current
	DESCRIPTION "Not urgent Line default disappeared"
	::= { pm200fr20traps 31 }

pm200fr20LineTrapUrgentGoesOn NOTIFICATION-TYPE
	OBJECTS {pm200fr20AlmLineDdmAlmPortn, pm200fr20trapLineNumber, pm200fr20trapBoardNumber}
	STATUS current
	DESCRIPTION "Urgent Line default is activated"
	::= { pm200fr20traps 32 }

pm200fr20LineTrapUrgentGoesOff NOTIFICATION-TYPE
	OBJECTS {pm200fr20AlmLineDdmAlmPortn, pm200fr20trapLineNumber, pm200fr20trapBoardNumber}
	STATUS current
	DESCRIPTION "Urgent Line default disappeared"
	::= { pm200fr20traps 33 }

pm200fr20LineTrapCritGoesOn NOTIFICATION-TYPE
	OBJECTS {pm200fr20AlmLineFailPortn , pm200fr20AlmLineHwFailPortn , pm200fr20trapLineNumber, pm200fr20trapBoardNumber}
	STATUS current
	DESCRIPTION "Critical Line default is activated"
	::= { pm200fr20traps 34 }

pm200fr20LineTrapCritGoesOff NOTIFICATION-TYPE
	OBJECTS {pm200fr20AlmLineFailPortn , pm200fr20AlmLineHwFailPortn , pm200fr20trapLineNumber, pm200fr20trapBoardNumber}
	STATUS current
	DESCRIPTION "Critical Line default disappeared"
	::= { pm200fr20traps 35 }






--- *****************************************************
---     CLIENT TRAPS
--- *****************************************************

pm200fr20ClientTrapNotUrgentGoesOn NOTIFICATION-TYPE
	OBJECTS {pm200fr20AlmSfpDdmWarningPortn, pm200fr20trapPortNumber, pm200fr20trapBoardNumber}
	STATUS current
	DESCRIPTION "Not urgent client default is activated"
	::= { pm200fr20traps 40 }

pm200fr20ClientTrapNotUrgentGoesOff NOTIFICATION-TYPE
	OBJECTS {pm200fr20AlmSfpDdmWarningPortn, pm200fr20trapPortNumber, pm200fr20trapBoardNumber}
	STATUS current
	DESCRIPTION "Not urgent client default disappeared"
	::= { pm200fr20traps 41 }

pm200fr20ClientTrapUrgentGoesOn NOTIFICATION-TYPE
	OBJECTS {pm200fr20AlmSfpDdmAlmPortn, pm200fr20trapPortNumber, pm200fr20trapBoardNumber}
	STATUS current
	DESCRIPTION "Urgent client default is activated"
	::= { pm200fr20traps 42 }

pm200fr20ClientTrapUrgentGoesOff NOTIFICATION-TYPE
	OBJECTS {pm200fr20AlmSfpDdmAlmPortn, pm200fr20trapPortNumber, pm200fr20trapBoardNumber}
	STATUS current
	DESCRIPTION "Urgent client default disappeared"
	::= { pm200fr20traps 43 }

pm200fr20ClientTrapCritGoesOn NOTIFICATION-TYPE
	OBJECTS {pm200fr20AlmFailAccPortn, pm200fr20AlmHwFailAccPortn, pm200fr20trapPortNumber, pm200fr20trapBoardNumber}
	STATUS current
	DESCRIPTION "Critical client default is activated"
	::= { pm200fr20traps 44 }

pm200fr20ClientTrapCritGoesOff NOTIFICATION-TYPE
	OBJECTS {pm200fr20AlmFailAccPortn, pm200fr20AlmHwFailAccPortn, pm200fr20trapPortNumber, pm200fr20trapBoardNumber}
	STATUS current
	DESCRIPTION "Critical client default disappeared"
	::= { pm200fr20traps 45 }






--- *****************************************************
---     HW TRAPS
--- *****************************************************

pm200fr20PowerTrapUrgentGoesOn NOTIFICATION-TYPE
	OBJECTS {pm200fr20AlmDefFuseB, pm200fr20AlmDefFuseA , pm200fr20trapBoardNumber}
	STATUS current
	DESCRIPTION "Urgent power supply default is activated"
	::= { pm200fr20traps 50 }

pm200fr20PowerTrapUrgentGoesOff NOTIFICATION-TYPE
	OBJECTS {pm200fr20AlmDefFuseB, pm200fr20AlmDefFuseA , pm200fr20trapBoardNumber}
	STATUS current
	DESCRIPTION "Urgent power supply default disappeared"
	::= { pm200fr20traps 51 }






END
