-- *****************************************************************
-- EKINOPS-Pm10010mr.TXT:  MIB
--
--MIB Part Number:3MI00032AAAD
--MIB Version:02
--
-- Copyright (c) 2016 by Ekinops
-- All rights reserved.
-- 
-- *****************************************************************

EKINOPS-Pm10010mr-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm10010mr MODULE-IDENTITY
        LAST-UPDATED "201606020000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201404100000Z"
	DESCRIPTION
	  "Creation for PM 100G METRO"
	REVISION "201410140000Z"
	DESCRIPTION
	  "OSNR help completion"
	REVISION "201501230000Z"
	DESCRIPTION
	  "Labels cosmetic updates"
	REVISION "201510210000Z"
	DESCRIPTION
	  "Add F0 objet"
	REVISION "201605200000Z"
	DESCRIPTION
	  "New AlarmType – synthesisAlarm (12)"
	REVISION "201606020000Z"
	DESCRIPTION
	  "Capabilities objects of Table 5"
        ::= { ekinops 63 }



--- *****************************************************
---     LEAF LEVEL 2
--- *****************************************************


pm10010mralarms OBJECT IDENTIFIER ::= { modulePm10010mr 2 }	
pm10010mrAlmOther OBJECT IDENTIFIER ::= { pm10010mralarms 1 }
pm10010mrAlmOtherNurg OBJECT IDENTIFIER ::= { pm10010mrAlmOther 1 }
pm10010mrAlmOtherUrg OBJECT IDENTIFIER ::= { pm10010mrAlmOther 2 }
pm10010mrAlmOtherCrit OBJECT IDENTIFIER ::= { pm10010mrAlmOther 3 }

pm10010mrAlmClient OBJECT IDENTIFIER ::= { pm10010mralarms 2 }
pm10010mrAlmClientNurg OBJECT IDENTIFIER ::= { pm10010mrAlmClient 1 }
pm10010mrAlmClientUrg OBJECT IDENTIFIER ::= { pm10010mrAlmClient 2 }
pm10010mrAlmClientCrit OBJECT IDENTIFIER ::= { pm10010mrAlmClient 3 }
	
pm10010mrAlmLine OBJECT IDENTIFIER ::= { pm10010mralarms 3 }
pm10010mrAlmLineNurg OBJECT IDENTIFIER ::= { pm10010mrAlmLine 1 }
pm10010mrAlmLineUrg OBJECT IDENTIFIER ::= { pm10010mrAlmLine 2 }
pm10010mrAlmLineCrit OBJECT IDENTIFIER ::= { pm10010mrAlmLine 3 }





pm10010mrmeasures OBJECT IDENTIFIER ::= { modulePm10010mr 3 }	
pm10010mrMesrOther OBJECT IDENTIFIER ::= { pm10010mrmeasures 1 }	
pm10010mrMesrClient OBJECT IDENTIFIER ::= { pm10010mrmeasures 2 }	
pm10010mrMesrLine OBJECT IDENTIFIER ::= { pm10010mrmeasures 3 }	




pm10010mrcounters OBJECT IDENTIFIER ::= { modulePm10010mr 4 }
pm10010mrCntOther OBJECT IDENTIFIER ::= { pm10010mrcounters 1 }
pm10010mrCntClient OBJECT IDENTIFIER ::= { pm10010mrcounters 2 }
pm10010mrCntLine OBJECT IDENTIFIER ::= { pm10010mrcounters 3 }


pm10010mrcontrolsWrite OBJECT IDENTIFIER ::= { modulePm10010mr 6 }
pm10010mrCtrlOther OBJECT IDENTIFIER ::= { pm10010mrcontrolsWrite 1 }
pm10010mrCtrlClient OBJECT IDENTIFIER ::= { pm10010mrcontrolsWrite 2 }
pm10010mrCtrlLine OBJECT IDENTIFIER ::= { pm10010mrcontrolsWrite 3 }

pm10010mrri OBJECT IDENTIFIER ::= { modulePm10010mr 7 }
pm10010mrriTable OBJECT IDENTIFIER ::= { pm10010mrri 1 }

pm10010mrdownload OBJECT IDENTIFIER ::= { modulePm10010mr 8 }
pm10010mrDwlOther OBJECT IDENTIFIER ::= { pm10010mrdownload 1 }
pm10010mrDwlClient OBJECT IDENTIFIER ::= { pm10010mrdownload 2 }
pm10010mrDwlLine OBJECT IDENTIFIER ::= { pm10010mrdownload 3 }


pm10010mrConfig OBJECT IDENTIFIER ::= { modulePm10010mr 9 }

pm10010mrtraps OBJECT IDENTIFIER ::= { modulePm10010mr 10 }



pm10010mrMonitoring OBJECT IDENTIFIER ::= { modulePm10010mr 11}

pm10010mrMonOther OBJECT IDENTIFIER ::= { pm10010mrMonitoring 1 }
pm10010mrMonRmon OBJECT IDENTIFIER ::= { pm10010mrMonOther 3 }

pm10010mrMonClient OBJECT IDENTIFIER ::= { pm10010mrMonitoring 2 }
pm10010mrMonClientRmonCounter OBJECT IDENTIFIER ::= { pm10010mrMonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm10010mrMultiRate ::= TEXTUAL-CONVENTION
    STATUS      current
    DESCRIPTION "different rate for a client port"
    SYNTAX INTEGER {
		rate100Mhz(0),
		rate250Mhz(1),
		rate500Mhz(2),
		rate1Ghz(3)
           }

Pm10010mrOtxMode ::= TEXTUAL-CONVENTION
    STATUS      current
    DESCRIPTION "Different modes on OTX-TLH on client and line ports"
    SYNTAX INTEGER {
		otx80mode(1),
		otx60mode(2),
		otxadjustmode(4)
           }

Pm10010mrOtxGrid ::= TEXTUAL-CONVENTION
    STATUS      current
    DESCRIPTION "Different grids on OTX-TLH on client and line ports"
    SYNTAX INTEGER {
		otxgrid200(200),
		otxgrid100(100),
		otxgrid50(50)
           }

Pm10010mrAdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm10010mrClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm10010mrProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm10010mrOtxChannel ::= TEXTUAL-CONVENTION
    STATUS      current
    DESCRIPTION "Channel selection on transceiver Tx line ports"
    SYNTAX INTEGER

Pm10010mrOrxChannel ::= TEXTUAL-CONVENTION
    STATUS      current
    DESCRIPTION "Channel selection on transceiver Rx line ports"
    SYNTAX INTEGER

Rm10010ClientIgnoreTimer ::= TEXTUAL-CONVENTION
    STATUS      current
    DESCRIPTION "Different values on the ignore timer on the client ports"
    SYNTAX INTEGER {
		ignoretimerclientvalue0(0),
		ignoretimerclientvalue1(1),
		ignoretimerclientvalue2(2),
		ignoretimerclientvalue3(3),
		ignoretimerclientvalue4(4),
		ignoretimerclientvalue5(5),
		ignoretimerclientvalue6(6),
		ignoretimerclientvalue7(7),
		ignoretimerclientvalue8(8),
		ignoretimerclientvalue9(9),
		ignoretimerclientvalue10(10)
           }

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm10010mrRinvReloadInventory OBJECT-TYPE
  SYNTAX EkiOnOff
  MAX-ACCESS read-write
  STATUS current
  DESCRIPTION
        "Reload the inventory: This OID triggers an 
         inventory reload."
  ::= { pm10010mrri 2 }

pm10010mrRinvHwPlatform OBJECT-TYPE
  SYNTAX DisplayString
  MAX-ACCESS read-only
  STATUS current
  DESCRIPTION
        "HW platform description: This OID contains the 
         description of the Hardware platform."
  ::= { pm10010mrri 3 }
  
pm10010mrRinvModulePlatform OBJECT-TYPE
  SYNTAX DisplayString
  MAX-ACCESS read-only
  STATUS current
  DESCRIPTION
        "Module platform description: This OID contains the 
         description of the Module."
  ::= { pm10010mrri 4 }
  
pm10010mrRinvSwPlatform OBJECT-TYPE
  SYNTAX DisplayString
  MAX-ACCESS read-only
  STATUS current
  DESCRIPTION
        "SW platform description: This OID contains the 
         description of the Software platform."
  ::= { pm10010mrri 5 }
  
pm10010mrRinvGwPlatform OBJECT-TYPE
  SYNTAX DisplayString
  MAX-ACCESS read-only
  STATUS current
  DESCRIPTION
        "GW platform desciption: This OID contains the 
         description of the Gateware platform."
  ::= { pm10010mrri 6 }


pm10010mrRinvSfpTable OBJECT-TYPE
      SYNTAX  SEQUENCE OF Pm10010mrRinvSfpEntry
      MAX-ACCESS  not-accessible
      STATUS  current
      DESCRIPTION
              "List of the SFPs on the selected module"
      ::= { pm10010mrriTable 1 }

pm10010mrRinvSfpEntry OBJECT-TYPE
        SYNTAX  Pm10010mrRinvSfpEntry
        MAX-ACCESS  not-accessible
        STATUS  current
        DESCRIPTION
              "Row definition for the SFP table"
        INDEX   { pm10010mrRinvSfpIndex }
        ::= { pm10010mrRinvSfpTable 1 }
    


Pm10010mrRinvSfpEntry::=
        SEQUENCE {
          pm10010mrRinvSfpIndex 
              Integer32,
          pm10010mrRinvsfp
              DisplayString
        }


    pm10010mrRinvSfpIndex OBJECT-TYPE
        SYNTAX  Integer32(1..16)
        MAX-ACCESS  read-only
        STATUS  current
        DESCRIPTION
              "Index for SFP table"
        ::= { pm10010mrRinvSfpEntry 1 }


    pm10010mrRinvsfp OBJECT-TYPE
        SYNTAX  DisplayString
        MAX-ACCESS  read-only
        STATUS  current
        DESCRIPTION
              "Inventory for the SFP: This OID contains the inventory for the SFP"
        ::= { pm10010mrRinvSfpEntry 2 }




pm10010mrRinvLineTable OBJECT-TYPE
      SYNTAX  SEQUENCE OF Pm10010mrRinvLineEntry
      MAX-ACCESS  not-accessible
      STATUS  current
      DESCRIPTION
              "List of the XFPs on the selected module"
      ::= { pm10010mrriTable 2 }

pm10010mrRinvLineEntry OBJECT-TYPE
        SYNTAX  Pm10010mrRinvLineEntry
        MAX-ACCESS  not-accessible
        STATUS  current
        DESCRIPTION
              "Row definition for the XFP table"
        INDEX   { pm10010mrRinvLineIndex }
        ::= { pm10010mrRinvLineTable 1 }
    


Pm10010mrRinvLineEntry::=
        SEQUENCE {
          pm10010mrRinvLineIndex 
              Integer32,
          pm10010mrRinvxfpLine
              DisplayString
        }


    pm10010mrRinvLineIndex OBJECT-TYPE
        SYNTAX  Integer32(1..16)
        MAX-ACCESS  read-only
        STATUS  current
        DESCRIPTION
              "Index for XFP table"
        ::= { pm10010mrRinvLineEntry 1 }


    pm10010mrRinvxfpLine OBJECT-TYPE
        SYNTAX  DisplayString
        MAX-ACCESS  read-only
        STATUS  current
        DESCRIPTION
              "Inventory for the XFP: This OID contains the inventory for the XFP"
        ::= { pm10010mrRinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm10010mrAlmsynthAlm0 OBJECT IDENTIFIER ::= { pm10010mrAlmOtherCrit 0 }




pm10010mrAlmDefFuseB OBJECT-TYPE
	  SYNTAX EkiOnOff
	  MAX-ACCESS read-only
	  STATUS current
	  DESCRIPTION
        "
        Fuse B Fail :This OID indicates 
        that the fuse of the power input 
        B is in fail condition <Help> Status 
        of the Fuse B <Condtype> DEF_FUSE_B 
        <Probcause> powerProblem (36) <Alarmtype> 
        equipmentAlarm (5) <Polarity> (2) 
        "
	  ::= { pm10010mrAlmsynthAlm0 16 }



pm10010mrAlmDefFuseA OBJECT-TYPE
	  SYNTAX EkiOnOff
	  MAX-ACCESS read-only
	  STATUS current
	  DESCRIPTION
        "
        Fuse A Fail :This OID indicates 
        that the fuse of the power input 
        A is in fail condition <Help> Status 
        of the Fuse A <Condtype> DEF_FUSE_A 
        <Probcause> powerProblem (36) <Alarmtype> 
        equipmentAlarm (5) <Polarity> (2) 
        "
	  ::= { pm10010mrAlmsynthAlm0 15 }



pm10010mrAlmModGlobFail OBJECT-TYPE
	  SYNTAX EkiOnOff
	  MAX-ACCESS read-only
	  STATUS current
	  DESCRIPTION
        "
        Module Failure :This OID is set 
        on detection of a failure originating 
        from the RM <Help> This alarm is 
        set on detection of a failure originating 
        from the equipment <Condtype> MOD_GLOB_FAIL 
        <Probcause> other (1) <Alarmtype> 
        synthesisAlarm (12)  <Polarity> 
        (2) 
        "
	  ::= { pm10010mrAlmsynthAlm0 9 }



pm10010mrAlmFailFan OBJECT-TYPE
	  SYNTAX EkiOnOff
	  MAX-ACCESS read-only
	  STATUS current
	  DESCRIPTION
        "
        Fan Fail :This OID is at 1 when 
        any fail occurs on the fan tray 
        <Help> This alarm indicates that 
        the Fan tray module is in a failure 
        condition <Condtype> FAIL_FAN <Probcause> 
        equipmentMalfunction (16) <Alarmtype> 
        equipmentAlarm (5) <Polarity> (2) 
        "
	  ::= { pm10010mrAlmsynthAlm0 2 }



--- *****************************************************
---     LEAF for the synthAlm2 article
--- *****************************************************
pm10010mrAlmsynthAlm2 OBJECT IDENTIFIER ::= { pm10010mrAlmOtherNurg 2 }




pm10010mrAlmMaintenanceOn OBJECT-TYPE
	  SYNTAX EkiOnOff
	  MAX-ACCESS read-only
	  STATUS current
	  DESCRIPTION
        "
        Maintenance Mode :This OID indicates 
        that the RM is in maintenance mode. 
        <Help> This alarm indicates that 
        the maintenance mode is enabled 
        on the PM <Condtype> MAINTENANCE_ON 
        <Probcause> informationalStatus(1000) 
        <Alarmtype> other (1) <Polarity> 
        (2) 
        "
	  ::= { pm10010mrAlmsynthAlm2 5 }



pm10010mrAlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> informationalStatus(1000) 
        <Alarmtype> other (1) <Polarity> 
        (2) 
        "
	  ::= { pm10010mrAlmsynthAlm2 4 }



pm10010mrAlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> informationalStatus(1000) 
        <Alarmtype> other (1) <Polarity> 
        (2) 
        "
	  ::= { pm10010mrAlmsynthAlm2 3 }



pm10010mrAlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> informationalStatus(1000) 
        <Alarmtype> other (1) <Polarity> 
        (2) 
        "
	  ::= { pm10010mrAlmsynthAlm2 2 }



pm10010mrAlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> informationalStatus(1000) 
        <Alarmtype> other (1) <Polarity> 
        (2) 
        "
	  ::= { pm10010mrAlmsynthAlm2 1 }



--- *********************************************************
---     TABLE for the pm10010mrAlmsynthAlmPort articles
--- *********************************************************

pm10010mrAlmsynthAlmPortTable OBJECT-TYPE
	SYNTAX  SEQUENCE OF Pm10010mrAlmsynthAlmPortEntry
	MAX-ACCESS not-accessible
	STATUS current
	DESCRIPTION
        "
        List of pm10010mrAlmsynthAlmPort 
        Article
        "
	::= { pm10010mrAlmClientCrit 8 }


pm10010mrAlmsynthAlmPortEntry OBJECT-TYPE
	SYNTAX Pm10010mrAlmsynthAlmPortEntry
	MAX-ACCESS not-accessible
	STATUS current
	DESCRIPTION
        "
        Row definition for the pm10010mrAlmsynthAlmPort 
        table
        "
	INDEX   { pm10010mrAlmsynthAlmPortIndex }
	::= { pm10010mrAlmsynthAlmPortTable 1 }


Pm10010mrAlmsynthAlmPortEntry ::=
	SEQUENCE {
	pm10010mrAlmsynthAlmPortIndex
		INTEGER,
	pm10010mrAlmUpCsfPortn
		EkiOnOff,
	pm10010mrAlmFailAccPortn
		EkiOnOff,
	pm10010mrAlmIdleInsertedPortn
		EkiOnOff,
	pm10010mrAlmSfpDdmAlmPortn
		EkiOnOff,
	pm10010mrAlmSfpDdmWarningPortn
		EkiOnOff,
	pm10010mrAlmDwCaisPortn
		EkiOnOff,
	pm10010mrAlmClientRemoteOosPortn
		EkiOnOff,
	pm10010mrAlmClientLocalOosPortn
		EkiOnOff,
	pm10010mrAlmDwLsdPortn
		EkiOnOff,
	pm10010mrAlmHwFailAccPortn
		EkiOnOff,
	pm10010mrAlmDdmAbsentPortn
		EkiOnOff,
	pm10010mrAlmSfpAbsentPortn
		EkiOnOff
	}


pm10010mrAlmsynthAlmPortIndex OBJECT-TYPE
	SYNTAX  INTEGER(0..128)
	MAX-ACCESS  read-only
	STATUS current
	DESCRIPTION
        "
        Index definition for the pm10010mrAlmsynthAlmPort 
        table
        "
	::= { pm10010mrAlmsynthAlmPortEntry 1 }


pm10010mrAlmUpCsfPortn OBJECT-TYPE
	SYNTAX  EkiOnOff
	MAX-ACCESS read-only
	STATUS current
	DESCRIPTION
        "
        Client Signal Fail Inserted :This 
        OID indicates a CSF has been inserted 
        in the upstream client port. <Help> 
        This status indicates if a Client 
        Signal Fail is currently inserted 
        on the line signal for this client 
        port <Condtype> UP_CSF_1 <Probcause> 
        informationalStatus(1000) <Alarmtype> 
        other (1) <Polarity> (2) 
        "
	::= { pm10010mrAlmsynthAlmPortEntry 17 }


pm10010mrAlmFailAccPortn OBJECT-TYPE
	SYNTAX  EkiOnOff
	MAX-ACCESS read-only
	STATUS current
	DESCRIPTION
        "
        Client Access Fail :This OID indicates 
        a failure on the Client port <Help> 
        This alarm indicates a failure
         on the Client port <Condtype>
         FAIL_ACC_1 <Probcause> equipmentMalfunction 
        (16) <Alarmtype> synthesisAlarm 
        (12) <Polarity> (2) 
        "
	::= { pm10010mrAlmsynthAlmPortEntry 13 }


pm10010mrAlmIdleInsertedPortn OBJECT-TYPE
	SYNTAX  EkiOnOff
	MAX-ACCESS read-only
	STATUS current
	DESCRIPTION
        "
        Idle Inserted :This OID indicates 
        the client output stream is replaced 
        by IDLE<Help> This alarm indicates 
        the client output stream is replaced 
        by IDLE <Condtype> IDLE_INSERTED 
        <Probcause> informationalStatus(1000) 
        <Alarmtype> other (1) <Polarity> 
        (2) 
        "
	::= { pm10010mrAlmsynthAlmPortEntry 12 }


pm10010mrAlmSfpDdmAlmPortn OBJECT-TYPE
	SYNTAX  EkiOnOff
	MAX-ACCESS read-only
	STATUS current
	DESCRIPTION
        "
        Alarm On Client Trscv DDM :This 
        OID indicates an alarm is being 
        received from the Client Transceiver 
        DDM <Help> This alarm indicates 
        if a DDM Alarm has been detected 
        on the client transceiver <Condtype> 
        SFP_DDM_ALM_1 <Probcause> inputOutputDeviceError 
        (24) <Alarmtype> synthesisAlarm 
        (12) <Polarity> (2) 
        "
	::= { pm10010mrAlmsynthAlmPortEntry 11 }


pm10010mrAlmSfpDdmWarningPortn OBJECT-TYPE
	SYNTAX  EkiOnOff
	MAX-ACCESS read-only
	STATUS current
	DESCRIPTION
        "
        Warning On Client Trscv DDM :This 
        OID indicates a warning is being 
        received from the Client Transceiver 
        DDM <Help> This alarm indicates 
        if a DDM Warning has been detected 
        on the client transceiver <Condtype> 
        SFP_DDM_WARNING_1 <Probcause> inputOutputDeviceError 
        (24) <Alarmtype> synthesisAlarm 
        (12) <Polarity> (2) 
        "
	::= { pm10010mrAlmsynthAlmPortEntry 10 }


pm10010mrAlmDwCaisPortn OBJECT-TYPE
	SYNTAX  EkiOnOff
	MAX-ACCESS read-only
	STATUS current
	DESCRIPTION
        "
        Client AIS Inserted :This OID
         indicates a CAIS has been inserted 
        on the output client port. <Help> 
        This status indicates if a Client 
        Alarm Indication Signal is currently 
        inserted on the client interface 
        <Condtype> DW_CAIS_1 <Probcause> 
        informationalStatus(1000) <Alarmtype> 
        other (1) <Polarity> (2) 
        "
	::= { pm10010mrAlmsynthAlmPortEntry 9 }


pm10010mrAlmClientRemoteOosPortn OBJECT-TYPE
	SYNTAX  EkiOnOff
	MAX-ACCESS read-only
	STATUS current
	DESCRIPTION
        "
        Remote Client Port In Service
         :This OID indicates that the remote 
        Client port is In Service (1) or 
        Out of Service (2) <Help> This
         status indicates if the remote 
        client port is in service <Condtype> 
        CLIENT_REMOTE_OOS <Probcause> informationalStatus(1000) 
        <Alarmtype> other (1) <Polarity> 
        (2) 
        "
	::= { pm10010mrAlmsynthAlmPortEntry 8 }


pm10010mrAlmClientLocalOosPortn OBJECT-TYPE
	SYNTAX  EkiOnOff
	MAX-ACCESS read-only
	STATUS current
	DESCRIPTION
        "
        Local Client Port In Service :This 
        OID indicates that the local Client 
        port is In Service (1) or Out of 
        Service (2) <Help> This status
         indicates if the local client
         port is in service <Condtype>
         CLIENT_LOCAL_OOS <Probcause> informationalStatus(1000) 
        <Alarmtype> other (1) <Polarity> 
        (2) 
        "
	::= { pm10010mrAlmsynthAlmPortEntry 7 }


pm10010mrAlmDwLsdPortn OBJECT-TYPE
	SYNTAX  EkiOnOff
	MAX-ACCESS read-only
	STATUS current
	DESCRIPTION
        "
        Client Trscv Laser Shutdown :This 
        OID indicates the Client transceiver 
        laser is shutdown <Help> This status 
        indicates if the client transceiver 
        laser is shutdown <Condtype> DW_LSD_1 
        <Probcause> other (1) <Alarmtype> 
        equipmentAlarm (5) <Polarity> (2) 
        "
	::= { pm10010mrAlmsynthAlmPortEntry 6 }


pm10010mrAlmHwFailAccPortn OBJECT-TYPE
	SYNTAX  EkiOnOff
	MAX-ACCESS read-only
	STATUS current
	DESCRIPTION
        "
        Client HW Fail :This OID indicates 
        a failure on client port, most
         probably caused by a HW issue. 
        <Help> This alarm indicates a failure 
        on client port, most probably caused 
        by a HW issue. <Condtype> HW_FAIL_ACC_1 
        <Probcause> equipmentMalfunction 
        (16) <Alarmtype> synthesisAlarm 
        (12) <Polarity> (2) 
        "
	::= { pm10010mrAlmsynthAlmPortEntry 5 }


pm10010mrAlmDdmAbsentPortn OBJECT-TYPE
	SYNTAX  EkiOnOff
	MAX-ACCESS read-only
	STATUS current
	DESCRIPTION
        "
        DDM Supported On Client Trscv
         :This OID indicates that the Client 
        transceiver supports the Digital 
        Diagnostic Monitoring function
         <Help> This status indicates if 
        the client transceiver includes 
        the DDM feature <Condtype> DDM_ABSENT_1 
        <Probcause> informationalStatus(1000) 
        <Alarmtype> other (1) <Polarity> 
        (2) 
        "
	::= { pm10010mrAlmsynthAlmPortEntry 3 }


pm10010mrAlmSfpAbsentPortn OBJECT-TYPE
	SYNTAX  EkiOnOff
	MAX-ACCESS read-only
	STATUS current
	DESCRIPTION
        "
        Client Optical Module Absent :This 
        OID indicates that the Transceiver 
        is not present in the client port. 
        <Help> This alarm indicates if
         the client transceiver is not
         plugged <Condtype> SFP_ABSENT_1 
        <Probcause> inputOutputDeviceError 
        (24) <Alarmtype> equipmentAlarm 
        (5) <Polarity> (2) <Event> ObjectCDINV
        "
	::= { pm10010mrAlmsynthAlmPortEntry 2 }


--- *********************************************************
---     TABLE for the pm10010mrAlmsynthAlmLine articles
--- *********************************************************

pm10010mrAlmsynthAlmLineTable OBJECT-TYPE
	SYNTAX  SEQUENCE OF Pm10010mrAlmsynthAlmLineEntry
	MAX-ACCESS not-accessible
	STATUS current
	DESCRIPTION
        "
        List of pm10010mrAlmsynthAlmLine 
        Article
        "
	::= { pm10010mrAlmLineCrit 24 }


pm10010mrAlmsynthAlmLineEntry OBJECT-TYPE
	SYNTAX Pm10010mrAlmsynthAlmLineEntry
	MAX-ACCESS not-accessible
	STATUS current
	DESCRIPTION
        "
        Row definition for the pm10010mrAlmsynthAlmLine 
        table
        "
	INDEX   { pm10010mrAlmsynthAlmLineIndex }
	::= { pm10010mrAlmsynthAlmLineTable 1 }


Pm10010mrAlmsynthAlmLineEntry ::=
	SEQUENCE {
	pm10010mrAlmsynthAlmLineIndex
		INTEGER,
	pm10010mrAlmLineActivePortn
		EkiOnOff,
	pm10010mrAlmLineFailPortn
		EkiOnOff,
	pm10010mrAlmLineDdmAlmPortn
		EkiOnOff,
	pm10010mrAlmLineDdmWarningPortn
		EkiOnOff,
	pm10010mrAlmUpRdiInsPortn
		EkiOnOff,
	pm10010mrAlmLineLocalOosPortn
		EkiOnOff,
	pm10010mrAlmXfpTxOffPortn
		EkiOnOff,
	pm10010mrAlmLineHwFailPortn
		EkiOnOff,
	pm10010mrAlmXfpInitNotComplPortn
		EkiOnOff,
	pm10010mrAlmXfpAbsentPortn
		EkiOnOff
	}


pm10010mrAlmsynthAlmLineIndex OBJECT-TYPE
	SYNTAX  INTEGER(0..128)
	MAX-ACCESS  read-only
	STATUS current
	DESCRIPTION
        "
        Index definition for the pm10010mrAlmsynthAlmLine 
        table
        "
	::= { pm10010mrAlmsynthAlmLineEntry 1 }


pm10010mrAlmLineActivePortn OBJECT-TYPE
	SYNTAX  EkiOnOff
	MAX-ACCESS read-only
	STATUS current
	DESCRIPTION
        "
        Line Active :This OID indicates 
        whether the line is active or standby. 
        <Help> This status indicates whether 
        the line is active or standby.
         <Condtype> LINE_ACTIVE <Probcause> 
        informationalStatus(1000) <Alarmtype> 
        other (1) <Polarity> (2) 
        "
	::= { pm10010mrAlmsynthAlmLineEntry 17 }


pm10010mrAlmLineFailPortn OBJECT-TYPE
	SYNTAX  EkiOnOff
	MAX-ACCESS read-only
	STATUS current
	DESCRIPTION
        "
        Line Port Failure :This OID indicates 
        a failure on the line port <Help> 
        This alarm indicates a failure
         on the line port <Condtype> LINE_FAIL 
        <Probcause> equipmentMalfunction 
        (16) <Alarmtype> synthesisAlarm 
        (12) <Polarity> (2) 
        "
	::= { pm10010mrAlmsynthAlmLineEntry 13 }


pm10010mrAlmLineDdmAlmPortn OBJECT-TYPE
	SYNTAX  EkiOnOff
	MAX-ACCESS read-only
	STATUS current
	DESCRIPTION
        "
        Alarm On Line Optical Module DDM 
        :This OID indicates an alarm is 
        present coming out of Line transceiver 
        DDM <Help> This alarm indicates 
        if a DDM Alarm has been detected 
        on the line transceiver <Condtype> 
        LINE_DDM_ALM <Probcause> inputOutputDeviceError 
        (24) <Alarmtype> synthesisAlarm 
        (12) <Polarity> (2) 
        "
	::= { pm10010mrAlmsynthAlmLineEntry 11 }


pm10010mrAlmLineDdmWarningPortn OBJECT-TYPE
	SYNTAX  EkiOnOff
	MAX-ACCESS read-only
	STATUS current
	DESCRIPTION
        "
        Warning On Line Optical Module 
        DDM :This OID indicates a warning 
        is present coming out of Line transceiver 
        DDM <Help> This alarm indicates 
        if a DDM Warning has been detected 
        on the line transceiver <Condtype> 
        LINE_DDM_WARNING <Probcause> inputOutputDeviceError 
        (24) <Alarmtype> synthesisAlarm 
        (12) <Polarity> (2) 
        "
	::= { pm10010mrAlmsynthAlmLineEntry 10 }


pm10010mrAlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal. <Help> This status indicates 
        if a MS-RDI/L-RDI is currently
         inserted on the line interface. 
        <Condtype> UP_RDI_INS <Probcause> 
        informationalStatus(1000) <Alarmtype> 
        other (1) <Polarity> (2) 
        "
	::= { pm10010mrAlmsynthAlmLineEntry 9 }


pm10010mrAlmLineLocalOosPortn OBJECT-TYPE
	SYNTAX  EkiOnOff
	MAX-ACCESS read-only
	STATUS current
	DESCRIPTION
        "
        Line Port In Service :This OID 
        indicates that the Line port is 
        In Service (1) of Out or Service 
        (2) <Help> This status indicates 
        if the line port is in service
         <Condtype> LINE_LOCAL_OOS <Probcause> 
        informationalStatus(1000) <Alarmtype> 
        other (1) <Polarity> (2) 
        "
	::= { pm10010mrAlmsynthAlmLineEntry 7 }


pm10010mrAlmXfpTxOffPortn OBJECT-TYPE
	SYNTAX  EkiOnOff
	MAX-ACCESS read-only
	STATUS current
	DESCRIPTION
        "
        Line Trscv Laser Shutdown :This 
        OID indicates the Line transceiver 
        laser is shutdown <Help> This status 
        indicates if the Line transceiver 
        laser is shutdown <Condtype> XFP_TX_OFF 
        <Probcause> other (1) <Alarmtype> 
        equipmentAlarm (5) <Polarity> (2) 
        "
	::= { pm10010mrAlmsynthAlmLineEntry 6 }


pm10010mrAlmLineHwFailPortn OBJECT-TYPE
	SYNTAX  EkiOnOff
	MAX-ACCESS read-only
	STATUS current
	DESCRIPTION
        "
        Line Port HW Failure :This OID 
        indicates a failure on line port, 
        most probably caused by a HW issue 
        <Help> This alarm indicates a failure 
        on line port, most probably caused 
        by a HW issue <Condtype> LINE_HW_FAIL 
        <Probcause> equipmentMalfunction 
        (16) <Alarmtype> synthesisAlarm 
        (12) <Polarity> (2) 
        "
	::= { pm10010mrAlmsynthAlmLineEntry 5 }


pm10010mrAlmXfpInitNotComplPortn OBJECT-TYPE
	SYNTAX  EkiOnOff
	MAX-ACCESS read-only
	STATUS current
	DESCRIPTION
        "
        Line Optical Module Ready :This 
        OID indicates that the optical
         interface is not operational.
         <Help> This status indicates if 
        the line transceiver has been correctly 
        initialized <Condtype> XFP_INIT_NOT_COMPL 
        <Probcause> equipmentMalfunction 
        (16) <Alarmtype> equipmentAlarm 
        (5) <Polarity> (2) 
        "
	::= { pm10010mrAlmsynthAlmLineEntry 3 }


pm10010mrAlmXfpAbsentPortn OBJECT-TYPE
	SYNTAX  EkiOnOff
	MAX-ACCESS read-only
	STATUS current
	DESCRIPTION
        "
        Line Optical Module Absent :This 
        OID indicates that the line optical 
        interface is not present. <Help> 
        This alarm indicates if the line 
        transceiver is not plugged <Condtype> 
        XFP_ABSENT <Probcause> inputOutputDeviceError 
        (24) <Alarmtype> equipmentAlarm 
        (5) <Polarity> (2) 
        "
	::= { pm10010mrAlmsynthAlmLineEntry 2 }


--- *****************************************************
---     LEAF for the clientModuleState article
--- *****************************************************
pm10010mrAlmclientModuleState OBJECT IDENTIFIER ::= { pm10010mrAlmOtherCrit 40 }




pm10010mrAlmCfpHighPowerDown OBJECT-TYPE
	  SYNTAX EkiOnOff
	  MAX-ACCESS read-only
	  STATUS current
	  DESCRIPTION
        "
        Client Trscv High Power Down :This 
        OID indicates the Client Trscv
         is entering Low Power state <Help> 
        Status indicating the Client Trscv 
        is entering Low Power state <Condtype> 
        CFP_HIGH_POWER_DOWN <Probcause> 
        informationalStatus(1000) <Alarmtype> 
        other (1) <Polarity> (2) 
        "
	  ::= { pm10010mrAlmclientModuleState 9 }



pm10010mrAlmCfpTxTurnOff OBJECT-TYPE
	  SYNTAX EkiOnOff
	  MAX-ACCESS read-only
	  STATUS current
	  DESCRIPTION
        "
        Client Trscv Laser Turn Off :This 
        OID indicates the Client Trscv
         is turning off its laser <Help> 
        Status indicating the Client Trscv 
        is turning off its laser <Condtype> 
        CFP_TX_TURN_OFF <Probcause> informationalStatus(1000) 
        <Alarmtype> other (1) <Polarity> 
        (2) 
        "
	  ::= { pm10010mrAlmclientModuleState 8 }



pm10010mrAlmCfpFault OBJECT-TYPE
	  SYNTAX EkiOnOff
	  MAX-ACCESS read-only
	  STATUS current
	  DESCRIPTION
        "
        Client Trscv Fault :This OID indicates 
        the Client Trscv is in Fault state 
        <Help> Status indicating the Client 
        Trscv is in Fault state <Condtype> 
        CFP_FAULT <Probcause> informationalStatus(1000) 
        <Alarmtype> other (1) <Polarity> 
        (2) 
        "
	  ::= { pm10010mrAlmclientModuleState 7 }



pm10010mrAlmCfpReady OBJECT-TYPE
	  SYNTAX EkiOnOff
	  MAX-ACCESS read-only
	  STATUS current
	  DESCRIPTION
        "
        Client Trscv Ready :This OID indicates 
        the Client Trscv is ready to operate 
        <Help> Status indicating the Client 
        Trscv is ready to operate <Condtype> 
        CFP_READY <Probcause> informationalStatus(1000) 
        <Alarmtype> other (1) <Polarity> 
        (2) 
        "
	  ::= { pm10010mrAlmclientModuleState 6 }



pm10010mrAlmCfpTxTurnOn OBJECT-TYPE
	  SYNTAX EkiOnOff
	  MAX-ACCESS read-only
	  STATUS current
	  DESCRIPTION
        "
        Client Trscv Laser Turn On :This 
        OID indicates the Client Trscv
         is turning on its laser <Help> 
        Status indicating the Client Trscv 
        is turning on its laser <Condtype> 
        CFP_TX_TURN_ON <Probcause> informationalStatus(1000) 
        <Alarmtype> other (1) <Polarity> 
        (2) 
        "
	  ::= { pm10010mrAlmclientModuleState 5 }



pm10010mrAlmCfpTxOff OBJECT-TYPE
	  SYNTAX EkiOnOff
	  MAX-ACCESS read-only
	  STATUS current
	  DESCRIPTION
        "
        Client Trscv Laser Shutdown :This 
        OID indicates the Client Trscv
         Laser is OFF <Help> Status indicating 
        the Client Trscv Laser is OFF <Condtype> 
        CFP_TX_OFF <Probcause> informationalStatus(1000) 
        <Alarmtype> other (1) <Polarity> 
        (2) 
        "
	  ::= { pm10010mrAlmclientModuleState 4 }



pm10010mrAlmCfpHighPowerUp OBJECT-TYPE
	  SYNTAX EkiOnOff
	  MAX-ACCESS read-only
	  STATUS current
	  DESCRIPTION
        "
        Client Trscv High Power Up :This 
        OID indicates the Client Trscv
         is leaving Low Power state <Help> 
        Status indicating the Client Trscv 
        is leaving Low Power state <Condtype> 
        CFP_HIGH_POWER_UP <Probcause> informationalStatus(1000) 
        <Alarmtype> other (1) <Polarity> 
        (2) 
        "
	  ::= { pm10010mrAlmclientModuleState 3 }



pm10010mrAlmCfpLowPower OBJECT-TYPE
	  SYNTAX EkiOnOff
	  MAX-ACCESS read-only
	  STATUS current
	  DESCRIPTION
        "
        Client Trscv Low Power :This OID 
        indicates the Client Trscv is in 
        low power state <Help> Status indicating 
        the Client Trscv is in low power 
        state <Condtype> CFP_LOW_POWER
         <Probcause> informationalStatus(1000) 
        <Alarmtype> other (1) <Polarity> 
        (2) 
        "
	  ::= { pm10010mrAlmclientModuleState 2 }



pm10010mrAlmCfpInitialize OBJECT-TYPE
	  SYNTAX EkiOnOff
	  MAX-ACCESS read-only
	  STATUS current
	  DESCRIPTION
        "
        Client Trscv Initialize :This
         OID indicates the Client Trscv 
        initialization is in progress <Help> 
        Status indicating the Client Trscv 
        initialization is in progress <Condtype> 
        CFP_INITIALIZE <Probcause> informationalStatus(1000) 
        <Alarmtype> other (1) <Polarity> 
        (2) 
        "
	  ::= { pm10010mrAlmclientModuleState 1 }



--- *****************************************************
---     LEAF for the clientModuleGeneralStatus article
--- *****************************************************
pm10010mrAlmclientModuleGeneralStatus OBJECT IDENTIFIER ::= { pm10010mrAlmOtherCrit 41 }




pm10010mrAlmCfpHwInterlock OBJECT-TYPE
	  SYNTAX EkiOnOff
	  MAX-ACCESS read-only
	  STATUS current
	  DESCRIPTION
        "
        Client Trscv Hardware Interlock 
        :This OID indicates the Client
         Trscv power is higher than the 
        cooling capacity <Help> Alarm indicating 
        the Client Trscv power is higher 
        than the cooling capacity <Condtype> 
        CFP_HW_INTERLOCK <Probcause> temperatureUnacceptable 
        (51) <Alarmtype> equipmentAlarm 
        (5) <Polarity> (2) 
        "
	  ::= { pm10010mrAlmclientModuleGeneralStatus 14 }



pm10010mrAlmCfpLossOfRefclk OBJECT-TYPE
	  SYNTAX EkiOnOff
	  MAX-ACCESS read-only
	  STATUS current
	  DESCRIPTION
        "
        Client Trscv Loss Of Ref Clock 
        :This OID indicates a Loss of Reference 
        clock is detected on the Client 
        Trscv <Help> Alarm indicating a 
        Loss of Reference clock is detected 
        on the Client Trscv <Condtype>
         CFP_LOSS_OF_REFCLK <Probcause> 
        inputOutputDeviceError (24) <Alarmtype> 
        equipmentAlarm (5) <Polarity> (2) 
        "
	  ::= { pm10010mrAlmclientModuleGeneralStatus 11 }



pm10010mrAlmCfpTxJitterPllLol OBJECT-TYPE
	  SYNTAX EkiOnOff
	  MAX-ACCESS read-only
	  STATUS current
	  DESCRIPTION
        "
        Client Trscv Tx Jitter PLL Loss 
        Of Lock :This OID indicates a Tx 
        Jitter PLL Loss of Lock is dtected 
        on the Client Trscv <Help> Alarm 
        indicating a Tx Jitter PLL Loss 
        of Lock is dtected on the Client 
        Trscv <Condtype> CFP_TX_JITTER_PLL_LOL 
        <Probcause> inputOutputDeviceError 
        (24) <Alarmtype> equipmentAlarm 
        (5) <Polarity> (2) 
        "
	  ::= { pm10010mrAlmclientModuleGeneralStatus 10 }



pm10010mrAlmCfpTxCmuLol OBJECT-TYPE
	  SYNTAX EkiOnOff
	  MAX-ACCESS read-only
	  STATUS current
	  DESCRIPTION
        "
        Client Trscv CMU Loss Of Lock
         :This OID indicates a Clock Multiplier 
        Unit Loss of Lock is detected on 
        the Client Trscv <Help> Alarm indicating 
        a Clock Multiplier Unit Loss of 
        Lock is detected on the Client
         Trscv <Condtype> CFP_TX_CMU_LOL 
        <Probcause> inputOutputDeviceError 
        (24) <Alarmtype> equipmentAlarm 
        (5) <Polarity> (2) 
        "
	  ::= { pm10010mrAlmclientModuleGeneralStatus 9 }



pm10010mrAlmCfpTxLosf OBJECT-TYPE
	  SYNTAX EkiOnOff
	  MAX-ACCESS read-only
	  STATUS current
	  DESCRIPTION
        "
        Client Trscv Loss Of Signal Functionality 
        :This OID indicates a Loss of Signal 
        functionality is detected on the 
        Client Trscv <Help> Alarm indicating 
        a Loss of Signal functionality
         is detected on the Client Trscv 
        <Condtype> CFP_TX_LOSF <Probcause> 
        lossOfSignal (30) <Alarmtype> equipmentAlarm 
        (5) <Polarity> (2) 
        "
	  ::= { pm10010mrAlmclientModuleGeneralStatus 8 }



pm10010mrAlmCfpTxHostLol OBJECT-TYPE
	  SYNTAX EkiOnOff
	  MAX-ACCESS read-only
	  STATUS current
	  DESCRIPTION
        "
        Client Trscv Tx Host Loss Of Lock 
        :This OID indicates of Loss of
         Lock is detected on the Client 
        Trscv Tx Host interface <Help>
         Alarm indicating of Loss of Lock 
        is detected on the Client Trscv 
        Tx Host interface <Condtype> CFP_TX_HOST_LOL 
        <Probcause> receiverFailure (42) 
        <Alarmtype> equipmentAlarm (5)
         <Polarity> (2) 
        "
	  ::= { pm10010mrAlmclientModuleGeneralStatus 7 }



pm10010mrAlmCfpRxLos OBJECT-TYPE
	  SYNTAX EkiOnOff
	  MAX-ACCESS read-only
	  STATUS current
	  DESCRIPTION
        "
        Client Trscv Loss Of Signal :This 
        OID indicates a Loss of Signal
         is detected on the Client Trscv 
        <Help> Alarm indicating a Loss
         of Signal is detected on the Client 
        Trscv <Condtype> CFP_RX_LOS <Probcause> 
        lossOfSignal (30) <Alarmtype> equipmentAlarm 
        (5) <Polarity> (2) 
        "
	  ::= { pm10010mrAlmclientModuleGeneralStatus 6 }



pm10010mrAlmCfpRxNetworkLol OBJECT-TYPE
	  SYNTAX EkiOnOff
	  MAX-ACCESS read-only
	  STATUS current
	  DESCRIPTION
        "
        Client Trscv Rx Network Loss Of 
        Lock :This OID indicates of Loss 
        of Lock is dected on the Client 
        Trscv Rx Network interface <Help> 
        Alarm indicating of Loss of Lock 
        is dected on the Client Trscv Rx 
        Network interface <Condtype> CFP_RX_NETWORK_LOL 
        <Probcause> receiverFailure (42) 
        <Alarmtype> equipmentAlarm (5)
         <Polarity> (2) 
        "
	  ::= { pm10010mrAlmclientModuleGeneralStatus 5 }



pm10010mrAlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating 
        an Out of alignment on the Client 
        Trscv Host Interface <Condtype> 
        CFP_OUT_OF_ALIGNMENT <Probcause> 
        receiverFailure (42) <Alarmtype> 
        equipmentAlarm (5) <Polarity> (2) 
        "
	  ::= { pm10010mrAlmclientModuleGeneralStatus 4 }



--- *****************************************************
---     LEAF for the clientGlobalAlarmSummary article
--- *****************************************************
pm10010mrAlmclientGlobalAlarmSummary OBJECT IDENTIFIER ::= { pm10010mrAlmOtherCrit 42 }




pm10010mrAlmCfpGlobAlarmAssertion  OBJECT-TYPE
	  SYNTAX EkiOnOff
	  MAX-ACCESS read-only
	  STATUS current
	  DESCRIPTION
        "
        Client Trscv Global Alarm :This 
        OID indicates at least one  Fault 
        or Status is detected on the Client 
        Trscv module <Help> Synthesis alarm 
        indicating at least one Alarm,
         Warning, Fault or Status is detected 
        on the Client Trscv module <Condtype> 
        CFP_GLOB_ALARM_ASSERTION  <Probcause> 
        informationalStatus(1000) <Alarmtype> 
        other (1) <Polarity> (2) 
        "
	  ::= { pm10010mrAlmclientGlobalAlarmSummary 16 }



pm10010mrAlmCfpHostLaneFaultStatus  OBJECT-TYPE
	  SYNTAX EkiOnOff
	  MAX-ACCESS read-only
	  STATUS current
	  DESCRIPTION
        "
        Client Trscv Host Fault And Status 
        :This OID indicates at least one 
        Fault or Status is detected on
         the Client Trscv Host Interface 
        <Help> Synthesis alarm indicating 
        at least one Fault or Status is 
        detected on the Client Trscv Host 
        Interface <Condtype> CFP_HOST_LANE_FAULT_STATUS 
         <Probcause> informationalStatus(1000) 
        <Alarmtype> other (1) <Polarity> 
        (2) 
        "
	  ::= { pm10010mrAlmclientGlobalAlarmSummary 15 }



pm10010mrAlmCfpNetworkLaneFaultStatus  OBJECT-TYPE
	  SYNTAX EkiOnOff
	  MAX-ACCESS read-only
	  STATUS current
	  DESCRIPTION
        "
        Client Trscv Network Fault And 
        Status :This OID indicates at least 
        one Fault or Status is detected 
        on the Client Trscv Network Interface 
        <Help> Synthesis alarm indicating 
        at least one Fault or Status is 
        detected on the Client Trscv Network 
        Interface <Condtype> CFP_NETWORK_LANE_FAULT_STATUS 
         <Probcause> informationalStatus(1000) 
        <Alarmtype> other (1) <Polarity> 
        (2) 
        "
	  ::= { pm10010mrAlmclientGlobalAlarmSummary 14 }



pm10010mrAlmCfpNetworkLaneAlarmWarning1 OBJECT-TYPE
	  SYNTAX EkiOnOff
	  MAX-ACCESS read-only
	  STATUS current
	  DESCRIPTION
        "
        Client Trscv Network Alarm And 
        Warning 1 :This OID indicates at 
        least one DDM  is detected on the 
        Client Trscv Network Interface
         <Help> Synthesis alarm indicating 
        at least one DDM Alarm or DDM Warning 
        is detected on the Client Trscv 
        Network Interface <Condtype> CFP_NETWORK_LANE_ALARM_WARNING_1 
        <Probcause> informationalStatus(1000) 
        <Alarmtype> other (1) <Polarity> 
        (2) 
        "
	  ::= { pm10010mrAlmclientGlobalAlarmSummary 13 }



pm10010mrAlmCfpModuleAlarmWarning2 OBJECT-TYPE
	  SYNTAX EkiOnOff
	  MAX-ACCESS read-only
	  STATUS current
	  DESCRIPTION
        "
        Client Trscv Module Alarm And
         Warning 2 :This OID indicates
         at least one DDM is detected on 
        the Client Trscv module <Help>
         Synthesis alarm indicating at
         least one DDM Alarm or DDM Warning 
        is detected on the Client Trscv 
        module <Condtype> CFP_MODULE_ALARM_WARNING_2 
        <Probcause> informationalStatus(1000) 
        <Alarmtype> other (1) <Polarity> 
        (2) 
        "
	  ::= { pm10010mrAlmclientGlobalAlarmSummary 12 }



pm10010mrAlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module 
        <Help> Synthesis alarm indicating 
        at least one DDM Alarm or DDM Warning 
        is detected on the Client Trscv 
        module <Condtype> CFP_MODULE_ALARM_WARNING_1 
         <Probcause> informationalStatus(1000) 
        <Alarmtype> other (1) <Polarity> 
        (2) 
        "
	  ::= { pm10010mrAlmclientGlobalAlarmSummary 11 }



pm10010mrAlmCfpModuleFault  OBJECT-TYPE
	  SYNTAX EkiOnOff
	  MAX-ACCESS read-only
	  STATUS current
	  DESCRIPTION
        "
        Client Trscv Module Fault :This 
        OID indicates at least one Fault 
        is detected on the Client Trscv 
        module <Help> Synthesis alarm indicating 
        at least one Fault is detected
         on the Client Trscv module <Condtype> 
        CFP_MODULE_FAULT  <Probcause> informationalStatus(1000) 
        <Alarmtype> other (1) <Polarity> 
        (2) 
        "
	  ::= { pm10010mrAlmclientGlobalAlarmSummary 10 }



pm10010mrAlmCfpModuleGeneralStatus  OBJECT-TYPE
	  SYNTAX EkiOnOff
	  MAX-ACCESS read-only
	  STATUS current
	  DESCRIPTION
        "
        Client Trscv General Status :This 
        OID indicates the Client Trscv
         module general status <Help> Synthesis 
        alarm indicating the Client Trscv 
        module general status <Condtype> 
        CFP_MODULE_GENERAL_STATUS  <Probcause> 
        informationalStatus(1000) <Alarmtype> 
        other (1) <Polarity> (2) 
        "
	  ::= { pm10010mrAlmclientGlobalAlarmSummary 9 }



pm10010mrAlmCfpModuleState  OBJECT-TYPE
	  SYNTAX EkiOnOff
	  MAX-ACCESS read-only
	  STATUS current
	  DESCRIPTION
        "
        Client Trscv Module State :This 
        OID indicates the Client Trscv
         module state <Help> Synthesis
         alarm indicating the Client Trscv 
        module state <Condtype> CFP_MODULE_STATE 
         <Probcause> informationalStatus(1000) 
        <Alarmtype> other (1) <Polarity> 
        (2) 
        "
	  ::= { pm10010mrAlmclientGlobalAlarmSummary 8 }



pm10010mrAlmCfpNetworkLaneAlarmWarning2 OBJECT-TYPE
	  SYNTAX EkiOnOff
	  MAX-ACCESS read-only
	  STATUS current
	  DESCRIPTION
        "
        Client Trscv Network Alarm And 
        Warning 2 :This OID indicates at 
        least one DDM is detected on the 
        Client Trscv Network Interface
         <Help> Synthesis alarm indicating 
        at least one DDM Alarm or DDM Warning 
        is detected on the Client Trscv 
        Network Interface <Condtype> CFP_NETWORK_LANE_ALARM_WARNING_2 
        <Probcause> informationalStatus(1000) 
        <Alarmtype> other (1) <Polarity> 
        (2) 
        "
	  ::= { pm10010mrAlmclientGlobalAlarmSummary 7 }



pm10010mrAlmCfpSoftGlobAlarmTest  OBJECT-TYPE
	  SYNTAX EkiOnOff
	  MAX-ACCESS read-only
	  STATUS current
	  DESCRIPTION
        "
        Client Trscv Global Alarm SW Test 
        :This OID indicates the Client
         Trscv Global Alarm This OID is 
        raised by SW request for test purpose 
        <Help> Status indicating the Client 
        Trscv Global Alarm is raised by 
        SW request for test purpose <Condtype> 
        CFP_SOFT_GLOB_ALARM_TEST  <Probcause> 
        informationalStatus(1000) <Alarmtype> 
        other (1) <Polarity> (2) 
        "
	  ::= { pm10010mrAlmclientGlobalAlarmSummary 1 }



--- *****************************************************
---     LEAF for the msaModuleState article
--- *****************************************************
pm10010mrAlmmsaModuleState OBJECT IDENTIFIER ::= { pm10010mrAlmOtherCrit 46 }




pm10010mrAlmMsaHighPowerDown OBJECT-TYPE
	  SYNTAX EkiOnOff
	  MAX-ACCESS read-only
	  STATUS current
	  DESCRIPTION
        "
        Line Trscv High Power Down :This 
        OID indicates the Line Trscv is 
        entering Low Power state <Help> 
        Status indicating the Line Trscv 
        is entering Low Power state <Condtype> 
        MSA_HIGH_POWER_DOWN <Probcause> 
        informationalStatus(1000) <Alarmtype> 
        other (1) <Polarity> (2) 
        "
	  ::= { pm10010mrAlmmsaModuleState 9 }



pm10010mrAlmMsaTxTurnOff OBJECT-TYPE
	  SYNTAX EkiOnOff
	  MAX-ACCESS read-only
	  STATUS current
	  DESCRIPTION
        "
        Line Trscv Laser Turn Off :This 
        OID indicates the Line Trscv is 
        turning off its laser <Help> Status 
        indicating the Line Trscv is turning 
        off its laser <Condtype> MSA_TX_TURN_OFF 
        <Probcause> informationalStatus(1000) 
        <Alarmtype> other (1) <Polarity> 
        (2) 
        "
	  ::= { pm10010mrAlmmsaModuleState 8 }



pm10010mrAlmMsaFault OBJECT-TYPE
	  SYNTAX EkiOnOff
	  MAX-ACCESS read-only
	  STATUS current
	  DESCRIPTION
        "
        Line Trscv Fault :This OID indicates 
        the Line Trscv is in Fault state 
        <Help> Status indicating the Line 
        Trscv is in Fault state <Condtype> 
        MSA_FAULT <Probcause> informationalStatus(1000) 
        <Alarmtype> other (1) <Polarity> 
        (2) 
        "
	  ::= { pm10010mrAlmmsaModuleState 7 }



pm10010mrAlmMsaReady OBJECT-TYPE
	  SYNTAX EkiOnOff
	  MAX-ACCESS read-only
	  STATUS current
	  DESCRIPTION
        "
        Line Trscv Ready :This OID indicates 
        the Line Trscv is ready to operate 
        <Help> Status indicating the Line 
        Trscv is ready to operate <Condtype> 
        MSA_READY <Probcause> informationalStatus(1000) 
        <Alarmtype> other (1) <Polarity> 
        (2) 
        "
	  ::= { pm10010mrAlmmsaModuleState 6 }



pm10010mrAlmMsaTxTurnOn OBJECT-TYPE
	  SYNTAX EkiOnOff
	  MAX-ACCESS read-only
	  STATUS current
	  DESCRIPTION
        "
        Line Trscv Laser Turn On :This 
        OID indicates the Line Trscv is 
        turning on its laser <Help> Status 
        indicating the Line Trscv is turning 
        on its laser <Condtype> MSA_TX_TURN_ON 
        <Probcause> informationalStatus(1000) 
        <Alarmtype> other (1) <Polarity> 
        (2) 
        "
	  ::= { pm10010mrAlmmsaModuleState 5 }



pm10010mrAlmMsaTxOff OBJECT-TYPE
	  SYNTAX EkiOnOff
	  MAX-ACCESS read-only
	  STATUS current
	  DESCRIPTION
        "
        Line Trscv Laser Shutdown :This 
        OID indicates the Line Trscv Laser 
        is OFF <Help> Status indicating 
        the Line Trscv Laser is OFF <Condtype> 
        MSA_TX_OFF <Probcause> informationalStatus(1000) 
        <Alarmtype> other (1) <Polarity> 
        (2) 
        "
	  ::= { pm10010mrAlmmsaModuleState 4 }



pm10010mrAlmMsaHighPowerUp OBJECT-TYPE
	  SYNTAX EkiOnOff
	  MAX-ACCESS read-only
	  STATUS current
	  DESCRIPTION
        "
        Line Trscv High Power Up :This 
        OID indicates the Line Trscv is 
        leaving Low Power state <Help>
         Status indicating the Line Trscv 
        is leaving Low Power state <Condtype> 
        MSA_HIGH_POWER_UP <Probcause> informationalStatus(1000) 
        <Alarmtype> other (1) <Polarity> 
        (2) 
        "
	  ::= { pm10010mrAlmmsaModuleState 3 }



pm10010mrAlmMsaLowPower OBJECT-TYPE
	  SYNTAX EkiOnOff
	  MAX-ACCESS read-only
	  STATUS current
	  DESCRIPTION
        "
        Line Trscv Low Power :This OID 
        indicates the Line Trscv is in
         low power state <Help> Status
         indicating the Line Trscv is in 
        low power state <Condtype> MSA_LOW_POWER 
        <Probcause> informationalStatus(1000) 
        <Alarmtype> other (1) <Polarity> 
        (2) 
        "
	  ::= { pm10010mrAlmmsaModuleState 2 }



pm10010mrAlmMsaInitialize OBJECT-TYPE
	  SYNTAX EkiOnOff
	  MAX-ACCESS read-only
	  STATUS current
	  DESCRIPTION
        "
        Line Trscv Initialize :This OID 
        indicates the Line Trscv initialization 
        is in progress <Help> Status indicating 
        the Line Trscv initialization is 
        in progress <Condtype> MSA_INITIALIZE 
        <Probcause> informationalStatus(1000) 
        <Alarmtype> other (1) <Polarity> 
        (2) 
        "
	  ::= { pm10010mrAlmmsaModuleState 1 }



--- *****************************************************
---     LEAF for the msaModuleGeneralStatus article
--- *****************************************************
pm10010mrAlmmsaModuleGeneralStatus OBJECT IDENTIFIER ::= { pm10010mrAlmOtherCrit 47 }




pm10010mrAlmMsaHwInterlock OBJECT-TYPE
	  SYNTAX EkiOnOff
	  MAX-ACCESS read-only
	  STATUS current
	  DESCRIPTION
        "
        Line Trscv Hardware Interlock
         :This OID indicates the Line Trscv 
        power is higher than the cooling 
        capacity <Help> Alarm indicating 
        the Line Trscv power is higher
         than the cooling capacity <Condtype> 
        MSA_HW_INTERLOCK <Probcause> temperatureUnacceptable 
        (51) <Alarmtype> equipmentAlarm 
        (5) <Polarity> (2) 
        "
	  ::= { pm10010mrAlmmsaModuleGeneralStatus 14 }



pm10010mrAlmMsaLossOfRefclk OBJECT-TYPE
	  SYNTAX EkiOnOff
	  MAX-ACCESS read-only
	  STATUS current
	  DESCRIPTION
        "
        Line Trscv Loss Of Ref Clock :This 
        OID indicates a Loss of Reference 
        clock is detected on the Line Trscv 
        <Help> Alarm indicating a Loss
         of Reference clock is detected 
        on the Line Trscv <Condtype> MSA_LOSS_OF_REFCLK 
        <Probcause> inputOutputDeviceError 
        (24) <Alarmtype> equipmentAlarm 
        (5) <Polarity> (2) 
        "
	  ::= { pm10010mrAlmmsaModuleGeneralStatus 11 }



pm10010mrAlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help> 
        Alarm indicating a Tx Jitter PLL 
        Loss of Lock is detected on the 
        Line Trscv <Condtype> MSA_TX_JITTER_PLL_LOL 
        <Probcause> inputOutputDeviceError 
        (24) <Alarmtype> equipmentAlarm 
        (5) <Polarity> (2) 
        "
	  ::= { pm10010mrAlmmsaModuleGeneralStatus 10 }



pm10010mrAlmMsaTxCmuLol OBJECT-TYPE
	  SYNTAX EkiOnOff
	  MAX-ACCESS read-only
	  STATUS current
	  DESCRIPTION
        "
        Line Trscv CMU Loss Of Lock :This 
        OID indicates a Clock Multiplier 
        Unit Loss of Lock is detected on 
        the Line Trscv <Help> Alarm indicating 
        a Clock Multiplier Unit Loss of 
        Lock is detected on the Line Trscv 
        <Condtype> MSA_TX_CMU_LOL <Probcause> 
        inputOutputDeviceError (24) <Alarmtype> 
        equipmentAlarm (5) <Polarity> (2) 
        "
	  ::= { pm10010mrAlmmsaModuleGeneralStatus 9 }



pm10010mrAlmMsaTxLosf OBJECT-TYPE
	  SYNTAX EkiOnOff
	  MAX-ACCESS read-only
	  STATUS current
	  DESCRIPTION
        "
        Line Trscv Loss Of Signal Functionality 
        :This OID indicates a Loss of Signal 
        functionality is detected on the 
        Line Trscv <Help> Alarm indicating 
        a Loss of Signal functionality
         is detected on the Line Trscv
         <Condtype> MSA_TX_LOSF <Probcause> 
        lossOfSignal (30) <Alarmtype> equipmentAlarm 
        (5) <Polarity> (2) 
        "
	  ::= { pm10010mrAlmmsaModuleGeneralStatus 8 }



pm10010mrAlmMsaTxHostLol OBJECT-TYPE
	  SYNTAX EkiOnOff
	  MAX-ACCESS read-only
	  STATUS current
	  DESCRIPTION
        "
        Line Trscv Tx Host Loss Of Lock 
        :This OID indicates of Loss of
         Lock is detected on the Line Trscv 
        Tx Host interface <Help> Alarm
         indicating of Loss of Lock is
         detected on the Line Trscv Tx
         Host interface <Condtype> MSA_TX_HOST_LOL 
        <Probcause> receiverFailure (42) 
        <Alarmtype> equipmentAlarm (5)
         <Polarity> (2) 
        "
	  ::= { pm10010mrAlmmsaModuleGeneralStatus 7 }



pm10010mrAlmMsaRxLos OBJECT-TYPE
	  SYNTAX EkiOnOff
	  MAX-ACCESS read-only
	  STATUS current
	  DESCRIPTION
        "
        Line Trscv Loss Of Signal :This 
        OID indicates a Loss of Signal
         is detected on the Line Trscv
         <Help> Alarm indicating a Loss 
        of Signal is detected on the Line 
        Trscv <Condtype> MSA_RX_LOS <Probcause> 
        lossOfSignal (30) <Alarmtype> equipmentAlarm 
        (5) <Polarity> (2) 
        "
	  ::= { pm10010mrAlmmsaModuleGeneralStatus 6 }



pm10010mrAlmMsaRxNetworkLol OBJECT-TYPE
	  SYNTAX EkiOnOff
	  MAX-ACCESS read-only
	  STATUS current
	  DESCRIPTION
        "
        Line Trscv Rx Network Loss Of
         Lock :This OID indicates of Loss 
        of Lock is detected on the Line 
        Trscv Rx Network interface <Help> 
        Alarm indicating of Loss of Lock 
        is detected on the Line Trscv Rx 
        Network interface <Condtype> MSA_RX_NETWORK_LOL 
        <Probcause> receiverFailure (42) 
        <Alarmtype> equipmentAlarm (5)
         <Polarity> (2) 
        "
	  ::= { pm10010mrAlmmsaModuleGeneralStatus 5 }



pm10010mrAlmMsaOutOfAlignment OBJECT-TYPE
	  SYNTAX EkiOnOff
	  MAX-ACCESS read-only
	  STATUS current
	  DESCRIPTION
        "
        Line Trscv Out Of Alignment :This 
        OID indicates an Out of alignment 
        on the Line Trscv Host Interface 
        <Help> Alarm indicating an Out
         of alignment on the Line Trscv 
        Host Interface <Condtype> MSA_OUT_OF_ALIGNMENT 
        <Probcause> receiverFailure (42) 
        <Alarmtype> equipmentAlarm (5)
         <Polarity> (2) 
        "
	  ::= { pm10010mrAlmmsaModuleGeneralStatus 4 }



--- *****************************************************
---     LEAF for the msaGlobalAlarmSummary article
--- *****************************************************
pm10010mrAlmmsaGlobalAlarmSummary OBJECT IDENTIFIER ::= { pm10010mrAlmOtherCrit 48 }




pm10010mrAlmMsaGlobAlarmAssertion  OBJECT-TYPE
	  SYNTAX EkiOnOff
	  MAX-ACCESS read-only
	  STATUS current
	  DESCRIPTION
        "
        Line Trscv Global Alarm :This
         OID indicates at least one Fault 
        or Status is detected on the Line 
        Trscv module <Help> Synthesis alarm 
        indicating at least one Alarm,
         Warning, Fault or Status is detected 
        on the Line Trscv module <Condtype> 
        MSA_GLOB_ALARM_ASSERTION  <Probcause> 
        informationalStatus(1000) <Alarmtype> 
        other (1) <Polarity> (2) 
        "
	  ::= { pm10010mrAlmmsaGlobalAlarmSummary 16 }



pm10010mrAlmMsaHostLaneFaultStatus  OBJECT-TYPE
	  SYNTAX EkiOnOff
	  MAX-ACCESS read-only
	  STATUS current
	  DESCRIPTION
        "
        Line Trscv Host Fault And Status 
        :This OID indicates at least one 
        Fault or Status is detected on
         the Line Trscv Host Interface
         <Help> Synthesis alarm indicating 
        at least one Fault or Status is 
        detected on the Line Trscv Host 
        Interface <Condtype> MSA_HOST_LANE_FAULT_STATUS 
         <Probcause> informationalStatus(1000) 
        <Alarmtype> other (1) <Polarity> 
        (2) 
        "
	  ::= { pm10010mrAlmmsaGlobalAlarmSummary 15 }



pm10010mrAlmMsaNetworkLaneFaultStatus  OBJECT-TYPE
	  SYNTAX EkiOnOff
	  MAX-ACCESS read-only
	  STATUS current
	  DESCRIPTION
        "
        Line Trscv Network Fault And Status 
        :This OID indicates at least one 
        Fault or Status is detected on
         the Line Trscv Network Interface 
        <Help> Synthesis alarm indicating 
        at least one Fault or Status is 
        detected on the Line Trscv Network 
        Interface <Condtype> MSA_NETWORK_LANE_FAULT_STATUS 
         <Probcause> informationalStatus(1000) 
        <Alarmtype> other (1) <Polarity> 
        (2) 
        "
	  ::= { pm10010mrAlmmsaGlobalAlarmSummary 14 }



pm10010mrAlmMsaNetworkLaneAlarmWarning1 OBJECT-TYPE
	  SYNTAX EkiOnOff
	  MAX-ACCESS read-only
	  STATUS current
	  DESCRIPTION
        "
        Line Trscv Network Alarm And Warning 
        1 :This OID indicates at least
         one DDM is detected on the Line 
        Trscv Network Interface <Help>
         Synthesis alarm indicating at
         least one DDM Alarm or DDM Warning 
        is detected on the Line Trscv Network 
        Interface <Condtype> MSA_NETWORK_LANE_ALARM_WARNING_1 
        <Probcause> informationalStatus(1000) 
        <Alarmtype> other (1) <Polarity> 
        (2) 
        "
	  ::= { pm10010mrAlmmsaGlobalAlarmSummary 13 }



pm10010mrAlmMsaModuleAlarmWarning2 OBJECT-TYPE
	  SYNTAX EkiOnOff
	  MAX-ACCESS read-only
	  STATUS current
	  DESCRIPTION
        "
        Line Trscv Module Alarm And Warning 
        2 :This OID indicates at least
         one DDM is detected on the Line 
        Trscv module <Help> Synthesis alarm 
        indicating at least one DDM Alarm 
        or DDM Warning is detected on the 
        Line Trscv module <Condtype> MSA_MODULE_ALARM_WARNING_2 
        <Probcause> informationalStatus(1000) 
        <Alarmtype> other (1) <Polarity> 
        (2) 
        "
	  ::= { pm10010mrAlmmsaGlobalAlarmSummary 12 }



pm10010mrAlmMsaModuleAlarmWarning1  OBJECT-TYPE
	  SYNTAX EkiOnOff
	  MAX-ACCESS read-only
	  STATUS current
	  DESCRIPTION
        "
        Line Trscv Module Alarm And Warning 
        1 :This OID indicates at least
         one DDM is detected on the Line 
        Trscv module <Help> Synthesis alarm 
        indicating at least one DDM Alarm 
        or DDM Warning is detected on the 
        Line Trscv module <Condtype> MSA_MODULE_ALARM_WARNING_1 
         <Probcause> informationalStatus(1000) 
        <Alarmtype> other (1) <Polarity> 
        (2) 
        "
	  ::= { pm10010mrAlmmsaGlobalAlarmSummary 11 }



pm10010mrAlmModuleFault  OBJECT-TYPE
	  SYNTAX EkiOnOff
	  MAX-ACCESS read-only
	  STATUS current
	  DESCRIPTION
        "
        Line Trscv Module Fault :This
         OID indicates at least one Fault 
        is detected on the Line Trscv module 
        <Help> Synthesis alarm indicating 
        at least one Fault is detected
         on the Line Trscv module <Condtype> 
        MODULE_FAULT  <Probcause> informationalStatus(1000) 
        <Alarmtype> other (1) <Polarity> 
        (2) 
        "
	  ::= { pm10010mrAlmmsaGlobalAlarmSummary 10 }



pm10010mrAlmMsaModuleGeneralStatus  OBJECT-TYPE
	  SYNTAX EkiOnOff
	  MAX-ACCESS read-only
	  STATUS current
	  DESCRIPTION
        "
        Line Trscv General Status :This 
        OID indicates the Line Trscv module 
        general <Help> Synthesis alarm
         indicating the Line Trscv module 
        general status <Condtype> MSA_MODULE_GENERAL_STATUS 
         <Probcause> informationalStatus(1000) 
        <Alarmtype> other (1) <Polarity> 
        (2) 
        "
	  ::= { pm10010mrAlmmsaGlobalAlarmSummary 9 }



pm10010mrAlmMsaModuleState  OBJECT-TYPE
	  SYNTAX EkiOnOff
	  MAX-ACCESS read-only
	  STATUS current
	  DESCRIPTION
        "
        Line Trscv Module State :This
         OID indicates the Line Trscv module 
        state <Help> Synthesis alarm indicating 
        the Line Trscv module state <Condtype> 
        MSA_MODULE_STATE  <Probcause> informationalStatus(1000) 
        <Alarmtype> other (1) <Polarity> 
        (2) 
        "
	  ::= { pm10010mrAlmmsaGlobalAlarmSummary 8 }



pm10010mrAlmMsaNetworkLaneAlarmWarning2 OBJECT-TYPE
	  SYNTAX EkiOnOff
	  MAX-ACCESS read-only
	  STATUS current
	  DESCRIPTION
        "
        Line Trscv Network Alarm And Warning 
        2 :This OID indicates at least
         one DDM This OID is detected on 
        the Line Trscv Network Interface 
        <Help> Synthesis alarm indicating 
        at least one DDM Alarm or DDM Warning 
        is detected on the Line Trscv Network 
        Interface <Condtype> MSA_NETWORK_LANE_ALARM_WARNING_2 
        <Probcause> informationalStatus(1000) 
        <Alarmtype> other (1) <Polarity> 
        (2) 
        "
	  ::= { pm10010mrAlmmsaGlobalAlarmSummary 7 }



pm10010mrAlmMsaNetworkHostAlarmStatus OBJECT-TYPE
	  SYNTAX EkiOnOff
	  MAX-ACCESS read-only
	  STATUS current
	  DESCRIPTION
        "
        Line Trscv Network/Host Alarm
         Status :This OID indicates the 
        state of the Network and Host interface 
        of the Line Trscv <Help> Synthesis 
        alarm indicating the alarm state 
        of the Network and Host interface 
        of the Line Trscv <Condtype> MSA_NETWORK_HOST_ALARM_STATUS 
        <Probcause> informationalStatus(1000) 
        <Alarmtype> other (1) <Polarity> 
        (2) 
        "
	  ::= { pm10010mrAlmmsaGlobalAlarmSummary 6 }



pm10010mrAlmMsaSoftGlobAlarmTest  OBJECT-TYPE
	  SYNTAX EkiOnOff
	  MAX-ACCESS read-only
	  STATUS current
	  DESCRIPTION
        "
        Line Trscv Global Alarm SW Test 
        :This OID indicates the Line Trscv 
        Global alarm This OID is raised 
        by SW request for test purpose
         <Help> Status indicating the Line 
        Trscv Global Alarm is raised by 
        SW request for test purpose <Condtype> 
        MSA_SOFT_GLOB_ALARM_TEST  <Probcause> 
        informationalStatus(1000) <Alarmtype> 
        other (1) <Polarity> (2) 
        "
	  ::= { pm10010mrAlmmsaGlobalAlarmSummary 1 }



--- *****************************************************
---     LEAF for the msaNetworkTxAlignment article
--- *****************************************************
pm10010mrAlmmsaNetworkTxAlignment OBJECT IDENTIFIER ::= { pm10010mrAlmOtherCrit 49 }




pm10010mrAlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected 
        on the Line Trscv Network interface 
        <Help> Alarm indicating a Tx Loss 
        of Alignment is detected on the 
        Line Trscv Network interface <Condtype> 
        NET_TX_LOSS_OF_ALIGNMENT <Probcause> 
        transmitterFailure (56) <Alarmtype> 
        equipmentAlarm (5) <Polarity> (2) 
        "
	  ::= { pm10010mrAlmmsaNetworkTxAlignment 16 }



pm10010mrAlmNetTxOutOfAlignment OBJECT-TYPE
	  SYNTAX EkiOnOff
	  MAX-ACCESS read-only
	  STATUS current
	  DESCRIPTION
        "
        Line Trscv Network Tx Out Of Alignment 
        :This OID indicates a Tx Out of 
        Alignment is detected on the Line 
        Trscv Network interface <Help>
         Alarm indicating a Tx Out of Alignment 
        is detected on the Line Trscv Network 
        interface <Condtype> NET_TX_OUT_OF_ALIGNMENT 
        <Probcause> transmitterFailure
         (56) <Alarmtype> equipmentAlarm 
        (5) <Polarity> (2) 
        "
	  ::= { pm10010mrAlmmsaNetworkTxAlignment 15 }



pm10010mrAlmNetTxCmuLockFault OBJECT-TYPE
	  SYNTAX EkiOnOff
	  MAX-ACCESS read-only
	  STATUS current
	  DESCRIPTION
        "
        Line Trscv Network Tx CMU Lock 
        Fault :This OID indicates a Tx
         Clock Multiplier Unit Lock Fault 
        is detected on the Line Trscv Network 
        interface <Help> Alarm indicating 
        a Tx Clock Multiplier Unit Lock 
        Fault is detected on the Line Trscv 
        Network interface <Condtype> NET_TX_CMU_LOCK_FAULT 
        <Probcause> transmitterFailure
         (56) <Alarmtype> equipmentAlarm 
        (5) <Polarity> (2) 
        "
	  ::= { pm10010mrAlmmsaNetworkTxAlignment 14 }



pm10010mrAlmNetTxReferenceClockFault OBJECT-TYPE
	  SYNTAX EkiOnOff
	  MAX-ACCESS read-only
	  STATUS current
	  DESCRIPTION
        "
        Line Trscv Network Tx Ref Clock 
        Fault :This OID indicates a Tx
         Reference Clock Fault is detected 
        on the Line Trscv Network interface 
        <Help> Alarm indicating a Tx Reference 
        Clock Fault is detected on the
         Line Trscv Network interface <Condtype> 
        NET_TX_REFERENCE_CLOCK_FAULT <Probcause> 
        transmitterFailure (56) <Alarmtype> 
        equipmentAlarm (5) <Polarity> (2) 
        "
	  ::= { pm10010mrAlmmsaNetworkTxAlignment 13 }



pm10010mrAlmNetTxTimingFault OBJECT-TYPE
	  SYNTAX EkiOnOff
	  MAX-ACCESS read-only
	  STATUS current
	  DESCRIPTION
        "
        Line Trscv Network Tx Timing Fault 
        :This OID indicates a Tx Timing 
        Fault is detected on the Line Trscv 
        Network interface <Help> Alarm
         indicating a Tx Timing Fault is 
        detected on the Line Trscv Network 
        interface <Condtype> NET_TX_TIMING_FAULT 
        <Probcause> transmitterFailure
         (56) <Alarmtype> equipmentAlarm 
        (5) <Polarity> (2) 
        "
	  ::= { pm10010mrAlmmsaNetworkTxAlignment 12 }



--- *****************************************************
---     LEAF for the msaNetworkRxAlignment article
--- *****************************************************
pm10010mrAlmmsaNetworkRxAlignment OBJECT IDENTIFIER ::= { pm10010mrAlmOtherCrit 50 }




pm10010mrAlmNetRxModemSyncDetectFault OBJECT-TYPE
	  SYNTAX EkiOnOff
	  MAX-ACCESS read-only
	  STATUS current
	  DESCRIPTION
        "
        Line Trscv Network Rx Modem Sync 
        Detect Fault :This OID indicates 
        a Rx Modem Synchronisation Detection 
        Fault is detected on the Line Trscv 
        Network interface <Help> Alarm
         indicating a Rx Modem Synchronisation 
        Detection Fault is detected on
         the Line Trscv Network interface 
        <Condtype> NET_RX_MODEM_SYNC_DETECT_FAULT 
        <Probcause> receiverFailure (42) 
        <Alarmtype> equipmentAlarm (5)
         <Polarity> (2) 
        "
	  ::= { pm10010mrAlmmsaNetworkRxAlignment 16 }



pm10010mrAlmNetRxModemLockFault OBJECT-TYPE
	  SYNTAX EkiOnOff
	  MAX-ACCESS read-only
	  STATUS current
	  DESCRIPTION
        "
        Line Trscv Network Rx Modem Lock 
        Fault :This OID indicates a Rx
         Modem Lock Fault is detected on 
        the Line Trscv Network interface 
        <Help> Alarm indicating a Rx Modem 
        Lock Fault is detected on the Line 
        Trscv Network interface <Condtype> 
        NET_RX_MODEM_LOCK_FAULT <Probcause> 
        receiverFailure (42) <Alarmtype> 
        equipmentAlarm (5) <Polarity> (2) 
        "
	  ::= { pm10010mrAlmmsaNetworkRxAlignment 15 }



pm10010mrAlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected 
        on the Line Trscv Network interface 
        <Help> Alarm indicating a Rx Loss 
        of Alignment is detected on the 
        Line Trscv Network interface <Condtype> 
        NET_RX_LOSS_OF_ALIGNMENT <Probcause> 
        receiverFailure (42) <Alarmtype> 
        equipmentAlarm (5) <Polarity> (2) 
        "
	  ::= { pm10010mrAlmmsaNetworkRxAlignment 14 }



pm10010mrAlmNetRxOutOfAlignment OBJECT-TYPE
	  SYNTAX EkiOnOff
	  MAX-ACCESS read-only
	  STATUS current
	  DESCRIPTION
        "
        Line Trscv Network Rx Out Of Alignment 
        :This OID indicates a Rx Out of 
        Alignment is detected on the Line 
        Trscv Network interface <Help>
         Alarm indicating a Rx Out of Alignment 
        is detected on the Line Trscv Network 
        interface <Condtype> NET_RX_OUT_OF_ALIGNMENT 
        <Probcause> receiverFailure (42) 
        <Alarmtype> equipmentAlarm (5)
         <Polarity> (2) 
        "
	  ::= { pm10010mrAlmmsaNetworkRxAlignment 13 }



pm10010mrAlmNetRxTimingFault OBJECT-TYPE
	  SYNTAX EkiOnOff
	  MAX-ACCESS read-only
	  STATUS current
	  DESCRIPTION
        "
        Line Trscv Network Rx Timing Fault 
        :This OID indicates a Rx Timing 
        Fault is detected on the Line Trscv 
        Network interface <Help> Alarm
         indicating a Rx Timing Fault is 
        detected on the Line Trscv Network 
        interface <Condtype> NET_RX_TIMING_FAULT 
        <Probcause> receiverFailure (42) 
        <Alarmtype> equipmentAlarm (5)
         <Polarity> (2) 
        "
	  ::= { pm10010mrAlmmsaNetworkRxAlignment 12 }



--- *****************************************************
---     LEAF for the msaNetworkHostNetworkAlarmSummary article
--- *****************************************************
pm10010mrAlmmsaNetworkHostNetworkAlarmSummary OBJECT IDENTIFIER ::= { pm10010mrAlmOtherCrit 51 }




pm10010mrAlmHostTxOtnStatus OBJECT-TYPE
	  SYNTAX EkiOnOff
	  MAX-ACCESS read-only
	  STATUS current
	  DESCRIPTION
        "
        Line Trscv Host Tx OTN :This OID 
        indicates a Tx OTN Fault is detected 
        on the Line Trscv Host interface 
        <Help> Synthesis Alarm indicating 
        a Tx OTN Fault is detected on the 
        Line Trscv Host interface <Condtype> 
        HOST_TX_OTN_STATUS <Probcause>
         informationalStatus(1000) <Alarmtype> 
        other (1) <Polarity> (2) 
        "
	  ::= { pm10010mrAlmmsaNetworkHostNetworkAlarmSummary 16 }



pm10010mrAlmHostTxAlignment OBJECT-TYPE
	  SYNTAX EkiOnOff
	  MAX-ACCESS read-only
	  STATUS current
	  DESCRIPTION
        "
        Line Trscv Host Tx Alignment :This 
        OID indicates a Tx Alignment Fault 
        is detected on the Line Trscv Host 
        interface <Help> Synthesis Alarm 
        indicating a Tx Alignment Fault 
        is detected on the Line Trscv Host 
        interface <Condtype> HOST_TX_ALIGNMENT 
        <Probcause> informationalStatus(1000) 
        <Alarmtype> other (1) <Polarity> 
        (2) 
        "
	  ::= { pm10010mrAlmmsaNetworkHostNetworkAlarmSummary 15 }



pm10010mrAlmHostRxAlignment OBJECT-TYPE
	  SYNTAX EkiOnOff
	  MAX-ACCESS read-only
	  STATUS current
	  DESCRIPTION
        "
        Line Trscv Host Rx Alignment :This 
        OID indicates a Rx Alignment Fault 
        is detected on the Line Trscv Host 
        interface <Help> Synthesis Alarm 
        indicating a Rx Alignment Fault 
        is detected on the Line Trscv Host 
        interface <Condtype> HOST_RX_ALIGNMENT 
        <Probcause> informationalStatus(1000) 
        <Alarmtype> other (1) <Polarity> 
        (2) 
        "
	  ::= { pm10010mrAlmmsaNetworkHostNetworkAlarmSummary 14 }



pm10010mrAlmNetworkRxOtn OBJECT-TYPE
	  SYNTAX EkiOnOff
	  MAX-ACCESS read-only
	  STATUS current
	  DESCRIPTION
        "
        Line Trscv Network Rx OTN :This 
        OID indicates a Rx OTN Fault is 
        detected on the Line Trscv Network 
        interface <Help> Synthesis Alarm 
        indicating a Rx OTN Fault is detected 
        on the Line Trscv Network interface 
        <Condtype> NETWORK_RX_OTN <Probcause> 
        informationalStatus(1000) <Alarmtype> 
        other (1) <Polarity> (2) 
        "
	  ::= { pm10010mrAlmmsaNetworkHostNetworkAlarmSummary 13 }



pm10010mrAlmNetworkRxAlignment OBJECT-TYPE
	  SYNTAX EkiOnOff
	  MAX-ACCESS read-only
	  STATUS current
	  DESCRIPTION
        "
        Line Trscv Network Rx Alignment 
        :This OID indicates a Rx Alignment 
        Fault is detected on the Line Trscv 
        Network interface <Help> Synthesis 
        Alarm indicating a Rx Alignment 
        Fault is detected on the Line Trscv 
        Network interface <Condtype> NETWORK_RX_ALIGNMENT 
        <Probcause> informationalStatus(1000) 
        <Alarmtype> other (1) <Polarity> 
        (2) 
        "
	  ::= { pm10010mrAlmmsaNetworkHostNetworkAlarmSummary 12 }



pm10010mrAlmNetworkTxAlignment OBJECT-TYPE
	  SYNTAX EkiOnOff
	  MAX-ACCESS read-only
	  STATUS current
	  DESCRIPTION
        "
        Line Trscv Network Tx Alignment 
        :This OID indicates a Tx Alignment 
        Fault is detected on the Line Trscv 
        Network interface <Help> Synthesis 
        Alarm indicating a Tx Alignment 
        Fault is detected on the Line Trscv 
        Network interface <Condtype> NETWORK_TX_ALIGNMENT 
        <Probcause> informationalStatus(1000) 
        <Alarmtype> other (1) <Polarity> 
        (2) 
        "
	  ::= { pm10010mrAlmmsaNetworkHostNetworkAlarmSummary 11 }



--- *****************************************************
---     LEAF for the msaHostTxAlignment article
--- *****************************************************
pm10010mrAlmmsaHostTxAlignment OBJECT IDENTIFIER ::= { pm10010mrAlmOtherCrit 52 }




pm10010mrAlmHostTxCdrLockFault OBJECT-TYPE
	  SYNTAX EkiOnOff
	  MAX-ACCESS read-only
	  STATUS current
	  DESCRIPTION
        "
        Line Trscv Host Tx CDR Lock Fault 
        :This OID indicates a Tx Clock
         Data Recovery Lock Fault is detected 
        on the Line Trscv Host interface 
        <Help> Alarm indicating a Tx Clock 
        Data Recovery Lock Fault is detected 
        on the Line Trscv Host interface 
        <Condtype> HOST_TX_CDR_LOCK_FAULT 
        <Probcause> receiverFailure (42) 
        <Alarmtype> equipmentAlarm (5)
         <Polarity> (2) 
        "
	  ::= { pm10010mrAlmmsaHostTxAlignment 16 }



pm10010mrAlmHostTxLossOfAlignment OBJECT-TYPE
	  SYNTAX EkiOnOff
	  MAX-ACCESS read-only
	  STATUS current
	  DESCRIPTION
        "
        Line Trscv Host Tx Loss Of Alignment 
        :This OID indicates a Tx Loss of 
        Alignment is detected on the Line 
        Trscv Host interface <Help> Alarm 
        indicating a Tx Loss of Alignment 
        is detected on the Line Trscv Host 
        interface <Condtype> HOST_TX_LOSS_OF_ALIGNMENT 
        <Probcause> receiverFailure (42) 
        <Alarmtype> equipmentAlarm (5)
         <Polarity> (2) 
        "
	  ::= { pm10010mrAlmmsaHostTxAlignment 15 }



pm10010mrAlmHostTxOutOfAlignment OBJECT-TYPE
	  SYNTAX EkiOnOff
	  MAX-ACCESS read-only
	  STATUS current
	  DESCRIPTION
        "
        Line Trscv Host Tx Out Of Alignment 
        :This OID indicates a Tx Out of 
        Alignment is detected on the Line 
        Trscv Host interface <Help> Alarm 
        indicating a Tx Out of Alignment 
        is detected on the Line Trscv Host 
        interface <Condtype> HOST_TX_OUT_OF_ALIGNMENT 
        <Probcause> receiverFailure (42) 
        <Alarmtype> equipmentAlarm (5)
         <Polarity> (2) 
        "
	  ::= { pm10010mrAlmmsaHostTxAlignment 14 }



pm10010mrAlmHostTxDeskewLockFault OBJECT-TYPE
	  SYNTAX EkiOnOff
	  MAX-ACCESS read-only
	  STATUS current
	  DESCRIPTION
        "
        Line Trscv Host Tx Deskew Lock 
        Fault :This OID indicates a Tx
         Deskew Lock Fault is detected
         on  the Line Trscv Host interface 
        <Help> Alarm indicating a Tx Deskew 
        Lock Fault is detected on  the
         Line Trscv Host interface <Condtype> 
        HOST_TX_DESKEW_LOCK_FAULT <Probcause> 
        receiverFailure (42) <Alarmtype> 
        equipmentAlarm (5) <Polarity> (2) 
        "
	  ::= { pm10010mrAlmmsaHostTxAlignment 13 }



--- *****************************************************
---     LEAF for the msaHostRxAlignment article
--- *****************************************************
pm10010mrAlmmsaHostRxAlignment OBJECT IDENTIFIER ::= { pm10010mrAlmOtherCrit 53 }




pm10010mrAlmHostRxLossOfAlignment OBJECT-TYPE
	  SYNTAX EkiOnOff
	  MAX-ACCESS read-only
	  STATUS current
	  DESCRIPTION
        "
        Line Trscv Host Rx Loss Of Alignment 
        :This OID indicates a Rx Loss of 
        Alignment is detected on the Line 
        Trscv Host interface <Help> Alarm 
        indicating a Rx Loss of Alignment 
        is detected on the Line Trscv Host 
        interface <Condtype> HOST_RX_LOSS_OF_ALIGNMENT 
        <Probcause> transmitterFailure
         (56) <Alarmtype> equipmentAlarm 
        (5) <Polarity> (2) 
        "
	  ::= { pm10010mrAlmmsaHostRxAlignment 16 }



pm10010mrAlmHostRxOutOfAlignment OBJECT-TYPE
	  SYNTAX EkiOnOff
	  MAX-ACCESS read-only
	  STATUS current
	  DESCRIPTION
        "
        Line Trscv Host Rx Out Of Alignment 
        :This OID indicates a Rx Out of 
        Alignment is detected on the Line 
        Trscv Host interface <Help> Alarm 
        indicating a Rx Out of Alignment 
        is detected on the Line Trscv Host 
        interface <Condtype> HOST_RX_OUT_OF_ALIGNMENT 
        <Probcause> transmitterFailure
         (56) <Alarmtype> equipmentAlarm 
        (5) <Polarity> (2) 
        "
	  ::= { pm10010mrAlmmsaHostRxAlignment 15 }



pm10010mrAlmHostRxCmuLockFault OBJECT-TYPE
	  SYNTAX EkiOnOff
	  MAX-ACCESS read-only
	  STATUS current
	  DESCRIPTION
        "
        Line Trscv Host Rx CMU Lock Fault 
        :This OID indicates a Rx Clock
         Multiplier Unit Lock Fault is
         detected on the Line Trscv Host 
        interface <Help> Alarm indicating 
        a Rx Clock Multiplier Unit Lock 
        Fault is detected on the Line Trscv 
        Host interface <Condtype> HOST_RX_CMU_LOCK_FAULT 
        <Probcause> transmitterFailure
         (56) <Alarmtype> equipmentAlarm 
        (5) <Polarity> (2) 
        "
	  ::= { pm10010mrAlmmsaHostRxAlignment 14 }



--- *********************************************************
---     TABLE for the pm10010mrAlmclientNetworkLaneAlarmWarning articles
--- *********************************************************

pm10010mrAlmclientNetworkLaneAlarmWarningTable OBJECT-TYPE
	SYNTAX  SEQUENCE OF Pm10010mrAlmclientNetworkLaneAlarmWarningEntry
	MAX-ACCESS not-accessible
	STATUS current
	DESCRIPTION
        "
        List of pm10010mrAlmclientNetworkLaneAlarmWarning 
        Article
        "
	::= { pm10010mrAlmClientNurg 56 }


pm10010mrAlmclientNetworkLaneAlarmWarningEntry OBJECT-TYPE
	SYNTAX Pm10010mrAlmclientNetworkLaneAlarmWarningEntry
	MAX-ACCESS not-accessible
	STATUS current
	DESCRIPTION
        "
        Row definition for the pm10010mrAlmclientNetworkLaneAlarmWarning 
        table
        "
	INDEX   { pm10010mrAlmclientNetworkLaneAlarmWarningIndex }
	::= { pm10010mrAlmclientNetworkLaneAlarmWarningTable 1 }


Pm10010mrAlmclientNetworkLaneAlarmWarningEntry ::=
	SEQUENCE {
	pm10010mrAlmclientNetworkLaneAlarmWarningIndex
		INTEGER,
	pm10010mrAlmClientBiasHighAlarmPortn
		EkiOnOff,
	pm10010mrAlmClientBiasHighWarningPortn
		EkiOnOff,
	pm10010mrAlmClientBiasLowWarningPortn
		EkiOnOff,
	pm10010mrAlmClientBiasLowAlarmPortn
		EkiOnOff,
	pm10010mrAlmClientTxPowerHighAlarmPortn
		EkiOnOff,
	pm10010mrAlmClientTxPowerHighWarningPortn
		EkiOnOff,
	pm10010mrAlmClientTxPowerLowWarningPortn
		EkiOnOff,
	pm10010mrAlmClientTxPowerLowAlarmPortn
		EkiOnOff,
	pm10010mrAlmClientLaserTempHighAlarmPortn
		EkiOnOff,
	pm10010mrAlmClientLaserTempHighWarningPortn
		EkiOnOff,
	pm10010mrAlmClientLaserTempLowWarningPortn
		EkiOnOff,
	pm10010mrAlmLaserTempLowAlarmPortn
		EkiOnOff,
	pm10010mrAlmClientRxPowerHighAlarmPortn
		EkiOnOff,
	pm10010mrAlmClientRxPowerHighWarningPortn
		EkiOnOff,
	pm10010mrAlmClientRxPowerLowWarningPortn
		EkiOnOff,
	pm10010mrAlmClientRxPowerLowAlarmPortn
		EkiOnOff
	}


pm10010mrAlmclientNetworkLaneAlarmWarningIndex OBJECT-TYPE
	SYNTAX  INTEGER(0..128)
	MAX-ACCESS  read-only
	STATUS current
	DESCRIPTION
        "
        Index definition for the pm10010mrAlmclientNetworkLaneAlarmWarning 
        table
        "
	::= { pm10010mrAlmclientNetworkLaneAlarmWarningEntry 1 }


pm10010mrAlmClientBiasHighAlarmPortn OBJECT-TYPE
	SYNTAX  EkiOnOff
	MAX-ACCESS read-only
	STATUS current
	DESCRIPTION
        "
        Client Trscv Bias High Alarm :This 
        OID indicates that the Trscv laser 
        bias current is higher than the 
        threshold value written in the
         Trscv EEPROM <Help> Alarm indicating 
        that the Trscv laser bias current 
        is higher than the threshold value 
        written in the Trscv EEPROM <Condtype> 
        CLIENT_BIAS_HIGH_ALARM <Probcause> 
        transmitterFailure (56) <Alarmtype> 
        equipmentAlarm (5) <Polarity> (2) 
        "
	::= { pm10010mrAlmclientNetworkLaneAlarmWarningEntry 17 }


pm10010mrAlmClientBiasHighWarningPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> CLIENT_BIAS_HIGH_WARNING 
        <Probcause> transmitterFailure
         (56) <Alarmtype> equipmentAlarm 
        (5) <Polarity> (2) 
        "
	::= { pm10010mrAlmclientNetworkLaneAlarmWarningEntry 16 }


pm10010mrAlmClientBiasLowWarningPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> CLIENT_BIAS_LOW_WARNING 
        <Probcause> transmitterFailure
         (56) <Alarmtype> equipmentAlarm 
        (5) <Polarity> (2) 
        "
	::= { pm10010mrAlmclientNetworkLaneAlarmWarningEntry 15 }


pm10010mrAlmClientBiasLowAlarmPortn OBJECT-TYPE
	SYNTAX  EkiOnOff
	MAX-ACCESS read-only
	STATUS current
	DESCRIPTION
        "
        Client Trscv Bias Low Alarm :This 
        OID indicates that the Trscv laser 
        bias current is lower than the
         threshold value written in the 
        Trscv EEPROM <Help> Alarm indicating 
        that the Trscv laser bias current 
        is lower than the threshold value 
        written in the Trscv EEPROM <Condtype> 
        CLIENT_BIAS_LOW_ALARM <Probcause> 
        transmitterFailure (56) <Alarmtype> 
        equipmentAlarm (5) <Polarity> (2) 
        "
	::= { pm10010mrAlmclientNetworkLaneAlarmWarningEntry 14 }


pm10010mrAlmClientTxPowerHighAlarmPortn OBJECT-TYPE
	SYNTAX  EkiOnOff
	MAX-ACCESS read-only
	STATUS current
	DESCRIPTION
        "
        Client Trscv Tx Power High Alarm 
        :This OID indicates that the Trscv 
        output power is higher than the 
        threshold value written in the
         Trscv EEPROM <Help> Alarm indicating 
        that the Trscv output power is
         higher than the threshold value 
        written in the Trscv EEPROM <Condtype> 
        CLIENT_TX_POWER_HIGH_ALARM <Probcause> 
        transmitterFailure (56) <Alarmtype> 
        equipmentAlarm (5) <Polarity> (2) 
        "
	::= { pm10010mrAlmclientNetworkLaneAlarmWarningEntry 13 }


pm10010mrAlmClientTxPowerHighWarningPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        CLIENT_TX_POWER_HIGH_WARNING <Probcause> 
        transmitterFailure (56) <Alarmtype> 
        equipmentAlarm (5) <Polarity> (2) 
        "
	::= { pm10010mrAlmclientNetworkLaneAlarmWarningEntry 12 }


pm10010mrAlmClientTxPowerLowWarningPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        CLIENT_TX_POWER_LOW_WARNING <Probcause> 
        transmitterFailure (56) <Alarmtype> 
        equipmentAlarm (5) <Polarity> (2) 
        "
	::= { pm10010mrAlmclientNetworkLaneAlarmWarningEntry 11 }


pm10010mrAlmClientTxPowerLowAlarmPortn OBJECT-TYPE
	SYNTAX  EkiOnOff
	MAX-ACCESS read-only
	STATUS current
	DESCRIPTION
        "
        Client Trscv Tx Power Low Alarm 
        :This OID indicates that the Trscv 
        output power is lower than the
         threshold value written in the 
        Trscv EEPROM <Help> Alarm indicating 
        that the Trscv output power is
         lower than the threshold value 
        written in the Trscv EEPROM <Condtype> 
        CLIENT_TX_POWER_LOW_ALARM <Probcause> 
        transmitterFailure (56) <Alarmtype> 
        equipmentAlarm (5) <Polarity> (2) 
        "
	::= { pm10010mrAlmclientNetworkLaneAlarmWarningEntry 10 }


pm10010mrAlmClientLaserTempHighAlarmPortn OBJECT-TYPE
	SYNTAX  EkiOnOff
	MAX-ACCESS read-only
	STATUS current
	DESCRIPTION
        "
        Client Trscv Laser Temp High Alarm 
        :This OID indicates that the Trscv 
        Laser Temperature is higher than 
        the threshold value written in
         the Trscv EEPROM <Help> Alarm
         indicating that the Trscv Laser 
        Temperature is higher than the
         threshold value written in the 
        Trscv EEPROM <Condtype> CLIENT_LASER_TEMP_HIGH_ALARM 
        <Probcause> temperatureUnacceptable 
        (51) <Alarmtype> equipmentAlarm 
        (5) <Polarity> (2) 
        "
	::= { pm10010mrAlmclientNetworkLaneAlarmWarningEntry 9 }


pm10010mrAlmClientLaserTempHighWarningPortn OBJECT-TYPE
	SYNTAX  EkiOnOff
	MAX-ACCESS read-only
	STATUS current
	DESCRIPTION
        "
        Client Trscv Laser Temp High Warning 
        :This OID indicates that the Trscv 
        Laser Temperature is higher than 
        the threshold value written in
         the Trscv EEPROM <Help> Warning 
        indicating that the Trscv Laser 
        Temperature is higher than the
         threshold value written in the 
        Trscv EEPROM <Condtype> CLIENT_LASER_TEMP_HIGH_WARNING 
        <Probcause> temperatureUnacceptable 
        (51) <Alarmtype> equipmentAlarm 
        (5) <Polarity> (2) 
        "
	::= { pm10010mrAlmclientNetworkLaneAlarmWarningEntry 8 }


pm10010mrAlmClientLaserTempLowWarningPortn OBJECT-TYPE
	SYNTAX  EkiOnOff
	MAX-ACCESS read-only
	STATUS current
	DESCRIPTION
        "
        Client Trscv Laser Temp Low Warning 
        :This OID indicates that the Trscv 
        Laser Temperature is lower than 
        the threshold value written in
         the Trscv EEPROM <Help> Warning 
        indicating that the Trscv Laser 
        Temperature is lower than the threshold 
        value written in the Trscv EEPROM 
        <Condtype> CLIENT_LASER_TEMP_LOW_WARNING 
        <Probcause> temperatureUnacceptable 
        (51) <Alarmtype> equipmentAlarm 
        (5) <Polarity> (2) 
        "
	::= { pm10010mrAlmclientNetworkLaneAlarmWarningEntry 7 }


pm10010mrAlmLaserTempLowAlarmPortn OBJECT-TYPE
	SYNTAX  EkiOnOff
	MAX-ACCESS read-only
	STATUS current
	DESCRIPTION
        "
        Client Trscv Laser Temp Low Alarm 
        :This OID indicates that the Trscv 
        Laser Temperature is lower than 
        the threshold value written in
         the Trscv EEPROM <Help> Alarm
         indicating that the Trscv Laser 
        Temperature is lower than the threshold 
        value written in the Trscv EEPROM 
        <Condtype> LASER_TEMP_LOW_ALARM 
        <Probcause> temperatureUnacceptable 
        (51) <Alarmtype> equipmentAlarm 
        (5) <Polarity> (2) 
        "
	::= { pm10010mrAlmclientNetworkLaneAlarmWarningEntry 6 }


pm10010mrAlmClientRxPowerHighAlarmPortn OBJECT-TYPE
	SYNTAX  EkiOnOff
	MAX-ACCESS read-only
	STATUS current
	DESCRIPTION
        "
        Client Trscv Rx Power High Alarm 
        :This OID indicates that the Trscv 
        input power is higher than the
         threshold value written in the 
        Trscv EEPROM <Help> Alarm indicating 
        that the Trscv input power is higher 
        than the threshold value written 
        in the Trscv EEPROM <Condtype>
         CLIENT_RX_POWER_HIGH_ALARM <Probcause> 
        receiveFailure (41) <Alarmtype> 
        equipmentAlarm (5) <Polarity> (2) 
        "
	::= { pm10010mrAlmclientNetworkLaneAlarmWarningEntry 5 }


pm10010mrAlmClientRxPowerHighWarningPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         CLIENT_RX_POWER_HIGH_WARNING <Probcause> 
        receiveFailure (41) <Alarmtype> 
        equipmentAlarm (5) <Polarity> (2) 
        "
	::= { pm10010mrAlmclientNetworkLaneAlarmWarningEntry 4 }


pm10010mrAlmClientRxPowerLowWarningPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         CLIENT_RX_POWER_LOW_WARNING <Probcause> 
        receiveFailure (41) <Alarmtype> 
        equipmentAlarm (5) <Polarity> (2) 
        "
	::= { pm10010mrAlmclientNetworkLaneAlarmWarningEntry 3 }


pm10010mrAlmClientRxPowerLowAlarmPortn OBJECT-TYPE
	SYNTAX  EkiOnOff
	MAX-ACCESS read-only
	STATUS current
	DESCRIPTION
        "
        Client Trscv Rx Power Low Alarm 
        :This OID indicates that the Trscv 
        input power is lower than the threshold 
        value written in the Trscv EEPROM 
        <Help> Alarm indicating that the 
        Trscv input power is lower than 
        the threshold value written in
         the Trscv EEPROM <Condtype> CLIENT_RX_POWER_LOW_ALARM 
        <Probcause> receiveFailure (41) 
        <Alarmtype> equipmentAlarm (5)
         <Polarity> (2) 
        "
	::= { pm10010mrAlmclientNetworkLaneAlarmWarningEntry 2 }


--- *********************************************************
---     TABLE for the pm10010mrAlmclientNetworkLaneFault articles
--- *********************************************************

pm10010mrAlmclientNetworkLaneFaultTable OBJECT-TYPE
	SYNTAX  SEQUENCE OF Pm10010mrAlmclientNetworkLaneFaultEntry
	MAX-ACCESS not-accessible
	STATUS current
	DESCRIPTION
        "
        List of pm10010mrAlmclientNetworkLaneFault 
        Article
        "
	::= { pm10010mrAlmClientUrg 72 }


pm10010mrAlmclientNetworkLaneFaultEntry OBJECT-TYPE
	SYNTAX Pm10010mrAlmclientNetworkLaneFaultEntry
	MAX-ACCESS not-accessible
	STATUS current
	DESCRIPTION
        "
        Row definition for the pm10010mrAlmclientNetworkLaneFault 
        table
        "
	INDEX   { pm10010mrAlmclientNetworkLaneFaultIndex }
	::= { pm10010mrAlmclientNetworkLaneFaultTable 1 }


Pm10010mrAlmclientNetworkLaneFaultEntry ::=
	SEQUENCE {
	pm10010mrAlmclientNetworkLaneFaultIndex
		INTEGER,
	pm10010mrAlmClientLaneTecFaultPortn
		EkiOnOff,
	pm10010mrAlmClientLaneWavelengthUnlockedPortn
		EkiOnOff,
	pm10010mrAlmClientLaneApdPowerSupplyPortn
		EkiOnOff,
	pm10010mrAlmClientLaneTxLosfPortn
		EkiOnOff,
	pm10010mrAlmClientLaneTxLolPortn
		EkiOnOff,
	pm10010mrAlmClientLaneRxLosPortn
		EkiOnOff,
	pm10010mrAlmClientLaneRxLolPortn
		EkiOnOff,
	pm10010mrAlmClientLaneRxFifoErrorPortn
		EkiOnOff
	}


pm10010mrAlmclientNetworkLaneFaultIndex OBJECT-TYPE
	SYNTAX  INTEGER(0..128)
	MAX-ACCESS  read-only
	STATUS current
	DESCRIPTION
        "
        Index definition for the pm10010mrAlmclientNetworkLaneFault 
        table
        "
	::= { pm10010mrAlmclientNetworkLaneFaultEntry 1 }


pm10010mrAlmClientLaneTecFaultPortn OBJECT-TYPE
	SYNTAX  EkiOnOff
	MAX-ACCESS read-only
	STATUS current
	DESCRIPTION
        "
        Client Network Lane TEC Fault
         :This OID indicates a TEC Fault 
        on the Client Trscv Network Lane 
        <Help> Alarm indicating a TEC Fault 
        on the Client Trscv Network Lane 
        <Condtype> CLIENT_LANE_TEC_FAULT 
        <Probcause> transmitterFailure
         (56) <Alarmtype> equipmentAlarm 
        (5) <Polarity> (2) 
        "
	::= { pm10010mrAlmclientNetworkLaneFaultEntry 17 }


pm10010mrAlmClientLaneWavelengthUnlockedPortn OBJECT-TYPE
	SYNTAX  EkiOnOff
	MAX-ACCESS read-only
	STATUS current
	DESCRIPTION
        "
        Client Network Lane Wavelength 
        Unlock :This OID indicates a Wavelength 
        unlock on the Client Trscv Network 
        Lane <Help> Alarm indicating a
         Wavelength unlock on the Client 
        Trscv Network Lane <Condtype> CLIENT_LANE_WAVELENGTH_UNLOCKED 
        <Probcause> transmitterFailure
         (56) <Alarmtype> equipmentAlarm 
        (5) <Polarity> (2) 
        "
	::= { pm10010mrAlmclientNetworkLaneFaultEntry 16 }


pm10010mrAlmClientLaneApdPowerSupplyPortn OBJECT-TYPE
	SYNTAX  EkiOnOff
	MAX-ACCESS read-only
	STATUS current
	DESCRIPTION
        "
        Client Network Lane APD Power
         Supply :This OID indicates an
         APD Power supply failure on the 
        Client Trscv Network Lane <Help> 
        Alarm indicating an APD Power supply 
        failure on the Client Trscv Network 
        Lane <Condtype> CLIENT_LANE_APD_POWER_SUPPLY 
        <Probcause> transmitterFailure
         (56) <Alarmtype> equipmentAlarm 
        (5) <Polarity> (2) 
        "
	::= { pm10010mrAlmclientNetworkLaneFaultEntry 15 }


pm10010mrAlmClientLaneTxLosfPortn OBJECT-TYPE
	SYNTAX  EkiOnOff
	MAX-ACCESS read-only
	STATUS current
	DESCRIPTION
        "
        Client Network Lane Tx Loss Of 
        Signal Functionality :This OID
         indicates a Tx Loss of Signal
         Functionality on the Client Trscv 
        Network Lane <Help> Alarm indicating 
        a Tx Loss of Signal Functionality 
        on the Client Trscv Network Lane 
        <Condtype> CLIENT_LANE_TX_LOSF
         <Probcause> transmitterFailure 
        (56) <Alarmtype> equipmentAlarm 
        (5) <Polarity> (2) 
        "
	::= { pm10010mrAlmclientNetworkLaneFaultEntry 9 }


pm10010mrAlmClientLaneTxLolPortn OBJECT-TYPE
	SYNTAX  EkiOnOff
	MAX-ACCESS read-only
	STATUS current
	DESCRIPTION
        "
        Client Network Lane Tx Loss Of 
        Lock :This OID indicates a Tx Loss 
        of Lock on the Client Trscv Network 
        Lane <Help> Alarm indicating a
         Tx Loss of Lock on the Client
         Trscv Network Lane <Condtype>
         CLIENT_LANE_TX_LOL <Probcause> 
        transmitterFailure (56) <Alarmtype> 
        equipmentAlarm (5) <Polarity> (2) 
        "
	::= { pm10010mrAlmclientNetworkLaneFaultEntry 8 }


pm10010mrAlmClientLaneRxLosPortn OBJECT-TYPE
	SYNTAX  EkiOnOff
	MAX-ACCESS read-only
	STATUS current
	DESCRIPTION
        "
        Client Network Lane Rx Loss Of 
        Signal :This OID indicates a Rx 
        Loss of Signal on the Client Trscv 
        Network Lane <Help> Alarm indicating 
        a Rx Loss of Signal on the Client 
        Trscv Network Lane <Condtype> CLIENT_LANE_RX_LOS 
        <Probcause> receiveFailure (41) 
        <Alarmtype> physicalViolation (9) 
        <Polarity> (2) 
        "
	::= { pm10010mrAlmclientNetworkLaneFaultEntry 6 }


pm10010mrAlmClientLaneRxLolPortn OBJECT-TYPE
	SYNTAX  EkiOnOff
	MAX-ACCESS read-only
	STATUS current
	DESCRIPTION
        "
        Client Network Lane Rx Loss Of 
        Lock :This OID indicates a Rx Loss 
        of Lock on the Client Trscv Network 
        Lane <Help> Alarm indicating a
         Rx Loss of Lock on the Client
         Trscv Network Lane <Condtype>
         CLIENT_LANE_RX_LOL <Probcause> 
        receiverFailure (42) <Alarmtype> 
        equipmentAlarm (5) <Polarity> (2) 
        "
	::= { pm10010mrAlmclientNetworkLaneFaultEntry 5 }


pm10010mrAlmClientLaneRxFifoErrorPortn OBJECT-TYPE
	SYNTAX  EkiOnOff
	MAX-ACCESS read-only
	STATUS current
	DESCRIPTION
        "
        Client Network Lane Rx FIFO Error 
        :This OID indicates a Rx FIFO Error 
        on the Client Trscv Network Lane 
        <Help> Alarm indicating a Rx FIFO 
        Error on the Client Trscv Network 
        Lane <Condtype> CLIENT_LANE_RX_FIFO_ERROR 
        <Probcause> receiverFailure (42) 
        <Alarmtype> equipmentAlarm (5)
         <Polarity> (2) 
        "
	::= { pm10010mrAlmclientNetworkLaneFaultEntry 4 }


--- *********************************************************
---     TABLE for the pm10010mrAlmclientHostLaneFault articles
--- *********************************************************

pm10010mrAlmclientHostLaneFaultTable OBJECT-TYPE
	SYNTAX  SEQUENCE OF Pm10010mrAlmclientHostLaneFaultEntry
	MAX-ACCESS not-accessible
	STATUS current
	DESCRIPTION
        "
        List of pm10010mrAlmclientHostLaneFault 
        Article
        "
	::= { pm10010mrAlmClientUrg 88 }


pm10010mrAlmclientHostLaneFaultEntry OBJECT-TYPE
	SYNTAX Pm10010mrAlmclientHostLaneFaultEntry
	MAX-ACCESS not-accessible
	STATUS current
	DESCRIPTION
        "
        Row definition for the pm10010mrAlmclientHostLaneFault 
        table
        "
	INDEX   { pm10010mrAlmclientHostLaneFaultIndex }
	::= { pm10010mrAlmclientHostLaneFaultTable 1 }


Pm10010mrAlmclientHostLaneFaultEntry ::=
	SEQUENCE {
	pm10010mrAlmclientHostLaneFaultIndex
		INTEGER,
	pm10010mrAlmRfDetectedPortn
		EkiOnOff,
	pm10010mrAlmLfDetectedPortn
		EkiOnOff,
	pm10010mrAlmClientLaneTxFifoErrorPortn
		EkiOnOff,
	pm10010mrAlmClientTxHostLolPortn
		EkiOnOff,
	pm10010mrAlmClientCsfDetectedPortn
		EkiOnOff,
	pm10010mrAlmClientLanesNotAlignedPortn
		EkiOnOff,
	pm10010mrAlmClientLanes6466UnlockPortn
		EkiOnOff,
	pm10010mrAlmClientLanesMarkerUnlockPortn
		EkiOnOff,
	pm10010mrAlmClientInputLossOfSigPortn
		EkiOnOff,
	pm10010mrAlmClientLossOfSyncPortn
		EkiOnOff
	}


pm10010mrAlmclientHostLaneFaultIndex OBJECT-TYPE
	SYNTAX  INTEGER(0..128)
	MAX-ACCESS  read-only
	STATUS current
	DESCRIPTION
        "
        Index definition for the pm10010mrAlmclientHostLaneFault 
        table
        "
	::= { pm10010mrAlmclientHostLaneFaultEntry 1 }


pm10010mrAlmRfDetectedPortn OBJECT-TYPE
	SYNTAX  EkiOnOff
	MAX-ACCESS read-only
	STATUS current
	DESCRIPTION
        "
        Remote Fault Signal Detected :This 
        OID indicates a Remote Fault Signal 
        is detected on the client input 
        port<Help> This alarm indicates 
        a Remote Fault Signal is detected 
        on the client input port <Condtype> 
        RF_DETECTED <Probcause> receiverFailure 
        (42) <Alarmtype> equipmentAlarm 
        (5) <Polarity> (2)
        "
	::= { pm10010mrAlmclientHostLaneFaultEntry 13 }


pm10010mrAlmLfDetectedPortn OBJECT-TYPE
	SYNTAX  EkiOnOff
	MAX-ACCESS read-only
	STATUS current
	DESCRIPTION
        "
        Local Fault Signal Detected :This 
        OID indicates a Local Fault Signal 
        is detected on the client input 
        port<Help> This alarm indicates 
        a Local Fault Signal is detected 
        on the client input port <Condtype> 
        LF_DETECTED <Probcause> receiverFailure 
        (42) <Alarmtype> equipmentAlarm 
        (5) <Polarity> (2)
        "
	::= { pm10010mrAlmclientHostLaneFaultEntry 12 }


pm10010mrAlmClientLaneTxFifoErrorPortn OBJECT-TYPE
	SYNTAX  EkiOnOff
	MAX-ACCESS read-only
	STATUS current
	DESCRIPTION
        "
        Client Host Lane Tx FIFO Error 
        :This OID indicates a Tx FIFO Error 
        on the Client Trscv Host Lane <Help> 
        Alarm indicating a Tx FIFO Error 
        on the Client Trscv Host Lane <Condtype> 
        CLIENT_LANE_TX_FIFO_ERROR <Probcause> 
        receiverFailure (42) <Alarmtype> 
        equipmentAlarm (5) <Polarity> (2)
        "
	::= { pm10010mrAlmclientHostLaneFaultEntry 11 }


pm10010mrAlmClientTxHostLolPortn OBJECT-TYPE
	SYNTAX  EkiOnOff
	MAX-ACCESS read-only
	STATUS current
	DESCRIPTION
        "
        Client Host Lane Tx Loss Of Lock 
        :This OID indicates a Tx Loss of 
        Lock on the Client Trscv Host Lane 
        <Help> Alarm indicating a Tx Loss 
        of Lock on the Client Trscv Host 
        Lane <Condtype> CLIENT_TX_HOST_LOL 
        <Probcause> receiverFailure (42) 
        <Alarmtype> equipmentAlarm (5)
         <Polarity> (2)
        "
	::= { pm10010mrAlmclientHostLaneFaultEntry 10 }


pm10010mrAlmClientCsfDetectedPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> CLIENT_CSF_DETECTED 
        <Probcause> receiveFailure (41) 
        <Alarmtype> other(1) <Polarity> 
        (2)
        "
	::= { pm10010mrAlmclientHostLaneFaultEntry 7 }


pm10010mrAlmClientLanesNotAlignedPortn OBJECT-TYPE
	SYNTAX  EkiOnOff
	MAX-ACCESS read-only
	STATUS current
	DESCRIPTION
        "
        Client Lanes Not Aligned :This 
        OID indicates the Client lanes
         are not aligned <Help> Alarm indicating 
        the Client lanes are not aligned 
        <Condtype> CLIENT_LANES_NOT_ALIGNED 
        <Probcause> receiveFailure (41) 
        <Alarmtype> integrityViolation
         (7) <Polarity> (2) 
        "
	::= { pm10010mrAlmclientHostLaneFaultEntry 6 }


pm10010mrAlmClientLanes6466UnlockPortn OBJECT-TYPE
	SYNTAX  EkiOnOff
	MAX-ACCESS read-only
	STATUS current
	DESCRIPTION
        "
        Client Lanes 64/66b Unlock :This 
        OID indicates the Client 64/66b 
        decoder is not lock <Help> Alarm 
        indicating the Client 64/66b decoder 
        is not lock <Condtype> CLIENT_LANES_64_66_UNLOCK 
        <Probcause> receiveFailure (41) 
        <Alarmtype> integrityViolation
         (7) <Polarity> (2) 
        "
	::= { pm10010mrAlmclientHostLaneFaultEntry 5 }


pm10010mrAlmClientLanesMarkerUnlockPortn OBJECT-TYPE
	SYNTAX  EkiOnOff
	MAX-ACCESS read-only
	STATUS current
	DESCRIPTION
        "
        Client Lanes Marker Unlock :This 
        OID indicates the Client lanes
         marker alignment is not lock <Help> 
        Alarm indicating the Client lanes 
        marker alignment is not lock <Condtype> 
        CLIENT_LANES_MARKER_UNLOCK <Probcause> 
        receiveFailure (41) <Alarmtype> 
        integrityViolation (7) <Polarity> 
        (2) 
        "
	::= { pm10010mrAlmclientHostLaneFaultEntry 4 }


pm10010mrAlmClientInputLossOfSigPortn OBJECT-TYPE
	SYNTAX  EkiOnOff
	MAX-ACCESS read-only
	STATUS current
	DESCRIPTION
        "
        Client Input Loss Of Signal :This 
        OID indicates a Loss of Signal
         is detected on the Client Trscv 
        <Help> Alarm indicating a Loss
         of Signal is detected on the Client 
        Trscv <Condtype> CLIENT_INPUT_LOSS_OF_SIG 
        <Probcause> receiveFailure (41) 
        <Alarmtype> physicalViolation (9) 
        <Polarity> (2) 
        "
	::= { pm10010mrAlmclientHostLaneFaultEntry 3 }


pm10010mrAlmClientLossOfSyncPortn OBJECT-TYPE
	SYNTAX  EkiOnOff
	MAX-ACCESS read-only
	STATUS current
	DESCRIPTION
        "
        Client Frame Alignment Loss :This 
        OID indicates the module is not 
        aligned with the incoming Client 
        signal <Help> Alarm indicating
         the module is not aligned with 
        the incoming client signal <Condtype> 
        CLIENT_LOSS_OF_SYNC <Probcause> 
        receiveFailure (41) <Alarmtype> 
        integrityViolation (7) <Polarity> 
        (2) 
        "
	::= { pm10010mrAlmclientHostLaneFaultEntry 2 }


--- *********************************************************
---     TABLE for the pm10010mrAlmlineNetworkLaneAlarmWarning1 articles
--- *********************************************************

pm10010mrAlmlineNetworkLaneAlarmWarning1Table OBJECT-TYPE
	SYNTAX  SEQUENCE OF Pm10010mrAlmlineNetworkLaneAlarmWarning1Entry
	MAX-ACCESS not-accessible
	STATUS current
	DESCRIPTION
        "
        List of pm10010mrAlmlineNetworkLaneAlarmWarning1 
        Article
        "
	::= { pm10010mrAlmLineNurg 104 }


pm10010mrAlmlineNetworkLaneAlarmWarning1Entry OBJECT-TYPE
	SYNTAX Pm10010mrAlmlineNetworkLaneAlarmWarning1Entry
	MAX-ACCESS not-accessible
	STATUS current
	DESCRIPTION
        "
        Row definition for the pm10010mrAlmlineNetworkLaneAlarmWarning1 
        table
        "
	INDEX   { pm10010mrAlmlineNetworkLaneAlarmWarning1Index }
	::= { pm10010mrAlmlineNetworkLaneAlarmWarning1Table 1 }


Pm10010mrAlmlineNetworkLaneAlarmWarning1Entry ::=
	SEQUENCE {
	pm10010mrAlmlineNetworkLaneAlarmWarning1Index
		INTEGER,
	pm10010mrAlmLineBiasHighAlarmPortn
		EkiOnOff,
	pm10010mrAlmLineBiasHighWarningPortn
		EkiOnOff,
	pm10010mrAlmLineBiasLowWarningPortn
		EkiOnOff,
	pm10010mrAlmLineBiasLowAlarmPortn
		EkiOnOff,
	pm10010mrAlmLineTxPowerHighAlarmPortn
		EkiOnOff,
	pm10010mrAlmLineTxPowerHighWarningPortn
		EkiOnOff,
	pm10010mrAlmLineTxPowerLowWarningPortn
		EkiOnOff,
	pm10010mrAlmLineTxPowerLowAlarmPortn
		EkiOnOff,
	pm10010mrAlmLineLaserTempHighAlarmPortn
		EkiOnOff,
	pm10010mrAlmLineLaserTempHighWarningPortn
		EkiOnOff,
	pm10010mrAlmLineLaserTempLowWarningPortn
		EkiOnOff,
	pm10010mrAlmLineLaserTempLowAlarmPortn
		EkiOnOff,
	pm10010mrAlmLineRxPowerHighAlarmPortn
		EkiOnOff,
	pm10010mrAlmLineRxPowerHighWarningPortn
		EkiOnOff,
	pm10010mrAlmLineRxPowerLowWarningPortn
		EkiOnOff,
	pm10010mrAlmLineRxPowerLowAlarmPortn
		EkiOnOff
	}


pm10010mrAlmlineNetworkLaneAlarmWarning1Index OBJECT-TYPE
	SYNTAX  INTEGER(0..128)
	MAX-ACCESS  read-only
	STATUS current
	DESCRIPTION
        "
        Index definition for the pm10010mrAlmlineNetworkLaneAlarmWarning1 
        table
        "
	::= { pm10010mrAlmlineNetworkLaneAlarmWarning1Entry 1 }


pm10010mrAlmLineBiasHighAlarmPortn OBJECT-TYPE
	SYNTAX  EkiOnOff
	MAX-ACCESS read-only
	STATUS current
	DESCRIPTION
        "
        Line Trscv Tx Bias High Alarm
         :This OID indicates that the Trscv 
        laser bias current is higher than 
        the threshold value written in
         the Trscv EEPROM <Help> Alarm
         indicating that the Trscv laser 
        bias current is higher than the 
        threshold value written in the
         Trscv EEPROM <Condtype> LINE_BIAS_HIGH_ALARM 
        <Probcause> transmitterFailure
         (56) <Alarmtype> equipmentAlarm 
        (5) <Polarity> (2) 
        "
	::= { pm10010mrAlmlineNetworkLaneAlarmWarning1Entry 17 }


pm10010mrAlmLineBiasHighWarningPortn OBJECT-TYPE
	SYNTAX  EkiOnOff
	MAX-ACCESS read-only
	STATUS current
	DESCRIPTION
        "
        Line Trscv Tx Bias High Warning 
        :This OID indicates that the Trscv 
        laser bias current is higher than 
        the threshold value written in
         the Trscv EEPROM <Help> Warning 
        indicating that the Trscv laser 
        bias current is higher than the 
        threshold value written in the
         Trscv EEPROM <Condtype> LINE_BIAS_HIGH_WARNING 
        <Probcause> transmitterFailure
         (56) <Alarmtype> equipmentAlarm 
        (5) <Polarity> (2) 
        "
	::= { pm10010mrAlmlineNetworkLaneAlarmWarning1Entry 16 }


pm10010mrAlmLineBiasLowWarningPortn OBJECT-TYPE
	SYNTAX  EkiOnOff
	MAX-ACCESS read-only
	STATUS current
	DESCRIPTION
        "
        Line Trscv Tx Bias Low Warning 
        :This OID indicates that the Trscv 
        laser bias current is lower than 
        the threshold value written in
         the Trscv EEPROM <Help> Warning 
        indicating that the Trscv laser 
        bias current is lower than the
         threshold value written in the 
        Trscv EEPROM <Condtype> LINE_BIAS_LOW_WARNING 
        <Probcause> transmitterFailure
         (56) <Alarmtype> equipmentAlarm 
        (5) <Polarity> (2) 
        "
	::= { pm10010mrAlmlineNetworkLaneAlarmWarning1Entry 15 }


pm10010mrAlmLineBiasLowAlarmPortn OBJECT-TYPE
	SYNTAX  EkiOnOff
	MAX-ACCESS read-only
	STATUS current
	DESCRIPTION
        "
        Line Trscv Tx Bias Low Alarm :This 
        OID indicates that the Trscv laser 
        bias current is lower than the
         threshold value written in the 
        Trscv EEPROM <Help> Alarm indicating 
        that the Trscv laser bias current 
        is lower than the threshold value 
        written in the Trscv EEPROM <Condtype> 
        LINE_BIAS_LOW_ALARM <Probcause> 
        transmitterFailure (56) <Alarmtype> 
        equipmentAlarm (5) <Polarity> (2) 
        "
	::= { pm10010mrAlmlineNetworkLaneAlarmWarning1Entry 14 }


pm10010mrAlmLineTxPowerHighAlarmPortn OBJECT-TYPE
	SYNTAX  EkiOnOff
	MAX-ACCESS read-only
	STATUS current
	DESCRIPTION
        "
        Line Trscv Tx Power High Alarm 
        :This OID indicates that the Trscv 
        output power is higher than the 
        threshold value written in the
         Trscv EEPROM <Help> Alarm indicating 
        that the Trscv output power is
         higher than the threshold value 
        written in the Trscv EEPROM <Condtype> 
        LINE_TX_POWER_HIGH_ALARM <Probcause> 
        transmitterFailure (56) <Alarmtype> 
        equipmentAlarm (5) <Polarity> (2) 
        "
	::= { pm10010mrAlmlineNetworkLaneAlarmWarning1Entry 13 }


pm10010mrAlmLineTxPowerHighWarningPortn OBJECT-TYPE
	SYNTAX  EkiOnOff
	MAX-ACCESS read-only
	STATUS current
	DESCRIPTION
        "
        Line Trscv Tx Power High Warning 
        :This OID indicates that the Trscv 
        output power is higher than the 
        threshold value written in the
         Trscv EEPROM <Help> Warning indicating 
        that the Trscv output power is
         higher than the threshold value 
        written in the Trscv EEPROM <Condtype> 
        LINE_TX_POWER_HIGH_WARNING <Probcause> 
        transmitterFailure (56) <Alarmtype> 
        equipmentAlarm (5) <Polarity> (2) 
        "
	::= { pm10010mrAlmlineNetworkLaneAlarmWarning1Entry 12 }


pm10010mrAlmLineTxPowerLowWarningPortn OBJECT-TYPE
	SYNTAX  EkiOnOff
	MAX-ACCESS read-only
	STATUS current
	DESCRIPTION
        "
        Line Trscv Tx Power Low Warning 
        :This OID indicates that the Trscv 
        output power is lower than the
         threshold value written in the 
        Trscv EEPROM <Help> Warning indicating 
        that the Trscv output power is
         lower than the threshold value 
        written in the Trscv EEPROM <Condtype> 
        LINE_TX_POWER_LOW_WARNING <Probcause> 
        transmitterFailure (56) <Alarmtype> 
        equipmentAlarm (5) <Polarity> (2) 
        "
	::= { pm10010mrAlmlineNetworkLaneAlarmWarning1Entry 11 }


pm10010mrAlmLineTxPowerLowAlarmPortn OBJECT-TYPE
	SYNTAX  EkiOnOff
	MAX-ACCESS read-only
	STATUS current
	DESCRIPTION
        "
        Line Trscv Tx Power Low Alarm
         :This OID indicates that the Trscv 
        output power is lower than the
         threshold value written in the 
        Trscv EEPROM <Help> Alarm indicating 
        that the Trscv output power is
         lower than the threshold value 
        written in the Trscv EEPROM <Condtype> 
        LINE_TX_POWER_LOW_ALARM <Probcause> 
        transmitterFailure (56) <Alarmtype> 
        equipmentAlarm (5) <Polarity> (2) 
        "
	::= { pm10010mrAlmlineNetworkLaneAlarmWarning1Entry 10 }


pm10010mrAlmLineLaserTempHighAlarmPortn OBJECT-TYPE
	SYNTAX  EkiOnOff
	MAX-ACCESS read-only
	STATUS current
	DESCRIPTION
        "
        Line Trscv Tx Laser Temp High
         Alarm :This OID indicates that 
        the Trscv Tx Laser Temperature
         is higher than the threshold value 
        written in the Trscv EEPROM <Help> 
        Alarm indicating that the Trscv 
        Tx Laser Temperature is higher
         than the threshold value written 
        in the Trscv EEPROM <Condtype>
         LINE_LASER_TEMP_HIGH_ALARM <Probcause> 
        temperatureUnacceptable (51) <Alarmtype> 
        equipmentAlarm (5) <Polarity> (2) 
        "
	::= { pm10010mrAlmlineNetworkLaneAlarmWarning1Entry 9 }


pm10010mrAlmLineLaserTempHighWarningPortn OBJECT-TYPE
	SYNTAX  EkiOnOff
	MAX-ACCESS read-only
	STATUS current
	DESCRIPTION
        "
        Line Trscv Tx Laser Temp High
         Warning :This OID indicates that 
        the Trscv Tx Laser Temperature
         is higher than the threshold value 
        written in the Trscv EEPROM <Help> 
        Warning indicating that the Trscv 
        Tx Laser Temperature is higher
         than the threshold value written 
        in the Trscv EEPROM <Condtype>
         LINE_LASER_TEMP_HIGH_WARNING <Probcause> 
        temperatureUnacceptable (51) <Alarmtype> 
        equipmentAlarm (5) <Polarity> (2) 
        "
	::= { pm10010mrAlmlineNetworkLaneAlarmWarning1Entry 8 }


pm10010mrAlmLineLaserTempLowWarningPortn OBJECT-TYPE
	SYNTAX  EkiOnOff
	MAX-ACCESS read-only
	STATUS current
	DESCRIPTION
        "
        Line Trscv Tx Laser Temp Low Warning 
        :This OID indicates that the Trscv 
        Tx Laser Temperature is lower than 
        the threshold value written in
         the Trscv EEPROM <Help> Warning 
        indicating that the Trscv Tx Laser 
        Temperature is lower than the threshold 
        value written in the Trscv EEPROM 
        <Condtype> LINE_LASER_TEMP_LOW_WARNING 
        <Probcause> temperatureUnacceptable 
        (51) <Alarmtype> equipmentAlarm 
        (5) <Polarity> (2) 
        "
	::= { pm10010mrAlmlineNetworkLaneAlarmWarning1Entry 7 }


pm10010mrAlmLineLaserTempLowAlarmPortn OBJECT-TYPE
	SYNTAX  EkiOnOff
	MAX-ACCESS read-only
	STATUS current
	DESCRIPTION
        "
        Line Trscv Tx Laser Temp Low Alarm 
        :This OID indicates that the Trscv 
        Tx Laser Temperature is lower than 
        the threshold value written in
         the Trscv EEPROM <Help> Alarm
         indicating that the Trscv Tx Laser 
        Temperature is lower than the threshold 
        value written in the Trscv EEPROM 
        <Condtype> LINE_LASER_TEMP_LOW_ALARM 
        <Probcause> temperatureUnacceptable 
        (51) <Alarmtype> equipmentAlarm 
        (5) <Polarity> (2) 
        "
	::= { pm10010mrAlmlineNetworkLaneAlarmWarning1Entry 6 }


pm10010mrAlmLineRxPowerHighAlarmPortn OBJECT-TYPE
	SYNTAX  EkiOnOff
	MAX-ACCESS read-only
	STATUS current
	DESCRIPTION
        "
        Line Trscv Rx Power High Alarm 
        :This OID indicates that the Trscv 
        input power is higher than the
         threshold value written in the 
        Trscv EEPROM <Help> Alarm indicating 
        that the Trscv input power is higher 
        than the threshold value written 
        in the Trscv EEPROM <Condtype>
         LINE_RX_POWER_HIGH_ALARM <Probcause> 
        receiveFailure (41) <Alarmtype> 
        equipmentAlarm (5) <Polarity> (2) 
        "
	::= { pm10010mrAlmlineNetworkLaneAlarmWarning1Entry 5 }


pm10010mrAlmLineRxPowerHighWarningPortn OBJECT-TYPE
	SYNTAX  EkiOnOff
	MAX-ACCESS read-only
	STATUS current
	DESCRIPTION
        "
        Line Trscv Rx Power High Warning 
        :This OID indicates that the Trscv 
        input power is higher than the
         threshold value written in the 
        Trscv EEPROM <Help> Warning indicating 
        that the Trscv input power is higher 
        than the threshold value written 
        in the Trscv EEPROM <Condtype>
         LINE_RX_POWER_HIGH_WARNING <Probcause> 
        receiveFailure (41) <Alarmtype> 
        equipmentAlarm (5) <Polarity> (2) 
        "
	::= { pm10010mrAlmlineNetworkLaneAlarmWarning1Entry 4 }


pm10010mrAlmLineRxPowerLowWarningPortn OBJECT-TYPE
	SYNTAX  EkiOnOff
	MAX-ACCESS read-only
	STATUS current
	DESCRIPTION
        "
        Line Trscv Rx Power Low Warning 
        :This OID indicates that the Trscv 
        input power is lower than the threshold 
        value written in the Trscv EEPROM 
        <Help> Warning indicating that
         the Trscv input power is lower 
        than the threshold value written 
        in the Trscv EEPROM <Condtype>
         LINE_RX_POWER_LOW_WARNING <Probcause> 
        receiveFailure (41) <Alarmtype> 
        equipmentAlarm (5) <Polarity> (2) 
        "
	::= { pm10010mrAlmlineNetworkLaneAlarmWarning1Entry 3 }


pm10010mrAlmLineRxPowerLowAlarmPortn OBJECT-TYPE
	SYNTAX  EkiOnOff
	MAX-ACCESS read-only
	STATUS current
	DESCRIPTION
        "
        Line Trscv Rx Power Low Alarm
         :This OID indicates that the Trscv 
        input power is lower than the threshold 
        value written in the Trscv EEPROM 
        <Help> Alarm indicating that the 
        Trscv input power is lower than 
        the threshold value written in
         the Trscv EEPROM <Condtype> LINE_RX_POWER_LOW_ALARM 
        <Probcause> receiveFailure (41) 
        <Alarmtype> equipmentAlarm (5)
         <Polarity> (2) 
        "
	::= { pm10010mrAlmlineNetworkLaneAlarmWarning1Entry 2 }


--- *********************************************************
---     TABLE for the pm10010mrAlmlineNetworkLaneAlarmWarning2 articles
--- *********************************************************

pm10010mrAlmlineNetworkLaneAlarmWarning2Table OBJECT-TYPE
	SYNTAX  SEQUENCE OF Pm10010mrAlmlineNetworkLaneAlarmWarning2Entry
	MAX-ACCESS not-accessible
	STATUS current
	DESCRIPTION
        "
        List of pm10010mrAlmlineNetworkLaneAlarmWarning2 
        Article
        "
	::= { pm10010mrAlmLineNurg 120 }


pm10010mrAlmlineNetworkLaneAlarmWarning2Entry OBJECT-TYPE
	SYNTAX Pm10010mrAlmlineNetworkLaneAlarmWarning2Entry
	MAX-ACCESS not-accessible
	STATUS current
	DESCRIPTION
        "
        Row definition for the pm10010mrAlmlineNetworkLaneAlarmWarning2 
        table
        "
	INDEX   { pm10010mrAlmlineNetworkLaneAlarmWarning2Index }
	::= { pm10010mrAlmlineNetworkLaneAlarmWarning2Table 1 }


Pm10010mrAlmlineNetworkLaneAlarmWarning2Entry ::=
	SEQUENCE {
	pm10010mrAlmlineNetworkLaneAlarmWarning2Index
		INTEGER,
	pm10010mrAlmRxLaserBiasHighAlarmPortn
		EkiOnOff,
	pm10010mrAlmRxLaserBiasHighWarningPortn
		EkiOnOff,
	pm10010mrAlmRxLaserBiasLowWarningPortn
		EkiOnOff,
	pm10010mrAlmRxLaserBiasLowAlarmPortn
		EkiOnOff,
	pm10010mrAlmRxLaserOutputHighAlarmPortn
		EkiOnOff,
	pm10010mrAlmRxLaserOutputHighWarningPortn
		EkiOnOff,
	pm10010mrAlmRxLaserOutputLowWarningPortn
		EkiOnOff,
	pm10010mrAlmRxLaserOutputLowAlarmPortn
		EkiOnOff,
	pm10010mrAlmRxLaserTempHighAlarmPortn
		EkiOnOff,
	pm10010mrAlmRxLaserTempHighWarningPortn
		EkiOnOff,
	pm10010mrAlmRxLaserTempLowWarningPortn
		EkiOnOff,
	pm10010mrAlmRxLaserTempLowAlarmPortn
		EkiOnOff,
	pm10010mrAlmTxModulatorBiasHighAlarmPortn
		EkiOnOff,
	pm10010mrAlmTxModulatorBiasHighWarningPortn
		EkiOnOff,
	pm10010mrAlmTxModulatorBiasLowWarningPortn
		EkiOnOff,
	pm10010mrAlmTxModulatorBiasLowAlarmPortn
		EkiOnOff
	}


pm10010mrAlmlineNetworkLaneAlarmWarning2Index OBJECT-TYPE
	SYNTAX  INTEGER(0..128)
	MAX-ACCESS  read-only
	STATUS current
	DESCRIPTION
        "
        Index definition for the pm10010mrAlmlineNetworkLaneAlarmWarning2 
        table
        "
	::= { pm10010mrAlmlineNetworkLaneAlarmWarning2Entry 1 }


pm10010mrAlmRxLaserBiasHighAlarmPortn OBJECT-TYPE
	SYNTAX  EkiOnOff
	MAX-ACCESS read-only
	STATUS current
	DESCRIPTION
        "
        Line Trscv Rx Bias High Alarm
         :This OID indicates that the Trscv 
        Rx laser bias current is higher 
        than the threshold value written 
        in the Trscv EEPROM <Help> Alarm 
        indicating that the Trscv Rx laser 
        bias current is higher than the 
        threshold value written in the
         Trscv EEPROM <Condtype> RX_LASER_BIAS_HIGH_ALARM 
        <Probcause> receiveFailure (41) 
        <Alarmtype> equipmentAlarm (5)
         <Polarity> (2) 
        "
	::= { pm10010mrAlmlineNetworkLaneAlarmWarning2Entry 17 }


pm10010mrAlmRxLaserBiasHighWarningPortn OBJECT-TYPE
	SYNTAX  EkiOnOff
	MAX-ACCESS read-only
	STATUS current
	DESCRIPTION
        "
        Line Trscv Rx Bias High Warning 
        :This OID indicates that the Trscv 
        Rx laser bias current is higher 
        than the threshold value written 
        in the Trscv EEPROM <Help> Warning 
        indicating that the Trscv Rx laser 
        bias current is higher than the 
        threshold value written in the
         Trscv EEPROM <Condtype> RX_LASER_BIAS_HIGH_WARNING 
        <Probcause> receiveFailure (41) 
        <Alarmtype> equipmentAlarm (5)
         <Polarity> (2) 
        "
	::= { pm10010mrAlmlineNetworkLaneAlarmWarning2Entry 16 }


pm10010mrAlmRxLaserBiasLowWarningPortn OBJECT-TYPE
	SYNTAX  EkiOnOff
	MAX-ACCESS read-only
	STATUS current
	DESCRIPTION
        "
        Line Trscv Rx Bias Low Warning 
        :This OID indicates that the Trscv 
        Rx laser bias current is lower
         than the threshold value written 
        in the Trscv EEPROM <Help> Warning 
        indicating that the Trscv Rx laser 
        bias current is lower than the
         threshold value written in the 
        Trscv EEPROM <Condtype> RX_LASER_BIAS_LOW_WARNING 
        <Probcause> receiveFailure (41) 
        <Alarmtype> equipmentAlarm (5)
         <Polarity> (2) 
        "
	::= { pm10010mrAlmlineNetworkLaneAlarmWarning2Entry 15 }


pm10010mrAlmRxLaserBiasLowAlarmPortn OBJECT-TYPE
	SYNTAX  EkiOnOff
	MAX-ACCESS read-only
	STATUS current
	DESCRIPTION
        "
        Line Trscv Rx Bias Low Alarm :This 
        OID indicates that the Trscv Rx 
        laser bias current is lower than 
        the threshold value written in
         the Trscv EEPROM <Help> Alarm
         indicating that the Trscv Rx laser 
        bias current is lower than the
         threshold value written in the 
        Trscv EEPROM <Condtype> RX_LASER_BIAS_LOW_ALARM 
        <Probcause> receiveFailure (41) 
        <Alarmtype> equipmentAlarm (5)
         <Polarity> (2) 
        "
	::= { pm10010mrAlmlineNetworkLaneAlarmWarning2Entry 14 }


pm10010mrAlmRxLaserOutputHighAlarmPortn OBJECT-TYPE
	SYNTAX  EkiOnOff
	MAX-ACCESS read-only
	STATUS current
	DESCRIPTION
        "
        Line Trscv Rx Output Power High 
        Alarm :This OID indicates that
         the Trscv Rx output power is higher 
        than the threshold value written 
        in the Trscv EEPROM <Help> Alarm 
        indicating that the Trscv Rx output 
        power is higher than the threshold 
        value written in the Trscv EEPROM 
        <Condtype> RX_LASER_OUTPUT_HIGH_ALARM 
        <Probcause> receiveFailure (41) 
        <Alarmtype> equipmentAlarm (5)
         <Polarity> (2) 
        "
	::= { pm10010mrAlmlineNetworkLaneAlarmWarning2Entry 13 }


pm10010mrAlmRxLaserOutputHighWarningPortn OBJECT-TYPE
	SYNTAX  EkiOnOff
	MAX-ACCESS read-only
	STATUS current
	DESCRIPTION
        "
        Line Trscv Rx Output Power High 
        Warning :This OID indicates that 
        the Trscv Rx output power is higher 
        than the threshold value written 
        in the Trscv EEPROM <Help> Warning 
        indicating that the Trscv Rx output 
        power is higher than the threshold 
        value written in the Trscv EEPROM 
        <Condtype> RX_LASER_OUTPUT_HIGH_WARNING 
        <Probcause> receiveFailure (41) 
        <Alarmtype> equipmentAlarm (5)
         <Polarity> (2) 
        "
	::= { pm10010mrAlmlineNetworkLaneAlarmWarning2Entry 12 }


pm10010mrAlmRxLaserOutputLowWarningPortn OBJECT-TYPE
	SYNTAX  EkiOnOff
	MAX-ACCESS read-only
	STATUS current
	DESCRIPTION
        "
        Line Trscv Rx Output Power Low 
        Warning :This OID indicates that 
        the Trscv Rx output power is lower 
        than the threshold value written 
        in the Trscv EEPROM <Help> Warning 
        indicating that the Trscv Rx output 
        power is lower than the threshold 
        value written in the Trscv EEPROM 
        <Condtype> RX_LASER_OUTPUT_LOW_WARNING 
        <Probcause> receiveFailure (41) 
        <Alarmtype> equipmentAlarm (5)
         <Polarity> (2) 
        "
	::= { pm10010mrAlmlineNetworkLaneAlarmWarning2Entry 11 }


pm10010mrAlmRxLaserOutputLowAlarmPortn OBJECT-TYPE
	SYNTAX  EkiOnOff
	MAX-ACCESS read-only
	STATUS current
	DESCRIPTION
        "
        Line Trscv Rx Output Power Low 
        Alarm :This OID indicates that
         the Trscv Rx output power is lower 
        than the threshold value written 
        in the Trscv EEPROM <Help> Alarm 
        indicating that the Trscv Rx output 
        power is lower than the threshold 
        value written in the Trscv EEPROM 
        <Condtype> RX_LASER_OUTPUT_LOW_ALARM 
        <Probcause> receiveFailure (41) 
        <Alarmtype> equipmentAlarm (5)
         <Polarity> (2) 
        "
	::= { pm10010mrAlmlineNetworkLaneAlarmWarning2Entry 10 }


pm10010mrAlmRxLaserTempHighAlarmPortn OBJECT-TYPE
	SYNTAX  EkiOnOff
	MAX-ACCESS read-only
	STATUS current
	DESCRIPTION
        "
        Line Trscv Rx Laser Temp High
         Alarm :This OID indicates that 
        the Trscv Rx Laser Temperature
         is higher than the threshold value 
        written in the Trscv EEPROM <Help> 
        Alarm indicating that the Trscv 
        Rx Laser Temperature is higher
         than the threshold value written 
        in the Trscv EEPROM <Condtype>
         RX_LASER_TEMP_HIGH_ALARM <Probcause> 
        temperatureUnacceptable (51) <Alarmtype> 
        equipmentAlarm (5) <Polarity> (2) 
        "
	::= { pm10010mrAlmlineNetworkLaneAlarmWarning2Entry 9 }


pm10010mrAlmRxLaserTempHighWarningPortn OBJECT-TYPE
	SYNTAX  EkiOnOff
	MAX-ACCESS read-only
	STATUS current
	DESCRIPTION
        "
        Line Trscv Rx Laser Temp High
         Warning :This OID indicates that 
        the Trscv Rx Laser Temperature
         is higher than the threshold value 
        written in the Trscv EEPROM <Help> 
        Warning indicating that the Trscv 
        Rx Laser Temperature is higher
         than the threshold value written 
        in the Trscv EEPROM <Condtype>
         RX_LASER_TEMP_HIGH_WARNING <Probcause> 
        temperatureUnacceptable (51) <Alarmtype> 
        equipmentAlarm (5) <Polarity> (2) 
        "
	::= { pm10010mrAlmlineNetworkLaneAlarmWarning2Entry 8 }


pm10010mrAlmRxLaserTempLowWarningPortn OBJECT-TYPE
	SYNTAX  EkiOnOff
	MAX-ACCESS read-only
	STATUS current
	DESCRIPTION
        "
        Line Trscv Rx Laser Temp Low Warning 
        :This OID indicates that the Trscv 
        Rx Laser Temperature is lower than 
        the threshold value written in
         the Trscv EEPROM <Help> Warning 
        indicating that the Trscv Rx Laser 
        Temperature is lower than the threshold 
        value written in the Trscv EEPROM 
        <Condtype> RX_LASER_TEMP_LOW_WARNING 
        <Probcause> temperatureUnacceptable 
        (51) <Alarmtype> equipmentAlarm 
        (5) <Polarity> (2) 
        "
	::= { pm10010mrAlmlineNetworkLaneAlarmWarning2Entry 7 }


pm10010mrAlmRxLaserTempLowAlarmPortn OBJECT-TYPE
	SYNTAX  EkiOnOff
	MAX-ACCESS read-only
	STATUS current
	DESCRIPTION
        "
        Line Trscv Rx Laser Temp Low Alarm 
        :This OID indicates that the Trscv 
        Rx Laser Temperature is lower than 
        the threshold value written in
         the Trscv EEPROM <Help> Alarm
         indicating that the Trscv Rx Laser 
        Temperature is lower than the threshold 
        value written in the Trscv EEPROM 
        <Condtype> RX_LASER_TEMP_LOW_ALARM 
        <Probcause> temperatureUnacceptable 
        (51) <Alarmtype> equipmentAlarm 
        (5) <Polarity> (2) 
        "
	::= { pm10010mrAlmlineNetworkLaneAlarmWarning2Entry 6 }


pm10010mrAlmTxModulatorBiasHighAlarmPortn OBJECT-TYPE
	SYNTAX  EkiOnOff
	MAX-ACCESS read-only
	STATUS current
	DESCRIPTION
        "
        Line Trscv Tx Modulator Bias High 
        Alarm :This OID indicates that
         the Trscv Tx modulator bias current 
        is higher than the threshold value 
        written in the Trscv EEPROM <Help> 
        Alarm indicating that the Trscv 
        Tx modulator bias current is higher 
        than the threshold value written 
        in the Trscv EEPROM <Condtype>
         TX_MODULATOR_BIAS_HIGH_ALARM <Probcause> 
        transmitterFailure (56) <Alarmtype> 
        equipmentAlarm (5) <Polarity> (2) 
        "
	::= { pm10010mrAlmlineNetworkLaneAlarmWarning2Entry 5 }


pm10010mrAlmTxModulatorBiasHighWarningPortn OBJECT-TYPE
	SYNTAX  EkiOnOff
	MAX-ACCESS read-only
	STATUS current
	DESCRIPTION
        "
        Line Trscv Tx Modulator Bias High 
        Warning :This OID indicates that 
        the Trscv Tx modulator bias current 
        is higher than the threshold value 
        written in the Trscv EEPROM <Help> 
        Warning indicating that the Trscv 
        Tx modulator bias current is higher 
        than the threshold value written 
        in the Trscv EEPROM <Condtype>
         TX_MODULATOR_BIAS_HIGH_WARNING 
        <Probcause> transmitterFailure
         (56) <Alarmtype> equipmentAlarm 
        (5) <Polarity> (2) 
        "
	::= { pm10010mrAlmlineNetworkLaneAlarmWarning2Entry 4 }


pm10010mrAlmTxModulatorBiasLowWarningPortn OBJECT-TYPE
	SYNTAX  EkiOnOff
	MAX-ACCESS read-only
	STATUS current
	DESCRIPTION
        "
        Line Trscv Tx Modulator Bias Low 
        Warning :This OID indicates that 
        the Trscv Tx modulator bias current 
        is lower than the threshold value 
        written in the Trscv EEPROM <Help> 
        Warning indicating that the Trscv 
        Tx modulator bias current is lower 
        than the threshold value written 
        in the Trscv EEPROM <Condtype>
         TX_MODULATOR_BIAS_LOW_WARNING
         <Probcause> transmitterFailure 
        (56) <Alarmtype> equipmentAlarm 
        (5) <Polarity> (2) 
        "
	::= { pm10010mrAlmlineNetworkLaneAlarmWarning2Entry 3 }


pm10010mrAlmTxModulatorBiasLowAlarmPortn OBJECT-TYPE
	SYNTAX  EkiOnOff
	MAX-ACCESS read-only
	STATUS current
	DESCRIPTION
        "
        Line Trscv Tx Modulator Bias Low 
        Alarm :This OID indicates that
         the Trscv Tx modulator bias current 
        is lower than the threshold value 
        written in the Trscv EEPROM <Help> 
        Alarm indicating that the Trscv 
        Tx modulator bias current is lower 
        than the threshold value written 
        in the Trscv EEPROM <Condtype>
         TX_MODULATOR_BIAS_LOW_ALARM <Probcause> 
        transmitterFailure (56) <Alarmtype> 
        equipmentAlarm (5) <Polarity> (2) 
        "
	::= { pm10010mrAlmlineNetworkLaneAlarmWarning2Entry 2 }


--- *********************************************************
---     TABLE for the pm10010mrAlmlineNetworkLaneFault articles
--- *********************************************************

pm10010mrAlmlineNetworkLaneFaultTable OBJECT-TYPE
	SYNTAX  SEQUENCE OF Pm10010mrAlmlineNetworkLaneFaultEntry
	MAX-ACCESS not-accessible
	STATUS current
	DESCRIPTION
        "
        List of pm10010mrAlmlineNetworkLaneFault 
        Article
        "
	::= { pm10010mrAlmLineUrg 136 }


pm10010mrAlmlineNetworkLaneFaultEntry OBJECT-TYPE
	SYNTAX Pm10010mrAlmlineNetworkLaneFaultEntry
	MAX-ACCESS not-accessible
	STATUS current
	DESCRIPTION
        "
        Row definition for the pm10010mrAlmlineNetworkLaneFault 
        table
        "
	INDEX   { pm10010mrAlmlineNetworkLaneFaultIndex }
	::= { pm10010mrAlmlineNetworkLaneFaultTable 1 }


Pm10010mrAlmlineNetworkLaneFaultEntry ::=
	SEQUENCE {
	pm10010mrAlmlineNetworkLaneFaultIndex
		INTEGER,
	pm10010mrAlmLineLaneTecFaultPortn
		EkiOnOff,
	pm10010mrAlmLineLaneWavelengthUnlockedPortn
		EkiOnOff,
	pm10010mrAlmLineLaneApdPowerSupplyPortn
		EkiOnOff,
	pm10010mrAlmLineLaneTxLosfPortn
		EkiOnOff,
	pm10010mrAlmLineLaneTxLolPortn
		EkiOnOff,
	pm10010mrAlmLineLaneRxLosPortn
		EkiOnOff,
	pm10010mrAlmLineLaneRxLolPortn
		EkiOnOff,
	pm10010mrAlmLineLaneRxFifoErrorPortn
		EkiOnOff,
	pm10010mrAlmLineLaneRxTecFaultPortn
		EkiOnOff
	}


pm10010mrAlmlineNetworkLaneFaultIndex OBJECT-TYPE
	SYNTAX  INTEGER(0..128)
	MAX-ACCESS  read-only
	STATUS current
	DESCRIPTION
        "
        Index definition for the pm10010mrAlmlineNetworkLaneFault 
        table
        "
	::= { pm10010mrAlmlineNetworkLaneFaultEntry 1 }


pm10010mrAlmLineLaneTecFaultPortn OBJECT-TYPE
	SYNTAX  EkiOnOff
	MAX-ACCESS read-only
	STATUS current
	DESCRIPTION
        "
        Line Network Lane TEC Fault :This 
        OID indicates a Tx TEC Fault on 
        the Line Trscv Network Lane <Help> 
        Alarm indicating a Tx TEC Fault 
        on the Line Trscv Network Lane
         <Condtype> LINE_LANE_TEC_FAULT 
        <Probcause> transmitterFailure
         (56) <Alarmtype> equipmentAlarm 
        (5) <Polarity> (2) 
        "
	::= { pm10010mrAlmlineNetworkLaneFaultEntry 17 }


pm10010mrAlmLineLaneWavelengthUnlockedPortn OBJECT-TYPE
	SYNTAX  EkiOnOff
	MAX-ACCESS read-only
	STATUS current
	DESCRIPTION
        "
        Line Network Lane Wavelength Unlock 
        :This OID indicates a Wavelength 
        unlock on the Line Trscv Network 
        Lane <Help> Alarm indicating a
         Wavelength unlock on the Line
         Trscv Network Lane <Condtype>
         LINE_LANE_WAVELENGTH_UNLOCKED
         <Probcause> transmitterFailure 
        (56) <Alarmtype> equipmentAlarm 
        (5) <Polarity> (2) 
        "
	::= { pm10010mrAlmlineNetworkLaneFaultEntry 16 }


pm10010mrAlmLineLaneApdPowerSupplyPortn OBJECT-TYPE
	SYNTAX  EkiOnOff
	MAX-ACCESS read-only
	STATUS current
	DESCRIPTION
        "
        Line Network Lane APD Power Supply 
        :This OID indicates an APD Power 
        supply failure on the Line Trscv 
        Network Lane <Help> Alarm indicating 
        an APD Power supply failure on
         the Line Trscv Network Lane <Condtype> 
        LINE_LANE_APD_POWER_SUPPLY <Probcause> 
        transmitterFailure (56) <Alarmtype> 
        equipmentAlarm (5) <Polarity> (2) 
        "
	::= { pm10010mrAlmlineNetworkLaneFaultEntry 15 }


pm10010mrAlmLineLaneTxLosfPortn OBJECT-TYPE
	SYNTAX  EkiOnOff
	MAX-ACCESS read-only
	STATUS current
	DESCRIPTION
        "
        Line Network Lane Tx Loss Of Signal 
        Functionality :This OID indicates 
        a Tx Loss of Signal Functionality 
        on the Line Trscv Network Lane
         <Help> Alarm indicating a Tx Loss 
        of Signal Functionality on the
         Line Trscv Network Lane <Condtype> 
        LINE_LANE_TX_LOSF <Probcause> transmitterFailure 
        (56) <Alarmtype> equipmentAlarm 
        (5) <Polarity> (2) 
        "
	::= { pm10010mrAlmlineNetworkLaneFaultEntry 9 }


pm10010mrAlmLineLaneTxLolPortn OBJECT-TYPE
	SYNTAX  EkiOnOff
	MAX-ACCESS read-only
	STATUS current
	DESCRIPTION
        "
        Line Network Lane Tx Loss Of Lock 
        :This OID indicates a Tx Loss of 
        Lock on the Line Trscv Network
         Lane <Help> Alarm indicating a 
        Tx Loss of Lock on the Line Trscv 
        Network Lane <Condtype> LINE_LANE_TX_LOL 
        <Probcause> transmitterFailure
         (56) <Alarmtype> equipmentAlarm 
        (5) <Polarity> (2) 
        "
	::= { pm10010mrAlmlineNetworkLaneFaultEntry 8 }


pm10010mrAlmLineLaneRxLosPortn OBJECT-TYPE
	SYNTAX  EkiOnOff
	MAX-ACCESS read-only
	STATUS current
	DESCRIPTION
        "
        Line Network Lane Rx Loss Of Signal 
        :This OID indicates a Rx Loss of 
        Signal on the Line Trscv Network 
        Lane <Help> Alarm indicating a
         Rx Loss of Signal on the Line
         Trscv Network Lane <Condtype>
         LINE_LANE_RX_LOS <Probcause> receiveFailure 
        (41) <Alarmtype> physicalViolation 
        (9) <Polarity> (2) 
        "
	::= { pm10010mrAlmlineNetworkLaneFaultEntry 6 }


pm10010mrAlmLineLaneRxLolPortn OBJECT-TYPE
	SYNTAX  EkiOnOff
	MAX-ACCESS read-only
	STATUS current
	DESCRIPTION
        "
        Line Network Lane Rx Loss Of Lock 
        :This OID indicates a Rx Loss of 
        Lock on the Line Trscv Network
         Lane <Help> Alarm indicating a 
        Rx Loss of Lock on the Line Trscv 
        Network Lane <Condtype> LINE_LANE_RX_LOL 
        <Probcause> receiverFailure (42) 
        <Alarmtype> equipmentAlarm (5)
         <Polarity> (2) 
        "
	::= { pm10010mrAlmlineNetworkLaneFaultEntry 5 }


pm10010mrAlmLineLaneRxFifoErrorPortn OBJECT-TYPE
	SYNTAX  EkiOnOff
	MAX-ACCESS read-only
	STATUS current
	DESCRIPTION
        "
        Line Network Lane Rx FIFO Error 
        :This OID indicates a Rx FIFO Error 
        on the Line Trscv Network Lane
         <Help> Alarm indicating a Rx FIFO 
        Error on the Line Trscv Network 
        Lane <Condtype> LINE_LANE_RX_FIFO_ERROR 
        <Probcause> receiverFailure (42) 
        <Alarmtype> equipmentAlarm (5)
         <Polarity> (2) 
        "
	::= { pm10010mrAlmlineNetworkLaneFaultEntry 4 }


pm10010mrAlmLineLaneRxTecFaultPortn OBJECT-TYPE
	SYNTAX  EkiOnOff
	MAX-ACCESS read-only
	STATUS current
	DESCRIPTION
        "
        Line Network Lane Rx TEC Fault 
        :This OID indicates a Rx TEC Fault 
        on the Line Trscv Network Lane
         <Help> Alarm indicating a Rx TEC 
        Fault on the Line Trscv Network 
        Lane <Condtype> LINE_LANE_RX_TEC_FAULT 
        <Probcause> receiverFailure (42) 
        <Alarmtype> equipmentAlarm (5)
         <Polarity> (2) 
        "
	::= { pm10010mrAlmlineNetworkLaneFaultEntry 3 }


--- *********************************************************
---     TABLE for the pm10010mrAlmlineHostLaneFault articles
--- *********************************************************

pm10010mrAlmlineHostLaneFaultTable OBJECT-TYPE
	SYNTAX  SEQUENCE OF Pm10010mrAlmlineHostLaneFaultEntry
	MAX-ACCESS not-accessible
	STATUS current
	DESCRIPTION
        "
        List of pm10010mrAlmlineHostLaneFault 
        Article
        "
	::= { pm10010mrAlmLineUrg 152 }


pm10010mrAlmlineHostLaneFaultEntry OBJECT-TYPE
	SYNTAX Pm10010mrAlmlineHostLaneFaultEntry
	MAX-ACCESS not-accessible
	STATUS current
	DESCRIPTION
        "
        Row definition for the pm10010mrAlmlineHostLaneFault 
        table
        "
	INDEX   { pm10010mrAlmlineHostLaneFaultIndex }
	::= { pm10010mrAlmlineHostLaneFaultTable 1 }


Pm10010mrAlmlineHostLaneFaultEntry ::=
	SEQUENCE {
	pm10010mrAlmlineHostLaneFaultIndex
		INTEGER,
	pm10010mrAlmLineTrxOverTempPortn
		EkiOnOff,
	pm10010mrAlmLinePowerDegradePortn
		EkiOnOff,
	pm10010mrAlmLineLaneTxFifoErrorPortn
		EkiOnOff,
	pm10010mrAlmLineTxHostLolPortn
		EkiOnOff,
	pm10010mrAlmLineSmIaeDetectedPortn
		EkiOnOff,
	pm10010mrAlmLineSmIaeInsertedPortn
		EkiOnOff,
	pm10010mrAlmLineSmBdiDetectedPortn
		EkiOnOff,
	pm10010mrAlmLineSmBdiInsertedPortn
		EkiOnOff,
	pm10010mrAlmLineLossOfFramePortn
		EkiOnOff,
	pm10010mrAlmLineInputLossOfSignalPortn
		EkiOnOff
	}


pm10010mrAlmlineHostLaneFaultIndex OBJECT-TYPE
	SYNTAX  INTEGER(0..128)
	MAX-ACCESS  read-only
	STATUS current
	DESCRIPTION
        "
        Index definition for the pm10010mrAlmlineHostLaneFault 
        table
        "
	::= { pm10010mrAlmlineHostLaneFaultEntry 1 }


pm10010mrAlmLineTrxOverTempPortn OBJECT-TYPE
	SYNTAX  EkiOnOff
	MAX-ACCESS read-only
	STATUS current
	DESCRIPTION
        "
        Temperature Critical Level :This 
        OID indicates the module temperature 
        is too high triggering the power 
        down protection mechanism <Help> 
        This alarm indicates the module 
        temperature is too high triggering 
        the power down protection mechanism 
        <Condtype> LINE_TRX_OVER_TEMP <Probcause> 
        temperatureUnacceptable (51) <Alarmtype> 
        equipmentAlarm (5) <Polarity> (2) 
        "
	::= { pm10010mrAlmlineHostLaneFaultEntry 17 }


pm10010mrAlmLinePowerDegradePortn OBJECT-TYPE
	SYNTAX  EkiOnOff
	MAX-ACCESS read-only
	STATUS current
	DESCRIPTION
        "
        3V3 Power Degrade :This OID indicates 
        the 3V3 power converter was in
         failure<Help> This alarm indicates 
        the 3V3 power converter was in
         failure <Condtype> LINE_POWER_DEGRADE 
        <Probcause> powerProblem (36) <Alarmtype> 
        equipmentAlarm (5) <Polarity> (2) 
        "
	::= { pm10010mrAlmlineHostLaneFaultEntry 16 }


pm10010mrAlmLineLaneTxFifoErrorPortn OBJECT-TYPE
	SYNTAX  EkiOnOff
	MAX-ACCESS read-only
	STATUS current
	DESCRIPTION
        "
        Line Host Lane Tx FIFO Error :This 
        OID indicates a Tx FIFO Error on 
        the Line Trscv Host Lane <Help> 
        Alarm indicating a Tx FIFO Error 
        on the Line Trscv Host Lane <Condtype> 
        LINE_LANE_TX_FIFO_ERROR <Probcause> 
        receiverFailure (42) <Alarmtype> 
        equipmentAlarm (5) <Polarity> (2) 
        "
	::= { pm10010mrAlmlineHostLaneFaultEntry 11 }


pm10010mrAlmLineTxHostLolPortn OBJECT-TYPE
	SYNTAX  EkiOnOff
	MAX-ACCESS read-only
	STATUS current
	DESCRIPTION
        "
        Line Host Lane Tx Loss Of Lock 
        :This OID indicates a Tx Loss of 
        Lock on the Line Trscv Host Lane 
        <Help> Alarm indicating a Tx Loss 
        of Lock on the Line Trscv Host
         Lane <Condtype> LINE_TX_HOST_LOL 
        <Probcause> receiverFailure (42) 
        <Alarmtype> equipmentAlarm (5)
         <Polarity> (2) 
        "
	::= { pm10010mrAlmlineHostLaneFaultEntry 10 }


pm10010mrAlmLineSmIaeDetectedPortn OBJECT-TYPE
	SYNTAX  EkiOnOff
	MAX-ACCESS read-only
	STATUS current
	DESCRIPTION
        "
        Line SM IAE Detected :This OID 
        indicates a SM Incoming Alignment 
        Error is detected on the incoming 
        Line signal <Help> Alarm indicating 
        a SM Incoming Alignment Error is 
        detected on the incoming Line signal 
        <Condtype> LINE_SM_IAE_DETECTED 
        <Probcause> receiveFailure (41) 
        <Alarmtype> integrityViolation
         (7) <Polarity> (2) 
        "
	::= { pm10010mrAlmlineHostLaneFaultEntry 7 }


pm10010mrAlmLineSmIaeInsertedPortn OBJECT-TYPE
	SYNTAX  EkiOnOff
	MAX-ACCESS read-only
	STATUS current
	DESCRIPTION
        "
        Line SM IAE Inserted :This OID 
        indicates a SM Incoming Alignment 
        Error is inserted on the outgoing 
        Line signal <Help> Status indicating 
        a SM Incoming Alignment Error is 
        inserted on the outgoing Line signal 
        <Condtype> LINE_SM_IAE_INSERTED 
        <Probcause> informationalStatus(1000) 
        <Alarmtype> other (1) <Polarity> 
        (2) 
        "
	::= { pm10010mrAlmlineHostLaneFaultEntry 6 }


pm10010mrAlmLineSmBdiDetectedPortn OBJECT-TYPE
	SYNTAX  EkiOnOff
	MAX-ACCESS read-only
	STATUS current
	DESCRIPTION
        "
        Line SM BDI Detected :This OID 
        indicates a SM Backward Defect
         Indication is detected on the
         incoming Line signal <Help> Alarm 
        indicating a SM Backward Defect 
        Indication is detected on the incoming 
        Line signal <Condtype> LINE_SM_BDI_DETECTED 
        <Probcause> receiveFailure (41) 
        <Alarmtype> integrityViolation
         (7) <Polarity> (2) 
        "
	::= { pm10010mrAlmlineHostLaneFaultEntry 5 }


pm10010mrAlmLineSmBdiInsertedPortn OBJECT-TYPE
	SYNTAX  EkiOnOff
	MAX-ACCESS read-only
	STATUS current
	DESCRIPTION
        "
        Line SM BDI Inserted :This OID 
        indicates a SM Backward Defect
         Indication is inserted on the
         outgoing Line signal <Help> Status 
        indicating a SM Backward Defect 
        Indication is inserted on the outgoing 
        Line signal <Condtype> LINE_SM_BDI_INSERTED 
        <Probcause> informationalStatus(1000) 
        <Alarmtype> other (1) <Polarity> 
        (2) 
        "
	::= { pm10010mrAlmlineHostLaneFaultEntry 4 }


pm10010mrAlmLineLossOfFramePortn OBJECT-TYPE
	SYNTAX  EkiOnOff
	MAX-ACCESS read-only
	STATUS current
	DESCRIPTION
        "
        Line Loss Of Frame :This OID indicates 
        the module is not aligned with
         the incoming Line signal <Help> 
        Alarm indicating the module is
         not aligned with the incoming
         Line signal <Condtype> LINE_LOSS_OF_FRAME 
        <Probcause> receiveFailure (41) 
        <Alarmtype> integrityViolation
         (7) <Polarity> (2) 
        "
	::= { pm10010mrAlmlineHostLaneFaultEntry 3 }


pm10010mrAlmLineInputLossOfSignalPortn OBJECT-TYPE
	SYNTAX  EkiOnOff
	MAX-ACCESS read-only
	STATUS current
	DESCRIPTION
        "
        Line Input Loss Of Signal :This 
        OID indicates a Loss of Signal
         is detected on the Line Trscv
         <Help> Alarm indicating a Loss 
        of Signal is detected on the Line 
        Trscv <Condtype> LINE_INPUT_LOSS_OF_SIGNAL 
        <Probcause> receiveFailure (41) 
        <Alarmtype> physicalViolation (9) 
        <Polarity> (2) 
        "
	::= { pm10010mrAlmlineHostLaneFaultEntry 2 }


--- *********************************************************
---     TABLE for the pm10010mrAlmlineNetworkLaneRxOtn articles
--- *********************************************************

pm10010mrAlmlineNetworkLaneRxOtnTable OBJECT-TYPE
	SYNTAX  SEQUENCE OF Pm10010mrAlmlineNetworkLaneRxOtnEntry
	MAX-ACCESS not-accessible
	STATUS current
	DESCRIPTION
        "
        List of pm10010mrAlmlineNetworkLaneRxOtn 
        Article
        "
	::= { pm10010mrAlmLineUrg 168 }


pm10010mrAlmlineNetworkLaneRxOtnEntry OBJECT-TYPE
	SYNTAX Pm10010mrAlmlineNetworkLaneRxOtnEntry
	MAX-ACCESS not-accessible
	STATUS current
	DESCRIPTION
        "
        Row definition for the pm10010mrAlmlineNetworkLaneRxOtn 
        table
        "
	INDEX   { pm10010mrAlmlineNetworkLaneRxOtnIndex }
	::= { pm10010mrAlmlineNetworkLaneRxOtnTable 1 }


Pm10010mrAlmlineNetworkLaneRxOtnEntry ::=
	SEQUENCE {
	pm10010mrAlmlineNetworkLaneRxOtnIndex
		INTEGER,
	pm10010mrAlmLineRxOtnLofPortn
		EkiOnOff,
	pm10010mrAlmLineRxOtnOofPortn
		EkiOnOff,
	pm10010mrAlmLineRxOtnLomPortn
		EkiOnOff,
	pm10010mrAlmLineRxOtnOomPortn
		EkiOnOff,
	pm10010mrAlmLineRxOtnIaePortn
		EkiOnOff,
	pm10010mrAlmLineRxSmBdiPortn
		EkiOnOff,
	pm10010mrAlmLineRxOtnOtuAisPortn
		EkiOnOff,
	pm10010mrAlmLineRxOtnOduAisPortn
		EkiOnOff
	}


pm10010mrAlmlineNetworkLaneRxOtnIndex OBJECT-TYPE
	SYNTAX  INTEGER(0..128)
	MAX-ACCESS  read-only
	STATUS current
	DESCRIPTION
        "
        Index definition for the pm10010mrAlmlineNetworkLaneRxOtn 
        table
        "
	::= { pm10010mrAlmlineNetworkLaneRxOtnEntry 1 }


pm10010mrAlmLineRxOtnLofPortn OBJECT-TYPE
	SYNTAX  EkiOnOff
	MAX-ACCESS read-only
	STATUS current
	DESCRIPTION
        "
        Line Network Rx LOF :This OID
         indicates a Loss of Frame is detected 
        on the Rx Network interface of
         the Line Trscv <Help> Alarm indicating 
        a Loss of Frame is detected on
         the Rx Network interface of the 
        Line Trscv <Condtype> LINE_RX_OTN_LOF 
        <Probcause> receiveFailure (41) 
        <Alarmtype> equipmentAlarm (5)
         <Polarity> (2) 
        "
	::= { pm10010mrAlmlineNetworkLaneRxOtnEntry 17 }


pm10010mrAlmLineRxOtnOofPortn OBJECT-TYPE
	SYNTAX  EkiOnOff
	MAX-ACCESS read-only
	STATUS current
	DESCRIPTION
        "
        Line Network Rx OOF :This OID
         indicates an Out of Frame is detected 
        on the Rx Network interface of
         the Line Trscv <Help> Alarm indicating 
        an Out of Frame is detected on
         the Rx Network interface of the 
        Line Trscv <Condtype> LINE_RX_OTN_OOF 
        <Probcause> receiveFailure (41) 
        <Alarmtype> equipmentAlarm (5)
         <Polarity> (2) 
        "
	::= { pm10010mrAlmlineNetworkLaneRxOtnEntry 16 }


pm10010mrAlmLineRxOtnLomPortn OBJECT-TYPE
	SYNTAX  EkiOnOff
	MAX-ACCESS read-only
	STATUS current
	DESCRIPTION
        "
        Line Network Rx LOM :This OID
         indicates a Loss of Multiframe 
        is detected on the Rx Network interface 
        of the Line Trscv <Help> Alarm
         indicating a Loss of Multiframe 
        is detected on the Rx Network interface 
        of the Line Trscv <Condtype> LINE_RX_OTN_LOM 
        <Probcause> receiveFailure (41) 
        <Alarmtype> equipmentAlarm (5)
         <Polarity> (2) 
        "
	::= { pm10010mrAlmlineNetworkLaneRxOtnEntry 15 }


pm10010mrAlmLineRxOtnOomPortn OBJECT-TYPE
	SYNTAX  EkiOnOff
	MAX-ACCESS read-only
	STATUS current
	DESCRIPTION
        "
        Line Network Rx OOM :This OID
         indicates an Out of Multiframe 
        is detected on the Rx Network interface 
        of the Line Trscv <Help> Alarm
         indicating an Out of Multiframe 
        is detected on the Rx Network interface 
        of the Line Trscv <Condtype> LINE_RX_OTN_OOM 
        <Probcause> receiveFailure (41) 
        <Alarmtype> equipmentAlarm (5)
         <Polarity> (2) 
        "
	::= { pm10010mrAlmlineNetworkLaneRxOtnEntry 14 }


pm10010mrAlmLineRxOtnIaePortn OBJECT-TYPE
	SYNTAX  EkiOnOff
	MAX-ACCESS read-only
	STATUS current
	DESCRIPTION
        "
        Line Network Rx IAE :This OID
         indicates an Incoming Alignment 
        Error is detected on the Rx Network 
        interface of the Line Trscv <Help> 
        Alarm indicating an Incoming Alignment 
        Error is detected on the Rx Network 
        interface of the Line Trscv <Condtype> 
        LINE_RX_OTN_IAE <Probcause> receiveFailure 
        (41) <Alarmtype> equipmentAlarm 
        (5) <Polarity> (2) 
        "
	::= { pm10010mrAlmlineNetworkLaneRxOtnEntry 13 }


pm10010mrAlmLineRxSmBdiPortn OBJECT-TYPE
	SYNTAX  EkiOnOff
	MAX-ACCESS read-only
	STATUS current
	DESCRIPTION
        "
        Line Network Rx SM BDI :This OID 
        indicates an SM Backward Defect 
        Indication is detected on the Rx 
        Network interface of the Line Trscv 
        <Help> Alarm indicating an SM Backward 
        Defect Indication is detected on 
        the Rx Network interface of the 
        Line Trscv <Condtype> LINE_RX_SM_BDI 
        <Probcause> informationalStatus(1000) 
        <Alarmtype> other (1) <Polarity> 
        (2) 
        "
	::= { pm10010mrAlmlineNetworkLaneRxOtnEntry 12 }


pm10010mrAlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of 
        the Line Trscv <Help> Alarm indicating 
        an OTU Alarm Indication Signal
         is detected on the Rx Network
         interface of the Line Trscv <Condtype> 
        LINE_RX_OTN_OTU_AIS <Probcause> 
        receiveFailure (41) <Alarmtype> 
        equipmentAlarm (5) <Polarity> (2) 
        "
	::= { pm10010mrAlmlineNetworkLaneRxOtnEntry 11 }


pm10010mrAlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of 
        the Line Trscv <Help> Alarm indicating 
        an ODU Alarm Indication Signal
         is detected on the Rx Network
         interface of the Line Trscv <Condtype> 
        LINE_RX_OTN_ODU_AIS <Probcause> 
        receiveFailure (41) <Alarmtype> 
        equipmentAlarm (5) <Polarity> (2) 
        "
	::= { pm10010mrAlmlineNetworkLaneRxOtnEntry 10 }


--- *********************************************************
---     TABLE for the pm10010mrAlmlineHostLaneTxOtn articles
--- *********************************************************

pm10010mrAlmlineHostLaneTxOtnTable OBJECT-TYPE
	SYNTAX  SEQUENCE OF Pm10010mrAlmlineHostLaneTxOtnEntry
	MAX-ACCESS not-accessible
	STATUS current
	DESCRIPTION
        "
        List of pm10010mrAlmlineHostLaneTxOtn 
        Article
        "
	::= { pm10010mrAlmLineUrg 184 }


pm10010mrAlmlineHostLaneTxOtnEntry OBJECT-TYPE
	SYNTAX Pm10010mrAlmlineHostLaneTxOtnEntry
	MAX-ACCESS not-accessible
	STATUS current
	DESCRIPTION
        "
        Row definition for the pm10010mrAlmlineHostLaneTxOtn 
        table
        "
	INDEX   { pm10010mrAlmlineHostLaneTxOtnIndex }
	::= { pm10010mrAlmlineHostLaneTxOtnTable 1 }


Pm10010mrAlmlineHostLaneTxOtnEntry ::=
	SEQUENCE {
	pm10010mrAlmlineHostLaneTxOtnIndex
		INTEGER,
	pm10010mrAlmLineTxOtnLofPortn
		EkiOnOff,
	pm10010mrAlmLineTxOtnOofPortn
		EkiOnOff,
	pm10010mrAlmLineTxOtnLomPortn
		EkiOnOff,
	pm10010mrAlmLineTxOtnOomPortn
		EkiOnOff,
	pm10010mrAlmLineTxOtnIaePortn
		EkiOnOff,
	pm10010mrAlmLineTxSmBdiPortn
		EkiOnOff,
	pm10010mrAlmLineTxOtnOtuAisPortn
		EkiOnOff,
	pm10010mrAlmLineTxOtnOduAisPortn
		EkiOnOff
	}


pm10010mrAlmlineHostLaneTxOtnIndex OBJECT-TYPE
	SYNTAX  INTEGER(0..128)
	MAX-ACCESS  read-only
	STATUS current
	DESCRIPTION
        "
        Index definition for the pm10010mrAlmlineHostLaneTxOtn 
        table
        "
	::= { pm10010mrAlmlineHostLaneTxOtnEntry 1 }


pm10010mrAlmLineTxOtnLofPortn OBJECT-TYPE
	SYNTAX  EkiOnOff
	MAX-ACCESS read-only
	STATUS current
	DESCRIPTION
        "
        Line Host Tx LOF :This OID indicates 
        a Loss of Frame is detected on
         the Tx Host interface of the Line 
        Trscv <Help> Alarm indicating a 
        Loss of Frame is detected on the 
        Tx Host interface of the Line Trscv 
        <Condtype> LINE_TX_OTN_LOF <Probcause> 
        receiveFailure (41) <Alarmtype> 
        equipmentAlarm (5) <Polarity> (2) 
        "
	::= { pm10010mrAlmlineHostLaneTxOtnEntry 17 }


pm10010mrAlmLineTxOtnOofPortn OBJECT-TYPE
	SYNTAX  EkiOnOff
	MAX-ACCESS read-only
	STATUS current
	DESCRIPTION
        "
        Line Host Tx OOF :This OID indicates 
        an Out of Frame is detected on
         the Tx Host interface of the Line 
        Trscv <Help> Alarm indicating an 
        Out of Frame is detected on the 
        Tx Host interface of the Line Trscv 
        <Condtype> LINE_TX_OTN_OOF <Probcause> 
        receiveFailure (41) <Alarmtype> 
        equipmentAlarm (5) <Polarity> (2) 
        "
	::= { pm10010mrAlmlineHostLaneTxOtnEntry 16 }


pm10010mrAlmLineTxOtnLomPortn OBJECT-TYPE
	SYNTAX  EkiOnOff
	MAX-ACCESS read-only
	STATUS current
	DESCRIPTION
        "
        Line Host Tx LOM :This OID indicates 
        a Loss of Multiframe is detected 
        on the Tx Host interface of the 
        Line Trscv <Help> Alarm indicating 
        a Loss of Multiframe is detected 
        on the Tx Host interface of the 
        Line Trscv <Condtype> LINE_TX_OTN_LOM 
        <Probcause> receiveFailure (41) 
        <Alarmtype> equipmentAlarm (5)
         <Polarity> (2) 
        "
	::= { pm10010mrAlmlineHostLaneTxOtnEntry 15 }


pm10010mrAlmLineTxOtnOomPortn OBJECT-TYPE
	SYNTAX  EkiOnOff
	MAX-ACCESS read-only
	STATUS current
	DESCRIPTION
        "
        Line Host Tx OOM :This OID indicates 
        an Out of Multiframe is detected 
        on the Tx Host interface of the 
        Line Trscv <Help> Alarm indicating 
        an Out of Multiframe is detected 
        on the Tx Host interface of the 
        Line Trscv <Condtype> LINE_TX_OTN_OOM 
        <Probcause> receiveFailure (41) 
        <Alarmtype> equipmentAlarm (5)
         <Polarity> (2) 
        "
	::= { pm10010mrAlmlineHostLaneTxOtnEntry 14 }


pm10010mrAlmLineTxOtnIaePortn OBJECT-TYPE
	SYNTAX  EkiOnOff
	MAX-ACCESS read-only
	STATUS current
	DESCRIPTION
        "
        Line Host Tx IAE :This OID indicates 
        an Incoming Alignment Error is
         detected on the Tx Host interface 
        of the Line Trscv <Help> Alarm
         indicating an Incoming Alignment 
        Error is detected on the Tx Host 
        interface of the Line Trscv <Condtype> 
        LINE_TX_OTN_IAE <Probcause> receiveFailure 
        (41) <Alarmtype> equipmentAlarm 
        (5) <Polarity> (2) 
        "
	::= { pm10010mrAlmlineHostLaneTxOtnEntry 13 }


pm10010mrAlmLineTxSmBdiPortn OBJECT-TYPE
	SYNTAX  EkiOnOff
	MAX-ACCESS read-only
	STATUS current
	DESCRIPTION
        "
        Line Host Tx SM BDI :This OID
         indicates an SM Backward Defect 
        Indication is detected on the Tx 
        Host interface of the Line Trscv 
        <Help> Alarm indicating an SM Backward 
        Defect Indication is detected on 
        the Tx Host interface of the Line 
        Trscv <Condtype> LINE_TX_SM_BDI 
        <Probcause> informationalStatus(1000) 
        <Alarmtype> other (1) <Polarity> 
        (2) 
        "
	::= { pm10010mrAlmlineHostLaneTxOtnEntry 12 }


pm10010mrAlmLineTxOtnOtuAisPortn OBJECT-TYPE
	SYNTAX  EkiOnOff
	MAX-ACCESS read-only
	STATUS current
	DESCRIPTION
        "
        Line Host Tx OTU AIS :This OID 
        indicates an OTU This OID Indication 
        Signal is detected on the Tx Host 
        interface of the Line Trscv <Help> 
        Alarm indicating an OTU Alarm Indication 
        Signal is detected on the Tx Host 
        interface of the Line Trscv <Condtype> 
        LINE_TX_OTN_OTU_AIS <Probcause> 
        receiveFailure (41) <Alarmtype> 
        equipmentAlarm (5) <Polarity> (2) 
        "
	::= { pm10010mrAlmlineHostLaneTxOtnEntry 11 }


pm10010mrAlmLineTxOtnOduAisPortn OBJECT-TYPE
	SYNTAX  EkiOnOff
	MAX-ACCESS read-only
	STATUS current
	DESCRIPTION
        "
        Line Host Tx ODU AIS :This OID 
        indicates an ODU This OID Indication 
        Signal is detected on the Tx Host 
        interface of the Line Trscv <Help> 
        Alarm indicating an ODU Alarm Indication 
        Signal is detected on the Tx Host 
        interface of the Line Trscv <Condtype> 
        LINE_TX_OTN_ODU_AIS <Probcause> 
        receiveFailure (41) <Alarmtype> 
        equipmentAlarm (5) <Polarity> (2) 
        "
	::= { pm10010mrAlmlineHostLaneTxOtnEntry 10 }


--- *********************************************************
---     TABLE for the pm10010mrAlmclientSfpAlmDdm articles
--- *********************************************************

pm10010mrAlmclientSfpAlmDdmTable OBJECT-TYPE
	SYNTAX  SEQUENCE OF Pm10010mrAlmclientSfpAlmDdmEntry
	MAX-ACCESS not-accessible
	STATUS current
	DESCRIPTION
        "
        List of pm10010mrAlmclientSfpAlmDdm 
        Article
        "
	::= { pm10010mrAlmClientUrg 216 }


pm10010mrAlmclientSfpAlmDdmEntry OBJECT-TYPE
	SYNTAX Pm10010mrAlmclientSfpAlmDdmEntry
	MAX-ACCESS not-accessible
	STATUS current
	DESCRIPTION
        "
        Row definition for the pm10010mrAlmclientSfpAlmDdm 
        table
        "
	INDEX   { pm10010mrAlmclientSfpAlmDdmIndex }
	::= { pm10010mrAlmclientSfpAlmDdmTable 1 }


Pm10010mrAlmclientSfpAlmDdmEntry ::=
	SEQUENCE {
	pm10010mrAlmclientSfpAlmDdmIndex
		INTEGER,
	pm10010mrAlmRxPwrHighAlaPortn
		EkiOnOff,
	pm10010mrAlmRxPwrLowAlaPortn
		EkiOnOff,
	pm10010mrAlmTempHighAlaPortn
		EkiOnOff,
	pm10010mrAlmTempLowAlaPortn
		EkiOnOff,
	pm10010mrAlmVccHighAlaPortn
		EkiOnOff,
	pm10010mrAlmVccLowAlaPortn
		EkiOnOff,
	pm10010mrAlmTxBiasHighAlaPortn
		EkiOnOff,
	pm10010mrAlmTxBiasLowAlaPortn
		EkiOnOff,
	pm10010mrAlmTxPwrHighAlaPortn
		EkiOnOff,
	pm10010mrAlmTxPwrLowAlaPortn
		EkiOnOff
	}


pm10010mrAlmclientSfpAlmDdmIndex OBJECT-TYPE
	SYNTAX  INTEGER(0..128)
	MAX-ACCESS  read-only
	STATUS current
	DESCRIPTION
        "
        Index definition for the pm10010mrAlmclientSfpAlmDdm 
        table
        "
	::= { pm10010mrAlmclientSfpAlmDdmEntry 1 }


pm10010mrAlmRxPwrHighAlaPortn OBJECT-TYPE
	SYNTAX  EkiOnOff
	MAX-ACCESS read-only
	STATUS current
	DESCRIPTION
        "
        Client Trscv Rx Power High :This 
        OID indicates that the Trscv input 
        power of port is higher than the 
        threshold value written in the
         Trscv EEPROM <Help> Alarm indicating 
        that the Trscv input power of port 
        is higher than the threshold value 
        written in the Trscv EEPROM <Condtype> 
        RX_PWR_HIGH_ALA_1 <Probcause> receiveFailure 
        (41) <Alarmtype> equipmentAlarm 
        (5) <Polarity> (2) 
        "
	::= { pm10010mrAlmclientSfpAlmDdmEntry 17 }


pm10010mrAlmRxPwrLowAlaPortn OBJECT-TYPE
	SYNTAX  EkiOnOff
	MAX-ACCESS read-only
	STATUS current
	DESCRIPTION
        "
        Client Trscv Rx Power Low :This 
        OID indicates that the Trscv input 
        power of port is lower than the 
        threshold value written in the
         Trscv EEPROM <Help> Alarm indicating 
        that the Trscv input power of port 
        is lower than the threshold value 
        written in the Trscv EEPROM <Condtype> 
        RX_PWR_LOW_ALA_1 <Probcause> receiveFailure 
        (41) <Alarmtype> equipmentAlarm 
        (5) <Polarity> (2) 
        "
	::= { pm10010mrAlmclientSfpAlmDdmEntry 16 }


pm10010mrAlmTempHighAlaPortn OBJECT-TYPE
	SYNTAX  EkiOnOff
	MAX-ACCESS read-only
	STATUS current
	DESCRIPTION
        "
        Client Trscv Temp High :This OID 
        indicates that the Trscv temperature 
        of port is higher than the threshold 
        value written in the Trscv EEPROM 
        <Help> Alarm indicating that the 
        Trscv temperature of port is higher 
        than the threshold value written 
        in the Trscv EEPROM <Condtype>
         TEMP_HIGH_ALA_1 <Probcause> temperatureUnacceptable 
        (51) <Alarmtype> equipmentAlarm 
        (5) <Polarity> (2) 
        "
	::= { pm10010mrAlmclientSfpAlmDdmEntry 9 }


pm10010mrAlmTempLowAlaPortn OBJECT-TYPE
	SYNTAX  EkiOnOff
	MAX-ACCESS read-only
	STATUS current
	DESCRIPTION
        "
        Client Trscv Temp Low :This OID 
        indicates that the Trscv temperature 
        of port is lower than the threshold 
        value written in the Trscv EEPROM 
        <Help> Alarm indicating that the 
        Trscv temperature of port is lower 
        than the threshold value written 
        in the Trscv EEPROM <Condtype>
         TEMP_LOW_ALA_1 <Probcause> temperatureUnacceptable 
        (51) <Alarmtype> equipmentAlarm 
        (5) <Polarity> (2) 
        "
	::= { pm10010mrAlmclientSfpAlmDdmEntry 8 }


pm10010mrAlmVccHighAlaPortn OBJECT-TYPE
	SYNTAX  EkiOnOff
	MAX-ACCESS read-only
	STATUS current
	DESCRIPTION
        "
        Client Trscv Power Supply High 
        :This OID indicates that the Trscv 
        power supply of port is higher
         than the threshold value written 
        in the Trscv EEPROM <Help> Alarm 
        indicating that the Trscv power 
        supply of port is higher than the 
        threshold value written in the
         Trscv EEPROM <Condtype> VCC_HIGH_ALA_1 
        <Probcause> powerProblem (36) <Alarmtype> 
        equipmentAlarm (5) <Polarity> (2) 
        "
	::= { pm10010mrAlmclientSfpAlmDdmEntry 7 }


pm10010mrAlmVccLowAlaPortn OBJECT-TYPE
	SYNTAX  EkiOnOff
	MAX-ACCESS read-only
	STATUS current
	DESCRIPTION
        "
        Client Trscv Power Supply Low
         :This OID indicates that the Trscv 
        power supply of port is lower than 
        the threshold value written in
         the Trscv EEPROM <Help> Alarm
         indicating that the Trscv power 
        supply of port is lower than the 
        threshold value written in the
         Trscv EEPROM <Condtype> VCC_LOW_ALA_1 
        <Probcause> powerProblem (36) <Alarmtype> 
        equipmentAlarm (5) <Polarity> (2) 
        "
	::= { pm10010mrAlmclientSfpAlmDdmEntry 6 }


pm10010mrAlmTxBiasHighAlaPortn OBJECT-TYPE
	SYNTAX  EkiOnOff
	MAX-ACCESS read-only
	STATUS current
	DESCRIPTION
        "
        Client Trscv Bias High :This OID 
        indicates that the Trscv laser
         bias current of port is higher 
        than the threshold value written 
        in the Trscv EEPROM <Help> Alarm 
        indicating that the Trscv laser 
        bias current of port is higher
         than the threshold value written 
        in the Trscv EEPROM <Condtype>
         TX_BIAS_HIGH_ALA_1 <Probcause> 
        transmitterFailure (56) <Alarmtype> 
        equipmentAlarm (5) <Polarity> (2) 
        "
	::= { pm10010mrAlmclientSfpAlmDdmEntry 5 }


pm10010mrAlmTxBiasLowAlaPortn OBJECT-TYPE
	SYNTAX  EkiOnOff
	MAX-ACCESS read-only
	STATUS current
	DESCRIPTION
        "
        Client Trscv Bias Low :This OID 
        indicates that the Trscv laser
         bias current of port is lower
         than the threshold value written 
        in the Trscv EEPROM <Help> Alarm 
        indicating that the Trscv laser 
        bias current of port is lower than 
        the threshold value written in
         the Trscv EEPROM <Condtype> TX_BIAS_LOW_ALA_1 
        <Probcause> transmitterFailure
         (56) <Alarmtype> equipmentAlarm 
        (5) <Polarity> (2) 
        "
	::= { pm10010mrAlmclientSfpAlmDdmEntry 4 }


pm10010mrAlmTxPwrHighAlaPortn OBJECT-TYPE
	SYNTAX  EkiOnOff
	MAX-ACCESS read-only
	STATUS current
	DESCRIPTION
        "
        Client Trscv Tx Power High :This 
        OID indicates that the Trscv output 
        power of port is higher than the 
        threshold value written in the
         Trscv EEPROM <Help> Alarm indicating 
        that the Trscv output power of
         port is higher than the threshold 
        value written in the Trscv EEPROM 
        <Condtype> TX_PWR_HIGH_ALA_1 <Probcause> 
        transmitterFailure (56) <Alarmtype> 
        equipmentAlarm (5) <Polarity> (2) 
        "
	::= { pm10010mrAlmclientSfpAlmDdmEntry 3 }


pm10010mrAlmTxPwrLowAlaPortn OBJECT-TYPE
	SYNTAX  EkiOnOff
	MAX-ACCESS read-only
	STATUS current
	DESCRIPTION
        "
        Client Trscv Tx Power Low :This 
        OID indicates that the Trscv output 
        power of port is lower than the 
        threshold value written in the
         Trscv EEPROM <Help> Alarm indicating 
        that the Trscv output power of
         port is lower than the threshold 
        value written in the Trscv EEPROM 
        <Condtype> TX_PWR_LOW_ALA_1 <Probcause> 
        transmitterFailure (56) <Alarmtype> 
        equipmentAlarm (5) <Polarity> (2) 
        "
	::= { pm10010mrAlmclientSfpAlmDdmEntry 2 }


--- *********************************************************
---     TABLE for the pm10010mrAlmclientSfpWarnDdm articles
--- *********************************************************

pm10010mrAlmclientSfpWarnDdmTable OBJECT-TYPE
	SYNTAX  SEQUENCE OF Pm10010mrAlmclientSfpWarnDdmEntry
	MAX-ACCESS not-accessible
	STATUS current
	DESCRIPTION
        "
        List of pm10010mrAlmclientSfpWarnDdm 
        Article
        "
	::= { pm10010mrAlmClientNurg 232 }


pm10010mrAlmclientSfpWarnDdmEntry OBJECT-TYPE
	SYNTAX Pm10010mrAlmclientSfpWarnDdmEntry
	MAX-ACCESS not-accessible
	STATUS current
	DESCRIPTION
        "
        Row definition for the pm10010mrAlmclientSfpWarnDdm 
        table
        "
	INDEX   { pm10010mrAlmclientSfpWarnDdmIndex }
	::= { pm10010mrAlmclientSfpWarnDdmTable 1 }


Pm10010mrAlmclientSfpWarnDdmEntry ::=
	SEQUENCE {
	pm10010mrAlmclientSfpWarnDdmIndex
		INTEGER,
	pm10010mrAlmRxPwrHighWngPortn
		EkiOnOff,
	pm10010mrAlmRxPwrLowWngPortn
		EkiOnOff,
	pm10010mrAlmTempHighWngPortn
		EkiOnOff,
	pm10010mrAlmTempLowWngPortn
		EkiOnOff,
	pm10010mrAlmVccHighWngPortn
		EkiOnOff,
	pm10010mrAlmVccLowWngPortn
		EkiOnOff,
	pm10010mrAlmTxBiasHighWngPortn
		EkiOnOff,
	pm10010mrAlmTxBiasLowWngPortn
		EkiOnOff,
	pm10010mrAlmTxPwrHighWngPortn
		EkiOnOff,
	pm10010mrAlmTxPwLowWngPortn
		EkiOnOff
	}


pm10010mrAlmclientSfpWarnDdmIndex OBJECT-TYPE
	SYNTAX  INTEGER(0..128)
	MAX-ACCESS  read-only
	STATUS current
	DESCRIPTION
        "
        Index definition for the pm10010mrAlmclientSfpWarnDdm 
        table
        "
	::= { pm10010mrAlmclientSfpWarnDdmEntry 1 }


pm10010mrAlmRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         RX_PWR_HIGH_WNG_1 <Probcause>
         receiveFailure (41) <Alarmtype> 
        equipmentAlarm (5) <Polarity> (2) 
        "
	::= { pm10010mrAlmclientSfpWarnDdmEntry 17 }


pm10010mrAlmRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         RX_PWR_LOW_WNG_1 <Probcause> receiveFailure 
        (41) <Alarmtype> equipmentAlarm 
        (5) <Polarity> (2) 
        "
	::= { pm10010mrAlmclientSfpWarnDdmEntry 16 }


pm10010mrAlmTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         TEMP_HIGH_WNG_1 <Probcause> temperatureUnacceptable 
        (51) <Alarmtype> equipmentAlarm 
        (5) <Polarity> (2) 
        "
	::= { pm10010mrAlmclientSfpWarnDdmEntry 9 }


pm10010mrAlmTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         TEMP_LOW_WNG_1 <Probcause> temperatureUnacceptable 
        (51) <Alarmtype> equipmentAlarm 
        (5) <Polarity> (2) 
        "
	::= { pm10010mrAlmclientSfpWarnDdmEntry 8 }


pm10010mrAlmVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> VCC_HIGH_WNG_1 <Probcause> 
        powerProblem (36) <Alarmtype> equipmentAlarm 
        (5) <Polarity> (2) 
        "
	::= { pm10010mrAlmclientSfpWarnDdmEntry 7 }


pm10010mrAlmVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> VCC_LOW_WNG_1 <Probcause> 
        powerProblem (36) <Alarmtype> equipmentAlarm 
        (5) <Polarity> (2) 
        "
	::= { pm10010mrAlmclientSfpWarnDdmEntry 6 }


pm10010mrAlmTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> TX_BIAS_HIGH_WNG_1 
        <Probcause> transmitterFailure
         (56) <Alarmtype> equipmentAlarm 
        (5) <Polarity> (2) 
        "
	::= { pm10010mrAlmclientSfpWarnDdmEntry 5 }


pm10010mrAlmTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> TX_BIAS_LOW_WNG_1 
        <Probcause> transmitterFailure
         (56) <Alarmtype> equipmentAlarm 
        (5) <Polarity> (2) 
        "
	::= { pm10010mrAlmclientSfpWarnDdmEntry 4 }


pm10010mrAlmTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        TX_PWR_HIGH_WNG_1 <Probcause> transmitterFailure 
        (56) <Alarmtype> equipmentAlarm 
        (5) <Polarity> (2) 
        "
	::= { pm10010mrAlmclientSfpWarnDdmEntry 3 }


pm10010mrAlmTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        TX_PW_LOW_WNG_1 <Probcause> transmitterFailure 
        (56) <Alarmtype> equipmentAlarm 
        (5) <Polarity> (2) 
        "
	::= { pm10010mrAlmclientSfpWarnDdmEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm10010mrCtrlconfMgnt1 OBJECT IDENTIFIER ::= { pm10010mrCtrlOther 1 }




pm10010mrCtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm10010mrCtrlconfMgnt1 14 }



pm10010mrCtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm10010mrCtrlconfMgnt1 10 }



pm10010mrCtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm10010mrCtrlconfMgnt1 2 }



pm10010mrCtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm10010mrCtrlconfMgnt1 1 }



--- *****************************************************
---     LEAF for the synth4 article
--- *****************************************************
pm10010mrCtrlsynth4 OBJECT IDENTIFIER ::= { pm10010mrCtrlOther 4 }




pm10010mrCtrlCorrelatOff OBJECT-TYPE
	  SYNTAX EkiOnOff
	  MAX-ACCESS read-write
	  STATUS current
	  DESCRIPTION
        "
        Disable Alarm Correlation :This 
        OID disables the alarm correlation 
        in the PM.
        "
	  ::= { pm10010mrCtrlsynth4 2 }



pm10010mrCtrlCorrelatOn OBJECT-TYPE
	  SYNTAX EkiOnOff
	  MAX-ACCESS read-write
	  STATUS current
	  DESCRIPTION
        "
        Enable Alarm Correlation :This 
        OID enables the alarm correlation 
        in the PM.
        "
	  ::= { pm10010mrCtrlsynth4 1 }



--- *****************************************************
---     LEAF for the swMgnt article
--- *****************************************************
pm10010mrCtrlswMgnt OBJECT IDENTIFIER ::= { pm10010mrCtrlOther 5 }




pm10010mrCtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm10010mrCtrlswMgnt 6 }



pm10010mrCtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm10010mrCtrlswMgnt 5 }



pm10010mrCtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm10010mrCtrlswMgnt 3 }



pm10010mrCtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm10010mrCtrlswMgnt 2 }



--- *****************************************************
---     LEAF for the gwMgnt article
--- *****************************************************
pm10010mrCtrlgwMgnt OBJECT IDENTIFIER ::= { pm10010mrCtrlOther 6 }




pm10010mrCtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm10010mrCtrlgwMgnt 8 }



pm10010mrCtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm10010mrCtrlgwMgnt 7 }



pm10010mrCtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm10010mrCtrlgwMgnt 6 }



pm10010mrCtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm10010mrCtrlgwMgnt 5 }



pm10010mrCtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm10010mrCtrlgwMgnt 1 }



--- *********************************************************
---     TABLE for the pm10010mrCtrlaccessLoop articles
--- *********************************************************

pm10010mrCtrlaccessLoopTable OBJECT-TYPE
	SYNTAX  SEQUENCE OF Pm10010mrCtrlaccessLoopEntry
	MAX-ACCESS not-accessible
	STATUS current
	DESCRIPTION
        "
        List of pm10010mrCtrlaccessLoop 
        Article
        "
	::= { pm10010mrCtrlClient 16 }


pm10010mrCtrlaccessLoopEntry OBJECT-TYPE
	SYNTAX Pm10010mrCtrlaccessLoopEntry
	MAX-ACCESS not-accessible
	STATUS current
	DESCRIPTION
        "
        Row definition for the pm10010mrCtrlaccessLoop 
        table
        "
	INDEX   { pm10010mrCtrlaccessLoopIndex }
	::= { pm10010mrCtrlaccessLoopTable 1 }


Pm10010mrCtrlaccessLoopEntry ::=
	SEQUENCE {
	pm10010mrCtrlaccessLoopIndex
		INTEGER,
	pm10010mrCtrlaccessLoopPortn
		EkiState
	}


pm10010mrCtrlaccessLoopIndex OBJECT-TYPE
	SYNTAX  INTEGER(0..128)
	MAX-ACCESS  read-only
	STATUS current
	DESCRIPTION
        "
        Index definition for the pm10010mrCtrlaccessLoop 
        table
        "
	::= { pm10010mrCtrlaccessLoopEntry 1 }


pm10010mrCtrlaccessLoopPortn OBJECT-TYPE
	SYNTAX  EkiState
	MAX-ACCESS read-write
	STATUS current
	DESCRIPTION
        "
        Client Facility Loopback :This 
        OID, when set at '1' puts the client 
        port in loopback, looping the received 
        10 Gb/s signal on the transmit
         10 Gb/s output.  <Help> This control 
        enables the Out Loopback on the 
        client port, looping the client 
        input signal on the client output
        "
	::= { pm10010mrCtrlaccessLoopEntry 2 }


--- *********************************************************
---     TABLE for the pm10010mrCtrlclientLoopToLine articles
--- *********************************************************

pm10010mrCtrlclientLoopToLineTable OBJECT-TYPE
	SYNTAX  SEQUENCE OF Pm10010mrCtrlclientLoopToLineEntry
	MAX-ACCESS not-accessible
	STATUS current
	DESCRIPTION
        "
        List of pm10010mrCtrlclientLoopToLine 
        Article
        "
	::= { pm10010mrCtrlClient 17 }


pm10010mrCtrlclientLoopToLineEntry OBJECT-TYPE
	SYNTAX Pm10010mrCtrlclientLoopToLineEntry
	MAX-ACCESS not-accessible
	STATUS current
	DESCRIPTION
        "
        Row definition for the pm10010mrCtrlclientLoopToLine 
        table
        "
	INDEX   { pm10010mrCtrlclientLoopToLineIndex }
	::= { pm10010mrCtrlclientLoopToLineTable 1 }


Pm10010mrCtrlclientLoopToLineEntry ::=
	SEQUENCE {
	pm10010mrCtrlclientLoopToLineIndex
		INTEGER,
	pm10010mrCtrlclientLoopToLinePortn
		EkiState
	}


pm10010mrCtrlclientLoopToLineIndex OBJECT-TYPE
	SYNTAX  INTEGER(0..128)
	MAX-ACCESS  read-only
	STATUS current
	DESCRIPTION
        "
        Index definition for the pm10010mrCtrlclientLoopToLine 
        table
        "
	::= { pm10010mrCtrlclientLoopToLineEntry 1 }


pm10010mrCtrlclientLoopToLinePortn OBJECT-TYPE
	SYNTAX  EkiState
	MAX-ACCESS read-write
	STATUS current
	DESCRIPTION
        "
        Client Terminal Loopback :This 
        OID, when set, puts the client
         port in loop back, looping the 
        10 Gb/s output signal on the 10 
        Gb/s input.<Help> This control
         enables the In Loopback on the 
        client port, looping the client 
        output signal on the client input
        "
	::= { pm10010mrCtrlclientLoopToLineEntry 2 }


--- *********************************************************
---     TABLE for the pm10010mrCtrlcsfUpIns articles
--- *********************************************************

pm10010mrCtrlcsfUpInsTable OBJECT-TYPE
	SYNTAX  SEQUENCE OF Pm10010mrCtrlcsfUpInsEntry
	MAX-ACCESS not-accessible
	STATUS current
	DESCRIPTION
        "
        List of pm10010mrCtrlcsfUpIns
         Article
        "
	::= { pm10010mrCtrlClient 21 }


pm10010mrCtrlcsfUpInsEntry OBJECT-TYPE
	SYNTAX Pm10010mrCtrlcsfUpInsEntry
	MAX-ACCESS not-accessible
	STATUS current
	DESCRIPTION
        "
        Row definition for the pm10010mrCtrlcsfUpIns 
        table
        "
	INDEX   { pm10010mrCtrlcsfUpInsIndex }
	::= { pm10010mrCtrlcsfUpInsTable 1 }


Pm10010mrCtrlcsfUpInsEntry ::=
	SEQUENCE {
	pm10010mrCtrlcsfUpInsIndex
		INTEGER,
	pm10010mrCtrlcsfUpInsPortn
		EkiState
	}


pm10010mrCtrlcsfUpInsIndex OBJECT-TYPE
	SYNTAX  INTEGER(0..128)
	MAX-ACCESS  read-only
	STATUS current
	DESCRIPTION
        "
        Index definition for the pm10010mrCtrlcsfUpIns 
        table
        "
	::= { pm10010mrCtrlcsfUpInsEntry 1 }


pm10010mrCtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm10010mrCtrlcsfUpInsEntry 2 }


--- *********************************************************
---     TABLE for the pm10010mrCtrlcaisDwIns articles
--- *********************************************************

pm10010mrCtrlcaisDwInsTable OBJECT-TYPE
	SYNTAX  SEQUENCE OF Pm10010mrCtrlcaisDwInsEntry
	MAX-ACCESS not-accessible
	STATUS current
	DESCRIPTION
        "
        List of pm10010mrCtrlcaisDwIns 
        Article
        "
	::= { pm10010mrCtrlClient 22 }


pm10010mrCtrlcaisDwInsEntry OBJECT-TYPE
	SYNTAX Pm10010mrCtrlcaisDwInsEntry
	MAX-ACCESS not-accessible
	STATUS current
	DESCRIPTION
        "
        Row definition for the pm10010mrCtrlcaisDwIns 
        table
        "
	INDEX   { pm10010mrCtrlcaisDwInsIndex }
	::= { pm10010mrCtrlcaisDwInsTable 1 }


Pm10010mrCtrlcaisDwInsEntry ::=
	SEQUENCE {
	pm10010mrCtrlcaisDwInsIndex
		INTEGER,
	pm10010mrCtrlcaisDwInsPortn
		EkiState
	}


pm10010mrCtrlcaisDwInsIndex OBJECT-TYPE
	SYNTAX  INTEGER(0..128)
	MAX-ACCESS  read-only
	STATUS current
	DESCRIPTION
        "
        Index definition for the pm10010mrCtrlcaisDwIns 
        table
        "
	::= { pm10010mrCtrlcaisDwInsEntry 1 }


pm10010mrCtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm10010mrCtrlcaisDwInsEntry 2 }


--- *********************************************************
---     TABLE for the pm10010mrCtrlcommAccessLoop articles
--- *********************************************************

pm10010mrCtrlcommAccessLoopTable OBJECT-TYPE
	SYNTAX  SEQUENCE OF Pm10010mrCtrlcommAccessLoopEntry
	MAX-ACCESS not-accessible
	STATUS current
	DESCRIPTION
        "
        List of pm10010mrCtrlcommAccessLoop 
        Article
        "
	::= { pm10010mrCtrlLine 64 }


pm10010mrCtrlcommAccessLoopEntry OBJECT-TYPE
	SYNTAX Pm10010mrCtrlcommAccessLoopEntry
	MAX-ACCESS not-accessible
	STATUS current
	DESCRIPTION
        "
        Row definition for the pm10010mrCtrlcommAccessLoop 
        table
        "
	INDEX   { pm10010mrCtrlcommAccessLoopIndex }
	::= { pm10010mrCtrlcommAccessLoopTable 1 }


Pm10010mrCtrlcommAccessLoopEntry ::=
	SEQUENCE {
	pm10010mrCtrlcommAccessLoopIndex
		INTEGER,
	pm10010mrCtrlcommAccessLoopPortn
		EkiState
	}


pm10010mrCtrlcommAccessLoopIndex OBJECT-TYPE
	SYNTAX  INTEGER(0..128)
	MAX-ACCESS  read-only
	STATUS current
	DESCRIPTION
        "
        Index definition for the pm10010mrCtrlcommAccessLoop 
        table
        "
	::= { pm10010mrCtrlcommAccessLoopEntry 1 }


pm10010mrCtrlcommAccessLoopPortn OBJECT-TYPE
	SYNTAX  EkiState
	MAX-ACCESS read-write
	STATUS current
	DESCRIPTION
        "
        Line Terminal Loopback :This OID, 
        when set, puts the module in common 
        access loop back, looping the 100 
        Gb/s output signal on the 100 Gb/s 
        input.<Help> This control enables 
        the In Loopback on the line port, 
        looping the 100 Gb/s output signal 
        on the 100 Gb/s input
        "
	::= { pm10010mrCtrlcommAccessLoopEntry 2 }


--- *********************************************************
---     TABLE for the pm10010mrCtrllineLoop articles
--- *********************************************************

pm10010mrCtrllineLoopTable OBJECT-TYPE
	SYNTAX  SEQUENCE OF Pm10010mrCtrllineLoopEntry
	MAX-ACCESS not-accessible
	STATUS current
	DESCRIPTION
        "
        List of pm10010mrCtrllineLoop
         Article
        "
	::= { pm10010mrCtrlLine 66 }


pm10010mrCtrllineLoopEntry OBJECT-TYPE
	SYNTAX Pm10010mrCtrllineLoopEntry
	MAX-ACCESS not-accessible
	STATUS current
	DESCRIPTION
        "
        Row definition for the pm10010mrCtrllineLoop 
        table
        "
	INDEX   { pm10010mrCtrllineLoopIndex }
	::= { pm10010mrCtrllineLoopTable 1 }


Pm10010mrCtrllineLoopEntry ::=
	SEQUENCE {
	pm10010mrCtrllineLoopIndex
		INTEGER,
	pm10010mrCtrllineLoopPortn
		EkiState
	}


pm10010mrCtrllineLoopIndex OBJECT-TYPE
	SYNTAX  INTEGER(0..128)
	MAX-ACCESS  read-only
	STATUS current
	DESCRIPTION
        "
        Index definition for the pm10010mrCtrllineLoop 
        table
        "
	::= { pm10010mrCtrllineLoopEntry 1 }


pm10010mrCtrllineLoopPortn OBJECT-TYPE
	SYNTAX  EkiState
	MAX-ACCESS read-write
	STATUS current
	DESCRIPTION
        "
        Line Facility Loopback :This OID, 
        when set at '1' puts the module 
        in line loopback mode, looping
         the received 100 Gb/s signal on 
        the transmit 100 Gb/s output. The 
        Upstream part of the module is
         timed on the 100 Gb/s recovered 
        clock in that case.<Help> This
         control enables the Out Loopback 
        on the line port, looping the 100 
        Gb/s input signal on the 100 Gb/s 
        output
        "
	::= { pm10010mrCtrllineLoopEntry 2 }


--- *********************************************************
---     TABLE for the pm10010mrCtrlfecDisable articles
--- *********************************************************

pm10010mrCtrlfecDisableTable OBJECT-TYPE
	SYNTAX  SEQUENCE OF Pm10010mrCtrlfecDisableEntry
	MAX-ACCESS not-accessible
	STATUS current
	DESCRIPTION
        "
        List of pm10010mrCtrlfecDisable 
        Article
        "
	::= { pm10010mrCtrlLine 69 }


pm10010mrCtrlfecDisableEntry OBJECT-TYPE
	SYNTAX Pm10010mrCtrlfecDisableEntry
	MAX-ACCESS not-accessible
	STATUS current
	DESCRIPTION
        "
        Row definition for the pm10010mrCtrlfecDisable 
        table
        "
	INDEX   { pm10010mrCtrlfecDisableIndex }
	::= { pm10010mrCtrlfecDisableTable 1 }


Pm10010mrCtrlfecDisableEntry ::=
	SEQUENCE {
	pm10010mrCtrlfecDisableIndex
		INTEGER,
	pm10010mrCtrlfecDisablePortn
		EkiState
	}


pm10010mrCtrlfecDisableIndex OBJECT-TYPE
	SYNTAX  INTEGER(0..128)
	MAX-ACCESS  read-only
	STATUS current
	DESCRIPTION
        "
        Index definition for the pm10010mrCtrlfecDisable 
        table
        "
	::= { pm10010mrCtrlfecDisableEntry 1 }


pm10010mrCtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pm10010mrCtrlfecDisableEntry 2 }


--- *****************************************************
---     LEAF for the ledTest article
--- *****************************************************
pm10010mrCtrlledTest OBJECT IDENTIFIER ::= { pm10010mrCtrlOther 192 }




pm10010mrCtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm10010mrCtrlledTest 3 }



pm10010mrCtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm10010mrCtrlledTest 2 }



pm10010mrCtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm10010mrCtrlledTest 1 }



--- *****************************************************
---     LEAF for the initSwitchMarvell article
--- *****************************************************
pm10010mrCtrlinitSwitchMarvell OBJECT IDENTIFIER ::= { pm10010mrCtrlOther 201 }




pm10010mrCtrlInitSwitchMarvell OBJECT-TYPE
	  SYNTAX EkiOnOff
	  MAX-ACCESS read-write
	  STATUS current
	  DESCRIPTION
        "
        Switch Initialization :This OID 
        operates an initialization of the 
        switch managed through the module 
         <Help>  This control activates 
        an initialization of the switch 
        managed through the module
        "
	  ::= { pm10010mrCtrlinitSwitchMarvell 1 }



--- *********************************************************
---     TABLE for the pm10010mrCtrlmsaLineLoop articles
--- *********************************************************

pm10010mrCtrlmsaLineLoopTable OBJECT-TYPE
	SYNTAX  SEQUENCE OF Pm10010mrCtrlmsaLineLoopEntry
	MAX-ACCESS not-accessible
	STATUS current
	DESCRIPTION
        "
        List of pm10010mrCtrlmsaLineLoop 
        Article
        "
	::= { pm10010mrCtrlLine 209 }


pm10010mrCtrlmsaLineLoopEntry OBJECT-TYPE
	SYNTAX Pm10010mrCtrlmsaLineLoopEntry
	MAX-ACCESS not-accessible
	STATUS current
	DESCRIPTION
        "
        Row definition for the pm10010mrCtrlmsaLineLoop 
        table
        "
	INDEX   { pm10010mrCtrlmsaLineLoopIndex }
	::= { pm10010mrCtrlmsaLineLoopTable 1 }


Pm10010mrCtrlmsaLineLoopEntry ::=
	SEQUENCE {
	pm10010mrCtrlmsaLineLoopIndex
		INTEGER,
	pm10010mrCtrlmsaLineLoopPortn
		EkiState
	}


pm10010mrCtrlmsaLineLoopIndex OBJECT-TYPE
	SYNTAX  INTEGER(0..128)
	MAX-ACCESS  read-only
	STATUS current
	DESCRIPTION
        "
        Index definition for the pm10010mrCtrlmsaLineLoop 
        table
        "
	::= { pm10010mrCtrlmsaLineLoopEntry 1 }


pm10010mrCtrlmsaLineLoopPortn OBJECT-TYPE
	SYNTAX  EkiState
	MAX-ACCESS read-write
	STATUS current
	DESCRIPTION
        "
        MSA Line Loop :This OID operates 
        a line loopback on the MSA Line 
         <Help>  This control defines the 
        line loop back of the line transceiver
        "
	::= { pm10010mrCtrlmsaLineLoopEntry 2 }


--- *********************************************************
---     TABLE for the pm10010mrCtrlmsaTxReset articles
--- *********************************************************

pm10010mrCtrlmsaTxResetTable OBJECT-TYPE
	SYNTAX  SEQUENCE OF Pm10010mrCtrlmsaTxResetEntry
	MAX-ACCESS not-accessible
	STATUS current
	DESCRIPTION
        "
        List of pm10010mrCtrlmsaTxReset 
        Article
        "
	::= { pm10010mrCtrlLine 210 }


pm10010mrCtrlmsaTxResetEntry OBJECT-TYPE
	SYNTAX Pm10010mrCtrlmsaTxResetEntry
	MAX-ACCESS not-accessible
	STATUS current
	DESCRIPTION
        "
        Row definition for the pm10010mrCtrlmsaTxReset 
        table
        "
	INDEX   { pm10010mrCtrlmsaTxResetIndex }
	::= { pm10010mrCtrlmsaTxResetTable 1 }


Pm10010mrCtrlmsaTxResetEntry ::=
	SEQUENCE {
	pm10010mrCtrlmsaTxResetIndex
		INTEGER,
	pm10010mrCtrlmsaTxResetPortn
		EkiState
	}


pm10010mrCtrlmsaTxResetIndex OBJECT-TYPE
	SYNTAX  INTEGER(0..128)
	MAX-ACCESS  read-only
	STATUS current
	DESCRIPTION
        "
        Index definition for the pm10010mrCtrlmsaTxReset 
        table
        "
	::= { pm10010mrCtrlmsaTxResetEntry 1 }


pm10010mrCtrlmsaTxResetPortn OBJECT-TYPE
	SYNTAX  EkiState
	MAX-ACCESS read-write
	STATUS current
	DESCRIPTION
        "
        Line MSA TX Reset :This OID resets 
        the TX portion of the MSA line
         module  <Help > This control 
         initiates a reset of the transmitting 
        side
        "
	::= { pm10010mrCtrlmsaTxResetEntry 2 }


--- *********************************************************
---     TABLE for the pm10010mrCtrlmsaRxReset articles
--- *********************************************************

pm10010mrCtrlmsaRxResetTable OBJECT-TYPE
	SYNTAX  SEQUENCE OF Pm10010mrCtrlmsaRxResetEntry
	MAX-ACCESS not-accessible
	STATUS current
	DESCRIPTION
        "
        List of pm10010mrCtrlmsaRxReset 
        Article
        "
	::= { pm10010mrCtrlLine 211 }


pm10010mrCtrlmsaRxResetEntry OBJECT-TYPE
	SYNTAX Pm10010mrCtrlmsaRxResetEntry
	MAX-ACCESS not-accessible
	STATUS current
	DESCRIPTION
        "
        Row definition for the pm10010mrCtrlmsaRxReset 
        table
        "
	INDEX   { pm10010mrCtrlmsaRxResetIndex }
	::= { pm10010mrCtrlmsaRxResetTable 1 }


Pm10010mrCtrlmsaRxResetEntry ::=
	SEQUENCE {
	pm10010mrCtrlmsaRxResetIndex
		INTEGER,
	pm10010mrCtrlmsaRxResetPortn
		EkiState
	}


pm10010mrCtrlmsaRxResetIndex OBJECT-TYPE
	SYNTAX  INTEGER(0..128)
	MAX-ACCESS  read-only
	STATUS current
	DESCRIPTION
        "
        Index definition for the pm10010mrCtrlmsaRxReset 
        table
        "
	::= { pm10010mrCtrlmsaRxResetEntry 1 }


pm10010mrCtrlmsaRxResetPortn OBJECT-TYPE
	SYNTAX  EkiState
	MAX-ACCESS read-write
	STATUS current
	DESCRIPTION
        "
        Line MSA RX Reset :This OID resets 
        the RX portion of the MSA line
         module  <Help > This control 
         initiates a reset of the receiving 
        side
        "
	::= { pm10010mrCtrlmsaRxResetEntry 2 }


--- *********************************************************
---     TABLE for the pm10010mrCtrlmsaShutdown articles
--- *********************************************************

pm10010mrCtrlmsaShutdownTable OBJECT-TYPE
	SYNTAX  SEQUENCE OF Pm10010mrCtrlmsaShutdownEntry
	MAX-ACCESS not-accessible
	STATUS current
	DESCRIPTION
        "
        List of pm10010mrCtrlmsaShutdown 
        Article
        "
	::= { pm10010mrCtrlLine 212 }


pm10010mrCtrlmsaShutdownEntry OBJECT-TYPE
	SYNTAX Pm10010mrCtrlmsaShutdownEntry
	MAX-ACCESS not-accessible
	STATUS current
	DESCRIPTION
        "
        Row definition for the pm10010mrCtrlmsaShutdown 
        table
        "
	INDEX   { pm10010mrCtrlmsaShutdownIndex }
	::= { pm10010mrCtrlmsaShutdownTable 1 }


Pm10010mrCtrlmsaShutdownEntry ::=
	SEQUENCE {
	pm10010mrCtrlmsaShutdownIndex
		INTEGER,
	pm10010mrCtrlmsaShutdownPortn
		EkiState
	}


pm10010mrCtrlmsaShutdownIndex OBJECT-TYPE
	SYNTAX  INTEGER(0..128)
	MAX-ACCESS  read-only
	STATUS current
	DESCRIPTION
        "
        Index definition for the pm10010mrCtrlmsaShutdown 
        table
        "
	::= { pm10010mrCtrlmsaShutdownEntry 1 }


pm10010mrCtrlmsaShutdownPortn OBJECT-TYPE
	SYNTAX  EkiState
	MAX-ACCESS read-write
	STATUS current
	DESCRIPTION
        "
        Line MSA Shutdown :This OID enters 
        a process to shutdown the MSA line 
        module  <Help > This control  initiates 
        a shutdown of the module
        "
	::= { pm10010mrCtrlmsaShutdownEntry 2 }


--- *****************************************************
---     LEAF for the resetCount article
--- *****************************************************
pm10010mrCtrlresetCount OBJECT IDENTIFIER ::= { pm10010mrCtrlOther 259 }




pm10010mrCtrlResetcount OBJECT-TYPE
	  SYNTAX EkiOnOff
	  MAX-ACCESS read-write
	  STATUS current
	  DESCRIPTION
        "
        Module Count Global Reset :This 
        OID resets all the errors counters 
        on the module  <Help > This control 
         initiates a reset of the errors 
        counters on the module
        "
	  ::= { pm10010mrCtrlresetCount 1 }



--- *****************************************************
---     LEAF for the resetRmon article
--- *****************************************************
pm10010mrCtrlresetRmon OBJECT IDENTIFIER ::= { pm10010mrCtrlOther 260 }




pm10010mrCtrlResetrmon OBJECT-TYPE
	  SYNTAX EkiOnOff
	  MAX-ACCESS read-write
	  STATUS current
	  DESCRIPTION
        "
        Module Rmon Global Reset :This 
        OID resets all the Rmon counters 
        on the module  <Help > This control 
         initiates a reset of the Rmon
         counters on the module
        "
	  ::= { pm10010mrCtrlresetRmon 1 }



--- *****************************************************
---     LEAF for the resetMeasurements article
--- *****************************************************
pm10010mrCtrlresetMeasurements OBJECT IDENTIFIER ::= { pm10010mrCtrlOther 261 }




pm10010mrCtrlResetmeasurements OBJECT-TYPE
	  SYNTAX EkiOnOff
	  MAX-ACCESS read-write
	  STATUS current
	  DESCRIPTION
        "
        Management Meas Global Reset :This 
        OID resets some measurements on 
        the management  <Help > This control 
         initiates a reset of some measurements 
        on the management
        "
	  ::= { pm10010mrCtrlresetMeasurements 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm10010mrCntclientInputErrorCounterLaneOne articles
--- *********************************************************

pm10010mrCntclientInputErrorCounterLaneOneTable OBJECT-TYPE
	SYNTAX  SEQUENCE OF Pm10010mrCntclientInputErrorCounterLaneOneEntry
	MAX-ACCESS not-accessible
	STATUS current
	DESCRIPTION
        "
        List of pm10010mrCntclientInputErrorCounterLaneOne 
        Article
        "
	::= { pm10010mrCntClient 16 }


pm10010mrCntclientInputErrorCounterLaneOneEntry OBJECT-TYPE
	SYNTAX Pm10010mrCntclientInputErrorCounterLaneOneEntry
	MAX-ACCESS not-accessible
	STATUS current
	DESCRIPTION
        "
        Row definition for the pm10010mrCntclientInputErrorCounterLaneOne 
        table
        "
	INDEX   { pm10010mrCntclientInputErrorCounterLaneOneIndex }
	::= { pm10010mrCntclientInputErrorCounterLaneOneTable 1 }


Pm10010mrCntclientInputErrorCounterLaneOneEntry ::=
	SEQUENCE {
	pm10010mrCntclientInputErrorCounterLaneOneIndex
		INTEGER,
	pm10010mrCntclientInputErrorCounterLaneOneValuePortn
		Counter32,
	pm10010mrCntclientInputErrorCounterLaneOneErrorPortn
		EkiOnOff,
	pm10010mrCntclientInputErrorCounterLaneOneOverloadPortn
		EkiOnOff
	}


pm10010mrCntclientInputErrorCounterLaneOneIndex OBJECT-TYPE
	SYNTAX  INTEGER(0..128)
	MAX-ACCESS  read-only
	STATUS current
	DESCRIPTION
        "
        Index definition for the pm10010mrCntclientInputErrorCounterLaneOne 
        table
        "
	::= { pm10010mrCntclientInputErrorCounterLaneOneEntry 1 }


pm10010mrCntclientInputErrorCounterLaneOneValuePortn OBJECT-TYPE
	SYNTAX  Counter32
	MAX-ACCESS read-only
	STATUS current
	DESCRIPTION
        "
        Client_Input_Error_Counter_Lane1 
        :This counter is incremented each 
        time a coding violation is detected 
        on the host lane of the client
         transceiver <Help> This counter 
        is incremented each time a coding 
        violation is detected on the host 
        lane of the client transceiver
        "
	::= { pm10010mrCntclientInputErrorCounterLaneOneEntry 2 }


pm10010mrCntclientInputErrorCounterLaneOneErrorPortn OBJECT-TYPE
	SYNTAX  EkiOnOff
	MAX-ACCESS read-only
	STATUS current
	DESCRIPTION
        "
        Client Input Counter Error :This 
        OID when set indicates the rate 
        adaptation removal counter value 
        is invalid on Port
        "
	::= { pm10010mrCntclientInputErrorCounterLaneOneEntry 3 }


pm10010mrCntclientInputErrorCounterLaneOneOverloadPortn OBJECT-TYPE
	SYNTAX  EkiOnOff
	MAX-ACCESS read-only
	STATUS current
	DESCRIPTION
        "
        Client Input Counter Overload
         :This OID when set indicates a 
        rate adaptation removal counter 
        overload on Port
        "
	::= { pm10010mrCntclientInputErrorCounterLaneOneEntry 4 }


--- *********************************************************
---     TABLE for the pm10010mrCntclientInputErrorCounterLaneTwo articles
--- *********************************************************

pm10010mrCntclientInputErrorCounterLaneTwoTable OBJECT-TYPE
	SYNTAX  SEQUENCE OF Pm10010mrCntclientInputErrorCounterLaneTwoEntry
	MAX-ACCESS not-accessible
	STATUS current
	DESCRIPTION
        "
        List of pm10010mrCntclientInputErrorCounterLaneTwo 
        Article
        "
	::= { pm10010mrCntClient 32 }


pm10010mrCntclientInputErrorCounterLaneTwoEntry OBJECT-TYPE
	SYNTAX Pm10010mrCntclientInputErrorCounterLaneTwoEntry
	MAX-ACCESS not-accessible
	STATUS current
	DESCRIPTION
        "
        Row definition for the pm10010mrCntclientInputErrorCounterLaneTwo 
        table
        "
	INDEX   { pm10010mrCntclientInputErrorCounterLaneTwoIndex }
	::= { pm10010mrCntclientInputErrorCounterLaneTwoTable 1 }


Pm10010mrCntclientInputErrorCounterLaneTwoEntry ::=
	SEQUENCE {
	pm10010mrCntclientInputErrorCounterLaneTwoIndex
		INTEGER,
	pm10010mrCntclientInputErrorCounterLaneTwoValuePortn
		Counter32,
	pm10010mrCntclientInputErrorCounterLaneTwoErrorPortn
		EkiOnOff,
	pm10010mrCntclientInputErrorCounterLaneTwoOverloadPortn
		EkiOnOff
	}


pm10010mrCntclientInputErrorCounterLaneTwoIndex OBJECT-TYPE
	SYNTAX  INTEGER(0..128)
	MAX-ACCESS  read-only
	STATUS current
	DESCRIPTION
        "
        Index definition for the pm10010mrCntclientInputErrorCounterLaneTwo 
        table
        "
	::= { pm10010mrCntclientInputErrorCounterLaneTwoEntry 1 }


pm10010mrCntclientInputErrorCounterLaneTwoValuePortn OBJECT-TYPE
	SYNTAX  Counter32
	MAX-ACCESS read-only
	STATUS current
	DESCRIPTION
        "
        Client_Input_Error_Counter_Lane2 
        :This counter is incremented each 
        time a coding violation is detected 
        on the host lane of the client
         transceiver <Help> This counter 
        is incremented each time a coding 
        violation is detected on the host 
        lane of the client transceiver
        "
	::= { pm10010mrCntclientInputErrorCounterLaneTwoEntry 2 }


pm10010mrCntclientInputErrorCounterLaneTwoErrorPortn OBJECT-TYPE
	SYNTAX  EkiOnOff
	MAX-ACCESS read-only
	STATUS current
	DESCRIPTION
        "
        Client Input Counter Error :This 
        OID when set indicates the client 
        error counter value is invalid
         on Port
        "
	::= { pm10010mrCntclientInputErrorCounterLaneTwoEntry 3 }


pm10010mrCntclientInputErrorCounterLaneTwoOverloadPortn OBJECT-TYPE
	SYNTAX  EkiOnOff
	MAX-ACCESS read-only
	STATUS current
	DESCRIPTION
        "
        Client Input Counter Overload
         :This OID when set indicates a 
        client input error counter overload 
        on Port
        "
	::= { pm10010mrCntclientInputErrorCounterLaneTwoEntry 4 }


--- *********************************************************
---     TABLE for the pm10010mrCntclientInputErrorCounter articles
--- *********************************************************

pm10010mrCntclientInputErrorCounterTable OBJECT-TYPE
	SYNTAX  SEQUENCE OF Pm10010mrCntclientInputErrorCounterEntry
	MAX-ACCESS not-accessible
	STATUS current
	DESCRIPTION
        "
        List of pm10010mrCntclientInputErrorCounter 
        Article
        "
	::= { pm10010mrCntClient 80 }


pm10010mrCntclientInputErrorCounterEntry OBJECT-TYPE
	SYNTAX Pm10010mrCntclientInputErrorCounterEntry
	MAX-ACCESS not-accessible
	STATUS current
	DESCRIPTION
        "
        Row definition for the pm10010mrCntclientInputErrorCounter 
        table
        "
	INDEX   { pm10010mrCntclientInputErrorCounterIndex }
	::= { pm10010mrCntclientInputErrorCounterTable 1 }


Pm10010mrCntclientInputErrorCounterEntry ::=
	SEQUENCE {
	pm10010mrCntclientInputErrorCounterIndex
		INTEGER,
	pm10010mrCntclientInputErrorCounterValuePortn
		Counter32,
	pm10010mrCntclientInputErrorCounterErrorPortn
		EkiOnOff,
	pm10010mrCntclientInputErrorCounterOverloadPortn
		EkiOnOff
	}


pm10010mrCntclientInputErrorCounterIndex OBJECT-TYPE
	SYNTAX  INTEGER(0..128)
	MAX-ACCESS  read-only
	STATUS current
	DESCRIPTION
        "
        Index definition for the pm10010mrCntclientInputErrorCounter 
        table
        "
	::= { pm10010mrCntclientInputErrorCounterEntry 1 }


pm10010mrCntclientInputErrorCounterValuePortn OBJECT-TYPE
	SYNTAX  Counter32
	MAX-ACCESS read-only
	STATUS current
	DESCRIPTION
        "
        Client Input Errors :This counter 
        is increased each time a 10b/8b 
        running disparity error is detected 
        on the Client input stream  <Help> 
         This counter gives the number
         of 10b/8b running disparity errors 
        on the client port
        "
	::= { pm10010mrCntclientInputErrorCounterEntry 2 }


pm10010mrCntclientInputErrorCounterErrorPortn OBJECT-TYPE
	SYNTAX  EkiOnOff
	MAX-ACCESS read-only
	STATUS current
	DESCRIPTION
        "
        Client Counter Error :This OID 
        when set indicates the client error 
        counter value is invalid on Port
        "
	::= { pm10010mrCntclientInputErrorCounterEntry 3 }


pm10010mrCntclientInputErrorCounterOverloadPortn OBJECT-TYPE
	SYNTAX  EkiOnOff
	MAX-ACCESS read-only
	STATUS current
	DESCRIPTION
        "
        Client Counter Overload :This
         OID when set indicates a client 
        input error counter overload on 
        Port
        "
	::= { pm10010mrCntclientInputErrorCounterEntry 4 }


--- *********************************************************
---     TABLE for the pm10010mrCntclientCbipCounter articles
--- *********************************************************

pm10010mrCntclientCbipCounterTable OBJECT-TYPE
	SYNTAX  SEQUENCE OF Pm10010mrCntclientCbipCounterEntry
	MAX-ACCESS not-accessible
	STATUS current
	DESCRIPTION
        "
        List of pm10010mrCntclientCbipCounter 
        Article
        "
	::= { pm10010mrCntClient 96 }


pm10010mrCntclientCbipCounterEntry OBJECT-TYPE
	SYNTAX Pm10010mrCntclientCbipCounterEntry
	MAX-ACCESS not-accessible
	STATUS current
	DESCRIPTION
        "
        Row definition for the pm10010mrCntclientCbipCounter 
        table
        "
	INDEX   { pm10010mrCntclientCbipCounterIndex }
	::= { pm10010mrCntclientCbipCounterTable 1 }


Pm10010mrCntclientCbipCounterEntry ::=
	SEQUENCE {
	pm10010mrCntclientCbipCounterIndex
		INTEGER,
	pm10010mrCntclientCbipCounterValuePortn
		Counter32,
	pm10010mrCntclientCbipCounterErrorPortn
		EkiOnOff,
	pm10010mrCntclientCbipCounterOverloadPortn
		EkiOnOff
	}


pm10010mrCntclientCbipCounterIndex OBJECT-TYPE
	SYNTAX  INTEGER(0..128)
	MAX-ACCESS  read-only
	STATUS current
	DESCRIPTION
        "
        Index definition for the pm10010mrCntclientCbipCounter 
        table
        "
	::= { pm10010mrCntclientCbipCounterEntry 1 }


pm10010mrCntclientCbipCounterValuePortn OBJECT-TYPE
	SYNTAX  Counter32
	MAX-ACCESS read-only
	STATUS current
	DESCRIPTION
        "
        Client Output Errors :This counter 
        is incremented each time a CBIP 
        parity error is detected on the 
        Client output stream  <Help>  This 
        counter gives the number of CBIP 
        errors on the client port
        "
	::= { pm10010mrCntclientCbipCounterEntry 2 }


pm10010mrCntclientCbipCounterErrorPortn OBJECT-TYPE
	SYNTAX  EkiOnOff
	MAX-ACCESS read-only
	STATUS current
	DESCRIPTION
        "
        Client Counter Error :This OID 
        when set indicates the CBIP error 
        counter value is invalid on Port
        "
	::= { pm10010mrCntclientCbipCounterEntry 3 }


pm10010mrCntclientCbipCounterOverloadPortn OBJECT-TYPE
	SYNTAX  EkiOnOff
	MAX-ACCESS read-only
	STATUS current
	DESCRIPTION
        "
        Client CBIP Counter Overload :This 
        OID when set indicates a CBIP error 
        counter overload on Port
        "
	::= { pm10010mrCntclientCbipCounterEntry 4 }


--- *********************************************************
---     TABLE for the pm10010mrCntlocalLineSmBip8ErrorCounter articles
--- *********************************************************

pm10010mrCntlocalLineSmBip8ErrorCounterTable OBJECT-TYPE
	SYNTAX  SEQUENCE OF Pm10010mrCntlocalLineSmBip8ErrorCounterEntry
	MAX-ACCESS not-accessible
	STATUS current
	DESCRIPTION
        "
        List of pm10010mrCntlocalLineSmBip8ErrorCounter 
        Article
        "
	::= { pm10010mrCntLine 192 }


pm10010mrCntlocalLineSmBip8ErrorCounterEntry OBJECT-TYPE
	SYNTAX Pm10010mrCntlocalLineSmBip8ErrorCounterEntry
	MAX-ACCESS not-accessible
	STATUS current
	DESCRIPTION
        "
        Row definition for the pm10010mrCntlocalLineSmBip8ErrorCounter 
        table
        "
	INDEX   { pm10010mrCntlocalLineSmBip8ErrorCounterIndex }
	::= { pm10010mrCntlocalLineSmBip8ErrorCounterTable 1 }


Pm10010mrCntlocalLineSmBip8ErrorCounterEntry ::=
	SEQUENCE {
	pm10010mrCntlocalLineSmBip8ErrorCounterIndex
		INTEGER,
	pm10010mrCntlocalLineSmBip8ErrorCounterValuePortn
		Counter64,
	pm10010mrCntlocalLineSmBip8ErrorCounterErrorPortn
		EkiOnOff,
	pm10010mrCntlocalLineSmBip8ErrorCounterOverloadPortn
		EkiOnOff
	}


pm10010mrCntlocalLineSmBip8ErrorCounterIndex OBJECT-TYPE
	SYNTAX  INTEGER(0..128)
	MAX-ACCESS  read-only
	STATUS current
	DESCRIPTION
        "
        Index definition for the pm10010mrCntlocalLineSmBip8ErrorCounter 
        table
        "
	::= { pm10010mrCntlocalLineSmBip8ErrorCounterEntry 1 }


pm10010mrCntlocalLineSmBip8ErrorCounterValuePortn OBJECT-TYPE
	SYNTAX  Counter64
	MAX-ACCESS read-only
	STATUS current
	DESCRIPTION
        "
        Line Input SM-BIP8 Errors :This 
        OID gives the current Bit Error 
        Rate (residual SM-BIP8 error) after 
        FEC   <Help> This counter gives 
        the current Bit Error Rate (residual 
        SM-BIP8 error) after FEC
        "
	::= { pm10010mrCntlocalLineSmBip8ErrorCounterEntry 2 }


pm10010mrCntlocalLineSmBip8ErrorCounterErrorPortn OBJECT-TYPE
	SYNTAX  EkiOnOff
	MAX-ACCESS read-only
	STATUS current
	DESCRIPTION
        "
        Line Counter Error :This OID when 
        set indicates the B1 error counter 
        value is invalid on Port
        "
	::= { pm10010mrCntlocalLineSmBip8ErrorCounterEntry 3 }


pm10010mrCntlocalLineSmBip8ErrorCounterOverloadPortn OBJECT-TYPE
	SYNTAX  EkiOnOff
	MAX-ACCESS read-only
	STATUS current
	DESCRIPTION
        "
        Line Counter Overload :This OID 
        when set indicates a B1 error counter 
        overload on Port
        "
	::= { pm10010mrCntlocalLineSmBip8ErrorCounterEntry 4 }


--- *********************************************************
---     TABLE for the pm10010mrCntlocalLineFecCorrectedErrorsCounter articles
--- *********************************************************

pm10010mrCntlocalLineFecCorrectedErrorsCounterTable OBJECT-TYPE
	SYNTAX  SEQUENCE OF Pm10010mrCntlocalLineFecCorrectedErrorsCounterEntry
	MAX-ACCESS not-accessible
	STATUS current
	DESCRIPTION
        "
        List of pm10010mrCntlocalLineFecCorrectedErrorsCounter 
        Article
        "
	::= { pm10010mrCntLine 193 }


pm10010mrCntlocalLineFecCorrectedErrorsCounterEntry OBJECT-TYPE
	SYNTAX Pm10010mrCntlocalLineFecCorrectedErrorsCounterEntry
	MAX-ACCESS not-accessible
	STATUS current
	DESCRIPTION
        "
        Row definition for the pm10010mrCntlocalLineFecCorrectedErrorsCounter 
        table
        "
	INDEX   { pm10010mrCntlocalLineFecCorrectedErrorsCounterIndex }
	::= { pm10010mrCntlocalLineFecCorrectedErrorsCounterTable 1 }


Pm10010mrCntlocalLineFecCorrectedErrorsCounterEntry ::=
	SEQUENCE {
	pm10010mrCntlocalLineFecCorrectedErrorsCounterIndex
		INTEGER,
	pm10010mrCntlocalLineFecCorrectedErrorsCounterValuePortn
		Counter64,
	pm10010mrCntlocalLineFecCorrectedErrorsCounterErrorPortn
		EkiOnOff,
	pm10010mrCntlocalLineFecCorrectedErrorsCounterOverloadPortn
		EkiOnOff
	}


pm10010mrCntlocalLineFecCorrectedErrorsCounterIndex OBJECT-TYPE
	SYNTAX  INTEGER(0..128)
	MAX-ACCESS  read-only
	STATUS current
	DESCRIPTION
        "
        Index definition for the pm10010mrCntlocalLineFecCorrectedErrorsCounter 
        table
        "
	::= { pm10010mrCntlocalLineFecCorrectedErrorsCounterEntry 1 }


pm10010mrCntlocalLineFecCorrectedErrorsCounterValuePortn OBJECT-TYPE
	SYNTAX  Counter64
	MAX-ACCESS read-only
	STATUS current
	DESCRIPTION
        "
        Line Input HD FEC Corrected Errors 
        :This OID gives the current Bit 
        Error Rate before the Hard Decision 
        FEC  <Help> This counter gives
         the current Bit Error Rate before 
        the Hard Decision FEC
        "
	::= { pm10010mrCntlocalLineFecCorrectedErrorsCounterEntry 2 }


pm10010mrCntlocalLineFecCorrectedErrorsCounterErrorPortn OBJECT-TYPE
	SYNTAX  EkiOnOff
	MAX-ACCESS read-only
	STATUS current
	DESCRIPTION
        "
        FEC Counter Error :This bit when 
        set indicates the FEC corrected 
        errors counter value is invalid 
        on Line
        "
	::= { pm10010mrCntlocalLineFecCorrectedErrorsCounterEntry 3 }


pm10010mrCntlocalLineFecCorrectedErrorsCounterOverloadPortn OBJECT-TYPE
	SYNTAX  EkiOnOff
	MAX-ACCESS read-only
	STATUS current
	DESCRIPTION
        "
        FEC Counter Overload :This bit 
        when set indicates a FEC corrected 
        errors counter overload on Line
        "
	::= { pm10010mrCntlocalLineFecCorrectedErrorsCounterEntry 4 }


--- *********************************************************
---     TABLE for the pm10010mrCntremoteLineSmBip8ErrorCounter articles
--- *********************************************************

pm10010mrCntremoteLineSmBip8ErrorCounterTable OBJECT-TYPE
	SYNTAX  SEQUENCE OF Pm10010mrCntremoteLineSmBip8ErrorCounterEntry
	MAX-ACCESS not-accessible
	STATUS current
	DESCRIPTION
        "
        List of pm10010mrCntremoteLineSmBip8ErrorCounter 
        Article
        "
	::= { pm10010mrCntLine 194 }


pm10010mrCntremoteLineSmBip8ErrorCounterEntry OBJECT-TYPE
	SYNTAX Pm10010mrCntremoteLineSmBip8ErrorCounterEntry
	MAX-ACCESS not-accessible
	STATUS current
	DESCRIPTION
        "
        Row definition for the pm10010mrCntremoteLineSmBip8ErrorCounter 
        table
        "
	INDEX   { pm10010mrCntremoteLineSmBip8ErrorCounterIndex }
	::= { pm10010mrCntremoteLineSmBip8ErrorCounterTable 1 }


Pm10010mrCntremoteLineSmBip8ErrorCounterEntry ::=
	SEQUENCE {
	pm10010mrCntremoteLineSmBip8ErrorCounterIndex
		INTEGER,
	pm10010mrCntremoteLineSmBip8ErrorCounterValuePortn
		Counter64,
	pm10010mrCntremoteLineSmBip8ErrorCounterErrorPortn
		EkiOnOff,
	pm10010mrCntremoteLineSmBip8ErrorCounterOverloadPortn
		EkiOnOff
	}


pm10010mrCntremoteLineSmBip8ErrorCounterIndex OBJECT-TYPE
	SYNTAX  INTEGER(0..128)
	MAX-ACCESS  read-only
	STATUS current
	DESCRIPTION
        "
        Index definition for the pm10010mrCntremoteLineSmBip8ErrorCounter 
        table
        "
	::= { pm10010mrCntremoteLineSmBip8ErrorCounterEntry 1 }


pm10010mrCntremoteLineSmBip8ErrorCounterValuePortn OBJECT-TYPE
	SYNTAX  Counter64
	MAX-ACCESS read-only
	STATUS current
	DESCRIPTION
        "
        Remote SM BIP8 :This OID gives 
        the current Bit Error Rate (residual 
        SM-BIP8 error) after FEC on the 
        remote side  <Help> This counter 
        gives the current Bit Error Rate 
        (residual SM-BIP8 error) after
         FEC on the remote side
        "
	::= { pm10010mrCntremoteLineSmBip8ErrorCounterEntry 2 }


pm10010mrCntremoteLineSmBip8ErrorCounterErrorPortn OBJECT-TYPE
	SYNTAX  EkiOnOff
	MAX-ACCESS read-only
	STATUS current
	DESCRIPTION
        "
        Remote Counter Error :
        "
	::= { pm10010mrCntremoteLineSmBip8ErrorCounterEntry 3 }


pm10010mrCntremoteLineSmBip8ErrorCounterOverloadPortn OBJECT-TYPE
	SYNTAX  EkiOnOff
	MAX-ACCESS read-only
	STATUS current
	DESCRIPTION
        "
        Remote Counter Overload :
        "
	::= { pm10010mrCntremoteLineSmBip8ErrorCounterEntry 4 }


--- *********************************************************
---     TABLE for the pm10010mrCntlineDfrmTimCnt articles
--- *********************************************************

pm10010mrCntlineDfrmTimCntTable OBJECT-TYPE
	SYNTAX  SEQUENCE OF Pm10010mrCntlineDfrmTimCntEntry
	MAX-ACCESS not-accessible
	STATUS current
	DESCRIPTION
        "
        List of pm10010mrCntlineDfrmTimCnt 
        Article
        "
	::= { pm10010mrCntLine 195 }


pm10010mrCntlineDfrmTimCntEntry OBJECT-TYPE
	SYNTAX Pm10010mrCntlineDfrmTimCntEntry
	MAX-ACCESS not-accessible
	STATUS current
	DESCRIPTION
        "
        Row definition for the pm10010mrCntlineDfrmTimCnt 
        table
        "
	INDEX   { pm10010mrCntlineDfrmTimCntIndex }
	::= { pm10010mrCntlineDfrmTimCntTable 1 }


Pm10010mrCntlineDfrmTimCntEntry ::=
	SEQUENCE {
	pm10010mrCntlineDfrmTimCntIndex
		INTEGER,
	pm10010mrCntlineDfrmTimCntValuePortn
		Counter64,
	pm10010mrCntlineDfrmTimCntErrorPortn
		EkiOnOff,
	pm10010mrCntlineDfrmTimCntOverloadPortn
		EkiOnOff
	}


pm10010mrCntlineDfrmTimCntIndex OBJECT-TYPE
	SYNTAX  INTEGER(0..128)
	MAX-ACCESS  read-only
	STATUS current
	DESCRIPTION
        "
        Index definition for the pm10010mrCntlineDfrmTimCnt 
        table
        "
	::= { pm10010mrCntlineDfrmTimCntEntry 1 }


pm10010mrCntlineDfrmTimCntValuePortn OBJECT-TYPE
	SYNTAX  Counter64
	MAX-ACCESS read-only
	STATUS current
	DESCRIPTION
        "
        Line Timer Counter :
        "
	::= { pm10010mrCntlineDfrmTimCntEntry 2 }


pm10010mrCntlineDfrmTimCntErrorPortn OBJECT-TYPE
	SYNTAX  EkiOnOff
	MAX-ACCESS read-only
	STATUS current
	DESCRIPTION
        "
        Line Counter Error :This OID when 
        set indicates the deframer timer 
        counter value is invalid on Port
        "
	::= { pm10010mrCntlineDfrmTimCntEntry 3 }


pm10010mrCntlineDfrmTimCntOverloadPortn OBJECT-TYPE
	SYNTAX  EkiOnOff
	MAX-ACCESS read-only
	STATUS current
	DESCRIPTION
        "
        Line Counter Overload :This OID 
        when set indicates a deframer timer 
        counter overload on Port
        "
	::= { pm10010mrCntlineDfrmTimCntEntry 4 }


--- *********************************************************
---     TABLE for the pm10010mrCntlocalLineTrscvFecCorrectedErrorCounter articles
--- *********************************************************

pm10010mrCntlocalLineTrscvFecCorrectedErrorCounterTable OBJECT-TYPE
	SYNTAX  SEQUENCE OF Pm10010mrCntlocalLineTrscvFecCorrectedErrorCounterEntry
	MAX-ACCESS not-accessible
	STATUS current
	DESCRIPTION
        "
        List of pm10010mrCntlocalLineTrscvFecCorrectedErrorCounter 
        Article
        "
	::= { pm10010mrCntLine 196 }


pm10010mrCntlocalLineTrscvFecCorrectedErrorCounterEntry OBJECT-TYPE
	SYNTAX Pm10010mrCntlocalLineTrscvFecCorrectedErrorCounterEntry
	MAX-ACCESS not-accessible
	STATUS current
	DESCRIPTION
        "
        Row definition for the pm10010mrCntlocalLineTrscvFecCorrectedErrorCounter 
        table
        "
	INDEX   { pm10010mrCntlocalLineTrscvFecCorrectedErrorCounterIndex }
	::= { pm10010mrCntlocalLineTrscvFecCorrectedErrorCounterTable 1 }


Pm10010mrCntlocalLineTrscvFecCorrectedErrorCounterEntry ::=
	SEQUENCE {
	pm10010mrCntlocalLineTrscvFecCorrectedErrorCounterIndex
		INTEGER,
	pm10010mrCntlocalLineTrscvFecCorrectedErrorCounterValuePortn
		Counter64,
	pm10010mrCntlocalLineTrscvFecCorrectedErrorCounterErrorPortn
		EkiOnOff,
	pm10010mrCntlocalLineTrscvFecCorrectedErrorCounterOverloadPortn
		EkiOnOff
	}


pm10010mrCntlocalLineTrscvFecCorrectedErrorCounterIndex OBJECT-TYPE
	SYNTAX  INTEGER(0..128)
	MAX-ACCESS  read-only
	STATUS current
	DESCRIPTION
        "
        Index definition for the pm10010mrCntlocalLineTrscvFecCorrectedErrorCounter 
        table
        "
	::= { pm10010mrCntlocalLineTrscvFecCorrectedErrorCounterEntry 1 }


pm10010mrCntlocalLineTrscvFecCorrectedErrorCounterValuePortn OBJECT-TYPE
	SYNTAX  Counter64
	MAX-ACCESS read-only
	STATUS current
	DESCRIPTION
        "
        Line Input SD FEC Corrected Errors 
        :This OID gives the current Bit 
        Error Rate before the Soft Decision 
        FEC  <Help> This counter gives
         the current Bit Error Rate before 
        the Soft Decision FEC
        "
	::= { pm10010mrCntlocalLineTrscvFecCorrectedErrorCounterEntry 2 }


pm10010mrCntlocalLineTrscvFecCorrectedErrorCounterErrorPortn OBJECT-TYPE
	SYNTAX  EkiOnOff
	MAX-ACCESS read-only
	STATUS current
	DESCRIPTION
        "
        Line Counter Error :This OID when 
        set indicates the deframer timer 
        counter value is invalid on Port
        "
	::= { pm10010mrCntlocalLineTrscvFecCorrectedErrorCounterEntry 3 }


pm10010mrCntlocalLineTrscvFecCorrectedErrorCounterOverloadPortn OBJECT-TYPE
	SYNTAX  EkiOnOff
	MAX-ACCESS read-only
	STATUS current
	DESCRIPTION
        "
        Line Counter Overload :This OID 
        when set indicates a deframer timer 
        counter overload on Port
        "
	::= { pm10010mrCntlocalLineTrscvFecCorrectedErrorCounterEntry 4 }


--- *********************************************************
---     TABLE for the pm10010mrCntlocalLineTrscvFecUncorrectedErrorCounter articles
--- *********************************************************

pm10010mrCntlocalLineTrscvFecUncorrectedErrorCounterTable OBJECT-TYPE
	SYNTAX  SEQUENCE OF Pm10010mrCntlocalLineTrscvFecUncorrectedErrorCounterEntry
	MAX-ACCESS not-accessible
	STATUS current
	DESCRIPTION
        "
        List of pm10010mrCntlocalLineTrscvFecUncorrectedErrorCounter 
        Article
        "
	::= { pm10010mrCntLine 197 }


pm10010mrCntlocalLineTrscvFecUncorrectedErrorCounterEntry OBJECT-TYPE
	SYNTAX Pm10010mrCntlocalLineTrscvFecUncorrectedErrorCounterEntry
	MAX-ACCESS not-accessible
	STATUS current
	DESCRIPTION
        "
        Row definition for the pm10010mrCntlocalLineTrscvFecUncorrectedErrorCounter 
        table
        "
	INDEX   { pm10010mrCntlocalLineTrscvFecUncorrectedErrorCounterIndex }
	::= { pm10010mrCntlocalLineTrscvFecUncorrectedErrorCounterTable 1 }


Pm10010mrCntlocalLineTrscvFecUncorrectedErrorCounterEntry ::=
	SEQUENCE {
	pm10010mrCntlocalLineTrscvFecUncorrectedErrorCounterIndex
		INTEGER,
	pm10010mrCntlocalLineTrscvFecUncorrectedErrorCounterValuePortn
		Counter64,
	pm10010mrCntlocalLineTrscvFecUncorrectedErrorCounterErrorPortn
		EkiOnOff,
	pm10010mrCntlocalLineTrscvFecUncorrectedErrorCounterOverloadPortn
		EkiOnOff
	}


pm10010mrCntlocalLineTrscvFecUncorrectedErrorCounterIndex OBJECT-TYPE
	SYNTAX  INTEGER(0..128)
	MAX-ACCESS  read-only
	STATUS current
	DESCRIPTION
        "
        Index definition for the pm10010mrCntlocalLineTrscvFecUncorrectedErrorCounter 
        table
        "
	::= { pm10010mrCntlocalLineTrscvFecUncorrectedErrorCounterEntry 1 }


pm10010mrCntlocalLineTrscvFecUncorrectedErrorCounterValuePortn OBJECT-TYPE
	SYNTAX  Counter64
	MAX-ACCESS read-only
	STATUS current
	DESCRIPTION
        "
        SD Uncorrected :This OID gives 
        the current Bit Error Rate after 
        the Soft Decision FEC (residual) 
         <Help> This counter gives the
         current Bit Error Rate after the 
        Soft Decision FEC (residual)
        "
	::= { pm10010mrCntlocalLineTrscvFecUncorrectedErrorCounterEntry 2 }


pm10010mrCntlocalLineTrscvFecUncorrectedErrorCounterErrorPortn OBJECT-TYPE
	SYNTAX  EkiOnOff
	MAX-ACCESS read-only
	STATUS current
	DESCRIPTION
        "
        Line Counter Error :This OID when 
        set indicates the deframer timer 
        counter value is invalid on Port
        "
	::= { pm10010mrCntlocalLineTrscvFecUncorrectedErrorCounterEntry 3 }


pm10010mrCntlocalLineTrscvFecUncorrectedErrorCounterOverloadPortn OBJECT-TYPE
	SYNTAX  EkiOnOff
	MAX-ACCESS read-only
	STATUS current
	DESCRIPTION
        "
        Line Counter Overload :This OID 
        when set indicates a deframer timer 
        counter overload on Port
        "
	::= { pm10010mrCntlocalLineTrscvFecUncorrectedErrorCounterEntry 4 }







--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm10010mrMonupRmonBytesCounterClientInput articles
--- *********************************************************

pm10010mrMonupRmonBytesCounterClientInputTable OBJECT-TYPE
	SYNTAX  SEQUENCE OF Pm10010mrMonupRmonBytesCounterClientInputEntry
	MAX-ACCESS not-accessible
	STATUS current
	DESCRIPTION
        "
        List of pm10010mrMonupRmonBytesCounterClientInput 
        Article
        "
	::= { pm10010mrMonClientRmonCounter 16 }


pm10010mrMonupRmonBytesCounterClientInputEntry OBJECT-TYPE
	SYNTAX Pm10010mrMonupRmonBytesCounterClientInputEntry
	MAX-ACCESS not-accessible
	STATUS current
	DESCRIPTION
        "
        Row definition for the pm10010mrMonupRmonBytesCounterClientInput 
        table
        "
	INDEX   { pm10010mrMonupRmonBytesCounterClientInputIndex }
	::= { pm10010mrMonupRmonBytesCounterClientInputTable 1 }


Pm10010mrMonupRmonBytesCounterClientInputEntry ::=
	SEQUENCE {
	pm10010mrMonupRmonBytesCounterClientInputIndex
		INTEGER,
	pm10010mrMonupRmonBytesCounterClientInputValuePortn
		Counter64,
	pm10010mrMonupRmonBytesCounterClientInputErrorPortn
		EkiOnOff,
	pm10010mrMonupRmonBytesCounterClientInputOverloadPortn
		EkiOnOff
	}


pm10010mrMonupRmonBytesCounterClientInputIndex OBJECT-TYPE
	SYNTAX  INTEGER(0..128)
	MAX-ACCESS  read-only
	STATUS current
	DESCRIPTION
        "
        Index definition for the pm10010mrMonupRmonBytesCounterClientInput 
        table
        "
	::= { pm10010mrMonupRmonBytesCounterClientInputEntry 1 }


pm10010mrMonupRmonBytesCounterClientInputValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pm10010mrMonupRmonBytesCounterClientInputEntry 2 }


pm10010mrMonupRmonBytesCounterClientInputErrorPortn OBJECT-TYPE
	SYNTAX  EkiOnOff
	MAX-ACCESS read-only
	STATUS current
	DESCRIPTION
        "
        Bytes Counter Error :This OID
         when set indicates the Bytes counter 
        value is invalid on client port
        "
	::= { pm10010mrMonupRmonBytesCounterClientInputEntry 3 }


pm10010mrMonupRmonBytesCounterClientInputOverloadPortn OBJECT-TYPE
	SYNTAX  EkiOnOff
	MAX-ACCESS read-only
	STATUS current
	DESCRIPTION
        "
        Bytes Counter Overload :This OID 
        when set indicates a Bytes counter 
        overload on client port
        "
	::= { pm10010mrMonupRmonBytesCounterClientInputEntry 4 }


--- *********************************************************
---     TABLE for the pm10010mrMonupRmonCrcErrorsCounterClientInput articles
--- *********************************************************

pm10010mrMonupRmonCrcErrorsCounterClientInputTable OBJECT-TYPE
	SYNTAX  SEQUENCE OF Pm10010mrMonupRmonCrcErrorsCounterClientInputEntry
	MAX-ACCESS not-accessible
	STATUS current
	DESCRIPTION
        "
        List of pm10010mrMonupRmonCrcErrorsCounterClientInput 
        Article
        "
	::= { pm10010mrMonClientRmonCounter 32 }


pm10010mrMonupRmonCrcErrorsCounterClientInputEntry OBJECT-TYPE
	SYNTAX Pm10010mrMonupRmonCrcErrorsCounterClientInputEntry
	MAX-ACCESS not-accessible
	STATUS current
	DESCRIPTION
        "
        Row definition for the pm10010mrMonupRmonCrcErrorsCounterClientInput 
        table
        "
	INDEX   { pm10010mrMonupRmonCrcErrorsCounterClientInputIndex }
	::= { pm10010mrMonupRmonCrcErrorsCounterClientInputTable 1 }


Pm10010mrMonupRmonCrcErrorsCounterClientInputEntry ::=
	SEQUENCE {
	pm10010mrMonupRmonCrcErrorsCounterClientInputIndex
		INTEGER,
	pm10010mrMonupRmonCrcErrorsCounterClientInputValuePortn
		Counter64,
	pm10010mrMonupRmonCrcErrorsCounterClientInputErrorPortn
		EkiOnOff,
	pm10010mrMonupRmonCrcErrorsCounterClientInputOverloadPortn
		EkiOnOff
	}


pm10010mrMonupRmonCrcErrorsCounterClientInputIndex OBJECT-TYPE
	SYNTAX  INTEGER(0..128)
	MAX-ACCESS  read-only
	STATUS current
	DESCRIPTION
        "
        Index definition for the pm10010mrMonupRmonCrcErrorsCounterClientInput 
        table
        "
	::= { pm10010mrMonupRmonCrcErrorsCounterClientInputEntry 1 }


pm10010mrMonupRmonCrcErrorsCounterClientInputValuePortn OBJECT-TYPE
	SYNTAX  Counter64
	MAX-ACCESS read-only
	STATUS current
	DESCRIPTION
        "
        Client Input B1/CRC Errors :This 
        counter is increased each time
         a B1/FCS error is detected on
         the client port  <Help>  This
         counter gives the number of B1/FCS 
        Errors received on the client port
        "
	::= { pm10010mrMonupRmonCrcErrorsCounterClientInputEntry 2 }


pm10010mrMonupRmonCrcErrorsCounterClientInputErrorPortn OBJECT-TYPE
	SYNTAX  EkiOnOff
	MAX-ACCESS read-only
	STATUS current
	DESCRIPTION
        "
        B1/FCS Errors Counter Error :This 
        OID when set indicates the B1/FCS 
        Errors counter value is invalid 
        on client port
        "
	::= { pm10010mrMonupRmonCrcErrorsCounterClientInputEntry 3 }


pm10010mrMonupRmonCrcErrorsCounterClientInputOverloadPortn OBJECT-TYPE
	SYNTAX  EkiOnOff
	MAX-ACCESS read-only
	STATUS current
	DESCRIPTION
        "
        B1/FCS Errors Counter Overload 
        :This OID when set indicates a
         B1/FCS Errors counter overload 
        on client port
        "
	::= { pm10010mrMonupRmonCrcErrorsCounterClientInputEntry 4 }


--- *********************************************************
---     TABLE for the pm10010mrMonupRmonPacketsCounterClientInput articles
--- *********************************************************

pm10010mrMonupRmonPacketsCounterClientInputTable OBJECT-TYPE
	SYNTAX  SEQUENCE OF Pm10010mrMonupRmonPacketsCounterClientInputEntry
	MAX-ACCESS not-accessible
	STATUS current
	DESCRIPTION
        "
        List of pm10010mrMonupRmonPacketsCounterClientInput 
        Article
        "
	::= { pm10010mrMonClientRmonCounter 48 }


pm10010mrMonupRmonPacketsCounterClientInputEntry OBJECT-TYPE
	SYNTAX Pm10010mrMonupRmonPacketsCounterClientInputEntry
	MAX-ACCESS not-accessible
	STATUS current
	DESCRIPTION
        "
        Row definition for the pm10010mrMonupRmonPacketsCounterClientInput 
        table
        "
	INDEX   { pm10010mrMonupRmonPacketsCounterClientInputIndex }
	::= { pm10010mrMonupRmonPacketsCounterClientInputTable 1 }


Pm10010mrMonupRmonPacketsCounterClientInputEntry ::=
	SEQUENCE {
	pm10010mrMonupRmonPacketsCounterClientInputIndex
		INTEGER,
	pm10010mrMonupRmonPacketsCounterClientInputValuePortn
		Counter64,
	pm10010mrMonupRmonPacketsCounterClientInputErrorPortn
		EkiOnOff,
	pm10010mrMonupRmonPacketsCounterClientInputOverloadPortn
		EkiOnOff
	}


pm10010mrMonupRmonPacketsCounterClientInputIndex OBJECT-TYPE
	SYNTAX  INTEGER(0..128)
	MAX-ACCESS  read-only
	STATUS current
	DESCRIPTION
        "
        Index definition for the pm10010mrMonupRmonPacketsCounterClientInput 
        table
        "
	::= { pm10010mrMonupRmonPacketsCounterClientInputEntry 1 }


pm10010mrMonupRmonPacketsCounterClientInputValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pm10010mrMonupRmonPacketsCounterClientInputEntry 2 }


pm10010mrMonupRmonPacketsCounterClientInputErrorPortn OBJECT-TYPE
	SYNTAX  EkiOnOff
	MAX-ACCESS read-only
	STATUS current
	DESCRIPTION
        "
        Packets Counter Error :This OID 
        when set indicates the Packets
         counter value is invalid on client 
        port
        "
	::= { pm10010mrMonupRmonPacketsCounterClientInputEntry 3 }


pm10010mrMonupRmonPacketsCounterClientInputOverloadPortn OBJECT-TYPE
	SYNTAX  EkiOnOff
	MAX-ACCESS read-only
	STATUS current
	DESCRIPTION
        "
        Packets Counter Overload :This 
        OID when set indicates a Packets 
        counter overload on client port
        "
	::= { pm10010mrMonupRmonPacketsCounterClientInputEntry 4 }


--- *********************************************************
---     TABLE for the pm10010mrMonupRmonBroadcastCounterClientInput articles
--- *********************************************************

pm10010mrMonupRmonBroadcastCounterClientInputTable OBJECT-TYPE
	SYNTAX  SEQUENCE OF Pm10010mrMonupRmonBroadcastCounterClientInputEntry
	MAX-ACCESS not-accessible
	STATUS current
	DESCRIPTION
        "
        List of pm10010mrMonupRmonBroadcastCounterClientInput 
        Article
        "
	::= { pm10010mrMonClientRmonCounter 64 }


pm10010mrMonupRmonBroadcastCounterClientInputEntry OBJECT-TYPE
	SYNTAX Pm10010mrMonupRmonBroadcastCounterClientInputEntry
	MAX-ACCESS not-accessible
	STATUS current
	DESCRIPTION
        "
        Row definition for the pm10010mrMonupRmonBroadcastCounterClientInput 
        table
        "
	INDEX   { pm10010mrMonupRmonBroadcastCounterClientInputIndex }
	::= { pm10010mrMonupRmonBroadcastCounterClientInputTable 1 }


Pm10010mrMonupRmonBroadcastCounterClientInputEntry ::=
	SEQUENCE {
	pm10010mrMonupRmonBroadcastCounterClientInputIndex
		INTEGER,
	pm10010mrMonupRmonBroadcastCounterClientInputValuePortn
		Counter64,
	pm10010mrMonupRmonBroadcastCounterClientInputErrorPortn
		EkiOnOff,
	pm10010mrMonupRmonBroadcastCounterClientInputOverloadPortn
		EkiOnOff
	}


pm10010mrMonupRmonBroadcastCounterClientInputIndex OBJECT-TYPE
	SYNTAX  INTEGER(0..128)
	MAX-ACCESS  read-only
	STATUS current
	DESCRIPTION
        "
        Index definition for the pm10010mrMonupRmonBroadcastCounterClientInput 
        table
        "
	::= { pm10010mrMonupRmonBroadcastCounterClientInputEntry 1 }


pm10010mrMonupRmonBroadcastCounterClientInputValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pm10010mrMonupRmonBroadcastCounterClientInputEntry 2 }


pm10010mrMonupRmonBroadcastCounterClientInputErrorPortn OBJECT-TYPE
	SYNTAX  EkiOnOff
	MAX-ACCESS read-only
	STATUS current
	DESCRIPTION
        "
        Broadcast Counter Error :This
         OID when set indicates the Broadcast 
        counter value is invalid on client 
        port
        "
	::= { pm10010mrMonupRmonBroadcastCounterClientInputEntry 3 }


pm10010mrMonupRmonBroadcastCounterClientInputOverloadPortn OBJECT-TYPE
	SYNTAX  EkiOnOff
	MAX-ACCESS read-only
	STATUS current
	DESCRIPTION
        "
        Broadcast Counter Overload :This 
        OID when set indicates a Broadcast 
        counter overload on client port
        "
	::= { pm10010mrMonupRmonBroadcastCounterClientInputEntry 4 }


--- *********************************************************
---     TABLE for the pm10010mrMonupRmonMulticastCounterClientInput articles
--- *********************************************************

pm10010mrMonupRmonMulticastCounterClientInputTable OBJECT-TYPE
	SYNTAX  SEQUENCE OF Pm10010mrMonupRmonMulticastCounterClientInputEntry
	MAX-ACCESS not-accessible
	STATUS current
	DESCRIPTION
        "
        List of pm10010mrMonupRmonMulticastCounterClientInput 
        Article
        "
	::= { pm10010mrMonClientRmonCounter 80 }


pm10010mrMonupRmonMulticastCounterClientInputEntry OBJECT-TYPE
	SYNTAX Pm10010mrMonupRmonMulticastCounterClientInputEntry
	MAX-ACCESS not-accessible
	STATUS current
	DESCRIPTION
        "
        Row definition for the pm10010mrMonupRmonMulticastCounterClientInput 
        table
        "
	INDEX   { pm10010mrMonupRmonMulticastCounterClientInputIndex }
	::= { pm10010mrMonupRmonMulticastCounterClientInputTable 1 }


Pm10010mrMonupRmonMulticastCounterClientInputEntry ::=
	SEQUENCE {
	pm10010mrMonupRmonMulticastCounterClientInputIndex
		INTEGER,
	pm10010mrMonupRmonMulticastCounterClientInputValuePortn
		Counter64,
	pm10010mrMonupRmonMulticastCounterClientInputErrorPortn
		EkiOnOff,
	pm10010mrMonupRmonMulticastCounterClientInputOverloadPortn
		EkiOnOff
	}


pm10010mrMonupRmonMulticastCounterClientInputIndex OBJECT-TYPE
	SYNTAX  INTEGER(0..128)
	MAX-ACCESS  read-only
	STATUS current
	DESCRIPTION
        "
        Index definition for the pm10010mrMonupRmonMulticastCounterClientInput 
        table
        "
	::= { pm10010mrMonupRmonMulticastCounterClientInputEntry 1 }


pm10010mrMonupRmonMulticastCounterClientInputValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pm10010mrMonupRmonMulticastCounterClientInputEntry 2 }


pm10010mrMonupRmonMulticastCounterClientInputErrorPortn OBJECT-TYPE
	SYNTAX  EkiOnOff
	MAX-ACCESS read-only
	STATUS current
	DESCRIPTION
        "
        Multicast Counter Error :This
         OID when set indicates the Multicast 
        counter value is invalid on client 
        port
        "
	::= { pm10010mrMonupRmonMulticastCounterClientInputEntry 3 }


pm10010mrMonupRmonMulticastCounterClientInputOverloadPortn OBJECT-TYPE
	SYNTAX  EkiOnOff
	MAX-ACCESS read-only
	STATUS current
	DESCRIPTION
        "
        Multicast Counter Overload :This 
        OID when set indicates a Multicast 
        counter overload on client port
        "
	::= { pm10010mrMonupRmonMulticastCounterClientInputEntry 4 }


--- *********************************************************
---     TABLE for the pm10010mrMonupRmonPauseFrameCounterClientInput articles
--- *********************************************************

pm10010mrMonupRmonPauseFrameCounterClientInputTable OBJECT-TYPE
	SYNTAX  SEQUENCE OF Pm10010mrMonupRmonPauseFrameCounterClientInputEntry
	MAX-ACCESS not-accessible
	STATUS current
	DESCRIPTION
        "
        List of pm10010mrMonupRmonPauseFrameCounterClientInput 
        Article
        "
	::= { pm10010mrMonClientRmonCounter 96 }


pm10010mrMonupRmonPauseFrameCounterClientInputEntry OBJECT-TYPE
	SYNTAX Pm10010mrMonupRmonPauseFrameCounterClientInputEntry
	MAX-ACCESS not-accessible
	STATUS current
	DESCRIPTION
        "
        Row definition for the pm10010mrMonupRmonPauseFrameCounterClientInput 
        table
        "
	INDEX   { pm10010mrMonupRmonPauseFrameCounterClientInputIndex }
	::= { pm10010mrMonupRmonPauseFrameCounterClientInputTable 1 }


Pm10010mrMonupRmonPauseFrameCounterClientInputEntry ::=
	SEQUENCE {
	pm10010mrMonupRmonPauseFrameCounterClientInputIndex
		INTEGER,
	pm10010mrMonupRmonPauseFrameCounterClientInputValuePortn
		Counter64,
	pm10010mrMonupRmonPauseFrameCounterClientInputErrorPortn
		EkiOnOff,
	pm10010mrMonupRmonPauseFrameCounterClientInputOverloadPortn
		EkiOnOff
	}


pm10010mrMonupRmonPauseFrameCounterClientInputIndex OBJECT-TYPE
	SYNTAX  INTEGER(0..128)
	MAX-ACCESS  read-only
	STATUS current
	DESCRIPTION
        "
        Index definition for the pm10010mrMonupRmonPauseFrameCounterClientInput 
        table
        "
	::= { pm10010mrMonupRmonPauseFrameCounterClientInputEntry 1 }


pm10010mrMonupRmonPauseFrameCounterClientInputValuePortn OBJECT-TYPE
	SYNTAX  Counter64
	MAX-ACCESS read-only
	STATUS current
	DESCRIPTION
        "
        Client Input Pause Frames :This 
        counter is increased each time
         a Pause frame is received on the 
        client port  <Help>  This counter 
        gives the number of Pause frames 
        received on the client port
        "
	::= { pm10010mrMonupRmonPauseFrameCounterClientInputEntry 2 }


pm10010mrMonupRmonPauseFrameCounterClientInputErrorPortn OBJECT-TYPE
	SYNTAX  EkiOnOff
	MAX-ACCESS read-only
	STATUS current
	DESCRIPTION
        "
        Pause Counter Error :This OID
         when set indicates the Pause counter 
        value is invalid on client port
        "
	::= { pm10010mrMonupRmonPauseFrameCounterClientInputEntry 3 }


pm10010mrMonupRmonPauseFrameCounterClientInputOverloadPortn OBJECT-TYPE
	SYNTAX  EkiOnOff
	MAX-ACCESS read-only
	STATUS current
	DESCRIPTION
        "
        Pause Counter Overload :This OID 
        when set indicates a Pause counter 
        overload on client port
        "
	::= { pm10010mrMonupRmonPauseFrameCounterClientInputEntry 4 }


--- *********************************************************
---     TABLE for the pm10010mrMondwRmonCrcErrorsCounterClientInput articles
--- *********************************************************

pm10010mrMondwRmonCrcErrorsCounterClientInputTable OBJECT-TYPE
	SYNTAX  SEQUENCE OF Pm10010mrMondwRmonCrcErrorsCounterClientInputEntry
	MAX-ACCESS not-accessible
	STATUS current
	DESCRIPTION
        "
        List of pm10010mrMondwRmonCrcErrorsCounterClientInput 
        Article
        "
	::= { pm10010mrMonClientRmonCounter 224 }


pm10010mrMondwRmonCrcErrorsCounterClientInputEntry OBJECT-TYPE
	SYNTAX Pm10010mrMondwRmonCrcErrorsCounterClientInputEntry
	MAX-ACCESS not-accessible
	STATUS current
	DESCRIPTION
        "
        Row definition for the pm10010mrMondwRmonCrcErrorsCounterClientInput 
        table
        "
	INDEX   { pm10010mrMondwRmonCrcErrorsCounterClientInputIndex }
	::= { pm10010mrMondwRmonCrcErrorsCounterClientInputTable 1 }


Pm10010mrMondwRmonCrcErrorsCounterClientInputEntry ::=
	SEQUENCE {
	pm10010mrMondwRmonCrcErrorsCounterClientInputIndex
		INTEGER,
	pm10010mrMondwRmonCrcErrorsCounterClientInputValuePortn
		Counter64,
	pm10010mrMondwRmonCrcErrorsCounterClientInputErrorPortn
		EkiOnOff,
	pm10010mrMondwRmonCrcErrorsCounterClientInputOverloadPortn
		EkiOnOff
	}


pm10010mrMondwRmonCrcErrorsCounterClientInputIndex OBJECT-TYPE
	SYNTAX  INTEGER(0..128)
	MAX-ACCESS  read-only
	STATUS current
	DESCRIPTION
        "
        Index definition for the pm10010mrMondwRmonCrcErrorsCounterClientInput 
        table
        "
	::= { pm10010mrMondwRmonCrcErrorsCounterClientInputEntry 1 }


pm10010mrMondwRmonCrcErrorsCounterClientInputValuePortn OBJECT-TYPE
	SYNTAX  Counter64
	MAX-ACCESS read-only
	STATUS current
	DESCRIPTION
        "
        Client Output B1/CRC Errors :This 
        counter is increased each time
         a B1/FCS error is detected on
         the output client port  <Help> 
         This counter gives the number
         of B1/CRC Errors detected on the 
        client port
        "
	::= { pm10010mrMondwRmonCrcErrorsCounterClientInputEntry 2 }


pm10010mrMondwRmonCrcErrorsCounterClientInputErrorPortn OBJECT-TYPE
	SYNTAX  EkiOnOff
	MAX-ACCESS read-only
	STATUS current
	DESCRIPTION
        "
        Output B1/FCS Errors Counter Error 
        :This OID when set indicates the 
        output B1/FCS Errors counter value 
        is invalid on client port
        "
	::= { pm10010mrMondwRmonCrcErrorsCounterClientInputEntry 3 }


pm10010mrMondwRmonCrcErrorsCounterClientInputOverloadPortn OBJECT-TYPE
	SYNTAX  EkiOnOff
	MAX-ACCESS read-only
	STATUS current
	DESCRIPTION
        "
        Output B1/FCS Errors Counter Overload 
        :This OID when set indicates an 
        output B1/FCS Errors counter overload 
        on client port
        "
	::= { pm10010mrMondwRmonCrcErrorsCounterClientInputEntry 4 }


--- *********************************************************
---     TABLE for the pm10010mrMondwRmonPacketsCounterClientInput articles
--- *********************************************************

pm10010mrMondwRmonPacketsCounterClientInputTable OBJECT-TYPE
	SYNTAX  SEQUENCE OF Pm10010mrMondwRmonPacketsCounterClientInputEntry
	MAX-ACCESS not-accessible
	STATUS current
	DESCRIPTION
        "
        List of pm10010mrMondwRmonPacketsCounterClientInput 
        Article
        "
	::= { pm10010mrMonClientRmonCounter 240 }


pm10010mrMondwRmonPacketsCounterClientInputEntry OBJECT-TYPE
	SYNTAX Pm10010mrMondwRmonPacketsCounterClientInputEntry
	MAX-ACCESS not-accessible
	STATUS current
	DESCRIPTION
        "
        Row definition for the pm10010mrMondwRmonPacketsCounterClientInput 
        table
        "
	INDEX   { pm10010mrMondwRmonPacketsCounterClientInputIndex }
	::= { pm10010mrMondwRmonPacketsCounterClientInputTable 1 }


Pm10010mrMondwRmonPacketsCounterClientInputEntry ::=
	SEQUENCE {
	pm10010mrMondwRmonPacketsCounterClientInputIndex
		INTEGER,
	pm10010mrMondwRmonPacketsCounterClientInputValuePortn
		Counter64,
	pm10010mrMondwRmonPacketsCounterClientInputErrorPortn
		EkiOnOff,
	pm10010mrMondwRmonPacketsCounterClientInputOverloadPortn
		EkiOnOff
	}


pm10010mrMondwRmonPacketsCounterClientInputIndex OBJECT-TYPE
	SYNTAX  INTEGER(0..128)
	MAX-ACCESS  read-only
	STATUS current
	DESCRIPTION
        "
        Index definition for the pm10010mrMondwRmonPacketsCounterClientInput 
        table
        "
	::= { pm10010mrMondwRmonPacketsCounterClientInputEntry 1 }


pm10010mrMondwRmonPacketsCounterClientInputValuePortn OBJECT-TYPE
	SYNTAX  Counter64
	MAX-ACCESS read-only
	STATUS current
	DESCRIPTION
        "
        Client Output Packets :This counter 
        is increased each time a packet 
        is transmitted on the client port. 
         <Help>  This counter gives the 
        number of packets detected on the 
        client port
        "
	::= { pm10010mrMondwRmonPacketsCounterClientInputEntry 2 }


pm10010mrMondwRmonPacketsCounterClientInputErrorPortn OBJECT-TYPE
	SYNTAX  EkiOnOff
	MAX-ACCESS read-only
	STATUS current
	DESCRIPTION
        "
        Output Packets Counter Error :This 
        OID when set indicates the output 
        Packets counter value is invalid 
        on client port
        "
	::= { pm10010mrMondwRmonPacketsCounterClientInputEntry 3 }


pm10010mrMondwRmonPacketsCounterClientInputOverloadPortn OBJECT-TYPE
	SYNTAX  EkiOnOff
	MAX-ACCESS read-only
	STATUS current
	DESCRIPTION
        "
        Output Packets Counter Overload 
        :This OID when set indicates an 
        output Packets counter overload 
        on client port
        "
	::= { pm10010mrMondwRmonPacketsCounterClientInputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm10010mrMesrsynth0 OBJECT-TYPE
	  SYNTAX EkiMeasureType
	  MAX-ACCESS read-only
	  STATUS deprecated
	  DESCRIPTION
        "
        Not Used :
        "
	  ::= { pm10010mrMesrOther 0 }



pm10010mrMesrsynth1 OBJECT-TYPE
	  SYNTAX EkiMeasureType
	  MAX-ACCESS read-only
	  STATUS deprecated
	  DESCRIPTION
        "
        Not Used :
        "
	  ::= { pm10010mrMesrOther 1 }



--- *****************************************************
---     LEAF for the pmIntervalNumber article
--- *****************************************************

pm10010mrMesrpmIntervalNumber OBJECT-TYPE
	  SYNTAX Unsigned32 (0..65535)
	  MAX-ACCESS read-only
	  STATUS current
	  DESCRIPTION
        "
        PM Interval Counter :
        "
	  ::= { pm10010mrMesrOther 7 }



--- *****************************************************
---     LEAF for the clientCfpTemp article
--- *****************************************************

pm10010mrMesrclientCfpTemp OBJECT-TYPE
	  SYNTAX Unsigned32 (0..65535)
	  MAX-ACCESS read-only
	  STATUS current
	  DESCRIPTION
        "
        Client Trscv Temperature :This 
        OID gives the temperature value 
        of the Client Transceiver, read 
        from the DDM (Digital Diagnostic 
        Monitoring) (Temperature = AV/256) 
        (Unit = C) <Help> This Measure
         gives the temperature value of 
        the Client Transceiver
        "
	  ::= { pm10010mrMesrClient 8 }



--- *****************************************************
---     LEAF for the clientCfp3v3Voltage article
--- *****************************************************

pm10010mrMesrclientCfp3v3Voltage OBJECT-TYPE
	  SYNTAX Unsigned32 (0..65535)
	  MAX-ACCESS read-only
	  STATUS current
	  DESCRIPTION
        "
        Client Trscv Voltage :This OID 
        gives the 3V3 voltage value of
         the Client Transceiver, read from 
        the DDM (Digital Diagnostic Monitoring) 
         (Voltage = AV/1000) (Unit = V) 
        <Help> This Measure gives the 3V3 
        voltage value of the Client Transceiver
        "
	  ::= { pm10010mrMesrClient 9 }



--- *****************************************************
---     LEAF for the clientSoaBiasCurrent article
--- *****************************************************

pm10010mrMesrclientSoaBiasCurrent OBJECT-TYPE
	  SYNTAX Unsigned32 (0..65535)
	  MAX-ACCESS read-only
	  STATUS current
	  DESCRIPTION
        "
        Client Trscv SOA Bias :This OID 
        gives the SOA bias value of the 
        Client Transceiver, read from the 
        DDM (Digital Diagnostic Monitoring) 
         (Bias = AV/500) (Unit = mA) <Help> 
        This Measure gives the SOA bias 
        value of the Client Transceiver
        "
	  ::= { pm10010mrMesrClient 10 }



--- *****************************************************
---     LEAF for the lineMsaTemp article
--- *****************************************************

pm10010mrMesrlineMsaTemp OBJECT-TYPE
	  SYNTAX Unsigned32 (0..65535)
	  MAX-ACCESS read-only
	  STATUS current
	  DESCRIPTION
        "
        Line Trscv Temperature :This OID 
        gives the temperature value of
         the Line Transceiver, read from 
        the DDM (Digital Diagnostic Monitoring) 
         (Temperature = AV/256) (Unit = 
        C) <Help> This Measure gives the 
        temperature value of the Line Transceiver.This 
        temperature must remain below 95°C 
        for proper operation
        "
	  ::= { pm10010mrMesrLine 12 }



--- *****************************************************
---     LEAF for the lineMsa3v3Voltage article
--- *****************************************************

pm10010mrMesrlineMsa3v3Voltage OBJECT-TYPE
	  SYNTAX Unsigned32 (0..65535)
	  MAX-ACCESS read-only
	  STATUS current
	  DESCRIPTION
        "
        Line Trscv Voltage :This OID gives 
        the 3V3 voltage value of the Line 
        Transceiver, read from the DDM
         (Digital Diagnostic Monitoring) 
        (Voltage = AV/1000) (Unit = V)
         <Help> This Measure gives the
         3V3 voltage value of the Line
         Transceiver
        "
	  ::= { pm10010mrMesrLine 13 }



--- *****************************************************
---     LEAF for the lineSoaBiasCurrent article
--- *****************************************************

pm10010mrMesrlineSoaBiasCurrent OBJECT-TYPE
	  SYNTAX Unsigned32 (0..65535)
	  MAX-ACCESS read-only
	  STATUS current
	  DESCRIPTION
        "
        Line Trscv SOA Bias :This OID
         gives the SOA bias value of the 
        Line Transceiver,read from the
         DDM (Digital Diagnostic Monitoring) 
         (Bias = AV/500) (Unit = mA) <Help> 
        This Measure gives the SOA bias 
        value of the Line Transceiver
        "
	  ::= { pm10010mrMesrLine 14 }



--- *********************************************************
---     TABLE for the pm10010mrMesrclientNetTxTemp articles
--- *********************************************************

pm10010mrMesrclientNetTxTempTable OBJECT-TYPE
	SYNTAX  SEQUENCE OF Pm10010mrMesrclientNetTxTempEntry
	MAX-ACCESS not-accessible
	STATUS current
	DESCRIPTION
        "
        List of pm10010mrMesrclientNetTxTemp 
        Article
        "
	::= { pm10010mrMesrClient 16 }


pm10010mrMesrclientNetTxTempEntry OBJECT-TYPE
	SYNTAX Pm10010mrMesrclientNetTxTempEntry
	MAX-ACCESS not-accessible
	STATUS current
	DESCRIPTION
        "
        Row definition for the pm10010mrMesrclientNetTxTemp 
        table
        "
	INDEX   { pm10010mrMesrclientNetTxTempIndex }
	::= { pm10010mrMesrclientNetTxTempTable 1 }


Pm10010mrMesrclientNetTxTempEntry ::=
	SEQUENCE {
	pm10010mrMesrclientNetTxTempIndex
		INTEGER,
	pm10010mrMesrclientNetTxTempPortn
		INTEGER 
	}


pm10010mrMesrclientNetTxTempIndex OBJECT-TYPE
	SYNTAX  INTEGER(0..128)
	MAX-ACCESS  read-only
	STATUS current
	DESCRIPTION
        "
        Index definition for the pm10010mrMesrclientNetTxTemp 
        table
        "
	::= { pm10010mrMesrclientNetTxTempEntry 1 }


pm10010mrMesrclientNetTxTempPortn OBJECT-TYPE
	SYNTAX  INTEGER (0..65535)
	MAX-ACCESS read-only
	STATUS current
	DESCRIPTION
        "
        Client Trscv Temperature :This 
        OID gives the Laser temperature 
        value of the Client Transceiver, 
        read from the DDM (Digital Diagnostic 
        Monitoring) (Temperature = AV/256) 
        (Unit = C) <Help> This Measure
         gives the Laser temperature value 
        of the Client Transceiver
        "
	::= { pm10010mrMesrclientNetTxTempEntry 2 }


--- *********************************************************
---     TABLE for the pm10010mrMesrclientNetTxBias articles
--- *********************************************************

pm10010mrMesrclientNetTxBiasTable OBJECT-TYPE
	SYNTAX  SEQUENCE OF Pm10010mrMesrclientNetTxBiasEntry
	MAX-ACCESS not-accessible
	STATUS current
	DESCRIPTION
        "
        List of pm10010mrMesrclientNetTxBias 
        Article
        "
	::= { pm10010mrMesrClient 32 }


pm10010mrMesrclientNetTxBiasEntry OBJECT-TYPE
	SYNTAX Pm10010mrMesrclientNetTxBiasEntry
	MAX-ACCESS not-accessible
	STATUS current
	DESCRIPTION
        "
        Row definition for the pm10010mrMesrclientNetTxBias 
        table
        "
	INDEX   { pm10010mrMesrclientNetTxBiasIndex }
	::= { pm10010mrMesrclientNetTxBiasTable 1 }


Pm10010mrMesrclientNetTxBiasEntry ::=
	SEQUENCE {
	pm10010mrMesrclientNetTxBiasIndex
		INTEGER,
	pm10010mrMesrclientNetTxBiasPortn
		INTEGER 
	}


pm10010mrMesrclientNetTxBiasIndex OBJECT-TYPE
	SYNTAX  INTEGER(0..128)
	MAX-ACCESS  read-only
	STATUS current
	DESCRIPTION
        "
        Index definition for the pm10010mrMesrclientNetTxBias 
        table
        "
	::= { pm10010mrMesrclientNetTxBiasEntry 1 }


pm10010mrMesrclientNetTxBiasPortn OBJECT-TYPE
	SYNTAX  INTEGER (0..65535)
	MAX-ACCESS read-only
	STATUS current
	DESCRIPTION
        "
        Client Trscv Laser Bias :This
         OID gives the Laser bias value 
        of the Client Transceiver, read 
        from the DDM (Digital Diagnostic 
        Monitoring) (Bias = AV/500) (Unit 
        = mA) <Help> This Measure gives 
        the Laser bias value of the Client 
        Transceiver
        "
	::= { pm10010mrMesrclientNetTxBiasEntry 2 }


--- *********************************************************
---     TABLE for the pm10010mrMesrclientNetTxPwr articles
--- *********************************************************

pm10010mrMesrclientNetTxPwrTable OBJECT-TYPE
	SYNTAX  SEQUENCE OF Pm10010mrMesrclientNetTxPwrEntry
	MAX-ACCESS not-accessible
	STATUS current
	DESCRIPTION
        "
        List of pm10010mrMesrclientNetTxPwr 
        Article
        "
	::= { pm10010mrMesrClient 48 }


pm10010mrMesrclientNetTxPwrEntry OBJECT-TYPE
	SYNTAX Pm10010mrMesrclientNetTxPwrEntry
	MAX-ACCESS not-accessible
	STATUS current
	DESCRIPTION
        "
        Row definition for the pm10010mrMesrclientNetTxPwr 
        table
        "
	INDEX   { pm10010mrMesrclientNetTxPwrIndex }
	::= { pm10010mrMesrclientNetTxPwrTable 1 }


Pm10010mrMesrclientNetTxPwrEntry ::=
	SEQUENCE {
	pm10010mrMesrclientNetTxPwrIndex
		INTEGER,
	pm10010mrMesrclientNetTxPwrPortn
		INTEGER 
	}


pm10010mrMesrclientNetTxPwrIndex OBJECT-TYPE
	SYNTAX  INTEGER(0..128)
	MAX-ACCESS  read-only
	STATUS current
	DESCRIPTION
        "
        Index definition for the pm10010mrMesrclientNetTxPwr 
        table
        "
	::= { pm10010mrMesrclientNetTxPwrEntry 1 }


pm10010mrMesrclientNetTxPwrPortn OBJECT-TYPE
	SYNTAX  INTEGER (0..65535)
	MAX-ACCESS read-only
	STATUS current
	DESCRIPTION
        "
        Client Trscv Tx Power :This OID 
        gives the transmit power value
         of the Client Transceiver, read 
        from the DDM (Digital Diagnostic 
        Monitoring) (Power = 10*log(AV)-40) 
        (Unit = dBm) <Help> This Measure 
        gives the transmit power value
         of the Client Transceiver
        "
	::= { pm10010mrMesrclientNetTxPwrEntry 2 }


--- *********************************************************
---     TABLE for the pm10010mrMesrclientNetRxPwr articles
--- *********************************************************

pm10010mrMesrclientNetRxPwrTable OBJECT-TYPE
	SYNTAX  SEQUENCE OF Pm10010mrMesrclientNetRxPwrEntry
	MAX-ACCESS not-accessible
	STATUS current
	DESCRIPTION
        "
        List of pm10010mrMesrclientNetRxPwr 
        Article
        "
	::= { pm10010mrMesrClient 64 }


pm10010mrMesrclientNetRxPwrEntry OBJECT-TYPE
	SYNTAX Pm10010mrMesrclientNetRxPwrEntry
	MAX-ACCESS not-accessible
	STATUS current
	DESCRIPTION
        "
        Row definition for the pm10010mrMesrclientNetRxPwr 
        table
        "
	INDEX   { pm10010mrMesrclientNetRxPwrIndex }
	::= { pm10010mrMesrclientNetRxPwrTable 1 }


Pm10010mrMesrclientNetRxPwrEntry ::=
	SEQUENCE {
	pm10010mrMesrclientNetRxPwrIndex
		INTEGER,
	pm10010mrMesrclientNetRxPwrPortn
		INTEGER 
	}


pm10010mrMesrclientNetRxPwrIndex OBJECT-TYPE
	SYNTAX  INTEGER(0..128)
	MAX-ACCESS  read-only
	STATUS current
	DESCRIPTION
        "
        Index definition for the pm10010mrMesrclientNetRxPwr 
        table
        "
	::= { pm10010mrMesrclientNetRxPwrEntry 1 }


pm10010mrMesrclientNetRxPwrPortn OBJECT-TYPE
	SYNTAX  INTEGER (0..65535)
	MAX-ACCESS read-only
	STATUS current
	DESCRIPTION
        "
        Client Trscv Rx Power :This OID 
        gives the receive power value of 
        the Client Transceiver, read in 
        the DDM (Digital Diagnostic Monitoring) 
        (Power = 10*log(AV)-40) (Unit = 
        dBm) <Help> This Measure gives
         the receive power value of the 
        Client Transceiver
        "
	::= { pm10010mrMesrclientNetRxPwrEntry 2 }


--- *********************************************************
---     TABLE for the pm10010mrMesrlineNetTxLaserOutputPwr articles
--- *********************************************************

pm10010mrMesrlineNetTxLaserOutputPwrTable OBJECT-TYPE
	SYNTAX  SEQUENCE OF Pm10010mrMesrlineNetTxLaserOutputPwrEntry
	MAX-ACCESS not-accessible
	STATUS current
	DESCRIPTION
        "
        List of pm10010mrMesrlineNetTxLaserOutputPwr 
        Article
        "
	::= { pm10010mrMesrLine 80 }


pm10010mrMesrlineNetTxLaserOutputPwrEntry OBJECT-TYPE
	SYNTAX Pm10010mrMesrlineNetTxLaserOutputPwrEntry
	MAX-ACCESS not-accessible
	STATUS current
	DESCRIPTION
        "
        Row definition for the pm10010mrMesrlineNetTxLaserOutputPwr 
        table
        "
	INDEX   { pm10010mrMesrlineNetTxLaserOutputPwrIndex }
	::= { pm10010mrMesrlineNetTxLaserOutputPwrTable 1 }


Pm10010mrMesrlineNetTxLaserOutputPwrEntry ::=
	SEQUENCE {
	pm10010mrMesrlineNetTxLaserOutputPwrIndex
		INTEGER,
	pm10010mrMesrlineNetTxLaserOutputPwrPortn
		INTEGER 
	}


pm10010mrMesrlineNetTxLaserOutputPwrIndex OBJECT-TYPE
	SYNTAX  INTEGER(0..128)
	MAX-ACCESS  read-only
	STATUS current
	DESCRIPTION
        "
        Index definition for the pm10010mrMesrlineNetTxLaserOutputPwr 
        table
        "
	::= { pm10010mrMesrlineNetTxLaserOutputPwrEntry 1 }


pm10010mrMesrlineNetTxLaserOutputPwrPortn OBJECT-TYPE
	SYNTAX  INTEGER (0..65535)
	MAX-ACCESS read-only
	STATUS current
	DESCRIPTION
        "
        Current Line Trscv Tx Power :This 
        OID gives the Tx Laser transmit 
        power value of the Line Transceiver, 
        read in the DDM (Digital Diagnostic 
        Monitoring) (Power = AV/100) (Unit 
        = dBm) <Help> This Measure gives 
        the Tx Laser transmit power value 
        of the Line Transceiver
        "
	::= { pm10010mrMesrlineNetTxLaserOutputPwrEntry 2 }


--- *********************************************************
---     TABLE for the pm10010mrMesrlineNetTxLaserTemp articles
--- *********************************************************

pm10010mrMesrlineNetTxLaserTempTable OBJECT-TYPE
	SYNTAX  SEQUENCE OF Pm10010mrMesrlineNetTxLaserTempEntry
	MAX-ACCESS not-accessible
	STATUS current
	DESCRIPTION
        "
        List of pm10010mrMesrlineNetTxLaserTemp 
        Article
        "
	::= { pm10010mrMesrLine 96 }


pm10010mrMesrlineNetTxLaserTempEntry OBJECT-TYPE
	SYNTAX Pm10010mrMesrlineNetTxLaserTempEntry
	MAX-ACCESS not-accessible
	STATUS current
	DESCRIPTION
        "
        Row definition for the pm10010mrMesrlineNetTxLaserTemp 
        table
        "
	INDEX   { pm10010mrMesrlineNetTxLaserTempIndex }
	::= { pm10010mrMesrlineNetTxLaserTempTable 1 }


Pm10010mrMesrlineNetTxLaserTempEntry ::=
	SEQUENCE {
	pm10010mrMesrlineNetTxLaserTempIndex
		INTEGER,
	pm10010mrMesrlineNetTxLaserTempPortn
		INTEGER 
	}


pm10010mrMesrlineNetTxLaserTempIndex OBJECT-TYPE
	SYNTAX  INTEGER(0..128)
	MAX-ACCESS  read-only
	STATUS current
	DESCRIPTION
        "
        Index definition for the pm10010mrMesrlineNetTxLaserTemp 
        table
        "
	::= { pm10010mrMesrlineNetTxLaserTempEntry 1 }


pm10010mrMesrlineNetTxLaserTempPortn OBJECT-TYPE
	SYNTAX  INTEGER (0..65535)
	MAX-ACCESS read-only
	STATUS current
	DESCRIPTION
        "
        Current Line Trscv Tx Laser Temperature 
        :This OID gives the Tx Laser Temperature 
        value of the Line Transceiver,
         read from the DDM (Digital Diagnostic 
        Monitoring) (Temperature = AV/256) 
        (Unit = C) <Help> This Measure
         gives the Tx Laser Temperature 
        value of the Line Transceiver
        "
	::= { pm10010mrMesrlineNetTxLaserTempEntry 2 }


--- *********************************************************
---     TABLE for the pm10010mrMesrlineNetTxBiasCurrent articles
--- *********************************************************

pm10010mrMesrlineNetTxBiasCurrentTable OBJECT-TYPE
	SYNTAX  SEQUENCE OF Pm10010mrMesrlineNetTxBiasCurrentEntry
	MAX-ACCESS not-accessible
	STATUS current
	DESCRIPTION
        "
        List of pm10010mrMesrlineNetTxBiasCurrent 
        Article
        "
	::= { pm10010mrMesrLine 112 }


pm10010mrMesrlineNetTxBiasCurrentEntry OBJECT-TYPE
	SYNTAX Pm10010mrMesrlineNetTxBiasCurrentEntry
	MAX-ACCESS not-accessible
	STATUS current
	DESCRIPTION
        "
        Row definition for the pm10010mrMesrlineNetTxBiasCurrent 
        table
        "
	INDEX   { pm10010mrMesrlineNetTxBiasCurrentIndex }
	::= { pm10010mrMesrlineNetTxBiasCurrentTable 1 }


Pm10010mrMesrlineNetTxBiasCurrentEntry ::=
	SEQUENCE {
	pm10010mrMesrlineNetTxBiasCurrentIndex
		INTEGER,
	pm10010mrMesrlineNetTxBiasCurrentPortn
		INTEGER 
	}


pm10010mrMesrlineNetTxBiasCurrentIndex OBJECT-TYPE
	SYNTAX  INTEGER(0..128)
	MAX-ACCESS  read-only
	STATUS current
	DESCRIPTION
        "
        Index definition for the pm10010mrMesrlineNetTxBiasCurrent 
        table
        "
	::= { pm10010mrMesrlineNetTxBiasCurrentEntry 1 }


pm10010mrMesrlineNetTxBiasCurrentPortn OBJECT-TYPE
	SYNTAX  INTEGER (0..65535)
	MAX-ACCESS read-only
	STATUS current
	DESCRIPTION
        "
        Current Line Trscv Tx Laser Bias 
        :This OID gives the Tx Laser Bias 
        value of the Line Transceiver,
         read from the DDM (Digital Diagnostic 
        Monitoring) (Bias = AV/10) (Unit 
        = mA) <Help> This Measure gives 
        the Tx Laser Bias value of the
         Line Transceiver
        "
	::= { pm10010mrMesrlineNetTxBiasCurrentEntry 2 }


--- *********************************************************
---     TABLE for the pm10010mrMesrlineNetRxInputPwr articles
--- *********************************************************

pm10010mrMesrlineNetRxInputPwrTable OBJECT-TYPE
	SYNTAX  SEQUENCE OF Pm10010mrMesrlineNetRxInputPwrEntry
	MAX-ACCESS not-accessible
	STATUS current
	DESCRIPTION
        "
        List of pm10010mrMesrlineNetRxInputPwr 
        Article
        "
	::= { pm10010mrMesrLine 128 }


pm10010mrMesrlineNetRxInputPwrEntry OBJECT-TYPE
	SYNTAX Pm10010mrMesrlineNetRxInputPwrEntry
	MAX-ACCESS not-accessible
	STATUS current
	DESCRIPTION
        "
        Row definition for the pm10010mrMesrlineNetRxInputPwr 
        table
        "
	INDEX   { pm10010mrMesrlineNetRxInputPwrIndex }
	::= { pm10010mrMesrlineNetRxInputPwrTable 1 }


Pm10010mrMesrlineNetRxInputPwrEntry ::=
	SEQUENCE {
	pm10010mrMesrlineNetRxInputPwrIndex
		INTEGER,
	pm10010mrMesrlineNetRxInputPwrPortn
		INTEGER 
	}


pm10010mrMesrlineNetRxInputPwrIndex OBJECT-TYPE
	SYNTAX  INTEGER(0..128)
	MAX-ACCESS  read-only
	STATUS current
	DESCRIPTION
        "
        Index definition for the pm10010mrMesrlineNetRxInputPwr 
        table
        "
	::= { pm10010mrMesrlineNetRxInputPwrEntry 1 }


pm10010mrMesrlineNetRxInputPwrPortn OBJECT-TYPE
	SYNTAX  INTEGER (0..65535)
	MAX-ACCESS read-only
	STATUS current
	DESCRIPTION
        "
        Current Line Trscv Rx Power :This 
        OID gives the Receive power value 
        of the Line Transceiver, read in 
        the DDM (Digital Diagnostic Monitoring) 
        (Power = AV/100) (Unit = dBm) <Help> 
        This Measure gives the Receive
         power value of the Line Transceiver
        "
	::= { pm10010mrMesrlineNetRxInputPwrEntry 2 }


--- *********************************************************
---     TABLE for the pm10010mrMesrlineResidualChromaticDisp articles
--- *********************************************************

pm10010mrMesrlineResidualChromaticDispTable OBJECT-TYPE
	SYNTAX  SEQUENCE OF Pm10010mrMesrlineResidualChromaticDispEntry
	MAX-ACCESS not-accessible
	STATUS current
	DESCRIPTION
        "
        List of pm10010mrMesrlineResidualChromaticDisp 
        Article
        "
	::= { pm10010mrMesrLine 144 }


pm10010mrMesrlineResidualChromaticDispEntry OBJECT-TYPE
	SYNTAX Pm10010mrMesrlineResidualChromaticDispEntry
	MAX-ACCESS not-accessible
	STATUS current
	DESCRIPTION
        "
        Row definition for the pm10010mrMesrlineResidualChromaticDisp 
        table
        "
	INDEX   { pm10010mrMesrlineResidualChromaticDispIndex }
	::= { pm10010mrMesrlineResidualChromaticDispTable 1 }


Pm10010mrMesrlineResidualChromaticDispEntry ::=
	SEQUENCE {
	pm10010mrMesrlineResidualChromaticDispIndex
		INTEGER,
	pm10010mrMesrlineResidualChromaticDispPortn
		INTEGER 
	}


pm10010mrMesrlineResidualChromaticDispIndex OBJECT-TYPE
	SYNTAX  INTEGER(0..128)
	MAX-ACCESS  read-only
	STATUS current
	DESCRIPTION
        "
        Index definition for the pm10010mrMesrlineResidualChromaticDisp 
        table
        "
	::= { pm10010mrMesrlineResidualChromaticDispEntry 1 }


pm10010mrMesrlineResidualChromaticDispPortn OBJECT-TYPE
	SYNTAX  INTEGER (0..65535)
	MAX-ACCESS read-only
	STATUS current
	DESCRIPTION
        "
        Current Residual Chromatic Dispersion 
        :This OID gives the current Residual 
        Chromatic Dispersion on the Line 
        interface  (Unit = ps/nm)<Help> 
        This measure gives the current
         Residual Chromatic Dispersion
         on the Line interface.
        "
	::= { pm10010mrMesrlineResidualChromaticDispEntry 2 }


--- *********************************************************
---     TABLE for the pm10010mrMesrlineDiffGroupDelay articles
--- *********************************************************

pm10010mrMesrlineDiffGroupDelayTable OBJECT-TYPE
	SYNTAX  SEQUENCE OF Pm10010mrMesrlineDiffGroupDelayEntry
	MAX-ACCESS not-accessible
	STATUS current
	DESCRIPTION
        "
        List of pm10010mrMesrlineDiffGroupDelay 
        Article
        "
	::= { pm10010mrMesrLine 148 }


pm10010mrMesrlineDiffGroupDelayEntry OBJECT-TYPE
	SYNTAX Pm10010mrMesrlineDiffGroupDelayEntry
	MAX-ACCESS not-accessible
	STATUS current
	DESCRIPTION
        "
        Row definition for the pm10010mrMesrlineDiffGroupDelay 
        table
        "
	INDEX   { pm10010mrMesrlineDiffGroupDelayIndex }
	::= { pm10010mrMesrlineDiffGroupDelayTable 1 }


Pm10010mrMesrlineDiffGroupDelayEntry ::=
	SEQUENCE {
	pm10010mrMesrlineDiffGroupDelayIndex
		INTEGER,
	pm10010mrMesrlineDiffGroupDelayPortn
		INTEGER 
	}


pm10010mrMesrlineDiffGroupDelayIndex OBJECT-TYPE
	SYNTAX  INTEGER(0..128)
	MAX-ACCESS  read-only
	STATUS current
	DESCRIPTION
        "
        Index definition for the pm10010mrMesrlineDiffGroupDelay 
        table
        "
	::= { pm10010mrMesrlineDiffGroupDelayEntry 1 }


pm10010mrMesrlineDiffGroupDelayPortn OBJECT-TYPE
	SYNTAX  INTEGER (0..65535)
	MAX-ACCESS read-only
	STATUS current
	DESCRIPTION
        "
        Current Differential Group Delay 
        :This OID gives the current Differential 
        Group Delay on the Line interface 
          (Unit = ps)<Help> This measure 
        gives the current Differential
         Group Delay on the Line interface.
        "
	::= { pm10010mrMesrlineDiffGroupDelayEntry 2 }


--- *********************************************************
---     TABLE for the pm10010mrMesrlineQFactor articles
--- *********************************************************

pm10010mrMesrlineQFactorTable OBJECT-TYPE
	SYNTAX  SEQUENCE OF Pm10010mrMesrlineQFactorEntry
	MAX-ACCESS not-accessible
	STATUS current
	DESCRIPTION
        "
        List of pm10010mrMesrlineQFactor 
        Article
        "
	::= { pm10010mrMesrLine 152 }


pm10010mrMesrlineQFactorEntry OBJECT-TYPE
	SYNTAX Pm10010mrMesrlineQFactorEntry
	MAX-ACCESS not-accessible
	STATUS current
	DESCRIPTION
        "
        Row definition for the pm10010mrMesrlineQFactor 
        table
        "
	INDEX   { pm10010mrMesrlineQFactorIndex }
	::= { pm10010mrMesrlineQFactorTable 1 }


Pm10010mrMesrlineQFactorEntry ::=
	SEQUENCE {
	pm10010mrMesrlineQFactorIndex
		INTEGER,
	pm10010mrMesrlineQFactorPortn
		INTEGER 
	}


pm10010mrMesrlineQFactorIndex OBJECT-TYPE
	SYNTAX  INTEGER(0..128)
	MAX-ACCESS  read-only
	STATUS current
	DESCRIPTION
        "
        Index definition for the pm10010mrMesrlineQFactor 
        table
        "
	::= { pm10010mrMesrlineQFactorEntry 1 }


pm10010mrMesrlineQFactorPortn OBJECT-TYPE
	SYNTAX  INTEGER (0..65535)
	MAX-ACCESS read-only
	STATUS current
	DESCRIPTION
        "
        Current Q Factor :This OID gives 
        the current Q Factor on the Line 
        interface   (Unit = dB) <Help>
         This measure gives the current 
        Q Factor on the Line interface.
        "
	::= { pm10010mrMesrlineQFactorEntry 2 }


--- *********************************************************
---     TABLE for the pm10010mrMesrlineCarrierFreqOffset articles
--- *********************************************************

pm10010mrMesrlineCarrierFreqOffsetTable OBJECT-TYPE
	SYNTAX  SEQUENCE OF Pm10010mrMesrlineCarrierFreqOffsetEntry
	MAX-ACCESS not-accessible
	STATUS current
	DESCRIPTION
        "
        List of pm10010mrMesrlineCarrierFreqOffset 
        Article
        "
	::= { pm10010mrMesrLine 156 }


pm10010mrMesrlineCarrierFreqOffsetEntry OBJECT-TYPE
	SYNTAX Pm10010mrMesrlineCarrierFreqOffsetEntry
	MAX-ACCESS not-accessible
	STATUS current
	DESCRIPTION
        "
        Row definition for the pm10010mrMesrlineCarrierFreqOffset 
        table
        "
	INDEX   { pm10010mrMesrlineCarrierFreqOffsetIndex }
	::= { pm10010mrMesrlineCarrierFreqOffsetTable 1 }


Pm10010mrMesrlineCarrierFreqOffsetEntry ::=
	SEQUENCE {
	pm10010mrMesrlineCarrierFreqOffsetIndex
		INTEGER,
	pm10010mrMesrlineCarrierFreqOffsetPortn
		INTEGER 
	}


pm10010mrMesrlineCarrierFreqOffsetIndex OBJECT-TYPE
	SYNTAX  INTEGER(0..128)
	MAX-ACCESS  read-only
	STATUS current
	DESCRIPTION
        "
        Index definition for the pm10010mrMesrlineCarrierFreqOffset 
        table
        "
	::= { pm10010mrMesrlineCarrierFreqOffsetEntry 1 }


pm10010mrMesrlineCarrierFreqOffsetPortn OBJECT-TYPE
	SYNTAX  INTEGER (0..65535)
	MAX-ACCESS read-only
	STATUS current
	DESCRIPTION
        "
        Current Carrier Frequency Offset 
        :This OID gives the current Carrier 
        Frequency Offset on the Line interface 
          (Unit = Mhz)<Help> This measure 
        gives the current Carrier Frequency 
        Offset on the Line interface.
        "
	::= { pm10010mrMesrlineCarrierFreqOffsetEntry 2 }


--- *********************************************************
---     TABLE for the pm10010mrMesrlineOsnr articles
--- *********************************************************

pm10010mrMesrlineOsnrTable OBJECT-TYPE
	SYNTAX  SEQUENCE OF Pm10010mrMesrlineOsnrEntry
	MAX-ACCESS not-accessible
	STATUS current
	DESCRIPTION
        "
        List of pm10010mrMesrlineOsnr
         Article
        "
	::= { pm10010mrMesrLine 160 }


pm10010mrMesrlineOsnrEntry OBJECT-TYPE
	SYNTAX Pm10010mrMesrlineOsnrEntry
	MAX-ACCESS not-accessible
	STATUS current
	DESCRIPTION
        "
        Row definition for the pm10010mrMesrlineOsnr 
        table
        "
	INDEX   { pm10010mrMesrlineOsnrIndex }
	::= { pm10010mrMesrlineOsnrTable 1 }


Pm10010mrMesrlineOsnrEntry ::=
	SEQUENCE {
	pm10010mrMesrlineOsnrIndex
		INTEGER,
	pm10010mrMesrlineOsnrPortn
		INTEGER 
	}


pm10010mrMesrlineOsnrIndex OBJECT-TYPE
	SYNTAX  INTEGER(0..128)
	MAX-ACCESS  read-only
	STATUS current
	DESCRIPTION
        "
        Index definition for the pm10010mrMesrlineOsnr 
        table
        "
	::= { pm10010mrMesrlineOsnrEntry 1 }


pm10010mrMesrlineOsnrPortn OBJECT-TYPE
	SYNTAX  INTEGER (0..65535)
	MAX-ACCESS read-only
	STATUS current
	DESCRIPTION
        "
        Current OSNR :This OID gives the 
        current OSNR on the Line interface 
         (OSNR = AV/10) (Unit = dB) <Help> 
        This measure gives the current
         OSNR on the Line interface.
        "
	::= { pm10010mrMesrlineOsnrEntry 2 }


--- *****************************************************
---     LEAF for the lineNetTxLaserOutputPwrAverage article
--- *****************************************************

pm10010mrMesrlineNetTxLaserOutputPwrAverage OBJECT-TYPE
	  SYNTAX Unsigned32 (0..65535)
	  MAX-ACCESS read-only
	  STATUS current
	  DESCRIPTION
        "
        Average Line Trscv Tx Power :This 
        OID gives the average Tx Laser
         transmit power value among the 
        network lanes of the Line Transceiver, 
        read in the DDM (Digital Diagnostic 
        Monitoring)  (Power = AV/100) (Unit 
        = dBm) (Unit = dBm) <Help> This 
        Measure gives the average Tx Laser 
        transmit power value among the
         network lanes of the Line Transceiver
        "
	  ::= { pm10010mrMesrOther 180 }



--- *****************************************************
---     LEAF for the lineNetTxLaserTempAverage article
--- *****************************************************

pm10010mrMesrlineNetTxLaserTempAverage OBJECT-TYPE
	  SYNTAX Unsigned32 (0..65535)
	  MAX-ACCESS read-only
	  STATUS current
	  DESCRIPTION
        "
        Average Line Trscv Tx Laser Temperature 
        :This OID gives the average Tx
         Laser Temperature value among
         the network lanes of the Line
         Transceiver, read from the DDM 
        (Digital Diagnostic Monitoring) 
        (Temperature = AV/256) (Unit =
         C) <Help> This Measure gives the 
        average Tx Laser Temperature value 
        among the network lanes of the
         Line Transceiver
        "
	  ::= { pm10010mrMesrOther 181 }



--- *****************************************************
---     LEAF for the lineNetTxBiasCurrentAverage article
--- *****************************************************

pm10010mrMesrlineNetTxBiasCurrentAverage OBJECT-TYPE
	  SYNTAX Unsigned32 (0..65535)
	  MAX-ACCESS read-only
	  STATUS current
	  DESCRIPTION
        "
        Average Line Trscv Tx Laser Bias 
        :This OID gives the average Tx
         Laser Bias value among the network 
        lanes of the Line Transceiver,
         read from the DDM (Digital Diagnostic 
        Monitoring) (Bias = AV/10) (Unit 
        = mA) <Help> This Measure gives 
        the average Tx Laser Bias value 
        among the network lanes of the
         Line Transceiver
        "
	  ::= { pm10010mrMesrOther 182 }



--- *****************************************************
---     LEAF for the lineNetRxInputPwrAverage article
--- *****************************************************

pm10010mrMesrlineNetRxInputPwrAverage OBJECT-TYPE
	  SYNTAX Unsigned32 (0..65535)
	  MAX-ACCESS read-only
	  STATUS current
	  DESCRIPTION
        "
        Average Line Trscv Rx Power :This 
        OID gives the average Receive power 
        value among the network lanes of 
        the Line Transceiver, read in the 
        DDM (Digital Diagnostic Monitoring) 
        (Power = AV/100) (Unit = dBm) <Help> 
        This Measure gives the average
         Receive power value among the
         network lanes of the Line Transceiver
        "
	  ::= { pm10010mrMesrOther 183 }



--- *****************************************************
---     LEAF for the lineResidualChromaticDispAverage article
--- *****************************************************

pm10010mrMesrlineResidualChromaticDispAverage OBJECT-TYPE
	  SYNTAX Unsigned32 (0..65535)
	  MAX-ACCESS read-only
	  STATUS current
	  DESCRIPTION
        "
        Average Residual Chromatic Dispersion 
        :This OID gives the average Residual 
        Chromatic Dispersion on the Line 
        interface since the last measure 
        reset <Help> This measure gives 
        the average Residual Chromatic
         Dispersion on the Line interface 
        since the last measure reset.
        "
	  ::= { pm10010mrMesrOther 184 }



--- *****************************************************
---     LEAF for the lineDiffGroupDelayAverage article
--- *****************************************************

pm10010mrMesrlineDiffGroupDelayAverage OBJECT-TYPE
	  SYNTAX Unsigned32 (0..65535)
	  MAX-ACCESS read-only
	  STATUS current
	  DESCRIPTION
        "
        Average Differential Group Delay 
        :This OID gives the average Group 
        Delay on the Line interface since 
        the last measure reset <Help> This 
        measure gives the average Differential 
        Group Delay on the Line interface 
        since the last measure reset.
        "
	  ::= { pm10010mrMesrOther 185 }



--- *****************************************************
---     LEAF for the lineQFactorAverage article
--- *****************************************************

pm10010mrMesrlineQFactorAverage OBJECT-TYPE
	  SYNTAX Unsigned32 (0..65535)
	  MAX-ACCESS read-only
	  STATUS current
	  DESCRIPTION
        "
        Average Q Factor :This OID gives 
        the average Q Factor on the Line 
        interface since the last measure 
        reset <Help> This measure gives 
        the average Q Factor on the Line 
        interface since the last measure 
        reset.
        "
	  ::= { pm10010mrMesrOther 186 }



--- *****************************************************
---     LEAF for the lineCarrierFreqOffsetAverage article
--- *****************************************************

pm10010mrMesrlineCarrierFreqOffsetAverage OBJECT-TYPE
	  SYNTAX Unsigned32 (0..65535)
	  MAX-ACCESS read-only
	  STATUS current
	  DESCRIPTION
        "
        Average Carrier Frequency Offset 
        :This OID gives the average Carrier 
        Frequency Offset on the Line interface 
        since the last measure reset <Help> 
        This measure gives the average
         Carrier Frequency Offset on the 
        Line interface since the last measure 
        reset
        "
	  ::= { pm10010mrMesrOther 187 }



--- *****************************************************
---     LEAF for the lineOsnrAverage article
--- *****************************************************

pm10010mrMesrlineOsnrAverage OBJECT-TYPE
	  SYNTAX Unsigned32 (0..65535)
	  MAX-ACCESS read-only
	  STATUS current
	  DESCRIPTION
        "
        Average OSNR :This OID gives the 
        average OSNR on the Line interface 
        since the last measure reset <Help> 
        This measure gives the average
         OSNR on the Line interface since 
        the last measure reset.
        "
	  ::= { pm10010mrMesrOther 188 }



--- *****************************************************
---     LEAF for the clientNetTxTempMin article
--- *****************************************************

pm10010mrMesrclientNetTxTempMin OBJECT-TYPE
	  SYNTAX Unsigned32 (0..65535)
	  MAX-ACCESS read-only
	  STATUS current
	  DESCRIPTION
        "
        Min Client Trscv Laser Temperature 
        :This OID gives the minimum Laser 
        temperature value among the network 
        lanes of the Client Transceiver, 
        read from the DDM (Digital Diagnostic 
        Monitoring) (Temperature = AV/256) 
        (Unit = C) <Help> This Measure
         gives the minimum Laser temperature 
        value among the network lanes of 
        the Client Transceiver
        "
	  ::= { pm10010mrMesrOther 192 }



--- *****************************************************
---     LEAF for the clientNetTxBiasMin article
--- *****************************************************

pm10010mrMesrclientNetTxBiasMin OBJECT-TYPE
	  SYNTAX Unsigned32 (0..65535)
	  MAX-ACCESS read-only
	  STATUS current
	  DESCRIPTION
        "
        Min Client Trscv Laser Bias :This 
        OID gives the minimum Laser bias 
        value among the network lanes of 
        the Client Transceiver, read from 
        the DDM (Digital Diagnostic Monitoring) 
        (Bias = AV/500) (Unit = mA) <Help> 
        This Measure gives the minimum
         Laser bias value among the network 
        lanes of the Client Transceiver
        "
	  ::= { pm10010mrMesrOther 193 }



--- *****************************************************
---     LEAF for the clientNetTxPwrMin article
--- *****************************************************

pm10010mrMesrclientNetTxPwrMin OBJECT-TYPE
	  SYNTAX Unsigned32 (0..65535)
	  MAX-ACCESS read-only
	  STATUS current
	  DESCRIPTION
        "
        Min Client Trscv Tx Power :This 
        OID gives the minimum transmit
         power value among the network
         lanes of the Client Transceiver, 
        read from the DDM (Digital Diagnostic 
        Monitoring) (Power = 10*log(AV)-40) 
        (Unit = dBm) <Help> This Measure 
        gives the minimum transmit power 
        value among the network lanes of 
        the Client Transceiver
        "
	  ::= { pm10010mrMesrOther 194 }



--- *****************************************************
---     LEAF for the clientNetRxPwrMin article
--- *****************************************************

pm10010mrMesrclientNetRxPwrMin OBJECT-TYPE
	  SYNTAX Unsigned32 (0..65535)
	  MAX-ACCESS read-only
	  STATUS current
	  DESCRIPTION
        "
        Min Client Trscv Rx Power :This 
        OID gives the minimum receive power 
        value among the network lanes of 
        the Client Transceiver, read in 
        the DDM (Digital Diagnostic Monitoring) 
        (Power = 10*log(AV)-40) (Unit = 
        dBm) <Help> This Measure gives
         the minimum receive power value 
        among the network lanes of the
         Client Transceiver
        "
	  ::= { pm10010mrMesrOther 195 }



--- *****************************************************
---     LEAF for the lineNetTxLaserOutputPwrMin article
--- *****************************************************

pm10010mrMesrlineNetTxLaserOutputPwrMin OBJECT-TYPE
	  SYNTAX Unsigned32 (0..65535)
	  MAX-ACCESS read-only
	  STATUS current
	  DESCRIPTION
        "
        Min Line Trscv Tx Power :This
         OID gives the minimum Tx Laser 
        transmit power value among the
         network lanes of the Line Transceiver, 
        read in the DDM (Digital Diagnostic 
        Monitoring)  (Power = AV/100) (Unit 
        = dBm) (Unit = dBm) <Help> This 
        Measure gives the minimum Tx Laser 
        transmit power value among the
         network lanes of the Line Transceiver
        "
	  ::= { pm10010mrMesrOther 196 }



--- *****************************************************
---     LEAF for the lineNetTxLaserTempMin article
--- *****************************************************

pm10010mrMesrlineNetTxLaserTempMin OBJECT-TYPE
	  SYNTAX Unsigned32 (0..65535)
	  MAX-ACCESS read-only
	  STATUS current
	  DESCRIPTION
        "
        Min Line Trscv Tx Laser Temperature 
        :This OID gives the minimum Tx
         Laser Temperature value among
         the network lanes of the Line
         Transceiver, read from the DDM 
        (Digital Diagnostic Monitoring) 
        (Temperature = AV/256) (Unit =
         C) <Help> This Measure gives the 
        minimum Tx Laser Temperature value 
        among the network lanes of the
         Line Transceiver
        "
	  ::= { pm10010mrMesrOther 197 }



--- *****************************************************
---     LEAF for the lineNetTxBiasCurrentMin article
--- *****************************************************

pm10010mrMesrlineNetTxBiasCurrentMin OBJECT-TYPE
	  SYNTAX Unsigned32 (0..65535)
	  MAX-ACCESS read-only
	  STATUS current
	  DESCRIPTION
        "
        Min Line Trscv Tx Laser Bias :This 
        OID gives the minimum Tx Laser
         Bias value among the network lanes 
        of the Line Transceiver, read from 
        the DDM (Digital Diagnostic Monitoring) 
        (Bias = AV/10) (Unit = mA) <Help> 
        This Measure gives the minimum
         Tx Laser Bias value among the
         network lanes of the Line Transceiver
        "
	  ::= { pm10010mrMesrOther 198 }



--- *****************************************************
---     LEAF for the lineNetRxInputPwrMin article
--- *****************************************************

pm10010mrMesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver, 
        read in the DDM (Digital Diagnostic 
        Monitoring) (Power = AV/100) (Unit 
        = dBm) <Help> This Measure gives 
        the minimum Receive power value 
        among the network lanes of the
         Line Transceiver
        "
	  ::= { pm10010mrMesrOther 199 }



--- *****************************************************
---     LEAF for the lineResidualChromaticDispMin article
--- *****************************************************

pm10010mrMesrlineResidualChromaticDispMin OBJECT-TYPE
	  SYNTAX Unsigned32 (0..65535)
	  MAX-ACCESS read-only
	  STATUS current
	  DESCRIPTION
        "
        Min Residual Chromatic Dispersion 
        :This OID gives the minimum Residual 
        Chromatic Dispersion on the Line 
        interface since the last measure 
        reset  (Unit = ps/nm)<Help> This 
        measure gives the minimum Residual 
        Chromatic Dispersion on the Line 
        interface since the last measure 
        reset.
        "
	  ::= { pm10010mrMesrOther 200 }



--- *****************************************************
---     LEAF for the lineDiffGroupDelayMin article
--- *****************************************************

pm10010mrMesrlineDiffGroupDelayMin OBJECT-TYPE
	  SYNTAX Unsigned32 (0..65535)
	  MAX-ACCESS read-only
	  STATUS current
	  DESCRIPTION
        "
        Min Differential Group Delay :This 
        OID gives the minimum Differential 
        Group Delay  on the Line interface 
        since the last measure reset  (Unit 
        = ps)<Help> This measure gives
         the minimum Differential Group 
        Delay on the Line interface since 
        the last measure reset.
        "
	  ::= { pm10010mrMesrOther 201 }



--- *****************************************************
---     LEAF for the lineQFactorMin article
--- *****************************************************

pm10010mrMesrlineQFactorMin OBJECT-TYPE
	  SYNTAX Unsigned32 (0..65535)
	  MAX-ACCESS read-only
	  STATUS current
	  DESCRIPTION
        "
        Min Q Factor :This OID gives the 
        minimum Q Factor on the Line interface 
        since the last measure reset  (Unit 
        = dB)<Help> This measure gives
         the minimum Q Factor on the Line 
        interface since the last measure 
        reset.
        "
	  ::= { pm10010mrMesrOther 202 }



--- *****************************************************
---     LEAF for the lineCarrierFreqOffsetMin article
--- *****************************************************

pm10010mrMesrlineCarrierFreqOffsetMin OBJECT-TYPE
	  SYNTAX Unsigned32 (0..65535)
	  MAX-ACCESS read-only
	  STATUS current
	  DESCRIPTION
        "
        Min Carrier Frequency Offset :This 
        OID gives the minimum Carrier Frequency 
        Offset on the Line interface since 
        the last measure reset  (Unit = 
        Mhz)<Help> This measure gives the 
        minimum Carrier Frequency Offset 
        on the Line interface since the 
        last measure reset
        "
	  ::= { pm10010mrMesrOther 203 }



--- *****************************************************
---     LEAF for the lineOsnrMin article
--- *****************************************************

pm10010mrMesrlineOsnrMin OBJECT-TYPE
	  SYNTAX Unsigned32 (0..65535)
	  MAX-ACCESS read-only
	  STATUS current
	  DESCRIPTION
        "
        Min OSNR :This OID gives the minimum 
        OSNR on the Line interface since 
        the last measure reset  (OSNR = 
        AV/10) (Unit = dB)<Help> This measure 
        gives the minimum OSNR on the Line 
        interface since the last measure 
        reset.
        "
	  ::= { pm10010mrMesrOther 204 }



--- *****************************************************
---     LEAF for the clientNetTxTempMax article
--- *****************************************************

pm10010mrMesrclientNetTxTempMax OBJECT-TYPE
	  SYNTAX Unsigned32 (0..65535)
	  MAX-ACCESS read-only
	  STATUS current
	  DESCRIPTION
        "
        Max Client Trscv Laser Temperature 
        :This OID gives the maximum Laser 
        temperature value among the network 
        lanes of the Client Transceiver, 
        read from the DDM (Digital Diagnostic 
        Monitoring) (Temperature = AV/256) 
        (Unit = C) <Help> This Measure
         gives the maximum Laser temperature 
        value among the network lanes of 
        the Client Transceiver
        "
	  ::= { pm10010mrMesrOther 208 }



--- *****************************************************
---     LEAF for the clientNetTxBiasMax article
--- *****************************************************

pm10010mrMesrclientNetTxBiasMax OBJECT-TYPE
	  SYNTAX Unsigned32 (0..65535)
	  MAX-ACCESS read-only
	  STATUS current
	  DESCRIPTION
        "
        Max Client Trscv Laser Bias :This 
        OID gives the maximum Laser bias 
        value among the network lanes of 
        the Client Transceiver, read from 
        the DDM (Digital Diagnostic Monitoring) 
        (Bias = AV/500) (Unit = mA) <Help> 
        This Measure gives the maximum
         Laser bias value among the network 
        lanes of the Client Transceiver
        "
	  ::= { pm10010mrMesrOther 209 }



--- *****************************************************
---     LEAF for the clientNetTxPwrMax article
--- *****************************************************

pm10010mrMesrclientNetTxPwrMax OBJECT-TYPE
	  SYNTAX Unsigned32 (0..65535)
	  MAX-ACCESS read-only
	  STATUS current
	  DESCRIPTION
        "
        Max Client Trscv Tx Power :This 
        OID gives the maximum transmit
         power value among the network
         lanes of the Client Transceiver, 
        read from the DDM (Digital Diagnostic 
        Monitoring) (Power = 10*log(AV)-40) 
        (Unit = dBm) <Help> This Measure 
        gives the maximum transmit power 
        value among the network lanes of 
        the Client Transceiver
        "
	  ::= { pm10010mrMesrOther 210 }



--- *****************************************************
---     LEAF for the clientNetRxPwrMax article
--- *****************************************************

pm10010mrMesrclientNetRxPwrMax OBJECT-TYPE
	  SYNTAX Unsigned32 (0..65535)
	  MAX-ACCESS read-only
	  STATUS current
	  DESCRIPTION
        "
        Max Client Trscv Rx Power :This 
        OID gives the maximum receive power 
        value among the network lanes of 
        the Client Transceiver, read in 
        the DDM (Digital Diagnostic Monitoring) 
        (Power = 10*log(AV)-40) (Unit = 
        dBm) <Help> This Measure gives
         the maximum receive power value 
        among the network lanes of the
         Client Transceiver
        "
	  ::= { pm10010mrMesrOther 211 }



--- *****************************************************
---     LEAF for the lineNetTxLaserOutputPwrMax article
--- *****************************************************

pm10010mrMesrlineNetTxLaserOutputPwrMax OBJECT-TYPE
	  SYNTAX Unsigned32 (0..65535)
	  MAX-ACCESS read-only
	  STATUS current
	  DESCRIPTION
        "
        Max Line Trscv Tx Power :This
         OID gives the maximum Tx Laser 
        transmit power value among the
         network lanes of the Line Transceiver, 
        read in the DDM (Digital Diagnostic 
        Monitoring) (Power = 10*log(AV)-40) 
        (Unit = dBm) <Help> This Measure 
        gives the maximum Tx Laser transmit 
        power value among the network lanes 
        of the Line Transceiver
        "
	  ::= { pm10010mrMesrOther 212 }



--- *****************************************************
---     LEAF for the lineNetTxLaserTempMax article
--- *****************************************************

pm10010mrMesrlineNetTxLaserTempMax OBJECT-TYPE
	  SYNTAX Unsigned32 (0..65535)
	  MAX-ACCESS read-only
	  STATUS current
	  DESCRIPTION
        "
        Max Line Trscv Tx Laser Temperature 
        :This OID gives the maximum Tx
         Laser Temperature value among
         the network lanes of the Line
         Transceiver, read from the DDM 
        (Digital Diagnostic Monitoring) 
        (Temperature = AV/256) (Unit =
         C) <Help> This Measure gives the 
        maximum Tx Laser Temperature value 
        among the network lanes of the
         Line Transceiver
        "
	  ::= { pm10010mrMesrOther 213 }



--- *****************************************************
---     LEAF for the lineNetTxBiasCurrentMax article
--- *****************************************************

pm10010mrMesrlineNetTxBiasCurrentMax OBJECT-TYPE
	  SYNTAX Unsigned32 (0..65535)
	  MAX-ACCESS read-only
	  STATUS current
	  DESCRIPTION
        "
        Max Line Trscv Tx Laser Bias :This 
        OID gives the maximum Tx Laser
         Bias value among the network lanes 
        of the Line Transceiver, read from 
        the DDM (Digital Diagnostic Monitoring) 
        (Bias = AV/10) (Unit = mA) <Help> 
        This Measure gives the maximum
         Tx Laser Bias value among the
         network lanes of the Line Transceiver
        "
	  ::= { pm10010mrMesrOther 214 }



--- *****************************************************
---     LEAF for the lineNetRxInputPwrMax article
--- *****************************************************

pm10010mrMesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver, 
        read in the DDM (Digital Diagnostic 
        Monitoring) (Power = 10*log(AV)-40) 
        (Unit = dBm) <Help> This Measure 
        gives the maximum Receive power 
        value among the network lanes of 
        the Line Transceiver
        "
	  ::= { pm10010mrMesrOther 215 }



--- *****************************************************
---     LEAF for the lineResidualChromaticDispMax article
--- *****************************************************

pm10010mrMesrlineResidualChromaticDispMax OBJECT-TYPE
	  SYNTAX Unsigned32 (0..65535)
	  MAX-ACCESS read-only
	  STATUS current
	  DESCRIPTION
        "
        Max Residual Chromatic Dispersion 
        :This OID gives the maximum Residual 
        Chromatic Dispersion on the Line 
        interface since the last measure 
        reset  (Unit = ps/nm)<Help> This 
        measure gives the maximum Residual 
        Chromatic Dispersion on the Line 
        interface since the last measure 
        reset.
        "
	  ::= { pm10010mrMesrOther 216 }



--- *****************************************************
---     LEAF for the lineDiffGroupDelayMax article
--- *****************************************************

pm10010mrMesrlineDiffGroupDelayMax OBJECT-TYPE
	  SYNTAX Unsigned32 (0..65535)
	  MAX-ACCESS read-only
	  STATUS current
	  DESCRIPTION
        "
        Max Differential Group Delay :This 
        OID gives the maximum Differential 
        Group Delay  on the Line interface 
        since the last measure reset  
         (Unit = ps)<Help> This measure 
        gives the maximum Differential
         Group Delay on the Line interface 
        since the last measure reset.
        "
	  ::= { pm10010mrMesrOther 217 }



--- *****************************************************
---     LEAF for the lineQFactorMax article
--- *****************************************************

pm10010mrMesrlineQFactorMax OBJECT-TYPE
	  SYNTAX Unsigned32 (0..65535)
	  MAX-ACCESS read-only
	  STATUS current
	  DESCRIPTION
        "
        Max Q Factor :This OID gives the 
        maximum Q Factor on the Line interface 
        since the last measure reset  (Unit 
        = dB)<Help> This measure gives
         the maximum Q Factor on the Line 
        interface since the last measure 
        reset.
        "
	  ::= { pm10010mrMesrOther 218 }



--- *****************************************************
---     LEAF for the lineCarrierFreqOffsetMax article
--- *****************************************************

pm10010mrMesrlineCarrierFreqOffsetMax OBJECT-TYPE
	  SYNTAX Unsigned32 (0..65535)
	  MAX-ACCESS read-only
	  STATUS current
	  DESCRIPTION
        "
        Max Carrier Frequency Offset :This 
        OID gives the maximum Carrier Frequency 
        Offset on the Line interface since 
        the last measure reset   (Unit
         = Mhz)<Help> This measure gives 
        the maximum Carrier Frequency Offset 
        on the Line interface since the 
        last measure reset.
        "
	  ::= { pm10010mrMesrOther 219 }



--- *****************************************************
---     LEAF for the lineOsnrMax article
--- *****************************************************

pm10010mrMesrlineOsnrMax OBJECT-TYPE
	  SYNTAX Unsigned32 (0..65535)
	  MAX-ACCESS read-only
	  STATUS current
	  DESCRIPTION
        "
        Max OSNR :This OID gives the maximum 
        OSNR on the Line interface since 
        the last measure reset  (OSNR = 
        AV/10) (Unit = dB)<Help> This measure 
        gives the maximum OSNR on the Line 
        interface since the last measure 
        reset
        "
	  ::= { pm10010mrMesrOther 220 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm10010mrDwlrestartProcess OBJECT IDENTIFIER ::= { pm10010mrDwlOther 0 }




pm10010mrDwlColdRestartProcessed OBJECT-TYPE
	  SYNTAX EkiOnOff
	  MAX-ACCESS read-only
	  STATUS current
	  DESCRIPTION
        "
        Cold Restart :This OID indicates 
        that the module last restart was 
        a Cold RESTART
        "
	  ::= { pm10010mrDwlrestartProcess 2 }



pm10010mrDwlWarmRestartProcessed OBJECT-TYPE
	  SYNTAX EkiOnOff
	  MAX-ACCESS read-only
	  STATUS current
	  DESCRIPTION
        "
        Warm Restart :This OID indicates 
        that the module last restart was 
        a Warm RESTART
        "
	  ::= { pm10010mrDwlrestartProcess 1 }



--- *****************************************************
---     LEAF for the swBanksUsed article
--- *****************************************************
pm10010mrDwlswBanksUsed OBJECT IDENTIFIER ::= { pm10010mrDwlOther 1 }




pm10010mrDwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pm10010mrDwlswBanksUsed 6 }



pm10010mrDwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pm10010mrDwlswBanksUsed 5 }



pm10010mrDwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pm10010mrDwlswBanksUsed 2 }



pm10010mrDwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pm10010mrDwlswBanksUsed 1 }



--- *****************************************************
---     LEAF for the gwBanksUsed article
--- *****************************************************
pm10010mrDwlgwBanksUsed OBJECT IDENTIFIER ::= { pm10010mrDwlOther 2 }




pm10010mrDwlGwBank4Notempty OBJECT-TYPE
	  SYNTAX EkiOnOff
	  MAX-ACCESS read-only
	  STATUS current
	  DESCRIPTION
        "
        GW bank 4 loaded :This OID indicates 
        a gateware is loaded in GW bank 
        4
        "
	  ::= { pm10010mrDwlgwBanksUsed 8 }



pm10010mrDwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pm10010mrDwlgwBanksUsed 7 }



pm10010mrDwlGwBank2Notempty OBJECT-TYPE
	  SYNTAX EkiOnOff
	  MAX-ACCESS read-only
	  STATUS current
	  DESCRIPTION
        "
        GW bank 2 loaded :This OID indicates 
        a gateware is loaded in GW bank 
        2
        "
	  ::= { pm10010mrDwlgwBanksUsed 6 }



pm10010mrDwlGwBank1Notempty OBJECT-TYPE
	  SYNTAX EkiOnOff
	  MAX-ACCESS read-only
	  STATUS current
	  DESCRIPTION
        "
        GW bank 1 loaded :This OID indicates 
        a gateware is loaded in GW bank 
        1  <Help>  This status indicates 
        if the GW bank 1 contains GW package
        "
	  ::= { pm10010mrDwlgwBanksUsed 5 }



pm10010mrDwlGwBank4Used OBJECT-TYPE
	  SYNTAX EkiOnOff
	  MAX-ACCESS read-only
	  STATUS current
	  DESCRIPTION
        "
        GW bank 4 active :This OID indicates 
        the module is working on GW bank 
        4
        "
	  ::= { pm10010mrDwlgwBanksUsed 4 }



pm10010mrDwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pm10010mrDwlgwBanksUsed 3 }



pm10010mrDwlGwBank2Used OBJECT-TYPE
	  SYNTAX EkiOnOff
	  MAX-ACCESS read-only
	  STATUS current
	  DESCRIPTION
        "
        GW bank 2 active :This OID indicates 
        the module is working on GW bank 
        2
        "
	  ::= { pm10010mrDwlgwBanksUsed 2 }



pm10010mrDwlGwBank1Used OBJECT-TYPE
	  SYNTAX EkiOnOff
	  MAX-ACCESS read-only
	  STATUS current
	  DESCRIPTION
        "
        GW bank 1 active :This OID indicates 
        the module is working on GW bank 
        1  <Help>  This status indicates 
        if the GW bank 1 is active or standby
        "
	  ::= { pm10010mrDwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm10010mrCfgAccessCAisCsf OBJECT IDENTIFIER ::= { pm10010mrConfig 1 }



--- *****************************************************
---     LEAF for the table 0012
--- *****************************************************

pm10010mrCfgClientcaiscsfTable OBJECT-TYPE
	SYNTAX  SEQUENCE OF Pm10010mrCfgClientcaiscsfEntry
	MAX-ACCESS not-accessible
	STATUS current
	DESCRIPTION
        "
        List of  Article
        "
	::= { pm10010mrCfgAccessCAisCsf 1 }


pm10010mrCfgClientcaiscsfEntry OBJECT-TYPE
	SYNTAX Pm10010mrCfgClientcaiscsfEntry
	MAX-ACCESS not-accessible
	STATUS current
	DESCRIPTION
        "
        Row definition for the accessCAisCsf 
        table
        "
	INDEX   { pm10010mrCfgClientcaiscsfIndex }
	::= { pm10010mrCfgClientcaiscsfTable 1 }


Pm10010mrCfgClientcaiscsfEntry ::=
	SEQUENCE {
	pm10010mrCfgClientcaiscsfIndex
		INTEGER,
	pm10010mrCfgReservePortn
		Unsigned32
	}


pm10010mrCfgClientcaiscsfIndex OBJECT-TYPE
	SYNTAX  INTEGER(0..128)
	MAX-ACCESS  read-only
	STATUS current
	DESCRIPTION
        "
        Index definition for the clientcaiscsf 
        table
        "
	::= { pm10010mrCfgClientcaiscsfEntry 1 }


pm10010mrCfgReservePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm10010mrCfgClientcaiscsfEntry 3 }


--- *****************************************************
---     LEAF for the table Group startup
--- *****************************************************

pm10010mrCfgStartup OBJECT IDENTIFIER ::= { pm10010mrConfig 2 }



--- *****************************************************
---     LEAF for the table 2110
--- *****************************************************

pm10010mrCfgClientStartupTable OBJECT-TYPE
	SYNTAX  SEQUENCE OF Pm10010mrCfgClientStartupEntry
	MAX-ACCESS not-accessible
	STATUS current
	DESCRIPTION
        "
        List of  Article
        "
	::= { pm10010mrCfgStartup 1 }


pm10010mrCfgClientStartupEntry OBJECT-TYPE
	SYNTAX Pm10010mrCfgClientStartupEntry
	MAX-ACCESS not-accessible
	STATUS current
	DESCRIPTION
        "
        Row definition for the startup 
        table
        "
	INDEX   { pm10010mrCfgClientStartupIndex }
	::= { pm10010mrCfgClientStartupTable 1 }


Pm10010mrCfgClientStartupEntry ::=
	SEQUENCE {
	pm10010mrCfgClientStartupIndex
		INTEGER,
	pm10010mrCfgSystConfPortPortn
		Unsigned32,
	pm10010mrCfgNetConfPortPortn
		Unsigned32,
	pm10010mrCfgIgnoreTimePortn
		Unsigned32,
	pm10010mrCfgOptionsPortPortn
		Unsigned32
	}


pm10010mrCfgClientStartupIndex OBJECT-TYPE
	SYNTAX  INTEGER(0..128)
	MAX-ACCESS  read-only
	STATUS current
	DESCRIPTION
        "
        Index definition for the clientStartup 
        table
        "
	::= { pm10010mrCfgClientStartupEntry 1 }


pm10010mrCfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm10010mrCfgClientStartupEntry 3 }


pm10010mrCfgNetConfPortPortn OBJECT-TYPE
	SYNTAX  Unsigned32 (0..65536)
	MAX-ACCESS read-write
	STATUS current
	DESCRIPTION
        "
        Default Settings on Client Port 
        :This  register configures the
         default initialisation settings 
        on the port.
        "
	::= { pm10010mrCfgClientStartupEntry 4 }


pm10010mrCfgIgnoreTimePortn OBJECT-TYPE
	SYNTAX  Unsigned32 (0..65536)
	MAX-ACCESS read-write
	STATUS current
	DESCRIPTION
        "
        Default Settings on Client Port 
        :This  register configures the
         default initialisation settings 
        on the port.
        "
	::= { pm10010mrCfgClientStartupEntry 6 }


pm10010mrCfgOptionsPortPortn OBJECT-TYPE
	SYNTAX  Unsigned32 (0..65536)
	MAX-ACCESS read-write
	STATUS current
	DESCRIPTION
        "
        Default Options on Client Port 
        :This register configures the default 
        options on the port.
        "
	::= { pm10010mrCfgClientStartupEntry 14 }


--- *****************************************************
---     LEAF for the table 2190
--- *****************************************************

pm10010mrCfgLineStartupTable OBJECT-TYPE
	SYNTAX  SEQUENCE OF Pm10010mrCfgLineStartupEntry
	MAX-ACCESS not-accessible
	STATUS current
	DESCRIPTION
        "
        List of  Article
        "
	::= { pm10010mrCfgStartup 2 }


pm10010mrCfgLineStartupEntry OBJECT-TYPE
	SYNTAX Pm10010mrCfgLineStartupEntry
	MAX-ACCESS not-accessible
	STATUS current
	DESCRIPTION
        "
        Row definition for the startup 
        table
        "
	INDEX   { pm10010mrCfgLineStartupIndex }
	::= { pm10010mrCfgLineStartupTable 1 }


Pm10010mrCfgLineStartupEntry ::=
	SEQUENCE {
	pm10010mrCfgLineStartupIndex
		INTEGER,
	pm10010mrCfgSystConfLinePortn
		Unsigned32,
	pm10010mrCfgOptionsLinePortn
		Unsigned32
	}


pm10010mrCfgLineStartupIndex OBJECT-TYPE
	SYNTAX  INTEGER(0..128)
	MAX-ACCESS  read-only
	STATUS current
	DESCRIPTION
        "
        Index definition for the lineStartup 
        table
        "
	::= { pm10010mrCfgLineStartupEntry 1 }


pm10010mrCfgSystConfLinePortn OBJECT-TYPE
	SYNTAX  Unsigned32 (0..65536)
	MAX-ACCESS read-write
	STATUS current
	DESCRIPTION
        "
        Default Settings on Line :This 
        register configures the default 
        initialisation settings on Line
        "
	::= { pm10010mrCfgLineStartupEntry 3 }


pm10010mrCfgOptionsLinePortn OBJECT-TYPE
	SYNTAX  Unsigned32 (0..65536)
	MAX-ACCESS read-write
	STATUS current
	DESCRIPTION
        "
        Default Options on Line :This
         register configures the default 
        options on the line
        "
	::= { pm10010mrCfgLineStartupEntry 14 }


--- *****************************************************
---     LEAF for the table 21AB
--- *****************************************************

pm10010mrCfgXfpTable OBJECT-TYPE
	SYNTAX  SEQUENCE OF Pm10010mrCfgXfpEntry
	MAX-ACCESS not-accessible
	STATUS current
	DESCRIPTION
        "
        List of  Article
        "
	::= { pm10010mrCfgStartup 3 }


pm10010mrCfgXfpEntry OBJECT-TYPE
	SYNTAX Pm10010mrCfgXfpEntry
	MAX-ACCESS not-accessible
	STATUS current
	DESCRIPTION
        "
        Row definition for the startup 
        table
        "
	INDEX   { pm10010mrCfgXfpIndex }
	::= { pm10010mrCfgXfpTable 1 }


Pm10010mrCfgXfpEntry ::=
	SEQUENCE {
	pm10010mrCfgXfpIndex
		INTEGER,
	pm10010mrCfgSystConfMsaLinePortn
		Unsigned32
	}


pm10010mrCfgXfpIndex OBJECT-TYPE
	SYNTAX  INTEGER(0..128)
	MAX-ACCESS  read-only
	STATUS current
	DESCRIPTION
        "
        Index definition for the xfp table
        "
	::= { pm10010mrCfgXfpEntry 1 }


pm10010mrCfgSystConfMsaLinePortn OBJECT-TYPE
	SYNTAX  Unsigned32 (0..65536)
	MAX-ACCESS read-write
	STATUS current
	DESCRIPTION
        "
        Default settings on MSA :This
         register configures the default 
        initialisation settings on MSA
        "
	::= { pm10010mrCfgXfpEntry 3 }


--- *****************************************************
---     LEAF for the table Group labels
--- *****************************************************

pm10010mrCfgLabels OBJECT IDENTIFIER ::= { pm10010mrConfig 3 }



--- *****************************************************
---     LEAF for the table 0003
--- *****************************************************

pm10010mrCfgLabelclientTable OBJECT-TYPE
	SYNTAX  SEQUENCE OF Pm10010mrCfgLabelclientEntry
	MAX-ACCESS not-accessible
	STATUS current
	DESCRIPTION
        "
        List of  Article
        "
	::= { pm10010mrCfgLabels 1 }


pm10010mrCfgLabelclientEntry OBJECT-TYPE
	SYNTAX Pm10010mrCfgLabelclientEntry
	MAX-ACCESS not-accessible
	STATUS current
	DESCRIPTION
        "
        Row definition for the labels
         table
        "
	INDEX   { pm10010mrCfgLabelclientIndex }
	::= { pm10010mrCfgLabelclientTable 1 }


Pm10010mrCfgLabelclientEntry ::=
	SEQUENCE {
	pm10010mrCfgLabelclientIndex
		INTEGER,
	pm10010mrCfgLabelclientPortn
		DisplayString
	}


pm10010mrCfgLabelclientIndex OBJECT-TYPE
	SYNTAX  INTEGER(0..128)
	MAX-ACCESS  read-only
	STATUS current
	DESCRIPTION
        "
        Index definition for the labelclient 
        table
        "
	::= { pm10010mrCfgLabelclientEntry 1 }


pm10010mrCfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm10010mrCfgLabelclientEntry 3 }


--- *****************************************************
---     LEAF for the table 0004
--- *****************************************************

pm10010mrCfgLabellineTable OBJECT-TYPE
	SYNTAX  SEQUENCE OF Pm10010mrCfgLabellineEntry
	MAX-ACCESS not-accessible
	STATUS current
	DESCRIPTION
        "
        List of  Article
        "
	::= { pm10010mrCfgLabels 2 }


pm10010mrCfgLabellineEntry OBJECT-TYPE
	SYNTAX Pm10010mrCfgLabellineEntry
	MAX-ACCESS not-accessible
	STATUS current
	DESCRIPTION
        "
        Row definition for the labels
         table
        "
	INDEX   { pm10010mrCfgLabellineIndex }
	::= { pm10010mrCfgLabellineTable 1 }


Pm10010mrCfgLabellineEntry ::=
	SEQUENCE {
	pm10010mrCfgLabellineIndex
		INTEGER,
	pm10010mrCfgLabellinePortn
		DisplayString
	}


pm10010mrCfgLabellineIndex OBJECT-TYPE
	SYNTAX  INTEGER(0..128)
	MAX-ACCESS  read-only
	STATUS current
	DESCRIPTION
        "
        Index definition for the labelline 
        table
        "
	::= { pm10010mrCfgLabellineEntry 1 }


pm10010mrCfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm10010mrCfgLabellineEntry 3 }


--- *****************************************************
---     LEAF for the table Group startuptlh
--- *****************************************************

pm10010mrCfgStartuptlh OBJECT IDENTIFIER ::= { pm10010mrConfig 4 }



--- *****************************************************
---     LEAF for the table 25AB
--- *****************************************************

pm10010mrCfgOtxtlhTable OBJECT-TYPE
	SYNTAX  SEQUENCE OF Pm10010mrCfgOtxtlhEntry
	MAX-ACCESS not-accessible
	STATUS current
	DESCRIPTION
        "
        List of  Article
        "
	::= { pm10010mrCfgStartuptlh 1 }


pm10010mrCfgOtxtlhEntry OBJECT-TYPE
	SYNTAX Pm10010mrCfgOtxtlhEntry
	MAX-ACCESS not-accessible
	STATUS current
	DESCRIPTION
        "
        Row definition for the startuptlh 
        table
        "
	INDEX   { pm10010mrCfgOtxtlhIndex }
	::= { pm10010mrCfgOtxtlhTable 1 }


Pm10010mrCfgOtxtlhEntry ::=
	SEQUENCE {
	pm10010mrCfgOtxtlhIndex
		INTEGER,
	pm10010mrCfgLinePwrLaserPortn
		Unsigned32,
	pm10010mrCfgLineFCurrentPortn
		Unsigned32,
	pm10010mrCfgLineGridCurrentPortn
		Unsigned32,
	pm10010mrCfgFPortn
		Unsigned32,
	pm10010mrCfgRxLineFCurrentPortn
		Unsigned32
	}


pm10010mrCfgOtxtlhIndex OBJECT-TYPE
	SYNTAX  INTEGER(0..128)
	MAX-ACCESS  read-only
	STATUS current
	DESCRIPTION
        "
        Index definition for the otxtlh 
        table
        "
	::= { pm10010mrCfgOtxtlhEntry 1 }


pm10010mrCfgLinePwrLaserPortn OBJECT-TYPE
	SYNTAX  Unsigned32 (0..65536)
	MAX-ACCESS read-write
	STATUS current
	DESCRIPTION
        "
        Defaut Line output Power :This 
        register configures the start-up 
        output power of the Line tranceiver 
         (Unit = dBm)
        "
	::= { pm10010mrCfgOtxtlhEntry 6 }


pm10010mrCfgLineFCurrentPortn OBJECT-TYPE
	SYNTAX  Unsigned32 (0..65536)
	MAX-ACCESS read-write
	STATUS current
	DESCRIPTION
        "
        Default Line transceiver Tx Channel 
        :This register configures the start-up 
        laser channel of the Line Tx transceiver
        "
	::= { pm10010mrCfgOtxtlhEntry 7 }


pm10010mrCfgLineGridCurrentPortn OBJECT-TYPE
	SYNTAX  Unsigned32 (0..65536)
	MAX-ACCESS read-write
	STATUS current
	DESCRIPTION
        "
        Default Line transceiver Grid
         :This register configures the
         start-up laser grid of the Line 
        transceiver
        "
	::= { pm10010mrCfgOtxtlhEntry 8 }


pm10010mrCfgFPortn OBJECT-TYPE
	SYNTAX  Unsigned32 (0..65536)
	MAX-ACCESS read-write
	STATUS current
	DESCRIPTION
        "
        Default Line TRX lowest Freq :This 
        register configures the start-up 
        lowest frequency of the Line transceiver
        "
	::= { pm10010mrCfgOtxtlhEntry 9 }


pm10010mrCfgRxLineFCurrentPortn OBJECT-TYPE
	SYNTAX  Unsigned32 (0..65536)
	MAX-ACCESS read-write
	STATUS current
	DESCRIPTION
        "
        Default Line transceiver Rx Channel 
        :This register configures the start-up 
        laser channel of the Line Rx transceiver
        "
	::= { pm10010mrCfgOtxtlhEntry 10 }


--- *****************************************************
---     LEAF for the table Group other
--- *****************************************************

pm10010mrCfgOther OBJECT IDENTIFIER ::= { pm10010mrConfig 5 }



--- *****************************************************
---     LEAF for the table 2300
--- *****************************************************

pm10010mrtablemoduleOther OBJECT IDENTIFIER ::= { pm10010mrCfgOther 1 }



pm10010mrCfgmode OBJECT-TYPE
	  SYNTAX Unsigned32 (0..65536)
	  MAX-ACCESS read-write
	  STATUS current
	  DESCRIPTION
        "
        Default settings on Module :This 
        register selects the configuration 
        mode of the module
        "
	  ::= { pm10010mrtablemoduleOther 2 }



pm10010mrCfgfanLowSpeedThreshold OBJECT-TYPE
	  SYNTAX Unsigned32 (0..65536)
	  MAX-ACCESS read-write
	  STATUS current
	  DESCRIPTION
        "
        Default settings on Module :This 
        register selects the speed threshold 
        of the fan's
        "
	  ::= { pm10010mrtablemoduleOther 3 }



pm10010mrCfgfanHighSpeedThreshold OBJECT-TYPE
	  SYNTAX Unsigned32 (0..65536)
	  MAX-ACCESS read-write
	  STATUS current
	  DESCRIPTION
        "
        Default settings on Module :This 
        register selects the speed threshold 
        of the fan's
        "
	  ::= { pm10010mrtablemoduleOther 4 }



--- *****************************************************
---     LEAF for the table Group startuptablefive
--- *****************************************************

pm10010mrCfgStartuptablefive OBJECT IDENTIFIER ::= { pm10010mrConfig 6 }



--- *****************************************************
---     LEAF for the table 0005
--- *****************************************************

pm10010mrCfgOtxtlhcapabilitiesTable OBJECT-TYPE
	SYNTAX  SEQUENCE OF Pm10010mrCfgOtxtlhcapabilitiesEntry
	MAX-ACCESS not-accessible
	STATUS current
	DESCRIPTION
        "
        List of  Article
        "
	::= { pm10010mrCfgStartuptablefive 1 }


pm10010mrCfgOtxtlhcapabilitiesEntry OBJECT-TYPE
	SYNTAX Pm10010mrCfgOtxtlhcapabilitiesEntry
	MAX-ACCESS not-accessible
	STATUS current
	DESCRIPTION
        "
        Row definition for the startuptablefive 
        table
        "
	INDEX   { pm10010mrCfgOtxtlhcapabilitiesIndex }
	::= { pm10010mrCfgOtxtlhcapabilitiesTable 1 }


Pm10010mrCfgOtxtlhcapabilitiesEntry ::=
	SEQUENCE {
	pm10010mrCfgOtxtlhcapabilitiesIndex
		INTEGER,
	pm10010mrCfgComponentTypePortn
		Unsigned32,
	pm10010mrCfgMiscellaneousPortn
		Unsigned32,
	pm10010mrCfgFirstChannelPortn
		Unsigned32,
	pm10010mrCfgLastChannelPortn
		Unsigned32,
	pm10010mrCfgGridPortn
		Unsigned32
	}


pm10010mrCfgOtxtlhcapabilitiesIndex OBJECT-TYPE
	SYNTAX  INTEGER(0..128)
	MAX-ACCESS  read-only
	STATUS current
	DESCRIPTION
        "
        Index definition for the otxtlhcapabilities 
        table
        "
	::= { pm10010mrCfgOtxtlhcapabilitiesEntry 1 }


pm10010mrCfgComponentTypePortn OBJECT-TYPE
	SYNTAX  Unsigned32 (0..65536)
	MAX-ACCESS read-only
	STATUS current
	DESCRIPTION
        "
        Component parameters :This OID 
        defines the component parameters
        "
	::= { pm10010mrCfgOtxtlhcapabilitiesEntry 3 }


pm10010mrCfgMiscellaneousPortn OBJECT-TYPE
	SYNTAX  Unsigned32 (0..65536)
	MAX-ACCESS read-only
	STATUS current
	DESCRIPTION
        "
        Miscellaneous default settings 
        :This OID defines the miscellaneous 
        parameters
        "
	::= { pm10010mrCfgOtxtlhcapabilitiesEntry 4 }


pm10010mrCfgFirstChannelPortn OBJECT-TYPE
	SYNTAX  Unsigned32 (0..65536)
	MAX-ACCESS read-only
	STATUS current
	DESCRIPTION
        "
        Number of the first channel of 
        the component :This OID defines 
        the first channel number of the 
        PM
        "
	::= { pm10010mrCfgOtxtlhcapabilitiesEntry 5 }


pm10010mrCfgLastChannelPortn OBJECT-TYPE
	SYNTAX  Unsigned32 (0..65536)
	MAX-ACCESS read-only
	STATUS current
	DESCRIPTION
        "
        Number of the last channel of
         the component :This OID defines 
        the last channel number of the
         PM
        "
	::= { pm10010mrCfgOtxtlhcapabilitiesEntry 6 }


pm10010mrCfgGridPortn OBJECT-TYPE
	SYNTAX  Unsigned32 (0..65536)
	MAX-ACCESS read-only
	STATUS current
	DESCRIPTION
        "
        Grid value of the component :This 
        OID defines the grid of the PM
        "
	::= { pm10010mrCfgOtxtlhcapabilitiesEntry 7 }



pm10010mrCfgWriteConfiguration  OBJECT-TYPE
	SYNTAX EkiOnOff
	MAX-ACCESS read-write
	STATUS current
	DESCRIPTION
	"Write configuration to module:This OID 
	 writes the complete configuration to the module"
	::= { pm10010mrConfig 257 }






--- *****************************************************
---     TRAP OBJECTS
--- *****************************************************

pm10010mrtrapPortNumber OBJECT-TYPE
	SYNTAX INTEGER(1..64)
	MAX-ACCESS read-only
	STATUS current
	DESCRIPTION
	"Last port which generates a trap"
	::= { pm10010mrtraps 2 }

pm10010mrtrapLineNumber OBJECT-TYPE
	SYNTAX INTEGER(1..64)
	MAX-ACCESS read-only
	STATUS current
	DESCRIPTION
	"Last Line which generates a trap"
	::= { pm10010mrtraps 3 }

pm10010mrtrapBoardNumber OBJECT-TYPE
	SYNTAX INTEGER(1..64)
	MAX-ACCESS read-only
	STATUS current
	DESCRIPTION
	"Last module which generates a trap"
	::= { pm10010mrtraps 4 }







--- *****************************************************
---     LINE TRAPS
--- *****************************************************

pm10010mrLineTrapNotUrgentGoesOn NOTIFICATION-TYPE
	OBJECTS {pm10010mrAlmLineDdmWarningPortn, pm10010mrtrapLineNumber, pm10010mrtrapBoardNumber}
	STATUS current
	--&FILTNAME    "PM10010MR Line Not Urgent ON"
	--&ACTIONS     { log, minor }
	--&MATCH       { pm10010mrAlmLineDdmWarningPortn "on", pm10010mrtrapLineNumber "$2", pm10010mrtrapBoardNumber "$3"}
	--&MESG        "DDM Warning appears on Line Port $2 of PM10010MR in Slot $3 ($A)"
	DESCRIPTION "Not urgent Line default is activated"
	::= { pm10010mrtraps 30 }

pm10010mrLineTrapNotUrgentGoesOff NOTIFICATION-TYPE
	OBJECTS {pm10010mrAlmLineDdmWarningPortn, pm10010mrtrapLineNumber, pm10010mrtrapBoardNumber}
	STATUS current
	--&FILTNAME    "PM10010MR Line Not Urgent OFF"
	--&ACTIONS     { log, normal }
	--&CLEARS      { "PM10010MR Line Not Urgent ON" }
	--&MATCH       { pm10010mrAlmLineDdmWarningPortn "on", pm10010mrtrapLineNumber "$2", pm10010mrtrapBoardNumber "$3"}
	--&MESG        "DDM Warning disappears on Line Port $2 of PM10010MR in Slot $3 ($A)"
	DESCRIPTION "Not urgent Line default disappeared"
	::= { pm10010mrtraps 31 }

pm10010mrLineTrapUrgentGoesOn NOTIFICATION-TYPE
	OBJECTS {pm10010mrAlmLineDdmAlmPortn, pm10010mrtrapLineNumber, pm10010mrtrapBoardNumber}
	STATUS current
	--&FILTNAME    "PM10010MR Line Urgent ON"
	--&ACTIONS     { log, major }
	--&MATCH       { pm10010mrAlmLineDdmAlmPortn "on", pm10010mrtrapLineNumber "$2", pm10010mrtrapBoardNumber "$3"}
	--&MESG        "DDM Alarm appears on Line Port $2 of PM10010MR in Slot $3 ($A)"
	DESCRIPTION "Urgent Line default is activated"
	::= { pm10010mrtraps 32 }

pm10010mrLineTrapUrgentGoesOff NOTIFICATION-TYPE
	OBJECTS {pm10010mrAlmLineDdmAlmPortn, pm10010mrtrapLineNumber, pm10010mrtrapBoardNumber}
	STATUS current
	--&FILTNAME    "PM10010MR Line Urgent OFF"
	--&ACTIONS     { log, normal }
	--&CLEARS      { "PM10010MR Line Urgent ON" }
	--&MATCH       { pm10010mrAlmLineDdmAlmPortn "on", pm10010mrtrapLineNumber "$2", pm10010mrtrapBoardNumber "$3"}
	--&MESG        "DDM Alarm disappears on Line Port $2 of PM10010MR in Slot $3 ($A)"
	DESCRIPTION "Urgent Line default disappeared"
	::= { pm10010mrtraps 33 }

pm10010mrLineTrapCritGoesOn NOTIFICATION-TYPE
	OBJECTS {pm10010mrAlmLineFailPortn , pm10010mrAlmLineHwFailPortn , pm10010mrtrapLineNumber, pm10010mrtrapBoardNumber}
	STATUS current
	--&FILTNAME    "PM10010MR Line Fail ON"
	--&ACTIONS     { log, critical }
	--&MATCH       { pm10010mrAlmLineFailPortn "on", pm10010mrAlmLineHwFailPortn "*", pm10010mrtrapLineNumber "$3", pm10010mrtrapBoardNumber "$4"}
	--&MESG        "Line Port $3 Down on PM10010MR in Slot $4 ($A)"
	
	--&FILTNAME    "PM10010MR Line HW Fail ON (Hidden)"
	--&ACTIONS     { info }
	--&MATCH       { pm10010mrAlmLineFailPortn "*", pm10010mrAlmLineHwFailPortn "on", pm10010mrtrapLineNumber "$3", pm10010mrtrapBoardNumber "$4"}
	--&MESG        "Line Port $3 Down on PM10010MR in Slot $4 ($A)"
	DESCRIPTION "Critical Line default is activated"
	::= { pm10010mrtraps 34 }

pm10010mrLineTrapCritGoesOff NOTIFICATION-TYPE
	OBJECTS {pm10010mrAlmLineFailPortn , pm10010mrAlmLineHwFailPortn , pm10010mrtrapLineNumber, pm10010mrtrapBoardNumber}
	STATUS current
	--&FILTNAME    "PM10010MR Line Fail OFF"
	--&ACTIONS     { log,  normal }
	--&CLEARS      { "PM10010MR Line Fail ON" }
	--&MATCH       { pm10010mrAlmLineFailPortn "on", pm10010mrAlmLineHwFailPortn "*", pm10010mrtrapLineNumber "$3", pm10010mrtrapBoardNumber "$4"}
	--&MESG        "Line Port $3 Up on PM10010MR in Slot $4 ($A)"

	--&FILTNAME    "PM10010MR Line HW Fail OFF (Hidden)"
	--&ACTIONS     { info }
	--&MATCH       { pm10010mrAlmLineFailPortn "*", pm10010mrAlmLineHwFailPortn "on", pm10010mrtrapLineNumber "$3", pm10010mrtrapBoardNumber "$4"}
	--&MESG        "Line Port $3 Up on PM10010MR in Slot $4 ($A)"
	DESCRIPTION "Critical Line default disappeared"
	::= { pm10010mrtraps 35 }






--- *****************************************************
---     CLIENT TRAPS
--- *****************************************************

pm10010mrClientTrapNotUrgentGoesOn NOTIFICATION-TYPE
	OBJECTS {pm10010mrAlmSfpDdmWarningPortn, pm10010mrtrapPortNumber, pm10010mrtrapBoardNumber}
	STATUS current
		--&FILTNAME    "PM10010MR Client Not Urgent ON"
		--&ACTIONS     { log, minor }
		--&MATCH       { pm10010mrAlmSfpDdmWarningPortn "on", pm10010mrtrapPortNumber "$2", pm10010mrtrapBoardNumber "$3"}
		--&MESG        "DDM Warning appears on Client Port $2 of PM10010MR in Slot $3 ($A)"
	DESCRIPTION "Not urgent client default is activated"
	::= { pm10010mrtraps 40 }

pm10010mrClientTrapNotUrgentGoesOff NOTIFICATION-TYPE
	OBJECTS {pm10010mrAlmSfpDdmWarningPortn, pm10010mrtrapPortNumber, pm10010mrtrapBoardNumber}
	STATUS current
		--&FILTNAME    "PM10010MR Client Not Urgent OFF"
		--&ACTIONS     { log, normal }
		--&CLEARS      { "PM10010MR Client Not Urgent ON" }
		--&MATCH       { pm10010mrAlmSfpDdmWarningPortn "on", pm10010mrtrapPortNumber "$2", pm10010mrtrapBoardNumber "$3"}
		--&MESG        "DDM Warning appears on Client Port $2 of PM10010MR in Slot $3 ($A)"
	DESCRIPTION "Not urgent client default disappeared"
	::= { pm10010mrtraps 41 }

pm10010mrClientTrapUrgentGoesOn NOTIFICATION-TYPE
	OBJECTS {pm10010mrAlmSfpDdmAlmPortn, pm10010mrtrapPortNumber, pm10010mrtrapBoardNumber}
	STATUS current
		--&FILTNAME    "PM10010MR Client Urgent ON"
		--&ACTIONS     { log, major }
		--&MATCH       { pm10010mrAlmSfpDdmAlmPortn "on", pm10010mrtrapPortNumber "$2", pm10010mrtrapBoardNumber "$3"}
		--&MESG        "DDM Alarm appears on Client Port $2 of PM10010MR in Slot $3 ($A)"
	DESCRIPTION "Urgent client default is activated"
	::= { pm10010mrtraps 42 }

pm10010mrClientTrapUrgentGoesOff NOTIFICATION-TYPE
	OBJECTS {pm10010mrAlmSfpDdmAlmPortn, pm10010mrtrapPortNumber, pm10010mrtrapBoardNumber}
	STATUS current
		--&FILTNAME    "PM10010MR Client Urgent OFF"
		--&ACTIONS     { log, normal }
		--&CLEARS      { "PM10010MR Client Urgent ON" }
		--&MATCH       { pm10010mrAlmSfpDdmAlmPortn "on", pm10010mrtrapPortNumber "$2", pm10010mrtrapBoardNumber "$3"}
		--&MESG        "DDM Alarm disappears on Client Port $2 of PM10010MR in Slot $3 ($A)"
	DESCRIPTION "Urgent client default disappeared"
	::= { pm10010mrtraps 43 }

pm10010mrClientTrapCritGoesOn NOTIFICATION-TYPE
	OBJECTS {pm10010mrAlmFailAccPortn, pm10010mrAlmHwFailAccPortn, pm10010mrtrapPortNumber, pm10010mrtrapBoardNumber}
	STATUS current
		--&FILTNAME    "PM10010MR Client Fail ON"
		--&ACTIONS     { log, critical }
		--&MATCH       { pm10010mrAlmFailAccPortn "on", pm10010mrAlmHwFailAccPortn "*", pm10010mrtrapPortNumber "$3", pm10010mrtrapBoardNumber "$4"}
		--&MESG        "Client Port $3 Down on PM10010MR in Slot $4 ($A)"
		
		--&FILTNAME    "PM10010MR Client HW Fail ON (Hidden)"
		--&ACTIONS     { info }
		--&MATCH       { pm10010mrAlmFailAccPortn "*", pm10010mrAlmHwFailAccPortn "on", pm10010mrtrapPortNumber "$3", pm10010mrtrapBoardNumber "$4"}
		--&MESG        "Client Port $3 Down on PM10010MR in Slot $4 ($A)"
	DESCRIPTION "Critical client default is activated"
	::= { pm10010mrtraps 44 }

pm10010mrClientTrapCritGoesOff NOTIFICATION-TYPE
	OBJECTS {pm10010mrAlmFailAccPortn, pm10010mrAlmHwFailAccPortn, pm10010mrtrapPortNumber, pm10010mrtrapBoardNumber}
	STATUS current
		--&FILTNAME    "PM10010MR Client Fail OFF"
		--&ACTIONS     { log, normal }
		--&CLEARS      { "PM10010MR Client Fail ON" }
		--&MATCH       { pm10010mrAlmFailAccPortn "on", pm10010mrAlmHwFailAccPortn "*", pm10010mrtrapPortNumber "$3", pm10010mrtrapBoardNumber "$4"}
		--&MESG        "Client Port $3 Up on PM10010MR in Slot $4 ($A)"
		
		--&FILTNAME    "PM10010MR Client HW Fail OFF (Hidden)"
		--&ACTIONS     { info }
		--&MATCH       { pm10010mrAlmFailAccPortn "*", pm10010mrAlmHwFailAccPortn "on", pm10010mrtrapPortNumber "$3", pm10010mrtrapBoardNumber "$4"}
		--&MESG        "Client Port $3 Up on PM10010MR in Slot $4 ($A)"
	DESCRIPTION "Critical client default disappeared"
	::= { pm10010mrtraps 45 }






--- *****************************************************
---     HW TRAPS
--- *****************************************************

pm10010mrPowerTrapUrgentGoesOn NOTIFICATION-TYPE
	OBJECTS {pm10010mrAlmDefFuseB, pm10010mrAlmDefFuseA , pm10010mrtrapBoardNumber}
	STATUS current
		--&FILTNAME    "PM10010MR Fuse A Fail ON"
		--&ACTIONS     { log, major }
		--&MATCH       { pm10010mrAlmDefFuseB "*", pm10010mrAlmDefFuseA "on", pm10010mrtrapBoardNumber "$3"}
		--&MESG        "Power Input A Fail on PM10010MR in Slot $3 ($A)"
	
		--&FILTNAME    "PM10010MR Fuse B Fail ON"
		--&ACTIONS     { log, major }
		--&MATCH       { pm10010mrAlmDefFuseB "on", pm10010mrAlmDefFuseA "*", pm10010mrtrapBoardNumber "$3"}
		--&MESG        "Power Input B Fail on PM10010MR in Slot $3 ($A)"
	DESCRIPTION "Urgent power supply default is activated"
	::= { pm10010mrtraps 50 }

pm10010mrPowerTrapUrgentGoesOff NOTIFICATION-TYPE
	OBJECTS {pm10010mrAlmDefFuseB, pm10010mrAlmDefFuseA , pm10010mrtrapBoardNumber}
	STATUS current
		--&FILTNAME    "PM10010MR Fuse A&B Fail OFF"
		--&ACTIONS     { log, normal}
		--&CLEARS      { "PM10010MR Fuse A Fail ON", "PM10010MR Fuse B Fail ON" }
		--&MATCH       { pm10010mrAlmDefFuseB "on", pm10010mrAlmDefFuseA "on", pm10010mrtrapBoardNumber "$3"}
		--&MESG        "Power Inputs A and B Present on PM10010MR in Slot $3 ($A)"
	DESCRIPTION "Urgent power supply default disappeared"
	::= { pm10010mrtraps 51 }






END
