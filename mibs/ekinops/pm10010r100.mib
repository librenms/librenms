-- *****************************************************************
-- EKINOPS-Pm10010r100.TXT:  MIB
--
--MIB Part Number:3MI00056AAAA
--MIB Version:04
--
-- Copyright (c) 2018 by Ekinops
-- All rights reserved.
-- 
-- *****************************************************************

EKINOPS-Pm10010r100-MIB DEFINITIONS ::= BEGIN

IMPORTS
	ekinops,
	EkiState,
	EkiOnOff,
	EkiMode,
	EkiProtocol,
	EkiApiState,
	EkiSynchroMode,
	EkiMeasureType
			FROM EKINOPS-MIB
        MODULE-IDENTITY,
        OBJECT-TYPE,
        NOTIFICATION-TYPE,
	Unsigned32,
	Integer32,
	Counter32,
	IpAddress                
        		FROM SNMPv2-SMI
 	TEXTUAL-CONVENTION,
	DisplayString
                FROM SNMPv2-TC;

modulePm10010r100 MODULE-IDENTITY
        LAST-UPDATED "201806040000Z"
        ORGANIZATION "Ekinops"
        CONTACT-INFO
         "Ekinops

          3, rue Blaise Pascal
          F-22300 Lannion / FRANCE

          Tel : +33 (0)2 96 05 00 30
          Fax : +33 (0)2 96 48 62 39

          E-mail: support@ekinops.fr"
        DESCRIPTION
          "Creation."

	REVISION "201805300000Z"
	DESCRIPTION
	  "Creation for PM10010R100"
        ::= { ekinops 97 }



--- *****************************************************
---     LEAF LEVEL 2
--- *****************************************************


pm10010r100alarms OBJECT IDENTIFIER ::= { modulePm10010r100 2 }	
pm10010r100AlmOther OBJECT IDENTIFIER ::= { pm10010r100alarms 1 }
pm10010r100AlmOtherNurg OBJECT IDENTIFIER ::= { pm10010r100AlmOther 1 }
pm10010r100AlmOtherUrg OBJECT IDENTIFIER ::= { pm10010r100AlmOther 2 }
pm10010r100AlmOtherCrit OBJECT IDENTIFIER ::= { pm10010r100AlmOther 3 }

pm10010r100AlmClient OBJECT IDENTIFIER ::= { pm10010r100alarms 2 }
pm10010r100AlmClientNurg OBJECT IDENTIFIER ::= { pm10010r100AlmClient 1 }
pm10010r100AlmClientUrg OBJECT IDENTIFIER ::= { pm10010r100AlmClient 2 }
pm10010r100AlmClientCrit OBJECT IDENTIFIER ::= { pm10010r100AlmClient 3 }
	
pm10010r100AlmLine OBJECT IDENTIFIER ::= { pm10010r100alarms 3 }
pm10010r100AlmLineNurg OBJECT IDENTIFIER ::= { pm10010r100AlmLine 1 }
pm10010r100AlmLineUrg OBJECT IDENTIFIER ::= { pm10010r100AlmLine 2 }
pm10010r100AlmLineCrit OBJECT IDENTIFIER ::= { pm10010r100AlmLine 3 }





pm10010r100measures OBJECT IDENTIFIER ::= { modulePm10010r100 3 }	
pm10010r100MesrOther OBJECT IDENTIFIER ::= { pm10010r100measures 1 }	
pm10010r100MesrClient OBJECT IDENTIFIER ::= { pm10010r100measures 2 }	
pm10010r100MesrLine OBJECT IDENTIFIER ::= { pm10010r100measures 3 }	




pm10010r100counters OBJECT IDENTIFIER ::= { modulePm10010r100 4 }
pm10010r100CntOther OBJECT IDENTIFIER ::= { pm10010r100counters 1 }
pm10010r100CntClient OBJECT IDENTIFIER ::= { pm10010r100counters 2 }
pm10010r100CntLine OBJECT IDENTIFIER ::= { pm10010r100counters 3 }


pm10010r100controlsWrite OBJECT IDENTIFIER ::= { modulePm10010r100 6 }
pm10010r100CtrlOther OBJECT IDENTIFIER ::= { pm10010r100controlsWrite 1 }
pm10010r100CtrlClient OBJECT IDENTIFIER ::= { pm10010r100controlsWrite 2 }
pm10010r100CtrlLine OBJECT IDENTIFIER ::= { pm10010r100controlsWrite 3 }

pm10010r100ri OBJECT IDENTIFIER ::= { modulePm10010r100 7 }
pm10010r100riTable OBJECT IDENTIFIER ::= { pm10010r100ri 1 }

pm10010r100download OBJECT IDENTIFIER ::= { modulePm10010r100 8 }
pm10010r100DwlOther OBJECT IDENTIFIER ::= { pm10010r100download 1 }
pm10010r100DwlClient OBJECT IDENTIFIER ::= { pm10010r100download 2 }
pm10010r100DwlLine OBJECT IDENTIFIER ::= { pm10010r100download 3 }


pm10010r100Config OBJECT IDENTIFIER ::= { modulePm10010r100 9 }

pm10010r100traps OBJECT IDENTIFIER ::= { modulePm10010r100 10 }



pm10010r100Monitoring OBJECT IDENTIFIER ::= { modulePm10010r100 11}

pm10010r100MonOther OBJECT IDENTIFIER ::= { pm10010r100Monitoring 1 }
pm10010r100MonRmon OBJECT IDENTIFIER ::= { pm10010r100MonOther 3 }

pm10010r100MonClient OBJECT IDENTIFIER ::= { pm10010r100Monitoring 2 }
pm10010r100MonClientRmonCounter OBJECT IDENTIFIER ::= { pm10010r100MonClient 4 }


--- *****************************************************
--- $$$$$$$$$$$$$$$$$$$$$$$$$$$$$$$$$$$$$$$$$$$$$$$$$$$$$
---     TEXTUAL-CONVENTION
--- $$$$$$$$$$$$$$$$$$$$$$$$$$$$$$$$$$$$$$$$$$$$$$$$$$$$$
--- *****************************************************

Pm10010r100MultiRate ::= TEXTUAL-CONVENTION
    STATUS      current
    DESCRIPTION "different rate for a client port"
    SYNTAX INTEGER {
		rate100Mhz(0),
		rate250Mhz(1),
		rate500Mhz(2),
		rate1Ghz(3)
           }

Pm10010r100OtxMode ::= TEXTUAL-CONVENTION
    STATUS      current
    DESCRIPTION "Different modes on OTX-TLH on client and line ports"
    SYNTAX INTEGER {
		otx80mode(1),
		otx60mode(2),
		otxadjustmode(4)
           }

Pm10010r100OtxGrid ::= TEXTUAL-CONVENTION
    STATUS      current
    DESCRIPTION "Different grids on OTX-TLH on client and line ports"
    SYNTAX INTEGER {
		otxgrid200(200),
		otxgrid100(100),
		otxgrid50(50)
           }

Pm10010r100AdjustValue ::= TEXTUAL-CONVENTION
    STATUS      current
    DESCRIPTION "Different values in Adjust mode on OTX-TLH on client and line ports"
    SYNTAX INTEGER {
		otxadjustvalue0(0),
		otxadjustvalue1(1),
		otxadjustvalue2(2),
		otxadjustvalue3(3),
		otxadjustvalue4(4),
		otxadjustvalue5(5),
		otxadjustvalue6(6),
		otxadjustvalue7(7),
		otxadjustvalue8(8),
		otxadjustvalue9(9),
		otxadjustvalue10(10)
           }

Pm10010r100ClientProtocol ::= TEXTUAL-CONVENTION
    STATUS      current
    DESCRIPTION "Different values on the protocol on the client ports"
    SYNTAX INTEGER {
		protocolclientvalue0(0),
		protocolclientvalue1(1),
		protocolclientvalue2(2),
		protocolclientvalue3(3),
		protocolclientvalue4(4),
		protocolclientvalue5(5),
		protocolclientvalue6(6),
		protocolclientvalue7(7),
		protocolclientvalue8(8)
           }

Pm10010r100ProtocolMode ::= TEXTUAL-CONVENTION
    STATUS      current
    DESCRIPTION "Different values on the protocol mode"
    SYNTAX INTEGER {
		protocolmodevalue0(0),
		protocolmodevalue1(1),
		protocolmodevalue2(2),
		protocolmodevalue3(3)
           }

Pm10010r100OtxChannel ::= TEXTUAL-CONVENTION
    STATUS      current
    DESCRIPTION "Channel selection on transceiver Tx line ports"
    SYNTAX INTEGER

Pm10010r100OrxChannel ::= TEXTUAL-CONVENTION
    STATUS      current
    DESCRIPTION "Channel selection on transceiver Rx line ports"
    SYNTAX INTEGER

--- *****************************************************
--- $$$$$$$$$$$$$$$$$$$$$$$$$$$$$$$$$$$$$$$$$$$$$$$$$$$$$
---     REMOTE INVENTORY
--- $$$$$$$$$$$$$$$$$$$$$$$$$$$$$$$$$$$$$$$$$$$$$$$$$$$$$
--- *****************************************************

pm10010r100RinvReloadInventory OBJECT-TYPE
  SYNTAX EkiOnOff
  MAX-ACCESS read-write
  STATUS current
  DESCRIPTION
        "Reload the inventory: This OID triggers an 
         inventory reload."
  ::= { pm10010r100ri 2 }

pm10010r100RinvHwPlatform OBJECT-TYPE
  SYNTAX DisplayString
  MAX-ACCESS read-only
  STATUS current
  DESCRIPTION
        "HW platform description: This OID contains the 
         description of the Hardware platform."
  ::= { pm10010r100ri 3 }
  
pm10010r100RinvModulePlatform OBJECT-TYPE
  SYNTAX DisplayString
  MAX-ACCESS read-only
  STATUS current
  DESCRIPTION
        "Module platform description: This OID contains the 
         description of the Module."
  ::= { pm10010r100ri 4 }
  
pm10010r100RinvSwPlatform OBJECT-TYPE
  SYNTAX DisplayString
  MAX-ACCESS read-only
  STATUS current
  DESCRIPTION
        "SW platform description: This OID contains the 
         description of the Software platform."
  ::= { pm10010r100ri 5 }
  
pm10010r100RinvGwPlatform OBJECT-TYPE
  SYNTAX DisplayString
  MAX-ACCESS read-only
  STATUS current
  DESCRIPTION
        "GW platform desciption: This OID contains the 
         description of the Gateware platform."
  ::= { pm10010r100ri 6 }


pm10010r100RinvSfpTable OBJECT-TYPE
      SYNTAX  SEQUENCE OF Pm10010r100RinvSfpEntry
      MAX-ACCESS  not-accessible
      STATUS  current
      DESCRIPTION
              "List of the SFPs on the selected module"
      ::= { pm10010r100riTable 1 }

pm10010r100RinvSfpEntry OBJECT-TYPE
        SYNTAX  Pm10010r100RinvSfpEntry
        MAX-ACCESS  not-accessible
        STATUS  current
        DESCRIPTION
              "Row definition for the SFP table"
        INDEX   { pm10010r100RinvSfpIndex }
        ::= { pm10010r100RinvSfpTable 1 }
    


Pm10010r100RinvSfpEntry::=
        SEQUENCE {
          pm10010r100RinvSfpIndex 
              Integer32,
          pm10010r100Rinvsfp
              DisplayString
        }


    pm10010r100RinvSfpIndex OBJECT-TYPE
        SYNTAX  Integer32(1..16)
        MAX-ACCESS  read-only
        STATUS  current
        DESCRIPTION
              "Index for SFP table"
        ::= { pm10010r100RinvSfpEntry 1 }


    pm10010r100Rinvsfp OBJECT-TYPE
        SYNTAX  DisplayString
        MAX-ACCESS  read-only
        STATUS  current
        DESCRIPTION
              "Inventory for the SFP: This OID contains the inventory for the SFP"
        ::= { pm10010r100RinvSfpEntry 2 }




pm10010r100RinvLineTable OBJECT-TYPE
      SYNTAX  SEQUENCE OF Pm10010r100RinvLineEntry
      MAX-ACCESS  not-accessible
      STATUS  current
      DESCRIPTION
              "List of the XFPs on the selected module"
      ::= { pm10010r100riTable 2 }

pm10010r100RinvLineEntry OBJECT-TYPE
        SYNTAX  Pm10010r100RinvLineEntry
        MAX-ACCESS  not-accessible
        STATUS  current
        DESCRIPTION
              "Row definition for the XFP table"
        INDEX   { pm10010r100RinvLineIndex }
        ::= { pm10010r100RinvLineTable 1 }
    


Pm10010r100RinvLineEntry::=
        SEQUENCE {
          pm10010r100RinvLineIndex 
              Integer32,
          pm10010r100RinvxfpLine
              DisplayString
        }


    pm10010r100RinvLineIndex OBJECT-TYPE
        SYNTAX  Integer32(1..16)
        MAX-ACCESS  read-only
        STATUS  current
        DESCRIPTION
              "Index for XFP table"
        ::= { pm10010r100RinvLineEntry 1 }


    pm10010r100RinvxfpLine OBJECT-TYPE
        SYNTAX  DisplayString
        MAX-ACCESS  read-only
        STATUS  current
        DESCRIPTION
              "Inventory for the XFP: This OID contains the inventory for the XFP"
        ::= { pm10010r100RinvLineEntry 2 }









--- *****************************************************
--- $$$$$$$$$$$$$$$$$$$$$$$$$$$$$$$$$$$$$$$$$$$$$$$$$$$$$
---     ALARMS
--- $$$$$$$$$$$$$$$$$$$$$$$$$$$$$$$$$$$$$$$$$$$$$$$$$$$$$
--- *****************************************************



--- *****************************************************
---     LEAF for the synthAlm0 article
--- *****************************************************
pm10010r100AlmsynthAlm0 OBJECT IDENTIFIER ::= { pm10010r100AlmOtherCrit 0 }




pm10010r100AlmDefFuseB OBJECT-TYPE
	  SYNTAX EkiOnOff
	  MAX-ACCESS read-only
	  STATUS current
	  DESCRIPTION
        "
        Fuse B Fail :This OID indicates 
        that the fuse of the power input 
        B is in fail condition <Help> Status 
        of the Fuse B <Condtype> DEF_FUSE_B 
        <Probcause> powerProblem (36) <Alarmtype> 
        equipmentAlarm (5) <Polarity> (2) 
        "
	  ::= { pm10010r100AlmsynthAlm0 16 }



pm10010r100AlmDefFuseA OBJECT-TYPE
	  SYNTAX EkiOnOff
	  MAX-ACCESS read-only
	  STATUS current
	  DESCRIPTION
        "
        Fuse A Fail :This OID indicates 
        that the fuse of the power input 
        A is in fail condition <Help> Status 
        of the Fuse A <Condtype> DEF_FUSE_A 
        <Probcause> powerProblem (36) <Alarmtype> 
        equipmentAlarm (5) <Polarity> (2) 
        "
	  ::= { pm10010r100AlmsynthAlm0 15 }



pm10010r100AlmModGlobFail OBJECT-TYPE
	  SYNTAX EkiOnOff
	  MAX-ACCESS read-only
	  STATUS current
	  DESCRIPTION
        "
        Module Failure :This OID is set 
        on detection of a failure originating 
        from the RM <Help> This alarm is 
        set on detection of a failure originating 
        from the equipment <Condtype> MOD_GLOB_FAIL 
        <Probcause> other (1) <Alarmtype> 
        synthesisAlarm (12) ) <Polarity> 
        (2) 
        "
	  ::= { pm10010r100AlmsynthAlm0 9 }



pm10010r100AlmFailFan OBJECT-TYPE
	  SYNTAX EkiOnOff
	  MAX-ACCESS read-only
	  STATUS current
	  DESCRIPTION
        "
        Fan Fail :This OID is at 1 when 
        any fail occurs on the fan tray 
        <Help> This alarm indicates that 
        the Fan tray module is in a failure 
        condition <Condtype> FAIL_FAN <Probcause> 
        equipmentMalfunction (16) <Alarmtype> 
        equipmentAlarm (5) <Polarity> (2) 
        "
	  ::= { pm10010r100AlmsynthAlm0 2 }



--- *****************************************************
---     LEAF for the synthAlm2 article
--- *****************************************************
pm10010r100AlmsynthAlm2 OBJECT IDENTIFIER ::= { pm10010r100AlmOtherNurg 2 }




pm10010r100AlmMaintenanceOn OBJECT-TYPE
	  SYNTAX EkiOnOff
	  MAX-ACCESS read-only
	  STATUS current
	  DESCRIPTION
        "
        Maintenance Mode :This OID indicates 
        that the RM is in maintenance mode. 
        <Help> This alarm indicates that 
        the maintenance mode is enabled 
        on the PM <Condtype> MAINTENANCE_ON 
        <Probcause> informationalStatus(1000) 
        <Alarmtype> other (1) <Polarity> 
        (2) 
        "
	  ::= { pm10010r100AlmsynthAlm2 5 }



pm10010r100AlmCorrelatOff OBJECT-TYPE
	  SYNTAX EkiOnOff
	  MAX-ACCESS read-only
	  STATUS current
	  DESCRIPTION
        "
        Not Used :This OID, when set,
         indicates that alarm correlation 
        is not being performed. <Condtype> 
        CORRELAT_OFF <Probcause> informationalStatus(1000) 
        <Alarmtype> other (1) <Polarity> 
        (2) 
        "
	  ::= { pm10010r100AlmsynthAlm2 4 }



pm10010r100AlmConfTableLoad OBJECT-TYPE
	  SYNTAX EkiOnOff
	  MAX-ACCESS read-only
	  STATUS current
	  DESCRIPTION
        "
        PM Configuration Load :This OID 
         is at 1 during the loading of
         configuration tables in the modules 
        RAM. <Condtype> CONF_TABLE_LOAD 
        <Probcause> informationalStatus(1000) 
        <Alarmtype> other (1) <Polarity> 
        (2) 
        "
	  ::= { pm10010r100AlmsynthAlm2 3 }



pm10010r100AlmInvUpload OBJECT-TYPE
	  SYNTAX EkiOnOff
	  MAX-ACCESS read-only
	  STATUS current
	  DESCRIPTION
        "
        Inventory Upload :This OID is
         at 1 during the uploading of PM 
        inventory information. <Condtype> 
        INV_UPLOAD <Probcause> informationalStatus(1000) 
        <Alarmtype> other (1) <Polarity> 
        (2) 
        "
	  ::= { pm10010r100AlmsynthAlm2 2 }



pm10010r100AlmConfTableSave OBJECT-TYPE
	  SYNTAX EkiOnOff
	  MAX-ACCESS read-only
	  STATUS current
	  DESCRIPTION
        "
        PM Configuration Save :This OID 
        is at 1 during the saving of a
         new configuration table in the 
        module Flash memory. <Condtype> 
        CONF_TABLE_SAVE <Probcause> informationalStatus(1000) 
        <Alarmtype> other (1) <Polarity> 
        (2) 
        "
	  ::= { pm10010r100AlmsynthAlm2 1 }



--- *********************************************************
---     TABLE for the pm10010r100AlmsynthAlmPort articles
--- *********************************************************

pm10010r100AlmsynthAlmPortTable OBJECT-TYPE
	SYNTAX  SEQUENCE OF Pm10010r100AlmsynthAlmPortEntry
	MAX-ACCESS not-accessible
	STATUS current
	DESCRIPTION
        "
        List of pm10010r100AlmsynthAlmPort 
        Article
        "
	::= { pm10010r100AlmClientCrit 8 }


pm10010r100AlmsynthAlmPortEntry OBJECT-TYPE
	SYNTAX Pm10010r100AlmsynthAlmPortEntry
	MAX-ACCESS not-accessible
	STATUS current
	DESCRIPTION
        "
        Row definition for the pm10010r100AlmsynthAlmPort 
        table
        "
	INDEX   { pm10010r100AlmsynthAlmPortIndex }
	::= { pm10010r100AlmsynthAlmPortTable 1 }


Pm10010r100AlmsynthAlmPortEntry ::=
	SEQUENCE {
	pm10010r100AlmsynthAlmPortIndex
		INTEGER,
	pm10010r100AlmUpCsfPortn
		EkiOnOff,
	pm10010r100AlmFailAccPortn
		EkiOnOff,
	pm10010r100AlmSfpDdmAlmPortn
		EkiOnOff,
	pm10010r100AlmSfpDdmWarningPortn
		EkiOnOff,
	pm10010r100AlmDwCaisPortn
		EkiOnOff,
	pm10010r100AlmClientRemoteOosPortn
		EkiOnOff,
	pm10010r100AlmClientLocalOosPortn
		EkiOnOff,
	pm10010r100AlmDwLsdPortn
		EkiOnOff,
	pm10010r100AlmHwFailAccPortn
		EkiOnOff,
	pm10010r100AlmDdmAbsentPortn
		EkiOnOff,
	pm10010r100AlmSfpAbsentPortn
		EkiOnOff
	}


pm10010r100AlmsynthAlmPortIndex OBJECT-TYPE
	SYNTAX  INTEGER(0..128)
	MAX-ACCESS  read-only
	STATUS current
	DESCRIPTION
        "
        Index definition for the pm10010r100AlmsynthAlmPort 
        table
        "
	::= { pm10010r100AlmsynthAlmPortEntry 1 }


pm10010r100AlmUpCsfPortn OBJECT-TYPE
	SYNTAX  EkiOnOff
	MAX-ACCESS read-only
	STATUS current
	DESCRIPTION
        "
        Client Signal Fail Inserted :This 
        OID indicates a CSF has been inserted 
        in the upstream client port. <Help> 
        This status indicates if a Client 
        Signal Fail is currently inserted 
        on the line signal for this client 
        port <Condtype> UP_CSF_1 <Probcause> 
        informationalStatus(1000) <Alarmtype> 
        other (1) <Polarity> (2) 
        "
	::= { pm10010r100AlmsynthAlmPortEntry 17 }


pm10010r100AlmFailAccPortn OBJECT-TYPE
	SYNTAX  EkiOnOff
	MAX-ACCESS read-only
	STATUS current
	DESCRIPTION
        "
        Client Access Fail :This OID indicates 
        a failure on the Client port <Help> 
        This alarm indicates a failure
         on the Client port <Condtype>
         FAIL_ACC_1 <Probcause> equipmentMalfunction 
        (16) <Alarmtype> synthesisAlarm 
        (12)  <Polarity> (2) 
        "
	::= { pm10010r100AlmsynthAlmPortEntry 13 }


pm10010r100AlmSfpDdmAlmPortn OBJECT-TYPE
	SYNTAX  EkiOnOff
	MAX-ACCESS read-only
	STATUS current
	DESCRIPTION
        "
        Alarm On Client Trscv DDM :This 
        OID indicates an alarm is being 
        received from the Client Transceiver 
        DDM <Help> This alarm indicates 
        if a DDM Alarm has been detected 
        on the client transceiver <Condtype> 
        SFP_DDM_ALM_1 <Probcause> inputOutputDeviceError 
        (24) <Alarmtype> synthesisAlarm 
        (12)  <Polarity> (2) 
        "
	::= { pm10010r100AlmsynthAlmPortEntry 11 }


pm10010r100AlmSfpDdmWarningPortn OBJECT-TYPE
	SYNTAX  EkiOnOff
	MAX-ACCESS read-only
	STATUS current
	DESCRIPTION
        "
        Warning On Client Trscv DDM :This 
        OID indicates a warning is being 
        received from the Client Transceiver 
        DDM <Help> This alarm indicates 
        if a DDM Warning has been detected 
        on the client transceiver <Condtype> 
        SFP_DDM_WARNING_1 <Probcause> inputOutputDeviceError 
        (24) <Alarmtype> synthesisAlarm 
        (12)  <Polarity> (2) 
        "
	::= { pm10010r100AlmsynthAlmPortEntry 10 }


pm10010r100AlmDwCaisPortn OBJECT-TYPE
	SYNTAX  EkiOnOff
	MAX-ACCESS read-only
	STATUS current
	DESCRIPTION
        "
        Client AIS Inserted :This OID
         indicates a CAIS has been inserted 
        on the output client port. <Help> 
        This status indicates if a Client 
        Alarm Indication Signal is currently 
        inserted on the client interface 
        <Condtype> DW_CAIS_1 <Probcause> 
        informationalStatus(1000) <Alarmtype> 
        other (1) <Polarity> (2) 
        "
	::= { pm10010r100AlmsynthAlmPortEntry 9 }


pm10010r100AlmClientRemoteOosPortn OBJECT-TYPE
	SYNTAX  EkiOnOff
	MAX-ACCESS read-only
	STATUS current
	DESCRIPTION
        "
        Remote Client Port In Service
         :This OID indicates that the remote 
        Client port is In Service (1) or 
        Out of Service (2) <Help> This
         status indicates if the remote 
        client port is in service <Condtype> 
        CLIENT_REMOTE_OOS <Probcause> informationalStatus(1000) 
        <Alarmtype> other (1) <Polarity> 
        (2) 
        "
	::= { pm10010r100AlmsynthAlmPortEntry 8 }


pm10010r100AlmClientLocalOosPortn OBJECT-TYPE
	SYNTAX  EkiOnOff
	MAX-ACCESS read-only
	STATUS current
	DESCRIPTION
        "
        Local Client Port In Service :This 
        OID indicates that the local Client 
        port is In Service (1) or Out of 
        Service (2) <Help> This status
         indicates if the local client
         port is in service <Condtype>
         CLIENT_LOCAL_OOS <Probcause> informationalStatus(1000) 
        <Alarmtype> other (1) <Polarity> 
        (2) 
        "
	::= { pm10010r100AlmsynthAlmPortEntry 7 }


pm10010r100AlmDwLsdPortn OBJECT-TYPE
	SYNTAX  EkiOnOff
	MAX-ACCESS read-only
	STATUS current
	DESCRIPTION
        "
        Client Trscv Laser Shutdown :This 
        OID indicates the Client transceiver 
        laser is shutdown <Help> This status 
        indicates if the client transceiver 
        laser is shutdown <Condtype> DW_LSD_1 
        <Probcause> other (1) <Alarmtype> 
        equipmentAlarm (5) <Polarity> (2) 
        "
	::= { pm10010r100AlmsynthAlmPortEntry 6 }


pm10010r100AlmHwFailAccPortn OBJECT-TYPE
	SYNTAX  EkiOnOff
	MAX-ACCESS read-only
	STATUS current
	DESCRIPTION
        "
        Client HW Fail :This OID indicates 
        a failure on client port, most
         probably caused by a HW issue. 
        <Help> This alarm indicates a failure 
        on client port, most probably caused 
        by a HW issue. <Condtype> HW_FAIL_ACC_1 
        <Probcause> equipmentMalfunction 
        (16) <Alarmtype> synthesisAlarm 
        (12)  <Polarity> (2) 
        "
	::= { pm10010r100AlmsynthAlmPortEntry 5 }


pm10010r100AlmDdmAbsentPortn OBJECT-TYPE
	SYNTAX  EkiOnOff
	MAX-ACCESS read-only
	STATUS current
	DESCRIPTION
        "
        DDM Supported On Client Trscv
         :This OID indicates that the Client 
        transceiver supports the Digital 
        Diagnostic Monitoring function
         <Help> This status indicates if 
        the client transceiver includes 
        the DDM feature <Condtype> DDM_ABSENT_1 
        <Probcause> informationalStatus(1000) 
        <Alarmtype> other (1) <Polarity> 
        (2) 
        "
	::= { pm10010r100AlmsynthAlmPortEntry 3 }


pm10010r100AlmSfpAbsentPortn OBJECT-TYPE
	SYNTAX  EkiOnOff
	MAX-ACCESS read-only
	STATUS current
	DESCRIPTION
        "
        Client Optical Module Absent :This 
        OID indicates that the Transceiver 
        is not present in the client port. 
        <Help> This alarm indicates if
         the client transceiver is not
         plugged <Condtype> SFP_ABSENT_1 
        <Probcause> inputOutputDeviceError 
        (24) <Alarmtype> equipmentAlarm 
        (5) <Polarity> (2) <Event> ObjectCDINV
        "
	::= { pm10010r100AlmsynthAlmPortEntry 2 }


--- *********************************************************
---     TABLE for the pm10010r100AlmsynthAlmLine articles
--- *********************************************************

pm10010r100AlmsynthAlmLineTable OBJECT-TYPE
	SYNTAX  SEQUENCE OF Pm10010r100AlmsynthAlmLineEntry
	MAX-ACCESS not-accessible
	STATUS current
	DESCRIPTION
        "
        List of pm10010r100AlmsynthAlmLine 
        Article
        "
	::= { pm10010r100AlmLineCrit 24 }


pm10010r100AlmsynthAlmLineEntry OBJECT-TYPE
	SYNTAX Pm10010r100AlmsynthAlmLineEntry
	MAX-ACCESS not-accessible
	STATUS current
	DESCRIPTION
        "
        Row definition for the pm10010r100AlmsynthAlmLine 
        table
        "
	INDEX   { pm10010r100AlmsynthAlmLineIndex }
	::= { pm10010r100AlmsynthAlmLineTable 1 }


Pm10010r100AlmsynthAlmLineEntry ::=
	SEQUENCE {
	pm10010r100AlmsynthAlmLineIndex
		INTEGER,
	pm10010r100AlmLineActivePortn
		EkiOnOff,
	pm10010r100AlmLineFailPortn
		EkiOnOff,
	pm10010r100AlmLineDdmAlmPortn
		EkiOnOff,
	pm10010r100AlmLineDdmWarningPortn
		EkiOnOff,
	pm10010r100AlmUpRdiInsPortn
		EkiOnOff,
	pm10010r100AlmLineLocalOosPortn
		EkiOnOff,
	pm10010r100AlmXfpTxOffPortn
		EkiOnOff,
	pm10010r100AlmLineHwFailPortn
		EkiOnOff,
	pm10010r100AlmXfpInitNotComplPortn
		EkiOnOff,
	pm10010r100AlmXfpAbsentPortn
		EkiOnOff
	}


pm10010r100AlmsynthAlmLineIndex OBJECT-TYPE
	SYNTAX  INTEGER(0..128)
	MAX-ACCESS  read-only
	STATUS current
	DESCRIPTION
        "
        Index definition for the pm10010r100AlmsynthAlmLine 
        table
        "
	::= { pm10010r100AlmsynthAlmLineEntry 1 }


pm10010r100AlmLineActivePortn OBJECT-TYPE
	SYNTAX  EkiOnOff
	MAX-ACCESS read-only
	STATUS current
	DESCRIPTION
        "
        Line Active :This OID indicates 
        whether the line is active or standby. 
        <Help> This status indicates whether 
        the line is active or standby.
         <Condtype> LINE_ACTIVE <Probcause> 
        informationalStatus(1000) <Alarmtype> 
        other (1) <Polarity> (2) 
        "
	::= { pm10010r100AlmsynthAlmLineEntry 17 }


pm10010r100AlmLineFailPortn OBJECT-TYPE
	SYNTAX  EkiOnOff
	MAX-ACCESS read-only
	STATUS current
	DESCRIPTION
        "
        Line Port Failure :This OID indicates 
        a failure on the line port <Help> 
        This alarm indicates a failure
         on the line port <Condtype> LINE_FAIL 
        <Probcause> equipmentMalfunction 
        (16) <Alarmtype> synthesisAlarm 
        (12)  <Polarity> (2) 
        "
	::= { pm10010r100AlmsynthAlmLineEntry 13 }


pm10010r100AlmLineDdmAlmPortn OBJECT-TYPE
	SYNTAX  EkiOnOff
	MAX-ACCESS read-only
	STATUS current
	DESCRIPTION
        "
        Alarm On Line Optical Module DDM 
        :This OID indicates an alarm is 
        present coming out of Line transceiver 
        DDM <Help> This alarm indicates 
        if a DDM Alarm has been detected 
        on the line transceiver <Condtype> 
        LINE_DDM_ALM <Probcause> inputOutputDeviceError 
        (24) <Alarmtype> synthesisAlarm 
        (12)  <Polarity> (2) 
        "
	::= { pm10010r100AlmsynthAlmLineEntry 11 }


pm10010r100AlmLineDdmWarningPortn OBJECT-TYPE
	SYNTAX  EkiOnOff
	MAX-ACCESS read-only
	STATUS current
	DESCRIPTION
        "
        Warning On Line Optical Module 
        DDM :This OID indicates a warning 
        is present coming out of Line transceiver 
        DDM <Help> This alarm indicates 
        if a DDM Warning has been detected 
        on the line transceiver <Condtype> 
        LINE_DDM_WARNING <Probcause> inputOutputDeviceError 
        (24) <Alarmtype> synthesisAlarm 
        (12)  <Polarity> (2) 
        "
	::= { pm10010r100AlmsynthAlmLineEntry 10 }


pm10010r100AlmUpRdiInsPortn OBJECT-TYPE
	SYNTAX  EkiOnOff
	MAX-ACCESS read-only
	STATUS current
	DESCRIPTION
        "
        MS-RDI/L-RDI Inserted On Line
         :This OID indicates an upstream 
        MS-RDI/L-RDI has been inserted
         in the outgoing 10 Gb/s SDH/SONET 
        signal. <Help> This status indicates 
        if a MS-RDI/L-RDI is currently
         inserted on the line interface. 
        <Condtype> UP_RDI_INS <Probcause> 
        informationalStatus(1000) <Alarmtype> 
        other (1) <Polarity> (2) 
        "
	::= { pm10010r100AlmsynthAlmLineEntry 9 }


pm10010r100AlmLineLocalOosPortn OBJECT-TYPE
	SYNTAX  EkiOnOff
	MAX-ACCESS read-only
	STATUS current
	DESCRIPTION
        "
        Line Port In Service :This OID 
        indicates that the Line port is 
        In Service (1) of Out or Service 
        (2) <Help> This status indicates 
        if the line port is in service
         <Condtype> LINE_LOCAL_OOS <Probcause> 
        informationalStatus(1000) <Alarmtype> 
        other (1) <Polarity> (2) 
        "
	::= { pm10010r100AlmsynthAlmLineEntry 7 }


pm10010r100AlmXfpTxOffPortn OBJECT-TYPE
	SYNTAX  EkiOnOff
	MAX-ACCESS read-only
	STATUS current
	DESCRIPTION
        "
        Line Trscv Laser Shutdown :This 
        OID indicates the Line transceiver 
        laser is shutdown <Help> This status 
        indicates if the Line transceiver 
        laser is shutdown <Condtype> XFP_TX_OFF 
        <Probcause> other (1) <Alarmtype> 
        equipmentAlarm (5) <Polarity> (2) 
        "
	::= { pm10010r100AlmsynthAlmLineEntry 6 }


pm10010r100AlmLineHwFailPortn OBJECT-TYPE
	SYNTAX  EkiOnOff
	MAX-ACCESS read-only
	STATUS current
	DESCRIPTION
        "
        Line Port HW Failure :This OID 
        indicates a failure on line port, 
        most probably caused by a HW issue 
        <Help> This alarm indicates a failure 
        on line port, most probably caused 
        by a HW issue <Condtype> LINE_HW_FAIL 
        <Probcause> equipmentMalfunction 
        (16) <Alarmtype> synthesisAlarm 
        (12)  <Polarity> (2) 
        "
	::= { pm10010r100AlmsynthAlmLineEntry 5 }


pm10010r100AlmXfpInitNotComplPortn OBJECT-TYPE
	SYNTAX  EkiOnOff
	MAX-ACCESS read-only
	STATUS current
	DESCRIPTION
        "
        Line Optical Module Ready :This 
        OID indicates that the optical
         interface is not operational.
         <Help> This status indicates if 
        the line transceiver has been correctly 
        initialized <Condtype> XFP_INIT_NOT_COMPL 
        <Probcause> equipmentMalfunction 
        (16) <Alarmtype> equipmentAlarm 
        (5) <Polarity> (2) 
        "
	::= { pm10010r100AlmsynthAlmLineEntry 3 }


pm10010r100AlmXfpAbsentPortn OBJECT-TYPE
	SYNTAX  EkiOnOff
	MAX-ACCESS read-only
	STATUS current
	DESCRIPTION
        "
        Line Optical Module Absent :This 
        OID indicates that the line optical 
        interface is not present. <Help> 
        This alarm indicates if the line 
        transceiver is not plugged <Condtype> 
        XFP_ABSENT <Probcause> inputOutputDeviceError 
        (24) <Alarmtype> equipmentAlarm 
        (5) <Polarity> (2) 
        "
	::= { pm10010r100AlmsynthAlmLineEntry 2 }


--- *****************************************************
---     LEAF for the clientModuleState article
--- *****************************************************
pm10010r100AlmclientModuleState OBJECT IDENTIFIER ::= { pm10010r100AlmOtherCrit 40 }




pm10010r100AlmCfpHighPowerDown OBJECT-TYPE
	  SYNTAX EkiOnOff
	  MAX-ACCESS read-only
	  STATUS current
	  DESCRIPTION
        "
        Client Trscv High Power Down :This 
        OID indicates the Client Trscv
         is entering Low Power state <Help> 
        Status indicating the Client Trscv 
        is entering Low Power state <Condtype> 
        CFP_HIGH_POWER_DOWN <Probcause> 
        informationalStatus(1000) <Alarmtype> 
        other (1) <Polarity> (2) 
        "
	  ::= { pm10010r100AlmclientModuleState 9 }



pm10010r100AlmCfpTxTurnOff OBJECT-TYPE
	  SYNTAX EkiOnOff
	  MAX-ACCESS read-only
	  STATUS current
	  DESCRIPTION
        "
        Client Trscv Laser Turn Off :This 
        OID indicates the Client Trscv
         is turning off its laser <Help> 
        Status indicating the Client Trscv 
        is turning off its laser <Condtype> 
        CFP_TX_TURN_OFF <Probcause> informationalStatus(1000) 
        <Alarmtype> other (1) <Polarity> 
        (2) 
        "
	  ::= { pm10010r100AlmclientModuleState 8 }



pm10010r100AlmCfpFault OBJECT-TYPE
	  SYNTAX EkiOnOff
	  MAX-ACCESS read-only
	  STATUS current
	  DESCRIPTION
        "
        Client Trscv Fault :This OID indicates 
        the Client Trscv is in Fault state 
        <Help> Status indicating the Client 
        Trscv is in Fault state <Condtype> 
        CFP_FAULT <Probcause> informationalStatus(1000) 
        <Alarmtype> other (1) <Polarity> 
        (2) 
        "
	  ::= { pm10010r100AlmclientModuleState 7 }



pm10010r100AlmCfpReady OBJECT-TYPE
	  SYNTAX EkiOnOff
	  MAX-ACCESS read-only
	  STATUS current
	  DESCRIPTION
        "
        Client Trscv Ready :This OID indicates 
        the Client Trscv is ready to operate 
        <Help> Status indicating the Client 
        Trscv is ready to operate <Condtype> 
        CFP_READY <Probcause> informationalStatus(1000) 
        <Alarmtype> other (1) <Polarity> 
        (2) 
        "
	  ::= { pm10010r100AlmclientModuleState 6 }



pm10010r100AlmCfpTxTurnOn OBJECT-TYPE
	  SYNTAX EkiOnOff
	  MAX-ACCESS read-only
	  STATUS current
	  DESCRIPTION
        "
        Client Trscv Laser Turn On :This 
        OID indicates the Client Trscv
         is turning on its laser <Help> 
        Status indicating the Client Trscv 
        is turning on its laser <Condtype> 
        CFP_TX_TURN_ON <Probcause> informationalStatus(1000) 
        <Alarmtype> other (1) <Polarity> 
        (2) 
        "
	  ::= { pm10010r100AlmclientModuleState 5 }



pm10010r100AlmCfpTxOff OBJECT-TYPE
	  SYNTAX EkiOnOff
	  MAX-ACCESS read-only
	  STATUS current
	  DESCRIPTION
        "
        Client Trscv Laser Shutdown :This 
        OID indicates the Client Trscv
         Laser is OFF <Help> Status indicating 
        the Client Trscv Laser is OFF <Condtype> 
        CFP_TX_OFF <Probcause> informationalStatus(1000) 
        <Alarmtype> other (1) <Polarity> 
        (2) 
        "
	  ::= { pm10010r100AlmclientModuleState 4 }



pm10010r100AlmCfpHighPowerUp OBJECT-TYPE
	  SYNTAX EkiOnOff
	  MAX-ACCESS read-only
	  STATUS current
	  DESCRIPTION
        "
        Client Trscv High Power Up :This 
        OID indicates the Client Trscv
         is leaving Low Power state <Help> 
        Status indicating the Client Trscv 
        is leaving Low Power state <Condtype> 
        CFP_HIGH_POWER_UP <Probcause> informationalStatus(1000) 
        <Alarmtype> other (1) <Polarity> 
        (2) 
        "
	  ::= { pm10010r100AlmclientModuleState 3 }



pm10010r100AlmCfpLowPower OBJECT-TYPE
	  SYNTAX EkiOnOff
	  MAX-ACCESS read-only
	  STATUS current
	  DESCRIPTION
        "
        Client Trscv Low Power :This OID 
        indicates the Client Trscv is in 
        low power state <Help> Status indicating 
        the Client Trscv is in low power 
        state <Condtype> CFP_LOW_POWER
         <Probcause> informationalStatus(1000) 
        <Alarmtype> other (1) <Polarity> 
        (2) 
        "
	  ::= { pm10010r100AlmclientModuleState 2 }



pm10010r100AlmCfpInitialize OBJECT-TYPE
	  SYNTAX EkiOnOff
	  MAX-ACCESS read-only
	  STATUS current
	  DESCRIPTION
        "
        Client Trscv Initialize :This
         OID indicates the Client Trscv 
        initialization is in progress <Help> 
        Status indicating the Client Trscv 
        initialization is in progress <Condtype> 
        CFP_INITIALIZE <Probcause> informationalStatus(1000) 
        <Alarmtype> other (1) <Polarity> 
        (2) 
        "
	  ::= { pm10010r100AlmclientModuleState 1 }



--- *****************************************************
---     LEAF for the clientModuleGeneralStatus article
--- *****************************************************
pm10010r100AlmclientModuleGeneralStatus OBJECT IDENTIFIER ::= { pm10010r100AlmOtherCrit 41 }




pm10010r100AlmCfpHwInterlock OBJECT-TYPE
	  SYNTAX EkiOnOff
	  MAX-ACCESS read-only
	  STATUS current
	  DESCRIPTION
        "
        Client Trscv Hardware Interlock 
        :This OID indicates the Client
         Trscv power is higher than the 
        cooling capacity <Help> Alarm indicating 
        the Client Trscv power is higher 
        than the cooling capacity <Condtype> 
        CFP_HW_INTERLOCK <Probcause> temperatureUnacceptable 
        (51) <Alarmtype> equipmentAlarm 
        (5) <Polarity> (2) 
        "
	  ::= { pm10010r100AlmclientModuleGeneralStatus 14 }



pm10010r100AlmCfpLossOfRefclk OBJECT-TYPE
	  SYNTAX EkiOnOff
	  MAX-ACCESS read-only
	  STATUS current
	  DESCRIPTION
        "
        Client Trscv Loss Of Ref Clock 
        :This OID indicates a Loss of Reference 
        clock is detected on the Client 
        Trscv <Help> Alarm indicating a 
        Loss of Reference clock is detected 
        on the Client Trscv <Condtype>
         CFP_LOSS_OF_REFCLK <Probcause> 
        inputOutputDeviceError (24) <Alarmtype> 
        equipmentAlarm (5) <Polarity> (2) 
        "
	  ::= { pm10010r100AlmclientModuleGeneralStatus 11 }



pm10010r100AlmCfpTxJitterPllLol OBJECT-TYPE
	  SYNTAX EkiOnOff
	  MAX-ACCESS read-only
	  STATUS current
	  DESCRIPTION
        "
        Client Trscv Tx Jitter PLL Loss 
        Of Lock :This OID indicates a Tx 
        Jitter PLL Loss of Lock is dtected 
        on the Client Trscv <Help> Alarm 
        indicating a Tx Jitter PLL Loss 
        of Lock is dtected on the Client 
        Trscv <Condtype> CFP_TX_JITTER_PLL_LOL 
        <Probcause> inputOutputDeviceError 
        (24) <Alarmtype> equipmentAlarm 
        (5) <Polarity> (2) 
        "
	  ::= { pm10010r100AlmclientModuleGeneralStatus 10 }



pm10010r100AlmCfpTxCmuLol OBJECT-TYPE
	  SYNTAX EkiOnOff
	  MAX-ACCESS read-only
	  STATUS current
	  DESCRIPTION
        "
        Client Trscv CMU Loss Of Lock
         :This OID indicates a Clock Multiplier 
        Unit Loss of Lock is detected on 
        the Client Trscv <Help> Alarm indicating 
        a Clock Multiplier Unit Loss of 
        Lock is detected on the Client
         Trscv <Condtype> CFP_TX_CMU_LOL 
        <Probcause> inputOutputDeviceError 
        (24) <Alarmtype> equipmentAlarm 
        (5) <Polarity> (2) 
        "
	  ::= { pm10010r100AlmclientModuleGeneralStatus 9 }



pm10010r100AlmCfpTxLosf OBJECT-TYPE
	  SYNTAX EkiOnOff
	  MAX-ACCESS read-only
	  STATUS current
	  DESCRIPTION
        "
        Client Trscv Loss Of Signal Functionality 
        :This OID indicates a Loss of Signal 
        functionality is detected on the 
        Client Trscv <Help> Alarm indicating 
        a Loss of Signal functionality
         is detected on the Client Trscv 
        <Condtype> CFP_TX_LOSF <Probcause> 
        lossOfSignal (30) <Alarmtype> equipmentAlarm 
        (5) <Polarity> (2) 
        "
	  ::= { pm10010r100AlmclientModuleGeneralStatus 8 }



pm10010r100AlmCfpTxHostLol OBJECT-TYPE
	  SYNTAX EkiOnOff
	  MAX-ACCESS read-only
	  STATUS current
	  DESCRIPTION
        "
        Client Trscv Tx Host Loss Of Lock 
        :This OID indicates of Loss of
         Lock is detected on the Client 
        Trscv Tx Host interface <Help>
         Alarm indicating of Loss of Lock 
        is detected on the Client Trscv 
        Tx Host interface <Condtype> CFP_TX_HOST_LOL 
        <Probcause> receiverFailure (42) 
        <Alarmtype> equipmentAlarm (5)
         <Polarity> (2) 
        "
	  ::= { pm10010r100AlmclientModuleGeneralStatus 7 }



pm10010r100AlmCfpRxLos OBJECT-TYPE
	  SYNTAX EkiOnOff
	  MAX-ACCESS read-only
	  STATUS current
	  DESCRIPTION
        "
        Client Trscv Loss Of Signal :This 
        OID indicates a Loss of Signal
         is detected on the Client Trscv 
        <Help> Alarm indicating a Loss
         of Signal is detected on the Client 
        Trscv <Condtype> CFP_RX_LOS <Probcause> 
        lossOfSignal (30) <Alarmtype> equipmentAlarm 
        (5) <Polarity> (2) 
        "
	  ::= { pm10010r100AlmclientModuleGeneralStatus 6 }



pm10010r100AlmCfpRxNetworkLol OBJECT-TYPE
	  SYNTAX EkiOnOff
	  MAX-ACCESS read-only
	  STATUS current
	  DESCRIPTION
        "
        Client Trscv Rx Network Loss Of 
        Lock :This OID indicates of Loss 
        of Lock is dected on the Client 
        Trscv Rx Network interface <Help> 
        Alarm indicating of Loss of Lock 
        is dected on the Client Trscv Rx 
        Network interface <Condtype> CFP_RX_NETWORK_LOL 
        <Probcause> receiverFailure (42) 
        <Alarmtype> equipmentAlarm (5)
         <Polarity> (2) 
        "
	  ::= { pm10010r100AlmclientModuleGeneralStatus 5 }



pm10010r100AlmCfpOutOfAlignment OBJECT-TYPE
	  SYNTAX EkiOnOff
	  MAX-ACCESS read-only
	  STATUS current
	  DESCRIPTION
        "
        Client Trscv Out Of Alignment
         :This OID indicates an Out of
         alignment on the Client Trscv
         Host Interface <Help> Alarm indicating 
        an Out of alignment on the Client 
        Trscv Host Interface <Condtype> 
        CFP_OUT_OF_ALIGNMENT <Probcause> 
        receiverFailure (42) <Alarmtype> 
        equipmentAlarm (5) <Polarity> (2) 
        "
	  ::= { pm10010r100AlmclientModuleGeneralStatus 4 }



--- *****************************************************
---     LEAF for the clientGlobalAlarmSummary article
--- *****************************************************
pm10010r100AlmclientGlobalAlarmSummary OBJECT IDENTIFIER ::= { pm10010r100AlmOtherCrit 42 }




pm10010r100AlmCfpGlobAlarmAssertion  OBJECT-TYPE
	  SYNTAX EkiOnOff
	  MAX-ACCESS read-only
	  STATUS current
	  DESCRIPTION
        "
        Client Trscv Global Alarm :This 
        OID indicates at least one  Fault 
        or Status is detected on the Client 
        Trscv module <Help> Synthesis alarm 
        indicating at least one Alarm,
         Warning, Fault or Status is detected 
        on the Client Trscv module <Condtype> 
        CFP_GLOB_ALARM_ASSERTION  <Probcause> 
        informationalStatus(1000) <Alarmtype> 
        other (1) <Polarity> (2) 
        "
	  ::= { pm10010r100AlmclientGlobalAlarmSummary 16 }



pm10010r100AlmCfpHostLaneFaultStatus  OBJECT-TYPE
	  SYNTAX EkiOnOff
	  MAX-ACCESS read-only
	  STATUS current
	  DESCRIPTION
        "
        Client Trscv Host Fault And Status 
        :This OID indicates at least one 
        Fault or Status is detected on
         the Client Trscv Host Interface 
        <Help> Synthesis alarm indicating 
        at least one Fault or Status is 
        detected on the Client Trscv Host 
        Interface <Condtype> CFP_HOST_LANE_FAULT_STATUS 
         <Probcause> informationalStatus(1000) 
        <Alarmtype> other (1) <Polarity> 
        (2) 
        "
	  ::= { pm10010r100AlmclientGlobalAlarmSummary 15 }



pm10010r100AlmCfpNetworkLaneFaultStatus  OBJECT-TYPE
	  SYNTAX EkiOnOff
	  MAX-ACCESS read-only
	  STATUS current
	  DESCRIPTION
        "
        Client Trscv Network Fault And 
        Status :This OID indicates at least 
        one Fault or Status is detected 
        on the Client Trscv Network Interface 
        <Help> Synthesis alarm indicating 
        at least one Fault or Status is 
        detected on the Client Trscv Network 
        Interface <Condtype> CFP_NETWORK_LANE_FAULT_STATUS 
         <Probcause> informationalStatus(1000) 
        <Alarmtype> other (1) <Polarity> 
        (2) 
        "
	  ::= { pm10010r100AlmclientGlobalAlarmSummary 14 }



pm10010r100AlmCfpNetworkLaneAlarmWarning1 OBJECT-TYPE
	  SYNTAX EkiOnOff
	  MAX-ACCESS read-only
	  STATUS current
	  DESCRIPTION
        "
        Client Trscv Network Alarm And 
        Warning 1 :This OID indicates at 
        least one DDM  is detected on the 
        Client Trscv Network Interface
         <Help> Synthesis alarm indicating 
        at least one DDM Alarm or DDM Warning 
        is detected on the Client Trscv 
        Network Interface <Condtype> CFP_NETWORK_LANE_ALARM_WARNING_1 
        <Probcause> informationalStatus(1000) 
        <Alarmtype> other (1) <Polarity> 
        (2) 
        "
	  ::= { pm10010r100AlmclientGlobalAlarmSummary 13 }



pm10010r100AlmCfpModuleAlarmWarning2 OBJECT-TYPE
	  SYNTAX EkiOnOff
	  MAX-ACCESS read-only
	  STATUS current
	  DESCRIPTION
        "
        Client Trscv Module Alarm And
         Warning 2 :This OID indicates
         at least one DDM is detected on 
        the Client Trscv module <Help>
         Synthesis alarm indicating at
         least one DDM Alarm or DDM Warning 
        is detected on the Client Trscv 
        module <Condtype> CFP_MODULE_ALARM_WARNING_2 
        <Probcause> informationalStatus(1000) 
        <Alarmtype> other (1) <Polarity> 
        (2) 
        "
	  ::= { pm10010r100AlmclientGlobalAlarmSummary 12 }



pm10010r100AlmCfpModuleAlarmWarning1  OBJECT-TYPE
	  SYNTAX EkiOnOff
	  MAX-ACCESS read-only
	  STATUS current
	  DESCRIPTION
        "
        Client Trscv Module Alarm And
         Warning 1 :This OID indicates
         at least one DDM  This OID is
         detected on the Client Trscv module 
        <Help> Synthesis alarm indicating 
        at least one DDM Alarm or DDM Warning 
        is detected on the Client Trscv 
        module <Condtype> CFP_MODULE_ALARM_WARNING_1 
         <Probcause> informationalStatus(1000) 
        <Alarmtype> other (1) <Polarity> 
        (2) 
        "
	  ::= { pm10010r100AlmclientGlobalAlarmSummary 11 }



pm10010r100AlmCfpModuleFault  OBJECT-TYPE
	  SYNTAX EkiOnOff
	  MAX-ACCESS read-only
	  STATUS current
	  DESCRIPTION
        "
        Client Trscv Module Fault :This 
        OID indicates at least one Fault 
        is detected on the Client Trscv 
        module <Help> Synthesis alarm indicating 
        at least one Fault is detected
         on the Client Trscv module <Condtype> 
        CFP_MODULE_FAULT  <Probcause> informationalStatus(1000) 
        <Alarmtype> other (1) <Polarity> 
        (2) 
        "
	  ::= { pm10010r100AlmclientGlobalAlarmSummary 10 }



pm10010r100AlmCfpModuleGeneralStatus  OBJECT-TYPE
	  SYNTAX EkiOnOff
	  MAX-ACCESS read-only
	  STATUS current
	  DESCRIPTION
        "
        Client Trscv General Status :This 
        OID indicates the Client Trscv
         module general status <Help> Synthesis 
        alarm indicating the Client Trscv 
        module general status <Condtype> 
        CFP_MODULE_GENERAL_STATUS  <Probcause> 
        informationalStatus(1000) <Alarmtype> 
        other (1) <Polarity> (2) 
        "
	  ::= { pm10010r100AlmclientGlobalAlarmSummary 9 }



pm10010r100AlmCfpModuleState  OBJECT-TYPE
	  SYNTAX EkiOnOff
	  MAX-ACCESS read-only
	  STATUS current
	  DESCRIPTION
        "
        Client Trscv Module State :This 
        OID indicates the Client Trscv
         module state <Help> Synthesis
         alarm indicating the Client Trscv 
        module state <Condtype> CFP_MODULE_STATE 
         <Probcause> informationalStatus(1000) 
        <Alarmtype> other (1) <Polarity> 
        (2) 
        "
	  ::= { pm10010r100AlmclientGlobalAlarmSummary 8 }



pm10010r100AlmCfpNetworkLaneAlarmWarning2 OBJECT-TYPE
	  SYNTAX EkiOnOff
	  MAX-ACCESS read-only
	  STATUS current
	  DESCRIPTION
        "
        Client Trscv Network Alarm And 
        Warning 2 :This OID indicates at 
        least one DDM is detected on the 
        Client Trscv Network Interface
         <Help> Synthesis alarm indicating 
        at least one DDM Alarm or DDM Warning 
        is detected on the Client Trscv 
        Network Interface <Condtype> CFP_NETWORK_LANE_ALARM_WARNING_2 
        <Probcause> informationalStatus(1000) 
        <Alarmtype> other (1) <Polarity> 
        (2) 
        "
	  ::= { pm10010r100AlmclientGlobalAlarmSummary 7 }



pm10010r100AlmCfpSoftGlobAlarmTest  OBJECT-TYPE
	  SYNTAX EkiOnOff
	  MAX-ACCESS read-only
	  STATUS current
	  DESCRIPTION
        "
        Client Trscv Global Alarm SW Test 
        :This OID indicates the Client
         Trscv Global Alarm This OID is 
        raised by SW request for test purpose 
        <Help> Status indicating the Client 
        Trscv Global Alarm is raised by 
        SW request for test purpose <Condtype> 
        CFP_SOFT_GLOB_ALARM_TEST  <Probcause> 
        informationalStatus(1000) <Alarmtype> 
        other (1) <Polarity> (2) 
        "
	  ::= { pm10010r100AlmclientGlobalAlarmSummary 1 }



--- *****************************************************
---     LEAF for the msaModuleState article
--- *****************************************************
pm10010r100AlmmsaModuleState OBJECT IDENTIFIER ::= { pm10010r100AlmOtherCrit 46 }




pm10010r100AlmMsaHighPowerDown OBJECT-TYPE
	  SYNTAX EkiOnOff
	  MAX-ACCESS read-only
	  STATUS current
	  DESCRIPTION
        "
        Line Trscv High Power Down :This 
        OID indicates the Line Trscv is 
        entering Low Power state <Help> 
        Status indicating the Line Trscv 
        is entering Low Power state <Condtype> 
        MSA_HIGH_POWER_DOWN <Probcause> 
        informationalStatus(1000) <Alarmtype> 
        other (1) <Polarity> (2) 
        "
	  ::= { pm10010r100AlmmsaModuleState 9 }



pm10010r100AlmMsaTxTurnOff OBJECT-TYPE
	  SYNTAX EkiOnOff
	  MAX-ACCESS read-only
	  STATUS current
	  DESCRIPTION
        "
        Line Trscv Laser Turn Off :This 
        OID indicates the Line Trscv is 
        turning off its laser <Help> Status 
        indicating the Line Trscv is turning 
        off its laser <Condtype> MSA_TX_TURN_OFF 
        <Probcause> informationalStatus(1000) 
        <Alarmtype> other (1) <Polarity> 
        (2) 
        "
	  ::= { pm10010r100AlmmsaModuleState 8 }



pm10010r100AlmMsaFault OBJECT-TYPE
	  SYNTAX EkiOnOff
	  MAX-ACCESS read-only
	  STATUS current
	  DESCRIPTION
        "
        Line Trscv Fault :This OID indicates 
        the Line Trscv is in Fault state 
        <Help> Status indicating the Line 
        Trscv is in Fault state <Condtype> 
        MSA_FAULT <Probcause> informationalStatus(1000) 
        <Alarmtype> other (1) <Polarity> 
        (2) 
        "
	  ::= { pm10010r100AlmmsaModuleState 7 }



pm10010r100AlmMsaReady OBJECT-TYPE
	  SYNTAX EkiOnOff
	  MAX-ACCESS read-only
	  STATUS current
	  DESCRIPTION
        "
        Line Trscv Ready :This OID indicates 
        the Line Trscv is ready to operate 
        <Help> Status indicating the Line 
        Trscv is ready to operate <Condtype> 
        MSA_READY <Probcause> informationalStatus(1000) 
        <Alarmtype> other (1) <Polarity> 
        (2) 
        "
	  ::= { pm10010r100AlmmsaModuleState 6 }



pm10010r100AlmMsaTxTurnOn OBJECT-TYPE
	  SYNTAX EkiOnOff
	  MAX-ACCESS read-only
	  STATUS current
	  DESCRIPTION
        "
        Line Trscv Laser Turn On :This 
        OID indicates the Line Trscv is 
        turning on its laser <Help> Status 
        indicating the Line Trscv is turning 
        on its laser <Condtype> MSA_TX_TURN_ON 
        <Probcause> informationalStatus(1000) 
        <Alarmtype> other (1) <Polarity> 
        (2) 
        "
	  ::= { pm10010r100AlmmsaModuleState 5 }



pm10010r100AlmMsaTxOff OBJECT-TYPE
	  SYNTAX EkiOnOff
	  MAX-ACCESS read-only
	  STATUS current
	  DESCRIPTION
        "
        Line Trscv Laser Shutdown :This 
        OID indicates the Line Trscv Laser 
        is OFF <Help> Status indicating 
        the Line Trscv Laser is OFF <Condtype> 
        MSA_TX_OFF <Probcause> informationalStatus(1000) 
        <Alarmtype> other (1) <Polarity> 
        (2) 
        "
	  ::= { pm10010r100AlmmsaModuleState 4 }



pm10010r100AlmMsaHighPowerUp OBJECT-TYPE
	  SYNTAX EkiOnOff
	  MAX-ACCESS read-only
	  STATUS current
	  DESCRIPTION
        "
        Line Trscv High Power Up :This 
        OID indicates the Line Trscv is 
        leaving Low Power state <Help>
         Status indicating the Line Trscv 
        is leaving Low Power state <Condtype> 
        MSA_HIGH_POWER_UP <Probcause> informationalStatus(1000) 
        <Alarmtype> other (1) <Polarity> 
        (2) 
        "
	  ::= { pm10010r100AlmmsaModuleState 3 }



pm10010r100AlmMsaLowPower OBJECT-TYPE
	  SYNTAX EkiOnOff
	  MAX-ACCESS read-only
	  STATUS current
	  DESCRIPTION
        "
        Line Trscv Low Power :This OID 
        indicates the Line Trscv is in
         low power state <Help> Status
         indicating the Line Trscv is in 
        low power state <Condtype> MSA_LOW_POWER 
        <Probcause> informationalStatus(1000) 
        <Alarmtype> other (1) <Polarity> 
        (2) 
        "
	  ::= { pm10010r100AlmmsaModuleState 2 }



pm10010r100AlmMsaInitialize OBJECT-TYPE
	  SYNTAX EkiOnOff
	  MAX-ACCESS read-only
	  STATUS current
	  DESCRIPTION
        "
        Line Trscv Initialize :This OID 
        indicates the Line Trscv initialization 
        is in progress <Help> Status indicating 
        the Line Trscv initialization is 
        in progress <Condtype> MSA_INITIALIZE 
        <Probcause> informationalStatus(1000) 
        <Alarmtype> other (1) <Polarity> 
        (2) 
        "
	  ::= { pm10010r100AlmmsaModuleState 1 }



--- *****************************************************
---     LEAF for the msaModuleGeneralStatus article
--- *****************************************************
pm10010r100AlmmsaModuleGeneralStatus OBJECT IDENTIFIER ::= { pm10010r100AlmOtherCrit 47 }




pm10010r100AlmMsaHwInterlock OBJECT-TYPE
	  SYNTAX EkiOnOff
	  MAX-ACCESS read-only
	  STATUS current
	  DESCRIPTION
        "
        Line Trscv Hardware Interlock
         :This OID indicates the Line Trscv 
        power is higher than the cooling 
        capacity <Help> Alarm indicating 
        the Line Trscv power is higher
         than the cooling capacity <Condtype> 
        MSA_HW_INTERLOCK <Probcause> temperatureUnacceptable 
        (51) <Alarmtype> equipmentAlarm 
        (5) <Polarity> (2) 
        "
	  ::= { pm10010r100AlmmsaModuleGeneralStatus 14 }



pm10010r100AlmMsaLossOfRefclk OBJECT-TYPE
	  SYNTAX EkiOnOff
	  MAX-ACCESS read-only
	  STATUS current
	  DESCRIPTION
        "
        Line Trscv Loss Of Ref Clock :This 
        OID indicates a Loss of Reference 
        clock is detected on the Line Trscv 
        <Help> Alarm indicating a Loss
         of Reference clock is detected 
        on the Line Trscv <Condtype> MSA_LOSS_OF_REFCLK 
        <Probcause> inputOutputDeviceError 
        (24) <Alarmtype> equipmentAlarm 
        (5) <Polarity> (2) 
        "
	  ::= { pm10010r100AlmmsaModuleGeneralStatus 11 }



pm10010r100AlmMsaTxJitterPllLol OBJECT-TYPE
	  SYNTAX EkiOnOff
	  MAX-ACCESS read-only
	  STATUS current
	  DESCRIPTION
        "
        Line Trscv Tx Jitter PLL Loss
         Of Lock :This OID indicates a
         Tx Jitter PLL Loss of Lock is
         detected on the Line Trscv <Help> 
        Alarm indicating a Tx Jitter PLL 
        Loss of Lock is detected on the 
        Line Trscv <Condtype> MSA_TX_JITTER_PLL_LOL 
        <Probcause> inputOutputDeviceError 
        (24) <Alarmtype> equipmentAlarm 
        (5) <Polarity> (2) 
        "
	  ::= { pm10010r100AlmmsaModuleGeneralStatus 10 }



pm10010r100AlmMsaTxCmuLol OBJECT-TYPE
	  SYNTAX EkiOnOff
	  MAX-ACCESS read-only
	  STATUS current
	  DESCRIPTION
        "
        Line Trscv CMU Loss Of Lock :This 
        OID indicates a Clock Multiplier 
        Unit Loss of Lock is detected on 
        the Line Trscv <Help> Alarm indicating 
        a Clock Multiplier Unit Loss of 
        Lock is detected on the Line Trscv 
        <Condtype> MSA_TX_CMU_LOL <Probcause> 
        inputOutputDeviceError (24) <Alarmtype> 
        equipmentAlarm (5) <Polarity> (2) 
        "
	  ::= { pm10010r100AlmmsaModuleGeneralStatus 9 }



pm10010r100AlmMsaTxLosf OBJECT-TYPE
	  SYNTAX EkiOnOff
	  MAX-ACCESS read-only
	  STATUS current
	  DESCRIPTION
        "
        Line Trscv Loss Of Signal Functionality 
        :This OID indicates a Loss of Signal 
        functionality is detected on the 
        Line Trscv <Help> Alarm indicating 
        a Loss of Signal functionality
         is detected on the Line Trscv
         <Condtype> MSA_TX_LOSF <Probcause> 
        lossOfSignal (30) <Alarmtype> equipmentAlarm 
        (5) <Polarity> (2) 
        "
	  ::= { pm10010r100AlmmsaModuleGeneralStatus 8 }



pm10010r100AlmMsaTxHostLol OBJECT-TYPE
	  SYNTAX EkiOnOff
	  MAX-ACCESS read-only
	  STATUS current
	  DESCRIPTION
        "
        Line Trscv Tx Host Loss Of Lock 
        :This OID indicates of Loss of
         Lock is detected on the Line Trscv 
        Tx Host interface <Help> Alarm
         indicating of Loss of Lock is
         detected on the Line Trscv Tx
         Host interface <Condtype> MSA_TX_HOST_LOL 
        <Probcause> receiverFailure (42) 
        <Alarmtype> equipmentAlarm (5)
         <Polarity> (2) 
        "
	  ::= { pm10010r100AlmmsaModuleGeneralStatus 7 }



pm10010r100AlmMsaRxLos OBJECT-TYPE
	  SYNTAX EkiOnOff
	  MAX-ACCESS read-only
	  STATUS current
	  DESCRIPTION
        "
        Line Trscv Loss Of Signal :This 
        OID indicates a Loss of Signal
         is detected on the Line Trscv
         <Help> Alarm indicating a Loss 
        of Signal is detected on the Line 
        Trscv <Condtype> MSA_RX_LOS <Probcause> 
        lossOfSignal (30) <Alarmtype> equipmentAlarm 
        (5) <Polarity> (2) 
        "
	  ::= { pm10010r100AlmmsaModuleGeneralStatus 6 }



pm10010r100AlmMsaRxNetworkLol OBJECT-TYPE
	  SYNTAX EkiOnOff
	  MAX-ACCESS read-only
	  STATUS current
	  DESCRIPTION
        "
        Line Trscv Rx Network Loss Of
         Lock :This OID indicates of Loss 
        of Lock is detected on the Line 
        Trscv Rx Network interface <Help> 
        Alarm indicating of Loss of Lock 
        is detected on the Line Trscv Rx 
        Network interface <Condtype> MSA_RX_NETWORK_LOL 
        <Probcause> receiverFailure (42) 
        <Alarmtype> equipmentAlarm (5)
         <Polarity> (2) 
        "
	  ::= { pm10010r100AlmmsaModuleGeneralStatus 5 }



pm10010r100AlmMsaOutOfAlignment OBJECT-TYPE
	  SYNTAX EkiOnOff
	  MAX-ACCESS read-only
	  STATUS current
	  DESCRIPTION
        "
        Line Trscv Out Of Alignment :This 
        OID indicates an Out of alignment 
        on the Line Trscv Host Interface 
        <Help> Alarm indicating an Out
         of alignment on the Line Trscv 
        Host Interface <Condtype> MSA_OUT_OF_ALIGNMENT 
        <Probcause> receiverFailure (42) 
        <Alarmtype> equipmentAlarm (5)
         <Polarity> (2) 
        "
	  ::= { pm10010r100AlmmsaModuleGeneralStatus 4 }



--- *****************************************************
---     LEAF for the msaGlobalAlarmSummary article
--- *****************************************************
pm10010r100AlmmsaGlobalAlarmSummary OBJECT IDENTIFIER ::= { pm10010r100AlmOtherCrit 48 }




pm10010r100AlmMsaGlobAlarmAssertion  OBJECT-TYPE
	  SYNTAX EkiOnOff
	  MAX-ACCESS read-only
	  STATUS current
	  DESCRIPTION
        "
        Line Trscv Global Alarm :This
         OID indicates at least one Fault 
        or Status is detected on the Line 
        Trscv module <Help> Synthesis alarm 
        indicating at least one Alarm,
         Warning, Fault or Status is detected 
        on the Line Trscv module <Condtype> 
        MSA_GLOB_ALARM_ASSERTION  <Probcause> 
        informationalStatus(1000) <Alarmtype> 
        other (1) <Polarity> (2) 
        "
	  ::= { pm10010r100AlmmsaGlobalAlarmSummary 16 }



pm10010r100AlmMsaHostLaneFaultStatus  OBJECT-TYPE
	  SYNTAX EkiOnOff
	  MAX-ACCESS read-only
	  STATUS current
	  DESCRIPTION
        "
        Line Trscv Host Fault And Status 
        :This OID indicates at least one 
        Fault or Status is detected on
         the Line Trscv Host Interface
         <Help> Synthesis alarm indicating 
        at least one Fault or Status is 
        detected on the Line Trscv Host 
        Interface <Condtype> MSA_HOST_LANE_FAULT_STATUS 
         <Probcause> informationalStatus(1000) 
        <Alarmtype> other (1) <Polarity> 
        (2) 
        "
	  ::= { pm10010r100AlmmsaGlobalAlarmSummary 15 }



pm10010r100AlmMsaNetworkLaneFaultStatus  OBJECT-TYPE
	  SYNTAX EkiOnOff
	  MAX-ACCESS read-only
	  STATUS current
	  DESCRIPTION
        "
        Line Trscv Network Fault And Status 
        :This OID indicates at least one 
        Fault or Status is detected on
         the Line Trscv Network Interface 
        <Help> Synthesis alarm indicating 
        at least one Fault or Status is 
        detected on the Line Trscv Network 
        Interface <Condtype> MSA_NETWORK_LANE_FAULT_STATUS 
         <Probcause> informationalStatus(1000) 
        <Alarmtype> other (1) <Polarity> 
        (2) 
        "
	  ::= { pm10010r100AlmmsaGlobalAlarmSummary 14 }



pm10010r100AlmMsaNetworkLaneAlarmWarning1 OBJECT-TYPE
	  SYNTAX EkiOnOff
	  MAX-ACCESS read-only
	  STATUS current
	  DESCRIPTION
        "
        Line Trscv Network Alarm And Warning 
        1 :This OID indicates at least
         one DDM is detected on the Line 
        Trscv Network Interface <Help>
         Synthesis alarm indicating at
         least one DDM Alarm or DDM Warning 
        is detected on the Line Trscv Network 
        Interface <Condtype> MSA_NETWORK_LANE_ALARM_WARNING_1 
        <Probcause> informationalStatus(1000) 
        <Alarmtype> other (1) <Polarity> 
        (2) 
        "
	  ::= { pm10010r100AlmmsaGlobalAlarmSummary 13 }



pm10010r100AlmMsaModuleAlarmWarning2 OBJECT-TYPE
	  SYNTAX EkiOnOff
	  MAX-ACCESS read-only
	  STATUS current
	  DESCRIPTION
        "
        Line Trscv Module Alarm And Warning 
        2 :This OID indicates at least
         one DDM is detected on the Line 
        Trscv module <Help> Synthesis alarm 
        indicating at least one DDM Alarm 
        or DDM Warning is detected on the 
        Line Trscv module <Condtype> MSA_MODULE_ALARM_WARNING_2 
        <Probcause> informationalStatus(1000) 
        <Alarmtype> other (1) <Polarity> 
        (2) 
        "
	  ::= { pm10010r100AlmmsaGlobalAlarmSummary 12 }



pm10010r100AlmMsaModuleAlarmWarning1  OBJECT-TYPE
	  SYNTAX EkiOnOff
	  MAX-ACCESS read-only
	  STATUS current
	  DESCRIPTION
        "
        Line Trscv Module Alarm And Warning 
        1 :This OID indicates at least
         one DDM is detected on the Line 
        Trscv module <Help> Synthesis alarm 
        indicating at least one DDM Alarm 
        or DDM Warning is detected on the 
        Line Trscv module <Condtype> MSA_MODULE_ALARM_WARNING_1 
         <Probcause> informationalStatus(1000) 
        <Alarmtype> other (1) <Polarity> 
        (2) 
        "
	  ::= { pm10010r100AlmmsaGlobalAlarmSummary 11 }



pm10010r100AlmModuleFault  OBJECT-TYPE
	  SYNTAX EkiOnOff
	  MAX-ACCESS read-only
	  STATUS current
	  DESCRIPTION
        "
        Line Trscv Module Fault :This
         OID indicates at least one Fault 
        is detected on the Line Trscv module 
        <Help> Synthesis alarm indicating 
        at least one Fault is detected
         on the Line Trscv module <Condtype> 
        MODULE_FAULT  <Probcause> informationalStatus(1000) 
        <Alarmtype> other (1) <Polarity> 
        (2) 
        "
	  ::= { pm10010r100AlmmsaGlobalAlarmSummary 10 }



pm10010r100AlmMsaModuleGeneralStatus  OBJECT-TYPE
	  SYNTAX EkiOnOff
	  MAX-ACCESS read-only
	  STATUS current
	  DESCRIPTION
        "
        Line Trscv General Status :This 
        OID indicates the Line Trscv module 
        general <Help> Synthesis alarm
         indicating the Line Trscv module 
        general status <Condtype> MSA_MODULE_GENERAL_STATUS 
         <Probcause> informationalStatus(1000) 
        <Alarmtype> other (1) <Polarity> 
        (2) 
        "
	  ::= { pm10010r100AlmmsaGlobalAlarmSummary 9 }



pm10010r100AlmMsaModuleState  OBJECT-TYPE
	  SYNTAX EkiOnOff
	  MAX-ACCESS read-only
	  STATUS current
	  DESCRIPTION
        "
        Line Trscv Module State :This
         OID indicates the Line Trscv module 
        state <Help> Synthesis alarm indicating 
        the Line Trscv module state <Condtype> 
        MSA_MODULE_STATE  <Probcause> informationalStatus(1000) 
        <Alarmtype> other (1) <Polarity> 
        (2) 
        "
	  ::= { pm10010r100AlmmsaGlobalAlarmSummary 8 }



pm10010r100AlmMsaNetworkLaneAlarmWarning2 OBJECT-TYPE
	  SYNTAX EkiOnOff
	  MAX-ACCESS read-only
	  STATUS current
	  DESCRIPTION
        "
        Line Trscv Network Alarm And Warning 
        2 :This OID indicates at least
         one DDM This OID is detected on 
        the Line Trscv Network Interface 
        <Help> Synthesis alarm indicating 
        at least one DDM Alarm or DDM Warning 
        is detected on the Line Trscv Network 
        Interface <Condtype> MSA_NETWORK_LANE_ALARM_WARNING_2 
        <Probcause> informationalStatus(1000) 
        <Alarmtype> other (1) <Polarity> 
        (2) 
        "
	  ::= { pm10010r100AlmmsaGlobalAlarmSummary 7 }



pm10010r100AlmMsaNetworkHostAlarmStatus OBJECT-TYPE
	  SYNTAX EkiOnOff
	  MAX-ACCESS read-only
	  STATUS current
	  DESCRIPTION
        "
        Line Trscv Network/Host Alarm
         Status :This OID indicates the 
        state of the Network and Host interface 
        of the Line Trscv <Help> Synthesis 
        alarm indicating the alarm state 
        of the Network and Host interface 
        of the Line Trscv <Condtype> MSA_NETWORK_HOST_ALARM_STATUS 
        <Probcause> informationalStatus(1000) 
        <Alarmtype> other (1) <Polarity> 
        (2) 
        "
	  ::= { pm10010r100AlmmsaGlobalAlarmSummary 6 }



pm10010r100AlmMsaSoftGlobAlarmTest  OBJECT-TYPE
	  SYNTAX EkiOnOff
	  MAX-ACCESS read-only
	  STATUS current
	  DESCRIPTION
        "
        Line Trscv Global Alarm SW Test 
        :This OID indicates the Line Trscv 
        Global alarm This OID is raised 
        by SW request for test purpose
         <Help> Status indicating the Line 
        Trscv Global Alarm is raised by 
        SW request for test purpose <Condtype> 
        MSA_SOFT_GLOB_ALARM_TEST  <Probcause> 
        informationalStatus(1000) <Alarmtype> 
        other (1) <Polarity> (2) 
        "
	  ::= { pm10010r100AlmmsaGlobalAlarmSummary 1 }



--- *****************************************************
---     LEAF for the msaNetworkTxAlignment article
--- *****************************************************
pm10010r100AlmmsaNetworkTxAlignment OBJECT IDENTIFIER ::= { pm10010r100AlmOtherCrit 49 }




pm10010r100AlmNetTxLossOfAlignment OBJECT-TYPE
	  SYNTAX EkiOnOff
	  MAX-ACCESS read-only
	  STATUS current
	  DESCRIPTION
        "
        Line Trscv Network Tx Loss Of
         Alignment :This OID indicates
         a Tx Loss of Alignment is detected 
        on the Line Trscv Network interface 
        <Help> Alarm indicating a Tx Loss 
        of Alignment is detected on the 
        Line Trscv Network interface <Condtype> 
        NET_TX_LOSS_OF_ALIGNMENT <Probcause> 
        transmitterFailure (56) <Alarmtype> 
        equipmentAlarm (5) <Polarity> (2) 
        "
	  ::= { pm10010r100AlmmsaNetworkTxAlignment 16 }



pm10010r100AlmNetTxOutOfAlignment OBJECT-TYPE
	  SYNTAX EkiOnOff
	  MAX-ACCESS read-only
	  STATUS current
	  DESCRIPTION
        "
        Line Trscv Network Tx Out Of Alignment 
        :This OID indicates a Tx Out of 
        Alignment is detected on the Line 
        Trscv Network interface <Help>
         Alarm indicating a Tx Out of Alignment 
        is detected on the Line Trscv Network 
        interface <Condtype> NET_TX_OUT_OF_ALIGNMENT 
        <Probcause> transmitterFailure
         (56) <Alarmtype> equipmentAlarm 
        (5) <Polarity> (2) 
        "
	  ::= { pm10010r100AlmmsaNetworkTxAlignment 15 }



pm10010r100AlmNetTxCmuLockFault OBJECT-TYPE
	  SYNTAX EkiOnOff
	  MAX-ACCESS read-only
	  STATUS current
	  DESCRIPTION
        "
        Line Trscv Network Tx CMU Lock 
        Fault :This OID indicates a Tx
         Clock Multiplier Unit Lock Fault 
        is detected on the Line Trscv Network 
        interface <Help> Alarm indicating 
        a Tx Clock Multiplier Unit Lock 
        Fault is detected on the Line Trscv 
        Network interface <Condtype> NET_TX_CMU_LOCK_FAULT 
        <Probcause> transmitterFailure
         (56) <Alarmtype> equipmentAlarm 
        (5) <Polarity> (2) 
        "
	  ::= { pm10010r100AlmmsaNetworkTxAlignment 14 }



pm10010r100AlmNetTxReferenceClockFault OBJECT-TYPE
	  SYNTAX EkiOnOff
	  MAX-ACCESS read-only
	  STATUS current
	  DESCRIPTION
        "
        Line Trscv Network Tx Ref Clock 
        Fault :This OID indicates a Tx
         Reference Clock Fault is detected 
        on the Line Trscv Network interface 
        <Help> Alarm indicating a Tx Reference 
        Clock Fault is detected on the
         Line Trscv Network interface <Condtype> 
        NET_TX_REFERENCE_CLOCK_FAULT <Probcause> 
        transmitterFailure (56) <Alarmtype> 
        equipmentAlarm (5) <Polarity> (2) 
        "
	  ::= { pm10010r100AlmmsaNetworkTxAlignment 13 }



pm10010r100AlmNetTxTimingFault OBJECT-TYPE
	  SYNTAX EkiOnOff
	  MAX-ACCESS read-only
	  STATUS current
	  DESCRIPTION
        "
        Line Trscv Network Tx Timing Fault 
        :This OID indicates a Tx Timing 
        Fault is detected on the Line Trscv 
        Network interface <Help> Alarm
         indicating a Tx Timing Fault is 
        detected on the Line Trscv Network 
        interface <Condtype> NET_TX_TIMING_FAULT 
        <Probcause> transmitterFailure
         (56) <Alarmtype> equipmentAlarm 
        (5) <Polarity> (2) 
        "
	  ::= { pm10010r100AlmmsaNetworkTxAlignment 12 }



--- *****************************************************
---     LEAF for the msaNetworkRxAlignment article
--- *****************************************************
pm10010r100AlmmsaNetworkRxAlignment OBJECT IDENTIFIER ::= { pm10010r100AlmOtherCrit 50 }




pm10010r100AlmNetRxModemSyncDetectFault OBJECT-TYPE
	  SYNTAX EkiOnOff
	  MAX-ACCESS read-only
	  STATUS current
	  DESCRIPTION
        "
        Line Trscv Network Rx Modem Sync 
        Detect Fault :This OID indicates 
        a Rx Modem Synchronisation Detection 
        Fault is detected on the Line Trscv 
        Network interface <Help> Alarm
         indicating a Rx Modem Synchronisation 
        Detection Fault is detected on
         the Line Trscv Network interface 
        <Condtype> NET_RX_MODEM_SYNC_DETECT_FAULT 
        <Probcause> receiverFailure (42) 
        <Alarmtype> equipmentAlarm (5)
         <Polarity> (2) 
        "
	  ::= { pm10010r100AlmmsaNetworkRxAlignment 16 }



pm10010r100AlmNetRxModemLockFault OBJECT-TYPE
	  SYNTAX EkiOnOff
	  MAX-ACCESS read-only
	  STATUS current
	  DESCRIPTION
        "
        Line Trscv Network Rx Modem Lock 
        Fault :This OID indicates a Rx
         Modem Lock Fault is detected on 
        the Line Trscv Network interface 
        <Help> Alarm indicating a Rx Modem 
        Lock Fault is detected on the Line 
        Trscv Network interface <Condtype> 
        NET_RX_MODEM_LOCK_FAULT <Probcause> 
        receiverFailure (42) <Alarmtype> 
        equipmentAlarm (5) <Polarity> (2) 
        "
	  ::= { pm10010r100AlmmsaNetworkRxAlignment 15 }



pm10010r100AlmNetRxLossOfAlignment OBJECT-TYPE
	  SYNTAX EkiOnOff
	  MAX-ACCESS read-only
	  STATUS current
	  DESCRIPTION
        "
        Line Trscv Network Rx Loss Of
         Alignment :This OID indicates
         a Rx Loss of Alignment is detected 
        on the Line Trscv Network interface 
        <Help> Alarm indicating a Rx Loss 
        of Alignment is detected on the 
        Line Trscv Network interface <Condtype> 
        NET_RX_LOSS_OF_ALIGNMENT <Probcause> 
        receiverFailure (42) <Alarmtype> 
        equipmentAlarm (5) <Polarity> (2) 
        "
	  ::= { pm10010r100AlmmsaNetworkRxAlignment 14 }



pm10010r100AlmNetRxOutOfAlignment OBJECT-TYPE
	  SYNTAX EkiOnOff
	  MAX-ACCESS read-only
	  STATUS current
	  DESCRIPTION
        "
        Line Trscv Network Rx Out Of Alignment 
        :This OID indicates a Rx Out of 
        Alignment is detected on the Line 
        Trscv Network interface <Help>
         Alarm indicating a Rx Out of Alignment 
        is detected on the Line Trscv Network 
        interface <Condtype> NET_RX_OUT_OF_ALIGNMENT 
        <Probcause> receiverFailure (42) 
        <Alarmtype> equipmentAlarm (5)
         <Polarity> (2) 
        "
	  ::= { pm10010r100AlmmsaNetworkRxAlignment 13 }



pm10010r100AlmNetRxTimingFault OBJECT-TYPE
	  SYNTAX EkiOnOff
	  MAX-ACCESS read-only
	  STATUS current
	  DESCRIPTION
        "
        Line Trscv Network Rx Timing Fault 
        :This OID indicates a Rx Timing 
        Fault is detected on the Line Trscv 
        Network interface <Help> Alarm
         indicating a Rx Timing Fault is 
        detected on the Line Trscv Network 
        interface <Condtype> NET_RX_TIMING_FAULT 
        <Probcause> receiverFailure (42) 
        <Alarmtype> equipmentAlarm (5)
         <Polarity> (2) 
        "
	  ::= { pm10010r100AlmmsaNetworkRxAlignment 12 }



--- *****************************************************
---     LEAF for the msaNetworkHostNetworkAlarmSummary article
--- *****************************************************
pm10010r100AlmmsaNetworkHostNetworkAlarmSummary OBJECT IDENTIFIER ::= { pm10010r100AlmOtherCrit 51 }




pm10010r100AlmHostTxOtnStatus OBJECT-TYPE
	  SYNTAX EkiOnOff
	  MAX-ACCESS read-only
	  STATUS current
	  DESCRIPTION
        "
        Line Trscv Host Tx OTN :This OID 
        indicates a Tx OTN Fault is detected 
        on the Line Trscv Host interface 
        <Help> Synthesis Alarm indicating 
        a Tx OTN Fault is detected on the 
        Line Trscv Host interface <Condtype> 
        HOST_TX_OTN_STATUS <Probcause>
         informationalStatus(1000) <Alarmtype> 
        other (1) <Polarity> (2) 
        "
	  ::= { pm10010r100AlmmsaNetworkHostNetworkAlarmSummary 16 }



pm10010r100AlmHostTxAlignment OBJECT-TYPE
	  SYNTAX EkiOnOff
	  MAX-ACCESS read-only
	  STATUS current
	  DESCRIPTION
        "
        Line Trscv Host Tx Alignment :This 
        OID indicates a Tx Alignment Fault 
        is detected on the Line Trscv Host 
        interface <Help> Synthesis Alarm 
        indicating a Tx Alignment Fault 
        is detected on the Line Trscv Host 
        interface <Condtype> HOST_TX_ALIGNMENT 
        <Probcause> informationalStatus(1000) 
        <Alarmtype> other (1) <Polarity> 
        (2) 
        "
	  ::= { pm10010r100AlmmsaNetworkHostNetworkAlarmSummary 15 }



pm10010r100AlmHostRxAlignment OBJECT-TYPE
	  SYNTAX EkiOnOff
	  MAX-ACCESS read-only
	  STATUS current
	  DESCRIPTION
        "
        Line Trscv Host Rx Alignment :This 
        OID indicates a Rx Alignment Fault 
        is detected on the Line Trscv Host 
        interface <Help> Synthesis Alarm 
        indicating a Rx Alignment Fault 
        is detected on the Line Trscv Host 
        interface <Condtype> HOST_RX_ALIGNMENT 
        <Probcause> informationalStatus(1000) 
        <Alarmtype> other (1) <Polarity> 
        (2) 
        "
	  ::= { pm10010r100AlmmsaNetworkHostNetworkAlarmSummary 14 }



pm10010r100AlmNetworkRxOtn OBJECT-TYPE
	  SYNTAX EkiOnOff
	  MAX-ACCESS read-only
	  STATUS current
	  DESCRIPTION
        "
        Line Trscv Network Rx OTN :This 
        OID indicates a Rx OTN Fault is 
        detected on the Line Trscv Network 
        interface <Help> Synthesis Alarm 
        indicating a Rx OTN Fault is detected 
        on the Line Trscv Network interface 
        <Condtype> NETWORK_RX_OTN <Probcause> 
        informationalStatus(1000) <Alarmtype> 
        other (1) <Polarity> (2) 
        "
	  ::= { pm10010r100AlmmsaNetworkHostNetworkAlarmSummary 13 }



pm10010r100AlmNetworkRxAlignment OBJECT-TYPE
	  SYNTAX EkiOnOff
	  MAX-ACCESS read-only
	  STATUS current
	  DESCRIPTION
        "
        Line Trscv Network Rx Alignment 
        :This OID indicates a Rx Alignment 
        Fault is detected on the Line Trscv 
        Network interface <Help> Synthesis 
        Alarm indicating a Rx Alignment 
        Fault is detected on the Line Trscv 
        Network interface <Condtype> NETWORK_RX_ALIGNMENT 
        <Probcause> informationalStatus(1000) 
        <Alarmtype> other (1) <Polarity> 
        (2) 
        "
	  ::= { pm10010r100AlmmsaNetworkHostNetworkAlarmSummary 12 }



pm10010r100AlmNetworkTxAlignment OBJECT-TYPE
	  SYNTAX EkiOnOff
	  MAX-ACCESS read-only
	  STATUS current
	  DESCRIPTION
        "
        Line Trscv Network Tx Alignment 
        :This OID indicates a Tx Alignment 
        Fault is detected on the Line Trscv 
        Network interface <Help> Synthesis 
        Alarm indicating a Tx Alignment 
        Fault is detected on the Line Trscv 
        Network interface <Condtype> NETWORK_TX_ALIGNMENT 
        <Probcause> informationalStatus(1000) 
        <Alarmtype> other (1) <Polarity> 
        (2) 
        "
	  ::= { pm10010r100AlmmsaNetworkHostNetworkAlarmSummary 11 }



--- *****************************************************
---     LEAF for the msaHostTxAlignment article
--- *****************************************************
pm10010r100AlmmsaHostTxAlignment OBJECT IDENTIFIER ::= { pm10010r100AlmOtherCrit 52 }




pm10010r100AlmHostTxCdrLockFault OBJECT-TYPE
	  SYNTAX EkiOnOff
	  MAX-ACCESS read-only
	  STATUS current
	  DESCRIPTION
        "
        Line Trscv Host Tx CDR Lock Fault 
        :This OID indicates a Tx Clock
         Data Recovery Lock Fault is detected 
        on the Line Trscv Host interface 
        <Help> Alarm indicating a Tx Clock 
        Data Recovery Lock Fault is detected 
        on the Line Trscv Host interface 
        <Condtype> HOST_TX_CDR_LOCK_FAULT 
        <Probcause> receiverFailure (42) 
        <Alarmtype> equipmentAlarm (5)
         <Polarity> (2) 
        "
	  ::= { pm10010r100AlmmsaHostTxAlignment 16 }



pm10010r100AlmHostTxLossOfAlignment OBJECT-TYPE
	  SYNTAX EkiOnOff
	  MAX-ACCESS read-only
	  STATUS current
	  DESCRIPTION
        "
        Line Trscv Host Tx Loss Of Alignment 
        :This OID indicates a Tx Loss of 
        Alignment is detected on the Line 
        Trscv Host interface <Help> Alarm 
        indicating a Tx Loss of Alignment 
        is detected on the Line Trscv Host 
        interface <Condtype> HOST_TX_LOSS_OF_ALIGNMENT 
        <Probcause> receiverFailure (42) 
        <Alarmtype> equipmentAlarm (5)
         <Polarity> (2) 
        "
	  ::= { pm10010r100AlmmsaHostTxAlignment 15 }



pm10010r100AlmHostTxOutOfAlignment OBJECT-TYPE
	  SYNTAX EkiOnOff
	  MAX-ACCESS read-only
	  STATUS current
	  DESCRIPTION
        "
        Line Trscv Host Tx Out Of Alignment 
        :This OID indicates a Tx Out of 
        Alignment is detected on the Line 
        Trscv Host interface <Help> Alarm 
        indicating a Tx Out of Alignment 
        is detected on the Line Trscv Host 
        interface <Condtype> HOST_TX_OUT_OF_ALIGNMENT 
        <Probcause> receiverFailure (42) 
        <Alarmtype> equipmentAlarm (5)
         <Polarity> (2) 
        "
	  ::= { pm10010r100AlmmsaHostTxAlignment 14 }



pm10010r100AlmHostTxDeskewLockFault OBJECT-TYPE
	  SYNTAX EkiOnOff
	  MAX-ACCESS read-only
	  STATUS current
	  DESCRIPTION
        "
        Line Trscv Host Tx Deskew Lock 
        Fault :This OID indicates a Tx
         Deskew Lock Fault is detected
         on  the Line Trscv Host interface 
        <Help> Alarm indicating a Tx Deskew 
        Lock Fault is detected on  the
         Line Trscv Host interface <Condtype> 
        HOST_TX_DESKEW_LOCK_FAULT <Probcause> 
        receiverFailure (42) <Alarmtype> 
        equipmentAlarm (5) <Polarity> (2) 
        "
	  ::= { pm10010r100AlmmsaHostTxAlignment 13 }



--- *****************************************************
---     LEAF for the msaHostRxAlignment article
--- *****************************************************
pm10010r100AlmmsaHostRxAlignment OBJECT IDENTIFIER ::= { pm10010r100AlmOtherCrit 53 }




pm10010r100AlmHostRxLossOfAlignment OBJECT-TYPE
	  SYNTAX EkiOnOff
	  MAX-ACCESS read-only
	  STATUS current
	  DESCRIPTION
        "
        Line Trscv Host Rx Loss Of Alignment 
        :This OID indicates a Rx Loss of 
        Alignment is detected on the Line 
        Trscv Host interface <Help> Alarm 
        indicating a Rx Loss of Alignment 
        is detected on the Line Trscv Host 
        interface <Condtype> HOST_RX_LOSS_OF_ALIGNMENT 
        <Probcause> transmitterFailure
         (56) <Alarmtype> equipmentAlarm 
        (5) <Polarity> (2) 
        "
	  ::= { pm10010r100AlmmsaHostRxAlignment 16 }



pm10010r100AlmHostRxOutOfAlignment OBJECT-TYPE
	  SYNTAX EkiOnOff
	  MAX-ACCESS read-only
	  STATUS current
	  DESCRIPTION
        "
        Line Trscv Host Rx Out Of Alignment 
        :This OID indicates a Rx Out of 
        Alignment is detected on the Line 
        Trscv Host interface <Help> Alarm 
        indicating a Rx Out of Alignment 
        is detected on the Line Trscv Host 
        interface <Condtype> HOST_RX_OUT_OF_ALIGNMENT 
        <Probcause> transmitterFailure
         (56) <Alarmtype> equipmentAlarm 
        (5) <Polarity> (2) 
        "
	  ::= { pm10010r100AlmmsaHostRxAlignment 15 }



pm10010r100AlmHostRxCmuLockFault OBJECT-TYPE
	  SYNTAX EkiOnOff
	  MAX-ACCESS read-only
	  STATUS current
	  DESCRIPTION
        "
        Line Trscv Host Rx CMU Lock Fault 
        :This OID indicates a Rx Clock
         Multiplier Unit Lock Fault is
         detected on the Line Trscv Host 
        interface <Help> Alarm indicating 
        a Rx Clock Multiplier Unit Lock 
        Fault is detected on the Line Trscv 
        Host interface <Condtype> HOST_RX_CMU_LOCK_FAULT 
        <Probcause> transmitterFailure
         (56) <Alarmtype> equipmentAlarm 
        (5) <Polarity> (2) 
        "
	  ::= { pm10010r100AlmmsaHostRxAlignment 14 }



--- *********************************************************
---     TABLE for the pm10010r100AlmclientNetworkLaneAlarmWarning articles
--- *********************************************************

pm10010r100AlmclientNetworkLaneAlarmWarningTable OBJECT-TYPE
	SYNTAX  SEQUENCE OF Pm10010r100AlmclientNetworkLaneAlarmWarningEntry
	MAX-ACCESS not-accessible
	STATUS current
	DESCRIPTION
        "
        List of pm10010r100AlmclientNetworkLaneAlarmWarning 
        Article
        "
	::= { pm10010r100AlmClientNurg 56 }


pm10010r100AlmclientNetworkLaneAlarmWarningEntry OBJECT-TYPE
	SYNTAX Pm10010r100AlmclientNetworkLaneAlarmWarningEntry
	MAX-ACCESS not-accessible
	STATUS current
	DESCRIPTION
        "
        Row definition for the pm10010r100AlmclientNetworkLaneAlarmWarning 
        table
        "
	INDEX   { pm10010r100AlmclientNetworkLaneAlarmWarningIndex }
	::= { pm10010r100AlmclientNetworkLaneAlarmWarningTable 1 }


Pm10010r100AlmclientNetworkLaneAlarmWarningEntry ::=
	SEQUENCE {
	pm10010r100AlmclientNetworkLaneAlarmWarningIndex
		INTEGER,
	pm10010r100AlmClientBiasHighAlarmPortn
		EkiOnOff,
	pm10010r100AlmClientBiasHighWarningPortn
		EkiOnOff,
	pm10010r100AlmClientBiasLowWarningPortn
		EkiOnOff,
	pm10010r100AlmClientBiasLowAlarmPortn
		EkiOnOff,
	pm10010r100AlmClientTxPowerHighAlarmPortn
		EkiOnOff,
	pm10010r100AlmClientTxPowerHighWarningPortn
		EkiOnOff,
	pm10010r100AlmClientTxPowerLowWarningPortn
		EkiOnOff,
	pm10010r100AlmClientTxPowerLowAlarmPortn
		EkiOnOff,
	pm10010r100AlmClientLaserTempHighAlarmPortn
		EkiOnOff,
	pm10010r100AlmClientLaserTempHighWarningPortn
		EkiOnOff,
	pm10010r100AlmClientLaserTempLowWarningPortn
		EkiOnOff,
	pm10010r100AlmLaserTempLowAlarmPortn
		EkiOnOff,
	pm10010r100AlmClientRxPowerHighAlarmPortn
		EkiOnOff,
	pm10010r100AlmClientRxPowerHighWarningPortn
		EkiOnOff,
	pm10010r100AlmClientRxPowerLowWarningPortn
		EkiOnOff,
	pm10010r100AlmClientRxPowerLowAlarmPortn
		EkiOnOff
	}


pm10010r100AlmclientNetworkLaneAlarmWarningIndex OBJECT-TYPE
	SYNTAX  INTEGER(0..128)
	MAX-ACCESS  read-only
	STATUS current
	DESCRIPTION
        "
        Index definition for the pm10010r100AlmclientNetworkLaneAlarmWarning 
        table
        "
	::= { pm10010r100AlmclientNetworkLaneAlarmWarningEntry 1 }


pm10010r100AlmClientBiasHighAlarmPortn OBJECT-TYPE
	SYNTAX  EkiOnOff
	MAX-ACCESS read-only
	STATUS current
	DESCRIPTION
        "
        Client Trscv Bias High Alarm :This 
        OID indicates that the Trscv laser 
        bias current is higher than the 
        threshold value written in the
         Trscv EEPROM <Help> Alarm indicating 
        that the Trscv laser bias current 
        is higher than the threshold value 
        written in the Trscv EEPROM <Condtype> 
        CLIENT_BIAS_HIGH_ALARM <Probcause> 
        transmitterFailure (56) <Alarmtype> 
        equipmentAlarm (5) <Polarity> (2) 
        "
	::= { pm10010r100AlmclientNetworkLaneAlarmWarningEntry 17 }


pm10010r100AlmClientBiasHighWarningPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> CLIENT_BIAS_HIGH_WARNING 
        <Probcause> transmitterFailure
         (56) <Alarmtype> equipmentAlarm 
        (5) <Polarity> (2) 
        "
	::= { pm10010r100AlmclientNetworkLaneAlarmWarningEntry 16 }


pm10010r100AlmClientBiasLowWarningPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> CLIENT_BIAS_LOW_WARNING 
        <Probcause> transmitterFailure
         (56) <Alarmtype> equipmentAlarm 
        (5) <Polarity> (2) 
        "
	::= { pm10010r100AlmclientNetworkLaneAlarmWarningEntry 15 }


pm10010r100AlmClientBiasLowAlarmPortn OBJECT-TYPE
	SYNTAX  EkiOnOff
	MAX-ACCESS read-only
	STATUS current
	DESCRIPTION
        "
        Client Trscv Bias Low Alarm :This 
        OID indicates that the Trscv laser 
        bias current is lower than the
         threshold value written in the 
        Trscv EEPROM <Help> Alarm indicating 
        that the Trscv laser bias current 
        is lower than the threshold value 
        written in the Trscv EEPROM <Condtype> 
        CLIENT_BIAS_LOW_ALARM <Probcause> 
        transmitterFailure (56) <Alarmtype> 
        equipmentAlarm (5) <Polarity> (2) 
        "
	::= { pm10010r100AlmclientNetworkLaneAlarmWarningEntry 14 }


pm10010r100AlmClientTxPowerHighAlarmPortn OBJECT-TYPE
	SYNTAX  EkiOnOff
	MAX-ACCESS read-only
	STATUS current
	DESCRIPTION
        "
        Client Trscv Tx Power High Alarm 
        :This OID indicates that the Trscv 
        output power is higher than the 
        threshold value written in the
         Trscv EEPROM <Help> Alarm indicating 
        that the Trscv output power is
         higher than the threshold value 
        written in the Trscv EEPROM <Condtype> 
        CLIENT_TX_POWER_HIGH_ALARM <Probcause> 
        transmitterFailure (56) <Alarmtype> 
        equipmentAlarm (5) <Polarity> (2) 
        "
	::= { pm10010r100AlmclientNetworkLaneAlarmWarningEntry 13 }


pm10010r100AlmClientTxPowerHighWarningPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        CLIENT_TX_POWER_HIGH_WARNING <Probcause> 
        transmitterFailure (56) <Alarmtype> 
        equipmentAlarm (5) <Polarity> (2) 
        "
	::= { pm10010r100AlmclientNetworkLaneAlarmWarningEntry 12 }


pm10010r100AlmClientTxPowerLowWarningPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        CLIENT_TX_POWER_LOW_WARNING <Probcause> 
        transmitterFailure (56) <Alarmtype> 
        equipmentAlarm (5) <Polarity> (2) 
        "
	::= { pm10010r100AlmclientNetworkLaneAlarmWarningEntry 11 }


pm10010r100AlmClientTxPowerLowAlarmPortn OBJECT-TYPE
	SYNTAX  EkiOnOff
	MAX-ACCESS read-only
	STATUS current
	DESCRIPTION
        "
        Client Trscv Tx Power Low Alarm 
        :This OID indicates that the Trscv 
        output power is lower than the
         threshold value written in the 
        Trscv EEPROM <Help> Alarm indicating 
        that the Trscv output power is
         lower than the threshold value 
        written in the Trscv EEPROM <Condtype> 
        CLIENT_TX_POWER_LOW_ALARM <Probcause> 
        transmitterFailure (56) <Alarmtype> 
        equipmentAlarm (5) <Polarity> (2) 
        "
	::= { pm10010r100AlmclientNetworkLaneAlarmWarningEntry 10 }


pm10010r100AlmClientLaserTempHighAlarmPortn OBJECT-TYPE
	SYNTAX  EkiOnOff
	MAX-ACCESS read-only
	STATUS current
	DESCRIPTION
        "
        Client Trscv Laser Temp High Alarm 
        :This OID indicates that the Trscv 
        Laser Temperature is higher than 
        the threshold value written in
         the Trscv EEPROM <Help> Alarm
         indicating that the Trscv Laser 
        Temperature is higher than the
         threshold value written in the 
        Trscv EEPROM <Condtype> CLIENT_LASER_TEMP_HIGH_ALARM 
        <Probcause> temperatureUnacceptable 
        (51) <Alarmtype> equipmentAlarm 
        (5) <Polarity> (2) 
        "
	::= { pm10010r100AlmclientNetworkLaneAlarmWarningEntry 9 }


pm10010r100AlmClientLaserTempHighWarningPortn OBJECT-TYPE
	SYNTAX  EkiOnOff
	MAX-ACCESS read-only
	STATUS current
	DESCRIPTION
        "
        Client Trscv Laser Temp High Warning 
        :This OID indicates that the Trscv 
        Laser Temperature is higher than 
        the threshold value written in
         the Trscv EEPROM <Help> Warning 
        indicating that the Trscv Laser 
        Temperature is higher than the
         threshold value written in the 
        Trscv EEPROM <Condtype> CLIENT_LASER_TEMP_HIGH_WARNING 
        <Probcause> temperatureUnacceptable 
        (51) <Alarmtype> equipmentAlarm 
        (5) <Polarity> (2) 
        "
	::= { pm10010r100AlmclientNetworkLaneAlarmWarningEntry 8 }


pm10010r100AlmClientLaserTempLowWarningPortn OBJECT-TYPE
	SYNTAX  EkiOnOff
	MAX-ACCESS read-only
	STATUS current
	DESCRIPTION
        "
        Client Trscv Laser Temp Low Warning 
        :This OID indicates that the Trscv 
        Laser Temperature is lower than 
        the threshold value written in
         the Trscv EEPROM <Help> Warning 
        indicating that the Trscv Laser 
        Temperature is lower than the threshold 
        value written in the Trscv EEPROM 
        <Condtype> CLIENT_LASER_TEMP_LOW_WARNING 
        <Probcause> temperatureUnacceptable 
        (51) <Alarmtype> equipmentAlarm 
        (5) <Polarity> (2) 
        "
	::= { pm10010r100AlmclientNetworkLaneAlarmWarningEntry 7 }


pm10010r100AlmLaserTempLowAlarmPortn OBJECT-TYPE
	SYNTAX  EkiOnOff
	MAX-ACCESS read-only
	STATUS current
	DESCRIPTION
        "
        Client Trscv Laser Temp Low Alarm 
        :This OID indicates that the Trscv 
        Laser Temperature is lower than 
        the threshold value written in
         the Trscv EEPROM <Help> Alarm
         indicating that the Trscv Laser 
        Temperature is lower than the threshold 
        value written in the Trscv EEPROM 
        <Condtype> LASER_TEMP_LOW_ALARM 
        <Probcause> temperatureUnacceptable 
        (51) <Alarmtype> equipmentAlarm 
        (5) <Polarity> (2) 
        "
	::= { pm10010r100AlmclientNetworkLaneAlarmWarningEntry 6 }


pm10010r100AlmClientRxPowerHighAlarmPortn OBJECT-TYPE
	SYNTAX  EkiOnOff
	MAX-ACCESS read-only
	STATUS current
	DESCRIPTION
        "
        Client Trscv Rx Power High Alarm 
        :This OID indicates that the Trscv 
        input power is higher than the
         threshold value written in the 
        Trscv EEPROM <Help> Alarm indicating 
        that the Trscv input power is higher 
        than the threshold value written 
        in the Trscv EEPROM <Condtype>
         CLIENT_RX_POWER_HIGH_ALARM <Probcause> 
        receiveFailure (41) <Alarmtype> 
        equipmentAlarm (5) <Polarity> (2) 
        "
	::= { pm10010r100AlmclientNetworkLaneAlarmWarningEntry 5 }


pm10010r100AlmClientRxPowerHighWarningPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         CLIENT_RX_POWER_HIGH_WARNING <Probcause> 
        receiveFailure (41) <Alarmtype> 
        equipmentAlarm (5) <Polarity> (2) 
        "
	::= { pm10010r100AlmclientNetworkLaneAlarmWarningEntry 4 }


pm10010r100AlmClientRxPowerLowWarningPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         CLIENT_RX_POWER_LOW_WARNING <Probcause> 
        receiveFailure (41) <Alarmtype> 
        equipmentAlarm (5) <Polarity> (2) 
        "
	::= { pm10010r100AlmclientNetworkLaneAlarmWarningEntry 3 }


pm10010r100AlmClientRxPowerLowAlarmPortn OBJECT-TYPE
	SYNTAX  EkiOnOff
	MAX-ACCESS read-only
	STATUS current
	DESCRIPTION
        "
        Client Trscv Rx Power Low Alarm 
        :This OID indicates that the Trscv 
        input power is lower than the threshold 
        value written in the Trscv EEPROM 
        <Help> Alarm indicating that the 
        Trscv input power is lower than 
        the threshold value written in
         the Trscv EEPROM <Condtype> CLIENT_RX_POWER_LOW_ALARM 
        <Probcause> receiveFailure (41) 
        <Alarmtype> equipmentAlarm (5)
         <Polarity> (2) 
        "
	::= { pm10010r100AlmclientNetworkLaneAlarmWarningEntry 2 }


--- *********************************************************
---     TABLE for the pm10010r100AlmclientNetworkLaneFault articles
--- *********************************************************

pm10010r100AlmclientNetworkLaneFaultTable OBJECT-TYPE
	SYNTAX  SEQUENCE OF Pm10010r100AlmclientNetworkLaneFaultEntry
	MAX-ACCESS not-accessible
	STATUS current
	DESCRIPTION
        "
        List of pm10010r100AlmclientNetworkLaneFault 
        Article
        "
	::= { pm10010r100AlmClientUrg 72 }


pm10010r100AlmclientNetworkLaneFaultEntry OBJECT-TYPE
	SYNTAX Pm10010r100AlmclientNetworkLaneFaultEntry
	MAX-ACCESS not-accessible
	STATUS current
	DESCRIPTION
        "
        Row definition for the pm10010r100AlmclientNetworkLaneFault 
        table
        "
	INDEX   { pm10010r100AlmclientNetworkLaneFaultIndex }
	::= { pm10010r100AlmclientNetworkLaneFaultTable 1 }


Pm10010r100AlmclientNetworkLaneFaultEntry ::=
	SEQUENCE {
	pm10010r100AlmclientNetworkLaneFaultIndex
		INTEGER,
	pm10010r100AlmClientLaneTecFaultPortn
		EkiOnOff,
	pm10010r100AlmClientLaneWavelengthUnlockedPortn
		EkiOnOff,
	pm10010r100AlmClientLaneApdPowerSupplyPortn
		EkiOnOff,
	pm10010r100AlmClientLaneTxLosfPortn
		EkiOnOff,
	pm10010r100AlmClientLaneTxLolPortn
		EkiOnOff,
	pm10010r100AlmClientLaneRxLosPortn
		EkiOnOff,
	pm10010r100AlmClientLaneRxLolPortn
		EkiOnOff,
	pm10010r100AlmClientLaneRxFifoErrorPortn
		EkiOnOff
	}


pm10010r100AlmclientNetworkLaneFaultIndex OBJECT-TYPE
	SYNTAX  INTEGER(0..128)
	MAX-ACCESS  read-only
	STATUS current
	DESCRIPTION
        "
        Index definition for the pm10010r100AlmclientNetworkLaneFault 
        table
        "
	::= { pm10010r100AlmclientNetworkLaneFaultEntry 1 }


pm10010r100AlmClientLaneTecFaultPortn OBJECT-TYPE
	SYNTAX  EkiOnOff
	MAX-ACCESS read-only
	STATUS current
	DESCRIPTION
        "
        Client Network Lane TEC Fault
         :This OID indicates a TEC Fault 
        on the Client Trscv Network Lane 
        <Help> Alarm indicating a TEC Fault 
        on the Client Trscv Network Lane 
        <Condtype> CLIENT_LANE_TEC_FAULT 
        <Probcause> transmitterFailure
         (56) <Alarmtype> equipmentAlarm 
        (5) <Polarity> (2) 
        "
	::= { pm10010r100AlmclientNetworkLaneFaultEntry 17 }


pm10010r100AlmClientLaneWavelengthUnlockedPortn OBJECT-TYPE
	SYNTAX  EkiOnOff
	MAX-ACCESS read-only
	STATUS current
	DESCRIPTION
        "
        Client Network Lane Wavelength 
        Unlock :This OID indicates a Wavelength 
        unlock on the Client Trscv Network 
        Lane <Help> Alarm indicating a
         Wavelength unlock on the Client 
        Trscv Network Lane <Condtype> CLIENT_LANE_WAVELENGTH_UNLOCKED 
        <Probcause> transmitterFailure
         (56) <Alarmtype> equipmentAlarm 
        (5) <Polarity> (2) 
        "
	::= { pm10010r100AlmclientNetworkLaneFaultEntry 16 }


pm10010r100AlmClientLaneApdPowerSupplyPortn OBJECT-TYPE
	SYNTAX  EkiOnOff
	MAX-ACCESS read-only
	STATUS current
	DESCRIPTION
        "
        Client Network Lane APD Power
         Supply :This OID indicates an
         APD Power supply failure on the 
        Client Trscv Network Lane <Help> 
        Alarm indicating an APD Power supply 
        failure on the Client Trscv Network 
        Lane <Condtype> CLIENT_LANE_APD_POWER_SUPPLY 
        <Probcause> transmitterFailure
         (56) <Alarmtype> equipmentAlarm 
        (5) <Polarity> (2) 
        "
	::= { pm10010r100AlmclientNetworkLaneFaultEntry 15 }


pm10010r100AlmClientLaneTxLosfPortn OBJECT-TYPE
	SYNTAX  EkiOnOff
	MAX-ACCESS read-only
	STATUS current
	DESCRIPTION
        "
        Client Network Lane Tx Loss Of 
        Signal Functionality :This OID
         indicates a Tx Loss of Signal
         Functionality on the Client Trscv 
        Network Lane <Help> Alarm indicating 
        a Tx Loss of Signal Functionality 
        on the Client Trscv Network Lane 
        <Condtype> CLIENT_LANE_TX_LOSF
         <Probcause> transmitterFailure 
        (56) <Alarmtype> equipmentAlarm 
        (5) <Polarity> (2) 
        "
	::= { pm10010r100AlmclientNetworkLaneFaultEntry 9 }


pm10010r100AlmClientLaneTxLolPortn OBJECT-TYPE
	SYNTAX  EkiOnOff
	MAX-ACCESS read-only
	STATUS current
	DESCRIPTION
        "
        Client Network Lane Tx Loss Of 
        Lock :This OID indicates a Tx Loss 
        of Lock on the Client Trscv Network 
        Lane <Help> Alarm indicating a
         Tx Loss of Lock on the Client
         Trscv Network Lane <Condtype>
         CLIENT_LANE_TX_LOL <Probcause> 
        transmitterFailure (56) <Alarmtype> 
        equipmentAlarm (5) <Polarity> (2) 
        "
	::= { pm10010r100AlmclientNetworkLaneFaultEntry 8 }


pm10010r100AlmClientLaneRxLosPortn OBJECT-TYPE
	SYNTAX  EkiOnOff
	MAX-ACCESS read-only
	STATUS current
	DESCRIPTION
        "
        Client Network Lane Rx Loss Of 
        Signal :This OID indicates a Rx 
        Loss of Signal on the Client Trscv 
        Network Lane <Help> Alarm indicating 
        a Rx Loss of Signal on the Client 
        Trscv Network Lane <Condtype> CLIENT_LANE_RX_LOS 
        <Probcause> receiveFailure (41) 
        <Alarmtype> physicalViolation (9) 
        <Polarity> (2) 
        "
	::= { pm10010r100AlmclientNetworkLaneFaultEntry 6 }


pm10010r100AlmClientLaneRxLolPortn OBJECT-TYPE
	SYNTAX  EkiOnOff
	MAX-ACCESS read-only
	STATUS current
	DESCRIPTION
        "
        Client Network Lane Rx Loss Of 
        Lock :This OID indicates a Rx Loss 
        of Lock on the Client Trscv Network 
        Lane <Help> Alarm indicating a
         Rx Loss of Lock on the Client
         Trscv Network Lane <Condtype>
         CLIENT_LANE_RX_LOL <Probcause> 
        receiverFailure (42) <Alarmtype> 
        equipmentAlarm (5) <Polarity> (2) 
        "
	::= { pm10010r100AlmclientNetworkLaneFaultEntry 5 }


pm10010r100AlmClientLaneRxFifoErrorPortn OBJECT-TYPE
	SYNTAX  EkiOnOff
	MAX-ACCESS read-only
	STATUS current
	DESCRIPTION
        "
        Client Network Lane Rx FIFO Error 
        :This OID indicates a Rx FIFO Error 
        on the Client Trscv Network Lane 
        <Help> Alarm indicating a Rx FIFO 
        Error on the Client Trscv Network 
        Lane <Condtype> CLIENT_LANE_RX_FIFO_ERROR 
        <Probcause> receiverFailure (42) 
        <Alarmtype> equipmentAlarm (5)
         <Polarity> (2) 
        "
	::= { pm10010r100AlmclientNetworkLaneFaultEntry 4 }


--- *********************************************************
---     TABLE for the pm10010r100AlmclientHostLaneFault articles
--- *********************************************************

pm10010r100AlmclientHostLaneFaultTable OBJECT-TYPE
	SYNTAX  SEQUENCE OF Pm10010r100AlmclientHostLaneFaultEntry
	MAX-ACCESS not-accessible
	STATUS current
	DESCRIPTION
        "
        List of pm10010r100AlmclientHostLaneFault 
        Article
        "
	::= { pm10010r100AlmClientUrg 88 }


pm10010r100AlmclientHostLaneFaultEntry OBJECT-TYPE
	SYNTAX Pm10010r100AlmclientHostLaneFaultEntry
	MAX-ACCESS not-accessible
	STATUS current
	DESCRIPTION
        "
        Row definition for the pm10010r100AlmclientHostLaneFault 
        table
        "
	INDEX   { pm10010r100AlmclientHostLaneFaultIndex }
	::= { pm10010r100AlmclientHostLaneFaultTable 1 }


Pm10010r100AlmclientHostLaneFaultEntry ::=
	SEQUENCE {
	pm10010r100AlmclientHostLaneFaultIndex
		INTEGER,
	pm10010r100AlmClientLaneTxFifoErrorPortn
		EkiOnOff,
	pm10010r100AlmClientTxHostLolPortn
		EkiOnOff,
	pm10010r100AlmClientCsfDetectedPortn
		EkiOnOff,
	pm10010r100AlmClientLanesNotAlignedPortn
		EkiOnOff,
	pm10010r100AlmClientLanes6466UnlockPortn
		EkiOnOff,
	pm10010r100AlmClientLanesMarkerUnlockPortn
		EkiOnOff,
	pm10010r100AlmClientInputLossOfSigPortn
		EkiOnOff,
	pm10010r100AlmClientLossOfSyncPortn
		EkiOnOff
	}


pm10010r100AlmclientHostLaneFaultIndex OBJECT-TYPE
	SYNTAX  INTEGER(0..128)
	MAX-ACCESS  read-only
	STATUS current
	DESCRIPTION
        "
        Index definition for the pm10010r100AlmclientHostLaneFault 
        table
        "
	::= { pm10010r100AlmclientHostLaneFaultEntry 1 }


pm10010r100AlmClientLaneTxFifoErrorPortn OBJECT-TYPE
	SYNTAX  EkiOnOff
	MAX-ACCESS read-only
	STATUS current
	DESCRIPTION
        "
        Client Host Lane Tx FIFO Error 
        :This OID indicates a Tx FIFO Error 
        on the Client Trscv Host Lane <Help> 
        Alarm indicating a Tx FIFO Error 
        on the Client Trscv Host Lane <Condtype> 
        CLIENT_LANE_TX_FIFO_ERROR <Probcause> 
        receiverFailure (42) <Alarmtype> 
        equipmentAlarm (5) <Polarity> (2) 
        "
	::= { pm10010r100AlmclientHostLaneFaultEntry 11 }


pm10010r100AlmClientTxHostLolPortn OBJECT-TYPE
	SYNTAX  EkiOnOff
	MAX-ACCESS read-only
	STATUS current
	DESCRIPTION
        "
        Client Host Lane Tx Loss Of Lock 
        :This OID indicates a Tx Loss of 
        Lock on the Client Trscv Host Lane 
        <Help> Alarm indicating a Tx Loss 
        of Lock on the Client Trscv Host 
        Lane <Condtype> CLIENT_TX_HOST_LOL 
        <Probcause> receiverFailure (42) 
        <Alarmtype> equipmentAlarm (5)
         <Polarity> (2) 
        "
	::= { pm10010r100AlmclientHostLaneFaultEntry 10 }


pm10010r100AlmClientCsfDetectedPortn OBJECT-TYPE
	SYNTAX  EkiOnOff
	MAX-ACCESS read-only
	STATUS current
	DESCRIPTION
        "
        Client Signal Fail Detected :This 
        OID indicates that a CSF has been 
        detected on client port in the
         downstream direction   <Help>
          This alarm indicates if a Client 
        Signal Fail has been detected in 
        the incoming line frame for this 
        client port <Condtype> CLIENT_CSF_DETECTED 
        <Probcause> receiveFailure (41) 
        <Alarmtype> other(1) <Polarity> 
        (2)
        "
	::= { pm10010r100AlmclientHostLaneFaultEntry 7 }


pm10010r100AlmClientLanesNotAlignedPortn OBJECT-TYPE
	SYNTAX  EkiOnOff
	MAX-ACCESS read-only
	STATUS current
	DESCRIPTION
        "
        Client Lanes Not Aligned :This 
        OID indicates the Client lanes
         are not aligned <Help> Alarm indicating 
        the Client lanes are not aligned 
        <Condtype> CLIENT_LANES_NOT_ALIGNED 
        <Probcause> receiveFailure (41) 
        <Alarmtype> integrityViolation
         (7) <Polarity> (2) 
        "
	::= { pm10010r100AlmclientHostLaneFaultEntry 6 }


pm10010r100AlmClientLanes6466UnlockPortn OBJECT-TYPE
	SYNTAX  EkiOnOff
	MAX-ACCESS read-only
	STATUS current
	DESCRIPTION
        "
        Client Lanes 64/66b Unlock :This 
        OID indicates the Client 64/66b 
        decoder is not lock <Help> Alarm 
        indicating the Client 64/66b decoder 
        is not lock <Condtype> CLIENT_LANES_64_66_UNLOCK 
        <Probcause> receiveFailure (41) 
        <Alarmtype> integrityViolation
         (7) <Polarity> (2) 
        "
	::= { pm10010r100AlmclientHostLaneFaultEntry 5 }


pm10010r100AlmClientLanesMarkerUnlockPortn OBJECT-TYPE
	SYNTAX  EkiOnOff
	MAX-ACCESS read-only
	STATUS current
	DESCRIPTION
        "
        Client Lanes Marker Unlock :This 
        OID indicates the Client lanes
         marker alignment is not lock <Help> 
        Alarm indicating the Client lanes 
        marker alignment is not lock <Condtype> 
        CLIENT_LANES_MARKER_UNLOCK <Probcause> 
        receiveFailure (41) <Alarmtype> 
        integrityViolation (7) <Polarity> 
        (2) 
        "
	::= { pm10010r100AlmclientHostLaneFaultEntry 4 }


pm10010r100AlmClientInputLossOfSigPortn OBJECT-TYPE
	SYNTAX  EkiOnOff
	MAX-ACCESS read-only
	STATUS current
	DESCRIPTION
        "
        Client Input Loss Of Signal :This 
        OID indicates a Loss of Signal
         is detected on the Client Trscv 
        <Help> Alarm indicating a Loss
         of Signal is detected on the Client 
        Trscv <Condtype> CLIENT_INPUT_LOSS_OF_SIG 
        <Probcause> receiveFailure (41) 
        <Alarmtype> physicalViolation (9) 
        <Polarity> (2) 
        "
	::= { pm10010r100AlmclientHostLaneFaultEntry 3 }


pm10010r100AlmClientLossOfSyncPortn OBJECT-TYPE
	SYNTAX  EkiOnOff
	MAX-ACCESS read-only
	STATUS current
	DESCRIPTION
        "
        Client Frame Alignment Loss :This 
        OID indicates the module is not 
        aligned with the incoming Client 
        signal <Help> Alarm indicating
         the module is not aligned with 
        the incoming client signal <Condtype> 
        CLIENT_LOSS_OF_SYNC <Probcause> 
        receiveFailure (41) <Alarmtype> 
        integrityViolation (7) <Polarity> 
        (2) 
        "
	::= { pm10010r100AlmclientHostLaneFaultEntry 2 }


--- *********************************************************
---     TABLE for the pm10010r100AlmlineNetworkLaneAlarmWarning1 articles
--- *********************************************************

pm10010r100AlmlineNetworkLaneAlarmWarning1Table OBJECT-TYPE
	SYNTAX  SEQUENCE OF Pm10010r100AlmlineNetworkLaneAlarmWarning1Entry
	MAX-ACCESS not-accessible
	STATUS current
	DESCRIPTION
        "
        List of pm10010r100AlmlineNetworkLaneAlarmWarning1 
        Article
        "
	::= { pm10010r100AlmLineNurg 104 }


pm10010r100AlmlineNetworkLaneAlarmWarning1Entry OBJECT-TYPE
	SYNTAX Pm10010r100AlmlineNetworkLaneAlarmWarning1Entry
	MAX-ACCESS not-accessible
	STATUS current
	DESCRIPTION
        "
        Row definition for the pm10010r100AlmlineNetworkLaneAlarmWarning1 
        table
        "
	INDEX   { pm10010r100AlmlineNetworkLaneAlarmWarning1Index }
	::= { pm10010r100AlmlineNetworkLaneAlarmWarning1Table 1 }


Pm10010r100AlmlineNetworkLaneAlarmWarning1Entry ::=
	SEQUENCE {
	pm10010r100AlmlineNetworkLaneAlarmWarning1Index
		INTEGER,
	pm10010r100AlmLineBiasHighAlarmPortn
		EkiOnOff,
	pm10010r100AlmLineBiasHighWarningPortn
		EkiOnOff,
	pm10010r100AlmLineBiasLowWarningPortn
		EkiOnOff,
	pm10010r100AlmLineBiasLowAlarmPortn
		EkiOnOff,
	pm10010r100AlmLineTxPowerHighAlarmPortn
		EkiOnOff,
	pm10010r100AlmLineTxPowerHighWarningPortn
		EkiOnOff,
	pm10010r100AlmLineTxPowerLowWarningPortn
		EkiOnOff,
	pm10010r100AlmLineTxPowerLowAlarmPortn
		EkiOnOff,
	pm10010r100AlmLineLaserTempHighAlarmPortn
		EkiOnOff,
	pm10010r100AlmLineLaserTempHighWarningPortn
		EkiOnOff,
	pm10010r100AlmLineLaserTempLowWarningPortn
		EkiOnOff,
	pm10010r100AlmLineLaserTempLowAlarmPortn
		EkiOnOff,
	pm10010r100AlmLineRxPowerHighAlarmPortn
		EkiOnOff,
	pm10010r100AlmLineRxPowerHighWarningPortn
		EkiOnOff,
	pm10010r100AlmLineRxPowerLowWarningPortn
		EkiOnOff,
	pm10010r100AlmLineRxPowerLowAlarmPortn
		EkiOnOff
	}


pm10010r100AlmlineNetworkLaneAlarmWarning1Index OBJECT-TYPE
	SYNTAX  INTEGER(0..128)
	MAX-ACCESS  read-only
	STATUS current
	DESCRIPTION
        "
        Index definition for the pm10010r100AlmlineNetworkLaneAlarmWarning1 
        table
        "
	::= { pm10010r100AlmlineNetworkLaneAlarmWarning1Entry 1 }


pm10010r100AlmLineBiasHighAlarmPortn OBJECT-TYPE
	SYNTAX  EkiOnOff
	MAX-ACCESS read-only
	STATUS current
	DESCRIPTION
        "
        Line Trscv Tx Bias High Alarm
         :This OID indicates that the Trscv 
        laser bias current is higher than 
        the threshold value written in
         the Trscv EEPROM <Help> Alarm
         indicating that the Trscv laser 
        bias current is higher than the 
        threshold value written in the
         Trscv EEPROM <Condtype> LINE_BIAS_HIGH_ALARM 
        <Probcause> transmitterFailure
         (56) <Alarmtype> equipmentAlarm 
        (5) <Polarity> (2) 
        "
	::= { pm10010r100AlmlineNetworkLaneAlarmWarning1Entry 17 }


pm10010r100AlmLineBiasHighWarningPortn OBJECT-TYPE
	SYNTAX  EkiOnOff
	MAX-ACCESS read-only
	STATUS current
	DESCRIPTION
        "
        Line Trscv Tx Bias High Warning 
        :This OID indicates that the Trscv 
        laser bias current is higher than 
        the threshold value written in
         the Trscv EEPROM <Help> Warning 
        indicating that the Trscv laser 
        bias current is higher than the 
        threshold value written in the
         Trscv EEPROM <Condtype> LINE_BIAS_HIGH_WARNING 
        <Probcause> transmitterFailure
         (56) <Alarmtype> equipmentAlarm 
        (5) <Polarity> (2) 
        "
	::= { pm10010r100AlmlineNetworkLaneAlarmWarning1Entry 16 }


pm10010r100AlmLineBiasLowWarningPortn OBJECT-TYPE
	SYNTAX  EkiOnOff
	MAX-ACCESS read-only
	STATUS current
	DESCRIPTION
        "
        Line Trscv Tx Bias Low Warning 
        :This OID indicates that the Trscv 
        laser bias current is lower than 
        the threshold value written in
         the Trscv EEPROM <Help> Warning 
        indicating that the Trscv laser 
        bias current is lower than the
         threshold value written in the 
        Trscv EEPROM <Condtype> LINE_BIAS_LOW_WARNING 
        <Probcause> transmitterFailure
         (56) <Alarmtype> equipmentAlarm 
        (5) <Polarity> (2) 
        "
	::= { pm10010r100AlmlineNetworkLaneAlarmWarning1Entry 15 }


pm10010r100AlmLineBiasLowAlarmPortn OBJECT-TYPE
	SYNTAX  EkiOnOff
	MAX-ACCESS read-only
	STATUS current
	DESCRIPTION
        "
        Line Trscv Tx Bias Low Alarm :This 
        OID indicates that the Trscv laser 
        bias current is lower than the
         threshold value written in the 
        Trscv EEPROM <Help> Alarm indicating 
        that the Trscv laser bias current 
        is lower than the threshold value 
        written in the Trscv EEPROM <Condtype> 
        LINE_BIAS_LOW_ALARM <Probcause> 
        transmitterFailure (56) <Alarmtype> 
        equipmentAlarm (5) <Polarity> (2) 
        "
	::= { pm10010r100AlmlineNetworkLaneAlarmWarning1Entry 14 }


pm10010r100AlmLineTxPowerHighAlarmPortn OBJECT-TYPE
	SYNTAX  EkiOnOff
	MAX-ACCESS read-only
	STATUS current
	DESCRIPTION
        "
        Line Trscv Tx Power High Alarm 
        :This OID indicates that the Trscv 
        output power is higher than the 
        threshold value written in the
         Trscv EEPROM <Help> Alarm indicating 
        that the Trscv output power is
         higher than the threshold value 
        written in the Trscv EEPROM <Condtype> 
        LINE_TX_POWER_HIGH_ALARM <Probcause> 
        transmitterFailure (56) <Alarmtype> 
        equipmentAlarm (5) <Polarity> (2) 
        "
	::= { pm10010r100AlmlineNetworkLaneAlarmWarning1Entry 13 }


pm10010r100AlmLineTxPowerHighWarningPortn OBJECT-TYPE
	SYNTAX  EkiOnOff
	MAX-ACCESS read-only
	STATUS current
	DESCRIPTION
        "
        Line Trscv Tx Power High Warning 
        :This OID indicates that the Trscv 
        output power is higher than the 
        threshold value written in the
         Trscv EEPROM <Help> Warning indicating 
        that the Trscv output power is
         higher than the threshold value 
        written in the Trscv EEPROM <Condtype> 
        LINE_TX_POWER_HIGH_WARNING <Probcause> 
        transmitterFailure (56) <Alarmtype> 
        equipmentAlarm (5) <Polarity> (2) 
        "
	::= { pm10010r100AlmlineNetworkLaneAlarmWarning1Entry 12 }


pm10010r100AlmLineTxPowerLowWarningPortn OBJECT-TYPE
	SYNTAX  EkiOnOff
	MAX-ACCESS read-only
	STATUS current
	DESCRIPTION
        "
        Line Trscv Tx Power Low Warning 
        :This OID indicates that the Trscv 
        output power is lower than the
         threshold value written in the 
        Trscv EEPROM <Help> Warning indicating 
        that the Trscv output power is
         lower than the threshold value 
        written in the Trscv EEPROM <Condtype> 
        LINE_TX_POWER_LOW_WARNING <Probcause> 
        transmitterFailure (56) <Alarmtype> 
        equipmentAlarm (5) <Polarity> (2) 
        "
	::= { pm10010r100AlmlineNetworkLaneAlarmWarning1Entry 11 }


pm10010r100AlmLineTxPowerLowAlarmPortn OBJECT-TYPE
	SYNTAX  EkiOnOff
	MAX-ACCESS read-only
	STATUS current
	DESCRIPTION
        "
        Line Trscv Tx Power Low Alarm
         :This OID indicates that the Trscv 
        output power is lower than the
         threshold value written in the 
        Trscv EEPROM <Help> Alarm indicating 
        that the Trscv output power is
         lower than the threshold value 
        written in the Trscv EEPROM <Condtype> 
        LINE_TX_POWER_LOW_ALARM <Probcause> 
        transmitterFailure (56) <Alarmtype> 
        equipmentAlarm (5) <Polarity> (2) 
        "
	::= { pm10010r100AlmlineNetworkLaneAlarmWarning1Entry 10 }


pm10010r100AlmLineLaserTempHighAlarmPortn OBJECT-TYPE
	SYNTAX  EkiOnOff
	MAX-ACCESS read-only
	STATUS current
	DESCRIPTION
        "
        Line Trscv Tx Laser Temp High
         Alarm :This OID indicates that 
        the Trscv Tx Laser Temperature
         is higher than the threshold value 
        written in the Trscv EEPROM <Help> 
        Alarm indicating that the Trscv 
        Tx Laser Temperature is higher
         than the threshold value written 
        in the Trscv EEPROM <Condtype>
         LINE_LASER_TEMP_HIGH_ALARM <Probcause> 
        temperatureUnacceptable (51) <Alarmtype> 
        equipmentAlarm (5) <Polarity> (2) 
        "
	::= { pm10010r100AlmlineNetworkLaneAlarmWarning1Entry 9 }


pm10010r100AlmLineLaserTempHighWarningPortn OBJECT-TYPE
	SYNTAX  EkiOnOff
	MAX-ACCESS read-only
	STATUS current
	DESCRIPTION
        "
        Line Trscv Tx Laser Temp High
         Warning :This OID indicates that 
        the Trscv Tx Laser Temperature
         is higher than the threshold value 
        written in the Trscv EEPROM <Help> 
        Warning indicating that the Trscv 
        Tx Laser Temperature is higher
         than the threshold value written 
        in the Trscv EEPROM <Condtype>
         LINE_LASER_TEMP_HIGH_WARNING <Probcause> 
        temperatureUnacceptable (51) <Alarmtype> 
        equipmentAlarm (5) <Polarity> (2) 
        "
	::= { pm10010r100AlmlineNetworkLaneAlarmWarning1Entry 8 }


pm10010r100AlmLineLaserTempLowWarningPortn OBJECT-TYPE
	SYNTAX  EkiOnOff
	MAX-ACCESS read-only
	STATUS current
	DESCRIPTION
        "
        Line Trscv Tx Laser Temp Low Warning 
        :This OID indicates that the Trscv 
        Tx Laser Temperature is lower than 
        the threshold value written in
         the Trscv EEPROM <Help> Warning 
        indicating that the Trscv Tx Laser 
        Temperature is lower than the threshold 
        value written in the Trscv EEPROM 
        <Condtype> LINE_LASER_TEMP_LOW_WARNING 
        <Probcause> temperatureUnacceptable 
        (51) <Alarmtype> equipmentAlarm 
        (5) <Polarity> (2) 
        "
	::= { pm10010r100AlmlineNetworkLaneAlarmWarning1Entry 7 }


pm10010r100AlmLineLaserTempLowAlarmPortn OBJECT-TYPE
	SYNTAX  EkiOnOff
	MAX-ACCESS read-only
	STATUS current
	DESCRIPTION
        "
        Line Trscv Tx Laser Temp Low Alarm 
        :This OID indicates that the Trscv 
        Tx Laser Temperature is lower than 
        the threshold value written in
         the Trscv EEPROM <Help> Alarm
         indicating that the Trscv Tx Laser 
        Temperature is lower than the threshold 
        value written in the Trscv EEPROM 
        <Condtype> LINE_LASER_TEMP_LOW_ALARM 
        <Probcause> temperatureUnacceptable 
        (51) <Alarmtype> equipmentAlarm 
        (5) <Polarity> (2) 
        "
	::= { pm10010r100AlmlineNetworkLaneAlarmWarning1Entry 6 }


pm10010r100AlmLineRxPowerHighAlarmPortn OBJECT-TYPE
	SYNTAX  EkiOnOff
	MAX-ACCESS read-only
	STATUS current
	DESCRIPTION
        "
        Line Trscv Rx Power High Alarm 
        :This OID indicates that the Trscv 
        input power is higher than the
         threshold value written in the 
        Trscv EEPROM <Help> Alarm indicating 
        that the Trscv input power is higher 
        than the threshold value written 
        in the Trscv EEPROM <Condtype>
         LINE_RX_POWER_HIGH_ALARM <Probcause> 
        receiveFailure (41) <Alarmtype> 
        equipmentAlarm (5) <Polarity> (2) 
        "
	::= { pm10010r100AlmlineNetworkLaneAlarmWarning1Entry 5 }


pm10010r100AlmLineRxPowerHighWarningPortn OBJECT-TYPE
	SYNTAX  EkiOnOff
	MAX-ACCESS read-only
	STATUS current
	DESCRIPTION
        "
        Line Trscv Rx Power High Warning 
        :This OID indicates that the Trscv 
        input power is higher than the
         threshold value written in the 
        Trscv EEPROM <Help> Warning indicating 
        that the Trscv input power is higher 
        than the threshold value written 
        in the Trscv EEPROM <Condtype>
         LINE_RX_POWER_HIGH_WARNING <Probcause> 
        receiveFailure (41) <Alarmtype> 
        equipmentAlarm (5) <Polarity> (2) 
        "
	::= { pm10010r100AlmlineNetworkLaneAlarmWarning1Entry 4 }


pm10010r100AlmLineRxPowerLowWarningPortn OBJECT-TYPE
	SYNTAX  EkiOnOff
	MAX-ACCESS read-only
	STATUS current
	DESCRIPTION
        "
        Line Trscv Rx Power Low Warning 
        :This OID indicates that the Trscv 
        input power is lower than the threshold 
        value written in the Trscv EEPROM 
        <Help> Warning indicating that
         the Trscv input power is lower 
        than the threshold value written 
        in the Trscv EEPROM <Condtype>
         LINE_RX_POWER_LOW_WARNING <Probcause> 
        receiveFailure (41) <Alarmtype> 
        equipmentAlarm (5) <Polarity> (2) 
        "
	::= { pm10010r100AlmlineNetworkLaneAlarmWarning1Entry 3 }


pm10010r100AlmLineRxPowerLowAlarmPortn OBJECT-TYPE
	SYNTAX  EkiOnOff
	MAX-ACCESS read-only
	STATUS current
	DESCRIPTION
        "
        Line Trscv Rx Power Low Alarm
         :This OID indicates that the Trscv 
        input power is lower than the threshold 
        value written in the Trscv EEPROM 
        <Help> Alarm indicating that the 
        Trscv input power is lower than 
        the threshold value written in
         the Trscv EEPROM <Condtype> LINE_RX_POWER_LOW_ALARM 
        <Probcause> receiveFailure (41) 
        <Alarmtype> equipmentAlarm (5)
         <Polarity> (2) 
        "
	::= { pm10010r100AlmlineNetworkLaneAlarmWarning1Entry 2 }


--- *********************************************************
---     TABLE for the pm10010r100AlmlineNetworkLaneAlarmWarning2 articles
--- *********************************************************

pm10010r100AlmlineNetworkLaneAlarmWarning2Table OBJECT-TYPE
	SYNTAX  SEQUENCE OF Pm10010r100AlmlineNetworkLaneAlarmWarning2Entry
	MAX-ACCESS not-accessible
	STATUS current
	DESCRIPTION
        "
        List of pm10010r100AlmlineNetworkLaneAlarmWarning2 
        Article
        "
	::= { pm10010r100AlmLineNurg 120 }


pm10010r100AlmlineNetworkLaneAlarmWarning2Entry OBJECT-TYPE
	SYNTAX Pm10010r100AlmlineNetworkLaneAlarmWarning2Entry
	MAX-ACCESS not-accessible
	STATUS current
	DESCRIPTION
        "
        Row definition for the pm10010r100AlmlineNetworkLaneAlarmWarning2 
        table
        "
	INDEX   { pm10010r100AlmlineNetworkLaneAlarmWarning2Index }
	::= { pm10010r100AlmlineNetworkLaneAlarmWarning2Table 1 }


Pm10010r100AlmlineNetworkLaneAlarmWarning2Entry ::=
	SEQUENCE {
	pm10010r100AlmlineNetworkLaneAlarmWarning2Index
		INTEGER,
	pm10010r100AlmRxLaserBiasHighAlarmPortn
		EkiOnOff,
	pm10010r100AlmRxLaserBiasHighWarningPortn
		EkiOnOff,
	pm10010r100AlmRxLaserBiasLowWarningPortn
		EkiOnOff,
	pm10010r100AlmRxLaserBiasLowAlarmPortn
		EkiOnOff,
	pm10010r100AlmRxLaserOutputHighAlarmPortn
		EkiOnOff,
	pm10010r100AlmRxLaserOutputHighWarningPortn
		EkiOnOff,
	pm10010r100AlmRxLaserOutputLowWarningPortn
		EkiOnOff,
	pm10010r100AlmRxLaserOutputLowAlarmPortn
		EkiOnOff,
	pm10010r100AlmRxLaserTempHighAlarmPortn
		EkiOnOff,
	pm10010r100AlmRxLaserTempHighWarningPortn
		EkiOnOff,
	pm10010r100AlmRxLaserTempLowWarningPortn
		EkiOnOff,
	pm10010r100AlmRxLaserTempLowAlarmPortn
		EkiOnOff,
	pm10010r100AlmTxModulatorBiasHighAlarmPortn
		EkiOnOff,
	pm10010r100AlmTxModulatorBiasHighWarningPortn
		EkiOnOff,
	pm10010r100AlmTxModulatorBiasLowWarningPortn
		EkiOnOff,
	pm10010r100AlmTxModulatorBiasLowAlarmPortn
		EkiOnOff
	}


pm10010r100AlmlineNetworkLaneAlarmWarning2Index OBJECT-TYPE
	SYNTAX  INTEGER(0..128)
	MAX-ACCESS  read-only
	STATUS current
	DESCRIPTION
        "
        Index definition for the pm10010r100AlmlineNetworkLaneAlarmWarning2 
        table
        "
	::= { pm10010r100AlmlineNetworkLaneAlarmWarning2Entry 1 }


pm10010r100AlmRxLaserBiasHighAlarmPortn OBJECT-TYPE
	SYNTAX  EkiOnOff
	MAX-ACCESS read-only
	STATUS current
	DESCRIPTION
        "
        Line Trscv Rx Bias High Alarm
         :This OID indicates that the Trscv 
        Rx laser bias current is higher 
        than the threshold value written 
        in the Trscv EEPROM <Help> Alarm 
        indicating that the Trscv Rx laser 
        bias current is higher than the 
        threshold value written in the
         Trscv EEPROM <Condtype> RX_LASER_BIAS_HIGH_ALARM 
        <Probcause> receiveFailure (41) 
        <Alarmtype> equipmentAlarm (5)
         <Polarity> (2) 
        "
	::= { pm10010r100AlmlineNetworkLaneAlarmWarning2Entry 17 }


pm10010r100AlmRxLaserBiasHighWarningPortn OBJECT-TYPE
	SYNTAX  EkiOnOff
	MAX-ACCESS read-only
	STATUS current
	DESCRIPTION
        "
        Line Trscv Rx Bias High Warning 
        :This OID indicates that the Trscv 
        Rx laser bias current is higher 
        than the threshold value written 
        in the Trscv EEPROM <Help> Warning 
        indicating that the Trscv Rx laser 
        bias current is higher than the 
        threshold value written in the
         Trscv EEPROM <Condtype> RX_LASER_BIAS_HIGH_WARNING 
        <Probcause> receiveFailure (41) 
        <Alarmtype> equipmentAlarm (5)
         <Polarity> (2) 
        "
	::= { pm10010r100AlmlineNetworkLaneAlarmWarning2Entry 16 }


pm10010r100AlmRxLaserBiasLowWarningPortn OBJECT-TYPE
	SYNTAX  EkiOnOff
	MAX-ACCESS read-only
	STATUS current
	DESCRIPTION
        "
        Line Trscv Rx Bias Low Warning 
        :This OID indicates that the Trscv 
        Rx laser bias current is lower
         than the threshold value written 
        in the Trscv EEPROM <Help> Warning 
        indicating that the Trscv Rx laser 
        bias current is lower than the
         threshold value written in the 
        Trscv EEPROM <Condtype> RX_LASER_BIAS_LOW_WARNING 
        <Probcause> receiveFailure (41) 
        <Alarmtype> equipmentAlarm (5)
         <Polarity> (2) 
        "
	::= { pm10010r100AlmlineNetworkLaneAlarmWarning2Entry 15 }


pm10010r100AlmRxLaserBiasLowAlarmPortn OBJECT-TYPE
	SYNTAX  EkiOnOff
	MAX-ACCESS read-only
	STATUS current
	DESCRIPTION
        "
        Line Trscv Rx Bias Low Alarm :This 
        OID indicates that the Trscv Rx 
        laser bias current is lower than 
        the threshold value written in
         the Trscv EEPROM <Help> Alarm
         indicating that the Trscv Rx laser 
        bias current is lower than the
         threshold value written in the 
        Trscv EEPROM <Condtype> RX_LASER_BIAS_LOW_ALARM 
        <Probcause> receiveFailure (41) 
        <Alarmtype> equipmentAlarm (5)
         <Polarity> (2) 
        "
	::= { pm10010r100AlmlineNetworkLaneAlarmWarning2Entry 14 }


pm10010r100AlmRxLaserOutputHighAlarmPortn OBJECT-TYPE
	SYNTAX  EkiOnOff
	MAX-ACCESS read-only
	STATUS current
	DESCRIPTION
        "
        Line Trscv Rx Output Power High 
        Alarm :This OID indicates that
         the Trscv Rx output power is higher 
        than the threshold value written 
        in the Trscv EEPROM <Help> Alarm 
        indicating that the Trscv Rx output 
        power is higher than the threshold 
        value written in the Trscv EEPROM 
        <Condtype> RX_LASER_OUTPUT_HIGH_ALARM 
        <Probcause> receiveFailure (41) 
        <Alarmtype> equipmentAlarm (5)
         <Polarity> (2) 
        "
	::= { pm10010r100AlmlineNetworkLaneAlarmWarning2Entry 13 }


pm10010r100AlmRxLaserOutputHighWarningPortn OBJECT-TYPE
	SYNTAX  EkiOnOff
	MAX-ACCESS read-only
	STATUS current
	DESCRIPTION
        "
        Line Trscv Rx Output Power High 
        Warning :This OID indicates that 
        the Trscv Rx output power is higher 
        than the threshold value written 
        in the Trscv EEPROM <Help> Warning 
        indicating that the Trscv Rx output 
        power is higher than the threshold 
        value written in the Trscv EEPROM 
        <Condtype> RX_LASER_OUTPUT_HIGH_WARNING 
        <Probcause> receiveFailure (41) 
        <Alarmtype> equipmentAlarm (5)
         <Polarity> (2) 
        "
	::= { pm10010r100AlmlineNetworkLaneAlarmWarning2Entry 12 }


pm10010r100AlmRxLaserOutputLowWarningPortn OBJECT-TYPE
	SYNTAX  EkiOnOff
	MAX-ACCESS read-only
	STATUS current
	DESCRIPTION
        "
        Line Trscv Rx Output Power Low 
        Warning :This OID indicates that 
        the Trscv Rx output power is lower 
        than the threshold value written 
        in the Trscv EEPROM <Help> Warning 
        indicating that the Trscv Rx output 
        power is lower than the threshold 
        value written in the Trscv EEPROM 
        <Condtype> RX_LASER_OUTPUT_LOW_WARNING 
        <Probcause> receiveFailure (41) 
        <Alarmtype> equipmentAlarm (5)
         <Polarity> (2) 
        "
	::= { pm10010r100AlmlineNetworkLaneAlarmWarning2Entry 11 }


pm10010r100AlmRxLaserOutputLowAlarmPortn OBJECT-TYPE
	SYNTAX  EkiOnOff
	MAX-ACCESS read-only
	STATUS current
	DESCRIPTION
        "
        Line Trscv Rx Output Power Low 
        Alarm :This OID indicates that
         the Trscv Rx output power is lower 
        than the threshold value written 
        in the Trscv EEPROM <Help> Alarm 
        indicating that the Trscv Rx output 
        power is lower than the threshold 
        value written in the Trscv EEPROM 
        <Condtype> RX_LASER_OUTPUT_LOW_ALARM 
        <Probcause> receiveFailure (41) 
        <Alarmtype> equipmentAlarm (5)
         <Polarity> (2) 
        "
	::= { pm10010r100AlmlineNetworkLaneAlarmWarning2Entry 10 }


pm10010r100AlmRxLaserTempHighAlarmPortn OBJECT-TYPE
	SYNTAX  EkiOnOff
	MAX-ACCESS read-only
	STATUS current
	DESCRIPTION
        "
        Line Trscv Rx Laser Temp High
         Alarm :This OID indicates that 
        the Trscv Rx Laser Temperature
         is higher than the threshold value 
        written in the Trscv EEPROM <Help> 
        Alarm indicating that the Trscv 
        Rx Laser Temperature is higher
         than the threshold value written 
        in the Trscv EEPROM <Condtype>
         RX_LASER_TEMP_HIGH_ALARM <Probcause> 
        temperatureUnacceptable (51) <Alarmtype> 
        equipmentAlarm (5) <Polarity> (2) 
        "
	::= { pm10010r100AlmlineNetworkLaneAlarmWarning2Entry 9 }


pm10010r100AlmRxLaserTempHighWarningPortn OBJECT-TYPE
	SYNTAX  EkiOnOff
	MAX-ACCESS read-only
	STATUS current
	DESCRIPTION
        "
        Line Trscv Rx Laser Temp High
         Warning :This OID indicates that 
        the Trscv Rx Laser Temperature
         is higher than the threshold value 
        written in the Trscv EEPROM <Help> 
        Warning indicating that the Trscv 
        Rx Laser Temperature is higher
         than the threshold value written 
        in the Trscv EEPROM <Condtype>
         RX_LASER_TEMP_HIGH_WARNING <Probcause> 
        temperatureUnacceptable (51) <Alarmtype> 
        equipmentAlarm (5) <Polarity> (2) 
        "
	::= { pm10010r100AlmlineNetworkLaneAlarmWarning2Entry 8 }


pm10010r100AlmRxLaserTempLowWarningPortn OBJECT-TYPE
	SYNTAX  EkiOnOff
	MAX-ACCESS read-only
	STATUS current
	DESCRIPTION
        "
        Line Trscv Rx Laser Temp Low Warning 
        :This OID indicates that the Trscv 
        Rx Laser Temperature is lower than 
        the threshold value written in
         the Trscv EEPROM <Help> Warning 
        indicating that the Trscv Rx Laser 
        Temperature is lower than the threshold 
        value written in the Trscv EEPROM 
        <Condtype> RX_LASER_TEMP_LOW_WARNING 
        <Probcause> temperatureUnacceptable 
        (51) <Alarmtype> equipmentAlarm 
        (5) <Polarity> (2) 
        "
	::= { pm10010r100AlmlineNetworkLaneAlarmWarning2Entry 7 }


pm10010r100AlmRxLaserTempLowAlarmPortn OBJECT-TYPE
	SYNTAX  EkiOnOff
	MAX-ACCESS read-only
	STATUS current
	DESCRIPTION
        "
        Line Trscv Rx Laser Temp Low Alarm 
        :This OID indicates that the Trscv 
        Rx Laser Temperature is lower than 
        the threshold value written in
         the Trscv EEPROM <Help> Alarm
         indicating that the Trscv Rx Laser 
        Temperature is lower than the threshold 
        value written in the Trscv EEPROM 
        <Condtype> RX_LASER_TEMP_LOW_ALARM 
        <Probcause> temperatureUnacceptable 
        (51) <Alarmtype> equipmentAlarm 
        (5) <Polarity> (2) 
        "
	::= { pm10010r100AlmlineNetworkLaneAlarmWarning2Entry 6 }


pm10010r100AlmTxModulatorBiasHighAlarmPortn OBJECT-TYPE
	SYNTAX  EkiOnOff
	MAX-ACCESS read-only
	STATUS current
	DESCRIPTION
        "
        Line Trscv Tx Modulator Bias High 
        Alarm :This OID indicates that
         the Trscv Tx modulator bias current 
        is higher than the threshold value 
        written in the Trscv EEPROM <Help> 
        Alarm indicating that the Trscv 
        Tx modulator bias current is higher 
        than the threshold value written 
        in the Trscv EEPROM <Condtype>
         TX_MODULATOR_BIAS_HIGH_ALARM <Probcause> 
        transmitterFailure (56) <Alarmtype> 
        equipmentAlarm (5) <Polarity> (2) 
        "
	::= { pm10010r100AlmlineNetworkLaneAlarmWarning2Entry 5 }


pm10010r100AlmTxModulatorBiasHighWarningPortn OBJECT-TYPE
	SYNTAX  EkiOnOff
	MAX-ACCESS read-only
	STATUS current
	DESCRIPTION
        "
        Line Trscv Tx Modulator Bias High 
        Warning :This OID indicates that 
        the Trscv Tx modulator bias current 
        is higher than the threshold value 
        written in the Trscv EEPROM <Help> 
        Warning indicating that the Trscv 
        Tx modulator bias current is higher 
        than the threshold value written 
        in the Trscv EEPROM <Condtype>
         TX_MODULATOR_BIAS_HIGH_WARNING 
        <Probcause> transmitterFailure
         (56) <Alarmtype> equipmentAlarm 
        (5) <Polarity> (2) 
        "
	::= { pm10010r100AlmlineNetworkLaneAlarmWarning2Entry 4 }


pm10010r100AlmTxModulatorBiasLowWarningPortn OBJECT-TYPE
	SYNTAX  EkiOnOff
	MAX-ACCESS read-only
	STATUS current
	DESCRIPTION
        "
        Line Trscv Tx Modulator Bias Low 
        Warning :This OID indicates that 
        the Trscv Tx modulator bias current 
        is lower than the threshold value 
        written in the Trscv EEPROM <Help> 
        Warning indicating that the Trscv 
        Tx modulator bias current is lower 
        than the threshold value written 
        in the Trscv EEPROM <Condtype>
         TX_MODULATOR_BIAS_LOW_WARNING
         <Probcause> transmitterFailure 
        (56) <Alarmtype> equipmentAlarm 
        (5) <Polarity> (2) 
        "
	::= { pm10010r100AlmlineNetworkLaneAlarmWarning2Entry 3 }


pm10010r100AlmTxModulatorBiasLowAlarmPortn OBJECT-TYPE
	SYNTAX  EkiOnOff
	MAX-ACCESS read-only
	STATUS current
	DESCRIPTION
        "
        Line Trscv Tx Modulator Bias Low 
        Alarm :This OID indicates that
         the Trscv Tx modulator bias current 
        is lower than the threshold value 
        written in the Trscv EEPROM <Help> 
        Alarm indicating that the Trscv 
        Tx modulator bias current is lower 
        than the threshold value written 
        in the Trscv EEPROM <Condtype>
         TX_MODULATOR_BIAS_LOW_ALARM <Probcause> 
        transmitterFailure (56) <Alarmtype> 
        equipmentAlarm (5) <Polarity> (2) 
        "
	::= { pm10010r100AlmlineNetworkLaneAlarmWarning2Entry 2 }


--- *********************************************************
---     TABLE for the pm10010r100AlmlineNetworkLaneFault articles
--- *********************************************************

pm10010r100AlmlineNetworkLaneFaultTable OBJECT-TYPE
	SYNTAX  SEQUENCE OF Pm10010r100AlmlineNetworkLaneFaultEntry
	MAX-ACCESS not-accessible
	STATUS current
	DESCRIPTION
        "
        List of pm10010r100AlmlineNetworkLaneFault 
        Article
        "
	::= { pm10010r100AlmLineUrg 136 }


pm10010r100AlmlineNetworkLaneFaultEntry OBJECT-TYPE
	SYNTAX Pm10010r100AlmlineNetworkLaneFaultEntry
	MAX-ACCESS not-accessible
	STATUS current
	DESCRIPTION
        "
        Row definition for the pm10010r100AlmlineNetworkLaneFault 
        table
        "
	INDEX   { pm10010r100AlmlineNetworkLaneFaultIndex }
	::= { pm10010r100AlmlineNetworkLaneFaultTable 1 }


Pm10010r100AlmlineNetworkLaneFaultEntry ::=
	SEQUENCE {
	pm10010r100AlmlineNetworkLaneFaultIndex
		INTEGER,
	pm10010r100AlmLineLaneTecFaultPortn
		EkiOnOff,
	pm10010r100AlmLineLaneWavelengthUnlockedPortn
		EkiOnOff,
	pm10010r100AlmLineLaneApdPowerSupplyPortn
		EkiOnOff,
	pm10010r100AlmLineLaneTxLosfPortn
		EkiOnOff,
	pm10010r100AlmLineLaneTxLolPortn
		EkiOnOff,
	pm10010r100AlmLineLaneRxLosPortn
		EkiOnOff,
	pm10010r100AlmLineLaneRxLolPortn
		EkiOnOff,
	pm10010r100AlmLineLaneRxFifoErrorPortn
		EkiOnOff,
	pm10010r100AlmLineLaneRxTecFaultPortn
		EkiOnOff
	}


pm10010r100AlmlineNetworkLaneFaultIndex OBJECT-TYPE
	SYNTAX  INTEGER(0..128)
	MAX-ACCESS  read-only
	STATUS current
	DESCRIPTION
        "
        Index definition for the pm10010r100AlmlineNetworkLaneFault 
        table
        "
	::= { pm10010r100AlmlineNetworkLaneFaultEntry 1 }


pm10010r100AlmLineLaneTecFaultPortn OBJECT-TYPE
	SYNTAX  EkiOnOff
	MAX-ACCESS read-only
	STATUS current
	DESCRIPTION
        "
        Line Network Lane TEC Fault :This 
        OID indicates a Tx TEC Fault on 
        the Line Trscv Network Lane <Help> 
        Alarm indicating a Tx TEC Fault 
        on the Line Trscv Network Lane
         <Condtype> LINE_LANE_TEC_FAULT 
        <Probcause> transmitterFailure
         (56) <Alarmtype> equipmentAlarm 
        (5) <Polarity> (2) 
        "
	::= { pm10010r100AlmlineNetworkLaneFaultEntry 17 }


pm10010r100AlmLineLaneWavelengthUnlockedPortn OBJECT-TYPE
	SYNTAX  EkiOnOff
	MAX-ACCESS read-only
	STATUS current
	DESCRIPTION
        "
        Line Network Lane Wavelength Unlock 
        :This OID indicates a Wavelength 
        unlock on the Line Trscv Network 
        Lane <Help> Alarm indicating a
         Wavelength unlock on the Line
         Trscv Network Lane <Condtype>
         LINE_LANE_WAVELENGTH_UNLOCKED
         <Probcause> transmitterFailure 
        (56) <Alarmtype> equipmentAlarm 
        (5) <Polarity> (2) 
        "
	::= { pm10010r100AlmlineNetworkLaneFaultEntry 16 }


pm10010r100AlmLineLaneApdPowerSupplyPortn OBJECT-TYPE
	SYNTAX  EkiOnOff
	MAX-ACCESS read-only
	STATUS current
	DESCRIPTION
        "
        Line Network Lane APD Power Supply 
        :This OID indicates an APD Power 
        supply failure on the Line Trscv 
        Network Lane <Help> Alarm indicating 
        an APD Power supply failure on
         the Line Trscv Network Lane <Condtype> 
        LINE_LANE_APD_POWER_SUPPLY <Probcause> 
        transmitterFailure (56) <Alarmtype> 
        equipmentAlarm (5) <Polarity> (2) 
        "
	::= { pm10010r100AlmlineNetworkLaneFaultEntry 15 }


pm10010r100AlmLineLaneTxLosfPortn OBJECT-TYPE
	SYNTAX  EkiOnOff
	MAX-ACCESS read-only
	STATUS current
	DESCRIPTION
        "
        Line Network Lane Tx Loss Of Signal 
        Functionality :This OID indicates 
        a Tx Loss of Signal Functionality 
        on the Line Trscv Network Lane
         <Help> Alarm indicating a Tx Loss 
        of Signal Functionality on the
         Line Trscv Network Lane <Condtype> 
        LINE_LANE_TX_LOSF <Probcause> transmitterFailure 
        (56) <Alarmtype> equipmentAlarm 
        (5) <Polarity> (2) 
        "
	::= { pm10010r100AlmlineNetworkLaneFaultEntry 9 }


pm10010r100AlmLineLaneTxLolPortn OBJECT-TYPE
	SYNTAX  EkiOnOff
	MAX-ACCESS read-only
	STATUS current
	DESCRIPTION
        "
        Line Network Lane Tx Loss Of Lock 
        :This OID indicates a Tx Loss of 
        Lock on the Line Trscv Network
         Lane <Help> Alarm indicating a 
        Tx Loss of Lock on the Line Trscv 
        Network Lane <Condtype> LINE_LANE_TX_LOL 
        <Probcause> transmitterFailure
         (56) <Alarmtype> equipmentAlarm 
        (5) <Polarity> (2) 
        "
	::= { pm10010r100AlmlineNetworkLaneFaultEntry 8 }


pm10010r100AlmLineLaneRxLosPortn OBJECT-TYPE
	SYNTAX  EkiOnOff
	MAX-ACCESS read-only
	STATUS current
	DESCRIPTION
        "
        Line Network Lane Rx Loss Of Signal 
        :This OID indicates a Rx Loss of 
        Signal on the Line Trscv Network 
        Lane <Help> Alarm indicating a
         Rx Loss of Signal on the Line
         Trscv Network Lane <Condtype>
         LINE_LANE_RX_LOS <Probcause> receiveFailure 
        (41) <Alarmtype> physicalViolation 
        (9) <Polarity> (2) 
        "
	::= { pm10010r100AlmlineNetworkLaneFaultEntry 6 }


pm10010r100AlmLineLaneRxLolPortn OBJECT-TYPE
	SYNTAX  EkiOnOff
	MAX-ACCESS read-only
	STATUS current
	DESCRIPTION
        "
        Line Network Lane Rx Loss Of Lock 
        :This OID indicates a Rx Loss of 
        Lock on the Line Trscv Network
         Lane <Help> Alarm indicating a 
        Rx Loss of Lock on the Line Trscv 
        Network Lane <Condtype> LINE_LANE_RX_LOL 
        <Probcause> receiverFailure (42) 
        <Alarmtype> equipmentAlarm (5)
         <Polarity> (2) 
        "
	::= { pm10010r100AlmlineNetworkLaneFaultEntry 5 }


pm10010r100AlmLineLaneRxFifoErrorPortn OBJECT-TYPE
	SYNTAX  EkiOnOff
	MAX-ACCESS read-only
	STATUS current
	DESCRIPTION
        "
        Line Network Lane Rx FIFO Error 
        :This OID indicates a Rx FIFO Error 
        on the Line Trscv Network Lane
         <Help> Alarm indicating a Rx FIFO 
        Error on the Line Trscv Network 
        Lane <Condtype> LINE_LANE_RX_FIFO_ERROR 
        <Probcause> receiverFailure (42) 
        <Alarmtype> equipmentAlarm (5)
         <Polarity> (2) 
        "
	::= { pm10010r100AlmlineNetworkLaneFaultEntry 4 }


pm10010r100AlmLineLaneRxTecFaultPortn OBJECT-TYPE
	SYNTAX  EkiOnOff
	MAX-ACCESS read-only
	STATUS current
	DESCRIPTION
        "
        Line Network Lane Rx TEC Fault 
        :This OID indicates a Rx TEC Fault 
        on the Line Trscv Network Lane
         <Help> Alarm indicating a Rx TEC 
        Fault on the Line Trscv Network 
        Lane <Condtype> LINE_LANE_RX_TEC_FAULT 
        <Probcause> receiverFailure (42) 
        <Alarmtype> equipmentAlarm (5)
         <Polarity> (2) 
        "
	::= { pm10010r100AlmlineNetworkLaneFaultEntry 3 }


--- *********************************************************
---     TABLE for the pm10010r100AlmlineHostLaneFault articles
--- *********************************************************

pm10010r100AlmlineHostLaneFaultTable OBJECT-TYPE
	SYNTAX  SEQUENCE OF Pm10010r100AlmlineHostLaneFaultEntry
	MAX-ACCESS not-accessible
	STATUS current
	DESCRIPTION
        "
        List of pm10010r100AlmlineHostLaneFault 
        Article
        "
	::= { pm10010r100AlmLineUrg 152 }


pm10010r100AlmlineHostLaneFaultEntry OBJECT-TYPE
	SYNTAX Pm10010r100AlmlineHostLaneFaultEntry
	MAX-ACCESS not-accessible
	STATUS current
	DESCRIPTION
        "
        Row definition for the pm10010r100AlmlineHostLaneFault 
        table
        "
	INDEX   { pm10010r100AlmlineHostLaneFaultIndex }
	::= { pm10010r100AlmlineHostLaneFaultTable 1 }


Pm10010r100AlmlineHostLaneFaultEntry ::=
	SEQUENCE {
	pm10010r100AlmlineHostLaneFaultIndex
		INTEGER,
	pm10010r100AlmLineLaneTxFifoErrorPortn
		EkiOnOff,
	pm10010r100AlmLineTxHostLolPortn
		EkiOnOff,
	pm10010r100AlmLineSmIaeDetectedPortn
		EkiOnOff,
	pm10010r100AlmLineSmIaeInsertedPortn
		EkiOnOff,
	pm10010r100AlmLineSmBdiDetectedPortn
		EkiOnOff,
	pm10010r100AlmLineSmBdiInsertedPortn
		EkiOnOff,
	pm10010r100AlmLineLossOfFramePortn
		EkiOnOff,
	pm10010r100AlmLineInputLossOfSignalPortn
		EkiOnOff
	}


pm10010r100AlmlineHostLaneFaultIndex OBJECT-TYPE
	SYNTAX  INTEGER(0..128)
	MAX-ACCESS  read-only
	STATUS current
	DESCRIPTION
        "
        Index definition for the pm10010r100AlmlineHostLaneFault 
        table
        "
	::= { pm10010r100AlmlineHostLaneFaultEntry 1 }


pm10010r100AlmLineLaneTxFifoErrorPortn OBJECT-TYPE
	SYNTAX  EkiOnOff
	MAX-ACCESS read-only
	STATUS current
	DESCRIPTION
        "
        Line Host Lane Tx FIFO Error :This 
        OID indicates a Tx FIFO Error on 
        the Line Trscv Host Lane <Help> 
        Alarm indicating a Tx FIFO Error 
        on the Line Trscv Host Lane <Condtype> 
        LINE_LANE_TX_FIFO_ERROR <Probcause> 
        receiverFailure (42) <Alarmtype> 
        equipmentAlarm (5) <Polarity> (2) 
        "
	::= { pm10010r100AlmlineHostLaneFaultEntry 11 }


pm10010r100AlmLineTxHostLolPortn OBJECT-TYPE
	SYNTAX  EkiOnOff
	MAX-ACCESS read-only
	STATUS current
	DESCRIPTION
        "
        Line Host Lane Tx Loss Of Lock 
        :This OID indicates a Tx Loss of 
        Lock on the Line Trscv Host Lane 
        <Help> Alarm indicating a Tx Loss 
        of Lock on the Line Trscv Host
         Lane <Condtype> LINE_TX_HOST_LOL 
        <Probcause> receiverFailure (42) 
        <Alarmtype> equipmentAlarm (5)
         <Polarity> (2) 
        "
	::= { pm10010r100AlmlineHostLaneFaultEntry 10 }


pm10010r100AlmLineSmIaeDetectedPortn OBJECT-TYPE
	SYNTAX  EkiOnOff
	MAX-ACCESS read-only
	STATUS current
	DESCRIPTION
        "
        Line SM IAE Detected :This OID 
        indicates a SM Incoming Alignment 
        Error is detected on the incoming 
        Line signal <Help> Alarm indicating 
        a SM Incoming Alignment Error is 
        detected on the incoming Line signal 
        <Condtype> LINE_SM_IAE_DETECTED 
        <Probcause> receiveFailure (41) 
        <Alarmtype> integrityViolation
         (7) <Polarity> (2) 
        "
	::= { pm10010r100AlmlineHostLaneFaultEntry 7 }


pm10010r100AlmLineSmIaeInsertedPortn OBJECT-TYPE
	SYNTAX  EkiOnOff
	MAX-ACCESS read-only
	STATUS current
	DESCRIPTION
        "
        Line SM IAE Inserted :This OID 
        indicates a SM Incoming Alignment 
        Error is inserted on the outgoing 
        Line signal <Help> Status indicating 
        a SM Incoming Alignment Error is 
        inserted on the outgoing Line signal 
        <Condtype> LINE_SM_IAE_INSERTED 
        <Probcause> informationalStatus(1000) 
        <Alarmtype> other (1) <Polarity> 
        (2) 
        "
	::= { pm10010r100AlmlineHostLaneFaultEntry 6 }


pm10010r100AlmLineSmBdiDetectedPortn OBJECT-TYPE
	SYNTAX  EkiOnOff
	MAX-ACCESS read-only
	STATUS current
	DESCRIPTION
        "
        Line SM BDI Detected :This OID 
        indicates a SM Backward Defect
         Indication is detected on the
         incoming Line signal <Help> Alarm 
        indicating a SM Backward Defect 
        Indication is detected on the incoming 
        Line signal <Condtype> LINE_SM_BDI_DETECTED 
        <Probcause> receiveFailure (41) 
        <Alarmtype> integrityViolation
         (7) <Polarity> (2) 
        "
	::= { pm10010r100AlmlineHostLaneFaultEntry 5 }


pm10010r100AlmLineSmBdiInsertedPortn OBJECT-TYPE
	SYNTAX  EkiOnOff
	MAX-ACCESS read-only
	STATUS current
	DESCRIPTION
        "
        Line SM BDI Inserted :This OID 
        indicates a SM Backward Defect
         Indication is inserted on the
         outgoing Line signal <Help> Status 
        indicating a SM Backward Defect 
        Indication is inserted on the outgoing 
        Line signal <Condtype> LINE_SM_BDI_INSERTED 
        <Probcause> informationalStatus(1000) 
        <Alarmtype> other (1) <Polarity> 
        (2) 
        "
	::= { pm10010r100AlmlineHostLaneFaultEntry 4 }


pm10010r100AlmLineLossOfFramePortn OBJECT-TYPE
	SYNTAX  EkiOnOff
	MAX-ACCESS read-only
	STATUS current
	DESCRIPTION
        "
        Line Loss Of Frame :This OID indicates 
        the module is not aligned with
         the incoming Line signal <Help> 
        Alarm indicating the module is
         not aligned with the incoming
         Line signal <Condtype> LINE_LOSS_OF_FRAME 
        <Probcause> receiveFailure (41) 
        <Alarmtype> integrityViolation
         (7) <Polarity> (2) 
        "
	::= { pm10010r100AlmlineHostLaneFaultEntry 3 }


pm10010r100AlmLineInputLossOfSignalPortn OBJECT-TYPE
	SYNTAX  EkiOnOff
	MAX-ACCESS read-only
	STATUS current
	DESCRIPTION
        "
        Line Input Loss Of Signal :This 
        OID indicates a Loss of Signal
         is detected on the Line Trscv
         <Help> Alarm indicating a Loss 
        of Signal is detected on the Line 
        Trscv <Condtype> LINE_INPUT_LOSS_OF_SIGNAL 
        <Probcause> receiveFailure (41) 
        <Alarmtype> physicalViolation (9) 
        <Polarity> (2) 
        "
	::= { pm10010r100AlmlineHostLaneFaultEntry 2 }


--- *********************************************************
---     TABLE for the pm10010r100AlmlineNetworkLaneRxOtn articles
--- *********************************************************

pm10010r100AlmlineNetworkLaneRxOtnTable OBJECT-TYPE
	SYNTAX  SEQUENCE OF Pm10010r100AlmlineNetworkLaneRxOtnEntry
	MAX-ACCESS not-accessible
	STATUS current
	DESCRIPTION
        "
        List of pm10010r100AlmlineNetworkLaneRxOtn 
        Article
        "
	::= { pm10010r100AlmLineUrg 168 }


pm10010r100AlmlineNetworkLaneRxOtnEntry OBJECT-TYPE
	SYNTAX Pm10010r100AlmlineNetworkLaneRxOtnEntry
	MAX-ACCESS not-accessible
	STATUS current
	DESCRIPTION
        "
        Row definition for the pm10010r100AlmlineNetworkLaneRxOtn 
        table
        "
	INDEX   { pm10010r100AlmlineNetworkLaneRxOtnIndex }
	::= { pm10010r100AlmlineNetworkLaneRxOtnTable 1 }


Pm10010r100AlmlineNetworkLaneRxOtnEntry ::=
	SEQUENCE {
	pm10010r100AlmlineNetworkLaneRxOtnIndex
		INTEGER,
	pm10010r100AlmLineRxOtnLofPortn
		EkiOnOff,
	pm10010r100AlmLineRxOtnOofPortn
		EkiOnOff,
	pm10010r100AlmLineRxOtnLomPortn
		EkiOnOff,
	pm10010r100AlmLineRxOtnOomPortn
		EkiOnOff,
	pm10010r100AlmLineRxOtnIaePortn
		EkiOnOff,
	pm10010r100AlmLineRxSmBdiPortn
		EkiOnOff,
	pm10010r100AlmLineRxOtnOtuAisPortn
		EkiOnOff,
	pm10010r100AlmLineRxOtnOduAisPortn
		EkiOnOff
	}


pm10010r100AlmlineNetworkLaneRxOtnIndex OBJECT-TYPE
	SYNTAX  INTEGER(0..128)
	MAX-ACCESS  read-only
	STATUS current
	DESCRIPTION
        "
        Index definition for the pm10010r100AlmlineNetworkLaneRxOtn 
        table
        "
	::= { pm10010r100AlmlineNetworkLaneRxOtnEntry 1 }


pm10010r100AlmLineRxOtnLofPortn OBJECT-TYPE
	SYNTAX  EkiOnOff
	MAX-ACCESS read-only
	STATUS current
	DESCRIPTION
        "
        Line Network Rx LOF :This OID
         indicates a Loss of Frame is detected 
        on the Rx Network interface of
         the Line Trscv <Help> Alarm indicating 
        a Loss of Frame is detected on
         the Rx Network interface of the 
        Line Trscv <Condtype> LINE_RX_OTN_LOF 
        <Probcause> receiveFailure (41) 
        <Alarmtype> equipmentAlarm (5)
         <Polarity> (2) 
        "
	::= { pm10010r100AlmlineNetworkLaneRxOtnEntry 17 }


pm10010r100AlmLineRxOtnOofPortn OBJECT-TYPE
	SYNTAX  EkiOnOff
	MAX-ACCESS read-only
	STATUS current
	DESCRIPTION
        "
        Line Network Rx OOF :This OID
         indicates an Out of Frame is detected 
        on the Rx Network interface of
         the Line Trscv <Help> Alarm indicating 
        an Out of Frame is detected on
         the Rx Network interface of the 
        Line Trscv <Condtype> LINE_RX_OTN_OOF 
        <Probcause> receiveFailure (41) 
        <Alarmtype> equipmentAlarm (5)
         <Polarity> (2) 
        "
	::= { pm10010r100AlmlineNetworkLaneRxOtnEntry 16 }


pm10010r100AlmLineRxOtnLomPortn OBJECT-TYPE
	SYNTAX  EkiOnOff
	MAX-ACCESS read-only
	STATUS current
	DESCRIPTION
        "
        Line Network Rx LOM :This OID
         indicates a Loss of Multiframe 
        is detected on the Rx Network interface 
        of the Line Trscv <Help> Alarm
         indicating a Loss of Multiframe 
        is detected on the Rx Network interface 
        of the Line Trscv <Condtype> LINE_RX_OTN_LOM 
        <Probcause> receiveFailure (41) 
        <Alarmtype> equipmentAlarm (5)
         <Polarity> (2) 
        "
	::= { pm10010r100AlmlineNetworkLaneRxOtnEntry 15 }


pm10010r100AlmLineRxOtnOomPortn OBJECT-TYPE
	SYNTAX  EkiOnOff
	MAX-ACCESS read-only
	STATUS current
	DESCRIPTION
        "
        Line Network Rx OOM :This OID
         indicates an Out of Multiframe 
        is detected on the Rx Network interface 
        of the Line Trscv <Help> Alarm
         indicating an Out of Multiframe 
        is detected on the Rx Network interface 
        of the Line Trscv <Condtype> LINE_RX_OTN_OOM 
        <Probcause> receiveFailure (41) 
        <Alarmtype> equipmentAlarm (5)
         <Polarity> (2) 
        "
	::= { pm10010r100AlmlineNetworkLaneRxOtnEntry 14 }


pm10010r100AlmLineRxOtnIaePortn OBJECT-TYPE
	SYNTAX  EkiOnOff
	MAX-ACCESS read-only
	STATUS current
	DESCRIPTION
        "
        Line Network Rx IAE :This OID
         indicates an Incoming Alignment 
        Error is detected on the Rx Network 
        interface of the Line Trscv <Help> 
        Alarm indicating an Incoming Alignment 
        Error is detected on the Rx Network 
        interface of the Line Trscv <Condtype> 
        LINE_RX_OTN_IAE <Probcause> receiveFailure 
        (41) <Alarmtype> equipmentAlarm 
        (5) <Polarity> (2) 
        "
	::= { pm10010r100AlmlineNetworkLaneRxOtnEntry 13 }


pm10010r100AlmLineRxSmBdiPortn OBJECT-TYPE
	SYNTAX  EkiOnOff
	MAX-ACCESS read-only
	STATUS current
	DESCRIPTION
        "
        Line Network Rx SM BDI :This OID 
        indicates an SM Backward Defect 
        Indication is detected on the Rx 
        Network interface of the Line Trscv 
        <Help> Alarm indicating an SM Backward 
        Defect Indication is detected on 
        the Rx Network interface of the 
        Line Trscv <Condtype> LINE_RX_SM_BDI 
        <Probcause> informationalStatus(1000) 
        <Alarmtype> other (1) <Polarity> 
        (2) 
        "
	::= { pm10010r100AlmlineNetworkLaneRxOtnEntry 12 }


pm10010r100AlmLineRxOtnOtuAisPortn OBJECT-TYPE
	SYNTAX  EkiOnOff
	MAX-ACCESS read-only
	STATUS current
	DESCRIPTION
        "
        Line Network Rx OTU AIS :This
         OID indicates an OTU This OID
         Indication Signal is detected
         on the Rx Network interface of 
        the Line Trscv <Help> Alarm indicating 
        an OTU Alarm Indication Signal
         is detected on the Rx Network
         interface of the Line Trscv <Condtype> 
        LINE_RX_OTN_OTU_AIS <Probcause> 
        receiveFailure (41) <Alarmtype> 
        equipmentAlarm (5) <Polarity> (2) 
        "
	::= { pm10010r100AlmlineNetworkLaneRxOtnEntry 11 }


pm10010r100AlmLineRxOtnOduAisPortn OBJECT-TYPE
	SYNTAX  EkiOnOff
	MAX-ACCESS read-only
	STATUS current
	DESCRIPTION
        "
        Line Network Rx ODU AIS :This
         OID indicates an ODU This OID
         Indication Signal is detected
         on the Rx Network interface of 
        the Line Trscv <Help> Alarm indicating 
        an ODU Alarm Indication Signal
         is detected on the Rx Network
         interface of the Line Trscv <Condtype> 
        LINE_RX_OTN_ODU_AIS <Probcause> 
        receiveFailure (41) <Alarmtype> 
        equipmentAlarm (5) <Polarity> (2) 
        "
	::= { pm10010r100AlmlineNetworkLaneRxOtnEntry 10 }


--- *********************************************************
---     TABLE for the pm10010r100AlmlineHostLaneTxOtn articles
--- *********************************************************

pm10010r100AlmlineHostLaneTxOtnTable OBJECT-TYPE
	SYNTAX  SEQUENCE OF Pm10010r100AlmlineHostLaneTxOtnEntry
	MAX-ACCESS not-accessible
	STATUS current
	DESCRIPTION
        "
        List of pm10010r100AlmlineHostLaneTxOtn 
        Article
        "
	::= { pm10010r100AlmLineUrg 184 }


pm10010r100AlmlineHostLaneTxOtnEntry OBJECT-TYPE
	SYNTAX Pm10010r100AlmlineHostLaneTxOtnEntry
	MAX-ACCESS not-accessible
	STATUS current
	DESCRIPTION
        "
        Row definition for the pm10010r100AlmlineHostLaneTxOtn 
        table
        "
	INDEX   { pm10010r100AlmlineHostLaneTxOtnIndex }
	::= { pm10010r100AlmlineHostLaneTxOtnTable 1 }


Pm10010r100AlmlineHostLaneTxOtnEntry ::=
	SEQUENCE {
	pm10010r100AlmlineHostLaneTxOtnIndex
		INTEGER,
	pm10010r100AlmLineTxOtnLofPortn
		EkiOnOff,
	pm10010r100AlmLineTxOtnOofPortn
		EkiOnOff,
	pm10010r100AlmLineTxOtnLomPortn
		EkiOnOff,
	pm10010r100AlmLineTxOtnOomPortn
		EkiOnOff,
	pm10010r100AlmLineTxOtnIaePortn
		EkiOnOff,
	pm10010r100AlmLineTxSmBdiPortn
		EkiOnOff,
	pm10010r100AlmLineTxOtnOtuAisPortn
		EkiOnOff,
	pm10010r100AlmLineTxOtnOduAisPortn
		EkiOnOff
	}


pm10010r100AlmlineHostLaneTxOtnIndex OBJECT-TYPE
	SYNTAX  INTEGER(0..128)
	MAX-ACCESS  read-only
	STATUS current
	DESCRIPTION
        "
        Index definition for the pm10010r100AlmlineHostLaneTxOtn 
        table
        "
	::= { pm10010r100AlmlineHostLaneTxOtnEntry 1 }


pm10010r100AlmLineTxOtnLofPortn OBJECT-TYPE
	SYNTAX  EkiOnOff
	MAX-ACCESS read-only
	STATUS current
	DESCRIPTION
        "
        Line Host Tx LOF :This OID indicates 
        a Loss of Frame is detected on
         the Tx Host interface of the Line 
        Trscv <Help> Alarm indicating a 
        Loss of Frame is detected on the 
        Tx Host interface of the Line Trscv 
        <Condtype> LINE_TX_OTN_LOF <Probcause> 
        receiveFailure (41) <Alarmtype> 
        equipmentAlarm (5) <Polarity> (2) 
        "
	::= { pm10010r100AlmlineHostLaneTxOtnEntry 17 }


pm10010r100AlmLineTxOtnOofPortn OBJECT-TYPE
	SYNTAX  EkiOnOff
	MAX-ACCESS read-only
	STATUS current
	DESCRIPTION
        "
        Line Host Tx OOF :This OID indicates 
        an Out of Frame is detected on
         the Tx Host interface of the Line 
        Trscv <Help> Alarm indicating an 
        Out of Frame is detected on the 
        Tx Host interface of the Line Trscv 
        <Condtype> LINE_TX_OTN_OOF <Probcause> 
        receiveFailure (41) <Alarmtype> 
        equipmentAlarm (5) <Polarity> (2) 
        "
	::= { pm10010r100AlmlineHostLaneTxOtnEntry 16 }


pm10010r100AlmLineTxOtnLomPortn OBJECT-TYPE
	SYNTAX  EkiOnOff
	MAX-ACCESS read-only
	STATUS current
	DESCRIPTION
        "
        Line Host Tx LOM :This OID indicates 
        a Loss of Multiframe is detected 
        on the Tx Host interface of the 
        Line Trscv <Help> Alarm indicating 
        a Loss of Multiframe is detected 
        on the Tx Host interface of the 
        Line Trscv <Condtype> LINE_TX_OTN_LOM 
        <Probcause> receiveFailure (41) 
        <Alarmtype> equipmentAlarm (5)
         <Polarity> (2) 
        "
	::= { pm10010r100AlmlineHostLaneTxOtnEntry 15 }


pm10010r100AlmLineTxOtnOomPortn OBJECT-TYPE
	SYNTAX  EkiOnOff
	MAX-ACCESS read-only
	STATUS current
	DESCRIPTION
        "
        Line Host Tx OOM :This OID indicates 
        an Out of Multiframe is detected 
        on the Tx Host interface of the 
        Line Trscv <Help> Alarm indicating 
        an Out of Multiframe is detected 
        on the Tx Host interface of the 
        Line Trscv <Condtype> LINE_TX_OTN_OOM 
        <Probcause> receiveFailure (41) 
        <Alarmtype> equipmentAlarm (5)
         <Polarity> (2) 
        "
	::= { pm10010r100AlmlineHostLaneTxOtnEntry 14 }


pm10010r100AlmLineTxOtnIaePortn OBJECT-TYPE
	SYNTAX  EkiOnOff
	MAX-ACCESS read-only
	STATUS current
	DESCRIPTION
        "
        Line Host Tx IAE :This OID indicates 
        an Incoming Alignment Error is
         detected on the Tx Host interface 
        of the Line Trscv <Help> Alarm
         indicating an Incoming Alignment 
        Error is detected on the Tx Host 
        interface of the Line Trscv <Condtype> 
        LINE_TX_OTN_IAE <Probcause> receiveFailure 
        (41) <Alarmtype> equipmentAlarm 
        (5) <Polarity> (2) 
        "
	::= { pm10010r100AlmlineHostLaneTxOtnEntry 13 }


pm10010r100AlmLineTxSmBdiPortn OBJECT-TYPE
	SYNTAX  EkiOnOff
	MAX-ACCESS read-only
	STATUS current
	DESCRIPTION
        "
        Line Host Tx SM BDI :This OID
         indicates an SM Backward Defect 
        Indication is detected on the Tx 
        Host interface of the Line Trscv 
        <Help> Alarm indicating an SM Backward 
        Defect Indication is detected on 
        the Tx Host interface of the Line 
        Trscv <Condtype> LINE_TX_SM_BDI 
        <Probcause> informationalStatus(1000) 
        <Alarmtype> other (1) <Polarity> 
        (2) 
        "
	::= { pm10010r100AlmlineHostLaneTxOtnEntry 12 }


pm10010r100AlmLineTxOtnOtuAisPortn OBJECT-TYPE
	SYNTAX  EkiOnOff
	MAX-ACCESS read-only
	STATUS current
	DESCRIPTION
        "
        Line Host Tx OTU AIS :This OID 
        indicates an OTU This OID Indication 
        Signal is detected on the Tx Host 
        interface of the Line Trscv <Help> 
        Alarm indicating an OTU Alarm Indication 
        Signal is detected on the Tx Host 
        interface of the Line Trscv <Condtype> 
        LINE_TX_OTN_OTU_AIS <Probcause> 
        receiveFailure (41) <Alarmtype> 
        equipmentAlarm (5) <Polarity> (2) 
        "
	::= { pm10010r100AlmlineHostLaneTxOtnEntry 11 }


pm10010r100AlmLineTxOtnOduAisPortn OBJECT-TYPE
	SYNTAX  EkiOnOff
	MAX-ACCESS read-only
	STATUS current
	DESCRIPTION
        "
        Line Host Tx ODU AIS :This OID 
        indicates an ODU This OID Indication 
        Signal is detected on the Tx Host 
        interface of the Line Trscv <Help> 
        Alarm indicating an ODU Alarm Indication 
        Signal is detected on the Tx Host 
        interface of the Line Trscv <Condtype> 
        LINE_TX_OTN_ODU_AIS <Probcause> 
        receiveFailure (41) <Alarmtype> 
        equipmentAlarm (5) <Polarity> (2) 
        "
	::= { pm10010r100AlmlineHostLaneTxOtnEntry 10 }


--- *********************************************************
---     TABLE for the pm10010r100AlmclientSfpAlmDdm articles
--- *********************************************************

pm10010r100AlmclientSfpAlmDdmTable OBJECT-TYPE
	SYNTAX  SEQUENCE OF Pm10010r100AlmclientSfpAlmDdmEntry
	MAX-ACCESS not-accessible
	STATUS current
	DESCRIPTION
        "
        List of pm10010r100AlmclientSfpAlmDdm 
        Article
        "
	::= { pm10010r100AlmClientUrg 216 }


pm10010r100AlmclientSfpAlmDdmEntry OBJECT-TYPE
	SYNTAX Pm10010r100AlmclientSfpAlmDdmEntry
	MAX-ACCESS not-accessible
	STATUS current
	DESCRIPTION
        "
        Row definition for the pm10010r100AlmclientSfpAlmDdm 
        table
        "
	INDEX   { pm10010r100AlmclientSfpAlmDdmIndex }
	::= { pm10010r100AlmclientSfpAlmDdmTable 1 }


Pm10010r100AlmclientSfpAlmDdmEntry ::=
	SEQUENCE {
	pm10010r100AlmclientSfpAlmDdmIndex
		INTEGER,
	pm10010r100AlmRxPwrHighAlaPortn
		EkiOnOff,
	pm10010r100AlmRxPwrLowAlaPortn
		EkiOnOff,
	pm10010r100AlmTempHighAlaPortn
		EkiOnOff,
	pm10010r100AlmTempLowAlaPortn
		EkiOnOff,
	pm10010r100AlmVccHighAlaPortn
		EkiOnOff,
	pm10010r100AlmVccLowAlaPortn
		EkiOnOff,
	pm10010r100AlmTxBiasHighAlaPortn
		EkiOnOff,
	pm10010r100AlmTxBiasLowAlaPortn
		EkiOnOff,
	pm10010r100AlmTxPwrHighAlaPortn
		EkiOnOff,
	pm10010r100AlmTxPwrLowAlaPortn
		EkiOnOff
	}


pm10010r100AlmclientSfpAlmDdmIndex OBJECT-TYPE
	SYNTAX  INTEGER(0..128)
	MAX-ACCESS  read-only
	STATUS current
	DESCRIPTION
        "
        Index definition for the pm10010r100AlmclientSfpAlmDdm 
        table
        "
	::= { pm10010r100AlmclientSfpAlmDdmEntry 1 }


pm10010r100AlmRxPwrHighAlaPortn OBJECT-TYPE
	SYNTAX  EkiOnOff
	MAX-ACCESS read-only
	STATUS current
	DESCRIPTION
        "
        Client Trscv Rx Power High :This 
        OID indicates that the Trscv input 
        power of port is higher than the 
        threshold value written in the
         Trscv EEPROM <Help> Alarm indicating 
        that the Trscv input power of port 
        is higher than the threshold value 
        written in the Trscv EEPROM <Condtype> 
        RX_PWR_HIGH_ALA_1 <Probcause> receiveFailure 
        (41) <Alarmtype> equipmentAlarm 
        (5) <Polarity> (2) 
        "
	::= { pm10010r100AlmclientSfpAlmDdmEntry 17 }


pm10010r100AlmRxPwrLowAlaPortn OBJECT-TYPE
	SYNTAX  EkiOnOff
	MAX-ACCESS read-only
	STATUS current
	DESCRIPTION
        "
        Client Trscv Rx Power Low :This 
        OID indicates that the Trscv input 
        power of port is lower than the 
        threshold value written in the
         Trscv EEPROM <Help> Alarm indicating 
        that the Trscv input power of port 
        is lower than the threshold value 
        written in the Trscv EEPROM <Condtype> 
        RX_PWR_LOW_ALA_1 <Probcause> receiveFailure 
        (41) <Alarmtype> equipmentAlarm 
        (5) <Polarity> (2) 
        "
	::= { pm10010r100AlmclientSfpAlmDdmEntry 16 }


pm10010r100AlmTempHighAlaPortn OBJECT-TYPE
	SYNTAX  EkiOnOff
	MAX-ACCESS read-only
	STATUS current
	DESCRIPTION
        "
        Client Trscv Temp High :This OID 
        indicates that the Trscv temperature 
        of port is higher than the threshold 
        value written in the Trscv EEPROM 
        <Help> Alarm indicating that the 
        Trscv temperature of port is higher 
        than the threshold value written 
        in the Trscv EEPROM <Condtype>
         TEMP_HIGH_ALA_1 <Probcause> temperatureUnacceptable 
        (51) <Alarmtype> equipmentAlarm 
        (5) <Polarity> (2) 
        "
	::= { pm10010r100AlmclientSfpAlmDdmEntry 9 }


pm10010r100AlmTempLowAlaPortn OBJECT-TYPE
	SYNTAX  EkiOnOff
	MAX-ACCESS read-only
	STATUS current
	DESCRIPTION
        "
        Client Trscv Temp Low :This OID 
        indicates that the Trscv temperature 
        of port is lower than the threshold 
        value written in the Trscv EEPROM 
        <Help> Alarm indicating that the 
        Trscv temperature of port is lower 
        than the threshold value written 
        in the Trscv EEPROM <Condtype>
         TEMP_LOW_ALA_1 <Probcause> temperatureUnacceptable 
        (51) <Alarmtype> equipmentAlarm 
        (5) <Polarity> (2) 
        "
	::= { pm10010r100AlmclientSfpAlmDdmEntry 8 }


pm10010r100AlmVccHighAlaPortn OBJECT-TYPE
	SYNTAX  EkiOnOff
	MAX-ACCESS read-only
	STATUS current
	DESCRIPTION
        "
        Client Trscv Power Supply High 
        :This OID indicates that the Trscv 
        power supply of port is higher
         than the threshold value written 
        in the Trscv EEPROM <Help> Alarm 
        indicating that the Trscv power 
        supply of port is higher than the 
        threshold value written in the
         Trscv EEPROM <Condtype> VCC_HIGH_ALA_1 
        <Probcause> powerProblem (36) <Alarmtype> 
        equipmentAlarm (5) <Polarity> (2) 
        "
	::= { pm10010r100AlmclientSfpAlmDdmEntry 7 }


pm10010r100AlmVccLowAlaPortn OBJECT-TYPE
	SYNTAX  EkiOnOff
	MAX-ACCESS read-only
	STATUS current
	DESCRIPTION
        "
        Client Trscv Power Supply Low
         :This OID indicates that the Trscv 
        power supply of port is lower than 
        the threshold value written in
         the Trscv EEPROM <Help> Alarm
         indicating that the Trscv power 
        supply of port is lower than the 
        threshold value written in the
         Trscv EEPROM <Condtype> VCC_LOW_ALA_1 
        <Probcause> powerProblem (36) <Alarmtype> 
        equipmentAlarm (5) <Polarity> (2) 
        "
	::= { pm10010r100AlmclientSfpAlmDdmEntry 6 }


pm10010r100AlmTxBiasHighAlaPortn OBJECT-TYPE
	SYNTAX  EkiOnOff
	MAX-ACCESS read-only
	STATUS current
	DESCRIPTION
        "
        Client Trscv Bias High :This OID 
        indicates that the Trscv laser
         bias current of port is higher 
        than the threshold value written 
        in the Trscv EEPROM <Help> Alarm 
        indicating that the Trscv laser 
        bias current of port is higher
         than the threshold value written 
        in the Trscv EEPROM <Condtype>
         TX_BIAS_HIGH_ALA_1 <Probcause> 
        transmitterFailure (56) <Alarmtype> 
        equipmentAlarm (5) <Polarity> (2) 
        "
	::= { pm10010r100AlmclientSfpAlmDdmEntry 5 }


pm10010r100AlmTxBiasLowAlaPortn OBJECT-TYPE
	SYNTAX  EkiOnOff
	MAX-ACCESS read-only
	STATUS current
	DESCRIPTION
        "
        Client Trscv Bias Low :This OID 
        indicates that the Trscv laser
         bias current of port is lower
         than the threshold value written 
        in the Trscv EEPROM <Help> Alarm 
        indicating that the Trscv laser 
        bias current of port is lower than 
        the threshold value written in
         the Trscv EEPROM <Condtype> TX_BIAS_LOW_ALA_1 
        <Probcause> transmitterFailure
         (56) <Alarmtype> equipmentAlarm 
        (5) <Polarity> (2) 
        "
	::= { pm10010r100AlmclientSfpAlmDdmEntry 4 }


pm10010r100AlmTxPwrHighAlaPortn OBJECT-TYPE
	SYNTAX  EkiOnOff
	MAX-ACCESS read-only
	STATUS current
	DESCRIPTION
        "
        Client Trscv Tx Power High :This 
        OID indicates that the Trscv output 
        power of port is higher than the 
        threshold value written in the
         Trscv EEPROM <Help> Alarm indicating 
        that the Trscv output power of
         port is higher than the threshold 
        value written in the Trscv EEPROM 
        <Condtype> TX_PWR_HIGH_ALA_1 <Probcause> 
        transmitterFailure (56) <Alarmtype> 
        equipmentAlarm (5) <Polarity> (2) 
        "
	::= { pm10010r100AlmclientSfpAlmDdmEntry 3 }


pm10010r100AlmTxPwrLowAlaPortn OBJECT-TYPE
	SYNTAX  EkiOnOff
	MAX-ACCESS read-only
	STATUS current
	DESCRIPTION
        "
        Client Trscv Tx Power Low :This 
        OID indicates that the Trscv output 
        power of port is lower than the 
        threshold value written in the
         Trscv EEPROM <Help> Alarm indicating 
        that the Trscv output power of
         port is lower than the threshold 
        value written in the Trscv EEPROM 
        <Condtype> TX_PWR_LOW_ALA_1 <Probcause> 
        transmitterFailure (56) <Alarmtype> 
        equipmentAlarm (5) <Polarity> (2) 
        "
	::= { pm10010r100AlmclientSfpAlmDdmEntry 2 }


--- *********************************************************
---     TABLE for the pm10010r100AlmclientSfpWarnDdm articles
--- *********************************************************

pm10010r100AlmclientSfpWarnDdmTable OBJECT-TYPE
	SYNTAX  SEQUENCE OF Pm10010r100AlmclientSfpWarnDdmEntry
	MAX-ACCESS not-accessible
	STATUS current
	DESCRIPTION
        "
        List of pm10010r100AlmclientSfpWarnDdm 
        Article
        "
	::= { pm10010r100AlmClientNurg 232 }


pm10010r100AlmclientSfpWarnDdmEntry OBJECT-TYPE
	SYNTAX Pm10010r100AlmclientSfpWarnDdmEntry
	MAX-ACCESS not-accessible
	STATUS current
	DESCRIPTION
        "
        Row definition for the pm10010r100AlmclientSfpWarnDdm 
        table
        "
	INDEX   { pm10010r100AlmclientSfpWarnDdmIndex }
	::= { pm10010r100AlmclientSfpWarnDdmTable 1 }


Pm10010r100AlmclientSfpWarnDdmEntry ::=
	SEQUENCE {
	pm10010r100AlmclientSfpWarnDdmIndex
		INTEGER,
	pm10010r100AlmRxPwrHighWngPortn
		EkiOnOff,
	pm10010r100AlmRxPwrLowWngPortn
		EkiOnOff,
	pm10010r100AlmTempHighWngPortn
		EkiOnOff,
	pm10010r100AlmTempLowWngPortn
		EkiOnOff,
	pm10010r100AlmVccHighWngPortn
		EkiOnOff,
	pm10010r100AlmVccLowWngPortn
		EkiOnOff,
	pm10010r100AlmTxBiasHighWngPortn
		EkiOnOff,
	pm10010r100AlmTxBiasLowWngPortn
		EkiOnOff,
	pm10010r100AlmTxPwrHighWngPortn
		EkiOnOff,
	pm10010r100AlmTxPwLowWngPortn
		EkiOnOff
	}


pm10010r100AlmclientSfpWarnDdmIndex OBJECT-TYPE
	SYNTAX  INTEGER(0..128)
	MAX-ACCESS  read-only
	STATUS current
	DESCRIPTION
        "
        Index definition for the pm10010r100AlmclientSfpWarnDdm 
        table
        "
	::= { pm10010r100AlmclientSfpWarnDdmEntry 1 }


pm10010r100AlmRxPwrHighWngPortn OBJECT-TYPE
	SYNTAX  EkiOnOff
	MAX-ACCESS read-only
	STATUS current
	DESCRIPTION
        "
        Client Trscv Rx Power High Warning 
        :This OID indicates that the Trscv 
        input power is higher than the
         threshold value written in the 
        Trscv EEPROM <Help> Warning indicating 
        that the Trscv input power is higher 
        than the threshold value written 
        in the Trscv EEPROM <Condtype>
         RX_PWR_HIGH_WNG_1 <Probcause>
         receiveFailure (41) <Alarmtype> 
        equipmentAlarm (5) <Polarity> (2) 
        "
	::= { pm10010r100AlmclientSfpWarnDdmEntry 17 }


pm10010r100AlmRxPwrLowWngPortn OBJECT-TYPE
	SYNTAX  EkiOnOff
	MAX-ACCESS read-only
	STATUS current
	DESCRIPTION
        "
        Client Trscv Rx Power Low Warning 
        :This OID indicates that the Trscv 
        input power is lower than the threshold 
        value written in the Trscv EEPROM 
        <Help> Warning indicating that
         the Trscv input power is lower 
        than the threshold value written 
        in the Trscv EEPROM <Condtype>
         RX_PWR_LOW_WNG_1 <Probcause> receiveFailure 
        (41) <Alarmtype> equipmentAlarm 
        (5) <Polarity> (2) 
        "
	::= { pm10010r100AlmclientSfpWarnDdmEntry 16 }


pm10010r100AlmTempHighWngPortn OBJECT-TYPE
	SYNTAX  EkiOnOff
	MAX-ACCESS read-only
	STATUS current
	DESCRIPTION
        "
        Client Trscv Temp High Warning 
        :This OID indicates that the Trscv 
        temperature is higher than the
         threshold value written in the 
        Trscv EEPROM <Help> Warning indicating 
        that the Trscv temperature is higher 
        than the threshold value written 
        in the Trscv EEPROM <Condtype>
         TEMP_HIGH_WNG_1 <Probcause> temperatureUnacceptable 
        (51) <Alarmtype> equipmentAlarm 
        (5) <Polarity> (2) 
        "
	::= { pm10010r100AlmclientSfpWarnDdmEntry 9 }


pm10010r100AlmTempLowWngPortn OBJECT-TYPE
	SYNTAX  EkiOnOff
	MAX-ACCESS read-only
	STATUS current
	DESCRIPTION
        "
        Client Trscv Temp Low Warning
         :This OID indicates that the Trscv 
        temperature is lower than the threshold 
        value written in the Trscv EEPROM 
        <Help> Warning indicating that
         the Trscv temperature is lower 
        than the threshold value written 
        in the Trscv EEPROM <Condtype>
         TEMP_LOW_WNG_1 <Probcause> temperatureUnacceptable 
        (51) <Alarmtype> equipmentAlarm 
        (5) <Polarity> (2) 
        "
	::= { pm10010r100AlmclientSfpWarnDdmEntry 8 }


pm10010r100AlmVccHighWngPortn OBJECT-TYPE
	SYNTAX  EkiOnOff
	MAX-ACCESS read-only
	STATUS current
	DESCRIPTION
        "
        Client Trscv Power Supply High 
        Warning :This OID indicates that 
        the Trscv power supply is higher 
        than the threshold value written 
        in the Trscv EEPROM <Help> Warning 
        indicating that the Trscv power 
        supply is higher than the threshold 
        value written in the Trscv EEPROM 
        <Condtype> VCC_HIGH_WNG_1 <Probcause> 
        powerProblem (36) <Alarmtype> equipmentAlarm 
        (5) <Polarity> (2) 
        "
	::= { pm10010r100AlmclientSfpWarnDdmEntry 7 }


pm10010r100AlmVccLowWngPortn OBJECT-TYPE
	SYNTAX  EkiOnOff
	MAX-ACCESS read-only
	STATUS current
	DESCRIPTION
        "
        Client Trscv Power Supply Low
         Warning :This OID indicates that 
        the Trscv power supply is lower 
        than the threshold value written 
        in the Trscv EEPROM <Help> Warning 
        indicating that the Trscv power 
        supply is lower than the threshold 
        value written in the Trscv EEPROM 
        <Condtype> VCC_LOW_WNG_1 <Probcause> 
        powerProblem (36) <Alarmtype> equipmentAlarm 
        (5) <Polarity> (2) 
        "
	::= { pm10010r100AlmclientSfpWarnDdmEntry 6 }


pm10010r100AlmTxBiasHighWngPortn OBJECT-TYPE
	SYNTAX  EkiOnOff
	MAX-ACCESS read-only
	STATUS current
	DESCRIPTION
        "
        Client Trscv Bias High Warning 
        :This OID indicates that the Trscv 
        laser bias current is higher than 
        the threshold value written in
         the Trscv EEPROM <Help> Warning 
        indicating that the Trscv laser 
        bias current is higher than the 
        threshold value written in the
         Trscv EEPROM <Condtype> TX_BIAS_HIGH_WNG_1 
        <Probcause> transmitterFailure
         (56) <Alarmtype> equipmentAlarm 
        (5) <Polarity> (2) 
        "
	::= { pm10010r100AlmclientSfpWarnDdmEntry 5 }


pm10010r100AlmTxBiasLowWngPortn OBJECT-TYPE
	SYNTAX  EkiOnOff
	MAX-ACCESS read-only
	STATUS current
	DESCRIPTION
        "
        Client Trscv Bias Low Warning
         :This OID indicates that the Trscv 
        laser bias current is lower than 
        the threshold value written in
         the Trscv EEPROM <Help> Warning 
        indicating that the Trscv laser 
        bias current is lower than the
         threshold value written in the 
        Trscv EEPROM <Condtype> TX_BIAS_LOW_WNG_1 
        <Probcause> transmitterFailure
         (56) <Alarmtype> equipmentAlarm 
        (5) <Polarity> (2) 
        "
	::= { pm10010r100AlmclientSfpWarnDdmEntry 4 }


pm10010r100AlmTxPwrHighWngPortn OBJECT-TYPE
	SYNTAX  EkiOnOff
	MAX-ACCESS read-only
	STATUS current
	DESCRIPTION
        "
        Client Trscv Tx Power High Warning 
        :This OID indicates that the Trscv 
        output power is higher than the 
        threshold value written in the
         Trscv EEPROM <Help> Warning indicating 
        that the Trscv output power is
         higher than the threshold value 
        written in the Trscv EEPROM <Condtype> 
        TX_PWR_HIGH_WNG_1 <Probcause> transmitterFailure 
        (56) <Alarmtype> equipmentAlarm 
        (5) <Polarity> (2) 
        "
	::= { pm10010r100AlmclientSfpWarnDdmEntry 3 }


pm10010r100AlmTxPwLowWngPortn OBJECT-TYPE
	SYNTAX  EkiOnOff
	MAX-ACCESS read-only
	STATUS current
	DESCRIPTION
        "
        Client Trscv Tx Power Low Warning 
        :This OID indicates that the Trscv 
        output power is lower than the
         threshold value written in the 
        Trscv EEPROM <Help> Warning indicating 
        that the Trscv output power is
         lower than the threshold value 
        written in the Trscv EEPROM <Condtype> 
        TX_PW_LOW_WNG_1 <Probcause> transmitterFailure 
        (56) <Alarmtype> equipmentAlarm 
        (5) <Polarity> (2) 
        "
	::= { pm10010r100AlmclientSfpWarnDdmEntry 2 }







--- *****************************************************
--- $$$$$$$$$$$$$$$$$$$$$$$$$$$$$$$$$$$$$$$$$$$$$$$$$$$$$
---     CONTROLS
--- $$$$$$$$$$$$$$$$$$$$$$$$$$$$$$$$$$$$$$$$$$$$$$$$$$$$$
--- *****************************************************



--- *****************************************************
---     LEAF for the confMgnt1 article
--- *****************************************************
pm10010r100CtrlconfMgnt1 OBJECT IDENTIFIER ::= { pm10010r100CtrlOther 1 }




pm10010r100CtrlConf2Clear1 OBJECT-TYPE
	  SYNTAX EkiOnOff
	  MAX-ACCESS read-write
	  STATUS current
	  DESCRIPTION
        "
        Clear Configuration Tables :This 
        OID clears the configuration tables 
        from configuration2 in the flash. 
         <Help>  This control restores
         the default configuration of the 
        module
        "
	  ::= { pm10010r100CtrlconfMgnt1 14 }



pm10010r100CtrlConf2Flash1 OBJECT-TYPE
	  SYNTAX EkiOnOff
	  MAX-ACCESS read-write
	  STATUS current
	  DESCRIPTION
        "
        Write Configuration Tables :This 
        OID saves the current configuration 
        of the PM as configuration2 in
         the flash.  <Help>  This control 
        saves the customer configuration 
        on the module
        "
	  ::= { pm10010r100CtrlconfMgnt1 10 }



pm10010r100CtrlConf2Load1 OBJECT-TYPE
	  SYNTAX EkiOnOff
	  MAX-ACCESS read-write
	  STATUS current
	  DESCRIPTION
        "
        Load Configuration Tables Set
         Nb 2 :When set this OID enables 
        loading from flash configuration2 
        into the PM.
        "
	  ::= { pm10010r100CtrlconfMgnt1 2 }



pm10010r100CtrlConf1Load1 OBJECT-TYPE
	  SYNTAX EkiOnOff
	  MAX-ACCESS read-write
	  STATUS current
	  DESCRIPTION
        "
        Load Configuration Tables Set
         Nb 1 :When set this OID enables 
        loading from flash configuration1 
        into the PM.
        "
	  ::= { pm10010r100CtrlconfMgnt1 1 }



--- *****************************************************
---     LEAF for the synth4 article
--- *****************************************************
pm10010r100Ctrlsynth4 OBJECT IDENTIFIER ::= { pm10010r100CtrlOther 4 }




pm10010r100CtrlCorrelatOff OBJECT-TYPE
	  SYNTAX EkiOnOff
	  MAX-ACCESS read-write
	  STATUS current
	  DESCRIPTION
        "
        Disable Alarm Correlation :This 
        OID disables the alarm correlation 
        in the PM.
        "
	  ::= { pm10010r100Ctrlsynth4 2 }



pm10010r100CtrlCorrelatOn OBJECT-TYPE
	  SYNTAX EkiOnOff
	  MAX-ACCESS read-write
	  STATUS current
	  DESCRIPTION
        "
        Enable Alarm Correlation :This 
        OID enables the alarm correlation 
        in the PM.
        "
	  ::= { pm10010r100Ctrlsynth4 1 }



--- *****************************************************
---     LEAF for the swMgnt article
--- *****************************************************
pm10010r100CtrlswMgnt OBJECT IDENTIFIER ::= { pm10010r100CtrlOther 5 }




pm10010r100CtrlLoadSwBank2 OBJECT-TYPE
	  SYNTAX EkiOnOff
	  MAX-ACCESS read-write
	  STATUS current
	  DESCRIPTION
        "
        Set Software Nb 2 As Active :This 
        OID, when set, loads the SW from 
        bank2 into the PM. It must be followed 
        by a reset.  <Help>  This controls 
        selects the second SW bank as the 
        active bank for the next module 
        reset
        "
	  ::= { pm10010r100CtrlswMgnt 6 }



pm10010r100CtrlLoadSwBank1 OBJECT-TYPE
	  SYNTAX EkiOnOff
	  MAX-ACCESS read-write
	  STATUS current
	  DESCRIPTION
        "
        Set Software Nb 1 As Active :This 
        OID, when set, loads the SW from 
        bank1 into the PM. It must be followed 
        by a reset.  <Help>  This controls 
        selects the first SW bank as the 
        active bank for the next module 
        reset
        "
	  ::= { pm10010r100CtrlswMgnt 5 }



pm10010r100CtrlWarmReset OBJECT-TYPE
	  SYNTAX EkiOnOff
	  MAX-ACCESS read-write
	  STATUS current
	  DESCRIPTION
        "
        PM Warm Reset :This OID, when
         set, causes a warm reset of the 
        PM. This reset is not traffic affecting, 
        and the configuration of PM remains 
        unchanged.  <Help>  This control 
        initiates a warm reset of the module. 
        "
	  ::= { pm10010r100CtrlswMgnt 3 }



pm10010r100CtrlColdReset OBJECT-TYPE
	  SYNTAX EkiOnOff
	  MAX-ACCESS read-write
	  STATUS current
	  DESCRIPTION
        "
        PM Cold Reset :This OID, when
         set, causes a cold reset of the 
        PM. This reset is traffic affecting, 
        and the configuration of PM is
         reloaded on start-up.  <Help>
          This control initiates a cold 
        reset of the module. 
        "
	  ::= { pm10010r100CtrlswMgnt 2 }



--- *****************************************************
---     LEAF for the gwMgnt article
--- *****************************************************
pm10010r100CtrlgwMgnt OBJECT IDENTIFIER ::= { pm10010r100CtrlOther 6 }




pm10010r100CtrlLoadGwBank4 OBJECT-TYPE
	  SYNTAX EkiOnOff
	  MAX-ACCESS read-write
	  STATUS current
	  DESCRIPTION
        "
        Set Gateware Nb 4 As Active :This 
        OID, when set, loads the GW from 
        bank4 (Flash) into the PM. It is 
        followed by an automatic gateware 
        cold reset.
        "
	  ::= { pm10010r100CtrlgwMgnt 8 }



pm10010r100CtrlLoadGwBank3 OBJECT-TYPE
	  SYNTAX EkiOnOff
	  MAX-ACCESS read-write
	  STATUS current
	  DESCRIPTION
        "
        Set Gateware Nb 3 As Active :This 
        OID, when set, loads the GW from 
        bank3 (Flash) into the PM. It is 
        followed by an automatic gateware 
        cold reset.  <Help>  This controls 
        initiates a cold reset of the module 
        and select the third GW bank as 
        the active bank
        "
	  ::= { pm10010r100CtrlgwMgnt 7 }



pm10010r100CtrlLoadGwBank2 OBJECT-TYPE
	  SYNTAX EkiOnOff
	  MAX-ACCESS read-write
	  STATUS current
	  DESCRIPTION
        "
        Set Gateware Nb 2 As Active :This 
        OID, when set, loads the GW from 
        bank2 (Flash) into the PM. It is 
        followed by an automatic gateware 
        cold reset.
        "
	  ::= { pm10010r100CtrlgwMgnt 6 }



pm10010r100CtrlLoadGwBank1 OBJECT-TYPE
	  SYNTAX EkiOnOff
	  MAX-ACCESS read-write
	  STATUS current
	  DESCRIPTION
        "
        Set Gateware Nb 1 As Active :This 
        OID, when set, loads the GW from 
        bank1 (Flash) into the PM. It is 
        followed by an automatic gateware 
        cold reset.  <Help>  This controls 
        initiates a cold reset of the module 
        and select the first GW bank as 
        the active bank
        "
	  ::= { pm10010r100CtrlgwMgnt 5 }



pm10010r100CtrlCurrentGwReset OBJECT-TYPE
	  SYNTAX EkiOnOff
	  MAX-ACCESS read-write
	  STATUS current
	  DESCRIPTION
        "
        Active Gateware Reset :This OID, 
        when set, resets the active gateware. 
        It is traffic affecting.
        "
	  ::= { pm10010r100CtrlgwMgnt 1 }



--- *********************************************************
---     TABLE for the pm10010r100CtrlaccessLoop articles
--- *********************************************************

pm10010r100CtrlaccessLoopTable OBJECT-TYPE
	SYNTAX  SEQUENCE OF Pm10010r100CtrlaccessLoopEntry
	MAX-ACCESS not-accessible
	STATUS current
	DESCRIPTION
        "
        List of pm10010r100CtrlaccessLoop 
        Article
        "
	::= { pm10010r100CtrlClient 16 }


pm10010r100CtrlaccessLoopEntry OBJECT-TYPE
	SYNTAX Pm10010r100CtrlaccessLoopEntry
	MAX-ACCESS not-accessible
	STATUS current
	DESCRIPTION
        "
        Row definition for the pm10010r100CtrlaccessLoop 
        table
        "
	INDEX   { pm10010r100CtrlaccessLoopIndex }
	::= { pm10010r100CtrlaccessLoopTable 1 }


Pm10010r100CtrlaccessLoopEntry ::=
	SEQUENCE {
	pm10010r100CtrlaccessLoopIndex
		INTEGER,
	pm10010r100CtrlaccessLoopPortn
		EkiState
	}


pm10010r100CtrlaccessLoopIndex OBJECT-TYPE
	SYNTAX  INTEGER(0..128)
	MAX-ACCESS  read-only
	STATUS current
	DESCRIPTION
        "
        Index definition for the pm10010r100CtrlaccessLoop 
        table
        "
	::= { pm10010r100CtrlaccessLoopEntry 1 }


pm10010r100CtrlaccessLoopPortn OBJECT-TYPE
	SYNTAX  EkiState
	MAX-ACCESS read-write
	STATUS current
	DESCRIPTION
        "
        Client Facility Loopback :This 
        OID, when set at '1' puts the client 
        port in loopback, looping the received 
        10 Gb/s signal on the transmit
         10 Gb/s output.  <Help> This control 
        enables the Out Loopback on the 
        client port, looping the client 
        input signal on the client output
        "
	::= { pm10010r100CtrlaccessLoopEntry 2 }


--- *********************************************************
---     TABLE for the pm10010r100CtrlclientLoopToLine articles
--- *********************************************************

pm10010r100CtrlclientLoopToLineTable OBJECT-TYPE
	SYNTAX  SEQUENCE OF Pm10010r100CtrlclientLoopToLineEntry
	MAX-ACCESS not-accessible
	STATUS current
	DESCRIPTION
        "
        List of pm10010r100CtrlclientLoopToLine 
        Article
        "
	::= { pm10010r100CtrlClient 17 }


pm10010r100CtrlclientLoopToLineEntry OBJECT-TYPE
	SYNTAX Pm10010r100CtrlclientLoopToLineEntry
	MAX-ACCESS not-accessible
	STATUS current
	DESCRIPTION
        "
        Row definition for the pm10010r100CtrlclientLoopToLine 
        table
        "
	INDEX   { pm10010r100CtrlclientLoopToLineIndex }
	::= { pm10010r100CtrlclientLoopToLineTable 1 }


Pm10010r100CtrlclientLoopToLineEntry ::=
	SEQUENCE {
	pm10010r100CtrlclientLoopToLineIndex
		INTEGER,
	pm10010r100CtrlclientLoopToLinePortn
		EkiState
	}


pm10010r100CtrlclientLoopToLineIndex OBJECT-TYPE
	SYNTAX  INTEGER(0..128)
	MAX-ACCESS  read-only
	STATUS current
	DESCRIPTION
        "
        Index definition for the pm10010r100CtrlclientLoopToLine 
        table
        "
	::= { pm10010r100CtrlclientLoopToLineEntry 1 }


pm10010r100CtrlclientLoopToLinePortn OBJECT-TYPE
	SYNTAX  EkiState
	MAX-ACCESS read-write
	STATUS current
	DESCRIPTION
        "
        Client Terminal Loopback :This 
        OID, when set, puts the client
         port in loop back, looping the 
        10 Gb/s output signal on the 10 
        Gb/s input.<Help> This control
         enables the In Loopback on the 
        client port, looping the client 
        output signal on the client input
        "
	::= { pm10010r100CtrlclientLoopToLineEntry 2 }


--- *********************************************************
---     TABLE for the pm10010r100CtrlcsfUpIns articles
--- *********************************************************

pm10010r100CtrlcsfUpInsTable OBJECT-TYPE
	SYNTAX  SEQUENCE OF Pm10010r100CtrlcsfUpInsEntry
	MAX-ACCESS not-accessible
	STATUS current
	DESCRIPTION
        "
        List of pm10010r100CtrlcsfUpIns 
        Article
        "
	::= { pm10010r100CtrlClient 21 }


pm10010r100CtrlcsfUpInsEntry OBJECT-TYPE
	SYNTAX Pm10010r100CtrlcsfUpInsEntry
	MAX-ACCESS not-accessible
	STATUS current
	DESCRIPTION
        "
        Row definition for the pm10010r100CtrlcsfUpIns 
        table
        "
	INDEX   { pm10010r100CtrlcsfUpInsIndex }
	::= { pm10010r100CtrlcsfUpInsTable 1 }


Pm10010r100CtrlcsfUpInsEntry ::=
	SEQUENCE {
	pm10010r100CtrlcsfUpInsIndex
		INTEGER,
	pm10010r100CtrlcsfUpInsPortn
		EkiState
	}


pm10010r100CtrlcsfUpInsIndex OBJECT-TYPE
	SYNTAX  INTEGER(0..128)
	MAX-ACCESS  read-only
	STATUS current
	DESCRIPTION
        "
        Index definition for the pm10010r100CtrlcsfUpIns 
        table
        "
	::= { pm10010r100CtrlcsfUpInsEntry 1 }


pm10010r100CtrlcsfUpInsPortn OBJECT-TYPE
	SYNTAX  EkiState
	MAX-ACCESS read-write
	STATUS current
	DESCRIPTION
        "
        Client Signal Fail Insertion :This 
        OID, when set, inserts  a client 
        signal fail in the upstream client 
        Port.  <Help>  This control inserts 
        a Client Signal Fail for the client 
        port
        "
	::= { pm10010r100CtrlcsfUpInsEntry 2 }


--- *********************************************************
---     TABLE for the pm10010r100CtrlcaisDwIns articles
--- *********************************************************

pm10010r100CtrlcaisDwInsTable OBJECT-TYPE
	SYNTAX  SEQUENCE OF Pm10010r100CtrlcaisDwInsEntry
	MAX-ACCESS not-accessible
	STATUS current
	DESCRIPTION
        "
        List of pm10010r100CtrlcaisDwIns 
        Article
        "
	::= { pm10010r100CtrlClient 22 }


pm10010r100CtrlcaisDwInsEntry OBJECT-TYPE
	SYNTAX Pm10010r100CtrlcaisDwInsEntry
	MAX-ACCESS not-accessible
	STATUS current
	DESCRIPTION
        "
        Row definition for the pm10010r100CtrlcaisDwIns 
        table
        "
	INDEX   { pm10010r100CtrlcaisDwInsIndex }
	::= { pm10010r100CtrlcaisDwInsTable 1 }


Pm10010r100CtrlcaisDwInsEntry ::=
	SEQUENCE {
	pm10010r100CtrlcaisDwInsIndex
		INTEGER,
	pm10010r100CtrlcaisDwInsPortn
		EkiState
	}


pm10010r100CtrlcaisDwInsIndex OBJECT-TYPE
	SYNTAX  INTEGER(0..128)
	MAX-ACCESS  read-only
	STATUS current
	DESCRIPTION
        "
        Index definition for the pm10010r100CtrlcaisDwIns 
        table
        "
	::= { pm10010r100CtrlcaisDwInsEntry 1 }


pm10010r100CtrlcaisDwInsPortn OBJECT-TYPE
	SYNTAX  EkiState
	MAX-ACCESS read-write
	STATUS current
	DESCRIPTION
        "
        Client AIS Insertion :This OID, 
        when set, inserts a client AIS
         on the downstream client Port. 
         <Help>  This control inserts a 
        Client AIS for the client port
        "
	::= { pm10010r100CtrlcaisDwInsEntry 2 }


--- *********************************************************
---     TABLE for the pm10010r100CtrlcommAccessLoop articles
--- *********************************************************

pm10010r100CtrlcommAccessLoopTable OBJECT-TYPE
	SYNTAX  SEQUENCE OF Pm10010r100CtrlcommAccessLoopEntry
	MAX-ACCESS not-accessible
	STATUS current
	DESCRIPTION
        "
        List of pm10010r100CtrlcommAccessLoop 
        Article
        "
	::= { pm10010r100CtrlLine 64 }


pm10010r100CtrlcommAccessLoopEntry OBJECT-TYPE
	SYNTAX Pm10010r100CtrlcommAccessLoopEntry
	MAX-ACCESS not-accessible
	STATUS current
	DESCRIPTION
        "
        Row definition for the pm10010r100CtrlcommAccessLoop 
        table
        "
	INDEX   { pm10010r100CtrlcommAccessLoopIndex }
	::= { pm10010r100CtrlcommAccessLoopTable 1 }


Pm10010r100CtrlcommAccessLoopEntry ::=
	SEQUENCE {
	pm10010r100CtrlcommAccessLoopIndex
		INTEGER,
	pm10010r100CtrlcommAccessLoopPortn
		EkiState
	}


pm10010r100CtrlcommAccessLoopIndex OBJECT-TYPE
	SYNTAX  INTEGER(0..128)
	MAX-ACCESS  read-only
	STATUS current
	DESCRIPTION
        "
        Index definition for the pm10010r100CtrlcommAccessLoop 
        table
        "
	::= { pm10010r100CtrlcommAccessLoopEntry 1 }


pm10010r100CtrlcommAccessLoopPortn OBJECT-TYPE
	SYNTAX  EkiState
	MAX-ACCESS read-write
	STATUS current
	DESCRIPTION
        "
        Line Terminal Loopback :This OID, 
        when set, puts the module in common 
        access loop back, looping the 100 
        Gb/s output signal on the 100 Gb/s 
        input.<Help> This control enables 
        the In Loopback on the line port, 
        looping the 100 Gb/s output signal 
        on the 100 Gb/s input
        "
	::= { pm10010r100CtrlcommAccessLoopEntry 2 }


--- *********************************************************
---     TABLE for the pm10010r100CtrllineLoop articles
--- *********************************************************

pm10010r100CtrllineLoopTable OBJECT-TYPE
	SYNTAX  SEQUENCE OF Pm10010r100CtrllineLoopEntry
	MAX-ACCESS not-accessible
	STATUS current
	DESCRIPTION
        "
        List of pm10010r100CtrllineLoop 
        Article
        "
	::= { pm10010r100CtrlLine 66 }


pm10010r100CtrllineLoopEntry OBJECT-TYPE
	SYNTAX Pm10010r100CtrllineLoopEntry
	MAX-ACCESS not-accessible
	STATUS current
	DESCRIPTION
        "
        Row definition for the pm10010r100CtrllineLoop 
        table
        "
	INDEX   { pm10010r100CtrllineLoopIndex }
	::= { pm10010r100CtrllineLoopTable 1 }


Pm10010r100CtrllineLoopEntry ::=
	SEQUENCE {
	pm10010r100CtrllineLoopIndex
		INTEGER,
	pm10010r100CtrllineLoopPortn
		EkiState
	}


pm10010r100CtrllineLoopIndex OBJECT-TYPE
	SYNTAX  INTEGER(0..128)
	MAX-ACCESS  read-only
	STATUS current
	DESCRIPTION
        "
        Index definition for the pm10010r100CtrllineLoop 
        table
        "
	::= { pm10010r100CtrllineLoopEntry 1 }


pm10010r100CtrllineLoopPortn OBJECT-TYPE
	SYNTAX  EkiState
	MAX-ACCESS read-write
	STATUS current
	DESCRIPTION
        "
        Line Facility Loopback :This OID, 
        when set at '1' puts the module 
        in line loopback mode, looping
         the received 100 Gb/s signal on 
        the transmit 100 Gb/s output. The 
        Upstream part of the module is
         timed on the 100 Gb/s recovered 
        clock in that case.<Help> This
         control enables the Out Loopback 
        on the line port, looping the 100 
        Gb/s input signal on the 100 Gb/s 
        output
        "
	::= { pm10010r100CtrllineLoopEntry 2 }


--- *********************************************************
---     TABLE for the pm10010r100CtrlfecDisable articles
--- *********************************************************

pm10010r100CtrlfecDisableTable OBJECT-TYPE
	SYNTAX  SEQUENCE OF Pm10010r100CtrlfecDisableEntry
	MAX-ACCESS not-accessible
	STATUS current
	DESCRIPTION
        "
        List of pm10010r100CtrlfecDisable 
        Article
        "
	::= { pm10010r100CtrlLine 69 }


pm10010r100CtrlfecDisableEntry OBJECT-TYPE
	SYNTAX Pm10010r100CtrlfecDisableEntry
	MAX-ACCESS not-accessible
	STATUS current
	DESCRIPTION
        "
        Row definition for the pm10010r100CtrlfecDisable 
        table
        "
	INDEX   { pm10010r100CtrlfecDisableIndex }
	::= { pm10010r100CtrlfecDisableTable 1 }


Pm10010r100CtrlfecDisableEntry ::=
	SEQUENCE {
	pm10010r100CtrlfecDisableIndex
		INTEGER,
	pm10010r100CtrlfecDisablePortn
		EkiState
	}


pm10010r100CtrlfecDisableIndex OBJECT-TYPE
	SYNTAX  INTEGER(0..128)
	MAX-ACCESS  read-only
	STATUS current
	DESCRIPTION
        "
        Index definition for the pm10010r100CtrlfecDisable 
        table
        "
	::= { pm10010r100CtrlfecDisableEntry 1 }


pm10010r100CtrlfecDisablePortn OBJECT-TYPE
	SYNTAX  EkiState
	MAX-ACCESS read-write
	STATUS current
	DESCRIPTION
        "
        Forward Error Correction Inhibition 
        :This OID, when set, inhibits the 
        Forward Error Correction feature 
        on the line input  <Help>  This 
        control enables/disables the Forward 
        Error Correction on the line interface
        "
	::= { pm10010r100CtrlfecDisableEntry 2 }


--- *****************************************************
---     LEAF for the ledTest article
--- *****************************************************
pm10010r100CtrlledTest OBJECT IDENTIFIER ::= { pm10010r100CtrlOther 192 }




pm10010r100CtrlLedOff OBJECT-TYPE
	  SYNTAX EkiOnOff
	  MAX-ACCESS read-write
	  STATUS current
	  DESCRIPTION
        "
        Leds Off :This OID switches off 
        all the Leds as a test feature. 
         <Help>  This control initiates 
        a test leds turning all the LEDs 
        to OFF
        "
	  ::= { pm10010r100CtrlledTest 3 }



pm10010r100CtrlRedLed OBJECT-TYPE
	  SYNTAX EkiOnOff
	  MAX-ACCESS read-write
	  STATUS current
	  DESCRIPTION
        "
        Red Leds Test :This OID switches 
        on all the red Leds as a test feature. 
         <Help>  This control initiates 
        a test leds turning all the LEDs 
        to red
        "
	  ::= { pm10010r100CtrlledTest 2 }



pm10010r100CtrlGreenLed OBJECT-TYPE
	  SYNTAX EkiOnOff
	  MAX-ACCESS read-write
	  STATUS current
	  DESCRIPTION
        "
        Green Leds Test :This OID switches 
        on all the green Leds as a test 
        feature.  <Help>  This control
         initiates a test leds turning
         all the LEDs to green
        "
	  ::= { pm10010r100CtrlledTest 1 }



--- *****************************************************
---     LEAF for the initSwitchMarvell article
--- *****************************************************
pm10010r100CtrlinitSwitchMarvell OBJECT IDENTIFIER ::= { pm10010r100CtrlOther 201 }




pm10010r100CtrlInitSwitchMarvell OBJECT-TYPE
	  SYNTAX EkiOnOff
	  MAX-ACCESS read-write
	  STATUS current
	  DESCRIPTION
        "
        Switch Initialization :This OID 
        operates an initialization of the 
        switch managed through the module 
         <Help>  This control activates 
        an initialization of the switch 
        managed through the module
        "
	  ::= { pm10010r100CtrlinitSwitchMarvell 1 }



--- *********************************************************
---     TABLE for the pm10010r100CtrlmsaLineLoop articles
--- *********************************************************

pm10010r100CtrlmsaLineLoopTable OBJECT-TYPE
	SYNTAX  SEQUENCE OF Pm10010r100CtrlmsaLineLoopEntry
	MAX-ACCESS not-accessible
	STATUS current
	DESCRIPTION
        "
        List of pm10010r100CtrlmsaLineLoop 
        Article
        "
	::= { pm10010r100CtrlLine 209 }


pm10010r100CtrlmsaLineLoopEntry OBJECT-TYPE
	SYNTAX Pm10010r100CtrlmsaLineLoopEntry
	MAX-ACCESS not-accessible
	STATUS current
	DESCRIPTION
        "
        Row definition for the pm10010r100CtrlmsaLineLoop 
        table
        "
	INDEX   { pm10010r100CtrlmsaLineLoopIndex }
	::= { pm10010r100CtrlmsaLineLoopTable 1 }


Pm10010r100CtrlmsaLineLoopEntry ::=
	SEQUENCE {
	pm10010r100CtrlmsaLineLoopIndex
		INTEGER,
	pm10010r100CtrlmsaLineLoopPortn
		EkiState
	}


pm10010r100CtrlmsaLineLoopIndex OBJECT-TYPE
	SYNTAX  INTEGER(0..128)
	MAX-ACCESS  read-only
	STATUS current
	DESCRIPTION
        "
        Index definition for the pm10010r100CtrlmsaLineLoop 
        table
        "
	::= { pm10010r100CtrlmsaLineLoopEntry 1 }


pm10010r100CtrlmsaLineLoopPortn OBJECT-TYPE
	SYNTAX  EkiState
	MAX-ACCESS read-write
	STATUS current
	DESCRIPTION
        "
        MSA Line Loop :This OID operates 
        a line loopback on the MSA Line 
         <Help>  This control defines the 
        line loop back of the line transceiver
        "
	::= { pm10010r100CtrlmsaLineLoopEntry 2 }


--- *********************************************************
---     TABLE for the pm10010r100CtrlmsaTxReset articles
--- *********************************************************

pm10010r100CtrlmsaTxResetTable OBJECT-TYPE
	SYNTAX  SEQUENCE OF Pm10010r100CtrlmsaTxResetEntry
	MAX-ACCESS not-accessible
	STATUS current
	DESCRIPTION
        "
        List of pm10010r100CtrlmsaTxReset 
        Article
        "
	::= { pm10010r100CtrlLine 210 }


pm10010r100CtrlmsaTxResetEntry OBJECT-TYPE
	SYNTAX Pm10010r100CtrlmsaTxResetEntry
	MAX-ACCESS not-accessible
	STATUS current
	DESCRIPTION
        "
        Row definition for the pm10010r100CtrlmsaTxReset 
        table
        "
	INDEX   { pm10010r100CtrlmsaTxResetIndex }
	::= { pm10010r100CtrlmsaTxResetTable 1 }


Pm10010r100CtrlmsaTxResetEntry ::=
	SEQUENCE {
	pm10010r100CtrlmsaTxResetIndex
		INTEGER,
	pm10010r100CtrlmsaTxResetPortn
		EkiState
	}


pm10010r100CtrlmsaTxResetIndex OBJECT-TYPE
	SYNTAX  INTEGER(0..128)
	MAX-ACCESS  read-only
	STATUS current
	DESCRIPTION
        "
        Index definition for the pm10010r100CtrlmsaTxReset 
        table
        "
	::= { pm10010r100CtrlmsaTxResetEntry 1 }


pm10010r100CtrlmsaTxResetPortn OBJECT-TYPE
	SYNTAX  EkiState
	MAX-ACCESS read-write
	STATUS current
	DESCRIPTION
        "
        Line MSA TX Reset :This OID resets 
        the TX portion of the MSA line
         module  <Help > This control 
         initiates a reset of the transmitting 
        side
        "
	::= { pm10010r100CtrlmsaTxResetEntry 2 }


--- *********************************************************
---     TABLE for the pm10010r100CtrlmsaRxReset articles
--- *********************************************************

pm10010r100CtrlmsaRxResetTable OBJECT-TYPE
	SYNTAX  SEQUENCE OF Pm10010r100CtrlmsaRxResetEntry
	MAX-ACCESS not-accessible
	STATUS current
	DESCRIPTION
        "
        List of pm10010r100CtrlmsaRxReset 
        Article
        "
	::= { pm10010r100CtrlLine 211 }


pm10010r100CtrlmsaRxResetEntry OBJECT-TYPE
	SYNTAX Pm10010r100CtrlmsaRxResetEntry
	MAX-ACCESS not-accessible
	STATUS current
	DESCRIPTION
        "
        Row definition for the pm10010r100CtrlmsaRxReset 
        table
        "
	INDEX   { pm10010r100CtrlmsaRxResetIndex }
	::= { pm10010r100CtrlmsaRxResetTable 1 }


Pm10010r100CtrlmsaRxResetEntry ::=
	SEQUENCE {
	pm10010r100CtrlmsaRxResetIndex
		INTEGER,
	pm10010r100CtrlmsaRxResetPortn
		EkiState
	}


pm10010r100CtrlmsaRxResetIndex OBJECT-TYPE
	SYNTAX  INTEGER(0..128)
	MAX-ACCESS  read-only
	STATUS current
	DESCRIPTION
        "
        Index definition for the pm10010r100CtrlmsaRxReset 
        table
        "
	::= { pm10010r100CtrlmsaRxResetEntry 1 }


pm10010r100CtrlmsaRxResetPortn OBJECT-TYPE
	SYNTAX  EkiState
	MAX-ACCESS read-write
	STATUS current
	DESCRIPTION
        "
        Line MSA RX Reset :This OID resets 
        the RX portion of the MSA line
         module  <Help > This control 
         initiates a reset of the receiving 
        side
        "
	::= { pm10010r100CtrlmsaRxResetEntry 2 }


--- *********************************************************
---     TABLE for the pm10010r100CtrlmsaShutdown articles
--- *********************************************************

pm10010r100CtrlmsaShutdownTable OBJECT-TYPE
	SYNTAX  SEQUENCE OF Pm10010r100CtrlmsaShutdownEntry
	MAX-ACCESS not-accessible
	STATUS current
	DESCRIPTION
        "
        List of pm10010r100CtrlmsaShutdown 
        Article
        "
	::= { pm10010r100CtrlLine 212 }


pm10010r100CtrlmsaShutdownEntry OBJECT-TYPE
	SYNTAX Pm10010r100CtrlmsaShutdownEntry
	MAX-ACCESS not-accessible
	STATUS current
	DESCRIPTION
        "
        Row definition for the pm10010r100CtrlmsaShutdown 
        table
        "
	INDEX   { pm10010r100CtrlmsaShutdownIndex }
	::= { pm10010r100CtrlmsaShutdownTable 1 }


Pm10010r100CtrlmsaShutdownEntry ::=
	SEQUENCE {
	pm10010r100CtrlmsaShutdownIndex
		INTEGER,
	pm10010r100CtrlmsaShutdownPortn
		EkiState
	}


pm10010r100CtrlmsaShutdownIndex OBJECT-TYPE
	SYNTAX  INTEGER(0..128)
	MAX-ACCESS  read-only
	STATUS current
	DESCRIPTION
        "
        Index definition for the pm10010r100CtrlmsaShutdown 
        table
        "
	::= { pm10010r100CtrlmsaShutdownEntry 1 }


pm10010r100CtrlmsaShutdownPortn OBJECT-TYPE
	SYNTAX  EkiState
	MAX-ACCESS read-write
	STATUS current
	DESCRIPTION
        "
        Line MSA Shutdown :This OID enters 
        a process to shutdown the MSA line 
        module  <Help > This control  initiates 
        a shutdown of the module
        "
	::= { pm10010r100CtrlmsaShutdownEntry 2 }


--- *****************************************************
---     LEAF for the resetCount article
--- *****************************************************
pm10010r100CtrlresetCount OBJECT IDENTIFIER ::= { pm10010r100CtrlOther 259 }




pm10010r100CtrlResetcount OBJECT-TYPE
	  SYNTAX EkiOnOff
	  MAX-ACCESS read-write
	  STATUS current
	  DESCRIPTION
        "
        Module Count Global Reset :This 
        OID resets all the errors counters 
        on the module  <Help > This control 
         initiates a reset of the errors 
        counters on the module
        "
	  ::= { pm10010r100CtrlresetCount 1 }



--- *****************************************************
---     LEAF for the resetRmon article
--- *****************************************************
pm10010r100CtrlresetRmon OBJECT IDENTIFIER ::= { pm10010r100CtrlOther 260 }




pm10010r100CtrlResetrmon OBJECT-TYPE
	  SYNTAX EkiOnOff
	  MAX-ACCESS read-write
	  STATUS current
	  DESCRIPTION
        "
        Module Rmon Global Reset :This 
        OID resets all the Rmon counters 
        on the module  <Help > This control 
         initiates a reset of the Rmon
         counters on the module
        "
	  ::= { pm10010r100CtrlresetRmon 1 }



--- *****************************************************
---     LEAF for the resetMeasurements article
--- *****************************************************
pm10010r100CtrlresetMeasurements OBJECT IDENTIFIER ::= { pm10010r100CtrlOther 261 }




pm10010r100CtrlResetmeasurements OBJECT-TYPE
	  SYNTAX EkiOnOff
	  MAX-ACCESS read-write
	  STATUS current
	  DESCRIPTION
        "
        Management Meas Global Reset :This 
        OID resets some measurements on 
        the management  <Help > This control 
         initiates a reset of some measurements 
        on the management
        "
	  ::= { pm10010r100CtrlresetMeasurements 1 }








--- *****************************************************
--- $$$$$$$$$$$$$$$$$$$$$$$$$$$$$$$$$$$$$$$$$$$$$$$$$$$$$
---     COUNTERS
--- $$$$$$$$$$$$$$$$$$$$$$$$$$$$$$$$$$$$$$$$$$$$$$$$$$$$$
--- *****************************************************



--- *********************************************************
---     TABLE for the pm10010r100CntclientInputSmBip8Error articles
--- *********************************************************

pm10010r100CntclientInputSmBip8ErrorTable OBJECT-TYPE
	SYNTAX  SEQUENCE OF Pm10010r100CntclientInputSmBip8ErrorEntry
	MAX-ACCESS not-accessible
	STATUS current
	DESCRIPTION
        "
        List of pm10010r100CntclientInputSmBip8Error 
        Article
        "
	::= { pm10010r100CntClient 16 }


pm10010r100CntclientInputSmBip8ErrorEntry OBJECT-TYPE
	SYNTAX Pm10010r100CntclientInputSmBip8ErrorEntry
	MAX-ACCESS not-accessible
	STATUS current
	DESCRIPTION
        "
        Row definition for the pm10010r100CntclientInputSmBip8Error 
        table
        "
	INDEX   { pm10010r100CntclientInputSmBip8ErrorIndex }
	::= { pm10010r100CntclientInputSmBip8ErrorTable 1 }


Pm10010r100CntclientInputSmBip8ErrorEntry ::=
	SEQUENCE {
	pm10010r100CntclientInputSmBip8ErrorIndex
		INTEGER,
	pm10010r100CntclientInputSmBip8ErrorValuePortn
		Counter32,
	pm10010r100CntclientInputSmBip8ErrorErrorPortn
		EkiOnOff,
	pm10010r100CntclientInputSmBip8ErrorOverloadPortn
		EkiOnOff
	}


pm10010r100CntclientInputSmBip8ErrorIndex OBJECT-TYPE
	SYNTAX  INTEGER(0..128)
	MAX-ACCESS  read-only
	STATUS current
	DESCRIPTION
        "
        Index definition for the pm10010r100CntclientInputSmBip8Error 
        table
        "
	::= { pm10010r100CntclientInputSmBip8ErrorEntry 1 }


pm10010r100CntclientInputSmBip8ErrorValuePortn OBJECT-TYPE
	SYNTAX  Counter32
	MAX-ACCESS read-only
	STATUS current
	DESCRIPTION
        "
        Client Input SM BIP8 Error :This 
        counter is incremented each time 
          <Help>  This counter gives the 
        number
        "
	::= { pm10010r100CntclientInputSmBip8ErrorEntry 2 }


pm10010r100CntclientInputSmBip8ErrorErrorPortn OBJECT-TYPE
	SYNTAX  EkiOnOff
	MAX-ACCESS read-only
	STATUS current
	DESCRIPTION
        "
        Client Input Counter Error :This 
        OID when set indicates the rate 
        adaptation removal counter value 
        is invalid on Port
        "
	::= { pm10010r100CntclientInputSmBip8ErrorEntry 3 }


pm10010r100CntclientInputSmBip8ErrorOverloadPortn OBJECT-TYPE
	SYNTAX  EkiOnOff
	MAX-ACCESS read-only
	STATUS current
	DESCRIPTION
        "
        Client Input Counter Overload
         :This OID when set indicates a 
        rate adaptation removal counter 
        overload on Port
        "
	::= { pm10010r100CntclientInputSmBip8ErrorEntry 4 }


--- *********************************************************
---     TABLE for the pm10010r100CntclientGfecInputError articles
--- *********************************************************

pm10010r100CntclientGfecInputErrorTable OBJECT-TYPE
	SYNTAX  SEQUENCE OF Pm10010r100CntclientGfecInputErrorEntry
	MAX-ACCESS not-accessible
	STATUS current
	DESCRIPTION
        "
        List of pm10010r100CntclientGfecInputError 
        Article
        "
	::= { pm10010r100CntClient 32 }


pm10010r100CntclientGfecInputErrorEntry OBJECT-TYPE
	SYNTAX Pm10010r100CntclientGfecInputErrorEntry
	MAX-ACCESS not-accessible
	STATUS current
	DESCRIPTION
        "
        Row definition for the pm10010r100CntclientGfecInputError 
        table
        "
	INDEX   { pm10010r100CntclientGfecInputErrorIndex }
	::= { pm10010r100CntclientGfecInputErrorTable 1 }


Pm10010r100CntclientGfecInputErrorEntry ::=
	SEQUENCE {
	pm10010r100CntclientGfecInputErrorIndex
		INTEGER,
	pm10010r100CntclientGfecInputErrorValuePortn
		Counter32,
	pm10010r100CntclientGfecInputErrorErrorPortn
		EkiOnOff,
	pm10010r100CntclientGfecInputErrorOverloadPortn
		EkiOnOff
	}


pm10010r100CntclientGfecInputErrorIndex OBJECT-TYPE
	SYNTAX  INTEGER(0..128)
	MAX-ACCESS  read-only
	STATUS current
	DESCRIPTION
        "
        Index definition for the pm10010r100CntclientGfecInputError 
        table
        "
	::= { pm10010r100CntclientGfecInputErrorEntry 1 }


pm10010r100CntclientGfecInputErrorValuePortn OBJECT-TYPE
	SYNTAX  Counter32
	MAX-ACCESS read-only
	STATUS current
	DESCRIPTION
        "
        Client GFEC Input Error :This
         counter is incremented each time 
          <Help>  This counter gives the 
        number
        "
	::= { pm10010r100CntclientGfecInputErrorEntry 2 }


pm10010r100CntclientGfecInputErrorErrorPortn OBJECT-TYPE
	SYNTAX  EkiOnOff
	MAX-ACCESS read-only
	STATUS current
	DESCRIPTION
        "
        Client Input Counter Error :This 
        OID when set indicates the client 
        error counter value is invalid
         on Port
        "
	::= { pm10010r100CntclientGfecInputErrorEntry 3 }


pm10010r100CntclientGfecInputErrorOverloadPortn OBJECT-TYPE
	SYNTAX  EkiOnOff
	MAX-ACCESS read-only
	STATUS current
	DESCRIPTION
        "
        Client Input Counter Overload
         :This OID when set indicates a 
        client input error counter overload 
        on Port
        "
	::= { pm10010r100CntclientGfecInputErrorEntry 4 }


--- *********************************************************
---     TABLE for the pm10010r100CntclientInputFecCorrectedError articles
--- *********************************************************

pm10010r100CntclientInputFecCorrectedErrorTable OBJECT-TYPE
	SYNTAX  SEQUENCE OF Pm10010r100CntclientInputFecCorrectedErrorEntry
	MAX-ACCESS not-accessible
	STATUS current
	DESCRIPTION
        "
        List of pm10010r100CntclientInputFecCorrectedError 
        Article
        "
	::= { pm10010r100CntClient 80 }


pm10010r100CntclientInputFecCorrectedErrorEntry OBJECT-TYPE
	SYNTAX Pm10010r100CntclientInputFecCorrectedErrorEntry
	MAX-ACCESS not-accessible
	STATUS current
	DESCRIPTION
        "
        Row definition for the pm10010r100CntclientInputFecCorrectedError 
        table
        "
	INDEX   { pm10010r100CntclientInputFecCorrectedErrorIndex }
	::= { pm10010r100CntclientInputFecCorrectedErrorTable 1 }


Pm10010r100CntclientInputFecCorrectedErrorEntry ::=
	SEQUENCE {
	pm10010r100CntclientInputFecCorrectedErrorIndex
		INTEGER,
	pm10010r100CntclientInputFecCorrectedErrorValuePortn
		Counter32,
	pm10010r100CntclientInputFecCorrectedErrorErrorPortn
		EkiOnOff,
	pm10010r100CntclientInputFecCorrectedErrorOverloadPortn
		EkiOnOff
	}


pm10010r100CntclientInputFecCorrectedErrorIndex OBJECT-TYPE
	SYNTAX  INTEGER(0..128)
	MAX-ACCESS  read-only
	STATUS current
	DESCRIPTION
        "
        Index definition for the pm10010r100CntclientInputFecCorrectedError 
        table
        "
	::= { pm10010r100CntclientInputFecCorrectedErrorEntry 1 }


pm10010r100CntclientInputFecCorrectedErrorValuePortn OBJECT-TYPE
	SYNTAX  Counter32
	MAX-ACCESS read-only
	STATUS current
	DESCRIPTION
        "
        Client Input FEC Corrected Error 
        :This counter is incremented each 
        time   <Help>  This counter gives 
        the number
        "
	::= { pm10010r100CntclientInputFecCorrectedErrorEntry 2 }


pm10010r100CntclientInputFecCorrectedErrorErrorPortn OBJECT-TYPE
	SYNTAX  EkiOnOff
	MAX-ACCESS read-only
	STATUS current
	DESCRIPTION
        "
        Client Counter Error :This OID 
        when set indicates the client error 
        counter value is invalid on Port
        "
	::= { pm10010r100CntclientInputFecCorrectedErrorEntry 3 }


pm10010r100CntclientInputFecCorrectedErrorOverloadPortn OBJECT-TYPE
	SYNTAX  EkiOnOff
	MAX-ACCESS read-only
	STATUS current
	DESCRIPTION
        "
        Client Counter Overload :This
         OID when set indicates a client 
        input error counter overload on 
        Port
        "
	::= { pm10010r100CntclientInputFecCorrectedErrorEntry 4 }


--- *********************************************************
---     TABLE for the pm10010r100CntclientInputRemoteSmBip8Error articles
--- *********************************************************

pm10010r100CntclientInputRemoteSmBip8ErrorTable OBJECT-TYPE
	SYNTAX  SEQUENCE OF Pm10010r100CntclientInputRemoteSmBip8ErrorEntry
	MAX-ACCESS not-accessible
	STATUS current
	DESCRIPTION
        "
        List of pm10010r100CntclientInputRemoteSmBip8Error 
        Article
        "
	::= { pm10010r100CntClient 96 }


pm10010r100CntclientInputRemoteSmBip8ErrorEntry OBJECT-TYPE
	SYNTAX Pm10010r100CntclientInputRemoteSmBip8ErrorEntry
	MAX-ACCESS not-accessible
	STATUS current
	DESCRIPTION
        "
        Row definition for the pm10010r100CntclientInputRemoteSmBip8Error 
        table
        "
	INDEX   { pm10010r100CntclientInputRemoteSmBip8ErrorIndex }
	::= { pm10010r100CntclientInputRemoteSmBip8ErrorTable 1 }


Pm10010r100CntclientInputRemoteSmBip8ErrorEntry ::=
	SEQUENCE {
	pm10010r100CntclientInputRemoteSmBip8ErrorIndex
		INTEGER,
	pm10010r100CntclientInputRemoteSmBip8ErrorValuePortn
		Counter32,
	pm10010r100CntclientInputRemoteSmBip8ErrorErrorPortn
		EkiOnOff,
	pm10010r100CntclientInputRemoteSmBip8ErrorOverloadPortn
		EkiOnOff
	}


pm10010r100CntclientInputRemoteSmBip8ErrorIndex OBJECT-TYPE
	SYNTAX  INTEGER(0..128)
	MAX-ACCESS  read-only
	STATUS current
	DESCRIPTION
        "
        Index definition for the pm10010r100CntclientInputRemoteSmBip8Error 
        table
        "
	::= { pm10010r100CntclientInputRemoteSmBip8ErrorEntry 1 }


pm10010r100CntclientInputRemoteSmBip8ErrorValuePortn OBJECT-TYPE
	SYNTAX  Counter32
	MAX-ACCESS read-only
	STATUS current
	DESCRIPTION
        "
        Client Input Remote SM BIP8 Error 
        :This counter is incremented each 
        time   <Help>  This counter gives 
        the number
        "
	::= { pm10010r100CntclientInputRemoteSmBip8ErrorEntry 2 }


pm10010r100CntclientInputRemoteSmBip8ErrorErrorPortn OBJECT-TYPE
	SYNTAX  EkiOnOff
	MAX-ACCESS read-only
	STATUS current
	DESCRIPTION
        "
        Client Counter Error :This OID 
        when set indicates the CBIP error 
        counter value is invalid on Port
        "
	::= { pm10010r100CntclientInputRemoteSmBip8ErrorEntry 3 }


pm10010r100CntclientInputRemoteSmBip8ErrorOverloadPortn OBJECT-TYPE
	SYNTAX  EkiOnOff
	MAX-ACCESS read-only
	STATUS current
	DESCRIPTION
        "
        Client CBIP Counter Overload :This 
        OID when set indicates a CBIP error 
        counter overload on Port
        "
	::= { pm10010r100CntclientInputRemoteSmBip8ErrorEntry 4 }


--- *********************************************************
---     TABLE for the pm10010r100CntlocalLineSmBip8ErrorCounter articles
--- *********************************************************

pm10010r100CntlocalLineSmBip8ErrorCounterTable OBJECT-TYPE
	SYNTAX  SEQUENCE OF Pm10010r100CntlocalLineSmBip8ErrorCounterEntry
	MAX-ACCESS not-accessible
	STATUS current
	DESCRIPTION
        "
        List of pm10010r100CntlocalLineSmBip8ErrorCounter 
        Article
        "
	::= { pm10010r100CntLine 192 }


pm10010r100CntlocalLineSmBip8ErrorCounterEntry OBJECT-TYPE
	SYNTAX Pm10010r100CntlocalLineSmBip8ErrorCounterEntry
	MAX-ACCESS not-accessible
	STATUS current
	DESCRIPTION
        "
        Row definition for the pm10010r100CntlocalLineSmBip8ErrorCounter 
        table
        "
	INDEX   { pm10010r100CntlocalLineSmBip8ErrorCounterIndex }
	::= { pm10010r100CntlocalLineSmBip8ErrorCounterTable 1 }


Pm10010r100CntlocalLineSmBip8ErrorCounterEntry ::=
	SEQUENCE {
	pm10010r100CntlocalLineSmBip8ErrorCounterIndex
		INTEGER,
	pm10010r100CntlocalLineSmBip8ErrorCounterValuePortn
		Counter64,
	pm10010r100CntlocalLineSmBip8ErrorCounterErrorPortn
		EkiOnOff,
	pm10010r100CntlocalLineSmBip8ErrorCounterOverloadPortn
		EkiOnOff
	}


pm10010r100CntlocalLineSmBip8ErrorCounterIndex OBJECT-TYPE
	SYNTAX  INTEGER(0..128)
	MAX-ACCESS  read-only
	STATUS current
	DESCRIPTION
        "
        Index definition for the pm10010r100CntlocalLineSmBip8ErrorCounter 
        table
        "
	::= { pm10010r100CntlocalLineSmBip8ErrorCounterEntry 1 }


pm10010r100CntlocalLineSmBip8ErrorCounterValuePortn OBJECT-TYPE
	SYNTAX  Counter64
	MAX-ACCESS read-only
	STATUS current
	DESCRIPTION
        "
        Line Input SM-BIP8 Errors :This 
        OID gives the current Bit Error 
        Rate (residual SM-BIP8 error) after 
        FEC   <Help> This counter gives 
        the current Bit Error Rate (residual 
        SM-BIP8 error) after FEC
        "
	::= { pm10010r100CntlocalLineSmBip8ErrorCounterEntry 2 }


pm10010r100CntlocalLineSmBip8ErrorCounterErrorPortn OBJECT-TYPE
	SYNTAX  EkiOnOff
	MAX-ACCESS read-only
	STATUS current
	DESCRIPTION
        "
        Line Counter Error :This OID when 
        set indicates the B1 error counter 
        value is invalid on Port
        "
	::= { pm10010r100CntlocalLineSmBip8ErrorCounterEntry 3 }


pm10010r100CntlocalLineSmBip8ErrorCounterOverloadPortn OBJECT-TYPE
	SYNTAX  EkiOnOff
	MAX-ACCESS read-only
	STATUS current
	DESCRIPTION
        "
        Line Counter Overload :This OID 
        when set indicates a B1 error counter 
        overload on Port
        "
	::= { pm10010r100CntlocalLineSmBip8ErrorCounterEntry 4 }


--- *********************************************************
---     TABLE for the pm10010r100CntlocalLineFecCorrectedErrorsCounter articles
--- *********************************************************

pm10010r100CntlocalLineFecCorrectedErrorsCounterTable OBJECT-TYPE
	SYNTAX  SEQUENCE OF Pm10010r100CntlocalLineFecCorrectedErrorsCounterEntry
	MAX-ACCESS not-accessible
	STATUS current
	DESCRIPTION
        "
        List of pm10010r100CntlocalLineFecCorrectedErrorsCounter 
        Article
        "
	::= { pm10010r100CntLine 193 }


pm10010r100CntlocalLineFecCorrectedErrorsCounterEntry OBJECT-TYPE
	SYNTAX Pm10010r100CntlocalLineFecCorrectedErrorsCounterEntry
	MAX-ACCESS not-accessible
	STATUS current
	DESCRIPTION
        "
        Row definition for the pm10010r100CntlocalLineFecCorrectedErrorsCounter 
        table
        "
	INDEX   { pm10010r100CntlocalLineFecCorrectedErrorsCounterIndex }
	::= { pm10010r100CntlocalLineFecCorrectedErrorsCounterTable 1 }


Pm10010r100CntlocalLineFecCorrectedErrorsCounterEntry ::=
	SEQUENCE {
	pm10010r100CntlocalLineFecCorrectedErrorsCounterIndex
		INTEGER,
	pm10010r100CntlocalLineFecCorrectedErrorsCounterValuePortn
		Counter64,
	pm10010r100CntlocalLineFecCorrectedErrorsCounterErrorPortn
		EkiOnOff,
	pm10010r100CntlocalLineFecCorrectedErrorsCounterOverloadPortn
		EkiOnOff
	}


pm10010r100CntlocalLineFecCorrectedErrorsCounterIndex OBJECT-TYPE
	SYNTAX  INTEGER(0..128)
	MAX-ACCESS  read-only
	STATUS current
	DESCRIPTION
        "
        Index definition for the pm10010r100CntlocalLineFecCorrectedErrorsCounter 
        table
        "
	::= { pm10010r100CntlocalLineFecCorrectedErrorsCounterEntry 1 }


pm10010r100CntlocalLineFecCorrectedErrorsCounterValuePortn OBJECT-TYPE
	SYNTAX  Counter64
	MAX-ACCESS read-only
	STATUS current
	DESCRIPTION
        "
        Line Input HD FEC Corrected Errors 
        :This OID gives the current Bit 
        Error Rate before the Hard Decision 
        FEC  <Help> This counter gives
         the current Bit Error Rate before 
        the Hard Decision FEC
        "
	::= { pm10010r100CntlocalLineFecCorrectedErrorsCounterEntry 2 }


pm10010r100CntlocalLineFecCorrectedErrorsCounterErrorPortn OBJECT-TYPE
	SYNTAX  EkiOnOff
	MAX-ACCESS read-only
	STATUS current
	DESCRIPTION
        "
        FEC Counter Error :This bit when 
        set indicates the FEC corrected 
        errors counter value is invalid 
        on Line
        "
	::= { pm10010r100CntlocalLineFecCorrectedErrorsCounterEntry 3 }


pm10010r100CntlocalLineFecCorrectedErrorsCounterOverloadPortn OBJECT-TYPE
	SYNTAX  EkiOnOff
	MAX-ACCESS read-only
	STATUS current
	DESCRIPTION
        "
        FEC Counter Overload :This bit 
        when set indicates a FEC corrected 
        errors counter overload on Line
        "
	::= { pm10010r100CntlocalLineFecCorrectedErrorsCounterEntry 4 }


--- *********************************************************
---     TABLE for the pm10010r100CntremoteLineSmBip8ErrorCounter articles
--- *********************************************************

pm10010r100CntremoteLineSmBip8ErrorCounterTable OBJECT-TYPE
	SYNTAX  SEQUENCE OF Pm10010r100CntremoteLineSmBip8ErrorCounterEntry
	MAX-ACCESS not-accessible
	STATUS current
	DESCRIPTION
        "
        List of pm10010r100CntremoteLineSmBip8ErrorCounter 
        Article
        "
	::= { pm10010r100CntLine 194 }


pm10010r100CntremoteLineSmBip8ErrorCounterEntry OBJECT-TYPE
	SYNTAX Pm10010r100CntremoteLineSmBip8ErrorCounterEntry
	MAX-ACCESS not-accessible
	STATUS current
	DESCRIPTION
        "
        Row definition for the pm10010r100CntremoteLineSmBip8ErrorCounter 
        table
        "
	INDEX   { pm10010r100CntremoteLineSmBip8ErrorCounterIndex }
	::= { pm10010r100CntremoteLineSmBip8ErrorCounterTable 1 }


Pm10010r100CntremoteLineSmBip8ErrorCounterEntry ::=
	SEQUENCE {
	pm10010r100CntremoteLineSmBip8ErrorCounterIndex
		INTEGER,
	pm10010r100CntremoteLineSmBip8ErrorCounterValuePortn
		Counter64,
	pm10010r100CntremoteLineSmBip8ErrorCounterErrorPortn
		EkiOnOff,
	pm10010r100CntremoteLineSmBip8ErrorCounterOverloadPortn
		EkiOnOff
	}


pm10010r100CntremoteLineSmBip8ErrorCounterIndex OBJECT-TYPE
	SYNTAX  INTEGER(0..128)
	MAX-ACCESS  read-only
	STATUS current
	DESCRIPTION
        "
        Index definition for the pm10010r100CntremoteLineSmBip8ErrorCounter 
        table
        "
	::= { pm10010r100CntremoteLineSmBip8ErrorCounterEntry 1 }


pm10010r100CntremoteLineSmBip8ErrorCounterValuePortn OBJECT-TYPE
	SYNTAX  Counter64
	MAX-ACCESS read-only
	STATUS current
	DESCRIPTION
        "
        Remote SM BIP8 :This OID gives 
        the current Bit Error Rate (residual 
        SM-BIP8 error) after FEC on the 
        remote side  <Help> This counter 
        gives the current Bit Error Rate 
        (residual SM-BIP8 error) after
         FEC on the remote side
        "
	::= { pm10010r100CntremoteLineSmBip8ErrorCounterEntry 2 }


pm10010r100CntremoteLineSmBip8ErrorCounterErrorPortn OBJECT-TYPE
	SYNTAX  EkiOnOff
	MAX-ACCESS read-only
	STATUS current
	DESCRIPTION
        "
        Remote Counter Error :
        "
	::= { pm10010r100CntremoteLineSmBip8ErrorCounterEntry 3 }


pm10010r100CntremoteLineSmBip8ErrorCounterOverloadPortn OBJECT-TYPE
	SYNTAX  EkiOnOff
	MAX-ACCESS read-only
	STATUS current
	DESCRIPTION
        "
        Remote Counter Overload :
        "
	::= { pm10010r100CntremoteLineSmBip8ErrorCounterEntry 4 }


--- *********************************************************
---     TABLE for the pm10010r100CntlineDfrmTimCnt articles
--- *********************************************************

pm10010r100CntlineDfrmTimCntTable OBJECT-TYPE
	SYNTAX  SEQUENCE OF Pm10010r100CntlineDfrmTimCntEntry
	MAX-ACCESS not-accessible
	STATUS current
	DESCRIPTION
        "
        List of pm10010r100CntlineDfrmTimCnt 
        Article
        "
	::= { pm10010r100CntLine 195 }


pm10010r100CntlineDfrmTimCntEntry OBJECT-TYPE
	SYNTAX Pm10010r100CntlineDfrmTimCntEntry
	MAX-ACCESS not-accessible
	STATUS current
	DESCRIPTION
        "
        Row definition for the pm10010r100CntlineDfrmTimCnt 
        table
        "
	INDEX   { pm10010r100CntlineDfrmTimCntIndex }
	::= { pm10010r100CntlineDfrmTimCntTable 1 }


Pm10010r100CntlineDfrmTimCntEntry ::=
	SEQUENCE {
	pm10010r100CntlineDfrmTimCntIndex
		INTEGER,
	pm10010r100CntlineDfrmTimCntValuePortn
		Counter64,
	pm10010r100CntlineDfrmTimCntErrorPortn
		EkiOnOff,
	pm10010r100CntlineDfrmTimCntOverloadPortn
		EkiOnOff
	}


pm10010r100CntlineDfrmTimCntIndex OBJECT-TYPE
	SYNTAX  INTEGER(0..128)
	MAX-ACCESS  read-only
	STATUS current
	DESCRIPTION
        "
        Index definition for the pm10010r100CntlineDfrmTimCnt 
        table
        "
	::= { pm10010r100CntlineDfrmTimCntEntry 1 }


pm10010r100CntlineDfrmTimCntValuePortn OBJECT-TYPE
	SYNTAX  Counter64
	MAX-ACCESS read-only
	STATUS current
	DESCRIPTION
        "
        Line Timer Counter :
        "
	::= { pm10010r100CntlineDfrmTimCntEntry 2 }


pm10010r100CntlineDfrmTimCntErrorPortn OBJECT-TYPE
	SYNTAX  EkiOnOff
	MAX-ACCESS read-only
	STATUS current
	DESCRIPTION
        "
        Line Counter Error :This OID when 
        set indicates the deframer timer 
        counter value is invalid on Port
        "
	::= { pm10010r100CntlineDfrmTimCntEntry 3 }


pm10010r100CntlineDfrmTimCntOverloadPortn OBJECT-TYPE
	SYNTAX  EkiOnOff
	MAX-ACCESS read-only
	STATUS current
	DESCRIPTION
        "
        Line Counter Overload :This OID 
        when set indicates a deframer timer 
        counter overload on Port
        "
	::= { pm10010r100CntlineDfrmTimCntEntry 4 }


--- *********************************************************
---     TABLE for the pm10010r100CntlocalLineTrscvFecCorrectedErrorCounter articles
--- *********************************************************

pm10010r100CntlocalLineTrscvFecCorrectedErrorCounterTable OBJECT-TYPE
	SYNTAX  SEQUENCE OF Pm10010r100CntlocalLineTrscvFecCorrectedErrorCounterEntry
	MAX-ACCESS not-accessible
	STATUS current
	DESCRIPTION
        "
        List of pm10010r100CntlocalLineTrscvFecCorrectedErrorCounter 
        Article
        "
	::= { pm10010r100CntLine 196 }


pm10010r100CntlocalLineTrscvFecCorrectedErrorCounterEntry OBJECT-TYPE
	SYNTAX Pm10010r100CntlocalLineTrscvFecCorrectedErrorCounterEntry
	MAX-ACCESS not-accessible
	STATUS current
	DESCRIPTION
        "
        Row definition for the pm10010r100CntlocalLineTrscvFecCorrectedErrorCounter 
        table
        "
	INDEX   { pm10010r100CntlocalLineTrscvFecCorrectedErrorCounterIndex }
	::= { pm10010r100CntlocalLineTrscvFecCorrectedErrorCounterTable 1 }


Pm10010r100CntlocalLineTrscvFecCorrectedErrorCounterEntry ::=
	SEQUENCE {
	pm10010r100CntlocalLineTrscvFecCorrectedErrorCounterIndex
		INTEGER,
	pm10010r100CntlocalLineTrscvFecCorrectedErrorCounterValuePortn
		Counter64,
	pm10010r100CntlocalLineTrscvFecCorrectedErrorCounterErrorPortn
		EkiOnOff,
	pm10010r100CntlocalLineTrscvFecCorrectedErrorCounterOverloadPortn
		EkiOnOff
	}


pm10010r100CntlocalLineTrscvFecCorrectedErrorCounterIndex OBJECT-TYPE
	SYNTAX  INTEGER(0..128)
	MAX-ACCESS  read-only
	STATUS current
	DESCRIPTION
        "
        Index definition for the pm10010r100CntlocalLineTrscvFecCorrectedErrorCounter 
        table
        "
	::= { pm10010r100CntlocalLineTrscvFecCorrectedErrorCounterEntry 1 }


pm10010r100CntlocalLineTrscvFecCorrectedErrorCounterValuePortn OBJECT-TYPE
	SYNTAX  Counter64
	MAX-ACCESS read-only
	STATUS current
	DESCRIPTION
        "
        Line Input SD FEC Corrected Errors 
        :This OID gives the current Bit 
        Error Rate before the Soft Decision 
        FEC  <Help> This counter gives
         the current Bit Error Rate before 
        the Soft Decision FEC
        "
	::= { pm10010r100CntlocalLineTrscvFecCorrectedErrorCounterEntry 2 }


pm10010r100CntlocalLineTrscvFecCorrectedErrorCounterErrorPortn OBJECT-TYPE
	SYNTAX  EkiOnOff
	MAX-ACCESS read-only
	STATUS current
	DESCRIPTION
        "
        Line Counter Error :This OID when 
        set indicates the deframer timer 
        counter value is invalid on Port
        "
	::= { pm10010r100CntlocalLineTrscvFecCorrectedErrorCounterEntry 3 }


pm10010r100CntlocalLineTrscvFecCorrectedErrorCounterOverloadPortn OBJECT-TYPE
	SYNTAX  EkiOnOff
	MAX-ACCESS read-only
	STATUS current
	DESCRIPTION
        "
        Line Counter Overload :This OID 
        when set indicates a deframer timer 
        counter overload on Port
        "
	::= { pm10010r100CntlocalLineTrscvFecCorrectedErrorCounterEntry 4 }


--- *********************************************************
---     TABLE for the pm10010r100CntlocalLineTrscvFecUncorrectedErrorCounter articles
--- *********************************************************

pm10010r100CntlocalLineTrscvFecUncorrectedErrorCounterTable OBJECT-TYPE
	SYNTAX  SEQUENCE OF Pm10010r100CntlocalLineTrscvFecUncorrectedErrorCounterEntry
	MAX-ACCESS not-accessible
	STATUS current
	DESCRIPTION
        "
        List of pm10010r100CntlocalLineTrscvFecUncorrectedErrorCounter 
        Article
        "
	::= { pm10010r100CntLine 197 }


pm10010r100CntlocalLineTrscvFecUncorrectedErrorCounterEntry OBJECT-TYPE
	SYNTAX Pm10010r100CntlocalLineTrscvFecUncorrectedErrorCounterEntry
	MAX-ACCESS not-accessible
	STATUS current
	DESCRIPTION
        "
        Row definition for the pm10010r100CntlocalLineTrscvFecUncorrectedErrorCounter 
        table
        "
	INDEX   { pm10010r100CntlocalLineTrscvFecUncorrectedErrorCounterIndex }
	::= { pm10010r100CntlocalLineTrscvFecUncorrectedErrorCounterTable 1 }


Pm10010r100CntlocalLineTrscvFecUncorrectedErrorCounterEntry ::=
	SEQUENCE {
	pm10010r100CntlocalLineTrscvFecUncorrectedErrorCounterIndex
		INTEGER,
	pm10010r100CntlocalLineTrscvFecUncorrectedErrorCounterValuePortn
		Counter64,
	pm10010r100CntlocalLineTrscvFecUncorrectedErrorCounterErrorPortn
		EkiOnOff,
	pm10010r100CntlocalLineTrscvFecUncorrectedErrorCounterOverloadPortn
		EkiOnOff
	}


pm10010r100CntlocalLineTrscvFecUncorrectedErrorCounterIndex OBJECT-TYPE
	SYNTAX  INTEGER(0..128)
	MAX-ACCESS  read-only
	STATUS current
	DESCRIPTION
        "
        Index definition for the pm10010r100CntlocalLineTrscvFecUncorrectedErrorCounter 
        table
        "
	::= { pm10010r100CntlocalLineTrscvFecUncorrectedErrorCounterEntry 1 }


pm10010r100CntlocalLineTrscvFecUncorrectedErrorCounterValuePortn OBJECT-TYPE
	SYNTAX  Counter64
	MAX-ACCESS read-only
	STATUS current
	DESCRIPTION
        "
        SD Uncorrected :This OID gives 
        the current Bit Error Rate after 
        the Soft Decision FEC (residual) 
         <Help> This counter gives the
         current Bit Error Rate after the 
        Soft Decision FEC (residual)
        "
	::= { pm10010r100CntlocalLineTrscvFecUncorrectedErrorCounterEntry 2 }


pm10010r100CntlocalLineTrscvFecUncorrectedErrorCounterErrorPortn OBJECT-TYPE
	SYNTAX  EkiOnOff
	MAX-ACCESS read-only
	STATUS current
	DESCRIPTION
        "
        Line Counter Error :This OID when 
        set indicates the deframer timer 
        counter value is invalid on Port
        "
	::= { pm10010r100CntlocalLineTrscvFecUncorrectedErrorCounterEntry 3 }


pm10010r100CntlocalLineTrscvFecUncorrectedErrorCounterOverloadPortn OBJECT-TYPE
	SYNTAX  EkiOnOff
	MAX-ACCESS read-only
	STATUS current
	DESCRIPTION
        "
        Line Counter Overload :This OID 
        when set indicates a deframer timer 
        counter overload on Port
        "
	::= { pm10010r100CntlocalLineTrscvFecUncorrectedErrorCounterEntry 4 }







--- *****************************************************
--- $$$$$$$$$$$$$$$$$$$$$$$$$$$$$$$$$$$$$$$$$$$$$$$$$$$$$
---     RMON
--- $$$$$$$$$$$$$$$$$$$$$$$$$$$$$$$$$$$$$$$$$$$$$$$$$$$$$
--- *****************************************************



--- *********************************************************
---     TABLE for the pm10010r100MonupRmonBytesCounterClientInput articles
--- *********************************************************

pm10010r100MonupRmonBytesCounterClientInputTable OBJECT-TYPE
	SYNTAX  SEQUENCE OF Pm10010r100MonupRmonBytesCounterClientInputEntry
	MAX-ACCESS not-accessible
	STATUS current
	DESCRIPTION
        "
        List of pm10010r100MonupRmonBytesCounterClientInput 
        Article
        "
	::= { pm10010r100MonClientRmonCounter 16 }


pm10010r100MonupRmonBytesCounterClientInputEntry OBJECT-TYPE
	SYNTAX Pm10010r100MonupRmonBytesCounterClientInputEntry
	MAX-ACCESS not-accessible
	STATUS current
	DESCRIPTION
        "
        Row definition for the pm10010r100MonupRmonBytesCounterClientInput 
        table
        "
	INDEX   { pm10010r100MonupRmonBytesCounterClientInputIndex }
	::= { pm10010r100MonupRmonBytesCounterClientInputTable 1 }


Pm10010r100MonupRmonBytesCounterClientInputEntry ::=
	SEQUENCE {
	pm10010r100MonupRmonBytesCounterClientInputIndex
		INTEGER,
	pm10010r100MonupRmonBytesCounterClientInputValuePortn
		Counter64,
	pm10010r100MonupRmonBytesCounterClientInputErrorPortn
		EkiOnOff,
	pm10010r100MonupRmonBytesCounterClientInputOverloadPortn
		EkiOnOff
	}


pm10010r100MonupRmonBytesCounterClientInputIndex OBJECT-TYPE
	SYNTAX  INTEGER(0..128)
	MAX-ACCESS  read-only
	STATUS current
	DESCRIPTION
        "
        Index definition for the pm10010r100MonupRmonBytesCounterClientInput 
        table
        "
	::= { pm10010r100MonupRmonBytesCounterClientInputEntry 1 }


pm10010r100MonupRmonBytesCounterClientInputValuePortn OBJECT-TYPE
	SYNTAX  Counter64
	MAX-ACCESS read-only
	STATUS current
	DESCRIPTION
        "
        Client Input Bytes :This counter 
        is increased each time a data byte 
        is received on the client port
          <Help>  This counter gives the 
        number of bytes received on the 
        client port
        "
	::= { pm10010r100MonupRmonBytesCounterClientInputEntry 2 }


pm10010r100MonupRmonBytesCounterClientInputErrorPortn OBJECT-TYPE
	SYNTAX  EkiOnOff
	MAX-ACCESS read-only
	STATUS current
	DESCRIPTION
        "
        Bytes Counter Error :This OID
         when set indicates the Bytes counter 
        value is invalid on client port
        "
	::= { pm10010r100MonupRmonBytesCounterClientInputEntry 3 }


pm10010r100MonupRmonBytesCounterClientInputOverloadPortn OBJECT-TYPE
	SYNTAX  EkiOnOff
	MAX-ACCESS read-only
	STATUS current
	DESCRIPTION
        "
        Bytes Counter Overload :This OID 
        when set indicates a Bytes counter 
        overload on client port
        "
	::= { pm10010r100MonupRmonBytesCounterClientInputEntry 4 }


--- *********************************************************
---     TABLE for the pm10010r100MonupRmonCrcErrorsCounterClientInput articles
--- *********************************************************

pm10010r100MonupRmonCrcErrorsCounterClientInputTable OBJECT-TYPE
	SYNTAX  SEQUENCE OF Pm10010r100MonupRmonCrcErrorsCounterClientInputEntry
	MAX-ACCESS not-accessible
	STATUS current
	DESCRIPTION
        "
        List of pm10010r100MonupRmonCrcErrorsCounterClientInput 
        Article
        "
	::= { pm10010r100MonClientRmonCounter 32 }


pm10010r100MonupRmonCrcErrorsCounterClientInputEntry OBJECT-TYPE
	SYNTAX Pm10010r100MonupRmonCrcErrorsCounterClientInputEntry
	MAX-ACCESS not-accessible
	STATUS current
	DESCRIPTION
        "
        Row definition for the pm10010r100MonupRmonCrcErrorsCounterClientInput 
        table
        "
	INDEX   { pm10010r100MonupRmonCrcErrorsCounterClientInputIndex }
	::= { pm10010r100MonupRmonCrcErrorsCounterClientInputTable 1 }


Pm10010r100MonupRmonCrcErrorsCounterClientInputEntry ::=
	SEQUENCE {
	pm10010r100MonupRmonCrcErrorsCounterClientInputIndex
		INTEGER,
	pm10010r100MonupRmonCrcErrorsCounterClientInputValuePortn
		Counter64,
	pm10010r100MonupRmonCrcErrorsCounterClientInputErrorPortn
		EkiOnOff,
	pm10010r100MonupRmonCrcErrorsCounterClientInputOverloadPortn
		EkiOnOff
	}


pm10010r100MonupRmonCrcErrorsCounterClientInputIndex OBJECT-TYPE
	SYNTAX  INTEGER(0..128)
	MAX-ACCESS  read-only
	STATUS current
	DESCRIPTION
        "
        Index definition for the pm10010r100MonupRmonCrcErrorsCounterClientInput 
        table
        "
	::= { pm10010r100MonupRmonCrcErrorsCounterClientInputEntry 1 }


pm10010r100MonupRmonCrcErrorsCounterClientInputValuePortn OBJECT-TYPE
	SYNTAX  Counter64
	MAX-ACCESS read-only
	STATUS current
	DESCRIPTION
        "
        Client Input B1/CRC Errors :This 
        counter is increased each time
         a B1/CRC error is detected on
         the client port  <Help>  This
         counter gives the number of B1/CRC 
        Errors received on the client port
        "
	::= { pm10010r100MonupRmonCrcErrorsCounterClientInputEntry 2 }


pm10010r100MonupRmonCrcErrorsCounterClientInputErrorPortn OBJECT-TYPE
	SYNTAX  EkiOnOff
	MAX-ACCESS read-only
	STATUS current
	DESCRIPTION
        "
        CRC Errors Counter Error :This 
        OID when set indicates the CRC
         Errors counter value is invalid 
        on client port
        "
	::= { pm10010r100MonupRmonCrcErrorsCounterClientInputEntry 3 }


pm10010r100MonupRmonCrcErrorsCounterClientInputOverloadPortn OBJECT-TYPE
	SYNTAX  EkiOnOff
	MAX-ACCESS read-only
	STATUS current
	DESCRIPTION
        "
        CRC Errors Counter Overload :This 
        OID when set indicates a CRC Errors 
        counter overload on client port
        "
	::= { pm10010r100MonupRmonCrcErrorsCounterClientInputEntry 4 }


--- *********************************************************
---     TABLE for the pm10010r100MonupRmonPacketsCounterClientInput articles
--- *********************************************************

pm10010r100MonupRmonPacketsCounterClientInputTable OBJECT-TYPE
	SYNTAX  SEQUENCE OF Pm10010r100MonupRmonPacketsCounterClientInputEntry
	MAX-ACCESS not-accessible
	STATUS current
	DESCRIPTION
        "
        List of pm10010r100MonupRmonPacketsCounterClientInput 
        Article
        "
	::= { pm10010r100MonClientRmonCounter 48 }


pm10010r100MonupRmonPacketsCounterClientInputEntry OBJECT-TYPE
	SYNTAX Pm10010r100MonupRmonPacketsCounterClientInputEntry
	MAX-ACCESS not-accessible
	STATUS current
	DESCRIPTION
        "
        Row definition for the pm10010r100MonupRmonPacketsCounterClientInput 
        table
        "
	INDEX   { pm10010r100MonupRmonPacketsCounterClientInputIndex }
	::= { pm10010r100MonupRmonPacketsCounterClientInputTable 1 }


Pm10010r100MonupRmonPacketsCounterClientInputEntry ::=
	SEQUENCE {
	pm10010r100MonupRmonPacketsCounterClientInputIndex
		INTEGER,
	pm10010r100MonupRmonPacketsCounterClientInputValuePortn
		Counter64,
	pm10010r100MonupRmonPacketsCounterClientInputErrorPortn
		EkiOnOff,
	pm10010r100MonupRmonPacketsCounterClientInputOverloadPortn
		EkiOnOff
	}


pm10010r100MonupRmonPacketsCounterClientInputIndex OBJECT-TYPE
	SYNTAX  INTEGER(0..128)
	MAX-ACCESS  read-only
	STATUS current
	DESCRIPTION
        "
        Index definition for the pm10010r100MonupRmonPacketsCounterClientInput 
        table
        "
	::= { pm10010r100MonupRmonPacketsCounterClientInputEntry 1 }


pm10010r100MonupRmonPacketsCounterClientInputValuePortn OBJECT-TYPE
	SYNTAX  Counter64
	MAX-ACCESS read-only
	STATUS current
	DESCRIPTION
        "
        Client Input Packets :This counter 
        is increased each time a packet 
        is received on the client port
          <Help>  This counter gives the 
        number of packets received on the 
        client port
        "
	::= { pm10010r100MonupRmonPacketsCounterClientInputEntry 2 }


pm10010r100MonupRmonPacketsCounterClientInputErrorPortn OBJECT-TYPE
	SYNTAX  EkiOnOff
	MAX-ACCESS read-only
	STATUS current
	DESCRIPTION
        "
        Packets Counter Error :This OID 
        when set indicates the Packets
         counter value is invalid on client 
        port
        "
	::= { pm10010r100MonupRmonPacketsCounterClientInputEntry 3 }


pm10010r100MonupRmonPacketsCounterClientInputOverloadPortn OBJECT-TYPE
	SYNTAX  EkiOnOff
	MAX-ACCESS read-only
	STATUS current
	DESCRIPTION
        "
        Packets Counter Overload :This 
        OID when set indicates a Packets 
        counter overload on client port
        "
	::= { pm10010r100MonupRmonPacketsCounterClientInputEntry 4 }


--- *********************************************************
---     TABLE for the pm10010r100MonupRmonBroadcastCounterClientInput articles
--- *********************************************************

pm10010r100MonupRmonBroadcastCounterClientInputTable OBJECT-TYPE
	SYNTAX  SEQUENCE OF Pm10010r100MonupRmonBroadcastCounterClientInputEntry
	MAX-ACCESS not-accessible
	STATUS current
	DESCRIPTION
        "
        List of pm10010r100MonupRmonBroadcastCounterClientInput 
        Article
        "
	::= { pm10010r100MonClientRmonCounter 64 }


pm10010r100MonupRmonBroadcastCounterClientInputEntry OBJECT-TYPE
	SYNTAX Pm10010r100MonupRmonBroadcastCounterClientInputEntry
	MAX-ACCESS not-accessible
	STATUS current
	DESCRIPTION
        "
        Row definition for the pm10010r100MonupRmonBroadcastCounterClientInput 
        table
        "
	INDEX   { pm10010r100MonupRmonBroadcastCounterClientInputIndex }
	::= { pm10010r100MonupRmonBroadcastCounterClientInputTable 1 }


Pm10010r100MonupRmonBroadcastCounterClientInputEntry ::=
	SEQUENCE {
	pm10010r100MonupRmonBroadcastCounterClientInputIndex
		INTEGER,
	pm10010r100MonupRmonBroadcastCounterClientInputValuePortn
		Counter64,
	pm10010r100MonupRmonBroadcastCounterClientInputErrorPortn
		EkiOnOff,
	pm10010r100MonupRmonBroadcastCounterClientInputOverloadPortn
		EkiOnOff
	}


pm10010r100MonupRmonBroadcastCounterClientInputIndex OBJECT-TYPE
	SYNTAX  INTEGER(0..128)
	MAX-ACCESS  read-only
	STATUS current
	DESCRIPTION
        "
        Index definition for the pm10010r100MonupRmonBroadcastCounterClientInput 
        table
        "
	::= { pm10010r100MonupRmonBroadcastCounterClientInputEntry 1 }


pm10010r100MonupRmonBroadcastCounterClientInputValuePortn OBJECT-TYPE
	SYNTAX  Counter64
	MAX-ACCESS read-only
	STATUS current
	DESCRIPTION
        "
        Client Input Broadcast Packets 
        :This counter is increased each 
        time a broadcast packet is received 
        on the client port  <Help>  This 
        counter gives the number of Broadcast 
        packets received on the client
         port
        "
	::= { pm10010r100MonupRmonBroadcastCounterClientInputEntry 2 }


pm10010r100MonupRmonBroadcastCounterClientInputErrorPortn OBJECT-TYPE
	SYNTAX  EkiOnOff
	MAX-ACCESS read-only
	STATUS current
	DESCRIPTION
        "
        Broadcast Counter Error :This
         OID when set indicates the Broadcast 
        counter value is invalid on client 
        port
        "
	::= { pm10010r100MonupRmonBroadcastCounterClientInputEntry 3 }


pm10010r100MonupRmonBroadcastCounterClientInputOverloadPortn OBJECT-TYPE
	SYNTAX  EkiOnOff
	MAX-ACCESS read-only
	STATUS current
	DESCRIPTION
        "
        Broadcast Counter Overload :This 
        OID when set indicates a Broadcast 
        counter overload on client port
        "
	::= { pm10010r100MonupRmonBroadcastCounterClientInputEntry 4 }


--- *********************************************************
---     TABLE for the pm10010r100MonupRmonMulticastCounterClientInput articles
--- *********************************************************

pm10010r100MonupRmonMulticastCounterClientInputTable OBJECT-TYPE
	SYNTAX  SEQUENCE OF Pm10010r100MonupRmonMulticastCounterClientInputEntry
	MAX-ACCESS not-accessible
	STATUS current
	DESCRIPTION
        "
        List of pm10010r100MonupRmonMulticastCounterClientInput 
        Article
        "
	::= { pm10010r100MonClientRmonCounter 80 }


pm10010r100MonupRmonMulticastCounterClientInputEntry OBJECT-TYPE
	SYNTAX Pm10010r100MonupRmonMulticastCounterClientInputEntry
	MAX-ACCESS not-accessible
	STATUS current
	DESCRIPTION
        "
        Row definition for the pm10010r100MonupRmonMulticastCounterClientInput 
        table
        "
	INDEX   { pm10010r100MonupRmonMulticastCounterClientInputIndex }
	::= { pm10010r100MonupRmonMulticastCounterClientInputTable 1 }


Pm10010r100MonupRmonMulticastCounterClientInputEntry ::=
	SEQUENCE {
	pm10010r100MonupRmonMulticastCounterClientInputIndex
		INTEGER,
	pm10010r100MonupRmonMulticastCounterClientInputValuePortn
		Counter64,
	pm10010r100MonupRmonMulticastCounterClientInputErrorPortn
		EkiOnOff,
	pm10010r100MonupRmonMulticastCounterClientInputOverloadPortn
		EkiOnOff
	}


pm10010r100MonupRmonMulticastCounterClientInputIndex OBJECT-TYPE
	SYNTAX  INTEGER(0..128)
	MAX-ACCESS  read-only
	STATUS current
	DESCRIPTION
        "
        Index definition for the pm10010r100MonupRmonMulticastCounterClientInput 
        table
        "
	::= { pm10010r100MonupRmonMulticastCounterClientInputEntry 1 }


pm10010r100MonupRmonMulticastCounterClientInputValuePortn OBJECT-TYPE
	SYNTAX  Counter64
	MAX-ACCESS read-only
	STATUS current
	DESCRIPTION
        "
        Client Input Multicast Packets 
        :This counter is increased each 
        time a Multicast packet is received 
        on the client port  <Help>  This 
        counter gives the number of Multicast 
        packets received on the client
         port
        "
	::= { pm10010r100MonupRmonMulticastCounterClientInputEntry 2 }


pm10010r100MonupRmonMulticastCounterClientInputErrorPortn OBJECT-TYPE
	SYNTAX  EkiOnOff
	MAX-ACCESS read-only
	STATUS current
	DESCRIPTION
        "
        Multicast Counter Error :This
         OID when set indicates the Multicast 
        counter value is invalid on client 
        port
        "
	::= { pm10010r100MonupRmonMulticastCounterClientInputEntry 3 }


pm10010r100MonupRmonMulticastCounterClientInputOverloadPortn OBJECT-TYPE
	SYNTAX  EkiOnOff
	MAX-ACCESS read-only
	STATUS current
	DESCRIPTION
        "
        Multicast Counter Overload :This 
        OID when set indicates a Multicast 
        counter overload on client port
        "
	::= { pm10010r100MonupRmonMulticastCounterClientInputEntry 4 }


--- *********************************************************
---     TABLE for the pm10010r100MonupRmonPauseFrameCounterClientInput articles
--- *********************************************************

pm10010r100MonupRmonPauseFrameCounterClientInputTable OBJECT-TYPE
	SYNTAX  SEQUENCE OF Pm10010r100MonupRmonPauseFrameCounterClientInputEntry
	MAX-ACCESS not-accessible
	STATUS current
	DESCRIPTION
        "
        List of pm10010r100MonupRmonPauseFrameCounterClientInput 
        Article
        "
	::= { pm10010r100MonClientRmonCounter 96 }


pm10010r100MonupRmonPauseFrameCounterClientInputEntry OBJECT-TYPE
	SYNTAX Pm10010r100MonupRmonPauseFrameCounterClientInputEntry
	MAX-ACCESS not-accessible
	STATUS current
	DESCRIPTION
        "
        Row definition for the pm10010r100MonupRmonPauseFrameCounterClientInput 
        table
        "
	INDEX   { pm10010r100MonupRmonPauseFrameCounterClientInputIndex }
	::= { pm10010r100MonupRmonPauseFrameCounterClientInputTable 1 }


Pm10010r100MonupRmonPauseFrameCounterClientInputEntry ::=
	SEQUENCE {
	pm10010r100MonupRmonPauseFrameCounterClientInputIndex
		INTEGER,
	pm10010r100MonupRmonPauseFrameCounterClientInputValuePortn
		Counter64,
	pm10010r100MonupRmonPauseFrameCounterClientInputErrorPortn
		EkiOnOff,
	pm10010r100MonupRmonPauseFrameCounterClientInputOverloadPortn
		EkiOnOff
	}


pm10010r100MonupRmonPauseFrameCounterClientInputIndex OBJECT-TYPE
	SYNTAX  INTEGER(0..128)
	MAX-ACCESS  read-only
	STATUS current
	DESCRIPTION
        "
        Index definition for the pm10010r100MonupRmonPauseFrameCounterClientInput 
        table
        "
	::= { pm10010r100MonupRmonPauseFrameCounterClientInputEntry 1 }


pm10010r100MonupRmonPauseFrameCounterClientInputValuePortn OBJECT-TYPE
	SYNTAX  Counter64
	MAX-ACCESS read-only
	STATUS current
	DESCRIPTION
        "
        Client Input Pause Frames :This 
        counter is increased each time
         a Pause frame is received on the 
        client port  <Help>  This counter 
        gives the number of Pause frames 
        received on the client port
        "
	::= { pm10010r100MonupRmonPauseFrameCounterClientInputEntry 2 }


pm10010r100MonupRmonPauseFrameCounterClientInputErrorPortn OBJECT-TYPE
	SYNTAX  EkiOnOff
	MAX-ACCESS read-only
	STATUS current
	DESCRIPTION
        "
        Pause Counter Error :This OID
         when set indicates the Pause counter 
        value is invalid on client port
        "
	::= { pm10010r100MonupRmonPauseFrameCounterClientInputEntry 3 }


pm10010r100MonupRmonPauseFrameCounterClientInputOverloadPortn OBJECT-TYPE
	SYNTAX  EkiOnOff
	MAX-ACCESS read-only
	STATUS current
	DESCRIPTION
        "
        Pause Counter Overload :This OID 
        when set indicates a Pause counter 
        overload on client port
        "
	::= { pm10010r100MonupRmonPauseFrameCounterClientInputEntry 4 }







--- *****************************************************
--- $$$$$$$$$$$$$$$$$$$$$$$$$$$$$$$$$$$$$$$$$$$$$$$$$$$$$
---     MEASURES
--- $$$$$$$$$$$$$$$$$$$$$$$$$$$$$$$$$$$$$$$$$$$$$$$$$$$$$
--- *****************************************************



pm10010r100Mesrsynth0 OBJECT-TYPE
	  SYNTAX EkiMeasureType
	  MAX-ACCESS read-only
	  STATUS deprecated
	  DESCRIPTION
        "
        Not Used :
        "
	  ::= { pm10010r100MesrOther 0 }



pm10010r100Mesrsynth1 OBJECT-TYPE
	  SYNTAX EkiMeasureType
	  MAX-ACCESS read-only
	  STATUS deprecated
	  DESCRIPTION
        "
        Not Used :
        "
	  ::= { pm10010r100MesrOther 1 }



--- *****************************************************
---     LEAF for the pmIntervalNumber article
--- *****************************************************

pm10010r100MesrpmIntervalNumber OBJECT-TYPE
	  SYNTAX Unsigned32 (0..65535)
	  MAX-ACCESS read-only
	  STATUS current
	  DESCRIPTION
        "
        PM Interval Counter :
        "
	  ::= { pm10010r100MesrOther 7 }



--- *****************************************************
---     LEAF for the clientCfpTemp article
--- *****************************************************

pm10010r100MesrclientCfpTemp OBJECT-TYPE
	  SYNTAX Unsigned32 (0..65535)
	  MAX-ACCESS read-only
	  STATUS current
	  DESCRIPTION
        "
        Client Trscv Temperature :This 
        OID gives the temperature value 
        of the Client Transceiver, read 
        from the DDM (Digital Diagnostic 
        Monitoring) (Temperature = AV/256) 
        (Unit = C) <Help> This Measure
         gives the temperature value of 
        the Client Transceiver
        "
	  ::= { pm10010r100MesrClient 8 }



--- *****************************************************
---     LEAF for the clientCfp3v3Voltage article
--- *****************************************************

pm10010r100MesrclientCfp3v3Voltage OBJECT-TYPE
	  SYNTAX Unsigned32 (0..65535)
	  MAX-ACCESS read-only
	  STATUS current
	  DESCRIPTION
        "
        Client Trscv Voltage :This OID 
        gives the 3V3 voltage value of
         the Client Transceiver, read from 
        the DDM (Digital Diagnostic Monitoring) 
         (Voltage = AV/1000) (Unit = V) 
        <Help> This Measure gives the 3V3 
        voltage value of the Client Transceiver
        "
	  ::= { pm10010r100MesrClient 9 }



--- *****************************************************
---     LEAF for the clientSoaBiasCurrent article
--- *****************************************************

pm10010r100MesrclientSoaBiasCurrent OBJECT-TYPE
	  SYNTAX Unsigned32 (0..65535)
	  MAX-ACCESS read-only
	  STATUS current
	  DESCRIPTION
        "
        Client Trscv SOA Bias :This OID 
        gives the SOA bias value of the 
        Client Transceiver, read from the 
        DDM (Digital Diagnostic Monitoring) 
         (Bias = AV/500) (Unit = mA) <Help> 
        This Measure gives the SOA bias 
        value of the Client Transceiver
        "
	  ::= { pm10010r100MesrClient 10 }



--- *****************************************************
---     LEAF for the lineMsaTemp article
--- *****************************************************

pm10010r100MesrlineMsaTemp OBJECT-TYPE
	  SYNTAX Unsigned32 (0..65535)
	  MAX-ACCESS read-only
	  STATUS current
	  DESCRIPTION
        "
        Line Trscv Temperature :This OID 
        gives the temperature value of
         the Line Transceiver, read from 
        the DDM (Digital Diagnostic Monitoring) 
         (Temperature = AV/256) (Unit = 
        C) <Help> This Measure gives the 
        temperature value of the Line Transceiver.This 
        temperature must remain below 95°C 
        for proper operation
        "
	  ::= { pm10010r100MesrLine 12 }



--- *****************************************************
---     LEAF for the lineMsa3v3Voltage article
--- *****************************************************

pm10010r100MesrlineMsa3v3Voltage OBJECT-TYPE
	  SYNTAX Unsigned32 (0..65535)
	  MAX-ACCESS read-only
	  STATUS current
	  DESCRIPTION
        "
        Line Trscv Voltage :This OID gives 
        the 3V3 voltage value of the Line 
        Transceiver, read from the DDM
         (Digital Diagnostic Monitoring) 
        (Voltage = AV/1000) (Unit = V)
         <Help> This Measure gives the
         3V3 voltage value of the Line
         Transceiver
        "
	  ::= { pm10010r100MesrLine 13 }



--- *****************************************************
---     LEAF for the lineSoaBiasCurrent article
--- *****************************************************

pm10010r100MesrlineSoaBiasCurrent OBJECT-TYPE
	  SYNTAX Unsigned32 (0..65535)
	  MAX-ACCESS read-only
	  STATUS current
	  DESCRIPTION
        "
        Line Trscv SOA Bias :This OID
         gives the SOA bias value of the 
        Line Transceiver,read from the
         DDM (Digital Diagnostic Monitoring) 
         (Bias = AV/500) (Unit = mA) <Help> 
        This Measure gives the SOA bias 
        value of the Line Transceiver
        "
	  ::= { pm10010r100MesrLine 14 }



--- *********************************************************
---     TABLE for the pm10010r100MesrclientNetTxTemp articles
--- *********************************************************

pm10010r100MesrclientNetTxTempTable OBJECT-TYPE
	SYNTAX  SEQUENCE OF Pm10010r100MesrclientNetTxTempEntry
	MAX-ACCESS not-accessible
	STATUS current
	DESCRIPTION
        "
        List of pm10010r100MesrclientNetTxTemp 
        Article
        "
	::= { pm10010r100MesrClient 16 }


pm10010r100MesrclientNetTxTempEntry OBJECT-TYPE
	SYNTAX Pm10010r100MesrclientNetTxTempEntry
	MAX-ACCESS not-accessible
	STATUS current
	DESCRIPTION
        "
        Row definition for the pm10010r100MesrclientNetTxTemp 
        table
        "
	INDEX   { pm10010r100MesrclientNetTxTempIndex }
	::= { pm10010r100MesrclientNetTxTempTable 1 }


Pm10010r100MesrclientNetTxTempEntry ::=
	SEQUENCE {
	pm10010r100MesrclientNetTxTempIndex
		INTEGER,
	pm10010r100MesrclientNetTxTempPortn
		INTEGER 
	}


pm10010r100MesrclientNetTxTempIndex OBJECT-TYPE
	SYNTAX  INTEGER(0..128)
	MAX-ACCESS  read-only
	STATUS current
	DESCRIPTION
        "
        Index definition for the pm10010r100MesrclientNetTxTemp 
        table
        "
	::= { pm10010r100MesrclientNetTxTempEntry 1 }


pm10010r100MesrclientNetTxTempPortn OBJECT-TYPE
	SYNTAX  INTEGER (0..65535)
	MAX-ACCESS read-only
	STATUS current
	DESCRIPTION
        "
        Client Trscv Temperature :This 
        OID gives the Laser temperature 
        value of the Client Transceiver, 
        read from the DDM (Digital Diagnostic 
        Monitoring) (Temperature = AV/256) 
        (Unit = C) <Help> This Measure
         gives the Laser temperature value 
        of the Client Transceiver
        "
	::= { pm10010r100MesrclientNetTxTempEntry 2 }


--- *********************************************************
---     TABLE for the pm10010r100MesrclientNetTxBias articles
--- *********************************************************

pm10010r100MesrclientNetTxBiasTable OBJECT-TYPE
	SYNTAX  SEQUENCE OF Pm10010r100MesrclientNetTxBiasEntry
	MAX-ACCESS not-accessible
	STATUS current
	DESCRIPTION
        "
        List of pm10010r100MesrclientNetTxBias 
        Article
        "
	::= { pm10010r100MesrClient 32 }


pm10010r100MesrclientNetTxBiasEntry OBJECT-TYPE
	SYNTAX Pm10010r100MesrclientNetTxBiasEntry
	MAX-ACCESS not-accessible
	STATUS current
	DESCRIPTION
        "
        Row definition for the pm10010r100MesrclientNetTxBias 
        table
        "
	INDEX   { pm10010r100MesrclientNetTxBiasIndex }
	::= { pm10010r100MesrclientNetTxBiasTable 1 }


Pm10010r100MesrclientNetTxBiasEntry ::=
	SEQUENCE {
	pm10010r100MesrclientNetTxBiasIndex
		INTEGER,
	pm10010r100MesrclientNetTxBiasPortn
		INTEGER 
	}


pm10010r100MesrclientNetTxBiasIndex OBJECT-TYPE
	SYNTAX  INTEGER(0..128)
	MAX-ACCESS  read-only
	STATUS current
	DESCRIPTION
        "
        Index definition for the pm10010r100MesrclientNetTxBias 
        table
        "
	::= { pm10010r100MesrclientNetTxBiasEntry 1 }


pm10010r100MesrclientNetTxBiasPortn OBJECT-TYPE
	SYNTAX  INTEGER (0..65535)
	MAX-ACCESS read-only
	STATUS current
	DESCRIPTION
        "
        Client Trscv Laser Bias :This
         OID gives the Laser bias value 
        of the Client Transceiver, read 
        from the DDM (Digital Diagnostic 
        Monitoring) (Bias = AV/500) (Unit 
        = mA) <Help> This Measure gives 
        the Laser bias value of the Client 
        Transceiver
        "
	::= { pm10010r100MesrclientNetTxBiasEntry 2 }


--- *********************************************************
---     TABLE for the pm10010r100MesrclientNetTxPwr articles
--- *********************************************************

pm10010r100MesrclientNetTxPwrTable OBJECT-TYPE
	SYNTAX  SEQUENCE OF Pm10010r100MesrclientNetTxPwrEntry
	MAX-ACCESS not-accessible
	STATUS current
	DESCRIPTION
        "
        List of pm10010r100MesrclientNetTxPwr 
        Article
        "
	::= { pm10010r100MesrClient 48 }


pm10010r100MesrclientNetTxPwrEntry OBJECT-TYPE
	SYNTAX Pm10010r100MesrclientNetTxPwrEntry
	MAX-ACCESS not-accessible
	STATUS current
	DESCRIPTION
        "
        Row definition for the pm10010r100MesrclientNetTxPwr 
        table
        "
	INDEX   { pm10010r100MesrclientNetTxPwrIndex }
	::= { pm10010r100MesrclientNetTxPwrTable 1 }


Pm10010r100MesrclientNetTxPwrEntry ::=
	SEQUENCE {
	pm10010r100MesrclientNetTxPwrIndex
		INTEGER,
	pm10010r100MesrclientNetTxPwrPortn
		INTEGER 
	}


pm10010r100MesrclientNetTxPwrIndex OBJECT-TYPE
	SYNTAX  INTEGER(0..128)
	MAX-ACCESS  read-only
	STATUS current
	DESCRIPTION
        "
        Index definition for the pm10010r100MesrclientNetTxPwr 
        table
        "
	::= { pm10010r100MesrclientNetTxPwrEntry 1 }


pm10010r100MesrclientNetTxPwrPortn OBJECT-TYPE
	SYNTAX  INTEGER (0..65535)
	MAX-ACCESS read-only
	STATUS current
	DESCRIPTION
        "
        Client Trscv Tx Power :This OID 
        gives the transmit power value
         of the Client Transceiver, read 
        from the DDM (Digital Diagnostic 
        Monitoring) (Power = 10*log(AV)-40) 
        (Unit = dBm) <Help> This Measure 
        gives the transmit power value
         of the Client Transceiver
        "
	::= { pm10010r100MesrclientNetTxPwrEntry 2 }


--- *********************************************************
---     TABLE for the pm10010r100MesrclientNetRxPwr articles
--- *********************************************************

pm10010r100MesrclientNetRxPwrTable OBJECT-TYPE
	SYNTAX  SEQUENCE OF Pm10010r100MesrclientNetRxPwrEntry
	MAX-ACCESS not-accessible
	STATUS current
	DESCRIPTION
        "
        List of pm10010r100MesrclientNetRxPwr 
        Article
        "
	::= { pm10010r100MesrClient 64 }


pm10010r100MesrclientNetRxPwrEntry OBJECT-TYPE
	SYNTAX Pm10010r100MesrclientNetRxPwrEntry
	MAX-ACCESS not-accessible
	STATUS current
	DESCRIPTION
        "
        Row definition for the pm10010r100MesrclientNetRxPwr 
        table
        "
	INDEX   { pm10010r100MesrclientNetRxPwrIndex }
	::= { pm10010r100MesrclientNetRxPwrTable 1 }


Pm10010r100MesrclientNetRxPwrEntry ::=
	SEQUENCE {
	pm10010r100MesrclientNetRxPwrIndex
		INTEGER,
	pm10010r100MesrclientNetRxPwrPortn
		INTEGER 
	}


pm10010r100MesrclientNetRxPwrIndex OBJECT-TYPE
	SYNTAX  INTEGER(0..128)
	MAX-ACCESS  read-only
	STATUS current
	DESCRIPTION
        "
        Index definition for the pm10010r100MesrclientNetRxPwr 
        table
        "
	::= { pm10010r100MesrclientNetRxPwrEntry 1 }


pm10010r100MesrclientNetRxPwrPortn OBJECT-TYPE
	SYNTAX  INTEGER (0..65535)
	MAX-ACCESS read-only
	STATUS current
	DESCRIPTION
        "
        Client Trscv Rx Power :This OID 
        gives the receive power value of 
        the Client Transceiver, read in 
        the DDM (Digital Diagnostic Monitoring) 
        (Power = 10*log(AV)-40) (Unit = 
        dBm) <Help> This Measure gives
         the receive power value of the 
        Client Transceiver
        "
	::= { pm10010r100MesrclientNetRxPwrEntry 2 }


--- *********************************************************
---     TABLE for the pm10010r100MesrlineNetTxLaserOutputPwr articles
--- *********************************************************

pm10010r100MesrlineNetTxLaserOutputPwrTable OBJECT-TYPE
	SYNTAX  SEQUENCE OF Pm10010r100MesrlineNetTxLaserOutputPwrEntry
	MAX-ACCESS not-accessible
	STATUS current
	DESCRIPTION
        "
        List of pm10010r100MesrlineNetTxLaserOutputPwr 
        Article
        "
	::= { pm10010r100MesrLine 80 }


pm10010r100MesrlineNetTxLaserOutputPwrEntry OBJECT-TYPE
	SYNTAX Pm10010r100MesrlineNetTxLaserOutputPwrEntry
	MAX-ACCESS not-accessible
	STATUS current
	DESCRIPTION
        "
        Row definition for the pm10010r100MesrlineNetTxLaserOutputPwr 
        table
        "
	INDEX   { pm10010r100MesrlineNetTxLaserOutputPwrIndex }
	::= { pm10010r100MesrlineNetTxLaserOutputPwrTable 1 }


Pm10010r100MesrlineNetTxLaserOutputPwrEntry ::=
	SEQUENCE {
	pm10010r100MesrlineNetTxLaserOutputPwrIndex
		INTEGER,
	pm10010r100MesrlineNetTxLaserOutputPwrPortn
		INTEGER 
	}


pm10010r100MesrlineNetTxLaserOutputPwrIndex OBJECT-TYPE
	SYNTAX  INTEGER(0..128)
	MAX-ACCESS  read-only
	STATUS current
	DESCRIPTION
        "
        Index definition for the pm10010r100MesrlineNetTxLaserOutputPwr 
        table
        "
	::= { pm10010r100MesrlineNetTxLaserOutputPwrEntry 1 }


pm10010r100MesrlineNetTxLaserOutputPwrPortn OBJECT-TYPE
	SYNTAX  INTEGER (0..65535)
	MAX-ACCESS read-only
	STATUS current
	DESCRIPTION
        "
        Current Line Trscv Tx Power :This 
        OID gives the Tx Laser transmit 
        power value of the Line Transceiver, 
        read in the DDM (Digital Diagnostic 
        Monitoring) (Power = AV/100) (Unit 
        = dBm) <Help> This Measure gives 
        the Tx Laser transmit power value 
        of the Line Transceiver
        "
	::= { pm10010r100MesrlineNetTxLaserOutputPwrEntry 2 }


--- *********************************************************
---     TABLE for the pm10010r100MesrlineNetTxLaserTemp articles
--- *********************************************************

pm10010r100MesrlineNetTxLaserTempTable OBJECT-TYPE
	SYNTAX  SEQUENCE OF Pm10010r100MesrlineNetTxLaserTempEntry
	MAX-ACCESS not-accessible
	STATUS current
	DESCRIPTION
        "
        List of pm10010r100MesrlineNetTxLaserTemp 
        Article
        "
	::= { pm10010r100MesrLine 96 }


pm10010r100MesrlineNetTxLaserTempEntry OBJECT-TYPE
	SYNTAX Pm10010r100MesrlineNetTxLaserTempEntry
	MAX-ACCESS not-accessible
	STATUS current
	DESCRIPTION
        "
        Row definition for the pm10010r100MesrlineNetTxLaserTemp 
        table
        "
	INDEX   { pm10010r100MesrlineNetTxLaserTempIndex }
	::= { pm10010r100MesrlineNetTxLaserTempTable 1 }


Pm10010r100MesrlineNetTxLaserTempEntry ::=
	SEQUENCE {
	pm10010r100MesrlineNetTxLaserTempIndex
		INTEGER,
	pm10010r100MesrlineNetTxLaserTempPortn
		INTEGER 
	}


pm10010r100MesrlineNetTxLaserTempIndex OBJECT-TYPE
	SYNTAX  INTEGER(0..128)
	MAX-ACCESS  read-only
	STATUS current
	DESCRIPTION
        "
        Index definition for the pm10010r100MesrlineNetTxLaserTemp 
        table
        "
	::= { pm10010r100MesrlineNetTxLaserTempEntry 1 }


pm10010r100MesrlineNetTxLaserTempPortn OBJECT-TYPE
	SYNTAX  INTEGER (0..65535)
	MAX-ACCESS read-only
	STATUS current
	DESCRIPTION
        "
        Current Line Trscv Tx Laser Temperature 
        :This OID gives the Tx Laser Temperature 
        value of the Line Transceiver,
         read from the DDM (Digital Diagnostic 
        Monitoring) (Temperature = AV/256) 
        (Unit = C) <Help> This Measure
         gives the Tx Laser Temperature 
        value of the Line Transceiver
        "
	::= { pm10010r100MesrlineNetTxLaserTempEntry 2 }


--- *********************************************************
---     TABLE for the pm10010r100MesrlineNetTxBiasCurrent articles
--- *********************************************************

pm10010r100MesrlineNetTxBiasCurrentTable OBJECT-TYPE
	SYNTAX  SEQUENCE OF Pm10010r100MesrlineNetTxBiasCurrentEntry
	MAX-ACCESS not-accessible
	STATUS current
	DESCRIPTION
        "
        List of pm10010r100MesrlineNetTxBiasCurrent 
        Article
        "
	::= { pm10010r100MesrLine 112 }


pm10010r100MesrlineNetTxBiasCurrentEntry OBJECT-TYPE
	SYNTAX Pm10010r100MesrlineNetTxBiasCurrentEntry
	MAX-ACCESS not-accessible
	STATUS current
	DESCRIPTION
        "
        Row definition for the pm10010r100MesrlineNetTxBiasCurrent 
        table
        "
	INDEX   { pm10010r100MesrlineNetTxBiasCurrentIndex }
	::= { pm10010r100MesrlineNetTxBiasCurrentTable 1 }


Pm10010r100MesrlineNetTxBiasCurrentEntry ::=
	SEQUENCE {
	pm10010r100MesrlineNetTxBiasCurrentIndex
		INTEGER,
	pm10010r100MesrlineNetTxBiasCurrentPortn
		INTEGER 
	}


pm10010r100MesrlineNetTxBiasCurrentIndex OBJECT-TYPE
	SYNTAX  INTEGER(0..128)
	MAX-ACCESS  read-only
	STATUS current
	DESCRIPTION
        "
        Index definition for the pm10010r100MesrlineNetTxBiasCurrent 
        table
        "
	::= { pm10010r100MesrlineNetTxBiasCurrentEntry 1 }


pm10010r100MesrlineNetTxBiasCurrentPortn OBJECT-TYPE
	SYNTAX  INTEGER (0..65535)
	MAX-ACCESS read-only
	STATUS current
	DESCRIPTION
        "
        Current Line Trscv Tx Laser Bias 
        :This OID gives the Tx Laser Bias 
        value of the Line Transceiver,
         read from the DDM (Digital Diagnostic 
        Monitoring) (Bias = AV/10) (Unit 
        = mA) <Help> This Measure gives 
        the Tx Laser Bias value of the
         Line Transceiver
        "
	::= { pm10010r100MesrlineNetTxBiasCurrentEntry 2 }


--- *********************************************************
---     TABLE for the pm10010r100MesrlineNetRxInputPwr articles
--- *********************************************************

pm10010r100MesrlineNetRxInputPwrTable OBJECT-TYPE
	SYNTAX  SEQUENCE OF Pm10010r100MesrlineNetRxInputPwrEntry
	MAX-ACCESS not-accessible
	STATUS current
	DESCRIPTION
        "
        List of pm10010r100MesrlineNetRxInputPwr 
        Article
        "
	::= { pm10010r100MesrLine 128 }


pm10010r100MesrlineNetRxInputPwrEntry OBJECT-TYPE
	SYNTAX Pm10010r100MesrlineNetRxInputPwrEntry
	MAX-ACCESS not-accessible
	STATUS current
	DESCRIPTION
        "
        Row definition for the pm10010r100MesrlineNetRxInputPwr 
        table
        "
	INDEX   { pm10010r100MesrlineNetRxInputPwrIndex }
	::= { pm10010r100MesrlineNetRxInputPwrTable 1 }


Pm10010r100MesrlineNetRxInputPwrEntry ::=
	SEQUENCE {
	pm10010r100MesrlineNetRxInputPwrIndex
		INTEGER,
	pm10010r100MesrlineNetRxInputPwrPortn
		INTEGER 
	}


pm10010r100MesrlineNetRxInputPwrIndex OBJECT-TYPE
	SYNTAX  INTEGER(0..128)
	MAX-ACCESS  read-only
	STATUS current
	DESCRIPTION
        "
        Index definition for the pm10010r100MesrlineNetRxInputPwr 
        table
        "
	::= { pm10010r100MesrlineNetRxInputPwrEntry 1 }


pm10010r100MesrlineNetRxInputPwrPortn OBJECT-TYPE
	SYNTAX  INTEGER (0..65535)
	MAX-ACCESS read-only
	STATUS current
	DESCRIPTION
        "
        Current Line Trscv Rx Power :This 
        OID gives the Receive power value 
        of the Line Transceiver, read in 
        the DDM (Digital Diagnostic Monitoring) 
        (Power = AV/100) (Unit = dBm) <Help> 
        This Measure gives the Receive
         power value of the Line Transceiver
        "
	::= { pm10010r100MesrlineNetRxInputPwrEntry 2 }


--- *********************************************************
---     TABLE for the pm10010r100MesrlineResidualChromaticDisp articles
--- *********************************************************

pm10010r100MesrlineResidualChromaticDispTable OBJECT-TYPE
	SYNTAX  SEQUENCE OF Pm10010r100MesrlineResidualChromaticDispEntry
	MAX-ACCESS not-accessible
	STATUS current
	DESCRIPTION
        "
        List of pm10010r100MesrlineResidualChromaticDisp 
        Article
        "
	::= { pm10010r100MesrLine 144 }


pm10010r100MesrlineResidualChromaticDispEntry OBJECT-TYPE
	SYNTAX Pm10010r100MesrlineResidualChromaticDispEntry
	MAX-ACCESS not-accessible
	STATUS current
	DESCRIPTION
        "
        Row definition for the pm10010r100MesrlineResidualChromaticDisp 
        table
        "
	INDEX   { pm10010r100MesrlineResidualChromaticDispIndex }
	::= { pm10010r100MesrlineResidualChromaticDispTable 1 }


Pm10010r100MesrlineResidualChromaticDispEntry ::=
	SEQUENCE {
	pm10010r100MesrlineResidualChromaticDispIndex
		INTEGER,
	pm10010r100MesrlineResidualChromaticDispPortn
		INTEGER 
	}


pm10010r100MesrlineResidualChromaticDispIndex OBJECT-TYPE
	SYNTAX  INTEGER(0..128)
	MAX-ACCESS  read-only
	STATUS current
	DESCRIPTION
        "
        Index definition for the pm10010r100MesrlineResidualChromaticDisp 
        table
        "
	::= { pm10010r100MesrlineResidualChromaticDispEntry 1 }


pm10010r100MesrlineResidualChromaticDispPortn OBJECT-TYPE
	SYNTAX  INTEGER (0..65535)
	MAX-ACCESS read-only
	STATUS current
	DESCRIPTION
        "
        Current Residual Chromatic Dispersion 
        :This OID gives the current Residual 
        Chromatic Dispersion on the Line 
        interface  (Unit = ps/nm)<Help> 
        This measure gives the current
         Residual Chromatic Dispersion
         on the Line interface.
        "
	::= { pm10010r100MesrlineResidualChromaticDispEntry 2 }


--- *********************************************************
---     TABLE for the pm10010r100MesrlineDiffGroupDelay articles
--- *********************************************************

pm10010r100MesrlineDiffGroupDelayTable OBJECT-TYPE
	SYNTAX  SEQUENCE OF Pm10010r100MesrlineDiffGroupDelayEntry
	MAX-ACCESS not-accessible
	STATUS current
	DESCRIPTION
        "
        List of pm10010r100MesrlineDiffGroupDelay 
        Article
        "
	::= { pm10010r100MesrLine 148 }


pm10010r100MesrlineDiffGroupDelayEntry OBJECT-TYPE
	SYNTAX Pm10010r100MesrlineDiffGroupDelayEntry
	MAX-ACCESS not-accessible
	STATUS current
	DESCRIPTION
        "
        Row definition for the pm10010r100MesrlineDiffGroupDelay 
        table
        "
	INDEX   { pm10010r100MesrlineDiffGroupDelayIndex }
	::= { pm10010r100MesrlineDiffGroupDelayTable 1 }


Pm10010r100MesrlineDiffGroupDelayEntry ::=
	SEQUENCE {
	pm10010r100MesrlineDiffGroupDelayIndex
		INTEGER,
	pm10010r100MesrlineDiffGroupDelayPortn
		INTEGER 
	}


pm10010r100MesrlineDiffGroupDelayIndex OBJECT-TYPE
	SYNTAX  INTEGER(0..128)
	MAX-ACCESS  read-only
	STATUS current
	DESCRIPTION
        "
        Index definition for the pm10010r100MesrlineDiffGroupDelay 
        table
        "
	::= { pm10010r100MesrlineDiffGroupDelayEntry 1 }


pm10010r100MesrlineDiffGroupDelayPortn OBJECT-TYPE
	SYNTAX  INTEGER (0..65535)
	MAX-ACCESS read-only
	STATUS current
	DESCRIPTION
        "
        Current Differential Group Delay 
        :This OID gives the current Differential 
        Group Delay on the Line interface 
          (Unit = ps)<Help> This measure 
        gives the current Differential
         Group Delay on the Line interface.
        "
	::= { pm10010r100MesrlineDiffGroupDelayEntry 2 }


--- *********************************************************
---     TABLE for the pm10010r100MesrlineQFactor articles
--- *********************************************************

pm10010r100MesrlineQFactorTable OBJECT-TYPE
	SYNTAX  SEQUENCE OF Pm10010r100MesrlineQFactorEntry
	MAX-ACCESS not-accessible
	STATUS current
	DESCRIPTION
        "
        List of pm10010r100MesrlineQFactor 
        Article
        "
	::= { pm10010r100MesrLine 152 }


pm10010r100MesrlineQFactorEntry OBJECT-TYPE
	SYNTAX Pm10010r100MesrlineQFactorEntry
	MAX-ACCESS not-accessible
	STATUS current
	DESCRIPTION
        "
        Row definition for the pm10010r100MesrlineQFactor 
        table
        "
	INDEX   { pm10010r100MesrlineQFactorIndex }
	::= { pm10010r100MesrlineQFactorTable 1 }


Pm10010r100MesrlineQFactorEntry ::=
	SEQUENCE {
	pm10010r100MesrlineQFactorIndex
		INTEGER,
	pm10010r100MesrlineQFactorPortn
		INTEGER 
	}


pm10010r100MesrlineQFactorIndex OBJECT-TYPE
	SYNTAX  INTEGER(0..128)
	MAX-ACCESS  read-only
	STATUS current
	DESCRIPTION
        "
        Index definition for the pm10010r100MesrlineQFactor 
        table
        "
	::= { pm10010r100MesrlineQFactorEntry 1 }


pm10010r100MesrlineQFactorPortn OBJECT-TYPE
	SYNTAX  INTEGER (0..65535)
	MAX-ACCESS read-only
	STATUS current
	DESCRIPTION
        "
        Current Q Factor :This OID gives 
        the current Q Factor on the Line 
        interface   (Unit = dB) <Help>
         This measure gives the current 
        Q Factor on the Line interface.
        "
	::= { pm10010r100MesrlineQFactorEntry 2 }


--- *********************************************************
---     TABLE for the pm10010r100MesrlineCarrierFreqOffset articles
--- *********************************************************

pm10010r100MesrlineCarrierFreqOffsetTable OBJECT-TYPE
	SYNTAX  SEQUENCE OF Pm10010r100MesrlineCarrierFreqOffsetEntry
	MAX-ACCESS not-accessible
	STATUS current
	DESCRIPTION
        "
        List of pm10010r100MesrlineCarrierFreqOffset 
        Article
        "
	::= { pm10010r100MesrLine 156 }


pm10010r100MesrlineCarrierFreqOffsetEntry OBJECT-TYPE
	SYNTAX Pm10010r100MesrlineCarrierFreqOffsetEntry
	MAX-ACCESS not-accessible
	STATUS current
	DESCRIPTION
        "
        Row definition for the pm10010r100MesrlineCarrierFreqOffset 
        table
        "
	INDEX   { pm10010r100MesrlineCarrierFreqOffsetIndex }
	::= { pm10010r100MesrlineCarrierFreqOffsetTable 1 }


Pm10010r100MesrlineCarrierFreqOffsetEntry ::=
	SEQUENCE {
	pm10010r100MesrlineCarrierFreqOffsetIndex
		INTEGER,
	pm10010r100MesrlineCarrierFreqOffsetPortn
		INTEGER 
	}


pm10010r100MesrlineCarrierFreqOffsetIndex OBJECT-TYPE
	SYNTAX  INTEGER(0..128)
	MAX-ACCESS  read-only
	STATUS current
	DESCRIPTION
        "
        Index definition for the pm10010r100MesrlineCarrierFreqOffset 
        table
        "
	::= { pm10010r100MesrlineCarrierFreqOffsetEntry 1 }


pm10010r100MesrlineCarrierFreqOffsetPortn OBJECT-TYPE
	SYNTAX  INTEGER (0..65535)
	MAX-ACCESS read-only
	STATUS current
	DESCRIPTION
        "
        Current Carrier Frequency Offset 
        :This OID gives the current Carrier 
        Frequency Offset on the Line interface 
          (Unit = Mhz)<Help> This measure 
        gives the current Carrier Frequency 
        Offset on the Line interface.
        "
	::= { pm10010r100MesrlineCarrierFreqOffsetEntry 2 }


--- *********************************************************
---     TABLE for the pm10010r100MesrlineOsnr articles
--- *********************************************************

pm10010r100MesrlineOsnrTable OBJECT-TYPE
	SYNTAX  SEQUENCE OF Pm10010r100MesrlineOsnrEntry
	MAX-ACCESS not-accessible
	STATUS current
	DESCRIPTION
        "
        List of pm10010r100MesrlineOsnr 
        Article
        "
	::= { pm10010r100MesrLine 160 }


pm10010r100MesrlineOsnrEntry OBJECT-TYPE
	SYNTAX Pm10010r100MesrlineOsnrEntry
	MAX-ACCESS not-accessible
	STATUS current
	DESCRIPTION
        "
        Row definition for the pm10010r100MesrlineOsnr 
        table
        "
	INDEX   { pm10010r100MesrlineOsnrIndex }
	::= { pm10010r100MesrlineOsnrTable 1 }


Pm10010r100MesrlineOsnrEntry ::=
	SEQUENCE {
	pm10010r100MesrlineOsnrIndex
		INTEGER,
	pm10010r100MesrlineOsnrPortn
		INTEGER 
	}


pm10010r100MesrlineOsnrIndex OBJECT-TYPE
	SYNTAX  INTEGER(0..128)
	MAX-ACCESS  read-only
	STATUS current
	DESCRIPTION
        "
        Index definition for the pm10010r100MesrlineOsnr 
        table
        "
	::= { pm10010r100MesrlineOsnrEntry 1 }


pm10010r100MesrlineOsnrPortn OBJECT-TYPE
	SYNTAX  INTEGER (0..65535)
	MAX-ACCESS read-only
	STATUS current
	DESCRIPTION
        "
        Current OSNR :This OID gives the 
        current OSNR on the Line interface 
          (OSNR = AV/10) (Unit = dB)<Help> 
        This measure gives the current
         OSNR on the Line interface.
        "
	::= { pm10010r100MesrlineOsnrEntry 2 }


--- *****************************************************
---     LEAF for the lineNetTxLaserOutputPwrAverage article
--- *****************************************************

pm10010r100MesrlineNetTxLaserOutputPwrAverage OBJECT-TYPE
	  SYNTAX Unsigned32 (0..65535)
	  MAX-ACCESS read-only
	  STATUS current
	  DESCRIPTION
        "
        Average Line Trscv Tx Power :This 
        OID gives the average Tx Laser
         transmit power value among the 
        network lanes of the Line Transceiver, 
        read in the DDM (Digital Diagnostic 
        Monitoring)  (Power = AV/100) (Unit 
        = dBm) (Unit = dBm) <Help> This 
        Measure gives the average Tx Laser 
        transmit power value among the
         network lanes of the Line Transceiver
        "
	  ::= { pm10010r100MesrOther 180 }



--- *****************************************************
---     LEAF for the lineNetTxLaserTempAverage article
--- *****************************************************

pm10010r100MesrlineNetTxLaserTempAverage OBJECT-TYPE
	  SYNTAX Unsigned32 (0..65535)
	  MAX-ACCESS read-only
	  STATUS current
	  DESCRIPTION
        "
        Average Line Trscv Tx Laser Temperature 
        :This OID gives the average Tx
         Laser Temperature value among
         the network lanes of the Line
         Transceiver, read from the DDM 
        (Digital Diagnostic Monitoring) 
        (Temperature = AV/256) (Unit =
         C) <Help> This Measure gives the 
        average Tx Laser Temperature value 
        among the network lanes of the
         Line Transceiver
        "
	  ::= { pm10010r100MesrOther 181 }



--- *****************************************************
---     LEAF for the lineNetTxBiasCurrentAverage article
--- *****************************************************

pm10010r100MesrlineNetTxBiasCurrentAverage OBJECT-TYPE
	  SYNTAX Unsigned32 (0..65535)
	  MAX-ACCESS read-only
	  STATUS current
	  DESCRIPTION
        "
        Average Line Trscv Tx Laser Bias 
        :This OID gives the average Tx
         Laser Bias value among the network 
        lanes of the Line Transceiver,
         read from the DDM (Digital Diagnostic 
        Monitoring) (Bias = AV/10) (Unit 
        = mA) <Help> This Measure gives 
        the average Tx Laser Bias value 
        among the network lanes of the
         Line Transceiver
        "
	  ::= { pm10010r100MesrOther 182 }



--- *****************************************************
---     LEAF for the lineNetRxInputPwrAverage article
--- *****************************************************

pm10010r100MesrlineNetRxInputPwrAverage OBJECT-TYPE
	  SYNTAX Unsigned32 (0..65535)
	  MAX-ACCESS read-only
	  STATUS current
	  DESCRIPTION
        "
        Average Line Trscv Rx Power :This 
        OID gives the average Receive power 
        value among the network lanes of 
        the Line Transceiver, read in the 
        DDM (Digital Diagnostic Monitoring) 
        (Power = AV/100) (Unit = dBm) <Help> 
        This Measure gives the average
         Receive power value among the
         network lanes of the Line Transceiver
        "
	  ::= { pm10010r100MesrOther 183 }



--- *****************************************************
---     LEAF for the lineResidualChromaticDispAverage article
--- *****************************************************

pm10010r100MesrlineResidualChromaticDispAverage OBJECT-TYPE
	  SYNTAX Unsigned32 (0..65535)
	  MAX-ACCESS read-only
	  STATUS current
	  DESCRIPTION
        "
        Average Residual Chromatic Dispersion 
        :This OID gives the average Residual 
        Chromatic Dispersion on the Line 
        interface since the last measure 
        reset <Help> This measure gives 
        the average Residual Chromatic
         Dispersion on the Line interface 
        since the last measure reset.
        "
	  ::= { pm10010r100MesrOther 184 }



--- *****************************************************
---     LEAF for the lineDiffGroupDelayAverage article
--- *****************************************************

pm10010r100MesrlineDiffGroupDelayAverage OBJECT-TYPE
	  SYNTAX Unsigned32 (0..65535)
	  MAX-ACCESS read-only
	  STATUS current
	  DESCRIPTION
        "
        Average Differential Group Delay 
        :This OID gives the average Group 
        Delay on the Line interface since 
        the last measure reset <Help> This 
        measure gives the average Differential 
        Group Delay on the Line interface 
        since the last measure reset.
        "
	  ::= { pm10010r100MesrOther 185 }



--- *****************************************************
---     LEAF for the lineQFactorAverage article
--- *****************************************************

pm10010r100MesrlineQFactorAverage OBJECT-TYPE
	  SYNTAX Unsigned32 (0..65535)
	  MAX-ACCESS read-only
	  STATUS current
	  DESCRIPTION
        "
        Average Q Factor :This OID gives 
        the average Q Factor on the Line 
        interface since the last measure 
        reset <Help> This measure gives 
        the average Q Factor on the Line 
        interface since the last measure 
        reset.
        "
	  ::= { pm10010r100MesrOther 186 }



--- *****************************************************
---     LEAF for the lineCarrierFreqOffsetAverage article
--- *****************************************************

pm10010r100MesrlineCarrierFreqOffsetAverage OBJECT-TYPE
	  SYNTAX Unsigned32 (0..65535)
	  MAX-ACCESS read-only
	  STATUS current
	  DESCRIPTION
        "
        Average Carrier Frequency Offset 
        :This OID gives the average Carrier 
        Frequency Offset on the Line interface 
        since the last measure reset <Help> 
        This measure gives the average
         Carrier Frequency Offset on the 
        Line interface since the last measure 
        reset
        "
	  ::= { pm10010r100MesrOther 187 }



--- *****************************************************
---     LEAF for the lineOsnrAverage article
--- *****************************************************

pm10010r100MesrlineOsnrAverage OBJECT-TYPE
	  SYNTAX Unsigned32 (0..65535)
	  MAX-ACCESS read-only
	  STATUS current
	  DESCRIPTION
        "
        Average OSNR :This OID gives the 
        average OSNR on the Line interface 
        since the last measure reset <Help> 
        This measure gives the average
         OSNR on the Line interface since 
        the last measure reset.
        "
	  ::= { pm10010r100MesrOther 188 }



--- *****************************************************
---     LEAF for the clientNetTxTempMin article
--- *****************************************************

pm10010r100MesrclientNetTxTempMin OBJECT-TYPE
	  SYNTAX Unsigned32 (0..65535)
	  MAX-ACCESS read-only
	  STATUS current
	  DESCRIPTION
        "
        Min Client Trscv Laser Temperature 
        :This OID gives the minimum Laser 
        temperature value among the network 
        lanes of the Client Transceiver, 
        read from the DDM (Digital Diagnostic 
        Monitoring) (Temperature = AV/256) 
        (Unit = C) <Help> This Measure
         gives the minimum Laser temperature 
        value among the network lanes of 
        the Client Transceiver
        "
	  ::= { pm10010r100MesrOther 192 }



--- *****************************************************
---     LEAF for the clientNetTxBiasMin article
--- *****************************************************

pm10010r100MesrclientNetTxBiasMin OBJECT-TYPE
	  SYNTAX Unsigned32 (0..65535)
	  MAX-ACCESS read-only
	  STATUS current
	  DESCRIPTION
        "
        Min Client Trscv Laser Bias :This 
        OID gives the minimum Laser bias 
        value among the network lanes of 
        the Client Transceiver, read from 
        the DDM (Digital Diagnostic Monitoring) 
        (Bias = AV/500) (Unit = mA) <Help> 
        This Measure gives the minimum
         Laser bias value among the network 
        lanes of the Client Transceiver
        "
	  ::= { pm10010r100MesrOther 193 }



--- *****************************************************
---     LEAF for the clientNetTxPwrMin article
--- *****************************************************

pm10010r100MesrclientNetTxPwrMin OBJECT-TYPE
	  SYNTAX Unsigned32 (0..65535)
	  MAX-ACCESS read-only
	  STATUS current
	  DESCRIPTION
        "
        Min Client Trscv Tx Power :This 
        OID gives the minimum transmit
         power value among the network
         lanes of the Client Transceiver, 
        read from the DDM (Digital Diagnostic 
        Monitoring) (Power = 10*log(AV)-40) 
        (Unit = dBm) <Help> This Measure 
        gives the minimum transmit power 
        value among the network lanes of 
        the Client Transceiver
        "
	  ::= { pm10010r100MesrOther 194 }



--- *****************************************************
---     LEAF for the clientNetRxPwrMin article
--- *****************************************************

pm10010r100MesrclientNetRxPwrMin OBJECT-TYPE
	  SYNTAX Unsigned32 (0..65535)
	  MAX-ACCESS read-only
	  STATUS current
	  DESCRIPTION
        "
        Min Client Trscv Rx Power :This 
        OID gives the minimum receive power 
        value among the network lanes of 
        the Client Transceiver, read in 
        the DDM (Digital Diagnostic Monitoring) 
        (Power = 10*log(AV)-40) (Unit = 
        dBm) <Help> This Measure gives
         the minimum receive power value 
        among the network lanes of the
         Client Transceiver
        "
	  ::= { pm10010r100MesrOther 195 }



--- *****************************************************
---     LEAF for the lineNetTxLaserOutputPwrMin article
--- *****************************************************

pm10010r100MesrlineNetTxLaserOutputPwrMin OBJECT-TYPE
	  SYNTAX Unsigned32 (0..65535)
	  MAX-ACCESS read-only
	  STATUS current
	  DESCRIPTION
        "
        Min Line Trscv Tx Power :This
         OID gives the minimum Tx Laser 
        transmit power value among the
         network lanes of the Line Transceiver, 
        read in the DDM (Digital Diagnostic 
        Monitoring)  (Power = AV/100) (Unit 
        = dBm) (Unit = dBm) <Help> This 
        Measure gives the minimum Tx Laser 
        transmit power value among the
         network lanes of the Line Transceiver
        "
	  ::= { pm10010r100MesrOther 196 }



--- *****************************************************
---     LEAF for the lineNetTxLaserTempMin article
--- *****************************************************

pm10010r100MesrlineNetTxLaserTempMin OBJECT-TYPE
	  SYNTAX Unsigned32 (0..65535)
	  MAX-ACCESS read-only
	  STATUS current
	  DESCRIPTION
        "
        Min Line Trscv Tx Laser Temperature 
        :This OID gives the minimum Tx
         Laser Temperature value among
         the network lanes of the Line
         Transceiver, read from the DDM 
        (Digital Diagnostic Monitoring) 
        (Temperature = AV/256) (Unit =
         C) <Help> This Measure gives the 
        minimum Tx Laser Temperature value 
        among the network lanes of the
         Line Transceiver
        "
	  ::= { pm10010r100MesrOther 197 }



--- *****************************************************
---     LEAF for the lineNetTxBiasCurrentMin article
--- *****************************************************

pm10010r100MesrlineNetTxBiasCurrentMin OBJECT-TYPE
	  SYNTAX Unsigned32 (0..65535)
	  MAX-ACCESS read-only
	  STATUS current
	  DESCRIPTION
        "
        Min Line Trscv Tx Laser Bias :This 
        OID gives the minimum Tx Laser
         Bias value among the network lanes 
        of the Line Transceiver, read from 
        the DDM (Digital Diagnostic Monitoring) 
        (Bias = AV/10) (Unit = mA) <Help> 
        This Measure gives the minimum
         Tx Laser Bias value among the
         network lanes of the Line Transceiver
        "
	  ::= { pm10010r100MesrOther 198 }



--- *****************************************************
---     LEAF for the lineNetRxInputPwrMin article
--- *****************************************************

pm10010r100MesrlineNetRxInputPwrMin OBJECT-TYPE
	  SYNTAX Unsigned32 (0..65535)
	  MAX-ACCESS read-only
	  STATUS current
	  DESCRIPTION
        "
        Min Line Trscv Rx Power :This
         OID gives the minimum Receive
         power value among the network
         lanes of the Line Transceiver, 
        read in the DDM (Digital Diagnostic 
        Monitoring) (Power = AV/100) (Unit 
        = dBm) <Help> This Measure gives 
        the minimum Receive power value 
        among the network lanes of the
         Line Transceiver
        "
	  ::= { pm10010r100MesrOther 199 }



--- *****************************************************
---     LEAF for the lineResidualChromaticDispMin article
--- *****************************************************

pm10010r100MesrlineResidualChromaticDispMin OBJECT-TYPE
	  SYNTAX Unsigned32 (0..65535)
	  MAX-ACCESS read-only
	  STATUS current
	  DESCRIPTION
        "
        Min Residual Chromatic Dispersion 
        :This OID gives the minimum Residual 
        Chromatic Dispersion on the Line 
        interface since the last measure 
        reset  (Unit = ps/nm)<Help> This 
        measure gives the minimum Residual 
        Chromatic Dispersion on the Line 
        interface since the last measure 
        reset.
        "
	  ::= { pm10010r100MesrOther 200 }



--- *****************************************************
---     LEAF for the lineDiffGroupDelayMin article
--- *****************************************************

pm10010r100MesrlineDiffGroupDelayMin OBJECT-TYPE
	  SYNTAX Unsigned32 (0..65535)
	  MAX-ACCESS read-only
	  STATUS current
	  DESCRIPTION
        "
        Min Differential Group Delay :This 
        OID gives the minimum Differential 
        Group Delay  on the Line interface 
        since the last measure reset  (Unit 
        = ps)<Help> This measure gives
         the minimum Differential Group 
        Delay on the Line interface since 
        the last measure reset.
        "
	  ::= { pm10010r100MesrOther 201 }



--- *****************************************************
---     LEAF for the lineQFactorMin article
--- *****************************************************

pm10010r100MesrlineQFactorMin OBJECT-TYPE
	  SYNTAX Unsigned32 (0..65535)
	  MAX-ACCESS read-only
	  STATUS current
	  DESCRIPTION
        "
        Min Q Factor :This OID gives the 
        minimum Q Factor on the Line interface 
        since the last measure reset  (Unit 
        = dB)<Help> This measure gives
         the minimum Q Factor on the Line 
        interface since the last measure 
        reset.
        "
	  ::= { pm10010r100MesrOther 202 }



--- *****************************************************
---     LEAF for the lineCarrierFreqOffsetMin article
--- *****************************************************

pm10010r100MesrlineCarrierFreqOffsetMin OBJECT-TYPE
	  SYNTAX Unsigned32 (0..65535)
	  MAX-ACCESS read-only
	  STATUS current
	  DESCRIPTION
        "
        Min Carrier Frequency Offset :This 
        OID gives the minimum Carrier Frequency 
        Offset on the Line interface since 
        the last measure reset  (Unit = 
        Mhz)<Help> This measure gives the 
        minimum Carrier Frequency Offset 
        on the Line interface since the 
        last measure reset
        "
	  ::= { pm10010r100MesrOther 203 }



--- *****************************************************
---     LEAF for the lineOsnrMin article
--- *****************************************************

pm10010r100MesrlineOsnrMin OBJECT-TYPE
	  SYNTAX Unsigned32 (0..65535)
	  MAX-ACCESS read-only
	  STATUS current
	  DESCRIPTION
        "
        Min OSNR :This OID gives the minimum 
        OSNR on the Line interface since 
        the last measure reset  (OSNR = 
        AV/10) (Unit = dB)<Help> This measure 
        gives the minimum OSNR on the Line 
        interface since the last measure 
        reset.
        "
	  ::= { pm10010r100MesrOther 204 }



--- *****************************************************
---     LEAF for the clientNetTxTempMax article
--- *****************************************************

pm10010r100MesrclientNetTxTempMax OBJECT-TYPE
	  SYNTAX Unsigned32 (0..65535)
	  MAX-ACCESS read-only
	  STATUS current
	  DESCRIPTION
        "
        Max Client Trscv Laser Temperature 
        :This OID gives the maximum Laser 
        temperature value among the network 
        lanes of the Client Transceiver, 
        read from the DDM (Digital Diagnostic 
        Monitoring) (Temperature = AV/256) 
        (Unit = C) <Help> This Measure
         gives the maximum Laser temperature 
        value among the network lanes of 
        the Client Transceiver
        "
	  ::= { pm10010r100MesrOther 208 }



--- *****************************************************
---     LEAF for the clientNetTxBiasMax article
--- *****************************************************

pm10010r100MesrclientNetTxBiasMax OBJECT-TYPE
	  SYNTAX Unsigned32 (0..65535)
	  MAX-ACCESS read-only
	  STATUS current
	  DESCRIPTION
        "
        Max Client Trscv Laser Bias :This 
        OID gives the maximum Laser bias 
        value among the network lanes of 
        the Client Transceiver, read from 
        the DDM (Digital Diagnostic Monitoring) 
        (Bias = AV/500) (Unit = mA) <Help> 
        This Measure gives the maximum
         Laser bias value among the network 
        lanes of the Client Transceiver
        "
	  ::= { pm10010r100MesrOther 209 }



--- *****************************************************
---     LEAF for the clientNetTxPwrMax article
--- *****************************************************

pm10010r100MesrclientNetTxPwrMax OBJECT-TYPE
	  SYNTAX Unsigned32 (0..65535)
	  MAX-ACCESS read-only
	  STATUS current
	  DESCRIPTION
        "
        Max Client Trscv Tx Power :This 
        OID gives the maximum transmit
         power value among the network
         lanes of the Client Transceiver, 
        read from the DDM (Digital Diagnostic 
        Monitoring) (Power = 10*log(AV)-40) 
        (Unit = dBm) <Help> This Measure 
        gives the maximum transmit power 
        value among the network lanes of 
        the Client Transceiver
        "
	  ::= { pm10010r100MesrOther 210 }



--- *****************************************************
---     LEAF for the clientNetRxPwrMax article
--- *****************************************************

pm10010r100MesrclientNetRxPwrMax OBJECT-TYPE
	  SYNTAX Unsigned32 (0..65535)
	  MAX-ACCESS read-only
	  STATUS current
	  DESCRIPTION
        "
        Max Client Trscv Rx Power :This 
        OID gives the maximum receive power 
        value among the network lanes of 
        the Client Transceiver, read in 
        the DDM (Digital Diagnostic Monitoring) 
        (Power = 10*log(AV)-40) (Unit = 
        dBm) <Help> This Measure gives
         the maximum receive power value 
        among the network lanes of the
         Client Transceiver
        "
	  ::= { pm10010r100MesrOther 211 }



--- *****************************************************
---     LEAF for the lineNetTxLaserOutputPwrMax article
--- *****************************************************

pm10010r100MesrlineNetTxLaserOutputPwrMax OBJECT-TYPE
	  SYNTAX Unsigned32 (0..65535)
	  MAX-ACCESS read-only
	  STATUS current
	  DESCRIPTION
        "
        Max Line Trscv Tx Power :This
         OID gives the maximum Tx Laser 
        transmit power value among the
         network lanes of the Line Transceiver, 
        read in the DDM (Digital Diagnostic 
        Monitoring) (Power = 10*log(AV)-40) 
        (Unit = dBm) <Help> This Measure 
        gives the maximum Tx Laser transmit 
        power value among the network lanes 
        of the Line Transceiver
        "
	  ::= { pm10010r100MesrOther 212 }



--- *****************************************************
---     LEAF for the lineNetTxLaserTempMax article
--- *****************************************************

pm10010r100MesrlineNetTxLaserTempMax OBJECT-TYPE
	  SYNTAX Unsigned32 (0..65535)
	  MAX-ACCESS read-only
	  STATUS current
	  DESCRIPTION
        "
        Max Line Trscv Tx Laser Temperature 
        :This OID gives the maximum Tx
         Laser Temperature value among
         the network lanes of the Line
         Transceiver, read from the DDM 
        (Digital Diagnostic Monitoring) 
        (Temperature = AV/256) (Unit =
         C) <Help> This Measure gives the 
        maximum Tx Laser Temperature value 
        among the network lanes of the
         Line Transceiver
        "
	  ::= { pm10010r100MesrOther 213 }



--- *****************************************************
---     LEAF for the lineNetTxBiasCurrentMax article
--- *****************************************************

pm10010r100MesrlineNetTxBiasCurrentMax OBJECT-TYPE
	  SYNTAX Unsigned32 (0..65535)
	  MAX-ACCESS read-only
	  STATUS current
	  DESCRIPTION
        "
        Max Line Trscv Tx Laser Bias :This 
        OID gives the maximum Tx Laser
         Bias value among the network lanes 
        of the Line Transceiver, read from 
        the DDM (Digital Diagnostic Monitoring) 
        (Bias = AV/10) (Unit = mA) <Help> 
        This Measure gives the maximum
         Tx Laser Bias value among the
         network lanes of the Line Transceiver
        "
	  ::= { pm10010r100MesrOther 214 }



--- *****************************************************
---     LEAF for the lineNetRxInputPwrMax article
--- *****************************************************

pm10010r100MesrlineNetRxInputPwrMax OBJECT-TYPE
	  SYNTAX Unsigned32 (0..65535)
	  MAX-ACCESS read-only
	  STATUS current
	  DESCRIPTION
        "
        Max Line Trscv Rx Power :This
         OID gives the maximum Receive
         power value among the network
         lanes of the Line Transceiver, 
        read in the DDM (Digital Diagnostic 
        Monitoring) (Power = 10*log(AV)-40) 
        (Unit = dBm) <Help> This Measure 
        gives the maximum Receive power 
        value among the network lanes of 
        the Line Transceiver
        "
	  ::= { pm10010r100MesrOther 215 }



--- *****************************************************
---     LEAF for the lineResidualChromaticDispMax article
--- *****************************************************

pm10010r100MesrlineResidualChromaticDispMax OBJECT-TYPE
	  SYNTAX Unsigned32 (0..65535)
	  MAX-ACCESS read-only
	  STATUS current
	  DESCRIPTION
        "
        Max Residual Chromatic Dispersion 
        :This OID gives the maximum Residual 
        Chromatic Dispersion on the Line 
        interface since the last measure 
        reset  (Unit = ps/nm)<Help> This 
        measure gives the maximum Residual 
        Chromatic Dispersion on the Line 
        interface since the last measure 
        reset.
        "
	  ::= { pm10010r100MesrOther 216 }



--- *****************************************************
---     LEAF for the lineDiffGroupDelayMax article
--- *****************************************************

pm10010r100MesrlineDiffGroupDelayMax OBJECT-TYPE
	  SYNTAX Unsigned32 (0..65535)
	  MAX-ACCESS read-only
	  STATUS current
	  DESCRIPTION
        "
        Max Differential Group Delay :This 
        OID gives the maximum Differential 
        Group Delay  on the Line interface 
        since the last measure reset  
         (Unit = ps)<Help> This measure 
        gives the maximum Differential
         Group Delay on the Line interface 
        since the last measure reset.
        "
	  ::= { pm10010r100MesrOther 217 }



--- *****************************************************
---     LEAF for the lineQFactorMax article
--- *****************************************************

pm10010r100MesrlineQFactorMax OBJECT-TYPE
	  SYNTAX Unsigned32 (0..65535)
	  MAX-ACCESS read-only
	  STATUS current
	  DESCRIPTION
        "
        Max Q Factor :This OID gives the 
        maximum Q Factor on the Line interface 
        since the last measure reset  (Unit 
        = dB)<Help> This measure gives
         the maximum Q Factor on the Line 
        interface since the last measure 
        reset.
        "
	  ::= { pm10010r100MesrOther 218 }



--- *****************************************************
---     LEAF for the lineCarrierFreqOffsetMax article
--- *****************************************************

pm10010r100MesrlineCarrierFreqOffsetMax OBJECT-TYPE
	  SYNTAX Unsigned32 (0..65535)
	  MAX-ACCESS read-only
	  STATUS current
	  DESCRIPTION
        "
        Max Carrier Frequency Offset :This 
        OID gives the maximum Carrier Frequency 
        Offset on the Line interface since 
        the last measure reset   (Unit
         = Mhz)<Help> This measure gives 
        the maximum Carrier Frequency Offset 
        on the Line interface since the 
        last measure reset.
        "
	  ::= { pm10010r100MesrOther 219 }



--- *****************************************************
---     LEAF for the lineOsnrMax article
--- *****************************************************

pm10010r100MesrlineOsnrMax OBJECT-TYPE
	  SYNTAX Unsigned32 (0..65535)
	  MAX-ACCESS read-only
	  STATUS current
	  DESCRIPTION
        "
        Max OSNR :This OID gives the maximum 
        OSNR on the Line interface since 
        the last measure reset  (OSNR = 
        AV/10) (Unit = dB)<Help> This measure 
        gives the maximum OSNR on the Line 
        interface since the last measure 
        reset
        "
	  ::= { pm10010r100MesrOther 220 }








--- *****************************************************
--- $$$$$$$$$$$$$$$$$$$$$$$$$$$$$$$$$$$$$$$$$$$$$$$$$$$$$
---     DOWNLOAD
--- $$$$$$$$$$$$$$$$$$$$$$$$$$$$$$$$$$$$$$$$$$$$$$$$$$$$$
--- *****************************************************



--- *****************************************************
---     LEAF for the restartProcess article
--- *****************************************************
pm10010r100DwlrestartProcess OBJECT IDENTIFIER ::= { pm10010r100DwlOther 0 }




pm10010r100DwlColdRestartProcessed OBJECT-TYPE
	  SYNTAX EkiOnOff
	  MAX-ACCESS read-only
	  STATUS current
	  DESCRIPTION
        "
        Cold Restart :This OID indicates 
        that the module last restart was 
        a Cold RESTART
        "
	  ::= { pm10010r100DwlrestartProcess 2 }



pm10010r100DwlWarmRestartProcessed OBJECT-TYPE
	  SYNTAX EkiOnOff
	  MAX-ACCESS read-only
	  STATUS current
	  DESCRIPTION
        "
        Warm Restart :This OID indicates 
        that the module last restart was 
        a Warm RESTART
        "
	  ::= { pm10010r100DwlrestartProcess 1 }



--- *****************************************************
---     LEAF for the swBanksUsed article
--- *****************************************************
pm10010r100DwlswBanksUsed OBJECT IDENTIFIER ::= { pm10010r100DwlOther 1 }




pm10010r100DwlSwBank2Notempty OBJECT-TYPE
	  SYNTAX EkiOnOff
	  MAX-ACCESS read-only
	  STATUS current
	  DESCRIPTION
        "
        SW bank 2 loaded :This OID indicates 
        a software is loaded in SW bank 
        2  <Help>  This status indicates 
        if the SW bank 2 contains SW package
        "
	  ::= { pm10010r100DwlswBanksUsed 6 }



pm10010r100DwlSwBank1Notempty OBJECT-TYPE
	  SYNTAX EkiOnOff
	  MAX-ACCESS read-only
	  STATUS current
	  DESCRIPTION
        "
        SW bank 1 loaded :This OID indicates 
        a software is loaded in SW bank 
        1  <Help>  This status indicates 
        if the SW bank 1 contains SW package
        "
	  ::= { pm10010r100DwlswBanksUsed 5 }



pm10010r100DwlSwBank2Used OBJECT-TYPE
	  SYNTAX EkiOnOff
	  MAX-ACCESS read-only
	  STATUS current
	  DESCRIPTION
        "
        SW bank 2 active :This OID indicates 
        the module is working on SW bank 
        2  <Help>  This status indicates 
        if the SW bank 2 is active or standby
        "
	  ::= { pm10010r100DwlswBanksUsed 2 }



pm10010r100DwlSwBank1Used OBJECT-TYPE
	  SYNTAX EkiOnOff
	  MAX-ACCESS read-only
	  STATUS current
	  DESCRIPTION
        "
        SW bank 1 active :This OID indicates 
        the module is working on SW bank 
        1  <Help>  This status indicates 
        if the SW bank 1 is active or standby
        "
	  ::= { pm10010r100DwlswBanksUsed 1 }



--- *****************************************************
---     LEAF for the gwBanksUsed article
--- *****************************************************
pm10010r100DwlgwBanksUsed OBJECT IDENTIFIER ::= { pm10010r100DwlOther 2 }




pm10010r100DwlGwBank4Notempty OBJECT-TYPE
	  SYNTAX EkiOnOff
	  MAX-ACCESS read-only
	  STATUS current
	  DESCRIPTION
        "
        GW bank 4 loaded :This OID indicates 
        a gateware is loaded in GW bank 
        4
        "
	  ::= { pm10010r100DwlgwBanksUsed 8 }



pm10010r100DwlGwBank3Notempty OBJECT-TYPE
	  SYNTAX EkiOnOff
	  MAX-ACCESS read-only
	  STATUS current
	  DESCRIPTION
        "
        GW bank 3 loaded :This OID indicates 
        a gateware is loaded in GW bank 
        3  <Help>  This status indicates 
        if the GW bank 3 contains GW package
        "
	  ::= { pm10010r100DwlgwBanksUsed 7 }



pm10010r100DwlGwBank2Notempty OBJECT-TYPE
	  SYNTAX EkiOnOff
	  MAX-ACCESS read-only
	  STATUS current
	  DESCRIPTION
        "
        GW bank 2 loaded :This OID indicates 
        a gateware is loaded in GW bank 
        2
        "
	  ::= { pm10010r100DwlgwBanksUsed 6 }



pm10010r100DwlGwBank1Notempty OBJECT-TYPE
	  SYNTAX EkiOnOff
	  MAX-ACCESS read-only
	  STATUS current
	  DESCRIPTION
        "
        GW bank 1 loaded :This OID indicates 
        a gateware is loaded in GW bank 
        1  <Help>  This status indicates 
        if the GW bank 1 contains GW package
        "
	  ::= { pm10010r100DwlgwBanksUsed 5 }



pm10010r100DwlGwBank4Used OBJECT-TYPE
	  SYNTAX EkiOnOff
	  MAX-ACCESS read-only
	  STATUS current
	  DESCRIPTION
        "
        GW bank 4 active :This OID indicates 
        the module is working on GW bank 
        4
        "
	  ::= { pm10010r100DwlgwBanksUsed 4 }



pm10010r100DwlGwBank3Used OBJECT-TYPE
	  SYNTAX EkiOnOff
	  MAX-ACCESS read-only
	  STATUS current
	  DESCRIPTION
        "
        GW bank 3 active :This OID indicates 
        the module is working on GW bank 
        3  <Help>  This status indicates 
        if the GW bank 3 is active or standby
        "
	  ::= { pm10010r100DwlgwBanksUsed 3 }



pm10010r100DwlGwBank2Used OBJECT-TYPE
	  SYNTAX EkiOnOff
	  MAX-ACCESS read-only
	  STATUS current
	  DESCRIPTION
        "
        GW bank 2 active :This OID indicates 
        the module is working on GW bank 
        2
        "
	  ::= { pm10010r100DwlgwBanksUsed 2 }



pm10010r100DwlGwBank1Used OBJECT-TYPE
	  SYNTAX EkiOnOff
	  MAX-ACCESS read-only
	  STATUS current
	  DESCRIPTION
        "
        GW bank 1 active :This OID indicates 
        the module is working on GW bank 
        1  <Help>  This status indicates 
        if the GW bank 1 is active or standby
        "
	  ::= { pm10010r100DwlgwBanksUsed 1 }








--- *****************************************************
--- $$$$$$$$$$$$$$$$$$$$$$$$$$$$$$$$$$$$$$$$$$$$$$$$$$$$$
---     CONFIG
--- $$$$$$$$$$$$$$$$$$$$$$$$$$$$$$$$$$$$$$$$$$$$$$$$$$$$$
--- *****************************************************



--- *****************************************************
---     LEAF for the table Group accessCAisCsf
--- *****************************************************

pm10010r100CfgAccessCAisCsf OBJECT IDENTIFIER ::= { pm10010r100Config 1 }



--- *****************************************************
---     LEAF for the table 0012
--- *****************************************************

pm10010r100CfgClientcaiscsfTable OBJECT-TYPE
	SYNTAX  SEQUENCE OF Pm10010r100CfgClientcaiscsfEntry
	MAX-ACCESS not-accessible
	STATUS current
	DESCRIPTION
        "
        List of  Article
        "
	::= { pm10010r100CfgAccessCAisCsf 1 }


pm10010r100CfgClientcaiscsfEntry OBJECT-TYPE
	SYNTAX Pm10010r100CfgClientcaiscsfEntry
	MAX-ACCESS not-accessible
	STATUS current
	DESCRIPTION
        "
        Row definition for the accessCAisCsf 
        table
        "
	INDEX   { pm10010r100CfgClientcaiscsfIndex }
	::= { pm10010r100CfgClientcaiscsfTable 1 }


Pm10010r100CfgClientcaiscsfEntry ::=
	SEQUENCE {
	pm10010r100CfgClientcaiscsfIndex
		INTEGER,
	pm10010r100CfgReservePortn
		Unsigned32
	}


pm10010r100CfgClientcaiscsfIndex OBJECT-TYPE
	SYNTAX  INTEGER(0..128)
	MAX-ACCESS  read-only
	STATUS current
	DESCRIPTION
        "
        Index definition for the clientcaiscsf 
        table
        "
	::= { pm10010r100CfgClientcaiscsfEntry 1 }


pm10010r100CfgReservePortn OBJECT-TYPE
	SYNTAX  Unsigned32 (0..65536)
	MAX-ACCESS read-write
	STATUS current
	DESCRIPTION
        "
        CAIS mode  on Client Port :This 
        register enables/disables port
          laser shutdown on CAIS insertion 
        condition
        "
	::= { pm10010r100CfgClientcaiscsfEntry 3 }


--- *****************************************************
---     LEAF for the table Group startup
--- *****************************************************

pm10010r100CfgStartup OBJECT IDENTIFIER ::= { pm10010r100Config 2 }



--- *****************************************************
---     LEAF for the table 2110
--- *****************************************************

pm10010r100CfgClientStartupTable OBJECT-TYPE
	SYNTAX  SEQUENCE OF Pm10010r100CfgClientStartupEntry
	MAX-ACCESS not-accessible
	STATUS current
	DESCRIPTION
        "
        List of  Article
        "
	::= { pm10010r100CfgStartup 1 }


pm10010r100CfgClientStartupEntry OBJECT-TYPE
	SYNTAX Pm10010r100CfgClientStartupEntry
	MAX-ACCESS not-accessible
	STATUS current
	DESCRIPTION
        "
        Row definition for the startup 
        table
        "
	INDEX   { pm10010r100CfgClientStartupIndex }
	::= { pm10010r100CfgClientStartupTable 1 }


Pm10010r100CfgClientStartupEntry ::=
	SEQUENCE {
	pm10010r100CfgClientStartupIndex
		INTEGER,
	pm10010r100CfgSystConfPortPortn
		Unsigned32,
	pm10010r100CfgNetConfPortPortn
		Unsigned32,
	pm10010r100CfgOptionsPortPortn
		Unsigned32
	}


pm10010r100CfgClientStartupIndex OBJECT-TYPE
	SYNTAX  INTEGER(0..128)
	MAX-ACCESS  read-only
	STATUS current
	DESCRIPTION
        "
        Index definition for the clientStartup 
        table
        "
	::= { pm10010r100CfgClientStartupEntry 1 }


pm10010r100CfgSystConfPortPortn OBJECT-TYPE
	SYNTAX  Unsigned32 (0..65536)
	MAX-ACCESS read-write
	STATUS current
	DESCRIPTION
        "
        Default Settings on Client Port 
        :This  register configures the
         default initialisation settings 
        on the port.
        "
	::= { pm10010r100CfgClientStartupEntry 3 }


pm10010r100CfgNetConfPortPortn OBJECT-TYPE
	SYNTAX  Unsigned32 (0..65536)
	MAX-ACCESS read-write
	STATUS current
	DESCRIPTION
        "
        Default Settings on Client Port 
        :This  register configures the
         default initialisation settings 
        on the port.
        "
	::= { pm10010r100CfgClientStartupEntry 4 }


pm10010r100CfgOptionsPortPortn OBJECT-TYPE
	SYNTAX  Unsigned32 (0..65536)
	MAX-ACCESS read-write
	STATUS current
	DESCRIPTION
        "
        Default Options on Client Port 
        :This register configures the default 
        options on the port.
        "
	::= { pm10010r100CfgClientStartupEntry 14 }


--- *****************************************************
---     LEAF for the table 2190
--- *****************************************************

pm10010r100CfgLineStartupTable OBJECT-TYPE
	SYNTAX  SEQUENCE OF Pm10010r100CfgLineStartupEntry
	MAX-ACCESS not-accessible
	STATUS current
	DESCRIPTION
        "
        List of  Article
        "
	::= { pm10010r100CfgStartup 2 }


pm10010r100CfgLineStartupEntry OBJECT-TYPE
	SYNTAX Pm10010r100CfgLineStartupEntry
	MAX-ACCESS not-accessible
	STATUS current
	DESCRIPTION
        "
        Row definition for the startup 
        table
        "
	INDEX   { pm10010r100CfgLineStartupIndex }
	::= { pm10010r100CfgLineStartupTable 1 }


Pm10010r100CfgLineStartupEntry ::=
	SEQUENCE {
	pm10010r100CfgLineStartupIndex
		INTEGER,
	pm10010r100CfgSystConfLinePortn
		Unsigned32,
	pm10010r100CfgOptionsLinePortn
		Unsigned32
	}


pm10010r100CfgLineStartupIndex OBJECT-TYPE
	SYNTAX  INTEGER(0..128)
	MAX-ACCESS  read-only
	STATUS current
	DESCRIPTION
        "
        Index definition for the lineStartup 
        table
        "
	::= { pm10010r100CfgLineStartupEntry 1 }


pm10010r100CfgSystConfLinePortn OBJECT-TYPE
	SYNTAX  Unsigned32 (0..65536)
	MAX-ACCESS read-write
	STATUS current
	DESCRIPTION
        "
        Default Settings on Line :This 
        register configures the default 
        initialisation settings on Line
        "
	::= { pm10010r100CfgLineStartupEntry 3 }


pm10010r100CfgOptionsLinePortn OBJECT-TYPE
	SYNTAX  Unsigned32 (0..65536)
	MAX-ACCESS read-write
	STATUS current
	DESCRIPTION
        "
        Default Options on Line :This
         register configures the default 
        options on the line
        "
	::= { pm10010r100CfgLineStartupEntry 14 }


--- *****************************************************
---     LEAF for the table 21AB
--- *****************************************************

pm10010r100CfgXfpTable OBJECT-TYPE
	SYNTAX  SEQUENCE OF Pm10010r100CfgXfpEntry
	MAX-ACCESS not-accessible
	STATUS current
	DESCRIPTION
        "
        List of  Article
        "
	::= { pm10010r100CfgStartup 3 }


pm10010r100CfgXfpEntry OBJECT-TYPE
	SYNTAX Pm10010r100CfgXfpEntry
	MAX-ACCESS not-accessible
	STATUS current
	DESCRIPTION
        "
        Row definition for the startup 
        table
        "
	INDEX   { pm10010r100CfgXfpIndex }
	::= { pm10010r100CfgXfpTable 1 }


Pm10010r100CfgXfpEntry ::=
	SEQUENCE {
	pm10010r100CfgXfpIndex
		INTEGER,
	pm10010r100CfgSystConfMsaLinePortn
		Unsigned32
	}


pm10010r100CfgXfpIndex OBJECT-TYPE
	SYNTAX  INTEGER(0..128)
	MAX-ACCESS  read-only
	STATUS current
	DESCRIPTION
        "
        Index definition for the xfp table
        "
	::= { pm10010r100CfgXfpEntry 1 }


pm10010r100CfgSystConfMsaLinePortn OBJECT-TYPE
	SYNTAX  Unsigned32 (0..65536)
	MAX-ACCESS read-write
	STATUS current
	DESCRIPTION
        "
        Default settings on MSA :This
         register configures the default 
        initialisation settings on MSA
        "
	::= { pm10010r100CfgXfpEntry 3 }


--- *****************************************************
---     LEAF for the table 2610
--- *****************************************************

pm10010r100CfgClientOtxtlhTable OBJECT-TYPE
	SYNTAX  SEQUENCE OF Pm10010r100CfgClientOtxtlhEntry
	MAX-ACCESS not-accessible
	STATUS current
	DESCRIPTION
        "
        List of  Article
        "
	::= { pm10010r100CfgStartup 4 }


pm10010r100CfgClientOtxtlhEntry OBJECT-TYPE
	SYNTAX Pm10010r100CfgClientOtxtlhEntry
	MAX-ACCESS not-accessible
	STATUS current
	DESCRIPTION
        "
        Row definition for the startup 
        table
        "
	INDEX   { pm10010r100CfgClientOtxtlhIndex }
	::= { pm10010r100CfgClientOtxtlhTable 1 }


Pm10010r100CfgClientOtxtlhEntry ::=
	SEQUENCE {
	pm10010r100CfgClientOtxtlhIndex
		INTEGER,
	pm10010r100CfgControlsPortn
		Unsigned32,
	pm10010r100CfgClientPwrLaserPortn
		Unsigned32,
	pm10010r100CfgClientFCurrentPortn
		Unsigned32,
	pm10010r100CfgClientGridCurrentPortn
		Unsigned32,
	pm10010r100CfgClientFoPortn
		Unsigned32
	}


pm10010r100CfgClientOtxtlhIndex OBJECT-TYPE
	SYNTAX  INTEGER(0..128)
	MAX-ACCESS  read-only
	STATUS current
	DESCRIPTION
        "
        Index definition for the clientOtxtlh 
        table
        "
	::= { pm10010r100CfgClientOtxtlhEntry 1 }


pm10010r100CfgControlsPortn OBJECT-TYPE
	SYNTAX  Unsigned32 (0..65536)
	MAX-ACCESS read-write
	STATUS deprecated
	DESCRIPTION
        "
        Defaut Client settings :This register 
        configures the start-up settings 
        on the ports
        "
	::= { pm10010r100CfgClientOtxtlhEntry 3 }


pm10010r100CfgClientPwrLaserPortn OBJECT-TYPE
	SYNTAX  Unsigned32 (0..65536)
	MAX-ACCESS read-write
	STATUS current
	DESCRIPTION
        "
        Defaut Client output Power :This 
        register configures the start-up 
        output power of the client transceiver 
         (Unit = dBm)
        "
	::= { pm10010r100CfgClientOtxtlhEntry 6 }


pm10010r100CfgClientFCurrentPortn OBJECT-TYPE
	SYNTAX  Unsigned32 (0..65536)
	MAX-ACCESS read-write
	STATUS current
	DESCRIPTION
        "
        Default Client transceiver Channel 
        :This register configures the start-up 
        laser channel of the client  transceiver
        "
	::= { pm10010r100CfgClientOtxtlhEntry 7 }


pm10010r100CfgClientGridCurrentPortn OBJECT-TYPE
	SYNTAX  Unsigned32 (0..65536)
	MAX-ACCESS read-write
	STATUS current
	DESCRIPTION
        "
        Default Client transceiver Grid 
        :This register configures the start-up 
        laser grid of the client transceiver
        "
	::= { pm10010r100CfgClientOtxtlhEntry 8 }


pm10010r100CfgClientFoPortn OBJECT-TYPE
	SYNTAX  Unsigned32 (0..65536)
	MAX-ACCESS read-write
	STATUS current
	DESCRIPTION
        "
        Default Client first Frequency 
        :This register configures the start-up 
        first frequency of the client transceiver
        "
	::= { pm10010r100CfgClientOtxtlhEntry 9 }


--- *****************************************************
---     LEAF for the table Group labels
--- *****************************************************

pm10010r100CfgLabels OBJECT IDENTIFIER ::= { pm10010r100Config 3 }



--- *****************************************************
---     LEAF for the table 0003
--- *****************************************************

pm10010r100CfgLabelclientTable OBJECT-TYPE
	SYNTAX  SEQUENCE OF Pm10010r100CfgLabelclientEntry
	MAX-ACCESS not-accessible
	STATUS current
	DESCRIPTION
        "
        List of  Article
        "
	::= { pm10010r100CfgLabels 1 }


pm10010r100CfgLabelclientEntry OBJECT-TYPE
	SYNTAX Pm10010r100CfgLabelclientEntry
	MAX-ACCESS not-accessible
	STATUS current
	DESCRIPTION
        "
        Row definition for the labels
         table
        "
	INDEX   { pm10010r100CfgLabelclientIndex }
	::= { pm10010r100CfgLabelclientTable 1 }


Pm10010r100CfgLabelclientEntry ::=
	SEQUENCE {
	pm10010r100CfgLabelclientIndex
		INTEGER,
	pm10010r100CfgLabelclientPortn
		DisplayString
	}


pm10010r100CfgLabelclientIndex OBJECT-TYPE
	SYNTAX  INTEGER(0..128)
	MAX-ACCESS  read-only
	STATUS current
	DESCRIPTION
        "
        Index definition for the labelclient 
        table
        "
	::= { pm10010r100CfgLabelclientEntry 1 }


pm10010r100CfgLabelclientPortn OBJECT-TYPE
	SYNTAX  DisplayString( SIZE(1..16))
	MAX-ACCESS read-write
	STATUS current
	DESCRIPTION
        "
        Default settings on the label
         of the Ports :These registers
         configures the default initialisation 
        settings of the labels of the ports.
        "
	::= { pm10010r100CfgLabelclientEntry 3 }


--- *****************************************************
---     LEAF for the table 0004
--- *****************************************************

pm10010r100CfgLabellineTable OBJECT-TYPE
	SYNTAX  SEQUENCE OF Pm10010r100CfgLabellineEntry
	MAX-ACCESS not-accessible
	STATUS current
	DESCRIPTION
        "
        List of  Article
        "
	::= { pm10010r100CfgLabels 2 }


pm10010r100CfgLabellineEntry OBJECT-TYPE
	SYNTAX Pm10010r100CfgLabellineEntry
	MAX-ACCESS not-accessible
	STATUS current
	DESCRIPTION
        "
        Row definition for the labels
         table
        "
	INDEX   { pm10010r100CfgLabellineIndex }
	::= { pm10010r100CfgLabellineTable 1 }


Pm10010r100CfgLabellineEntry ::=
	SEQUENCE {
	pm10010r100CfgLabellineIndex
		INTEGER,
	pm10010r100CfgLabellinePortn
		DisplayString
	}


pm10010r100CfgLabellineIndex OBJECT-TYPE
	SYNTAX  INTEGER(0..128)
	MAX-ACCESS  read-only
	STATUS current
	DESCRIPTION
        "
        Index definition for the labelline 
        table
        "
	::= { pm10010r100CfgLabellineEntry 1 }


pm10010r100CfgLabellinePortn OBJECT-TYPE
	SYNTAX  DisplayString( SIZE(1..16))
	MAX-ACCESS read-write
	STATUS current
	DESCRIPTION
        "
        Default settings on the label
         of the lines :These registers
         configures the default initialisation 
        settings of the labels of the lines.
        "
	::= { pm10010r100CfgLabellineEntry 3 }


--- *****************************************************
---     LEAF for the table Group startuptlh
--- *****************************************************

pm10010r100CfgStartuptlh OBJECT IDENTIFIER ::= { pm10010r100Config 4 }



--- *****************************************************
---     LEAF for the table 25AB
--- *****************************************************

pm10010r100CfgOtxtlhTable OBJECT-TYPE
	SYNTAX  SEQUENCE OF Pm10010r100CfgOtxtlhEntry
	MAX-ACCESS not-accessible
	STATUS current
	DESCRIPTION
        "
        List of  Article
        "
	::= { pm10010r100CfgStartuptlh 1 }


pm10010r100CfgOtxtlhEntry OBJECT-TYPE
	SYNTAX Pm10010r100CfgOtxtlhEntry
	MAX-ACCESS not-accessible
	STATUS current
	DESCRIPTION
        "
        Row definition for the startuptlh 
        table
        "
	INDEX   { pm10010r100CfgOtxtlhIndex }
	::= { pm10010r100CfgOtxtlhTable 1 }


Pm10010r100CfgOtxtlhEntry ::=
	SEQUENCE {
	pm10010r100CfgOtxtlhIndex
		INTEGER,
	pm10010r100CfgLinePwrLaserPortn
		Unsigned32,
	pm10010r100CfgLineFCurrentPortn
		Unsigned32,
	pm10010r100CfgLineGridCurrentPortn
		Unsigned32,
	pm10010r100CfgFPortn
		Unsigned32,
	pm10010r100CfgRxLineFCurrentPortn
		Unsigned32
	}


pm10010r100CfgOtxtlhIndex OBJECT-TYPE
	SYNTAX  INTEGER(0..128)
	MAX-ACCESS  read-only
	STATUS current
	DESCRIPTION
        "
        Index definition for the otxtlh 
        table
        "
	::= { pm10010r100CfgOtxtlhEntry 1 }


pm10010r100CfgLinePwrLaserPortn OBJECT-TYPE
	SYNTAX  Unsigned32 (0..65536)
	MAX-ACCESS read-write
	STATUS current
	DESCRIPTION
        "
        Defaut Line output Power :This 
        register configures the start-up 
        output power of the Line tranceiver 
         (Unit = dBm)
        "
	::= { pm10010r100CfgOtxtlhEntry 6 }


pm10010r100CfgLineFCurrentPortn OBJECT-TYPE
	SYNTAX  Unsigned32 (0..65536)
	MAX-ACCESS read-write
	STATUS current
	DESCRIPTION
        "
        Default Line transceiver Tx Channel 
        :This register configures the start-up 
        laser channel of the Line Tx transceiver
        "
	::= { pm10010r100CfgOtxtlhEntry 7 }


pm10010r100CfgLineGridCurrentPortn OBJECT-TYPE
	SYNTAX  Unsigned32 (0..65536)
	MAX-ACCESS read-write
	STATUS current
	DESCRIPTION
        "
        Default Line transceiver Grid
         :This register configures the
         start-up laser grid of the Line 
        transceiver
        "
	::= { pm10010r100CfgOtxtlhEntry 8 }


pm10010r100CfgFPortn OBJECT-TYPE
	SYNTAX  Unsigned32 (0..65536)
	MAX-ACCESS read-write
	STATUS current
	DESCRIPTION
        "
        Default Line TRX lowest Freq :This 
        register configures the start-up 
        lowest frequency of the Line transceiver
        "
	::= { pm10010r100CfgOtxtlhEntry 9 }


pm10010r100CfgRxLineFCurrentPortn OBJECT-TYPE
	SYNTAX  Unsigned32 (0..65536)
	MAX-ACCESS read-write
	STATUS current
	DESCRIPTION
        "
        Default Line transceiver Rx Channel 
        :This register configures the start-up 
        laser channel of the Line Rx transceiver
        "
	::= { pm10010r100CfgOtxtlhEntry 10 }


--- *****************************************************
---     LEAF for the table Group other
--- *****************************************************

pm10010r100CfgOther OBJECT IDENTIFIER ::= { pm10010r100Config 5 }



--- *****************************************************
---     LEAF for the table 2300
--- *****************************************************

pm10010r100tablemoduleOther OBJECT IDENTIFIER ::= { pm10010r100CfgOther 1 }



pm10010r100Cfgmode OBJECT-TYPE
	  SYNTAX Unsigned32 (0..65536)
	  MAX-ACCESS read-write
	  STATUS current
	  DESCRIPTION
        "
        Default settings on Module :This 
        register selects the configuration 
        mode of the module
        "
	  ::= { pm10010r100tablemoduleOther 2 }



pm10010r100CfgnonLinearEffectsThresholds OBJECT-TYPE
	  SYNTAX Unsigned32 (0..65536)
	  MAX-ACCESS read-write
	  STATUS current
	  DESCRIPTION
        "
        Default settings on Module :This 
        register selects the speed threshold 
        of the fan's
        "
	  ::= { pm10010r100tablemoduleOther 3 }



pm10010r100CfgfanHighSpeedThreshold OBJECT-TYPE
	  SYNTAX Unsigned32 (0..65536)
	  MAX-ACCESS read-write
	  STATUS current
	  DESCRIPTION
        "
        Default settings on Module :This 
        register selects the speed threshold 
        of the fan's
        "
	  ::= { pm10010r100tablemoduleOther 4 }



--- *****************************************************
---     LEAF for the table Group startuptablefive
--- *****************************************************

pm10010r100CfgStartuptablefive OBJECT IDENTIFIER ::= { pm10010r100Config 6 }



--- *****************************************************
---     LEAF for the table 0005
--- *****************************************************

pm10010r100CfgOtxtlhcapabilitiesTable OBJECT-TYPE
	SYNTAX  SEQUENCE OF Pm10010r100CfgOtxtlhcapabilitiesEntry
	MAX-ACCESS not-accessible
	STATUS current
	DESCRIPTION
        "
        List of  Article
        "
	::= { pm10010r100CfgStartuptablefive 1 }


pm10010r100CfgOtxtlhcapabilitiesEntry OBJECT-TYPE
	SYNTAX Pm10010r100CfgOtxtlhcapabilitiesEntry
	MAX-ACCESS not-accessible
	STATUS current
	DESCRIPTION
        "
        Row definition for the startuptablefive 
        table
        "
	INDEX   { pm10010r100CfgOtxtlhcapabilitiesIndex }
	::= { pm10010r100CfgOtxtlhcapabilitiesTable 1 }


Pm10010r100CfgOtxtlhcapabilitiesEntry ::=
	SEQUENCE {
	pm10010r100CfgOtxtlhcapabilitiesIndex
		INTEGER,
	pm10010r100CfgComponentTypePortn
		Unsigned32,
	pm10010r100CfgMiscellaneousPortn
		Unsigned32,
	pm10010r100CfgFirstChannelPortn
		Unsigned32,
	pm10010r100CfgLastChannelPortn
		Unsigned32,
	pm10010r100CfgGridPortn
		Unsigned32
	}


pm10010r100CfgOtxtlhcapabilitiesIndex OBJECT-TYPE
	SYNTAX  INTEGER(0..128)
	MAX-ACCESS  read-only
	STATUS current
	DESCRIPTION
        "
        Index definition for the otxtlhcapabilities 
        table
        "
	::= { pm10010r100CfgOtxtlhcapabilitiesEntry 1 }


pm10010r100CfgComponentTypePortn OBJECT-TYPE
	SYNTAX  Unsigned32 (0..65536)
	MAX-ACCESS read-only
	STATUS current
	DESCRIPTION
        "
        Component parameters :This OID 
        defines the component parameters
        "
	::= { pm10010r100CfgOtxtlhcapabilitiesEntry 3 }


pm10010r100CfgMiscellaneousPortn OBJECT-TYPE
	SYNTAX  Unsigned32 (0..65536)
	MAX-ACCESS read-only
	STATUS current
	DESCRIPTION
        "
        Miscellaneous default settings 
        :This OID defines the miscellaneous 
        parameters
        "
	::= { pm10010r100CfgOtxtlhcapabilitiesEntry 4 }


pm10010r100CfgFirstChannelPortn OBJECT-TYPE
	SYNTAX  Unsigned32 (0..65536)
	MAX-ACCESS read-only
	STATUS current
	DESCRIPTION
        "
        Number of the first channel of 
        the component :This OID defines 
        the first channel number of the 
        PM
        "
	::= { pm10010r100CfgOtxtlhcapabilitiesEntry 5 }


pm10010r100CfgLastChannelPortn OBJECT-TYPE
	SYNTAX  Unsigned32 (0..65536)
	MAX-ACCESS read-only
	STATUS current
	DESCRIPTION
        "
        Number of the last channel of
         the component :This OID defines 
        the last channel number of the
         PM
        "
	::= { pm10010r100CfgOtxtlhcapabilitiesEntry 6 }


pm10010r100CfgGridPortn OBJECT-TYPE
	SYNTAX  Unsigned32 (0..65536)
	MAX-ACCESS read-only
	STATUS current
	DESCRIPTION
        "
        Grid value of the component :This 
        OID defines the grid of the PM
        "
	::= { pm10010r100CfgOtxtlhcapabilitiesEntry 7 }



pm10010r100CfgWriteConfiguration  OBJECT-TYPE
	SYNTAX EkiOnOff
	MAX-ACCESS read-write
	STATUS current
	DESCRIPTION
	"Write configuration to module:This OID 
	 writes the complete configuration to the module"
	::= { pm10010r100Config 257 }






--- *****************************************************
---     TRAP OBJECTS
--- *****************************************************

pm10010r100trapPortNumber OBJECT-TYPE
	SYNTAX INTEGER(1..64)
	MAX-ACCESS read-only
	STATUS current
	DESCRIPTION
	"Last port which generates a trap"
	::= { pm10010r100traps 2 }

pm10010r100trapLineNumber OBJECT-TYPE
	SYNTAX INTEGER(1..64)
	MAX-ACCESS read-only
	STATUS current
	DESCRIPTION
	"Last Line which generates a trap"
	::= { pm10010r100traps 3 }

pm10010r100trapBoardNumber OBJECT-TYPE
	SYNTAX INTEGER(1..64)
	MAX-ACCESS read-only
	STATUS current
	DESCRIPTION
	"Last module which generates a trap"
	::= { pm10010r100traps 4 }







--- *****************************************************
---     LINE TRAPS
--- *****************************************************

pm10010r100LineTrapNotUrgentGoesOn NOTIFICATION-TYPE
	OBJECTS {pm10010r100AlmLineDdmWarningPortn, pm10010r100trapLineNumber, pm10010r100trapBoardNumber}
	STATUS current
	DESCRIPTION "Not urgent Line default is activated"
	::= { pm10010r100traps 30 }

pm10010r100LineTrapNotUrgentGoesOff NOTIFICATION-TYPE
	OBJECTS {pm10010r100AlmLineDdmWarningPortn, pm10010r100trapLineNumber, pm10010r100trapBoardNumber}
	STATUS current
	DESCRIPTION "Not urgent Line default disappeared"
	::= { pm10010r100traps 31 }

pm10010r100LineTrapUrgentGoesOn NOTIFICATION-TYPE
	OBJECTS {pm10010r100AlmLineDdmAlmPortn, pm10010r100trapLineNumber, pm10010r100trapBoardNumber}
	STATUS current
	DESCRIPTION "Urgent Line default is activated"
	::= { pm10010r100traps 32 }

pm10010r100LineTrapUrgentGoesOff NOTIFICATION-TYPE
	OBJECTS {pm10010r100AlmLineDdmAlmPortn, pm10010r100trapLineNumber, pm10010r100trapBoardNumber}
	STATUS current
	DESCRIPTION "Urgent Line default disappeared"
	::= { pm10010r100traps 33 }

pm10010r100LineTrapCritGoesOn NOTIFICATION-TYPE
	OBJECTS {pm10010r100AlmLineFailPortn , pm10010r100AlmLineHwFailPortn , pm10010r100trapLineNumber, pm10010r100trapBoardNumber}
	STATUS current
	DESCRIPTION "Critical Line default is activated"
	::= { pm10010r100traps 34 }

pm10010r100LineTrapCritGoesOff NOTIFICATION-TYPE
	OBJECTS {pm10010r100AlmLineFailPortn , pm10010r100AlmLineHwFailPortn , pm10010r100trapLineNumber, pm10010r100trapBoardNumber}
	STATUS current
	DESCRIPTION "Critical Line default disappeared"
	::= { pm10010r100traps 35 }






--- *****************************************************
---     CLIENT TRAPS
--- *****************************************************

pm10010r100ClientTrapNotUrgentGoesOn NOTIFICATION-TYPE
	OBJECTS {pm10010r100AlmSfpDdmWarningPortn, pm10010r100trapPortNumber, pm10010r100trapBoardNumber}
	STATUS current
	DESCRIPTION "Not urgent client default is activated"
	::= { pm10010r100traps 40 }

pm10010r100ClientTrapNotUrgentGoesOff NOTIFICATION-TYPE
	OBJECTS {pm10010r100AlmSfpDdmWarningPortn, pm10010r100trapPortNumber, pm10010r100trapBoardNumber}
	STATUS current
	DESCRIPTION "Not urgent client default disappeared"
	::= { pm10010r100traps 41 }

pm10010r100ClientTrapUrgentGoesOn NOTIFICATION-TYPE
	OBJECTS {pm10010r100AlmSfpDdmAlmPortn, pm10010r100trapPortNumber, pm10010r100trapBoardNumber}
	STATUS current
	DESCRIPTION "Urgent client default is activated"
	::= { pm10010r100traps 42 }

pm10010r100ClientTrapUrgentGoesOff NOTIFICATION-TYPE
	OBJECTS {pm10010r100AlmSfpDdmAlmPortn, pm10010r100trapPortNumber, pm10010r100trapBoardNumber}
	STATUS current
	DESCRIPTION "Urgent client default disappeared"
	::= { pm10010r100traps 43 }

pm10010r100ClientTrapCritGoesOn NOTIFICATION-TYPE
	OBJECTS {pm10010r100AlmFailAccPortn, pm10010r100AlmHwFailAccPortn, pm10010r100trapPortNumber, pm10010r100trapBoardNumber}
	STATUS current
	DESCRIPTION "Critical client default is activated"
	::= { pm10010r100traps 44 }

pm10010r100ClientTrapCritGoesOff NOTIFICATION-TYPE
	OBJECTS {pm10010r100AlmFailAccPortn, pm10010r100AlmHwFailAccPortn, pm10010r100trapPortNumber, pm10010r100trapBoardNumber}
	STATUS current
	DESCRIPTION "Critical client default disappeared"
	::= { pm10010r100traps 45 }






--- *****************************************************
---     HW TRAPS
--- *****************************************************

pm10010r100PowerTrapUrgentGoesOn NOTIFICATION-TYPE
	OBJECTS {pm10010r100AlmDefFuseB, pm10010r100AlmDefFuseA , pm10010r100trapBoardNumber}
	STATUS current
	DESCRIPTION "Urgent power supply default is activated"
	::= { pm10010r100traps 50 }

pm10010r100PowerTrapUrgentGoesOff NOTIFICATION-TYPE
	OBJECTS {pm10010r100AlmDefFuseB, pm10010r100AlmDefFuseA , pm10010r100trapBoardNumber}
	STATUS current
	DESCRIPTION "Urgent power supply default disappeared"
	::= { pm10010r100traps 51 }






END
